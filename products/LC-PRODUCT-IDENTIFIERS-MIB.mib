--  ========================================================================
--  LANCAST PROPRIETARY PRODUCT IDENTIFIERS MIB
--    This mib file is provided to support the entPhysicalVendorType
--    referred to in the entity MIB, RFC 2037.
--  =========================================================================
--
--  ========================================================================
--  LANCAST PART NUMBER DESCRIPTION:  XXXX-XX-XX
--  
--  PRODUCT      MODULE          SPEED     VERSION  -  PRODUCT  -  PRODUCT
--  SERIES       GROUP                                 SPECIFIC    GROUP
--  ======       =========       =======   =======     ========    ========
--   7- 7000     1- SINGLE       11- 10M     1         XX          75- 7500 MANAGED
--     chassis   2- DUAL         31- 100                               chassis
--               3- REDUNDANT
--
--   ex:
--       7111-18-75
--       7000 chassis, single twister, 10M, version 1, product 18, 7500 managed chassis
--  ==================================================================================
--

   LC-PRODUCT-IDENTIFIERS-MIB

--  NOTES: 
--    1) ADDITIONS TO ANY GROUP SHOULD BE ADDED TO THE BOTTOM OF EACH GROUP
--       TO PREVENT INCONSISTENCIES WITH NMS APPLICATIONS
--
--    2) The mib compiler renames a MIB Module name by adding
--       an extension of -A.  This results in the following error:
--       The module identity for "LC-PRODUCT-IDENTIFIERS-MIB-A" conflicts with 
--       the one for "LC-PRODUCT-IDENTIFIERS-MIB" which prevents the generation
--       of an output file.  
--
--       This is resolved by commenting out the following in the control file:
--       a) the IMPORT statement of MODULE-IDENTITY
--       b) the full MODULE-IDENTITY clause AND replace it with:
--
--       productIdentifiers OBJECT IDENTIFIER ::= { lancastMibModulesA 4 }  
--       
--       You will get the following warning but it can be ignored.
--         "Warning:  A MIB module must start with exactly one invocation of
--         the MODULE-IDENTITY macro immediately following an optional IMPORTS
--         clause."


   DEFINITIONS ::= BEGIN

   IMPORTS
   
   MODULE-IDENTITY, OBJECT-TYPE
        FROM SNMPv2-SMI
   lancastMibModulesA
        FROM LANCAST-MIB; 
 
-- ============================================================
-- MODULE IDENTITY & REVISION HISTORY
-- ============================================================
   productIdentifiers  MODULE-IDENTITY
      LAST-UPDATED    "9907081200Z"    -- 07/08/99 
      ORGANIZATION    "Lancast Inc"
      CONTACT-INFO    "Contact:
                       Customer Service
                       Tel: 1-800-952-6227 ext 136
                       Fax: 1-603-594-2887
                       Web: info@lancast.com"
      DESCRIPTION
              "This is the enterprise MIB definition file for the 
              Product Identifiers of Lancast Managed products.
              
              Copyright 1999 Lancast Inc."              

      REVISION     "9907161200Z"     -- 07/16/99
      DESCRIPTION  "REV 2.0 
                         added fixedPortIdentifier group to moduleIdentifiers
                             and added objects 1-5.
                         added protocolIndependent group to moduleIdentifiers"
              
      REVISION     "9907081200Z"     -- 07/08/99
      DESCRIPTION  "REV 2.0 
                         added rateAdapterIdentifier group to moduleIdentifiers
                         moved mib to lancast.lancastV2MibModules node
                         added oem17500Chassis group to chassisIdentifiers
                         added singleTwister object 28"
              
      REVISION     "9903031200Z"     -- 03/31/99
      DESCRIPTION  "REV 1.0  
                         original Draft"
              
      ::= { lancastMibModulesA 4 }
 
    
--  ======================================================================
--   PRODUCT IDENTIFIERS BRANCH OID:   1.3.6.1.4.1.2745.1.4 
--  ======================================================================
--  stacks                           OBJECT IDENTIFIER ::= { productIdentifiers 1 }

    chassisIdentifiers               OBJECT IDENTIFIER ::= { productIdentifiers 2 }
    lc7500Chassis                    OBJECT IDENTIFIER ::= { chassisIdentifiers 1 }
    oem17500Chassis                  OBJECT IDENTIFIER ::= { chassisIdentifiers 2 }    
    
    powerSupplyIdentifiers           OBJECT IDENTIFIER ::= { productIdentifiers 3 }
    lc7500PowerSupply                OBJECT IDENTIFIER ::= { powerSupplyIdentifiers 1 }
       
    moduleIdentifiers                OBJECT IDENTIFIER ::= { productIdentifiers 4 }
    mgmntModuleIdentifiers           OBJECT IDENTIFIER ::= { moduleIdentifiers 1 }  
    singleTwisterIdentifiers         OBJECT IDENTIFIER ::= { moduleIdentifiers 2 }
    dualTwisterIdentifiers           OBJECT IDENTIFIER ::= { moduleIdentifiers 3 }
    redundantTwisterIdentifiers      OBJECT IDENTIFIER ::= { moduleIdentifiers 4 }
    displayModuleIdentifiers         OBJECT IDENTIFIER ::= { moduleIdentifiers 5 }  
    rateAdapterIdentifiers           OBJECT IDENTIFIER ::= { moduleIdentifiers 6 }
    fixedPortIdentifiers             OBJECT IDENTIFIER ::= { moduleIdentifiers 7 }
    protocolIndependentIdentifiers   OBJECT IDENTIFIER ::= { moduleIdentifiers 8 }

    
--  switchModuleIdentifiers     OBJECT IDENTIFIER ::= { moduleIdentifiers ????? }


--  ======================================================================
--  lc7500Chassis product Identifier Group
--  ======================================================================

   twelveSlot2PS750012 OBJECT-TYPE
      SYNTAX      OBJECT IDENTIFIER
      MAX-ACCESS  not-accessible
      STATUS      current
      DESCRIPTION
      "An indication of the vendor-specific hardware type of the physical entity."
    ::= { lc7500Chassis 1 }

   thirteenSlotTelco2PS750013 OBJECT-TYPE
      SYNTAX      OBJECT IDENTIFIER
      MAX-ACCESS  not-accessible
      STATUS      current
      DESCRIPTION
      "An indication of the vendor-specific hardware type of the physical entity."
    ::= { lc7500Chassis 2 }

   seventeenSlot1PSFixed75001701 OBJECT-TYPE
      SYNTAX      OBJECT IDENTIFIER
      MAX-ACCESS  not-accessible
      STATUS      current
      DESCRIPTION
      "An indication of the vendor-specific hardware type of the physical entity."
    ::= { lc7500Chassis 3 }

   seventeenSlot2PSFixed75001702 OBJECT-TYPE
      SYNTAX      OBJECT IDENTIFIER
      MAX-ACCESS  not-accessible
      STATUS      current
      DESCRIPTION
      "An indication of the vendor-specific hardware type of the physical entity."
    ::= { lc7500Chassis 4 }

   seventeenSlot2PSHotSwapSwitch750017DX OBJECT-TYPE
      SYNTAX      OBJECT IDENTIFIER
      MAX-ACCESS  not-accessible
      STATUS      current
      DESCRIPTION
      "An indication of the vendor-specific hardware type of the physical entity."
    ::= { lc7500Chassis 5 }

--  ======================================================================
--  oem7500Chassis product Identifier Group
--  ======================================================================

   oem1TwelveSlot2PS750012 OBJECT-TYPE
      SYNTAX      OBJECT IDENTIFIER
      MAX-ACCESS  not-accessible
      STATUS      current
      DESCRIPTION
      "An indication of the vendor-specific hardware type of the physical entity."
    ::= { oem17500Chassis 1 }

   oem1SeventeenSlot1PSFixed75001701 OBJECT-TYPE
      SYNTAX      OBJECT IDENTIFIER
      MAX-ACCESS  not-accessible
      STATUS      current
      DESCRIPTION
      "An indication of the vendor-specific hardware type of the physical entity."
    ::= { oem17500Chassis 2 }

   oem1SeventeenSlot2PSFixed75001702 OBJECT-TYPE
      SYNTAX      OBJECT IDENTIFIER
      MAX-ACCESS  not-accessible
      STATUS      current
      DESCRIPTION
      "An indication of the vendor-specific hardware type of the physical entity."
    ::= { oem17500Chassis 3 }

   oem1SeventeenSlot2PSHotSwapSwitch750017DX OBJECT-TYPE
      SYNTAX      OBJECT IDENTIFIER
      MAX-ACCESS  not-accessible
      STATUS      current
      DESCRIPTION
      "An indication of the vendor-specific hardware type of the physical entity."
    ::= { oem17500Chassis 4 }


--  ======================================================================
--  Power Supply product Identifiers
--  ======================================================================    
    acPowerSupply7500AC   OBJECT-TYPE
      SYNTAX      OBJECT IDENTIFIER
      MAX-ACCESS  not-accessible
      STATUS      current
      DESCRIPTION
      "An indication of the vendor-specific hardware type of the physical entity."
    ::= { lc7500PowerSupply 1 }

    dcPowerSupply7500DC   OBJECT-TYPE
      SYNTAX      OBJECT IDENTIFIER
      MAX-ACCESS  not-accessible
      STATUS      current
      DESCRIPTION
      "An indication of the vendor-specific hardware type of the physical entity."
    ::= { lc7500PowerSupply 2 }
       

--  ======================================================================
--  Management Module product Identifier Group
--  ======================================================================
    singleEthernetMgmntModule7501M  OBJECT-TYPE
      SYNTAX      OBJECT IDENTIFIER
      MAX-ACCESS  not-accessible
      STATUS      current
      DESCRIPTION
      "An indication of the vendor-specific hardware type of the physical entity."
    ::= { mgmntModuleIdentifiers 1 }

    dualEthernetMgmntModule7502M  OBJECT-TYPE
      SYNTAX      OBJECT IDENTIFIER
      MAX-ACCESS  not-accessible
      STATUS      current
      DESCRIPTION
      "An indication of the vendor-specific hardware type of the physical entity."
    ::= { mgmntModuleIdentifiers 2 }

    redundantMgmntModule7501RM  OBJECT-TYPE
      SYNTAX      OBJECT IDENTIFIER
      MAX-ACCESS  not-accessible
      STATUS      current
      DESCRIPTION
      "An indication of the vendor-specific hardware type of the physical entity."
    ::= { mgmntModuleIdentifiers 3 }

--  ======================================================================
--  10M & 100M Single Twister Module product Identifier Group
--  ======================================================================
    tpToBnc10MSingleTwisterModule71111275 OBJECT-TYPE
      SYNTAX      OBJECT IDENTIFIER
      MAX-ACCESS  not-accessible
      STATUS      current
      DESCRIPTION
      "An indication of the vendor-specific hardware type of the physical entity."
    ::= { singleTwisterIdentifiers 1 }   

    tpToFlMmSt10MSingleTwisterModule71111575  OBJECT-TYPE
      SYNTAX      OBJECT IDENTIFIER
      MAX-ACCESS  not-accessible
      STATUS      current
      DESCRIPTION
      "An indication of the vendor-specific hardware type of the physical entity."
    ::= { singleTwisterIdentifiers 2 }   

    tpToFlSmSt10MSingleTwisterModule71111675  OBJECT-TYPE
      SYNTAX      OBJECT IDENTIFIER
      MAX-ACCESS  not-accessible
      STATUS      current
      DESCRIPTION
      "An indication of the vendor-specific hardware type of the physical entity."
    ::= { singleTwisterIdentifiers 3 }   
    
    tpToSmaMm10MSingleTwisterModule71111875  OBJECT-TYPE
      SYNTAX      OBJECT IDENTIFIER
      MAX-ACCESS  not-accessible
      STATUS      current
      DESCRIPTION
      "An indication of the vendor-specific hardware type of the physical entity."
    ::= { singleTwisterIdentifiers 4 }   
            
    txToFxMmSc100MSingleTwisterModule71311375 OBJECT-TYPE
      SYNTAX      OBJECT IDENTIFIER
      MAX-ACCESS  not-accessible
      STATUS      current
      DESCRIPTION
      "An indication of the vendor-specific hardware type of the physical entity."
    ::= { singleTwisterIdentifiers 5 }   

    txToFxMmSt100MSingleTwisterModule71311575 OBJECT-TYPE
      SYNTAX      OBJECT IDENTIFIER
      MAX-ACCESS  not-accessible
      STATUS      current
      DESCRIPTION
      "An indication of the vendor-specific hardware type of the physical entity."
    ::= { singleTwisterIdentifiers 6 }   

    txToFxSmSc100MSingleTwisterModule71311475 OBJECT-TYPE
      SYNTAX      OBJECT IDENTIFIER
      MAX-ACCESS  not-accessible
      STATUS      current
      DESCRIPTION
      "An indication of the vendor-specific hardware type of the physical entity."
    ::= { singleTwisterIdentifiers 7 }   

    txToFxSmSc40Km100MSingleTwisterModule71311775 OBJECT-TYPE
      SYNTAX      OBJECT IDENTIFIER
      MAX-ACCESS  not-accessible
      STATUS      current
      DESCRIPTION
      "An indication of the vendor-specific hardware type of the physical entity."
    ::= { singleTwisterIdentifiers 8 }   

    fxMmScToFxSmSc100MSingleTwisterModule71313475 OBJECT-TYPE
      SYNTAX      OBJECT IDENTIFIER
      MAX-ACCESS  not-accessible
      STATUS      current
      DESCRIPTION
      "An indication of the vendor-specific hardware type of the physical entity."
    ::= { singleTwisterIdentifiers 9 }   

    fxMmStToFxSmSc100MSingleTwisterModule71315475 OBJECT-TYPE
      SYNTAX      OBJECT IDENTIFIER
      MAX-ACCESS  not-accessible
      STATUS      current
      DESCRIPTION
      "An indication of the vendor-specific hardware type of the physical entity."
    ::= { singleTwisterIdentifiers 10 }   
    
    txToFxSmSt100MSingleTwisterModule71311675 OBJECT-TYPE
      SYNTAX      OBJECT IDENTIFIER
      MAX-ACCESS  not-accessible
      STATUS      current
      DESCRIPTION
      "An indication of the vendor-specific hardware type of the physical entity."
    ::= { singleTwisterIdentifiers 11 }   
    
    fxMmScToFxSmSt100MSingleTwisterModule71313675 OBJECT-TYPE
      SYNTAX      OBJECT IDENTIFIER
      MAX-ACCESS  not-accessible
      STATUS      current
      DESCRIPTION
      "An indication of the vendor-specific hardware type of the physical entity."
    ::= { singleTwisterIdentifiers 12 }   

    fxMmStToFxSmSt100MSingleTwisterModule71315675 OBJECT-TYPE
      SYNTAX      OBJECT IDENTIFIER
      MAX-ACCESS  not-accessible
      STATUS      current
      DESCRIPTION
      "An indication of the vendor-specific hardware type of the physical entity."
    ::= { singleTwisterIdentifiers 13 }   
    
  tpToTp10MSingleTwisterModule78111175 OBJECT-TYPE
      SYNTAX      OBJECT IDENTIFIER
      MAX-ACCESS  not-accessible
      STATUS      current
      DESCRIPTION
      "An indication of the vendor-specific hardware type of the physical entity."
    ::= { singleTwisterIdentifiers 14 } 

  tpToMmSc10MSingleTwisterModule71111375 OBJECT-TYPE
      SYNTAX      OBJECT IDENTIFIER
      MAX-ACCESS  not-accessible
      STATUS      current
      DESCRIPTION
      "An indication of the vendor-specific hardware type of the physical entity."
    ::= { singleTwisterIdentifiers 15 } 

  txToTx10MSingleTwisterModule78311175 OBJECT-TYPE
      SYNTAX      OBJECT IDENTIFIER
      MAX-ACCESS  not-accessible
      STATUS      current
      DESCRIPTION
      "An indication of the vendor-specific hardware type of the physical entity."
    ::= { singleTwisterIdentifiers 16 } 

  mmScToMmSc100MSingleTwisterModule78313375 OBJECT-TYPE
      SYNTAX      OBJECT IDENTIFIER
      MAX-ACCESS  not-accessible
      STATUS      current
      DESCRIPTION
      "An indication of the vendor-specific hardware type of the physical entity."      
    ::= { singleTwisterIdentifiers 17 } 
    
  mmStToMmSt100MSingleTwisterModule78315575 OBJECT-TYPE
      SYNTAX      OBJECT IDENTIFIER
      MAX-ACCESS  not-accessible
      STATUS      current
      DESCRIPTION
      "An indication of the vendor-specific hardware type of the physical entity."
    ::= { singleTwisterIdentifiers 18 } 
    
  txToMmScSx100MSingleTwisterModule71311A75 OBJECT-TYPE
      SYNTAX      OBJECT IDENTIFIER
      MAX-ACCESS  not-accessible
      STATUS      current
      DESCRIPTION
      "An indication of the vendor-specific hardware type of the physical entity."
    ::= { singleTwisterIdentifiers 19 }                         
    
  txToMmStSx100MSingleTwisterModule71311B75 OBJECT-TYPE
      SYNTAX      OBJECT IDENTIFIER
      MAX-ACCESS  not-accessible
      STATUS      current
      DESCRIPTION
      "An indication of the vendor-specific hardware type of the physical entity."
    ::= { singleTwisterIdentifiers 20 }         

  tpToMmMtrj100MSingleTwisterModule71311E75 OBJECT-TYPE
      SYNTAX      OBJECT IDENTIFIER
      MAX-ACCESS  not-accessible
      STATUS      current
      DESCRIPTION
      "An indication of the vendor-specific hardware type of the physical entity."
    ::= { singleTwisterIdentifiers 21 }
    
  tpToSmMtrj100MSingleTwisterModule71311F75 OBJECT-TYPE
      SYNTAX      OBJECT IDENTIFIER
      MAX-ACCESS  not-accessible
      STATUS      current
      DESCRIPTION
      "An indication of the vendor-specific hardware type of the physical entity."
    ::= { singleTwisterIdentifiers 22 }
    
  tpToMmVf45100MSingleTwisterModule71311G75 OBJECT-TYPE
      SYNTAX      OBJECT IDENTIFIER
      MAX-ACCESS  not-accessible
      STATUS      current
      DESCRIPTION
      "An indication of the vendor-specific hardware type of the physical entity."
    ::= { singleTwisterIdentifiers 23 }

  mmMtrjToScSm100MSingleTwisterModule7131E475 OBJECT-TYPE
      SYNTAX      OBJECT IDENTIFIER
      MAX-ACCESS  not-accessible
      STATUS      current
      DESCRIPTION
      "An indication of the vendor-specific hardware type of the physical entity."
    ::= { singleTwisterIdentifiers 24 }

  mmMtrjToStSm100MSingleTwisterModule7131E675 OBJECT-TYPE
      SYNTAX      OBJECT IDENTIFIER
      MAX-ACCESS  not-accessible
      STATUS      current
      DESCRIPTION
      "An indication of the vendor-specific hardware type of the physical entity."
    ::= { singleTwisterIdentifiers 25 }

  mmMtrjToMmMtrj100MSingleTwisterModule7831EE75 OBJECT-TYPE
      SYNTAX      OBJECT IDENTIFIER
      MAX-ACCESS  not-accessible
      STATUS      current
      DESCRIPTION
      "An indication of the vendor-specific hardware type of the physical entity."
    ::= { singleTwisterIdentifiers 26 }
    
  mmMtrjToSmMtrj100MSingleTwisterModule7131EF75 OBJECT-TYPE
      SYNTAX      OBJECT IDENTIFIER
      MAX-ACCESS  not-accessible
      STATUS      current
      DESCRIPTION
      "An indication of the vendor-specific hardware type of the physical entity."
    ::= { singleTwisterIdentifiers 27 }     

  txToScSm100MSingleTwisterModuleExLongHaul71311J75 OBJECT-TYPE
      SYNTAX      OBJECT IDENTIFIER
      MAX-ACCESS  not-accessible
      STATUS      current
      DESCRIPTION
      "An indication of the vendor-specific hardware type of the physical entity."
    ::= { singleTwisterIdentifiers 28 }

--  ======================================================================
--  10M Dual Telco Twister Module product Identifier Group
--  ======================================================================   
    tpDualTwisterModule72111175 OBJECT-TYPE
      SYNTAX      OBJECT IDENTIFIER
      MAX-ACCESS  not-accessible
      STATUS      current
      DESCRIPTION
      "An indication of the vendor-specific hardware type of the physical entity."
    ::= { dualTwisterIdentifiers 1 }   


    flMmScDualTwisterModule72113375 OBJECT-TYPE
      SYNTAX      OBJECT IDENTIFIER
      MAX-ACCESS  not-accessible
      STATUS      current
      DESCRIPTION
      "An indication of the vendor-specific hardware type of the physical entity."
    ::= { dualTwisterIdentifiers 2 }   

    flMmStDualTwisterModule72115575 OBJECT-TYPE
      SYNTAX      OBJECT IDENTIFIER
      MAX-ACCESS  not-accessible
      STATUS      current
      DESCRIPTION
      "An indication of the vendor-specific hardware type of the physical entity."
    ::= { dualTwisterIdentifiers 3 }   

    flSmStDualTwisterModule72116675 OBJECT-TYPE
      SYNTAX      OBJECT IDENTIFIER
      MAX-ACCESS  not-accessible
      STATUS      current
      DESCRIPTION
      "An indication of the vendor-specific hardware type of the physical entity."
    ::= { dualTwisterIdentifiers 4 }   


--  ======================================================================
--  10M & 100M Redundant Twister Module product Identifier Group
--  ======================================================================       
    txToDualTx100MRedundantTwisterModule77311175  OBJECT-TYPE
      SYNTAX      OBJECT IDENTIFIER
      MAX-ACCESS  not-accessible
      STATUS      current
      DESCRIPTION
      "An indication of the vendor-specific hardware type of the physical entity."
    ::= { redundantTwisterIdentifiers 1 }

    txToDualFxMmSc100MRedundantTwisterModule77311375  OBJECT-TYPE
      SYNTAX      OBJECT IDENTIFIER
      MAX-ACCESS  not-accessible
      STATUS      current
      DESCRIPTION
      "An indication of the vendor-specific hardware type of the physical entity."
    ::= { redundantTwisterIdentifiers 2 }

    txToDualfxSmSc100MRedundantTwisterModule77311475  OBJECT-TYPE
      SYNTAX      OBJECT IDENTIFIER
      MAX-ACCESS  not-accessible
      STATUS      current
      DESCRIPTION
      "An indication of the vendor-specific hardware type of the physical entity."
    ::= { redundantTwisterIdentifiers 3 }

    txToDualFxMmSt100MRedundantTwisterModule77311575  OBJECT-TYPE
      SYNTAX      OBJECT IDENTIFIER
      MAX-ACCESS  not-accessible
      STATUS      current
      DESCRIPTION
      "An indication of the vendor-specific hardware type of the physical entity."
    ::= { redundantTwisterIdentifiers 4 }
      
    txToDualFxSmSt100MRedundantTwisterModule77311675  OBJECT-TYPE
      SYNTAX      OBJECT IDENTIFIER
      MAX-ACCESS  not-accessible
      STATUS      current
      DESCRIPTION
      "An indication of the vendor-specific hardware type of the physical entity."
    ::= { redundantTwisterIdentifiers 5 }
      
    tpToDualTp10MRedundantTwisterModule77111175  OBJECT-TYPE
      SYNTAX      OBJECT IDENTIFIER
      MAX-ACCESS  not-accessible
      STATUS      current
      DESCRIPTION
      "An indication of the vendor-specific hardware type of the physical entity."      
    ::= { redundantTwisterIdentifiers 6 }

--  ======================================================================
--  Display Module product Identifier Group
--  ======================================================================       
    displayModule7500D  OBJECT-TYPE
      SYNTAX      OBJECT IDENTIFIER
      MAX-ACCESS  not-accessible
      STATUS      current
      DESCRIPTION
      "An indication of the vendor-specific hardware type of the physical entity."
    ::= { displayModuleIdentifiers 1 }
        
--  ======================================================================
--  Rate Adpater product Identifier Group
--  ======================================================================       
    tx10M100MToTx10M100MRateAdapterModule76211175  OBJECT-TYPE
      SYNTAX      OBJECT IDENTIFIER
      MAX-ACCESS  not-accessible
      STATUS      current
      DESCRIPTION
      "An indication of the vendor-specific hardware type of physical entity.
          TX 10/100M To TX 10/100M. "
    ::= { rateAdapterIdentifiers 1 }
                       
    tx10M100MToFxMmSc10M100MRateAdapterModule76411375  OBJECT-TYPE
      SYNTAX      OBJECT IDENTIFIER
      MAX-ACCESS  not-accessible
      STATUS      current
      DESCRIPTION
      "An indication of the vendor-specific hardware type of physical entity.
          TX 10/100M To FX MM SC 10/100M. "
    ::= { rateAdapterIdentifiers 2 }

    tx10M100MToFxMmSt10M100MRateAdapterModule76411575  OBJECT-TYPE
      SYNTAX      OBJECT IDENTIFIER
      MAX-ACCESS  not-accessible
      STATUS      current
      DESCRIPTION
      "An indication of the vendor-specific hardware type of physical entity.
          TX 10/100M To FX MM ST 10/100M. "
    ::= { rateAdapterIdentifiers 3 }

    tx10M100MToFxMmMt10M100MRateAdapterModule76411E75  OBJECT-TYPE
      SYNTAX      OBJECT IDENTIFIER
      MAX-ACCESS  not-accessible
      STATUS      current
      DESCRIPTION
      "An indication of the vendor-specific hardware type of physical entity.
          TX 10/100M To FX MM MT 10/100M. "
    ::= { rateAdapterIdentifiers 4 }            

    tx10M100MToFxMmVf10M100MRateAdapterModule76411G75  OBJECT-TYPE
      SYNTAX      OBJECT IDENTIFIER
      MAX-ACCESS  not-accessible
      STATUS      current
      DESCRIPTION
      "An indication of the vendor-specific hardware type of physical entity.      
          TX 10/100M To FX MM VF 10/100M. "
    ::= { rateAdapterIdentifiers 5 }

   tx10M100MToFxScSm100MRateAdapterModule76411475  OBJECT-TYPE
      SYNTAX      OBJECT IDENTIFIER
      MAX-ACCESS  not-accessible
      STATUS      current
      DESCRIPTION
      "An indication of the vendor-specific hardware type of physical entity.
         TX 10/100M To FX SC SM 10/100M. "      
    ::= { rateAdapterIdentifiers 6 }
    
    tx10M100MToFxScSMLongHaul100MRateAdapterModule76411775  OBJECT-TYPE
      SYNTAX      OBJECT IDENTIFIER
      MAX-ACCESS  not-accessible
      STATUS      current
      DESCRIPTION
      "An indication of the vendor-specific hardware type of physical entity.
          TX 10/100M To FX SC SM Long Haul 100M. "
    ::= { rateAdapterIdentifiers 7 }         
 
    flMmSt10MToTx10M100MRateAdapterModule76115175  OBJECT-TYPE
      SYNTAX      OBJECT IDENTIFIER
      MAX-ACCESS  not-accessible
      STATUS      current
      DESCRIPTION
      "An indication of the vendor-specific hardware type of physical entity.
          FL MM ST 10M to TX 10M/100M. "
    ::= { rateAdapterIdentifiers 8 }    

    flMmSt10MToFxMmSc100MRateAdapterModule76415375  OBJECT-TYPE
      SYNTAX      OBJECT IDENTIFIER
      MAX-ACCESS  not-accessible
      STATUS      current
      DESCRIPTION
      "An indication of the vendor-specific hardware type of physical entity.
          FL MM ST 10M TO FX MM SC 100M. "
    ::= { rateAdapterIdentifiers 9 }        

    flMmSt10MToFxMmSt100MRateAdapterModule76415575  OBJECT-TYPE
      SYNTAX      OBJECT IDENTIFIER
      MAX-ACCESS  not-accessible
      STATUS      current
      DESCRIPTION
      "An indication of the vendor-specific hardware type of physical entity.
          FL MM ST 10M TO FX MM ST 100M. "
    ::= { rateAdapterIdentifiers 10 }

--  ======================================================================
--  Fixed Port product Identifier Group
--  ======================================================================       
    twelvePort10MTelcoToFlMmStModule371295M  OBJECT-TYPE
      SYNTAX      OBJECT IDENTIFIER
      MAX-ACCESS  not-accessible
      STATUS      current
      DESCRIPTION
      "An indication of the vendor-specific hardware type of physical entity. "
    ::= { fixedPortIdentifiers 1 }
    
    twelvePort10MTelcoToFlVf45Module37129GM  OBJECT-TYPE
      SYNTAX      OBJECT IDENTIFIER
      MAX-ACCESS  not-accessible
      STATUS      current
      DESCRIPTION
      "An indication of the vendor-specific hardware type of physical entity. "
    ::= { fixedPortIdentifiers 2 }

    sixPort10MTelcoToFlMmStModule370615M  OBJECT-TYPE
      SYNTAX      OBJECT IDENTIFIER
      MAX-ACCESS  not-accessible
      STATUS      current
      DESCRIPTION
      "An indication of the vendor-specific hardware type of physical entity. "
    ::= { fixedPortIdentifiers 3 }

    sixPort10MTelcoToFlSmStModule370616M  OBJECT-TYPE
      SYNTAX      OBJECT IDENTIFIER
      MAX-ACCESS  not-accessible
      STATUS      current
      DESCRIPTION
      "An indication of the vendor-specific hardware type of physical entity. "
    ::= { fixedPortIdentifiers 4 }

    sixPort10MTelcoToFlMmVf45Module37061GM  OBJECT-TYPE
      SYNTAX      OBJECT IDENTIFIER
      MAX-ACCESS  not-accessible
      STATUS      current
      DESCRIPTION
      "An indication of the vendor-specific hardware type of physical entity. "
    ::= { fixedPortIdentifiers 5 }
    
--  ======================================================================
--  Protocol Independent product Identifier Group
--  ======================================================================       
    mmSCSXToScSmLX1000MGigTwisterModule7151AD75 OBJECT-TYPE
      SYNTAX      OBJECT IDENTIFIER
      MAX-ACCESS  not-accessible
      STATUS      current
      DESCRIPTION
      "An indication of the vendor-specific hardware type of the physical entity."
    ::= { protocolIndependentIdentifiers 1 }

    mmSCSXToMtrjSmLX1000MGigTwisterModule7151AF75 OBJECT-TYPE
      SYNTAX      OBJECT IDENTIFIER
      MAX-ACCESS  not-accessible
      STATUS      current
      DESCRIPTION
      "An indication of the vendor-specific hardware type of the physical entity."
    ::= { protocolIndependentIdentifiers 2 }

    mmMtrjSXToScSmLX1000MGigTwisterModule7151ED75 OBJECT-TYPE
      SYNTAX      OBJECT IDENTIFIER
      MAX-ACCESS  not-accessible
      STATUS      current
      DESCRIPTION
      "An indication of the vendor-specific hardware type of the physical entity."
    ::= { protocolIndependentIdentifiers 3 }

    mmMtrjSXToMtrjSmLX1000MGigTwisterModule7151EF75 OBJECT-TYPE
      SYNTAX      OBJECT IDENTIFIER
      MAX-ACCESS  not-accessible
      STATUS      current
      DESCRIPTION
      "An indication of the vendor-specific hardware type of the physical entity."
    ::= { protocolIndependentIdentifiers 4 }

  
END
