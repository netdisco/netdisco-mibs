HM2-PRODUCTS-MIB DEFINITIONS ::= BEGIN

--
-- *************************************************************
-- Hirschmann Products MIB
-- *************************************************************
--

IMPORTS
    MODULE-IDENTITY, OBJECT-IDENTITY
        FROM SNMPv2-SMI -- RFC 2578
    hm2ConfigurationMibs
    	FROM HM2-TC-MIB;

hm2ProductsMib MODULE-IDENTITY
	LAST-UPDATED "201103160000Z" -- March 16, 2011
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Hirschmann products MIB.
         Copyright (C) 2011. All Rights Reserved."
    REVISION     "201103160000Z" -- March 16, 2011
    DESCRIPTION
         "Initial version."
    ::= { hm2ConfigurationMibs 2 }

--
-- *************************************************************
-- hm2Products group
-- *************************************************************
-- 
hm2ProductFamily OBJECT-IDENTITY
    			 STATUS  	current
    			 DESCRIPTION "Hirschmann product family."
    			 ::= { hm2ProductsMib 1 }
    			 
hm2ModuleFamily OBJECT-IDENTITY
    			 STATUS  	current
    			 DESCRIPTION "Hirschmann module family."
    			 ::= { hm2ProductsMib 2 }

                    
-- Product families                    
ees	 OBJECT-IDENTITY
   	 STATUS  	current
   	 DESCRIPTION "Hirschmann Embedded Ethernet Switch family."
   	 ::= { hm2ProductFamily 1 }

rsp	 OBJECT-IDENTITY
   	 STATUS  	current
   	 DESCRIPTION "Hirschmann Rail Switch Power family."
   	 ::= { hm2ProductFamily 2 }

eagle	 OBJECT-IDENTITY
   	 STATUS  	current
   	 DESCRIPTION "Hirschmann Eagle family."
   	 ::= { hm2ProductFamily 3 }

msp	 OBJECT-IDENTITY
   	 STATUS  	current
   	 DESCRIPTION "Hirschmann MICE Switch Power family."
   	 ::= { hm2ProductFamily 4 }

rsps OBJECT-IDENTITY
   	 STATUS  	current
   	 DESCRIPTION "Hirschmann Rail Switch Power Smart family."
   	 ::= { hm2ProductFamily 5 }  
   	 
rspl OBJECT-IDENTITY
   	 STATUS  	current
   	 DESCRIPTION "Hirschmann Rail Switch Power Lite family."
   	 ::= { hm2ProductFamily 6 } 	 
   	
eesx OBJECT-IDENTITY
   	 STATUS  	current
   	 DESCRIPTION "Hirschmann Embedded Ethernet Switch eXtend family."
   	 ::= { hm2ProductFamily 7 } 	
   	  
rspe OBJECT-IDENTITY
   	 STATUS  	current
   	 DESCRIPTION "Hirschmann Rail Switch Power Enhanced family."
   	 ::= { hm2ProductFamily 8 } 

tofino OBJECT-IDENTITY
   	 STATUS  	current
   	 DESCRIPTION "Hirschmann TOFINO family."
   	 ::= { hm2ProductFamily 9 } 
   	    	 
grs OBJECT-IDENTITY
   	 STATUS  	current
   	 DESCRIPTION "Hirschmann GREYHOUND family."
   	 ::= { hm2ProductFamily 10 } 
	 
octopus OBJECT-IDENTITY
   	 STATUS  	current
   	 DESCRIPTION "Hirschmann Octopus family."
   	 ::= { hm2ProductFamily 11 } 
   	 
red OBJECT-IDENTITY
   	 STATUS  	current
   	 DESCRIPTION "Hirschmann RED family."
   	 ::= { hm2ProductFamily 12 } 
   	 
rdd OBJECT-IDENTITY
   	 STATUS  	current
   	 DESCRIPTION "Hirschmann RDD family."
   	 ::= { hm2ProductFamily 13 } 
   	 
-- Module families                  
msm	 OBJECT-IDENTITY
   	 STATUS  	current
   	 DESCRIPTION "Hirschmann Mice Switch Power Module family."
   	 ::= { hm2ModuleFamily 1 }

rspm OBJECT-IDENTITY
   	 STATUS  	current
   	 DESCRIPTION "Hirschmann Rail Switch Power Module family."
   	 ::= { hm2ModuleFamily 2 }

grm OBJECT-IDENTITY
   	 STATUS  	current
   	 DESCRIPTION "Hirschmann GREYHOUND Module family."
   	 ::= { hm2ModuleFamily 3 }

gmm OBJECT-IDENTITY
   	 STATUS  	current
   	 DESCRIPTION "Hirschmann GREYHOUND Switch Module family."
   	 ::= { hm2ModuleFamily 4 }
   	 
   	 
--         
-- Device groups per family (EES)
--         
ees20-0600	 OBJECT-IDENTITY
   	 	 	 STATUS  	current
   	 	 	 DESCRIPTION "Hirschmann Embedded Ethernet Switch EES20-0600 device."
   	 	 	 ::= { ees 1 }

ees25-0600	 OBJECT-IDENTITY
   	 	 	 STATUS  	current
   	 	 	 DESCRIPTION "Hirschmann Embedded Ethernet Switch EES25-0600 device."
   	 	 	 ::= { ees 2 }

--         
-- Device groups per family (RSP)
--         
rsp20-11003z6tt	 OBJECT-IDENTITY
   	 	 	 	 STATUS  	current
   	 	 	 	 DESCRIPTION "Hirschmann Rail Switch Power RSP20-1103Z6TT device."
   	 	 	 	 ::= { rsp 1 }

rsp20-11003z6zt	 OBJECT-IDENTITY
   	 	 	 	 STATUS  	current
   	 	 	 	 DESCRIPTION "Hirschmann Rail Switch Power RSP20-11003Z6ZT device."
   	 	 	 	 ::= { rsp 2 }

rsp25-11003z6tt	 OBJECT-IDENTITY
   	 	 	 	 STATUS  	current
   	 	 	 	 DESCRIPTION "Hirschmann Rail Switch Power RSP25-11003Z6TT device."
   	 	 	 	 ::= { rsp 3 }

rsp25-11003z6zt	 OBJECT-IDENTITY
   	 	 	 	 STATUS  	current
   	 	 	 	 DESCRIPTION "Hirschmann Rail Switch Power RSP25-11003Z6ZT device."
   	 	 	 	 ::= { rsp 4 }

rsp30-08033o6tt	 OBJECT-IDENTITY
   	 	 	 	 STATUS  	current
   	 	 	 	 DESCRIPTION "Hirschmann Rail Switch Power RSP30-08033O6TT device."
   	 	 	 	 ::= { rsp 5 }

rsp30-08033o6zt	 OBJECT-IDENTITY
   	 	 	 	 STATUS  	current
   	 	 	 	 DESCRIPTION "Hirschmann Rail Switch Power RSP30-08033O6ZT device."
   	 	 	 	 ::= { rsp 6 }

rsp35-08033o6tt	 OBJECT-IDENTITY
   	 	 	 	 STATUS  	current
   	 	 	 	 DESCRIPTION "Hirschmann Rail Switch Power RSP35-08033O6TT device."
   	 	 	 	 ::= { rsp 7 }

rsp35-08033o6zt  OBJECT-IDENTITY
   	 	 	 	 STATUS  	current
   	 	 	 	 DESCRIPTION "Hirschmann Rail Switch Power RSP35-08033O6ZT device."
   	 	 	 	 ::= { rsp 8 }
   	 	 	 	 
--                          
-- Device groups per family (Eagle)
--         
eagle20-0400999TT999  OBJECT-IDENTITY
			STATUS  	current
			DESCRIPTION "EAGLE20 with 4 Fast Ethernet ports."
			::= { eagle 1 }
eagle20-0400999TTC99  OBJECT-IDENTITY
			STATUS  	current
			DESCRIPTION "EAGLE20 with 4 Fast Ethernet ports and GPRS/UMTS modem."
			::= { eagle 2 }
eagle20-0400999TTCAA  OBJECT-IDENTITY
			STATUS  	current
			DESCRIPTION "EAGLE20 with 4 Fast Ethernet ports and GPRS/UMTS modem."
			::= { eagle 3 }
eagle20-0400999TTCAB  OBJECT-IDENTITY
			STATUS  	current
			DESCRIPTION "EAGLE20 with 4 Fast Ethernet ports and GPRS/UMTS modem."
			::= { eagle 4 }
eagle20-0400999TTCVA  OBJECT-IDENTITY
			STATUS  	current
			DESCRIPTION "EAGLE20 with 4 Fast Ethernet ports and GPRS/UMTS modem."
			::= { eagle 5 }
eagle20-0400999TTCVB  OBJECT-IDENTITY
			STATUS  	current
			DESCRIPTION "EAGLE20 with 4 Fast Ethernet ports and GPRS/UMTS modem."
			::= { eagle 6 }
eagle20-0400999TTCH2  OBJECT-IDENTITY
			STATUS  	current
			DESCRIPTION "EAGLE20 with 4 Fast Ethernet ports and GPRS/UMTS modem."
			::= { eagle 7 }
eagle20-0400999TTCP2  OBJECT-IDENTITY
			STATUS  	current
			DESCRIPTION "EAGLE20 with 4 Fast Ethernet ports and GPRS/UMTS modem."
			::= { eagle 8 }
eagle20-0400999TT9AA  OBJECT-IDENTITY
			STATUS  	current
			DESCRIPTION "EAGLE20 with 4 Fast Ethernet ports."
			::= { eagle 20 }
eagle20-0400999TT9AB  OBJECT-IDENTITY
			STATUS  	current
			DESCRIPTION "EAGLE20 with 4 Fast Ethernet ports."
			::= { eagle 21 }
eagle20-0400999TT9VA  OBJECT-IDENTITY
			STATUS  	current
			DESCRIPTION "EAGLE20 with 4 Fast Ethernet ports."
			::= { eagle 22 }
eagle20-0400999TT9VB  OBJECT-IDENTITY
			STATUS  	current
			DESCRIPTION "EAGLE20 with 4 Fast Ethernet ports."
			::= { eagle 23 }
eagle20-0400999TT9H2  OBJECT-IDENTITY
			STATUS  	current
			DESCRIPTION "EAGLE20 with 4 Fast Ethernet ports."
			::= { eagle 24 }
eagle20-0400999TT9P2  OBJECT-IDENTITY
			STATUS  	current
			DESCRIPTION "EAGLE20 with 4 Fast Ethernet ports."
			::= { eagle 25 }

eagle30-04022O6TT999  OBJECT-IDENTITY
			STATUS  	current
			DESCRIPTION "EAGLE30 with 2 Gigabit Ethernet ports, 4 Fast Ethernet ports."
			::= { eagle 40 }
eagle30-04022O6TTC99  OBJECT-IDENTITY
			STATUS  	current
			DESCRIPTION "EAGLE30 with 2 Gigabit Ethernet ports, 4 Fast Ethernet ports and GPRS/UMTS modem."
			::= { eagle 41 }
eagle30-04022O6TTCAA  OBJECT-IDENTITY
			STATUS  	current
			DESCRIPTION "EAGLE30 with 2 Gigabit Ethernet ports, 4 Fast Ethernet ports and GPRS/UMTS modem."
			::= { eagle 42 }
eagle30-04022O6TTCAB  OBJECT-IDENTITY
			STATUS  	current
			DESCRIPTION "EAGLE30 with 2 Gigabit Ethernet ports, 4 Fast Ethernet ports and GPRS/UMTS modem."
			::= { eagle 43 }
eagle30-04022O6TTCVA  OBJECT-IDENTITY
			STATUS  	current
			DESCRIPTION "EAGLE30 with 2 Gigabit Ethernet ports, 4 Fast Ethernet ports and GPRS/UMTS modem."
			::= { eagle 44 }
eagle30-04022O6TTCVB  OBJECT-IDENTITY
			STATUS  	current
			DESCRIPTION "EAGLE30 with 2 Gigabit Ethernet ports, 4 Fast Ethernet ports and GPRS/UMTS modem."
			::= { eagle 45 }
eagle30-04022O6TTCH2  OBJECT-IDENTITY
			STATUS  	current
			DESCRIPTION "EAGLE30 with 2 Gigabit Ethernet ports, 4 Fast Ethernet ports and GPRS/UMTS modem."
			::= { eagle 46 }
eagle30-04022O6TTCP2  OBJECT-IDENTITY
			STATUS  	current
			DESCRIPTION "EAGLE30 with 2 Gigabit Ethernet ports, 4 Fast Ethernet ports and GPRS/UMTS modem."
			::= { eagle 47 }
eagle30-04022O6TT9AA  OBJECT-IDENTITY
			STATUS  	current
			DESCRIPTION "EAGLE30 with 2 Gigabit Ethernet ports, 4 Fast Ethernet ports."
			::= { eagle 60 }
eagle30-04022O6TT9AB  OBJECT-IDENTITY
			STATUS  	current
			DESCRIPTION "EAGLE30 with 2 Gigabit Ethernet ports, 4 Fast Ethernet ports."
			::= { eagle 61 }
eagle30-04022O6TT9VA  OBJECT-IDENTITY
			STATUS  	current
			DESCRIPTION "EAGLE30 with 2 Gigabit Ethernet ports, 4 Fast Ethernet ports."
			::= { eagle 62 }
eagle30-04022O6TT9VB  OBJECT-IDENTITY
			STATUS  	current
			DESCRIPTION "EAGLE30 with 2 Gigabit Ethernet ports, 4 Fast Ethernet ports."
			::= { eagle 63 }
eagle30-04022O6TT9H2  OBJECT-IDENTITY
			STATUS  	current
			DESCRIPTION "EAGLE30 with 2 Gigabit Ethernet ports, 4 Fast Ethernet ports."
			::= { eagle 64 }
eagle30-04022O6TT9P2  OBJECT-IDENTITY
			STATUS  	current
			DESCRIPTION "EAGLE30 with 2 Gigabit Ethernet ports, 4 Fast Ethernet ports."
			::= { eagle 65 }

--         
-- Device groups per family (MSP)
--         
msp30-0804	OBJECT-IDENTITY
   	 		STATUS  	current
   	 	 	DESCRIPTION "Hirschmann MICE Switch Power MSP30-0804 device."
   	 	 	::= { msp 1 }
msp32-0804	OBJECT-IDENTITY
   	 		STATUS  	current
   	 	 	DESCRIPTION "Hirschmann MICE Switch Power MSP32-0804 device."
   	 	 	::= { msp 2 }
msp30-1604	OBJECT-IDENTITY
   	 		STATUS  	current
   	 	 	DESCRIPTION "Hirschmann MICE Switch Power MSP30-1604 device."
   	 	 	::= { msp 3 }
msp32-1604	OBJECT-IDENTITY
   	 		STATUS  	current
   	 	 	DESCRIPTION "Hirschmann MICE Switch Power MSP32-1604 device."
   	 	 	::= { msp 4 }
msp30-2404	OBJECT-IDENTITY
   	 		STATUS  	current
   	 	 	DESCRIPTION "Hirschmann MICE Switch Power MSP30-2404 device."
   	 	 	::= { msp 5 }
msp32-2404	OBJECT-IDENTITY
   	 		STATUS  	current
   	 	 	DESCRIPTION "Hirschmann MICE Switch Power MSP32-2404 device."
   	 	 	::= { msp 6 }

--         
-- Device groups per family (RSPS)
--         
rsps20-06002z6yt	 OBJECT-IDENTITY
   	 	 	 STATUS  	current
   	 	 	 DESCRIPTION "Hirschmann Rail Switch Power Smart RSPS20-06002Z6YT device."
   	 	 	 ::= { rsps 1 }

rsps20-06002z6tt	 OBJECT-IDENTITY
   	 	 	 STATUS  	current
   	 	 	 DESCRIPTION "Hirschmann Rail Switch Power Smart RSPS20-06002Z6TT device."
   	 	 	 ::= { rsps 2 }

rsps20-06002t1tt	 OBJECT-IDENTITY
   	 	 	 STATUS  	current
   	 	 	 DESCRIPTION "Hirschmann Rail Switch Power Smart RSPS20-06002T1TT device."
   	 	 	 ::= { rsps 3 }
  
rsps25-06002z6yt	 OBJECT-IDENTITY
   	 	 	 STATUS  	current
   	 	 	 DESCRIPTION "Hirschmann Rail Switch Power Smart RSPS25-06002Z6YT device."
   	 	 	 ::= { rsps 4 }

rsps25-06002z6tt	 OBJECT-IDENTITY
   	 	 	 STATUS  	current
   	 	 	 DESCRIPTION "Hirschmann Rail Switch Power Smart RSPS25-06002Z6TT device."
   	 	 	 ::= { rsps 5 }

rsps25-06002t1tt	 OBJECT-IDENTITY
   	 	 	 STATUS  	current
   	 	 	 DESCRIPTION "Hirschmann Rail Switch Power Smart RSPS25-06002T1TT device."
   	 	 	 ::= { rsps 6 } 

--         
-- Device groups per family (RSPL)
--     

rspl20-08002z6tt  OBJECT-IDENTITY
   	 	 	 	 STATUS  	current
   	 	 	 	 DESCRIPTION "Hirschmann Rail Switch Power Lite RSPL20-08002Z6TT device."
   	 	 	 	 ::= { rspl 1 }
   	 	 	 	 
rspl20-08002z6yt  OBJECT-IDENTITY
   	 	 	 	 STATUS  	current
   	 	 	 	 DESCRIPTION "Hirschmann Rail Switch Power Lite RSPL20-08002Z6YT device."
   	 	 	 	 ::= { rspl 2 }
   	 	 	 	 
rspl30-08022o7yt  OBJECT-IDENTITY
   	 	 	 	 STATUS  	current
   	 	 	 	 DESCRIPTION "Hirschmann Rail Switch Power Lite RSPL30-0802207YT device."
   	 	 	 	 ::= { rspl 3 }
   	 	 	 	 
rspl30-08022o7zt  OBJECT-IDENTITY
   	 	 	 	 STATUS  	current
   	 	 	 	 DESCRIPTION "Hirschmann Rail Switch Power Lite RSPL30-0802207ZT device."
   	 	 	 	 ::= { rspl 4 }

--         
-- Device groups per family (EESX)
--         
eesx20-0800	 OBJECT-IDENTITY
   	 	 	 STATUS  	current
   	 	 	 DESCRIPTION "Hirschmann Embedded Ethernet Switch eXtend EES20-0800 device."
   	 	 	 ::= { eesx 1 }

eesx30-0802	 OBJECT-IDENTITY
   	 	 	 STATUS  	current
   	 	 	 DESCRIPTION "Hirschmann Embedded Ethernet Switch eXtend EES30-0802 device."
   	 	 	 ::= { eesx 2 }
  
--         
-- Device groups per family (RSPE)
--         
rspe30-24044O7T99	 OBJECT-IDENTITY
   	 	 	 	 STATUS  	current
   	 	 	 	 DESCRIPTION "Hirschmann Rail Switch Power rspe30-24044O7T99 device."
   	 	 	 	 ::= { rspe 1 }

rspe32-24044O7T99	 OBJECT-IDENTITY
   	 	 	 	 STATUS  	current
   	 	 	 	 DESCRIPTION "Hirschmann Rail Switch Power rspe30-24044O7T99 device."
   	 	 	 	 ::= { rspe 2 }

rspe35-24044O7T99	 OBJECT-IDENTITY
   	 	 	 	 STATUS  	current
   	 	 	 	 DESCRIPTION "Hirschmann Rail Switch Power rspe30-24044O7T99 device."
   	 	 	 	 ::= { rspe 3 }

rspe37-24044O7T99	 OBJECT-IDENTITY
   	 	 	 	 STATUS  	current
   	 	 	 	 DESCRIPTION "Hirschmann Rail Switch Power rspe30-24044O7T99 device."
   				 ::= { rspe 4 }
   				 
--
-- Device groups per family (GRS)
--         
grs1020-16t9	 OBJECT-IDENTITY
   	 	 	 	 STATUS  	current
   	 	 	 	 DESCRIPTION "Hirschmann GREYHOUND with 16 TX Fast Ethernet ports."
   	 	 	 	 ::= { grs 1 }

grs1020-8t8z	 OBJECT-IDENTITY
   	 	 	 	 STATUS  	current
   	 	 	 	 DESCRIPTION "Hirschmann GREYHOUND with 8 TX and 8 FX Fast Ethernet ports."
   	 	 	 	 ::= { grs 2 }

grs1120-16t9	 OBJECT-IDENTITY
   	 	 	 	 STATUS  	current
   	 	 	 	 DESCRIPTION "Hirschmann GREYHOUND with 16 TX Fast Ethernet ports."
   	 	 	 	 ::= { grs 3 }

grs1120-8t8z	 OBJECT-IDENTITY
   	 	 	 	 STATUS  	current
   	 	 	 	 DESCRIPTION "Hirschmann GREYHOUND with 8 TX and 8 FX Fast Ethernet ports."
   	 	 	 	 ::= { grs 4 }

grs1030-16t9	 OBJECT-IDENTITY
   	 	 	 	 STATUS  	current
   	 	 	 	 DESCRIPTION "Hirschmann GREYHOUND with 4 TX/FX Combo Gigabit Ethernet ports and 16 TX Fast Ethernet ports."
   	 	 	 	 ::= { grs 5 }

grs1030-8t8z	 OBJECT-IDENTITY
   	 	 	 	 STATUS  	current
   	 	 	 	 DESCRIPTION "Hirschmann GREYHOUND with 4 TX/FX Combo Gigabit Ethernet ports, 8 TX and 8 FX Fast Ethernet ports."
   	 	 	 	 ::= { grs 6 }

grs1130-16t9	 OBJECT-IDENTITY
   	 	 	 	 STATUS  	current
   	 	 	 	 DESCRIPTION "Hirschmann GREYHOUND with 4 TX/FX Combo Gigabit Ethernet ports and 16 TX Fast Ethernet ports."
   	 	 	 	 ::= { grs 7 }

grs1130-8t8z	 OBJECT-IDENTITY
   	 	 	 	 STATUS  	current
   	 	 	 	 DESCRIPTION "Hirschmann GREYHOUND with 4 TX/FX Combo Gigabit Ethernet ports, 8 TX and 8 FX Fast Ethernet ports."
   	 	 	 	 ::= { grs 8 }

grs1042-at2z 	 OBJECT-IDENTITY
   	 	 	 	 STATUS  	current
   	 	 	 	 DESCRIPTION "Hirschmann GREYHOUND Switch with 2 FX Gigabit and 10 TX Ethernet ports."
   	 	 	 	 ::= { grs 1000 }
   	 	 	 
grs1142-at2z  	 OBJECT-IDENTITY
   	 	 	 	 STATUS  	current
   	 	 	 	 DESCRIPTION "Hirschmann GREYHOUND Switch with 2 FX Gigabit and 10 TX Ethernet ports."
   	 	 	 	 ::= { grs 1001 }

grs1042-6t6z  	 OBJECT-IDENTITY
   	 	 	 	 STATUS  	current
   	 	 	 	 DESCRIPTION "Hirschmann GREYHOUND Switch with 6 FX Gigabit and 6 TX Ethernet ports."
   	 	 	 	 ::= { grs 1002 }
   	 	 	 
grs1142-6t6z  	 OBJECT-IDENTITY
   	 	 	 	 STATUS  	current
   	 	 	 	 DESCRIPTION "Hirschmann GREYHOUND Switch with 6 FX Gigabit and 6 TX Ethernet ports."
   	 	 	 	 ::= { grs 1003 }

--
-- Device groups per family (OCTOPUS)
--         
os20-000800  OBJECT-IDENTITY
           STATUS   current
           DESCRIPTION "Hirschmann Octopus Switch device."
           ::= { octopus 1 }
os20-001200  OBJECT-IDENTITY
           STATUS   current
           DESCRIPTION "Hirschmann Octopus Switch device."
           ::= { octopus 2 }
os20-002000  OBJECT-IDENTITY
           STATUS   current
           DESCRIPTION "Hirschmann Octopus Switch device."
           ::= { octopus 3 }
os20-002800  OBJECT-IDENTITY
           STATUS   current
           DESCRIPTION "Hirschmann Octopus Switch device."
           ::= { octopus 4 }
os24-111200  OBJECT-IDENTITY
           STATUS   current
           DESCRIPTION "Hirschmann Octopus Switch device."
           ::= { octopus 5 }
os24-101200  OBJECT-IDENTITY
           STATUS   current
           DESCRIPTION "Hirschmann Octopus Switch device."
           ::= { octopus 6 }
os24-081200  OBJECT-IDENTITY
           STATUS   current
           DESCRIPTION "Hirschmann Octopus Switch device."
           ::= { octopus 7 }
os24-152000  OBJECT-IDENTITY
           STATUS   current
           DESCRIPTION "Hirschmann Octopus Switch device."
           ::= { octopus 8 }
os24-152800  OBJECT-IDENTITY
           STATUS   current
           DESCRIPTION "Hirschmann Octopus Switch device."
           ::= { octopus 9 }
os24-142000  OBJECT-IDENTITY
           STATUS   current
           DESCRIPTION "Hirschmann Octopus Switch device."
           ::= { octopus 10 }
os24-142800  OBJECT-IDENTITY
           STATUS   current
           DESCRIPTION "Hirschmann Octopus Switch device."
           ::= { octopus 11 }
os24-122000  OBJECT-IDENTITY
           STATUS   current
           DESCRIPTION "Hirschmann Octopus Switch device."
           ::= { octopus 12 }
os24-122800  OBJECT-IDENTITY
           STATUS   current
           DESCRIPTION "Hirschmann Octopus Switch device."
           ::= { octopus 13 }
os30-000802  OBJECT-IDENTITY
           STATUS   current
           DESCRIPTION "Hirschmann Octopus Switch device."
           ::= { octopus 14 }
os30-001602  OBJECT-IDENTITY
           STATUS   current
           DESCRIPTION "Hirschmann Octopus Switch device."
           ::= { octopus 15 }
os30-002402  OBJECT-IDENTITY
           STATUS   current
           DESCRIPTION "Hirschmann Octopus Switch device."
           ::= { octopus 16 }
os34-100802  OBJECT-IDENTITY
           STATUS   current
           DESCRIPTION "Hirschmann Octopus Switch device."
           ::= { octopus 17 }
os34-141602  OBJECT-IDENTITY
           STATUS   current
           DESCRIPTION "Hirschmann Octopus Switch device."
           ::= { octopus 18 }
os34-142402  OBJECT-IDENTITY
           STATUS   current
           DESCRIPTION "Hirschmann Octopus Switch device."
           ::= { octopus 19 }
os30-000804  OBJECT-IDENTITY
           STATUS   current
           DESCRIPTION "Hirschmann Octopus Switch device."
           ::= { octopus 20 }
os30-001604  OBJECT-IDENTITY
           STATUS   current
           DESCRIPTION "Hirschmann Octopus Switch device."
           ::= { octopus 21 }
os30-002404  OBJECT-IDENTITY
           STATUS   current
           DESCRIPTION "Hirschmann Octopus Switch device."
           ::= { octopus 22 }
os34-110804  OBJECT-IDENTITY
           STATUS   current
           DESCRIPTION "Hirschmann Octopus Switch device."
           ::= { octopus 23 }
os34-100804  OBJECT-IDENTITY
           STATUS   current
           DESCRIPTION "Hirschmann Octopus Switch device."
           ::= { octopus 24 }
os34-080804  OBJECT-IDENTITY
           STATUS   current
           DESCRIPTION "Hirschmann Octopus Switch device."
           ::= { octopus 25 }
os34-151604  OBJECT-IDENTITY
           STATUS   current
           DESCRIPTION "Hirschmann Octopus Switch device."
           ::= { octopus 26 }
os34-152404  OBJECT-IDENTITY
           STATUS   current
           DESCRIPTION "Hirschmann Octopus Switch device."
           ::= { octopus 27 }
os34-141604  OBJECT-IDENTITY
           STATUS   current
           DESCRIPTION "Hirschmann Octopus Switch device."
           ::= { octopus 28 }
os34-142404  OBJECT-IDENTITY
           STATUS   current
           DESCRIPTION "Hirschmann Octopus Switch device."
           ::= { octopus 29 }
os34-121604  OBJECT-IDENTITY
           STATUS   current
           DESCRIPTION "Hirschmann Octopus Switch device."
           ::= { octopus 30 }
os34-122404  OBJECT-IDENTITY
           STATUS   current
           DESCRIPTION "Hirschmann Octopus Switch device."
           ::= { octopus 31 }

--         
-- Device groups per family (RED)
--         

red25-04002t1tt	 OBJECT-IDENTITY
   	 	 	 STATUS  	current
   	 	 	 DESCRIPTION "Hirschmann RED25 with 4 TX Fast Ethernet ports."
   	 	 	 ::= { red 1 }

red25-04002z6tt	 OBJECT-IDENTITY
           STATUS  	current
           DESCRIPTION "Hirschmann RED25 with 2 TX and 2 FX Fast Ethernet ports."
           ::= { red 2 }	 

--         
-- Device groups per family (RDD)
--         

raildatadiodeinput	 OBJECT-IDENTITY
   	 	 	 STATUS  	current
   	 	 	 DESCRIPTION "Hirschmann RDD left."
   	 	 	 ::= { rdd 1 }

raildatadiodeoutput	 OBJECT-IDENTITY
   	 	 	 STATUS  	current
   	 	 	 DESCRIPTION "Hirschmann RDD right."
   	 	 	 ::= { rdd 2 }	
   	 	 	 
--
-- Module groups per family (MSM)
--
msm-4tx		OBJECT-IDENTITY
			STATUS	current
			DESCRIPTION "Hirschmann MICE Switch Power MSM module with 4 TX ports."
			::= { msm 1 }
msm-3tx-1fx	OBJECT-IDENTITY
			STATUS	current
			DESCRIPTION "Hirschmann MICE Switch Power MSM module with 3 TX ports and 1 FX port."
			::= { msm 2 }
msm-2tx-2fx	OBJECT-IDENTITY
			STATUS	current
			DESCRIPTION "Hirschmann MICE Switch Power MSM module with 2 TX ports and 2 FX ports."
			::= { msm 3 }
msm-1tx-3fx	OBJECT-IDENTITY
			STATUS	current
			DESCRIPTION "Hirschmann MICE Switch Power MSM module with 1 TX ports and 3 FX ports."
			::= { msm 4 }
msm-4fx 	OBJECT-IDENTITY
			STATUS	current
			DESCRIPTION "Hirschmann MICE Switch Power MSM module with 4 FX ports."
			::= { msm 5 }
msm-4txfx	OBJECT-IDENTITY
			STATUS	current
			DESCRIPTION "Hirschmann MICE Switch Power MSM module with 4 TX and 4 SFP combo ports."
			::= { msm 6 }
msm-4io		OBJECT-IDENTITY
			STATUS	current
			DESCRIPTION "Hirschmann MICE Switch Power MSM module with 4 IO ports."
			::= { msm 100 }

--
-- Module groups per family (RSPM)
--
rspm20-8tx OBJECT-IDENTITY
			STATUS	current
			DESCRIPTION "Hirschmann Rail Switch Power Enhanced module with 8 TX ports."
			::= { rspm 1 }
			
rspm22-8tx OBJECT-IDENTITY
			STATUS	current
			DESCRIPTION "Hirschmann Rail Switch Power Enhanced module with 8 TX ports and POE."
			::= { rspm 2 }
			
rspm20-4tx-4fx	OBJECT-IDENTITY
			STATUS	current
			DESCRIPTION "Hirschmann Rail Switch Power Enhanced module with 4 TX and 4 FX ports."
			::= { rspm 3 }
			
rspm22-4tx-4fx	OBJECT-IDENTITY
			STATUS	current
			DESCRIPTION "Hirschmann Rail Switch Power Enhanced module with 4 TX and 4 FX ports and POE."
			::= { rspm 4 }
			
rspm20-8fx OBJECT-IDENTITY
			STATUS	current
			DESCRIPTION "Hirschmann Rail Switch Power Enhanced module with 8 FX ports."
			::= { rspm 5 }						

--
-- Module groups per family (GRM)
--
grm20-8tx OBJECT-IDENTITY
			STATUS	current
			DESCRIPTION "Hirschmann GREYHOUND Module with 8 TX ports."
			::= { grm 1 }
			
grm20-8fx OBJECT-IDENTITY
			STATUS	current
			DESCRIPTION "Hirschmann GREYHOUND Module with 8 FX ports."
			::= { grm 2 }
			
grm20-4tx-4fx	OBJECT-IDENTITY
			STATUS	current
			DESCRIPTION "Hirschmann GREYHOUND Module with 4 TX and 4 FX ports."
			::= { grm 3 }
			
--
-- Module groups per family (GMM)
--
gmm20-8fx OBJECT-IDENTITY
			STATUS	current
			DESCRIPTION "Hirschmann GREYHOUND Switch Module with 8 FX ports."
			::= { gmm 1 }
			
gmm30-4tx-4fx OBJECT-IDENTITY
			STATUS	current
			DESCRIPTION "Hirschmann GREYHOUND Switch Module with 4 TX and 4 FX ports."
			::= { gmm 2 }
			
gmm32-4tx-4fx OBJECT-IDENTITY
			STATUS	current
			DESCRIPTION "Hirschmann GREYHOUND Switch Module with 4 TX PoE and 4 FX ports."
			::= { gmm 3 }
			
gmm40-4tx-4fx OBJECT-IDENTITY
			STATUS	current
			DESCRIPTION "Hirschmann GREYHOUND Switch Module with 4 TX and 4 FX ports."
			::= { gmm 4 }
			
gmm40-8fx OBJECT-IDENTITY
			STATUS	current
			DESCRIPTION "Hirschmann GREYHOUND Switch Module with 8 FX ports."
			::= { gmm 5 }
			
gmm40-8tx OBJECT-IDENTITY
			STATUS	current
			DESCRIPTION "Hirschmann GREYHOUND Switch Module with 8 TX ports."
			::= { gmm 6 }
			
gmm42-4tx-4fx OBJECT-IDENTITY
			STATUS	current
			DESCRIPTION "Hirschmann GREYHOUND Switch Module with 4 TX PoE and 4 FX ports."
			::= { gmm 7 }
			
gmm42-8tx OBJECT-IDENTITY
			STATUS	current
			DESCRIPTION "Hirschmann GREYHOUND Switch Module with 8 TX PoE ports."
			::= { gmm 8 }
			
END
