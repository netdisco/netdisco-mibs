--
-- ==================================================================
--  Copyright (c) 1999 - 2008 Siemens Enterpise Communications
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
--  Copyright (c) 1999 - 2008 Siemens Enterpise Communications
-- ==================================================================
--
-- **************************************************************************
-- Revision History
-- 08/01/02    K. Teelucksingh    Initial code
-- 05/08/03    Polly Yu           Updated copyright text  
-- 06/12/08    C. Chatzidimitriou Updated MIB to be fully compatible with SNMPv2
--
-- **************************************************************************

SURPASS-RTP-MIB DEFINITIONS ::= BEGIN

-- **************************************************************************
IMPORTS
    MODULE-IDENTITY, OBJECT-IDENTITY, enterprises                          
         FROM SNMPv2-SMI;  

-- **************************************************************************

--
-- Siemens-specific branch
-- surpass = 1.3.6.1.4.1.4329.2.18
--
   surpassRtp MODULE-IDENTITY
        LAST-UPDATED "200806111500Z"
        ORGANIZATION "Siemens Network Convergence LLC"
        CONTACT-INFO
            " "
        DESCRIPTION
            "This is the top level identity for Surpass RTP
             (Resilient Telco Platform) based products and Managed 
             Objects. "
             
        REVISION     "200806111500Z"
        DESCRIPTION
                     "Updated the MIB to be fully compatible with SNMPv2"

        ::= { surpass 2 }
         
    siemens OBJECT-IDENTITY
        STATUS current
        DESCRIPTION
            "The authoritative identity of the enterprise Siemens AG."
        ::= { enterprises 4329 }

    iandcAdmin OBJECT-IDENTITY
        STATUS current
        DESCRIPTION
            "The Siemens I&C product-specific MIBs."
        ::= { siemens 2 }

    surpass OBJECT-IDENTITY
        STATUS current
        DESCRIPTION
            "The authoritative identity of the I&C Surpass products."
        ::= { iandcAdmin  18 }

    surpassRtpProducts OBJECT-IDENTITY
        STATUS current
        DESCRIPTION
            "The top-level registry for Siemens
             Surpass RTP-based products."
        ::= { surpassRtp 1 }

    surpassRtpAdmin OBJECT-IDENTITY
        STATUS current
        DESCRIPTION
            "The top-level registry  for Siemens 
             Surpass RTP-based MIBs. "
        ::= { surpassRtp 2 }

END
