C-PRODUCT-BASE-L-SPECIFIC DEFINITIONS ::= BEGIN

IMPORTS
	sysGenInfo,
	sysIpConfigLocalHost			FROM C-PRODUCT-BASE-MIB
        DisplayString                           FROM RFC1213-MIB
	IpAddress                               FROM RFC1155-SMI
	OBJECT-TYPE                             FROM RFC-1212;

-- Data Types

--
-- sys Table (Standby code and Switch Code only applied in PBS700)
--
sysGenStandbyCodeRelease OBJECT-TYPE
    SYNTAX  DisplayString
    ACCESS  read-only
    STATUS  mandatory
    DESCRIPTION
            "Firmware revision of the standby code in the managed
             node."
    ::= { sysGenInfo 9 }

sysGenSwitchCodeBank OBJECT-TYPE
    SYNTAX  INTEGER { switch (1) }
    ACCESS  read-write
    STATUS  mandatory
    DESCRIPTION
            "This is the command to switch to the standby code.
             A read request always returns 0.
             Warning: switching code bank will cause reset of
             the managed node."
    ::= { sysGenInfo 10 }


--
-- IP config (Slip Port applied in PBS700)
--
sysIpConfigLocalHostSlipAddress OBJECT-TYPE
    SYNTAX  IpAddress
    ACCESS  read-only
    STATUS  mandatory
    DESCRIPTION
            "Local host's SLIP address."
    ::= { sysIpConfigLocalHost 5 }

sysIpConfigLocalHostSlipSubnetMask OBJECT-TYPE
    SYNTAX  IpAddress
    ACCESS  read-only
    STATUS  mandatory
    DESCRIPTION
            "Local host's SLIP subnet mask."
    ::= { sysIpConfigLocalHost 6 }


END
