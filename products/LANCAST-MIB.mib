LANCAST-MIB   DEFINITIONS ::= BEGIN

   IMPORTS
   MODULE-IDENTITY       FROM SNMPv2-SMI
   enterprises           FROM SNMPv2-SMI;
   

-- ============================================================
-- MODULE IDENTITY & REVISION HISTORY
-- ============================================================
    lancast MODULE-IDENTITY
      LAST-UPDATED    "9903031200Z"
      ORGANIZATION    "Lancast Inc"
      CONTACT-INFO    "Contact:
                       Customer Service
                       Tel: 1-800-526-2278 ext 136
                       Fax: 1-603-594-2887
                       Web: info@lancast.com"
      DESCRIPTION
              "This is the enterprise MIB definition file for 
              all Lancast Managed products.
              
              Copyright 1999 Lancast Inc."
              
      REVISION "9903031200Z"
              
      DESCRIPTION           
              "REV 1.0  original Draft"
        
      ::= { enterprises 2745 }


   lancastMibModulesA  OBJECT IDENTIFIER ::= { lancast 1 }
   lancastTraps        OBJECT IDENTIFIER ::= { lancastMibModulesA 0}
   
      
   END
