ADTRAN-ATLAS-PRODUCTS-MIB       DEFINITIONS     ::=     BEGIN

IMPORTS
    enterprises
        FROM RFC1155-SMI;

-- OBJECT IDENTIFIERS
adtran                  OBJECT IDENTIFIER ::= { enterprises 664 }

adProducts              OBJECT IDENTIFIER ::= { adtran 1 }

adATLAS800              OBJECT IDENTIFIER ::= { adProducts 143 }
adATLASGeneric          OBJECT IDENTIFIER ::= { adProducts 154 }
adATLAS800Plus          OBJECT IDENTIFIER ::= { adProducts 155 }
adATLAS890              OBJECT IDENTIFIER ::= { adProducts 299 }
adATLAS810              OBJECT IDENTIFIER ::= { adProducts 344 }
adATLAS830              OBJECT IDENTIFIER ::= { adProducts 430 }

adATLASGenericOC        OBJECT IDENTIFIER ::= { adProducts 157 }
adATLAST1PRI4OC         OBJECT IDENTIFIER ::= { adProducts 158 }
adATLASV35Nx4OC         OBJECT IDENTIFIER ::= { adProducts 159 }
adATLASUBRI8OC          OBJECT IDENTIFIER ::= { adProducts 160 }
adATLAST3OC             OBJECT IDENTIFIER ::= { adProducts 161 }
adATLASSerialOC         OBJECT IDENTIFIER ::= { adProducts 162 }
adATLASModemOC          OBJECT IDENTIFIER ::= { adProducts 163 }
adATLASE1OC             OBJECT IDENTIFIER ::= { adProducts 164 }
adATLASHDLCOC           OBJECT IDENTIFIER ::= { adProducts 165 }
adATLASCompVoiceOC      OBJECT IDENTIFIER ::= { adProducts 166 }
adATLASt3DI             OBJECT IDENTIFIER ::= { adProducts 255 }
adATLASussi             OBJECT IDENTIFIER ::= { adProducts 256 }
adATLASimux             OBJECT IDENTIFIER ::= { adProducts 257 }
adATLASRdntAcPs         OBJECT IDENTIFIER ::= { adProducts 420 }
adATLASRdntDcPs         OBJECT IDENTIFIER ::= { adProducts 421 }
adATLAS890Cntrlr        OBJECT IDENTIFIER ::= { adProducts 422 }
adATLASOctBRI           OBJECT IDENTIFIER ::= { adProducts 423 }
adATLAS890AcPs          OBJECT IDENTIFIER ::= { adProducts 424 }
adATLAS890DcPs          OBJECT IDENTIFIER ::= { adProducts 425 }
adATLASNxT1hssi         OBJECT IDENTIFIER ::= { adProducts 427 }
adATLASNxT1IMUX         OBJECT IDENTIFIER ::= { adProducts 428 }
adATLASvideo            OBJECT IDENTIFIER ::= { adProducts 429 }

adATLAS550              OBJECT IDENTIFIER ::= { adProducts 219 }        -- ATLAS 550
adATLAS550VCom		OBJECT IDENTIFIER ::= { adProducts 269 }	-- ATLAS 550 4,8,16,24 Channel Voice Compression Resource Modules - 1200312Lx (x = 1,2,3,5)
adATLAS550IMux		OBJECT IDENTIFIER ::= { adProducts 270 }	-- ATLAS 550 Nx56/64 BONDing Resource Module - 1200326L1
adATLAS550T1		OBJECT IDENTIFIER ::= { adProducts 271 }	-- ATLAS 550 T1/PRI Network Interface Module - 1200307L1
adATLAS550DualT1	OBJECT IDENTIFIER ::= { adProducts 272 }	-- ATLAS 550 Dual T1/PRI Option Module - 1200314L1
adATLAS550DualNx	OBJECT IDENTIFIER ::= { adProducts 273 }	-- ATLAS 550 Dual Nx56/64 Option Module - 1200311L1
adATLAS550QuadBRI	OBJECT IDENTIFIER ::= { adProducts 274 }	-- ATLAS 550 Quad Basic Rate ISDN Option Module - 1200315L1
adATLAS550OctFXS	OBJECT IDENTIFIER ::= { adProducts 275 }	-- ATLAS 550 Octal FXS Option Module - 1200309L1
adATLAS550OctFXO	OBJECT IDENTIFIER ::= { adProducts 276 }	-- ATLAS 550 Octal FXO Option Module - 1200310L1
adATLAS550QuadFXS	OBJECT IDENTIFIER ::= { adProducts 277 }	-- ATLAS 550 Quad FXS Option Module - 1200328L1
adATLAS550QuadFXO	OBJECT IDENTIFIER ::= { adProducts 278 }	-- ATLAS 550 Quad FXO Option Module - 1200329L1
adATLAS550RsrcHost	OBJECT IDENTIFIER ::= { adProducts 279 }	-- ATLAS 550 Resource Host Module - 1200324L1
adATLAS550E1		OBJECT IDENTIFIER ::= { adProducts 280 }	-- ATLAS 550 E1/PRA Network Interface Module - 1200308L1
adATLAS550EM		OBJECT IDENTIFIER ::= { adProducts 281 }	-- ATLAS 550 Octal E&M Option Module - 1200313L1
adATLAS550PVRM		OBJECT IDENTIFIER ::= { adProducts 313 }	-- ATLAS 550 32 Channel ADPCM Resource Module - 1200752L1
adATLAS550NxT1hssi	OBJECT IDENTIFIER ::= { adProducts 382 }	-- ATLAS 550 NxT1 HSSI Option Module - 1200346L1
adATLAS550MdmMgmt	OBJECT IDENTIFIER ::= { adProducts 396 }	-- ATLAS 550 Modem Management Network Module (1200341L1)
adATLAS550BriDbu	OBJECT IDENTIFIER ::= { adProducts 397 }	-- ATLAS 550 BRI DBU Network Interface Module (1200327L1)
adATLAS550DualUssi	OBJECT IDENTIFIER ::= { adProducts 398 }	-- ATLAS 550 Dual USSI Module (1200754L1)
adATLAS550QuadT1	OBJECT IDENTIFIER ::= { adProducts 399 }	-- ATLAS 550 Quad T1/PRI Module (1200755L1)
adATLAS550LgcyData	OBJECT IDENTIFIER ::= { adProducts 400 }	-- ATLAS 550 Legacy Data Module (1200342L1)
adATLAS550PbxRsrc       OBJECT IDENTIFIER ::= { adProducts 405 }        -- ATLAS 550 PBX Resource Module (1200756L1)
adATLAS550Pots          OBJECT IDENTIFIER ::= { adProducts 406 }        -- ATLAS 550 Lifeline/POTS Network Module (1200757L1)
adATLAS550OctDss        OBJECT IDENTIFIER ::= { adProducts 407 }        -- ATLAS 550 Octal DSS Option Module (1200758L1)
adATLAS550qStBri        OBJECT IDENTIFIER ::= { adProducts 408 }        -- ATLAS 550 Quad BRI-S/T Option Module (1200764L1)
adATLAS550NxT1Imux      OBJECT IDENTIFIER ::= { adProducts 409 }        -- ATLAS 550 NxT1 IMUX Option Module (1200347L1)
adNthvProdCode          OBJECT IDENTIFIER ::= { adProducts 410 }        -- ATLAS 550 NxT1 HSSI Option Module w/ V.35 Support (1200346L2)

adATLAS890              OBJECT IDENTIFIER ::= { adProducts 299 }

END
