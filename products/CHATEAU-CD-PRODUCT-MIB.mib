CHATEAU-CD-PRODUCT-MIB DEFINITIONS ::= BEGIN

--
--               Chateau Systems, Inc
--                  CD Product MIB
--                      SMIv2
--                 November 14, 2005
--
--
-- The objects defined in this MIB are located under the
-- private.enterprises subtree as shown below:
--
--
--
--   iso(1).org(3).dod(6).internet(1)
--                           |
--                        private(4)
--                           |
--                      enterprises(1)
--                           |
--                   chateausystems(10910)
--                           |
--              _____________|___________
--             |                         |
--    chateauExperimental(1)   chateauRegistrations(2)
--                                       |
--                                       |
--                  _____________________|__________
--                 |                                |
--                 |                                |
--    chateauGlobalRegistrations(1)        chateauProducts(2)
--                 |                                |
--                 |                                |
--                 |                    chateauConsumerProducts(3)
--        chateauProductRegs(1)                     |
--                 |                                |
--    chateauConsumerProductRegs(3)        chateauCDProduct(1)
--                 |                                |
--      (OID Registrations)               chateauCDProductMIB(1)
--
--
--
--
-- OBJECT SUMMARY:
--
-- All objects within this MIB are prefixed with the OBJECT IDENTIFIER "ccdp"
-- where "ccdp" is defined by:
--
--      iso(1).org(3).dod(6).internet(1).private(4).enterprises(1).
--      chateausystems(10910).chateauRegistrations(2).chateauProducts(2).
--      chateauConsumerProducts(3).chateauCDProduct(1)
--
-- OBJECT NAME                                     OBJECT OID
-- ----------------------------------------        ---------------------
--
-- chateauCDProductMIB                              ccdp.1
--    chateauCDProdConfig                           ccdp.1.1
--       cdStaticConfig                             ccdp.1.1.1
--          cdStCfgManufacturer                     ccdp.1.1.1.1
--          cdStCfgModel                            ccdp.1.1.1.2
--          cdStCfgFirmwareRev                      ccdp.1.1.1.10
--       cdDynamicConfig                            ccdp.1.1.2
--          cdDynCfgUserAlias                       ccdp.1.1.2.1
--    chateauCDProdControl                          ccdp.1.2
--       cdCtlPower                                 ccdp.1.2.1
--       cdCtlTrayDoor                              ccdp.1.2.2
--       cdCtlPlaying                               ccdp.1.2.3
--    chateauCDProdStatus                           ccdp.1.3
--       cdChassisStatus                            ccdp.1.3.1
--          cdChStPowerOnHours                      ccdp.1.3.1.1
--          cdChStLaserOnHours                      ccdp.1.3.1.2
--          cdChStCrcErrorCtr                       ccdp.1.3.1.3
--          cdChStTemperature                       ccdp.1.3.1.4
--          cdChStPowerSupply                       ccdp.1.3.1.5
--       cdChangerStatus                            ccdp.1.3.2
--          cdChangerNbrCdSlots                     ccdp.1.3.2.1
--          cdChangerSlotTable                      ccdp.1.3.2.2
--             cdChangerSlotEntry                   ccdp.1.3.2.2.1
--                cdChangerSlotNbr                  ccdp.1.3.2.2.1.1
--                cdChangerSlotStatus               ccdp.1.3.2.2.1.2
--                cdChangerSlotCDTrackPlaying       ccdp.1.3.2.2.1.3
--                cdChangerCDNbrTracks              ccdp.1.3.2.2.1.4
--          cdChangerCDTrackTable                   ccdp.1.3.2.3
--             cdChangerCDTrackEntry                ccdp.1.3.2.3.1
--                cdChangerCDTrackNbr               ccdp.1.3.2.3.1.1
--                cdChangerCDTrackPlaying           ccdp.1.3.2.3.1.2
--                cdChangerCDTrackLengthSecs        ccdp.1.3.2.3.1.3
--                cdChangerCDTrackLengthStr         ccdp.1.3.2.3.1.4
--                cdChangerCDTrackTitle             ccdp.1.3.2.3.1.5
--                cdChangerCDTrackArtist            ccdp.1.3.2.3.1.6
--    chateauCDProdEvents                           ccdp.1.10
--       cdEventControl                             ccdp.1.10.1
--          cdEvCtlAgtPollFreq                      ccdp.1.10.1.1
--          cdChassisTempAlarmThresh                ccdp.1.10.1.2
--          cdChassisTempEvTrapEn                   ccdp.1.10.1.10
--          cdPowerSupplyEvTrapEn                   ccdp.1.10.1.20
--       cdEventDescriptors                         ccdp.1.10.2
--          cdEvSeverity                            ccdp.1.10.2.1
--          cdEvDescription                         ccdp.1.10.2.2
--       cdEventList                                ccdp.1.10.0
--          cdChassisTempAlarmEv                    ccdp.1.10.0.10
--          cdChassisTempOkayEv                     ccdp.1.10.0.11
--          cdPowerSupplyEv                         ccdp.1.10.0.20
--
--    chateauCDProdConformance                      ccdp.1.20
--       cdConformanceGroups                        ccdp.1.20.1
--          cdProdConfigGroup                       ccdp.1.20.1.1
--          cdProdControlGroup                      ccdp.1.20.1.2
--          cdProdStatusGroup                       ccdp.1.20.1.3
--          cdProdEventGroup                        ccdp.1.20.1.4
--          cdProdNotificationsGroup                ccdp.1.20.1.5
--       cdCompliance                               ccdp.1.20.2
--
--


      IMPORTS
          MODULE-IDENTITY, OBJECT-IDENTITY, NOTIFICATION-TYPE,
          OBJECT-TYPE, Unsigned32, Integer32, Counter32
              FROM SNMPv2-SMI

          OBJECT-GROUP, NOTIFICATION-GROUP, MODULE-COMPLIANCE
              FROM SNMPv2-CONF

          DisplayString, TruthValue
              FROM SNMPv2-TC

          chateauCDProduct, ChateauTrapControl, ChateauEventSeverity
              FROM CHATEAUSYSTEMS-REGISTRATIONS-MIB;



     chateauCDProductMIB  MODULE-IDENTITY
      LAST-UPDATED "200511090000Z"
      ORGANIZATION "Chateau Systems, Inc."
      CONTACT-INFO
      "Larry R. Walsh
       Chateau Systems, Inc
       PO Box 898
       Stanwood, WA 98292
       USA

       360 387-2615

       larrywalsh@chateausystems.com

       www.chateausystems.com"

      DESCRIPTION
       "This MIB defines Nodes and Data Objects to support
        Chateau Systems CD Players.

        This MIB has been distributed as part of the handout
        materials from the SNMP Technology Seminar presented
        by Chateau Systems.

        Any person or organization making use of this example MIB is
        responsible for ensuring its complete suitability for their
        own purposes. This includes the text of the legal disclaimers
        below, as well as all other aspects.

        Chateau Systems reserves the right to make changes in
        specifications and other information contained
        in this document without prior notice.
        The reader should contact Chateau Systems to determine
        whether or not such changes have been made.

        In no event shall Chateau Systems be liable for any
        incidental, indirect, special, or consequential damages
        whatsoever (including but not limited to lost profits)
        arising out of or related to this document or the
        information contained in it, even if Chateau Systems has
        been advised of, known, or should have known, the
        possibility of such damages.

        Chateau Systems grants vendors, end-users, and other interested
        parties a non-exclusive license to use this specification
        in connection with the management of Chateau Systems products.

        Copyright November 2005 Chateau Systems, Inc."

        REVISION      "200511090000Z"
        DESCRIPTION
        "First Release."

        ::= { chateauCDProduct 1 }


--
--    chateauCDProdConfig                           ccdp.1.1
--

chateauCDProdConfig OBJECT-IDENTITY
    STATUS current
    DESCRIPTION
       "CD Configuration Organizational node"
    ::= { chateauCDProductMIB 1 }


--
--       cdStaticConfig                             ccdp.1.1.1
--

cdStaticConfig OBJECT-IDENTITY
    STATUS current
    DESCRIPTION
       "CD Static Configuration Node"
    ::= { chateauCDProdConfig 1 }


--          cdStCfgManufacturer                     ccdp.1.1.1.1

cdStCfgManufacturer   OBJECT-TYPE
    SYNTAX      OBJECT IDENTIFIER
    MAX-ACCESS  read-only
    STATUS      current
    DESCRIPTION
        "The IANA issued Enterprise OID for this Product's Manufacturer."
    ::= { cdStaticConfig 1 }


--          cdStCfgModel                            ccdp.1.1.1.2

cdStCfgModel   OBJECT-TYPE
    SYNTAX      DisplayString (SIZE(4..16))
    MAX-ACCESS  read-only
    STATUS      current
    DESCRIPTION
        "Manufacturer's Model Designation"
    ::= { cdStaticConfig 2 }


--          cdStCfgFirmwareRev                      ccdp.1.1.1.10

cdStCfgFirmwareRev   OBJECT-TYPE
    SYNTAX      DisplayString
    MAX-ACCESS  read-only
    STATUS      current
    DESCRIPTION
        "The Firmware Revision for currently loaded firmware"
    ::= { cdStaticConfig 10 }


--
--       cdDynamicConfig                            ccdp.1.1.2
--

cdDynamicConfig OBJECT-IDENTITY
    STATUS current
    DESCRIPTION
       "CD Dynamic Configuration Node"
    ::= { chateauCDProdConfig 2 }


--          cdDynCfgUserAlias                       ccdp.1.1.2.1

 cdDynCfgUserAlias   OBJECT-TYPE
    SYNTAX      DisplayString (SIZE(0..16))
    MAX-ACCESS  read-write
    STATUS      current
    DESCRIPTION
        "Any user assigned name for this CD player"
    ::= { cdDynamicConfig 1 }


--
--    chateauCDProdControl                          ccdp.1.2
--

chateauCDProdControl OBJECT-IDENTITY
    STATUS current
    DESCRIPTION
       "CD Control Organizational node"
    ::= { chateauCDProductMIB 2 }


--       cdCtlPower                                 ccdp.1.2.1

cdCtlPower   OBJECT-TYPE
    SYNTAX      INTEGER
                { on(1),
                  off(2)
                }
    MAX-ACCESS  read-write
    STATUS      current
    DESCRIPTION
        "Indicated CD Player Power status.
         Can be modified by the user."
    ::= { chateauCDProdControl 1 }


--       cdCtlTrayDoor                              ccdp.1.2.2

cdCtlTrayDoor   OBJECT-TYPE
    SYNTAX      INTEGER
                { closed(1),
                  open(2)
                }
    MAX-ACCESS  read-write
    STATUS      current
    DESCRIPTION
        "CD Player tray door status.
         Can be modified by the user.
         If cdCtlPower = off,
         then the user cannot modify this value."
    ::= { chateauCDProdControl 2 }


--       cdCtlPlaying                               ccdp.1.2.3

cdCtlPlaying   OBJECT-TYPE
    SYNTAX      TruthValue
    MAX-ACCESS  read-write
    STATUS      current
    DESCRIPTION
        "CD Player 'play' status.
         Can be modified by the user.
         If cdCtlPower = off
         OR cdCtlTrayDoor = open,
         then the user cannot modify this value."
    ::= { chateauCDProdControl 3 }


--
--    chateauCDProdStatus                           ccdp.1.3
--

chateauCDProdStatus  OBJECT-IDENTITY
    STATUS current
    DESCRIPTION
       "CD Player Status organizational node"
    ::= { chateauCDProductMIB 3 }


--
--       cdChassisStatus                            ccdp.1.3.1
--

cdChassisStatus  OBJECT-IDENTITY
    STATUS current
    DESCRIPTION
       "CD Player Chassis status node"
    ::= { chateauCDProdStatus 1 }


--          cdChStPowerOnHours                      ccdp.1.3.1.1

cdChStPowerOnHours   OBJECT-TYPE
    SYNTAX      Unsigned32
    MAX-ACCESS  read-only
    STATUS      current
    DESCRIPTION
        "The total number of hours that this CD Player
         has been powered on in its lifetime."
    ::= { cdChassisStatus 1 }


--          cdChStLaserOnHours                      ccdp.1.3.1.2

cdChStLaserOnHours   OBJECT-TYPE
    SYNTAX      Unsigned32
    MAX-ACCESS  read-only
    STATUS      current
    DESCRIPTION
        "The total number of hours that this CD Player's
         Laser has been powered on in its lifetime.
         Trending this value may predict Laser failures."
    ::= { cdChassisStatus 2 }


--          cdChStCrcErrorCtr                       ccdp.1.3.1.3

cdChStCrcErrorCtr   OBJECT-TYPE
    SYNTAX      Counter32
    MAX-ACCESS  read-only
    STATUS      current
    DESCRIPTION
        "Counter for CRC errors encountered reading CDs.
         This Counter is initialized whenever the CD Player
         is powered on."
    ::= { cdChassisStatus 3 }


--          cdChStTemperature                       ccdp.1.3.1.4

cdChStTemperature   OBJECT-TYPE
    SYNTAX      Integer32
    UNITS       "Celcius"
    MAX-ACCESS  read-only
    STATUS      current
    DESCRIPTION
        "CD Player internal chassis temperature."
    ::= { cdChassisStatus 4 }


--          cdChStPowerSupply                       ccdp.1.3.1.5

cdChStPowerSupply   OBJECT-TYPE
    SYNTAX      INTEGER
                { okay(1),
                  voltageError(2)
                }
    MAX-ACCESS  read-only
    STATUS      current
    DESCRIPTION
        "CD Player Power Supply status."
    ::= { cdChassisStatus 5 }



--
--       cdChangerStatus                            ccdp.1.3.2
--

cdChangerStatus  OBJECT-IDENTITY
    STATUS current
    DESCRIPTION
       "CD Player Changer status node"
    ::= { chateauCDProdStatus 2 }


--          cdChangerNbrCdSlots                     ccdp.1.3.2.1

cdChangerNbrCdSlots   OBJECT-TYPE
    SYNTAX      Unsigned32 (1..8)
    MAX-ACCESS  read-only
    STATUS      current
    DESCRIPTION
        "The maximum number of CDs that can be loaded into
         this CD player.
         The size of (number of indexed entries in) the cdChangerSlotTable."
    ::= { cdChangerStatus 1 }



--
--          cdChangerSlotTable                      ccdp.1.3.2.2
--             cdChangerSlotEntry                   ccdp.1.3.2.2.1
--

cdChangerSlotTable OBJECT-TYPE
    SYNTAX      SEQUENCE OF CdChangerSlotEntry
    MAX-ACCESS  not-accessible
    STATUS      current
    DESCRIPTION
        "CD Changer Slot Table."
    ::= { cdChangerStatus 2 }


cdChangerSlotEntry  OBJECT-TYPE
    SYNTAX      CdChangerSlotEntry
    MAX-ACCESS  not-accessible
    STATUS      current
    DESCRIPTION
        "An entry in cdChangerSlotTable."
    INDEX   { cdChangerSlotNbr }
    ::= { cdChangerSlotTable 1 }


CdChangerSlotEntry  ::=
    SEQUENCE {
              cdChangerSlotNbr             Unsigned32,
              cdChangerSlotStatus          INTEGER,
              cdChangerSlotCDTrackPlaying  Unsigned32,
              cdChangerCDNbrTracks         Unsigned32
             }


--                cdChangerSlotNbr                  ccdp.1.3.2.2.1.1

cdChangerSlotNbr   OBJECT-TYPE
    SYNTAX      Unsigned32 (1..8)
    MAX-ACCESS  not-accessible
    STATUS      current
    DESCRIPTION
        "Slot number and table index."
    ::= { cdChangerSlotEntry 1 }


--                cdChangerSlotStatus               ccdp.1.3.2.2.1.2

cdChangerSlotStatus   OBJECT-TYPE
    SYNTAX      INTEGER
                { containsCD(1),
                  empty(2)
                }
    MAX-ACCESS  read-only
    STATUS      current
    DESCRIPTION
        "CD Changer Slot Status."
    ::= { cdChangerSlotEntry 2 }


--                cdChangerSlotCDTrackPlaying       ccdp.1.3.2.2.1.3

cdChangerSlotCDTrackPlaying   OBJECT-TYPE
    SYNTAX      Unsigned32
    MAX-ACCESS  read-only
    STATUS      current
    DESCRIPTION
        "If a CD is currently playing, this is the Track Number.
         This is also the value of cdChangerCDTrackNbr for the CD that is playing.
         = 0 if no CD is currently playing."
    ::= { cdChangerSlotEntry 3 }


--                cdChangerCDNbrTracks              ccdp.1.3.2.2.1.4

cdChangerCDNbrTracks   OBJECT-TYPE
    SYNTAX      Unsigned32
    MAX-ACCESS  read-only
    STATUS      current
    DESCRIPTION
        "The number of Tracks on this CD.
         This is also the size the sub-table cdChangerCDTrackTable
         for this CD - ie, the maximum value of cdChangerCDTrackNbr."
    ::= { cdChangerSlotEntry 4 }



--
--          cdChangerCDTrackTable                   ccdp.1.3.2.3
--             cdChangerCDTrackEntry                ccdp.1.3.2.3.1
--

cdChangerCDTrackTable OBJECT-TYPE
    SYNTAX      SEQUENCE OF CdChangerCDTrackEntry
    MAX-ACCESS  not-accessible
    STATUS      current
    DESCRIPTION
        "Changer Track Table for a single CD."
    ::= { cdChangerStatus 3 }


cdChangerCDTrackEntry  OBJECT-TYPE
    SYNTAX     CdChangerCDTrackEntry
    MAX-ACCESS  not-accessible
    STATUS      current
    DESCRIPTION
        "An entry in cdChangerCDTrackTable."
    INDEX   { cdChangerSlotNbr, cdChangerCDTrackNbr }
    ::= { cdChangerCDTrackTable 1 }


CdChangerCDTrackEntry  ::=
    SEQUENCE {
              cdChangerCDTrackNbr         Unsigned32,
              cdChangerCDTrackPlaying     TruthValue,
              cdChangerCDTrackLengthSecs  Unsigned32,
              cdChangerCDTrackLengthStr   DisplayString,
              cdChangerCDTrackTitle       DisplayString,
              cdChangerCDTrackArtist      DisplayString
             }


--                cdChangerCDTrackNbr               ccdp.1.3.2.3.1.1

cdChangerCDTrackNbr   OBJECT-TYPE
    SYNTAX      Unsigned32
    MAX-ACCESS  not-accessible
    STATUS      current
    DESCRIPTION
        "CD Track Number and Table Index"
    ::= { cdChangerCDTrackEntry 1 }


--                cdChangerCDTrackPlaying           ccdp.1.3.2.3.1.2

cdChangerCDTrackPlaying   OBJECT-TYPE
    SYNTAX      TruthValue
    MAX-ACCESS  read-only
    STATUS      current
    DESCRIPTION
        "= true if this Track is currently playing.
         Only one Track can be true at a time."
    ::= { cdChangerCDTrackEntry 2 }



--                cdChangerCDTrackLengthSecs        ccdp.1.3.2.3.1.3

cdChangerCDTrackLengthSecs   OBJECT-TYPE
    SYNTAX      Unsigned32
    MAX-ACCESS  read-only
    STATUS      current
    DESCRIPTION
        "Track time in seconds."
    ::= { cdChangerCDTrackEntry 3 }


--                cdChangerCDTrackLengthStr         ccdp.1.3.2.3.1.4

cdChangerCDTrackLengthStr   OBJECT-TYPE
    SYNTAX      DisplayString
    MAX-ACCESS  read-only
    STATUS      current
    DESCRIPTION
        "Track time in minutes and seconds displayed as text."
    ::= { cdChangerCDTrackEntry 4 }


--                cdChangerCDTrackTitle             ccdp.1.3.2.3.1.5

cdChangerCDTrackTitle   OBJECT-TYPE
    SYNTAX      DisplayString (SIZE(0..64))
    MAX-ACCESS  read-only
    STATUS      current
    DESCRIPTION
        "CD Track Title.
         NULL string if information is not available."
    ::= { cdChangerCDTrackEntry 5 }


--                cdChangerCDTrackArtist            ccdp.1.3.2.3.1.6

cdChangerCDTrackArtist   OBJECT-TYPE
    SYNTAX      DisplayString (SIZE(0..64))
    MAX-ACCESS  read-only
    STATUS      current
    DESCRIPTION
        "CD Track Artist.
         NULL string if information is not available."
    ::= { cdChangerCDTrackEntry 6 }




--
--    chateauCDProdEvents                           ccdp.1.10
--

chateauCDProdEvents  OBJECT-IDENTITY
    STATUS current
    DESCRIPTION
       "CD Player Event Data and Trap Definitions
        are organized under this node."
    ::= { chateauCDProductMIB 10 }


--
--       cdEventControl                             ccdp.1.10.1
--

cdEventControl  OBJECT-IDENTITY
    STATUS current
    DESCRIPTION
       "Node for data affecting Agent Trap Management Semantics"
    ::= { chateauCDProdEvents 1 }


--          cdEvCtlAgtPollFreq                      ccdp.1.10.1.1

cdEvCtlAgtPollFreq   OBJECT-TYPE
    SYNTAX      Unsigned32
    UNITS       "seconds"
    MAX-ACCESS  read-write
    STATUS      current
    DESCRIPTION
        "How often the Agent polls the CD Player for trappable conditions.
         Set = 0 to disable all traps.
         Persistent through system resets."
    DEFVAL {30}
    ::= { cdEventControl 1 }


--          cdChassisTempAlarmThresh                ccdp.1.10.1.2

cdChassisTempAlarmThresh   OBJECT-TYPE
    SYNTAX      Integer32
    UNITS       "Celcius"
    MAX-ACCESS  read-write
    STATUS      current
    DESCRIPTION
        "User settable to define the Chassis Temperature
         past which a Chassis Temperature Alarm will occur.
         Agent semantics will apply hysterisis logic so
         that traps to not repeat unecessarily when the
         chassis temperature is very close to this threshold.
         Persistent through system resets."
    DEFVAL { 40 }
    ::= { cdEventControl 2 }


--          cdChassisTempEvTrapEn                   ccdp.1.10.1.10

cdChassisTempEvTrapEn   OBJECT-TYPE
    SYNTAX      ChateauTrapControl
    MAX-ACCESS  read-write
    STATUS      current
    DESCRIPTION
        "User settable to disable/enable Chassis Temperature alarms
         and okay events.
         Persistent through system resets."
    DEFVAL { trapEnable }
    ::= { cdEventControl 10 }

--          cdPowerSupplyEvTrapEn                   ccdp.1.10.1.20

cdPowerSupplyEvTrapEn   OBJECT-TYPE
    SYNTAX      ChateauTrapControl
    MAX-ACCESS  read-write
    STATUS      current
    DESCRIPTION
        "User settable to disable/enable Power Supply alarms
         and okay events.
         Persistent through system resets."
    DEFVAL { trapEnable }
    ::= { cdEventControl 20 }


--
--       cdEventDescriptors                         ccdp.1.10.2
--

cdEventDescriptors  OBJECT-IDENTITY
    STATUS current
    DESCRIPTION
       "Event Descriptor Node"
    ::= { chateauCDProdEvents 2 }



--          cdEvSeverity                            ccdp.1.10.2.1

cdEvSeverity   OBJECT-TYPE
    SYNTAX      ChateauEventSeverity
    MAX-ACCESS  accessible-for-notify
    STATUS      current
    DESCRIPTION
        "This value is sent with each trap as an
         indication of the intended severity of the event."
    ::= { cdEventDescriptors 1 }


--          cdEvDescription                         ccdp.1.10.2.2

cdEvDescription   OBJECT-TYPE
    SYNTAX      DisplayString (SIZE(0..64))
    MAX-ACCESS  accessible-for-notify
    STATUS      current
    DESCRIPTION
        "Text which may provide the user with further diagnostic information."
    ::= { cdEventDescriptors 2 }


--
--       cdEventList                                ccdp.1.10.0
--

cdEventList  OBJECT-IDENTITY
    STATUS current
    DESCRIPTION
       "Notification Objects are organized under this node."
    ::= { chateauCDProdEvents 0 }


--          cdChassisTempAlarmEv                    ccdp.1.10.0.10

cdChassisTempAlarmEv NOTIFICATION-TYPE
    OBJECTS
    {
        cdDynCfgUserAlias,
        cdStCfgModel,
        cdChStTemperature,
        cdEvSeverity,
        cdEvDescription
    }
    STATUS  current
    DESCRIPTION
        "Sent when cdChStTemperature > cdChassisTempAlarmThresh.
         Will not be resent until cdChStTemperature drops below
         cdChasisTempAlarmThresh less 10%.
         This trap can be disabled by setting cdChassisTempEvTrapEn = trapDisable."
    ::= { cdEventList 10 }


--          cdChassisTempOkayEv                     ccdp.1.10.0.11

cdChassisTempOkayEv NOTIFICATION-TYPE
    OBJECTS
    {
        cdDynCfgUserAlias,
        cdStCfgModel,
        cdChStTemperature,
        cdEvSeverity,
        cdEvDescription
    }
    STATUS  current
    DESCRIPTION
        "Sent when cdChStTemperature drops below cdChassisTempAlarmThresh.
         This trap can be disabled by setting cdChassisTempEvTrapEn = trapDisable."
    ::= { cdEventList 11 }


--          cdPowerSupplyEv                         ccdp.1.10.0.20

cdPowerSupplyEv NOTIFICATION-TYPE
    OBJECTS
    {
        cdDynCfgUserAlias,
        cdStCfgModel,
        cdChStPowerSupply,
        cdEvSeverity,
        cdEvDescription
    }
    STATUS  current
    DESCRIPTION
        "Sent when cdChStPowerSupply changes from okay to voltageError,
         or from voltageError to okay.
         This trap can be disabled by setting cdPowerSupplyEvTrapEn = trapDisable."
    ::= { cdEventList 20 }




-- ______________________________________________________________
--
-- Chateau CD Product Conformance Objects
--
-- ______________________________________________________________


--
--    chateauCDProdConformance                      ccdp.1.20
--

chateauCDProdConformance OBJECT-IDENTITY
    STATUS current
    DESCRIPTION
      "Organizational node for Conformance Objects."
    ::= { chateauCDProductMIB 20 }


--
--       cdConformanceGroups                        ccdp.1.20.1
--

cdConformanceGroups  OBJECT-IDENTITY
    STATUS current
    DESCRIPTION
      "Organizational node for Conformance Groups."
    ::= { chateauCDProdConformance 1 }


--          cdProdConfigGroup                       ccdp.1.20.1.1

cdProdConfigGroup OBJECT-GROUP
    OBJECTS
    {
--    chateauCDProdConfig
--       cdStaticConfig
            cdStCfgManufacturer,
            cdStCfgModel,
            cdStCfgFirmwareRev,
--       cdDynamicConfig
            cdDynCfgUserAlias
    }
    STATUS current
    DESCRIPTION
    "cdProdConfigGroup"
    ::= { cdConformanceGroups  1 }


--          cdProdControlGroup                      ccdp.1.20.1.2

cdProdControlGroup OBJECT-GROUP
    OBJECTS
    {
--    chateauCDProdControl
         cdCtlPower,
         cdCtlTrayDoor,
         cdCtlPlaying
    }
    STATUS current
    DESCRIPTION
    "cdProdControlGroup"
    ::= { cdConformanceGroups 2 }


--          cdProdStatusGroup                       ccdp.1.20.1.3

cdProdStatusGroup OBJECT-GROUP
    OBJECTS
    {
--    chateauCDProdStatus
--       cdChassisStatus
            cdChStPowerOnHours,
            cdChStLaserOnHours,
            cdChStCrcErrorCtr,
            cdChStTemperature,
            cdChStPowerSupply,
--       cdChangerStatus
            cdChangerNbrCdSlots,
--          cdChangerSlotTable
--             cdChangerSlotEntry
--                cdChangerSlotNbr
                  cdChangerSlotStatus,
                  cdChangerSlotCDTrackPlaying,
                  cdChangerCDNbrTracks,
--          cdChangerCDTrackTable
--             cdChangerCDTrackEntry
--                cdChangerCDTrackNbr
                  cdChangerCDTrackPlaying,
                  cdChangerCDTrackLengthSecs,
                  cdChangerCDTrackLengthStr,
                  cdChangerCDTrackTitle,
                  cdChangerCDTrackArtist
    }
    STATUS current
    DESCRIPTION
    "cdProdStatusGroup"
    ::= { cdConformanceGroups 3 }


--          cdProdEventGroup                        ccdp.1.20.1.4

cdProdEventGroup OBJECT-GROUP
    OBJECTS
    {
--    chateauCDProdEvents
--       cdEventControl
            cdEvCtlAgtPollFreq,
            cdChassisTempAlarmThresh,
            cdChassisTempEvTrapEn,
            cdPowerSupplyEvTrapEn,
--       cdEventDescriptors
            cdEvSeverity,
            cdEvDescription
    }
    STATUS current
    DESCRIPTION
    "cdProdEventGroup"
    ::= { cdConformanceGroups 4 }


--          cdProdNotificationsGroup                ccdp.1.20.1.5

cdProdNotificationsGroup  NOTIFICATION-GROUP
    NOTIFICATIONS
    {
--    chateauCDProdEvents
--       cdEventList
            cdChassisTempAlarmEv,
            cdChassisTempOkayEv,
            cdPowerSupplyEv
    }
    STATUS current
    DESCRIPTION
    "cdProdNotificationsGroup"
    ::= { cdConformanceGroups 5 }



--
--       cdCompliance                               ccdp.1.20.2
--

cdCompliance MODULE-COMPLIANCE
    STATUS current
    DESCRIPTION
        "Specification of mandatory & non-mandatory
         MIB objects."
    MODULE -- This Module
    MANDATORY-GROUPS
        {
         cdProdConfigGroup,
         cdProdStatusGroup,
         cdProdEventGroup,
         cdProdNotificationsGroup
        }

    GROUP  cdProdControlGroup
    DESCRIPTION "A non-mandatory group."

::= { chateauCDProdConformance 2 }



END
