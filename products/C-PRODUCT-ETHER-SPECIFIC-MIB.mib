C-PRODUCT-ETHER-SPECIFIC-MIB DEFINITIONS ::= BEGIN


IMPORTS
    portSlot,
    portNumber				FROM C-PRODUCT-BASE-MIB
    ipOverAtm				FROM C-PRODUCT-ETHER-MIB
    IpAddress, Counter                  FROM RFC1155-SMI
    PhysAddress                         FROM RFC1213-MIB
    OBJECT-TYPE                         FROM RFC-1212;


     -- The IP over ATM Group
     -- IP over ATM Configuration

     ipAtmTbl OBJECT-TYPE
          SYNTAX SEQUENCE OF IpAtmEntry
          ACCESS not-accessible
          STATUS mandatory
          DESCRIPTION
               "The IP over ATM configuration table."
          ::= { ipOverAtm 1 }

     ipAtmEntry OBJECT-TYPE
          SYNTAX IpAtmEntry
          ACCESS not-accessible
          STATUS mandatory
          DESCRIPTION
               "Information about one IP over ATM configuration entry."
          INDEX { portSlot, portNumber }
          ::= { ipAtmTbl 1 }

     IpAtmEntry ::= SEQUENCE {
             ipAtmIpCntl
                 INTEGER ,
             ipAtmBrCntl
                 INTEGER ,
             ipAtmVcSideId
                 INTEGER ,
             ipAtmLanRtrIpAddr
                 IpAddress ,
             ipAtmLanRtrIpMask
                 IpAddress ,
             ipAtmLanRtrMacAddr
                 PhysAddress ,
             ipAtmAtmRtrIpAddr
                 IpAddress ,
             ipAtmAtmRtrIpMask
                 IpAddress, 
             portIpAddress
                IpAddress,
             portIpSubnetMask
                IpAddress,
             ipAtmVcOtherSideId
                 INTEGER 
     }

     ipAtmIpCntl OBJECT-TYPE
          SYNTAX INTEGER {
                       disable(1),
                       enable(2)
               }
          ACCESS read-write
          STATUS mandatory
          DESCRIPTION
               "The IP control status. When enabled, the virtual circuit
                specified here is used to pass IP traffic as routed frames.
                The IP control status."
          ::= { ipAtmEntry 1 }

     ipAtmBrCntl OBJECT-TYPE
          SYNTAX INTEGER {
                       disable(1),
                       enable(2)
               }
          ACCESS read-write
          STATUS mandatory
          DESCRIPTION
               "The Bridging control status. When enabled, the virtual circuit
                specified here is also used to pass bridging frames."
          ::= { ipAtmEntry 2 }

     ipAtmVcSideId OBJECT-TYPE
          SYNTAX INTEGER (0..2147483647)
          ACCESS read-write
          STATUS mandatory
          DESCRIPTION
               "This field is the global VC side id
	       of the LAN side of the IP/ATM VC, 
	       or 0 if no VC is assigned"
          ::= { ipAtmEntry 3 }

     ipAtmLanRtrIpAddr OBJECT-TYPE
          SYNTAX IpAddress
          ACCESS read-write
          STATUS mandatory
          DESCRIPTION
               "This is the ip address of the router on ethernet port."
          ::= { ipAtmEntry 4 }

     ipAtmLanRtrIpMask OBJECT-TYPE
          SYNTAX IpAddress
          ACCESS read-write
          STATUS mandatory
          DESCRIPTION
               "This is the ip subnet mask of the router on ethernet port."
          ::= { ipAtmEntry 5 }

     ipAtmLanRtrMacAddr OBJECT-TYPE
          SYNTAX  PhysAddress
          ACCESS  read-only
          STATUS  mandatory
          DESCRIPTION
               "LAN Router's MAC-layer address."
          ::= { ipAtmEntry 6 }

     ipAtmAtmRtrIpAddr OBJECT-TYPE
          SYNTAX IpAddress
          ACCESS read-write
          STATUS mandatory
          DESCRIPTION
               "This is the ip address of the LIS router on ATM side."
          ::= { ipAtmEntry 7 }

     ipAtmAtmRtrIpMask OBJECT-TYPE
          SYNTAX IpAddress
          ACCESS read-write
          STATUS mandatory
          DESCRIPTION
               "This is the ip subnet mask of the LIS router on ATM side."
          ::= { ipAtmEntry 8 }

     portIpAddress OBJECT-TYPE
          SYNTAX IpAddress
          ACCESS read-write
          STATUS mandatory
          DESCRIPTION
               "This is the ip address of ethernet port."
          ::= { ipAtmEntry 9 }

     portIpSubnetMask OBJECT-TYPE
          SYNTAX IpAddress
          ACCESS read-write
          STATUS mandatory
          DESCRIPTION
               "This is the subnet mask of ethernet port"
          ::= { ipAtmEntry 10 }

     ipAtmVcOtherSideId OBJECT-TYPE
          SYNTAX INTEGER (0..2147483647)
          ACCESS read-write
          STATUS mandatory
          DESCRIPTION
               "This field is the global VC other side id
	       of the IP/ATM VC, or 0 if no VC is assigned"
          ::= { ipAtmEntry 11 }


     -- IP over ATM statistics

     ipAtmStatTbl OBJECT-TYPE
          SYNTAX SEQUENCE OF IpAtmStatEntry
          ACCESS not-accessible
          STATUS mandatory        
          DESCRIPTION
               "The IP over ATM statistics table."
          ::= { ipOverAtm 2 }

     ipAtmStatEntry OBJECT-TYPE
          SYNTAX IpAtmStatEntry
          ACCESS not-accessible
          STATUS mandatory
          DESCRIPTION
               "Information about one IP over ATM statistics entry."
          INDEX { portSlot, portNumber }
          ::= { ipAtmStatTbl 1 }

     IpAtmStatEntry ::= SEQUENCE {
             ipAtmStatLanIpRcv
                 Counter ,
             ipAtmStatLanIpFwd
                 Counter ,
             ipAtmStatLanIpDrop
                 Counter ,
             ipAtmStatLanArpReq
                 Counter ,
             ipAtmStatLanArpRes
                 Counter ,
             ipAtmStatAtmIpRcv
                 Counter ,
             ipAtmStatAtmIpFwd
                 Counter ,
             ipAtmStatAtmIpDrop
                 Counter ,
             ipAtmStatAtmArpReq
                 Counter ,
             ipAtmStatAtmArpRes
                 Counter
     }

     ipAtmStatLanIpRcv OBJECT-TYPE
          SYNTAX  Counter
          ACCESS  read-only
          STATUS  mandatory
          DESCRIPTION
               "The total number of IP packets received on the Port"
          ::= { ipAtmStatEntry 1 }

     ipAtmStatLanIpFwd OBJECT-TYPE
          SYNTAX  Counter
          ACCESS  read-only
          STATUS  mandatory
          DESCRIPTION
               "The total number of IP packets received from the Port and forwarded"
          ::= { ipAtmStatEntry 2 }

     ipAtmStatLanIpDrop OBJECT-TYPE
          SYNTAX  Counter
          ACCESS  read-only
          STATUS  mandatory
          DESCRIPTION
               "The total number of IP packets received from the Port and dropped"
          ::= { ipAtmStatEntry 3 }

     ipAtmStatLanArpReq OBJECT-TYPE
          SYNTAX  Counter
          ACCESS  read-only
          STATUS  mandatory
          DESCRIPTION
               "The total number of ARP request packets received on the Port"
          ::= { ipAtmStatEntry 4 }

     ipAtmStatLanArpRes OBJECT-TYPE
          SYNTAX  Counter
          ACCESS  read-only
          STATUS  mandatory
          DESCRIPTION
               "The total number of ARP response packets received on the Port"
          ::= { ipAtmStatEntry 5 }

     ipAtmStatAtmIpRcv OBJECT-TYPE
          SYNTAX  Counter
          ACCESS  read-only
          STATUS  mandatory
          DESCRIPTION
               "The total number of IP packets received on the VC assigned at this
                port"
          ::= { ipAtmStatEntry 6 }

     ipAtmStatAtmIpFwd OBJECT-TYPE
          SYNTAX  Counter
          ACCESS  read-only
          STATUS  mandatory
          DESCRIPTION
               "The total number of IP packets received from the VC and forwarded"
          ::= { ipAtmStatEntry 7 }

     ipAtmStatAtmIpDrop OBJECT-TYPE
          SYNTAX  Counter
          ACCESS  read-only
          STATUS  mandatory
          DESCRIPTION
               "The total number of IP packets received from the VC and dropped"
          ::= { ipAtmStatEntry 8 }

     ipAtmStatAtmArpReq OBJECT-TYPE
          SYNTAX  Counter
          ACCESS  read-only
          STATUS  mandatory
          DESCRIPTION
               "The total number of ARP request packets received on the VC"
          ::= { ipAtmStatEntry 9 } 

     ipAtmStatAtmArpRes OBJECT-TYPE
          SYNTAX  Counter
          ACCESS  read-only
          STATUS  mandatory
          DESCRIPTION
               "The total number of ARP response packets received on the VC"
          ::= { ipAtmStatEntry 10 }

     END
