-- $Id: rstone-smi-mib.txt,v 1.2 2000/07/14 08:59:34 hyung Exp $

RSTONE-SMI-MIB DEFINITIONS ::= BEGIN

IMPORTS
        MODULE-IDENTITY,
        OBJECT-IDENTITY
           FROM SNMPv2-SMI
        enterprises
           FROM RFC1155-SMI;


riverstoneNetworks MODULE-IDENTITY   
    LAST-UPDATED "200004150000Z"
    ORGANIZATION "Riverstone Networks, Inc"
    CONTACT-INFO
    "Riverstone Networks, Inc
     5200 Great America Parkway
     Santa Clara CA USA 95054
     PHONE:+1 408.878.6500
     EMAIL: nms-eng@riverstonenet.com
     WEB: http://www.riverstonenet.com"
     DESCRIPTION
            "This mib module defines the enterprise managed object space
	     operated by Riverstone Networks, Inc
             http://www.riverstonenet.com/products. 

             Copyright (C) Riverstone Networks, Inc 2000"

    REVISION     "200004150000Z"
    DESCRIPTION
      "Riverstone SMI top layer organization. "
	 ::= { enterprises 5567 }  

riverstoneProducts OBJECT-IDENTITY
        STATUS  current
        DESCRIPTION
            "All Riverstone Product Families that include
             SNMP management are identified by these sysObjectIDs 
             under this branch."
        ::= { riverstoneNetworks 1 }

riverstoneMibs OBJECT-IDENTITY
        STATUS  current
        DESCRIPTION
            "All Riverstone enterprise MIBs are defined under riverstoneMibs"
        ::= { riverstoneNetworks 2 }

riverstoneAgentCapabilities OBJECT-IDENTITY
        STATUS  current
        DESCRIPTION
           "Agent Capability MIBS are defined under this branch."
        ::= { riverstoneNetworks 10 }

END
