-- ------------------------------------------------------
-- TRIPP LITE PRODUCTS MIB
-- Copyright (c) 1999-2016 Tripp Lite
-- All rights reserved
--
-- Revision History:
-- 03/13/2013 v12.06 Consolidated for PAL v12.06
-- 04/14/2014 v15.00 Consolidated for PAL v15.00
-- 12/04/2014 v15.00 Created ATS section
-- 03/19/2015 v15.00 Created tlpPduHeatsink and tlpAtsHeatsink
-- 04/20/2015 v15.00 Added tlpAtsConfigVoltageRangeTable
-- 06/08/2015 v15.00 Added tlpAtsInputBadVoltageThreshold
-- 08/19/2015 v15.00 Added tlpAtsConfigThresholdTable
-- 10/16/2015 v15.00 Added tlpAtsConfigSource#ReturnTime
-- 11/10/2015 v15.00 Refactored tlpUps
-- 11/25/2015 v15.00 Refactored UPS, PDU and ATS input sections
-- 01/08/2016 v15.00 Added tlpAtsConfigVoltageRangeLimitsTable
-- 01/20/2016 v15.00 Added tlpDeviceIdentUptime
-- 01/25/2016 v15.00 Redefined tlpUpsAlarmLoadLevelAboveThreshold
-- 02/02/2016 v15.00 Reworked tlpAgentAttributes
-- 06/22/2016 v15.00 Refactored MIB to extend from tripplite.mib
-- ------------------------------------------------------

TRIPPLITE-PRODUCTS DEFINITIONS ::= BEGIN

IMPORTS
  DisplayString,
  TruthValue,
  TimeStamp,
  RowStatus
    FROM SNMPv2-TC
  OBJECT-GROUP,
  NOTIFICATION-GROUP
    FROM SNMPv2-CONF
  MODULE-IDENTITY,
  OBJECT-IDENTITY,
  OBJECT-TYPE,
  NOTIFICATION-TYPE,
  Gauge32,
  Integer32,
  Unsigned32,
  enterprises,
  IpAddress,
  TimeTicks
    FROM SNMPv2-SMI
  tripplite
    FROM TRIPPLITE;

tlpProducts MODULE-IDENTITY
  LAST-UPDATED "201606221115Z"
  ORGANIZATION "Tripp Lite"
  CONTACT-INFO
    "Software Engineering
    Tripp Lite
    1111 W. 35th St.
    Chicago, IL 60609"
  DESCRIPTION
    "This MIB module defines MIB objects which provide mechanisms for
    remote management capabilities of Tripp Lite PowerAlert and related
    software."
  REVISION "201606221115Z"
  DESCRIPTION
    "Refactored MIB to extend from tripplite.mib"
  REVISION "201602021115Z"
  DESCRIPTION
    "Redefined tlpUpsAlarmLoadLevelAboveThreshold"
  REVISION "201601251230Z"
  DESCRIPTION
    "Redefined Reworked tlpAgentAttributes"
  REVISION "201601201200Z"
  DESCRIPTION
    "Added tlpDeviceIdentUptime"
  REVISION "201601081140Z"
  DESCRIPTION
    "Added tlpAtsConfigVoltageRangeLimitsTable"
  REVISION "201511251300Z"
  DESCRIPTION
    "Refactored UPS, PDU and ATS input sections"
  REVISION "201511101300Z"
  DESCRIPTION
    "Refactored tlpUps"
  REVISION "201510161230Z"
  DESCRIPTION
    "Added tlpAtsConfigSource#ReturnTime"
  REVISION "201508191200Z"
  DESCRIPTION
    "Added tlpAtsConfigThresholdTable"
  REVISION "201412041000Z"
  DESCRIPTION
    "Created ATS device-specific section"
  REVISION "201404140900Z"
  DESCRIPTION
    "Consolidated and Released for PAL v12.07.007x"
  
  ::= { tripplite 1 }

-- tlpProducts                 OBJECT IDENTIFIER   ::= { tripplite 1 }

tlpHardware                 OBJECT IDENTIFIER   ::= { tlpProducts 1 }
tlpSoftware                 OBJECT IDENTIFIER   ::= { tlpProducts 2 }
tlpAlarms                   OBJECT IDENTIFIER   ::= { tlpProducts 3 }
tlpNotify                   OBJECT IDENTIFIER   ::= { tlpProducts 4 }

tlpDevice                   OBJECT IDENTIFIER   ::= { tlpHardware 1 }
tlpDeviceDetail             OBJECT IDENTIFIER   ::= { tlpHardware 2 }
tlpDeviceTypes              OBJECT IDENTIFIER   ::= { tlpHardware 3 }

tlpUps                      OBJECT IDENTIFIER   ::= { tlpDeviceTypes 1 }
tlpPdu                      OBJECT IDENTIFIER   ::= { tlpDeviceTypes 2 }
tlpEnvirosense              OBJECT IDENTIFIER   ::= { tlpDeviceTypes 3 }
tlpAts                      OBJECT IDENTIFIER   ::= { tlpDeviceTypes 4 }
tlpCooling                  OBJECT IDENTIFIER   ::= { tlpDeviceTypes 5 }
tlpKvm                      OBJECT IDENTIFIER   ::= { tlpDeviceTypes 6 }
tlpRackTrack                OBJECT IDENTIFIER   ::= { tlpDeviceTypes 7 }
tlpSwitch                   OBJECT IDENTIFIER   ::= { tlpDeviceTypes 8 }

tlpUpsIdent                 OBJECT IDENTIFIER   ::= { tlpUps 1 }
tlpUpsDevice                OBJECT IDENTIFIER   ::= { tlpUps 2 }
tlpUpsDetail                OBJECT IDENTIFIER   ::= { tlpUps 3 }
tlpUpsControl               OBJECT IDENTIFIER   ::= { tlpUps 4 }
tlpUpsConfig                OBJECT IDENTIFIER   ::= { tlpUps 5 }

tlpUpsBattery               OBJECT IDENTIFIER   ::= { tlpUpsDetail 1 }
tlpUpsInput                 OBJECT IDENTIFIER   ::= { tlpUpsDetail 2 }
tlpUpsOutput                OBJECT IDENTIFIER   ::= { tlpUpsDetail 3 }
tlpUpsBypass                OBJECT IDENTIFIER   ::= { tlpUpsDetail 4 }
tlpUpsOutlet                OBJECT IDENTIFIER   ::= { tlpUpsDetail 5 }
tlpUpsWatchdog              OBJECT IDENTIFIER   ::= { tlpUpsDetail 6 }

tlpPduIdent                 OBJECT IDENTIFIER   ::= { tlpPdu 1 }
tlpPduDevice                OBJECT IDENTIFIER   ::= { tlpPdu 2 }
tlpPduDetail                OBJECT IDENTIFIER   ::= { tlpPdu 3 }
tlpPduControl               OBJECT IDENTIFIER   ::= { tlpPdu 4 }
tlpPduConfig                OBJECT IDENTIFIER   ::= { tlpPdu 5 }

tlpPduInput                 OBJECT IDENTIFIER   ::= { tlpPduDetail 1 }
tlpPduOutput                OBJECT IDENTIFIER   ::= { tlpPduDetail 2 }
tlpPduOutlet                OBJECT IDENTIFIER   ::= { tlpPduDetail 3 }
tlpPduCircuit               OBJECT IDENTIFIER   ::= { tlpPduDetail 4 }
tlpPduBreaker               OBJECT IDENTIFIER   ::= { tlpPduDetail 5 }
tlpPduHeatsink              OBJECT IDENTIFIER   ::= { tlpPduDetail 6 }

tlpEnvIdent                 OBJECT IDENTIFIER   ::= { tlpEnvirosense 1 }
-- tlpEnvDevice             OBJECT IDENTIFIER   ::= { tlpEnvirosense 2 }
tlpEnvDetail                OBJECT IDENTIFIER   ::= { tlpEnvirosense 3 }
-- tlpEnvControl            OBJECT IDENTIFIER   ::= { tlpEnvirosense 4 }
tlpEnvConfig                OBJECT IDENTIFIER   ::= { tlpEnvirosense 5 }

tlpAtsIdent                 OBJECT IDENTIFIER   ::= { tlpAts 1 }
tlpAtsDevice                OBJECT IDENTIFIER   ::= { tlpAts 2 }
tlpAtsDetail                OBJECT IDENTIFIER   ::= { tlpAts 3 }
tlpAtsControl               OBJECT IDENTIFIER   ::= { tlpAts 4 }
tlpAtsConfig                OBJECT IDENTIFIER   ::= { tlpAts 5 }

tlpAtsInput                 OBJECT IDENTIFIER   ::= { tlpAtsDetail 1 }
tlpAtsOutput                OBJECT IDENTIFIER   ::= { tlpAtsDetail 2 }
tlpAtsOutlet                OBJECT IDENTIFIER   ::= { tlpAtsDetail 3 }
tlpAtsCircuit               OBJECT IDENTIFIER   ::= { tlpAtsDetail 4 }
tlpAtsBreaker               OBJECT IDENTIFIER   ::= { tlpAtsDetail 5 }
tlpAtsHeatsink              OBJECT IDENTIFIER   ::= { tlpAtsDetail 6 }

tlpCoolingIdent             OBJECT IDENTIFIER   ::= { tlpCooling 1 }
tlpCoolingDevice            OBJECT IDENTIFIER   ::= { tlpCooling 2 }
tlpCoolingDetail            OBJECT IDENTIFIER   ::= { tlpCooling 3 }
tlpCoolingControl           OBJECT IDENTIFIER   ::= { tlpCooling 4 }
tlpCoolingConfig            OBJECT IDENTIFIER   ::= { tlpCooling 5 }

tlpCoolingInput             OBJECT IDENTIFIER   ::= { tlpCoolingDetail 1 }
tlpCoolingOutput            OBJECT IDENTIFIER   ::= { tlpCoolingDetail 2 }

tlpKvmIdent                 OBJECT IDENTIFIER   ::= { tlpKvm 1 }
tlpKvmDevice                OBJECT IDENTIFIER   ::= { tlpKvm 2 }
tlpKvmDetail                OBJECT IDENTIFIER   ::= { tlpKvm 3 }
tlpKvmControl               OBJECT IDENTIFIER   ::= { tlpKvm 4 }
tlpKvmConfig                OBJECT IDENTIFIER   ::= { tlpKvm 5 }

tlpRackTrackIdent           OBJECT IDENTIFIER   ::= { tlpRackTrack 1 }
tlpRackTrackDevice          OBJECT IDENTIFIER   ::= { tlpRackTrack 2 }
tlpRackTrackDetail          OBJECT IDENTIFIER   ::= { tlpRackTrack 3 }
tlpRackTrackControl         OBJECT IDENTIFIER   ::= { tlpRackTrack 4 }
tlpRackTrackConfig          OBJECT IDENTIFIER   ::= { tlpRackTrack 5 }

tlpSwitchIdent              OBJECT IDENTIFIER   ::= { tlpSwitch 1 }
tlpSwitchDevice             OBJECT IDENTIFIER   ::= { tlpSwitch 2 }
tlpSwitchDetail             OBJECT IDENTIFIER   ::= { tlpSwitch 3 }
tlpSwitchControl            OBJECT IDENTIFIER   ::= { tlpSwitch 4 }
tlpSwitchConfig             OBJECT IDENTIFIER   ::= { tlpSwitch 5 }

tlpAgentDetails             OBJECT IDENTIFIER   ::= { tlpSoftware 1 }
tlpAgentSettings            OBJECT IDENTIFIER   ::= { tlpSoftware 2 }
tlpAgentContacts            OBJECT IDENTIFIER   ::= { tlpSoftware 3 }

tlpAgentIdent               OBJECT IDENTIFIER   ::= { tlpAgentDetails 1}
tlpAgentAttributes          OBJECT IDENTIFIER   ::= { tlpAgentDetails 2}

tlpAgentConfig              OBJECT IDENTIFIER   ::= { tlpAgentSettings 1}

tlpAgentEmailContacts       OBJECT IDENTIFIER   ::= { tlpAgentContacts 1}
tlpAgentSnmpContacts        OBJECT IDENTIFIER   ::= { tlpAgentContacts 2}

tlpAlarmsWellKnown          OBJECT IDENTIFIER   ::= { tlpAlarms 3 }
tlpAlarmControl             OBJECT IDENTIFIER   ::= { tlpAlarms 4 }

tlpAgentAlarms              OBJECT IDENTIFIER   ::= { tlpAlarmsWellKnown 1 }
tlpDeviceAlarms             OBJECT IDENTIFIER   ::= { tlpAlarmsWellKnown 2 }
tlpUpsAlarms                OBJECT IDENTIFIER   ::= { tlpAlarmsWellKnown 3 }
tlpPduAlarms                OBJECT IDENTIFIER   ::= { tlpAlarmsWellKnown 4 }
tlpEnvAlarms                OBJECT IDENTIFIER   ::= { tlpAlarmsWellKnown 5 }
tlpAtsAlarms                OBJECT IDENTIFIER   ::= { tlpAlarmsWellKnown 6 }
tlpCoolingAlarms            OBJECT IDENTIFIER   ::= { tlpAlarmsWellKnown 7 }
tlpKvmAlarms                OBJECT IDENTIFIER   ::= { tlpAlarmsWellKnown 8 }
tlpRackTrackAlarms          OBJECT IDENTIFIER   ::= { tlpAlarmsWellKnown 9 }
tlpSwitchAlarms             OBJECT IDENTIFIER   ::= { tlpAlarmsWellKnown 10 }

tlpNotifications            OBJECT IDENTIFIER   ::= { tlpNotify 1 }

tlpDeviceNumDevices OBJECT-TYPE
    SYNTAX Unsigned32
    MAX-ACCESS read-only
    STATUS current
    DESCRIPTION
        "The number of devices that this agent is currently managing."
    ::= { tlpDevice 1 }

tlpDeviceTable OBJECT-TYPE
    SYNTAX SEQUENCE OF TlpDeviceEntry
    MAX-ACCESS not-accessible
    STATUS current
    DESCRIPTION
        "A list of device table entries.  The number of entries
        is given by the value of tlpDevicesNumDevices."
    ::= { tlpDevice 2 }

tlpDeviceEntry OBJECT-TYPE
    SYNTAX TlpDeviceEntry
    MAX-ACCESS not-accessible
    STATUS current
    DESCRIPTION
        "An entry containing information applicable to a particular device
        managed by this agent."
    INDEX { tlpDeviceIndex }
    ::= { tlpDeviceTable 1 }

TlpDeviceEntry ::= SEQUENCE {
    tlpDeviceIndex                  Unsigned32,
    tlpDeviceRowStatus              RowStatus,
    tlpDeviceType                   OBJECT IDENTIFIER,
    tlpDeviceManufacturer           DisplayString,
    tlpDeviceModel                  DisplayString,
    tlpDeviceName                   DisplayString,
    tlpDeviceID                     INTEGER,
    tlpDeviceLocation               DisplayString,
    tlpDeviceRegion                 DisplayString,
    tlpDeviceStatus                 INTEGER }

tlpDeviceIndex OBJECT-TYPE
    SYNTAX Unsigned32
    MAX-ACCESS read-only
    STATUS current
    DESCRIPTION
        "The table row index for the device."
    ::= { tlpDeviceEntry 1 }

tlpDeviceRowStatus OBJECT-TYPE
    SYNTAX RowStatus
    MAX-ACCESS read-only
    STATUS current
    DESCRIPTION
        "Used with table edits to indicate the status of a given row in
        tlDeviceTable."
    ::= { tlpDeviceEntry 2 }

tlpDeviceType OBJECT-TYPE
    SYNTAX OBJECT IDENTIFIER
    MAX-ACCESS read-only
    STATUS current
    DESCRIPTION
        "The type of device. One of the appropriate hardware types:
        ups, pdu, envirosense, etc."
    ::= { tlpDeviceEntry 3 }

tlpDeviceManufacturer OBJECT-TYPE
    SYNTAX DisplayString
    MAX-ACCESS read-only
    STATUS current
    DESCRIPTION
        "The name of the manufacturer."
    ::= { tlpDeviceEntry 4 }

tlpDeviceModel OBJECT-TYPE
    SYNTAX DisplayString
    MAX-ACCESS read-only
    STATUS current
    DESCRIPTION
        "The model designation."
    ::= { tlpDeviceEntry 5 }

tlpDeviceName OBJECT-TYPE
    SYNTAX DisplayString
    MAX-ACCESS read-write
    STATUS current
    DESCRIPTION
        "A user-supplied name for the device."
    ::= { tlpDeviceEntry 6 }

tlpDeviceID OBJECT-TYPE
    SYNTAX INTEGER (0..65535)
    MAX-ACCESS read-write
    STATUS current
    DESCRIPTION
        "A user-supplied ID for the device."
    ::= { tlpDeviceEntry 7 }

tlpDeviceLocation OBJECT-TYPE
    SYNTAX DisplayString
    MAX-ACCESS read-write
    STATUS current
    DESCRIPTION
        "A user-supplied location for the device."
    ::= { tlpDeviceEntry 8 }

tlpDeviceRegion OBJECT-TYPE
    SYNTAX DisplayString
    MAX-ACCESS read-write
    STATUS current
    DESCRIPTION
        "A user-supplied region for the device."
    ::= { tlpDeviceEntry 9 }

tlpDeviceStatus OBJECT-TYPE
    SYNTAX INTEGER {
        none(0),
        critical(1),
        warning(2),
        info(3),
        status(4),
        offline(5),
        custom(6),
        configuration(7) }
    MAX-ACCESS read-only
    STATUS current
    DESCRIPTION
        "The currently most critical alarm status for the device."
    ::= { tlpDeviceEntry 10 }

tlpDeviceIdentTable OBJECT-TYPE
    SYNTAX SEQUENCE OF TlpDeviceIdentEntry
    MAX-ACCESS not-accessible
    STATUS current
    DESCRIPTION
        "The identity details of each device in device table. The number
        of entries is given by the value of tlpDevicesNumDevices."
    ::= { tlpDeviceDetail 1 }

tlpDeviceIdentEntry OBJECT-TYPE
    SYNTAX TlpDeviceIdentEntry
    MAX-ACCESS not-accessible
    STATUS current
    DESCRIPTION
        "An entry containing details for a particular device."
        INDEX { tlpDeviceIndex }
    ::= { tlpDeviceIdentTable 1 }

TlpDeviceIdentEntry ::= SEQUENCE {
    tlpDeviceIdentProtocol              DisplayString,
    tlpDeviceIdentCommPortType          INTEGER,
    tlpDeviceIdentCommPortName          DisplayString,
    tlpDeviceIdentFirmwareVersion       DisplayString,
    tlpDeviceIdentSerialNum             DisplayString,
    tlpDeviceIdentDateInstalled         DisplayString,
    tlpDeviceIdentHardwareVersion       DisplayString,
    tlpDeviceIdentCurrentUptime         DisplayString,
    tlpDeviceIdentTotalUptime           DisplayString }

tlpDeviceIdentProtocol OBJECT-TYPE
    SYNTAX DisplayString
    MAX-ACCESS read-only
    STATUS current
    DESCRIPTION
        "The Tripplite protocol used to communicate with the device."
    ::= { tlpDeviceIdentEntry 1 }

tlpDeviceIdentCommPortType OBJECT-TYPE
    SYNTAX INTEGER {
        unknown(0),
        serial(1),
        usb(2),
        hid(3),
        simulated(4),
        unittest(5) }
    MAX-ACCESS read-only
    STATUS current
    DESCRIPTION
        "The type of communications port used to connect with the device."
    ::= { tlpDeviceIdentEntry 2 }

tlpDeviceIdentCommPortName OBJECT-TYPE
    SYNTAX DisplayString
    MAX-ACCESS read-only
    STATUS current
    DESCRIPTION
        "The name of the communications port."
    ::= { tlpDeviceIdentEntry 3 }

tlpDeviceIdentFirmwareVersion OBJECT-TYPE
    SYNTAX DisplayString
    MAX-ACCESS read-only
    STATUS current
    DESCRIPTION
        "The firmware version of the device."
    ::= { tlpDeviceIdentEntry 4 }

tlpDeviceIdentSerialNum OBJECT-TYPE
    SYNTAX DisplayString
    MAX-ACCESS read-only
    STATUS current
    DESCRIPTION
        "The serial number of the device."
    ::= { tlpDeviceIdentEntry 5 }

tlpDeviceIdentDateInstalled OBJECT-TYPE
    SYNTAX DisplayString
    MAX-ACCESS read-write
    STATUS current
    DESCRIPTION
        "The installation date for this device in the format of mm/dd/yyyy."
    ::= { tlpDeviceIdentEntry 6 }

tlpDeviceIdentHardwareVersion OBJECT-TYPE
    SYNTAX DisplayString
    MAX-ACCESS read-only
    STATUS current
    DESCRIPTION
        "The hardware revision of the device. This value will return ERROR_NO_SUCH_NAME
        if not supported by the device."
    ::= { tlpDeviceIdentEntry 7 }

tlpDeviceIdentCurrentUptime OBJECT-TYPE
    SYNTAX DisplayString
    MAX-ACCESS read-only
    STATUS current
    DESCRIPTION
        "The device uptime since its last startup. The format of this value is a comma-
        delimited string representing days, hours and minutes. For example, the value of
        123,4,5 represents 123 days, 4 hours and 5 minutes. This value will return
        ERROR_NO_SUCH_NAME if not supported by the device."
    ::= { tlpDeviceIdentEntry 8 }

tlpDeviceIdentTotalUptime OBJECT-TYPE
    SYNTAX DisplayString
    MAX-ACCESS read-only
    STATUS current
    DESCRIPTION
        "The cumulative (total) uptime for the device. The format of this value is a comma-
        delimited string representing days, hours and minutes. For example, the value of
        123,4,5 represents 123 days, 4 hours and 5 minutes. This value will return
        ERROR_NO_SUCH_NAME if not supported by the device."
    ::= { tlpDeviceIdentEntry 9 }

-- ups

tlpUpsIdentNumUps OBJECT-TYPE
    SYNTAX Unsigned32
    MAX-ACCESS read-only
    STATUS current
    DESCRIPTION
        "The number of ups devices that this agent is currently managing."
    ::= { tlpUpsIdent 1 }

tlpUpsIdentTable OBJECT-TYPE
    SYNTAX SEQUENCE OF TlpUpsIdentEntry
    MAX-ACCESS not-accessible
    STATUS current
    DESCRIPTION
        "The identity details of each ups in device table. This is a
        sparse dependent table, and will contain some subset of devices
        that are upss."
    ::= { tlpUpsIdent 2 }

tlpUpsIdentEntry OBJECT-TYPE
    SYNTAX TlpUpsIdentEntry
    MAX-ACCESS not-accessible
    STATUS current
    DESCRIPTION
        "An entry containing details for a particular ups."
    INDEX { tlpDeviceIndex }
    ::= { tlpUpsIdentTable 1 }

TlpUpsIdentEntry ::= SEQUENCE {
    tlpUpsIdentNumInputs                Unsigned32,
    tlpUpsIdentNumOutputs               Unsigned32,
    tlpUpsIdentNumBypass                Unsigned32,
    tlpUpsIdentNumPhases                Unsigned32,
    tlpUpsIdentNumOutlets               Unsigned32,
    tlpUpsIdentNumOutletGroups          Unsigned32,
    tlpUpsIdentNumBatteryPacks          Unsigned32 }

tlpUpsIdentNumInputs OBJECT-TYPE
    SYNTAX Unsigned32
    MAX-ACCESS read-only
    STATUS current
    DESCRIPTION
        "The number of input lines supported by the ups."
    ::= { tlpUpsIdentEntry 1 }

tlpUpsIdentNumOutputs OBJECT-TYPE
    SYNTAX Unsigned32
    MAX-ACCESS read-only
    STATUS current
    DESCRIPTION
        "The number of output lines supported by the ups."
    ::= { tlpUpsIdentEntry 2 }

tlpUpsIdentNumBypass OBJECT-TYPE
    SYNTAX Unsigned32
    MAX-ACCESS read-only
    STATUS current
    DESCRIPTION
        "The number of bypass lines supported by the ups."
    ::= { tlpUpsIdentEntry 3 }

tlpUpsIdentNumPhases OBJECT-TYPE
    SYNTAX Unsigned32
    MAX-ACCESS read-only
    STATUS current
    DESCRIPTION
        "The number of phases supported by the ups."
    ::= { tlpUpsIdentEntry 4 }

tlpUpsIdentNumOutlets OBJECT-TYPE
    SYNTAX Unsigned32
    MAX-ACCESS read-only
    STATUS current
    DESCRIPTION
        "The number of receptacles supported by the ups."
    ::= { tlpUpsIdentEntry 5 }

tlpUpsIdentNumOutletGroups OBJECT-TYPE
    SYNTAX Unsigned32
    MAX-ACCESS read-only
    STATUS current
    DESCRIPTION
        "The number of receptacle groups supported by the ups."
    ::= { tlpUpsIdentEntry 6 }

tlpUpsIdentNumBatteryPacks OBJECT-TYPE
    SYNTAX Unsigned32
    MAX-ACCESS read-only
    STATUS current
    DESCRIPTION
        "The number of battery packs, internal and external combined,
        supported by the ups."
    ::= { tlpUpsIdentEntry 7 }

tlpUpsSupportsTable OBJECT-TYPE
    SYNTAX SEQUENCE OF TlpUpsSupportsEntry
    MAX-ACCESS not-accessible
    STATUS current
    DESCRIPTION
        "The supported details of each ups in device table. This is a
        sparse dependent table, and will contain some subset of devices
        that are upss."
    ::= { tlpUpsIdent 3 }

tlpUpsSupportsEntry OBJECT-TYPE
    SYNTAX TlpUpsSupportsEntry
    MAX-ACCESS not-accessible
    STATUS current
    DESCRIPTION
        "An entry containing supported details for a particular ups."
    INDEX { tlpDeviceIndex }
    ::= { tlpUpsSupportsTable 1 }

TlpUpsSupportsEntry ::= SEQUENCE {
    tlpUpsSupportsEnergywise            TruthValue,
    tlpUpsSupportsRampShed              TruthValue,
    tlpUpsSupportsOutletGroup           TruthValue,
    tlpUpsSupportsOutletCurrentPower    TruthValue,
    tlpUpsSupportsOutletVoltage         TruthValue }

tlpUpsSupportsEnergywise OBJECT-TYPE
    SYNTAX TruthValue
    MAX-ACCESS read-only
    STATUS current
    DESCRIPTION
        "Indicates whether the ups supports Cisco EnergyWise."
    ::= { tlpUpsSupportsEntry 1 }

tlpUpsSupportsRampShed OBJECT-TYPE
    SYNTAX TruthValue
    MAX-ACCESS read-only
    STATUS current
    DESCRIPTION
        "Indicates whether the ups supports ramping and shedding."
    ::= { tlpUpsSupportsEntry 2 }

tlpUpsSupportsOutletGroup OBJECT-TYPE
    SYNTAX TruthValue
    MAX-ACCESS read-only
    STATUS current
    DESCRIPTION
        "Indicates whether the ups supports outlet groups."
    ::= { tlpUpsSupportsEntry 3 }

tlpUpsSupportsOutletCurrentPower OBJECT-TYPE
    SYNTAX TruthValue
    MAX-ACCESS read-only
    STATUS current
    DESCRIPTION
        "Indicates whether the ups reports individual receptacle current
        and power measurements. Devices that do not support individual
        receptacle measurements will always return ERROR_NO_SUCH_NAME for
        tlpUpsOutletCurrent and tlpUpsOutletPower."
    ::= { tlpUpsSupportsEntry 4 }

tlpUpsSupportsOutletVoltage OBJECT-TYPE
    SYNTAX TruthValue
    MAX-ACCESS read-only
    STATUS current
    DESCRIPTION
        "Indicates whether the ups reports individual receptacle voltage
        measurements. Devices that do not support individual receptacle
        measurements will always return ERROR_NO_SUCH_NAME for
        tlpUpsOutletVoltage."
    ::= { tlpUpsSupportsEntry 5 }

tlpUpsDeviceTable OBJECT-TYPE
    SYNTAX SEQUENCE OF TlpUpsDeviceEntry
    MAX-ACCESS not-accessible
    STATUS current
    DESCRIPTION
        "The device details of each ups in device table. This is a
        sparse dependent table, and will contain some subset of devices
        that are upss."
    ::= { tlpUpsDevice 1 }

tlpUpsDeviceEntry OBJECT-TYPE
    SYNTAX TlpUpsDeviceEntry
    MAX-ACCESS not-accessible
    STATUS current
    DESCRIPTION
        "An entry containing device details for a particular ups."
    INDEX { tlpDeviceIndex }
    ::= { tlpUpsDeviceTable 1 }

TlpUpsDeviceEntry ::= SEQUENCE {
    tlpUpsDeviceMainLoadState           INTEGER,
    tlpUpsDeviceMainLoadControllable    TruthValue,
    tlpUpsDeviceMainLoadCommand         INTEGER,
    tlpUpsDevicePowerOnDelay            Integer32,
    tlpUpsDeviceTestDate                DisplayString,
    tlpUpsDeviceTestResultsStatus       INTEGER,
    tlpUpsDeviceTemperatureC            Integer32,
    tlpUpsDeviceTemperatureF            Integer32 }

tlpUpsDeviceMainLoadState OBJECT-TYPE
    SYNTAX INTEGER {
        unknown(0),
        off(1),
        on(2) }
    MAX-ACCESS read-only
    STATUS current
    DESCRIPTION
        "The current state of the main output of the device."
    ::= { tlpUpsDeviceEntry 1 }

tlpUpsDeviceMainLoadControllable OBJECT-TYPE
    SYNTAX TruthValue
    MAX-ACCESS read-only
    STATUS current
    DESCRIPTION
        "Indicates whether or not the main output is controllable, and whether
        the ups can be turned off and on."
    ::= { tlpUpsDeviceEntry 2 }

tlpUpsDeviceMainLoadCommand OBJECT-TYPE
    SYNTAX INTEGER {
        idle(0),
        turnOff(1),
        turnOn(2),
        cycle(3) }
    MAX-ACCESS read-write
    STATUS current
    DESCRIPTION
        "Reading this value will always return 0. Setting this value to
        turnOff(1) will turn off the main output of the ups. Setting this
        value to turnOn(2) will turn on the main output of the ups. Setting
        this value to cycle(3) will turn off the main output, then turn it
        back on."
    ::= { tlpUpsDeviceEntry 3 }

tlpUpsDevicePowerOnDelay OBJECT-TYPE
    SYNTAX Integer32
    MAX-ACCESS read-write
    STATUS current
    DESCRIPTION
        "The configurable delay value, which sets the amount of additional
        time a given device will wait before it connects to a valid AC
        source. By default the delay value is set to 0."
    ::= { tlpUpsDeviceEntry 4 }

tlpUpsDeviceTestDate OBJECT-TYPE
    SYNTAX DisplayString
    MAX-ACCESS read-only
    STATUS current
    DESCRIPTION
        "The date of the last self-test run on the ups, in the format YYYY-MM-DD."
    ::= { tlpUpsDeviceEntry 5 }

tlpUpsDeviceTestResultsStatus OBJECT-TYPE
    SYNTAX INTEGER {
        noTest(0),
        doneAndPassed(1),
        doneAndWarning(2),
        doneAndError(3),
        aborted(4),
        inProgress(5),
        noTestInitiated(6),
        badBattery(7),
        overCurrent(8),
        batteryFailed(9) }
    MAX-ACCESS read-only
    STATUS current
    DESCRIPTION
        "The result of the last self-test run on the ups."
    ::= { tlpUpsDeviceEntry 6 }

tlpUpsDeviceTemperatureC OBJECT-TYPE
    SYNTAX Integer32
    UNITS "degrees Centigrade"
    MAX-ACCESS read-only
    STATUS current
    DESCRIPTION
        "The ambient temperature at or near the ups casing. Temperature
        measurements are not supported on all models. If not supported,
        this value will always return ERROR_NO_SUCH_NAME."
    ::= { tlpUpsDeviceEntry 7 }

tlpUpsDeviceTemperatureF OBJECT-TYPE
    SYNTAX Integer32
    UNITS "degrees Farenheit"
    MAX-ACCESS read-only
    STATUS current
    DESCRIPTION
        "The ambient temperature at or near the ups casing. Temperature
        measurements are not supported on all models. If not supported,
        this value will always return ERROR_NO_SUCH_NAME."
    ::= { tlpUpsDeviceEntry 8 }

tlpUpsBatterySummaryTable OBJECT-TYPE
    SYNTAX SEQUENCE OF TlpUpsBatterySummaryEntry
    MAX-ACCESS not-accessible
    STATUS current
    DESCRIPTION
        "The battery system summary of each ups in the device
        table. This is a sparse dependent table, and will contain the
        number of entries based upon the number of upss managed by
        the agent as reported by tlpUpsIdentNumUps."
    ::= { tlpUpsBattery 1 }

tlpUpsBatterySummaryEntry OBJECT-TYPE
    SYNTAX TlpUpsBatterySummaryEntry
    MAX-ACCESS not-accessible
    STATUS current
    DESCRIPTION
        "An entry containing information applicable to a particular
        battery system managed by this agent."
    INDEX { tlpDeviceIndex }
    ::= { tlpUpsBatterySummaryTable 1 }

TlpUpsBatterySummaryEntry ::= SEQUENCE {
    tlpUpsBatteryStatus                     INTEGER,
    tlpUpsSecondsOnBattery                  Unsigned32,
    tlpUpsEstimatedMinutesRemaining         Unsigned32,
    tlpUpsEstimatedChargeRemaining          INTEGER,
    tlpUpsBatteryRunTimeRemaining           TimeTicks }

tlpUpsBatteryStatus OBJECT-TYPE
    SYNTAX INTEGER {
        unknown(1),
        batteryNormal(2),
        batteryLow(3),
        batteryDepleted(4) }
    MAX-ACCESS read-only
    STATUS current
    DESCRIPTION
        "The indication of the capacity remaining in the UPS system's
        batteries. A value of batteryNormal indicates that the
        remaining run-time is greater than tlpUpsConfigLowBattTime. A
        value of batteryLow indicates that the remaining battery run-time
        is less than or equal to tlpUpsConfigLowBattTime.  A value of
        batteryDepleted indicates that the UPS will be unable to sustain
        the present load when and if the utility power is lost (including
        the possibility that the utility power is currently absent and
        the UPS is unable to sustain the output)."
    ::= { tlpUpsBatterySummaryEntry 1 }

tlpUpsSecondsOnBattery OBJECT-TYPE
    SYNTAX Unsigned32
    UNITS "seconds"
    MAX-ACCESS read-only
    STATUS current
    DESCRIPTION
        "If the unit is on battery power, the elapsed time since the UPS
        last switched to battery power, or the time since the network
        management subsystem was last restarted, whichever is less. Zero
        shall be returned if the unit is not on battery power."
    ::= { tlpUpsBatterySummaryEntry 2 }

tlpUpsEstimatedMinutesRemaining OBJECT-TYPE
    SYNTAX Unsigned32
    UNITS "minutes"
    MAX-ACCESS read-only
    STATUS current
    DESCRIPTION
        "An estimate of the time to battery charge depletion
        under the present load conditions if the utility power
        is off and remains off, or if it were to be lost and
        remain off."
    ::= { tlpUpsBatterySummaryEntry 3 }

tlpUpsEstimatedChargeRemaining OBJECT-TYPE
    SYNTAX INTEGER (0..100)
    UNITS "percent"
    MAX-ACCESS read-only
    STATUS current
    DESCRIPTION
        "An estimate of the battery charge remaining expressed
        as a percent of full charge."
    ::= { tlpUpsBatterySummaryEntry 4 }

tlpUpsBatteryRunTimeRemaining OBJECT-TYPE
    SYNTAX TimeTicks
    MAX-ACCESS read-only
    STATUS current
    DESCRIPTION
        "The run time remaining before batteries are exhausted. If the device
        does not support run time remaining, then the agent reports
        ERROR_NO_SUCH_NAME."
    ::= { tlpUpsBatterySummaryEntry 5 }

tlpUpsBatteryDetailTable OBJECT-TYPE
    SYNTAX SEQUENCE OF TlpUpsBatteryDetailEntry
    MAX-ACCESS not-accessible
    STATUS current
    DESCRIPTION
        "The battery detail of each ups in the device table. This is a sparse
        dependent table, and will contain the number of entries based upon the
        number of upss managed by the agent as reported by tlpUpsIdentNumUps."
    ::= { tlpUpsBattery 2 }

tlpUpsBatteryDetailEntry OBJECT-TYPE
    SYNTAX TlpUpsBatteryDetailEntry
    MAX-ACCESS not-accessible
    STATUS current
    DESCRIPTION
        "An entry containing information applicable to a particular
        battery system managed by this agent."
    INDEX { tlpDeviceIndex }
    ::= { tlpUpsBatteryDetailTable 1 }

TlpUpsBatteryDetailEntry ::= SEQUENCE {
    tlpUpsBatteryDetailVoltage              Unsigned32,
    tlpUpsBatteryDetailCurrent              Unsigned32,
    tlpUpsBatteryDetailCapacity             INTEGER,
    tlpUpsBatteryDetailCharge               INTEGER,
    tlpUpsBatteryDetailChargerStatus        INTEGER }

tlpUpsBatteryDetailVoltage OBJECT-TYPE
    SYNTAX Unsigned32
    UNITS "0.1 Volt DC"
    MAX-ACCESS read-only
    STATUS current
    DESCRIPTION
        "The magnitude of the present battery voltage."
    ::= { tlpUpsBatteryDetailEntry 1 }

tlpUpsBatteryDetailCurrent OBJECT-TYPE
    SYNTAX Unsigned32
    UNITS "0.1 Amp DC"
    MAX-ACCESS read-only
    STATUS current
    DESCRIPTION
        "The present battery current."
    ::= { tlpUpsBatteryDetailEntry 2 }

tlpUpsBatteryDetailCapacity OBJECT-TYPE
    SYNTAX INTEGER (0..100)
    UNITS "percent"
    MAX-ACCESS read-only
    STATUS current
    DESCRIPTION
        "The estimated remaining battery capacity expressed as a percent of
        full capacity."
    ::= { tlpUpsBatteryDetailEntry 3 }

tlpUpsBatteryDetailCharge OBJECT-TYPE
    SYNTAX INTEGER {
        floating(0),
        charging(1),
        resting(2),
        discharging(3),
        normal(4),
        standby(5) }
    MAX-ACCESS read-only
    STATUS current
    DESCRIPTION
        "Denotes the charge state of the battery."
    ::= { tlpUpsBatteryDetailEntry 4 }

tlpUpsBatteryDetailChargerStatus OBJECT-TYPE
    SYNTAX INTEGER {
        ok(0),
        inFaultCondition(1) }
    MAX-ACCESS read-only
    STATUS current
    DESCRIPTION
        "The status of the battery charger. If the device does not support this
        value, then the agent will report ERROR_NO_SUCH_NAME."
    ::= { tlpUpsBatteryDetailEntry 5 }

tlpUpsBatteryPackIdentTable OBJECT-TYPE
    SYNTAX SEQUENCE OF TlpUpsBatteryIdentEntry
    MAX-ACCESS not-accessible
    STATUS current
    DESCRIPTION
        "The battery identification details for each ups in the device
        table. This is a sparse dependent table, and will contain the
        number of entries based upon the number of upss managed by the
        agent as reported by upsIdentNumUps and the number of battery
        battery packs per each as reported by tlpUpsNumBatteryPacks."
    ::= { tlpUpsBattery 3 }

tlpUpsBatteryPackIdentEntry OBJECT-TYPE
    SYNTAX TlpUpsBatteryIdentEntry
    MAX-ACCESS not-accessible
    STATUS current
    DESCRIPTION
        "An entry containing information applicable to a particular
        battery pack managed by this agent."
    INDEX { tlpDeviceIndex, tlpUpsBatteryPackIdentIndex }
    ::= { tlpUpsBatteryPackIdentTable 1 }

TlpUpsBatteryIdentEntry ::= SEQUENCE {
    tlpUpsBatteryPackIdentIndex             Unsigned32,
    tlpUpsBatteryPackIdentManufacturer      DisplayString,
    tlpUpsBatteryPackIdentModel             DisplayString,
    tlpUpsBatteryPackIdentSerialNum         DisplayString,
    tlpUpsBatteryPackIdentFirmware          DisplayString,
    tlpUpsBatteryPackIdentSKU               DisplayString }

tlpUpsBatteryPackIdentIndex OBJECT-TYPE
    SYNTAX Unsigned32
    MAX-ACCESS read-only
    STATUS current
    DESCRIPTION
        "The table row index for the ups battery pack."
    ::= { tlpUpsBatteryPackIdentEntry 1 }

tlpUpsBatteryPackIdentManufacturer OBJECT-TYPE
    SYNTAX DisplayString
    MAX-ACCESS read-only
    STATUS current
    DESCRIPTION
        "The manufacturer of the battery pack. If the device does not
        support this value, then the agent reports ERROR_NO_SUCH_NAME." 
    ::= { tlpUpsBatteryPackIdentEntry 2 }

tlpUpsBatteryPackIdentModel OBJECT-TYPE
    SYNTAX DisplayString
    MAX-ACCESS read-only
    STATUS current
    DESCRIPTION
        "The model or device name of the battery pack. If the device does not
        support this value, then the agent reports ERROR_NO_SUCH_NAME." 
    ::= { tlpUpsBatteryPackIdentEntry 3 }

tlpUpsBatteryPackIdentSerialNum OBJECT-TYPE
    SYNTAX DisplayString
    MAX-ACCESS read-only
    STATUS current
    DESCRIPTION
        "The serial number of the battery pack. If the device does not support
        this value, then the agent reports ERROR_NO_SUCH_NAME." 
    ::= { tlpUpsBatteryPackIdentEntry 4 }

tlpUpsBatteryPackIdentFirmware OBJECT-TYPE
    SYNTAX DisplayString
    MAX-ACCESS read-only
    STATUS current
    DESCRIPTION
        "The firmware of the battery pack. If the device does not support this
        value, then the agent reports ERROR_NO_SUCH_NAME." 
    ::= { tlpUpsBatteryPackIdentEntry 5 }

tlpUpsBatteryPackIdentSKU OBJECT-TYPE
    SYNTAX DisplayString
    MAX-ACCESS read-only
    STATUS current
    DESCRIPTION
        "The SKU of the battery pack. If the device does not support this value,
        then the agent reports ERROR_NO_SUCH_NAME." 
    ::= { tlpUpsBatteryPackIdentEntry 6 }

tlpUpsBatteryPackConfigTable OBJECT-TYPE
    SYNTAX SEQUENCE OF TlpUpsBatteryConfigEntry
    MAX-ACCESS not-accessible
    STATUS current
    DESCRIPTION
        "The battery configuration details for each ups in the device
        table. This is a sparse dependent table, and will contain the
        number of entries based upon the number of upss managed by the
        agent as reported by upsIdentNumUps and the number of battery
        battery packs per each as reported by tlpUpsNumBatteryPacks."
    ::= { tlpUpsBattery 4 }

tlpUpsBatteryPackConfigEntry OBJECT-TYPE
    SYNTAX TlpUpsBatteryConfigEntry
    MAX-ACCESS not-accessible
    STATUS current
    DESCRIPTION
        "An entry containing information applicable to a particular
        battery pack managed by this agent."
    INDEX { tlpDeviceIndex, tlpUpsBatteryPackIdentIndex }
    ::= { tlpUpsBatteryPackConfigTable 1 }

TlpUpsBatteryConfigEntry ::= SEQUENCE {
    tlpUpsBatteryPackConfigChemistry            INTEGER,
    tlpUpsBatteryPackConfigStyle                INTEGER,
    tlpUpsBatteryPackConfigLocation             INTEGER,
    tlpUpsBatteryPackConfigStrings              Unsigned32,
    tlpUpsBatteryPackConfigBatteriesPerString   Unsigned32,
    tlpUpsBatteryPackConfigCellsPerBattery      INTEGER,
    tlpUpsBatteryPackConfigNumBatteries         Unsigned32,
    tlpUpsBatteryPackConfigCapacityUnits        INTEGER,
    tlpUpsBatteryPackConfigDesignCapacity       Unsigned32,
    tlpUpsBatteryPackConfigCellCapacity         Unsigned32,
    tlpUpsBatteryPackConfigMinCellVoltage       Unsigned32,
    tlpUpsBatteryPackConfigMaxCellVoltage       Unsigned32 }

tlpUpsBatteryPackConfigChemistry OBJECT-TYPE
    SYNTAX INTEGER {
        unknown(0),
        leadAcid(1),
        nickelCadmium(2),
        lithiumIon(3) }
    MAX-ACCESS read-only
    STATUS current
    DESCRIPTION
        "The type of battery pack."
    ::= { tlpUpsBatteryPackConfigEntry 1 }

tlpUpsBatteryPackConfigStyle OBJECT-TYPE
    SYNTAX INTEGER {
        unknown(0),
        nonsmart(1),
        smart(2),
        bms(3) }
    MAX-ACCESS read-only
    STATUS current
    DESCRIPTION
        "The style of battery pack."
    ::= { tlpUpsBatteryPackConfigEntry 2 }

tlpUpsBatteryPackConfigLocation OBJECT-TYPE
    SYNTAX INTEGER {
        unknown(0),
        internal(1),
        external(2) }
    MAX-ACCESS read-only
    STATUS current
    DESCRIPTION
        "The location of the battery pack."
    ::= { tlpUpsBatteryPackConfigEntry 3 }

tlpUpsBatteryPackConfigStrings OBJECT-TYPE
    SYNTAX Unsigned32
    MAX-ACCESS read-only
    STATUS current
    DESCRIPTION
        "The number of series strings in parallel contained in the battery
        pack. If the device does not support this value, then the agent will
        report ERROR_NO_SUCH_NAME."
    ::= { tlpUpsBatteryPackConfigEntry 4 }

tlpUpsBatteryPackConfigBatteriesPerString OBJECT-TYPE
    SYNTAX Unsigned32
    MAX-ACCESS read-only
    STATUS current
    DESCRIPTION
        "The number of battery per each string in the battery pack. If the
        device does not support this value, then the agent will report
        ERROR_NO_SUCH_NAME."
    ::= { tlpUpsBatteryPackConfigEntry 5 }

tlpUpsBatteryPackConfigCellsPerBattery OBJECT-TYPE
    SYNTAX INTEGER {
        unknown(0),
        one(1),
        two(2),
        four(4),
        six(6) }
    MAX-ACCESS read-only
    STATUS current
    DESCRIPTION
        "The number of cells per battery.."
    ::= { tlpUpsBatteryPackConfigEntry 6 }

tlpUpsBatteryPackConfigNumBatteries OBJECT-TYPE
    SYNTAX Unsigned32
    MAX-ACCESS read-only
    STATUS current
    DESCRIPTION
        "The total number of batteries contained in the battery pack. If the device
        does not support this value, then the agent will report ERROR_NO_SUCH_NAME."
    ::= { tlpUpsBatteryPackConfigEntry 7 }

tlpUpsBatteryPackConfigCapacityUnits OBJECT-TYPE
    SYNTAX INTEGER {
        mAHr(0),
        mWHr(1) }
    MAX-ACCESS read-only
    STATUS current
    DESCRIPTION
        "The units of measurement used for tlpUpsBatteryPackConfigDesignCapacity and
        tlpUpsBatteryPackConfigCellCapacity. If supported, this value will report either
        mAHR(1), amps per hour, or mWhr(1), watts per hour. If the device does not
        support this value, then the agent will report ERROR_NO_SUCH_NAME."
    ::= { tlpUpsBatteryPackConfigEntry 8 }

tlpUpsBatteryPackConfigDesignCapacity OBJECT-TYPE
    SYNTAX Unsigned32
    MAX-ACCESS read-only
    STATUS current
    DESCRIPTION
        "The theoretical or nominal capacity of the battery pack in the measurement
        defined by tlpUpsBatteryPackConfigCapacityUnits. If the device does not support
        this value, then the agent will report ERROR_NO_SUCH_NAME."
    ::= { tlpUpsBatteryPackConfigEntry 9 }

tlpUpsBatteryPackConfigCellCapacity OBJECT-TYPE
    SYNTAX Unsigned32
    MAX-ACCESS read-only
    STATUS current
    DESCRIPTION
        "The capacity of the batteries in the measurement defined by
        tlpUpsBatteryPackConfigCapacityUnits. If the device does not support this value,
        then the agent will report ERROR_NO_SUCH_NAME."
    ::= { tlpUpsBatteryPackConfigEntry 10 }

tlpUpsBatteryPackConfigMinCellVoltage OBJECT-TYPE
    SYNTAX Unsigned32
    MAX-ACCESS read-only
    STATUS current
    DESCRIPTION
        "The minimum cell voltage for the batteries. If the device does not support
        this value, then the agent will report ERROR_NO_SUCH_NAME."
    ::= { tlpUpsBatteryPackConfigEntry 11 }

tlpUpsBatteryPackConfigMaxCellVoltage OBJECT-TYPE
    SYNTAX Unsigned32
    MAX-ACCESS read-only
    STATUS current
    DESCRIPTION
        "The maximum cell voltage for the batteries. If the device does not support
        this value, then the agent will report ERROR_NO_SUCH_NAME."
    ::= { tlpUpsBatteryPackConfigEntry 12 }

tlpUpsBatteryPackDetailTable OBJECT-TYPE
    SYNTAX SEQUENCE OF TlpUpsBatteryPackDetailEntry
    MAX-ACCESS not-accessible
    STATUS current
    DESCRIPTION
        "The details of each battery pack for each ups in the device
        table. This is a sparse dependent table, and will contain the
        number of entries based upon the number of upss and battery
        packs managed by the agent as reported by tlpUpsIdentNumUps
        and tlpUpsIdentNumBatteryPacks."
    ::= { tlpUpsBattery 5 }

tlpUpsBatteryPackDetailEntry OBJECT-TYPE
    SYNTAX TlpUpsBatteryPackDetailEntry
    MAX-ACCESS not-accessible
    STATUS current
    DESCRIPTION
        "An entry containing information applicable to a particular
        battery system managed by this agent."
    INDEX { tlpDeviceIndex, tlpUpsBatteryPackIdentIndex }
    ::= { tlpUpsBatteryPackDetailTable 1 }

TlpUpsBatteryPackDetailEntry ::= SEQUENCE {
    tlpUpsBatteryPackDetailCondition            INTEGER,
    tlpUpsBatteryPackDetailTemperatureC         Unsigned32,
    tlpUpsBatteryPackDetailTemperatureF         Unsigned32,
    tlpUpsBatteryPackDetailAge                  Unsigned32,
    tlpUpsBatteryPackDetailLastReplaceDate      DisplayString,
    tlpUpsBatteryPackDetailNextReplaceDate      DisplayString,
    tlpUpsBatteryPackDetailCycleCount           Unsigned32 }

tlpUpsBatteryPackDetailCondition OBJECT-TYPE
    SYNTAX INTEGER {
        unknown(0),
        good(1),
        weak(2),
        bad(3) }
    MAX-ACCESS read-only
    STATUS current
    DESCRIPTION
        "The condition of the battery. A bad battery should be replaced."
    ::= { tlpUpsBatteryPackDetailEntry 1 }

tlpUpsBatteryPackDetailTemperatureC OBJECT-TYPE
    SYNTAX Unsigned32
    UNITS "degrees Centigrade"
    MAX-ACCESS read-only
    STATUS current
    DESCRIPTION
        "The ambient temperature at or near the UPS Battery casing."
    ::= { tlpUpsBatteryPackDetailEntry 2 }

tlpUpsBatteryPackDetailTemperatureF OBJECT-TYPE
    SYNTAX Unsigned32
    UNITS "0.1 degrees Farenheit"
    MAX-ACCESS read-only
    STATUS current
    DESCRIPTION
        "The ambient temperature at or near the UPS Battery casing."
    ::= { tlpUpsBatteryPackDetailEntry 3 }

tlpUpsBatteryPackDetailAge OBJECT-TYPE
    SYNTAX Unsigned32
    UNITS "0.1 Years"
    MAX-ACCESS read-only
    STATUS current
    DESCRIPTION
        "The age of the battery in years. This is equal to the current
        date minus tlpUpsBatteryPackIdentInstallDate."
    ::= { tlpUpsBatteryPackDetailEntry 4 }

tlpUpsBatteryPackDetailLastReplaceDate OBJECT-TYPE
    SYNTAX DisplayString
    MAX-ACCESS read-write
    STATUS current
    DESCRIPTION
        "The date when the batteries were last replaced in YYYYMMDD format." 
    ::= { tlpUpsBatteryPackDetailEntry 5 }

tlpUpsBatteryPackDetailNextReplaceDate OBJECT-TYPE
    SYNTAX DisplayString
    MAX-ACCESS read-only
    STATUS current
    DESCRIPTION
        "The date when the batteries should next be replaced in YYYYMMDD
        format."
    ::= { tlpUpsBatteryPackDetailEntry 6 }

tlpUpsBatteryPackDetailCycleCount OBJECT-TYPE
    SYNTAX Unsigned32
    MAX-ACCESS read-only
    STATUS current
    DESCRIPTION
        "The number of times the battery went into invert mode. This number
        is incremented by 1 each time the unit goes on battery mode (with
        the exception of Self Test mode). If the device does not support this
        value, then the agent will report ERROR_NO_SUCH_NAME."
    ::= { tlpUpsBatteryPackDetailEntry 7 }

tlpUpsInputTable OBJECT-TYPE
    SYNTAX SEQUENCE OF TlpUpsInputEntry
    MAX-ACCESS not-accessible
    STATUS current
    DESCRIPTION
        "The input details of each ups in the device table. This is
        a sparse dependent table, and will contain the number of entries
        based upon the number of upss managed by the agent as reported
        by tlpUpsIdentNumUps."
    ::= { tlpUpsInput 1 }

tlpUpsInputEntry OBJECT-TYPE
    SYNTAX TlpUpsInputEntry
    MAX-ACCESS not-accessible
    STATUS current
    DESCRIPTION
        "An entry containing information applicable to all input lines per
        each ups managed by this agent."
    INDEX { tlpDeviceIndex }
    ::= { tlpUpsInputTable 1 }

TlpUpsInputEntry ::= SEQUENCE {
    tlpUpsInputLineBads                         INTEGER,
    tlpUpsInputNominalVoltage                   Unsigned32,
    tlpUpsInputNominalFrequency                 Unsigned32,
    tlpUpsInputLowTransferVoltage               Unsigned32,
    tlpUpsInputLowTransferVoltageLowerBound     Unsigned32,
    tlpUpsInputLowTransferVoltageUpperBound     Unsigned32,
    tlpUpsInputHighTransferVoltage              Unsigned32,
    tlpUpsInputHighTransferVoltageLowerBound    Unsigned32,
    tlpUpsInputHighTransferVoltageUpperBound    Unsigned32 }

tlpUpsInputLineBads OBJECT-TYPE
    SYNTAX INTEGER
    MAX-ACCESS read-only
    STATUS current
    DESCRIPTION
        "A count of the number of times the input entered an out-of-tolerance
        condition as defined by the manufacturer.  This count is incremented
        by one each time the input transitions from zero out-of-tolerance
        lines to one or more input lines out-of-tolerance. This value is not
        supported on all units. If the ups does not support this value, then
        the agent reports ERROR_NO_SUCH_NAME."
    ::= { tlpUpsInputEntry 1 }

tlpUpsInputNominalVoltage OBJECT-TYPE
    SYNTAX Unsigned32
    MAX-ACCESS read-only
    STATUS current
    DESCRIPTION
        "The nominal value of the input line voltage. This value may not
        be supported on all models. If not supported, this value will return
        ERROR_NO_SUCH_NAME."
    ::= { tlpUpsInputEntry 2 }

tlpUpsInputNominalFrequency OBJECT-TYPE
    SYNTAX Unsigned32
    MAX-ACCESS read-only
    STATUS current
    DESCRIPTION
        "The nominal value of the input line frequency. This value may not
        be supported on all models. If not supported, this value will return
        ERROR_NO_SUCH_NAME."
    ::= { tlpUpsInputEntry 3 }

tlpUpsInputLowTransferVoltage OBJECT-TYPE
    SYNTAX Unsigned32
    UNITS "0.1 Volts"
    MAX-ACCESS read-only
    STATUS current
    DESCRIPTION
        "The minimum line voltage allowed before the ups system transfers to
         battery backup."
    ::= { tlpUpsInputEntry 4 }

tlpUpsInputLowTransferVoltageLowerBound OBJECT-TYPE
    SYNTAX Unsigned32
    UNITS "0.1 Volts"
    MAX-ACCESS read-only
    STATUS current
    DESCRIPTION
        "The lower boundary value of tlpUpsInputLowTransferVoltage as dictated
        by the hardware of the unit."
    ::= { tlpUpsInputEntry 5 }

tlpUpsInputLowTransferVoltageUpperBound OBJECT-TYPE
    SYNTAX Unsigned32
    UNITS "0.1 Volts"
    MAX-ACCESS read-only
    STATUS current
    DESCRIPTION
        "The upper boundary value of tlpUpsInputLowTransferVoltage as dictated
        by the hardware of the unit."
    ::= { tlpUpsInputEntry 6 }

tlpUpsInputHighTransferVoltage OBJECT-TYPE
    SYNTAX Unsigned32
    UNITS "0.1 Volts"
    MAX-ACCESS read-only
    STATUS current
    DESCRIPTION
        "The maximum line voltage allowed before the ups system transfers to
        battery backup."
    ::= { tlpUpsInputEntry 7 }

tlpUpsInputHighTransferVoltageLowerBound OBJECT-TYPE
    SYNTAX Unsigned32
    UNITS "0.1 Volts"
    MAX-ACCESS read-only
    STATUS current
    DESCRIPTION
        "The lower boundary value of tlpUpsInputHighTransferVoltage as dictated
        by the hardware of the unit."
    ::= { tlpUpsInputEntry 8 }

tlpUpsInputHighTransferVoltageUpperBound OBJECT-TYPE
    SYNTAX Unsigned32
    UNITS "0.1 Volts"
    MAX-ACCESS read-only
    STATUS current
    DESCRIPTION
        "The upper boundary value of tlpUpsInputHighTransferVoltage as dictated
        by the hardware of the unit."
    ::= { tlpUpsInputEntry 9 }

tlpUpsInputPhaseTable OBJECT-TYPE
    SYNTAX SEQUENCE OF TlpUpsInputPhaseEntry
    MAX-ACCESS not-accessible
    STATUS current
    DESCRIPTION
        "The input phase details of each ups in the device table. This is
        a sparse dependent table, and will contain the number of entries
        based upon the number of upss managed by the agent as reported
        by tlpUpsIdentNumUps and tlpUpsIdentNumPhases."
    ::= { tlpUpsInput 2 }

tlpUpsInputPhaseEntry OBJECT-TYPE
    SYNTAX TlpUpsInputPhaseEntry
    MAX-ACCESS not-accessible
    STATUS current
    DESCRIPTION
        "An entry containing information applicable to a particular
        input phase managed by this agent."
    INDEX { tlpDeviceIndex, tlpUpsInputPhaseIndex }
    ::= { tlpUpsInputPhaseTable 1 }

TlpUpsInputPhaseEntry ::= SEQUENCE {
    tlpUpsInputPhaseIndex            Unsigned32,
    tlpUpsInputPhaseFrequency        Unsigned32,
    tlpUpsInputPhaseVoltage          Unsigned32,
    tlpUpsInputPhaseVoltageMin       Unsigned32,
    tlpUpsInputPhaseVoltageMax       Unsigned32,
    tlpUpsInputPhaseCurrent          Unsigned32,
    tlpUpsInputPhasePower            Unsigned32 }

tlpUpsInputPhaseIndex OBJECT-TYPE
    SYNTAX Unsigned32
    MAX-ACCESS read-only
    STATUS current
    DESCRIPTION
        "The table row index for the ups input phase."
    ::= { tlpUpsInputPhaseEntry 1 }

tlpUpsInputPhaseFrequency OBJECT-TYPE
    SYNTAX Unsigned32
    UNITS "0.1 Hertz"
    MAX-ACCESS read-only
    STATUS current
    DESCRIPTION
        "The present input frequency for a given input line."
    ::= { tlpUpsInputPhaseEntry 2 }

tlpUpsInputPhaseVoltage OBJECT-TYPE
    SYNTAX Unsigned32
    UNITS "0.1 Volt DC"
    MAX-ACCESS read-only
    STATUS current
    DESCRIPTION
        "The magnitude of the present input voltage for a given input line."
    ::= { tlpUpsInputPhaseEntry 3 }

tlpUpsInputPhaseVoltageMin OBJECT-TYPE
    SYNTAX Unsigned32
    UNITS "0.1 Volt DC"
    MAX-ACCESS read-write
    STATUS current
    DESCRIPTION
        "The minimum input voltage value since the last reset of this
        value for a given input line. If any value is written to either
        tlpUpsInputVoltageMin or tlpUpsInputVoltageMax, both will be reset to
        their appropriate minimum and maximum values."
    ::= { tlpUpsInputPhaseEntry 4 }

tlpUpsInputPhaseVoltageMax OBJECT-TYPE
    SYNTAX Unsigned32
    UNITS "0.1 Volt DC"
    MAX-ACCESS read-write
    STATUS current
    DESCRIPTION
        "The maximum input voltage value since the last reset of this
        value for a given input line. If any value is written to either
        tlpUpsInputVoltageMin or tlpUpsInputVoltageMax, both will be reset to
        their appropriate minimum and maximum values."
    ::= { tlpUpsInputPhaseEntry 5 }

tlpUpsInputPhaseCurrent OBJECT-TYPE
    SYNTAX Unsigned32
    UNITS "0.01 Amp DC"
    MAX-ACCESS read-only
    STATUS current
    DESCRIPTION
        "The magnitude of the present input current."
    ::= { tlpUpsInputPhaseEntry 6 }

tlpUpsInputPhasePower OBJECT-TYPE
    SYNTAX Unsigned32
    UNITS "Watts"
    MAX-ACCESS read-only
    STATUS current
    DESCRIPTION
        "The magnitude of the present input true power."
    ::= { tlpUpsInputPhaseEntry 7 }

tlpUpsOutputTable OBJECT-TYPE
    SYNTAX SEQUENCE OF TlpUpsOutputEntry
    MAX-ACCESS not-accessible
    STATUS current
    DESCRIPTION
        "The output details of each ups in the device table. This is a sparse
        dependent table, and will contain the number of entries based upon the
        number of upss managed by the agent as reported by tlpUpsIdentNumUps."
    ::= { tlpUpsOutput 1 }

tlpUpsOutputEntry OBJECT-TYPE
    SYNTAX TlpUpsOutputEntry
    MAX-ACCESS not-accessible
    STATUS current
    DESCRIPTION
        "An entry containing information applicable to a particular
        output line managed by this agent."
    INDEX { tlpDeviceIndex }
    ::= { tlpUpsOutputTable 1 }

TlpUpsOutputEntry ::= SEQUENCE {
    tlpUpsOutputSource              INTEGER,
    tlpUpsOutputNominalVoltage      Unsigned32,
    tlpUpsOutputFrequency           Unsigned32 }

tlpUpsOutputSource OBJECT-TYPE
    SYNTAX INTEGER {
        unknown(0),
        other(1),
        none(2),
        normal(3),
        bypass(4),
        battery(5),
        boosting(6),
        reducing(7),
        second(8),
        economy(9) }
    MAX-ACCESS read-only
    STATUS current
    DESCRIPTION
        "The present source of output power. The enumeration none(2)
        indicates that there is no source of output power (and
        therefore no output power), for example, the system has opened
        the output breaker."
    ::= { tlpUpsOutputEntry 1 }

tlpUpsOutputNominalVoltage OBJECT-TYPE
    SYNTAX Unsigned32
    MAX-ACCESS read-only
    STATUS current
    DESCRIPTION
        "The nominal value of the output voltage. This value may not be
        supported on all models. If not supported, the agent reports
        ERROR_NO_SUCH_NAME."
    ::= { tlpUpsOutputEntry 2 }

tlpUpsOutputFrequency OBJECT-TYPE
    SYNTAX Unsigned32
    UNITS "0.1 Hertz"
    MAX-ACCESS read-only
    STATUS current
    DESCRIPTION
        "The present output frequency. The output frequency on most ups
        devices is common across all output lines. Some ups devices, however,
        maintain the output frequency per each line. If a common frequency is
        supported by the ups, then this frequency will contain the common
        frequency value. If not supported, the agent reports ERROR_NO_SUCH_NAME."
    ::= { tlpUpsOutputEntry 3 }

tlpUpsOutputLineTable OBJECT-TYPE
    SYNTAX SEQUENCE OF TlpUpsOutputLineEntry
    MAX-ACCESS not-accessible
    STATUS current
    DESCRIPTION
        "The output line details of each ups in the device table. This is
        a sparse dependent table, and will contain the number of entries
        based upon the number of upss managed by the agent as reported
        by tlpUpsIdentNumUps."
    ::= { tlpUpsOutput 2 }

tlpUpsOutputLineEntry OBJECT-TYPE
    SYNTAX TlpUpsOutputLineEntry
    MAX-ACCESS not-accessible
    STATUS current
    DESCRIPTION
        "An entry containing information applicable to a particular
        output line managed by this agent."
    INDEX { tlpDeviceIndex, tlpUpsOutputLineIndex }
    ::= { tlpUpsOutputLineTable 1 }

TlpUpsOutputLineEntry ::= SEQUENCE {
    tlpUpsOutputLineIndex           Unsigned32,
    tlpUpsOutputLineVoltage         Unsigned32,
    tlpUpsOutputLineCurrent         Unsigned32,
    tlpUpsOutputLinePower           Unsigned32,
    tlpUpsOutputLinePercentLoad     INTEGER,
    tlpUpsOutputLineFrequency       Unsigned32 }

tlpUpsOutputLineIndex OBJECT-TYPE
    SYNTAX Unsigned32
    MAX-ACCESS read-only
    STATUS current
    DESCRIPTION
        "The table row index for the ups output line."
    ::= { tlpUpsOutputLineEntry 1 }

tlpUpsOutputLineVoltage OBJECT-TYPE
    SYNTAX Unsigned32
    UNITS "0.1 Volt DC"
    MAX-ACCESS read-only
    STATUS current
    DESCRIPTION
        "The magnitude of the present output voltage for a given output line."
    ::= { tlpUpsOutputLineEntry 2 }

tlpUpsOutputLineCurrent OBJECT-TYPE
    SYNTAX Unsigned32
    UNITS "0.1 Amp"
    MAX-ACCESS read-only
    STATUS current
    DESCRIPTION
        "The present output current."
    ::= { tlpUpsOutputLineEntry 3 }

tlpUpsOutputLinePower OBJECT-TYPE
    SYNTAX Unsigned32
    UNITS "Watts"
    MAX-ACCESS read-only
    STATUS current
    DESCRIPTION
        "The present output true power."
    ::= { tlpUpsOutputLineEntry 4 }

tlpUpsOutputLinePercentLoad OBJECT-TYPE
    SYNTAX INTEGER (0..200)
    UNITS "percent"
    MAX-ACCESS read-only
    STATUS current
    DESCRIPTION
        "The percentage of the UPS power capacity presently being used on
        this output line, i.e., the greater of the percent load of true
        power capacity and the percent load of VA."
    ::= { tlpUpsOutputLineEntry 5 }

tlpUpsOutputLineFrequency OBJECT-TYPE
    SYNTAX Unsigned32
    UNITS "0.1 Hertz"
    MAX-ACCESS read-only
    STATUS current
    DESCRIPTION
        "The present output frequency on this output line. The output frequency on
        most ups devices is common across all output lines. Some ups devices, however,
        maintain the output frequency per each line. If a per line frequency is
        supported by the ups, then this frequency value will reports the value of this
        line. If not supported, the agent reports ERROR_NO_SUCH_NAME."
    ::= { tlpUpsOutputLineEntry 6 }

tlpUpsBypassTable OBJECT-TYPE
    SYNTAX SEQUENCE OF TlpUpsBypassEntry
    MAX-ACCESS not-accessible
    STATUS current
    DESCRIPTION
        "The bypass details of each ups in the device table. This is a sparse
        dependent table, and will contain the number of entries based upon the
        number of upss managed by the agent as reported by tlpUpsIdentNumUps."
    ::= { tlpUpsBypass 1 }

tlpUpsBypassEntry OBJECT-TYPE
    SYNTAX TlpUpsBypassEntry
    MAX-ACCESS not-accessible
    STATUS current
    DESCRIPTION
        "An entry containing information applicable to all input lines per
        each ups managed by this agent."
    INDEX { tlpDeviceIndex }
    ::= { tlpUpsBypassTable 1 }

TlpUpsBypassEntry ::= SEQUENCE {
    tlpUpsBypassFrequency          Unsigned32 }

tlpUpsBypassFrequency OBJECT-TYPE
    SYNTAX Unsigned32
    UNITS "0.1 Hertz"
    MAX-ACCESS read-only
    STATUS current
    DESCRIPTION
        "The present bypass frequency."
    ::= { tlpUpsBypassEntry 1 }

tlpUpsBypassLineTable OBJECT-TYPE
    SYNTAX SEQUENCE OF TlpUpsBypassLineEntry
    MAX-ACCESS not-accessible
    STATUS current
    DESCRIPTION
        "The bypass line details of each ups in the device table. This is
        a sparse dependent table, and will contain the number of entries
        based upon the number of upss managed by the agent as reported
        by tlpUpsIdentNumUps."
    ::= { tlpUpsBypass 2 }

tlpUpsBypassLineEntry OBJECT-TYPE
    SYNTAX TlpUpsBypassLineEntry
    MAX-ACCESS not-accessible
    STATUS current
    DESCRIPTION
        "An entry containing information applicable to a particular
        bypass line managed by this agent."
    INDEX { tlpDeviceIndex, tlpUpsBypassLineIndex }
    ::= { tlpUpsBypassLineTable 1 }

TlpUpsBypassLineEntry ::= SEQUENCE {
    tlpUpsBypassLineIndex           Unsigned32,
    tlpUpsBypassLineVoltage         Unsigned32,
    tlpUpsBypassLineCurrent         Unsigned32,
    tlpUpsBypassLinePower           Unsigned32 }

tlpUpsBypassLineIndex OBJECT-TYPE
    SYNTAX Unsigned32
    MAX-ACCESS read-only
    STATUS current
    DESCRIPTION
        "The bypass line identifier."
    ::= { tlpUpsBypassLineEntry 1 }

tlpUpsBypassLineVoltage OBJECT-TYPE
    SYNTAX Unsigned32
    UNITS "0.1 Volt DC"
    MAX-ACCESS read-only
    STATUS current
    DESCRIPTION
        "The present bypass voltage."
    ::= { tlpUpsBypassLineEntry 2 }

tlpUpsBypassLineCurrent OBJECT-TYPE
    SYNTAX Unsigned32
    UNITS "0.1 Amp"
    MAX-ACCESS read-only
    STATUS current
    DESCRIPTION
        "The present bypass current."
    ::= { tlpUpsBypassLineEntry 3 }

tlpUpsBypassLinePower OBJECT-TYPE
    SYNTAX Unsigned32
    UNITS "Watts"
    MAX-ACCESS read-only
    STATUS current
    DESCRIPTION
        "The present true power conveyed by the bypass."
    ::= { tlpUpsBypassLineEntry 4 }

tlpUpsOutletTable OBJECT-TYPE
    SYNTAX SEQUENCE OF TlpUpsOutletEntry
    MAX-ACCESS not-accessible
    STATUS current
    DESCRIPTION
        "The details of each ups outlet in the device table. This is
        a sparse dependent table, and will contain the number of entries
        based upon the number of upss managed by the agent as reported
        by tlpUpsIdentNumUps."
    ::= { tlpUpsOutlet 1 }

tlpUpsOutletEntry OBJECT-TYPE
    SYNTAX TlpUpsOutletEntry
    MAX-ACCESS not-accessible
    STATUS current
    DESCRIPTION
        "An entry containing information applicable to a particular outlet
        managed by this agent."
    INDEX { tlpDeviceIndex, tlpUpsOutletIndex }
    ::= { tlpUpsOutletTable 1 }

TlpUpsOutletEntry ::= SEQUENCE {
    tlpUpsOutletIndex               Unsigned32,
    tlpUpsOutletName                DisplayString,
    tlpUpsOutletDescription         DisplayString,
    tlpUpsOutletState               INTEGER,
    tlpUpsOutletControllable        TruthValue,
    tlpUpsOutletCommand             INTEGER,
    tlpUpsOutletVoltage             Unsigned32,
    tlpUpsOutletCurrent             Unsigned32,
    tlpUpsOutletPower               Unsigned32,
    tlpUpsOutletRampAction          INTEGER,
    tlpUpsOutletRampDelay           Integer32,
    tlpUpsOutletShedAction          INTEGER,
    tlpUpsOutletShedDelay           Integer32,
    tlpUpsOutletGroup               Integer32 }

tlpUpsOutletIndex OBJECT-TYPE
    SYNTAX Unsigned32
    MAX-ACCESS read-only
    STATUS current
    DESCRIPTION
        "The table row index for the ups outlet."
    ::= { tlpUpsOutletEntry 1 }

tlpUpsOutletName OBJECT-TYPE
    SYNTAX DisplayString
    MAX-ACCESS read-write
    STATUS current
    DESCRIPTION
        "A user-definable string identifying the name of the outlet."
    ::= { tlpUpsOutletEntry 2 }

tlpUpsOutletDescription OBJECT-TYPE
    SYNTAX DisplayString
    MAX-ACCESS read-write
    STATUS current
    DESCRIPTION
        "A user-definable string identifying the device(s) connected to
        the given outlet."
    ::= { tlpUpsOutletEntry 3 }

tlpUpsOutletState OBJECT-TYPE
    SYNTAX INTEGER {
        unknown(0),
        off(1),
        on(2) }
    MAX-ACCESS read-only
    STATUS current
    DESCRIPTION
        "The current state of the outlet."
    ::= { tlpUpsOutletEntry 4 }

tlpUpsOutletControllable OBJECT-TYPE
    SYNTAX TruthValue
    MAX-ACCESS read-only
    STATUS current
    DESCRIPTION
        "Denotes whether this outlet is controllable."
    ::= { tlpUpsOutletEntry 5 }

tlpUpsOutletCommand OBJECT-TYPE
    SYNTAX INTEGER {
        idle(0),
        turnOff(1),
        turnOn(2),
        cycle(3) }
    MAX-ACCESS read-write
    STATUS current
    DESCRIPTION
        "Reading this value will always return 0. Setting this value
        to turnOff(1) will turn off the outlet. Setting this value
        to turnOn(2) will turn on the outlet. Setting this value to
        cycle(3) will turn the outlet off, then turn it back on."
    ::= { tlpUpsOutletEntry 6 }

tlpUpsOutletVoltage OBJECT-TYPE
    SYNTAX Unsigned32
    UNITS "0.1 Volt DC"
    MAX-ACCESS read-only
    STATUS current
    DESCRIPTION
        "The magnitude of the present output voltage for a given outlet.
        If the voltage measurement is not supported for an individual
        receptacle regardless whether device-wide or just for this
        receptacle, then this value will always return ERROR_NO_SUCH_NAME.
        Device-wide support for receptacle voltage measurements is denoted
        by tlpUpsSupportsOutletVoltage."
    ::= { tlpUpsOutletEntry 7 }

tlpUpsOutletCurrent OBJECT-TYPE
    SYNTAX Unsigned32
    UNITS "0.01 RMS Amp"
    MAX-ACCESS read-only
    STATUS current
    DESCRIPTION
        "The present output current, in hundreths of amps, of a given outlet.
        If the current measurement is not supported for an individual
        receptacle regardless whether device-wide or just for this
        receptacle, then this value will always return ERROR_NO_SUCH_NAME.
        Device-wide support for receptacle current measurements is denoted
        by tlpUpsSupportsCurrentPower."
    ::= { tlpUpsOutletEntry 8 }

tlpUpsOutletPower OBJECT-TYPE
    SYNTAX Unsigned32
    UNITS "Watts"
    MAX-ACCESS read-only
    STATUS current
    DESCRIPTION
        "The output power of a given outlet. If the power measurement is
        not supported for an individual receptacle regardless whether
        device-wide or just for this receptacle, then this value will
        always return ERROR_NO_SUCH_NAME. Device-wide support for receptacle
        power measurements is denoted by tlpUpsSupportsCurrentPower."
    ::= { tlpUpsOutletEntry 9 }

tlpUpsOutletRampAction OBJECT-TYPE
    SYNTAX INTEGER {
        remainOff(0),
        turnOnAfterDelay(1) }
    MAX-ACCESS read-write
    STATUS current
    DESCRIPTION
        "The ramp action to take on a given outlet when powering on the
        device. If this receptacle is not controllable, as denoted by
        tlpUpsOutletControllable, then this value will always return
        ERROR_NO_SUCH_NAME."
    ::= { tlpUpsOutletEntry 10 }

tlpUpsOutletRampDelay OBJECT-TYPE
    SYNTAX Integer32
    UNITS "seconds"
    MAX-ACCESS read-write
    STATUS current
    DESCRIPTION
        "The number of seconds to delay before powering on the given outlet.
        If this receptacle is not controllable, as denoted by
        tlpUpsOutletControllable, then this value will always return
        ERROR_NO_SUCH_NAME."
    ::= { tlpUpsOutletEntry 11 }

tlpUpsOutletShedAction OBJECT-TYPE
    SYNTAX INTEGER {
        remainOn(0),
        turnOffAfterDelay(1) }
    MAX-ACCESS read-write
    STATUS current
    DESCRIPTION
        "The shed action to take on a given outlet when powering off the
        device. If this receptacle is not controllable, as denoted by
        tlpUpsOutletControllable, then this value will always return
        ERROR_NO_SUCH_NAME."
    ::= { tlpUpsOutletEntry 12 }

tlpUpsOutletShedDelay OBJECT-TYPE
    SYNTAX Integer32
    UNITS "seconds"
    MAX-ACCESS read-write
    STATUS current
    DESCRIPTION
        "The number of seconds to delay before powering off the given outlet.
        If this receptacle is not controllable, as denoted by
        tlpUpsOutletControllable, then this value will always return
        ERROR_NO_SUCH_NAME."
    ::= { tlpUpsOutletEntry 13 }

tlpUpsOutletGroup OBJECT-TYPE
    SYNTAX Integer32
    MAX-ACCESS read-write
    STATUS current
    DESCRIPTION
        "The tlpUpsOutletGroupIndex group index of the respective group to
        which the given outlet is assigned, or zero (0) if the given
        outlet is not grouped."
    ::= { tlpUpsOutletEntry 14 }

tlpUpsOutletGroupTable OBJECT-TYPE
    SYNTAX SEQUENCE OF TlpUpsOutletGroupEntry
    MAX-ACCESS not-accessible
    STATUS current
    DESCRIPTION
        "The receptacle grouping details of each ups in device table.
        This is a sparse dependent table, and will contain the number
        of entries based upon the value of tlpUpsIdentNumOutletGroups per
        each device."
    ::= { tlpUpsOutlet 2 }

tlpUpsOutletGroupEntry OBJECT-TYPE
    SYNTAX TlpUpsOutletGroupEntry
    MAX-ACCESS not-accessible
    STATUS current
    DESCRIPTION
        "An entry containing information applicable to a particular outlet
        group managed by this agent."
    INDEX { tlpDeviceIndex, tlpUpsOutletGroupIndex }
    ::= { tlpUpsOutletGroupTable 1 }

TlpUpsOutletGroupEntry ::= SEQUENCE {
    tlpUpsOutletGroupIndex              Unsigned32,
    tlpUpsOutletGroupRowStatus	        RowStatus,
    tlpUpsOutletGroupName               DisplayString,
    tlpUpsOutletGroupDescription        DisplayString,
    tlpUpsOutletGroupState              INTEGER,
    tlpUpsOutletGroupCommand            INTEGER }

tlpUpsOutletGroupIndex OBJECT-TYPE
    SYNTAX Unsigned32
    MAX-ACCESS read-only
    STATUS current
    DESCRIPTION
        "The table row index for the ups outlet group."
    ::= { tlpUpsOutletGroupEntry 1 }

tlpUpsOutletGroupRowStatus OBJECT-TYPE
    SYNTAX RowStatus
    MAX-ACCESS read-write
    STATUS current
    DESCRIPTION
        "Row status for the tlpUpsOutletGroupTable"
    ::= { tlpUpsOutletGroupEntry 2 }

tlpUpsOutletGroupName OBJECT-TYPE
    SYNTAX DisplayString
    MAX-ACCESS read-write
    STATUS current
    DESCRIPTION
        "The name of this outlet group."
    ::= { tlpUpsOutletGroupEntry 3 }

tlpUpsOutletGroupDescription OBJECT-TYPE
    SYNTAX DisplayString
    MAX-ACCESS read-write
    STATUS current
    DESCRIPTION
        "A description for this outlet group."
    ::= { tlpUpsOutletGroupEntry 4 }

tlpUpsOutletGroupState OBJECT-TYPE
    SYNTAX INTEGER {
        unknown(0),
        off(1),
        on(2),
        mixed(3) }
    MAX-ACCESS read-only
    STATUS current
    DESCRIPTION
        "The current state of the outlet group. This value will report
        off(1) if all outlets in the group are off, on(2) if all outlets
        in the group are on, mixed(3) if some outlets in the group are
        off and others are on, or unknown(0) if the state of the outlets
        cannot be determined."
    ::= { tlpUpsOutletGroupEntry 5 }

tlpUpsOutletGroupCommand OBJECT-TYPE
    SYNTAX INTEGER {
        idle(0),
        turnOff(1),
        turnOn(2),
        cycle(3) }
    MAX-ACCESS read-write
    STATUS current
    DESCRIPTION
        "Reading this value will always return 0. Setting this value to
        turnOff(1) will turn off every outlet associated with the group.
        Setting this value to turnOn(2) will turn on every outlet associated
        with the group. Setting this value to cycle(3) will turn off every
        outlet associated with the group, then turn each outlet back on."
    ::= { tlpUpsOutletGroupEntry 6 }

tlpUpsWatchdogTable OBJECT-TYPE
    SYNTAX SEQUENCE OF TlpUpsWatchdogEntry
    MAX-ACCESS not-accessible
    STATUS current
    DESCRIPTION
        "The watchdog details of each ups in device table. This is a
        sparse dependent table, and will contain some subset of devices
        that are upss."
    ::= { tlpUpsWatchdog 1 }

tlpUpsWatchdogEntry OBJECT-TYPE
    SYNTAX TlpUpsWatchdogEntry
    MAX-ACCESS not-accessible
    STATUS current
    DESCRIPTION
        "An entry containing watchdog details for a particular ups."
    INDEX { tlpDeviceIndex }
    ::= { tlpUpsWatchdogTable 1 }

TlpUpsWatchdogEntry ::= SEQUENCE {
    tlpUpsWatchdogSupported              TruthValue,
    tlpUpsWatchdogSecsBeforeReboot       Unsigned32 }

tlpUpsWatchdogSupported OBJECT-TYPE
    SYNTAX TruthValue
    MAX-ACCESS read-only
    STATUS current
    DESCRIPTION
        "Indicates whether or not this ups supports a watchdog reboot."
    ::= { tlpUpsWatchdogEntry 1 }

tlpUpsWatchdogSecsBeforeReboot OBJECT-TYPE
    SYNTAX Unsigned32
    MAX-ACCESS read-write
    STATUS current
    DESCRIPTION
        "The maximum number of seconds that can expire between polls that
        the engine makes to the ups for data.  If this time runs out, then
        the ups will cycle its outputs.  Set this to zero to turns disable
        this feature."
    ::= { tlpUpsWatchdogEntry 2 }

tlpUpsControlTable OBJECT-TYPE
    SYNTAX SEQUENCE OF TlpUpsControlEntry
    MAX-ACCESS not-accessible
    STATUS current
    DESCRIPTION
        "The actionable controls for each ups in device table. This is a
        sparse dependent table, and will contain some subset of devices
        that are upss."
    ::= { tlpUpsControl 1 }

tlpUpsControlEntry OBJECT-TYPE
    SYNTAX TlpUpsControlEntry
    MAX-ACCESS not-accessible
    STATUS current
    DESCRIPTION
        "An entry containing controls for a particular ups."
    INDEX { tlpDeviceIndex }
    ::= { tlpUpsControlTable 1 }

TlpUpsControlEntry ::= SEQUENCE {
    tlpUpsControlSelfTest       TruthValue,
    tlpUpsControlRamp           TruthValue,
    tlpUpsControlShed           TruthValue,
    tlpUpsControlUpsOn          TruthValue,
    tlpUpsControlUpsOff         TruthValue,
    tlpUpsControlUpsReboot      TruthValue,
    tlpUpsControlBypass         INTEGER }

tlpUpsControlSelfTest OBJECT-TYPE
    SYNTAX TruthValue
    MAX-ACCESS read-write
    STATUS current
    DESCRIPTION
        "Set to TRUE to initiate a self test on the ups."
    ::= { tlpUpsControlEntry 1 }
  
tlpUpsControlRamp OBJECT-TYPE
    SYNTAX TruthValue
    MAX-ACCESS read-write
    STATUS current
    DESCRIPTION
        "Set to TRUE to initiate the pre-designated ramp
        sequence on the ups."
    ::= { tlpUpsControlEntry 2 }
  
tlpUpsControlShed OBJECT-TYPE
    SYNTAX TruthValue
    MAX-ACCESS read-write
    STATUS current
    DESCRIPTION
        "Set to TRUE to initiate the pre-designated shed
        sequence on the ups."
    ::= { tlpUpsControlEntry 3 }
  
tlpUpsControlUpsOn OBJECT-TYPE
    SYNTAX TruthValue
    MAX-ACCESS read-write
    STATUS current
    DESCRIPTION
        "Set to TRUE to turn the ups on."
    ::= { tlpUpsControlEntry 4 }

tlpUpsControlUpsOff OBJECT-TYPE
    SYNTAX TruthValue
    MAX-ACCESS read-write
    STATUS current
    DESCRIPTION
        "Set to TRUE to turn the ups off."
    ::= { tlpUpsControlEntry 5 }

tlpUpsControlUpsReboot OBJECT-TYPE
    SYNTAX TruthValue
    MAX-ACCESS read-write
    STATUS current
    DESCRIPTION
        "Set to TRUE to reboot the ups."
    ::= { tlpUpsControlEntry 6 }

tlpUpsControlBypass OBJECT-TYPE
    SYNTAX INTEGER {
        disable(0),
        enable(1) }
    MAX-ACCESS read-write
    STATUS current
    DESCRIPTION
        "This switches the ups in and out of bypass mode. This value returns
        the current bypass mode: disable(0) if the ups is not in bypass mode,
        enable(1) if the ups is in bypass mode. Set to disable(0) to exit
        bypass mode, or enable(1) to enter bypass mode. If switching bypass
        mode is not supported, this value will return ERROR_NO_SUCH_NAME."
    ::= { tlpUpsControlEntry 7 }

tlpUpsConfigTable OBJECT-TYPE
    SYNTAX SEQUENCE OF TlpUpsConfigEntry
    MAX-ACCESS not-accessible
    STATUS current
    DESCRIPTION
        "The configuration details of each ups in the device table. This is
        a sparse dependent table, and will contain the number of entries
        based upon the number of upss managed by the agent as reported by
        tlpUpsIdentNumUps."
    ::= { tlpUpsConfig 1 }

tlpUpsConfigEntry OBJECT-TYPE
    SYNTAX TlpUpsConfigEntry
    MAX-ACCESS not-accessible
    STATUS current
    DESCRIPTION
        "An entry containing information applicable to all input lines per
        each ups managed by this agent."
    INDEX { tlpDeviceIndex }
    ::= { tlpUpsConfigTable 1 }

TlpUpsConfigEntry ::= SEQUENCE {
    tlpUpsConfigInputVoltage                Unsigned32,
    tlpUpsConfigInputFrequency              Unsigned32,
    tlpUpsConfigOutputVoltage               Unsigned32,
    tlpUpsConfigOutputFrequency             Unsigned32,
    tlpUpsConfigAudibleStatus               INTEGER,
    tlpUpsConfigAutoBatteryTest             INTEGER,
    tlpUpsConfigAutoRestartAfterShutdown    INTEGER,
    tlpUpsConfigAutoRampOnTransition        INTEGER,
    tlpUpsConfigAutoShedOnTransition        INTEGER,
    tlpUpsConfigBypassLowerLimitPercent     INTEGER,
    tlpUpsConfigBypassUpperLimitPercent     INTEGER,
    tlpUpsConfigBypassLowerLimitVoltage     Unsigned32,
    tlpUpsConfigBypassUpperLimitVoltage     Unsigned32,
    tlpUpsConfigColdStart                   INTEGER,
    tlpUpsConfigEconomicMode                INTEGER,
    tlpUpsConfigFaultAction                 INTEGER,
    tlpUpsConfigOffMode                     INTEGER,
    tlpUpsConfigLineSensitivity             INTEGER }

tlpUpsConfigInputVoltage OBJECT-TYPE
    SYNTAX Unsigned32
    UNITS "Volts"
    MAX-ACCESS read-write
    STATUS current
    DESCRIPTION
        "The nominal value of the input line voltage. This value may not
        be supported on all models. If not supported, this value will return
        ERROR_NO_SUCH_NAME. This value may not be writable on all models. If
        not writable, the value will be rejected and an appropriate error
        message will be returned."
    ::= { tlpUpsConfigEntry 1 }

tlpUpsConfigInputFrequency OBJECT-TYPE
    SYNTAX Unsigned32
    UNITS "0.1 Hertz"
    MAX-ACCESS read-write
    STATUS current
    DESCRIPTION
        "The nominal input frequency. On those systems which support read-write
        access to this object, if there is an attempt to set this variable to a
        value that is not supported, the request must be rejected and the agent
        shall respond with an appropriate error message, i.e., badValue for
        SNMPv1, or inconsistentValue for SNMPv2."
    ::= { tlpUpsConfigEntry 2 }

tlpUpsConfigOutputVoltage OBJECT-TYPE
    SYNTAX Unsigned32
    UNITS "Volts"
    MAX-ACCESS read-write
    STATUS current
    DESCRIPTION
        "The nominal value of the output voltage. This value may not be
        supported on all models. If not supported, the agent reports
        ERROR_NO_SUCH_NAME. This value may not be writable on all models. If
        not writable, the value will be rejected and an appropriate error
        message will be returned."
    ::= { tlpUpsConfigEntry 3 }

tlpUpsConfigOutputFrequency OBJECT-TYPE
    SYNTAX Unsigned32
    UNITS "0.1 Hertz"
    MAX-ACCESS read-write
    STATUS current
    DESCRIPTION
    "The nominal output frequency. On those systems which support read-write
    access to this object, if there is an attempt to set this variable to a
    value that is not supported, the request will be rejected and the agent
    will respond with an appropriate error message."
    ::= { tlpUpsConfigEntry 4 }

tlpUpsConfigAudibleStatus OBJECT-TYPE
    SYNTAX INTEGER {
        disabled(1),
        enabled(2),
        muted(3) }
    MAX-ACCESS read-write
    STATUS current
    DESCRIPTION
        "The requested state of the audible alarm. When in the disabled state,
        the audible alarm should never sound. The enabled state is self-
        describing. Setting this object to muted(3) when the audible alarm is
        sounding shall temporarily silence the alarm. It will remain muted until
        it would normally stop sounding and the value returned for read operations
        during this period shall equal muted(3). At the end of this period, the
        value shall revert to enabled(2). Writes of the value muted(3) when the
        audible alarm is not sounding shall be accepted but otherwise shall have no
        effect."
    ::= { tlpUpsConfigEntry 5 }

tlpUpsConfigAutoBatteryTest OBJECT-TYPE
    SYNTAX INTEGER {
        disabled(0),
        biweekly(1),
        monthly(2),
        quarterly(3),
        semiannually(4) }
    MAX-ACCESS read-write
    STATUS current
    DESCRIPTION
        "When disabled(0), the ups will not perform an automatic battery selftest.
        When set to another value, the ups will perform an automatic selftest in
        the approximate period defined by each respective enumerated value. This
        feature is generally not recommended."
    ::= { tlpUpsConfigEntry 6 }

tlpUpsConfigAutoRestartAfterShutdown OBJECT-TYPE
    SYNTAX INTEGER {
        disabled(0),
        enabled(1) }
    MAX-ACCESS read-write
    STATUS current
    DESCRIPTION
        "When enabled(1), the ups should autorestart after a shutdown from battery
        mode if valid AC is applied. When disabled(0), the ups should not autorestart
        when AC is restored and instead power up into standby mode."
    ::= { tlpUpsConfigEntry 7 }

tlpUpsConfigAutoRampOnTransition OBJECT-TYPE
    SYNTAX INTEGER {
        disabled(0),
        enabled(1) }
    MAX-ACCESS read-write
    STATUS current
    DESCRIPTION
        "When enabled(1), the ups should perform its preconfigured ramp sequence when
        valid AC is restored while in battery mode. If this value is not supported by
        the ups, then this value will always return ERROR_NO_SUCH_NAME."
    ::= { tlpUpsConfigEntry 8 }

tlpUpsConfigAutoShedOnTransition OBJECT-TYPE
    SYNTAX INTEGER {
        disabled(0),
        enabled(1) }
    MAX-ACCESS read-write
    STATUS current
    DESCRIPTION
        "When enabled(1), the ups should perform its preconfigured shed sequence when
        valid AC is lost causing the ups to enter battery mode. If this value is not
        supported by the ups, then this value will always return ERROR_NO_SUCH_NAME."
    ::= { tlpUpsConfigEntry 9 }

tlpUpsConfigBypassLowerLimitPercent OBJECT-TYPE
    SYNTAX INTEGER (-20..-5)
    UNITS "percent"
    MAX-ACCESS read-write
    STATUS current
    DESCRIPTION
        "The lowest AC input voltage allowed to be output to the load while in bypass
        mode. This setting is expressed as a percentage from nominal voltage. If this
        value is not supported by the ups, then this value will always return
        ERROR_NO_SUCH_NAME."
    ::= { tlpUpsConfigEntry 10 }

tlpUpsConfigBypassUpperLimitPercent OBJECT-TYPE
    SYNTAX INTEGER (5..20)
    UNITS "percent"
    MAX-ACCESS read-write
    STATUS current
    DESCRIPTION
        "The highest AC input voltage allowed to be output to the load while in bypass
        mode. This setting is expressed as a percentage from nominal voltage. If this
        value is not supported by the ups, then this value will always return
        ERROR_NO_SUCH_NAME."
    ::= { tlpUpsConfigEntry 11 }

tlpUpsConfigBypassLowerLimitVoltage OBJECT-TYPE
    SYNTAX Unsigned32
    UNITS "Volts"
    MAX-ACCESS read-write
    STATUS current
    DESCRIPTION
        "The lowest AC input voltage allowed to be output to the load while in bypass
        mode. If this value is not supported by the ups, then this value will always
        return ERROR_NO_SUCH_NAME."
    ::= { tlpUpsConfigEntry 12 }

tlpUpsConfigBypassUpperLimitVoltage OBJECT-TYPE
    SYNTAX Unsigned32
    UNITS "Volts"
    MAX-ACCESS read-write
    STATUS current
    DESCRIPTION
        "The highest AC input voltage allowed to be output to the load while in bypass
        mode. If this value is not supported by the ups, then this value will always
        return ERROR_NO_SUCH_NAME."
    ::= { tlpUpsConfigEntry 13 }

tlpUpsConfigColdStart OBJECT-TYPE
    SYNTAX INTEGER {
        disabled(0),
        enabled(1) }
    MAX-ACCESS read-write
    STATUS current
    DESCRIPTION
        "This option enables or disables the ability to turn the ups on without AC
        supplied. If this value is not supported by the ups, then this value will
        always return ERROR_NO_SUCH_NAME."
    ::= { tlpUpsConfigEntry 14 }

tlpUpsConfigEconomicMode OBJECT-TYPE
    SYNTAX INTEGER {
        online(0),
        economy(1),
        constant50Hz(2),
        constant60Hz(3),
        constantAuto(4),
        autoAdaptive(5) }
    MAX-ACCESS read-write
    STATUS current
    DESCRIPTION
        "The configurable economic mode options for the ups. The online(0) mode is
        the default configuration of most upss, which is synonymous as having the
        economic mode disabled. The economy(1) mode is the typical configuration to
        run in economy mode, which is synonymous as having the economic mode enabled.
        Constant50Hz(2) is a power strategy, which fixes the output frequency at 50Hz.
        Constant60Hz(3) is a power stragegy, which fixes the output frequency at 60Hz.
        ConstantAuto(4) regulates the output frequency at nominal input frequency.
        AutoAdaptive(5) mode will cause the ups to automatically switch between
        online(0), maximum quality, and economy(1), maximum efficiency, to improve
        efficiency during stable utility periods and improve output regulation during
        unstable utility periods. Not all values are supported by all upss. Most upss,
        if supportive of economic mode, only supports online(0) and economy(1). If the
        ups does not support economic mode, then this value will always return
        ERROR_NO_SUCH_NAME."
    ::= { tlpUpsConfigEntry 15 }

tlpUpsConfigFaultAction OBJECT-TYPE
    SYNTAX INTEGER {
        bypass(0),
        standby(1) }
    MAX-ACCESS read-write
    STATUS current
    DESCRIPTION
        "Determines the action to take if the output needs to be shut down due to a
        fault condition, limited by the type of fault incurred. When configured for
        bypass(0), the ups will go to bypass on a fault condition. When configured
        for standby(1), the ups will go to standby mode on a fault condition. Either
        configuration will be valid as long as AC input is within normal line voltage
        and frequency limits when the fault condition occurs. If the line is outside
        these limits, the ups will turn off. If this value is not supported by the ups,
        then this value will always return ERROR_NO_SUCH_NAME."
    ::= { tlpUpsConfigEntry 16 }

tlpUpsConfigOffMode OBJECT-TYPE
    SYNTAX INTEGER {
        standby(0),
        bypass(1) }
    MAX-ACCESS read-write
    STATUS current
    DESCRIPTION
        "This option governs what mode the ups should go into when AC input is
        available, but the load is either off or not battery backed up. If this
        setting is configured for bypass(1), the intention is that any time the ups
        would normally go into standby mode, it would instead go into bypass mode. Note
        that this setting does not dictate the mode for fault conditions, which is
        governed by tlpUpsConfigFaultAction. If this value is not supported by the ups,
        then this value will always return ERROR_NO_SUCH_NAME."
    ::= { tlpUpsConfigEntry 17 }

tlpUpsConfigLineSensitivity OBJECT-TYPE
    SYNTAX INTEGER {
        normal(0),
        reduced(1),
        fullyReduced(2) }
    MAX-ACCESS read-write
    STATUS current
    DESCRIPTION
        "Adjusts the AC line voltage sensitivity setting. If this value is not supported
        by the ups, then this value will always return ERROR_NO_SUCH_NAME."
    ::= { tlpUpsConfigEntry 18 }

tlpUpsConfigAutoRestartTable OBJECT-TYPE
    SYNTAX SEQUENCE OF TlpUpsConfigAutoRestartEntry
    MAX-ACCESS not-accessible
    STATUS current
    DESCRIPTION
        "The configurable automatic restart options of each ups in device table.
        This is a sparse dependent table, and will contain some subset of devices
        that are upss. Not all options are available on all upss."
    ::= { tlpUpsConfig 2 }

tlpUpsConfigAutoRestartEntry OBJECT-TYPE
    SYNTAX TlpUpsConfigAutoRestartEntry
    MAX-ACCESS not-accessible
    STATUS current
    DESCRIPTION
        "An entry containing configurable automatic restart options for a particular
        ups."
    INDEX { tlpDeviceIndex }
    ::= { tlpUpsConfigAutoRestartTable 1 }

TlpUpsConfigAutoRestartEntry ::= SEQUENCE {
    tlpUpsConfigAutoRestartInverterShutdown     INTEGER,
    tlpUpsConfigAutoRestartDelayedWakeup        INTEGER,
    tlpUpsConfigAutoRestartLowVoltageCutoff     INTEGER,
    tlpUpsConfigAutoRestartOverLoad             INTEGER,
    tlpUpsConfigAutoRestartOverTemperature      INTEGER }

tlpUpsConfigAutoRestartInverterShutdown OBJECT-TYPE
    SYNTAX INTEGER {
        disabled(0),
        enabled(1) }
    MAX-ACCESS read-write
    STATUS current
    DESCRIPTION
        "If enabled(1) and the ups is turned off from invert mode (via user
        interaction), if line becomes valid, the ups will automatically go to line
        mode. If disabled(0), the ups will turn back on and go to standby mode
        instead."
    ::= { tlpUpsConfigAutoRestartEntry 1 }

tlpUpsConfigAutoRestartDelayedWakeup OBJECT-TYPE
    SYNTAX INTEGER {
        disabled(0),
        enabled(1) }
    MAX-ACCESS read-write
    STATUS current
    DESCRIPTION
        "If enabled(1) and power fails during a DelayBeforeStartup and line remains
        invalid after the timeout expires, the ups will be set to turn back on
        automatically. If disabled(0), the ups will turn back on and go to standby
        mode instead."
    ::= { tlpUpsConfigAutoRestartEntry 2 }

tlpUpsConfigAutoRestartLowVoltageCutoff OBJECT-TYPE
    SYNTAX INTEGER {
        disabled(0),
        enabled(1) }
    MAX-ACCESS read-write
    STATUS current
    DESCRIPTION
        "If enabled(1) and the ups is turned off from invert mode (via low voltage
        cutoff), if line becomes valid, the ups will automatically go to line mode.
        If disabled(0), the ups will turn back on and go to standby mode instead."
    ::= { tlpUpsConfigAutoRestartEntry 3 }

tlpUpsConfigAutoRestartOverLoad OBJECT-TYPE
    SYNTAX INTEGER {
        disabled(0),
        enabled(1) }
    MAX-ACCESS read-write
    STATUS current
    DESCRIPTION
        "If enabled(1) and the ups is turned off from invert mode (via overload), if
        line becomes valid, the ups will automatically go to line mode. If disabled(0),
        the ups will turn back on and go to standby mode instead."
    ::= { tlpUpsConfigAutoRestartEntry 4 }

tlpUpsConfigAutoRestartOverTemperature OBJECT-TYPE
    SYNTAX INTEGER {
        disabled(0),
        enabled(1) }
    MAX-ACCESS read-write
    STATUS current
    DESCRIPTION
        "If enabled(1) and the ups is turned off from invert mode (via over temperature),
        if line becomes valid, the ups will automatically go to line mode. If disabled(0),
        the ups will turn back on and go to standby mode instead."
    ::= { tlpUpsConfigAutoRestartEntry 5 }

tlpUpsConfigThresholdTable OBJECT-TYPE
    SYNTAX SEQUENCE OF TlpUpsConfigThresholdEntry
    MAX-ACCESS not-accessible
    STATUS current
    DESCRIPTION
        "The configurable threshold options of each ups in device table. This
        is a sparse dependent table, and will contain some subset of devices that
        are upss. Not all options are available on all upss."
    ::= { tlpUpsConfig 3 }

tlpUpsConfigThresholdEntry OBJECT-TYPE
    SYNTAX TlpUpsConfigThresholdEntry
    MAX-ACCESS not-accessible
    STATUS current
    DESCRIPTION
        "An entry containing configurable threshold options for a particular ups."
    INDEX { tlpDeviceIndex }
    ::= { tlpUpsConfigThresholdTable 1 }

TlpUpsConfigThresholdEntry ::= SEQUENCE {
    tlpUpsConfigBatteryAgeThreshold             Unsigned32,
    tlpUpsConfigLowBatteryThreshold             INTEGER,
    tlpUpsConfigLowBatteryTime                  Unsigned32,
    tlpUpsConfigOverLoadThreshold               INTEGER }

tlpUpsConfigBatteryAgeThreshold OBJECT-TYPE
    SYNTAX Unsigned32
    UNITS "months"
    MAX-ACCESS read-write
    STATUS current
    DESCRIPTION
        "The number of months for a battery to be in service. The battery age alarm,
        tlpUpsAlarmBatteryAgeAboveThreshold, is triggered when the current date
        exceeds tlpUpsBatteryPackIdentInstallDate by tlpUpsConfigBatteryAgeThreshold
        months."
    ::= { tlpUpsConfigThresholdEntry 1 }

tlpUpsConfigLowBatteryThreshold OBJECT-TYPE
    SYNTAX INTEGER (5..95)
    UNITS "percent"
    MAX-ACCESS read-write
    STATUS current
    DESCRIPTION
        "This value denotes the percentage of battery capacity remaining warning
        level. The low battery alarm, tlpUpsAlarmLowBattery, is triggered when
        tlpUpsEstimatedChargeRemaining drops below this value."
    ::= { tlpUpsConfigThresholdEntry 2 }

tlpUpsConfigLowBatteryTime OBJECT-TYPE
    SYNTAX Unsigned32
    UNITS "seconds"
    MAX-ACCESS read-write
    STATUS current
    DESCRIPTION
        "The value in seconds of tlpUpsEstimatedMinutesRemaining at which a lowBattery
        condition is declared. For agents which support only discrete (discontinuous)
        values, then the agent shall round up to the next supported value. If the
        requested value is larger than the largest supported value, then the largest
        supported value shall be selected."
    ::= { tlpUpsConfigThresholdEntry 3 }

tlpUpsConfigOverLoadThreshold OBJECT-TYPE
    SYNTAX INTEGER (5..105)
    UNITS "percent"
    MAX-ACCESS read-write
    STATUS current
    DESCRIPTION
        "This value denotes the percentage of load at which the overload condition
        occurs. The overload alarm, tlpUpsAlarmOutputOverload, is triggered when the
        percentage of output load exceeds this value."
    ::= { tlpUpsConfigThresholdEntry 4 }

-- pdu

tlpPduIdentNumPdu OBJECT-TYPE
    SYNTAX Unsigned32
    MAX-ACCESS read-only
    STATUS current
    DESCRIPTION
        "The number of pdu devices that this agent is currently managing."
    ::= { tlpPduIdent 1 }

tlpPduIdentTable OBJECT-TYPE
    SYNTAX SEQUENCE OF TlpPduIdentEntry
    MAX-ACCESS not-accessible
    STATUS current
    DESCRIPTION
        "The identity details of each pdu in device table. This is a
        sparse dependent table, and will contain some subset of devices
        that are pdus."
    ::= { tlpPduIdent 2 }

tlpPduIdentEntry OBJECT-TYPE
    SYNTAX TlpPduIdentEntry
    MAX-ACCESS not-accessible
    STATUS current
    DESCRIPTION
        "An entry containing details for a particular pdu."
    INDEX { tlpDeviceIndex }
    ::= { tlpPduIdentTable 1 }

TlpPduIdentEntry ::= SEQUENCE {
    tlpPduIdentNumInputs                Unsigned32,
    tlpPduIdentNumOutputs               Unsigned32,
    tlpPduIdentNumPhases                Unsigned32,
    tlpPduIdentNumOutlets               Unsigned32,
    tlpPduIdentNumOutletGroups          Unsigned32,
    tlpPduIdentNumCircuits              Unsigned32,
    tlpPduIdentNumBreakers              Unsigned32,
    tlpPduIdentNumHeatsinks             Unsigned32 }

tlpPduIdentNumInputs OBJECT-TYPE
    SYNTAX Unsigned32
    MAX-ACCESS read-only
    STATUS current
    DESCRIPTION
        "The number of input lines supported by the pdu."
    ::= { tlpPduIdentEntry 1 }

tlpPduIdentNumOutputs OBJECT-TYPE
    SYNTAX Unsigned32
    MAX-ACCESS read-only
    STATUS current
    DESCRIPTION
        "The number of output lines supported by the pdu."
    ::= { tlpPduIdentEntry 2 }

tlpPduIdentNumPhases OBJECT-TYPE
    SYNTAX Unsigned32
    MAX-ACCESS read-only
    STATUS current
    DESCRIPTION
        "The number of phases supported by the pdu."
    ::= { tlpPduIdentEntry 3 }

tlpPduIdentNumOutlets OBJECT-TYPE
    SYNTAX Unsigned32
    MAX-ACCESS read-only
    STATUS current
    DESCRIPTION
        "The number of receptacles supported by the pdu."
    ::= { tlpPduIdentEntry 4 }

tlpPduIdentNumOutletGroups OBJECT-TYPE
    SYNTAX Unsigned32
    MAX-ACCESS read-only
    STATUS current
    DESCRIPTION
        "The number of receptacle groups supported by the pdu."
    ::= { tlpPduIdentEntry 5 }

tlpPduIdentNumCircuits OBJECT-TYPE
    SYNTAX Unsigned32
    MAX-ACCESS read-only
    STATUS current
    DESCRIPTION
        "The number of circuits supported by the pdu."
    ::= { tlpPduIdentEntry 6 }

tlpPduIdentNumBreakers OBJECT-TYPE
    SYNTAX Unsigned32
    MAX-ACCESS read-only
    STATUS current
    DESCRIPTION
        "The number of bank breakers supported by the pdu."
    ::= { tlpPduIdentEntry 7 }

tlpPduIdentNumHeatsinks OBJECT-TYPE
    SYNTAX Unsigned32
    MAX-ACCESS read-only
    STATUS current
    DESCRIPTION
        "The number of heatsink thermistors supported by the pdu."
    ::= { tlpPduIdentEntry 8 }

tlpPduSupportsTable OBJECT-TYPE
    SYNTAX SEQUENCE OF TlpPduSupportsEntry
    MAX-ACCESS not-accessible
    STATUS current
    DESCRIPTION
        "The supported details of each pdu in device table. This is a
        sparse dependent table, and will contain some subset of devices
        that are pdus."
    ::= { tlpPduIdent 3 }

tlpPduSupportsEntry OBJECT-TYPE
    SYNTAX TlpPduSupportsEntry
    MAX-ACCESS not-accessible
    STATUS current
    DESCRIPTION
        "An entry containing supported details for a particular pdu."
    INDEX { tlpDeviceIndex }
    ::= { tlpPduSupportsTable 1 }

TlpPduSupportsEntry ::= SEQUENCE {
    tlpPduSupportsEnergywise            TruthValue,
    tlpPduSupportsRampShed              TruthValue,
    tlpPduSupportsOutletGroup           TruthValue,
    tlpPduSupportsOutletCurrentPower    TruthValue,
    tlpPduSupportsOutletVoltage         TruthValue }

tlpPduSupportsEnergywise OBJECT-TYPE
    SYNTAX TruthValue
    MAX-ACCESS read-only
    STATUS current
    DESCRIPTION
        "Indicates whether the pdu supports Cisco EnergyWise."
    ::= { tlpPduSupportsEntry 1 }

tlpPduSupportsRampShed OBJECT-TYPE
    SYNTAX TruthValue
    MAX-ACCESS read-only
    STATUS current
    DESCRIPTION
        "Indicates whether the pdu supports ramping and shedding."
    ::= { tlpPduSupportsEntry 2 }

tlpPduSupportsOutletGroup OBJECT-TYPE
    SYNTAX TruthValue
    MAX-ACCESS read-only
    STATUS current
    DESCRIPTION
        "Indicates whether the pdu supports outlet groups."
    ::= { tlpPduSupportsEntry 3 }

tlpPduSupportsOutletCurrentPower OBJECT-TYPE
    SYNTAX TruthValue
    MAX-ACCESS read-only
    STATUS current
    DESCRIPTION
        "Indicates whether the pdu reports individual receptacle current
        and power measurements. Devices that do not support individual
        receptacle measurements will always return ERROR_NO_SUCH_NAME for
        tlpPduOutletCurrent and tlpPduOutletPower."
    ::= { tlpPduSupportsEntry 4 }

tlpPduSupportsOutletVoltage OBJECT-TYPE
    SYNTAX TruthValue
    MAX-ACCESS read-only
    STATUS current
    DESCRIPTION
        "Indicates whether the pdu reports individual receptacle voltage
        measurements. Devices that do not support individual receptacle
        measurements will always return ERROR_NO_SUCH_NAME for
        tlpPduOutletVoltage."
    ::= { tlpPduSupportsEntry 5 }

tlpPduDisplayTable OBJECT-TYPE
    SYNTAX SEQUENCE OF TlpPduDisplayEntry
    MAX-ACCESS not-accessible
    STATUS current
    DESCRIPTION
        "The display details of each pdu in device table. This is a
        sparse dependent table, and will contain some subset of devices
        that are pdus."
    ::= { tlpPduIdent 4 }

tlpPduDisplayEntry OBJECT-TYPE
    SYNTAX TlpPduDisplayEntry
    MAX-ACCESS not-accessible
    STATUS current
    DESCRIPTION
        "An entry containing display details for a particular pdu."
    INDEX { tlpDeviceIndex }
    ::= { tlpPduDisplayTable 1 }

TlpPduDisplayEntry ::= SEQUENCE {
    tlpPduDisplayScheme             INTEGER,
    tlpPduDisplayOrientation        INTEGER,
    tlpPduDisplayAutoScroll         INTEGER,
    tlpPduDisplayIntensity          INTEGER,
    tlpPduDisplayUnits              INTEGER }

tlpPduDisplayScheme OBJECT-TYPE
    SYNTAX INTEGER {
        schemeReverse(0),
        schemeNormal(1) }
    MAX-ACCESS read-write
    STATUS current
    DESCRIPTION
        "Indicates the display scheme of the LED display. The value
        schemeReverse(0) indicates the tricolor LED indicator uses an
        alternate pattern. The value schemeNormal(1) indicates the
        LED indicator uses the standard pattern. This value may not
        be supported on all models. If not supported, the value will
        always return schemeNormal(1)."
    ::= { tlpPduDisplayEntry 1 }

tlpPduDisplayOrientation OBJECT-TYPE
    SYNTAX INTEGER {
        displayNormal(0),
        displayReverse(1) }
    MAX-ACCESS read-write
    STATUS current
    DESCRIPTION
        "Indicates the physical orientation of the LED display. The value
        displayNormal(0) indicates the display is right-side-up (normal).
        The value displayReverse(1) indicates the display is upside-down.
        This value may not be supported on all models. If not supported,
        the value will always return displayNormal(0)."
    ::= { tlpPduDisplayEntry 2 }

tlpPduDisplayAutoScroll OBJECT-TYPE
    SYNTAX INTEGER {
        scrollDisabled(0),
        scrollEnabled(1) }
    MAX-ACCESS read-write
    STATUS current
    DESCRIPTION
        "Indicates whether the LED display automatically scrolls through
        displaying status values."
    ::= { tlpPduDisplayEntry 3 }

tlpPduDisplayIntensity OBJECT-TYPE
    SYNTAX INTEGER {
        intensity25(1),
        intensity50(2),
        intensity75(3),
        intensity100(4) }
    MAX-ACCESS read-write
    STATUS current
    DESCRIPTION
        "Indicates the intensity, as a percentage, of the LED display. The
        value intensity100(4) indicates the display is at 100% intensity.
        The other values indicate the display is at a lesser intensity based
        upon the respective percentage denoted."
    ::= { tlpPduDisplayEntry 4 }

tlpPduDisplayUnits OBJECT-TYPE
    SYNTAX INTEGER {
        normal(0),
        metric(1) }
    MAX-ACCESS read-write
    STATUS current
    DESCRIPTION
        "Indicates the units of measurement displayed on the LED display.
        The value normal(0) indicates that a temperature value, for example,
        is displayed in degrees Farenheit. The value metric(1) indicates a
        temperature value is displayed in degrees Celsius."
    ::= { tlpPduDisplayEntry 5 }

tlpPduDeviceTable OBJECT-TYPE
    SYNTAX SEQUENCE OF TlpPduDeviceEntry
    MAX-ACCESS not-accessible
    STATUS current
    DESCRIPTION
        "The device details of each pdu in device table. This is a
        sparse dependent table, and will contain some subset of devices
        that are pdus."
    ::= { tlpPduDevice 1 }

tlpPduDeviceEntry OBJECT-TYPE
    SYNTAX TlpPduDeviceEntry
    MAX-ACCESS not-accessible
    STATUS current
    DESCRIPTION
        "An entry containing device details for a particular pdu."
    INDEX { tlpDeviceIndex }
    ::= { tlpPduDeviceTable 1 }

TlpPduDeviceEntry ::= SEQUENCE {
    tlpPduDeviceMainLoadState               INTEGER,
    tlpPduDeviceMainLoadControllable        TruthValue,
    tlpPduDeviceMainLoadCommand             INTEGER,
    tlpPduDevicePowerOnDelay                Integer32,
    tlpPduDeviceTotalInputPowerRating       Integer32,
    tlpPduDeviceTemperatureC                Integer32,
    tlpPduDeviceTemperatureF                Integer32,
    tlpPduDevicePhaseImbalance              INTEGER,
    tlpPduDeviceOutputPowerTotal            Unsigned32,
    tlpPduDeviceAggregatePowerFactor        Unsigned32,
    tlpPduDeviceOutputCurrentPrecision      INTEGER }

tlpPduDeviceMainLoadState OBJECT-TYPE
    SYNTAX INTEGER {
        unknown(0),
        off(1),
        on(2) }
    MAX-ACCESS read-only
    STATUS current
    DESCRIPTION
        "The current state of the main output of the device."
    ::= { tlpPduDeviceEntry 1 }

tlpPduDeviceMainLoadControllable OBJECT-TYPE
    SYNTAX TruthValue
    MAX-ACCESS read-only
    STATUS current
    DESCRIPTION
        "Indicates whether or not the main output is controllable, and whether
        the ups can be turned off and on."
    ::= { tlpPduDeviceEntry 2 }

tlpPduDeviceMainLoadCommand OBJECT-TYPE
    SYNTAX INTEGER {
        idle(0),
        turnOff(1),
        turnOn(2),
        cycle(3) }
    MAX-ACCESS read-write
    STATUS current
    DESCRIPTION
        "Reading this value will always return 0. Setting this value to
        turnOff(1) will turn off the main output of the ups. Setting this
        value to turnOn(2) will turn on the main output of the ups. Setting
        this value to cycle(3) will turn off the main output, then turn it
        back on."
    ::= { tlpPduDeviceEntry 3 }

tlpPduDevicePowerOnDelay OBJECT-TYPE
    SYNTAX Integer32
    MAX-ACCESS read-write
    STATUS current
    DESCRIPTION
        "The configurable delay value, which sets the amount of additional
        time a given device will wait before it connects to a valid AC
        source. By default the delay value is set to 0. For devices with
        multiple AC input sources, this delay only applies to the primary
        input source."
    ::= { tlpPduDeviceEntry 4 }

tlpPduDeviceTotalInputPowerRating OBJECT-TYPE
    SYNTAX Integer32
    UNITS "Watts"
    MAX-ACCESS read-only
    STATUS current
    DESCRIPTION
        "The total input power rating of all phases on the device. This
        value may not be supported on all models. If not supported, this
        value will always return ERROR_NO_SUCH_NAME."
    ::= { tlpPduDeviceEntry 5 }

tlpPduDeviceTemperatureC OBJECT-TYPE
    SYNTAX Integer32
    UNITS "degrees Centigrade"
    MAX-ACCESS read-only
    STATUS current
    DESCRIPTION
        "The ambient temperature at or near the PDU casing. Temperature
        measurements are not supported on all models. If not supported,
        this value will always return ERROR_NO_SUCH_NAME."
    ::= { tlpPduDeviceEntry 6 }

tlpPduDeviceTemperatureF OBJECT-TYPE
    SYNTAX Integer32
    UNITS "degrees Farenheit"
    MAX-ACCESS read-only
    STATUS current
    DESCRIPTION
        "The ambient temperature at or near the PDU casing. Temperature
        measurements are not supported on all models. If not supported,
        this value will always return ERROR_NO_SUCH_NAME."
    ::= { tlpPduDeviceEntry 7 }

tlpPduDevicePhaseImbalance OBJECT-TYPE
    SYNTAX INTEGER (0..200)
    UNITS "percent"
    MAX-ACCESS read-only
    STATUS current
    DESCRIPTION
        "The percentage of imbalance of the three phases. This value is in
        the range from 0% imbalance to 100% imbalance. The lower the value,
        the better balanced the phases are. If all load is on a single phase,
        the imbalance is defined as 100%."
    ::= { tlpPduDeviceEntry 8 }

tlpPduDeviceOutputPowerTotal OBJECT-TYPE
    SYNTAX Unsigned32
    UNITS "Watts"
    MAX-ACCESS read-only
    STATUS current
    DESCRIPTION
        "The AC output total power for all circuits."
    ::= { tlpPduDeviceEntry 9 }

tlpPduDeviceAggregatePowerFactor OBJECT-TYPE
    SYNTAX Unsigned32
    UNITS "0.1 Watts"
    MAX-ACCESS read-only
    STATUS current
    DESCRIPTION
        "The aggregrate power factor of all phases."
  ::= { tlpPduDeviceEntry 10 }

tlpPduDeviceOutputCurrentPrecision OBJECT-TYPE
    SYNTAX INTEGER {
        none(0),
        tenths(1),
        hundredths(2) }
    MAX-ACCESS read-only
    STATUS current
    DESCRIPTION
        "Output current is reported by tlpPduOutputCurrent, tlpPduOutputCurrentMin
        and tlpPduOutputCurrentMax. These values are all reported in hundredths
        (0.01A), which accommodates all models; however, on any given device the
        actual precision may vary. This value describes the actual precision, which
        can be used as a divisor against the output current values to obtain the
        true output current measurement. For example, if tlpPduOutputCurrent reports
        530 and tlpPduDeviceOutputCurrentPrecision is tenths(1), then the actual
        output current is 5.3."
    ::= { tlpPduDeviceEntry 11 }

tlpPduInputTable OBJECT-TYPE
    SYNTAX SEQUENCE OF TlpPduInputEntry
    MAX-ACCESS not-accessible
    STATUS current
    DESCRIPTION
        "The input details of each pdu in device table. This is a sparse
        dependent table, and will contain the number of entries based upon
        the number of pdus managed by the agent as reported by tlpPduIdentNumPdus."
    ::= { tlpPduInput 1 }

tlpPduInputEntry OBJECT-TYPE
    SYNTAX TlpPduInputEntry
    MAX-ACCESS not-accessible
    STATUS current
    DESCRIPTION
        "An entry containing information applicable to a particular pdu managed
        by this agent."
    INDEX { tlpDeviceIndex }
    ::= { tlpPduInputTable 1 }

TlpPduInputEntry ::= SEQUENCE {
    tlpPduInputNominalVoltage                   Unsigned32,
    tlpPduInputNominalVoltagePhaseToPhase       Unsigned32,
    tlpPduInputNominalVoltagePhaseToNeutral     Unsigned32,
    tlpPduInputLowTransferVoltage               Unsigned32,
    tlpPduInputLowTransferVoltageLowerBound     Unsigned32,
    tlpPduInputLowTransferVoltageUpperBound     Unsigned32,
    tlpPduInputHighTransferVoltage              Unsigned32,
    tlpPduInputHighTransferVoltageLowerBound    Unsigned32,
    tlpPduInputHighTransferVoltageUpperBound    Unsigned32,
    tlpPduInputCurrentLimit                     Unsigned32 }

tlpPduInputNominalVoltage OBJECT-TYPE
    SYNTAX Unsigned32
    MAX-ACCESS read-only
    STATUS current
    DESCRIPTION
        "The nominal value of the input line voltage. This value may not
        be supported on all models. If not supported, this value will return
        ERROR_NO_SUCH_NAME."
    ::= { tlpPduInputEntry 1 }

tlpPduInputNominalVoltagePhaseToPhase OBJECT-TYPE
    SYNTAX Unsigned32
    UNITS "0.1 Volt DC"
    MAX-ACCESS read-only
    STATUS current
    DESCRIPTION
        "The nominal value of the input line voltage as measured from
        phase to phase. This value may not be supported on all models.
        If not supported, this value will always return zero."
    ::= { tlpPduInputEntry 2 }

tlpPduInputNominalVoltagePhaseToNeutral OBJECT-TYPE
    SYNTAX Unsigned32
    UNITS "0.1 Volt DC"
    MAX-ACCESS read-only
    STATUS current
    DESCRIPTION
        "The nominal value of the input line voltage as measured from
        phase to neutral. This value may not be supported on all models.
        If not supported, this value will always return zero."
    ::= { tlpPduInputEntry 3 }

tlpPduInputLowTransferVoltage OBJECT-TYPE
    SYNTAX Unsigned32
    UNITS "0.1 Volts"
    MAX-ACCESS read-only
    STATUS current
    DESCRIPTION
        "The minimum line voltage allowed before the unit disconnects the
        AC input connection. This value may not be writable on all models.
        If not writable, the value will be rejected and an appropriate error
        message will be returned. When supported, the minimum and maximum
        values allowed are dictated by tlpPduInputLowTransferVoltageLowerBound
        and tlpPduInputLowTransferVoltageUpperBound respectively."
    ::= { tlpPduInputEntry 4 }

tlpPduInputLowTransferVoltageLowerBound OBJECT-TYPE
    SYNTAX Unsigned32
    UNITS "Volts"
    MAX-ACCESS read-only
    STATUS current
    DESCRIPTION
        "The lower boundary value of tlpPduInputLowTransferVoltage as dictated
        by the hardware of the unit."
    ::= { tlpPduInputEntry 5 }

tlpPduInputLowTransferVoltageUpperBound OBJECT-TYPE
    SYNTAX Unsigned32
    UNITS "Volts"
    MAX-ACCESS read-only
    STATUS current
    DESCRIPTION
        "The upper boundary value of tlpPduInputLowTransferVoltage as dictated
        by the hardware of the unit."
    ::= { tlpPduInputEntry 6 }

tlpPduInputHighTransferVoltage OBJECT-TYPE
    SYNTAX Unsigned32
    UNITS "0.1 Volts"
    MAX-ACCESS read-only
    STATUS current
    DESCRIPTION
        "The maximum line voltage allowed before the unit disconnects the
        AC input connection. This value may not be writable on all models.
        If not writable, the value will be rejected and an appropriate error
        message will be returned. When supported, the minimum and maximum
        values allowed are dictated by tlpPduInputHighTransferVoltageLowerBound
        and tlpPduInputHighTransferVoltageUpperBound respectively."
    ::= { tlpPduInputEntry 7 }

tlpPduInputHighTransferVoltageLowerBound OBJECT-TYPE
    SYNTAX Unsigned32
    UNITS "Volts"
    MAX-ACCESS read-only
    STATUS current
    DESCRIPTION
        "The lower boundary value of tlpPduInputHighTransferVoltage as dictated
        by the hardware of the unit."
    ::= { tlpPduInputEntry 8 }

tlpPduInputHighTransferVoltageUpperBound OBJECT-TYPE
    SYNTAX Unsigned32
    UNITS "Volts"
    MAX-ACCESS read-only
    STATUS current
    DESCRIPTION
        "The upper boundary value of tlpPduInputHighTransferVoltage as dictated
        by the hardware of the unit."
    ::= { tlpPduInputEntry 9 }

tlpPduInputCurrentLimit OBJECT-TYPE
    SYNTAX Unsigned32
    UNITS "Amp DC"
    MAX-ACCESS read-only
    STATUS current
    DESCRIPTION
        "The capacity of each phase conductor in the pdu limited by the AC input
        cord or any other potential limiting factors unique to a given unit."
    ::= { tlpPduInputEntry 10 }

tlpPduInputPhaseTable OBJECT-TYPE
    SYNTAX SEQUENCE OF TlpPduInputPhaseEntry
    MAX-ACCESS not-accessible
    STATUS current
    DESCRIPTION
        "The input phase details of each pdu in device table. This is a sparse
        dependent table, and will contain the number of entries based upon
        the value of tlpPduIdentNumInputs and tlpPduIdentNumPhases per each
        device."
    ::= { tlpPduInput 2 }

tlpPduInputPhaseEntry OBJECT-TYPE
    SYNTAX TlpPduInputPhaseEntry
    MAX-ACCESS not-accessible
    STATUS current
    DESCRIPTION
        "An entry containing information applicable to a particular input
        phase managed by this agent."
    INDEX { tlpDeviceIndex, tlpPduInputPhaseIndex }
    ::= { tlpPduInputPhaseTable 1 }

TlpPduInputPhaseEntry ::= SEQUENCE {
    tlpPduInputPhaseIndex            Unsigned32,
    tlpPduInputPhasePhaseType        INTEGER,
    tlpPduInputPhaseFrequency        Unsigned32,
    tlpPduInputPhaseVoltage          Unsigned32,
    tlpPduInputPhaseVoltageMin       Unsigned32,
    tlpPduInputPhaseVoltageMax       Unsigned32,
    tlpPduInputPhaseCurrent          Unsigned32 }

tlpPduInputPhaseIndex OBJECT-TYPE
    SYNTAX Unsigned32
    MAX-ACCESS read-only
    STATUS current
    DESCRIPTION
        "The table row index for the pdu phase."
    ::= { tlpPduInputPhaseEntry 1 }

tlpPduInputPhasePhaseType OBJECT-TYPE
    SYNTAX INTEGER {
        phaseToNeutral(0),
        phaseToPhase(1) }
    MAX-ACCESS read-only
    STATUS current
    DESCRIPTION
        "Denotes whether measurements are phase to neutral(0) or phase
        to phase(1)."
    ::= { tlpPduInputPhaseEntry 2 }

tlpPduInputPhaseFrequency OBJECT-TYPE
    SYNTAX Unsigned32
    UNITS "0.1 Hertz"
    MAX-ACCESS read-only
    STATUS current
    DESCRIPTION
        "The present input frequency for a given phase."
    ::= { tlpPduInputPhaseEntry 3 }

tlpPduInputPhaseVoltage OBJECT-TYPE
    SYNTAX Unsigned32
    UNITS "0.1 Volt DC"
    MAX-ACCESS read-only
    STATUS current
    DESCRIPTION
        "The magnitude of the present input voltage for a given phase."
    ::= { tlpPduInputPhaseEntry 4 }

tlpPduInputPhaseVoltageMin OBJECT-TYPE
    SYNTAX Unsigned32
    UNITS "0.1 Volt DC"
    MAX-ACCESS read-write
    STATUS current
    DESCRIPTION
        "The minimum input voltage value since the last reset of this
        value for a given phase. If any value is written to either
        tlpPduInputVoltageMin or tlpPduInputVoltageMax, both will be
        reset to their appropriate minimum and maximum values."
    ::= { tlpPduInputPhaseEntry 5 }

tlpPduInputPhaseVoltageMax OBJECT-TYPE
    SYNTAX Unsigned32
    UNITS "0.1 Volt DC"
    MAX-ACCESS read-write
    STATUS current
    DESCRIPTION
        "The maximum input voltage value since the last reset of this
        value for a given phase. If any value is written to either
        tlpPduInputVoltageMin or tlpPduInputVoltageMax, both will be
        reset to their appropriate minimum and maximum values."
    ::= { tlpPduInputPhaseEntry 6 }

tlpPduInputPhaseCurrent OBJECT-TYPE
    SYNTAX Unsigned32
    UNITS "0.01 Amp DC"
    MAX-ACCESS read-only
    STATUS current
    DESCRIPTION
        "The magnitude of the present input current for a given phase."
    ::= { tlpPduInputPhaseEntry 7 }

tlpPduOutputTable OBJECT-TYPE
    SYNTAX SEQUENCE OF TlpPduOutputEntry
    MAX-ACCESS not-accessible
    STATUS current
    DESCRIPTION
        "The output details of each pdu in device table. This is a sparse
        dependent table, and will contain the number of entries based upon
        the value of tlpPduIdentNumOutputs per each device."
    ::= { tlpPduOutput 1 }

tlpPduOutputEntry OBJECT-TYPE
    SYNTAX TlpPduOutputEntry
    MAX-ACCESS not-accessible
    STATUS current
    DESCRIPTION
        "An entry containing output information applicable to a particular
        phase managed by this agent."
    INDEX { tlpDeviceIndex, tlpPduOutputIndex }
    ::= { tlpPduOutputTable 1 }

TlpPduOutputEntry ::= SEQUENCE {
    tlpPduOutputIndex               Unsigned32,
    tlpPduOutputPhase               INTEGER,
    tlpPduOutputPhaseType           INTEGER,
    tlpPduOutputVoltage             Unsigned32,
    tlpPduOutputCurrent             Unsigned32,
    tlpPduOutputCurrentMin          Unsigned32,
    tlpPduOutputCurrentMax          Unsigned32,
    tlpPduOutputActivePower         Unsigned32,
    tlpPduOutputPowerFactor         Unsigned32,
    tlpPduOutputSource              INTEGER }

tlpPduOutputIndex OBJECT-TYPE
    SYNTAX Unsigned32
    MAX-ACCESS read-only
    STATUS current
    DESCRIPTION
        "The table row index for the pdu phase."
    ::= { tlpPduOutputEntry 1 }

tlpPduOutputPhase OBJECT-TYPE
    SYNTAX INTEGER {
        phase1(1),
        phase2(2),
        phase3(3) }
    MAX-ACCESS read-only
    STATUS current
    DESCRIPTION
        "Indicates the phase associated with the output line."
    ::= { tlpPduOutputEntry 2 }

tlpPduOutputPhaseType OBJECT-TYPE
    SYNTAX INTEGER {
        phaseToNeutral(0),
        phaseToPhase(1) }
    MAX-ACCESS read-only
    STATUS current
    DESCRIPTION
        "Denotes whether measurements are phase to neutral(0) or phase
        to phase(1)."
    ::= { tlpPduOutputEntry 3 }

tlpPduOutputVoltage OBJECT-TYPE
    SYNTAX Unsigned32
    UNITS "0.1 Volt DC"
    MAX-ACCESS read-only
    STATUS current
    DESCRIPTION
        "The magnitude of the present output voltage for a given output line."
    ::= { tlpPduOutputEntry 4 }

tlpPduOutputCurrent OBJECT-TYPE
    SYNTAX Unsigned32
    UNITS "0.01 Amp DC"
    MAX-ACCESS read-only
    STATUS current
    DESCRIPTION
        "The output current, in hundreths of amps, for a given phase."
    ::= { tlpPduOutputEntry 5 }

tlpPduOutputCurrentMin OBJECT-TYPE
    SYNTAX Unsigned32
    UNITS "0.01 Amp DC"
    MAX-ACCESS read-only
    STATUS current
    DESCRIPTION
        "The minimum current observed for a given phase since last reset."
    ::= { tlpPduOutputEntry 6 }

tlpPduOutputCurrentMax OBJECT-TYPE
    SYNTAX Unsigned32
    UNITS "0.01 Amp DC"
    MAX-ACCESS read-only
    STATUS current
    DESCRIPTION
        "The maximum current observed for a given phase since last reset."
    ::= { tlpPduOutputEntry 7 }

tlpPduOutputActivePower OBJECT-TYPE
    SYNTAX Unsigned32
    UNITS "Watts"
    MAX-ACCESS read-only
    STATUS current
    DESCRIPTION
        "The output power for a given phase."
    ::= { tlpPduOutputEntry 8 }

tlpPduOutputPowerFactor OBJECT-TYPE
    SYNTAX Unsigned32
    UNITS "0.01 percent"
    MAX-ACCESS read-only
    STATUS current
    DESCRIPTION
        "The output power factor, in hundreths of a percent, for a given
        phase."
    ::= { tlpPduOutputEntry 9 }

tlpPduOutputSource OBJECT-TYPE
    SYNTAX INTEGER {
        none(0),
        normal(1) }
    MAX-ACCESS read-only
    STATUS current
    DESCRIPTION
        "The present source of output power. The enumeration none(0)
        indicates that there is no source of output power (and
        therefore no output power), for example, the system has opened
        the output breaker."
    ::= { tlpPduOutputEntry 10 }

tlpPduOutletTable OBJECT-TYPE
    SYNTAX SEQUENCE OF TlpPduOutletEntry
    MAX-ACCESS not-accessible
    STATUS current
    DESCRIPTION
        "The receptacle status details of each pdu in device table. This
        is a sparse dependent table, and will contain the number of entries
        based upon the value of tlpPduIdentNumOutlets per each device."
    ::= { tlpPduOutlet 1 }

tlpPduOutletEntry OBJECT-TYPE
    SYNTAX TlpPduOutletEntry
    MAX-ACCESS not-accessible
    STATUS current
    DESCRIPTION
        "An entry containing information applicable to a particular outlet
        managed by this agent."
    INDEX { tlpDeviceIndex, tlpPduOutletIndex }
    ::= { tlpPduOutletTable 1 }

TlpPduOutletEntry ::= SEQUENCE {
    tlpPduOutletIndex                   Unsigned32,
    tlpPduOutletName                    DisplayString,
    tlpPduOutletDescription             DisplayString,
    tlpPduOutletState                   INTEGER,
    tlpPduOutletControllable            TruthValue,
    tlpPduOutletCommand                 INTEGER,
    tlpPduOutletVoltage                 Unsigned32,
    tlpPduOutletCurrent                 Unsigned32,
    tlpPduOutletPower                   Unsigned32,
    tlpPduOutletRampAction              INTEGER,
    tlpPduOutletRampDelay               Integer32,
    tlpPduOutletShedAction              INTEGER,
    tlpPduOutletShedDelay               Integer32,
    tlpPduOutletGroup                   Integer32,
    tlpPduOutletBank                    Integer32,
    tlpPduOutletCircuit                 Integer32,
    tlpPduOutletPhase                   INTEGER }

tlpPduOutletIndex OBJECT-TYPE
    SYNTAX Unsigned32
    MAX-ACCESS read-only
    STATUS current
    DESCRIPTION
        "The table row index for the pdu outlet."
    ::= { tlpPduOutletEntry 1 }

tlpPduOutletName OBJECT-TYPE
    SYNTAX DisplayString
    MAX-ACCESS read-write
    STATUS current
    DESCRIPTION
        "A user-definable string identifying the name of the outlet."
    ::= { tlpPduOutletEntry 2 }

tlpPduOutletDescription OBJECT-TYPE
    SYNTAX DisplayString
    MAX-ACCESS read-write
    STATUS current
    DESCRIPTION
        "A user-definable string identifying the device(s) connected to
        the given outlet."
    ::= { tlpPduOutletEntry 3 }

tlpPduOutletState OBJECT-TYPE
    SYNTAX INTEGER {
        unknown(0),
        off(1),
        on(2) }
    MAX-ACCESS read-only
    STATUS current
    DESCRIPTION
        "The current state of the outlet."
    ::= { tlpPduOutletEntry 4 }

tlpPduOutletControllable OBJECT-TYPE
    SYNTAX TruthValue
    MAX-ACCESS read-only
    STATUS current
    DESCRIPTION
        "Denotes whether this outlet is controllable."
    ::= { tlpPduOutletEntry 5 }

tlpPduOutletCommand OBJECT-TYPE
    SYNTAX INTEGER {
        idle(0),
        turnOff(1),
        turnOn(2),
        cycle(3) }
    MAX-ACCESS read-write
    STATUS current
    DESCRIPTION
        "Reading this value will always return 0. Setting this value
        to turnOff(1) will turn off the outlet. Setting this value
        to turnOn(2) will turn on the outlet. Setting this value to
        cycle(3) will turn the outlet off, then turn it back on."
    ::= { tlpPduOutletEntry 6 }

tlpPduOutletVoltage OBJECT-TYPE
    SYNTAX Unsigned32
    UNITS "0.1 Volt DC"
    MAX-ACCESS read-only
    STATUS current
    DESCRIPTION
        "The magnitude of the present output voltage for a given outlet.
        If the voltage measurement is not supported for an individual
        receptacle regardless whether device-wide or just for this
        receptacle, then this value will always return ERROR_NO_SUCH_NAME.
        Device-wide support for receptacle voltage measurements is denoted
        by tlpPduSupportsOutletVoltage."
    ::= { tlpPduOutletEntry 7 }

tlpPduOutletCurrent OBJECT-TYPE
    SYNTAX Unsigned32
    UNITS "0.01 RMS Amp"
    MAX-ACCESS read-only
    STATUS current
    DESCRIPTION
        "The present output current, in hundreths of amps, of a given outlet.
        If the current measurement is not supported for an individual
        receptacle regardless whether device-wide or just for this
        receptacle, then this value will always return ERROR_NO_SUCH_NAME.
        Device-wide support for receptacle current measurements is denoted
        by tlpPduSupportsCurrentPower."
    ::= { tlpPduOutletEntry 8 }

tlpPduOutletPower OBJECT-TYPE
    SYNTAX Unsigned32
    UNITS "Watts"
    MAX-ACCESS read-only
    STATUS current
    DESCRIPTION
        "The output power of a given outlet. If the power measurement is
        not supported for an individual receptacle regardless whether
        device-wide or just for this receptacle, then this value will
        always return ERROR_NO_SUCH_NAME. Device-wide support for receptacle
        power measurements is denoted by tlpPduSupportsCurrentPower."
    ::= { tlpPduOutletEntry 9 }

tlpPduOutletRampAction OBJECT-TYPE
    SYNTAX INTEGER {
        remainOff(0),
        turnOnAfterDelay(1) }
    MAX-ACCESS read-write
    STATUS current
    DESCRIPTION
        "The ramp action to take on a given outlet when powering on the
        device. If this receptacle is not controllable, as denoted by
        tlpPduOutletControllable, then this value will always return
        ERROR_NO_SUCH_NAME."
    ::= { tlpPduOutletEntry 10 }

tlpPduOutletRampDelay OBJECT-TYPE
    SYNTAX Integer32
    UNITS "seconds"
    MAX-ACCESS read-write
    STATUS current
    DESCRIPTION
        "The number of seconds to delay before powering on the given outlet.
        If this receptacle is not controllable, as denoted by
        tlpPduOutletControllable, then this value will always return
        ERROR_NO_SUCH_NAME."
    ::= { tlpPduOutletEntry 11 }

tlpPduOutletShedAction OBJECT-TYPE
    SYNTAX INTEGER {
        remainOn(0),
        turnOffAfterDelay(1) }
    MAX-ACCESS read-write
    STATUS current
    DESCRIPTION
        "The shed action to take on a given outlet when powering off the
        device. If this receptacle is not controllable, as denoted by
        tlpPduOutletControllable, then this value will always return
        ERROR_NO_SUCH_NAME."
    ::= { tlpPduOutletEntry 12 }

tlpPduOutletShedDelay OBJECT-TYPE
    SYNTAX Integer32
    UNITS "seconds"
    MAX-ACCESS read-write
    STATUS current
    DESCRIPTION
        "The number of seconds to delay before powering off the given outlet.
        If this receptacle is not controllable, as denoted by
        tlpPduOutletControllable, then this value will always return
        ERROR_NO_SUCH_NAME."
    ::= { tlpPduOutletEntry 13 }

tlpPduOutletGroup OBJECT-TYPE
    SYNTAX Integer32
    MAX-ACCESS read-write
    STATUS current
    DESCRIPTION
        "The tlpPduOutletGroupIndex group index of the respective group to
        which the given outlet is assigned, or zero (0) if the given
        outlet is not grouped."
    ::= { tlpPduOutletEntry 14 }

tlpPduOutletBank OBJECT-TYPE
    SYNTAX Integer32
    MAX-ACCESS read-only
    STATUS current
    DESCRIPTION
        "Indicates on which bank the given outlet is located."
    ::= { tlpPduOutletEntry 15 }

tlpPduOutletCircuit OBJECT-TYPE
    SYNTAX Integer32
    MAX-ACCESS read-only
    STATUS current
    DESCRIPTION
        "Indicates on which circuit the given outlet is wired."
    ::= { tlpPduOutletEntry 16 }

tlpPduOutletPhase OBJECT-TYPE
    SYNTAX INTEGER {
        unknown(0),
        phase1(1),
        phase2(2),
        phase3(3),
        phase1-2(4),
        phase2-3(5),
        phase3-1(6) }
    MAX-ACCESS read-only
    STATUS current
    DESCRIPTION
        "Indicates on which phase or phases the given outlet is
        associated. For single phase devices, this object will
        always return phase1(1). For 3-phase devices with outlets
        wired to a single phase, this object will return phase1(1),
        phase2(2) or phase3(3). For 3-phase devices with outlets
        wired to two phases, this object will return phase1-2(4)
        for phases 1 and 2, phase2-3(5) for phases 2 and 3, and
        phase3-1(6) for phases 3 and 1. Devices that do not report
        phase connections will return unknown(0)."
    ::= { tlpPduOutletEntry 17 }

tlpPduOutletGroupTable OBJECT-TYPE
    SYNTAX SEQUENCE OF TlpPduOutletGroupEntry
    MAX-ACCESS not-accessible
    STATUS current
    DESCRIPTION
        "The receptacle grouping details of each pdu in device table.
        This is a sparse dependent table, and will contain the number
        of entries based upon the value of tlpPduIdentNumOutletGroups per
        each device."
    ::= { tlpPduOutlet 2 }

tlpPduOutletGroupEntry OBJECT-TYPE
    SYNTAX TlpPduOutletGroupEntry
    MAX-ACCESS not-accessible
    STATUS current
    DESCRIPTION
        "An entry containing information applicable to a particular outlet
        group managed by this agent."
    INDEX { tlpDeviceIndex, tlpPduOutletGroupIndex }
    ::= { tlpPduOutletGroupTable 1 }

TlpPduOutletGroupEntry ::= SEQUENCE {
    tlpPduOutletGroupIndex              Unsigned32,
    tlpPduOutletGroupRowStatus	        RowStatus,
    tlpPduOutletGroupName               DisplayString,
    tlpPduOutletGroupDescription        DisplayString,
    tlpPduOutletGroupState              INTEGER,
    tlpPduOutletGroupCommand            INTEGER }

tlpPduOutletGroupIndex OBJECT-TYPE
    SYNTAX Unsigned32
    MAX-ACCESS read-only
    STATUS current
    DESCRIPTION
        "The table row index for the pdu outlet group."
    ::= { tlpPduOutletGroupEntry 1 }

tlpPduOutletGroupRowStatus OBJECT-TYPE
    SYNTAX RowStatus
    MAX-ACCESS read-write
    STATUS current
    DESCRIPTION
        "Row status for the tlpPduOutletGroupTable"
    ::= { tlpPduOutletGroupEntry 2 }

tlpPduOutletGroupName OBJECT-TYPE
    SYNTAX DisplayString
    MAX-ACCESS read-write
    STATUS current
    DESCRIPTION
        "The name of this outlet group."
    ::= { tlpPduOutletGroupEntry 3 }

tlpPduOutletGroupDescription OBJECT-TYPE
    SYNTAX DisplayString
    MAX-ACCESS read-write
    STATUS current
    DESCRIPTION
        "A description for this outlet group."
    ::= { tlpPduOutletGroupEntry 4 }

tlpPduOutletGroupState OBJECT-TYPE
    SYNTAX INTEGER {
        unknown(0),
        off(1),
        on(2),
        mixed(3) }
    MAX-ACCESS read-only
    STATUS current
    DESCRIPTION
        "The current state of the outlet group. This value will report
        off(1) if all outlets in the group are off, on(2) if all outlets
        in the group are on, mixed(3) if some outlets in the group are
        off and others are on, or unknown(0) if the state of the outlets
        cannot be determined."
    ::= { tlpPduOutletGroupEntry 5 }

tlpPduOutletGroupCommand OBJECT-TYPE
    SYNTAX INTEGER {
        turnOff(1),
        turnOn(2),
        cycle(3) }
    MAX-ACCESS read-write
    STATUS current
    DESCRIPTION
        "Reading this value will always return 0. Setting this value to
        turnOff(1) will turn off every outlet associated with the group.
        Setting this value to turnOn(2) will turn on every outlet associated
        with the group. Setting this value to cycle(3) will turn off every
        outlet associated with the group, then turn each outlet back on."
    ::= { tlpPduOutletGroupEntry 6 }

tlpPduCircuitTable OBJECT-TYPE
    SYNTAX SEQUENCE OF TlpPduCircuitEntry
    MAX-ACCESS not-accessible
    STATUS current
    DESCRIPTION
        "A list of pdu circuit table entries.  The number of entries
        is given by the value of tlpPduIdentNumCircuits."
    ::= { tlpPduCircuit 1 }

tlpPduCircuitEntry OBJECT-TYPE
    SYNTAX TlpPduCircuitEntry
    MAX-ACCESS not-accessible
    STATUS current
    DESCRIPTION
        "An entry containing information applicable to a particular circuit
        managed by this agent."
    INDEX { tlpDeviceIndex, tlpPduCircuitIndex }
    ::= { tlpPduCircuitTable 1 }

TlpPduCircuitEntry ::= SEQUENCE {
    tlpPduCircuitIndex              Unsigned32,
    tlpPduCircuitPhase              INTEGER,
    tlpPduCircuitInputVoltage       Integer32,
    tlpPduCircuitTotalCurrent       Integer32,
    tlpPduCircuitCurrentLimit       Integer32,
    tlpPduCircuitCurrentMin         Integer32,
    tlpPduCircuitCurrentMax         Integer32,
    tlpPduCircuitTotalPower         Integer32,
    tlpPduCircuitPowerFactor        INTEGER,
    tlpPduCircuitUtilization        Unsigned32 }

tlpPduCircuitIndex OBJECT-TYPE
    SYNTAX Unsigned32
    MAX-ACCESS read-only
    STATUS current
    DESCRIPTION
        "The table row index for the pdu circuit."
    ::= { tlpPduCircuitEntry 1 }

tlpPduCircuitPhase OBJECT-TYPE
    SYNTAX INTEGER {
        unknown(0),
        phase1(1),
        phase2(2),
        phase3(3),
        phase1-2(4),
        phase2-3(5),
        phase3-1(6) }
    MAX-ACCESS read-only
    STATUS current
    DESCRIPTION
        "Indicates on which phase or phases the given circuit is
        wired. For single phase devices, this object will always
        return phase1(1). For 3-phase devices with outlets wired
        to a single phase, this object will return phase1(1),
        phase2(2) or phase3(3). For 3-phase devices with outlets
        wired to two phases, this object will return phase1-2(4)
        for phases 1 and 2, phase2-3(5) for phases 2 and 3, and
        phase3-1(6) for phases 3 and 1. Devices that do not report
        phase connections will return unknown(0)."
    ::= { tlpPduCircuitEntry 2 }

tlpPduCircuitInputVoltage OBJECT-TYPE
    SYNTAX Integer32
    UNITS "0.1 Volt DC"
    MAX-ACCESS read-only
    STATUS current
    DESCRIPTION
        "The input voltage for a circuit."
    ::= { tlpPduCircuitEntry 3 }

tlpPduCircuitTotalCurrent OBJECT-TYPE
    SYNTAX Integer32
    UNITS "0.01 Amp DC"
    MAX-ACCESS read-only
    STATUS current
    DESCRIPTION
        "The total current for all receptacles in a given circuit."
    ::= { tlpPduCircuitEntry 4 }

tlpPduCircuitCurrentLimit OBJECT-TYPE
    SYNTAX Integer32
    UNITS "0.01 Amp DC"
    MAX-ACCESS read-only
    STATUS current
    DESCRIPTION
        "The current capacity of a circuit in the system limited by
        the circuit breaker or wiring used in a given unit."
    ::= { tlpPduCircuitEntry 5 }

tlpPduCircuitCurrentMin OBJECT-TYPE
    SYNTAX Integer32
    UNITS "0.01 Amp DC"
    MAX-ACCESS read-only
    STATUS current
    DESCRIPTION
        "The minimum total current for all receptacles in a given
        circuit since last reset."
    ::= { tlpPduCircuitEntry 6 }

tlpPduCircuitCurrentMax OBJECT-TYPE
    SYNTAX Integer32
    UNITS "0.01 Amp DC"
    MAX-ACCESS read-only
    STATUS current
    DESCRIPTION
        "The maximum total current for all receptacles in a given
        circuit since last reset."
    ::= { tlpPduCircuitEntry 7 }

tlpPduCircuitTotalPower OBJECT-TYPE
    SYNTAX Integer32
    UNITS "Watts"
    MAX-ACCESS read-only
    STATUS current
    DESCRIPTION
        "The total power for all receptacles in a given circuit."
    ::= { tlpPduCircuitEntry 8 }

tlpPduCircuitPowerFactor OBJECT-TYPE
    SYNTAX INTEGER (0..200)
    UNITS "percent"
    MAX-ACCESS read-only
    STATUS current
    DESCRIPTION
        "The power factor for all receptacles in a given circuit."
    ::= { tlpPduCircuitEntry 9 }

tlpPduCircuitUtilization OBJECT-TYPE
    SYNTAX Unsigned32
    UNITS "0.01 %"
    MAX-ACCESS read-only
    STATUS current
    DESCRIPTION
        "The percentage of utilization of a given circuit. This is typically
        a calculation of tlpPduCircuitTotalCurrent / tlpPduCircuitCurrentLimit."
    ::= { tlpPduCircuitEntry 10 }

tlpPduBreakerTable OBJECT-TYPE
    SYNTAX SEQUENCE OF TlpPduBreakerEntry
    MAX-ACCESS not-accessible
    STATUS current
    DESCRIPTION
        "A list of pdu bank breaker table entries. The number of entries
        is given by the value of tlpPduIdentNumBreakers."
    ::= { tlpPduBreaker 1 }

tlpPduBreakerEntry OBJECT-TYPE
    SYNTAX TlpPduBreakerEntry
    MAX-ACCESS not-accessible
    STATUS current
    DESCRIPTION
        "An entry containing information applicable to a particular bank
        breaker managed by this agent."
    INDEX { tlpDeviceIndex, tlpPduBreakerIndex }
    ::= { tlpPduBreakerTable 1 }

TlpPduBreakerEntry ::= SEQUENCE {
    tlpPduBreakerIndex          Unsigned32,
    tlpPduBreakerStatus         INTEGER }

tlpPduBreakerIndex OBJECT-TYPE
    SYNTAX Unsigned32
    MAX-ACCESS read-only
    STATUS current
    DESCRIPTION
        "The table row index for the pdu bank breaker."
    ::= { tlpPduBreakerEntry 1 }

tlpPduBreakerStatus OBJECT-TYPE
    SYNTAX INTEGER {
        open(0),
        closed(1),
        notInstalled(2) }
    MAX-ACCESS read-only
    STATUS current
    DESCRIPTION
        "Indicates whether the bank breaker is open(0), closed(1) or not
        installed(2)."
    ::= { tlpPduBreakerEntry 2 }

tlpPduHeatsinkTable OBJECT-TYPE
    SYNTAX SEQUENCE OF TlpPduHeatsinkEntry
    MAX-ACCESS not-accessible
    STATUS current
    DESCRIPTION
        "A list of pdu heatsink thermistor table entries. The number of entries
        is given by the value of tlpPduIdentNumHeatsinks."
    ::= { tlpPduHeatsink 1 }

tlpPduHeatsinkEntry OBJECT-TYPE
    SYNTAX TlpPduHeatsinkEntry
    MAX-ACCESS not-accessible
    STATUS current
    DESCRIPTION
        "An entry containing information applicable to a particular heatsink
        thermistor managed by this agent."
    INDEX { tlpDeviceIndex, tlpPduHeatsinkIndex }
    ::= { tlpPduHeatsinkTable 1 }

TlpPduHeatsinkEntry ::= SEQUENCE {
    tlpPduHeatsinkIndex             Unsigned32,
    tlpPduHeatsinkStatus            INTEGER,
    tlpPduHeatsinkTemperatureC      Integer32,
    tlpPduHeatsinkTemperatureF      Integer32 }

tlpPduHeatsinkIndex OBJECT-TYPE
    SYNTAX Unsigned32
    MAX-ACCESS read-only
    STATUS current
    DESCRIPTION
        "The table row index for the pdu heatsink thermistor."
    ::= { tlpPduHeatsinkEntry 1 }

tlpPduHeatsinkStatus OBJECT-TYPE
    SYNTAX INTEGER {
        notAvailable(0),
        available(1) }
    MAX-ACCESS read-only
    STATUS current
    DESCRIPTION
        "Indicates whether the heatsink thermistor is available. The entry
        will return notAvailable(0) if a thermistor is either non-existent or
        disconnected, or available(1) when connected."
    ::= { tlpPduHeatsinkEntry 2 }

tlpPduHeatsinkTemperatureC OBJECT-TYPE
    SYNTAX Integer32
    UNITS "0.1 degrees Centigrade"
    MAX-ACCESS read-only
    STATUS current
    DESCRIPTION
        "The temperature at the heatsink termistor in tenths degrees Centigrade.
        Heatsink temperature measurements are not supported on all models. If
        not supported, this value will always return ERROR_NO_SUCH_NAME."
    ::= { tlpPduHeatsinkEntry 3 }

tlpPduHeatsinkTemperatureF OBJECT-TYPE
    SYNTAX Integer32
    UNITS "0.1 degrees Farenheit"
    MAX-ACCESS read-only
    STATUS current
    DESCRIPTION
        "The temperature at the heatsink termistor in tenths degrees Farenheit.
        Heatsink temperature measurements are not supported on all models. If
        not supported, this value will always return ERROR_NO_SUCH_NAME."
    ::= { tlpPduHeatsinkEntry 4 }

tlpPduControlTable OBJECT-TYPE
    SYNTAX SEQUENCE OF TlpPduControlEntry
    MAX-ACCESS not-accessible
    STATUS current
    DESCRIPTION
        "The actionable controls for each pdu in device table. This is a
        sparse dependent table, and will contain some subset of devices
        that are pdus."
    ::= { tlpPduControl 1 }

tlpPduControlEntry OBJECT-TYPE
    SYNTAX TlpPduControlEntry
    MAX-ACCESS not-accessible
    STATUS current
    DESCRIPTION
        "An entry containing controls for a particular pdu."
    INDEX { tlpDeviceIndex }
    ::= { tlpPduControlTable 1 }

TlpPduControlEntry ::= SEQUENCE {
    tlpPduControlRamp           TruthValue,
    tlpPduControlShed           TruthValue,
    tlpPduControlPduOn          TruthValue,
    tlpPduControlPduOff         TruthValue,
    tlpPduControlPduReboot      TruthValue }

tlpPduControlRamp OBJECT-TYPE
    SYNTAX TruthValue
    MAX-ACCESS read-write
    STATUS current
    DESCRIPTION
        "Set to TRUE to initiate the pre-designated ramp
        sequence on the pdu."
    ::= { tlpPduControlEntry 1 }
  
tlpPduControlShed OBJECT-TYPE
    SYNTAX TruthValue
    MAX-ACCESS read-write
    STATUS current
    DESCRIPTION
        "Set to TRUE to initiate the pre-designated shed
        sequence on the pdu."
    ::= { tlpPduControlEntry 2 }
  
tlpPduControlPduOn OBJECT-TYPE
    SYNTAX TruthValue
    MAX-ACCESS read-write
    STATUS current
    DESCRIPTION
        "Set to TRUE to turn the pdu on."
    ::= { tlpPduControlEntry 3 }

tlpPduControlPduOff OBJECT-TYPE
    SYNTAX TruthValue
    MAX-ACCESS read-write
    STATUS current
    DESCRIPTION
        "Set to TRUE to turn the pdu off."
    ::= { tlpPduControlEntry 4 }

tlpPduControlPduReboot OBJECT-TYPE
    SYNTAX TruthValue
    MAX-ACCESS read-write
    STATUS current
    DESCRIPTION
        "Set to TRUE to reboot the pdu."
    ::= { tlpPduControlEntry 5 }

tlpPduConfigTable OBJECT-TYPE
    SYNTAX SEQUENCE OF TlpPduConfigEntry
    MAX-ACCESS not-accessible
    STATUS current
    DESCRIPTION
        "The configuration options of each pdu in device table. This
        is a sparse dependent table, and will contain some subset of
        devices that are pdus. Not all options are available on all
        pdus."
    ::= { tlpPduConfig 1 }

tlpPduConfigEntry OBJECT-TYPE
    SYNTAX TlpPduConfigEntry
    MAX-ACCESS not-accessible
    STATUS current
    DESCRIPTION
        "An entry containing configuration options for a particular pdu."
    INDEX { tlpDeviceIndex }
    ::= { tlpPduConfigTable 1 }

TlpPduConfigEntry ::= SEQUENCE {
    tlpPduConfigInputVoltage            Unsigned32 }

tlpPduConfigInputVoltage OBJECT-TYPE
    SYNTAX Unsigned32
    MAX-ACCESS read-write
    STATUS current
    DESCRIPTION
        "The nominal value of the input line voltage. This value may not
        be supported on all models. If not supported, this value will return
        ERROR_NO_SUCH_NAME. This value may not be writable on all models. If
        not writable, the value will be rejected and an appropriate error
        message will be returned."
    ::= { tlpPduConfigEntry 1 }

-- envirosense

tlpEnvIdentNumEnvirosense OBJECT-TYPE
    SYNTAX Unsigned32
    MAX-ACCESS read-only
    STATUS current
    DESCRIPTION
        "The number of envirosense devices that this agent is currently managing."
    ::= { tlpEnvIdent 1 }

tlpEnvIdentTable OBJECT-TYPE
    SYNTAX SEQUENCE OF TlpEnvIdentEntry
    MAX-ACCESS not-accessible
    STATUS current
    DESCRIPTION
        "The identity details of each envirosense in device table. The
        number of entries is given by the value of tlpDevicesNumDevices."
    ::= { tlpEnvIdent 2 }

tlpEnvIdentEntry OBJECT-TYPE
    SYNTAX TlpEnvIdentEntry
    MAX-ACCESS not-accessible
    STATUS current
    DESCRIPTION
        "An entry containing details for a particular envirosense."
    INDEX { tlpDeviceIndex }
    ::= { tlpEnvIdentTable 1 }

TlpEnvIdentEntry ::= SEQUENCE {
    tlpEnvIdentTempSupported        TruthValue,
    tlpEnvIdentHumiditySupported    TruthValue,
    tlpEnvNumInputContacts          Unsigned32,
    tlpEnvNumOutputContacts         Unsigned32 }

tlpEnvIdentTempSupported OBJECT-TYPE
    SYNTAX TruthValue
    MAX-ACCESS read-only
    STATUS current
    DESCRIPTION
        "Indicates whether or not temperature is supported."
    ::= { tlpEnvIdentEntry 1 }

tlpEnvIdentHumiditySupported OBJECT-TYPE
    SYNTAX TruthValue
    MAX-ACCESS read-only
    STATUS current
    DESCRIPTION
        "Indicates whether or not temperature is supported."
    ::= { tlpEnvIdentEntry 2 }

tlpEnvNumInputContacts OBJECT-TYPE
    SYNTAX Unsigned32
    MAX-ACCESS read-only
    STATUS current
    DESCRIPTION
        "The number of input contacts supported by the envirosense."
    ::= { tlpEnvIdentEntry 3 }

tlpEnvNumOutputContacts OBJECT-TYPE
    SYNTAX Unsigned32
    MAX-ACCESS read-only
    STATUS current
    DESCRIPTION
        "The number of output contacts supported by the envirosense."
    ::= { tlpEnvIdentEntry 4 }

tlpEnvTemperatureTable OBJECT-TYPE
    SYNTAX SEQUENCE OF TlpEnvTemperatureEntry
    MAX-ACCESS not-accessible
    STATUS current
    DESCRIPTION
        "The temperature details of each envirosense in device table. The
        number of entries is given by the value of tlpDevicesNumDevices."
    ::= { tlpEnvDetail 1 }

tlpEnvTemperatureEntry OBJECT-TYPE
    SYNTAX TlpEnvTemperatureEntry
    MAX-ACCESS not-accessible
    STATUS current
    DESCRIPTION
        "An entry containing temperature details for a particular
        envirosense."
        INDEX { tlpDeviceIndex }
    ::= { tlpEnvTemperatureTable 1 }

TlpEnvTemperatureEntry ::= SEQUENCE {
    tlpEnvTemperatureC              Integer32,
    tlpEnvTemperatureF              Integer32,
    tlpEnvTemperatureInAlarm        TruthValue }

tlpEnvTemperatureC OBJECT-TYPE
    SYNTAX Integer32
    UNITS "degrees Centigrade"
    MAX-ACCESS read-only
    STATUS current
    DESCRIPTION
        "The ambient temperature."
    ::= { tlpEnvTemperatureEntry 1 }

tlpEnvTemperatureF OBJECT-TYPE
    SYNTAX Integer32
    UNITS "0.1 degrees Farenheit"
    MAX-ACCESS read-only
    STATUS current
    DESCRIPTION
        "The ambient temperature."
    ::= { tlpEnvTemperatureEntry 2 }

tlpEnvTemperatureInAlarm OBJECT-TYPE
    SYNTAX TruthValue
    MAX-ACCESS read-only
    STATUS current
    DESCRIPTION
        "Indicates whether or not temperature is in alarm."
    ::= { tlpEnvTemperatureEntry 3 }

tlpEnvHumidityTable OBJECT-TYPE
    SYNTAX SEQUENCE OF TlpEnvHumidityEntry
    MAX-ACCESS not-accessible
    STATUS current
    DESCRIPTION
        "The humidity details of each envirosense in device table. The
        number of entries is given by the value of tlpDevicesNumDevices."
    ::= { tlpEnvDetail 2 }

tlpEnvHumidityEntry OBJECT-TYPE
    SYNTAX TlpEnvHumidityEntry
    MAX-ACCESS not-accessible
    STATUS current
    DESCRIPTION
        "An entry containing humidity details for a particular
        envirosense."
        INDEX { tlpDeviceIndex }
    ::= { tlpEnvHumidityTable 1 }

TlpEnvHumidityEntry ::= SEQUENCE {
    tlpEnvHumidityHumidity          INTEGER,
    tlpEnvHumidityInAlarm           TruthValue }

tlpEnvHumidityHumidity OBJECT-TYPE
    SYNTAX INTEGER (0..100)
    UNITS "percent"
    MAX-ACCESS read-only
    STATUS current
    DESCRIPTION
        "The ambient humidity."
    ::= { tlpEnvHumidityEntry 1 }

tlpEnvHumidityInAlarm OBJECT-TYPE
    SYNTAX TruthValue
    MAX-ACCESS read-only
    STATUS current
    DESCRIPTION
        "Indicates whether or not humidity is in alarm."
    ::= { tlpEnvHumidityEntry 2 }

tlpEnvInputContactTable OBJECT-TYPE
    SYNTAX SEQUENCE OF TlpEnvInputContactEntry
    MAX-ACCESS not-accessible
    STATUS current
    DESCRIPTION
        "The input contact details of each envirosense in device table.
        The number of entries is given by the value of tlpDevicesNumDevices."
    ::= { tlpEnvDetail 3 }

tlpEnvInputContactEntry OBJECT-TYPE
    SYNTAX TlpEnvInputContactEntry
    MAX-ACCESS not-accessible
    STATUS current
    DESCRIPTION
        "An entry containing input contact details for a particular
        envirosense."
        INDEX { tlpDeviceIndex, tlpEnvInputContactIndex }
    ::= { tlpEnvInputContactTable 1 }

TlpEnvInputContactEntry ::= SEQUENCE {
    tlpEnvInputContactIndex             Unsigned32,
    tlpEnvInputContactName              DisplayString,
    tlpEnvInputContactNormalState       INTEGER,
    tlpEnvInputContactCurrentState      INTEGER,
    tlpEnvInputContactInAlarm           TruthValue }

tlpEnvInputContactIndex OBJECT-TYPE
    SYNTAX Unsigned32
    MAX-ACCESS read-only
    STATUS current
    DESCRIPTION
        "The table row index for the envirosense input contact details."
    ::= { tlpEnvInputContactEntry 1 }

tlpEnvInputContactName OBJECT-TYPE
    SYNTAX DisplayString
    MAX-ACCESS read-write
    STATUS current
    DESCRIPTION
        "The name or description of the contact."
    ::= { tlpEnvInputContactEntry 2 }

tlpEnvInputContactNormalState OBJECT-TYPE
    SYNTAX INTEGER {
        open(0),
        closed(1) }
    MAX-ACCESS read-write
    STATUS current
    DESCRIPTION
        "The normal operating position of the contact."
    ::= { tlpEnvInputContactEntry 3 }

tlpEnvInputContactCurrentState OBJECT-TYPE
    SYNTAX INTEGER {
        open(0),
        closed(1) }
    MAX-ACCESS read-only
    STATUS current
    DESCRIPTION
        "The current state of the contact."
    ::= { tlpEnvInputContactEntry 4 }

tlpEnvInputContactInAlarm OBJECT-TYPE
    SYNTAX TruthValue
    MAX-ACCESS read-only
    STATUS current
    DESCRIPTION
        "Indicates whether or not the contact is in alarm."
    ::= { tlpEnvInputContactEntry 5 }

tlpEnvOutputContactTable OBJECT-TYPE
    SYNTAX SEQUENCE OF TlpEnvOutputContactEntry
    MAX-ACCESS not-accessible
    STATUS current
    DESCRIPTION
        "The output contact details of each envirosense in device table.
        The number of entries is given by the value of tlpDevicesNumDevices."
    ::= { tlpEnvDetail 4 }

tlpEnvOutputContactEntry OBJECT-TYPE
    SYNTAX TlpEnvOutputContactEntry
    MAX-ACCESS not-accessible
    STATUS current
    DESCRIPTION
        "An entry containing output contact details for a particular
        envirosense."
        INDEX { tlpDeviceIndex, tlpEnvOutputContactIndex }
    ::= { tlpEnvOutputContactTable 1 }

TlpEnvOutputContactEntry ::= SEQUENCE {
    tlpEnvOutputContactIndex            Unsigned32,
    tlpEnvOutputContactName             DisplayString,
    tlpEnvOutputContactNormalState      INTEGER,
    tlpEnvOutputContactCurrentState     INTEGER,
    tlpEnvOutputContactInAlarm          TruthValue }

tlpEnvOutputContactIndex OBJECT-TYPE
    SYNTAX Unsigned32
    MAX-ACCESS read-only
    STATUS current
    DESCRIPTION
        "The table row index for the envirosense output contact details."
    ::= { tlpEnvOutputContactEntry 1 }

tlpEnvOutputContactName OBJECT-TYPE
    SYNTAX DisplayString
    MAX-ACCESS read-write
    STATUS current
    DESCRIPTION
        "The name or description of the contact."
    ::= { tlpEnvOutputContactEntry 2 }

tlpEnvOutputContactNormalState OBJECT-TYPE
    SYNTAX INTEGER {
        open(0),
        closed(1) }
    MAX-ACCESS read-write
    STATUS current
    DESCRIPTION
        "The normal operating position of the contact."
    ::= { tlpEnvOutputContactEntry 3 }

tlpEnvOutputContactCurrentState OBJECT-TYPE
    SYNTAX INTEGER {
        open(0),
        closed(1) }
    MAX-ACCESS read-write
    STATUS current
    DESCRIPTION
        "The current state of the contact."
    ::= { tlpEnvOutputContactEntry 4 }

tlpEnvOutputContactInAlarm OBJECT-TYPE
    SYNTAX TruthValue
    MAX-ACCESS read-only
    STATUS current
    DESCRIPTION
        "Indicates whether or not the contact is in alarm."
    ::= { tlpEnvOutputContactEntry 5 }

tlpEnvConfigTable OBJECT-TYPE
    SYNTAX SEQUENCE OF TlpEnvConfigEntry
    MAX-ACCESS not-accessible
    STATUS current
    DESCRIPTION
        "The configuration options of each envirosense in device table.
        This is a sparse dependent table, and will contain some subset of
        devices that are envirosenses. Not all options are available on
        all envirosenses."
    ::= { tlpEnvConfig 1 }

tlpEnvConfigEntry OBJECT-TYPE
    SYNTAX TlpEnvConfigEntry
    MAX-ACCESS not-accessible
    STATUS current
    DESCRIPTION
        "An entry containing configuration options for a particular
        envirosenses."
    INDEX { tlpDeviceIndex }
    ::= { tlpEnvConfigTable 1 }

TlpEnvConfigEntry ::= SEQUENCE {
    tlpEnvTemperatureLowLimit           Integer32,
    tlpEnvTemperatureHighLimit          Integer32,
    tlpEnvHumidityLowLimit              INTEGER,
    tlpEnvHumidityHighLimit             INTEGER }

tlpEnvTemperatureLowLimit OBJECT-TYPE
    SYNTAX Integer32
    UNITS "degrees Farenheit"
    MAX-ACCESS read-write
    STATUS current
    DESCRIPTION
        "The lower alarm limit for ambient temperature."
    ::= { tlpEnvConfigEntry 1 }

tlpEnvTemperatureHighLimit OBJECT-TYPE
    SYNTAX Integer32
    UNITS "degrees Farenheit"
    MAX-ACCESS read-write
    STATUS current
    DESCRIPTION
        "The upper alarm limit for ambient temperature."
    ::= { tlpEnvConfigEntry 2 }

tlpEnvHumidityLowLimit OBJECT-TYPE
    SYNTAX INTEGER (0..100)
    UNITS "percent"
    MAX-ACCESS read-write
    STATUS current
    DESCRIPTION
        "The lower alarm limit for ambient humidity."
    ::= { tlpEnvConfigEntry 3 }

tlpEnvHumidityHighLimit OBJECT-TYPE
    SYNTAX INTEGER (0..100)
    UNITS "percent"
    MAX-ACCESS read-write
    STATUS current
    DESCRIPTION
        "The upper alarm limit for ambient humidity."
    ::= { tlpEnvConfigEntry 4 }

-- ats

tlpAtsIdentNumAts OBJECT-TYPE
    SYNTAX Unsigned32
    MAX-ACCESS read-only
    STATUS current
    DESCRIPTION
        "The number of ats devices that this agent is currently managing."
    ::= { tlpAtsIdent 1 }

tlpAtsIdentTable OBJECT-TYPE
    SYNTAX SEQUENCE OF TlpAtsIdentEntry
    MAX-ACCESS not-accessible
    STATUS current
    DESCRIPTION
        "The identity details of each ats in device table. This is a
        sparse dependent table, and will contain some subset of devices
        that are atss."
    ::= { tlpAtsIdent 2 }

tlpAtsIdentEntry OBJECT-TYPE
    SYNTAX TlpAtsIdentEntry
    MAX-ACCESS not-accessible
    STATUS current
    DESCRIPTION
        "An entry containing details for a particular ats."
    INDEX { tlpDeviceIndex }
    ::= { tlpAtsIdentTable 1 }

TlpAtsIdentEntry ::= SEQUENCE {
    tlpAtsIdentNumInputs                Unsigned32,
    tlpAtsIdentNumOutputs               Unsigned32,
    tlpAtsIdentNumPhases                Unsigned32,
    tlpAtsIdentNumOutlets               Unsigned32,
    tlpAtsIdentNumOutletGroups          Unsigned32,
    tlpAtsIdentNumCircuits              Unsigned32,
    tlpAtsIdentNumBreakers              Unsigned32,
    tlpAtsIdentNumHeatsinks             Unsigned32 }

tlpAtsIdentNumInputs OBJECT-TYPE
    SYNTAX Unsigned32
    MAX-ACCESS read-only
    STATUS current
    DESCRIPTION
        "The number of inputs supported by the ats."
    ::= { tlpAtsIdentEntry 1 }

tlpAtsIdentNumOutputs OBJECT-TYPE
    SYNTAX Unsigned32
    MAX-ACCESS read-only
    STATUS current
    DESCRIPTION
        "The number of outputs supported by the ats."
    ::= { tlpAtsIdentEntry 2 }

tlpAtsIdentNumPhases OBJECT-TYPE
    SYNTAX Unsigned32
    MAX-ACCESS read-only
    STATUS current
    DESCRIPTION
        "The number of phases per input supported by the ats."
    ::= { tlpAtsIdentEntry 3 }

tlpAtsIdentNumOutlets OBJECT-TYPE
    SYNTAX Unsigned32
    MAX-ACCESS read-only
    STATUS current
    DESCRIPTION
        "The number of receptacles supported by the ats."
    ::= { tlpAtsIdentEntry 4 }

tlpAtsIdentNumOutletGroups OBJECT-TYPE
    SYNTAX Unsigned32
    MAX-ACCESS read-only
    STATUS current
    DESCRIPTION
        "The number of receptacle groups supported by the ats."
    ::= { tlpAtsIdentEntry 5 }

tlpAtsIdentNumCircuits OBJECT-TYPE
    SYNTAX Unsigned32
    MAX-ACCESS read-only
    STATUS current
    DESCRIPTION
        "The number of circuits supported by the ats."
    ::= { tlpAtsIdentEntry 6 }

tlpAtsIdentNumBreakers OBJECT-TYPE
    SYNTAX Unsigned32
    MAX-ACCESS read-only
    STATUS current
    DESCRIPTION
        "The number of bank breakers supported by the ats."
    ::= { tlpAtsIdentEntry 7 }

tlpAtsIdentNumHeatsinks OBJECT-TYPE
    SYNTAX Unsigned32
    MAX-ACCESS read-only
    STATUS current
    DESCRIPTION
        "The number of heatsink thermistors supported by the ats."
    ::= { tlpAtsIdentEntry 8 }

tlpAtsSupportsTable OBJECT-TYPE
    SYNTAX SEQUENCE OF TlpAtsSupportsEntry
    MAX-ACCESS not-accessible
    STATUS current
    DESCRIPTION
        "The supported details of each ats in device table. This is a
        sparse dependent table, and will contain some subset of devices
        that are atss."
    ::= { tlpAtsIdent 3 }

tlpAtsSupportsEntry OBJECT-TYPE
    SYNTAX TlpAtsSupportsEntry
    MAX-ACCESS not-accessible
    STATUS current
    DESCRIPTION
        "An entry containing supported details for a particular ats."
    INDEX { tlpDeviceIndex }
    ::= { tlpAtsSupportsTable 1 }

TlpAtsSupportsEntry ::= SEQUENCE {
    tlpAtsSupportsEnergywise            TruthValue,
    tlpAtsSupportsRampShed              TruthValue,
    tlpAtsSupportsOutletGroup           TruthValue,
    tlpAtsSupportsOutletCurrentPower    TruthValue,
    tlpAtsSupportsOutletVoltage         TruthValue }

tlpAtsSupportsEnergywise OBJECT-TYPE
    SYNTAX TruthValue
    MAX-ACCESS read-only
    STATUS current
    DESCRIPTION
        "Indicates whether the ats supports Cisco EnergyWise."
    ::= { tlpAtsSupportsEntry 1 }

tlpAtsSupportsRampShed OBJECT-TYPE
    SYNTAX TruthValue
    MAX-ACCESS read-only
    STATUS current
    DESCRIPTION
        "Indicates whether the ats supports ramping and shedding."
    ::= { tlpAtsSupportsEntry 2 }

tlpAtsSupportsOutletGroup OBJECT-TYPE
    SYNTAX TruthValue
    MAX-ACCESS read-only
    STATUS current
    DESCRIPTION
        "Indicates whether the ats supports outlet groups."
    ::= { tlpAtsSupportsEntry 3 }

tlpAtsSupportsOutletCurrentPower OBJECT-TYPE
    SYNTAX TruthValue
    MAX-ACCESS read-only
    STATUS current
    DESCRIPTION
        "Indicates whether the ats reports individual receptacle current
        and power measurements. Devices that do not support individual
        receptacle measurements will always return ERROR_NO_SUCH_NAME for
        tlpAtsOutletCurrent and tlpAtsOutletPower."
    ::= { tlpAtsSupportsEntry 4 }

tlpAtsSupportsOutletVoltage OBJECT-TYPE
    SYNTAX TruthValue
    MAX-ACCESS read-only
    STATUS current
    DESCRIPTION
        "Indicates whether the ats reports individual receptacle voltage
        measurements. Devices that do not support individual receptacle
        measurements will always return ERROR_NO_SUCH_NAME for
        tlpAtsOutletVoltage."
    ::= { tlpAtsSupportsEntry 5 }

tlpAtsDisplayTable OBJECT-TYPE
    SYNTAX SEQUENCE OF TlpAtsDisplayEntry
    MAX-ACCESS not-accessible
    STATUS current
    DESCRIPTION
        "The display details of each ats in device table. This is a
        sparse dependent table, and will contain some subset of devices
        that are atss."
    ::= { tlpAtsIdent 4 }

tlpAtsDisplayEntry OBJECT-TYPE
    SYNTAX TlpAtsDisplayEntry
    MAX-ACCESS not-accessible
    STATUS current
    DESCRIPTION
        "An entry containing display details for a particular ats."
    INDEX { tlpDeviceIndex }
    ::= { tlpAtsDisplayTable 1 }

TlpAtsDisplayEntry ::= SEQUENCE {
    tlpAtsDisplayScheme             INTEGER,
    tlpAtsDisplayOrientation        INTEGER,
    tlpAtsDisplayAutoScroll         INTEGER,
    tlpAtsDisplayIntensity          INTEGER,
    tlpAtsDisplayUnits              INTEGER }

tlpAtsDisplayScheme OBJECT-TYPE
    SYNTAX INTEGER {
        schemeReverse(0),
        schemeNormal(1) }
    MAX-ACCESS read-write
    STATUS current
    DESCRIPTION
        "Indicates the display scheme of the LED display. The value
        schemeReverse(0) indicates the tricolor LED indicator uses an
        alternate pattern. The value schemeNormal(1) indicates the
        LED indicator uses the standard pattern. This value may not
        be supported on all models. If not supported, the value will
        always return schemeNormal(1)."
    ::= { tlpAtsDisplayEntry 1 }

tlpAtsDisplayOrientation OBJECT-TYPE
    SYNTAX INTEGER {
        displayNormal(0),
        displayReverse(1) }
    MAX-ACCESS read-write
    STATUS current
    DESCRIPTION
        "Indicates the physical orientation of the LED display. The value
        displayNormal(0) indicates the display is right-side-up (normal).
        The value displayReverse(1) indicates the display is upside-down.
        This value may not be supported on all models. If not supported,
        the value will always return displayNormal(0)."
    ::= { tlpAtsDisplayEntry 2 }

tlpAtsDisplayAutoScroll OBJECT-TYPE
    SYNTAX INTEGER {
        scrollDisabled(0),
        scrollEnabled(1) }
    MAX-ACCESS read-write
    STATUS current
    DESCRIPTION
        "Indicates whether the LED display automatically scrolls through
        displaying status values."
    ::= { tlpAtsDisplayEntry 3 }

tlpAtsDisplayIntensity OBJECT-TYPE
    SYNTAX INTEGER {
        intensity25(1),
        intensity50(2),
        intensity75(3),
        intensity100(4) }
    MAX-ACCESS read-write
    STATUS current
    DESCRIPTION
        "Indicates the intensity, as a percentage, of the LED display. The
        value intensity100(4) indicates the display is at 100% intensity.
        The other values indicate the display is at a lesser intensity based
        upon the respective percentage denoted."
    ::= { tlpAtsDisplayEntry 4 }

tlpAtsDisplayUnits OBJECT-TYPE
    SYNTAX INTEGER {
        normal(0),
        metric(1) }
    MAX-ACCESS read-write
    STATUS current
    DESCRIPTION
        "Indicates the units of measurement displayed on the LED display.
        The value normal(0) indicates that a temperature value, for example,
        is displayed in degrees Farenheit. The value metric(1) indicates a
        temperature value is displayed in degrees Celsius."
    ::= { tlpAtsDisplayEntry 5 }

tlpAtsDeviceTable OBJECT-TYPE
    SYNTAX SEQUENCE OF TlpAtsDeviceEntry
    MAX-ACCESS not-accessible
    STATUS current
    DESCRIPTION
        "The device details of each ats in device table. This is a
        sparse dependent table, and will contain some subset of devices
        that are atss."
    ::= { tlpAtsDevice 1 }

tlpAtsDeviceEntry OBJECT-TYPE
    SYNTAX TlpAtsDeviceEntry
    MAX-ACCESS not-accessible
    STATUS current
    DESCRIPTION
        "An entry containing device details for a particular ats."
    INDEX { tlpDeviceIndex }
    ::= { tlpAtsDeviceTable 1 }

TlpAtsDeviceEntry ::= SEQUENCE {
    tlpAtsDeviceMainLoadState               INTEGER,
    tlpAtsDeviceMainLoadControllable        TruthValue,
    tlpAtsDeviceMainLoadCommand             INTEGER,
    tlpAtsDevicePowerOnDelay                Integer32,
    tlpAtsDeviceTotalInputPowerRating       Integer32,
    tlpAtsDeviceTemperatureC                Integer32,
    tlpAtsDeviceTemperatureF                Integer32,
    tlpAtsDevicePhaseImbalance              INTEGER,
    tlpAtsDeviceOutputPowerTotal            Unsigned32,
    tlpAtsDeviceAggregatePowerFactor        Unsigned32,
    tlpAtsDeviceOutputCurrentPrecision      INTEGER,
    tlpAtsDeviceGeneralFault                TruthValue }

tlpAtsDeviceMainLoadState OBJECT-TYPE
    SYNTAX INTEGER {
        unknown(0),
        off(1),
        on(2) }
    MAX-ACCESS read-only
    STATUS current
    DESCRIPTION
        "The current state of the main output of the device."
    ::= { tlpAtsDeviceEntry 1 }

tlpAtsDeviceMainLoadControllable OBJECT-TYPE
    SYNTAX TruthValue
    MAX-ACCESS read-only
    STATUS current
    DESCRIPTION
        "Indicates whether or not the main output is controllable, and whether
        the ups can be turned off and on."
    ::= { tlpAtsDeviceEntry 2 }

tlpAtsDeviceMainLoadCommand OBJECT-TYPE
    SYNTAX INTEGER {
        idle(0),
        turnOff(1),
        turnOn(2),
        cycle(3) }
    MAX-ACCESS read-write
    STATUS current
    DESCRIPTION
        "Reading this value will always return 0. Setting this value to
        turnOff(1) will turn off the main output of the ups. Setting this
        value to turnOn(2) will turn on the main output of the ups. Setting
        this value to cycle(3) will turn off the main output, then turn it
        back on."
    ::= { tlpAtsDeviceEntry 3 }

tlpAtsDevicePowerOnDelay OBJECT-TYPE
    SYNTAX Integer32
    MAX-ACCESS read-write
    STATUS current
    DESCRIPTION
        "The configurable delay value, which sets the amount of additional
        time a given device will wait before it connects to a valid AC
        source. By default the delay value is set to 0. For devices with
        multiple AC input sources, this delay only applies to the primary
        input source."
    ::= { tlpAtsDeviceEntry 4 }

tlpAtsDeviceTotalInputPowerRating OBJECT-TYPE
    SYNTAX Integer32
    UNITS "Watts"
    MAX-ACCESS read-only
    STATUS current
    DESCRIPTION
        "The total input power rating of all phases on the device. This
        value may not be supported on all models. If not supported, this
        value will always return ERROR_NO_SUCH_NAME."
    ::= { tlpAtsDeviceEntry 5 }

tlpAtsDeviceTemperatureC OBJECT-TYPE
    SYNTAX Integer32
    UNITS "degrees Centigrade"
    MAX-ACCESS read-only
    STATUS current
    DESCRIPTION
        "The ambient temperature at or near the ats casing. Temperature
        measurements are not supported on all models. If not supported,
        this value will always return ERROR_NO_SUCH_NAME."
    ::= { tlpAtsDeviceEntry 6 }

tlpAtsDeviceTemperatureF OBJECT-TYPE
    SYNTAX Integer32
    UNITS "degrees Farenheit"
    MAX-ACCESS read-only
    STATUS current
    DESCRIPTION
        "The ambient temperature at or near the ats casing. Temperature
        measurements are not supported on all models. If not supported,
        this value will always return ERROR_NO_SUCH_NAME."
    ::= { tlpAtsDeviceEntry 7 }

tlpAtsDevicePhaseImbalance OBJECT-TYPE
    SYNTAX INTEGER (0..200)
    UNITS "percent"
    MAX-ACCESS read-only
    STATUS current
    DESCRIPTION
        "The percentage of imbalance of the three phases. This value is in
        the range from 0% imbalance to 100% imbalance. The lower the value,
        the better balanced the phases are. If all load is on a single phase,
        the imbalance is defined as 100%."
    ::= { tlpAtsDeviceEntry 8 }

tlpAtsDeviceOutputPowerTotal OBJECT-TYPE
    SYNTAX Unsigned32
    UNITS "Watts"
    MAX-ACCESS read-only
    STATUS current
    DESCRIPTION
        "The AC output total power for all circuits."
    ::= { tlpAtsDeviceEntry 9 }

tlpAtsDeviceAggregatePowerFactor OBJECT-TYPE
    SYNTAX Unsigned32
    UNITS "0.1 Watts"
    MAX-ACCESS read-only
    STATUS current
    DESCRIPTION
        "The aggregrate power factor of all phases."
  ::= { tlpAtsDeviceEntry 10 }

tlpAtsDeviceOutputCurrentPrecision OBJECT-TYPE
    SYNTAX INTEGER {
        none(0),
        tenths(1),
        hundredths(2) }
    MAX-ACCESS read-only
    STATUS current
    DESCRIPTION
        "Output current is reported by tlpAtsOutputCurrent, tlpAtsOutputCurrentMin
        and tlpAtsOutputCurrentMax. These values are all reported in hundredths
        (0.01A), which accommodates all models; however, on any given device the
        actual precision may vary. This value describes the actual precision, which
        can be used as a divisor against the output current values to obtain the
        true output current measurement. For example, if tlpAtsOutputCurrent reports
        530 and tlpAtsDeviceOutputCurrentPrecision is tenths(1), then the actual
        output current is 5.3."
    ::= { tlpAtsDeviceEntry 11 }

tlpAtsDeviceGeneralFault OBJECT-TYPE
    SYNTAX TruthValue
    MAX-ACCESS read-only
    STATUS current
    DESCRIPTION
        "Indicates whether or not the ats is in a system fault condition. When the
        ats is in such a fault condition, the condition can be cleared with
        tlpAtsControlResetGeneralFault."
    ::= { tlpAtsDeviceEntry 12 }

tlpAtsInputTable OBJECT-TYPE
    SYNTAX SEQUENCE OF TlpAtsInputEntry
    MAX-ACCESS not-accessible
    STATUS current
    DESCRIPTION
        "The input details of each ats in device table. This is a sparse
        dependent table, and will contain the number of entries based upon
        the number of atss managed by the agent as reported by tlpAtsIdentNumAts."
    ::= { tlpAtsInput 1 }

tlpAtsInputEntry OBJECT-TYPE
    SYNTAX TlpAtsInputEntry
    MAX-ACCESS not-accessible
    STATUS current
    DESCRIPTION
        "An entry containing information applicable to a particular primary
        input phase managed by this agent."
    INDEX { tlpDeviceIndex }
    ::= { tlpAtsInputTable 1 }

TlpAtsInputEntry ::= SEQUENCE {
    tlpAtsInputNominalVoltage                   Unsigned32,
    tlpAtsInputNominalVoltagePhaseToPhase       Unsigned32,
    tlpAtsInputNominalVoltagePhaseToNeutral     Unsigned32,
    tlpAtsInputBadTransferVoltage               Unsigned32,
    tlpAtsInputBadTransferVoltageLowerBound     Unsigned32,
    tlpAtsInputBadTransferVoltageUpperBound     Unsigned32,
    tlpAtsInputHighTransferVoltage              Unsigned32,
    tlpAtsInputHighTransferVoltageLowerBound    Unsigned32,
    tlpAtsInputHighTransferVoltageUpperBound    Unsigned32,
    tlpAtsInputFairVoltageThreshold             Unsigned32,
    tlpAtsInputBadVoltageThreshold              Unsigned32,
    tlpAtsInputSourceAvailability               INTEGER,
    tlpAtsInputSourceInUse                      INTEGER,
    tlpAtsInputSourceTransitionCount            Unsigned32,
    tlpAtsInputCurrentLimit                     Unsigned32 }

tlpAtsInputNominalVoltage OBJECT-TYPE
    SYNTAX Unsigned32
    MAX-ACCESS read-only
    STATUS current
    DESCRIPTION
        "The nominal value of the input line voltage. This value may not
        be supported on all models. If not supported, this value will return
        ERROR_NO_SUCH_NAME."
    ::= { tlpAtsInputEntry 1 }

tlpAtsInputNominalVoltagePhaseToPhase OBJECT-TYPE
    SYNTAX Unsigned32
    UNITS "0.1 Volt DC"
    MAX-ACCESS read-only
    STATUS current
    DESCRIPTION
        "The nominal value of the input line voltage as measured from
        phase to phase. This value may not be supported on all models.
        If not supported, this value will always return zero."
    ::= { tlpAtsInputEntry 2 }

tlpAtsInputNominalVoltagePhaseToNeutral OBJECT-TYPE
    SYNTAX Unsigned32
    UNITS "0.1 Volt DC"
    MAX-ACCESS read-only
    STATUS current
    DESCRIPTION
        "The nominal value of the input line voltage as measured from
        phase to neutral. This value may not be supported on all models.
        If not supported, this value will always return zero."
    ::= { tlpAtsInputEntry 3 }

tlpAtsInputBadTransferVoltage OBJECT-TYPE
    SYNTAX Unsigned32
    UNITS "0.1 Volts"
    MAX-ACCESS read-only
    STATUS current
    DESCRIPTION
        "The minimum line voltage allowed before the unit disconnects the
        AC input connection."
    ::= { tlpAtsInputEntry 4 }

tlpAtsInputBadTransferVoltageLowerBound OBJECT-TYPE
    SYNTAX Unsigned32
    UNITS "Volts"
    MAX-ACCESS read-only
    STATUS current
    DESCRIPTION
        "The lower boundary value of tlpAtsInputBadTransferVoltage as dictated
        by the hardware of the unit."
    ::= { tlpAtsInputEntry 5 }

tlpAtsInputBadTransferVoltageUpperBound OBJECT-TYPE
    SYNTAX Unsigned32
    UNITS "Volts"
    MAX-ACCESS read-only
    STATUS current
    DESCRIPTION
        "The upper boundary value of tlpAtsInputBadTransferVoltage as dictated
        by the hardware of the unit."
    ::= { tlpAtsInputEntry 6 }

tlpAtsInputHighTransferVoltage OBJECT-TYPE
    SYNTAX Unsigned32
    UNITS "0.1 Volts"
    MAX-ACCESS read-only
    STATUS current
    DESCRIPTION
        "The maximum line voltage allowed before the unit disconnects the
        AC input connection."
    ::= { tlpAtsInputEntry 7 }

tlpAtsInputHighTransferVoltageLowerBound OBJECT-TYPE
    SYNTAX Unsigned32
    UNITS "Volts"
    MAX-ACCESS read-only
    STATUS current
    DESCRIPTION
        "The lower boundary value of tlpAtsInputHighTransferVoltage as dictated
        by the hardware of the unit."
    ::= { tlpAtsInputEntry 8 }

tlpAtsInputHighTransferVoltageUpperBound OBJECT-TYPE
    SYNTAX Unsigned32
    UNITS "Volts"
    MAX-ACCESS read-only
    STATUS current
    DESCRIPTION
        "The upper boundary value of tlpAtsInputHighTransferVoltage as dictated
        by the hardware of the unit."
    ::= { tlpAtsInputEntry 9 }

tlpAtsInputFairVoltageThreshold OBJECT-TYPE
    SYNTAX Unsigned32
    UNITS "Volts"
    MAX-ACCESS read-only
    STATUS current
    DESCRIPTION
        "The voltage level at which the device will transition between sources."
    ::= { tlpAtsInputEntry 10 }

tlpAtsInputBadVoltageThreshold OBJECT-TYPE
    SYNTAX Unsigned32
    UNITS "Volts"
    MAX-ACCESS read-only
    STATUS current
    DESCRIPTION
        "The minimum line voltage allowed before the device disconnects the AC input
        connection."
    ::= { tlpAtsInputEntry 11 }

tlpAtsInputSourceAvailability OBJECT-TYPE
    SYNTAX INTEGER {
        none(0),
        inputSourceA(1),
        inputSourceB(2),
        inputSourceAB(3) }
    MAX-ACCESS read-only
    STATUS current
    DESCRIPTION
        "The determination as to which of two AC input lines are available.
        The agent will return either inputSourceA(1) or inputSourceB(2) if
        only one line is available, or inputSourceAB(3) if both lines are
        available. The agent will never return none(0) since the device will
        be powered off if neither line is available."
    ::= { tlpAtsInputEntry 12 } 

tlpAtsInputSourceInUse OBJECT-TYPE
    SYNTAX INTEGER {
        inputSourceA(0),
        inputSourceB(1) }
    MAX-ACCESS read-only
    STATUS current
    DESCRIPTION
        "The determination as to which one of two AC input lines is in use. Not all
        devices support the reporting of which source is currently in use. If not
        supported, this value will always return ERROR_NO_SUCH_NAME."
    ::= { tlpAtsInputEntry 13 }

tlpAtsInputSourceTransitionCount OBJECT-TYPE
    SYNTAX Unsigned32
    MAX-ACCESS read-only
    STATUS current
    DESCRIPTION
        "The number of times the device transitions between primary and secondary
        sources. Most devices are limied to 65533 transitions, after which the
        value will not increment. If not supported, this value will always return
        ERROR_NO_SUCH_NAME."
    ::= { tlpAtsInputEntry 14 }

tlpAtsInputCurrentLimit OBJECT-TYPE
    SYNTAX Unsigned32
    UNITS "Amp DC"
    MAX-ACCESS read-only
    STATUS current
    DESCRIPTION
        "The capacity of each phase conductor in the ats limited by the AC input
        cord or any other potential limiting factors unique to a given unit. If not
        supported, this value will always return ERROR_NO_SUCH_NAME."
    ::= { tlpAtsInputEntry 15 }

tlpAtsInputPhaseTable OBJECT-TYPE
    SYNTAX SEQUENCE OF TlpAtsInputPhaseEntry
    MAX-ACCESS not-accessible
    STATUS current
    DESCRIPTION
        "The input phase details of each ats in device table. This is a sparse
        dependent table, and will contain the number of entries based upon
        the value of tlpAtsIdentNumInputs and tlpAtsIdentNumPhases per each
        device."
    ::= { tlpAtsInput 2 }

tlpAtsInputPhaseEntry OBJECT-TYPE
    SYNTAX TlpAtsInputPhaseEntry
    MAX-ACCESS not-accessible
    STATUS current
    DESCRIPTION
        "An entry containing information applicable to a particular primary
        input phase managed by this agent."
    INDEX { tlpDeviceIndex, tlpAtsInputLineIndex, tlpAtsInputPhaseIndex }
    ::= { tlpAtsInputPhaseTable 1 }

TlpAtsInputPhaseEntry ::= SEQUENCE {
    tlpAtsInputLineIndex                    Unsigned32,
    tlpAtsInputPhaseIndex                   Unsigned32,
    tlpAtsInputPhaseType                    INTEGER,
    tlpAtsInputPhaseFrequency               Unsigned32,
    tlpAtsInputPhaseVoltage                 Unsigned32,
    tlpAtsInputPhaseVoltageMin              Unsigned32,
    tlpAtsInputPhaseVoltageMax              Unsigned32,
    tlpAtsInputPhaseCurrent                 Unsigned32 }

tlpAtsInputLineIndex OBJECT-TYPE
    SYNTAX Unsigned32
    MAX-ACCESS read-only
    STATUS current
    DESCRIPTION
        "The table row index for the input line on the ats."
    ::= { tlpAtsInputPhaseEntry 1 }

tlpAtsInputPhaseIndex OBJECT-TYPE
    SYNTAX Unsigned32
    MAX-ACCESS read-only
    STATUS current
    DESCRIPTION
        "The table row index for the input phase for the input line."
    ::= { tlpAtsInputPhaseEntry 2 }

tlpAtsInputPhaseType OBJECT-TYPE
    SYNTAX INTEGER {
        phaseToNeutral(0),
        phaseToPhase(1) }
    MAX-ACCESS read-only
    STATUS current
    DESCRIPTION
        "Denotes whether measurements are phase to neutral(0) or phase
        to phase(1)."
    ::= { tlpAtsInputPhaseEntry 3 }

tlpAtsInputPhaseFrequency OBJECT-TYPE
    SYNTAX Unsigned32
    UNITS "0.1 Hertz"
    MAX-ACCESS read-only
    STATUS current
    DESCRIPTION
        "The present input frequency for a given phase."
    ::= { tlpAtsInputPhaseEntry 4 }

tlpAtsInputPhaseVoltage OBJECT-TYPE
    SYNTAX Unsigned32
    UNITS "0.1 Volt DC"
    MAX-ACCESS read-only
    STATUS current
    DESCRIPTION
        "The magnitude of the present input voltage for a given phase."
    ::= { tlpAtsInputPhaseEntry 5 }

tlpAtsInputPhaseVoltageMin OBJECT-TYPE
    SYNTAX Unsigned32
    UNITS "0.1 Volt DC"
    MAX-ACCESS read-write
    STATUS current
    DESCRIPTION
        "The minimum input voltage value since the last reset of this
        value for a given phase. If any value is written to either
        tlpAtsInputVoltageMin or tlpAtsInputVoltageMax, both
        will be reset to their appropriate minimum and maximum values."
    ::= { tlpAtsInputPhaseEntry 6 }

tlpAtsInputPhaseVoltageMax OBJECT-TYPE
    SYNTAX Unsigned32
    UNITS "0.1 Volt DC"
    MAX-ACCESS read-write
    STATUS current
    DESCRIPTION
        "The maximum input voltage value since the last reset of this
        value for a given phase. If any value is written to either
        tlpAtsInputVoltageMin or tlpAtsInputVoltageMax, both
        will be reset to their appropriate minimum and maximum values."
    ::= { tlpAtsInputPhaseEntry 7 }

tlpAtsInputPhaseCurrent OBJECT-TYPE
    SYNTAX Unsigned32
    UNITS "0.01 Amp DC"
    MAX-ACCESS read-only
    STATUS current
    DESCRIPTION
        "The magnitude of the present input current for a given phase."
    ::= { tlpAtsInputPhaseEntry 8 }

tlpAtsOutputTable OBJECT-TYPE
    SYNTAX SEQUENCE OF TlpAtsOutputEntry
    MAX-ACCESS not-accessible
    STATUS current
    DESCRIPTION
        "The output details of each ats in device table. This is a sparse
        dependent table, and will contain the number of entries based upon
        the value of tlpAtsIdentNumOutputs per each device."
    ::= { tlpAtsOutput 1 }

tlpAtsOutputEntry OBJECT-TYPE
    SYNTAX TlpAtsOutputEntry
    MAX-ACCESS not-accessible
    STATUS current
    DESCRIPTION
        "An entry containing output information applicable to a particular
        phase managed by this agent."
    INDEX { tlpDeviceIndex, tlpAtsOutputIndex }
    ::= { tlpAtsOutputTable 1 }

TlpAtsOutputEntry ::= SEQUENCE {
    tlpAtsOutputIndex               Unsigned32,
    tlpAtsOutputPhase               INTEGER,
    tlpAtsOutputPhaseType           INTEGER,
    tlpAtsOutputVoltage             Unsigned32,
    tlpAtsOutputCurrent             Unsigned32,
    tlpAtsOutputCurrentMin          Unsigned32,
    tlpAtsOutputCurrentMax          Unsigned32,
    tlpAtsOutputActivePower         Unsigned32,
    tlpAtsOutputPowerFactor         Unsigned32,
    tlpAtsOutputSource              INTEGER }

tlpAtsOutputIndex OBJECT-TYPE
    SYNTAX Unsigned32
    MAX-ACCESS read-only
    STATUS current
    DESCRIPTION
        "The table row index for the ats phase."
    ::= { tlpAtsOutputEntry 1 }

tlpAtsOutputPhase OBJECT-TYPE
    SYNTAX INTEGER {
        phase1(1),
        phase2(2),
        phase3(3) }
    MAX-ACCESS read-only
    STATUS current
    DESCRIPTION
        "Indicates the phase associated with the output line."
    ::= { tlpAtsOutputEntry 2 }

tlpAtsOutputPhaseType OBJECT-TYPE
    SYNTAX INTEGER {
        phaseToNeutral(0),
        phaseToPhase(1) }
    MAX-ACCESS read-only
    STATUS current
    DESCRIPTION
        "Denotes whether measurements are phase to neutral(0) or phase
        to phase(1)."
    ::= { tlpAtsOutputEntry 3 }

tlpAtsOutputVoltage OBJECT-TYPE
    SYNTAX Unsigned32
    UNITS "0.1 Volt DC"
    MAX-ACCESS read-only
    STATUS current
    DESCRIPTION
        "The magnitude of the present output voltage for a given output line."
    ::= { tlpAtsOutputEntry 4 }

tlpAtsOutputCurrent OBJECT-TYPE
    SYNTAX Unsigned32
    UNITS "0.01 Amp DC"
    MAX-ACCESS read-only
    STATUS current
    DESCRIPTION
        "The output current, in hundreths of amps, for a given phase."
    ::= { tlpAtsOutputEntry 5 }

tlpAtsOutputCurrentMin OBJECT-TYPE
    SYNTAX Unsigned32
    UNITS "0.01 Amp DC"
    MAX-ACCESS read-only
    STATUS current
    DESCRIPTION
        "The minimum current observed for a given phase since last reset."
    ::= { tlpAtsOutputEntry 6 }

tlpAtsOutputCurrentMax OBJECT-TYPE
    SYNTAX Unsigned32
    UNITS "0.01 Amp DC"
    MAX-ACCESS read-only
    STATUS current
    DESCRIPTION
        "The maximum current observed for a given phase since last reset."
    ::= { tlpAtsOutputEntry 7 }

tlpAtsOutputActivePower OBJECT-TYPE
    SYNTAX Unsigned32
    UNITS "Watts"
    MAX-ACCESS read-only
    STATUS current
    DESCRIPTION
        "The output power for a given phase."
    ::= { tlpAtsOutputEntry 8 }

tlpAtsOutputPowerFactor OBJECT-TYPE
    SYNTAX Unsigned32
    UNITS "0.01 percent"
    MAX-ACCESS read-only
    STATUS current
    DESCRIPTION
        "The output power factor, in hundreths of a percent, for a given
        phase."
    ::= { tlpAtsOutputEntry 9 }

tlpAtsOutputSource OBJECT-TYPE
    SYNTAX INTEGER {
        none(0),
        normal(1) }
    MAX-ACCESS read-only
    STATUS current
    DESCRIPTION
        "The present source of output power. The enumeration none(0)
        indicates that there is no source of output power (and
        therefore no output power), for example, the system has opened
        the output breaker."
    ::= { tlpAtsOutputEntry 10 }

tlpAtsOutletTable OBJECT-TYPE
    SYNTAX SEQUENCE OF TlpAtsOutletEntry
    MAX-ACCESS not-accessible
    STATUS current
    DESCRIPTION
        "The receptacle status details of each ats in device table. This
        is a sparse dependent table, and will contain the number of entries
        based upon the value of tlpAtsIdentNumOutlets per each device."
    ::= { tlpAtsOutlet 1 }

tlpAtsOutletEntry OBJECT-TYPE
    SYNTAX TlpAtsOutletEntry
    MAX-ACCESS not-accessible
    STATUS current
    DESCRIPTION
        "An entry containing information applicable to a particular outlet
        managed by this agent."
    INDEX { tlpDeviceIndex, tlpAtsOutletIndex }
    ::= { tlpAtsOutletTable 1 }

TlpAtsOutletEntry ::= SEQUENCE {
    tlpAtsOutletIndex                   Unsigned32,
    tlpAtsOutletName                    DisplayString,
    tlpAtsOutletDescription             DisplayString,
    tlpAtsOutletState                   INTEGER,
    tlpAtsOutletControllable            TruthValue,
    tlpAtsOutletCommand                 INTEGER,
    tlpAtsOutletVoltage                 Unsigned32,
    tlpAtsOutletCurrent                 Unsigned32,
    tlpAtsOutletPower                   Unsigned32,
    tlpAtsOutletRampAction              INTEGER,
    tlpAtsOutletRampDelay               Integer32,
    tlpAtsOutletShedAction              INTEGER,
    tlpAtsOutletShedDelay               Integer32,
    tlpAtsOutletGroup                   Integer32,
    tlpAtsOutletBank                    Integer32,
    tlpAtsOutletCircuit                 Integer32,
    tlpAtsOutletPhase                   INTEGER }

tlpAtsOutletIndex OBJECT-TYPE
    SYNTAX Unsigned32
    MAX-ACCESS read-only
    STATUS current
    DESCRIPTION
        "The table row index for the ats outlet."
    ::= { tlpAtsOutletEntry 1 }

tlpAtsOutletName OBJECT-TYPE
    SYNTAX DisplayString
    MAX-ACCESS read-write
    STATUS current
    DESCRIPTION
        "A user-definable string identifying the name of the outlet."
    ::= { tlpAtsOutletEntry 2 }

tlpAtsOutletDescription OBJECT-TYPE
    SYNTAX DisplayString
    MAX-ACCESS read-write
    STATUS current
    DESCRIPTION
        "A user-definable string identifying the device(s) connected to
        the given outlet."
    ::= { tlpAtsOutletEntry 3 }

tlpAtsOutletState OBJECT-TYPE
    SYNTAX INTEGER {
        unknown(0),
        off(1),
        on(2) }
    MAX-ACCESS read-only
    STATUS current
    DESCRIPTION
        "The current state of the outlet."
    ::= { tlpAtsOutletEntry 4 }

tlpAtsOutletControllable OBJECT-TYPE
    SYNTAX TruthValue
    MAX-ACCESS read-only
    STATUS current
    DESCRIPTION
        "Denotes whether this outlet is controllable."
    ::= { tlpAtsOutletEntry 5 }

tlpAtsOutletCommand OBJECT-TYPE
    SYNTAX INTEGER {
        idle(0),
        turnOff(1),
        turnOn(2),
        cycle(3) }
    MAX-ACCESS read-write
    STATUS current
    DESCRIPTION
        "Reading this value will always return 0. Setting this value
        to turnOff(1) will turn off the outlet. Setting this value
        to turnOn(2) will turn on the outlet. Setting this value to
        cycle(3) will turn the outlet off, then turn it back on."
    ::= { tlpAtsOutletEntry 6 }

tlpAtsOutletVoltage OBJECT-TYPE
    SYNTAX Unsigned32
    UNITS "0.1 Volt DC"
    MAX-ACCESS read-only
    STATUS current
    DESCRIPTION
        "The magnitude of the present output voltage for a given outlet.
        If the voltage measurement is not supported for an individual
        receptacle regardless whether device-wide or just for this
        receptacle, then this value will always return ERROR_NO_SUCH_NAME.
        Device-wide support for receptacle voltage measurements is denoted
        by tlpAtsSupportsOutletVoltage."
    ::= { tlpAtsOutletEntry 7 }

tlpAtsOutletCurrent OBJECT-TYPE
    SYNTAX Unsigned32
    UNITS "0.01 RMS Amp"
    MAX-ACCESS read-only
    STATUS current
    DESCRIPTION
        "The present output current, in hundreths of amps, of a given outlet.
        If the current measurement is not supported for an individual
        receptacle regardless whether device-wide or just for this
        receptacle, then this value will always return ERROR_NO_SUCH_NAME.
        Device-wide support for receptacle current measurements is denoted
        by tlpAtsSupportsCurrentPower."
    ::= { tlpAtsOutletEntry 8 }

tlpAtsOutletPower OBJECT-TYPE
    SYNTAX Unsigned32
    UNITS "Watts"
    MAX-ACCESS read-only
    STATUS current
    DESCRIPTION
        "The output power of a given outlet. If the power measurement is
        not supported for an individual receptacle regardless whether
        device-wide or just for this receptacle, then this value will
        always return ERROR_NO_SUCH_NAME. Device-wide support for receptacle
        power measurements is denoted by tlpAtsSupportsCurrentPower."
    ::= { tlpAtsOutletEntry 9 }

tlpAtsOutletRampAction OBJECT-TYPE
    SYNTAX INTEGER {
        remainOff(0),
        turnOnAfterDelay(1)
    }
    MAX-ACCESS read-write
    STATUS current
    DESCRIPTION
        "The ramp action to take on a given outlet when powering on the
        device. If this receptacle is not controllable, as denoted by
        tlpAtsOutletControllable, then this value will always return
        ERROR_NO_SUCH_NAME."
    ::= { tlpAtsOutletEntry 10 }

tlpAtsOutletRampDelay OBJECT-TYPE
    SYNTAX Integer32
    UNITS "seconds"
    MAX-ACCESS read-write
    STATUS current
    DESCRIPTION
        "The number of seconds to delay before powering on the given outlet.
        If this receptacle is not controllable, as denoted by
        tlpAtsOutletControllable, then this value will always return
        ERROR_NO_SUCH_NAME."
    ::= { tlpAtsOutletEntry 11 }

tlpAtsOutletShedAction OBJECT-TYPE
    SYNTAX INTEGER {
        remainOn(0),
        turnOffAfterDelay(1)
    }
    MAX-ACCESS read-write
    STATUS current
    DESCRIPTION
        "The shed action to take on a given outlet when powering off the
        device. If this receptacle is not controllable, as denoted by
        tlpAtsOutletControllable, then this value will always return
        ERROR_NO_SUCH_NAME."
    ::= { tlpAtsOutletEntry 12 }

tlpAtsOutletShedDelay OBJECT-TYPE
    SYNTAX Integer32
    UNITS "seconds"
    MAX-ACCESS read-write
    STATUS current
    DESCRIPTION
        "The number of seconds to delay before powering off the given outlet.
        If this receptacle is not controllable, as denoted by
        tlpAtsOutletControllable, then this value will always return
        ERROR_NO_SUCH_NAME."
    ::= { tlpAtsOutletEntry 13 }

tlpAtsOutletGroup OBJECT-TYPE
    SYNTAX Integer32
    MAX-ACCESS read-write
    STATUS current
    DESCRIPTION
        "The tlpAtsOutletGroupIndex group index of the respective group to
        which the given outlet is assigned, or zero (0) if the given
        outlet is not grouped."
    ::= { tlpAtsOutletEntry 14 }

tlpAtsOutletBank OBJECT-TYPE
    SYNTAX Integer32
    MAX-ACCESS read-only
    STATUS current
    DESCRIPTION
        "Indicates on which bank the given outlet is located."
    ::= { tlpAtsOutletEntry 15 }

tlpAtsOutletCircuit OBJECT-TYPE
    SYNTAX Integer32
    MAX-ACCESS read-only
    STATUS current
    DESCRIPTION
        "Indicates on which circuit the given outlet is wired."
    ::= { tlpAtsOutletEntry 16 }

tlpAtsOutletPhase OBJECT-TYPE
    SYNTAX INTEGER {
        unknown(0),
        phase1(1),
        phase2(2),
        phase3(3),
        phase1-2(4),
        phase2-3(5),
        phase3-1(6) }
    MAX-ACCESS read-only
    STATUS current
    DESCRIPTION
        "Indicates on which phase or phases the given outlet is
        associated. For single phase devices, this object will
        always return phase1(1). For 3-phase devices with outlets
        wired to a single phase, this object will return phase1(1),
        phase2(2) or phase3(3). For 3-phase devices with outlets
        wired to two phases, this object will return phase1-2(4)
        for phases 1 and 2, phase2-3(5) for phases 2 and 3, and
        phase3-1(6) for phases 3 and 1. Devices that do not report
        phase connections will return unknown(0)."
    ::= { tlpAtsOutletEntry 17 }

tlpAtsOutletGroupTable OBJECT-TYPE
    SYNTAX SEQUENCE OF TlpAtsOutletGroupEntry
    MAX-ACCESS not-accessible
    STATUS current
    DESCRIPTION
        "The receptacle grouping details of each ats in device table.
        This is a sparse dependent table, and will contain the number
        of entries based upon the value of tlpAtsIdentNumOutletGroups per
        each device."
    ::= { tlpAtsOutlet 2 }

tlpAtsOutletGroupEntry OBJECT-TYPE
    SYNTAX TlpAtsOutletGroupEntry
    MAX-ACCESS not-accessible
    STATUS current
    DESCRIPTION
        "An entry containing information applicable to a particular outlet
        group managed by this agent."
    INDEX { tlpDeviceIndex, tlpAtsOutletGroupIndex }
    ::= { tlpAtsOutletGroupTable 1 }

TlpAtsOutletGroupEntry ::= SEQUENCE {
    tlpAtsOutletGroupIndex              Unsigned32,
    tlpAtsOutletGroupRowStatus	        RowStatus,
    tlpAtsOutletGroupName               DisplayString,
    tlpAtsOutletGroupDescription        DisplayString,
    tlpAtsOutletGroupState              INTEGER,
    tlpAtsOutletGroupCommand            INTEGER }

tlpAtsOutletGroupIndex OBJECT-TYPE
    SYNTAX Unsigned32
    MAX-ACCESS read-only
    STATUS current
    DESCRIPTION
        "The table row index for the ats outlet group."
    ::= { tlpAtsOutletGroupEntry 1 }

tlpAtsOutletGroupRowStatus OBJECT-TYPE
    SYNTAX RowStatus
    MAX-ACCESS read-write
    STATUS current
    DESCRIPTION
        "Row status for the tlpAtsOutletGroupTable"
    ::= { tlpAtsOutletGroupEntry 2 }

tlpAtsOutletGroupName OBJECT-TYPE
    SYNTAX DisplayString
    MAX-ACCESS read-write
    STATUS current
    DESCRIPTION
        "The name of this outlet group."
    ::= { tlpAtsOutletGroupEntry 3 }

tlpAtsOutletGroupDescription OBJECT-TYPE
    SYNTAX DisplayString
    MAX-ACCESS read-write
    STATUS current
    DESCRIPTION
        "A description for this outlet group."
    ::= { tlpAtsOutletGroupEntry 4 }

tlpAtsOutletGroupState OBJECT-TYPE
    SYNTAX INTEGER {
        unknown(0),
        off(1),
        on(2),
        mixed(3) }
    MAX-ACCESS read-only
    STATUS current
    DESCRIPTION
        "The current state of the outlet group. This value will report
        off(1) if all outlets in the group are off, on(2) if all outlets
        in the group are on, mixed(3) if some outlets in the group are
        off and others are on, or unknown(0) if the state of the outlets
        cannot be determined."
    ::= { tlpAtsOutletGroupEntry 5 }

tlpAtsOutletGroupCommand OBJECT-TYPE
    SYNTAX INTEGER {
        turnOff(1),
        turnOn(2),
        cycle(3) }
    MAX-ACCESS read-write
    STATUS current
    DESCRIPTION
        "Reading this value will always return 0. Setting this value to
        turnOff(1) will turn off every outlet associated with the group.
        Setting this value to turnOn(2) will turn on every outlet associated
        with the group. Setting this value to cycle(3) will turn off every
        outlet associated with the group, then turn each outlet back on."
    ::= { tlpAtsOutletGroupEntry 6 }

tlpAtsCircuitTable OBJECT-TYPE
    SYNTAX SEQUENCE OF TlpAtsCircuitEntry
    MAX-ACCESS not-accessible
    STATUS current
    DESCRIPTION
        "A list of ats circuit table entries.  The number of entries
        is given by the value of tlpAtsIdentNumCircuits."
    ::= { tlpAtsCircuit 1 }

tlpAtsCircuitEntry OBJECT-TYPE
    SYNTAX TlpAtsCircuitEntry
    MAX-ACCESS not-accessible
    STATUS current
    DESCRIPTION
        "An entry containing information applicable to a particular circuit
        managed by this agent."
    INDEX { tlpDeviceIndex, tlpAtsCircuitIndex }
    ::= { tlpAtsCircuitTable 1 }

TlpAtsCircuitEntry ::= SEQUENCE {
    tlpAtsCircuitIndex              Unsigned32,
    tlpAtsCircuitPhase              INTEGER,
    tlpAtsCircuitInputVoltage       Integer32,
    tlpAtsCircuitTotalCurrent       Integer32,
    tlpAtsCircuitCurrentLimit       Integer32,
    tlpAtsCircuitCurrentMin         Integer32,
    tlpAtsCircuitCurrentMax         Integer32,
    tlpAtsCircuitTotalPower         Integer32,
    tlpAtsCircuitPowerFactor        INTEGER,
    tlpAtsCircuitUtilization        Unsigned32 }

tlpAtsCircuitIndex OBJECT-TYPE
    SYNTAX Unsigned32
    MAX-ACCESS read-only
    STATUS current
    DESCRIPTION
        "The table row index for the ats circuit."
    ::= { tlpAtsCircuitEntry 1 }

tlpAtsCircuitPhase OBJECT-TYPE
    SYNTAX INTEGER {
        unknown(0),
        phase1(1),
        phase2(2),
        phase3(3),
        phase1-2(4),
        phase2-3(5),
        phase3-1(6) }
    MAX-ACCESS read-only
    STATUS current
    DESCRIPTION
        "Indicates on which phase or phases the given circuit is
        wired. For single phase devices, this object will always
        return phase1(1). For 3-phase devices with outlets wired
        to a single phase, this object will return phase1(1),
        phase2(2) or phase3(3). For 3-phase devices with outlets
        wired to two phases, this object will return phase1-2(4)
        for phases 1 and 2, phase2-3(5) for phases 2 and 3, and
        phase3-1(6) for phases 3 and 1. Devices that do not report
        phase connections will return unknown(0)."
    ::= { tlpAtsCircuitEntry 2 }

tlpAtsCircuitInputVoltage OBJECT-TYPE
    SYNTAX Integer32
    UNITS "0.1 Volt DC"
    MAX-ACCESS read-only
    STATUS current
    DESCRIPTION
        "The input voltage for a circuit."
    ::= { tlpAtsCircuitEntry 3 }

tlpAtsCircuitTotalCurrent OBJECT-TYPE
    SYNTAX Integer32
    UNITS "0.01 Amp DC"
    MAX-ACCESS read-only
    STATUS current
    DESCRIPTION
        "The total current for all receptacles in a given circuit."
    ::= { tlpAtsCircuitEntry 4 }

tlpAtsCircuitCurrentLimit OBJECT-TYPE
    SYNTAX Integer32
    UNITS "0.01 Amp DC"
    MAX-ACCESS read-only
    STATUS current
    DESCRIPTION
        "The current capacity of a circuit in the system limited by
        the circuit breaker or wiring used in a given unit."
    ::= { tlpAtsCircuitEntry 5 }

tlpAtsCircuitCurrentMin OBJECT-TYPE
    SYNTAX Integer32
    UNITS "0.01 Amp DC"
    MAX-ACCESS read-only
    STATUS current
    DESCRIPTION
        "The minimum total current for all receptacles in a given
        circuit since last reset."
    ::= { tlpAtsCircuitEntry 6 }

tlpAtsCircuitCurrentMax OBJECT-TYPE
    SYNTAX Integer32
    UNITS "0.01 Amp DC"
    MAX-ACCESS read-only
    STATUS current
    DESCRIPTION
        "The maximum total current for all receptacles in a given
        circuit since last reset."
    ::= { tlpAtsCircuitEntry 7 }

tlpAtsCircuitTotalPower OBJECT-TYPE
    SYNTAX Integer32
    UNITS "Watts"
    MAX-ACCESS read-only
    STATUS current
    DESCRIPTION
        "The total power for all receptacles in a given circuit."
    ::= { tlpAtsCircuitEntry 8 }

tlpAtsCircuitPowerFactor OBJECT-TYPE
    SYNTAX INTEGER (0..200)
    UNITS "percent"
    MAX-ACCESS read-only
    STATUS current
    DESCRIPTION
        "The power factor for all receptacles in a given circuit."
    ::= { tlpAtsCircuitEntry 9 }

tlpAtsCircuitUtilization OBJECT-TYPE
    SYNTAX Unsigned32
    UNITS "0.01 %"
    MAX-ACCESS read-only
    STATUS current
    DESCRIPTION
        "The percentage of utilization of a given circuit. This is typically
        a calculation of tlpAtsCircuitTotalCurrent / tlpAtsCircuitCurrentLimit."
    ::= { tlpAtsCircuitEntry 10 }

tlpAtsBreakerTable OBJECT-TYPE
    SYNTAX SEQUENCE OF TlpAtsBreakerEntry
    MAX-ACCESS not-accessible
    STATUS current
    DESCRIPTION
        "A list of ats bank breaker table entries. The number of entries
        is given by the value of tlpAtsIdentNumBreakers."
    ::= { tlpAtsBreaker 1 }

tlpAtsBreakerEntry OBJECT-TYPE
    SYNTAX TlpAtsBreakerEntry
    MAX-ACCESS not-accessible
    STATUS current
    DESCRIPTION
        "An entry containing information applicable to a particular bank
        breaker managed by this agent."
    INDEX { tlpDeviceIndex, tlpAtsBreakerIndex }
    ::= { tlpAtsBreakerTable 1 }

TlpAtsBreakerEntry ::= SEQUENCE {
    tlpAtsBreakerIndex          Unsigned32,
    tlpAtsBreakerStatus         INTEGER }

tlpAtsBreakerIndex OBJECT-TYPE
    SYNTAX Unsigned32
    MAX-ACCESS read-only
    STATUS current
    DESCRIPTION
        "The table row index for the ats bank breaker."
    ::= { tlpAtsBreakerEntry 1 }

tlpAtsBreakerStatus OBJECT-TYPE
    SYNTAX INTEGER {
        open(0),
        closed(1),
        notInstalled(2) }
    MAX-ACCESS read-only
    STATUS current
    DESCRIPTION
        "Indicates whether the bank breaker is open(0), closed(1) or not
        installed(2)."
    ::= { tlpAtsBreakerEntry 2 }

tlpAtsHeatsinkTable OBJECT-TYPE
    SYNTAX SEQUENCE OF TlpAtsHeatsinkEntry
    MAX-ACCESS not-accessible
    STATUS current
    DESCRIPTION
        "A list of ats heatsink thermistor table entries. The number of entries
        is given by the value of tlpAtsIdentNumHeatsinks."
    ::= { tlpAtsHeatsink 1 }

tlpAtsHeatsinkEntry OBJECT-TYPE
    SYNTAX TlpAtsHeatsinkEntry
    MAX-ACCESS not-accessible
    STATUS current
    DESCRIPTION
        "An entry containing information applicable to a particular heatsink
        thermistor managed by this agent."
    INDEX { tlpDeviceIndex, tlpAtsHeatsinkIndex }
    ::= { tlpAtsHeatsinkTable 1 }

TlpAtsHeatsinkEntry ::= SEQUENCE {
    tlpAtsHeatsinkIndex             Unsigned32,
    tlpAtsHeatsinkStatus            INTEGER,
    tlpAtsHeatsinkTemperatureC      Integer32,
    tlpAtsHeatsinkTemperatureF      Integer32 }

tlpAtsHeatsinkIndex OBJECT-TYPE
    SYNTAX Unsigned32
    MAX-ACCESS read-only
    STATUS current
    DESCRIPTION
        "The table row index for the ats heatsink thermistor."
    ::= { tlpAtsHeatsinkEntry 1 }

tlpAtsHeatsinkStatus OBJECT-TYPE
    SYNTAX INTEGER {
        notAvailable(0),
        available(1) }
    MAX-ACCESS read-only
    STATUS current
    DESCRIPTION
        "Indicates whether the heatsink thermistor is available. The entry
        will return notAvailable(0) if a thermistor is either non-existent or
        disconnected, or available(1) when connected."
    ::= { tlpAtsHeatsinkEntry 2 }

tlpAtsHeatsinkTemperatureC OBJECT-TYPE
    SYNTAX Integer32
    UNITS "0.1 degrees Centigrade"
    MAX-ACCESS read-only
    STATUS current
    DESCRIPTION
        "The temperature at the heatsink termistor in tenths degrees Centigrade.
        Heatsink temperature measurements are not supported on all models. If
        not supported, this value will always return ERROR_NO_SUCH_NAME."
    ::= { tlpAtsHeatsinkEntry 3 }

tlpAtsHeatsinkTemperatureF OBJECT-TYPE
    SYNTAX Integer32
    UNITS "0.1 degrees Farenheit"
    MAX-ACCESS read-only
    STATUS current
    DESCRIPTION
        "The temperature at the heatsink termistor in tenths degrees Farenheit.
        Heatsink temperature measurements are not supported on all models. If
        not supported, this value will always return ERROR_NO_SUCH_NAME."
    ::= { tlpAtsHeatsinkEntry 4 }

tlpAtsControlTable OBJECT-TYPE
    SYNTAX SEQUENCE OF TlpAtsControlEntry
    MAX-ACCESS not-accessible
    STATUS current
    DESCRIPTION
        "The actionable controls for each ats in device table. This is a
        sparse dependent table, and will contain some subset of devices
        that are atss."
    ::= { tlpAtsControl 1 }

tlpAtsControlEntry OBJECT-TYPE
    SYNTAX TlpAtsControlEntry
    MAX-ACCESS not-accessible
    STATUS current
    DESCRIPTION
        "An entry containing controls for a particular ats."
    INDEX { tlpDeviceIndex }
    ::= { tlpAtsControlTable 1 }

TlpAtsControlEntry ::= SEQUENCE {
    tlpAtsControlRamp               TruthValue,
    tlpAtsControlShed               TruthValue,
    tlpAtsControlAtsOn              TruthValue,
    tlpAtsControlAtsOff             TruthValue,
    tlpAtsControlAtsReboot          TruthValue,
    tlpAtsControlResetGeneralFault  TruthValue }

tlpAtsControlRamp OBJECT-TYPE
    SYNTAX TruthValue
    MAX-ACCESS read-write
    STATUS current
    DESCRIPTION
        "Set to TRUE to initiate the pre-designated ramp
        sequence on the ats."
    ::= { tlpAtsControlEntry 1 }
  
tlpAtsControlShed OBJECT-TYPE
    SYNTAX TruthValue
    MAX-ACCESS read-write
    STATUS current
    DESCRIPTION
        "Set to TRUE to initiate the pre-designated shed
        sequence on the ats."
    ::= { tlpAtsControlEntry 2 }
  
tlpAtsControlAtsOn OBJECT-TYPE
    SYNTAX TruthValue
    MAX-ACCESS read-write
    STATUS current
    DESCRIPTION
        "Set to TRUE to turn the ats on."
    ::= { tlpAtsControlEntry 3 }

tlpAtsControlAtsOff OBJECT-TYPE
    SYNTAX TruthValue
    MAX-ACCESS read-write
    STATUS current
    DESCRIPTION
        "Set to TRUE to turn the ats off."
    ::= { tlpAtsControlEntry 4 }

tlpAtsControlAtsReboot OBJECT-TYPE
    SYNTAX TruthValue
    MAX-ACCESS read-write
    STATUS current
    DESCRIPTION
        "Set to TRUE to reboot the ats."
    ::= { tlpAtsControlEntry 5 }

tlpAtsControlResetGeneralFault OBJECT-TYPE
    SYNTAX TruthValue
    MAX-ACCESS read-write
    STATUS current
    DESCRIPTION
        "Set to TRUE to reset the general fault alarm indicated by
        tlpAtsDeviceGeneralFault."
    ::= { tlpAtsControlEntry 6 }

tlpAtsConfigTable OBJECT-TYPE
    SYNTAX SEQUENCE OF TlpAtsConfigEntry
    MAX-ACCESS not-accessible
    STATUS current
    DESCRIPTION
        "The configuration options of each ats in device table. This
        is a sparse dependent table, and will contain some subset of
        devices that are atss. Not all options are available on all
        atss."
    ::= { tlpAtsConfig 1 }

tlpAtsConfigEntry OBJECT-TYPE
    SYNTAX TlpAtsConfigEntry
    MAX-ACCESS not-accessible
    STATUS current
    DESCRIPTION
        "An entry containing configuration options for a particular ats."
    INDEX { tlpDeviceIndex }
    ::= { tlpAtsConfigTable 1 }

TlpAtsConfigEntry ::= SEQUENCE {
    tlpAtsConfigInputVoltage                Unsigned32,
    tlpAtsConfigSourceSelect                INTEGER,
    tlpAtsConfigSource1ReturnTime           Unsigned32,
    tlpAtsConfigSource2ReturnTime           Unsigned32,
    tlpAtsConfigAutoRampOnTransition        INTEGER,
    tlpAtsConfigAutoShedOnTransition        INTEGER }

tlpAtsConfigInputVoltage OBJECT-TYPE
    SYNTAX Unsigned32
    MAX-ACCESS read-write
    STATUS current
    DESCRIPTION
        "The nominal value of the input line voltage. This value may not
        be supported on all models. If not supported, this value will return
        ERROR_NO_SUCH_NAME. This value may not be writable on all models. If
        not writable, the value will be rejected and an appropriate error
        message will be returned."
    ::= { tlpAtsConfigEntry 1 }

tlpAtsConfigSourceSelect OBJECT-TYPE
    SYNTAX INTEGER {
        inputSourceA(1),
        inputSourceB(2) }
    MAX-ACCESS read-write
    STATUS current
    DESCRIPTION
        "The determination as to which of two AC input lines is designated
        as the primary input source. The other is designated as the
        secondary input source. This value will always return inputSourceA(1)
        for devices with a single input source. Setting this value is
        supported only on selected models."
    ::= { tlpAtsConfigEntry 2 }

tlpAtsConfigSource1ReturnTime OBJECT-TYPE
    SYNTAX Unsigned32
    MAX-ACCESS read-write
    STATUS current
    DESCRIPTION
        "The nominal time to delay a transition to Source 1, if it is the
        preferred source."
    ::= { tlpAtsConfigEntry 3 }

tlpAtsConfigSource2ReturnTime OBJECT-TYPE
    SYNTAX Unsigned32
    MAX-ACCESS read-write
    STATUS current
    DESCRIPTION
        "The nominal time to delay a transition to Source 2, if it is the
        preferred source."
    ::= { tlpAtsConfigEntry 4 }

tlpAtsConfigAutoRampOnTransition OBJECT-TYPE
    SYNTAX INTEGER {
        disabled(0),
        enabled(1) }
    MAX-ACCESS read-write
    STATUS current
    DESCRIPTION
        "When enabled(1), the ats should perform its preconfigured ramp sequence when
        the input source transfers from its designated secondary source to its
        designated primary source. This value not supported on all ats devices. If not
        supported, then this value will always return ERROR_NO_SUCH_NAME."
    ::= { tlpAtsConfigEntry 5 }

tlpAtsConfigAutoShedOnTransition OBJECT-TYPE
    SYNTAX INTEGER {
        disabled(0),
        enabled(1) }
    MAX-ACCESS read-write
    STATUS current
    DESCRIPTION
        "When enabled(1), the ats should perform its preconfigured shed sequence when
        the input source transfers from its designated primary source to its designated
        secondary source. This value not supported on all ats devices. If not supported,
        then this value will always return ERROR_NO_SUCH_NAME."
    ::= { tlpAtsConfigEntry 6 }

tlpAtsConfigVoltageRangeTable OBJECT-TYPE
    SYNTAX SEQUENCE OF TlpAtsConfigVoltageRangeEntry
    MAX-ACCESS not-accessible
    STATUS current
    DESCRIPTION
        "The voltage range options in this table is intended to configure the
        operating voltages of an ats. This is a sparse dependent table, and will
        contain some subset of devices that are atss. All voltage points defined
        in this table are listed in a specific order from high to low. All voltage
        points must satsify the conditions and ranges defined for each point. Any
        point violating any of the relative limits will be rejected.

        For optimal operation, it is recommended that tlpAtsConfigHighVoltageReset
        be set lower than tlpAtsConfigHighVoltageTransfer by a margin no less than 1%
        of tlpAtsConfigHighVoltageTransfer; and that tlpAtsConfigSource1TransferReset
        (tlpAtsConfigSource2TransferReset) be set higher than
        tlpAtsConfigSource1BrownoutSet (tlpAtsConfigSource2BrownoutSet) by a margin no
        less than 1% of tlpAtsConfigSource1BrownoutSet (tlpAtsConfigSource2BrownoutSet).

        *The upper limit of line voltage is tlpAtsInputHighTransferVoltageUpperBound.
        The lower limit of line voltage is tlpAtsInputBadTransferVoltageLowerBound. All
        minimum and maximum limits for each voltage point are all exlusive unless
        indicated otherwise."
    ::= { tlpAtsConfig 2 }

tlpAtsConfigVoltageRangeEntry OBJECT-TYPE
    SYNTAX TlpAtsConfigVoltageRangeEntry
    MAX-ACCESS not-accessible
    STATUS current
    DESCRIPTION
        "An entry containing voltage range configuration options for a particular ats."
    INDEX { tlpDeviceIndex }
    ::= { tlpAtsConfigVoltageRangeTable 1 }

TlpAtsConfigVoltageRangeEntry ::= SEQUENCE {
    tlpAtsConfigHighVoltageTransfer     Unsigned32,
    tlpAtsConfigHighVoltageReset        Unsigned32,
    tlpAtsConfigSource1TransferReset    Unsigned32,
    tlpAtsConfigSource1BrownoutSet      Unsigned32,
    tlpAtsConfigSource1TransferSet      Unsigned32,
    tlpAtsConfigSource2TransferReset    Unsigned32,
    tlpAtsConfigSource2BrownoutSet      Unsigned32,
    tlpAtsConfigSource2TransferSet      Unsigned32,
    tlpAtsConfigLowVoltageReset         Unsigned32,
    tlpAtsConfigLowVoltageTransfer      Unsigned32 }

tlpAtsConfigHighVoltageTransfer OBJECT-TYPE
    SYNTAX Unsigned32
    UNITS "0.1 Volts"
    MAX-ACCESS read-write
    STATUS current
    DESCRIPTION
        "The maximum line voltage allowed before the unit disconnects the
        AC input connection. The maximum value allowed is dictated by
        tlpAtsInputHighTransferVoltageUpperBound (inclusively). The minimum
        value allowed is dictated by tlpAtsConfigHighVoltageReset. This value
        may not be configurable on all models. If not supported, this value will
        return ERROR_NO_SUCH_NAME."
    ::= { tlpAtsConfigVoltageRangeEntry 1 }

tlpAtsConfigHighVoltageReset OBJECT-TYPE
    SYNTAX Unsigned32
    UNITS "0.1 Volts"
    MAX-ACCESS read-write
    STATUS current
    DESCRIPTION
        "If a unit is disconnected due to over-voltage, the line voltage has to
        fall below this value before the unit re-connects the AC input connection.
        The maximum value allowed is dictated by tlpAtsConfigHighVoltageTransfer.
        The minimum value allowed is dictated by the greater of
        tlpAtsConfigSource1TransferReset and tlpAtsConfigSource2TransferReset. If
        not supported, this value will return ERROR_NO_SUCH_NAME."
    ::= { tlpAtsConfigVoltageRangeEntry 2 }

tlpAtsConfigSource1TransferReset OBJECT-TYPE
    SYNTAX Unsigned32
    UNITS "0.1 Volts"
    MAX-ACCESS read-write
    STATUS current
    DESCRIPTION
        "If input source 1 voltage level is above this value, a unit connected to
        source 2 will transition to source 1 (if it is the preferred source). The
        maximum value allowed is dictated by tlpAtsConfigHighVoltageReset. The
        minimum value allowed is dictated by tlpAtsConfigSource1BrownoutSet. If not
        supported, this value will return ERROR_NO_SUCH_NAME."
    ::= { tlpAtsConfigVoltageRangeEntry 3 }

tlpAtsConfigSource1BrownoutSet OBJECT-TYPE
    SYNTAX Unsigned32
    UNITS "0.1 Volts"
    MAX-ACCESS read-write
    STATUS current
    DESCRIPTION
        "This value dictates the voltage level below which source 1 goes into a
        brown out condition. The maximum value allowed is dictated by
        tlpAtsConfigSource1TransferReset. The minimum value allowed is dictated by
        tlpAtsConfigSource1TransferSet. If not supported, this value will return
        ERROR_NO_SUCH_NAME."
    ::= { tlpAtsConfigVoltageRangeEntry 4 }

tlpAtsConfigSource1TransferSet OBJECT-TYPE
    SYNTAX Unsigned32
    UNITS "0.1 Volts"
    MAX-ACCESS read-write
    STATUS current
    DESCRIPTION
        "If input source 1 voltage level falls below this value, a unit connected to
        source 1 will transition to source 2 (if it is in fair condition as denoted
        by tlpAtsConfigSource2TransferSet). The maximum value allowed is dictated by
        tlpAtsConfigSource1BrownoutSet. The minimum value allowed is dictated by
        tlpAtsConfigLowVoltageReset. If not supported, this value will return
        ERROR_NO_SUCH_NAME."
    ::= { tlpAtsConfigVoltageRangeEntry 5 }

tlpAtsConfigSource2TransferReset OBJECT-TYPE
    SYNTAX Unsigned32
    UNITS "0.1 Volts"
    MAX-ACCESS read-write
    STATUS current
    DESCRIPTION
        "If input source 2 voltage level is above this value, a unit connected to
        source 1 will transition to source 2 (if it is the preferred source). The
        maximum value allowed is dictated by tlpAtsConfigHighVoltageReset. The
        minimum value allowed is dictated by tlpAtsConfigSource2BrownoutSet. If not
        supported, this value will return ERROR_NO_SUCH_NAME."
    ::= { tlpAtsConfigVoltageRangeEntry 6 }

tlpAtsConfigSource2BrownoutSet OBJECT-TYPE
    SYNTAX Unsigned32
    UNITS "0.1 Volts"
    MAX-ACCESS read-write
    STATUS current
    DESCRIPTION
        "This value dictates the voltage level below which source 2 goes into a
        brown out condition. The maximum value allowed is dictated by
        tlpAtsConfigSource2TransferReset. The minimum value allowed is dictated by
        tlpAtsConfigSource2TransferSet. If not supported, this value will return
        ERROR_NO_SUCH_NAME."
    ::= { tlpAtsConfigVoltageRangeEntry 7 }

tlpAtsConfigSource2TransferSet OBJECT-TYPE
    SYNTAX Unsigned32
    UNITS "0.1 Volts"
    MAX-ACCESS read-write
    STATUS current
    DESCRIPTION
        "If input source 2 voltage level falls below this value, a unit connected to
        source 2 will transition to source 1 (if it is in fair condition as denoted
        by tlpAtsConfigSource1TransferSet). The maximum value allowed is dictated by
        tlpAtsConfigSource2BrownoutSet. The minimum value allowed is dictated by
        tlpAtsConfigLowVoltageReset. If not supported, this value will return
        ERROR_NO_SUCH_NAME."
    ::= { tlpAtsConfigVoltageRangeEntry 8 }

tlpAtsConfigLowVoltageReset OBJECT-TYPE
    SYNTAX Unsigned32
    UNITS "0.1 Volts"
    MAX-ACCESS read-write
    STATUS current
    DESCRIPTION
        "If a unit is disconnected due to under-voltage or is not powered up yet, the
        line voltage has to rise above this value before the unit gets connected to
        the AC input connection. The maximum value allowed is dictated by the lesser
        value of tlpAtsConfigSource1TransferSet and tlpAtsConfigSource2TransferSet.
        The minimum value allowed is dictated by tlpAtsConfigLowVoltageTransfer. If
        not supported, this value will return ERROR_NO_SUCH_NAME."
    ::= { tlpAtsConfigVoltageRangeEntry 9 }

tlpAtsConfigLowVoltageTransfer OBJECT-TYPE
    SYNTAX Unsigned32
    UNITS "0.1 Volts"
    MAX-ACCESS read-write
    STATUS current
    DESCRIPTION
        "The minimum line voltage allowed before the unit disconnects the
        AC input connection. The maximum value allowed is dictated by
        tlpAtsConfigLowVoltageReset. The minimum value allowed is dictated by
        tlpAtsInputBadTransferVoltageLowerBound (inclusively). If not supported, this
        value will return ERROR_NO_SUCH_NAME."
    ::= { tlpAtsConfigVoltageRangeEntry 10 }

tlpAtsConfigVoltageRangeLimitsTable OBJECT-TYPE
    SYNTAX SEQUENCE OF TlpAtsConfigVoltageRangeLimitsEntry
    MAX-ACCESS not-accessible
    STATUS current
    DESCRIPTION
        "The voltage range table, as documented by tlpAtsConfigVoltageRangeTable requires
        that all changes adhere with stack order, from high transfer voltage down to low
        transfer voltage. In addition to stack order, certain voltage range values have
        limits defining the absolute minimum and absolute maximum for such values. Any
        voltage value violating any respective limit defined herein will be rejected."
    ::= { tlpAtsConfig 3 }

tlpAtsConfigVoltageRangeLimitsEntry OBJECT-TYPE
    SYNTAX TlpAtsConfigVoltageRangeLimitsEntry
    MAX-ACCESS not-accessible
    STATUS current
    DESCRIPTION
        "An entry containing voltage range limits configuration options for a particular ats."
    INDEX { tlpDeviceIndex }
    ::= { tlpAtsConfigVoltageRangeLimitsTable 1 }

TlpAtsConfigVoltageRangeLimitsEntry ::= SEQUENCE {
    tlpAtsConfigSourceBrownoutSetMinimum    Unsigned32,
    tlpAtsConfigSourceBrownoutSetMaximum    Unsigned32,
    tlpAtsConfigSourceTransferSetMinimum    Unsigned32,
    tlpAtsConfigSourceTransferSetMaximum    Unsigned32 }

tlpAtsConfigSourceBrownoutSetMinimum OBJECT-TYPE
    SYNTAX Unsigned32
    UNITS "0.1 Volts"
    MAX-ACCESS read-write
    STATUS current
    DESCRIPTION
        "This value dictates the absolute lower limit by which tlpAtsConfigSource1BrownoutSet
        and tlpAtsConfigSource2BrownoutSet can be set. tlpAtsConfigSource1TransferSet and
        tlpAtsConfigSource2TransferSet, respectively, are also used when determining the
        lowest value a brownout value can be set at any given time. If not supported, this
        value will return ERROR_NO_SUCH_NAME."
    ::= { tlpAtsConfigVoltageRangeLimitsEntry 1 }

tlpAtsConfigSourceBrownoutSetMaximum OBJECT-TYPE
    SYNTAX Unsigned32
    UNITS "0.1 Volts"
    MAX-ACCESS read-write
    STATUS current
    DESCRIPTION
        "This value dictates the absolute upper limit by which tlpAtsConfigSource1BrownoutSet
        and tlpAtsConfigSource2BrownoutSet can be set. tlpAtsConfigSource1TransferReset and
        tlpAtsConfigSource2TransferReset, respectively, are also used when determining the
        greatest value a brownout value can be set at any given time. If not supported, this
        value will return ERROR_NO_SUCH_NAME."
    ::= { tlpAtsConfigVoltageRangeLimitsEntry 2 }

tlpAtsConfigSourceTransferSetMinimum OBJECT-TYPE
    SYNTAX Unsigned32
    UNITS "0.1 Volts"
    MAX-ACCESS read-write
    STATUS current
    DESCRIPTION
        "This value dictates the absolute lower limit by which tlpAtsConfigSource1TransferSet
        and tlpAtsConfigSource2TransferSet can be set. tlpAtsConfigLowVoltageReset is also
        used when determining the lowest value a transferset value can be set at any given
        time. If not supported, this value will return ERROR_NO_SUCH_NAME."
    ::= { tlpAtsConfigVoltageRangeLimitsEntry 3 }

tlpAtsConfigSourceTransferSetMaximum OBJECT-TYPE
    SYNTAX Unsigned32
    UNITS "0.1 Volts"
    MAX-ACCESS read-write
    STATUS current
    DESCRIPTION
        "This value dictates the absolute upper limit by which tlpAtsConfigSource1TransferSet
        and tlpAtsConfigSource2TransferSet can be set. tlpAtsConfigSource1BrownoutSet and
        tlpAtsConfigSource2BrownoutSet, respectively, are also used when determining the
        greatest value a transferset value can be set at any given time. If not supported,
        this value will return ERROR_NO_SUCH_NAME."
    ::= { tlpAtsConfigVoltageRangeLimitsEntry 4 }

tlpAtsConfigThresholdTable OBJECT-TYPE
    SYNTAX SEQUENCE OF TlpAtsConfigThresholdEntry
    MAX-ACCESS not-accessible
    STATUS current
    DESCRIPTION
        "The configurable threshold options of each ats in device table. This
        is a sparse dependent table, and will contain some subset of devices that
        are atss. Not all options are available on all atss."
    ::= { tlpAtsConfig 4 }

tlpAtsConfigThresholdEntry OBJECT-TYPE
    SYNTAX TlpAtsConfigThresholdEntry
    MAX-ACCESS not-accessible
    STATUS current
    DESCRIPTION
        "An entry containing configurable threshold options for a particular ats."
    INDEX { tlpDeviceIndex }
    ::= { tlpAtsConfigThresholdTable 1 }

TlpAtsConfigThresholdEntry ::= SEQUENCE {
    tlpAtsConfigOverCurrentThreshold            Unsigned32,
    tlpAtsConfigOverTemperatureThreshold        Unsigned32,
    tlpAtsConfigOverVoltageThreshold            Unsigned32,
    tlpAtsConfigOverLoadThreshold               Unsigned32 }

tlpAtsConfigOverCurrentThreshold OBJECT-TYPE
    SYNTAX Unsigned32
    UNITS "0.1 Amps"
    MAX-ACCESS read-write
    STATUS current
    DESCRIPTION
        "The output current measurement at which an over current condition is reported.
        This value may not be supported on all models. If not supported, this value
        will return ERROR_NO_SUCH_NAME."
    ::= { tlpAtsConfigThresholdEntry 1 }

tlpAtsConfigOverTemperatureThreshold OBJECT-TYPE
    SYNTAX Unsigned32
    UNITS "0.1 Centigrade"
    MAX-ACCESS read-write
    STATUS current
    DESCRIPTION
        "The system temperature at which an over temperature condition is reported.
        This value may not be supported on all models. If not supported, this value
        will return ERROR_NO_SUCH_NAME."
    ::= { tlpAtsConfigThresholdEntry 2 }

tlpAtsConfigOverVoltageThreshold OBJECT-TYPE
    SYNTAX Unsigned32
    UNITS "0.1 Volts"
    MAX-ACCESS read-write
    STATUS current
    DESCRIPTION
        "The input voltage measurement at which an over voltage condition is reported.
        This value may not be supported on all models. If not supported, this value
        will return ERROR_NO_SUCH_NAME."
    ::= { tlpAtsConfigThresholdEntry 3 }

tlpAtsConfigOverLoadThreshold OBJECT-TYPE
    SYNTAX Unsigned32
    MAX-ACCESS read-write
    STATUS current
    DESCRIPTION
        "The system load at which an overload condition is reported. This value may not
        be supported on all models. If not supported, this value will return
        ERROR_NO_SUCH_NAME."
    ::= { tlpAtsConfigThresholdEntry 4 }

-- cooling

tlpCoolingIdentNumCooling OBJECT-TYPE
    SYNTAX Unsigned32
    MAX-ACCESS read-only
    STATUS current
    DESCRIPTION
        "The number of cooling devices that this agent is currently managing."
    ::= { tlpCoolingIdent 1 }

-- kvm

tlpKvmIdentNumKvm OBJECT-TYPE
    SYNTAX Unsigned32
    MAX-ACCESS read-only
    STATUS current
    DESCRIPTION
        "The number of kvm devices that this agent is currently managing."
    ::= { tlpKvmIdent 1 }

-- rackTrack

tlpRackTrackIdentNumRackTrack OBJECT-TYPE
    SYNTAX Unsigned32
    MAX-ACCESS read-only
    STATUS current
    DESCRIPTION
        "The number of rack track devices that this agent is currently managing."
    ::= { tlpRackTrackIdent 1 }

-- switch

tlpSwitchIdentNumSwitch OBJECT-TYPE
    SYNTAX Unsigned32
    MAX-ACCESS read-only
    STATUS current
    DESCRIPTION
        "The number of switch devices that this agent is currently managing."
    ::= { tlpSwitchIdent 1 }

-- software

tlpAgentType OBJECT-TYPE
    SYNTAX INTEGER {
        unknown(0),
        pal(1),
        pansa(2),
        delta(3),
        sinetica(4),
        netos6(5),
        netos7(6),
        panms(7),
        nmc5(8) }
    MAX-ACCESS read-only
    STATUS current
    DESCRIPTION
        "The type of PowerAlert engine providing this data."
    ::= { tlpAgentIdent 1 }

tlpAgentVersion OBJECT-TYPE
    SYNTAX DisplayString
    MAX-ACCESS read-only
    STATUS current
    DESCRIPTION
        "The version of the agent software."
    ::= { tlpAgentIdent 2 }

tlpAgentDriverVersion OBJECT-TYPE
    SYNTAX DisplayString
    MAX-ACCESS read-only
    STATUS current
    DESCRIPTION
        "The driver version of the agent software."
    ::= { tlpAgentIdent 3 }

tlpAgentMAC OBJECT-TYPE
    SYNTAX DisplayString
    MAX-ACCESS read-only
    STATUS current
    DESCRIPTION
        "The MAC Address of the agent."
    ::= { tlpAgentIdent 4 }

tlpAgentSerialNum OBJECT-TYPE
    SYNTAX DisplayString
    MAX-ACCESS read-only
    STATUS current
    DESCRIPTION
        "Serial number of the web card providing the agent data. This value is
        only supported by a web card agent. PowerAlert for PC (PAL) agents do
        not support this value and will return ERROR_NO_SUCH_NAME."
    ::= { tlpAgentIdent 5 }

tlpAgentUuid OBJECT-TYPE
    SYNTAX DisplayString
    MAX-ACCESS read-only
    STATUS current
    DESCRIPTION
        "Universally unique identifier for this host in the form 8-4-4-4-12 for a
        total of 36 characters (32 alphanumeric characters and four hyphens). For
        example: 550e8400-e29b-41d4-a716-446655440000."
    ::= { tlpAgentIdent 6 }

tlpAgentAttributesSupports  OBJECT IDENTIFIER
    ::= { tlpAgentAttributes 1 }

tlpAgentAttributesSupportsHTTP OBJECT-TYPE
    SYNTAX TruthValue
    MAX-ACCESS read-only
    STATUS current
    DESCRIPTION
        "Indicates whether the agent supports HTTP connections."
    ::= { tlpAgentAttributesSupports 1 }

tlpAgentAttributesSupportsHTTPS OBJECT-TYPE
    SYNTAX TruthValue
    MAX-ACCESS read-only
    STATUS current
    DESCRIPTION
        "Indicates whether the agent supports HTTPS connections."
    ::= { tlpAgentAttributesSupports 2 }

tlpAgentAttributesSupportsFTP OBJECT-TYPE
    SYNTAX TruthValue
    MAX-ACCESS read-only
    STATUS current
    DESCRIPTION
        "Indicates whether the agent supports FTP connections."
    ::= { tlpAgentAttributesSupports 3 }

tlpAgentAttributesSupportsTelnetMenu OBJECT-TYPE
    SYNTAX TruthValue
    MAX-ACCESS read-only
    STATUS current
    DESCRIPTION
        "Indicates whether the agent supports Telnet menu connections."
    ::= { tlpAgentAttributesSupports 4 }

tlpAgentAttributesSupportsTelnetCLI OBJECT-TYPE
    SYNTAX TruthValue
    MAX-ACCESS read-only
    STATUS current
    DESCRIPTION
        "Indicates whether the agent supports Telnet CLI connections."
    ::= { tlpAgentAttributesSupports 5 }

tlpAgentAttributesSupportsSSHMenu OBJECT-TYPE
    SYNTAX TruthValue
    MAX-ACCESS read-only
    STATUS current
    DESCRIPTION
        "Indicates whether the agent supports SSH menu connections."
    ::= { tlpAgentAttributesSupports 6 }

tlpAgentAttributesSupportsSSHCLI OBJECT-TYPE
    SYNTAX TruthValue
    MAX-ACCESS read-only
    STATUS current
    DESCRIPTION
        "Indicates whether the agent supports SSH CLI connections."
    ::= { tlpAgentAttributesSupports 7 }

tlpAgentAttributesSupportsSNMP OBJECT-TYPE
    SYNTAX TruthValue
    MAX-ACCESS read-only
    STATUS current
    DESCRIPTION
        "Indicates whether the agent supports SNMP connections."
    ::= { tlpAgentAttributesSupports 8 }

tlpAgentAttributesSupportsSNMPTrap OBJECT-TYPE
    SYNTAX TruthValue
    MAX-ACCESS read-only
    STATUS current
    DESCRIPTION
        "Indicates whether the agent supports listening for SNMP traps. This
        is only applicable for network monitoring applications, PowerAlert
        Shutdown Agent for an example, that connect to a web card or PowerAlert
        Local and listen for outbound traps. As such, this value is not supported
        and will always return 2(false) for a web card or PowerAlert Local."
    ::= { tlpAgentAttributesSupports 9 }

tlpAgentAttributesAutostart  OBJECT IDENTIFIER
    ::= { tlpAgentAttributes 2 }

tlpAgentAttributesAutostartHTTP OBJECT-TYPE
    SYNTAX TruthValue
    MAX-ACCESS read-only
    STATUS current
    DESCRIPTION
        "Indicates whether the agent autostarts HTTP services."
    ::= { tlpAgentAttributesAutostart 1 }

tlpAgentAttributesAutostartHTTPS OBJECT-TYPE
    SYNTAX TruthValue
    MAX-ACCESS read-only
    STATUS current
    DESCRIPTION
        "Indicates whether the agent autostarts HTTPS services."
    ::= { tlpAgentAttributesAutostart 2 }

tlpAgentAttributesAutostartFTP OBJECT-TYPE
    SYNTAX TruthValue
    MAX-ACCESS read-only
    STATUS current
    DESCRIPTION
        "Indicates whether the agent autostarts FTP services."
    ::= { tlpAgentAttributesAutostart 3 }

tlpAgentAttributesAutostartTelnetMenu OBJECT-TYPE
    SYNTAX TruthValue
    MAX-ACCESS read-only
    STATUS current
    DESCRIPTION
        "Indicates whether the agent autostarts Telnet menu services."
    ::= { tlpAgentAttributesAutostart 4 }

tlpAgentAttributesAutostartTelnetCLI OBJECT-TYPE
    SYNTAX TruthValue
    MAX-ACCESS read-only
    STATUS current
    DESCRIPTION
        "Indicates whether the agent autostarts Telnet CLI services."
    ::= { tlpAgentAttributesAutostart 5 }

tlpAgentAttributesAutostartSSHMenu OBJECT-TYPE
    SYNTAX TruthValue
    MAX-ACCESS read-only
    STATUS current
    DESCRIPTION
        "Indicates whether the agent autostarts SSH menu services."
    ::= { tlpAgentAttributesAutostart 6 }

tlpAgentAttributesAutostartSSHCLI OBJECT-TYPE
    SYNTAX TruthValue
    MAX-ACCESS read-only
    STATUS current
    DESCRIPTION
        "Indicates whether the agent autostarts SSH CLI services."
    ::= { tlpAgentAttributesAutostart 7 }

tlpAgentAttributesAutostartSNMP OBJECT-TYPE
    SYNTAX TruthValue
    MAX-ACCESS read-only
    STATUS current
    DESCRIPTION
        "Indicates whether the agent autostarts SNMP services."
    ::= { tlpAgentAttributesAutostart 8 }

tlpAgentAttributesSnmp  OBJECT IDENTIFIER
    ::= { tlpAgentAttributes 3 }

tlpAgentAttributesSNMPv1Enabled OBJECT-TYPE
    SYNTAX TruthValue
    MAX-ACCESS read-only
    STATUS current
    DESCRIPTION
        "Indicates whether the agent will allow SNMPv1 connections."
    ::= { tlpAgentAttributesSnmp 1 }

tlpAgentAttributesSNMPv2cEnabled OBJECT-TYPE
    SYNTAX TruthValue
    MAX-ACCESS read-only
    STATUS current
    DESCRIPTION
        "Indicates whether the agent will allow SNMPv2c connections."
    ::= { tlpAgentAttributesSnmp 2 }

tlpAgentAttributesSNMPv3Enabled OBJECT-TYPE
    SYNTAX TruthValue
    MAX-ACCESS read-only
    STATUS current
    DESCRIPTION
        "Indicates whether the agent will allow SNMPv3 connections."
    ::= { tlpAgentAttributesSnmp 3 }

tlpAgentAttributesPorts  OBJECT IDENTIFIER
    ::= { tlpAgentAttributes 4 }

tlpAgentAttributesHTTPPort OBJECT-TYPE
    SYNTAX Unsigned32
    MAX-ACCESS read-only
    STATUS current
    DESCRIPTION
        "The port used for HTTP communications."
    ::= { tlpAgentAttributesPorts 1 }

tlpAgentAttributesHTTPSPort OBJECT-TYPE
    SYNTAX Unsigned32
    MAX-ACCESS read-only
    STATUS current
    DESCRIPTION
        "The port used for HTTPS communications."
    ::= { tlpAgentAttributesPorts 2 }

tlpAgentAttributesFTPPort OBJECT-TYPE
    SYNTAX Unsigned32
    MAX-ACCESS read-only
    STATUS current
    DESCRIPTION
        "The port used for FTP communications."
    ::= { tlpAgentAttributesPorts 3 }

tlpAgentAttributesTelnetMenuPort OBJECT-TYPE
    SYNTAX Unsigned32
    MAX-ACCESS read-only
    STATUS current
    DESCRIPTION
        "The port used for Telnet Menu communications."
    ::= { tlpAgentAttributesPorts 4 }

tlpAgentAttributesTelnetCLIPort OBJECT-TYPE
    SYNTAX Unsigned32
    MAX-ACCESS read-only
    STATUS current
    DESCRIPTION
        "The port used for Telnet CLI communications."
    ::= { tlpAgentAttributesPorts 5 }

tlpAgentAttributesSSHMenuPort OBJECT-TYPE
    SYNTAX Unsigned32
    MAX-ACCESS read-only
    STATUS current
    DESCRIPTION
        "The port used for SSH Menu communications."
    ::= { tlpAgentAttributesPorts 6 }

tlpAgentAttributesSSHCLIPort OBJECT-TYPE
    SYNTAX Unsigned32
    MAX-ACCESS read-only
    STATUS current
    DESCRIPTION
        "The port used for SSH CLI communications."
    ::= { tlpAgentAttributesPorts 7 }

tlpAgentAttributesSNMPPort OBJECT-TYPE
    SYNTAX Unsigned32
    MAX-ACCESS read-only
    STATUS current
    DESCRIPTION
        "The port used for SNMP communications."
    ::= { tlpAgentAttributesPorts 8 }

tlpAgentAttributesSNMPTrapPort OBJECT-TYPE
    SYNTAX Unsigned32
    MAX-ACCESS read-only
    STATUS current
    DESCRIPTION
        "The port used for SNMP trap and notifications."
    ::= { tlpAgentAttributesPorts 9 }

tlpAgentConfigRemoteRegistration OBJECT-TYPE
    SYNTAX DisplayString
    MAX-ACCESS read-write
    STATUS current
    DESCRIPTION
        "Registers an SNMP contact's IP address and the port on which 
        the contact is listening for SNMP traps.  Setting this
        value is used to CREATE a table entry in a non-standard way.
        Getting this value will return a string INADDR_ANY and any
        port number.
    
        The port number should always be included. When unregistering
        an SNMP contact, the requester's IP address should be provided
        with a port number of 0.  When setting or unsetting this OID, 
        the IP address string should never be 0 nor should it be empty.

        The registration uses its default community string to register
        each contact. To use a community other than the default, then
        it must be appended to the end of the string delimited with a
        comma.
    
        The address should be of the format 0.0.0.0:00000 for IPv4. 
        If IPv6 is supported, use the bracket-enclosed format given 
        in IETF RFC 2732 Section 2, with the following examples:
    
        [FEDC:BA98:7654:3210:FEDC:BA98:7654:3210]:80
        [1080:0:0:0:8:800:200C:417A]:162
        [3ffe:2a00:100:7031::1]:162
        [1080::8:800:200C:417A]:162,myCommunity
        [::192.9.5.5]:162,myCommunity
        [::FFFF:129.144.52.38]:80
        [2010:836B:4179::836B:4179]:162"
    ::= { tlpAgentConfig 1 }

tlpAgentConfigCurrentTime OBJECT-TYPE
    SYNTAX DisplayString
    MAX-ACCESS read-write
    STATUS current
    DESCRIPTION
        "The current date and time of the system."
    ::= { tlpAgentConfig 2 }

tlpAgentNumEmailContacts OBJECT-TYPE
    SYNTAX Unsigned32
    MAX-ACCESS read-only
    STATUS current
    DESCRIPTION
        "The number of email contacts currently defined in the agent."
    ::= { tlpAgentEmailContacts 1 }

tlpAgentEmailContactTable OBJECT-TYPE
    SYNTAX SEQUENCE OF TlpAgentEmailContactEntry
    MAX-ACCESS not-accessible
    STATUS current
    DESCRIPTION
        "A list of email contact entries. The number of entries is given by
        the value of tlpAgentNumEmailContacts."
    ::= { tlpAgentEmailContacts 2 }
  
tlpAgentEmailContactEntry OBJECT-TYPE
    SYNTAX TlpAgentEmailContactEntry
    MAX-ACCESS not-accessible
    STATUS current
    DESCRIPTION
        "An entry containing the details of an email contact."
    INDEX { tlpAgentEmailContactIndex }
    ::= { tlpAgentEmailContactTable 1 }

TlpAgentEmailContactEntry ::= SEQUENCE {
    tlpAgentEmailContactIndex           Unsigned32,
    tlpAgentEmailContactRowStatus       RowStatus,
    tlpAgentEmailContactName            DisplayString,
    tlpAgentEmailContactAddress         DisplayString }

tlpAgentEmailContactIndex OBJECT-TYPE
    SYNTAX Unsigned32
    MAX-ACCESS read-only
    STATUS current
    DESCRIPTION
        "The table row index for the email contact."
    ::= { tlpAgentEmailContactEntry 1 }

tlpAgentEmailContactRowStatus OBJECT-TYPE
    SYNTAX RowStatus
    MAX-ACCESS read-write
    STATUS current
    DESCRIPTION
        "Row status for the tlpAgentEmailContactTable."
    ::= { tlpAgentEmailContactEntry 2 }
  
tlpAgentEmailContactName OBJECT-TYPE
    SYNTAX DisplayString
    MAX-ACCESS read-write
    STATUS current
    DESCRIPTION
        "The name of the email contact."
    ::= { tlpAgentEmailContactEntry 3 }

tlpAgentEmailContactAddress OBJECT-TYPE
    SYNTAX DisplayString
    MAX-ACCESS read-write
    STATUS current
    DESCRIPTION
        "The address of the email contact."
    ::= { tlpAgentEmailContactEntry 4 }

tlpAgentNumSnmpContacts OBJECT-TYPE
    SYNTAX Unsigned32
    MAX-ACCESS read-only
    STATUS current
    DESCRIPTION
        "The number of SNMP contacts currently defined in the agent."
    ::= { tlpAgentSnmpContacts 1 }

tlpAgentSnmpContactTable OBJECT-TYPE
    SYNTAX SEQUENCE OF TlpAgentSnmpContactEntry
    MAX-ACCESS not-accessible
    STATUS current
    DESCRIPTION
        "A list of SNMP contact entries. The number of entries is given by
        the value of tlpAgentNumSnmpContacts."
    ::= { tlpAgentSnmpContacts 2 }
  
tlpAgentSnmpContactEntry OBJECT-TYPE
    SYNTAX TlpAgentSnmpContactEntry
    MAX-ACCESS not-accessible
    STATUS current
    DESCRIPTION
        "An entry containing the details of an SNMP contact."
        INDEX { tlpAgentSnmpContactIndex }
    ::= { tlpAgentSnmpContactTable 1 }

TlpAgentSnmpContactEntry ::= SEQUENCE {
    tlpAgentSnmpContactIndex            Unsigned32,
    tlpAgentSnmpContactRowStatus        RowStatus,
    tlpAgentSnmpContactName             DisplayString,
    tlpAgentSnmpContactIpAddress        DisplayString,
    tlpAgentSnmpContactPort             Unsigned32,
    tlpAgentSnmpContactSnmpVersion      INTEGER,
    tlpAgentSnmpContactSecurityName     DisplayString,
    tlpAgentSnmpContactPrivPassword     DisplayString,
    tlpAgentSnmpContactAuthPassword     DisplayString }

tlpAgentSnmpContactIndex OBJECT-TYPE
    SYNTAX Unsigned32
    MAX-ACCESS read-only
    STATUS current
    DESCRIPTION
        "The table row index for the SNMP contact."
    ::= { tlpAgentSnmpContactEntry 1 }

tlpAgentSnmpContactRowStatus OBJECT-TYPE
    SYNTAX RowStatus
    MAX-ACCESS read-write
    STATUS current
    DESCRIPTION
        "Row status for the tlpAgentSnmpContactTable."
    ::= { tlpAgentSnmpContactEntry 2 }
  
tlpAgentSnmpContactName OBJECT-TYPE
    SYNTAX DisplayString
    MAX-ACCESS read-write
    STATUS current
    DESCRIPTION
        "The name of the SNMP contact."
    ::= { tlpAgentSnmpContactEntry 3 }

tlpAgentSnmpContactIpAddress OBJECT-TYPE
    SYNTAX DisplayString
    MAX-ACCESS read-write
    STATUS current
    DESCRIPTION
        "The IP address of the SNMP contact."
    ::= { tlpAgentSnmpContactEntry 4 }
  
tlpAgentSnmpContactPort OBJECT-TYPE
    SYNTAX Unsigned32
    MAX-ACCESS read-write
    STATUS current
    DESCRIPTION
        "The port of the SNMP contact."
    ::= { tlpAgentSnmpContactEntry 5 }
  
tlpAgentSnmpContactSnmpVersion OBJECT-TYPE
    SYNTAX INTEGER {
        snmpv1(1),
        snmpv2c(2),
        snmpv3(3) }
    MAX-ACCESS read-write
    STATUS current
    DESCRIPTION
        "The SNMP contact version to use for sending traps."
    ::= { tlpAgentSnmpContactEntry 6 }
  
tlpAgentSnmpContactSecurityName OBJECT-TYPE
    SYNTAX DisplayString
    MAX-ACCESS read-write
    STATUS current
    DESCRIPTION
        "The security name for the SNMP contact."
    ::= { tlpAgentSnmpContactEntry 7 }
    
tlpAgentSnmpContactPrivPassword OBJECT-TYPE
    SYNTAX DisplayString
    MAX-ACCESS read-write
    STATUS current
    DESCRIPTION
        "The privacy password to use for sending V3 traps to the SNMP
        contact."
    ::= { tlpAgentSnmpContactEntry 8 }
  
tlpAgentSnmpContactAuthPassword OBJECT-TYPE
    SYNTAX DisplayString
    MAX-ACCESS read-write
    STATUS current
    DESCRIPTION
        "The authentication password to use for sending V3 traps to the
        SNMP contact."
    ::= { tlpAgentSnmpContactEntry 9 }

-- alarms

tlpAlarmsPresent OBJECT-TYPE
    SYNTAX Unsigned32
    MAX-ACCESS read-only
    STATUS current
    DESCRIPTION
        "The present number of active alarm conditions."
    ::= { tlpAlarms 1 }

tlpAlarmTable OBJECT-TYPE
    SYNTAX SEQUENCE OF TlpDeviceAlarmEntry
    MAX-ACCESS not-accessible
    STATUS current
    DESCRIPTION
        "A list of alarm conditions for all devices managed by this agent. This
        table contains zero, one, or many rows at any moment, depending upon
        the number of alarm conditions in effect or conditions not acnowledged.
        The agent creates a row in the table each time a condition is detected
        and deletes that row when that condition no longer pertains (becomes
        inactive and is acknowledged). The agent creates the first row with
        tlpAlarmId equal to 1, and increments the value of tlpAlarmId each time
        a new row is created, wrapping to the first free value greater than or
        equal to 1 when the maximum value of tlpAlarmId would otherwise be
        exceeded. Consequently, after multiple operations, the table may become
        sparse (e.g., containing entries for rows 95, 100, 101, and 203) and the
        entries should not be assumed to be in chronological order because
        tlpAlarmId might have wrapped.

        The number of rows in the table at any given time is reflected by
        the value of tlpAlarmsPresent."
    ::= { tlpAlarms 2 }

tlpAlarmEntry OBJECT-TYPE
    SYNTAX TlpDeviceAlarmEntry
    MAX-ACCESS not-accessible
    STATUS current
    DESCRIPTION
        "An entry containing information application to a particular
        alarm."
    INDEX { tlpAlarmId }
    ::= { tlpAlarmTable 1 }

TlpDeviceAlarmEntry ::= SEQUENCE {
    tlpAlarmId                Unsigned32,
    tlpAlarmDescr             OBJECT IDENTIFIER,
    tlpAlarmTime              TimeStamp,
    tlpAlarmTableRef          OBJECT IDENTIFIER,
    tlpAlarmTableRowRef       OBJECT IDENTIFIER,
    tlpAlarmDetail            DisplayString,
    tlpAlarmType              INTEGER,
    tlpAlarmState             INTEGER,
    tlpAlarmAcknowledged      INTEGER }

tlpAlarmId OBJECT-TYPE
    SYNTAX Unsigned32
    MAX-ACCESS read-only
    STATUS current
    DESCRIPTION
        "A unique identifier for an alarm condition. This value will remain
        constant for the duration of the alarm condition."
    ::= { tlpAlarmEntry 1 }

tlpAlarmDescr OBJECT-TYPE
    SYNTAX OBJECT IDENTIFIER
    MAX-ACCESS read-only
    STATUS current
    DESCRIPTION
        "A reference of the alarm description object. The object referenced
        should not be accessbile, but rather be used to provide a unique
        description for the alarm condition. The object referenced will be a
        well known alarm object associated with the device on which the alarm
        condition is active."
    ::= { tlpAlarmEntry 2 }

tlpAlarmTime OBJECT-TYPE
    SYNTAX TimeStamp
    MAX-ACCESS read-only
    STATUS current
    DESCRIPTION
        "The value of sysUpTime when the alarm condition was detected. If the
        alarm condition was detected at the time of agent startup and presumably
        existed before agent startup, the value of tlpAlarmsTime shall equal
        0."
    ::= { tlpAlarmEntry 3 }
  
tlpAlarmTableRef OBJECT-TYPE
    SYNTAX OBJECT IDENTIFIER
    MAX-ACCESS read-only
    STATUS current
    DESCRIPTION
        "This value references the OID of a table object applicable to the alarm
        condition. This, in conjunction with the table row as defined by
        tlpAlarmTableRowRef, specifies the object/row within this table to which
        the alarm condition applies.

        Example 1 -- The following sample values will be returned for a UPS on
        battery:
        tlpAlarmId                28
        tlpAlarmDescr             tlpUpsAlarmOnBattery
        tlpAlarmTime              12345678
        tlpAlarmTableRef          tlpDeviceTable
        tlpAlarmTableRowRef       tlpDeviceIndex.2
        tlpAlarmDetail            On Battery
        tlpAlarmType              warning
        tlpAlarmState             active
        tlpAlarmAcknowledged      notAcknowledged

        In the above example, tlpAlarmTableRef references the device table and
        tlpAlarmTableRowRef references the 2nd managed device in that table.

        Example 2 -- The following sample values will be returned for a PDU with
        a load turned off:
        tlpAlarmId                46
        tlpAlarmDescr             tlpPduAlarmLoadOff
        tlpAlarmTime              12345678
        tlpAlarmTableRef          tlpPduOutletTable
        tlpAlarmTableRowRef       tlpOutletIndex.1.4
        tlpAlarmDetail            Load Off
        tlpAlarmType              warning
        tlpAlarmState             active
        tlpAlarmAcknowledged      acknowledged

        In the above example, tlpAlarmTableRef references the pdu outlet table and
        tlpAlarmTableRowRef references the 4th outlet on the 1st managed device."
    ::= { tlpAlarmEntry 4 }

tlpAlarmTableRowRef OBJECT-TYPE
    SYNTAX OBJECT IDENTIFIER
    MAX-ACCESS read-only
    STATUS current
    DESCRIPTION
        "This value is used in conjunction with tlpAlarmTableRef to define the
        object associated with this alarm condition. See the description of
        tlpAlarmTableRef for more information."
    ::= { tlpAlarmEntry 5 }

tlpAlarmDetail OBJECT-TYPE
    SYNTAX DisplayString
    MAX-ACCESS read-only
    STATUS current
    DESCRIPTION
        "A textual description of the alarm condition."
    ::= { tlpAlarmEntry 6 }

tlpAlarmType OBJECT-TYPE
    SYNTAX INTEGER {
        critical(1),
        warning(2),
        info(3),
        status(4),
        offline(5),
        custom(6) }
    MAX-ACCESS read-only
    STATUS current
    DESCRIPTION
        "The category/group of this alarm."
    ::= { tlpAlarmEntry 7 }

tlpAlarmState OBJECT-TYPE
    SYNTAX INTEGER {
        active(1),
        inactive(2) }
    MAX-ACCESS read-only
    STATUS current
    DESCRIPTION
        "The current state of this alarm condition. An active(1) alarm is a condition
        that currently exists. An inactive(2) alarm is a condition that no longer exists
        because the alarm either cleared or was resolved. Each alarm condition must be
        cleared and acknowledged before it is removed from this table (see
        tlpAlarmAcknowledged)."
    ::= { tlpAlarmEntry 8 }

tlpAlarmAcknowledged OBJECT-TYPE
    SYNTAX INTEGER {
        notAcknowledged(1),
        acknowledged(2) }
    MAX-ACCESS read-write
    STATUS current
    DESCRIPTION
        "Denotes whether the alarm condition has been acknowledged. The agent will
        return notAcknowledged(1) if the condition has not been acknowledged, or
        acknowledged(2) when acknowledged. Writing the value acknowledged(2) for an
        alarm acknowledges the alarm condition. Each alarm condition must be cleared
        and acknowledged before it is removed from this table; therefore, even if
        acknowledged, the alarm will remain in this table until the alarm becomes
        inactive as denoted by tlpAlarmState."
    ::= { tlpAlarmEntry 9 }

tlpAlarmCommunicationsLost OBJECT-IDENTITY
    STATUS current
    DESCRIPTION
        "A problem has been encountered in the communications between the agent
        and the device."
    ::= { tlpDeviceAlarms 1 }

tlpAlarmUserDefined OBJECT IDENTIFIER
    ::= { tlpDeviceAlarms 2 }

tlpAlarmUserDefined01 OBJECT-IDENTITY
    STATUS current
    DESCRIPTION
        "User-defined event 1 is in alarm."
    ::= { tlpAlarmUserDefined 1 }

tlpAlarmUserDefined02 OBJECT-IDENTITY
    STATUS current
    DESCRIPTION
        "User-defined event 2 is in alarm."
    ::= { tlpAlarmUserDefined 2 }

tlpAlarmUserDefined03 OBJECT-IDENTITY
    STATUS current
    DESCRIPTION
        "User-defined event 3 is in alarm."
    ::= { tlpAlarmUserDefined 3 }

tlpAlarmUserDefined04 OBJECT-IDENTITY
    STATUS current
    DESCRIPTION
        "User-defined event 4 is in alarm."
    ::= { tlpAlarmUserDefined 4 }

tlpAlarmUserDefined05 OBJECT-IDENTITY
    STATUS current
    DESCRIPTION
        "User-defined event 5 is in alarm."
    ::= { tlpAlarmUserDefined 5 }

tlpAlarmUserDefined06 OBJECT-IDENTITY
    STATUS current
    DESCRIPTION
        "User-defined event 6 is in alarm."
    ::= { tlpAlarmUserDefined 6 }

tlpAlarmUserDefined07 OBJECT-IDENTITY
    STATUS current
    DESCRIPTION
        "User-defined event 7 is in alarm."
    ::= { tlpAlarmUserDefined 7 }

tlpAlarmUserDefined08 OBJECT-IDENTITY
    STATUS current
    DESCRIPTION
        "User-defined event 8 is in alarm."
    ::= { tlpAlarmUserDefined 8 }

tlpAlarmUserDefined09 OBJECT-IDENTITY
    STATUS current
    DESCRIPTION
        "User-defined event 9 is in alarm."
    ::= { tlpAlarmUserDefined 9 }

tlpUpsAlarmBatteryBad OBJECT-IDENTITY
    STATUS current
    DESCRIPTION
        "One or more batteries have been determined to require replacement."
    ::= { tlpUpsAlarms 1 }

tlpUpsAlarmOnBattery OBJECT-IDENTITY
    STATUS current
    DESCRIPTION
        "The UPS is drawing power from the batteries."
    ::= { tlpUpsAlarms 2 }

tlpUpsAlarmLowBattery OBJECT-IDENTITY
    STATUS current
    DESCRIPTION
        "The remaining battery charge is less than or equal to the percentage of
        capacity warning specified by tlpUpsConfigBatteryCapacityThreshold."
    ::= { tlpUpsAlarms 3 }

tlpUpsAlarmDepletedBattery OBJECT-IDENTITY
    STATUS current
    DESCRIPTION
        "The UPS will be unable to sustain the present load when and if
        the utility power is lost."
    ::= { tlpUpsAlarms 4 }

tlpUpsAlarmTempBad OBJECT-IDENTITY
    STATUS current
    DESCRIPTION
        "A temperature is out of tolerance."
    ::= { tlpUpsAlarms 5 }

tlpUpsAlarmInputBad OBJECT-IDENTITY
    STATUS current
    DESCRIPTION
        "An input condition is out of tolerance."
    ::= { tlpUpsAlarms 6 }

tlpUpsAlarmOutputBad OBJECT-IDENTITY
    STATUS current
    DESCRIPTION
        "An output condition (other than OutputOverload) is out of
        tolerance."
    ::= { tlpUpsAlarms 7 }

tlpUpsAlarmOutputOverload OBJECT-IDENTITY
    STATUS current
    DESCRIPTION
        "The output load exceeds the UPS output capacity."
    ::= { tlpUpsAlarms 8 }

tlpUpsAlarmOnBypass OBJECT-IDENTITY
    STATUS current
    DESCRIPTION
        "The Bypass is presently engaged on the UPS."
    ::= { tlpUpsAlarms 9 }

tlpUpsAlarmBypassBad OBJECT-IDENTITY
    STATUS current
    DESCRIPTION
        "The Bypass is out of tolerance."
    ::= { tlpUpsAlarms 10 }

tlpUpsAlarmOutputOffAsRequested OBJECT-IDENTITY
    STATUS current
    DESCRIPTION
        "The UPS has shutdown as requested, i.e., the output is off."
    ::= { tlpUpsAlarms 11 }

tlpUpsAlarmUpsOffAsRequested OBJECT-IDENTITY
    STATUS current
    DESCRIPTION
        "The entire UPS has shutdown as commanded."
    ::= { tlpUpsAlarms 12 }

tlpUpsAlarmChargerFailed OBJECT-IDENTITY
    STATUS current
    DESCRIPTION
        "An uncorrected problem has been detected within the UPS
        charger subsystem."
    ::= { tlpUpsAlarms 13 }

tlpUpsAlarmUpsOutputOff OBJECT-IDENTITY
    STATUS current
    DESCRIPTION
        "The output of the UPS is in the off state."
    ::= { tlpUpsAlarms 14 }

tlpUpsAlarmUpsSystemOff OBJECT-IDENTITY
    STATUS current
    DESCRIPTION
        "The UPS system is in the off state."
    ::= { tlpUpsAlarms 15 }

tlpUpsAlarmFanFailure OBJECT-IDENTITY
    STATUS current
    DESCRIPTION
        "The failure of one or more fans in the UPS has been detected."
    ::= { tlpUpsAlarms 16 }

tlpUpsAlarmFuseFailure OBJECT-IDENTITY
    STATUS current
    DESCRIPTION
        "The failure of one or more fuses has been detected."
    ::= { tlpUpsAlarms 17 }

tlpUpsAlarmGeneralFault OBJECT-IDENTITY
    STATUS current
    DESCRIPTION
        "A general fault in the UPS has been detected."
    ::= { tlpUpsAlarms 18 }

tlpUpsAlarmDiagnosticTestFailed OBJECT-IDENTITY
    STATUS current
    DESCRIPTION
        "The result of the last diagnostic test indicates a failure."
    ::= { tlpUpsAlarms 19 }

tlpUpsAlarmAwaitingPower OBJECT-IDENTITY
    STATUS current
    DESCRIPTION
        "The UPS output is off and the UPS is awaiting the return of
        input power."
    ::= { tlpUpsAlarms 20 }

tlpUpsAlarmShutdownPending OBJECT-IDENTITY
    STATUS current
    DESCRIPTION
        "A tlpUpsShutdownAfterDelay countdown is underway."
    ::= { tlpUpsAlarms 21 }

tlpUpsAlarmShutdownImminent OBJECT-IDENTITY
    STATUS current
    DESCRIPTION
        "The UPS will turn off power to the load in less than 5 seconds;
        this may be either a timed shutdown or a low battery shutdown."
    ::= { tlpUpsAlarms 22 }

tlpUpsAlarmLoadLevelAboveThreshold OBJECT IDENTIFIER
    ::= { tlpUpsAlarms 23 }

tlpUpsAlarmLoadLevelAboveThresholdTotal OBJECT-IDENTITY
    STATUS current
    DESCRIPTION
        "The total load level is above the designated threshold."
    ::= { tlpUpsAlarmLoadLevelAboveThreshold 1 }

tlpUpsAlarmLoadLevelAboveThresholdPhase1 OBJECT-IDENTITY
    STATUS current
    DESCRIPTION
        "The load level on phase 1 exceeds load limits."
    ::= { tlpUpsAlarmLoadLevelAboveThreshold 2 }

tlpUpsAlarmLoadLevelAboveThresholdPhase2 OBJECT-IDENTITY
    STATUS current
    DESCRIPTION
        "The load level on phase 2 exceeds load limits."
    ::= { tlpUpsAlarmLoadLevelAboveThreshold 3 }

tlpUpsAlarmLoadLevelAboveThresholdPhase3 OBJECT-IDENTITY
    STATUS current
    DESCRIPTION
        "The load level on phase 3 exceeds load limits."
    ::= { tlpUpsAlarmLoadLevelAboveThreshold 4 }

tlpUpsAlarmOutputCurrentChanged OBJECT-IDENTITY
    STATUS current
    DESCRIPTION
        "The output current changed from its last known value."
    ::= { tlpUpsAlarms 24 }

tlpUpsAlarmBatteryAgeAboveThreshold OBJECT-IDENTITY
    STATUS current
    DESCRIPTION
        "One or more batteries have been determined to require replacement."
    ::= { tlpUpsAlarms 25 }

tlpUpsAlarmLoadOff OBJECT IDENTIFIER
    ::= { tlpUpsAlarms 26 }

tlpUpsAlarmLoadOff01 OBJECT-IDENTITY
    STATUS current
    DESCRIPTION
        "Load 1 is off."
    ::= { tlpUpsAlarmLoadOff 1 }

tlpUpsAlarmLoadOff02 OBJECT-IDENTITY
    STATUS current
    DESCRIPTION
        "Load 2 is off."
    ::= { tlpUpsAlarmLoadOff 2 }

tlpUpsAlarmLoadOff03 OBJECT-IDENTITY
    STATUS current
    DESCRIPTION
        "Load 3 is off."
    ::= { tlpUpsAlarmLoadOff 3 }

tlpUpsAlarmLoadOff04 OBJECT-IDENTITY
    STATUS current
    DESCRIPTION
        "Load 4 is off."
    ::= { tlpUpsAlarmLoadOff 4 }

tlpUpsAlarmLoadOff05 OBJECT-IDENTITY
    STATUS current
    DESCRIPTION
        "Load 5 is off."
    ::= { tlpUpsAlarmLoadOff 5 }

tlpUpsAlarmLoadOff06 OBJECT-IDENTITY
    STATUS current
    DESCRIPTION
        "Load 6 is off."
    ::= { tlpUpsAlarmLoadOff 6 }

tlpUpsAlarmLoadOff07 OBJECT-IDENTITY
    STATUS current
    DESCRIPTION
        "Load 7 is off."
    ::= { tlpUpsAlarmLoadOff 7 }

tlpUpsAlarmLoadOff08 OBJECT-IDENTITY
    STATUS current
    DESCRIPTION
        "Load 8 is off."
    ::= { tlpUpsAlarmLoadOff 8 }

tlpUpsAlarmLoadOff09 OBJECT-IDENTITY
    STATUS current
    DESCRIPTION
        "Load 9 is off."
    ::= { tlpUpsAlarmLoadOff 9 }

tlpUpsAlarmLoadOff10 OBJECT-IDENTITY
    STATUS current
    DESCRIPTION
        "Load 10 is off."
    ::= { tlpUpsAlarmLoadOff 10 }

tlpUpsAlarmLoadOff11 OBJECT-IDENTITY
    STATUS current
    DESCRIPTION
        "Load 11 is off."
    ::= { tlpUpsAlarmLoadOff 11 }

tlpUpsAlarmLoadOff12 OBJECT-IDENTITY
    STATUS current
    DESCRIPTION
        "Load 12 is off."
    ::= { tlpUpsAlarmLoadOff 12 }

tlpUpsAlarmLoadOff13 OBJECT-IDENTITY
    STATUS current
    DESCRIPTION
        "Load 13 is off."
    ::= { tlpUpsAlarmLoadOff 13 }

tlpUpsAlarmLoadOff14 OBJECT-IDENTITY
    STATUS current
    DESCRIPTION
        "Load 14 is off."
    ::= { tlpUpsAlarmLoadOff 14 }

tlpUpsAlarmLoadOff15 OBJECT-IDENTITY
    STATUS current
    DESCRIPTION
        "Load 15 is off."
    ::= { tlpUpsAlarmLoadOff 15 }

tlpUpsAlarmLoadOff16 OBJECT-IDENTITY
    STATUS current
    DESCRIPTION
        "Load 16 is off."
    ::= { tlpUpsAlarmLoadOff 16 }

tlpUpsAlarmLoadOff17 OBJECT-IDENTITY
    STATUS current
    DESCRIPTION
        "Load 17 is off."
    ::= { tlpUpsAlarmLoadOff 17 }

tlpUpsAlarmLoadOff18 OBJECT-IDENTITY
    STATUS current
    DESCRIPTION
        "Load 18 is off."
    ::= { tlpUpsAlarmLoadOff 18 }

tlpUpsAlarmLoadOff19 OBJECT-IDENTITY
    STATUS current
    DESCRIPTION
        "Load 19 is off."
    ::= { tlpUpsAlarmLoadOff 19 }

tlpUpsAlarmLoadOff20 OBJECT-IDENTITY
    STATUS current
    DESCRIPTION
        "Load 20 is off."
    ::= { tlpUpsAlarmLoadOff 20 }

tlpUpsAlarmLoadOff21 OBJECT-IDENTITY
    STATUS current
    DESCRIPTION
        "Load 21 is off."
    ::= { tlpUpsAlarmLoadOff 21 }

tlpUpsAlarmLoadOff22 OBJECT-IDENTITY
    STATUS current
    DESCRIPTION
        "Load 22 is off."
    ::= { tlpUpsAlarmLoadOff 22 }

tlpUpsAlarmLoadOff23 OBJECT-IDENTITY
    STATUS current
    DESCRIPTION
        "Load 23 is off."
    ::= { tlpUpsAlarmLoadOff 23 }

tlpUpsAlarmLoadOff24 OBJECT-IDENTITY
    STATUS current
    DESCRIPTION
        "Load 24 is off."
    ::= { tlpUpsAlarmLoadOff 24 }

tlpUpsAlarmLoadOff25 OBJECT-IDENTITY
    STATUS current
    DESCRIPTION
        "Load 25 is off."
    ::= { tlpUpsAlarmLoadOff 25 }

tlpUpsAlarmLoadOff26 OBJECT-IDENTITY
    STATUS current
    DESCRIPTION
        "Load 26 is off."
    ::= { tlpUpsAlarmLoadOff 26 }

tlpUpsAlarmLoadOff27 OBJECT-IDENTITY
    STATUS current
    DESCRIPTION
        "Load 27 is off."
    ::= { tlpUpsAlarmLoadOff 27 }

tlpUpsAlarmLoadOff28 OBJECT-IDENTITY
    STATUS current
    DESCRIPTION
        "Load 28 is off."
    ::= { tlpUpsAlarmLoadOff 28 }

tlpUpsAlarmLoadOff29 OBJECT-IDENTITY
    STATUS current
    DESCRIPTION
        "Load 29 is off."
    ::= { tlpUpsAlarmLoadOff 29 }

tlpUpsAlarmLoadOff30 OBJECT-IDENTITY
    STATUS current
    DESCRIPTION
        "Load 30 is off."
    ::= { tlpUpsAlarmLoadOff 30 }

tlpUpsAlarmLoadOff31 OBJECT-IDENTITY
    STATUS current
    DESCRIPTION
        "Load 31 is off."
    ::= { tlpUpsAlarmLoadOff 31 }

tlpUpsAlarmLoadOff32 OBJECT-IDENTITY
    STATUS current
    DESCRIPTION
        "Load 32 is off."
    ::= { tlpUpsAlarmLoadOff 32 }

tlpUpsAlarmLoadOff33 OBJECT-IDENTITY
    STATUS current
    DESCRIPTION
        "Load 33 is off."
    ::= { tlpUpsAlarmLoadOff 33 }

tlpUpsAlarmLoadOff34 OBJECT-IDENTITY
    STATUS current
    DESCRIPTION
        "Load 34 is off."
    ::= { tlpUpsAlarmLoadOff 34 }

tlpUpsAlarmLoadOff35 OBJECT-IDENTITY
    STATUS current
    DESCRIPTION
        "Load 35 is off."
    ::= { tlpUpsAlarmLoadOff 35 }

tlpUpsAlarmLoadOff36 OBJECT-IDENTITY
    STATUS current
    DESCRIPTION
        "Load 36 is off."
    ::= { tlpUpsAlarmLoadOff 36 }

tlpUpsAlarmLoadOff37 OBJECT-IDENTITY
    STATUS current
    DESCRIPTION
        "Load 37 is off."
    ::= { tlpUpsAlarmLoadOff 37 }

tlpUpsAlarmLoadOff38 OBJECT-IDENTITY
    STATUS current
    DESCRIPTION
        "Load 38 is off."
    ::= { tlpUpsAlarmLoadOff 38 }

tlpUpsAlarmLoadOff39 OBJECT-IDENTITY
    STATUS current
    DESCRIPTION
        "Load 39 is off."
    ::= { tlpUpsAlarmLoadOff 39 }

tlpUpsAlarmLoadOff40 OBJECT-IDENTITY
    STATUS current
    DESCRIPTION
        "Load 40 is off."
    ::= { tlpUpsAlarmLoadOff 40 }

tlpUpsAlarmCurrentAboveThreshold OBJECT IDENTIFIER
    ::= { tlpUpsAlarms 27 }

tlpUpsAlarmCurrentAboveThreshold1 OBJECT-IDENTITY
    STATUS current
    DESCRIPTION
        "The output current on phase 1 exceeds load limits."
    ::= { tlpUpsAlarmCurrentAboveThreshold 1 }

tlpUpsAlarmCurrentAboveThreshold2 OBJECT-IDENTITY
    STATUS current
    DESCRIPTION
        "The output current on phase 2 exceeds load limits."
    ::= { tlpUpsAlarmCurrentAboveThreshold 2 }

tlpUpsAlarmCurrentAboveThreshold3 OBJECT-IDENTITY
    STATUS current
    DESCRIPTION
        "The output current on phase 3 exceeds load limits."
    ::= { tlpUpsAlarmCurrentAboveThreshold 3 }

tlpUpsAlarmRuntimeBelowWarningLevel OBJECT-IDENTITY
    STATUS current
    DESCRIPTION
        "The battery seconds remaining is below warning level."
    ::= { tlpUpsAlarms 28 }

tlpUpsAlarmBusStartVoltageLow OBJECT-IDENTITY
    STATUS current
    DESCRIPTION
        "The inverter start up bus voltage is too low."
    ::= { tlpUpsAlarms 29 }

tlpUpsAlarmBusOverVoltage OBJECT-IDENTITY
    STATUS current
    DESCRIPTION
        "The inverter bus voltage is too high."
    ::= { tlpUpsAlarms 30 }

tlpUpsAlarmBusUnderVoltage OBJECT-IDENTITY
    STATUS current
    DESCRIPTION
        "The inverter bus voltage is too low."
    ::= { tlpUpsAlarms 31 }

tlpUpsAlarmBusVoltageUnbalanced OBJECT-IDENTITY
    STATUS current
    DESCRIPTION
        "The inverter bus voltage is not balanced."
    ::= { tlpUpsAlarms 32 }

tlpUpsAlarmInverterSoftStartBad OBJECT-IDENTITY
    STATUS current
    DESCRIPTION
        "The inverter bus voltage cannot reach desired voltage within a
        specified duration."
    ::= { tlpUpsAlarms 33 }

tlpUpsAlarmInverterOverVoltage OBJECT-IDENTITY
    STATUS current
    DESCRIPTION
        "The inverter voltage is too high."
    ::= { tlpUpsAlarms 34 }

tlpUpsAlarmInverterUnderVoltage OBJECT-IDENTITY
    STATUS current
    DESCRIPTION
        "The inverter voltage is too low."
    ::= { tlpUpsAlarms 35 }

tlpUpsAlarmInverterCircuitBad OBJECT-IDENTITY
    STATUS current
    DESCRIPTION
        "The inverter output is shorted."
    ::= { tlpUpsAlarms 36 }

tlpUpsAlarmBatteryOverVoltage OBJECT-IDENTITY
    STATUS current
    DESCRIPTION
        "The battery voltage is too high."
    ::= { tlpUpsAlarms 37 }

tlpUpsAlarmBatteryUnderVoltage OBJECT-IDENTITY
    STATUS current
    DESCRIPTION
        "The battery voltage is too low."
    ::= { tlpUpsAlarms 38 }

tlpUpsAlarmSiteWiringFault OBJECT-IDENTITY
    STATUS current
    DESCRIPTION
        "The utility input wiring is faulty."
    ::= { tlpUpsAlarms 39 }

tlpUpsAlarmOverTemperatureProtection OBJECT-IDENTITY
    STATUS current
    DESCRIPTION
        "The over temperature protection is activated."
    ::= { tlpUpsAlarms 40 }

tlpUpsAlarmOverCharged OBJECT-IDENTITY
    STATUS current
    DESCRIPTION
        "The UPS is over charged."
    ::= { tlpUpsAlarms 41 }

tlpUpsAlarmEPOActive OBJECT-IDENTITY
    STATUS current
    DESCRIPTION
        "The EPO is currently activate."
    ::= { tlpUpsAlarms 42 }

tlpUpsAlarmBypassFrequencyBad OBJECT-IDENTITY
    STATUS current
    DESCRIPTION
        "The bypass frequency is out of tolerance."
    ::= { tlpUpsAlarms 43 }

tlpUpsAlarmExternalSmartBatteryAgeAboveThreshold OBJECT-IDENTITY
    STATUS current
    DESCRIPTION
        "One or more external smart batteries have been determined to require
        replacement."
    ::= { tlpUpsAlarms 44 }

tlpUpsAlarmExternalNonSmartBatteryAgeAboveThreshold OBJECT-IDENTITY
    STATUS current
    DESCRIPTION
        "One or more external non-smart batteries have been determined to require
        replacement."
    ::= { tlpUpsAlarms 45 }

tlpUpsAlarmSmartBatteryCommLost OBJECT-IDENTITY
    STATUS current
    DESCRIPTION
        "Communications with the smart batteries was lost."
    ::= { tlpUpsAlarms 46 }

tlpUpsAlarmLoadsNotAllOn OBJECT-IDENTITY
    STATUS current
    DESCRIPTION
        "One of more loads are not on."
    ::= { tlpUpsAlarms 47 }

tlpPduAlarmLoadLevelAboveThreshold OBJECT-IDENTITY
    STATUS current
    DESCRIPTION
        "The load level is above the designated threshold."
    ::= { tlpPduAlarms 1 }

tlpPduAlarmInputBad OBJECT-IDENTITY
    STATUS current
    DESCRIPTION
        "An input condition is out of tolerance."
    ::= { tlpPduAlarms 2 }

tlpPduAlarmOutputBad OBJECT-IDENTITY
    STATUS current
    DESCRIPTION
        "An output condition (other than OutputOverload) is  out of
        tolerance."
    ::= { tlpPduAlarms 3 }

tlpPduAlarmOutputOverload OBJECT-IDENTITY
    STATUS current
    DESCRIPTION
        "The output load exceeds the pdu output capacity."
    ::= { tlpPduAlarms 4 }

tlpPduAlarmOutputOff OBJECT-IDENTITY
    STATUS current
    DESCRIPTION
        "The output of the pdu is in the off state."
    ::= { tlpPduAlarms 5 }

tlpPduAlarmLoadOff OBJECT IDENTIFIER
    ::= { tlpPduAlarms 6 }

tlpPduAlarmLoadOff01 OBJECT-IDENTITY
    STATUS current
    DESCRIPTION
        "Load 1 is off."
    ::= { tlpPduAlarmLoadOff 1 }

tlpPduAlarmLoadOff02 OBJECT-IDENTITY
    STATUS current
    DESCRIPTION
        "Load 2 is off."
    ::= { tlpPduAlarmLoadOff 2 }

tlpPduAlarmLoadOff03 OBJECT-IDENTITY
    STATUS current
    DESCRIPTION
        "Load 3 is off."
    ::= { tlpPduAlarmLoadOff 3 }

tlpPduAlarmLoadOff04 OBJECT-IDENTITY
    STATUS current
    DESCRIPTION
        "Load 4 is off."
    ::= { tlpPduAlarmLoadOff 4 }

tlpPduAlarmLoadOff05 OBJECT-IDENTITY
    STATUS current
    DESCRIPTION
        "Load 5 is off."
    ::= { tlpPduAlarmLoadOff 5 }

tlpPduAlarmLoadOff06 OBJECT-IDENTITY
    STATUS current
    DESCRIPTION
        "Load 6 is off."
    ::= { tlpPduAlarmLoadOff 6 }

tlpPduAlarmLoadOff07 OBJECT-IDENTITY
    STATUS current
    DESCRIPTION
        "Load 7 is off."
    ::= { tlpPduAlarmLoadOff 7 }

tlpPduAlarmLoadOff08 OBJECT-IDENTITY
    STATUS current
    DESCRIPTION
        "Load 8 is off."
    ::= { tlpPduAlarmLoadOff 8 }

tlpPduAlarmLoadOff09 OBJECT-IDENTITY
    STATUS current
    DESCRIPTION
        "Load 9 is off."
    ::= { tlpPduAlarmLoadOff 9 }

tlpPduAlarmLoadOff10 OBJECT-IDENTITY
    STATUS current
    DESCRIPTION
        "Load 10 is off."
    ::= { tlpPduAlarmLoadOff 10 }

tlpPduAlarmLoadOff11 OBJECT-IDENTITY
    STATUS current
    DESCRIPTION
        "Load 11 is off."
    ::= { tlpPduAlarmLoadOff 11 }

tlpPduAlarmLoadOff12 OBJECT-IDENTITY
    STATUS current
    DESCRIPTION
        "Load 12 is off."
    ::= { tlpPduAlarmLoadOff 12 }

tlpPduAlarmLoadOff13 OBJECT-IDENTITY
    STATUS current
    DESCRIPTION
        "Load 13 is off."
    ::= { tlpPduAlarmLoadOff 13 }

tlpPduAlarmLoadOff14 OBJECT-IDENTITY
    STATUS current
    DESCRIPTION
        "Load 14 is off."
    ::= { tlpPduAlarmLoadOff 14 }

tlpPduAlarmLoadOff15 OBJECT-IDENTITY
    STATUS current
    DESCRIPTION
        "Load 15 is off."
    ::= { tlpPduAlarmLoadOff 15 }

tlpPduAlarmLoadOff16 OBJECT-IDENTITY
    STATUS current
    DESCRIPTION
        "Load 16 is off."
    ::= { tlpPduAlarmLoadOff 16 }

tlpPduAlarmLoadOff17 OBJECT-IDENTITY
    STATUS current
    DESCRIPTION
        "Load 17 is off."
    ::= { tlpPduAlarmLoadOff 17 }

tlpPduAlarmLoadOff18 OBJECT-IDENTITY
    STATUS current
    DESCRIPTION
        "Load 18 is off."
    ::= { tlpPduAlarmLoadOff 18 }

tlpPduAlarmLoadOff19 OBJECT-IDENTITY
    STATUS current
    DESCRIPTION
        "Load 19 is off."
    ::= { tlpPduAlarmLoadOff 19 }

tlpPduAlarmLoadOff20 OBJECT-IDENTITY
    STATUS current
    DESCRIPTION
        "Load 20 is off."
    ::= { tlpPduAlarmLoadOff 20 }

tlpPduAlarmLoadOff21 OBJECT-IDENTITY
    STATUS current
    DESCRIPTION
        "Load 21 is off."
    ::= { tlpPduAlarmLoadOff 21 }

tlpPduAlarmLoadOff22 OBJECT-IDENTITY
    STATUS current
    DESCRIPTION
        "Load 22 is off."
    ::= { tlpPduAlarmLoadOff 22 }

tlpPduAlarmLoadOff23 OBJECT-IDENTITY
    STATUS current
    DESCRIPTION
        "Load 23 is off."
    ::= { tlpPduAlarmLoadOff 23 }

tlpPduAlarmLoadOff24 OBJECT-IDENTITY
    STATUS current
    DESCRIPTION
        "Load 24 is off."
    ::= { tlpPduAlarmLoadOff 24 }

tlpPduAlarmLoadOff25 OBJECT-IDENTITY
    STATUS current
    DESCRIPTION
        "Load 25 is off."
    ::= { tlpPduAlarmLoadOff 25 }

tlpPduAlarmLoadOff26 OBJECT-IDENTITY
    STATUS current
    DESCRIPTION
        "Load 26 is off."
    ::= { tlpPduAlarmLoadOff 26 }

tlpPduAlarmLoadOff27 OBJECT-IDENTITY
    STATUS current
    DESCRIPTION
        "Load 27 is off."
    ::= { tlpPduAlarmLoadOff 27 }

tlpPduAlarmLoadOff28 OBJECT-IDENTITY
    STATUS current
    DESCRIPTION
        "Load 28 is off."
    ::= { tlpPduAlarmLoadOff 28 }

tlpPduAlarmLoadOff29 OBJECT-IDENTITY
    STATUS current
    DESCRIPTION
        "Load 29 is off."
    ::= { tlpPduAlarmLoadOff 29 }

tlpPduAlarmLoadOff30 OBJECT-IDENTITY
    STATUS current
    DESCRIPTION
        "Load 30 is off."
    ::= { tlpPduAlarmLoadOff 30 }

tlpPduAlarmLoadOff31 OBJECT-IDENTITY
    STATUS current
    DESCRIPTION
        "Load 31 is off."
    ::= { tlpPduAlarmLoadOff 31 }

tlpPduAlarmLoadOff32 OBJECT-IDENTITY
    STATUS current
    DESCRIPTION
        "Load 32 is off."
    ::= { tlpPduAlarmLoadOff 32 }

tlpPduAlarmLoadOff33 OBJECT-IDENTITY
    STATUS current
    DESCRIPTION
        "Load 33 is off."
    ::= { tlpPduAlarmLoadOff 33 }

tlpPduAlarmLoadOff34 OBJECT-IDENTITY
    STATUS current
    DESCRIPTION
        "Load 34 is off."
    ::= { tlpPduAlarmLoadOff 34 }

tlpPduAlarmLoadOff35 OBJECT-IDENTITY
    STATUS current
    DESCRIPTION
        "Load 35 is off."
    ::= { tlpPduAlarmLoadOff 35 }

tlpPduAlarmLoadOff36 OBJECT-IDENTITY
    STATUS current
    DESCRIPTION
        "Load 36 is off."
    ::= { tlpPduAlarmLoadOff 36 }

tlpPduAlarmLoadOff37 OBJECT-IDENTITY
    STATUS current
    DESCRIPTION
        "Load 37 is off."
    ::= { tlpPduAlarmLoadOff 37 }

tlpPduAlarmLoadOff38 OBJECT-IDENTITY
    STATUS current
    DESCRIPTION
        "Load 38 is off."
    ::= { tlpPduAlarmLoadOff 38 }

tlpPduAlarmLoadOff39 OBJECT-IDENTITY
    STATUS current
    DESCRIPTION
        "Load 39 is off."
    ::= { tlpPduAlarmLoadOff 39 }

tlpPduAlarmLoadOff40 OBJECT-IDENTITY
    STATUS current
    DESCRIPTION
        "Load 40 is off."
    ::= { tlpPduAlarmLoadOff 40 }

tlpPduAlarmCircuitBreakerOpen OBJECT IDENTIFIER
    ::= { tlpPduAlarms 7 }

tlpPduAlarmCircuitBreakerOpen01 OBJECT-IDENTITY
    STATUS current
    DESCRIPTION
        "Circuit breaker 1 is open."
    ::= { tlpPduAlarmCircuitBreakerOpen 1 }

tlpPduAlarmCircuitBreakerOpen02 OBJECT-IDENTITY
    STATUS current
    DESCRIPTION
        "Circuit breaker 2 is open."
    ::= { tlpPduAlarmCircuitBreakerOpen 2 }

tlpPduAlarmCircuitBreakerOpen03 OBJECT-IDENTITY
    STATUS current
    DESCRIPTION
        "Circuit breaker 3 is open."
    ::= { tlpPduAlarmCircuitBreakerOpen 3 }

tlpPduAlarmCircuitBreakerOpen04 OBJECT-IDENTITY
    STATUS current
    DESCRIPTION
        "Circuit breaker 4 is open."
    ::= { tlpPduAlarmCircuitBreakerOpen 4 }

tlpPduAlarmCircuitBreakerOpen05 OBJECT-IDENTITY
    STATUS current
    DESCRIPTION
        "Circuit breaker 5 is open."
    ::= { tlpPduAlarmCircuitBreakerOpen 5 }

tlpPduAlarmCircuitBreakerOpen06 OBJECT-IDENTITY
    STATUS current
    DESCRIPTION
        "Circuit breaker 6 is open."
    ::= { tlpPduAlarmCircuitBreakerOpen 6 }

tlpPduAlarmCurrentAboveThreshold OBJECT IDENTIFIER
    ::= { tlpPduAlarms 8 }

tlpPduAlarmCurrentAboveThreshold1 OBJECT-IDENTITY
    STATUS current
    DESCRIPTION
        "The output current on phase 1 exceeds load limits."
    ::= { tlpPduAlarmCurrentAboveThreshold 1 }

tlpPduAlarmCurrentAboveThreshold2 OBJECT-IDENTITY
    STATUS current
    DESCRIPTION
        "The output current on phase 2 exceeds load limits."
    ::= { tlpPduAlarmCurrentAboveThreshold 2 }

tlpPduAlarmCurrentAboveThreshold3 OBJECT-IDENTITY
    STATUS current
    DESCRIPTION
        "The output current on phase 3 exceeds load limits."
    ::= { tlpPduAlarmCurrentAboveThreshold 3 }

tlpPduAlarmLoadsNotAllOn OBJECT-IDENTITY
    STATUS current
    DESCRIPTION
        "One of more loads are not on."
    ::= { tlpPduAlarms 9 }

tlpEnvAlarmTemperatureBeyondLimits OBJECT-IDENTITY
    STATUS current
    DESCRIPTION
        "The temperature exceeds limits."
    ::= { tlpEnvAlarms 1 }

tlpEnvAlarmHumidityBeyondLimits OBJECT-IDENTITY
    STATUS current
    DESCRIPTION
        "The humidity exceeds limits."
    ::= { tlpEnvAlarms 2 }

tlpEnvAlarmInputContact OBJECT IDENTIFIER
    ::= { tlpEnvAlarms 3 }

tlpEnvAlarmInputContact01 OBJECT-IDENTITY
    STATUS current
    DESCRIPTION
        "Input contact 1 is in alarm."
    ::= { tlpEnvAlarmInputContact 1 }

tlpEnvAlarmInputContact02 OBJECT-IDENTITY
    STATUS current
    DESCRIPTION
        "Input contact 2 is in alarm."
    ::= { tlpEnvAlarmInputContact 2 }

tlpEnvAlarmInputContact03 OBJECT-IDENTITY
    STATUS current
    DESCRIPTION
        "Input contact 3 is in alarm."
    ::= { tlpEnvAlarmInputContact 3 }

tlpEnvAlarmInputContact04 OBJECT-IDENTITY
    STATUS current
    DESCRIPTION
        "Input contact 4 is in alarm."
    ::= { tlpEnvAlarmInputContact 4 }

tlpEnvAlarmOutputContact OBJECT IDENTIFIER
    ::= { tlpEnvAlarms 4 }

tlpEnvAlarmOutputContact01 OBJECT-IDENTITY
    STATUS current
    DESCRIPTION
        "Output contact 1 is in alarm."
    ::= { tlpEnvAlarmOutputContact 1 }

tlpEnvAlarmOutputContact02 OBJECT-IDENTITY
    STATUS current
    DESCRIPTION
        "Output contact 2 is in alarm."
    ::= { tlpEnvAlarmOutputContact 2 }

tlpEnvAlarmOutputContact03 OBJECT-IDENTITY
    STATUS current
    DESCRIPTION
        "Output contact 3 is in alarm."
    ::= { tlpEnvAlarmOutputContact 3 }

tlpEnvAlarmOutputContact04 OBJECT-IDENTITY
    STATUS current
    DESCRIPTION
        "Output contact 4 is in alarm."
    ::= { tlpEnvAlarmOutputContact 4 }

tlpAtsAlarmOutage OBJECT IDENTIFIER
    ::= { tlpAtsAlarms 1 }

tlpAtsAlarmSource1Outage OBJECT-IDENTITY
    STATUS current
    DESCRIPTION
        "Input on source 1 is not present. For atss with the designation
        of primary and secondary, this alarm denotes input on the primary
        source is not present."
    ::= { tlpAtsAlarmOutage 1 }

tlpAtsAlarmSource2Outage OBJECT-IDENTITY
    STATUS current
    DESCRIPTION
        "Input on source 2 is not present. For atss with the designation
        of primary and secondary, this alarm denotes input on the secondary
        source is not present."
    ::= { tlpAtsAlarmOutage 2 }

tlpAtsAlarmTemperature OBJECT IDENTIFIER
    ::= { tlpAtsAlarms 2 }

tlpAtsAlarmSystemTemperature OBJECT-IDENTITY
    STATUS current
    DESCRIPTION
        "The system temperature is out of tolerance."
    ::= { tlpAtsAlarmTemperature 1 }

tlpAtsAlarmSource1Temperature OBJECT-IDENTITY
    STATUS current
    DESCRIPTION
        "The source 1 temperature is out of tolerance."
    ::= { tlpAtsAlarmTemperature 2 }

tlpAtsAlarmSource2Temperature OBJECT-IDENTITY
    STATUS current
    DESCRIPTION
        "The source 2 temperature is out of tolerance."
    ::= { tlpAtsAlarmTemperature 3 }

tlpAtsAlarmLoadLevelAboveThreshold OBJECT-IDENTITY
    STATUS current
    DESCRIPTION
        "The load level is above the designated threshold."
    ::= { tlpAtsAlarms 3 }

tlpAtsAlarmInputBad OBJECT-IDENTITY
    STATUS current
    DESCRIPTION
        "An input condition is out of tolerance."
    ::= { tlpAtsAlarms 4 }

tlpAtsAlarmOutputBad OBJECT-IDENTITY
    STATUS current
    DESCRIPTION
        "An output condition (other than OutputOverload) is  out of
        tolerance."
    ::= { tlpAtsAlarms 5 }

tlpAtsAlarmOutputOverload OBJECT-IDENTITY
    STATUS current
    DESCRIPTION
        "The output load exceeds the ats output capacity."
    ::= { tlpAtsAlarms 6 }

tlpAtsAlarmOutputOff OBJECT-IDENTITY
    STATUS current
    DESCRIPTION
        "The output of the ats is in the off state."
    ::= { tlpAtsAlarms 7 }

tlpAtsAlarmLoadOff OBJECT IDENTIFIER
    ::= { tlpAtsAlarms 8 }

tlpAtsAlarmLoadOff01 OBJECT-IDENTITY
    STATUS current
    DESCRIPTION
        "Load 1 is off."
    ::= { tlpAtsAlarmLoadOff 1 }

tlpAtsAlarmLoadOff02 OBJECT-IDENTITY
    STATUS current
    DESCRIPTION
        "Load 2 is off."
    ::= { tlpAtsAlarmLoadOff 2 }

tlpAtsAlarmLoadOff03 OBJECT-IDENTITY
    STATUS current
    DESCRIPTION
        "Load 3 is off."
    ::= { tlpAtsAlarmLoadOff 3 }

tlpAtsAlarmLoadOff04 OBJECT-IDENTITY
    STATUS current
    DESCRIPTION
        "Load 4 is off."
    ::= { tlpAtsAlarmLoadOff 4 }

tlpAtsAlarmLoadOff05 OBJECT-IDENTITY
    STATUS current
    DESCRIPTION
        "Load 5 is off."
    ::= { tlpAtsAlarmLoadOff 5 }

tlpAtsAlarmLoadOff06 OBJECT-IDENTITY
    STATUS current
    DESCRIPTION
        "Load 6 is off."
    ::= { tlpAtsAlarmLoadOff 6 }

tlpAtsAlarmLoadOff07 OBJECT-IDENTITY
    STATUS current
    DESCRIPTION
        "Load 7 is off."
    ::= { tlpAtsAlarmLoadOff 7 }

tlpAtsAlarmLoadOff08 OBJECT-IDENTITY
    STATUS current
    DESCRIPTION
        "Load 8 is off."
    ::= { tlpAtsAlarmLoadOff 8 }

tlpAtsAlarmLoadOff09 OBJECT-IDENTITY
    STATUS current
    DESCRIPTION
        "Load 9 is off."
    ::= { tlpAtsAlarmLoadOff 9 }

tlpAtsAlarmLoadOff10 OBJECT-IDENTITY
    STATUS current
    DESCRIPTION
        "Load 10 is off."
    ::= { tlpAtsAlarmLoadOff 10 }

tlpAtsAlarmLoadOff11 OBJECT-IDENTITY
    STATUS current
    DESCRIPTION
        "Load 11 is off."
    ::= { tlpAtsAlarmLoadOff 11 }

tlpAtsAlarmLoadOff12 OBJECT-IDENTITY
    STATUS current
    DESCRIPTION
        "Load 12 is off."
    ::= { tlpAtsAlarmLoadOff 12 }

tlpAtsAlarmLoadOff13 OBJECT-IDENTITY
    STATUS current
    DESCRIPTION
        "Load 13 is off."
    ::= { tlpAtsAlarmLoadOff 13 }

tlpAtsAlarmLoadOff14 OBJECT-IDENTITY
    STATUS current
    DESCRIPTION
        "Load 14 is off."
    ::= { tlpAtsAlarmLoadOff 14 }

tlpAtsAlarmLoadOff15 OBJECT-IDENTITY
    STATUS current
    DESCRIPTION
        "Load 15 is off."
    ::= { tlpAtsAlarmLoadOff 15 }

tlpAtsAlarmLoadOff16 OBJECT-IDENTITY
    STATUS current
    DESCRIPTION
        "Load 16 is off."
    ::= { tlpAtsAlarmLoadOff 16 }

tlpAtsAlarmLoadOff17 OBJECT-IDENTITY
    STATUS current
    DESCRIPTION
        "Load 17 is off."
    ::= { tlpAtsAlarmLoadOff 17 }

tlpAtsAlarmLoadOff18 OBJECT-IDENTITY
    STATUS current
    DESCRIPTION
        "Load 18 is off."
    ::= { tlpAtsAlarmLoadOff 18 }

tlpAtsAlarmLoadOff19 OBJECT-IDENTITY
    STATUS current
    DESCRIPTION
        "Load 19 is off."
    ::= { tlpAtsAlarmLoadOff 19 }

tlpAtsAlarmLoadOff20 OBJECT-IDENTITY
    STATUS current
    DESCRIPTION
        "Load 20 is off."
    ::= { tlpAtsAlarmLoadOff 20 }

tlpAtsAlarmLoadOff21 OBJECT-IDENTITY
    STATUS current
    DESCRIPTION
        "Load 21 is off."
    ::= { tlpAtsAlarmLoadOff 21 }

tlpAtsAlarmLoadOff22 OBJECT-IDENTITY
    STATUS current
    DESCRIPTION
        "Load 22 is off."
    ::= { tlpAtsAlarmLoadOff 22 }

tlpAtsAlarmLoadOff23 OBJECT-IDENTITY
    STATUS current
    DESCRIPTION
        "Load 23 is off."
    ::= { tlpAtsAlarmLoadOff 23 }

tlpAtsAlarmLoadOff24 OBJECT-IDENTITY
    STATUS current
    DESCRIPTION
        "Load 24 is off."
    ::= { tlpAtsAlarmLoadOff 24 }

tlpAtsAlarmLoadOff25 OBJECT-IDENTITY
    STATUS current
    DESCRIPTION
        "Load 25 is off."
    ::= { tlpAtsAlarmLoadOff 25 }

tlpAtsAlarmLoadOff26 OBJECT-IDENTITY
    STATUS current
    DESCRIPTION
        "Load 26 is off."
    ::= { tlpAtsAlarmLoadOff 26 }

tlpAtsAlarmLoadOff27 OBJECT-IDENTITY
    STATUS current
    DESCRIPTION
        "Load 27 is off."
    ::= { tlpAtsAlarmLoadOff 27 }

tlpAtsAlarmLoadOff28 OBJECT-IDENTITY
    STATUS current
    DESCRIPTION
        "Load 28 is off."
    ::= { tlpAtsAlarmLoadOff 28 }

tlpAtsAlarmLoadOff29 OBJECT-IDENTITY
    STATUS current
    DESCRIPTION
        "Load 29 is off."
    ::= { tlpAtsAlarmLoadOff 29 }

tlpAtsAlarmLoadOff30 OBJECT-IDENTITY
    STATUS current
    DESCRIPTION
        "Load 30 is off."
    ::= { tlpAtsAlarmLoadOff 30 }

tlpAtsAlarmLoadOff31 OBJECT-IDENTITY
    STATUS current
    DESCRIPTION
        "Load 31 is off."
    ::= { tlpAtsAlarmLoadOff 31 }

tlpAtsAlarmLoadOff32 OBJECT-IDENTITY
    STATUS current
    DESCRIPTION
        "Load 32 is off."
    ::= { tlpAtsAlarmLoadOff 32 }

tlpAtsAlarmLoadOff33 OBJECT-IDENTITY
    STATUS current
    DESCRIPTION
        "Load 33 is off."
    ::= { tlpAtsAlarmLoadOff 33 }

tlpAtsAlarmLoadOff34 OBJECT-IDENTITY
    STATUS current
    DESCRIPTION
        "Load 34 is off."
    ::= { tlpAtsAlarmLoadOff 34 }

tlpAtsAlarmLoadOff35 OBJECT-IDENTITY
    STATUS current
    DESCRIPTION
        "Load 35 is off."
    ::= { tlpAtsAlarmLoadOff 35 }

tlpAtsAlarmLoadOff36 OBJECT-IDENTITY
    STATUS current
    DESCRIPTION
        "Load 36 is off."
    ::= { tlpAtsAlarmLoadOff 36 }

tlpAtsAlarmLoadOff37 OBJECT-IDENTITY
    STATUS current
    DESCRIPTION
        "Load 37 is off."
    ::= { tlpAtsAlarmLoadOff 37 }

tlpAtsAlarmLoadOff38 OBJECT-IDENTITY
    STATUS current
    DESCRIPTION
        "Load 38 is off."
    ::= { tlpAtsAlarmLoadOff 38 }

tlpAtsAlarmLoadOff39 OBJECT-IDENTITY
    STATUS current
    DESCRIPTION
        "Load 39 is off."
    ::= { tlpAtsAlarmLoadOff 39 }

tlpAtsAlarmLoadOff40 OBJECT-IDENTITY
    STATUS current
    DESCRIPTION
        "Load 40 is off."
    ::= { tlpAtsAlarmLoadOff 40 }

tlpAtsAlarmCircuitBreakerOpen OBJECT IDENTIFIER
    ::= { tlpAtsAlarms 9 }

tlpAtsAlarmCircuitBreakerOpen01 OBJECT-IDENTITY
    STATUS current
    DESCRIPTION
        "Circuit breaker 1 is open."
    ::= { tlpAtsAlarmCircuitBreakerOpen 1 }

tlpAtsAlarmCircuitBreakerOpen02 OBJECT-IDENTITY
    STATUS current
    DESCRIPTION
        "Circuit breaker 2 is open."
    ::= { tlpAtsAlarmCircuitBreakerOpen 2 }

tlpAtsAlarmCircuitBreakerOpen03 OBJECT-IDENTITY
    STATUS current
    DESCRIPTION
        "Circuit breaker 3 is open."
    ::= { tlpAtsAlarmCircuitBreakerOpen 3 }

tlpAtsAlarmCircuitBreakerOpen04 OBJECT-IDENTITY
    STATUS current
    DESCRIPTION
        "Circuit breaker 4 is open."
    ::= { tlpAtsAlarmCircuitBreakerOpen 4 }

tlpAtsAlarmCircuitBreakerOpen05 OBJECT-IDENTITY
    STATUS current
    DESCRIPTION
        "Circuit breaker 5 is open."
    ::= { tlpAtsAlarmCircuitBreakerOpen 5 }

tlpAtsAlarmCircuitBreakerOpen06 OBJECT-IDENTITY
    STATUS current
    DESCRIPTION
        "Circuit breaker 6 is open."
    ::= { tlpAtsAlarmCircuitBreakerOpen 6 }

tlpAtsAlarmCurrentAboveThreshold OBJECT IDENTIFIER
    ::= { tlpAtsAlarms 10 }

tlpAtsAlarmCurrentAboveThresholdA1 OBJECT-IDENTITY
    STATUS current
    DESCRIPTION
        "The output current on input source 1 phase 1 exceeds load limits."
    ::= { tlpAtsAlarmCurrentAboveThreshold 1 }

tlpAtsAlarmCurrentAboveThresholdA2 OBJECT-IDENTITY
    STATUS current
    DESCRIPTION
        "The output current on input source 1 phase 2 exceeds load limits."
    ::= { tlpAtsAlarmCurrentAboveThreshold 2 }

tlpAtsAlarmCurrentAboveThresholdA3 OBJECT-IDENTITY
    STATUS current
    DESCRIPTION
        "The output current on input source 1 phase 3 exceeds load limits."
    ::= { tlpAtsAlarmCurrentAboveThreshold 3 }

tlpAtsAlarmCurrentAboveThresholdB1 OBJECT-IDENTITY
    STATUS current
    DESCRIPTION
        "The output current on input source 2 phase 1 exceeds load limits."
    ::= { tlpAtsAlarmCurrentAboveThreshold 4 }

tlpAtsAlarmCurrentAboveThresholdB2 OBJECT-IDENTITY
    STATUS current
    DESCRIPTION
        "The output current on input source 2 phase 2 exceeds load limits."
    ::= { tlpAtsAlarmCurrentAboveThreshold 5 }

tlpAtsAlarmCurrentAboveThresholdB3 OBJECT-IDENTITY
    STATUS current
    DESCRIPTION
        "The output current on input source 2 phase 3 exceeds load limits."
    ::= { tlpAtsAlarmCurrentAboveThreshold 6 }

tlpAtsAlarmLoadsNotAllOn OBJECT-IDENTITY
    STATUS current
    DESCRIPTION
        "One of more loads are not on."
    ::= { tlpAtsAlarms 11 }

tlpAtsAlarmGeneralFault OBJECT-IDENTITY
    STATUS current
    DESCRIPTION
        "A general fault in the ats has been detected."
    ::= { tlpAtsAlarms 12 }

tlpAtsAlarmVoltage OBJECT IDENTIFIER
    ::= { tlpAtsAlarms 13 }

tlpAtsAlarmOverVoltage OBJECT-IDENTITY
    STATUS current
    DESCRIPTION
        "The input voltage is out of tolerance."
    ::= { tlpAtsAlarmVoltage 1 }

tlpAtsAlarmSource1OverVoltage OBJECT-IDENTITY
    STATUS current
    DESCRIPTION
        "The voltage on source 1 is out of tolerance."
    ::= { tlpAtsAlarmVoltage 2 }

tlpAtsAlarmSource2OverVoltage OBJECT-IDENTITY
    STATUS current
    DESCRIPTION
        "The voltage on source 2 is out of tolerance."
    ::= { tlpAtsAlarmVoltage 3 }

tlpAtsAlarmFrequency OBJECT IDENTIFIER
    ::= { tlpAtsAlarms 14 }

tlpAtsAlarmSource1InvalidFrequency OBJECT-IDENTITY
    STATUS current
    DESCRIPTION
        "The voltage on source 1 is out of tolerance."
    ::= { tlpAtsAlarmFrequency 1 }

tlpAtsAlarmSource2InvalidFrequency OBJECT-IDENTITY
    STATUS current
    DESCRIPTION
        "The voltage on source 2 is out of tolerance."
    ::= { tlpAtsAlarmFrequency 2 }

tlpCoolingAlarmSupplyAirSensorFault OBJECT-IDENTITY
    STATUS current
    DESCRIPTION
        "The supply air sensor is in fault."
    ::= { tlpCoolingAlarms 1 }

tlpCoolingAlarmReturnAirSensorFault OBJECT-IDENTITY
    STATUS current
    DESCRIPTION
        "The return air sensor is in fault."
    ::= { tlpCoolingAlarms 2 }

tlpCoolingAlarmCondenserInletAirSensorFault OBJECT-IDENTITY
    STATUS current
    DESCRIPTION
        "The condenser inlet air sensor is in fault."
    ::= { tlpCoolingAlarms 3 }

tlpCoolingAlarmCondenserOutletAirSensorFault OBJECT-IDENTITY
    STATUS current
    DESCRIPTION
        "The condenser outlet air sensor is in fault."
    ::= { tlpCoolingAlarms 4 }

tlpCoolingAlarmSuctionTemperatureSensorFault OBJECT-IDENTITY
    STATUS current
    DESCRIPTION
        "The suction temperature sensor is in fault."
    ::= { tlpCoolingAlarms 5 }

tlpCoolingAlarmEvaporatorTemperatureSensorFault OBJECT-IDENTITY
    STATUS current
    DESCRIPTION
        "The evaporator temperature sensor is in fault."
    ::= { tlpCoolingAlarms 6 }

tlpCoolingAlarmAirFilterClogged OBJECT-IDENTITY
    STATUS current
    DESCRIPTION
        "The air filter is clogged."
    ::= { tlpCoolingAlarms 7 }

tlpCoolingAlarmAirFilterRunHoursViolation OBJECT-IDENTITY
    STATUS current
    DESCRIPTION
        "The air filter run hours was violated."
    ::= { tlpCoolingAlarms 8 }

tlpCoolingAlarmSuctionPressureSensorFault OBJECT-IDENTITY
    STATUS current
    DESCRIPTION
        "The suction pressure sensor is in fault."
    ::= { tlpCoolingAlarms 9 }

tlpCoolingAlarmInverterCommunicationsFault OBJECT-IDENTITY
    STATUS current
    DESCRIPTION
        "The inverter communications is in fault."
    ::= { tlpCoolingAlarms 10 }

tlpCoolingAlarmRemoteShutdownViaInputContact OBJECT-IDENTITY
    STATUS current
    DESCRIPTION
        "A remote shutdown was triggerd by an input contact."
    ::= { tlpCoolingAlarms 11 }

tlpCoolingAlarmCondensatePumpFault OBJECT-IDENTITY
    STATUS current
    DESCRIPTION
        "The condensate pump is in fault."
    ::= { tlpCoolingAlarms 12 }

tlpCoolingAlarmLowRefrigerantStartupFault OBJECT-IDENTITY
    STATUS current
    DESCRIPTION
        "The low refrigerant startup is in fault."
    ::= { tlpCoolingAlarms 13 }

tlpCoolingAlarmCondenserFanFault OBJECT-IDENTITY
    STATUS current
    DESCRIPTION
        "The condenser fan is in fault."
    ::= { tlpCoolingAlarms 14 }

tlpCoolingAlarmCondenserFailure OBJECT-IDENTITY
    STATUS current
    DESCRIPTION
        "The condenser has failed."
    ::= { tlpCoolingAlarms 15 }

tlpCoolingAlarmEvaporatorCoolingFailure OBJECT-IDENTITY
    STATUS current
    DESCRIPTION
        "The evaporator cooling is in fault."
    ::= { tlpCoolingAlarms 16 }

tlpCoolingAlarmReturnAirTempHigh OBJECT-IDENTITY
    STATUS current
    DESCRIPTION
        "The return air temperature is high."
    ::= { tlpCoolingAlarms 17 }

tlpCoolingAlarmSupplyAirTempHigh OBJECT-IDENTITY
    STATUS current
    DESCRIPTION
        "The supply air temperature is high."
    ::= { tlpCoolingAlarms 18 }

tlpCoolingAlarmEvaporatorFailure OBJECT-IDENTITY
    STATUS current
    DESCRIPTION
        "The evaporator has failed."
    ::= { tlpCoolingAlarms 19 }

tlpCoolingAlarmEvaporatorFreezeUp OBJECT-IDENTITY
    STATUS current
    DESCRIPTION
        "The evaporator is frozen."
    ::= { tlpCoolingAlarms 20 }

tlpCoolingAlarmDischargePressureHigh OBJECT-IDENTITY
    STATUS current
    DESCRIPTION
        "The discharge pressure is high."
    ::= { tlpCoolingAlarms 21 }

tlpCoolingAlarmPressureGaugeFailure OBJECT-IDENTITY
    STATUS current
    DESCRIPTION
        "The pressure gauge has failed."
    ::= { tlpCoolingAlarms 22 }

tlpCoolingAlarmDischargePressurePersistentHigh OBJECT-IDENTITY
    STATUS current
    DESCRIPTION
        "The discharge pressure is persistently high."
    ::= { tlpCoolingAlarms 23 }

tlpCoolingAlarmSuctionPressureLowStartFailure OBJECT-IDENTITY
    STATUS current
    DESCRIPTION
        "Cannot start due to low suction pressure."
    ::= { tlpCoolingAlarms 24 }

tlpCoolingAlarmSuctionPressureLow OBJECT-IDENTITY
    STATUS current
    DESCRIPTION
        "The suction pressure is low."
    ::= { tlpCoolingAlarms 25 }

tlpCoolingAlarmSuctionPressurePersistentLow OBJECT-IDENTITY
    STATUS current
    DESCRIPTION
        "The suction pressure is persistently low."
    ::= { tlpCoolingAlarms 26 }

tlpCoolingAlarmStartupLinePressureImbalance OBJECT-IDENTITY
    STATUS current
    DESCRIPTION
        "The startup line pressure is in imbalance."
    ::= { tlpCoolingAlarms 27 }

tlpCoolingAlarmCompressorFailure OBJECT-IDENTITY
    STATUS current
    DESCRIPTION
        "The compressor has failed."
    ::= { tlpCoolingAlarms 28 }

tlpCoolingAlarmCurrentLimit OBJECT-IDENTITY
    STATUS current
    DESCRIPTION
        "The current is out of range."
    ::= { tlpCoolingAlarms 29 }

tlpCoolingAlarmWaterLeak OBJECT-IDENTITY
    STATUS current
    DESCRIPTION
        "Water is leaking."
    ::= { tlpCoolingAlarms 30 }

tlpCoolingAlarmFanUnderCurrent OBJECT-IDENTITY
    STATUS current
    DESCRIPTION
        "The fan is under current."
    ::= { tlpCoolingAlarms 31 }

tlpCoolingAlarmFanOverCurrent OBJECT-IDENTITY
    STATUS current
    DESCRIPTION
        "The fan is over current."
    ::= { tlpCoolingAlarms 32 }

tlpCoolingAlarmDischargePressureSensorFault OBJECT-IDENTITY
    STATUS current
    DESCRIPTION
        "The discharge pressure sensor is in fault."
    ::= { tlpCoolingAlarms 33 }

tlpCoolingAlarmWaterFull OBJECT-IDENTITY
    STATUS current
    DESCRIPTION
        "Water is Full."
    ::= { tlpCoolingAlarms 34 }

tlpCoolingAlarmAutoCoolingOn OBJECT-IDENTITY
    STATUS current
    DESCRIPTION
        "Automatic cooling was activated to lower the temperature below the
        remote set point."
    ::= { tlpCoolingAlarms 35 }

tlpCoolingAlarmPowerButtonPressed OBJECT-IDENTITY
    STATUS current
    DESCRIPTION
        "Power button was pressed on the front panel."
    ::= { tlpCoolingAlarms 36 }

tlpCoolingAlarmDisconnectedFromDevice OBJECT-IDENTITY
    STATUS current
    DESCRIPTION
        "The device communications is disconnected."
    ::= { tlpCoolingAlarms 37 }

tlpAlarmControlTable OBJECT-TYPE
    SYNTAX SEQUENCE OF TlpAlarmControlEntry
    MAX-ACCESS not-accessible
    STATUS current
    DESCRIPTION
        "A list of alarm conditions supported for each device managed by this
        agent. This table contains zero, one, or many rows depending upon the
        number of available alarms managed by each device."
    ::= { tlpAlarmControl 1 }

tlpAlarmControlEntry OBJECT-TYPE
    SYNTAX TlpAlarmControlEntry
    MAX-ACCESS not-accessible
    STATUS current
    DESCRIPTION
        "An entry containing details for a particular alarm condition."
    INDEX { tlpDeviceIndex, tlpAlarmControlIndex }
    ::= { tlpAlarmControlTable 1 }

TlpAlarmControlEntry ::= SEQUENCE {
    tlpAlarmControlIndex                Unsigned32,
    tlpAlarmControlDescr                OBJECT IDENTIFIER,
    tlpAlarmControlDetail               DisplayString,
    tlpAlarmControlSeverity             INTEGER }

tlpAlarmControlIndex OBJECT-TYPE
    SYNTAX Unsigned32
    MAX-ACCESS read-only
    STATUS current
    DESCRIPTION
        "The table row index for this alarm control entry for this device. The
        index of any one row represents the index of the alarm entry within the
        agent system. As such, the index values for any one device is not
        guaranteed to start with 1 or be numerically sequential."
    ::= { tlpAlarmControlEntry 1 }

tlpAlarmControlDescr OBJECT-TYPE
    SYNTAX OBJECT IDENTIFIER
    MAX-ACCESS read-only
    STATUS current
    DESCRIPTION
        "A reference of the alarm description object. The object referenced
        should not be accessbile, but rather be used to provide a unique
        description for the alarm condition. The object referenced will be a
        well known alarm object associated with the device on which the alarm
        condition is active. This will be the same object description of an
        alarm when in alarm as referenced by tlpAlarmDescr."
    ::= { tlpAlarmControlEntry 2 }

tlpAlarmControlDetail OBJECT-TYPE
    SYNTAX DisplayString
    MAX-ACCESS read-only
    STATUS current
    DESCRIPTION
        "A textual description of the alarm condition. This will be the same
        textual description of an alarm when in alarm as referenced by
        tlpAlarmDetail."
    ::= { tlpAlarmControlEntry 3 }

tlpAlarmControlSeverity OBJECT-TYPE
    SYNTAX INTEGER {
        critical(1),
        warning(2),
        info(3) }
    MAX-ACCESS read-write
    STATUS current
    DESCRIPTION
        "The severity of this alarm, which can be configured as desired for
        each alarm condition. This will be the same severity used when in alarm
        as referenced by tlpAlarmType."
    ::= { tlpAlarmControlEntry 4 }

-- notifications

tlpNotificationsAlarmEntryAdded NOTIFICATION-TYPE
    OBJECTS { tlpAlarmId, tlpAlarmDescr, tlpAlarmTime,
              tlpAlarmTableRef, tlpAlarmTableRowRef, tlpAlarmDetail,
              tlpAlarmType }
    STATUS current
    DESCRIPTION
        "This notification is sent each time an alarm condition is inserted into
        the device alarm table, tlpAlarmTable."
    ::= { tlpNotifications 1 }

tlpNotificationsAlarmEntryRemoved NOTIFICATION-TYPE
    OBJECTS { tlpAlarmId, tlpAlarmDescr, tlpAlarmTime,
              tlpAlarmTableRef, tlpAlarmTableRowRef, tlpAlarmDetail,
              tlpAlarmType }
    STATUS current
    DESCRIPTION
        "This notification is sent each time an alarm condition is removed from
        the device alarm table, tlpAlarmTable."
    ::= { tlpNotifications 2 }

tlpNotifySystemStartup NOTIFICATION-TYPE
    STATUS current
    DESCRIPTION
        "Used to inform another entity of an agent's startup. The varbinds that follow are:

        OBJ1      = tlpAgentType
        Obj1Value = The type of engine providing this data
        OBJ2      = tlpAgentVersion
        Obj2Value = The current version of the engine
        OBJ3      = tlpAgentMAC
        Obj3Value = The MAC address of the engine
        OBJ4      = tlpAgentSerialNum
        Obj4Value = The serial number of the web card [should be 0 on PC]
    
        --- if this trap is extended, place all static OIDs above this mark. all objects below
        --- the number of devices (tlpDeviceNumDevices) is explicit as per device for enumeration by
        --- the target receiver
    
        OBJ5      = tlpDeviceNumDevices
        Obj5Value = The number of devices attached

        --- The following objects will be replicated per each device:

        OBJ6      = The OID for an entry of tlpDeviceManufacturer, indexed by device
        Obj6Value = The device's manufacturer
        OBJ7      = The OID for an entry of tlpDeviceModel, indexed by device
        Obj7Value = The device's model name
        OBJ8      = The OID for an entry of tlpDeviceName, indexed by device
        Obj8Value = The device's display name
        OBJ9      = The OID for an entry of tlpDeviceLocation, indexed by device
        Obj9Value = The device's location
        OBJ10     = The OID for an entry of tlpDeviceRegion, indexed by device
        Obj10Value= The device's region
        OBJ11     = The OID for an entry of tlpDeviceProtocol, indexed by device
        Obj11Value= The device's protocol (display string format)
        "
    ::= { tlpNotifications 3 }

tlpNotifySystemShutdown NOTIFICATION-TYPE
    STATUS current
    DESCRIPTION
        "Used to inform another entity of an agent's shutdown. The varbinds that follow are:

        OBJ1      = tlpAgentType
        Obj1Value = The type of engine providing this data
        OBJ2      = tlpAgentVersion
        Obj2Value = The current version of the engine
        OBJ3      = tlpAgentMAC
        Obj3Value = The MAC address of the engine
        OBJ4      = tlpAgentSerialNum
        Obj4Value = The serial number of the web card [should be 0 on PC]
    
        --- if this trap is extended, place all static OIDs above this mark. all objects below
        --- the number of devices (tlpDeviceNumDevices) is explicit as per device for enumeration by
        --- the target receiver
    
        OBJ5      = tlpDeviceNumDevices
        Obj5Value = The number of devices attached

        --- The following objects will be replicated per each device:

        OBJ6      = The OID for an entry of tlpDeviceManufacturer, indexed by device
        Obj6Value = The device's manufacturer
        OBJ7      = The OID for an entry of tlpDeviceModel, indexed by device
        Obj7Value = The device's model name
        OBJ8      = The OID for an entry of tlpDeviceName, indexed by device
        Obj8Value = The device's display name
        OBJ9      = The OID for an entry of tlpDeviceLocation, indexed by device
        Obj9Value = The device's location
        OBJ10     = The OID for an entry of tlpDeviceRegion, indexed by device
        Obj10Value= The device's region
        OBJ11     = The OID for an entry of tlpDeviceProtocol, indexed by device
        Obj11Value= The device's protocol (display string format)
        "
    ::= { tlpNotifications 4 }

tlpNotifySystemUpdate NOTIFICATION-TYPE
  STATUS current
  DESCRIPTION
    "Used to inform another entity of an engine's startup. The varbinds that follow are:

    OBJ1      = tlpAgentType
    Obj1Value = The type of engine providing this data
    OBJ2      = tlpAgentVersion
    Obj2Value = The current version of the engine
    OBJ3      = tlpAgentMAC
    Obj3Value = The MAC address of the engine
    OBJ4      = tlpAgentSerialNum
    Obj4Value = The serial number of the web card [should be 0 on PC]
    
    --- if this trap is extended, place all static OIDs above this mark. all objects below
    --- the number of devices (tlpDeviceNumDevices) is explicit as per device for enumeration by
    --- the target receiver
    
    OBJ5      = tlpDeviceNumDevices
    Obj5Value = The number of devices attached

    --- The following objects will be replicated per each device:

    OBJ6      = The OID for an entry of tlpDeviceManufacturer, indexed by device
    Obj6Value = The device's manufacturer
    OBJ7      = The OID for an entry of tlpDeviceModel, indexed by device
    Obj7Value = The device's model name
    OBJ8      = The OID for an entry of tlpDeviceName, indexed by device
    Obj8Value = The device's display name
    OBJ9      = The OID for an entry of tlpDeviceLocation, indexed by device
    Obj9Value = The device's location
    OBJ10     = The OID for an entry of tlpDeviceRegion, indexed by device
    Obj10Value= The device's region
    OBJ11     = The OID for an entry of tlpDeviceProtocol, indexed by device
    Obj11Value= The device's protocol (display string format)
    "
  ::= { tlpNotifications 5 }

END
