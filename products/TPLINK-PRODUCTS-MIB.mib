TPLINK-PRODUCTS-MIB DEFINITIONS ::= BEGIN
	IMPORTS
        MODULE-IDENTITY
                FROM SNMPv2-SMI
		tplinkProducts
				FROM TPLINK-MIB;

		
	tplink-tlsl5428		OBJECT IDENTIFIER ::= { tplinkProducts 1 }
	tplink-tlsl3452		OBJECT IDENTIFIER ::= { tplinkProducts 2 }
	tplink-tlsg3424		OBJECT IDENTIFIER ::= { tplinkProducts 3 }
	tplink-tlsg3216		OBJECT IDENTIFIER ::= { tplinkProducts 4 }
	tplink-tlsg3210		OBJECT IDENTIFIER ::= { tplinkProducts 5 }
	tplink-tlsl3428		OBJECT IDENTIFIER ::= { tplinkProducts 6 }
	tplink-tlsg5428		OBJECT IDENTIFIER ::= { tplinkProducts 7 }
	tplink-tlsg3424p	OBJECT IDENTIFIER ::= { tplinkProducts 8 }
	tplink-tlsg5412f	OBJECT IDENTIFIER ::= { tplinkProducts 9 }
	tplink-t2700-28tct	OBJECT IDENTIFIER ::= { tplinkProducts 10 }
	tplink-tlsl2428		OBJECT IDENTIFIER ::= { tplinkProducts 11 }
	tplink-tlsg2216		OBJECT IDENTIFIER ::= { tplinkProducts 12 }
	tplink-tlsg2424		OBJECT IDENTIFIER ::= { tplinkProducts 13 }
	tplink-tlsg5428cn	OBJECT IDENTIFIER ::= { tplinkProducts 14 }
	tplink-tlsg2452	 	OBJECT IDENTIFIER ::= { tplinkProducts 15 }
	tplink-tlsl2218		OBJECT IDENTIFIER ::= { tplinkProducts 16 }
	tplink-tlsg2424p	OBJECT IDENTIFIER ::= { tplinkProducts 17 }
	tplink-tlsg2210		OBJECT IDENTIFIER ::= { tplinkProducts 18 }
	tplink-tlsl2210		OBJECT IDENTIFIER ::= { tplinkProducts 19 }
	tplink-t3700g-28tq	OBJECT IDENTIFIER ::= { tplinkProducts 20 }
	tplink-tlsl2226p	OBJECT IDENTIFIER ::= { tplinkProducts 21 }
	tplink-tlsl2452		OBJECT IDENTIFIER ::= { tplinkProducts 22 }
	tplink-tlsl2218p	OBJECT IDENTIFIER ::= { tplinkProducts 23 }
	tplink-tlsg3424-ipv6	OBJECT IDENTIFIER ::= { tplinkProducts 24 }
	tplink-tlsg2008		OBJECT IDENTIFIER ::= { tplinkProducts 25 }
	tplink-tlsg2210p	OBJECT IDENTIFIER ::= { tplinkProducts 26 }
	tplink-t2700g-28tq	OBJECT IDENTIFIER ::= { tplinkProducts 27 }
	tplink-t1600g-28ts	OBJECT IDENTIFIER ::= { tplinkProducts 28 }
	tplink-t1600g-52ts	OBJECT IDENTIFIER ::= { tplinkProducts 29 }
	tplink-t3700g-54tq	OBJECT IDENTIFIER ::= { tplinkProducts 30 }
	tplink-t1700g-28tq	OBJECT IDENTIFIER ::= { tplinkProducts 31 }
	tplink-t1700g-52tq	OBJECT IDENTIFIER ::= { tplinkProducts 32 }
	tplink-t2600g-28ts	OBJECT IDENTIFIER ::= { tplinkProducts 33 }
	tplink-t2600g-52ts	OBJECT IDENTIFIER ::= { tplinkProducts 34 }
	tplink-t1600g-28ps	OBJECT IDENTIFIER ::= { tplinkProducts 37 }
	tplink-t1600g-52ps	OBJECT IDENTIFIER ::= { tplinkProducts 38 }
	tplink-tlsg2224p	OBJECT IDENTIFIER ::= { tplinkProducts 39 }
	tplink-tlsg3428 	OBJECT IDENTIFIER ::= { tplinkProducts 40 }
	tplink-t1700x-16ts	OBJECT IDENTIFIER ::= { tplinkProducts 41 }

		
END
