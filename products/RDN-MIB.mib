-- *****************************************************************
-- RDN-MIB.mib:
-- Motorola BSR's Enterprise Definition MIB
--
-- Copyright (C) 2000, 2008 by Motorola, Inc.
-- All rights reserved.
-- *****************************************************************
RDN-MIB DEFINITIONS ::= BEGIN

        IMPORTS
            MODULE-IDENTITY, enterprises
                FROM SNMPv2-SMI;


		-- RiverDelta enterprise module definition

        riverdelta MODULE-IDENTITY
            LAST-UPDATED "200808080000Z" -- August 8, 2008
            ORGANIZATION "Motorola"
            CONTACT-INFO "Motorola
                          Customer Service
                          101 Tournament Drive
                          Horsham, PA 19044
                          US Tel: +1 888 944 4357
                          Int Tel: +1 215 323 0044
	                  Fax: +1 215 323 1502
                          Email: CPSSupport@Motorola.com"
            DESCRIPTION
                    "MIB module definition for Motorola.

		    Copyright (C) 2000, 2008 by Motorola, Inc.
	     	    All rights reserved."

	    REVISION "200808080000Z"  -- 08 August 2008
	    DESCRIPTION
		    "Added Copyright Statement into MIB modules's
	       	    description."

	    REVISION     "200311050000Z"
            DESCRIPTION
                    "+  Updated the CONTACT-INFO.
	             +  Reorder REVISION/DESCRIPTION in required 
                        reverse chronological order."
            REVISION     "200304290000Z"
            DESCRIPTION
                    "Clean up CONTACT-INFO."
            REVISION     "200005230000Z"
            DESCRIPTION
                    "Moved 'riverdelta' definition into a separate
		     file; this allows an external module to not include 
                     the entire riverdelta chassis mib when needing 
                     only the 'riverdelta' definition."
            REVISION     "200004040000Z"
            DESCRIPTION
                    "Initial creation."
            ::= { enterprises 4981 }

    END
