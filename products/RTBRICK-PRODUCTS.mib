RTBRICK-PRODUCTS DEFINITIONS ::= BEGIN

--
-- Top-level infrastructure of the RtBrick enterprise MIB tree
--

IMPORTS
    MODULE-IDENTITY, OBJECT-TYPE,
    Integer32, enterprises FROM SNMPv2-SMI
    TEXTUAL-CONVENTION, DisplayString,
    PhysAddress, TruthValue, RowStatus,
    TimeStamp, AutonomousType, TestAndIncr   FROM SNMPv2-TC
    rtbrickProducts, rtbrickModules          FROM RTBRICK-MIB;


rtbrickProductsMIB MODULE-IDENTITY
    LAST-UPDATED "201804140000Z"
    ORGANIZATION "RtBrick"
    CONTACT-INFO "E-mail: Stefan Lieberth <stefan@rtbrick.com>"
    DESCRIPTION
	    "RtBrick Product Information"
    REVISION     "201804140000Z"
    DESCRIPTION  "Initial revision"
    ::= { rtbrickModules 1 }

-- EC-AS5916-54XK 48-port SFP+ plus 6-port QSFP28 Router
rtbrickECAS591654XK OBJECT IDENTIFIER ::= { rtbrickProducts 1 }

END
