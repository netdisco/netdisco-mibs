KAV-FOR-LINUX-FS-MIB DEFINITIONS ::= BEGIN
--
-- Top-level of Kaspersky AntiVirus for Linux file server
--

IMPORTS
   MODULE-IDENTITY
           FROM SNMPv2-SMI
   kaspersky
           FROM KASPERSKY-MIB;

kav4LinuxFS MODULE-IDENTITY
   LAST-UPDATED "200810011800Z"
   ORGANIZATION "www.kaspersky.com"
   CONTACT-INFO "Kaspersky Lab"
   DESCRIPTION "Defined the MIB tree for KAV4 for Linux FS."
   -- revisions
   REVISION     "200810011800Z"
   DESCRIPTION  
           "Kaspersky AntiVirus for Linux FS initial tree was born."
   ::= { kaspersky 1046 }

END
