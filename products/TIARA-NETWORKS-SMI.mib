-- *****************************************************************
-- tiaranet-smi.mib:  Tiara Networks Enterprise SMI
--
-- April,1st 1998, Shyla
--
--
-- Copyright (c) 1998-2005 by Tiara Networks, Inc.
-- All rights reserved.
-- 
-- *****************************************************************


TIARA-NETWORKS-SMI 


DEFINITIONS ::= BEGIN

IMPORTS
	MODULE-IDENTITY,
	OBJECT-IDENTITY,
	enterprises
		FROM SNMPv2-SMI
        TEXTUAL-CONVENTION 
                FROM SNMPv2-TC;

tiaraNetworks MODULE-IDENTITY
	LAST-UPDATED "9904230000Z"
	ORGANIZATION "Tiara Networks, Inc."
	CONTACT-INFO
		"	Tiara Networks
			Customer Service

		Postal: 113 Fourier Ave
			Fremont, CA  94539
			USA

		   Tel: +1 510-360-0140
		   Fax: +1 510-360-0144

		E-mail: cs@tiaranet.com"
	DESCRIPTION
		"The Structure of Management Information for the
		Tiara Networks enterprise MIB."
	REVISION      "9304010000Z"
	DESCRIPTION
		"Initial version of this MIB module."
	::= { enterprises 3174 }	-- assigned by IANA


tiaraProducts OBJECT-IDENTITY
	STATUS	current
	DESCRIPTION
		"tiaraProducts is the root OBJECT IDENTIFIER from
		which sysObjectID values are assigned.  Actual
		values are defined in TIARA-PRODUCTS-MIB."
	::= { tiaraNetworks 1 }

tiaraMgmt OBJECT-IDENTITY
	STATUS	current
	DESCRIPTION
		"tiaraMgmt is the main subtree for Management groups."
	::= { tiaraNetworks 2 }

tiaraModules OBJECT-IDENTITY
	STATUS	current
	DESCRIPTION
		"tiaraModules provides a root object identifier
		from which MODULE-IDENTITY values may be assigned."
	::= { tiaraNetworks 3 }

tiaraExperiment OBJECT-IDENTITY
	STATUS	current
	DESCRIPTION
		"tiaraExperiment is the main subtree for individual groups
		which are used internally,not for production release.
		"
	::= { tiaraNetworks 4 }

tiaraInterfaces OBJECT-IDENTITY 
        STATUS  current
        DESCRIPTION
                "tiaraInterfaces is the main subtree for individual interface
                groups."
	::= { tiaraMgmt 7 }


END
