-- Memotec Enterprise CX PRODUCT MIB 
-- May 1994
-- Revision 1.3

CXProduct-SMI 

DEFINITIONS ::= BEGIN

IMPORTS
  DisplayString
    FROM RFC1213-MIB
  cxProduct
    FROM MEMOTEC-SMI;

 --  Proprietary data types used 
 --  throughout cxProduct groups
SapIndex    ::=     INTEGER (1..255)
Alias       ::=     DisplayString (SIZE (0..32))
ThruputClass    ::=     INTEGER {
            bps75           (3),
            bps150          (4),
            bps300          (5),
            bps600          (6),
            bps1200 (7),
            bps2400 (8),
            bps4800 (9),
            bps9600 (10),
            bps19200        (11),
            bps48000        (12),
            bps64000        (13)
            }

cxMc600
OBJECT IDENTIFIER
::= { cxProduct  1 }

cxPx600
OBJECT IDENTIFIER
::= { cxProduct  2 }

cxViewing
OBJECT IDENTIFIER 
::= { cxProduct  3 }

cxChassis
OBJECT IDENTIFIER 
::= { cxProduct  4 }

cxSystem
OBJECT IDENTIFIER 
::= { cxProduct  5 }

cxApplication 
OBJECT IDENTIFIER 
::= { cxProduct  6 }

cxRegistration
OBJECT IDENTIFIER
::= { cxProduct  7 }

cxPrivate
OBJECT IDENTIFIER
::= { cxProduct  8 }

cxChassis2
OBJECT IDENTIFIER 
::= { cxProduct  9 }




--Type of chassis registered within the cxProduct



--  This object ID type is read in the 
--  sysObjectID in the system group 
--  implemented in the Network 
--  Management Element.







cxRegChassis
OBJECT IDENTIFIER 
::= { cxRegistration  1 }

cxRegChasCX1000
OBJECT IDENTIFIER 
::= { cxRegChassis  1 }

cxRegChasCX900
OBJECT IDENTIFIER 
::= { cxRegChassis  2 }

cxRegChasCX950
OBJECT IDENTIFIER 
::= { cxRegChassis  3 }


--Registered type of sub sytem 
--registered within the cxProduct



-- This object ID type is read in the
-- cxChasSubSysObjecID object implemented 
-- in the Network Management Element 
-- cxChasSubSysTable.







cxRegSubSystem
OBJECT IDENTIFIER 
::= { cxRegistration  2 }

cxRegSubSysMC600
OBJECT IDENTIFIER
::= { cxRegSubSystem 1}

cxRegSubSysAC600
OBJECT IDENTIFIER
::= { cxRegSubSystem 2}

cxRegSubSysPX600 
OBJECT IDENTIFIER
::= { cxRegSubSystem 3}

cxRegSubSysFR600 
OBJECT IDENTIFIER
::= { cxRegSubSystem 4}

cxRegSubSysCL600 
OBJECT IDENTIFIER
::= { cxRegSubSystem 5}

cxRegSubSysLF600 
OBJECT IDENTIFIER
::= { cxRegSubSystem 6}

cxRegSubSysDI600 
OBJECT IDENTIFIER
::= { cxRegSubSystem 7}

cxRegSubSysFX600 
OBJECT IDENTIFIER
::= { cxRegSubSystem 8}


--System Software Modules







cxModuleHardware
OBJECT IDENTIFIER 
::= { cxSystem  1 }

cxIoHardware
OBJECT IDENTIFIER 
::= { cxSystem  2 }

cxFileServer
OBJECT IDENTIFIER 
::= { cxSystem  3 }

cxSecurityLevel
OBJECT IDENTIFIER 
::= { cxSystem  4 }

cxOperatingSystem
OBJECT IDENTIFIER 
::= { cxSystem  5 }

cxConsoleDriver
OBJECT IDENTIFIER 
::= { cxSystem  6 }

cxInterApplicationModule
OBJECT IDENTIFIER 
::= { cxSystem  7 }

cxUserInterface
OBJECT IDENTIFIER 
::= { cxSystem  8 }

cxTokenBus
OBJECT IDENTIFIER 
::= { cxSystem  9 }

cxLanIoPort
OBJECT IDENTIFIER 
::= { cxSystem  10 }

cxSubSysInfo
OBJECT IDENTIFIER
::= { cxSystem  11 }

cxIoHwInfo
OBJECT IDENTIFIER
::= { cxSystem  12 }

cxSystemManagement
OBJECT IDENTIFIER
::= { cxSystem  13 }

cxCommonConsole
OBJECT IDENTIFIER
::= { cxSystem  14 }

cxPmb
OBJECT IDENTIFIER
::= { cxSystem  15 }

cxPortManager
OBJECT IDENTIFIER
::= { cxSystem 16 }

cxEventManager
OBJECT IDENTIFIER
::= { cxSystem 17 }

cxDownload
OBJECT IDENTIFIER
::= { cxSystem  18 }


-- Application  Software Modules







cxBitOrientedProtocolDriver
OBJECT IDENTIFIER
::= { cxApplication  1 }

cxFrameRelayInterfaceModule
OBJECT IDENTIFIER
::= { cxApplication  2 }

cxFrameRelay
OBJECT IDENTIFIER
::= { cxApplication  3 }

cxSdxi
OBJECT IDENTIFIER
::= { cxApplication  4 }

cxGwMux
OBJECT IDENTIFIER
::= { cxApplication  5 }

-- imported by the cxif.mib

cxIf
OBJECT IDENTIFIER 
::= { cxApplication  6 }

-- imported by the cxdot3.mib and cxdot5.mib

cxTransmission
OBJECT IDENTIFIER 
::= { cxApplication  7 }

-- imported by the cxconv.mib

cxConv
OBJECT IDENTIFIER 
::= { cxApplication  8 }

-- imported by the cxdot1.mib


cxDot1dBridge
OBJECT IDENTIFIER 
::= { cxApplication  9 }

-- imported by the cxip.mib

cxIp
OBJECT IDENTIFIER 
::= { cxApplication  10 }

-- imported by the cxip.mib


cxIcmp
OBJECT IDENTIFIER 
::= { cxApplication  11 }

-- imported by the cxip.mib


cxUdp
OBJECT IDENTIFIER 
::= { cxApplication  12 }

-- imported by the cxipx.mib

cxIpx
OBJECT IDENTIFIER 
::= { cxApplication  13 }


cxCfgDot1dBase
OBJECT IDENTIFIER 
::= { cxApplication  14 }


cxCfgIpSap
OBJECT IDENTIFIER 
::= { cxApplication  15 }


cxCfgIp
OBJECT IDENTIFIER 
::= { cxApplication  16 }


cxCfgSrBase
OBJECT IDENTIFIER 
::= { cxApplication  17 }


cxGwFr
OBJECT IDENTIFIER 
::= { cxApplication  18 }


cxGwX25
OBJECT IDENTIFIER 
::= { cxApplication  19 }

cxPppAsyncDriver
OBJECT IDENTIFIER 
::= { cxApplication  20 }

cxFltIp
OBJECT IDENTIFIER 
::= { cxApplication  21 }

cxFltIpx 
OBJECT IDENTIFIER 
::= { cxApplication  22 }

cxAdxi 
OBJECT IDENTIFIER 
::= { cxApplication  23 }

cxCompression 
OBJECT IDENTIFIER 
::= { cxApplication  24 }

cxEthernetDriver
OBJECT IDENTIFIER
::= { cxApplication  25 }

cxPpp 
OBJECT IDENTIFIER 
::= { cxApplication  26 }

-- these are new to the CX900!

cxLapBD
OBJECT IDENTIFIER 
::= { cxApplication  27 }

cxLapBConv
OBJECT IDENTIFIER 
::= { cxApplication  28 }

cxX25
OBJECT IDENTIFIER 
::= { cxApplication  29 }

cxAsync
OBJECT IDENTIFIER 
::= { cxApplication  30 }

cxSNA
OBJECT IDENTIFIER 
::= { cxApplication  31 }

cxISDN
OBJECT IDENTIFIER 
::= { cxApplication  32 }

cxLlcFrConv
OBJECT IDENTIFIER 
::= { cxApplication  33 }

cxLlcim
OBJECT IDENTIFIER 
::= { cxApplication  34 }

cxSnalc
OBJECT IDENTIFIER 
::= { cxApplication  35 }

cxBOPIO
OBJECT IDENTIFIER 
::= { cxApplication  36 }

cxSDLC
OBJECT IDENTIFIER 
::= { cxApplication  37 }

cxQLLC
OBJECT IDENTIFIER 
::= { cxApplication  38 }

cxDds
OBJECT IDENTIFIER 
::= { cxApplication  39 }

cxUTst
OBJECT IDENTIFIER 
::= { cxApplication  40 }

cxUDrv
OBJECT IDENTIFIER 
::= { cxApplication  41 }

cxV34
OBJECT IDENTIFIER 
::= { cxApplication  42 }

cxOSP
OBJECT IDENTIFIER 
::= { cxApplication  43 }

cxAsyncIo
OBJECT IDENTIFIER 
::= { cxApplication  44 }

cxEthIo
OBJECT IDENTIFIER 
::= { cxApplication  45 }

cxDial
OBJECT IDENTIFIER 
::= { cxApplication  46 }

cxLlcLanConv
OBJECT IDENTIFIER 
::= { cxApplication  47 }

cxBCM
OBJECT IDENTIFIER 
::= { cxApplication  48 }

cxMLPPP
OBJECT IDENTIFIER 
::= { cxApplication  49 }

cxVR
OBJECT IDENTIFIER 
::= { cxApplication  50 }

cxTrdIo
OBJECT IDENTIFIER 
::= { cxApplication  51 }

cxDSX1
OBJECT IDENTIFIER 
::= { cxApplication  52 }

cxDSX1Ext
OBJECT IDENTIFIER 
::= { cxApplication  53 }

cxGim
OBJECT IDENTIFIER 
::= { cxApplication  55 }

cxBsc
OBJECT IDENTIFIER 
::= { cxApplication  56 }

cxDsp
OBJECT IDENTIFIER 
::= { cxApplication  57 }

cxAtmDxi
OBJECT IDENTIFIER 
::= { cxApplication  58 }

cxCAS
OBJECT IDENTIFIER 
::= { cxApplication  59 }

cxST
OBJECT IDENTIFIER 
::= { cxApplication  60 }

cxAtmPhy
OBJECT IDENTIFIER 
::= { cxApplication  61 }

cxAtmExt
OBJECT IDENTIFIER 
::= { cxApplication  62 }

cxPCM
OBJECT IDENTIFIER 
::= { cxApplication  63 }



-- others protocol layers or modules must be added  here... 

cxACTE
OBJECT IDENTIFIER 
::= { cxPrivate  1 }

cxT1E1
OBJECT IDENTIFIER 
::= { cxPrivate  2 }  

cxDataScope
OBJECT IDENTIFIER 
::= { cxPrivate  3 }

cxBri
OBJECT IDENTIFIER 
::= { cxPrivate  4 }


END
