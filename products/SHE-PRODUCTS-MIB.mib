--
-- she-products-mib.mib
-- MIB generated by MG-SOFT Visual MIB Builder Version 6.0  Build 88
-- Monday, November 09, 2009 at 14:50:36
--

-- Start of ClearCase branch-information of current release:
-- she-products-mib.mib   /main/she_main_grf/3
-- End of ClearCase branch-information.

	SHE-PRODUCTS-MIB DEFINITIONS ::= BEGIN
 
		IMPORTS
			she			
				FROM AN-MIB;
	
	
--
-- Node definitions
--
	
		sheProducts OBJECT IDENTIFIER ::= { she 101 }

		
		shehiX OBJECT IDENTIFIER ::= { sheProducts 1 }

		
		hiX5630-M600 OBJECT IDENTIFIER ::= { shehiX 1 }

		
		hiX5635-M1200 OBJECT IDENTIFIER ::= { shehiX 2 }

		
		hiX5625-M400 OBJECT IDENTIFIER ::= { shehiX 3 }

		
		hiX5635-M1100 OBJECT IDENTIFIER ::= { shehiX 4 }

		
		hiX5635-G1100 OBJECT IDENTIFIER ::= { shehiX 5 }

		
		hiX5630-G600 OBJECT IDENTIFIER ::= { shehiX 6 }

		
		hiX5625-G400 OBJECT IDENTIFIER ::= { shehiX 7 }

		
		hiX5622-G200 OBJECT IDENTIFIER ::= { shehiX 8 }

		
	
	END

--
-- she-products-mib.mib
--
