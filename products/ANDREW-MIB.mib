--
-- Andrew.mib
-- MIB generated by MG-SOFT Visual MIB Builder Version 3.0 Build 253
-- Wednesday, August 06, 2003 at 14:09:47
--

ANDREW-MIB DEFINITIONS ::= BEGIN

--	andrew.mib
--	Revision:	1.00
--	Product No: 	UTMC Header MIB
--	Date:		14th May 2003
--	Written:	Douglas Dorst

--	Revision History
--	V1.00   14/5/2003	First Issue				DMD
--	V1.01	31/3/2005	add esaProducts branch			BWW

--	Andrew Corporation
--	2601 Telecom Parkway
--	Richardson, TX. 75082-3521 
--      USA
--	Tel 972 952 9700
--	Fax 972 952 0004
--      email 


--	This module provides the branching node definitions for the
--      Andrew Corporation Enterprise MIB designation.

--	Defined OIDs from RFC1155-SMI        ;
          IMPORTS
              MODULE-IDENTITY
                  FROM SNMPv2-SMI
              MODULE-COMPLIANCE, OBJECT-GROUP
                  FROM SNMPv2-CONF
   	         enterprises
    	            FROM RFC1155-SMI
        	;
--        ccitt        	OBJECT IDENTIFIER ::= { 0 }
--        null         	OBJECT IDENTIFIER ::= { ccitt 0 }

--        iso          	OBJECT IDENTIFIER ::= { 1 }
--        org          	OBJECT IDENTIFIER ::= { iso 3 }
--        dod          	OBJECT IDENTIFIER ::= { org 6 }
--        internet     	OBJECT IDENTIFIER ::= { dod 1 }
--        directory    	OBJECT IDENTIFIER ::= { internet 1 }
--        mgmt         	OBJECT IDENTIFIER ::= { internet 2 }
--        experimental 	OBJECT IDENTIFIER ::= { internet 3 }
--        private      	OBJECT IDENTIFIER ::= { internet 4 }
--        enterprises  	OBJECT IDENTIFIER ::= { private 1 }
	      andrew       		  OBJECT IDENTIFIER ::= { enterprises 331 }
	      andrewProducts      OBJECT IDENTIFIER ::= { andrew 1 }
	      esaSystems          OBJECT IDENTIFIER ::= { andrewProducts  1 }
	      wirelessInnovations OBJECT IDENTIFIER ::= { andrewProducts  2 }    
	      oneBase             OBJECT IDENTIFIER ::= { andrewProducts  3 } 
	      esaProducts         OBJECT IDENTIFIER ::= { andrewProducts  4 }   
	      bsaSystems          OBJECT IDENTIFIER ::= { andrewProducts  5 }  
	      
END
