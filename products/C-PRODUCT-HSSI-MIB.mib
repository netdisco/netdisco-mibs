C-PRODUCT-HSSI-MIB DEFINITIONS ::= BEGIN


IMPORTS
    hssicard                          FROM C-PRODUCT-GROUP-MIB
    portSlot, portNumber, TimeAndDate FROM C-PRODUCT-BASE-MIB
    Gauge                             FROM RFC1155-SMI
    OBJECT-TYPE                       FROM RFC-1212;

-- HSSI groups

hssiPort      OBJECT IDENTIFIER ::= { hssicard 1 }
hssiPortStats OBJECT IDENTIFIER ::= { hssicard 2 }

-- HSSI Port Group (hssiPort)

hssiPortTable OBJECT-TYPE
    SYNTAX SEQUENCE OF HssiPortEntry
    ACCESS not-accessible
    STATUS mandatory
    DESCRIPTION
            "The HSSI port information table."
    ::= { hssiPort 1 }

hssiPortEntry OBJECT-TYPE
    SYNTAX HssiPortEntry
    ACCESS not-accessible
    STATUS mandatory
    DESCRIPTION
            "Information about a HSSI port."
    INDEX { portSlot, portNumber }
    ::= { hssiPortTable 1 }

HssiPortEntry ::=
    SEQUENCE {
        hssiPortLoopbackType
            INTEGER,
        hssiPortPeakRate
            INTEGER,
        hssiPortScramble
            INTEGER,
        hssiPortLineRate
            INTEGER
    }

hssiPortLoopbackType OBJECT-TYPE
    SYNTAX INTEGER { none        (1), -- no loopback
                     networkLine (2),
                     localCard   (3) }
    ACCESS read-write
    STATUS mandatory
    DESCRIPTION
            "Loopback type of the HSSI port."
    DEFVAL { none }
    ::= { hssiPortEntry 1 }

hssiPortPeakRate OBJECT-TYPE
    SYNTAX INTEGER (5..44)
    ACCESS read-write
    STATUS mandatory
    DESCRIPTION
            "Peak data transfer rate of the HSSI port.  Unit: Mbps."
    ::= { hssiPortEntry 2 }

hssiPortScramble OBJECT-TYPE
    SYNTAX INTEGER { no(1), 
                     yes(2) }
    ACCESS read-write
    STATUS mandatory
    DESCRIPTION
            "ATM payload scrambling for the HSSI port."
    DEFVAL { yes }
    ::= { hssiPortEntry 3 }

hssiPortLineRate OBJECT-TYPE
    SYNTAX INTEGER 
    ACCESS read-only
    STATUS mandatory
    DESCRIPTION
            "Physical Line data transfer rate of the HSSI port. Unit: CPS."
    ::= { hssiPortEntry 4 }


-- HSSI Port Stats Group (hssiPortStats)

hssiPortStatsTable OBJECT-TYPE
    SYNTAX SEQUENCE OF HssiPortStatsEntry
    ACCESS not-accessible
    STATUS mandatory
    DESCRIPTION
            "The HSSI port stats information table."
    ::= { hssiPortStats 1 }

hssiPortStatsEntry OBJECT-TYPE
    SYNTAX HssiPortStatsEntry
    ACCESS not-accessible
    STATUS mandatory
    DESCRIPTION
            "Information about a HSSI port stats."
    INDEX { portSlot, portNumber }
    ::= { hssiPortStatsTable 1 }

HssiPortStatsEntry ::=
    SEQUENCE {
        hssiPortRxCells
            Gauge,
        hssiPortTxCells
            Gauge,
        hssiPortIdleUnassignedCells
            Gauge,
        hssiPortHCSErrorCells
            Gauge,
        hssiPortResetTimeDate
            TimeAndDate,
        hssiPortResetStats
            INTEGER,
        hssiPortUtilRxCells
            INTEGER,
        hssiPortUtilTxCells
            INTEGER
    }

hssiPortRxCells OBJECT-TYPE
    SYNTAX  Gauge
    ACCESS  read-only
    STATUS  mandatory
    DESCRIPTION
            "The counter associated with the received cells, encountered
            on the ATM interface."
    ::= { hssiPortStatsEntry 1 }

hssiPortTxCells OBJECT-TYPE
    SYNTAX  Gauge
    ACCESS  read-only
    STATUS  mandatory
    DESCRIPTION
            "The counter associated with the transmitted cells, encountered
            on the ATM interface."
    ::= { hssiPortStatsEntry 2 }

hssiPortIdleUnassignedCells OBJECT-TYPE
    SYNTAX  Gauge
    ACCESS  read-only
    STATUS  mandatory
    DESCRIPTION
            "The counter associated with the idle/unassigned cells, encountered
            on the ATM interface."
    ::= { hssiPortStatsEntry 3 }

hssiPortHCSErrorCells OBJECT-TYPE
    SYNTAX  Gauge
    ACCESS  read-only
    STATUS  mandatory
    DESCRIPTION
            "The counter associated with the HCS errored cells, encountered
            on the ATM interface."
    ::= { hssiPortStatsEntry 4 }

hssiPortResetTimeDate OBJECT-TYPE
    SYNTAX  TimeAndDate
    ACCESS  read-only
    STATUS  mandatory
    DESCRIPTION
            "The reset time and date of ATM stats on this ATM interface."
    ::= { hssiPortStatsEntry 5 }

hssiPortResetStats OBJECT-TYPE
    SYNTAX  INTEGER { reset (1) }
    ACCESS  write-only
    STATUS  mandatory
    DESCRIPTION
            "This field is used to reset the atm statistics for the hssi port.
             If a get is performed on this command, the result will always
             be zero"
    ::= { hssiPortStatsEntry 6 }

hssiPortUtilRxCells OBJECT-TYPE
    SYNTAX  INTEGER 
    ACCESS  read-only
    STATUS  mandatory
    DESCRIPTION
            "The Utilization of received Cell is calculcated as 
             received cells divided by Line Rate.  "
    ::= { hssiPortStatsEntry 7 }

hssiPortUtilTxCells OBJECT-TYPE
    SYNTAX  INTEGER 
    ACCESS  read-only
    STATUS  mandatory
    DESCRIPTION
            "The Utilization of transmitted Cell is calculcated as 
             transmitted cells divided by Line Rate.  "
   ::= { hssiPortStatsEntry 8 }

END
