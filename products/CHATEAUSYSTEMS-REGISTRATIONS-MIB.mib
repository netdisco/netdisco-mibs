CHATEAUSYSTEMS-REGISTRATIONS-MIB DEFINITIONS ::= BEGIN

--
--               Chateau Systems, Inc
--              SMI Registrations MIB
--                      SMIv2
--                 November 14, 2005
--
--
-- This MIB registers certain high level node definitions,
-- under which all Chateau Systems MIBs are organized.
--
--
-- The objects defined in this MIB are located under the
-- private.enterprises subtree as shown below:
--
--
--
--   iso(1).org(3).dod(6).internet(1)
--                           |
--                        private(4)
--                           |
--                      enterprises(1)
--                           |
--                   chateausystems(10910)
--                           |
--              _____________|___________
--             |                         |
--    chateauExperimental(1)   chateauRegistrations(2)
--                                       |
--                                       |
--                  _____________________|__________
--                 |                                |
--                 |                                |
--    chateauGlobalRegistrations(1)        chateauProducts(2)
--                 |                                |
--                 |                                |
--                 |                    chateauConsumerProducts(3)
--        chateauProductRegs(1)                     |
--                 |                                |
--    chateauConsumerProductRegs(3)        chateauCDProduct(1)
--                 |
--      (OID Registrations)
--
--
--
--
-- OBJECT SUMMARY:
--
-- All objects within this MIB are prefixed with the OBJECT IDENTIFIER "cs"
-- where "cs" is defined by:
--
--      iso(1).org(3).dod(6).internet(1).private(4).enterprises(1).
--      chateausystems(10910)
--
-- OBJECT NAME                                     OBJECT OID
-- ----------------------------------------        ---------------------
--
-- chateauExperimental                             cs.1
-- chateauRegistrations                            cs.2
--   chateauGlobalRegistrations                    cs.2.1
--      chateauProductRegs                         cs.2.1.1
--        chateauConsumerProductRegs               cs.2.1.1.3
--           chateauCDProductReg                   cs.2.1.1.3.1
--   chateauProducts                               cs.2.2
--      chateauConsumerProducts                    cs.2.2.3
--         chateauCDProduct                        cs.2.2.3.1
--
--


      IMPORTS
          MODULE-IDENTITY, OBJECT-IDENTITY, enterprises
              FROM SNMPv2-SMI
          TEXTUAL-CONVENTION
              FROM SNMPv2-TC;




      chateausystems MODULE-IDENTITY
      LAST-UPDATED "200511090000Z"
      ORGANIZATION "Chateau Systems, Inc."
      CONTACT-INFO
      "Larry R. Walsh
       Chateau Systems, Inc
       PO Box 898
       Stanwood, WA 98292
       USA

       360 387-2615

       larrywalsh@chateausystems.com

       www.chateausystems.com"

      DESCRIPTION
       "This MIB defines high level nodes that are used to
        organize Chateau Systems Registrations and
        MIBs into ordered groups.

        This MIB also contains Chateau Systems Enterprise-specific
        Textual Convention definitions.

        This MIB is intended to be IMPORT'ed by all other
        Chateau Systems MIBs.

        This MIB has been distributed as part of the handout
        materials from the SNMP Technology Seminar presented
        by Chateau Systems.

        Any person or organization making use of this example MIB is
        responsible for ensuring its complete suitability for their
        own purposes. This includes the text of the legal disclaimers
        below, as well as all other aspects.

        Chateau Systems reserves the right to make changes in
        specifications and other information contained
        in this document without prior notice.
        The reader should contact Chateau Systems to determine
        whether or not such changes have been made.

        In no event shall Chateau Systems be liable for any
        incidental, indirect, special, or consequential damages
        whatsoever (including but not limited to lost profits)
        arising out of or related to this document or the
        information contained in it, even if Chateau Systems has
        been advised of, known, or should have known, the
        possibility of such damages.

        Chateau Systems grants vendors, end-users, and other interested
        parties a non-exclusive license to use this specification
        in connection with the management of Chateau Systems products.

        Copyright November 2005 Chateau Systems, Inc."

        REVISION      "200511090000Z"
        DESCRIPTION
        "Added Consumer CD Product Nodes."

        REVISION      "200202200000Z"
        DESCRIPTION
        "First Release."

        ::= { enterprises 10910}


--
-- Chateau Systems Experimental Registrations
--

chateauExperimental OBJECT-IDENTITY
    STATUS current
    DESCRIPTION
       "All experimental MIBs are organized under
        this node. When those MIBs have been fully developed and tested,
        they will be moved under the chateauRegistrations Node.
        MIBs which are in Beta-test status may also appear
        under this experimental node."
    ::= { chateausystems 1 }

--
-- Chateau Systems Registrations for Released MIBs and Global Registrations
--

chateauRegistrations OBJECT-IDENTITY
    STATUS current
    DESCRIPTION
       "All MIBs (that have completed testing),
        along with associated registration data, are
        organized under this node. This includes Global
        Registrations, Product MIBs, and registration of
        MIBs in other categories."
    ::= { chateausystems 2 }


--
-- Chateau Systems Global Registrations
--

chateauGlobalRegistrations OBJECT-IDENTITY
    STATUS current
    DESCRIPTION
      "This node is intended for global registration information
       only. EG, OID definitions that register products."
    ::= { chateauRegistrations 1 }


chateauProductRegs OBJECT-IDENTITY
    STATUS current
    DESCRIPTION
      "Specific Product Registrations are under this node."
    ::= { chateauGlobalRegistrations 1 }



chateauConsumerProductRegs OBJECT-IDENTITY
    STATUS current
    DESCRIPTION
      "Consumer Product Registrations are under this node."
    ::= { chateauProductRegs 3 }



chateauCDProductReg OBJECT-IDENTITY
    STATUS current
    DESCRIPTION
      "The OID of this node is the definition of the authoritative
       registration for the Chateau Systems CD Product."
    ::= { chateauConsumerProductRegs 1 }


--
-- Chateau Systems Product MIB Registrations
--

chateauProducts OBJECT-IDENTITY
    STATUS current
    DESCRIPTION
       "All Chateau Systems Product MIBs are organized
        under this node."
    ::= { chateauRegistrations 2 }


chateauConsumerProducts OBJECT-IDENTITY
    STATUS current
    DESCRIPTION
       "All Chateau Systems Consumer Product MIBs are
        organized under this node"
    ::= { chateauProducts 3 }


chateauCDProduct OBJECT-IDENTITY
    STATUS current
    DESCRIPTION
       "Chateau CD Product MIBs are organized under this node."
    ::= { chateauConsumerProducts 1 }



--
-- Chateau Systems Corporation unique TEXTUAL-CONVENTION definitions
--


ChateauTrapControl ::= TEXTUAL-CONVENTION
    STATUS    current
    DESCRIPTION
        "Used to enable or disable specific Traps."
    SYNTAX    INTEGER
                {
                  trapEnable(1),
                  trapDisable(2)
                }


ChateauEventSeverity ::= TEXTUAL-CONVENTION
    STATUS    current
    DESCRIPTION
        "Used to assign severities to detected events.
         Event Severity data is sent with Traps, to
         indicate the severity of particular Traps.
         Spaces have been left in the enumerated
         definitions to any future severity definitions.
         For example:
           { normal(1), warning(2), minor(3), major(4), critical(5)}"

    SYNTAX    INTEGER
                {
                  normal(1),
                  warning(2),
                  major(4)
                }



END
