C-PRODUCT-SIM-STAT-MIB DEFINITIONS ::= BEGIN


IMPORTS
    qsim                 FROM C-PRODUCT-GROUP-MIB
    TimeAndDate,
    portSlot,
    portNumber,
    vcpSideId 		 FROM C-PRODUCT-BASE-MIB
    Counter              FROM RFC1155-SMI
    OBJECT-TYPE          FROM RFC-1212;

-- Data Types

-- Serial Interface Module (SIM) Statistics groups

simStat         OBJECT IDENTIFIER ::= { qsim   5 } -- cover qsim, hsim, etc.

simPortStat     OBJECT IDENTIFIER ::= { simStat 1 }
simAtmVcStat    OBJECT IDENTIFIER ::= { simStat 2 }
simDxiVcStat    OBJECT IDENTIFIER ::= { simStat 3 }
simFrameRelayVcStat
                OBJECT IDENTIFIER ::= { simStat 4 }
simLmiStat      OBJECT IDENTIFIER ::= { simStat 5 }
simNewAtmVcStat    OBJECT IDENTIFIER ::= { simStat 6 }
simNewDxiVcStat    OBJECT IDENTIFIER ::= { simStat 7 }
simNewFrameRelayVcStat
                 OBJECT IDENTIFIER ::= { simStat 8 }


-- Serial Interface Module Port Statistics subgroup (simPortStat)
-- This table is used to access the frame statistics on the ports.
-- This group should cover a variety of port types including 
-- QSIM(V.35, RS422), HSIM, and (OSIM)8-port T1

simPortStatTable OBJECT-TYPE
    SYNTAX SEQUENCE OF SimPortStatEntry
    ACCESS not-accessible
    STATUS mandatory
    DESCRIPTION
            "The Serial Interface Module Port Statistics table. "
    ::= { simPortStat 1 }

simPortStatEntry OBJECT-TYPE
    SYNTAX SimPortStatEntry
    ACCESS not-accessible
    STATUS mandatory
    DESCRIPTION
            "Information about a Serial Interface Module Port Statistics.
             The slot number (portSlot) of this card can be from 4 to 6.  
             The port number (portNumber) can be from 1 to 4 for QSIM,
             1 for HSIM, and from 1 to 8 for OSIM."
    INDEX { portSlot, portNumber }
    ::= { simPortStatTable 1 }

SimPortStatEntry ::=
    SEQUENCE {
        simPortClrStatCmd
            INTEGER,
        simPortClrStatTime
            TimeAndDate,
        simPortRxFrames 
            Counter,
        simPortTxFrames 
            Counter,
        simPortInvalidFrames 
            Counter,
        simPortCongestedFrames 
            Counter,
        simPortRxOctets
            Counter,
        simPortTxOctets
            Counter,
        simPortRxFcsErrs
            Counter
    }

simPortClrStatCmd OBJECT-TYPE
    SYNTAX  INTEGER { 
                      clear (1)
                    }
    ACCESS  read-write
    STATUS  mandatory
    DESCRIPTION
            "This is issued to clear all statistics of this port.
             The current time will be stored at simPortClrStatTime."
    ::= { simPortStatEntry 1 }

simPortClrStatTime OBJECT-TYPE
    SYNTAX  TimeAndDate
    ACCESS  read-only
    STATUS  mandatory
    DESCRIPTION
            "The time when the last statistics was clear."
    ::= { simPortStatEntry 2 }

simPortRxFrames OBJECT-TYPE
    SYNTAX Counter
    ACCESS read-only
    STATUS mandatory
    DESCRIPTION
            "Total received frames with good FCS at this port 
             since last counter reset."
    ::= { simPortStatEntry 3 }

simPortTxFrames OBJECT-TYPE
    SYNTAX Counter
    ACCESS read-only
    STATUS mandatory
    DESCRIPTION
            "Total transmitted frames at this port since last counter reset.
             These frames were transmitted successfuly."
    ::= { simPortStatEntry 4 }

simPortInvalidFrames OBJECT-TYPE
    SYNTAX Counter
    ACCESS read-only
    STATUS mandatory
    DESCRIPTION
            "Total received invalid frames at this port since last 
             counter reset. These frames are received with good FCS but can
             not be processed due to wrong content."
    ::= { simPortStatEntry 5 }

simPortCongestedFrames OBJECT-TYPE
    SYNTAX Counter
    ACCESS read-only
    STATUS mandatory
    DESCRIPTION
            "Total congested frames at this port since last counter reset.
             These frames were not transmitted due to link congestion."
    ::= { simPortStatEntry 6 }

simPortRxOctets OBJECT-TYPE
    SYNTAX Counter
    ACCESS read-only
    STATUS mandatory
    DESCRIPTION
            "Total received octets with good FCS at this port 
             since last counter reset."
    ::= { simPortStatEntry 7 }

simPortTxOctets OBJECT-TYPE
    SYNTAX Counter
    ACCESS read-only
    STATUS mandatory
    DESCRIPTION
            "Total transmitted octets at this port 
             since last counter reset."
    ::= { simPortStatEntry 8 }

simPortRxFcsErrs OBJECT-TYPE
    SYNTAX Counter
    ACCESS read-only
    STATUS mandatory
    DESCRIPTION
            "Total received frames with bad FCS at this port 
             since last counter reset."
    ::= { simPortStatEntry 9 }


-- Serial Interface Module ATM VC Statistics subgroup (simAtmVcStat)
-- This table is used to access the frame statistics on ATM VCs.
-- This group should cover a variety of port types including 
-- QSIM(V.35, RS422), HSIM, and (OSIM)8-port T1
-- This table is for AB9300 & AB9600 Rel2.0 onwards

simNewAtmVcStatTable OBJECT-TYPE
    SYNTAX SEQUENCE OF SimNewAtmVcStatEntry
    ACCESS not-accessible
    STATUS mandatory
    DESCRIPTION
            "The Serial Interface Module ATM VC Statistics table. "
    ::= { simNewAtmVcStat 1 }

simNewAtmVcStatEntry OBJECT-TYPE
    SYNTAX SimNewAtmVcStatEntry
    ACCESS not-accessible
    STATUS mandatory
    DESCRIPTION
            "Information about a Serial Interface Module ATM VC Statistics.
             The slot number (portSlot) of this card can be from 4 to 6.  
             The port number (portNumber) can be from 1 to 4 for QSIM,
             1 for HSIM, and from 1 to 8 for OSIM."
    INDEX { vcpSideId }
    ::= { simNewAtmVcStatTable 1 }


SimNewAtmVcStatEntry ::=
    SEQUENCE {
        simNewAtmVcClrStatCmd
            INTEGER,
        simNewAtmVcClrStatTime
            TimeAndDate,
        simNewAtmVcRxFrames   
            Counter,
        simNewAtmVcTxFrames 
            Counter,
        simNewAtmVcInvalidFrames 
            Counter,
        simNewAtmVcCongestedFrames 
            Counter
    }

simNewAtmVcClrStatCmd OBJECT-TYPE
    SYNTAX  INTEGER { 
                      clear (1)
                    }
    ACCESS  read-write
    STATUS  mandatory
    DESCRIPTION
            "This is issued to clear all statistics of this ATM VC.
             The current time will be stored at simNewAtmVcClrStatTime."
    ::= { simNewAtmVcStatEntry 1 }

simNewAtmVcClrStatTime OBJECT-TYPE
    SYNTAX  TimeAndDate
    ACCESS  read-only
    STATUS  mandatory
    DESCRIPTION
            "The time when the last statistics was clear."
    ::= { simNewAtmVcStatEntry 2 }

simNewAtmVcRxFrames OBJECT-TYPE
    SYNTAX Counter
    ACCESS read-only
    STATUS mandatory
    DESCRIPTION
            "Total received frames at this ATM VC 
             since last counter reset."
    ::= { simNewAtmVcStatEntry 3 }

simNewAtmVcTxFrames OBJECT-TYPE
    SYNTAX Counter
    ACCESS read-only
    STATUS mandatory
    DESCRIPTION
            "Total transmitted frames at this ATM VC since last counter reset.
             These frames were transmitted successfuly."
    ::= { simNewAtmVcStatEntry 4 }

simNewAtmVcInvalidFrames OBJECT-TYPE
    SYNTAX Counter
    ACCESS read-only
    STATUS mandatory
    DESCRIPTION
            "Total received invalid frames at this ATM VC since last 
             counter reset. These frames are received with good VC id but can
             not be processed due to wrong content."
    ::= { simNewAtmVcStatEntry 5 }

simNewAtmVcCongestedFrames OBJECT-TYPE
    SYNTAX Counter
    ACCESS read-only
    STATUS mandatory
    DESCRIPTION
            "Total congested frames at this ATM VC since last counter reset.
             These frames were not transmitted due to link congestion."
    ::= { simNewAtmVcStatEntry 6 }


-- Serial Interface Module DXI VC Statistics subgroup (simDxiVcStat)
-- This table is used to access the frame statistics on DXI VCs.
-- This group should cover a variety of port types including 
-- QSIM(V.35, RS422), HSIM, and (OSIM)8-port T1
-- This new table is for AB9600 Rel 2.0 & AB9300

simNewDxiVcStatTable OBJECT-TYPE
    SYNTAX SEQUENCE OF SimNewDxiVcStatEntry
    ACCESS not-accessible
    STATUS mandatory
    DESCRIPTION
            "The Serial Interface Module DXI VC Statistics table. "
    ::= { simNewDxiVcStat 1 }

simNewDxiVcStatEntry OBJECT-TYPE
    SYNTAX SimNewDxiVcStatEntry
    ACCESS not-accessible
    STATUS mandatory
    DESCRIPTION
            "Information about a Serial Interface Module DXI VC Statistics.
             The slot number (portSlot) of this card can be from 4 to 6.  
             The port number (portNumber) can be from 1 to 4 for QSIM,
             1 for HSIM, and from 1 to 8 for OSIM."
    INDEX { vcpSideId }
    ::= { simNewDxiVcStatTable 1 }


SimNewDxiVcStatEntry ::=
    SEQUENCE {
        simNewDxiVcClrStatCmd
            INTEGER,
        simNewDxiVcClrStatTime
            TimeAndDate,
        simNewDxiVcRxFrames   
            Counter,
        simNewDxiVcTxFrames 
            Counter,
        simNewDxiVcInvalidFrames 
            Counter,
        simNewDxiVcCongestedFrames 
            Counter,
        simNewDxiVcRxOctets
            Counter,
        simNewDxiVcTxOctets
            Counter,
        simNewDxiVcRxClp
            Counter
    }

simNewDxiVcClrStatCmd OBJECT-TYPE
    SYNTAX  INTEGER { 
                      clear (1)
                    }
    ACCESS  read-write
    STATUS  mandatory
    DESCRIPTION
            "This is issued to clear all statistics of this DXI VC.
             The current time will be stored at simDxiVcClrStatTime."
    ::= { simNewDxiVcStatEntry 1 }

simNewDxiVcClrStatTime OBJECT-TYPE
    SYNTAX  TimeAndDate
    ACCESS  read-only
    STATUS  mandatory
    DESCRIPTION
            "The time when the last statistics was clear."
    ::= { simNewDxiVcStatEntry 2 }

simNewDxiVcRxFrames OBJECT-TYPE
    SYNTAX Counter
    ACCESS read-only
    STATUS mandatory
    DESCRIPTION
            "Total received frames at this DXI VC 
             since last counter reset."
    ::= { simNewDxiVcStatEntry 3 }

simNewDxiVcTxFrames OBJECT-TYPE
    SYNTAX Counter
    ACCESS read-only
    STATUS mandatory
    DESCRIPTION
            "Total transmitted frames at this DXI VC since last counter reset.
             These frames were transmitted successfuly."
    ::= { simNewDxiVcStatEntry 4 }

simNewDxiVcInvalidFrames OBJECT-TYPE
    SYNTAX Counter
    ACCESS read-only
    STATUS mandatory
    DESCRIPTION
            "Total received invalid frames at this DXI VC since last 
             counter reset. These frames are received with good VC id but can
             not be processed due to wrong content."
    ::= { simNewDxiVcStatEntry 5 }

simNewDxiVcCongestedFrames OBJECT-TYPE
    SYNTAX Counter
    ACCESS read-only
    STATUS mandatory
    DESCRIPTION
            "Total congested frames at this DXI VC since last counter reset.
             These frames were not transmitted due to link congestion."
    ::= { simNewDxiVcStatEntry 6 }

simNewDxiVcRxOctets OBJECT-TYPE
    SYNTAX Counter
    ACCESS read-only
    STATUS mandatory
    DESCRIPTION
            "Total received octets at this DXI VC 
             since last counter reset."
    ::= { simNewDxiVcStatEntry 7 }

simNewDxiVcTxOctets OBJECT-TYPE
    SYNTAX Counter
    ACCESS read-only
    STATUS mandatory
    DESCRIPTION
            "Total transmitted octets at this DXI VC 
             since last counter reset."
    ::= { simNewDxiVcStatEntry 8 }

simNewDxiVcRxClp OBJECT-TYPE
    SYNTAX Counter
    ACCESS read-only
    STATUS mandatory
    DESCRIPTION
            "Total received frames with CLP bit set at this DXI VC 
             since last counter reset."
    ::= { simNewDxiVcStatEntry 9 }

-- Serial Interface Module FR VC Statistics subgroup (simFrameRelayVcStat)
-- This table is used to access the frame statistics on FR VCs.
-- This group should cover a variety of port types including 
-- QSIM(V.35, RS422), HSIM, and (OSIM)8-port T1

simNewFrameRelayVcStatTable OBJECT-TYPE
    SYNTAX SEQUENCE OF SimNewFrameRelayVcStatEntry
    ACCESS not-accessible
    STATUS mandatory
    DESCRIPTION
            "The Serial Interface Module FR VC Statistics table. "
    ::= { simNewFrameRelayVcStat 1 }

simNewFrameRelayVcStatEntry OBJECT-TYPE
    SYNTAX SimNewFrameRelayVcStatEntry
    ACCESS not-accessible
    STATUS mandatory
    DESCRIPTION
            "Information about a Serial Interface Module FR VC Statistics.
             The slot number (portSlot) of this card can be from 4 to 6.  
             The port number (portNumber) can be from 1 to 4 for QSIM,
             1 for HSIM, and from 1 to 8 for OSIM."
    INDEX { vcpSideId }
    ::= { simNewFrameRelayVcStatTable 1 }


SimNewFrameRelayVcStatEntry ::=
    SEQUENCE {
        simNewFrameRelayVcClrStatCmd
            INTEGER,
        simNewFrameRelayVcClrStatTime
            TimeAndDate,
        simNewFrameRelayVcRxFrames   
            Counter,
        simNewFrameRelayVcTxFrames 
            Counter,
        simNewFrameRelayVcInvalidFrames 
            Counter,
        simNewFrameRelayVcCongestedFrames 
            Counter,
        simNewFrameRelayVcRxOctets
            Counter,
        simNewFrameRelayVcTxOctets
            Counter,
        simNewFrameRelayVcRxDe
            Counter,
        simNewFrameRelayVcRxFecn
            Counter,
        simNewFrameRelayVcRxBecn
            Counter
    }

simNewFrameRelayVcClrStatCmd OBJECT-TYPE
    SYNTAX  INTEGER { 
                      clear (1)
                    }
    ACCESS  read-write
    STATUS  mandatory
    DESCRIPTION
            "This is issued to clear all statistics of this FR VC.
             The current time will be stored at simNewFrameRelayVcClrStatTime."
    ::= { simNewFrameRelayVcStatEntry 1 }

simNewFrameRelayVcClrStatTime OBJECT-TYPE
    SYNTAX  TimeAndDate
    ACCESS  read-only
    STATUS  mandatory
    DESCRIPTION
            "The time when the last statistics was clear."
    ::= { simNewFrameRelayVcStatEntry 2 }

simNewFrameRelayVcRxFrames OBJECT-TYPE
    SYNTAX Counter
    ACCESS read-only
    STATUS mandatory
    DESCRIPTION
            "Total received frames at this FR VC 
             since last counter reset."
    ::= { simNewFrameRelayVcStatEntry 3 }

simNewFrameRelayVcTxFrames OBJECT-TYPE
    SYNTAX Counter
    ACCESS read-only
    STATUS mandatory
    DESCRIPTION
            "Total transmitted frames at this FR VC since last counter reset.
             These frames were transmitted successfuly."
    ::= { simNewFrameRelayVcStatEntry 4 }

simNewFrameRelayVcInvalidFrames OBJECT-TYPE
    SYNTAX Counter
    ACCESS read-only
    STATUS mandatory
    DESCRIPTION
            "Total received invalid frames at this FR VC since last 
             counter reset. These frames are received with good VC id but can
             not be processed due to wrong content."
    ::= { simNewFrameRelayVcStatEntry 5 }

simNewFrameRelayVcCongestedFrames OBJECT-TYPE
    SYNTAX Counter
    ACCESS read-only
    STATUS mandatory
    DESCRIPTION
            "Total congested frames at this FR VC since last counter reset.
             These frames were not transmitted due to link congestion."
    ::= { simNewFrameRelayVcStatEntry 6 }

simNewFrameRelayVcRxOctets OBJECT-TYPE
    SYNTAX Counter
    ACCESS read-only
    STATUS mandatory
    DESCRIPTION
            "Total received octets at this FR VC 
             since last counter reset."
    ::= { simNewFrameRelayVcStatEntry 7 }

simNewFrameRelayVcTxOctets OBJECT-TYPE
    SYNTAX Counter
    ACCESS read-only
    STATUS mandatory
    DESCRIPTION
            "Total transmitted octets at this FR VC 
             since last counter reset."
    ::= { simNewFrameRelayVcStatEntry 8 }

simNewFrameRelayVcRxDe OBJECT-TYPE
    SYNTAX Counter
    ACCESS read-only
    STATUS mandatory
    DESCRIPTION
            "Total received frames with DE bit set at this FR VC 
             since last counter reset."
    ::= { simNewFrameRelayVcStatEntry 9 }

simNewFrameRelayVcRxFecn OBJECT-TYPE
    SYNTAX Counter
    ACCESS read-only
    STATUS mandatory
    DESCRIPTION
            "Total received frames with FECN bit set at this FR VC 
             since last counter reset."
    ::= { simNewFrameRelayVcStatEntry 10 }

simNewFrameRelayVcRxBecn OBJECT-TYPE
    SYNTAX Counter
    ACCESS read-only
    STATUS mandatory
    DESCRIPTION
            "Total received frames with BECN bit set at this FR VC 
             since last counter reset."
    ::= { simNewFrameRelayVcStatEntry 11 }

--
-- LMI statistics group (simLmiStatTable)
--

simLmiStatTable OBJECT-TYPE
    SYNTAX SEQUENCE OF SimLmiStatEntry
    ACCESS not-accessible
    STATUS mandatory
    DESCRIPTION
            "LMI statistics table."
    ::= { simLmiStat 1 }

simLmiStatEntry OBJECT-TYPE
    SYNTAX SimLmiStatEntry
    ACCESS not-accessible
    STATUS mandatory
    DESCRIPTION
            "LMI statistics entry.  The slot index (portSlot) of this
             entry can be from 4 to 6.  The port index (portNumber) can
             be from 1 to 8 for FAM, 1 to 4 for QSIM and 1 for HSIM."
    INDEX { portSlot, portNumber }
    ::= { simLmiStatTable 1 }

SimLmiStatEntry ::=
    SEQUENCE {
        simLmiClrStatCmd
            INTEGER,
        simLmiClrStatTime
            TimeAndDate,
        simLmiReceivedFrames   
            Counter,
        simLmiDiscardedFrames   
            Counter,
        simLmiUserLivTimeouts   
            Counter,
        simLmiUserXmtLivRequests 
            Counter,
        simLmiUserRcvLivResponses
            Counter,
        simLmiUserXmtFullStatusRequests
            Counter,
        simLmiUserRcvFullStatusResponses
            Counter,
        simLmiUserLossSeqNumSyncs
            Counter,
        simLmiUserRcvUnconfigPvcs
            Counter,
        simLmiNetworkPvTimeouts
            Counter,
        simLmiNetworkRcvLivRequests
            Counter,
        simLmiNetworkXmtLivResponses 
            Counter,
        simLmiNetworkRcvFullStatusRequests
            Counter,
        simLmiNetworkXmtFullStatusResponses
            Counter,
        simLmiNetworkLossSeqNumSyncs
            Counter
    }

simLmiClrStatCmd OBJECT-TYPE
    SYNTAX  INTEGER { clear (1) }
    ACCESS  read-write
    STATUS  mandatory
    DESCRIPTION
            "This is a command to clear all LMI statistics.  This object
             applies when LMI protocol is not 'none'."
    ::= { simLmiStatEntry 1 }

simLmiClrStatTime OBJECT-TYPE
    SYNTAX  TimeAndDate
    ACCESS  read-only
    STATUS  mandatory
    DESCRIPTION
            "The time when the last LMI statistics was cleared.  This object
             applies when LMI protocol is not 'none'."
    ::= { simLmiStatEntry 2 }

simLmiReceivedFrames OBJECT-TYPE
    SYNTAX Counter
    ACCESS read-only
    STATUS mandatory
    DESCRIPTION
            "Received LMI frames.  This object applies when LMI protocol is
             not 'none'."
    ::= { simLmiStatEntry 3 }

simLmiDiscardedFrames OBJECT-TYPE
    SYNTAX Counter
    ACCESS read-only
    STATUS mandatory
    DESCRIPTION
            "Discarded LMI frames.  This object applies when LMI protocol is
             not 'none'."
    ::= { simLmiStatEntry 4 }

simLmiUserLivTimeouts OBJECT-TYPE
    SYNTAX Counter
    ACCESS read-only
    STATUS mandatory
    DESCRIPTION
            "User-side LIV timeouts.  This object applies when LMI
             procedure is user-side or bidirectional."
    ::= { simLmiStatEntry 5 }

simLmiUserXmtLivRequests OBJECT-TYPE
    SYNTAX Counter
    ACCESS read-only
    STATUS mandatory
    DESCRIPTION
            "User-side LIV requests.  This object applies when LMI
             procedure is user-side or bidirectional."
    ::= { simLmiStatEntry 6 }

simLmiUserRcvLivResponses OBJECT-TYPE
    SYNTAX Counter
    ACCESS read-only
    STATUS mandatory
    DESCRIPTION
            "User-side LIV responses.  This object applies when LMI
             procedure is user-side or bidirectional."
    ::= { simLmiStatEntry 7 }

simLmiUserXmtFullStatusRequests OBJECT-TYPE
    SYNTAX Counter
    ACCESS read-only
    STATUS mandatory
    DESCRIPTION
            "User-side full status requests.  This object applies when
             LMI procedure is user-side or bidirectional."
    ::= { simLmiStatEntry 8 }

simLmiUserRcvFullStatusResponses OBJECT-TYPE
    SYNTAX Counter
    ACCESS read-only
    STATUS mandatory
    DESCRIPTION
            "User-side full status responses.  This object applies when
             LMI procedure is user-side or bidirectional."
    ::= { simLmiStatEntry 9 }

simLmiUserLossSeqNumSyncs OBJECT-TYPE
    SYNTAX Counter
    ACCESS read-only
    STATUS mandatory
    DESCRIPTION
            "User-side loss of sequence number synchronization.  This object
             applies when LMI procedure is user-side or bidirectional."
    ::= { simLmiStatEntry 10 }

simLmiUserRcvUnconfigPvcs OBJECT-TYPE
    SYNTAX Counter
    ACCESS read-only
    STATUS mandatory
    DESCRIPTION
            "User-side unconfigured PVCs.  This object applies when LMI
             procedure is user-side or bidirectional."
    ::= { simLmiStatEntry 11 }

simLmiNetworkPvTimeouts OBJECT-TYPE
    SYNTAX Counter
    ACCESS read-only
    STATUS mandatory
    DESCRIPTION
            "Network-side PV timeouts.  This object applies when LMI
             procedure is network-side or bidirectional."
    ::= { simLmiStatEntry 12 }

simLmiNetworkRcvLivRequests OBJECT-TYPE
    SYNTAX Counter
    ACCESS read-only
    STATUS mandatory
    DESCRIPTION
            "Network-side LIV requests.  This object applies when LMI
             procedure is network-side or bidirectional."
    ::= { simLmiStatEntry 13 }

simLmiNetworkXmtLivResponses OBJECT-TYPE
    SYNTAX Counter
    ACCESS read-only
    STATUS mandatory
    DESCRIPTION
            "Network-side LIV responses.  This object applies when LMI
             procedure is network-side or bidirectional."
    ::= { simLmiStatEntry 14 }

simLmiNetworkRcvFullStatusRequests OBJECT-TYPE
    SYNTAX Counter
    ACCESS read-only
    STATUS mandatory
    DESCRIPTION
            "Network-side full status requests.  This object applies when LMI
             procedure is network-side or bidirectional."
    ::= { simLmiStatEntry 15 }

simLmiNetworkXmtFullStatusResponses OBJECT-TYPE
    SYNTAX Counter
    ACCESS read-only
    STATUS mandatory
    DESCRIPTION
            "Network-side full status responses.  This object applies when LMI
             procedure is network-side or bidirectional."
    ::= { simLmiStatEntry 16 }

simLmiNetworkLossSeqNumSyncs OBJECT-TYPE
    SYNTAX Counter
    ACCESS read-only
    STATUS mandatory
    DESCRIPTION
            "Network-side loss of sequence number synchronization.  This object
             applies when LMI procedure is network-side or bidirectional."
    ::= { simLmiStatEntry 17 }

END
