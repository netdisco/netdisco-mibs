--
-- WIRELESS-INNOVATIONS-PRODUCTS-MIB.mib
-- MIB generated by MG-SOFT Visual MIB Builder Version 3.0 Build 253
-- Tuesday, December 18, 2012 at 17:25:11
--

	WIRELESS-INNOVATIONS-PRODUCTS-MIB DEFINITIONS ::= BEGIN
 
		IMPORTS
			wirelessInnovations			
				FROM ANDREW-MIB			
			PhysicalIndex			
				FROM ENTITY-MIB			
			OBJECT-GROUP, MODULE-COMPLIANCE, NOTIFICATION-GROUP			
				FROM SNMPv2-CONF			
			sysName			
				FROM SNMPv2-MIB			
			Integer32, Unsigned32, Gauge32, Counter32, OBJECT-TYPE, 
			MODULE-IDENTITY, OBJECT-IDENTITY, NOTIFICATION-TYPE			
				FROM SNMPv2-SMI			
			TruthValue, VariablePointer, DateAndTime, TEXTUAL-CONVENTION			
				FROM SNMPv2-TC;
	
	
		wirelessInnovationsProducts MODULE-IDENTITY 
			LAST-UPDATED "201212181725Z"		-- December 18, 2012 at 17:25 GMT
			ORGANIZATION 
				"Wireless Innovations"
			CONTACT-INFO 
				"Industriering 10
				86675 Buchdorf
				Germany"
			DESCRIPTION 
				"MIB for Wireless Innovations distributed management system."
			REVISION "201212181725Z"		-- December 18, 2012 at 17:25 GMT
			DESCRIPTION
				"1.6.0.0
				Changed:
				- TC CTA: Description extended (Example 5+6).
				- basicAgentConditionChangedConfig: Extended with locationLatency
				- connVpnServerPhysicalIP: Description extended, made Read Only.
				                           Now several VPN servers supported, see 'connVpnServerGroups'
				- connVpnManagerVirtualIP: Description extended
				Added:
				- object identity 'basicGpsData'
				- changedLocationAreaEvent
				- connAgentInformTimeout
				- connAgentInformRetries
				- connOpenVpnProtocol
				- connVpnClientVirtualIP
				- connVpnNotificationDestinationIsAlarmRecipient
				- connVpnConnectionMode
				- object identity 'connVpnServerGroups'
				- connVpnDisconnectTrigger
				- connAgentZoneChangeNotificationsEnabled
				- object identity 'ionU'"
			REVISION "201102171315Z"		-- February 17, 2011 at 13:15 GMT
			DESCRIPTION
				"1.5.3.0
				Changed:
				- commonDeviceSwUpdateActivationRemoval: Description extended.
				- swNeededFilesTable: Description extended.
				Added:
				- swNeededFilesTable.swNeededFilesImmediateActivationRequired
				- swNeededFilesTable.swNeededFilesImmediateActivationSync
				- swFinalActivationNotification"
			REVISION "201012141715Z"		-- December 14, 2010 at 17:15 GMT
			DESCRIPTION
				"1.5.2.0
				Added:
				- connAgentWebCommunicationProtocol"
			REVISION "201011030825Z"		-- November 03, 2010 at 08:25 GMT
			DESCRIPTION
				"1.5.1.0
				Changed:
				- basicAgentOutOfOperationArea: Description extended.
				- connAgentUID2: Description extended.
				- changedParameterEvent: new object (basicCurrentTime), description extended"
			REVISION "201006011300Z"		-- June 01, 2010 at 13:00 GMT
			DESCRIPTION
				"1.5.0.0
				Changed:
				- TC Version: range extended (empty string is allowed).
				- alarmTrapCounter: description extended.
				- alarmTrap: new object (basicAgentLocationIdentification) added
				- changedParameterEvent: new objects (basicAgentLocationIdentification,basicAgentLocationAlias,basicAgentOutOfOperationArea,basicAgentConditionChangedConfig,connAgentUID2)
				- changedIPAddressEvent: new object (connAgentUID2)
				- agentUpAndRunningEvent: new objects (basicAgentOutOfOperationArea,connAgentUID2,swActivePackageVersion,swActivePackagePatchLevel) added
				- object identity 'commonDeviceFileTransfer.fUpload': several descriptions extended.
				
				Added:
				- basicAgentLocationIdentification
				- basicAgentLocationAlias
				- basicAgentOutOfOperationArea
				- basicAgentConditionChangedConfig
				- alarmConfig2Latency
				- connAgentUID2
				- agentShutdownEvent
				- fulDestFolder
				- object identity 'commonDeviceSwUpdateActivationRemoval'
				"
			REVISION "200912141630Z"		-- December 14, 2009 at 16:30 GMT
			DESCRIPTION
				"1.4.0.0
				Changed:
				- TC CTA: Description extended (Example 4).
				- alarmConfigTable -> obsolete. This table is no longer supported.
				  New table is alarmConfig2Table.
				- alarmUsertextTable -> obsolete. This table is no longer supported.
				  New table is alarmUsertext2Table.
				- featureKeyNew: string size corrected (empty string is allowed).
				
				Added:
				- object identity 'commonDeviceFileTransfer.fUpload'"
			REVISION "200802211600Z"		-- February 21, 2008 at 16:00 GMT
			DESCRIPTION
				"1.3.1.0
				Changed:
				- TC SpecificProblem: range extended
				- connAndrewVpnAuthUsername: range corrected
				- connAndrewVpnAuthPassword: range corrected
				- connAgentDisconnectTrigger: description corrected
				- featureKeyNew: description corrected
				- TC CTA,
				  alarmUsertext4CTA,
				  alarmThreshold4CTA,
				  alarmEquipmentCTA: description extended to describe the extended CTA handling"
			REVISION "200709281440Z"		-- September 28, 2007 at 14:40 GMT
			DESCRIPTION
				"1.3.0.0
				Changed:
				- heartbeatEvent: new object added
				- changedIPAddressEvent: added 3 new objects
				- connAgntOrigIfExtraSetting: range extended
				
				Added:
				- TC PositiveIntegerButNotZero
				- TC PositiveIntegerIncludingZero
				- object idendity 'alarmThresholds'
				- alarmSummary
				- connAgentDisconnectTrigger
				- object idendity 'connAgentVpn'
				- connAgntOrigAlwaysOnInactivityTimer
				- object idendity 'commonDeviceFeatureKeys'
				- child node groupION
				- optionalObjectsGroup"
			REVISION "200703301100Z"		-- March 30, 2007 at 11:00 GMT
			DESCRIPTION
				"1.2.2.0
				Added child node groupMiniRepeater"
			REVISION "200611071714Z"		-- November 07, 2006 at 17:14 GMT
			DESCRIPTION
				"1.2.1.0
				Added child node groupAMR"
			REVISION "200512091514Z"		-- December 09, 2005 at 15:14 GMT
			DESCRIPTION
				"1.2.0.0
				Descriptions corrected/extended:
				- alarmTrapCounter: extended, because of new agentUpAndRunningEvent
				
				Added:
				- TC NotificationType
				- TC Severity4Set
				- alarmSeveritiesSupported4Set
				- alarmConfigTable
				- alarmUsertextTable
				- connAgentNotificationType
				- agentRebootRequiredEvent
				- agentUpAndRunningEvent"
			REVISION "200511171700Z"		-- November 17, 2005 at 17:00 GMT
			DESCRIPTION
				"1.1.1.0
				Changed:
				- basicAgentIPAddress -> obsolete. This object is no longer supported.
				- connAgentMainConnectivityType -> obsolete. This object is no longer supported.
				  New objects are 'connAgentMainConnectivity' and corresponding 'connAgntOrigIfConnectionType'.
				- connAgntOrigIfConnectivityType -> obsolete. This object is no longer supported.
				  New objects are 'connAgntOrigIfNetworkType' and 'connAgntOrigIfConnectionType'.
				
				Descriptions corrected/extended:
				- commonDeviceConnectivity.*Password*: return value corrected/harmonized with actual implementation
				- connAgntOrigIfExtraSetting: extended
				- connAttachPSODrequesterSMS: extended
				
				Added:
				- TC NetworkType
				- TC ConnectionType
				- connAgentMainConnectivity
				- connAgntOrigIfNetworkType
				- connAgntOrigIfConnectionType
				- connAttachPSODbySMSenabled
				- connAgentSMSserviceCenter
				- connAgentSmsWlTable"
			REVISION "200505121645Z"		-- May 12, 2005 at 16:45 GMT
			DESCRIPTION
				"1.1.0.0
				Removed still unused placeholders:
				- groupTMA
				- groupTMB
				- groupSR
				- groupNodeB
				- groupLOMC
				- groupMMR
				
				Changed:
				- basicAgentIPAddress -> deprecated. New object is 'connManOrigAgentIPAddressCS'
				- Syntax alarmHeartbeatInterval: Unsigned32 -> Gauge32 (same base syntax)
				
				Descriptions corrected/extended:
				- alarmPerceivedSeverity: harmonized with corresponding TC
				- alarmID: is not alarm table index
				- changedIPAddressEvent: extended
				
				Added:
				- TC ConnectivityType
				- object identity 'commonDeviceConnectivity'
				  + connAgentUID, appended to every private/enterprise trap
				  + connAgentMainConnectivityType
				  + connAgentIPAddressLAN
				  + object identity 'connManagerOriginated'
				    * connManOrigAgentIPAddressCS
				    * connManOrigAuthUsernameCS
				    * connManOrigAuthPasswordCS
				    * connManOrigIdleTimeoutCS
				  + object identity 'connAgentOriginated'
				    * connAgntOrigIfTable
				      ~ connAgntOrigIfIndex
				      ~ connAgntOrigIfConnectivityType
				      ~ connAgntOrigIfEnabled
				      ~ connAgntOrigIfExtraSetting
				      ~ connAgntOrigIfPhoneNo
				      ~ connAgntOrigIfAuthUsername
				      ~ connAgntOrigIfAuthPassword
				  + connAgntOrigIdleTimeoutPSODreqBySMS
				  + connAttachPSODrequesterSMS, added to changedIPAddressEvent
				- object identity 'commonDeviceControl'
				  + ctrlApplication"
			REVISION "200410281651Z"		-- October 28, 2004 at 16:51 GMT
			DESCRIPTION
				"1.0.0.6
				Added basicAgentIPAddressNew and changedIPAddressEvent."
			REVISION "200402031133Z"		-- February 03, 2004 at 11:33 GMT
			DESCRIPTION
				"1.0.0.5
				Added basicAgentIPAddress.
				"
			REVISION "200310300946Z"		-- October 30, 2003 at 09:46 GMT
			DESCRIPTION
				"1.0.0.4
				Updated heartBeat interval range."
			REVISION "200309111007Z"		-- September 11, 2003 at 10:07 GMT
			DESCRIPTION
				"1.0.0.3
				Added back alarmIDX.
				Changed alarm table index to alarmIDX."
			REVISION "200309101035Z"		-- September 10, 2003 at 10:35 GMT
			DESCRIPTION
				"1.0.0.2
				Removed the following from alarm table:
				  alarmIDX
				  alarmTrendIndication
				  alarmEquipmentCIN
				  alarmEquipmentDescription
				  alarmEquipmentSerialNo
				  alarmPhysicalAlias
				
				Removed the following trend indications:
				  TrendIndication
				  CIN
				  SerialNo
				
				Made alarmID index into alarm table.
				Created textual convention, alarmDescrString.
				Changed alarmAdditionalText syntax to alarmDescrString.
				Updated alarmEquipmentCTA description to include use of 0 as CTA for stand-alone devices."
			REVISION "200309091644Z"		-- September 09, 2003 at 16:44 GMT
			DESCRIPTION
				"1.0.0.1
				Added alarmTrapCounter to alarmTrap definition.
				Added alarmID to alarm table.
				Replaced UTCTime with standard DateAndTime.
				Removed UTCTime textual convention.
				"
			REVISION "200308061545Z"		-- August 06, 2003 at 15:45 GMT
			DESCRIPTION
				"1.0.0.0
				Created."
			::= { wirelessInnovations 1 }
		
	
--
-- Textual conventions
--
	
		AlarmDescrString ::= TEXTUAL-CONVENTION
			STATUS current
			DESCRIPTION 
				"An octet string containing alarm description
				information in human-readable form."
			SYNTAX OCTET STRING (SIZE (0..128))
			
		Version ::= TEXTUAL-CONVENTION
			STATUS current
			DESCRIPTION 
				"Hierarchical nested major and minor version, release, and build identification.
				Syntax: '<major>.<minor>.<release>.<build>' or empty string.
				        Each part has 1 up to 3 digits (0-9), '.<build>' at the end is optional.
				Example: 1.0.5.328"
			SYNTAX OCTET STRING (SIZE (0 | 5..15))
			
		IPAddressAndPort ::= TEXTUAL-CONVENTION
			STATUS current
			DESCRIPTION 
				"An IP address with up to 21 characters in the format a.b.c.d:port, e.g. 192.168.1.2:164.
				If the port is omitted, then the colon must also be omitted.
				
				Note!
				In future versions this may be extended to support IPv6 addresses 
				(2001:0db8:85a3:08d3:1319:8a2e:0370:7344) and DNS names (testhost.testcompany.com). 
				Then this TC will change to an octet string without size range (or just an upper limit)."
			SYNTAX OCTET STRING (SIZE (7..21))
			
		SpecificProblem ::= TEXTUAL-CONVENTION
			STATUS current
			DESCRIPTION 
				"Specific Problem is defined in accordance with definitions 
				given in ITU-T Recommendation X.733 clause 8.1.2.2.
				
				The list of Specific Problem codes for Wireless Innovations Products
				is maintained in Buchdorf."
			SYNTAX Unsigned32 (0..65535)
			
		Severity ::= TEXTUAL-CONVENTION
			STATUS current
			DESCRIPTION 
				"According to X733 and common alarm list:
				0=indeterminate
				1=critical
				2=major
				3=minor
				4=warning
				5=cleared
				6=information"
			SYNTAX INTEGER
				{
				indeterminate(0),
				critical(1),
				major(2),
				minor(3),
				warning(4),
				cleared(5),
				information(6)
				}
			
		EventType ::= TEXTUAL-CONVENTION
			STATUS current
			DESCRIPTION 
				"The event type of an alarm. See also: 
				- ISO/IEC 10164-4, chapter 8.1.1
				- ISO/IEC 10165-2, chapter 14.2"
			SYNTAX INTEGER
				{
				communications(1),
				qualityOfService(2),
				processingError(3),
				equipment(4),
				environmental(5)
				}
			
		ProbableCause ::= TEXTUAL-CONVENTION
			STATUS current
			DESCRIPTION 
				"See ISO/IEC 10164-4, chapter 8.1.2.1"
			SYNTAX INTEGER
				{
				unknown(0),
				adapterError(1),
				applicationSubsystemFailure(2),
				bandwidthReduced(3),
				callEstablishmentError(4),
				communicationsProtocolError(5),
				communicationsSubsystemFailure(6),
				configurationOrCustomizationError(7),
				congestion(8),
				corruptData(9),
				cpuCyclesLimitExceeded(10),
				dTEDCEInterfaceError(11),
				dataSetOrModemError(12),
				degradedSignal(13),
				enclosureDoorOpen(14),
				equipmentMalfunction(15),
				excessiveVibration(16),
				fileError(17),
				fireDetected(18),
				floodDetected(19),
				framingError(20),
				heatingOrVentilationOrCoolingSystemProblem(21),
				humidityUnacceptable(22),
				inputOutputDeviceError(23),
				inputDeviceError(24),
				lANError(25),
				leakDetected(26),
				localNodeTransmissionError(27),
				lossOfFrame(28),
				lossOfSignal(29),
				materialSupplyExhausted(30),
				multiplexerProblem(31),
				outOfMemory(32),
				outputDeviceError(33),
				performanceDegraded(34),
				powerProblem(35),
				pressureUnacceptable(36),
				processorProblem(37),
				pumpFailure(38),
				queueSizeExceeded(39),
				receiveFailure(40),
				receiverFailure(41),
				remoteNodeTransmissionError(42),
				resourceAtOrNearingCapacity(43),
				responseTimeExcessive(44),
				retransmissionRateExcessive(45),
				softwareError(46),
				softwareProgramAbnormallyTerminated(47),
				softwareProgramError(48),
				storageCapacityProblem(49),
				temperatureUnacceptable(50),
				thresholdCrossed(51),
				timingProblem(52),
				toxicLeakDetected(53),
				transmitFailure(54),
				transmitterFailure(55),
				underlyingResourceUnavailable(56),
				versionMismatch(57),
				snmpTrapColdStart(100),
				snmpTrapWarmStart(101),
				snmpTrapLinkDown(102),
				snmpTrapLinkUp(103),
				snmpTrapAuthenticationFailure(104),
				snmpTrapEgpNeighborloss(105),
				snmpTrapEnterpriseSpecific(106),
				snmpTrapLinkUpDown(107)
				}
			
		CTA ::= TEXTUAL-CONVENTION
			STATUS current
			DESCRIPTION 
				"This is the Common Topology Address and is built in a hierarchical form:
				First_level_add, second_level_add, third_level_add,....
				Syntax is 
				<integer>.<integer>.<integer>.... 
				
				V1.2.2.0 extension:
				There are cases where there are multiple nodes using the same hierarchy levels.
				In order to distinguish between these nodes, additional parameters are needed.
				These optional parameters follow the final hierarchy level, beginning with a colon. 
				The parameter list is also colon-delimited.  The interpretation of these parameters is 
				defined through the alarmID-specific master database and is well known to both
				the agent and the manager.
				
				Extended syntax is
				<TopoAdr>{.<TopoAdr>}[{:<ParN>}]
				{enclosed in curly brackets means occurrence zero, one or more times}
				[enclosed in square brackets is optional]
				<TopoAdr>:
				CTA as already defined in previous versions. Allowed characters {'0'..'9'}
				<ParN>:
				Additional Parameter. Allowed characters {'0'..'9'}, minus sign '-', 'e', 'E' 
				and decimal point '.'
				This provides for integer and floating point parameters. If a <ParN> contains a
				'e', 'E' or '.' the manager has to do a string to float conversion of <ParN>
				otherwise <ParN> has to be converted from String to integer.
				
				V1.6.0.0 extension:
				- any FQDN (Fully Qualified Domain Name), SDN (System Distinguish Name) 
				  or similar may also be used as CTA
				- String Parameter may also be used as Additional Parameter
				Therefore allowed characters for <TopoAdr> and <ParN> introduced with V1.2.2.0 extension 
				are now any ASCII character.
				
				
				
				Example 1:
				First level=RS485 address (i.e. Midas master unit, or BCell subrack) 
				Second level= Midas remote unit, or BCell slot address in a subrack,
				Third level=..Midas NSO out of Midas remote unit or BCell remote unit attached to a slot..) 
				
				Example 2:
				Non-distributed system such as the NodeM would use 0 as its CTA.
				
				Example 3:
				CTA=0:2:1 -> NodeA alarm at RF slot 2, group 1
				
				Example 4:
				CTA=0:1 -> NodeA external alarm of the device plugged into input 1
				of the user-interface connector.
				
				Example 5:
				CTA=Rack1.Subrack2.Slot4 -> ION-U Slot 4 in Subrack 2 of Rack 1
				
				Example 6:
				CTA=SRMU128.RU3:1:2100MHz -> ION-M RU 3 of optical link 128, parameter 1 = 1, parameter 2 = '2100MHz' (as string)"
			SYNTAX OCTET STRING (SIZE (1..64))
			
		ConnectivityType ::= TEXTUAL-CONVENTION
			STATUS current
			DESCRIPTION 
				"Type of connection the agent is connected to the network.
				1=CSOD (Circuit Switched network, 'On Demand')
				2=CSAO (Circuit Switched network, 'Always On')
				3=PSOD (Packet Switched network, 'On Demand')
				4=PSAO (Packet Switched network, 'Always On')
				5=DCOD (circuit switched Direct Connection over serial line, 'On Demand')
				6=DCAO (circuit switched Direct Connection over serial line, 'Always On')
				7=SMS  (Short Message Service, this is always a 'On Demand' connection)
				8=LAN  (Local Area Network, this is always a 'Always On' connection)"
			SYNTAX INTEGER
				{
				csod(1),
				csao(2),
				psod(3),
				psao(4),
				dcod(5),
				dcao(6),
				sms(7),
				lan(8)
				}
			
		NetworkType ::= TEXTUAL-CONVENTION
			STATUS current
			DESCRIPTION 
				"Network type.
				1=CS  (Circuit Switched network)
				2=PS  (Packet Switched network)
				3=DC  (circuit switched Direct Connection over serial line)
				4=SMS (Short Message Service)
				5=LAN (Local Area Network)"
			SYNTAX INTEGER
				{
				cs(1),
				ps(2),
				dc(3),
				sms(4),
				lan(5)
				}
			
		ConnectionType ::= TEXTUAL-CONVENTION
			STATUS current
			DESCRIPTION 
				"Actual type of connection the agent is connected to the network.
				0= Not applicable for the network type
				1='On Demand'
				2='Always On'"
			SYNTAX INTEGER
				{
				notApplicable(0),
				onDemand(1),
				alwaysOn(2)
				}
			
		NotificationType ::= TEXTUAL-CONVENTION
			STATUS current
			DESCRIPTION 
				"Notification type used for outgoing notifications.
				1=SNMP trap
				2=SNMP inform"
			SYNTAX INTEGER
				{
				trap(1),
				inform(2)
				}
			
		Severity4Set ::= TEXTUAL-CONVENTION
			DISPLAY-HINT 
				"b"
			STATUS current
			DESCRIPTION 
				"Bitcoded value indication the supported alarm severity levels within a SET:
				Bit0=indeterminate (0x01)
				Bit1=critical      (0x02)
				Bit2=major         (0x04)
				Bit3=minor         (0x08)
				Bit4=warning       (0x10)
				Bit5=disable       (0x20)
				Bit6=information   (0x40)
				Bit7 not used, always not set"
			SYNTAX INTEGER (-128..127)
			
		PositiveIntegerButNotZero ::= TEXTUAL-CONVENTION
			STATUS current
			DESCRIPTION 
				"All integers > 0"
			SYNTAX Integer32 (1..2147483647)
			
		PositiveIntegerIncludingZero ::= TEXTUAL-CONVENTION
			STATUS current
			DESCRIPTION 
				"All integers >= 0"
			SYNTAX Integer32 (0..2147483647)
			
	
--
-- Node definitions
--
	
		-- 1.3.6.1.4.1.331.1.2.1.1
		commonDeviceObjects OBJECT-IDENTITY
			STATUS current
			DESCRIPTION 
				"Objects valid for common objects."
			::= { wirelessInnovationsProducts 1 }
		
		-- 1.3.6.1.4.1.331.1.2.1.1.1
		commonDeviceBasic OBJECT-IDENTITY
			STATUS current
			DESCRIPTION 
				"Basic information."
			::= { commonDeviceObjects 1 }
		
		-- 1.3.6.1.4.1.331.1.2.1.1.1.1
		basicAgentVersion OBJECT-TYPE
			SYNTAX Version
			MAX-ACCESS read-only
			STATUS current
			DESCRIPTION
				"This is the software version of the agent and is determined according
				to the software version control rules of the particular device."
			::= { commonDeviceBasic 1 }
		
		-- 1.3.6.1.4.1.331.1.2.1.1.1.2
		basicCurrentMibVersion OBJECT-TYPE
			SYNTAX Version
			MAX-ACCESS read-only
			STATUS current
			DESCRIPTION
				"This object denotes the current MIB's version.
				
				This value is built by the first line of the DESCRIPTION value of the 
				most recent REVISION statement of the current MIB's MODULE IDENTITY object.
				
				Please note, that this comment makes only sense if it is included and read 
				in the component specific MIB."
			::= { commonDeviceBasic 2 }
		
		-- 1.3.6.1.4.1.331.1.2.1.1.1.3
		basicWirelessInnovationsMibVersion OBJECT-TYPE
			SYNTAX Version
			MAX-ACCESS read-only
			STATUS current
			DESCRIPTION
				"The version of the WIRELESS-INNOVATIONS-PRODUCTS-MIB, which is included 
				in this (component specific) MIB.
				
				This value is the same as the first line of the DESCRIPTION value of the 
				most recent REVISION statement of the WIRELESS-INNOVATIONS-PRODUCTS-MIB's 
				MODULE IDENTITY object (wirelessInnovations)."
			::= { commonDeviceBasic 3 }
		
		-- 1.3.6.1.4.1.331.1.2.1.1.1.4
		basicCurrentTime OBJECT-TYPE
			SYNTAX DateAndTime
			MAX-ACCESS read-write
			STATUS current
			DESCRIPTION
				"Current time in Coordinated Universal Time (UTC) format."
			::= { commonDeviceBasic 4 }
		
		-- 1.3.6.1.4.1.331.1.2.1.1.1.5
		basicAgentIPAddress OBJECT-TYPE
			SYNTAX IPAddressAndPort
			MAX-ACCESS read-write
			STATUS obsolete
			DESCRIPTION
				"Note!
				This object is obsolete and no longer supported.
				New object is 'connManOrigAgentIPAddressCS'.
				
				
				This is the IP address of the DCM used in dial-in access.
				
				Since the DCM does not use a port number for the agent, setting
				the port has no affect.
				Setting this address to 0.0.0.0 causes the DCM to revert back
				to the default IP address."
			::= { commonDeviceBasic 5 }
		
		-- 1.3.6.1.4.1.331.1.2.1.1.1.6
		basicAgentIPAddressNew OBJECT-TYPE
			SYNTAX IPAddressAndPort
			MAX-ACCESS accessible-for-notify
			STATUS current
			DESCRIPTION
				"This OID is used in the changedIPAddressEvent only."
			::= { commonDeviceBasic 6 }
		
		-- 1.3.6.1.4.1.331.1.2.1.1.1.7
		basicAgentLocationIdentification OBJECT-TYPE
			SYNTAX OCTET STRING
			MAX-ACCESS read-only
			STATUS current
			DESCRIPTION
				"Geographic location identification of the Agent, either GPS coordinates or 
				the serving cell identification of the Agent's wireless modem (Location Area).
				If the Agent has a GPS receiver the GPS coordinates should be responded, otherwise the LA.
				If neither the GPS coordinates nor the LA is known to the Agent, an empty string should be responded.
				
				This location id is always a comma separated string.
				
				Syntax for GPS coordinates:
				'GPS,<latitude>,<longitude>'
				<latitude>: numeric value (decimal), positive value for north, negative for south, including a decimal point.
				            Allowed characters '-','0'..'9','.'
				<longitude>: numeric value (decimal), positive value for east, negative for west, including a decimal point.
				             Allowed characters '-','0'..'9','.'
				E.g. 'GPS,42.4088172912598,-71.1735153198242', 'GPS,-1.2,12.34'
				
				Syntax for LA:
				'LA,<mcc>,<mnc>,<lac>,<ci>'
				<mcc>: mobile country code, allowed characters '0'..'9'
				<mnc>: mobile network code, allowed characters '0'..'9'
				<lac>: location area code (decimal), allowed characters '0'..'9'
				<ci>: cell identity (decimal), allowed characters '0'..'9'
				If any value is unknown, it has to be left empty but the corresponding comma has to be provided.
				E.g. 'LA,123,12,67890,1234', 'LA,321,21,456,'
				"
			::= { commonDeviceBasic 7 }
		
		-- 1.3.6.1.4.1.331.1.2.1.1.1.8
		basicAgentLocationAlias OBJECT-TYPE
			SYNTAX OCTET STRING
			MAX-ACCESS read-only
			STATUS current
			DESCRIPTION
				"Alias name of the geographic location area (zone name) where the Agent is currently in. 
				If the Agent does not support geographic location identification, 
				an empty string should be responded."
			::= { commonDeviceBasic 8 }
		
		-- 1.3.6.1.4.1.331.1.2.1.1.1.9
		basicAgentOutOfOperationArea OBJECT-TYPE
			SYNTAX TruthValue
			MAX-ACCESS read-only
			STATUS current
			DESCRIPTION
				"Indicates whether the Agent is currently out of operation.
				This may be caused e.g. by geographical location change (moving out of active areas / active zones) or
				by entering any other inactive operating mode (standby).
				This object has also to be sent within the changedParameterEvent notification, so the manager is able 
				to track the operational state (availability status) of the Agent.
				The Manager has to consider that if this object is true, the Agent may not send any further 
				notifications/alarms and may not accessible via remote connection until the Agent comes back to operation.
				If the Agent does not support geographic location identification and any other inactive operation modes, 
				always false should be responded."
			::= { commonDeviceBasic 9 }
		
		-- 1.3.6.1.4.1.331.1.2.1.1.1.10
		basicAgentConditionChangedConfig OBJECT-TYPE
			SYNTAX INTEGER
				{
				userMaintenance(0),
				locationChange(1),
				locationLatency(2)
				}
			MAX-ACCESS accessible-for-notify
			STATUS current
			DESCRIPTION
				"This OID is used in the changedParameterEvent only.
				Indicates the condition why the changedParameterEvent was fired.
				
				0 = user maintenance via another user interface caused parameter changes.
				1 = location (zone) change caused immediate parameter changes.
				2 = location (zone) change caused parameter changes after latency expired (V1.6.0.0 extension).
				
				If the Agent does not support conditional configuration changes or the
				changedParameterEvent was fired because of user changes, 0 has to be used."
			::= { commonDeviceBasic 10 }
		
		-- 1.3.6.1.4.1.331.1.2.1.1.1.11
		basicGpsData OBJECT-IDENTITY
			STATUS current
			DESCRIPTION 
				"GPS data and related Objects.
				If the Agent doesn't support GPS data at all, always 'no such object' 
				has to be returned to any request within this section."
			::= { commonDeviceBasic 11 }
		
		-- 1.3.6.1.4.1.331.1.2.1.1.1.11.1
		gpsDataTimestamp OBJECT-TYPE
			SYNTAX DateAndTime
			MAX-ACCESS read-only
			STATUS current
			DESCRIPTION
				"Timestamp of GPS data set reported by GPS device."
			::= { basicGpsData 1 }
		
		-- 1.3.6.1.4.1.331.1.2.1.1.1.11.2
		gpsZoneName OBJECT-TYPE
			SYNTAX OCTET STRING
			MAX-ACCESS read-only
			STATUS current
			DESCRIPTION
				"Zone name related to GPS position (gpsLatitude/gpsLongitude) or empty string in 
				case the position is not within a zone.
				
				Note!
				In case the actual position reflects the crossing of a common border of two zones 
				(one zone left, other zone entered), the zone name of the entered zone is used here."
			::= { basicGpsData 2 }
		
		-- 1.3.6.1.4.1.331.1.2.1.1.1.11.3
		gpsLatitude OBJECT-TYPE
			SYNTAX OCTET STRING
			MAX-ACCESS read-only
			STATUS current
			DESCRIPTION
				"Position latitude.
				Numeric value (decimal), positive value for north, negative for south, including a decimal point.
				Allowed characters '-','0'..'9','.'"
			::= { basicGpsData 3 }
		
		-- 1.3.6.1.4.1.331.1.2.1.1.1.11.4
		gpsLongitude OBJECT-TYPE
			SYNTAX OCTET STRING
			MAX-ACCESS read-only
			STATUS current
			DESCRIPTION
				"Position longitude.
				Numeric value (decimal), positive value for east, negative for west, including a decimal point.
				Allowed characters '-','0'..'9','.'"
			::= { basicGpsData 4 }
		
		-- 1.3.6.1.4.1.331.1.2.1.1.1.11.5
		gpsSpeed OBJECT-TYPE
			SYNTAX OCTET STRING
			MAX-ACCESS read-only
			STATUS current
			DESCRIPTION
				"Speed in km/h.
				Numeric value (decimal) including a decimal point.
				Allowed characters '0'..'9','.'"
			::= { basicGpsData 5 }
		
		-- 1.3.6.1.4.1.331.1.2.1.1.1.11.6
		gpsBearingDegree OBJECT-TYPE
			SYNTAX OCTET STRING
			MAX-ACCESS read-only
			STATUS current
			DESCRIPTION
				"Direction in relation to north in degree.
				Numeric value (decimal) including a decimal point.
				Allowed characters '0'..'9','.'"
			::= { basicGpsData 6 }
		
		-- 1.3.6.1.4.1.331.1.2.1.1.1.11.7
		gpsAltitude OBJECT-TYPE
			SYNTAX OCTET STRING
			MAX-ACCESS read-only
			STATUS current
			DESCRIPTION
				"Position altitude or empty string in case altitude is not available.
				Numeric value (decimal) including a decimal point.
				Allowed characters '0'..'9','.'"
			::= { basicGpsData 7 }
		
		-- 1.3.6.1.4.1.331.1.2.1.1.1.11.8
		gpsNoOfSatellites OBJECT-TYPE
			SYNTAX Integer32
			MAX-ACCESS read-only
			STATUS current
			DESCRIPTION
				"Number of used satellites (decimal)."
			::= { basicGpsData 8 }
		
		-- 1.3.6.1.4.1.331.1.2.1.1.1.11.50
		gpsEventData OBJECT-IDENTITY
			STATUS current
			DESCRIPTION 
				"Additional GPS event data."
			::= { basicGpsData 50 }
		
		-- 1.3.6.1.4.1.331.1.2.1.1.1.11.50.1
		gpsEventType OBJECT-TYPE
			SYNTAX INTEGER
				{
				startMovingDetected(1),
				stopMovingDetected(2),
				gpsZoneEntering(3),
				gpsZoneLeaving(4),
				gpsHeartbeat(5)
				}
			MAX-ACCESS accessible-for-notify
			STATUS current
			DESCRIPTION
				"GPS event type.
				1 = Agent has detected start moving
				2 = Agent has detected stop moving
				3 = Agent has entered a GPS zone
				4 = Agent has left a GPS zone
				5 = GPS event heartbeat
				
				Note!
				In case the actual position reflects the crossing of a common border of two zones 
				(one zone left, other zone entered), only the entering of the new zone is indicated."
			::= { gpsEventData 1 }
		
		-- 1.3.6.1.4.1.331.1.2.1.1.1.11.50.2
		gpsEventTime OBJECT-TYPE
			SYNTAX DateAndTime
			MAX-ACCESS accessible-for-notify
			STATUS current
			DESCRIPTION
				"GPS event generation time in Coordinated Universal Time (UTC) format."
			::= { gpsEventData 2 }
		
		-- 1.3.6.1.4.1.331.1.2.1.1.1.11.50.3
		gpsEvent NOTIFICATION-TYPE
			OBJECTS { sysName, connAgentUID, connAgentUID2, gpsEventType, gpsEventTime, 
				gpsDataTimestamp, gpsZoneName, gpsLatitude, gpsLongitude, gpsSpeed, 
				gpsBearingDegree, gpsAltitude, gpsNoOfSatellites }
			STATUS current
			DESCRIPTION 
				"Notification sent by the agent to indicate the occurrence of any type of GPS event (see gpsEventType)."
			::= { gpsEventData 3 }
		
		-- 1.3.6.1.4.1.331.1.2.1.1.1.11.51
		gpsEventConfiguration OBJECT-IDENTITY
			STATUS current
			DESCRIPTION 
				"Additional GPS event configuration data."
			::= { basicGpsData 51 }
		
		-- 1.3.6.1.4.1.331.1.2.1.1.1.11.51.1
		gpsEventEnabled OBJECT-TYPE
			SYNTAX TruthValue
			MAX-ACCESS read-write
			STATUS current
			DESCRIPTION
				"Object that shows resp. controls whether the GPS event notification is enabled or not."
			::= { gpsEventConfiguration 1 }
		
		-- 1.3.6.1.4.1.331.1.2.1.1.1.11.51.2
		gpsEventDestinationIsAlarmRecipient OBJECT-TYPE
			SYNTAX TruthValue
			MAX-ACCESS read-write
			STATUS current
			DESCRIPTION
				"Object that shows resp. controls whether the GPS event notification destination is the 
				standard notification destination (true: destination is alarmRecipient) or not (false: 
				destination is gpsEventDestination)."
			::= { gpsEventConfiguration 2 }
		
		-- 1.3.6.1.4.1.331.1.2.1.1.1.11.51.3
		gpsEventDestination OBJECT-TYPE
			SYNTAX IPAddressAndPort
			MAX-ACCESS read-write
			STATUS current
			DESCRIPTION
				"Object that shows resp. controls the destination of the GPS event notification. 
				Setting the IP address to 0.0.0.0 will also have the effect of disabling the notification
				forwarding (like setting gpsEventEnabled to false).
				
				Note!
				In case gpsEventDestinationIsAlarmRecipient is true, this object is just read-only and 
				reflects the alarmRecipient object setting. Then a SET request on this object will fail 
				with an appropriate error."
			::= { gpsEventConfiguration 3 }
		
		-- 1.3.6.1.4.1.331.1.2.1.1.1.11.51.4
		gpsHeartbeatInterval OBJECT-TYPE
			SYNTAX Gauge32
			MAX-ACCESS read-write
			STATUS current
			DESCRIPTION
				"Object that shows resp. controls the GPS event heartbeat interval (in minutes).
				
				Set this object to 0 in order to disable the GPS event of type heartbeat. 
				Set this object to any value but 0 in order to enable the GPS event heartbeat notification.
				
				Default value is 0.
				Allowed range is 0 to 6000 minutes (or 0 to 100 hours)."
			::= { gpsEventConfiguration 4 }
		
		-- 1.3.6.1.4.1.331.1.2.1.1.2
		commonDeviceAlarm OBJECT-IDENTITY
			STATUS current
			DESCRIPTION 
				"Alarm objects."
			::= { commonDeviceObjects 2 }
		
		-- 1.3.6.1.4.1.331.1.2.1.1.2.1
		alarmRecipient OBJECT-TYPE
			SYNTAX IPAddressAndPort
			MAX-ACCESS read-write
			STATUS current
			DESCRIPTION
				"The recipient of all notifications. 
				This IP address can be changed in order to switch the recipient to another (auxiliary) 
				recipient.  It can be useful if the OMC must be switched off for maintenance or other 
				purpose.
				NOTE: Setting the IP address to 0.0.0.0 will have the effect of disabling notification
				forwarding.
				"
			::= { commonDeviceAlarm 1 }
		
		-- 1.3.6.1.4.1.331.1.2.1.1.2.2
		alarmForwardingEnabled OBJECT-TYPE
			SYNTAX TruthValue
			MAX-ACCESS read-write
			STATUS current
			DESCRIPTION
				"Set this value to true(1) in order to enable alarm forwarding. Note, that 
				the alarm recipients IP address has to be set to alarmRecipient prior to 
				enable alarm forwarding. 
				Set this value to false(2) in order to disable alarm forwarding."
			::= { commonDeviceAlarm 2 }
		
		-- 1.3.6.1.4.1.331.1.2.1.1.2.3
		alarmHeartbeatInterval OBJECT-TYPE
			SYNTAX Gauge32 (0..6000)
			MAX-ACCESS read-write
			STATUS current
			DESCRIPTION
				"The heartbeat mechanism is an alternative to OMC polling. 
				A heartbeatEvent notification is sent by the agent to indicate that the device 
				and the connection are still active. 
				Set this object to 0 in order to disable the heartbeat. 
				Set this object to any value but 0 in order to enable the heartbeatEvent notification.
				The value set determines the interval of the heartbeatEvents in minutes.
				Default value is 0.
				Allowed range is 0 to 6000 minutes (or 0 to 100 hours)."
			::= { commonDeviceAlarm 3 }
		
		-- 1.3.6.1.4.1.331.1.2.1.1.2.4
		alarmSynchronize OBJECT-TYPE
			SYNTAX TruthValue
			MAX-ACCESS read-write
			STATUS current
			DESCRIPTION
				"This object must be set to true(1) in order to force the agent to resend 
				all active alarms to the current manager.
				Setting this object to false(2) has no effect.
				
				On GET requests always false(2) is returned."
			::= { commonDeviceAlarm 4 }
		
		-- 1.3.6.1.4.1.331.1.2.1.1.2.5
		alarmTrapCounter OBJECT-TYPE
			SYNTAX Counter32
			MAX-ACCESS read-only
			STATUS current
			DESCRIPTION
				"This is the counter indicating how many total notifications
				have been sent from the device since last bootup (or reboot).
				The counter is included in every private/enterprise notification.
				
				The counter starts at 0 on system bootup (or reboot).
				Upon wrapping, the counter starts at 1, not 0.
				Since the standard notifications ColdStart and WarmStart will be implemented, 
				any boot (or reboot) sequence will trigger the following notification sequence:
				1. ColdStart/WarmStart notification.
				1a changedIPAddressEvent  with counter = 0 if IP address has been changed during agent downtime.
				1b swActivationProgress   with counter + 1 resp. counter = 0 (depending on 1a was fired or not) 
				                                           if agent startup has triggert the activation of a new software package.
				                                           Note: This is an optional notification, it depends on the agent 
				                                           implementation whether he is able to detect that the startup was 
				                                           triggert by the activation of a new software package or not.
				2. agentUpAndRunningEvent with counter + 1 resp. counter = 0 (depending on 1a/1b was fired or not) 
				                                           if agent is finally up and running.
				2a HeartBeat notification with counter + 1 if HeartBeat enabled.
				3. alarm/other notifications with counter + 1 according to alarm/other conditions detected
				   once the agent starts operating."
			::= { commonDeviceAlarm 5 }
		
		-- 1.3.6.1.4.1.331.1.2.1.1.2.6
		alarmTable OBJECT-TYPE
			SYNTAX SEQUENCE OF AlarmEntry
			MAX-ACCESS not-accessible
			STATUS current
			DESCRIPTION
				"The alarm table lists all the alarms currently active into the equipment.
				An entry is added to the table anytime an alarm condition raises. 
				An entry is removed from the table according to the following conditions:
				1. the alarm condition ceases (e.g. door open-->door closed). Any Manager GET/GETbulk
				shall leave the table unaffected
				2. the alarm condition is a lacthed-type (e.g. configuration error) and no clear 
				events is possible, therefore the only way to remove the entry from the list is to 
				clear automatically after a GET/GETbulk from the manager. This kind of alarms 
				will always be assigned a severity level 'information (6)'
				
				
				
				 
				"
			::= { commonDeviceAlarm 6 }
		
		-- 1.3.6.1.4.1.331.1.2.1.1.2.6.1
		alarmEntry OBJECT-TYPE
			SYNTAX AlarmEntry
			MAX-ACCESS not-accessible
			STATUS current
			DESCRIPTION
				"Alarm table entry."
			INDEX { alarmIDX }
			::= { alarmTable 1 }
		
		AlarmEntry ::=
			SEQUENCE { 
				alarmIDX
					Unsigned32,
				alarmID
					Integer32,
				alarmSpecificProblem
					SpecificProblem,
				alarmPerceivedSeverity
					Severity,
				alarmEventDateTime
					DateAndTime,
				alarmEventType
					EventType,
				alarmProbableCause
					ProbableCause,
				alarmAdditionalText
					AlarmDescrString,
				alarmEquipmentCTA
					CTA,
				alarmPhysicalIndex
					PhysicalIndex,
				alarmEquipmentPointer
					VariablePointer
			 }

		-- 1.3.6.1.4.1.331.1.2.1.1.2.6.1.1
		alarmIDX OBJECT-TYPE
			SYNTAX Unsigned32
			MAX-ACCESS not-accessible
			STATUS current
			DESCRIPTION
				"Table index to identify the instance."
			::= { alarmEntry 1 }
		
		-- 1.3.6.1.4.1.331.1.2.1.1.2.6.1.2
		alarmID OBJECT-TYPE
			SYNTAX Integer32 (1..100000)
			MAX-ACCESS read-only
			STATUS current
			DESCRIPTION
				"This is the most generic identifier of the problem."
			::= { alarmEntry 2 }
		
		-- 1.3.6.1.4.1.331.1.2.1.1.2.6.1.3
		alarmSpecificProblem OBJECT-TYPE
			SYNTAX SpecificProblem
			MAX-ACCESS read-only
			STATUS current
			DESCRIPTION
				"X733 compliance: specific problem unique code,according to a common alarm list.
				This unique list will be maintained at a central location."
			::= { alarmEntry 3 }
		
		-- 1.3.6.1.4.1.331.1.2.1.1.2.6.1.4
		alarmPerceivedSeverity OBJECT-TYPE
			SYNTAX Severity
			MAX-ACCESS read-only
			STATUS current
			DESCRIPTION
				"According to X733 and common alarm list:
				0=indeterminate
				1=critical
				2=major
				3=minor
				4=warning
				5=cleared
				6=information"
			::= { alarmEntry 4 }
		
		-- 1.3.6.1.4.1.331.1.2.1.1.2.6.1.5
		alarmEventDateTime OBJECT-TYPE
			SYNTAX DateAndTime
			MAX-ACCESS read-only
			STATUS current
			DESCRIPTION
				"X733 compatibility: time stamp for alarm condition change
				changes can occur on severity level (including set and clear)
				"
			::= { alarmEntry 5 }
		
		-- 1.3.6.1.4.1.331.1.2.1.1.2.6.1.6
		alarmEventType OBJECT-TYPE
			SYNTAX EventType
			MAX-ACCESS read-only
			STATUS current
			DESCRIPTION
				"According to X733 and common alarm list:The Event Type categorises the alarm."
			::= { alarmEntry 6 }
		
		-- 1.3.6.1.4.1.331.1.2.1.1.2.6.1.7
		alarmProbableCause OBJECT-TYPE
			SYNTAX ProbableCause
			MAX-ACCESS read-only
			STATUS current
			DESCRIPTION
				"According to X733 and common alarm list:The Probable Cause defines further qualification of an alarm."
			::= { alarmEntry 7 }
		
		-- 1.3.6.1.4.1.331.1.2.1.1.2.6.1.8
		alarmAdditionalText OBJECT-TYPE
			SYNTAX AlarmDescrString
			MAX-ACCESS read-only
			STATUS current
			DESCRIPTION
				"According to X733 and common alarm list: The Additional Text allows a 
				free form text description to be reported. It contains a formatted 
				description of the alarm.
				
				If additional information regarding the alarm is unknown, a zero-length
				string may be used.  Otherwise, no string over 128 bytes may be sent."
			::= { alarmEntry 8 }
		
		-- 1.3.6.1.4.1.331.1.2.1.1.2.6.1.9
		alarmEquipmentCTA OBJECT-TYPE
			SYNTAX CTA
			MAX-ACCESS read-only
			STATUS current
			DESCRIPTION
				"Must be a Common Topology Address (CTA)
				This represents the topological address of the equipment below the Agent
				and references the alarm source.
				It may also contain optional parameters, details see textual convention CTA."
			::= { alarmEntry 9 }
		
		-- 1.3.6.1.4.1.331.1.2.1.1.2.6.1.10
		alarmPhysicalIndex OBJECT-TYPE
			SYNTAX PhysicalIndex
			MAX-ACCESS read-only
			STATUS current
			DESCRIPTION
				"This objects carries the value of entPhysicalIndex of the affected component."
			::= { alarmEntry 10 }
		
		-- 1.3.6.1.4.1.331.1.2.1.1.2.6.1.11
		alarmEquipmentPointer OBJECT-TYPE
			SYNTAX VariablePointer
			MAX-ACCESS read-only
			STATUS current
			DESCRIPTION
				"The purpose of this object is to provide a pointer (OID) into the component
				specific MIB that relates most directly to this particular alarm.  If this
				alarm is best described by multiple objects in the component specific MIB,
				the object should be closest common OID.
				
				An example would be a MMR remote unit instance that is coded in a table of MMR 
				instances.
				"
			::= { alarmEntry 11 }
		
		-- 1.3.6.1.4.1.331.1.2.1.1.2.7
		alarmChangedParameterPointer OBJECT-TYPE
			SYNTAX VariablePointer
			MAX-ACCESS accessible-for-notify
			STATUS current
			DESCRIPTION
				"This OID is used in the changedParameterEvent only. It is a pointer to a 
				component-specific object, whose parameter was changed. It points to the 
				highest part of the tree where changes where made. That is, the manager is 
				required to perform a WALK on this OID in order to get the current settings."
			::= { commonDeviceAlarm 7 }
		
		-- 1.3.6.1.4.1.331.1.2.1.1.2.8
		alarmSeveritiesSupported4Set OBJECT-TYPE
			SYNTAX Severity4Set
			MAX-ACCESS read-only
			STATUS current
			DESCRIPTION
				"Bitcoded value indication the supported alarm severity levels within a SET
				via the alarmConfigTable:
				Bit0=indeterminate (0x01)
				Bit1=critical      (0x02)
				Bit2=major         (0x04)
				Bit3=minor         (0x08)
				Bit4=warning       (0x10)
				Bit5=disable       (0x20)
				Bit6=information   (0x40)
				Bit7 not used, always not set
				
				E.g:
				00111110 (0x3E, 62): critical, major, minor, warning and disable supported.
				0: setting/changing alarm severity levels not supported at all."
			::= { commonDeviceAlarm 8 }
		
		-- 1.3.6.1.4.1.331.1.2.1.1.2.9
		alarmConfigTable OBJECT-TYPE
			SYNTAX SEQUENCE OF AlarmConfigEntry
			MAX-ACCESS not-accessible
			STATUS obsolete
			DESCRIPTION
				"Agent alarm configuration table. This table lists all alarms supported by the agent.
				It is used to read resp. change default alarm parameter settings.
				This settings apply system-wide, even in distributed systems for every CTA."
			::= { commonDeviceAlarm 9 }
		
		-- 1.3.6.1.4.1.331.1.2.1.1.2.9.1
		alarmConfigEntry OBJECT-TYPE
			SYNTAX AlarmConfigEntry
			MAX-ACCESS not-accessible
			STATUS obsolete
			DESCRIPTION
				"Alarm configuration table entry."
			INDEX { alarmConfig4alarmID }
			::= { alarmConfigTable 1 }
		
		AlarmConfigEntry ::=
			SEQUENCE { 
				alarmConfig4alarmID
					Integer32,
				alarmConfigSeverity
					Severity
			 }

		-- 1.3.6.1.4.1.331.1.2.1.1.2.9.1.1
		alarmConfig4alarmID OBJECT-TYPE
			SYNTAX Integer32 (1..100000)
			MAX-ACCESS read-only
			STATUS obsolete
			DESCRIPTION
				"Referenced alarm ID: This is the most generic identifier of the alarm."
			::= { alarmConfigEntry 1 }
		
		-- 1.3.6.1.4.1.331.1.2.1.1.2.9.1.2
		alarmConfigSeverity OBJECT-TYPE
			SYNTAX Severity
			MAX-ACCESS read-write
			STATUS obsolete
			DESCRIPTION
				"Reading this object indicates the current level the alarm is set at.
				Setting this object changes the current level accordingly.
				Note!
				Severity 5=cleared in this context indicates that the alarm is disabled/to be disabled.
				Setting this object to any other level than supported (indicated by alarmSeveritiesSupported4Set)
				is not valid and results in a return of wrongValue."
			::= { alarmConfigEntry 2 }
		
		-- 1.3.6.1.4.1.331.1.2.1.1.2.10
		alarmUsertextTable OBJECT-TYPE
			SYNTAX SEQUENCE OF AlarmUsertextEntry
			MAX-ACCESS not-accessible
			STATUS obsolete
			DESCRIPTION
				"Agent alarm user text configuration table. This table lists all alarms that support 
				user defined text.
				It is used to read resp. change default alarm user text settings.
				This settings specific for every CTA within a distributed system."
			::= { commonDeviceAlarm 10 }
		
		-- 1.3.6.1.4.1.331.1.2.1.1.2.10.1
		alarmUsertextEntry OBJECT-TYPE
			SYNTAX AlarmUsertextEntry
			MAX-ACCESS not-accessible
			STATUS obsolete
			DESCRIPTION
				"Alarm user text configuration table entry."
			INDEX { alarmUsertext4CTA, alarmUsertext4alarmID }
			::= { alarmUsertextTable 1 }
		
		AlarmUsertextEntry ::=
			SEQUENCE { 
				alarmUsertext4CTA
					CTA,
				alarmUsertext4alarmID
					Integer32,
				alarmUsertext
					OCTET STRING
			 }

		-- 1.3.6.1.4.1.331.1.2.1.1.2.10.1.1
		alarmUsertext4CTA OBJECT-TYPE
			SYNTAX CTA
			MAX-ACCESS read-only
			STATUS obsolete
			DESCRIPTION
				"Referenced Common Topology Address.
				It may also contain optional parameters, details see textual convention CTA."
			::= { alarmUsertextEntry 1 }
		
		-- 1.3.6.1.4.1.331.1.2.1.1.2.10.1.2
		alarmUsertext4alarmID OBJECT-TYPE
			SYNTAX Integer32 (1..100000)
			MAX-ACCESS read-only
			STATUS obsolete
			DESCRIPTION
				"Referenced alarm ID: This is the most generic identifier of the alarm."
			::= { alarmUsertextEntry 2 }
		
		-- 1.3.6.1.4.1.331.1.2.1.1.2.10.1.3
		alarmUsertext OBJECT-TYPE
			SYNTAX OCTET STRING (SIZE (0..20))
			MAX-ACCESS read-write
			STATUS obsolete
			DESCRIPTION
				"User defined text for referenced alarmID at referenced CTA."
			::= { alarmUsertextEntry 3 }
		
		-- 1.3.6.1.4.1.331.1.2.1.1.2.11
		alarmThresholds OBJECT-IDENTITY
			STATUS current
			DESCRIPTION 
				"With this section alarm thresholds are handled. If the agent doesn't support
				alarm threshold management at all, always 'no such object' has to be returned 
				to any request within this section."
			::= { commonDeviceAlarm 11 }
		
		-- 1.3.6.1.4.1.331.1.2.1.1.2.11.1
		alarmThresholdTable OBJECT-TYPE
			SYNTAX SEQUENCE OF AlarmThresholdEntry
			MAX-ACCESS not-accessible
			STATUS current
			DESCRIPTION
				"This table provides threshold information for each alarm that has
				user-defined thresholds.  
				
				Thresholds can be thought of as single or ranged.  A single threshold
				is one in which an alarm is generated if a measurement falls below or
				rises above the threshold.  For example, if we have a temperature
				threshold of 50 C, any temperature above this threshold will generate
				an alarm.  A range in this case is not needed.  However, common sense
				dictates that a value which cannot be represented by the hardware should
				not be used in a SET, so an upper range (or lower as the case may be)
				is still implied.
				
				The settings in this table are specific for every CTA within a distributed 
				system.  They are also specific to a particular alarm type, represented
				by the alarm ID.  Since there may be as many as two thresholds for an
				alarm (minimum and maximum), this must be accounted for also.  Therefore,
				this table is indexed by the following:
				
				  - alarmThreshold4CTA
				  - alarmThresholdalarmID
				  - alarmThresholdIdx
				
				If not applicable to a particular agent implementation, 'no such object' must be 
				returned to any request within this table.
				
				All alarms with a single threshold or simple linear ranged threshold can be 
				completely described by the few basic objects in this table and the network manager 
				can easily set up these thresholds properly. In this case, 
				alarmThresholdPointerToValueLookupTableMainIndex is set to 0.  For example, 
				NodeX DL and UL RSSI alarms fall into this category.
				
				For alarms with more complex threshold ranges or whose set values cannot 
				describe them, the object, alarmThresholdPointerToValueLookupTableMainIndex
				points into alarmThresholdValueLookupTable where each allowed value is defined
				and described.  These alarms include NodeX VSWR ratios, external alarm polarity, etc."
			::= { alarmThresholds 1 }
		
		-- 1.3.6.1.4.1.331.1.2.1.1.2.11.1.1
		alarmThresholdEntry OBJECT-TYPE
			SYNTAX AlarmThresholdEntry
			MAX-ACCESS not-accessible
			STATUS current
			DESCRIPTION
				"Alarm threshold configuration table entry."
			INDEX { alarmThreshold4CTA, alarmThreshold4alarmID, alarmThresholdIdx }
			::= { alarmThresholdTable 1 }
		
		AlarmThresholdEntry ::=
			SEQUENCE { 
				alarmThreshold4CTA
					CTA,
				alarmThreshold4alarmID
					Integer32,
				alarmThresholdIdx
					INTEGER,
				alarmThresholdDescription
					OCTET STRING,
				alarmThresholdUnit
					OCTET STRING,
				alarmThresholdScale
					Integer32,
				alarmThresholdStepValue
					Integer32,
				alarmThresholdMinValueAllowed
					Integer32,
				alarmThresholdMaxValueAllowed
					Integer32,
				alarmThresholdActValue
					Integer32,
				alarmThresholdPointerToValueLookupTableMainIndex
					PositiveIntegerIncludingZero
			 }

		-- 1.3.6.1.4.1.331.1.2.1.1.2.11.1.1.1
		alarmThreshold4CTA OBJECT-TYPE
			SYNTAX CTA
			MAX-ACCESS read-only
			STATUS current
			DESCRIPTION
				"1st table index. Referenced Common Topology Address.
				In distributed systems the threshold for the same alarm may be configured 
				different depending on the topology address of the alarm source.
				It may also contain optional parameters, details see textual convention CTA."
			::= { alarmThresholdEntry 1 }
		
		-- 1.3.6.1.4.1.331.1.2.1.1.2.11.1.1.2
		alarmThreshold4alarmID OBJECT-TYPE
			SYNTAX Integer32 (1..100000)
			MAX-ACCESS read-only
			STATUS current
			DESCRIPTION
				"2nd table index. Referenced alarm ID: This is the most generic identifier of the alarm."
			::= { alarmThresholdEntry 2 }
		
		-- 1.3.6.1.4.1.331.1.2.1.1.2.11.1.1.3
		alarmThresholdIdx OBJECT-TYPE
			SYNTAX INTEGER (1..2)
			MAX-ACCESS read-only
			STATUS current
			DESCRIPTION
				"Some alarms have just a single threshold, others have a minimum and a maximum threshold.
				This index identifies whether this is a single, minimum, or maximum threshold.
				
				Possible values:
				1 - single or minimum threshold
				2 - maximum threshold"
			::= { alarmThresholdEntry 3 }
		
		-- 1.3.6.1.4.1.331.1.2.1.1.2.11.1.1.4
		alarmThresholdDescription OBJECT-TYPE
			SYNTAX OCTET STRING
			MAX-ACCESS read-only
			STATUS current
			DESCRIPTION
				"Textual description of the referenced threshold entry."
			::= { alarmThresholdEntry 4 }
		
		-- 1.3.6.1.4.1.331.1.2.1.1.2.11.1.1.5
		alarmThresholdUnit OBJECT-TYPE
			SYNTAX OCTET STRING
			MAX-ACCESS read-only
			STATUS current
			DESCRIPTION
				"Unit of the referenced threshold entry.
				E.g. dB, dBm, Hz, ... or empty string."
			::= { alarmThresholdEntry 5 }
		
		-- 1.3.6.1.4.1.331.1.2.1.1.2.11.1.1.6
		alarmThresholdScale OBJECT-TYPE
			SYNTAX Integer32
			MAX-ACCESS read-only
			STATUS current
			DESCRIPTION
				"This is the scale factor for the referenced threshold entry and only
				applies to simple thresholds.  The value should be 0 in the case of
				a complex threshold.  Otherwise, this number is a base 10 exponent 
				value.
				
				It applies to the following values:
				- alarmThresholdStepValue
				- alarmThresholdMinValueAllowed
				- alarmThresholdMaxValueAllowed
				- alarmThresholdActValue
				All these values are multiplied with alarmThresholdScale power of 10.
				
				E.g.alarmThresholdActValue is 125 and alarmThresholdScale is -1 
				==> real actual value is 12.5"
			::= { alarmThresholdEntry 6 }
		
		-- 1.3.6.1.4.1.331.1.2.1.1.2.11.1.1.7
		alarmThresholdStepValue OBJECT-TYPE
			SYNTAX Integer32
			MAX-ACCESS read-only
			STATUS current
			DESCRIPTION
				"This object only applies to simple thresholds.  It is used to 
				identify the discrete  intermediate values of the complete 
				threshold range from alarmThresholdMinValueAllowed to 
				alarmThresholdMaxValueAllowed.
				
				In the case of complex thresholds, the value should be 0."
			::= { alarmThresholdEntry 7 }
		
		-- 1.3.6.1.4.1.331.1.2.1.1.2.11.1.1.8
		alarmThresholdMinValueAllowed OBJECT-TYPE
			SYNTAX Integer32
			MAX-ACCESS read-only
			STATUS current
			DESCRIPTION
				"Possible values:
				
				Simple thresholds with defined ranges: 
				  This is the allowed minimum value of the threshold range.
				
				Single minimum thresholds: 
				  This is the value the entity should not fall below.
				
				Single maximum thresholds and complex thresholds: 
				  This value should be 0."
			::= { alarmThresholdEntry 8 }
		
		-- 1.3.6.1.4.1.331.1.2.1.1.2.11.1.1.9
		alarmThresholdMaxValueAllowed OBJECT-TYPE
			SYNTAX Integer32
			MAX-ACCESS read-only
			STATUS current
			DESCRIPTION
				"Possible values:
				
				Simple thresholds with defined ranges: 
				  This is the allowed maximum value of the threshold range.
				
				Single maximum thresholds: 
				  This is the value the entity should not rise above.
				
				Single minimum thresholds and complex thresholds: 
				  This value should be 0."
			::= { alarmThresholdEntry 9 }
		
		-- 1.3.6.1.4.1.331.1.2.1.1.2.11.1.1.10
		alarmThresholdActValue OBJECT-TYPE
			SYNTAX Integer32
			MAX-ACCESS read-write
			STATUS current
			DESCRIPTION
				"This is the actual value of the referenced threshold entry. For simple threshold ranges,
				please refer to alarmThresholdMinValueAllowed and alarmThresholdMaxValueAllowed
				for the allowed range.
				
				Complex ranges are defined by corresponding entries in 
				alarmThresholdValueLookupTable."
			::= { alarmThresholdEntry 10 }
		
		-- 1.3.6.1.4.1.331.1.2.1.1.2.11.1.1.11
		alarmThresholdPointerToValueLookupTableMainIndex OBJECT-TYPE
			SYNTAX PositiveIntegerIncludingZero
			MAX-ACCESS read-only
			STATUS current
			DESCRIPTION
				"For complex alarm thresholds, this is the pointer into the 
				alarmThresholdValueLookupTable.
				
				This object does not apply to simple thresholds and should be 
				0 in those cases."
			::= { alarmThresholdEntry 11 }
		
		-- 1.3.6.1.4.1.331.1.2.1.1.2.11.2
		alarmThresholdValueLookupTable OBJECT-TYPE
			SYNTAX SEQUENCE OF AlarmThresholdValueLookupEntry
			MAX-ACCESS not-accessible
			STATUS current
			DESCRIPTION
				"This table contains the threshold values of those alarms with
				ranges that are:
				1. not linear or 
				2. cannot be described in by the few basic parameters in alarmThresholdTable.
				
				Alarm thresholds with these characteristics are referred to as complex 
				thresholds and include NodeX VSWR ratios and external alarm polarity.  
				
				Alarms whose thresholds fall into this class must still be set
				in a fairly simple manner and the allowed values must be clearly
				communicated to the network manager.  Therefore an integer value
				must be mapped to an ASCII string describing the particular
				setting.  
				
				This table must be presented such that alarmThresholdLookupValue 
				objects are in ascending order based on their values."
			::= { alarmThresholds 2 }
		
		-- 1.3.6.1.4.1.331.1.2.1.1.2.11.2.1
		alarmThresholdValueLookupEntry OBJECT-TYPE
			SYNTAX AlarmThresholdValueLookupEntry
			MAX-ACCESS not-accessible
			STATUS current
			DESCRIPTION
				"Alarm threshold value lookup table entry."
			INDEX { alarmThresholdLookupMainIdx, alarmThresholdLookupValueIdx }
			::= { alarmThresholdValueLookupTable 1 }
		
		AlarmThresholdValueLookupEntry ::=
			SEQUENCE { 
				alarmThresholdLookupMainIdx
					PositiveIntegerButNotZero,
				alarmThresholdLookupValueIdx
					PositiveIntegerButNotZero,
				alarmThresholdLookupValue
					Integer32,
				alarmThresholdLookupValueDescription
					OCTET STRING
			 }

		-- 1.3.6.1.4.1.331.1.2.1.1.2.11.2.1.1
		alarmThresholdLookupMainIdx OBJECT-TYPE
			SYNTAX PositiveIntegerButNotZero
			MAX-ACCESS read-only
			STATUS current
			DESCRIPTION
				"Main table index referenced by alarmThresholdPointerToValueLookupTableMainIndex."
			::= { alarmThresholdValueLookupEntry 1 }
		
		-- 1.3.6.1.4.1.331.1.2.1.1.2.11.2.1.2
		alarmThresholdLookupValueIdx OBJECT-TYPE
			SYNTAX PositiveIntegerButNotZero
			MAX-ACCESS read-only
			STATUS current
			DESCRIPTION
				"2nd table index. References the possible threshold values."
			::= { alarmThresholdValueLookupEntry 2 }
		
		-- 1.3.6.1.4.1.331.1.2.1.1.2.11.2.1.3
		alarmThresholdLookupValue OBJECT-TYPE
			SYNTAX Integer32
			MAX-ACCESS read-only
			STATUS current
			DESCRIPTION
				"This object indicates a value that may be used to set alarmThresholdActValue for
				the corresponding alarm.  Instances of this object must be ordered such that 
				their values are ascending."
			::= { alarmThresholdValueLookupEntry 3 }
		
		-- 1.3.6.1.4.1.331.1.2.1.1.2.11.2.1.4
		alarmThresholdLookupValueDescription OBJECT-TYPE
			SYNTAX OCTET STRING
			MAX-ACCESS read-only
			STATUS current
			DESCRIPTION
				"This is the ascii string indicating the 'real' set value, including the units if applicable.
				For example if setting an external alarm polarity, this object may be 'active high'."
			::= { alarmThresholdValueLookupEntry 4 }
		
		-- 1.3.6.1.4.1.331.1.2.1.1.2.12
		alarmSummary OBJECT-TYPE
			SYNTAX Severity
			MAX-ACCESS read-only
			STATUS current
			DESCRIPTION
				"System summary alarm status.
				Can be used for a simple system summary alarm polling.
				This object gets also delivered with the heartbeatEvent notification."
			::= { commonDeviceAlarm 12 }
		
		-- 1.3.6.1.4.1.331.1.2.1.1.2.13
		alarmConfig2Table OBJECT-TYPE
			SYNTAX SEQUENCE OF AlarmConfig2Entry
			MAX-ACCESS not-accessible
			STATUS current
			DESCRIPTION
				"Agent alarm configuration table. This table lists all alarms supported by the agent.
				It is used to read resp. change default alarm parameter settings.
				This settings apply system-wide, even in distributed systems for every CTA."
			::= { commonDeviceAlarm 13 }
		
		-- 1.3.6.1.4.1.331.1.2.1.1.2.13.1
		alarmConfig2Entry OBJECT-TYPE
			SYNTAX AlarmConfig2Entry
			MAX-ACCESS not-accessible
			STATUS current
			DESCRIPTION
				"Alarm configuration table entry."
			INDEX { alarmConfig2CTAidx, alarmConfig2alarmIDidx }
			::= { alarmConfig2Table 1 }
		
		AlarmConfig2Entry ::=
			SEQUENCE { 
				alarmConfig2CTAidx
					CTA,
				alarmConfig2alarmIDidx
					Integer32,
				alarmConfig2Severity
					Severity,
				alarmConfig2Latency
					Gauge32
			 }

		-- 1.3.6.1.4.1.331.1.2.1.1.2.13.1.1
		alarmConfig2CTAidx OBJECT-TYPE
			SYNTAX CTA
			MAX-ACCESS read-only
			STATUS current
			DESCRIPTION
				"Referenced Common Topology Address.
				It may also contain optional parameters, details see textual convention CTA."
			::= { alarmConfig2Entry 1 }
		
		-- 1.3.6.1.4.1.331.1.2.1.1.2.13.1.2
		alarmConfig2alarmIDidx OBJECT-TYPE
			SYNTAX Integer32 (1..100000)
			MAX-ACCESS read-only
			STATUS current
			DESCRIPTION
				"Referenced alarm ID: This is the most generic identifier of the alarm."
			::= { alarmConfig2Entry 2 }
		
		-- 1.3.6.1.4.1.331.1.2.1.1.2.13.1.3
		alarmConfig2Severity OBJECT-TYPE
			SYNTAX Severity
			MAX-ACCESS read-write
			STATUS current
			DESCRIPTION
				"Reading this object indicates the current level the alarm is set at.
				Setting this object changes the current level accordingly.
				Note!
				Severity 5=cleared in this context indicates that the alarm is disabled/to be disabled.
				Setting this object to any other level than supported (indicated by alarmSeveritiesSupported4Set)
				is not valid and results in a return of wrongValue."
			::= { alarmConfig2Entry 3 }
		
		-- 1.3.6.1.4.1.331.1.2.1.1.2.13.1.4
		alarmConfig2Latency OBJECT-TYPE
			SYNTAX Gauge32
			MAX-ACCESS read-write
			STATUS current
			DESCRIPTION
				"Alarm raise latency in seconds.
				Note: This object may not given for all alarms."
			::= { alarmConfig2Entry 4 }
		
		-- 1.3.6.1.4.1.331.1.2.1.1.2.14
		alarmUsertext2Table OBJECT-TYPE
			SYNTAX SEQUENCE OF AlarmUsertext2Entry
			MAX-ACCESS not-accessible
			STATUS current
			DESCRIPTION
				"Agent alarm user text configuration table. This table lists all alarms that support 
				user defined text.
				It is used to read resp. change default alarm user text settings.
				This settings specific for every CTA within a distributed system."
			::= { commonDeviceAlarm 14 }
		
		-- 1.3.6.1.4.1.331.1.2.1.1.2.14.1
		alarmUsertext2Entry OBJECT-TYPE
			SYNTAX AlarmUsertext2Entry
			MAX-ACCESS not-accessible
			STATUS current
			DESCRIPTION
				"Alarm user text configuration table entry."
			INDEX { alarmUsertext2CTAidx, alarmUsertext2alarmIDidx }
			::= { alarmUsertext2Table 1 }
		
		AlarmUsertext2Entry ::=
			SEQUENCE { 
				alarmUsertext2CTAidx
					CTA,
				alarmUsertext2alarmIDidx
					Integer32,
				alarmUsertext2
					OCTET STRING
			 }

		-- 1.3.6.1.4.1.331.1.2.1.1.2.14.1.1
		alarmUsertext2CTAidx OBJECT-TYPE
			SYNTAX CTA
			MAX-ACCESS read-only
			STATUS current
			DESCRIPTION
				"Referenced Common Topology Address.
				It may also contain optional parameters, details see textual convention CTA."
			::= { alarmUsertext2Entry 1 }
		
		-- 1.3.6.1.4.1.331.1.2.1.1.2.14.1.2
		alarmUsertext2alarmIDidx OBJECT-TYPE
			SYNTAX Integer32 (1..100000)
			MAX-ACCESS read-only
			STATUS current
			DESCRIPTION
				"Referenced alarm ID: This is the most generic identifier of the alarm."
			::= { alarmUsertext2Entry 2 }
		
		-- 1.3.6.1.4.1.331.1.2.1.1.2.14.1.3
		alarmUsertext2 OBJECT-TYPE
			SYNTAX OCTET STRING (SIZE (0..20))
			MAX-ACCESS read-write
			STATUS current
			DESCRIPTION
				"User defined text for referenced alarmID at referenced CTA."
			::= { alarmUsertext2Entry 3 }
		
		-- 1.3.6.1.4.1.331.1.2.1.1.3
		commonDeviceNotification OBJECT-IDENTITY
			STATUS current
			DESCRIPTION 
				"Notification objects."
			::= { commonDeviceObjects 3 }
		
		-- 1.3.6.1.4.1.331.1.2.1.1.3.1
		alarmTrap NOTIFICATION-TYPE
			OBJECTS { sysName, alarmTrapCounter, alarmID, alarmSpecificProblem, alarmPerceivedSeverity, 
				alarmEventDateTime, alarmEventType, alarmProbableCause, alarmAdditionalText, alarmEquipmentCTA, 
				alarmPhysicalIndex, alarmEquipmentPointer, connAgentUID, basicAgentLocationIdentification }
			STATUS current
			DESCRIPTION 
				"Trap workflow:
				- this notification is sent any time an alarm raises or gets cleared
				- no acknowledge is required if sent as trap (not valid if sent as inform)
				- the alarm trap is sent once, without any repetitions if sent as trap (not valid if sent as inform)
				- the trap counter starts from 0 after reboot
				- each notification following notification increases the trap counter by 1 in order
				  to provide an unique trap counter.
				- the trap counter wraps back to 1 after it reaches its maximum value (if this case 
				  should ever arise) in order to provide easy detect reboot capability
				
				V1.5.0.0 extension:
				- basicAgentLocationIdentification.
				  For backward compatibility the manager has to use an empty string 
				  if this object is not provided with the notification."
			::= { commonDeviceNotification 1 }
		
		-- 1.3.6.1.4.1.331.1.2.1.1.3.2
		heartbeatEvent NOTIFICATION-TYPE
			OBJECTS { sysName, alarmTrapCounter, connAgentUID, alarmSummary }
			STATUS current
			DESCRIPTION 
				"A notification sent by the agent to indicate that the device and the connection
				are still active. The send interval is decided by means of alarmHeartbeatInterval.
				Heartbeat mechanism is an alternative to OMC daily polling."
			::= { commonDeviceNotification 2 }
		
		-- 1.3.6.1.4.1.331.1.2.1.1.3.3
		changedParameterEvent NOTIFICATION-TYPE
			OBJECTS { sysName, alarmTrapCounter, alarmChangedParameterPointer, connAgentUID, basicAgentLocationIdentification, 
				basicAgentLocationAlias, basicAgentOutOfOperationArea, basicAgentConditionChangedConfig, connAgentUID2, basicCurrentTime
				 }
			STATUS current
			DESCRIPTION 
				"If manual user changes via other interfaces than SNMP, 
				automatic changes based on geographic location change 
				or any operating mode change happened, this notification is send to the OMC determined 
				by the value of alarmRecipient (in case of manual user changes after logout).
				
				
				V1.5.0.0 extensions:
				This notification has also to be send if automatic configuration changes were made based on 
				geographic location changes, or any other operating mode change happened.
				- basicAgentLocationIdentification contains the geographic location identification of the Agent.
				For backward compatibility the manager has to use an empty string 
				if this object is not provided with the notification.
				- basicAgentLocationAlias contains the geographic location area (zone) name.
				  For backward compatibility the manager has to use an empty string 
				  if this object is not provided with the notification.
				- basicAgentOutOfOperationArea indicates whether the Agent is out of operation (true) or not (false).
				  For backward compatibility the manager has to use false 
				  if this object is not provided with the notification.
				  Depending on this object the Manager has to suspend (basicAgentOutOfOperationArea==true) resp. 
				  resume (basicAgentOutOfOperationArea==false) the heartbeat supervision of the corresponding 
				  system (if activated).
				- basicAgentConditionChangedConfig indicates whether this notification was fired because of 
				  user maintenance (0) or other conditions (details see description of the object itself).
				  For backward compatibility the manager has to use 0 
				  if this object is not provided with the notification.
				- connAgentUID2. Enables the manager to detect system replacement at agent side (connAgentUID changed 
				  while connAgentUID2 keeps equal or vice versa). Added also to this notification because 
				  the system may have been replaced while it was out of operation so that the 
				  agentUpAndRunningEvent may not has been sent out. 
				  For backward compatibility the manager has to use an empty string 
				  if this object is not provided with the notification.
				
				V1.5.1.0 extension:
				- basicCurrentTime contains the date/timestamp when the event occurred."
			::= { commonDeviceNotification 3 }
		
		-- 1.3.6.1.4.1.331.1.2.1.1.3.4
		changedIPAddressEvent NOTIFICATION-TYPE
			OBJECTS { sysName, alarmTrapCounter, basicAgentIPAddressNew, connAgentUID, connAttachPSODrequesterSMS, 
				connAgntOrigIfNetworkType, connVpnEnabled, connVpnAgentIPIsVirtual, connAgentUID2 }
			STATUS current
			DESCRIPTION 
				"Used to notify a new agent IP address to the manager determined by the value of 
				alarmRecipient resp. connVpnManagerVirtualIP. This is NOT used if the agent is 
				connected 'On Demand' to a circuit switched network. 
				As the standard SNMP notification is 'fire and forget' and may get lost during 
				distribution, this notification has to be send periodically with a suitable period 
				(see also latest revision of specification Q0359R0 OAM Communication).
				Possible scenarios for sending this notification:
				LAN: IP address was changed during runtime by administrator or DHCP.
				CSAO: Initial connection to the network or reconnection after unexpected disconnect.
				PSAO: Initial connection to the packet data network access server or reconnection after 
				      unexpected disconnect.
				PSOD: Connection to the packet data network access server was invoked by an incoming SMS. 
				      In this case connAttachPSODrequesterSMS is set to the SMS sender number, in all 
				      other scenarios connAttachPSODrequesterSMS is set to an empty string.
				      
				Note!
				This notification MUST NOT be sent: 
				- if the IP address change was explicitely invoked by the manager with a SET on 
				  connAgentIPAddressLAN or connManOrigAgentIPAddressCS.
				- if the agent is connected 'On Demand' to a packet switched network and the connection 
				  to the network is initiated by the agent itself in order to send out any other 
				  notification (entConfigChange, alarmTrap, heartbeatEvent, changedParameterEvent, ...).
				- if the agent is connected 'On Demand' to a circuit switched network.
				
				V1.3.0.0 extensions:
				- connAgntOrigIfNetworkType identifies the network type for that the new IP address is valid.
				  For backward compatibility the manager has to use PS if this object is not provided with
				  the notification.
				- connVpnEnabled identifies whether VPN is enabled or not.
				  For backward compatibility the manager has to use false if this object is not provided with
				  the notification.
				- connVpnAgentIPIsVirtual identifies whether the reported IP address is a virtual VPN
				  address or not.
				  For backward compatibility the manager has to use false if this object is not provided with
				  the notification.
				If VPN is enabled, additionally the virtual agent VPN IP address has to be reported
				as soon as the VPN tunnel is established. In that case the manager has to wait for the
				virtual VPN IP address before starting communication.
				
				V1.5.0.0 extension:
				- connAgentUID2. Enables the manager to detect system replacement at agent side (connAgentUID changed 
				  while connAgentUID2 keeps equal or vice versa). Added also to this notification because it may be 
				  fired before agentUpAndRunningEvent (see description alarmTrapCounter).
				  For backward compatibility the manager has to use an empty string 
				  if this object is not provided with the notification."
			::= { commonDeviceNotification 4 }
		
		-- 1.3.6.1.4.1.331.1.2.1.1.3.5
		agentRebootRequiredEvent NOTIFICATION-TYPE
			OBJECTS { sysName, alarmTrapCounter, connAgentUID }
			STATUS current
			DESCRIPTION 
				"This notification is sent if any configuration change by the manager requires
				an agent reboot."
			::= { commonDeviceNotification 5 }
		
		-- 1.3.6.1.4.1.331.1.2.1.1.3.6
		agentUpAndRunningEvent NOTIFICATION-TYPE
			OBJECTS { sysName, alarmTrapCounter, connAgentUID, basicAgentVersion, basicCurrentMibVersion, 
				basicWirelessInnovationsMibVersion, basicAgentOutOfOperationArea, connAgentUID2, swActivePackageVersion, swActivePackagePatchLevel
				 }
			STATUS current
			DESCRIPTION 
				"This notification is sent to indicate any agent startup.
				
				V1.5.0.0 extension:
				- basicAgentOutOfOperationArea indicates whether the Agent is out of its operational 
				  area (true) or not (false).
				  For backward compatibility the manager has to use false 
				  if this object is not provided with the notification.
				- connAgentUID2. Enables the manager to detect system replacement at agent side (connAgentUID changed 
				  while connAgentUID2 keeps equal or vice versa).
				  For backward compatibility the manager has to use an empty string 
				  if this object is not provided with the notification.
				- swActivePackageVersion.
				  For backward compatibility the manager has to use an empty string 
				  if this object is not provided with the notification.
				- swActivePackagePatchLevel.
				  For backward compatibility the manager has to use zero 
				  if this object is not provided with the notification.
				- On reception of this notification and if the Agent is not out of its operational 
				  area (basicAgentOutOfOperationArea==false), the Manager has to resume the heartbeat 
				  supervision of the corresponding system (if activated)."
			::= { commonDeviceNotification 6 }
		
		-- 1.3.6.1.4.1.331.1.2.1.1.3.7
		agentShutdownEvent NOTIFICATION-TYPE
			OBJECTS { sysName, alarmTrapCounter, connAgentUID }
			STATUS current
			DESCRIPTION 
				"This notification is sent by the Agent during shutdown to indicate that the system 
				will be 'out of service'.
				
				On reception of this notification the Manager has to suspend the heartbeat supervision 
				of the corresponding system (if activated)."
			::= { commonDeviceNotification 7 }
		
		-- 1.3.6.1.4.1.331.1.2.1.1.3.8
		changedLocationAreaEvent NOTIFICATION-TYPE
			OBJECTS { sysName, alarmTrapCounter, connAgentUID, connAgentUID2, basicCurrentTime, 
				basicAgentLocationIdentification, basicAgentLocationAlias }
			STATUS current
			DESCRIPTION 
				"This notification is sent by the Agent in case of a location (zone) change that caused 
				no other parameter changes.
				
				In case of a location (zone) change that caused immediate or latency delayed parameter 
				changes, the changedParameterEvent is used instead."
			::= { commonDeviceNotification 8 }
		
		-- 1.3.6.1.4.1.331.1.2.1.1.4
		commonDeviceConformance OBJECT-IDENTITY
			STATUS current
			DESCRIPTION 
				"Conformance objects."
			::= { commonDeviceObjects 4 }
		
		-- 1.3.6.1.4.1.331.1.2.1.1.4.1
		commonDeviceBasicGroup OBJECT-GROUP
			OBJECTS { basicAgentVersion, basicCurrentMibVersion, basicWirelessInnovationsMibVersion, basicCurrentTime, basicAgentIPAddressNew, 
				basicAgentLocationIdentification, basicAgentLocationAlias, basicAgentOutOfOperationArea, basicAgentConditionChangedConfig }
			STATUS current
			DESCRIPTION 
				"A collection of objects providing basic device status 
				and control."
			::= { commonDeviceConformance 1 }
		
		-- 1.3.6.1.4.1.331.1.2.1.1.4.2
		commonDeviceAlarmGroup OBJECT-GROUP
			OBJECTS { alarmRecipient, alarmForwardingEnabled, alarmHeartbeatInterval, alarmSynchronize, alarmTrapCounter, 
				alarmID, alarmSpecificProblem, alarmPerceivedSeverity, alarmEventDateTime, alarmEventType, 
				alarmProbableCause, alarmAdditionalText, alarmEquipmentCTA, alarmPhysicalIndex, alarmEquipmentPointer, 
				alarmChangedParameterPointer, alarmSeveritiesSupported4Set, alarmConfig2CTAidx, alarmConfig2alarmIDidx, alarmConfig2Severity, 
				alarmUsertext2CTAidx, alarmUsertext2alarmIDidx, alarmUsertext2, alarmSummary }
			STATUS current
			DESCRIPTION 
				"A collection of alarm information common to all devices."
			::= { commonDeviceConformance 2 }
		
		-- 1.3.6.1.4.1.331.1.2.1.1.4.3
		commonDeviceNotificationGroup NOTIFICATION-GROUP
			NOTIFICATIONS { alarmTrap, heartbeatEvent, changedParameterEvent, changedIPAddressEvent, agentRebootRequiredEvent, 
				agentUpAndRunningEvent }
			STATUS current
			DESCRIPTION 
				"A collection of notifications common to all devices."
			::= { commonDeviceConformance 3 }
		
		-- 1.3.6.1.4.1.331.1.2.1.1.4.4
		commonDeviceCompliance OBJECT-IDENTITY
			STATUS current
			DESCRIPTION 
				"Compliance objects."
			::= { commonDeviceConformance 4 }
		
		-- 1.3.6.1.4.1.331.1.2.1.1.4.4.1
		commonDeviceBasicCompliance MODULE-COMPLIANCE
			STATUS current
			DESCRIPTION 
				"The compliance statement for all devices in this system."
			MODULE -- this module
				MANDATORY-GROUPS { commonDeviceBasicGroup, commonDeviceAlarmGroup, commonDeviceNotificationGroup, commonDeviceConnectivityGroup, commonDeviceControlGroup
					 }
			::= { commonDeviceCompliance 1 }
		
		-- 1.3.6.1.4.1.331.1.2.1.1.4.5
		commonDeviceConnectivityGroup OBJECT-GROUP
			OBJECTS { connAgentUID, connAgentIPAddressLAN, connAgentMainConnectivity, connAgentNotificationType, connAgentUID2, 
				connAgentSmsWlIndex, connAgentSmsWlNumber, connManOrigAgentIPAddressCS, connManOrigAuthUsernameCS, connManOrigAuthPasswordCS, 
				connManOrigIdleTimeoutCS, connAgntOrigIfIndex, connAgntOrigIfEnabled, connAgntOrigIfExtraSetting, connAgntOrigIfPhoneNo, 
				connAgntOrigIfAuthUsername, connAgntOrigIfAuthPassword, connAgntOrigIfNetworkType, connAgntOrigIfConnectionType, connAgntOrigIdleTimeoutPSODreqBySMS, 
				connAttachPSODrequesterSMS, connAttachPSODbySMSenabled, connAgentSMSserviceCenter, connAgentDisconnectTrigger, connAgntOrigAlwaysOnInactivityTimer
				 }
			STATUS current
			DESCRIPTION 
				"A collection of objects providing for connectivity control."
			::= { commonDeviceConformance 5 }
		
		-- 1.3.6.1.4.1.331.1.2.1.1.4.6
		commonDeviceControlGroup OBJECT-GROUP
			OBJECTS { ctrlApplication }
			STATUS current
			DESCRIPTION 
				"A collection of device control objects."
			::= { commonDeviceConformance 6 }
		
		-- 1.3.6.1.4.1.331.1.2.1.1.4.97
		optionalNotificationsGroup NOTIFICATION-GROUP
			NOTIFICATIONS { agentShutdownEvent, swActivationProgress, changedLocationAreaEvent, gpsEvent }
			STATUS current
			DESCRIPTION 
				"A collection of optional notifications."
			::= { commonDeviceConformance 97 }
		
		-- 1.3.6.1.4.1.331.1.2.1.1.4.98
		optionalObjectsGroup OBJECT-GROUP
			OBJECTS { alarmThreshold4CTA, alarmThreshold4alarmID, alarmThresholdIdx, alarmThresholdDescription, alarmThresholdUnit, 
				alarmThresholdScale, alarmThresholdStepValue, alarmThresholdMinValueAllowed, alarmThresholdMaxValueAllowed, alarmThresholdActValue, 
				alarmThresholdPointerToValueLookupTableMainIndex, alarmThresholdLookupMainIdx, alarmThresholdLookupValueIdx, alarmThresholdLookupValue, alarmThresholdLookupValueDescription, 
				alarmConfig2Latency, connVpnEnabled, connVpnManagerVirtualIP, connVpnAgentIPIsVirtual, connAndrewVpnEncryptionType, 
				connAndrewVpnAuthUsername, connAndrewVpnAuthPassword, connAndrewVpnKeepAliveTime, featureKeyDescription, featureKeyEnabled, 
				featureKeyNew, fulState, fulSegmentationSupported, fulFilename, fulMD5, 
				fulUploadURL, fulResultOk, fulResultString, fulDestFolder, swActivePackageVersion, 
				swActivePackagePatchLevel, swPackagesAvailable, swPackagesPatchlevel, swState, swPackageVersion, 
				swPackagePatchLevel, swActivationForced, swStateResultOk, swStateResultString, swNeededFilesFilename, 
				swNeededFilesFolder, swNeededFilesImmediateActivationRequired, swNeededFilesImmediateActivationSync, gpsHeartbeatInterval, gpsEventDestination, 
				gpsEventDestinationIsAlarmRecipient, gpsEventEnabled, gpsEventTime, gpsEventType, gpsNoOfSatellites, 
				gpsAltitude, gpsBearingDegree, gpsSpeed, gpsLongitude, gpsLatitude, 
				gpsZoneName, gpsDataTimestamp, connVpnAssignedServerGroupNo, connVpnServerAssignState, connVpnConnectionMode, 
				connVpnNotificationDestinationIsAlarmRecipient, connVpnClientVirtualIP, connOpenVpnProtocol, connAgentInformRetries, connAgentInformTimeout, 
				connAgentZoneChangeNotificationsEnabled, connVpnDisconnectTrigger, connVpnServerPhysicalIP, connVpnAssignedServerType, connVpnServerGroupIdx, 
				connVpnServerMainIP, connVpnServerBackupIP, swFinalActivationNotification, connAgentWebCommunicationProtocol }
			STATUS current
			DESCRIPTION 
				"A collection of optional objects."
			::= { commonDeviceConformance 98 }
		
		-- 1.3.6.1.4.1.331.1.2.1.1.4.99
		obsoleteObjectsGroup OBJECT-GROUP
			OBJECTS { basicAgentIPAddress, connAgentMainConnectivityType, connAgntOrigIfConnectivityType, alarmConfig4alarmID, alarmConfigSeverity, 
				alarmUsertext4CTA, alarmUsertext4alarmID, alarmUsertext }
			STATUS obsolete
			DESCRIPTION 
				"This group contains all objects whose status has been changed to obsolete."
			::= { commonDeviceConformance 99 }
		
		-- 1.3.6.1.4.1.331.1.2.1.1.5
		commonDeviceConnectivity OBJECT-IDENTITY
			STATUS current
			DESCRIPTION 
				"Connectivity objects."
			::= { commonDeviceObjects 5 }
		
		-- 1.3.6.1.4.1.331.1.2.1.1.5.1
		connAgentUID OBJECT-TYPE
			SYNTAX OCTET STRING (SIZE (0..40))
			MAX-ACCESS read-only
			STATUS current
			DESCRIPTION
				"This is the agent unique identifier. The manager uses this UID to distinguish the agents 
				integrated in the managers database. It has to be included in every private/enterprise trap.
				Besides the sysName, which is for free customer use and gets displayed at any agent or
				manager GUI, this is the internal unique communication identifier between manager and agent 
				at communication protocol level.
				This is a read only factory setting, it can be e.g. a MAC address, a Windows GUID or 
				similar unique identifier. If this setting is not available at the agent, always an 
				empty string has to be returned.
				
				For backward compatibility:
				If the manager receives an empty connAgentUID it has to use the sysName for system 
				identification, as already implemented with mib versions prior to version 1.1.0.0"
			::= { commonDeviceConnectivity 1 }
		
		-- 1.3.6.1.4.1.331.1.2.1.1.5.2
		connAgentMainConnectivityType OBJECT-TYPE
			SYNTAX ConnectivityType
			MAX-ACCESS read-write
			STATUS obsolete
			DESCRIPTION
				"Note!
				This object is obsolete and no longer supported.
				New objects are 'connAgentMainConnectivity' and corresponding 'connAgntOrigIfConnectionType'.
				
				Agent main connectivity type. 
				This identifies resp. sets the preferred method and interface the agent connects 
				to the network. It depends on the agent implementation whether all connectivity types 
				are supported."
			::= { commonDeviceConnectivity 2 }
		
		-- 1.3.6.1.4.1.331.1.2.1.1.5.3
		connAgentIPAddressLAN OBJECT-TYPE
			SYNTAX IPAddressAndPort
			MAX-ACCESS read-write
			STATUS current
			DESCRIPTION
				"This is the IP address of the agent, if the agent is connected to a LAN network.
				The port number is that one the agent listens for SNMP GET/SET requests.
				
				It depends on the agent implementation whether a SET request is supported at all or 
				maybe only setting the port gets rejected.
				Maybe setting the LAN IP address is only allowed to the LAN administrator outside the 
				agent application (e.g. by DHCP or manually). Nevertheless a GET request has to reflect
				the actual setting, return 0.0.0.0:0 if LAN connection is not supported.
				
				Setting a new value should get active immediately (but this may depend on the operating 
				system running at the agent)."
			::= { commonDeviceConnectivity 3 }
		
		-- 1.3.6.1.4.1.331.1.2.1.1.5.4
		connAgentMainConnectivity OBJECT-TYPE
			SYNTAX NetworkType
			MAX-ACCESS read-write
			STATUS current
			DESCRIPTION
				"Agent main connectivity. 
				This identifies resp. sets the preferred interface the agent connects to the network.
				It depends on the agent implementation whether all interfaces/network types are supported."
			::= { commonDeviceConnectivity 4 }
		
		-- 1.3.6.1.4.1.331.1.2.1.1.5.5
		connAgentNotificationType OBJECT-TYPE
			SYNTAX NotificationType
			MAX-ACCESS read-write
			STATUS current
			DESCRIPTION
				"Notification type the agent uses for any event defined within commonDeviceNotification 
				and any component specific event.
				See TC NotificationType."
			::= { commonDeviceConnectivity 5 }
		
		-- 1.3.6.1.4.1.331.1.2.1.1.5.6
		connAgentUID2 OBJECT-TYPE
			SYNTAX OCTET STRING (SIZE (0..40))
			MAX-ACCESS read-only
			STATUS current
			DESCRIPTION
				"This is an alternative unique identifier of the Agent. 
				This UID can be used by the Manager to detect system replacement at Agent side (connAgentUID changed 
				while connAgentUID2 keeps equal or vice versa).
				It is also included in the private/enterprise agentUpAndRunningEvent, changedParameterEvent and 
				changedIPAddressEvent notification.
				This is a read only factory setting, it can be e.g. the IMSI identification of the Agent's 
				wireless modem SIM card, a concatenation of the HW-ID and serial number out of the HW HID 
				the Agent is running on or a similar unique identifier. 
				If this ID is not available at the Agent, always an empty string has to be returned."
			::= { commonDeviceConnectivity 6 }
		
		-- 1.3.6.1.4.1.331.1.2.1.1.5.7
		connAgentWebCommunicationProtocol OBJECT-TYPE
			SYNTAX INTEGER
				{
				http(1),
				https(2),
				httpAndHttps(3)
				}
			MAX-ACCESS read-write
			STATUS current
			DESCRIPTION
				"This object indicates / controls which web communication protocol is active at the Agent.
				This setting applies to any HTTP based communication: Agent standard WEB interface 
				and SNMP triggered file transfer (commonDeviceFileTransfer).
				
				1 = HTTP
				2 = HTTPS
				3 = HTTP and HTTPS (in this case it is up to the Manager / web client to use HTTP or HTTPS)
				
				A change of this setting may require a restart of the WEB server at the Agent. 
				In this case the WEB server restart is triggered by the Agent immediately with the 
				successful SET request.
				
				If this object is not supported by the Agent, the Manager has to use HTTP."
			::= { commonDeviceConnectivity 7 }
		
		-- 1.3.6.1.4.1.331.1.2.1.1.5.8
		connAgentInformTimeout OBJECT-TYPE
			SYNTAX INTEGER
				{
				s10(10),
				s20(20),
				s30(30),
				s40(40),
				s50(50),
				m1(60),
				m2(120),
				m3(180),
				m4(240),
				m5(300),
				m6(360),
				m7(420),
				m8(480),
				m9(540),
				m10(600)
				}
			MAX-ACCESS read-write
			STATUS current
			DESCRIPTION
				"This object shows/controls the timeout (in seconds) used by the Agent waiting for inform 
				responses before resending.
				Valid values are: 
				10s, 20s, 30s, 40s, 50s, 1min, 2min, 3min, 4min, 5min, 6min, 7min, 8min, 9min, 10min."
			::= { commonDeviceConnectivity 8 }
		
		-- 1.3.6.1.4.1.331.1.2.1.1.5.9
		connAgentInformRetries OBJECT-TYPE
			SYNTAX Integer32 (-1 | 1..20)
			MAX-ACCESS read-write
			STATUS current
			DESCRIPTION
				"This object shows/controls the number of retries used by the Agent in case inform resending.
				Allowed range is 1 to 20 times or -1.
				The value of -1 indicates retries forever until the inform resonse gets received."
			::= { commonDeviceConnectivity 9 }
		
		-- 1.3.6.1.4.1.331.1.2.1.1.5.10
		connManagerOriginated OBJECT-IDENTITY
			STATUS current
			DESCRIPTION 
				"Connectivity objects for connections initiated by the manager."
			::= { commonDeviceConnectivity 10 }
		
		-- 1.3.6.1.4.1.331.1.2.1.1.5.10.1
		connManOrigAgentIPAddressCS OBJECT-TYPE
			SYNTAX IPAddressAndPort
			MAX-ACCESS read-write
			STATUS current
			DESCRIPTION
				"This is the IP address of the agent, if the agent gets accessed by an incoming 
				circuit switched call (address of the agent dial-in server).
				The port number is that one the agent listens for SNMP GET/SET requests.
				
				It depends on the agent implementation whether a SET request is supported at all 
				or maybe only setting the port gets rejected.
				Nevertheless a GET request has to reflect the actual setting, return 0.0.0.0:0 if 
				circuit switched connection is not supported.
				Setting a new value should not affect the current connection, only future dial-in 
				connections (but this may depend on the operating system running at the agent)."
			::= { connManagerOriginated 1 }
		
		-- 1.3.6.1.4.1.331.1.2.1.1.5.10.2
		connManOrigAuthUsernameCS OBJECT-TYPE
			SYNTAX OCTET STRING (SIZE (0..20))
			MAX-ACCESS read-write
			STATUS current
			DESCRIPTION
				"This is the username for PPP authentication, if the agent gets accessed by an incoming 
				circuit switched call.
				It depends on the agent implementation whether a SET request is supported.
				Setting a new value should not affect the current connection, only future dial-in 
				connections (but this may depend on the operating system running at the agent)."
			::= { connManagerOriginated 2 }
		
		-- 1.3.6.1.4.1.331.1.2.1.1.5.10.3
		connManOrigAuthPasswordCS OBJECT-TYPE
			SYNTAX OCTET STRING (SIZE (0..14))
			MAX-ACCESS read-write
			STATUS current
			DESCRIPTION
				"This is the password for PPP authentication, if the agent gets accessed by an incoming 
				circuit switched call.
				For security reasons it is highly recommended that reading this object returns 
				14 asterisk character '**************'.
				Setting a new value should not affect the current connection, only future dial-in 
				connections (but this may depend on the operating system running at the agent)."
			::= { connManagerOriginated 3 }
		
		-- 1.3.6.1.4.1.331.1.2.1.1.5.10.4
		connManOrigIdleTimeoutCS OBJECT-TYPE
			SYNTAX INTEGER (0..60)
			MAX-ACCESS read-write
			STATUS current
			DESCRIPTION
				"Communication idle timeout in minutes for agent incoming circuit switched connections.
				When expires the agent should drop the incoming circuit switched connection.
				A value of 0 denotes an infinite time (incoming connection never dropped by the agent).
				The default value is 0."
			::= { connManagerOriginated 4 }
		
		-- 1.3.6.1.4.1.331.1.2.1.1.5.11
		connAgentOriginated OBJECT-IDENTITY
			STATUS current
			DESCRIPTION 
				"Connectivity objects for connections initiated by the agent."
			::= { commonDeviceConnectivity 11 }
		
		-- 1.3.6.1.4.1.331.1.2.1.1.5.11.1
		connAgntOrigIfTable OBJECT-TYPE
			SYNTAX SEQUENCE OF ConnAgntOrigIfEntry
			MAX-ACCESS not-accessible
			STATUS current
			DESCRIPTION
				"Agent connectivity interface table. This table lists all possible interfaces that can 
				be used for network connections at agent side."
			::= { connAgentOriginated 1 }
		
		-- 1.3.6.1.4.1.331.1.2.1.1.5.11.1.1
		connAgntOrigIfEntry OBJECT-TYPE
			SYNTAX ConnAgntOrigIfEntry
			MAX-ACCESS not-accessible
			STATUS current
			DESCRIPTION
				"Interface table entry.
				It depends on the agent implementation and connectivity type whether all
				the table entry objects are used at all resp. how it is interpreted.
				If an object is not applicable, a GET should return an empty value 
				and a SET should return the notWritable error status."
			INDEX { connAgntOrigIfIndex }
			::= { connAgntOrigIfTable 1 }
		
		ConnAgntOrigIfEntry ::=
			SEQUENCE { 
				connAgntOrigIfIndex
					PositiveIntegerButNotZero,
				connAgntOrigIfConnectivityType
					ConnectivityType,
				connAgntOrigIfEnabled
					INTEGER,
				connAgntOrigIfExtraSetting
					OCTET STRING,
				connAgntOrigIfPhoneNo
					OCTET STRING,
				connAgntOrigIfAuthUsername
					OCTET STRING,
				connAgntOrigIfAuthPassword
					OCTET STRING,
				connAgntOrigIfNetworkType
					NetworkType,
				connAgntOrigIfConnectionType
					ConnectionType
			 }

		-- 1.3.6.1.4.1.331.1.2.1.1.5.11.1.1.1
		connAgntOrigIfIndex OBJECT-TYPE
			SYNTAX PositiveIntegerButNotZero
			MAX-ACCESS read-only
			STATUS current
			DESCRIPTION
				"Table index. Also used to indicate the priority for interfaces of the same 
				network type. Lower indexes indicate higher priority."
			::= { connAgntOrigIfEntry 1 }
		
		-- 1.3.6.1.4.1.331.1.2.1.1.5.11.1.1.2
		connAgntOrigIfConnectivityType OBJECT-TYPE
			SYNTAX ConnectivityType
			MAX-ACCESS read-only
			STATUS obsolete
			DESCRIPTION
				"Note!
				This object is obsolete and no longer supported.
				New objects are 'connAgntOrigIfNetworkType' and 'connAgntOrigIfConnectionType'.
				
				Connectivity type of this interface."
			::= { connAgntOrigIfEntry 2 }
		
		-- 1.3.6.1.4.1.331.1.2.1.1.5.11.1.1.3
		connAgntOrigIfEnabled OBJECT-TYPE
			SYNTAX INTEGER
				{
				notApplicable(0),
				enabled(1),
				disabled(2)
				}
			MAX-ACCESS read-write
			STATUS current
			DESCRIPTION
				"This object shows/controls whether this interface is enabled or disabled.
				It also shows whether or not such control is applicable.
				
				A GET may return:
				  notApplicable(0)
				  enabled(1)
				  disabled(2)
				
				The value, notApplicable(0) is used to identify those interfaces that cannot be
				enabled or disabled by this object.
				
				Setting this object to notApplicable(0) is not valid and results in a return 
				of wrongValue.
				Setting this object to enabled(1) enables this interface.
				Setting this object to disabled(2) disables this interface.
				
				In the case of an interface that does not support this control object, it is 
				only legal to GET the value.  A GET must always return notApplicable(0).  Any 
				SET must return notWritable."
			::= { connAgntOrigIfEntry 3 }
		
		-- 1.3.6.1.4.1.331.1.2.1.1.5.11.1.1.4
		connAgntOrigIfExtraSetting OBJECT-TYPE
			SYNTAX OCTET STRING (SIZE (0..80))
			MAX-ACCESS read-write
			STATUS current
			DESCRIPTION
				"Depending on network type, used for: 
				- CS, PS: modem / network initialization string.
				- SMS: SMS prefix.
				- DC, LAN: not used."
			::= { connAgntOrigIfEntry 4 }
		
		-- 1.3.6.1.4.1.331.1.2.1.1.5.11.1.1.5
		connAgntOrigIfPhoneNo OBJECT-TYPE
			SYNTAX OCTET STRING (SIZE (0..31))
			MAX-ACCESS read-write
			STATUS current
			DESCRIPTION
				"Depending on network type, e.g. used for:
				- circuit switched dial-out PPP connections:
				  Telephone number of the recipient for all notifications.
				- packet switched network connection:
				  Access code for the packet data network access server.
				- SMS: destination SMS number."
			::= { connAgntOrigIfEntry 5 }
		
		-- 1.3.6.1.4.1.331.1.2.1.1.5.11.1.1.6
		connAgntOrigIfAuthUsername OBJECT-TYPE
			SYNTAX OCTET STRING (SIZE (0..40))
			MAX-ACCESS read-write
			STATUS current
			DESCRIPTION
				"Username. Depending on network type, e.g. used for:
				- circuit switched dial-out PPP connections:
				  This string is used to authenticate the user's access to the OMC remote access server.
				- packet switched network connection:
				  This string is used to authenticate the user's access to the packet data network 
				  access server."
			::= { connAgntOrigIfEntry 6 }
		
		-- 1.3.6.1.4.1.331.1.2.1.1.5.11.1.1.7
		connAgntOrigIfAuthPassword OBJECT-TYPE
			SYNTAX OCTET STRING (SIZE (0..14))
			MAX-ACCESS read-write
			STATUS current
			DESCRIPTION
				"Password, for security reasons it is highly recommended that reading this object returns 
				14 asterisk character '**************'.
				
				Depending on network type, e.g. used for:
				- circuit switched dial-out PPP connections:
				  This string is used to authenticate the user's access to the OMC remote access server.
				- packet switched network connection:
				  This string is used to authenticate the user's access to the packet data network 
				  access server."
			::= { connAgntOrigIfEntry 7 }
		
		-- 1.3.6.1.4.1.331.1.2.1.1.5.11.1.1.8
		connAgntOrigIfNetworkType OBJECT-TYPE
			SYNTAX NetworkType
			MAX-ACCESS read-only
			STATUS current
			DESCRIPTION
				"Network type of this interface. See TC NetworkType."
			::= { connAgntOrigIfEntry 8 }
		
		-- 1.3.6.1.4.1.331.1.2.1.1.5.11.1.1.9
		connAgntOrigIfConnectionType OBJECT-TYPE
			SYNTAX ConnectionType
			MAX-ACCESS read-write
			STATUS current
			DESCRIPTION
				"Connection type of this interface. See TC ConnectionType.
				This object shows/controls the connection type of this interface.
				It also shows whether or not such control is applicable.
				
				A GET may return:
				  notApplicable(0)
				  onDemand(1)
				  alwaysOn(2)
				
				The value notApplicable(0) is used to identify those interfaces that do not
				distinguish the connection type.
				
				Setting this object to notApplicable(0) is not valid and results in a return 
				of wrongValue.
				
				In the case of an interface that does not support this control object, it is 
				only legal to GET the value.  A GET must always return notApplicable(0).  Any 
				SET must return notWritable."
			::= { connAgntOrigIfEntry 9 }
		
		-- 1.3.6.1.4.1.331.1.2.1.1.5.11.2
		connAgntOrigIdleTimeoutPSODreqBySMS OBJECT-TYPE
			SYNTAX INTEGER (1..60)
			MAX-ACCESS read-write
			STATUS current
			DESCRIPTION
				"Communication idle timeout in minutes for agent side 'On Demand' packet switched 
				network connection.
				Note!
				This applies ONLY when the connect request was issued by SMS.
				When expires the agent should drop this connection.
				The default value is 5."
			::= { connAgentOriginated 2 }
		
		-- 1.3.6.1.4.1.331.1.2.1.1.5.11.3
		connAttachPSODrequesterSMS OBJECT-TYPE
			SYNTAX OCTET STRING (SIZE (0..31))
			MAX-ACCESS accessible-for-notify
			STATUS current
			DESCRIPTION
				"This OID is used in the changedIPAddressEvent only.
				If the agent is connected PSOD and the connection to the packet data network access server 
				was invoked by an incoming SMS, this object is set to the SMS sender number, in all 
				other scenarios connAttachPSODrequesterSMS is set to an empty string."
			::= { connAgentOriginated 3 }
		
		-- 1.3.6.1.4.1.331.1.2.1.1.5.11.4
		connAttachPSODbySMSenabled OBJECT-TYPE
			SYNTAX TruthValue
			MAX-ACCESS read-write
			STATUS current
			DESCRIPTION
				"Shows/sets whether SMS initiated packet switched network connection in the 'On demand'
				mode is enabled or disabled."
			::= { connAgentOriginated 4 }
		
		-- 1.3.6.1.4.1.331.1.2.1.1.5.11.5
		connAgentSMSserviceCenter OBJECT-TYPE
			SYNTAX OCTET STRING (SIZE (0..31))
			MAX-ACCESS read-write
			STATUS current
			DESCRIPTION
				"SMS service center number."
			::= { connAgentOriginated 5 }
		
		-- 1.3.6.1.4.1.331.1.2.1.1.5.11.6
		connAgentDisconnectTrigger OBJECT-TYPE
			SYNTAX INTEGER
				{
				notApplicable(0),
				disconnect(1)
				}
			MAX-ACCESS read-write
			STATUS current
			DESCRIPTION
				"With this object the manager is able to force a disconnect of an active agent 
				originated network connection.
				
				A GET always returns notApplicable(0).
				
				A SET to notApplicable(0) has no affect and triggers no further agent activity.
				A SET to disconnect(1) will cause the agent to disconnect from the 
				  network and behave according the actual connectivity settings.
				  Note: The response has to be sent before disconnecting from network.
				  If disconnect is not applicable to the current connection network
				  type (e.g. LAN, SMS), error inconsistentValue has to be returned."
			::= { connAgentOriginated 6 }
		
		-- 1.3.6.1.4.1.331.1.2.1.1.5.11.7
		connAgentVpn OBJECT-IDENTITY
			STATUS current
			DESCRIPTION 
				"VPN communication objects. If the agent doesn't support VPN at all, always 'no such object'
				has to be returned to any request within this section."
			::= { connAgentOriginated 7 }
		
		-- 1.3.6.1.4.1.331.1.2.1.1.5.11.7.1
		connVpnEnabled OBJECT-TYPE
			SYNTAX TruthValue
			MAX-ACCESS read-write
			STATUS current
			DESCRIPTION
				"This object shows/controls whether VPN communication is enabled or disabled."
			::= { connAgentVpn 1 }
		
		-- 1.3.6.1.4.1.331.1.2.1.1.5.11.7.2
		connVpnServerPhysicalIP OBJECT-TYPE
			SYNTAX IPAddressAndPort
			MAX-ACCESS read-only
			STATUS current
			DESCRIPTION
				"Physical IP address and port of actually connected VPN server.
				
				In case VPN is actually not connected, '0.0.0.0' will be responded."
			::= { connAgentVpn 2 }
		
		-- 1.3.6.1.4.1.331.1.2.1.1.5.11.7.3
		connVpnManagerVirtualIP OBJECT-TYPE
			SYNTAX IPAddressAndPort
			MAX-ACCESS read-write
			STATUS current
			DESCRIPTION
				"Virtual VPN IP address and port of the recipient of all notifications in case VPN
				is enabled. Otherwise alarmRecipient (physical IP address) is used.
				
				Note!
				In case the Agent does not distinguish the notification destination for VPN and standard 
				connection, this object reflects the setting of alarmRecipient and a SET request on this 
				object will fail with an appropriate error."
			::= { connAgentVpn 3 }
		
		-- 1.3.6.1.4.1.331.1.2.1.1.5.11.7.4
		connVpnAgentIPIsVirtual OBJECT-TYPE
			SYNTAX TruthValue
			MAX-ACCESS accessible-for-notify
			STATUS current
			DESCRIPTION
				"This OID is used in the changedIPAddressEvent only, see also description there.
				Indicates whether the reported IP address is a virtual VPN address or not."
			::= { connAgentVpn 4 }
		
		-- 1.3.6.1.4.1.331.1.2.1.1.5.11.7.5
		connAndrewVpn OBJECT-IDENTITY
			STATUS current
			DESCRIPTION 
				"Andrew VPN objects."
			::= { connAgentVpn 5 }
		
		-- 1.3.6.1.4.1.331.1.2.1.1.5.11.7.5.1
		connAndrewVpnEncryptionType OBJECT-TYPE
			SYNTAX INTEGER
				{
				cryptNone(0),
				cryptAES128(1),
				cryptBlowfish64(2),
				cryptBlowfish32(3)
				}
			MAX-ACCESS read-write
			STATUS current
			DESCRIPTION
				"Encryption type for transferred data except keep alive packet."
			::= { connAndrewVpn 1 }
		
		-- 1.3.6.1.4.1.331.1.2.1.1.5.11.7.5.2
		connAndrewVpnAuthUsername OBJECT-TYPE
			SYNTAX OCTET STRING (SIZE (0..31))
			MAX-ACCESS read-write
			STATUS current
			DESCRIPTION
				"VPN authentication user name. 
				This string is used to authenticate the access to the VPN server."
			::= { connAndrewVpn 2 }
		
		-- 1.3.6.1.4.1.331.1.2.1.1.5.11.7.5.3
		connAndrewVpnAuthPassword OBJECT-TYPE
			SYNTAX OCTET STRING (SIZE (0..31))
			MAX-ACCESS read-write
			STATUS current
			DESCRIPTION
				"VPN authentication password.
				This string is used to authenticate the access to the VPN server.
				For security reasons it is highly recommended that 
				reading this object returns always asterisk characters '**************'."
			::= { connAndrewVpn 3 }
		
		-- 1.3.6.1.4.1.331.1.2.1.1.5.11.7.5.4
		connAndrewVpnKeepAliveTime OBJECT-TYPE
			SYNTAX Integer32 (30..3600)
			MAX-ACCESS read-write
			STATUS current
			DESCRIPTION
				"Keep alive interval in seconds.
				Cyclic I am alive communication between VPN client and server."
			::= { connAndrewVpn 4 }
		
		-- 1.3.6.1.4.1.331.1.2.1.1.5.11.7.6
		connOpenVpn OBJECT-IDENTITY
			STATUS current
			DESCRIPTION 
				"Open VPN objects."
			::= { connAgentVpn 6 }
		
		-- 1.3.6.1.4.1.331.1.2.1.1.5.11.7.6.1
		connOpenVpnProtocol OBJECT-TYPE
			SYNTAX INTEGER
				{
				udp(1),
				tcp(2)
				}
			MAX-ACCESS read-write
			STATUS current
			DESCRIPTION
				"Protocol for communicating with OpenVPN server - UDP or TCP."
			::= { connOpenVpn 1 }
		
		-- 1.3.6.1.4.1.331.1.2.1.1.5.11.7.7
		connVpnClientVirtualIP OBJECT-TYPE
			SYNTAX IPAddressAndPort
			MAX-ACCESS read-only
			STATUS current
			DESCRIPTION
				"Actual virtual IP address of the Agent (VPN client).
				In case VPN is currently not connected, 0.0.0.0 has to be responded."
			::= { connAgentVpn 7 }
		
		-- 1.3.6.1.4.1.331.1.2.1.1.5.11.7.8
		connVpnNotificationDestinationIsAlarmRecipient OBJECT-TYPE
			SYNTAX TruthValue
			MAX-ACCESS read-write
			STATUS current
			DESCRIPTION
				"Object that shows resp. controls in case of VPN connection whether the destination for all 
				notifications is the standard notification destination (true: destination is alarmRecipient) 
				or not (false: destination is connVpnManagerVirtualIP).
				
				Note!
				In case the Agent does not distinguish the notification destination for VPN and standard 
				connection, a SET request on this object will fail with an appropriate error."
			::= { connAgentVpn 8 }
		
		-- 1.3.6.1.4.1.331.1.2.1.1.5.11.7.9
		connVpnConnectionMode OBJECT-TYPE
			SYNTAX INTEGER
				{
				unknownOrNotApplicable(1),
				vpnFailed(2),
				vpnConnected(3)
				}
			MAX-ACCESS read-only
			STATUS current
			DESCRIPTION
				"Object that shows whether the current VPN mode is secure (vpnConnected) or in unsecure 
				fallback mode (vpnFailed).
				
				unknownOrNotApplicable is used in case VPN is disabled."
			::= { connAgentVpn 9 }
		
		-- 1.3.6.1.4.1.331.1.2.1.1.5.11.7.10
		connVpnServerGroups OBJECT-IDENTITY
			STATUS current
			DESCRIPTION 
				"Objects handling VPN server groups.
				Due to server scalability and failover aspects more than one server may be used. 
				The server groups identify the different server instances."
			::= { connAgentVpn 10 }
		
		-- 1.3.6.1.4.1.331.1.2.1.1.5.11.7.10.1
		connVpnServerAssignState OBJECT-TYPE
			SYNTAX INTEGER
				{
				unknownOrNotApplicable(1),
				unassigned(2),
				assigned(3)
				}
			MAX-ACCESS read-only
			STATUS current
			DESCRIPTION
				"Object that shows whether the Agent/VPN client is assigned to a VPN server group.
				
				unknownOrNotApplicable is used in case VPN is disabled."
			::= { connVpnServerGroups 1 }
		
		-- 1.3.6.1.4.1.331.1.2.1.1.5.11.7.10.2
		connVpnAssignedServerGroupNo OBJECT-TYPE
			SYNTAX PositiveIntegerIncludingZero
			MAX-ACCESS read-only
			STATUS current
			DESCRIPTION
				"Object that shows the actual assigned VPN server group number (>0) or 0 in case 
				VPN server is not assigned."
			::= { connVpnServerGroups 2 }
		
		-- 1.3.6.1.4.1.331.1.2.1.1.5.11.7.10.3
		connVpnAssignedServerType OBJECT-TYPE
			SYNTAX INTEGER
				{
				unknownOrNotApplicable(1),
				main(2),
				backup(3)
				}
			MAX-ACCESS read-only
			STATUS current
			DESCRIPTION
				"Object that shows whether the Agent/VPN client is actually connected to 
				resp. currently trying to connect the main or backup VPN server.
				
				unknownOrNotApplicable is used in case VPN is disabled."
			::= { connVpnServerGroups 3 }
		
		-- 1.3.6.1.4.1.331.1.2.1.1.5.11.7.10.10
		connVpnServerGroupTable OBJECT-TYPE
			SYNTAX SEQUENCE OF ConnVpnServerGroupEntry
			MAX-ACCESS not-accessible
			STATUS current
			DESCRIPTION
				"Table that holds VPN server groups. 
				Due to scalability aspects more than one entry may be used. This table identifies the 
				different server group instances of the different server types (main/backup). 
				During client side server scan procedure the servers decide to accept a connection request 
				from a particular client or not so the client can find its assigned server instance."
			::= { connVpnServerGroups 10 }
		
		-- 1.3.6.1.4.1.331.1.2.1.1.5.11.7.10.10.1
		connVpnServerGroupEntry OBJECT-TYPE
			SYNTAX ConnVpnServerGroupEntry
			MAX-ACCESS not-accessible
			STATUS current
			DESCRIPTION
				"Description."
			INDEX { connVpnServerGroupIdx }
			::= { connVpnServerGroupTable 1 }
		
		ConnVpnServerGroupEntry ::=
			SEQUENCE { 
				connVpnServerGroupIdx
					PositiveIntegerButNotZero,
				connVpnServerMainIP
					IPAddressAndPort,
				connVpnServerBackupIP
					IPAddressAndPort
			 }

		-- 1.3.6.1.4.1.331.1.2.1.1.5.11.7.10.10.1.1
		connVpnServerGroupIdx OBJECT-TYPE
			SYNTAX PositiveIntegerButNotZero
			MAX-ACCESS read-only
			STATUS current
			DESCRIPTION
				"Table index to identify the instance. Corresponds with VPN server group number."
			::= { connVpnServerGroupEntry 1 }
		
		-- 1.3.6.1.4.1.331.1.2.1.1.5.11.7.10.10.1.2
		connVpnServerMainIP OBJECT-TYPE
			SYNTAX IPAddressAndPort
			MAX-ACCESS read-write
			STATUS current
			DESCRIPTION
				"Main VPN server physical IP address and port."
			::= { connVpnServerGroupEntry 2 }
		
		-- 1.3.6.1.4.1.331.1.2.1.1.5.11.7.10.10.1.3
		connVpnServerBackupIP OBJECT-TYPE
			SYNTAX IPAddressAndPort
			MAX-ACCESS read-write
			STATUS current
			DESCRIPTION
				"Backup VPN server physical IP address and port."
			::= { connVpnServerGroupEntry 3 }
		
		-- 1.3.6.1.4.1.331.1.2.1.1.5.11.7.11
		connVpnDisconnectTrigger OBJECT-TYPE
			SYNTAX INTEGER
				{
				notApplicable(0),
				disconnect(1)
				}
			MAX-ACCESS read-write
			STATUS current
			DESCRIPTION
				"With this object the manager is able to force an immediate VPN disconnect.
				
				A GET always returns notApplicable(0).
				
				A SET to notApplicable(0) has no affect and triggers no further agent activity.
				A SET to disconnect(1) will cause the agent to disconnect VPN and behave afterwards 
				  according the actual connectivity settings.
				  Note: The response has to be sent before disconnecting VPN.
				  If disconnect is not applicable (VPN not connected), error inconsistentValue has to be returned."
			::= { connAgentVpn 11 }
		
		-- 1.3.6.1.4.1.331.1.2.1.1.5.11.8
		connAgntOrigAlwaysOnInactivityTimer OBJECT-TYPE
			SYNTAX Integer32 (0 | 30..1440)
			MAX-ACCESS read-write
			STATUS current
			DESCRIPTION
				"Communication idle timeout (related to application oriented incoming data requests) 
				in minutes for agent outgoing always on connections.
				When expired the agent should drop and reconnect the outgoing always on connection.
				A value of 0 denotes an infinite time (outgoing always on connection never dropped 
				by the agent, except main connectivity was changed and new connection type is no
				longer always on).
				The default value is 0.
				Allowed range is 30 to 1440 minutes (24 hours)."
			::= { connAgentOriginated 8 }
		
		-- 1.3.6.1.4.1.331.1.2.1.1.5.12
		connAgentSmsWlTable OBJECT-TYPE
			SYNTAX SEQUENCE OF ConnAgentSmsWlEntry
			MAX-ACCESS not-accessible
			STATUS current
			DESCRIPTION
				"Agent SMS whitelist table. This table lists all accepted SMS numbers 
				for incoming SMS requests."
			::= { commonDeviceConnectivity 12 }
		
		-- 1.3.6.1.4.1.331.1.2.1.1.5.12.1
		connAgentSmsWlEntry OBJECT-TYPE
			SYNTAX ConnAgentSmsWlEntry
			MAX-ACCESS not-accessible
			STATUS current
			DESCRIPTION
				"Description."
			INDEX { connAgentSmsWlIndex }
			::= { connAgentSmsWlTable 1 }
		
		ConnAgentSmsWlEntry ::=
			SEQUENCE { 
				connAgentSmsWlIndex
					PositiveIntegerButNotZero,
				connAgentSmsWlNumber
					OCTET STRING
			 }

		-- 1.3.6.1.4.1.331.1.2.1.1.5.12.1.1
		connAgentSmsWlIndex OBJECT-TYPE
			SYNTAX PositiveIntegerButNotZero
			MAX-ACCESS read-only
			STATUS current
			DESCRIPTION
				"Table index to identify the instance."
			::= { connAgentSmsWlEntry 1 }
		
		-- 1.3.6.1.4.1.331.1.2.1.1.5.12.1.2
		connAgentSmsWlNumber OBJECT-TYPE
			SYNTAX OCTET STRING (SIZE (0..31))
			MAX-ACCESS read-write
			STATUS current
			DESCRIPTION
				"Authorized SMS phone number for incoming SMS requests."
			::= { connAgentSmsWlEntry 2 }
		
		-- 1.3.6.1.4.1.331.1.2.1.1.5.13
		connAgentZoneChangeNotificationsEnabled OBJECT-TYPE
			SYNTAX TruthValue
			MAX-ACCESS read-write
			STATUS current
			DESCRIPTION
				"This object shows/controls whether all location area change based notifications are enabled or not.
				Location area change based notifications are:
				- changedParameterEvent[basicAgentConditionChangedConfig=locationChange]  (->immediate RF configuration change)
				- changedParameterEvent[basicAgentConditionChangedConfig=locationLatency] (->RF configuration change after latency expired)
				- changedLocationAreaEvent (->no RF configuration change)"
			::= { commonDeviceConnectivity 13 }
		
		-- 1.3.6.1.4.1.331.1.2.1.1.6
		commonDeviceControl OBJECT-IDENTITY
			STATUS current
			DESCRIPTION 
				"Device and agent application control objects.  Objects in this group provide
				for resetting of remote devices.  In the future, other control such as 
				software download and disaster recovery will be provided."
			::= { commonDeviceObjects 6 }
		
		-- 1.3.6.1.4.1.331.1.2.1.1.6.1
		ctrlApplication OBJECT-TYPE
			SYNTAX INTEGER
				{
				running(0),
				reboot(1),
				restart(2)
				}
			MAX-ACCESS read-write
			STATUS current
			DESCRIPTION
				"This object allows the agent application to be reset and if needed, the 
				operating system as well.
				
				A GET must return running(0). 
				
				A SET to reboot(1) causes a complete reboot of the operating system and 
				agent application.
				A SET to restart(2) causes an agent application restart.
				A SET to running(0) is not valid and results in a return of wrongValue.
				
				Note: before starting the reboot/restart the agent has to send back the SET response."
			::= { commonDeviceControl 1 }
		
		-- 1.3.6.1.4.1.331.1.2.1.1.7
		commonDeviceFeatureKeys OBJECT-IDENTITY
			STATUS current
			DESCRIPTION 
				"With this section software features of the agent are handled. If the agent doesn't support
				software feature keys at all, always 'no such object' has to be returned to any request
				within this section."
			::= { commonDeviceObjects 7 }
		
		-- 1.3.6.1.4.1.331.1.2.1.1.7.1
		featureKeyTable OBJECT-TYPE
			SYNTAX SEQUENCE OF FeatureKeyEntry
			MAX-ACCESS not-accessible
			STATUS current
			DESCRIPTION
				"This table lists all possible SW features supported by the agent."
			::= { commonDeviceFeatureKeys 1 }
		
		-- 1.3.6.1.4.1.331.1.2.1.1.7.1.1
		featureKeyEntry OBJECT-TYPE
			SYNTAX FeatureKeyEntry
			MAX-ACCESS not-accessible
			STATUS current
			DESCRIPTION
				"Description."
			INDEX { featureKeyIdx }
			::= { featureKeyTable 1 }
		
		FeatureKeyEntry ::=
			SEQUENCE { 
				featureKeyIdx
					Integer32,
				featureKeyDescription
					OCTET STRING,
				featureKeyEnabled
					TruthValue
			 }

		-- 1.3.6.1.4.1.331.1.2.1.1.7.1.1.1
		featureKeyIdx OBJECT-TYPE
			SYNTAX Integer32 (1..32)
			MAX-ACCESS not-accessible
			STATUS current
			DESCRIPTION
				"Table index."
			::= { featureKeyEntry 1 }
		
		-- 1.3.6.1.4.1.331.1.2.1.1.7.1.1.2
		featureKeyDescription OBJECT-TYPE
			SYNTAX OCTET STRING
			MAX-ACCESS read-only
			STATUS current
			DESCRIPTION
				"Textual description of the feature."
			::= { featureKeyEntry 2 }
		
		-- 1.3.6.1.4.1.331.1.2.1.1.7.1.1.3
		featureKeyEnabled OBJECT-TYPE
			SYNTAX TruthValue
			MAX-ACCESS read-only
			STATUS current
			DESCRIPTION
				"This object shows whether the feature is enabled or not."
			::= { featureKeyEntry 3 }
		
		-- 1.3.6.1.4.1.331.1.2.1.1.7.2
		featureKeyNew OBJECT-TYPE
			SYNTAX OCTET STRING (SIZE (0 | 42))
			MAX-ACCESS read-write
			STATUS current
			DESCRIPTION
				"With this object a new SW feature can be enabled by writing a valid feature key.
				
				A GET always returns an empty string.
				A SET with an invalid feature key results in an error being returned."
			::= { commonDeviceFeatureKeys 2 }
		
		-- 1.3.6.1.4.1.331.1.2.1.1.8
		commonDeviceFileTransfer OBJECT-IDENTITY
			STATUS current
			DESCRIPTION 
				"Objects for file transfer control. The actual file transfer is done via HTTP.
				In this section the following naming definition applies:
				- file upload: file transfer from Manager to Agent.
				- file download: file transfer from Agent to Manager."
			::= { commonDeviceObjects 8 }
		
		-- 1.3.6.1.4.1.331.1.2.1.1.8.1
		fUpload OBJECT-IDENTITY
			STATUS current
			DESCRIPTION 
				"Objects for file upload control. The actual file transfer is done via HTTP POST.
				If the Agent doesn't support file upload at all, always 'no such object' has to be returned to any request within this section.
				
				General:
				- Any state transition not shown in the state diagram (except state transcision to idle - see idle description) 
				  is not allowed and should respond an SNMP error code. Before responding the error code, fulResultOk 
				  and fulResultString should be prepared accordingly.
				
				Preconditions for file upload are:
				- fulState = idle (default at Agent startup)
				- fulResultOk = false (default at Agent startup)
				- fulDestFolder (V1.5.0.0 extension), fulFilename, fulMD5, fulUploadURL and fulResultString are empty (defaults at Agent startup)
				
				Workflow file upload:
				- Manager sets fulState = preparation
				- Manager gets fulSegmentationSupported
				  If segmentation is supported, the Manager performs all neccessary internal actions to prepare file segmentation.
				  This step is optional. If more than one file should be uploaded, the Manager typically checks fulSegmentationSupported only once.
				- Manager sets fulDestFolder (V1.5.0.0 extension)
				  This step is optional. If not set it is up to the Agent where to store the file.
				- Manager sets fulFilename
				  Upon this, the Agent prepares the upload URL in fulUploadURL (before responding the set fulFilename request)
				- Manager gets fulUploadURL
				- Manager sets fulMD5
				  This step is optional. The Manager may want to upload a file without MD5 checksum test (e.g. MD5 checksum unknown).
				- Manager sets fulState = inProgress
				  Manager performs the actual HTTP file transfer of the file <fulFilename> resp. all segments of the file 
				  <fulFilename.name>_n_of_m.<fulFilename.extension> using fulUploadURL together with the HTTP POST command. If fulFilename is part of 
				  fulUploadURL and file segmentation is used, the Manager has to insert the segment numbering (_n_of_m) into fulUploadURL accordingly.
				  In case of segmented file upload the Agent shall autonomously reassemble the segments to the entire file after last segment was received.
				- Manager sets fulState = md5check
				  Agent performs the MD5 check (optional, if fulMD5 is not empty), sets fulResultOk and fulResultString accordingly and finally
				  Agent sets fulState = md5checkDone
				- Manager gets fulState in a loop until fulState = md5checkDone
				- Manager gets fulResultOk and fulResultString
				  Manager gives corresponding user feedback.
				- Manager sets fulState = idle
				  Upon this, the Agent resets fulResultOk to false and fulFilename, fulMD5, fulUploadURL and fulResultString to empty string."
			::= { commonDeviceFileTransfer 1 }
		
		-- 1.3.6.1.4.1.331.1.2.1.1.8.1.1
		fulState OBJECT-TYPE
			SYNTAX INTEGER
				{
				idle(1),
				preparation(2),
				inProgress(3),
				md5check(4),
				md5checkDone(5)
				}
			MAX-ACCESS read-write
			STATUS current
			DESCRIPTION
				"File upload state.
				
				idle:
				State idle indicates that no file upload is active.
				Initial and final state.
				State transition back to idle is always initiated by the SNMP Manager and has to be possible out of any state (including idle).
				Upon this, the Agent resets fulResultOk to false and all the other objects to the default values listed in the file upload preconditions above.
				
				preparation:
				File upload preparation state, the SNMP Manager provides name and MD5 hash of the file to be uploaded. The SNMP Agent provides the upload URL.
				State transition to preparation is always initiated by the SNMP Manager.
				
				inProgress:
				State where the actual HTTP file upload takes place.
				State transition to inProgress is always initiated by the SNMP Manager.
				
				md5check:
				State after the actual HTTP file upload is finished, where the SNMP Agent verifies the upload result by a MD5 checksum test.
				State transition to md5check is always initiated by the SNMP Manager.
				
				md5checkDone:
				Upload verification is finished, SNMP Agent provides the result to the SNMP Manager (fulResultOk and fulResultString prepared accordingly by the SNMP Agent).
				State transition to md5checkDone is always initiated by the SNMP Agent."
			::= { fUpload 1 }
		
		-- 1.3.6.1.4.1.331.1.2.1.1.8.1.2
		fulSegmentationSupported OBJECT-TYPE
			SYNTAX TruthValue
			MAX-ACCESS read-only
			STATUS current
			DESCRIPTION
				"Indicates whether the Agent supports segmented file upload or not."
			::= { fUpload 2 }
		
		-- 1.3.6.1.4.1.331.1.2.1.1.8.1.3
		fulFilename OBJECT-TYPE
			SYNTAX OCTET STRING
			MAX-ACCESS read-write
			STATUS current
			DESCRIPTION
				"Name of file to upload.
				Set only allowed if fulState = preparation."
			::= { fUpload 3 }
		
		-- 1.3.6.1.4.1.331.1.2.1.1.8.1.4
		fulMD5 OBJECT-TYPE
			SYNTAX OCTET STRING (SIZE (0 | 32))
			MAX-ACCESS read-write
			STATUS current
			DESCRIPTION
				"128 bit MD5 hash of file to upload represented as a sequence of 32 hexadecimal lowercase characters.
				Set only allowed if fulState = preparation."
			::= { fUpload 4 }
		
		-- 1.3.6.1.4.1.331.1.2.1.1.8.1.5
		fulUploadURL OBJECT-TYPE
			SYNTAX OCTET STRING
			MAX-ACCESS read-only
			STATUS current
			DESCRIPTION
				"URL for file upload to be used by the Manager together with the HTTP POST command."
			::= { fUpload 5 }
		
		-- 1.3.6.1.4.1.331.1.2.1.1.8.1.6
		fulResultOk OBJECT-TYPE
			SYNTAX TruthValue
			MAX-ACCESS read-only
			STATUS current
			DESCRIPTION
				"File upload result, indicates whether file upload was successful or not.
				
				Value only valid if fulState = md5checkDone 
				or any state transition responded an error code."
			::= { fUpload 6 }
		
		-- 1.3.6.1.4.1.331.1.2.1.1.8.1.7
		fulResultString OBJECT-TYPE
			SYNTAX OCTET STRING
			MAX-ACCESS read-only
			STATUS current
			DESCRIPTION
				"Detailed description of file upload result.
				Syntax: 'E'(rror)|'W'(arning)|'I'(nfo)+': <Result text>' or empty string.
				
				Possible result strings (examples):
				- 'I: File upload successfully finished'
				- 'W: File upload successfully finished but MD5 checksum not tested'
				   possible if fulMD5 is empty (optional step in workflow) when fulState = md5check
				- 'E: File <fulFilename> not found'
				- 'E: MD5 checksum error'
				
				Value only valid if fulState = md5checkDone 
				or any state transition responded an error code."
			::= { fUpload 7 }
		
		-- 1.3.6.1.4.1.331.1.2.1.1.8.1.8
		fulDestFolder OBJECT-TYPE
			SYNTAX OCTET STRING
			MAX-ACCESS read-write
			STATUS current
			DESCRIPTION
				"V1.5.0.0 extension:
				Destination folder of file to upload. If the folder does not yet exist, the Agent has to create it 
				during the SET request. 
				Path separator character is the slash '/'. 
				This may be an absolute (leading slash) or relative path (no leading slash) to the HTTP server 
				file transfer root folder at Agent side. 
				
				It has to be considered that there may be or may not be a trailing slash during GET or SET requests.
				
				Set only allowed if fulState = preparation."
			::= { fUpload 8 }
		
		-- 1.3.6.1.4.1.331.1.2.1.1.9
		commonDeviceSwUpdateActivationRemoval OBJECT-IDENTITY
			STATUS current
			DESCRIPTION 
				"Objects to control Agent software update, activation or removal.
				If the Agent doesn't support software update/activation/removal at all, always 'no such object' 
				has to be returned to any request within this section.
				
				General:
				- Any state transition not shown in the state diagram (except state transcision to idle - see idle description) 
				  is not allowed and should respond an SNMP error code. Before responding the error code, fulStateResultOk 
				  and fulStateResultString should be prepared accordingly.
				- swActivePackageVersion and swActivePackagePatchLevel show the version and patch level of the actual active 
				  SW package at the Agent.
				- swPackagesTable lists always all SW packages that are available at the Agent.
				  Note: Depending on the Agent implementation swPackagesTable may list one (NodeA), two (NodeAM) or 
				  several (ION) available packages.
				
				Preconditions for SW update (all workflows) are:
				- swState = idle (default at Agent startup)
				- swStateResultOk and swActivationForced = false (default at Agent startup)
				- swPackageVersion, swStateResultString and swNeededFilesTable are empty (defaults at Agent startup)
				- swPackagePatchLevel = 0 (default at Agent startup)
				
				Workflow SW update - file transfer:
				- Manager sets swPackageVersion
				- Manager sets swPackagePatchLevel
				- Manager sets swState = versionReq
				  Manager performs file upload of the SW package TOC file
				- Manager sets swState = prepareVersionRsp
				  Agent analyzes the TOC file, updates swNeededFilesTable accordingly, 
				  sets swStateResultOk and swStateResultString accordingly and finally
				  Agent sets swState = versionRsp
				- Manager gets swState in a loop until swState = versionRsp
				- Manager gets swStateResultOk and swStateResultString 
				  Manager gives corresponding user feedback.
				- Manager sets swState = fileTransfer
				  Manager sends all necessary files to the Agent using File Upload (commonDeviceFileTransfer.fUpload)
				- If all files are uploaded, 
				  Manager sets swState = fileTransferDone
				  Agent updates swPackagesTable with the actual transferred package swPackageVersion / swPackagePatchLevel 
				  before sending the SNMP SET response.
				- Manager can go on with
				  package activation or
				  cancel (back to idle)
				
				Workflow SW update - package activation:
				- Manager sets swPackageVersion
				- Manager sets swPackagePatchLevel
				- Manager sets swActivationForced accordingly (default should be 'false')
				- Manager sets swState = versionActivation
				  Agent performs the neccessary actions to activate the SW package (package uncompression, 
				  database migration if not up to date, distribute SW to sub components,...), 
				  provides regular SW activation notifications (swActivationProgress, swState = versionActivation 
				  and progress info in swStateResultString), 
				  sets swStateResultOk and swStateResultString accordingly and finally
				  Agent sets swState = versionActivationOrRemovalDone and 
				  sends final SW activation notification (swState = versionActivationOrRemovalDone)
				- Manager processes received SW activation notifications and gives corresponding user feedback
				- Manager waits for final SW activation notification and (optional, only with AlwaysOn connection)
				  may get the swState in a loop until swState = versionActivationOrRemovalDone
				  In case of timeout waiting for the final SW activation notification (which may get lost if not send as inform) 
				  the Manager finally gets swState, swStateResultOk and swStateResultString
				- Manager gives corresponding final user feedback.
				- Note: Depending on the Agent implementation package activation may force an Agent restart / reboot. 
				  Nevertheless the Agent should provide the final SW activation notification during startup.
				  If the Agent is not able to do this (see also alarmTrapCounter description), 
				  the agentUpAndRunningEvent indicates the end of the package activation. 
				  If in this case within the agentUpAndRunningEvent the reported swActivePackageVersion 
				  is equal to the requested swPackageVersion and the reported swActivePackagePatchLevel 
				  is equal to the requested swPackagePatchLevel the package activation was successful, otherwise not.
				  The Manager has to consider this issue.
				
				Workflow SW update - package removal:
				- Manager sets swPackageVersion
				- Manager sets swPackagePatchLevel
				- Manager sets swState = versionRemoval
				  Agent performs the neccessary actions to remove the SW package, removes corresponding swPackageVersion / swPackagePatchLevel 
				  entry from swPackagesTable, sets swStateResultOk and swStateResultString accordingly and finally
				  Agent sets swState = versionActivationOrRemovalDone
				- Manager gets swState in a loop until swState = versionActivationOrRemovalDone
				- Manager gets swStateResultOk and swStateResultString 
				  Manager gives corresponding user feedback.
				- Note: Depending on the Agent implementation package removal may not be supported. In this case the Agent should 
				  respond an appropriate error like during an invalid state transicion (see General above).
				
				Workflow cancel SW update:
				- Manager sets swState = idle
				  Upon this, the Agent resets swStateResultOk to false and all the other objects to the default values 
				  listed in the SW update preconditions above.
				
				
				V1.5.3.0 workflow extensions - immediate file activation after upload: 
				Manager detects swNeededFilesImmediateActivationRequired=true during fileTransfer after successful upload of a file. 
				In this case: 
				- Manager stops continuing fileTransfer of the remaining files by setting swState = fileTransferDone 
				  and continues with SW package activation immediately. 
				- Manager waits for file activation synchronization notification identified by swNeededFilesImmediateActivationSync. 
				- Agent performs corresponding file activation actions on SW package activation request and 
				  sends corresponding file activation synchronization notification when finished (reboot may take place). 
				- Manager immediately starts SW update file transfer newly for the remaining files to upload. 
				  In this case the Agent might not request previously uploaded and already activated files again, 
				  otherwise there will be an endless upload/activation loop. 
				  If there are no remaining files to upload: 
				- Manager verifies the overall SW package activation result.
				Note:
				Relevant for the overall SW package activation result is just the SW package version / result 
				information sent with the file activation finished synchronization notification for the 
				last file within swNeededFilesTable. For all other intermediate file activations the SW package
				version information may be not available or empty resp. the result may be false.
				In case the last file within swNeededFilesTable does not need immediate activation, 
				swFinalActivationNotification is relevant for the overall SW package activation result. 
				If the swFinalActivationNotification object is not available, the Manager has to assume the agentUpAndRunningEvent."
			::= { commonDeviceObjects 9 }
		
		-- 1.3.6.1.4.1.331.1.2.1.1.9.1
		swActivePackageVersion OBJECT-TYPE
			SYNTAX Version
			MAX-ACCESS read-only
			STATUS current
			DESCRIPTION
				"Version of the actual active SW package at the Agent.
				Typically this version is equal to basicAgentVersion but e.g. in distributed systems it may differ."
			::= { commonDeviceSwUpdateActivationRemoval 1 }
		
		-- 1.3.6.1.4.1.331.1.2.1.1.9.2
		swActivePackagePatchLevel OBJECT-TYPE
			SYNTAX PositiveIntegerIncludingZero
			MAX-ACCESS read-only
			STATUS current
			DESCRIPTION
				"Patch level of the actual active SW package at the Agent."
			::= { commonDeviceSwUpdateActivationRemoval 2 }
		
		-- 1.3.6.1.4.1.331.1.2.1.1.9.3
		swPackagesTable OBJECT-TYPE
			SYNTAX SEQUENCE OF SwPackagesEntry
			MAX-ACCESS not-accessible
			STATUS current
			DESCRIPTION
				"This table lists all SW packages that are available at the Agent."
			::= { commonDeviceSwUpdateActivationRemoval 3 }
		
		-- 1.3.6.1.4.1.331.1.2.1.1.9.3.1
		swPackagesEntry OBJECT-TYPE
			SYNTAX SwPackagesEntry
			MAX-ACCESS not-accessible
			STATUS current
			DESCRIPTION
				"Description."
			INDEX { swPackagesIdx }
			::= { swPackagesTable 1 }
		
		SwPackagesEntry ::=
			SEQUENCE { 
				swPackagesIdx
					PositiveIntegerButNotZero,
				swPackagesAvailable
					Version,
				swPackagesPatchlevel
					PositiveIntegerIncludingZero
			 }

		-- 1.3.6.1.4.1.331.1.2.1.1.9.3.1.1
		swPackagesIdx OBJECT-TYPE
			SYNTAX PositiveIntegerButNotZero
			MAX-ACCESS not-accessible
			STATUS current
			DESCRIPTION
				"Table index."
			::= { swPackagesEntry 1 }
		
		-- 1.3.6.1.4.1.331.1.2.1.1.9.3.1.2
		swPackagesAvailable OBJECT-TYPE
			SYNTAX Version
			MAX-ACCESS read-only
			STATUS current
			DESCRIPTION
				"Version of available SW package."
			::= { swPackagesEntry 2 }
		
		-- 1.3.6.1.4.1.331.1.2.1.1.9.3.1.3
		swPackagesPatchlevel OBJECT-TYPE
			SYNTAX PositiveIntegerIncludingZero
			MAX-ACCESS read-only
			STATUS current
			DESCRIPTION
				"Patch level of available SW package."
			::= { swPackagesEntry 3 }
		
		-- 1.3.6.1.4.1.331.1.2.1.1.9.4
		swState OBJECT-TYPE
			SYNTAX INTEGER
				{
				idle(1),
				versionReq(2),
				prepareVersionRsp(3),
				versionRsp(4),
				fileTransfer(5),
				fileTransferDone(6),
				versionActivation(7),
				versionActivationOrRemovalDone(8),
				versionRemoval(9)
				}
			MAX-ACCESS read-write
			STATUS current
			DESCRIPTION
				"SW update / activation / removal state.
				
				idle:
				State idle indicates that no SW update / activation / removal is active.
				Initial state.
				State transition back to idle is always initiated by the SNMP Manager and has to be possible out of any state (including idle).
				Upon this, the Agent resets swStateResultOk to false and all the other objects to the default values listed in the SW update preconditions above.
				
				versionReq:
				SW update version request state, the SNMP Manager provides details of new SW package (file upload of TOC file) to the SNMP Agent.
				State transition to versionReq is always initiated by the SNMP Manager.
				
				prepareVersionRsp:
				During prepareVersionRsp state the Agent analyzes the TOC file. The Agent prepares the information which files are needed to be uploaded for the new SW package and which SW packages are already available at the Agent.
				State transition to prepareVersionRsp is always initiated by the SNMP Manager.
				
				versionRsp:
				In state versionRsp the Agent provides the data prepared during prepareVersionRsp and the data is ready to be read by the Manager.
				State transition to versionRsp is always initiated by the SNMP Agent.
				
				fileTransfer:
				State where the actual HTTP file upload of all the needed files of the new SW package takes place.
				State transition to fileTransfer is always initiated by the SNMP Manager.
				
				fileTransferDone:
				File transter is finished, new SW package is available at the Agent and is ready for activation.
				State transition to fileTransterDone is always initiated by the SNMP Manager.
				
				versionActivation:
				During versionActivation the Agent performs all necessary activities to activate the new SW package version. If during version activation the Agent has to reboot, the state has to be preserved.
				State transition to versionActivation is always initiated by the SNMP Manager.
				
				versionActivationOrRemovalDone:
				SW package activation or removal is finished.
				Final state.
				State transition to versionActivationOrRemovalDone is always initiated by the SNMP Agent.
				
				versionRemoval:
				State to initiate the removal of a SW package. The SNMP Manager provides SW package version to the SNMP Agent.
				State transition to versionRemoval is always initiated by the SNMP Manager."
			::= { commonDeviceSwUpdateActivationRemoval 4 }
		
		-- 1.3.6.1.4.1.331.1.2.1.1.9.5
		swPackageVersion OBJECT-TYPE
			SYNTAX Version
			MAX-ACCESS read-write
			STATUS current
			DESCRIPTION
				"Version of new SW package to be updated / activated / removed."
			::= { commonDeviceSwUpdateActivationRemoval 5 }
		
		-- 1.3.6.1.4.1.331.1.2.1.1.9.6
		swPackagePatchLevel OBJECT-TYPE
			SYNTAX PositiveIntegerIncludingZero
			MAX-ACCESS read-write
			STATUS current
			DESCRIPTION
				"Patch level of new SW package to be updated / activated / removed."
			::= { commonDeviceSwUpdateActivationRemoval 6 }
		
		-- 1.3.6.1.4.1.331.1.2.1.1.9.7
		swActivationForced OBJECT-TYPE
			SYNTAX TruthValue
			MAX-ACCESS read-write
			STATUS current
			DESCRIPTION
				"SW package activation 'force' option."
			::= { commonDeviceSwUpdateActivationRemoval 7 }
		
		-- 1.3.6.1.4.1.331.1.2.1.1.9.8
		swStateResultOk OBJECT-TYPE
			SYNTAX TruthValue
			MAX-ACCESS read-only
			STATUS current
			DESCRIPTION
				"Actual state result, indicates whether transition to actual state was successful or not.
				
				Value only valid if swState = versionRsp or versionActivationOrRemovalDone 
				or any state transition responded an error code."
			::= { commonDeviceSwUpdateActivationRemoval 8 }
		
		-- 1.3.6.1.4.1.331.1.2.1.1.9.9
		swStateResultString OBJECT-TYPE
			SYNTAX OCTET STRING
			MAX-ACCESS read-only
			STATUS current
			DESCRIPTION
				"Detailed description of actual state result.
				Syntax: 'E'(rror)|'W'(arning)|'I'(nfo)+': <Result text>' or empty string.
				
				Possible result strings (examples):
				- 'I: SW package <swPackageVersion> successfully uploaded'
				- 'I: SW package <swPackageVersion> successfully activated'
				- 'E: Timeout during file <swuNeededFilesFilename> upload'
				- 'E: SW package <swPackageVersion> activation error'
				- 'E: SW package <swPackageVersion> not available for activation'
				
				Value only valid if swState = versionRsp or versionActivationOrRemovalDone 
				or any state transition responded an error code."
			::= { commonDeviceSwUpdateActivationRemoval 9 }
		
		-- 1.3.6.1.4.1.331.1.2.1.1.9.10
		swNeededFilesTable OBJECT-TYPE
			SYNTAX SEQUENCE OF SwNeededFilesEntry
			MAX-ACCESS not-accessible
			STATUS current
			DESCRIPTION
				"This table lists all files of the new SW package that are not yet available at the Agent.
				
				V1.5.3.0 extension:
				- immediate file activation after upload introduced.
				- in case the Agent requires a specific file upload sequence during swState fileTransfer, 
				  this table has to be filled accordingly by the Agent 
				  and the Manager has to upload the files accordingly:
				  Sequence order ascending according table index."
			::= { commonDeviceSwUpdateActivationRemoval 10 }
		
		-- 1.3.6.1.4.1.331.1.2.1.1.9.10.1
		swNeededFilesEntry OBJECT-TYPE
			SYNTAX SwNeededFilesEntry
			MAX-ACCESS not-accessible
			STATUS current
			DESCRIPTION
				"Description."
			INDEX { swNeededFilesIdx }
			::= { swNeededFilesTable 1 }
		
		SwNeededFilesEntry ::=
			SEQUENCE { 
				swNeededFilesIdx
					PositiveIntegerButNotZero,
				swNeededFilesFilename
					OCTET STRING,
				swNeededFilesFolder
					OCTET STRING,
				swNeededFilesImmediateActivationRequired
					TruthValue,
				swNeededFilesImmediateActivationSync
					OBJECT IDENTIFIER
			 }

		-- 1.3.6.1.4.1.331.1.2.1.1.9.10.1.1
		swNeededFilesIdx OBJECT-TYPE
			SYNTAX PositiveIntegerButNotZero
			MAX-ACCESS not-accessible
			STATUS current
			DESCRIPTION
				"Table index."
			::= { swNeededFilesEntry 1 }
		
		-- 1.3.6.1.4.1.331.1.2.1.1.9.10.1.2
		swNeededFilesFilename OBJECT-TYPE
			SYNTAX OCTET STRING
			MAX-ACCESS read-only
			STATUS current
			DESCRIPTION
				"Name of a needed file which is part of the new SW package."
			::= { swNeededFilesEntry 2 }
		
		-- 1.3.6.1.4.1.331.1.2.1.1.9.10.1.3
		swNeededFilesFolder OBJECT-TYPE
			SYNTAX OCTET STRING
			MAX-ACCESS read-only
			STATUS current
			DESCRIPTION
				"Corresponding folder for swNeededFilesFilename. 
				Path separator character is the slash '/'. 
				This is a relative path (no leading slash) within the new SW package.
				The Manager has to consider that there may be or may not be a trailing slash."
			::= { swNeededFilesEntry 3 }
		
		-- 1.3.6.1.4.1.331.1.2.1.1.9.10.1.4
		swNeededFilesImmediateActivationRequired OBJECT-TYPE
			SYNTAX TruthValue
			MAX-ACCESS read-only
			STATUS current
			DESCRIPTION
				"This object identifies whether the file needs immediate activation after upload or not.
				If this object is not available, the Manager has to assume false."
			::= { swNeededFilesEntry 4 }
		
		-- 1.3.6.1.4.1.331.1.2.1.1.9.10.1.5
		swNeededFilesImmediateActivationSync OBJECT-TYPE
			SYNTAX OBJECT IDENTIFIER
			MAX-ACCESS read-only
			STATUS current
			DESCRIPTION
				"In case swNeededFilesImmediateActivationRequired is true, this object identifies the file 
				activation finished synchronization notification, sent out by the Agent when all steps of the file 
				activation process are done (Agent reboot may be necessary).
				Possible values are null or object not available (in case swNeededFilesImmediateActivationRequired 
				is false or not available) resp. either the agentUpAndRunningEvent or 
				swActivationProgress (swState=versionActivationOrRemovalDone) notification, because just this two 
				notifications contain corresponding SW package version information the Manager can use to verify 
				the activation result.
				
				Note:
				Relevant for the overall SW package activation result is just the SW package version / result 
				information sent with the file activation finished synchronization notification for the 
				last file within swNeededFilesTable. For all other intermediate file activations the SW package
				version information may be not available or empty resp. the result may be false.
				In case the last file within swNeededFilesTable does not need immediate activation, 
				swFinalActivationNotification is relevant for the overall SW package activation result."
			::= { swNeededFilesEntry 5 }
		
		-- 1.3.6.1.4.1.331.1.2.1.1.9.11
		swFinalActivationNotification OBJECT-TYPE
			SYNTAX OBJECT IDENTIFIER
			MAX-ACCESS read-only
			STATUS current
			DESCRIPTION
				"This object identifies the final SW package activation finished notification, sent out by the Agent 
				at the end of a SW package activation when all steps of the activation process are done.
				Possible values are either the agentUpAndRunningEvent or 
				swActivationProgress (swState=versionActivationOrRemovalDone) notification, because just this two 
				notifications contain corresponding SW package version information the Manager can use to verify 
				the activation result.
				If this object is not available, the Manager has to assume the agentUpAndRunningEvent."
			::= { commonDeviceSwUpdateActivationRemoval 11 }
		
		-- 1.3.6.1.4.1.331.1.2.1.1.9.20
		swActivationProgress NOTIFICATION-TYPE
			OBJECTS { sysName, alarmTrapCounter, connAgentUID, swState, swPackageVersion, 
				swPackagePatchLevel, swStateResultOk, swStateResultString }
			STATUS current
			DESCRIPTION 
				"This notification is sent to provide SW package activation progress information to the Manager.
				
				Progress information strings during activation come with swState = versionActivation and
				final notification when activation is finished comes with swState = versionActivationOrRemovalDone. 
				swStateResultOk and swStateResultString indicate the final result."
			::= { commonDeviceSwUpdateActivationRemoval 20 }
		
		-- 1.3.6.1.4.1.331.1.2.1.2
		groupNodeM OBJECT-IDENTITY
			STATUS current
			DESCRIPTION 
				"Placeholder for all Node products."
			::= { wirelessInnovationsProducts 2 }
		
		-- 1.3.6.1.4.1.331.1.2.1.3
		groupBCELL OBJECT-IDENTITY
			STATUS current
			DESCRIPTION 
				"Placeholder for all Brite-Cell products."
			::= { wirelessInnovationsProducts 3 }
		
		-- 1.3.6.1.4.1.331.1.2.1.4
		groupAMR OBJECT-IDENTITY
			STATUS current
			DESCRIPTION 
				"Placeholder for all AMR products."
			::= { wirelessInnovationsProducts 4 }
		
		-- 1.3.6.1.4.1.331.1.2.1.5
		groupMiniRepeater OBJECT-IDENTITY
			STATUS current
			DESCRIPTION 
				"Placeholder for all miniRepeater products"
			::= { wirelessInnovationsProducts 5 }
		
		-- 1.3.6.1.4.1.331.1.2.1.6
		groupION OBJECT-IDENTITY
			STATUS current
			DESCRIPTION 
				"Placeholder for all ION products."
			::= { wirelessInnovationsProducts 6 }
		
		-- 1.3.6.1.4.1.331.1.2.1.6.1
		ionM OBJECT-IDENTITY
			STATUS current
			DESCRIPTION 
				"ION-M section."
			::= { groupION 1 }
		
		-- 1.3.6.1.4.1.331.1.2.1.6.2
		ionB OBJECT-IDENTITY
			STATUS current
			DESCRIPTION 
				"ION-B section."
			::= { groupION 2 }
		
		-- 1.3.6.1.4.1.331.1.2.1.6.3
		ionU OBJECT-IDENTITY
			STATUS current
			DESCRIPTION 
				"ION-U section."
			::= { groupION 3 }
		
	
	END

--
-- WIRELESS-INNOVATIONS-PRODUCTS-MIB.mib
--
