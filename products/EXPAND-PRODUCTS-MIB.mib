--
-- EXPAND-PRODUCTS-MIB.my
-- MIB generated by MG-SOFT Visual MIB Builder Version 3.0 Build 253
-- Sunday, July 28, 2002 at 07:55:48
--

-- 
-- Expand Networks. Products.
-- Product Line MIB Version 1.0.8

	EXPAND-PRODUCTS-MIB DEFINITIONS ::= BEGIN
 
		IMPORTS
			expandProducts			
				FROM EXPAND-NETWORKS-SMI;
	
	
--
-- Node definitions
--
	
		-- 1.1
		accelerator4000 OBJECT IDENTIFIER ::= { expandProducts 1 }
		
		-- 1.2
		accelerator2700 OBJECT IDENTIFIER ::= { expandProducts 2 }
		
		-- 1.3
		accelerator4800 OBJECT IDENTIFIER ::= { expandProducts 3 }
		
		-- 1.4
		accelerator2800 OBJECT IDENTIFIER ::= { expandProducts 4 }
		
		-- 1.5
		accelerator1800 OBJECT IDENTIFIER ::= { expandProducts 5 }
		
		-- 1.6
		accelerator4802 OBJECT IDENTIFIER ::= { expandProducts 6 }
		
	
	END

--
-- EXPAND-PRODUCTS-MIB.my
--
