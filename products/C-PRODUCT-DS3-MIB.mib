C-PRODUCT-DS3-MIB DEFINITIONS ::= BEGIN


IMPORTS
    ds3card                           FROM C-PRODUCT-GROUP-MIB
    portSlot, portNumber, TimeAndDate FROM C-PRODUCT-BASE-MIB
    Gauge                             FROM RFC1155-SMI
    OBJECT-TYPE                       FROM RFC-1212;

-- DS3 groups

ds3Port      OBJECT IDENTIFIER ::= { ds3card 1 }
ds3PortStats OBJECT IDENTIFIER ::= { ds3card 2 }
ds3PortClearStats OBJECT IDENTIFIER ::= { ds3card 3 }

-- DS3 Port Group (ds3Port)

ds3PortTable OBJECT-TYPE
    SYNTAX SEQUENCE OF Ds3PortEntry
    ACCESS not-accessible
    STATUS mandatory
    DESCRIPTION
            "The DS3 port information table."
    ::= { ds3Port 1 }

ds3PortEntry OBJECT-TYPE
    SYNTAX Ds3PortEntry
    ACCESS not-accessible
    STATUS mandatory
    DESCRIPTION
            "Information about a DS3 port."
    INDEX { portSlot, portNumber }
    ::= { ds3PortTable 1 }

Ds3PortEntry ::=
    SEQUENCE {
        ds3PortLoopbackType
            INTEGER,
        ds3PortLboLength
            INTEGER,
        ds3PortPeakRate
            INTEGER,
        ds3PortFraming
            INTEGER,
        ds3PortCellMap
            INTEGER,
        ds3PortScramble
            INTEGER,
        ds3PortTiming
            INTEGER,
        ds3PortPlcpTiming
            INTEGER,
        ds3PortCtxTiming
            INTEGER,
        ds3PortFeacLoopback
            INTEGER,
        ds3PortLineRate
            INTEGER
    }

ds3PortLoopbackType OBJECT-TYPE
    SYNTAX INTEGER { none        (1), -- no loopback
                     networkLine (2),
                     localCard   (3),
                     networkCard (4) }
    ACCESS read-write
    STATUS mandatory
    DESCRIPTION
            "Loopback type of the DS3 port."
    DEFVAL { none }
    ::= { ds3PortEntry 1 }

ds3PortLboLength OBJECT-TYPE
    SYNTAX INTEGER { lessThan255(1),
                     moreThan255(2) }
    ACCESS read-write
    STATUS mandatory
    DESCRIPTION
            "Cable length for the DS3 port."
    DEFVAL { lessThan255 }
    ::= { ds3PortEntry 2 }

ds3PortPeakRate OBJECT-TYPE
    SYNTAX INTEGER (5..41)
    ACCESS read-write
    STATUS mandatory
    DESCRIPTION
            "Peak data transfer rate of the DS3 port.  Unit: Mbps."
    ::= { ds3PortEntry 3 }

ds3PortFraming OBJECT-TYPE
    SYNTAX INTEGER { cbit(1), 
                     m23(2) }
    ACCESS read-write
    STATUS mandatory
    DESCRIPTION
            "Cbit or M23 framing for the DS3 port."
    DEFVAL { cbit }
    ::= { ds3PortEntry 4 }

ds3PortCellMap OBJECT-TYPE
    SYNTAX INTEGER { clear(1), 
                     plcp(2) }
    ACCESS read-write
    STATUS mandatory
    DESCRIPTION
            "ATM cell mapping for the DS3 port."
    DEFVAL { plcp }
    ::= { ds3PortEntry 5 }

ds3PortScramble OBJECT-TYPE
    SYNTAX INTEGER { no(1), 
                     yes(2) }
    ACCESS read-write
    STATUS mandatory
    DESCRIPTION
            "ATM payload scrambling for the DS3 port."
    DEFVAL { yes }
    ::= { ds3PortEntry 6 }

ds3PortTiming OBJECT-TYPE
    SYNTAX INTEGER { loop(1), 
                     system(2) }
    ACCESS read-write
    STATUS mandatory
    DESCRIPTION
            "DS3 timing source."
    DEFVAL { system }
    ::= { ds3PortEntry 7 }

ds3PortPlcpTiming OBJECT-TYPE
    SYNTAX INTEGER { ds3Timing(1), 
                     systemClock(2) }
    ACCESS read-write
    STATUS mandatory
    DESCRIPTION
            "PLCP timing source for the DS3 port."
    DEFVAL { ds3Timing }
    ::= { ds3PortEntry 8 }

ds3PortCtxTiming OBJECT-TYPE
    SYNTAX INTEGER { plcpClock(1), 
                     ds3rxClock(2) }
    ACCESS read-write
    STATUS mandatory
    DESCRIPTION
            "CTX timing source from the DS3 port."
    DEFVAL { ds3rxClock }
    ::= { ds3PortEntry 9 }

ds3PortFeacLoopback OBJECT-TYPE
    SYNTAX INTEGER { disable(1), 
                     enable(2) }
    ACCESS read-write
    STATUS mandatory
    DESCRIPTION
            "FEAC loopback for the DS3 port."
    DEFVAL { disable }
    ::= { ds3PortEntry 10 }

ds3PortLineRate OBJECT-TYPE
    SYNTAX INTEGER 
    ACCESS read-only
    STATUS mandatory
    DESCRIPTION
            "Physical Line data transfer rate of the DS3 port. Unit: CPS."
    ::= { ds3PortEntry 11 }


-- DS3 Port Stats Group (ds3PortStats)

ds3PortStatsTable OBJECT-TYPE
    SYNTAX SEQUENCE OF Ds3PortStatsEntry
    ACCESS not-accessible
    STATUS mandatory
    DESCRIPTION
            "The DS3 port stats information table."
    ::= { ds3PortStats 1 }

ds3PortStatsEntry OBJECT-TYPE
    SYNTAX Ds3PortStatsEntry
    ACCESS not-accessible
    STATUS mandatory
    DESCRIPTION
            "Information about a DS3 port stats."
    INDEX { portSlot, portNumber }
    ::= { ds3PortStatsTable 1 }

Ds3PortStatsEntry ::=
    SEQUENCE {
	ds3PortRxCells
	    Gauge,
	ds3PortTxCells
	    Gauge,
	ds3PortIdleUnassignedCells
	    Gauge,
	ds3PortHCSErrorCells
	    Gauge,
	ds3PortResetTimeDate
	    TimeAndDate,
	ds3PortResetStats
            INTEGER,
	ds3PortUtilRxCells
	    INTEGER,
	ds3PortUtilTxCells
	    INTEGER
    }

ds3PortRxCells OBJECT-TYPE
    SYNTAX  Gauge
    ACCESS  read-only
    STATUS  mandatory
    DESCRIPTION
            "The counter associated with the received cells, encountered
            on the ATM interface."
    ::= { ds3PortStatsEntry 1 }

ds3PortTxCells OBJECT-TYPE
    SYNTAX  Gauge
    ACCESS  read-only
    STATUS  mandatory
    DESCRIPTION
            "The counter associated with the transmitted cells, encountered
            on the ATM interface."
    ::= { ds3PortStatsEntry 2 }

ds3PortIdleUnassignedCells OBJECT-TYPE
    SYNTAX  Gauge
    ACCESS  read-only
    STATUS  mandatory
    DESCRIPTION
            "The counter associated with the idle/unassigned cells, encountered
            on the ATM interface."
    ::= { ds3PortStatsEntry 3 }

ds3PortHCSErrorCells OBJECT-TYPE
    SYNTAX  Gauge
    ACCESS  read-only
    STATUS  mandatory
    DESCRIPTION
            "The counter associated with the HCS errored cells, encountered
            on the ATM interface."
    ::= { ds3PortStatsEntry 4 }

ds3PortResetTimeDate OBJECT-TYPE
    SYNTAX  TimeAndDate
    ACCESS  read-only
    STATUS  mandatory
    DESCRIPTION
            "The reset time and date of ATM stats on this ATM interface."
    ::= { ds3PortStatsEntry 5 }

ds3PortResetStats OBJECT-TYPE
    SYNTAX  INTEGER { reset (1) }
    ACCESS  write-only
    STATUS  mandatory
    DESCRIPTION
            "This field is used to reset the atm statistics for the ds3 port.
             If a get is performed on this command, the result will always 
             be zero"
    ::= { ds3PortStatsEntry 6 }

ds3PortUtilRxCells OBJECT-TYPE
    SYNTAX  INTEGER 
    ACCESS  read-only
    STATUS  mandatory
    DESCRIPTION
            "The Utilization of received Cell is calculated as 
             received cells divided by Line Rate."
    ::= { ds3PortStatsEntry 7 }

ds3PortUtilTxCells OBJECT-TYPE
    SYNTAX  INTEGER 
    ACCESS  read-only
    STATUS  mandatory
    DESCRIPTION
            "The Utilization of transmitted Cell is calculated as 
             transmitted cells divided by Line Rate.  "
    ::= { ds3PortStatsEntry 8 }

ds3PortClearStatsTable OBJECT-TYPE
    SYNTAX SEQUENCE OF Ds3PortClearStatsEntry
    ACCESS not-accessible
    STATUS mandatory
    DESCRIPTION
            "This table is used to reset the performance monitoring data
	     for ds3 port."
    ::= { ds3PortClearStats 1 } 

ds3PortClearStatsEntry OBJECT-TYPE
    SYNTAX Ds3PortClearStatsEntry
    ACCESS not-accessible
    STATUS mandatory
    DESCRIPTION
            "Information about a DS3 port."
    INDEX { portSlot, portNumber }
    ::= { ds3PortClearStatsTable 1 }

Ds3PortClearStatsEntry ::=
	SEQUENCE 
	{
	     ds3PortResetPMData	
		INTEGER 
	}	

ds3PortResetPMData OBJECT-TYPE
    SYNTAX  INTEGER { reset (1) }
    ACCESS  write-only
    STATUS  mandatory
    DESCRIPTION
            "This field is used to reset the performance monitoring 
	     data for the ds3 port.  If a get is performed on this command, 
	     the result will always be zero"
    ::= { ds3PortClearStatsEntry 1 } 

END
