SALIX-PRODUCTS-MIB DEFINITIONS ::= BEGIN

IMPORTS
         OBJECT-IDENTITY, MODULE-IDENTITY, OBJECT-TYPE, Unsigned32          FROM SNMPv2-SMI

         salixRegistrations, salixGroups,
         salixProducts, salixGeneric      FROM SALIX-MIB;
         
-- Define the SALIX Technologies node and define the HNE MIB beneath it

salixProductsMIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB containing OID Values for SALIX products"
     ::= { salixGeneric 1 }         
         
         
-- Hne product information

  hne               OBJECT IDENTIFIER ::= { salixRegistrations 1 }

  hneAgent          OBJECT IDENTIFIER ::= { salixRegistrations 2 }

  hneAgentMajorVersion OBJECT-TYPE
               SYNTAX         Unsigned32
               MAX-ACCESS     read-only
               STATUS         current
               DESCRIPTION
                              "An entry in the dDownloadTable that
           identifies the parameters necessary to download software to
           plug-in unit(s)."
               ::= { hneAgent 1 }

  hneAgentSubVersion OBJECT-TYPE
                 SYNTAX         Unsigned32
                 MAX-ACCESS     read-only
                 STATUS         current
                 DESCRIPTION
                                "An entry in the hneSysHrSWInstalledDownloadTable that
             identifies the parameters necessary to download software to
             plug-in unit(s)."
                 ::= { hneAgent 2 }
                 

-- ITX Product Information
                 
   itx            OBJECT-IDENTITY
      STATUS      current
      DESCRIPTION
         "The IT-XChange product OID"
   ::= { salixRegistrations 3 }

END
