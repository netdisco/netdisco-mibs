-- *****************************************************************
--
-- stn-products.mib:  
--      Spring Tide Networks Product Object Identifier Assignments
--
--
--      Copyright (c) 1999, 2000 by Spring Tide Networks, Inc.
--                      ALL RIGHTS RESERVED       
--
-- *****************************************************************

-- Top level object definitions for Spring Tide Network Enterprise MIB

STN-PRODUCTS-MIB DEFINITIONS ::= BEGIN
  
    IMPORTS
        MODULE-IDENTITY
            FROM SNMPv2-SMI

        OBJECT-GROUP,
        MODULE-COMPLIANCE        
            FROM SNMPv2-CONF

        stnMibModules,
        stnProducts
            FROM SPRING-TIDE-NETWORKS-SMI;


   stnProductsMIB MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "The initial revision."
        REVISION        "9905010000Z"

        DESCRIPTION
            "This MIB module defines MIB objects which provide
             mechanisms to remotely monitor the parameters used
             by an SNMP entity for the generation of SNMP messages."
       ::= { stnMibModules 2 }


    -- The products section is mostly used to define the sysObjectId
    -- values for various products.  

    stn5000     OBJECT IDENTIFIER ::= { stnProducts 1 }


END
