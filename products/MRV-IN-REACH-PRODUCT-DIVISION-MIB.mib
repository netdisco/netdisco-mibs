-- $Id: ir-mib.mib,v 1.1 2002/06/27 15:38:10 sse Exp $
            MRV-IN-REACH-PRODUCT-DIVISION-MIB DEFINITIONS ::= BEGIN

                    IMPORTS
 enterprises FROM RFC1155-SMI;



            mrvInReachProductDivision     OBJECT IDENTIFIER ::= { enterprises 33 }
            agent           OBJECT IDENTIFIER ::= { mrvInReachProductDivision 8 }

            -- This is a MIB module for all MRV Communications In-Reach 
            -- Products Division systems.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- Textual Conventions

            -- This data type is used throughout the mrvInReachProductDivision private MIB
            -- to model an absolute date and time.
            -- In order, the octets contain the following information:
            -- century, year within century (0..99), month (1..12),
            -- day (1..31), hour (0..23), minute (0..59),
            -- second (0..59), hundredth (0..99).  If the century
            -- value is zero, the date and time are unknown, and the
            -- other values are meaningless.

            DateTime ::=
                OCTET STRING (SIZE (8))

            -- This data type is used throughout the mrvInReachProductDivision private MIB
            -- to indicate the type of an address stored in a related
            -- octet string.

            AddressType ::=
                INTEGER  { 
                           unknown(1), 
                           other(2), 
                           local(3),
                           ip(4), 
                           ethernet(5) 
                         }

            -- This data type is used throughout the mrvInReachProductDivision private MIB
            -- to indicate an address with a type attached.  The type is
            -- the first byte.  The address immediately follows the
            -- type, occupying the appropriate number of bytes, (0..31).
            -- The type values are:
            --     1   unknown
            --     2   other
            --     3   local
            --     4   ip
            --     5   ethernet

            TypedAddress ::=
                OCTET STRING (SIZE (1..32))

            -- This data type is used throughout the mrvInReachProductDivision private MIB
            -- to indicate the type of software running on a system. 

            SoftwareType ::=
                INTEGER  { 
                           terminalServer(1), 
                           bridge(3), 
                           repeater(4),
                           bridgeRouter(5), 
                           router(6),
                           bridgeRouterRepeater(7), 
                           switch(8), 
                           oem(9) 
                         }

            -- This data type is used throughout the mrvInReachProductDivision private MIB
            -- to indicate the type of a system's main function 
            -- hardware.  


            HardwareType ::=
                INTEGER  { 
                           unknown(1),
                           em1608(29), 
                           ir7520(30), 
                           ir9020(31), 
                           ir7020(32),
                           mxTServJ8(33), 
                           mxTservJ16(34), 
                           mxManF2(35),
                           mx1500(36), 
                           mx1100(37), 
                           mx1800(38),
                           mxNpcP1(39), 
                           mxTsrLJ16(40), 
                           mxTsrvLJ8(41), 
                           mxTsrvMj8(42), 
                           mxTsrvNJ8(43), 
                           mxTsrvOJ8(44),
                           mx1400(45), 
                           mx6510(46),
                           mxRb2(47),  
                           mx1500x8(49), 
                           mx1710(50), 
                           mx2710(51),
                           ts3395(52), 
                           mx1120(53), 
                           mx1520(54),
                           mx1820(55), 
                           mx2220(56), 
                           mx3510(57),
                           mx6625(58), 
                           mx2120(59), 
                           mx6020(60),
                           mx3610(61), 
                           etsmim(62), 
                           mx3010(63),
                           mx6025(64), 
                           lannetTs(65), 
                           fn1500(66),
                           dpXp1(67), 
                           mx3710(68), 
                           mx3210(69),
                           mx6710(70), 
                           mx6220(71),
                           mx1600a(74), 
                           mx1450(75),
                           ts720(76), 
                           so3395aTs(77), 
                           mx1608(78),
                           mx2210a(79), 
                           br401(80), 
                           mx6800a(81),
                           notApplicable(83), 
                           rp210(84),
                           mx6800b(85), 
                           mx1620(86), 
                           mx2240(87),
                           ps3m(88), 
                           lb2Wan(89), 
                           nio1600(90),
                           asy160(91), 
                           mx1640(92), 
                           br220(93),
                           rp211(94), 
                           br221(95), 
                           mx2210b(96),
                           mx1600b(97), 
                           mx1600c(98), 
                           mx800a(99),
                           mx1600d(100), 
                           tokenRing(101), 
                           mx800b(102),
                           br501(103), 
                           br350(105), 
                           br350ExpansionSlot(107),
                           n3000(108), 
                           br402(109), 
                           sw610(110), 
                           sw610S(111), 
                           br501s(112),
                           br501c(113), 
                           br501sc(114),
                           routeRunnerIsdnSt(115), 
                           routeRunner(116),
                           mx1608a(117),  
                           routerRunnerIsdnU(118),
                           mx1608b(119),  
                           mx1604(120),  
                           n3000Ias(123),
                           irMgr0Rdc(124), 
                           ir9040(125),
                           ir7040(126),
                           irMgr0(127),
                           irM800(128),
                           irM700(129),
                           ir8020(130),
                           ir8040(131),
                           ir7004(132),
                           ir7008(133),
                           ir8004(134),
                           ir8008(135),
                           irM900(136),
                           irMGR0AC(137),                       
                           irMGR0AC-IN(138),                       
                           ir9004(139),                       
                           ir9008(140),                       
                           ir9504(141),                       
                           n3000SP(230) 
                         }

            -- This data type is used throughout the mrvInReachProductDivision private MIB
            -- to indicate the type of chassis hardware.

            ChassisType ::= 
                 INTEGER { other(1), mx45xx(2), net9000(3), net9000SWITCH(4) }

            -- This data type is used throughout the mrvInReachProductDivision private MIB
            -- to indicate the type of I/O hardware.

            IOType ::=
                 INTEGER { 
                           io616(16),
                           dualE175(32), 
                           dualT1(33), 
                           bri8(34), 
                           io351d(35),
                           io352d(36),
                           dualE1120(37), 
                           singleT1(38), 
                           singleE175(39),
                           singleE1120(40),
                           io625(128),
                           io626(129),
                           io601(144), 
                           io602(145), 
                           io603(146),
                           io601A(147), 
                           io602A(148), 
                           io603A(149),
                           io604(150), 
                           io621(155),  
                           io622(156),
                           io623(157),
                           io624(158), 
                           io301x12(160), 
                           io521(174),
                           io522(175), 
                           io512x3(176), 
                           io511x3(177),
                           io520(178),
                           io514(179), 
                           io513(180), 
                           io470x4(182), 
                           io469x2(183),
                           io467x4(184), 
                           io467x2(185), 
                           io468x4(186),
                           io468x2(187), 
                           io466x4(188), 
                           io465x2(189),
                           io464x4(190), 
                           io463x2(191), 
                           io201(192), 
                           io202(193), 
                           io204(194), 
                           io203(195), 
                           io251(196), 
                           io231(197), 
                           io254(198),
                           io206(199), 
                           io253(200), 
                           io256(201), 
                           io201a(202), 
                           io202a(203), 
                           io203a(204), 
                           ioRepeater(207),
                           io205x12(209),
                           io205(210), 
                           io255(214), 
                           io722(224),
                           io721(225), 
                           io411(226), 
                           io724(227),
                           io725(231),
                           io723(232), 
                           io462(233), 
                           io412(234),
                           ioTS16a(235),  
                           ioTS16b(236),  
                           io461(237), 
                           io101(238), 
                           io119(239) 
                         }


            -- Agent Object Identifiers

            -- A mrvInReachProductDivision agent identifer has the following fields:
            --
            --     mrvInReachProductDivision.agent.software.variant.version
            --
            -- Where:
            --
            --     mrvInReachProductDivision.agent  is an ordinary OID prefix. Note that
            --                         mrvInReachProductDivision's original form for
            --                         such OID's used the value 1 for agent
            --                         and had no variant or version.  Later
            --                         forms included variant and version in
            --                         an inconsistent manner.
            --
            --     software       a value of the mrvInReachProductDivision SoftwareType
            --                    textual convention.
            --
            --     variant        a variant within a software type,
            --                    typically hardware dependent.  If the
            --                    software has no variants, it uses the
            --                    value 1.
            --
            --     version        a version number within the variant,
            --                    increased by one each time that
            --                    variant's agent changes in a way that
            --                    is significant to its MIB
            --                    capabilities description

            -- Terminal Servers

            terminalServer   OBJECT IDENTIFIER ::= { agent 1 }

            --     MAXserver variants, 1M memory
            tsMxCard1M       OBJECT IDENTIFIER ::= { terminalServer 1 }
            tsMxBox1M        OBJECT IDENTIFIER ::= { terminalServer 2 }

            --     MAXserver variants, 1M memory
            tsMxCard         OBJECT IDENTIFIER ::= { terminalServer 3 }
            tsMxBox          OBJECT IDENTIFIER ::= { terminalServer 4 }

            --     Network 9000 variant
            tsN9             OBJECT IDENTIFIER ::= { terminalServer 5 }

            --     Printer controller variant
            tsPrint          OBJECT IDENTIFIER ::= { terminalServer 6 }

            --     X.25 Gateway variant
            tsX25            OBJECT IDENTIFIER ::= { terminalServer 7 }

            --  InReach-Product-Division and Environmental Manager variants. These models
            --  use their hardwareType as the agent variant.
            em1608           OBJECT IDENTIFIER ::= { terminalServer 29 }
            ir7520           OBJECT IDENTIFIER ::= { terminalServer 30 }
            ir9020           OBJECT IDENTIFIER ::= { terminalServer 31 }
            ir7020           OBJECT IDENTIFIER ::= { terminalServer 32 }
            irMgr0Rdc        OBJECT IDENTIFIER ::= { terminalServer 124 }
            ir9040           OBJECT IDENTIFIER ::= { terminalServer 125 }
            ir7040           OBJECT IDENTIFIER ::= { terminalServer 126 }
            irMgr0           OBJECT IDENTIFIER ::= { terminalServer 127 }
            irM800           OBJECT IDENTIFIER ::= { terminalServer 128 }
            irM700           OBJECT IDENTIFIER ::= { terminalServer 129 }
            ir8020           OBJECT IDENTIFIER ::= { terminalServer 130 }
            ir8040           OBJECT IDENTIFIER ::= { terminalServer 131 }
            ir7004           OBJECT IDENTIFIER ::= { terminalServer 132 }
            ir7008           OBJECT IDENTIFIER ::= { terminalServer 133 }
            ir8004           OBJECT IDENTIFIER ::= { terminalServer 134 }
            ir8008           OBJECT IDENTIFIER ::= { terminalServer 135 }
            irM900           OBJECT IDENTIFIER ::= { terminalServer 136 }
            irMGR0AC         OBJECT IDENTIFIER ::= { terminalServer 137 }
            irMGR0AC-IN      OBJECT IDENTIFIER ::= { terminalServer 138 }
            ir9004           OBJECT IDENTIFIER ::= { terminalServer 139 }
            ir9008           OBJECT IDENTIFIER ::= { terminalServer 140 }
            ir9504           OBJECT IDENTIFIER ::= { terminalServer 141 }

            -- Bridges

            bridge                 OBJECT IDENTIFIER ::= { agent 3 }

            -- Repeaters

            repeater               OBJECT IDENTIFIER ::= { agent 4 }

            --     MAXserver variant
            rpMx                   OBJECT IDENTIFIER ::= { repeater 1 }

            --     Network 9000 variant
            rpN9                   OBJECT IDENTIFIER ::= { repeater 2 }

            -- Bridge/Routers

            bridgeRouter           OBJECT IDENTIFIER ::= { agent 5 }

            --     MAXserver variant
            bridgeRouterMx         OBJECT IDENTIFIER ::= { bridgeRouter 1 }

            --     Network 9000 variant
            bridgeRouterN9         OBJECT IDENTIFIER ::= { bridgeRouter 2 }

            -- Network 3000 variant
            bridgeRouterN3         OBJECT IDENTIFIER ::=  { bridgeRouter 3 }

            -- Network 3000 RouteRunner variant
            bridgeRouterN2         OBJECT IDENTIFIER ::=  { bridgeRouter 4 }

            -- EdgeBlaster variant
            bridgeRouterEB         OBJECT IDENTIFIER ::=  { bridgeRouter 5 }

            -- Bridge/Router/Repeaters

            bridgeRouterRepeater   OBJECT IDENTIFIER ::= { agent 7 }

            -- Switches

            switch                 OBJECT IDENTIFIER ::= { agent 8 }

            -- OEM Devices

            oem                    OBJECT IDENTIFIER ::= { agent 9 }

            --     NetVantage variant
            netVantage             OBJECT IDENTIFIER ::= { oem 1 }
            --     NetVantage product variants
            nv8516TT               OBJECT IDENTIFIER ::= { netVantage 1 }
            nv8516FF               OBJECT IDENTIFIER ::= { netVantage 2 }

            -- NBase Devices

            nbase                    OBJECT IDENTIFIER ::= { agent 10 }
            nbaseSwitch              OBJECT IDENTIFIER ::= { nbase 1 }
            nbaseSwitchN9            OBJECT IDENTIFIER ::= { nbaseSwitch 1 }

END
