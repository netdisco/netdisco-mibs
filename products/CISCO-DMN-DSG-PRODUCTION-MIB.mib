--*********************************************************************
-- CISCO-DMN-DSG-PRODUCTION.mib : Mib file for Production Information.
--
-- August 2010, Tel MIB Team
--
--
-- Copyright (c) 1999-2010 by cisco Systems, Inc.
-- All rights reserved.
--*********************************************************************
    
CISCO-DMN-DSG-PRODUCTION-MIB DEFINITIONS ::= BEGIN

IMPORTS 
    MODULE-IDENTITY,
    OBJECT-TYPE,Integer32
        FROM SNMPv2-SMI
   DisplayString
        FROM SNMPv2-TC
    OBJECT-GROUP, MODULE-COMPLIANCE
        FROM SNMPv2-CONF
    ciscoDSGUtilities
        FROM CISCO-DMN-DSG-ROOT-MIB;


ciscoDSGProd MODULE-IDENTITY
    LAST-UPDATED  "201008240700Z" -- August 24 2010 07:00:00 GMT
    ORGANIZATION    "Cisco Systems, Inc."
    CONTACT-INFO   
       "Cisco Systems, Inc.
        Customer Service 
        Postal: 170 W Tasman Drive
        San Jose, CA 95134
        USA  
        Tel: +1 800 553 NETS
        
        E-mail: cs-ipsla@cisco.com"
    DESCRIPTION   "Cisco Production MIB."

    REVISION        "201008240700Z"
    DESCRIPTION     "V01.00.01 2010-08-24
                    Added itmes : prodBoardModelNum,
                    prodBoardModelName, prodBoardCatalogNum,
                    prodBoardCustomerCode and prodBoardFpgaType." 

    REVISION        "200912201200Z"
    DESCRIPTION     "V01.00.00 2009-12-20
                    Initial Version." 

    ::= { ciscoDSGUtilities 21 }

prodInfo                    OBJECT IDENTIFIER ::= { ciscoDSGProd 1 }

--*******************************
-- Production Info Branch
--*******************************

prodHostName  OBJECT-TYPE
    SYNTAX  DisplayString(SIZE(0..14))
    MAX-ACCESS  read-write
    STATUS  current
    DESCRIPTION
        "User Configurable hostname of this Unit."
    ::= { prodInfo 1 }

prodTrackingId  OBJECT-TYPE
    SYNTAX  DisplayString(SIZE(0..12))
    MAX-ACCESS  read-only
    STATUS  current
    DESCRIPTION
        "Unit Tracking ID."
    ::= { prodInfo 2 }

prodModelNo OBJECT-TYPE
    SYNTAX  DisplayString(SIZE(0..49))
    MAX-ACCESS  read-only
    STATUS  current
    DESCRIPTION
        "Model Number."
    ::= { prodInfo  3 }

prodModelName OBJECT-TYPE
    SYNTAX  DisplayString(SIZE(0..49))
    MAX-ACCESS  read-only
    STATUS  current
    DESCRIPTION
        "Model Name."
    ::= { prodInfo 4 }

prodCatalogNo OBJECT-TYPE
    SYNTAX  DisplayString(SIZE(0..49))
    MAX-ACCESS  read-only
    STATUS  current
    DESCRIPTION
        "Catalogue Number."
    ::= { prodInfo 5 }

prodCustomerCode OBJECT-TYPE
    SYNTAX  DisplayString(SIZE(0..49))
    MAX-ACCESS  read-only
    STATUS  current
    DESCRIPTION
        "Customer Code."
    ::= { prodInfo 6 }

prodLimitVer  OBJECT-TYPE
    SYNTAX  DisplayString(SIZE(0..49))
    MAX-ACCESS  read-only
    STATUS  current
    DESCRIPTION
        "Oldest Compatible Application Version."
    ::= { prodInfo 7 }

prodFPGADesignation  OBJECT-TYPE
    SYNTAX  Integer32(0..0)
    MAX-ACCESS  read-only
    STATUS  current
    DESCRIPTION 
        "Production FPGA Designation."
    ::={ prodInfo 8 }

END
