-- *************************************************************************
--
-- SPRING-TIDE-NETWORKS.smi:  
--      Spring Tide Networks Enterprise Structure of Management Information
--
--
--      Copyright (c) 1999, 2000 by Spring Tide Networks, Inc.
--                      ALL RIGHTS RESERVED       
--
-- *************************************************************************


SPRING-TIDE-NETWORKS-SMI DEFINITIONS ::= BEGIN

    IMPORTS
        MODULE-IDENTITY,
        OBJECT-IDENTITY,
        enterprises
                FROM SNMPv2-SMI;

    springtidenet MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "The Structure of Management Information for the
                         Spring Tide Networks enterprise MIBs."
        ::= { enterprises 3551 }        -- assigned by IANA


    stnProducts OBJECT-IDENTITY
        STATUS  current
        DESCRIPTION
                "stnProducts is the root OBJECT IDENTIFIER from
                 which sysObjectID values are assigned.  Actual
                 values are defined in stn-products-mib."
        ::= { springtidenet 1 }

    stnSystems OBJECT-IDENTITY
        STATUS  current
        DESCRIPTION
                "stnSystems is the root OBJECT IDENTIFIER from
                 which sysObjectID values are assigned.  Actual
                 values are defined in stn-???-mib."
        ::= { springtidenet 2 }


   stnExtensions OBJECT-IDENTITY
        STATUS  current
        DESCRIPTION
                "stnExtensions is the root OBJECT IDENTIFIER from
                 which sysObjectID values are assigned.  Actual
                 values are defined in stn-???-mib."
        ::= { springtidenet 3 }


    stnTemporary OBJECT-IDENTITY
        STATUS  current
        DESCRIPTION
                "stnTemporary provides a root object identifier
                 from which temporary mibs may be based.
                 MIBs are typicially based here if they fall in one 
                 of two categories:

                 1) are IETF work-in-process mibs which have not
                 been assigned a permanent object identifier by
                 the IANA.

                 2) are stn work-in-process which has not been
                 assigned a permanent object identifier by the
                 stn assigned number authority, typicially because
                 the mib is not ready for deployment.

                 NOTE WELL:  support for mibs in the stnTemporary
                 subtree will be deleted when a permanent object
                 identifier assignment is made."
        ::= { springtidenet 4 }


    stnMibModules OBJECT-IDENTITY
        STATUS  current
        DESCRIPTION
                "stnModules provides a root object identifier
                 from which MODULE-IDENTITY values may be assigned."
        ::= { springtidenet 5 }


--    stnChassis        OBJECT IDENTIFIER ::= { stnSystems 1 }
--    stnVersion        OBJECT IDENTIFIER ::= { stnSystems 2 }
--    stnInterface      OBJECT IDENTIFIER ::= { stnSystems 3 }
--    stnSystem         OBJECT IDENTIFIER ::= { stnSystems 4 }
--    stnSession        OBJECT IDENTIFIER ::= { stnSystems 5 }
--    stnATM            OBJECT IDENTIFIER ::= { stnSystems 6 }
--    stnRouter         OBJECT IDENTIFIER ::= { stnSystems 7 }
--    stnIKE            OBJECT IDENTIFIER ::= { stnSystems 8 }
--    stnIpSec          OBJECT IDENTIFIER ::= { stnSystems 9 }
--    stnAAA            OBJECT IDENTIFIER ::= { stnSystems 10 }
--    stnPm 		OBJECT IDENTIFIER ::= { stnSystems 11 }
--    stnIpRouting      OBJECT IDENTIFIER ::= { stnSystems 12 }
--    stnLog            OBJECT IDENTIFIER ::= { stnSystems 13 }
--    stnSnmp           OBJECT IDENTIFIER ::= { stnSystems 14 }
--    stnFlash		OBJECT IDENTIFIER ::= { stnSystems 15 }
--    stnTime		OBJECT IDENTIFIER ::= { stnSystems 16 }
--    stnUsers		OBJECT IDENTIFIER ::= { stnSystems 17 }
--    stnFeatures	OBJECT IDENTIFIER ::= { stnSystems 18 }

    stnConfig		    OBJECT IDENTIFIER ::= { stnSystems 99 }
    stnNotificationPrefix   OBJECT IDENTIFIER ::= { stnSystems 100 }
    stnNotification	    OBJECT IDENTIFIER ::= { stnNotificationPrefix 0 }

    stnTmpProtocols	    OBJECT IDENTIFIER ::= { stnTemporary 1 }

END
