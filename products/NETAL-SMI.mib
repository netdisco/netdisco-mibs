NETAL-SMI DEFINITIONS ::= BEGIN

IMPORTS
        MODULE-IDENTITY, OBJECT-IDENTITY, enterprises
		FROM SNMPv2-SMI;

networkAlchemy MODULE-IDENTITY
    LAST-UPDATED "200010250000Z"
    ORGANIZATION "Network Alchemy, Inc."
    CONTACT-INFO 
		 "	Network Alchemy
			Customer Support

		  Postal: 1538 Pacific Av.
			Santa Cruz, CA 95060
			USA
	          E-Mail: snmp-contact@network-alchemy.com"

    DESCRIPTION "The Structure of Management Information for the
		 Network Alchemy enterprise."
    REVISION "200010250000Z"
    DESCRIPTION "Cleanup."
    ::= { enterprises 2972 }

netalProducts OBJECT-IDENTITY
        STATUS  current
        DESCRIPTION
                "netalProducts is the root OBJECT IDENTIFIER from
                which sysObjectID values are assigned.  Actual
                values are defined in the NETAL-PRODUCTS-MIB."
        ::= { networkAlchemy 1 }


netalMgmt OBJECT-IDENTITY
        STATUS  current
        DESCRIPTION
                "netalMgmt is the main subtree for new mib development."
        ::= { networkAlchemy 2 }

netalExperiment OBJECT-IDENTITY
        STATUS  current
        DESCRIPTION
                "netalExperiment provides a root object identifier
                from which experimental mibs may be temporarily
                based.  mibs are typicially based here if they
                fall in one of two categories
                1) are IETF work-in-process mibs which have not
                   been assigned a permanent object identifier by
                   the IANA.
                2) are Network Alchemy work-in-process which has 
		   not been assigned a permanent object identifier 
		   by the Network Alchemy assigned number authority, 
		   typicially because the MIB is not ready for deployment.

                NOTE WELL:  support for MIBs in the netalExperiment
                subtree will be deleted when a permanent object
                identifier assignment is made."
        ::= { networkAlchemy 3 }

netalAdmin OBJECT-IDENTITY
        STATUS  current
        DESCRIPTION
                "netalAdmin is reserved for administratively assigned
                OBJECT IDENTIFIERS, i.e. those not associated with MIB
                objects"
        ::= { networkAlchemy 4 }

netalModules OBJECT-IDENTITY
        STATUS  current
        DESCRIPTION
                "netalModules provides a root object identifier
                from which MODULE-IDENTITY values may be assigned."
        ::= { networkAlchemy 5 }

netalTraps OBJECT-IDENTITY
        STATUS  current
        DESCRIPTION
                "All the traps send by and from the Network Alchemy
		Crypto Cluster fall under here."
        ::= { networkAlchemy 6 }

cryptoCluster  OBJECT-IDENTITY  
	STATUS current
	DESCRIPTION "Crypto Cluster MIB"
	::= { netalMgmt 1 }

ipsec  OBJECT-IDENTITY
	STATUS current
	DESCRIPTION "IPSEC MIB"
	::= { netalMgmt 2 }

hardware OBJECT-IDENTITY
	STATUS current
	DESCRIPTION "Crypto Cluster Hardware MIB"
	::= { netalMgmt 3 }

vpn     OBJECT-IDENTITY
	STATUS current
	DESCRIPTION "Crypto Cluster VPN (tunnel) MIB"
	::= { netalMgmt 4 }

config  OBJECT-IDENTITY
	STATUS current
	DESCRIPTION "Configuration administration parameters"
	::= { netalMgmt 5 }

END
