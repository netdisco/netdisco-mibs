XEROX-COMMON-MIB DEFINITIONS ::= BEGIN
IMPORTS
        enterprises, mgmt, OBJECT-IDENTITY, MODULE-IDENTITY,
        OBJECT-TYPE,
        NOTIFICATION-TYPE,
        Counter32, Gauge32, Integer32
                FROM SNMPv2-SMI       
        RowStatus, TruthValue, DisplayString,
        DateAndTime,
	AutonomousType, 
        TEXTUAL-CONVENTION
                FROM SNMPv2-TC        
        MODULE-COMPLIANCE, OBJECT-GROUP
                FROM SNMPv2-CONF        
        hrDeviceIndex, InternationalDisplayString,
        hrDeviceStatus,
        hrSWRunIndex,
        hrSWInstalledIndex,
        hrStorageIndex,
        ProductID
                FROM HOST-RESOURCES-MIB 
        IANACharset
                FROM IANA-CHARSET-MIB        
        jmJobEntry,
        jmJobState,
        jmJobStateReasons1,
        jmNumberOfInterveningJobs,
        jmJobKOctetsPerCopyRequested,
        jmJobKOctetsProcessed,
        jmJobImpressionsPerCopyRequested,
        jmJobImpressionsCompleted
            FROM Job-Monitoring-MIB     -- IETF RFC 2707

        PresentOnOff,
        prtGeneralEntry,
        prtInputEntry,
        prtOutputEntry,
        prtChannelEntry,
        prtInterpreterEntry,
        prtInterpreterIndex
            FROM Printer-MIB            ;
xerox MODULE-IDENTITY
    LAST-UPDATED "0209170000Z"
    ORGANIZATION "Xerox Corporation -
                  Xerox Common Management Interface Working Group"
    CONTACT-INFO "
                     XCMI Editors
        E-Mail       coherence@crt.xerox.com
    "
    DESCRIPTION
        "Xerox Common MIB Root Module, Version 5.10.pub.
        Copyright (C) 1997-2002 Xerox Corporation. All Rights Reserved."
    ::= { enterprises 253 }
xeroxCommonMIB OBJECT-IDENTITY
    STATUS      current
    DESCRIPTION
        "The root of the Xerox Common MIB module.
         xeroxCommonMIB ::= { iso(1) org(3) dod(6) internet(1)
                              private(4) enterprises(1) Xerox(253) 8 }"
    ::= { xerox 8 }
xcmGeneralTC OBJECT-IDENTITY -- MODULE-IDENTITY
    STATUS   current
    DESCRIPTION "
        Version:    5.601.pub
        Xerox General Textual Conventions
        See section 9 'Supplement' of XCMI General TC for
        implementation and conformance guidance for this TC module.
        Copyright (C) 1995-2005 Xerox Corporation. All Rights Reserved."
    ::= { xeroxCommonMIB 50 }
--
--
Cardinal16 ::= TEXTUAL-CONVENTION
    STATUS      current
    DESCRIPTION "
        The representation for non-negative integers.
        Used for indices in small tables where 0 means not specified.
        It avoids use of the sign bit."
    SYNTAX      INTEGER (0..32767)       
Cardinal32 ::= TEXTUAL-CONVENTION
    STATUS      current
    DESCRIPTION "
        The representation for non-negative integers.
        Used for indices in large tables where 0 means not specified.
        Same size as ISO 10175 (avoids use of sign bit)."
    SYNTAX      INTEGER (0..2147483647)  
Cardinal64High ::= TEXTUAL-CONVENTION
    STATUS      current
    DESCRIPTION "
        The high-order 31 bits of a 62-bit non-negative integer
        (0..2**62-1).  A manager must get or set the high
        and low parts in the same operation."
    SYNTAX      INTEGER (0..2147483647)  
Cardinal64Low ::= TEXTUAL-CONVENTION
    STATUS      current
    DESCRIPTION "
        The low-order 31 bits of a 62-bit non-negative integer
        (0..2**62-1).  A manager must get or set the high
        and low parts in the same operation."
    SYNTAX      INTEGER (0..2147483647)  
CodedCountry ::= TEXTUAL-CONVENTION
    STATUS      current
    DESCRIPTION "
        A two character country or territory abbreviation from
        ISO/IEC 3166:1993 - Codes for the Representation of
        Names of Countries.
        Examples: US, FR, DE
        A null string SHALL indicate that the country or territory
        is not defined."
    SYNTAX      OCTET STRING (SIZE(0..2))
CodedLanguage ::= TEXTUAL-CONVENTION
    STATUS      current
    DESCRIPTION "
        A two character language abbreviation as defined in
        ISO/IEC 639:1988 - Codes For the Representation of
        Names of Languages.
        Examples EN, GB, CA, FR, DE.
        An empty string SHALL indicate that the language
        is not defined."
    SYNTAX      OCTET STRING (SIZE(0..2))
CodeIndexedStringIndex ::= TEXTUAL-CONVENTION
    STATUS      current
    DESCRIPTION "
        The representation of string data which the agent can provide
        in one or more character sets (but not further localized).
        Typically this representation is used because the string data
        is relatively dynamic, changing too rapidly for full
        localization; or because the data exists inherently in only one
        or a limited number of character sets and cannot meaningfully
        be further localized.
        The value is an index into a single global string table, 
        xcmGenCodeIndexedStringTable.  A subsidiary index into the
        xcmGenCodeIndexedStringTable is the IANA registered enum
        (see the CodedCharSet textual-convention in RFC 1759) for the 
        coded character set desired by the management station (from 
        among the coded character sets supported by the SNMP agent).
        A 0 index value SHALL indicate that there is no associated entry
        in the string table.
        32 bits are needed because Jobs can use up 10-12 code-indexed
        strings per job."
    SYNTAX      INTEGER (0..2147483647)  
Counter64High ::= TEXTUAL-CONVENTION
    STATUS      current
    DESCRIPTION "
        The high-order 32 bits of a 63-bit counter (0..2**63-1).
        A manager must get or set the high and low parts in the
        same operation."
    SYNTAX      Counter32  
Counter64Low ::= TEXTUAL-CONVENTION
    STATUS      current
    DESCRIPTION "
        The low-order 31 bits of a 63-bit counter (0..2**63-1).
        A manager must get or set the high and low parts in the
        same operation."
    SYNTAX      INTEGER (0..2147483647)  
Gauge64High ::= TEXTUAL-CONVENTION
    STATUS      current
    DESCRIPTION "
        The high-order 32 bits of a 63-bit gauge (0..2**63-1).
        A manager must get or set the high and low parts in the
        same operation."
    SYNTAX      Gauge32  
Gauge64Low ::= TEXTUAL-CONVENTION
    STATUS      current
    DESCRIPTION "
        The low-order 31 bits of a 63-bit gauge (0..2**63-1).
        A manager must get or set the high and low parts in the
        same operation."
    SYNTAX      INTEGER (0..2147483647)  
Integer64High ::= TEXTUAL-CONVENTION
    STATUS      current
    DESCRIPTION "
        The high-order 32 bits of a 63-bit signed integer
        (-2**62..2**62-1).  A manager must get or set the high
        and low parts in the same operation."
    SYNTAX      Integer32
Integer64Low ::= TEXTUAL-CONVENTION
    STATUS      current
    DESCRIPTION "
        The low-order 31 bits of a 63-bit signed integer
        (-2**62..2**62-1).  A manager must get or set the high
        and low parts in the same operation."
    SYNTAX      INTEGER (0..2147483647)  
Ordinal16 ::= TEXTUAL-CONVENTION
    STATUS      current
    DESCRIPTION "
        The representation for positive integers.
        Used for indices in small tables where 0 is illegal.
        It avoids use of the sign bit.."
    SYNTAX      INTEGER (1..32767)  
Ordinal32 ::= TEXTUAL-CONVENTION
    STATUS      current
    DESCRIPTION "
        The representation for positive integers.
        Same size as ISO 10175 (avoids use of sign bit)."
    SYNTAX      INTEGER (1..2147483647)  
Ordinal64High ::= TEXTUAL-CONVENTION
    STATUS      current
    DESCRIPTION "
        The high-order 31 bits of a 62-bit positive integer
        (1..2**62-1).  A manager must get or set the high
        and low parts in the same operation."
    SYNTAX      INTEGER (0..2147483647)  
Ordinal64Low ::= TEXTUAL-CONVENTION
    STATUS      current
    DESCRIPTION "
        The low-order 31 bits of a 62-bit positive integer
        (1..2**62-1).  A manager must get or set the high
        and low parts in the same operation."
    SYNTAX      INTEGER (0..2147483647)  
--
     zeroDotZero OBJECT IDENTIFIER ::= { 0 0 }
--
   xcmGenZeroDotZero OBJECT-IDENTITY
       STATUS      current  
       DESCRIPTION "
           A value used for null object identifiers prior to XCMI v5.1.
           Do not use.  Instead use the standard definition in
           RFC 1902/2578 - 'zeroDotZero' - left here for compatibility."
       ::= { zeroDotZero 0 }
XcmFixedLocaleDisplayString ::= TEXTUAL-CONVENTION
    STATUS      current
    DESCRIPTION "
        This data type is used to model textual information in some
        localization (language, country, and character set), which is
        fixed (ie, NOT capable of being altered by management station
        request).  This textual information SHALL be represented in the
        localization which is indicated by the current value of
        'xcmGenFixedLocalizationIndex'."
    REFERENCE "
        See:    'XcmFixedLocaleUtf8String' in this module.
        See:    'XcmNamedLocaleUtf8String' in this module.
        See:    'InternationalDisplayString' in IETF Host Resources MIB
        (RFC 2790), 'DisplayString' in IETF SNMPv2 TC (RFC 1903/2579),
        'CodeIndexedStringIndex' in this module, and 'OCTET STRING' in
        OSI ASN.1 (CCITT X.208/X.209 | ISO 8824/8825)."
    SYNTAX      OCTET STRING (SIZE (0..255))
XcmFixedLocaleUtf8String ::= TEXTUAL-CONVENTION
    STATUS      current
    DESCRIPTION "
        This data type is used to model textual information in the UTF-8
        character set and some locale (language/country), which is
        fixed (ie, NOT capable of being altered by management station
        request).  This textual information SHALL be represented in
        UTF-8 and the locale which is indicated by the current value of
        'xcmGenFixedLocalizationIndex'."
    REFERENCE "
        See:    'UTF-8, a transformation of ISO 10646' (RFC 2279) and
        'IETF Policy on Character Sets and Languages' (RFC 2277).
        See:    'XcmFixedLocaleDisplayString' in this module.
        See:    'XcmNamedLocaleUtf8String' in this module.
        See:    'InternationalDisplayString' in IETF Host Resources MIB
        (RFC 2790), 'DisplayString' in IETF SNMPv2 TC (RFC 1903/2579),
        'CodeIndexedStringIndex' in this module, and 'OCTET STRING' in
        OSI ASN.1 (CCITT X.208/X.209 | ISO 8824/8825)."
    SYNTAX      OCTET STRING (SIZE (0..255))
XcmNamedLocaleUtf8String ::= TEXTUAL-CONVENTION
    STATUS      current
    DESCRIPTION "
        This data type is used to model textual information in the UTF-8
        character set and some locale (language/country), which is
        named (ie, explicitly named by a parallel column or attribute or
        by the operation context)."
    REFERENCE "
        See:    'UTF-8, a transformation of ISO 10646' (RFC 2279) and
        'IETF Policy on Character Sets and Languages' (RFC 2277).
        See:    'XcmFixedLocaleDisplayString' in this module.
        See:    'XcmFixedLocaleUtf8String' in this module.
        See:    'InternationalDisplayString' in IETF Host Resources MIB
        (RFC 2790), 'DisplayString' in IETF SNMPv2 TC (RFC 1903/2579),
        'CodeIndexedStringIndex' in this module, and 'OCTET STRING' in
        OSI ASN.1 (CCITT X.208/X.209 | ISO 8824/8825)."
    SYNTAX      OCTET STRING (SIZE (0..255))
XcmGenGroupSupport ::= TEXTUAL-CONVENTION
    STATUS      current
    DESCRIPTION "
        The terse conformance statement of ALL mandatory, conditionally
        mandatory, and optional XCMI General MIB object groups which are
        supported by this management agent implementation (ie, version)
        on this host system, specified in a bit-mask.
        The current set of values (which MAY be extended in the future)
        is given below:
              1 : xcmGenCurrentLocalizationGroup    
              2 : xcmGenLocalizationGroup           
              4 : xcmGenCodeIndexedStringGroup      
              8 : xcmGenCodedCharSetGroup           
             16 : xcmGenFixedLocalizationGroup      
             32 : xcmGenLockGroup                   
             64 : xcmGenReconfGroup                 
            128 : xcmGenOptionGroup                 
            256 : xcmGenClientDataGroup             
            512 : xcmGenTrapClientGroup             
           1024 : xcmGenTrapViewGroup               
           2048 : xcmGenBaseGroup                   
           4096 : xcmGenMessageMapGroup             
           8192 : xcmGenMessageTextGroup            
          16384 : xcmGenNotifyRuleGroup             
          32768 : xcmGenNotifyDetailGroup           
        Usage:  Conforming management agents SHALL accurately
        report their support for XCMI General MIB object groups."
    SYNTAX      INTEGER (0..2147483647)  
XcmGenLogFullPolicy ::= TEXTUAL-CONVENTION
    STATUS      current
    DESCRIPTION "
        The current policy for handling job/request/event log 'full'
        (in MIBs, in shared RAM, on disk, etc), on this host system."
    SYNTAX      INTEGER {
        other(1),                       
        unknown(2),                     
        disableService(3),              
        disableAndPauseService(4),      
        enableServiceAndFlushLog(5),    
        enableServiceAndFlushOldest(6)  
    }
XcmGenMessageMapStringLabel ::= TEXTUAL-CONVENTION
    STATUS      current
    DESCRIPTION "
        This syntax is used to specify a Xerox standard or experiemental
        message string label associated with the current value of the
        message string pointed to by 'xcmGenMessageMapStringIndexOID'.
        Usage:  Experimental message string labels SHOULD NOT be used in
        shipping versions of Xerox-branded products or services.  They
        exist solely to facilitate rapid product development cycles.
        Usage:  All Xerox message string label values SHALL
        be specified using display (NOT space) characters from the IANA
        registered charset 'utf-8' (ie, the UTF-8 octet-stream encoding
        of ISO-10646 UCS-4, described in RFC 2279).
        Usage:  All Xerox message string label values SHALL
        contain no more than 64 UTF-8 display characters AND no more
        than 128 total octets (in some scripts, less than 64 characters
        in UTF-8 octet-stream encoding).
        Usage:  All Xerox message string label values SHALL
        conform to the syntax specified below.  A 'format', 'namespace',
        'module', or 'field' component SHALL NOT contain hyphens.  A
        'format', 'namespace', or 'module' component SHALL use
        lowercase.  A 'field' or 'qualifier' component MAY use mixed
        case (see examples below).  A 'field' component MAY be use an
        abbreviated MIB object tag or other standardized identifier.
        ONLY a terminal 'qualifier' component MAY contain hyphens.  Each
        component SHALL be separated by a hyphen '-' character.
            msg_label   =
                format '-' namespace '-' module '-' field '-' qualifier
            msg_label   =
                std_label / exp_label
        Usage:  All Xerox standard message string label values
        SHALL conform to the refined syntax specified below.
            std_label   =
                std_fmt '-' std_ns '-' module '-' field '-' qualifier
            std_fmt     =
                'xs'        
              / 'x?'        
            std_ns      =
                'ansi'      
              / 'dmtf'      
              / 'ecma'      
              / 'ieee'      
              / 'ietf'      
              / 'iso'       
              / 'itu'       
              / 'omg'       
              / 'pwg'       
              / 'xcmi'      
              / 'xopen'     
              / 'w3c'       
            module      =   
            field       =   
            qualifier   =   
        Examples of well-formed standard message string labels:
            xs-iso-10175-mediaSize-iso-a4   
            xs-iso-10175-mediaSize-iso-b4   
            xs-iso-10175-mediaType-envelope
            xs-iso-10175-mediaType-transparency
            xs-iso-10175-mediaColor-white
            xs-iso-10175-mediaColor-yellow
            xs-ietf-rfc1759-alertDescription-coverOpen
            xs-pwg-jobmon-processingMessage-completed
            xs-xcmi-11hostx-deviceDescription-dc230ST
        Usage:  All Xerox experimental message string label values
        SHALL conform to the refined syntax specified below.
            exp_label   =
                exp_fmt '-' exp_ns '-' module '-' field '-' qualifier
            exp_fmt     =
                'xx'        
            exp_ns      =
                std_ns '.' prod_ns
            std_ns      =   
            prod_ns     =   
            module      =   
            field       =   
            qualifier   =   
        Examples of well-formed experimental message string labels:
            xx-ietf.dcs265-rfc1759-alertDescription-skyIsFalling
            xx-xcmi.dc230-11hostx-deviceDescription-dc230ST
            xx-xcmi.belize-11hostx-systemFaultString-missingWidgets
        Note:   New or refined message label syntaxes MAY be defined in
        future versions of this XCMI General TC."
    REFERENCE "
        See:    'xcmGenMessageMapStringLabel' in XCMI General MIB.
        See:    'deviceLifetimeUsage', 'deviceAccountingUsage',
                'deviceLifetimeErrorCount', and
                'deviceLifetimeWarningCount' in 'XcmHrDevDetailType'
                textual convention in XCMI Host Resources Ext TC."
    SYNTAX      OCTET STRING (SIZE (0..128))
XcmGenNotifyDetailType ::= TEXTUAL-CONVENTION
    STATUS      current
    DESCRIPTION "
        The type of notify detail stored in this conceptual row
        in 'xcmGenNotifyDetailTable'.
        Usage:  Conforming XCMI management stations and agents SHALL
        encode notify details as UTF-8 strings (like SLPv2, RFC 2608).
        - Integers SHALL be encoded as (signed) decimal strings.
        - Booleans SHALL be encoded as 'true' or 'false' strings.
        - Strings SHALL be encoded as UTF-8 character strings.
        - Binary data (e.g., 'userCertificate') SHALL be stored
        in SLPv2 opaque encoding (leading '\FF' and escaped octets).
        Usage:  Conformant implementations MUST encrypt passwords, keys,
        and other security information in 'xcmGenNotifyDetailString'."
    REFERENCE "
        See:    Section 5 'Subscription Object' and
                Section 5.3 'Subscription Template Attributes' and
                section 5.4 'Subscription Description Attributes' in
                IPP Notify (draft-ietf-ipp-not-spec-06.txt).
        See:    Section 5 'Service Attributes' (encoding rules) in
                Service Location Protocol v2 (RFC 2608)."
    SYNTAX      INTEGER {
--
--
--
--
--
--
--
--
--
        other(1),
        unknown(2),
        notifyRecipientURI(10),
        notifyEventNames(20),
        notifyEventDelay(21),
        notifySeverityFilter(22),
        notifyTrainingFilter(23),
        notifyMessageHeaderKeys(30),
        notifyMessageHeaderText(31),
        notifyMessageContentKeys(32),
        notifyMessageContentText(33)
    }
XcmGenNotifySchemeSupport ::= TEXTUAL-CONVENTION
    STATUS      current
    DESCRIPTION "
        The terse conformance statement of ALL notification URI schemes
        which are supported by this management agent implementation
        (ie, version) on this host system, specified in a bit-mask.
        The current set of values (which MAY be extended in the future)
        is given below:
              1 : uriNotifySNMP   
              2 : uriNotifyMailto 
              4 : uriNotifyHTTP   
              8 : uriNotifyHTTPS  
             16 : uriNotifyFTP    
        Usage:  Conforming management agents SHALL accurately
        report their support for notification URI schemes."
    REFERENCE "
        See:    'xcmGenBaseNotifySchemeSupport' and
                'xcmGenBaseSNMPDomainSupport' in XCMI General MIB.
        See:    Cited IETF URI/URL specifications."
    SYNTAX      INTEGER (0..2147483647)  
XcmGenNotifySeverityFilter ::= TEXTUAL-CONVENTION
    STATUS      current
    DESCRIPTION "
        This type is used to specify a notification severity filter
        supported by this management agent for notification traffic
        in ALL domains specified by 'xcmGenBaseSNMPDomainSupport' and
        'xcmGenBaseNotifySchemeSupport' (for URI-based notification),
        specified in a bit-mask.
        The current set of values (which MAY be extended in the future)
        is given below:
              1 : severityReport            
              2 : severityWarning           
              4 : severitySoftError         
              8 : severityHardError         
             16 : severityTestReport        
             32 : severityTestWarning       
             64 : severityTestSoftError     
            128 : severityTestHardError     
            256 : severityInternalError     
        Usage:  The terminology 'report', 'warning', and 'error' is
        coherent with the IETF IPP event notification work-in-progress
        and with the IETF Printer MIB (RFC 1759).
        Usage:  Individual trap definitions MAY further constrain which
        notifications are 'in scope'.
        Usage:  Conforming management agents SHALL accurately
        report their support for notification severity filters."
    REFERENCE "
        See:    'prtAlertSeverityLevel' in IETF Printer MIB (RFC 1759).
        See:    'xcmGenBaseNotifySeveritySupport' and
                'xcmGenTrapViewNotifySeverity' in XCMI General MIB."
    SYNTAX      INTEGER (0..2147483647)  
XcmGenNotifyTrainingFilter ::= TEXTUAL-CONVENTION
    STATUS      current
    DESCRIPTION "
        This type is used to specify a notification training filter
        supported by this management agent for notification traffic
        in ALL domains specified by 'xcmGenBaseSNMPDomainSupport' and
        'xcmGenBaseNotifySchemeSupport' (for URI-based notification),
        specified in a bit-mask.
        The current set of values (which MAY be extended in the future)
        is given below:
              1 : trainingOther             
              2 : trainingUnknown           
              4 : trainingNone              
              8 : trainingTrained           
             16 : trainingFieldService      
             32 : trainingManagement        
             64 : trainingNoIntervention    
        Usage:  The terminology used here is coherent with the IETF
        Printer MIB (RFC 1759).
        Usage:  Individual trap definitions MAY further constrain which
        notifications are 'in scope'.
        Usage:  Conforming management agents SHALL accurately
        report their support for notification training filters."
    REFERENCE "
        See:    'prtAlertTrainingLevel' in IETF Printer MIB (RFC 1759).
        See:    'xcmGenBaseNotifyTrainingSupport' and
                'xcmGenTrapViewNotifyTraining' in XCMI General MIB."
    SYNTAX      INTEGER (0..2147483647)  
XcmGenOptionValueSyntax ::= TEXTUAL-CONVENTION
    STATUS      current
    DESCRIPTION "
        A reconfiguration option, device detail, storage detail,
        service detail, or security profile detail value syntax,
        used by system administrators and end users to specify
        the correct value syntax for this option or detail.
        Usage:  This option or detail value syntax is used to
        select which of the three value objects SHALL be used to
        contain the value of this option or detail.
      * An option or detail value syntax of 'oidObject'
        indicates that 'xcm...ValueOID' SHALL be used to specify
        an actual object type, defined with 'OBJECT-TYPE'.
      * An option or detail value syntax of 'oidAutonomous'
        indicates that 'xcm...ValueOID' SHALL be used to specify
        an autonomous object type, defined with 'OBJECT-IDENTITY' or
        simply 'OBJECT IDENTIFIER'.
      * An option or detail value syntax of 'stringBinary'
        indicates that 'xcm...ValueString' SHALL be used to
        specify a (possibly) 'binary' (or 'non-printing') value string.
      * An option or detail value syntax of 'stringDisplay'
        indicates that 'xcm...ValueString' SHALL be used to
        specify a 'displayable' (or 'printing') value string.
      * An option or detail value syntax of 'stringLocalization'
        indicates that 'xcm...ValueLocalization' (for options) or
        'xcmGenFixedLocalizationIndex' (for details) SHALL be used
        to control the localization of the value string
        (with an underlying type of 'XcmGenFixedLocaleDisplayString').
      * An option or detail value syntax of 'stringCodedCharSet'
        indicates that 'xcm...ValueCodedCharSet' (for options) or
        'xcmGenFixedLocalizationIndex' (for details) SHALL be used
        to control the character set ONLY of the value string
        (with an underlying type of 'CodeIndexedStringIndex').
      * An option or detail value syntax of 'stringDynamicLocalization'
        indicates that 'xcmGenCurrentLocalization' SHALL be used
        to control the localization of the value string
        (with an underlying type of 'InternationalDisplayString').
      * An option or detail value syntax of 'stringUtf8Localization'
        indicates that 'xcm...ValueLocalization' (for options) or
        'xcmGenFixedLocalizationIndex' (for details) SHALL be used
        to control the localization of the value string
        (with an underlying type of 'XcmGenFixedLocaleUtf8String')."
    REFERENCE "
        See:    'xcmGenOptionTable' in XCMI General MIB
        See:    'xcmCommsOptionTable' in XCMI Comms Config MIB
        See:    'xcmHrDevDetailTable' in XCMI Host Resources Ext MIB
        See:    'xcmHrStorageDetailTable' in XCMI Host Resources Ext MIB
        See:    'xcmSvcMonServiceDetailTable' in XCMI Service Mon MIB
        See:    'xcmSecProfileDetailTable' in XCMI Security MIB"
    SYNTAX      INTEGER {
        other(1),                       
        unknown(2),
        integerNumber(3),               
        integerCounter(4),              
        integerEnum(5),                 
        integerGauge(6),                
        integerIndex(7),                
        integerTruthValue(8),           
        oidObject(9),                   
        oidAutonomous(10),              
        stringBinary(11),               
        stringDisplay(12),              
        stringLocalization(13),         
        stringCodedCharSet(14),         
        stringDynamicLocalization(15),  
        stringUtf8Localization(16)      
    }
XcmGenReconfOptionState ::= TEXTUAL-CONVENTION
    STATUS      current
    DESCRIPTION "
        The processing state of ALL pending reconfiguration options of
        this host system.
        A write to this object by an (authorized) management station
        invokes a request for validation (or activation) of ALL pending
        reconfiguration options of this host system.
        A read of this object returns 'idle', 'validateInProgress', or
        'activateInProgress' to report the processing state of the last
        'validate...' or 'activate...' request.
        It is mandatory that a conforming management agent ensure that,
        at system initialization, this object SHALL be set to a
        value of 'idle'.
      * 'idle' - NO processing is 'in progress' for either 'validate...'
        or 'activate...' of any pending reconfiguration options.
      * 'validateForImmediateChange' - this management agent (and host
        system) SHALL perform ALL possible and appropriate validation of
        ALL pending reconfiguration options (reporting the FIRST error
        encountered during validation), so that reconfiguration could
        be performed successfully via 'activateForImmediateChange'.
      * 'validateForRebootChange' - this management agent (and host
        system) SHALL perform ALL possible and appropriate validation of
        ALL pending reconfiguration options (reporting the FIRST error
        encountered during validation), so that reconfiguration could
        be performed successfully via 'activateForRebootChange'.
      * 'validateForImmediateReboot' - this management agent (and host
        system) SHALL perform ALL possible and appropriate validation of
        ALL pending reconfiguration options (reporting the FIRST error
        encountered during validation), so that reconfiguration could
        be performed successfully via 'activateForImmediateReboot'.
      * 'validateInProgress' - indicates that this management agent (and
        host system) are currently performing validation of ALL pending
        reconfiguration options.
        Note:   Conforming implementations NEED NOT support more than
        ONE of the above three 'validation...' operations.
      * 'activateForImmediateChange' - this management agent (and host
        system) SHALL perform immediate reconfiguration, NOT reboot, for
        ALL pending reconfiguration options (reporting the FIRST error
        encountered during validation).
        For all conforming implementations, this reconfiguration SHALL
        ALWAYS take effect immediately, WITHOUT host system reboot!
        Note:   Conforming implementations are STRONGLY encouraged to
        consider supporting 'benign' reconfiguration in this manner.
      * 'activateForRebootChange' - this management agent (and host
        system) SHALL perform delayed reconfiguration, NOT reboot, for
        ALL pending reconfiguration options (reporting the FIRST error
        encountered during validation).
        For all conforming implementations, this reconfiguration SHALL
        ALWAYS take effect delayed, AFTER subsequent host system reboot!
        Note:   Conforming implementations NEED NOT support 'caching' of
        multiple outstanding 'sets of reconfiguration' in this manner.
      * 'activateForImmediateReboot' - this management agent (and host
        system) SHALL perform immediate reconfiguration, AND reboot, for
        ALL pending reconfiguration options (reporting the FIRST error
        encountered during validation).
        For all conforming implementations, this reconfiguration SHALL
        ALWAYS take effect immediately, WITH host system reboot!
        Note:   Conforming implementations are STRONGLY encouraged to
        consider secure alternatives (eg, Device Mgmt) for system reset.
      * 'activateInProgress' - indicates that this management agent (and
        host system) are currently performing activation of ALL pending
        reconfiguration options.
        Note:   Conforming implementations NEED NOT support more than
        ONE of the above three 'activation...' operations."
    REFERENCE "
        See:    'xcmGenReconfError[Index|Status]'"
    SYNTAX      INTEGER {
        idle(1),                        
        validateForImmediateChange(2),  
        validateForRebootChange(3),     
        validateForImmediateReboot(4),  
        validateInProgress(5),          
        activateForImmediateChange(6),  
        activateForRebootChange(7),     
        activateForImmediateReboot(8),  
        activateInProgress(9)           
    }
XcmGenRowPersistence ::= TEXTUAL-CONVENTION
    STATUS      current
    DESCRIPTION "
        This type is used to specify the persistence of this
        conceptual row in a table.
        Usage:  Conforming management agents SHALL interpret
        persistence as follows:
        1)  'volatile' rows NEED NOT be saved across power cycles,
            MAY contain one or more 'read-[create|write|only]' objects,
            and their underlying storage MAY be removable,
            and conforming management agents NEED NOT delete such rows
            (eg, a block in RAM, PCMCIA card, etc);
        2)  'nonvolatile' rows SHALL be saved across power cycles,
            MAY contain one or more 'read-[write|only]' objects,
            and their underlying storage MAY be removable,
            and conforming management agents MAY delete such rows
            (eg, a sector on CD-ROM, font cartridge, hard disk, etc);
        3)  'permanent' rows SHALL be saved across power cycles,
            MAY contain one or more 'read-[write|only]' objects,
            and their underlying storage SHALL NOT be removable,
            and conforming management agents SHALL NOT delete such rows
            (eg, a sector on EEPROM, battery-backed RAM, bubble, etc);
        4)  'readonly' rows SHALL be saved across power cycles,
            SHALL contain exclusively 'read-only' objects,
            and their underlying storage SHALL NOT be removable,
            and conforming management agents SHALL NOT delete such rows
            (eg, a sector on ROM, ASIC, etc).
        Usage:  Dynamically created rows MAY ONLY be given 'volatile'
        or 'nonvolatile' persistence.
        Note:   Equivalent to SNMPv2 'StorageType' textual convention,
        which has an unfortunately ambiguous name."
    REFERENCE "
        See:    'hrStorageType' in the Storage group of the
                IETF Host Resources MIB (RFC 2790).
        See:    'StorageType' textual convention in the
                Historic SNMPv2 Party MIB (RFC 1447).
        See:    'StorageType' textual convention in the
                IETF SNMPv2 Textual Conventions (RFC 2579)."
    SYNTAX      INTEGER {
        other(1),
        unknown(2),
        volatile(3),                    
        nonvolatile(4),                 
        permanent(5),                   
        readonly(6)                     
    }
XcmGenSNMPDomain ::= TEXTUAL-CONVENTION
    STATUS      current
    DESCRIPTION "
        This type is used to specify a transport domain (address
        and name space) which is supported by this management agent
        for SNMP protocol traffic (SNMP responses, SNMP traps, etc),
        in ALL versions specified by 'xcmGenBaseSNMPVersionSupport'.
        This type is also used to allow the 'xcmGenTrapClientTable' to
        be used with any URI scheme (e.g., 'mailto:') for notifications,
        by specifying 'uriNotifyDomain'."
    REFERENCE "
        See:    'xcmGenBaseSNMPDomainSupport' and
                'xcmGenTrapClientSNMPDomain' in XCMI General MIB.
        See:    Cited IETF SNMP specifications."
    SYNTAX      INTEGER {
        snmpUDPDomain(1),               
        snmpCLNSDomain(2),              
        snmpCONSDomain(3),              
        snmpDDPDomain(4),               
        snmpIPXDomain(5),               
        snmpNetBIOSDomain(10),          
        snmpNetBEUIDomain(11),          
        snmpTCPDomain(20),              
        snmpIPHostNameDomain(21),       
        uriNotifyDomain(30)             
    }
XcmGenSNMPVersion ::= TEXTUAL-CONVENTION
    STATUS      current
    DESCRIPTION "
        This type is used to specify an SNMP version (RFC 1157, RFC
        1905, etc) which is supported by this management agent
        for SNMP protocol traffic (SNMP responses, SNMP traps, etc),
        in ALL domains specified by 'xcmGenBaseSNMPDomainSupport'."
    REFERENCE "
        See:    'xcmGenBaseSNMPVersionSupport' and
                'xcmGenTrapClientSNMPVersion' in XCMI General MIB.
        See:    Cited IETF SNMP specifications."
    SYNTAX      INTEGER {
        unknown(1),                     
        other(2),                       
        snmpV1Community(3),             
        snmpV1Party(4),                 
        snmpV2Party(5),                 
        snmpV2Community(6),             
        snmpV2Usec(7),                  
        snmpV2Star(8),                  
        snmpV2Secure(9),                
        snmpV3Secure(10)                
    }
XcmGenSNMPv2ErrorStatus ::= TEXTUAL-CONVENTION
    STATUS      current
    DESCRIPTION "
        Usage:  This type specifies the SMIv2 equivalent of the SMIv1
        'ErrorStatus' textual convention as an enumerated type.
        Note:   The enum of '0' (zero) in this textual convention is
        illegal in strict SMIv1 (see section 3.2.1.1 of RFC 1155), so
        this TC must be converted to an integer range for pure SMIv1."
    REFERENCE "
        See:    'error-status' in SNMPv2 Protocol (RFC 1448/1905)"
    SYNTAX      INTEGER {
        noError(0),
        tooBig(1),
        noSuchName(2),                  
        badValue(3),                    
        readOnly(4),                    
        genErr(5),
        noAccess(6),
        wrongType(7),
        wrongLength(8),
        wrongEncoding(9),
        wrongValue(10),
        noCreation(11),
        inconsistentValue(12),
        resourceUnavailable(13),
        commitFailed(14),
        undoFailed(15),
        authorizationError(16),
        notWritable(17),
        inconsistentName(18), 
        failedDueToPowerSaverState(19), 
        requestTimedOut(20) 
    }
XcmGlobalUniqueID ::= TEXTUAL-CONVENTION
    STATUS      current
    DESCRIPTION "
        A management station or management agent specifies an object of
        type 'GlobalUniqueID' to uniquely label a client job request, a
        system administration request, or ANY other managed object (or
        set of managed objects) which are required to be unambiguously
        identified in a distributed network environment.
        An object of type 'GlobalUniqueID' SHALL be a textual string
        representation in standard 'dotted decimal' form of an OID.
        An object of type 'GlobalUniqueID' SHALL be composed of three
        mandatory sections (plus zero or more optional sections),
        as follows:
                nodeID.userID.seqID[[.subID1]...[.subIDn]]
        Each of the sections SHALL be separated by a dot ('.').  The
        three mandatory sections and any specified optional sections
        (in left to right order) SHALL be:
        1)  A globally unambiguous (within at least the network domain
            of the Requestor and Responder host systems) dotted decimal
            'nodeID' of the Requestor host system which explicitly or
            implicitly labelled this managed object, either:
            a)  A domain specific network layer address
                (eg, IETF IP address for 'nodeIDTypeIP'); OR
            b)  A domain specific datalink MAC sublayer address
                (eg, ISO 8802-5 MAC address for 'nodeIDType88025').
        2)  A locally unambiguous (within at least the Requestor and/or
            Responder host systems) dotted decimal 'userID' (ie, user
            identifier) of the user who explicitly or implicitly
            labelled this managed object.
        3)  A locally unambiguous (within at least the Requestor and/or
            Responder host systems) dotted decimal 'seqID' (ie, sequence
            identifier) assigned by the host system or user who
            explicitly or implicitly labelled this managed object.
        4)  A locally unambiguous (within at least the Requestor and/or
            Responder host systems) dotted decimal 'subID' (ie, sequence
            sub-identifier) assigned by the host system or user who
            explicitly or implicitly labelled this managed object.
        Usage:  Conforming implementations MAY use one or more optional
        sections in an 'XcmGlobalUniqueID', for example to assign a
        sub-job identifier for job distribution services (e.g., fax to
        multiple destinations specified in the PDL of an input 'print'
        job - using an original 'xcmJobClientId' which is augmented by
        the server that splits up the destinations into separate jobs).
        Usage:  Conforming implementations SHALL NOT specify BOTH the
        first ('nodeID') and second ('userID') sections as 'empty', but
        one OR the other section MAY take on an 'empty' value (see
        below).  The third ('seqID') section SHALL NOT be 'empty'.
        Each of the three mandatory sections and any optional sections
        SHALL be composed of one mandatory and two optional subsections,
        as follows:
                sectionLength.sectionType.sectionValue
        Each of the subsections SHALL be separated by a dot ('.').  The
        three subsections (in left to right order) SHALL be:
        1)  A mandatory 'sectionLength', which specifies the decimal
            count of dotted decimal 'components' in the associated
            'sectionValue' - this 'sectionLength' SHALL NOT be
            self-inclusive and SHALL NOT include the single 'component'
            of the 'sectionType' - a 'sectionLength' of decimal zero
            ('0') SHALL indicate an 'empty' section, and the associated
            two subsections ('sectionType' and 'sectionValue') SHALL be
            omitted.
        2)  An optional 'sectionType', selected from the standard
            'sectionType' choices applicable to this section (below).
        3)  An optional 'sectionValue', specified as a dotted decimal
            string of 'components', each 'component' separated by a dot
            ('.').
        The standard 'sectionType' choices (one set for each section)
        SHALL be as follows:
        1)  'nodeIDType' 
              1 : nodeIDTypeOther       
              2 : nodeIDTypeUnknown     
             11 : nodeIDTypeIP          
             12 : nodeIDTypeCLNS        
             13 : nodeIDTypeCONS        
             14 : nodeIDTypeDDP         
             15 : nodeIDTypeIPX         
             16 : nodeIDTypeNetBIOS     
             31 : nodeIDType88023       
             32 : nodeIDType88024       
             33 : nodeIDType88025       
             34 : nodeIDType88026       
        2)  'userIDType' 
              1 : userIDTypeOther       
              2 : userIDTypeUnknown     
             11 : userIDTypeSystem      
             12 : userIDTypeSubnet      
             13 : userIDTypeNetwork     
             14 : userIDTypeGlobal      
        3)  'seqIDType' 
              1 : seqIDTypeOther        
              2 : seqIDTypeUnknown      
             11 : seqIDTypeSystem       
             12 : seqIDTypeProcess      
             13 : seqIDTypeThread       
        4)  'subIDType' 
              1 : subIDTypeOther        
              2 : subIDTypeUnknown      
             11 : subIDTypeSystem       
             12 : subIDTypeProcess      
             13 : subIDTypeThread       
        Usage:  A 'seqID' of any type SHALL be system-unique.
        Usage:  A 'seqID' of type 'seqIDTypeProcess' SHALL be prefixed
        (if necessary) by a system-unique dotted decimal 'processID'.
        Usage:  A 'seqID' of type 'seqIDTypeThread' SHALL be prefixed
        (if necessary) by a system-unique dotted decimal 'threadID'
        (possibly itself prefixed by a system-unique 'processID').
        Example:  A request submitted from a client end system running
        the IETF Internet Protocol Suite (IPS), with an IP address of
        '13.240.128.21', without a specified dotted decimal 'userID',
        might include an 'xcmJobClientId' of the following form:
            '4.11.13.240.128.21.0.1.11.3045.1.11.23' [GlobalUniqueID]
            |---------1--------|2|----3----|---4---| [Sections]
        1)  The mandatory first section ('nodeID') consists of:
            a)  'sectionLength' of '4';
            b)  'sectionType' of '11' ('nodeIDTypeIP'); and
            c)  'sectionValue' of '13.240.128.21' (4 components).
        2)  The mandatory second section ('userID') consists of:
            a)  'sectionLength' of '0' (ie, 'empty' section).
        3)  The mandatory third section ('seqID') consists of:
            a)  'sectionLength' of '1';
            b)  'sectionType' of '11' ('seqIDTypeSystem'); and
            c)  'sectionValue' of '3045' (one component).
        4)  The optional fourth section ('subID') consists of:
            a)  'sectionLength' of '1';
            b)  'sectionType' of '11' ('subIDTypeSystem'); and
            c)  'sectionValue' of '23' (one component)."
    SYNTAX      OCTET STRING (SIZE (0..255))
--
--
--
xCmGeneralDummy     OBJECT IDENTIFIER ::= { xcmGeneralTC 999 }
xCmGenCardinal16 OBJECT-TYPE
    SYNTAX      Cardinal16
    MAX-ACCESS  not-accessible
    STATUS      current
    DESCRIPTION "Dummy - DO NOT USE"
    ::= { xCmGeneralDummy 1 }
xCmGenCardinal32 OBJECT-TYPE
    SYNTAX      Cardinal32
    MAX-ACCESS  not-accessible
    STATUS      current
    DESCRIPTION "Dummy - DO NOT USE"
    ::= { xCmGeneralDummy 2 }
xCmGenCardinal64High OBJECT-TYPE
    SYNTAX      Cardinal64High
    MAX-ACCESS  not-accessible
    STATUS      current
    DESCRIPTION "Dummy - DO NOT USE"
    ::= { xCmGeneralDummy 3 }
xCmGenCardinal64Low OBJECT-TYPE
    SYNTAX      Cardinal64Low
    MAX-ACCESS  not-accessible
    STATUS      current
    DESCRIPTION "Dummy - DO NOT USE"
    ::= { xCmGeneralDummy 4 }
xCmGenCodedCountry OBJECT-TYPE
    SYNTAX      CodedCountry
    MAX-ACCESS  not-accessible
    STATUS      current
    DESCRIPTION "Dummy - DO NOT USE"
    ::= { xCmGeneralDummy 5 }
xCmGenCodedLanguage OBJECT-TYPE
    SYNTAX      CodedLanguage
    MAX-ACCESS  not-accessible
    STATUS      current
    DESCRIPTION "Dummy - DO NOT USE"
    ::= { xCmGeneralDummy 6 }
xCmGenCodeIndexedStringIndex OBJECT-TYPE
    SYNTAX      CodeIndexedStringIndex
    MAX-ACCESS  not-accessible
    STATUS      current
    DESCRIPTION "Dummy - DO NOT USE"
    ::= { xCmGeneralDummy 7 }
xCmGenCounter64High OBJECT-TYPE
    SYNTAX      Counter64High
    MAX-ACCESS  not-accessible
    STATUS      current
    DESCRIPTION "Dummy - DO NOT USE"
    ::= { xCmGeneralDummy 8 }
xCmGenCounter64Low OBJECT-TYPE
    SYNTAX      Counter64Low
    MAX-ACCESS  not-accessible
    STATUS      current
    DESCRIPTION "Dummy - DO NOT USE"
    ::= { xCmGeneralDummy 9 }
xCmGenGauge64High OBJECT-TYPE
    SYNTAX      Gauge64High
    MAX-ACCESS  not-accessible
    STATUS      current
    DESCRIPTION "Dummy - DO NOT USE"
    ::= { xCmGeneralDummy 10 }
xCmGenGauge64Low OBJECT-TYPE
    SYNTAX      Gauge64Low
    MAX-ACCESS  not-accessible
    STATUS      current
    DESCRIPTION "Dummy - DO NOT USE"
    ::= { xCmGeneralDummy 11 }
xCmGenInteger64High OBJECT-TYPE
    SYNTAX      Integer64High
    MAX-ACCESS  not-accessible
    STATUS      current
    DESCRIPTION "Dummy - DO NOT USE"
    ::= { xCmGeneralDummy 12 }
xCmGenInteger64Low OBJECT-TYPE
    SYNTAX      Integer64Low
    MAX-ACCESS  not-accessible
    STATUS      current
    DESCRIPTION "Dummy - DO NOT USE"
    ::= { xCmGeneralDummy 13 }
xCmGenOrdinal16 OBJECT-TYPE
    SYNTAX      Ordinal16
    MAX-ACCESS  not-accessible
    STATUS      current
    DESCRIPTION "Dummy - DO NOT USE"
    ::= { xCmGeneralDummy 14 }
xCmGenOrdinal32 OBJECT-TYPE
    SYNTAX      Ordinal32
    MAX-ACCESS  not-accessible
    STATUS      current
    DESCRIPTION "Dummy - DO NOT USE"
    ::= { xCmGeneralDummy 15 }
xCmGenOrdinal64High OBJECT-TYPE
    SYNTAX      Ordinal64High
    MAX-ACCESS  not-accessible
    STATUS      current
    DESCRIPTION "Dummy - DO NOT USE"
    ::= { xCmGeneralDummy 16 }
xCmGenOrdinal64Low OBJECT-TYPE
    SYNTAX      Ordinal64Low
    MAX-ACCESS  not-accessible
    STATUS      current
    DESCRIPTION "Dummy - DO NOT USE"
    ::= { xCmGeneralDummy 17 }
xCmGenFixedLocaleDisplayString OBJECT-TYPE
    SYNTAX      XcmFixedLocaleDisplayString
    MAX-ACCESS  not-accessible
    STATUS      current
    DESCRIPTION "Dummy - DO NOT USE"
    ::= { xCmGeneralDummy 18 }
xCmGenGroupSupport OBJECT-TYPE
    SYNTAX      XcmGenGroupSupport
    MAX-ACCESS  not-accessible
    STATUS      current
    DESCRIPTION "Dummy - DO NOT USE"
    ::= { xCmGeneralDummy 19 }
xCmGenLogFullPolicy OBJECT-TYPE
    SYNTAX      XcmGenLogFullPolicy
    MAX-ACCESS  not-accessible
    STATUS      current
    DESCRIPTION "Dummy - DO NOT USE"
    ::= { xCmGeneralDummy 20 }
xCmGenOptionValueSyntax OBJECT-TYPE
    SYNTAX      XcmGenOptionValueSyntax
    MAX-ACCESS  not-accessible
    STATUS      current
    DESCRIPTION "Dummy - DO NOT USE"
    ::= { xCmGeneralDummy 21 }
xCmGenReconfOptionState OBJECT-TYPE
    SYNTAX      XcmGenReconfOptionState
    MAX-ACCESS  not-accessible
    STATUS      current
    DESCRIPTION "Dummy - DO NOT USE"
    ::= { xCmGeneralDummy 22 }
xCmGenRowPersistence OBJECT-TYPE
    SYNTAX      XcmGenRowPersistence
    MAX-ACCESS  not-accessible
    STATUS      current
    DESCRIPTION "Dummy - DO NOT USE"
    ::= { xCmGeneralDummy 23 }
xCmGenSNMPDomain OBJECT-TYPE
    SYNTAX      XcmGenSNMPDomain
    MAX-ACCESS  not-accessible
    STATUS      current
    DESCRIPTION "Dummy - DO NOT USE"
    ::= { xCmGeneralDummy 24 }
xCmGenSNMPVersion OBJECT-TYPE
    SYNTAX      XcmGenSNMPVersion
    MAX-ACCESS  not-accessible
    STATUS      current
    DESCRIPTION "Dummy - DO NOT USE"
    ::= { xCmGeneralDummy 25 }
xCmGenSNMPv2ErrorStatus OBJECT-TYPE
    SYNTAX      XcmGenSNMPv2ErrorStatus
    MAX-ACCESS  not-accessible
    STATUS      current
    DESCRIPTION "Dummy - DO NOT USE"
    ::= { xCmGeneralDummy 26 }
xCmGenGlobalUniqueID OBJECT-TYPE
    SYNTAX      XcmGlobalUniqueID
    MAX-ACCESS  not-accessible
    STATUS      current
    DESCRIPTION "Dummy - DO NOT USE"
    ::= { xCmGeneralDummy 27 }
xCmGenFixedLocaleUtf8String OBJECT-TYPE
    SYNTAX      XcmFixedLocaleUtf8String
    MAX-ACCESS  not-accessible
    STATUS      current
    DESCRIPTION "Dummy - DO NOT USE"
    ::= { xCmGeneralDummy 28 }
xCmGenMessageMapStringLabel OBJECT-TYPE
    SYNTAX      XcmGenMessageMapStringLabel
    MAX-ACCESS  not-accessible
    STATUS      current
    DESCRIPTION "Dummy - DO NOT USE"
    ::= { xCmGeneralDummy 29 }
xCmGenNamedLocaleUtf8String OBJECT-TYPE
    SYNTAX      XcmNamedLocaleUtf8String
    MAX-ACCESS  not-accessible
    STATUS      current
    DESCRIPTION "Dummy - DO NOT USE"
    ::= { xCmGeneralDummy 30 }
xCmGenNotifySchemeSupport OBJECT-TYPE
    SYNTAX      XcmGenNotifySchemeSupport
    MAX-ACCESS  not-accessible
    STATUS      current
    DESCRIPTION "Dummy - DO NOT USE"
    ::= { xCmGeneralDummy 31 }
xCmGenNotifySeverityFilter OBJECT-TYPE
    SYNTAX      XcmGenNotifySeverityFilter
    MAX-ACCESS  not-accessible
    STATUS      current
    DESCRIPTION "Dummy - DO NOT USE"
    ::= { xCmGeneralDummy 32 }
xCmGenNotifyTrainingFilter OBJECT-TYPE
    SYNTAX      XcmGenNotifyTrainingFilter
    MAX-ACCESS  not-accessible
    STATUS      current
    DESCRIPTION "Dummy - DO NOT USE"
    ::= { xCmGeneralDummy 33 }
xCmGenNotifyDetailType OBJECT-TYPE
    SYNTAX      XcmGenNotifyDetailType
    MAX-ACCESS  not-accessible
    STATUS      current
    DESCRIPTION "Dummy - DO NOT USE"
    ::= { xCmGeneralDummy 34 }
xcmGeneralMIB OBJECT-IDENTITY -- MODULE-IDENTITY
    STATUS   current
    DESCRIPTION "
        Version:    5.402.pub
        Xerox General MIB
        See section 9 'Supplement' of XCMI General TC for
        implementation and conformance guidance for this MIB module.
        Copyright (C) 1995-2005 Xerox Corporation. All Rights Reserved."
    ::= { xeroxCommonMIB 51 }
xcmGenZeroDummy OBJECT IDENTIFIER ::= { zeroDotZero 51 }
--
--
xcmGenBase                  OBJECT IDENTIFIER ::= { xcmGeneralMIB 1 }
xcmGenBaseTable OBJECT-TYPE
    SYNTAX      SEQUENCE OF XcmGenBaseEntry
    MAX-ACCESS  not-accessible
    STATUS      current
    DESCRIPTION "
        A table of general counters and capabilities for ease of use
        of the XCMI General MIB on this host system.
        Usage:  The ONLY valid row in the 'xcmGenBaseTable'
        SHALL have an 'xcmGenBaseIndex' of one ('1')."
    ::= { xcmGenBase 2 }
xcmGenBaseEntry OBJECT-TYPE
    SYNTAX      XcmGenBaseEntry
    MAX-ACCESS  not-accessible
    STATUS      current
    DESCRIPTION "
        An entry of general counters and capabilities for ease of use
        of the XCMI General MIB on this host system.
        Usage:  The ONLY valid row in the 'xcmGenBaseTable'
        SHALL have an 'xcmGenBaseIndex' of one ('1')."
    INDEX       { xcmGenBaseIndex }
    ::= { xcmGenBaseTable 1 }
XcmGenBaseEntry ::= SEQUENCE {
        xcmGenBaseIndex                 Ordinal32,
        xcmGenBaseRowStatus             RowStatus,
        xcmGenBaseSystemHrDeviceIndex   Cardinal32,
        xcmGenBaseGroupSupport          XcmGenGroupSupport,
        xcmGenBaseGroupCreateSupport    XcmGenGroupSupport,
        xcmGenBaseGroupUpdateSupport    XcmGenGroupSupport,
        xcmGenBaseClientDataMaxSupport  Cardinal32,
        xcmGenBaseOptionSyntaxSupport   Cardinal32,
        xcmGenBaseReconfStateSupport    Cardinal32,
        xcmGenBaseSNMPDomainSupport     Cardinal32,
        xcmGenBaseSNMPTrapSupport       TruthValue,
        xcmGenBaseSNMPVersionSupport    Cardinal32,
        xcmGenBaseSNMPReadCommunity     OCTET STRING,
        xcmGenBaseSNMPWriteCommunity    OCTET STRING,
        xcmGenBaseSNMPTrapCommunity     OCTET STRING,
        xcmGenBaseGroupWalkHidden       XcmGenGroupSupport,
        xcmGenBaseNotifySchemeSupport    XcmGenNotifySchemeSupport,
        xcmGenBaseNotifySeveritySupport  XcmGenNotifySeverityFilter,
        xcmGenBaseNotifyTrainingSupport  XcmGenNotifyTrainingFilter,
        xcmGenBaseSystem1284DeviceId     DisplayString, 
        xcmGenBaseSNMPWarningTrapSupport TruthValue
    }
xcmGenBaseIndex OBJECT-TYPE
    SYNTAX      Ordinal32
    MAX-ACCESS  not-accessible
    STATUS      current
    DESCRIPTION "
        A unique value used by this host system to identify this
        conceptual row in the 'xcmGenBaseTable'.
        Usage:  The ONLY valid row in the 'xcmGenBaseTable'
        SHALL have an 'xcmGenBaseIndex' of one ('1')."
    ::= { xcmGenBaseEntry 1 }
xcmGenBaseRowStatus OBJECT-TYPE
    SYNTAX      RowStatus
    MAX-ACCESS  read-only
    STATUS      current
    DESCRIPTION "
        This object is used to display status of the ONLY valid
        conceptual row in the 'xcmGenBaseTable'.
        Usage:  'xcmGenBaseRowStatus' is 'read-only' because
        the ONLY valid conceptual row SHALL NOT be deleted."
    ::= { xcmGenBaseEntry 2 }
xcmGenBaseSystemHrDeviceIndex OBJECT-TYPE
    SYNTAX      Cardinal32
    MAX-ACCESS  read-only
    STATUS      current
    DESCRIPTION "
        The value of 'hrDeviceIndex' corresponding to the platform
        associated conceptual row in the 'hrDeviceTable' representing
        the CPU device (of type 'hrDeviceProcessor'), which currently
        supports the executing process/thread of this management agent."
    REFERENCE "
        See:    'hrDeviceIndex' in the Device group of the
                IETF Host Resources MIB (RFC 2790).
        See:    'xcmHrStoragePlatformDeviceIndex' in the Storage Ext
                group of the XCMI Host Resources Ext MIB."
    DEFVAL      { 0 }                   
    ::= { xcmGenBaseEntry 3 }
xcmGenBaseGroupSupport OBJECT-TYPE
    SYNTAX      XcmGenGroupSupport
    MAX-ACCESS  read-only
    STATUS      current
    DESCRIPTION "
        The terse conformance statement of ALL mandatory, conditionally
        mandatory, and optional XCMI General MIB object groups which are
        supported by this management agent implementation (ie, version)
        on this host system, specified in a bit-mask.
        Usage:  Conforming management agents SHALL accurately
        report their support for the XCMI General MIB object groups."
    DEFVAL      { 3584 }                
    ::= { xcmGenBaseEntry 4 }
xcmGenBaseGroupCreateSupport OBJECT-TYPE
    SYNTAX      XcmGenGroupSupport
    MAX-ACCESS  read-only
    STATUS      current
    DESCRIPTION "
        The terse conformance statement of ALL mandatory, conditionally
        mandatory, and optional XCMI General MIB object groups which are
        supported for dynamic row creation (via '...RowStatus')
        by this management agent implementation (ie, version)
        on this host system, specified in a bit-mask.
        Usage:  Conforming management agents SHALL accurately
        report their support for the XCMI General MIB object groups."
    DEFVAL      { 1536 }                
    ::= { xcmGenBaseEntry 5 }
xcmGenBaseGroupUpdateSupport OBJECT-TYPE
    SYNTAX      XcmGenGroupSupport
    MAX-ACCESS  read-only
    STATUS      current
    DESCRIPTION "
        The terse conformance statement of ALL mandatory, conditionally
        mandatory, and optional XCMI General MIB object groups which are
        supported for existing row update (via SNMP Set-Request PDUs)
        by this management agent implementation (ie, version)
        on this host system, specified in a bit-mask.
        Usage:  Conforming management agents SHALL accurately
        report their support for the XCMI General MIB object groups."
    DEFVAL      { 3584 }                
    ::= { xcmGenBaseEntry 6 }
xcmGenBaseClientDataMaxSupport OBJECT-TYPE
    SYNTAX      Cardinal32
    MAX-ACCESS  read-only
    STATUS      current
    DESCRIPTION "
        The maximum 'xcmGenClientDataLength' supported for ANY
        conceptual row in the 'xcmGenClientDataTable'.
        Usage:  Conforming implementations NEED NOT support maximum
        'xcmGenClientDataLength' greater than 1 octet."
    REFERENCE "
        See:    'xcmGenClientDataLength'"
    DEFVAL      { 0 }                   
    ::= { xcmGenBaseEntry 7 }
xcmGenBaseOptionSyntaxSupport OBJECT-TYPE
    SYNTAX      Cardinal32
    MAX-ACCESS  read-only
    STATUS      current
    DESCRIPTION "
        The 'xcmGenOptionValueSyntax' values supported for ANY
        conceptual row in the 'xcmGenOptionTable'.
        Usage:  Conforming management agents SHALL report their
        supported values as a 'bit-mask' formed via the bit-wise OR of
        '2**(n)', where (n) is each supported enumerated value in the
        in the 'XcmGenOptionValueSyntax' textual convention."
    REFERENCE "
        See:    'XcmGenOptionValueSyntax' in the XCMI General TC"
    DEFVAL      { 0 }                   
    ::= { xcmGenBaseEntry 8 }
xcmGenBaseReconfStateSupport OBJECT-TYPE
    SYNTAX      Cardinal32
    MAX-ACCESS  read-only
    STATUS      current
    DESCRIPTION "
        The 'xcmGenReconfOptionState' values supported for ANY
        conceptual row in the 'xcmGenReconfTable'.
        Usage:  Conforming management agents SHALL report their
        supported values as a 'bit-mask' formed via the bit-wise OR of
        '2**(n)', where (n) is each supported enumerated value in the
        in the 'XcmGenReconfOptionState' textual convention."
    REFERENCE "
        See:    'XcmGenReconfOptionState' in the XCMI General TC"
    DEFVAL      { 0 }                   
    ::= { xcmGenBaseEntry 9 }
xcmGenBaseSNMPDomainSupport OBJECT-TYPE
    SYNTAX      Cardinal32
    MAX-ACCESS  read-only
    STATUS      current
    DESCRIPTION "
        This object is used to specify ALL transport domains (address
        and name spaces) which are supported by this management agent
        for SNMP protocol traffic (SNMP responses, SNMP traps, etc),
        in ALL versions specified by 'xcmGenBaseSNMPVersionSupport'.
        This object is also used to allow the 'xcmGenTrapClientTable' to
        be used with any URI scheme (e.g., 'mailto:') for notifications,
        by specifying 'uriNotifyDomain'.
        Usage:  Conforming management agents SHALL report their
        supported values as a 'bit-mask' formed via the bit-wise OR of
        '2**(n)', where (n) is each supported enumerated value in the
        in the 'XcmGenSNMPDomain' textual convention."
    REFERENCE "
        See:    'XcmGenSNMPDomain' in the XCMI General TC
        See:    'xcmGenTrapClientSNMP[Domain|Version]'."
    ::= { xcmGenBaseEntry 10 }
xcmGenBaseSNMPTrapSupport OBJECT-TYPE
    SYNTAX      TruthValue
    MAX-ACCESS  read-only
    STATUS      current
    DESCRIPTION "
        This object SHALL be 'true' if this management agent
        supports SNMP traps (in any SNMP domain and SNMP version)
        and MAY support the 'xcmGenTrapClientTable'.
        This object SHALL be 'false' if this management agent does NOT
        support SNMP traps (in any SNMP domain and SNMP version)
        and does NOT support the 'xcmGenTrapClientTable'."
    REFERENCE "
        See:    'xcmGenBaseGroupSupport' for 'xcmGenTrapClientTable'"
    ::= { xcmGenBaseEntry 11 }
xcmGenBaseSNMPVersionSupport OBJECT-TYPE
    SYNTAX      Cardinal32
    MAX-ACCESS  read-only
    STATUS      current
    DESCRIPTION "
        This object is used to specify ALL SNMP versions (RFC 1157, RFC
        1905, etc) which are supported by this management agent
        for SNMP protocol traffic (SNMP responses, SNMP traps, etc),
        in ALL domains specified by 'xcmGenBaseSNMPDomainSupport'.
        Usage:  Conforming management agents SHALL report their
        supported values as a 'bit-mask' formed via the bit-wise OR of
        '2**(n)', where (n) is each supported enumerated value in the
        in the 'XcmGenSNMPVersion' textual convention."
    REFERENCE "
        See:    'XcmGenSNMPVersion' in the XCMI General TC
        See:    'xcmGenTrapClientSNMP[Domain|Version]'."
    ::= { xcmGenBaseEntry 12 }
xcmGenBaseSNMPReadCommunity OBJECT-TYPE
    SYNTAX      OCTET STRING (SIZE (0..64))
    MAX-ACCESS  read-write
    STATUS      current
    DESCRIPTION "
        This object is used to specify a 'read community name' valid
        for use in SNMPv1c and SNMPv2c 'Get|GetNext|GetBulk' PDUs
        received (SNMP requests) and generated (SNMP responses)
        by this management agent.
        Usage:  Note that the object 'xcmGenBaseSNMPWriteCommunity'
        SHALL ALSO be used to specify a 'read community name' valid
        for use in SNMPv1c and SNMPv2c 'Get|GetNext|GetBulk'
        PDUs received (SNMP requests) and generated (SNMP responses)
        by this management agent.  Note however that the object
        'xcmGenBaseSNMPTrapCommunity' SHALL NOT be used to specify a
        'read community name' valid in SNMP 'Get|GetNext|GetBulk'.
        Note:   XCMI-defined community name objects support 64 octets
        maximum length and configurable charsets, for consistency with
        the 'snmpCommunityName' object defined in the SNMP Community MIB
        defined in RFC 2576 (March 2000).
        Note:   Products MAY ship with a market-specific factory default
        locale with a charset other than 'utf-8', eg, in Japan a product
        might factory default to 'shift-jis(17)' or 'iso-2022-jp(39)'.
        Such products MUST implement the 'xcmGenFixedLocalizationTable',
        to prevent ambiguity about the factory default charset.
        Usage:  For best interworking with the ('utf-8' charset ONLY)
        closely related 'snmpCommunitySecurityName' object in RFC 2576,
        conforming management stations and management agents SHOULD NOT
        configure community names longer than 32 octets.
        Usage:  For best interworking with third-party applications,
        conforming management stations and management agents SHOULD NOT
        configure empty (zero-length or all spaces) community names.
        Usage:  All XCMI conforming management agents SHALL treat
        a valid 'write community name' as a valid 'read community name'
        and SHALL NOT increment 'snmpInBadCommunityNames' (unknown name)
        or 'snmpInBadCommunityUses' (wrong community name for operation)
        counters in the SNMPv2 Agent MIB (RFC 1907).
        Usage:  All XCMI conforming management agents are
        STRONGLY RECOMMENDED to support an authenticated SNMP SetRequest
        to this object, changing the system 'read community name'
        (for best interworking with third-party management stations).
        Usage:  All XCMI conforming management agents: a) SHALL
        return a zero length string in response to an SNMP GetRequest of
        this object; b) are STRONGLY RECOMMENDED to default
        this object to the string 'public' (in the static charset); and
        c) MAY support multiple valid 'read community names' (by using
        'xcmGenBaseReadCommunity' as a 'window' to a community list via
        'device[Set|List]' device operations in the Device Mgmt group
        of the XCMI Host Resources Ext MIB).
        Usage:  This object is of type 'XcmFixedLocaleDisplayString',
        with an (opaque) locale and an explicit charset which is
        specified in the 'xcmGenLocalizationCharSet' object indexed
        by 'hrDeviceIndex' per 'xcmGenBaseSystemHrDeviceIndex' and
        'xcmGenLocalizationIndex' per 'xcmGenFixedLocalizationIndex'.
        If 'xcmGenLocalizationTable' or 'xcmGenFixedLocalizationTable'
        are not implemented on this host system, then the charset SHALL
        be 'utf-8(106)', ISO 10646-1 in 'UTF-8' stream encoding.
        Usage:  All XCMI conforming management agents SHALL allow
        any defined character in the configured charset of this object.
        All XCMI conforming management stations SHOULD NOT write control
        characters or other non-display characters into this object.
        WARNING:  Changing the only valid 'read community name' of an
        SNMP management agent will cause a COMPLETE loss of
        communications unless all associated SNMP management stations
        (clients) ALSO change over to the new 'read community name'!!!"
    REFERENCE "
        See:    SNMPv1c (RFC 1157) and SNMPv2c (RFC 1905).
        See:    'Coexistence between SNMPv1, SNMPv2, and SNMPv3'
                RFC 2576, March 2000.
        See:    'xcmGenBaseSNMP[Write|Trap]Community'."
    ::= { xcmGenBaseEntry 13 }
xcmGenBaseSNMPWriteCommunity OBJECT-TYPE
    SYNTAX      OCTET STRING (SIZE (0..64))
    MAX-ACCESS  read-write
    STATUS      current
    DESCRIPTION "
        This object is used to specify a 'write community name' valid
        for use in SNMPv1c and SNMPv2c 'Set' PDUs
        received (SNMP requests) and generated (SNMP responses)
        by this management agent.
        Usage:  Note that the object 'xcmGenBaseSNMPWriteCommunity'
        SHALL ALSO be used to specify a 'read community name' valid
        for use in SNMPv1c and SNMPv2c 'Get|GetNext|GetBulk'
        PDUs received (SNMP requests) and generated (SNMP responses)
        by this management agent.  Note however that the object
        'xcmGenBaseSNMPTrapCommunity' SHALL NOT be used to specify a
        'read community name' valid in SNMP 'Get|GetNext|GetBulk'.
        Usage:  All XCMI conforming management agents SHALL treat
        a valid 'write community name' as a valid 'read community name'
        and SHALL NOT increment 'snmpInBadCommunityNames' (unknown name)
        or 'snmpInBadCommunityUses' (wrong community name for operation)
        counters in the SNMPv2 Agent MIB (RFC 1907).
        Note:   XCMI-defined community name objects support 64 octets
        maximum length and configurable charsets, for consistency with
        the 'snmpCommunityName' object defined in the SNMP Community MIB
        defined in RFC 2576 (March 2000).
        Note:   Products MAY ship with a market-specific factory default
        locale with a charset other than 'utf-8', eg, in Japan a product
        might factory default to 'shift-jis(17)' or 'iso-2022-jp(39)'.
        Such products MUST implement the 'xcmGenFixedLocalizationTable',
        to prevent ambiguity about the factory default charset.
        Usage:  For best interworking with the ('utf-8' charset ONLY)
        closely related 'snmpCommunitySecurityName' object in RFC 2576,
        conforming management stations and management agents SHOULD NOT
        configure community names longer than 32 octets.
        Usage:  For best interworking with third-party applications,
        conforming management stations and management agents SHOULD NOT
        configure empty (zero-length or all spaces) community names.
        Usage:  All XCMI conforming management agents are
        STRONGLY RECOMMENDED to support an authenticated SNMP SetRequest
        to this object, changing the system 'write community name'
        (for best interworking with third-party management stations).
        Usage:  All XCMI conforming management agents: a) SHALL
        return a zero length string in response to an SNMP GetRequest of
        this object; b) are STRONGLY RECOMMENDED to default
        this object to the string 'public' (in the static charset); and
        c) MAY support multiple valid 'write community names' (by using
        'xcmGenBaseWriteCommunity' as a 'window' to a community list via
        'device[Set|List]' device operations in the Device Mgmt group
        of the XCMI Host Resources Ext MIB).
        Usage:  This object is of type 'XcmFixedLocaleDisplayString'
        (see DESCRIPTION of 'xcmGenBaseSNMPReadCommunity' above).
        If 'xcmGenLocalizationTable' or 'xcmGenFixedLocalizationTable'
        are not implemented on this host system, then the charset SHALL
        be 'utf-8(106)', ISO 10646-1 in 'UTF-8' stream encoding.
        Usage:  All XCMI conforming management agents SHALL allow
        any defined character in the configured charset of this object.
        All XCMI conforming management stations SHOULD NOT write control
        characters or other non-display characters into this object.
        Usage:  When an SNMP management stations CHANGES the value of
        this 'write community name', an XCMI conforming management agent
        SHALL use the old (previous) 'write community name' when
        generating the SNMP response to the 'Set' PDU, for consistency.
        WARNING:  Changing the only valid 'write community name' of an
        SNMP management agent will cause a COMPLETE loss of
        communications unless all associated SNMP management stations
        (clients) ALSO change over to the new 'write community name'!!!"
    REFERENCE "
        See:    SNMPv1c (RFC 1157) and SNMPv2c (RFC 1905).
        See:    'Coexistence between SNMPv1, SNMPv2, and SNMPv3'
                RFC 2576, March 2000.
        See:    'xcmGenBaseSNMP[Read|Trap]Community'."
    ::= { xcmGenBaseEntry 14 }
xcmGenBaseSNMPTrapCommunity OBJECT-TYPE
    SYNTAX      OCTET STRING (SIZE (0..64))
    MAX-ACCESS  read-write
    STATUS      current
    DESCRIPTION "
        This object is used to specify a 'trap community name' valid
        for use in SNMPv1c and SNMPv2c 'Inform|Trap' PDUs
        received (SNMP requests) and generated (SNMP traps)
        by this management agent.
        Usage:  Note that the object 'xcmGenBaseSNMPWriteCommunity'
        SHALL ALSO be used to specify a 'read community name' valid
        for use in SNMPv1c and SNMPv2c 'Get|GetNext|GetBulk'
        PDUs received (SNMP requests) and generated (SNMP responses)
        by this management agent.  Note however that the object
        'xcmGenBaseSNMPTrapCommunity' SHALL NOT be used to specify a
        'read community name' valid in SNMP 'Get|GetNext|GetBulk'.
        Note:   XCMI-defined community name objects support 64 octets
        maximum length and configurable charsets, for consistency with
        the 'snmpCommunityName' object defined in the SNMP Community MIB
        defined in RFC 2576 (March 2000).
        Note:   Products MAY ship with a market-specific factory default
        locale with a charset other than 'utf-8', eg, in Japan a product
        might factory default to 'shift-jis(17)' or 'iso-2022-jp(39)'.
        Such products MUST implement the 'xcmGenFixedLocalizationTable',
        to prevent ambiguity about the factory default charset.
        Usage:  For best interworking with the ('utf-8' charset ONLY)
        closely related 'snmpCommunitySecurityName' object in RFC 2576,
        conforming management stations and management agents SHOULD NOT
        configure community names longer than 32 octets.
        Usage:  For best interworking with third-party applications,
        conforming management stations and management agents SHOULD NOT
        configure empty (zero-length or all spaces) community names.
        Usage:  All XCMI conforming management agents are
        STRONGLY RECOMMENDED to support an authenticated SNMP SetRequest
        to this object, changing the system 'trap community name'
        (for best interworking with third-party management stations).
        Usage:  All XCMI conforming management agents: a) SHALL
        return a zero length string in response to an SNMP GetRequest of
        this object; b) are STRONGLY RECOMMENDED to default
        this object to the string 'public' (in the static charset); and
        c) MAY support multiple valid 'trap community names' (by using
        'xcmGenBaseTrapCommunity' as a 'window' to a community list via
        'device[Set|List]' device operations in the Device Mgmt group
        of the XCMI Host Resources Ext MIB).
        Usage:  This object is of type 'XcmFixedLocaleDisplayString'
        (see DESCRIPTION of 'xcmGenBaseSNMPReadCommunity' above).
        If 'xcmGenLocalizationTable' or 'xcmGenFixedLocalizationTable'
        are not implemented on this host system, then the charset SHALL
        be 'utf-8(106)', ISO 10646-1 in 'UTF-8' stream encoding.
        Usage:  All XCMI conforming management agents SHALL allow
        any defined character in the configured charset of this object.
        All XCMI conforming management stations SHOULD NOT write control
        characters or other non-display characters into this object.
        WARNING:  Changing the only valid 'trap community name' of an
        SNMP management agent will cause a COMPLETE loss of
        communications unless all associated SNMP management stations
        (clients) ALSO change over to the new 'trap community name'!!!"
    REFERENCE "
        See:    SNMPv1c (RFC 1157) and SNMPv2c (RFC 1905).
        See:    'Coexistence between SNMPv1, SNMPv2, and SNMPv3'
                RFC 2576, March 2000.
        See:    'xcmGenBaseSNMP[Read|Write]Community'.
        See:    'xcmGenTrapClientSNMPCommunity'."
    ::= { xcmGenBaseEntry 15 }
xcmGenBaseGroupWalkHidden OBJECT-TYPE
    SYNTAX      XcmGenGroupSupport
    MAX-ACCESS  read-write
    STATUS      current
    DESCRIPTION "
        The terse control/report vector of ALL mandatory, conditionally
        mandatory, and optional XCMI General MIB object groups which are
        hidden from MIB walks (via SNMP GetNext or GetBulk PDUs)
        by this management agent implementation (ie, version)
        on this host system, specified in a bit-mask.
        Usage:  When an object group is currently 'hidden' via
        'xcmGenBaseGroupWalkHidden', XCMI conforming management agents
        SHALL skip over that object group to the next
        lexicographically higher object for GetNext or GetBulk requests.
        Usage:  Conforming management agents SHOULD hide the Message Map
        Message Text object groups from MIB walks (as they MAY contain
        thousands of conceptual rows in typical implementations).
        Usage:  Conforming management agents SHALL accurately
        report their hidden MIB walk XCMI General MIB object groups."
    DEFVAL      { 12288 }               
    ::= { xcmGenBaseEntry 16 }
xcmGenBaseNotifySchemeSupport OBJECT-TYPE
    SYNTAX      XcmGenNotifySchemeSupport
    MAX-ACCESS  read-only
    STATUS      current
    DESCRIPTION "
        The terse conformance statement of ALL notification URI schemes
        which are supported by this management agent implementation
        (ie, version) on this host system, specified in a bit-mask.
        Usage:  Conforming management agents SHALL accurately
        report their support for notification URI schemes."
    REFERENCE "
        See:    'XcmGenNotifySchemeSupport' in XCMI General TC.
        See:    'xcmGenBaseSNMPDomainSupport' in XCMI General MIB."
    DEFVAL      { 1 }                   
    ::= { xcmGenBaseEntry 17 }
xcmGenBaseNotifySeveritySupport OBJECT-TYPE
    SYNTAX      XcmGenNotifySeverityFilter
    MAX-ACCESS  read-only
    STATUS      current
    DESCRIPTION "
        The terse conformance statement of ALL notification severity
        filters supported by this management agent implementation
        (ie, version) on this host system, specified in a bit-mask.
        Usage:  Individual trap definitions MAY further constrain which
        notifications are 'in scope'.
        Usage:  Conforming management agents SHALL accurately
        report their support for notification severity filters."
    REFERENCE "
        See:    'prtAlertSeverityLevel' in IETF Printer MIB (RFC 1759).
        See:    'XcmGenNotifySeverityFilter' in XCMI General TC.
        See:    'xcmGenTrapViewNotifySeverity' in XCMI General MIB."
    DEFVAL      { 15 }                  
    ::= { xcmGenBaseEntry 18 }
xcmGenBaseNotifyTrainingSupport OBJECT-TYPE
    SYNTAX      XcmGenNotifyTrainingFilter
    MAX-ACCESS  read-only
    STATUS      current
    DESCRIPTION "
        The terse conformance statement of ALL notification training
        filters supported by this management agent implementation
        (ie, version) on this host system, specified in a bit-mask.
        Usage:  Individual trap definitions MAY further constrain which
        notifications are 'in scope'.
        Usage:  Conforming management agents SHALL accurately
        report their support for notification training filters."
    REFERENCE "
        See:    'prtAlertTrainingLevel' in IETF Printer MIB (RFC 1759).
        See:    'XcmGenNotifyTrainingFilter' in XCMI General TC.
        See:    'xcmGenTrapViewNotifyTraining' in XCMI General MIB."
    DEFVAL      { 60 }                  
    ::= { xcmGenBaseEntry 19 }
xcmGenBaseSystem1284DeviceId OBJECT-TYPE
       SYNTAX     DisplayString (SIZE (0..255))
       MAX-ACCESS read-only
       STATUS     current
       DESCRIPTION "                                                   
         The value of this variable MUST exactly match the 
         IEEE 1284-2000 Device ID string, except the length field MUST 
         NOT be specified. The value is assigned by the Printer vendor 
         and MUST NOT be localized by the agent.   
         The IEEE 1284-2000 Device ID is a length field followed by a 
         case-sensitive string of ASCII characters defining peripheral 
         characteristics and/or capabilities. For the purposes of this 
         specification, the length bytes MUST NOT be included. The 
         Device ID sequence is composed of a series of keys and values 
         of the form:
            key: value {,value} repeated for each key
         As indicated, each key will have one value, and MAY have more 
         than one value. The minimum necessary keys (case-sensitive) are
           MANUFACTURER, COMMAND SET, and MODEL. 
         (These keys MAY be abbreviated as MFG, CMD, and MDL 
         respectively.) Each implementation MUST supply these three keys
         and possibly additional ones as well. Each key (and each value)
         is a string of characters. Any characters except colon (:), 
         comma (,), and semi-colon (;) MAY be included as part of the 
         key (or value) string. Any leading or trailing white space in 
         the string is ignored by the parsing program (but is still 
         counted as part of the overall length of the sequence). 
         An example ID String, showing optional comment and active 
         command set keys and their associated values (the text is 
         actually all on one line):
            MFG:Xerox;
            CMD:PCL,POSTSCRIPT,PJL;
            MDL:WorkCentre Pro 32C;
            CLS:PRINTER;
            DES: Xerox WorkCentre Pro 32C"
    ::= { xcmGenBaseEntry 20 }
xcmGenBaseSNMPWarningTrapSupport OBJECT-TYPE
    SYNTAX      TruthValue
    MAX-ACCESS  read-write
    STATUS      current
    DESCRIPTION "
        This object SHALL be 'true' if this management agent
        supports sending SNMP warning traps. This object SHALL 
        be 'false'if this management agent does NOT support 
        sending SNMP warning traps.
        This does not change the behavior of support for
        sending 'Error Cleared' traps such sending a
        trap when an alertRemovalOfBinaryChangeEntry
        is added to the Alert Table."
    DEFVAL      { false }   
    ::= { xcmGenBaseEntry 21 }
--
--
--
--
xcmGenCurrentLocalization   OBJECT IDENTIFIER ::= { xcmGeneralMIB 3 }
xcmGenCurrentLocalizationTable OBJECT-TYPE
    SYNTAX      SEQUENCE OF XcmGenCurrentLocalizationEntry
    MAX-ACCESS  not-accessible
    STATUS      current
    DESCRIPTION "
        A table of general localization information per device.  It is
        put in a table so it can be per device using the hrDeviceIndex."
    ::= { xcmGenCurrentLocalization 1 }
xcmGenCurrentLocalizationEntry OBJECT-TYPE
    SYNTAX      XcmGenCurrentLocalizationEntry
    MAX-ACCESS  not-accessible
    STATUS      current
    DESCRIPTION "
        Contains the scalar objects that we want to be per device."
    INDEX       { hrDeviceIndex }
    ::= { xcmGenCurrentLocalizationTable 1 }
XcmGenCurrentLocalizationEntry ::= SEQUENCE {
        xcmGenCurrentLocalizationIndex  Ordinal16,
        xcmGenCurrLocalizationRowStatus RowStatus
    }
xcmGenCurrentLocalizationIndex OBJECT-TYPE
    SYNTAX      Ordinal16
    MAX-ACCESS  read-create
    STATUS      current
    DESCRIPTION "
        The value of the 'xcmGenLocalizationIndex' corresponding to the
        current language, country, and character set which SHALL be
        used for all objects of type 'InternationalDisplayString' in
        all legacy MIBs.
        Note the Printer MIB has a similar mechanism which controls only
        objects (of type OCTET STRING) which are in the Printer MIB."
    ::= { xcmGenCurrentLocalizationEntry 1 }
xcmGenCurrLocalizationRowStatus OBJECT-TYPE
    SYNTAX      RowStatus
    MAX-ACCESS  read-create
    STATUS      current
    DESCRIPTION "
        This object manages the row status of this conceptual row in
        the 'xcmGenCurrentLocalizationTable'.
        Usage:  Conforming implementations which support static rows
        SHALL support 'active' and 'notInService' writes to this
        'xcmGenCurrLocalizationRowStatus' row status object; and
        SHALL clear the 'xcmGenCurrentLocalizationGroup' bit in
        'xcmGenBaseGroupCreateSupport' in the 'xcmGenBaseTable'.
        Usage:  Conforming implementations which support dynamic rows
        SHALL support 'createAndGo' and 'destroy' writes to this
        'xcmGenCurrLocalizationRowStatus' row status object; and
        SHALL set the 'xcmGenCurrentLocalizationGroup' bit in
        'xcmGenBaseGroupCreateSupport' in the 'xcmGenBaseTable'.
        Usage:  Conforming implementations NEED NOT support dynamic row
        creation (via 'createAndGo(4)') nor dynamic row deletion (via
        'destroy(6)').
        Usage:  Conforming implementations MAY support a single, static
        conceptual row, but SHALL allocate that row with an
        'hrDeviceIndex' value of one ('1').
        Usage:  This row status SHALL be set, to 'active(1)' (for
        static rows) or 'createAndGo(4)' (for dynamic rows),
        in the same PDU which sets the
        current locale in 'xcmGenCurrentLocalizationIndex'
        (thus activating/allocating this conceptual row).
        Usage:  To explicitly release this conceptual row, a management
        station SHALL set 'xcmGenCurrLocalizationRowStatus' to
        'notInService(2)' (for static rows) or 'destroy(6)' (for dynamic
        rows).
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'RowStatus' in IETF SNMPv2 TC (RFC 1443/1903/2579).
        See:    'xcmHrDevMgmtCommandData' in XCMI HRX MIB and
                'xcmSecUserMgmtData' in XCMI Security MIB."
    ::= { xcmGenCurrentLocalizationEntry 2 }
--
--
--
--
xcmGenLocalization          OBJECT IDENTIFIER ::= { xcmGeneralMIB 4 }
xcmGenLocalizationTable OBJECT-TYPE
    SYNTAX      SEQUENCE OF XcmGenLocalizationEntry
    MAX-ACCESS  not-accessible
    STATUS      current
    DESCRIPTION "
        The available localizations in this device."
    ::= { xcmGenLocalization 1 }
xcmGenLocalizationEntry OBJECT-TYPE
    SYNTAX      XcmGenLocalizationEntry
    MAX-ACCESS  not-accessible
    STATUS      current
    DESCRIPTION "
        An entry exists in this table for each Localization, i.e. for
        each combination of Language, Country (or Territory) and Coded 
        Character Set, that is supported in some objects of type
        'InternationalDisplayString', 'XcmFixedLocaleDisplayString',
        'XcmFixedLocaleUtf8String', or 'XcmNamedLocaleUtf8String'
        for each device on this managed system."
    INDEX       { hrDeviceIndex,
                  xcmGenLocalizationIndex }
    ::= { xcmGenLocalizationTable 1 }
XcmGenLocalizationEntry ::= SEQUENCE {
        xcmGenLocalizationIndex         Ordinal16,
        xcmGenLocalizationRowStatus     RowStatus,
        xcmGenLocalizationASCIIName     DisplayString,
        xcmGenLocalizationName          InternationalDisplayString,
        xcmGenLocalizationLanguage      CodedLanguage,
        xcmGenLocalizationCountry       CodedCountry,
        xcmGenLocalizationCharSet       IANACharset
    }
xcmGenLocalizationIndex OBJECT-TYPE
    SYNTAX      Ordinal16
    MAX-ACCESS  not-accessible
    STATUS      current
    DESCRIPTION "
        A unique value used by the device to identify this
        localization entry."
    ::= { xcmGenLocalizationEntry 1 }
xcmGenLocalizationRowStatus OBJECT-TYPE
    SYNTAX      RowStatus
    MAX-ACCESS  read-create
    STATUS      current
    DESCRIPTION "
        This object manages the row status of this conceptual row in
        the 'xcmGenLocalizationTable'.
        Usage:  Conforming implementations which support static rows
        SHALL support 'active' and 'notInService' writes to this
        'xcmGenLocalizationRowStatus' row status object; and
        SHALL clear the 'xcmGenLocalizationGroup' bit in
        'xcmGenBaseGroupCreateSupport' in the 'xcmGenBaseTable'.
        Usage:  Conforming implementations which support dynamic rows
        SHALL support 'createAndGo' and 'destroy' writes to this
        'xcmGenLocalizationRowStatus' row status object; and
        SHALL set the 'xcmGenLocalizationGroup' bit in
        'xcmGenBaseGroupCreateSupport' in the 'xcmGenBaseTable'.
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'RowStatus' in IETF SNMPv2 TC (RFC 1443/1903/2579).
        See:    'xcmHrDevMgmtCommandData' in XCMI HRX MIB and
                'xcmSecUserMgmtData' in XCMI Security MIB."
    ::= { xcmGenLocalizationEntry 2 }
xcmGenLocalizationASCIIName OBJECT-TYPE
    SYNTAX      DisplayString (SIZE (0..255))
    MAX-ACCESS  read-create
    STATUS      current
    DESCRIPTION "
        The unlocalized human readable name in NVT ASCII of the
        localization with the language, followed by the country 
        (or territory), followed by the character set.
        Example: English US ASCII"
    DEFVAL     { ''H }
    ::= { xcmGenLocalizationEntry 3 }
xcmGenLocalizationName OBJECT-TYPE
    SYNTAX      InternationalDisplayString (SIZE (0..255))
    MAX-ACCESS  read-create
    STATUS      current
    DESCRIPTION "
        The localized human readable name of the localization with
        the language, followed by the country (or territory),
        followed by the character set. 
        Example: Japanese Japan Kanji (Represented with Kanji chars.)"
    DEFVAL     { ''H }                   
    ::= { xcmGenLocalizationEntry 4 }
xcmGenLocalizationLanguage OBJECT-TYPE
    SYNTAX      CodedLanguage
    MAX-ACCESS  read-create
    STATUS      current
    DESCRIPTION "
        A two character language abreviation from ISO 639:1988
        - Codes For the Representation of Names of Languages.
        Examples EN, GB, CA, FR, DE."
    DEFVAL     { ''H }                   
    ::= { xcmGenLocalizationEntry 5 }
xcmGenLocalizationCountry OBJECT-TYPE
    SYNTAX      CodedCountry
    MAX-ACCESS  read-create
    STATUS      current
    DESCRIPTION "
        A two character country or territory abbreviation from
        ISO 3166:1993 - Codes for the Representation of Names of
        Countries.
        Examples: US, FR, DE, ..."
    DEFVAL      { ''H }          
    ::= { xcmGenLocalizationEntry 6 }
xcmGenLocalizationCharSet OBJECT-TYPE
    SYNTAX      IANACharset
    MAX-ACCESS  read-create
    STATUS      current
    DESCRIPTION "
        The charset used for this localization.
        The value is the enum for the charset registered
        with IANA.  See the 'IANACharset' textual-convention in the
        Printer MIB (RFC 1759)."
    DEFVAL      { other }         
    ::= { xcmGenLocalizationEntry 7 }
--
--
--
--
--
xcmGenCodeIndexedString     OBJECT IDENTIFIER ::= { xcmGeneralMIB 5 }
xcmGenCodeIndexedStringTable OBJECT-TYPE
    SYNTAX      SEQUENCE OF XcmGenCodeIndexedStringEntry
    MAX-ACCESS  not-accessible
    STATUS      current
    DESCRIPTION "
        The current charset-indexed strings for this device."
    ::= { xcmGenCodeIndexedString 1 }
xcmGenCodeIndexedStringEntry OBJECT-TYPE
    SYNTAX      XcmGenCodeIndexedStringEntry
    MAX-ACCESS  not-accessible
    STATUS      current
    DESCRIPTION "
        An entry exists in this table containing a charset-indexed
        string in a particular charset.  There are separate sets of
        charset-indexed strings for each device.
        If an agent supports multiple charset representations
        of a charset-indexed string, including code conversion between,
        there will be a separate entry for each such charset
        representation.
        Usage:  'xcmGenCodeIndexedStringCharSet' selects which charset
        representation is to be returned.  The value of
        'xcmGenCodeIndexedStringCharSet' is the charset enum
        registered with IANA. See the 'IANACharset' textual-convention
        in the Printer MIB (RFC 1759).
        Usage:  Conforming management agents SHALL NOT 'reuse' values of
        'xcmGenCodeIndexedStringIndex' until its' 32-bit value wraps.
        This prevents access to 'xcmGenCodeIndexedStringData' contents
        via 'stale' pointers (previously cached from XCMI Job Monitoring
        MIB or XCMI Resources MIB).
        Note:   Conforming management stations SHOULD interwork with
        earlier (pre-XCMI 3.1) management agents which MAY 'reuse'
        values of 'xcmGenCodeIndexedStringIndex'.  By first reading the
        pointer object in XCMI Job Monitoring MIB or XCMI Resources MIB,
        the manager will avoid 'stale' pointer processing errors."
    INDEX       { hrDeviceIndex,
                  xcmGenCodeIndexedStringIndex,
                  xcmGenCodeIndexedStringCharSet }
    ::= { xcmGenCodeIndexedStringTable 1 }
XcmGenCodeIndexedStringEntry ::= SEQUENCE {
        xcmGenCodeIndexedStringIndex         CodeIndexedStringIndex,
        xcmGenCodeIndexedStringCharSet       IANACharset,  
        xcmGenCodeIndexedStringRowStat       RowStatus,
        xcmGenCodeIndexedStringData          OCTET STRING
    }
xcmGenCodeIndexedStringIndex OBJECT-TYPE
    SYNTAX      CodeIndexedStringIndex (1..2147483647)
    MAX-ACCESS  not-accessible
    STATUS      current
    DESCRIPTION "
        A unique value used by the device, along with the following
        'xcmGenCodeIndexedStringCharSet', to identify this
        charset-indexed string entry.
        Usage:  Conforming management agents SHALL NOT 'reuse' values of
        'xcmGenCodeIndexedStringIndex' until its' 32-bit value wraps.
        This prevents access to 'xcmGenCodeIndexedStringData' contents
        via 'stale' pointers (previously cached from XCMI Job Monitoring
        MIB or XCMI Resources MIB).
        Note:   Conforming management stations SHOULD interwork with
        earlier (pre-XCMI 3.1) management agents which MAY 'reuse'
        values of 'xcmGenCodeIndexedStringIndex'.  By first reading the
        pointer object in XCMI Job Monitoring MIB or XCMI Resources MIB,
        the manager will avoid 'stale' pointer processing errors."
    ::= { xcmGenCodeIndexedStringEntry 1 }
xcmGenCodeIndexedStringCharSet OBJECT-TYPE
    SYNTAX      IANACharset
    MAX-ACCESS  not-accessible
    STATUS      current
    DESCRIPTION "
        The charset used for this charset-indexed string entry.
        Usage:  The value is the enum for the charset registered
        with IANA.  See the 'IANACharset' textual-convention in the
        Printer MIB (RFC 1759)."
    ::= { xcmGenCodeIndexedStringEntry 2 }
xcmGenCodeIndexedStringRowStat OBJECT-TYPE
    SYNTAX      RowStatus
    MAX-ACCESS  read-create
    STATUS      current
    DESCRIPTION "
        This object manages the row status of this conceptual row in
        the 'xcmGenCodeIndexedStringTable'.
        Usage:  Conforming implementations which support static rows
        SHALL support 'active' and 'notInService' writes to this
        'xcmGenCodeIndexedStringRowStat' row status object; and
        SHALL clear the 'xcmGenCodeIndexedStringGroup' bit in
        'xcmGenBaseGroupCreateSupport' in the 'xcmGenBaseTable'.
        Usage:  Conforming implementations which support dynamic rows
        SHALL support 'createAndGo' and 'destroy' writes to this
        'xcmGenCodeIndexedStringRowStat' row status object; and
        SHALL set the 'xcmGenCodeIndexedStringGroup' bit in
        'xcmGenBaseGroupCreateSupport' in the 'xcmGenBaseTable'.
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'RowStatus' in IETF SNMPv2 TC (RFC 1443/1903/2579).
        See:    'xcmHrDevMgmtCommandData' in XCMI HRX MIB and
                'xcmSecUserMgmtData' in XCMI Security MIB."
    ::= { xcmGenCodeIndexedStringEntry 3 }
xcmGenCodeIndexedStringData OBJECT-TYPE
    SYNTAX      OCTET STRING (SIZE (0..255))
    MAX-ACCESS  read-create
    STATUS      current
    DESCRIPTION "
        This is the actual charset-indexed string data, in the charset
        identified by 'xcmGenCodeIndexedStringCharSet'."
    DEFVAL     { ''H }      
    ::= { xcmGenCodeIndexedStringEntry 4 }
--
--
--
--
xcmGenCodedCharSet          OBJECT IDENTIFIER ::= { xcmGeneralMIB 6 }
xcmGenCodedCharSetTable OBJECT-TYPE
    SYNTAX      SEQUENCE OF XcmGenCodedCharSetEntry
    MAX-ACCESS  not-accessible
    STATUS      current
    DESCRIPTION "
        The supported charsets for this device."
    ::= { xcmGenCodedCharSet 1 }
xcmGenCodedCharSetEntry OBJECT-TYPE
    SYNTAX      XcmGenCodedCharSetEntry
    MAX-ACCESS  not-accessible
    STATUS      current
    DESCRIPTION "
        An entry exists in this table for each charset
        supported in some objects of 'CodeIndexedStringIndex' type for
        each device."
    INDEX       { hrDeviceIndex,
                  xcmGenCodedCharSetCharSet }
    ::= { xcmGenCodedCharSetTable 1 }
XcmGenCodedCharSetEntry ::= SEQUENCE {
        xcmGenCodedCharSetCharSet       IANACharset,
        xcmGenCodedCharSetRowStatus     RowStatus,
        xcmGenCodedCharSetASCIIName     DisplayString
    }
xcmGenCodedCharSetCharSet OBJECT-TYPE
    SYNTAX      IANACharset
    MAX-ACCESS  not-accessible
    STATUS      current
    DESCRIPTION "
        The supported charset enum identifier, used an index
        for this table.  The value is the enum for the charset
        registered with IANA."
    REFERENCE "
        See the 'IANACharset' textual-convention in the Printer MIB."
    ::= { xcmGenCodedCharSetEntry 1 }
xcmGenCodedCharSetRowStatus OBJECT-TYPE
    SYNTAX      RowStatus
    MAX-ACCESS  read-create
    STATUS      current
    DESCRIPTION "
        This object manages the row status of this conceptual row in
        the 'xcmGenCodedCharSetTable'.
        Usage:  Conforming implementations which support static rows
        SHALL support 'active' and 'notInService' writes to this
        'xcmGenCodedCharSetRowStatus' row status object; and
        SHALL clear the 'xcmGenCodedCharSetGroup' bit in
        'xcmGenBaseGroupCreateSupport' in the 'xcmGenBaseTable'.
        Usage:  Conforming implementations which support dynamic rows
        SHALL support 'createAndGo' and 'destroy' writes to this
        'xcmGenCodedCharSetRowStatus' row status object; and
        SHALL set the 'xcmGenCodedCharSetGroup' bit in
        'xcmGenBaseGroupCreateSupport' in the 'xcmGenBaseTable'.
        Usage:  Conforming implementations NEED NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'RowStatus' in IETF SNMPv2 TC (RFC 1443/1903/2579).
        See:    'xcmHrDevMgmtCommandData' in XCMI HRX MIB and
                'xcmSecUserMgmtData' in XCMI Security MIB."
    ::= { xcmGenCodedCharSetEntry 2 }
xcmGenCodedCharSetASCIIName OBJECT-TYPE
    SYNTAX      DisplayString (SIZE (0..255))
    MAX-ACCESS  read-create
    STATUS      current
    DESCRIPTION "
        The unlocalized human readable name in ASCII of the
        charset.
        Example: 'ASCII'"
    DEFVAL     { ''H }                        
    ::= { xcmGenCodedCharSetEntry 3 }
--
--
--
--
xcmGenFixedLocalization     OBJECT IDENTIFIER ::= { xcmGeneralMIB 7 }
xcmGenFixedLocalizationTable OBJECT-TYPE
    SYNTAX      SEQUENCE OF XcmGenFixedLocalizationEntry
    MAX-ACCESS  not-accessible
    STATUS      current
    DESCRIPTION "
        A table of fixed localization information per device.  It is
        put in a table so it can be per device using the hrDeviceIndex."
    REFERENCE "
        See:    'XcmFixedLocale[Display|Utf8]String' in the
                XCMI General TC."
    ::= { xcmGenFixedLocalization 1 }
xcmGenFixedLocalizationEntry OBJECT-TYPE
    SYNTAX      XcmGenFixedLocalizationEntry
    MAX-ACCESS  not-accessible
    STATUS      current
    DESCRIPTION "
        An entry of fixed localization information per device."
    REFERENCE "
        See:    'XcmFixedLocale[Display|Utf8]String' in the
                XCMI General TC."
    INDEX       { hrDeviceIndex }
    ::= { xcmGenFixedLocalizationTable 1 }
XcmGenFixedLocalizationEntry ::= SEQUENCE {
        xcmGenFixedLocalizationIndex    Ordinal16,
        xcmGenFixedLocalizationRowStat  RowStatus
    }
xcmGenFixedLocalizationIndex OBJECT-TYPE
    SYNTAX      Ordinal16
    MAX-ACCESS  read-create
    STATUS      current
    DESCRIPTION "
        The value of the 'xcmGenLocalizationIndex' corresponding to the
        current language, country, and character set which SHALL be
        used for all objects of type 'XcmFixedLocaleDisplayString'
        in all current and future MIBs.
        Also, the value of the 'xcmGenLocalizationIndex' corresponding
        to the language and country (but FIXED UTF-8) which SHALL be
        used for all objects of type 'XcmFixedLocaleUtf8String'
        in all current and future MIBs."
    REFERENCE "
        See:    'XcmFixedLocale[Display|Utf8]String' in the
                XCMI General TC.
        See:    'UTF-8, a transformation of ISO 10646' (RFC 2279) and
        'IETF Policy on Character Sets and Languages' (RFC 2277)."
    ::= { xcmGenFixedLocalizationEntry 1 }
xcmGenFixedLocalizationRowStat OBJECT-TYPE
    SYNTAX      RowStatus
    MAX-ACCESS  read-create
    STATUS      current
    DESCRIPTION "
        This object manages the row status of this conceptual row in
        the 'xcmGenFixedLocalizationTable'.
        Usage:  Conforming implementations which support static rows
        SHALL support 'active' and 'notInService' writes to this
        'xcmGenFixedLocalizationRowStat' row status object; and
        SHALL clear the 'xcmGenFixedLocalizationGroup' bit in
        'xcmGenBaseGroupCreateSupport' in the 'xcmGenBaseTable'.
        Usage:  Conforming implementations which support dynamic rows
        SHALL support 'createAndGo' and 'destroy' writes to this
        'xcmGenFixedLocalizationRowStat' row status object; and
        SHALL set the 'xcmGenFixedLocalizationGroup' bit in
        'xcmGenBaseGroupCreateSupport' in the 'xcmGenBaseTable'.
        Usage:  Conforming implementations NEED NOT support dynamic row
        creation (via 'createAndGo(4)') nor dynamic row deletion (via
        'destroy(6)').
        Usage:  Conforming implementations MAY support a single, static
        conceptual row, but SHALL allocate that row with an
        'hrDeviceIndex' value of one ('1').
        Usage:  This row status SHALL be set, to 'active(1)' (for
        static rows) or 'createAndGo(4)' (for dynamic rows),
        in the same PDU which sets the
        fixed locale in 'xcmGenFixedLocalizationIndex'
        (thus activating/allocating this conceptual row).
        Usage:  To explicitly release this conceptual row, a management
        station SHALL set 'xcmGenFixedLocalizationRowStat' to
        'notInService(2)' (for static rows) or 'destroy(6)' (for dynamic
        rows).
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'RowStatus' in IETF SNMPv2 TC (RFC 1443/1903/2579).
        See:    'xcmHrDevMgmtCommandData' in XCMI HRX MIB and
                'xcmSecUserMgmtData' in XCMI Security MIB."
    ::= { xcmGenFixedLocalizationEntry 2 }
--
--
--
--
--
xcmGenLock                  OBJECT IDENTIFIER ::= { xcmGeneralMIB 8 }
--
--
xcmGenLockSimple OBJECT-IDENTITY
    STATUS      current
    DESCRIPTION "
        This subtree is current.  Subordinate objects are leaf objects."
    ::= { xcmGenLock 1 }
xcmGenLockSupportMaxTimer OBJECT-TYPE
    SYNTAX      Cardinal32
    UNITS       "seconds"
    MAX-ACCESS  read-only
    STATUS      current
    DESCRIPTION "
        The advisory lock supported max owner timer (in seconds) for
        use for ANY advisory lock in the 'xcmGenLockTable'.
        Usage:  The value zero ('0') represents 'no limit'.
        Usage:  This supported max timer represents an XCMI enhancement
        to the traditional advisory lock mechanism used in existing IETF
        MIB modules (eg, RFC 1573).  It provides reliable information to
        a management station contending for advisory locks, about the
        MAXIMUM time supported (ie, permitted) for ANY advisory lock by
        the management agent on this host system."
    REFERENCE "
        See:    'xcmGenLockCurrentMaxTimer' and 'xcmGenLockOwnerTimer'"
    DEFVAL      { 0 }                   
    ::= { xcmGenLockSimple 1 }
xcmGenLockCurrentMaxTimer OBJECT-TYPE
    SYNTAX      Cardinal32
    UNITS       "seconds"
    MAX-ACCESS  read-only
    STATUS      current
    DESCRIPTION "
        The advisory lock current max owner timer (in seconds) in
        use for ANY advisory lock in the 'xcmGenLockTable'.
        Usage:  This current max timer represents an XCMI enhancement
        to the traditional advisory lock mechanism used in existing IETF
        MIB modules (eg, RFC 1573).  It provides reliable information to
        a management station contending for advisory locks, about the
        current MAXIMUM time until expiration for ALL advisory locks for
        the management agent on this host system.
        Note:   To acquire an advisory lock on an ENTIRE host system,
        a conforming management station (or management agent) SHALL
        examine 'xcmGenLockCurrentMaxTimer', add an appropriate
        delta for eventual processing, and lock the 'xcmGenLockTable'
        itself.  When 'xcmGenLockCurrentLockCount' subsequently becomes
        one (1), the requesting management station (or management agent)
        has acquired a lock on the ENTIRE host system (since no OTHER
        entity MAY acquire any further lock, because 'xcmGenLockTable'
        has become 'read-only' to all other entities), and MAY proceed
        accordingly."
    REFERENCE "
        See:    'xcmGenLockSupportMaxTimer' and 'xcmGenLockOwnerTimer'"
    DEFVAL      { 0 }                   
    ::= { xcmGenLockSimple 2 }
xcmGenLockCurrentLockCount OBJECT-TYPE
    SYNTAX      Cardinal32
    MAX-ACCESS  read-only
    STATUS      current
    DESCRIPTION "
        The count of entries (rows) which are currently in the 'active'
        state in 'xcmGenLockTable'.
        Usage:  This current lock count represents an XCMI enhancement
        to the traditional advisory lock mechanism used in existing IETF
        MIB modules (eg, RFC 1573)."
    REFERENCE "
        See:    'xcmGenLockHighestLockIndex'"
    DEFVAL      { 0 }                   
    ::= { xcmGenLockSimple 3 }
xcmGenLockHighestLockIndex OBJECT-TYPE
    SYNTAX      Cardinal32
    MAX-ACCESS  read-only
    STATUS      current
    DESCRIPTION "
        The highest advisory lock index which has been active in the
        'xcmGenLockTable'.
        Usage:  This highest lock index represents an XCMI enhancement
        to the traditional advisory lock mechanism used in existing IETF
        MIB modules (eg, RFC 1573)."
    REFERENCE "
        See:    'xcmGenLockCurrentLockCount'"
    DEFVAL      { 0 }                   
    ::= { xcmGenLockSimple 4 }
xcmGenLockSupportMaxCount OBJECT-TYPE
    SYNTAX      Cardinal32
    MAX-ACCESS  read-only
    STATUS      current
    DESCRIPTION "
        The maximum number of simultaneous entries (rows) supported
        for the 'xcmGenLockTable'.
        Usage:  The value zero ('0') represents 'no limit'."
    REFERENCE "
        See:    'xcmGenLockCurrentLockCount'"
    DEFVAL      { 0 }                   
    ::= { xcmGenLockSimple 5 }
--
--
xcmGenLockTable OBJECT-TYPE
    SYNTAX      SEQUENCE OF XcmGenLockEntry
    MAX-ACCESS  not-accessible
    STATUS      current
    DESCRIPTION "
        A table containing 'advisory contention lock' objects for
        various subtrees of MIB objects from the complete set of IETF
        and XCMI MIB modules implemented by this host system.
        Note:   To acquire an advisory lock on an ENTIRE host system,
        a conforming management station (or management agent) SHALL
        examine 'xcmGenLockCurrentMaxTimer', add an appropriate
        delta for eventual processing, and lock the 'xcmGenLockTable'
        itself.  When 'xcmGenLockCurrentLockCount' subsequently becomes
        one (1), the requesting management station (or management agent)
        has acquired a lock on the ENTIRE host system (since no OTHER
        entity MAY acquire any further lock, because 'xcmGenLockTable'
        has become 'read-only' to all other entities), and MAY proceed
        accordingly."
    REFERENCE "
        See:    'ifTestOwner' and the 'OwnerString' textual convention
        in Evolution of the Interfaces Group of MIB-II (RFC 1573)."
    ::= { xcmGenLock 2 }
xcmGenLockEntry OBJECT-TYPE
    SYNTAX      XcmGenLockEntry
    MAX-ACCESS  not-accessible
    STATUS      current
    DESCRIPTION "
        An entry containing 'advisory contention lock' objects for one
        specific subtree of MIB objects from the complete set of IETF
        and XCMI MIB modules implemented by this host system."
    INDEX       { xcmGenLockIndex }
    ::= { xcmGenLockTable 1 }
XcmGenLockEntry ::= SEQUENCE {
        xcmGenLockIndex                 Ordinal32,
        xcmGenLockRowStatus             RowStatus,
        xcmGenLockOwnerString           OCTET STRING,
        xcmGenLockOwnerSubtree          OBJECT IDENTIFIER,
        xcmGenLockOwnerTimer            Cardinal32
    }
--
--
xcmGenLockIndex OBJECT-TYPE
    SYNTAX      Ordinal32
    MAX-ACCESS  not-accessible
    STATUS      current
    DESCRIPTION "
        A unique value used by this host system to identify this
        conceptual row in the 'xcmGenLockTable' - each conceptual row in
        the 'xcmGenLockTable' represents an 'advisory contention lock'
        on a specific subtree of MIB objects from the complete set of
        IETF and XCMI MIB modules implemented by this host system."
    REFERENCE "
        See:    'XcmGenLockIndex' textual convention"
    ::= { xcmGenLockEntry 1 }
xcmGenLockRowStatus OBJECT-TYPE
    SYNTAX      RowStatus
    MAX-ACCESS  read-create
    STATUS      current
    DESCRIPTION "
        This object manages the row status of this conceptual row in
        the 'xcmGenLockTable'.
        Usage:  Conforming implementations which support static rows
        SHALL support 'active' and 'notInService' writes to this
        'xcmGenLockRowStatus' row status object; and
        SHALL clear the 'xcmGenLockGroup' bit in
        'xcmGenBaseGroupCreateSupport' in the 'xcmGenBaseTable'.
        Usage:  Conforming implementations which support dynamic rows
        SHALL support 'createAndGo' and 'destroy' writes to this
        'xcmGenLockRowStatus' row status object; and
        SHALL set the 'xcmGenLockGroup' bit in
        'xcmGenBaseGroupCreateSupport' in the 'xcmGenBaseTable'.
        Usage:  Conforming implementations NEED NOT support dynamic row
        creation (via 'createAndGo(4)') nor dynamic row deletion (via
        'destroy(6)').
        Usage:  Conforming implementations MAY support a single, static
        conceptual row, but SHALL allocate that row with an
        'xcmGenLockIndex' value of one ('1').
        Usage:  Conforming management stations, when they first create
        or activate rows in this table, SHALL set
        'xcmGenLockRowStatus' to 'active(1)' (for static rows) or
        'createAndGo(4)' (for dynamic rows),
        'xcmGenLockOwnerString' (if an owner string is available),
        'xcmGenLockOwnerSubtree' (if not 'zeroDotZero'), and
        'xcmGenLockOwnerTimer' (to a suitable value)
        SIMULTANEOUSLY (in the same SNMP Set-Request PDU).
        Usage:  Conforming management agents SHALL NOT accept sets to
        'xcmGenLockOwnerString', or
        'xcmGenLockOwnerSubtree'
        AFTER row creation (these objects are 'write-once').
        Usage:  To explicitly release this advisory lock, the current
        lock owner (management station or management agent) SHALL
        set 'xcmGenLockRowStatus' in this row to 'notInService(2)' (for
        static rows) or 'destroy(6)' (for dynamic rows).
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'xcmGenLockSupportMaxCount' (limit object).
        See:    'RowStatus' in IETF SNMPv2 TC (RFC 1443/1903/2579).
        See:    'xcmHrDevMgmtCommandData' in XCMI HRX MIB and
                'xcmSecUserMgmtData' in XCMI Security MIB."
    ::= { xcmGenLockEntry 2 }
xcmGenLockOwnerString OBJECT-TYPE
    SYNTAX      OCTET STRING (SIZE (0..255))
    MAX-ACCESS  read-create             
    STATUS      current
    DESCRIPTION "
        The advisory lock owner string corresponding to the current
        'owner' of this advisory lock.
        Usage:  Conforming management stations, when they first create
        or activate rows in this table, SHALL set
        'xcmGenLockRowStatus' to 'active(1)' (for static rows) or
        'createAndGo(4)' (for dynamic rows),
        'xcmGenLockOwnerString' (if an owner string is available),
        'xcmGenLockOwnerSubtree' (if not 'zeroDotZero'), and
        'xcmGenLockOwnerTimer' (to a suitable value)
        SIMULTANEOUSLY (in the same SNMP Set-Request PDU).
        Usage:  Conforming management agents SHALL NOT accept sets to
        'xcmGenLockOwnerString', or
        'xcmGenLockOwnerSubtree'
        AFTER row creation (these objects are 'write-once').
        Usage:  This owner string SHALL contain one or more of
        the following:
        a)  Textual form of the management station's transport address;
        b)  Management station name (eg, domain name); and/or
        c)  Network management person's name, location, or phone.
        In the instance that the management agent itself is the 'owner',
        this object SHALL be set to a string beginning with
        'agent' (in English).
        Usage:  This object is of type 'XcmFixedLocaleDisplayString'."
    REFERENCE "
        See:    'xcmGenLockRowStatus', 'xcmGenLockOwnerSubtree', and
                'xcmGenLockOwnerTimer'.
        See:    'ifTestOwner' and the 'OwnerString' textual convention
        in Evolution of the Interfaces Group of MIB-II (RFC 1573)."
    DEFVAL      { ''H }                 
    ::= { xcmGenLockEntry 3 }
xcmGenLockOwnerSubtree OBJECT-TYPE
    SYNTAX      OBJECT IDENTIFIER
    MAX-ACCESS  read-create             
    STATUS      current
    DESCRIPTION "
        The advisory lock owner subtree (ie, scope) for the current
        'owner' of this advisory lock.
        Usage:  Conforming management stations, when they first create
        or activate rows in this table, SHALL set
        'xcmGenLockRowStatus' to 'active(1)' (for static rows) or
        'createAndGo(4)' (for dynamic rows),
        'xcmGenLockOwnerString' (if an owner string is available),
        'xcmGenLockOwnerSubtree' (if not 'zeroDotZero'), and
        'xcmGenLockOwnerTimer' (to a suitable value)
        SIMULTANEOUSLY (in the same SNMP Set-Request PDU).
        Usage:  Conforming management agents SHALL NOT accept sets to
        'xcmGenLockOwnerString', or
        'xcmGenLockOwnerSubtree'
        AFTER row creation (these objects are 'write-once').
        Usage:  This owner subtree represents an XCMI enhancement to
        the traditional advisory lock mechanism used in existing IETF
        MIB modules (eg, RFC 1573)."
    REFERENCE "
        See:    'xcmGenLockRowStatus', 'xcmGenLockOwnerString', and
                'xcmGenLockOwnerTimer'."
    DEFVAL      { zeroDotZero }   
    ::= { xcmGenLockEntry 4 }
xcmGenLockOwnerTimer OBJECT-TYPE
    SYNTAX      Cardinal32
    UNITS       "seconds"
    MAX-ACCESS  read-create
    STATUS      current
    DESCRIPTION "
        The advisory lock owner lock time remaining for the current
        'owner' of this advisory lock (in seconds).
        Usage:  A conforming management agent MAY choose to reduce the
        'credit' granted as a result of a set to this owner lock timer,
        at its sole discretion (see 'xcmGenLockSupportMaxTimer' object).
        Usage:  Conforming management stations, when they first create
        or activate rows in this table, SHALL set
        'xcmGenLockRowStatus' to 'active(1)' (for static rows) or
        'createAndGo(4)' (for dynamic rows),
        'xcmGenLockOwnerString' (if an owner string is available),
        'xcmGenLockOwnerSubtree' (if not 'zeroDotZero'), and
        'xcmGenLockOwnerTimer' (to a suitable value)
        SIMULTANEOUSLY (in the same SNMP Set-Request PDU).
        Usage:  Conforming management agents SHALL NOT accept sets to
        'xcmGenLockOwnerString', or
        'xcmGenLockOwnerSubtree'
        AFTER row creation (these objects are 'write-once').
        Usage:  A conforming management station MAY choose to increase
        or reduce the value of this owner lock timer, subsequent to
        initial row creation, for example to 'refresh' the timer for an
        additional time interval.
        Usage:  A conforming management station SHALL NOT reduce the
        value of this owner lock timer to zero (as an indirect 'destroy'
        operation).  A conforming management agent SHALL reject
        any such set to zero of this owner lock timer.
        Usage:  This owner lock timer represents an XCMI enhancement to
        the traditional advisory lock mechanism used in existing IETF
        MIB modules (eg, RFC 1573).  It provides reliable information to
        a management station (or management agent) contending for this
        advisory lock, about the MAXIMUM time until this advisory lock
        lock will be released (either by explicit action of the owner of
        the advisory lock or by 'timeout' handling of the management
        agent itself)."
    REFERENCE "
        See:    'xcmGenLockRowStatus', 'xcmGenLockOwnerSubtree', and
        'xcmGenLockOwnerSubtree'."
    ::= { xcmGenLockEntry 5 }
--
--
--
--
xcmGenReconf                OBJECT IDENTIFIER ::= { xcmGeneralMIB 9 }
--
--
xcmGenReconfSimple OBJECT-IDENTITY
    STATUS      current
    DESCRIPTION "
        This subtree is current.  Subordinate objects are leaf objects."
    ::= { xcmGenReconf 1 }
xcmGenReconfActivations OBJECT-TYPE
    SYNTAX      Counter32
    MAX-ACCESS  read-only
    STATUS      current
    DESCRIPTION "
        The count of SUCCESSFUL 'activations' of reconfiguration for
        this host system:  invoked by SUCCESSFUL writes to the
        'xcmGenReconfOptionState' reconfiguration invocation object of
        'activateFor[ImmediateChange|RebootChange|ImmediateReboot]';
        and followed by SUCCESSFUL completions of 'activation' (without
        errors reports in 'xcmGenReconfError[Index|Status]').
        Usage:  Although no default value ('DEFVAL' clause) is permitted
        (by IETF SMIv2) for this counter, conforming host systems SHALL
        zero this counter upon conceptual row creation."
    REFERENCE "
        See:    'xcmGenReconfOptionState'"
    ::= { xcmGenReconfSimple 1 }
xcmGenReconfEntryCount OBJECT-TYPE
    SYNTAX      Counter32
    MAX-ACCESS  read-only
    STATUS      current
    DESCRIPTION "
        The count of entries (rows) which are currently in the 'active'
        state in 'xcmGenReconfTable'."
    ::= { xcmGenReconfSimple 2 }
xcmGenReconfSupportMaxCount OBJECT-TYPE
    SYNTAX      Cardinal32
    MAX-ACCESS  read-only
    STATUS      current
    DESCRIPTION "
        The maximum number of simultaneous entries (rows) supported
        for the 'xcmGenReconfTable'.
        Usage:  The value zero ('0') represents 'no limit'."
    DEFVAL      { 0 }                   
    ::= { xcmGenReconfSimple 3 }
--
--
xcmGenReconfTable OBJECT-TYPE
    SYNTAX      SEQUENCE OF XcmGenReconfEntry
    MAX-ACCESS  not-accessible
    STATUS      current
    DESCRIPTION "
        A table containing information on a 'reconfiguration request',
        for use in atomic reconfiguration of this host system.
        Usage:  A conforming management station (or management agent)
        SHALL lock 'xcmGenReconfTable' and 'xcmGenOptionTable'
        before attempting to perform any 'reconfiguration request' on a
        host system (via the 'xcmGenLockTable')."
    ::= { xcmGenReconf 2 }
xcmGenReconfEntry OBJECT-TYPE
    SYNTAX      XcmGenReconfEntry
    MAX-ACCESS  not-accessible
    STATUS      current
    DESCRIPTION "
        An entry containing information on a 'reconfiguration request',
        for use in atomic reconfiguration of this host system.
        Usage:  The ONLY valid row in the 'xcmGenReconfTable' for each
        supported device ('hrDeviceIndex') SHALL have an
        'xcmGenReconfIndex' of one ('1')."
    INDEX       { hrDeviceIndex,
                  xcmGenReconfIndex }
    ::= { xcmGenReconfTable 1 }
XcmGenReconfEntry ::= SEQUENCE {
        xcmGenReconfIndex               Ordinal32,
        xcmGenReconfRowStatus           RowStatus,
        xcmGenReconfOptionIndex         Cardinal32,
        xcmGenReconfOptionState         XcmGenReconfOptionState,
        xcmGenReconfErrorIndex          Cardinal32,
        xcmGenReconfErrorStatus         XcmGenSNMPv2ErrorStatus
    }
--
--
xcmGenReconfIndex OBJECT-TYPE
    SYNTAX      Ordinal32
    MAX-ACCESS  not-accessible
    STATUS      current
    DESCRIPTION "
        A unique value used by this host system to identify this
        conceptual row in the 'xcmGenReconfTable'.
        Usage:  The ONLY valid row in the 'xcmGenReconfTable' for each
        supported device ('hrDeviceIndex') SHALL have an
        'xcmGenReconfIndex' of one ('1')."
    REFERENCE "
        See:    System, Device, and Software Installed/Running groups
                in the IETF Host Resources MIB (RFC 2790).
        See:    Device Info, Device Mgmt, and Device Detail groups
                in the XCMI Host Resources Ext MIB."
    ::= { xcmGenReconfEntry 1 }
xcmGenReconfRowStatus OBJECT-TYPE
    SYNTAX      RowStatus
    MAX-ACCESS  read-create
    STATUS      current
    DESCRIPTION "
        This object manages the row status of this conceptual row in
        the 'xcmGenReconfTable'.
        Usage:  Conforming implementations which support static rows
        SHALL support 'active' and 'notInService' writes to this
        'xcmGenReconfRowStatus' row status object; and
        SHALL clear the 'xcmGenReconfGroup' bit in
        'xcmGenBaseGroupCreateSupport' in the 'xcmGenBaseTable'.
        Usage:  Conforming implementations which support dynamic rows
        SHALL support 'createAndGo' and 'destroy' writes to this
        'xcmGenReconfRowStatus' row status object; and
        SHALL set the 'xcmGenReconfGroup' bit in
        'xcmGenBaseGroupCreateSupport' in the 'xcmGenBaseTable'.
        Usage:  Conforming management agents SHALL support
        'active(1)' and SHOULD support 'notInService(2)' or 'destroy(6)'
        (to 'release' the 'reconfiguration request').
        Usage:  Conforming management agents NEED NOT support
        'createAndGo(4)', and SHOULD NOT support 'notReady(3)' or
        'createAndWait(5)'.
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'xcmGenReconfSupportMaxCount' (limit object).
        See:    'RowStatus' in IETF SNMPv2 TC (RFC 1443/1903/2579).
        See:    'xcmHrDevMgmtCommandData' in XCMI HRX MIB and
                'xcmSecUserMgmtData' in XCMI Security MIB."
    ::= { xcmGenReconfEntry 2 }
xcmGenReconfOptionIndex OBJECT-TYPE
    SYNTAX      Cardinal32
    MAX-ACCESS  read-create
    STATUS      current
    DESCRIPTION "
        The value of 'xcmGenOptionIndex' corresponding to the first
        pending reconfiguration option (in 'xcmGenOptionTable'), or
        zero if there are no pending reconfiguration options for this
        host system.
        Usage:  This 'chain' represents pending reconfiguration
        options of this host system."
    REFERENCE "
        See:    'xcmGenReconfActiveOptionIndex'"
    DEFVAL      { 0 }                   
    ::= { xcmGenReconfEntry 3 }
xcmGenReconfOptionState OBJECT-TYPE
    SYNTAX      XcmGenReconfOptionState
    MAX-ACCESS  read-create
    STATUS      current
    DESCRIPTION "
        The processing state of ALL pending reconfiguration options of
        this host system.
        A write to this object by an (authorized) management station
        invokes a request for validation (or activation) of ALL pending
        reconfiguration options of this host system.
        A read of this object returns 'idle', 'validateInProgress', or
        'activateInProgress' to report the processing state of the last
        'validate...' or 'activate...' request.
        It is mandatory that a conforming management agent ensure that,
        at system initialization, this object SHALL be set to a
        value of 'idle'.
        Usage:  Conforming management agents SHALL 'reject' any
        SNMP Set-Request to 'xcmGenReconfOptionState'
        while another management operation is already in progress
        (ie, while 'xcmGenReconfOptionState' is NOT equal to 'idle')
        with 'badValue' (SNMPv1) or 'inconsistentValue' (SNMPv2/v3).
        Usage:  See section 3.4 'Secure Modes of Operation' and section
        3.5 'Secure SNMP Get/Set Requests' in XCMI Security TC, for
        details of secure modes of access to this option state object."
    REFERENCE "
        See:    'xcmGenReconfError[Index|Status]'
        See:    'XcmGenReconfOptionState', in the companion XCMI
        CC TC, for details of 'validation' and 'activation' operations.
        See:    'xcmHrDevMgmtCommandData' in XCMI HRX MIB and
                'xcmSecUserMgmtData' in XCMI Security MIB."
    DEFVAL      { idle }                
    ::= { xcmGenReconfEntry 4 }
xcmGenReconfErrorIndex OBJECT-TYPE
    SYNTAX      Cardinal32
    MAX-ACCESS  read-only
    STATUS      current
    DESCRIPTION "
        The value of 'xcmGenOptionIndex' corresponding to the first
        pending reconfiguration option (in 'xcmGenOptionTable') which
        was found to be 'in error' (during 'validate' or 'activate'
        reconfiguration processing for this host system), or zero
        if no error was found (eg, consistency, range, etc)."
    REFERENCE "
        See:    'xcmGenReconfErrorStatus'"
    DEFVAL      { 0 }                   
    ::= { xcmGenReconfEntry 5 }
xcmGenReconfErrorStatus OBJECT-TYPE
    SYNTAX      XcmGenSNMPv2ErrorStatus
    MAX-ACCESS  read-only
    STATUS      current
    DESCRIPTION "
        The reconfiguration error status corresponding to the first
        pending reconfiguration option (in 'xcmGenOptionTable') which
        was found to be 'in error' (during 'validate' or 'activate'
        reconfiguration processing for this host system), or 'noError'
        if no error was found (eg, consistency, range, etc)."
    REFERENCE "
        See:    'xcmGenReconfErrorIndex'"
    ::= { xcmGenReconfEntry 6 }
--
--
--
--
xcmGenOption                OBJECT IDENTIFIER ::= { xcmGeneralMIB 10 }
--
--
xcmGenOptionSimple OBJECT-IDENTITY
    STATUS      current                 
    DESCRIPTION "
        This subtree is current.  Subordinate objects are leaf objects."
    ::= { xcmGenOption 1 }
--
--
--
--
--
xcmGenOptionOperation
    OBJECT IDENTIFIER ::= { xcmGenOptionSimple 1 }
xcmGenOptionOperationInsert
    OBJECT IDENTIFIER ::= { xcmGenOptionOperation 1 }
xcmGenOptionOperationDelete
    OBJECT IDENTIFIER ::= { xcmGenOptionOperation 2 }
xcmGenOptionOperationReplace
    OBJECT IDENTIFIER ::= { xcmGenOptionOperation 3 }
xcmGenOptionEntryCount OBJECT-TYPE
    SYNTAX      Counter32
    MAX-ACCESS  read-only
    STATUS      current
    DESCRIPTION "
        The count of entries (rows) which are currently in the 'active'
        state in 'xcmGenOptionTable'."
    ::= { xcmGenOptionSimple 2 }
xcmGenOptionSupportMaxCount OBJECT-TYPE
    SYNTAX      Cardinal32
    MAX-ACCESS  read-only
    STATUS      current
    DESCRIPTION "
        The maximum number of simultaneous entries (rows) supported
        for the 'xcmGenOptionTable'.
        Usage:  The value zero ('0') represents 'no limit'."
    DEFVAL      { 0 }                   
    ::= { xcmGenOptionSimple 3 }
--
--
xcmGenOptionTable OBJECT-TYPE
    SYNTAX      SEQUENCE OF XcmGenOptionEntry
    MAX-ACCESS  not-accessible
    STATUS      current
    DESCRIPTION "
        A table containing information on reconfiguration options,
        for use in atomic reconfiguration of this host system.
        Usage:  A conforming management station (or management agent)
        SHALL lock 'xcmGenReconfTable' and 'xcmGenOptionTable'
        before attempting to perform any 'reconfiguration request' on a
        host system (via the 'xcmGenLockTable').
        Note:   The 'xcmGenOptionTable' is indexed by 'hrDeviceIndex',
        so the 'hrDeviceIndex' element of a columnar object instance ID
        (ie, fully specified object identifier) NEED NOT be specified in
        'xcmGenOptionTypeOID'.  To reconfigure objects indexed by
        several devices in 'hrDeviceTable' of the IETF Host Resources
        MIB (RFC 2790), a conforming management station SHALL use
        several rows in 'xcmGenReconfTable' and several trees of objects
        in 'xcmGenOptionTable' with appropriate 'hrDeviceIndex' values.
        To reconfigure objects which are actually NOT indexed by
        'hrDeviceIndex', it is RECOMMENDED that rows be used in
        'xcmGenOptionTable' which are indexed by 'hrDeviceIndex' for an
        'hrDeviceType' of 'hrDeviceUnknown'."
    ::= { xcmGenOption 2 }
xcmGenOptionEntry OBJECT-TYPE
    SYNTAX      XcmGenOptionEntry
    MAX-ACCESS  not-accessible
    STATUS      current
    DESCRIPTION "
        An entry containing information on a reconfiguration option,
        for use in atomic reconfiguration of this host system."
    INDEX       { hrDeviceIndex,
                  xcmGenOptionIndex }
    ::= { xcmGenOptionTable 1 }
XcmGenOptionEntry ::= SEQUENCE {
        xcmGenOptionIndex               Ordinal32,
        xcmGenOptionRowStatus           RowStatus,
        xcmGenOptionTypeOID             OBJECT IDENTIFIER,
        xcmGenOptionValueSyntax         XcmGenOptionValueSyntax,
        xcmGenOptionValueInteger        Integer32,
        xcmGenOptionValueOID            OBJECT IDENTIFIER,
        xcmGenOptionValueString         OCTET STRING,
        xcmGenOptionValueLocalization   Cardinal32,
        xcmGenOptionValueCodedCharSet   IANACharset,
        xcmGenOptionNextIndex           Cardinal32,
        xcmGenOptionPreviousIndex       Cardinal32,
        xcmGenOptionFamilyIndex         Cardinal32
    }
--
--
xcmGenOptionIndex OBJECT-TYPE
    SYNTAX      Ordinal32
    MAX-ACCESS  not-accessible
    STATUS      current
    DESCRIPTION "
        A unique value used by this host system to identify this
        conceptual row in the 'xcmGenOptionTable'."
    ::= { xcmGenOptionEntry 1 }
xcmGenOptionRowStatus OBJECT-TYPE
    SYNTAX      RowStatus
    MAX-ACCESS  read-create
    STATUS      current
    DESCRIPTION "
        This object manages the row status of this conceptual row in
        the 'xcmGenOptionTable'.
        Usage:  Conforming implementations which support static rows
        SHALL support 'active' and 'notInService' writes to this
        'xcmGenOptionRowStatus' row status object; and
        SHALL clear the 'xcmGenOptionGroup' bit in
        'xcmGenBaseGroupCreateSupport' in the 'xcmGenBaseTable'.
        Usage:  Conforming implementations which support dynamic rows
        SHALL support 'createAndGo' and 'destroy' writes to this
        'xcmGenOptionRowStatus' row status object; and
        SHALL set the 'xcmGenOptionGroup' bit in
        'xcmGenBaseGroupCreateSupport' in the 'xcmGenBaseTable'.
        Usage:  Conforming management agents SHALL support
        'active(1)' and SHOULD support 'notInService(2)' or 'destroy(6)'
        (to 'release' the 'reconfiguration option').
        Usage:  Conforming management agents NEED NOT support
        'createAndGo(4)', and SHOULD NOT support 'notReady(3)' or
        'createAndWait(5)'.
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'xcmGenOptionSupportMaxCount' (limit object).
        See:    'RowStatus' in IETF SNMPv2 TC (RFC 1443/1903/2579).
        See:    'xcmHrDevMgmtCommandData' in XCMI HRX MIB and
                'xcmSecUserMgmtData' in XCMI Security MIB."
    ::= { xcmGenOptionEntry 2 }
xcmGenOptionTypeOID OBJECT-TYPE
    SYNTAX      OBJECT IDENTIFIER
    MAX-ACCESS  read-create
    STATUS      current
    DESCRIPTION "
        An unambiguous reconfiguration option type,
        used by system administrators and end users to identify
        this reconfiguration option.
        Usage:  Since this reconfiguration option type is specified
        as an object identifier, it MAY be taken from any IETF, Xerox,
        third- party, or product-specific MIB, or it MAY simply be any
        IETF SMIv2-style 'autonomous type'."
    DEFVAL      { zeroDotZero }   
    ::= { xcmGenOptionEntry 3 }
xcmGenOptionValueSyntax OBJECT-TYPE
    SYNTAX      XcmGenOptionValueSyntax
    MAX-ACCESS  read-create
    STATUS      current
    DESCRIPTION "
        A reconfiguration option value syntax,
        used by system administrators and end users to specify
        the correct value syntax for this reconfiguration option.
        Usage:  This reconfiguration option value syntax is used to
        select which of the following three objects SHALL be used to
        contain the value of this reconfiguration option."
    DEFVAL      { unknown }             
    ::= { xcmGenOptionEntry 4 }
xcmGenOptionValueInteger OBJECT-TYPE
    SYNTAX      Integer32
    MAX-ACCESS  read-create
    STATUS      current
    DESCRIPTION "
        A reconfiguration option value integer,
        used by system administrators and end users to specify
        the current value for a reconfiguration option
        with a base value syntax of 'INTEGER'.
        Note: This object has the type 'Integer32', rather than
        'INTEGER'.  This a work-around to compiler warnings which occur
        when 'INTEGER' is used without a range specification.  And if
        we had range qualified, it would have been identical to the
        SNMP 'Integer32' type.  In SNMPv2, only the 'Counter64 is an
        integer type wider 32 bits, and for backward compatibility we
        depricated the use of Counter64."
    REFERENCE "
        See:    'xcmGenOptionValueSyntax' and 'xcmGenOptionTypeOID'"
    DEFVAL      { 0 }                   
    ::= { xcmGenOptionEntry 5 }
xcmGenOptionValueOID OBJECT-TYPE
    SYNTAX      OBJECT IDENTIFIER
    MAX-ACCESS  read-create
    STATUS      current
    DESCRIPTION "
        A reconfiguration option value OID (object identifier),
        used by system administrators and end users to specify
        the current value for a reconfiguration option
        with a base value syntax of 'OBJECT IDENTIFIER'."
    REFERENCE "
        See:    'xcmGenOptionValueSyntax' and 'xcmGenOptionTypeOID'"
    DEFVAL      { zeroDotZero }   
    ::= { xcmGenOptionEntry 6 }
xcmGenOptionValueString OBJECT-TYPE
    SYNTAX      OCTET STRING (SIZE (0..255))
    MAX-ACCESS  read-create
    STATUS      current
    DESCRIPTION
        "A reconfiguration option value string,
        used by system administrators and end users to specify
        the current value for a reconfiguration option
        with a base value syntax of 'OCTET STRING'.
        Usage:  This object is of type 'XcmFixedLocaleDisplayString'
        (if 'xcmGenOptionValueLocalization' is zero)
        or 'XcmNamedLocaleUtf8String'
        (if 'xcmGenOptionValueLocalization' is non-zero)."
    REFERENCE
        "See:   'xcmGenOptionValueSyntax' and 'xcmGenOptionTypeOID'
        See:    'xcmGenFixedLocalizationIndex' in XCMI General MIB."
    DEFVAL      { ''H }                 
    ::= { xcmGenOptionEntry 7 }
xcmGenOptionValueLocalization OBJECT-TYPE
    SYNTAX      Cardinal32
    MAX-ACCESS  read-create
    STATUS      current
    DESCRIPTION
        "A reconfiguration option value localization,
        used by system administrators and end users to specify
        the ALTERNATE localization for a reconfiguration option
        (different from 'xcmGenFixedLocalizationIndex'), so that
        'xcmGenOptionValueString' becomes 'XcmNamedLocaleUtf8String'.
        Usage:  For a reconfiguration option string to which POSIX-style
        localization (territory, language, character set) is applicable
        (non-keyword) this object MAY contain a suitable index value for
        'xcmGenLocalizationIndex' from the XCMI General MIB, or zero to
        indicate 'none'."
    REFERENCE
        "See:   'xcmGenOptionValueSyntax' and 'xcmGenOptionTypeOID'.
        See:    'xcmGenFixedLocalizationIndex' in XCMI General MIB."
    DEFVAL      { 0 }                   
    ::= { xcmGenOptionEntry 8 }
xcmGenOptionValueCodedCharSet OBJECT-TYPE
    SYNTAX      IANACharset
    MAX-ACCESS  read-create
    STATUS      current
    DESCRIPTION
        "A reconfiguration option value character set,
        used by system administrators and end users to specify
        the ALTERNATE character set for a reconfiguration option
        (different from 'xcmGenFixedLocalizationIndex'), so that
        'xcmGenOptionValueString' is unambiguous.
        Usage:  XCMI conforming management agents SHALL ONLY allow
        Sets of this object to 'other' (none) or 'utf-8' (Unicode/
        ISO-10646 in the UTF-8 encoding, a proper superset of US-ASCII),
        for consistency with the Xerox Unicode Coherence Standard."
    REFERENCE
        "See:   'xcmGenOptionValueSyntax' and 'xcmGenOptionTypeOID'.
        See:    'IANACharset' in IETF Printer MIB (RFC 1759).
        See:    'xcmGenCodedCharSetTable' in XCMI General MIB."
    DEFVAL      { other }               
    ::= { xcmGenOptionEntry 9 }
--
--
xcmGenOptionNextIndex OBJECT-TYPE
    SYNTAX      Cardinal32
    MAX-ACCESS  read-create
    STATUS      current
    DESCRIPTION "
        The value of 'xcmGenOptionIndex' corresponding to the next
        'chained' conceptual row in the 'xcmGenOptionTable', or zero
        if this is the last associated conceptual row in a particular
        vertical 'chain' within a given set.
        Usage:  Generally, reconfiguration options (of similar or unlike
        type) are 'chained' vertically via '...[Next|Previous]Index'.
        But, in the case where particular communications options MUST
        be 'tightly coupled', they SHOULD be 'shelved' horizontally via
        '...[Family|Previous]Index' (eg, an IP address and an IP subnet
        mask)."
    DEFVAL      { 0 }                   
    ::= { xcmGenOptionEntry 10 }
xcmGenOptionPreviousIndex OBJECT-TYPE
    SYNTAX      Cardinal32
    MAX-ACCESS  read-create
    STATUS      current
    DESCRIPTION "
        The value of 'xcmGenOptionIndex' corresponding to a previous
        associated conceptual row in the 'xcmGenOptionTable', or zero
        if this is the first associated conceptual row in a given set.
        Usage:  This object provides common 'backward' linkage for BOTH
        the 'xcmGenOptionNextIndex' and 'xcmGenOptionFamilyIndex'
        linkage objects.  A previous conceptual row MAY 'forward'
        reference this conceptual row via either '...NextIndex' or
        '...FamilyIndex' - ie, a given conceptual row MAY 'forward'
        reference EXACTLY zero, one, or two 'later' conceptual rows."
    DEFVAL      { 0 }                   
    ::= { xcmGenOptionEntry 11 }
xcmGenOptionFamilyIndex OBJECT-TYPE
    SYNTAX      Cardinal32
    MAX-ACCESS  read-create
    STATUS      current
    DESCRIPTION "
        The value of 'xcmGenOptionIndex' corresponding to a next
        'family' conceptual row in the 'xcmGenOptionTable', or zero
        if this conceptual row has no associated 'family' members.
        Usage:  Generally, reconfiguration options (of similar or unlike
        type) are 'chained' vertically via '...[Next|Previous]Index'.
        But, in the case where particular reconfiguration options MUST
        be 'tightly coupled', they SHOULD be 'shelved' horizontally via
        '...FamilyIndex' (eg, an IP address and an IP subnet mask)."
    DEFVAL      { 0 }                   
    ::= { xcmGenOptionEntry 12 }
--
--
--
--
xcmGenClientData            OBJECT IDENTIFIER ::= { xcmGeneralMIB 11 }
--
--
xcmGenClientDataSimple OBJECT-IDENTITY
    STATUS      current
    DESCRIPTION "
        This subtree is current.  Subordinate objects are leaf objects."
    ::= { xcmGenClientData 1 }
xcmGenClientDataEntryCount OBJECT-TYPE
    SYNTAX      Counter32
    MAX-ACCESS  read-only
    STATUS      current
    DESCRIPTION "
        The count of entries (rows) which are currently in the 'active'
        state in 'xcmGenClientDataTable'."
    ::= { xcmGenClientDataSimple 1 }
xcmGenClientDataLastIndex OBJECT-TYPE
    SYNTAX      Cardinal32
    MAX-ACCESS  read-only
    STATUS      current
    DESCRIPTION "
        The last entry index (regardless of its current state) in
        the 'xcmGenClientDataTable' of this General MIB,
        on this host system.
        Usage:  This last entry index explicitly bounds the valid range
        of 'xcmGenClientDataIndex'."
    ::= { xcmGenClientDataSimple 2 }
xcmGenClientDataSupportMaxCount OBJECT-TYPE
    SYNTAX      Cardinal32
    MAX-ACCESS  read-only
    STATUS      current
    DESCRIPTION "
        The maximum number of simultaneous entries (rows) supported
        for the 'xcmGenClientDataTable'.
        Usage:  The value zero ('0') represents 'no limit'."
    DEFVAL      { 0 }                   
    ::= { xcmGenClientDataSimple 3 }
--
--
xcmGenClientDataTable OBJECT-TYPE
    SYNTAX      SEQUENCE OF XcmGenClientDataEntry
    MAX-ACCESS  not-accessible
    STATUS      current
    DESCRIPTION "
        A table containing 'client data' objects for use by conforming
        management stations/agents, particularly during installation
        of this host system.
        Usage:  For managed systems which support static rows (ie,
        'read-write'), a management station (or management agent) SHALL
        search 'xcmGenClientDataRowStatus', to determine the
        appropriate value of 'xcmGenClientDataIndex' to use when
        allocating an existing row in the 'xcmGenClientDataTable'.
        Usage:  For managed systems which support dynamic rows (ie,
        'read-create'), a management station (or management agent) SHALL
        examine 'xcmGenClientDataLastIndex', to determine the
        appropriate value of 'xcmGenClientDataIndex' to use when
        creating a new row in the 'xcmGenClientDataTable'.
        Usage:  Throughout this specification, the term 'stable storage'
        refers to storage which is reliable over long durations (years)
        and is NOT destroyed by host system reboot (eg, battery-backed
        DRAM is 'stable storage' - while simple DRAM is NOT 'stable
        storage').  Examples of valid 'stable storage' include:  NVRAM,
        hard disk, EEPROM, etc.
        Usage:  Conforming implementations SHALL preserve active
        'client data' objects across management agent power cycles,
        and SHALL implement one of the following two methods:
        1)  The agent SHALL store 'client data' objects directly in
            'stable storage'; or
        2)  The agent SHALL automatically checkpoint all active 'client
            data' objects to 'stable storage' with reasonable frequency
            (either due to a write to some 'client data' object, or upon
            expiration of a product-specific timeout).
        Usage:  Conforming implementations MAY (optionally) support
        one of the following two 'checkpoint protocols':
        1)  A client sends a 'Set' of 'xcmGenClientDataRowStatus' to
            'active(1)', to request that a 'checkpoint' be performed;
        2a) An agent which supports 'rapid checkpoint',
            completes the checkpoint to 'stable storage', and
            sends a 'SetResponse' with 'noError(0)';
            <or>
        2b) An agent which supports 'delayed checkpoint',
            changes 'xcmGenClientDataRowStatus' to 'notInService(2)',
            sends a 'SetResponse' with 'noError(0)',
            completes the checkpoint to 'stable storage', and later
            changes 'xcmGenClientDataRowStatus' back to 'active(1)'."
    ::= { xcmGenClientData 2 }
xcmGenClientDataEntry OBJECT-TYPE
    SYNTAX      XcmGenClientDataEntry
    MAX-ACCESS  not-accessible
    STATUS      current
    DESCRIPTION "
        An entry containing 'client data' objects for use by conforming
        management stations/agents, particularly during installation
        of this host system."
    INDEX       { xcmGenClientDataIndex }
    ::= { xcmGenClientDataTable 1 }
XcmGenClientDataEntry ::= SEQUENCE {
        xcmGenClientDataIndex           Ordinal32,
        xcmGenClientDataRowStatus       RowStatus,
        xcmGenClientDataRequestDate     DateAndTime,
        xcmGenClientDataRequestID       XcmGlobalUniqueID,
        xcmGenClientDataProductID       ProductID,
        xcmGenClientDataLength          Cardinal32,
        xcmGenClientDataString          OCTET STRING
    }
--
--
xcmGenClientDataIndex OBJECT-TYPE
    SYNTAX      Ordinal32
    MAX-ACCESS  not-accessible
    STATUS      current
    DESCRIPTION "
        A unique value used by this host system to identify this
        conceptual row in the 'xcmGenClientDataTable'.
        Usage:  Conforming implementations which only support a single,
        statically allocated row, SHALL allocate that row with an
        'xcmGenClientDataIndex' value of one (1)."
    ::= { xcmGenClientDataEntry 1 }
xcmGenClientDataRowStatus OBJECT-TYPE
    SYNTAX      RowStatus
    MAX-ACCESS  read-create
    STATUS      current
    DESCRIPTION "
        This object manages the row status of this conceptual row in
        the 'xcmGenClientDataTable'.
        Usage:  Conforming implementations which support static rows
        SHALL support 'active' and 'notInService' writes to this
        'xcmGenClientDataRowStatus' row status object; and
        SHALL clear the 'xcmGenClientDataGroup' bit in
        'xcmGenBaseGroupCreateSupport' in the 'xcmGenBaseTable'.
        Usage:  Conforming implementations which support dynamic rows
        SHALL support 'createAndGo' and 'destroy' writes to this
        'xcmGenClientDataRowStatus' row status object; and
        SHALL set the 'xcmGenClientDataGroup' bit in
        'xcmGenBaseGroupCreateSupport' in the 'xcmGenBaseTable'.
        Usage:  Conforming implementations NEED NOT support dynamic row
        creation (via 'createAndGo(4)') nor dynamic row deletion (via
        'destroy(6)').
        Usage:  Conforming implementations MAY support a single, static
        conceptual row, but SHALL allocate that row with an
        'xcmGenClientDataIndex' value of one ('1').
        Usage:  Conforming management stations, when they first create
        or activate rows in this table, SHALL set
        'xcmGenClientDataRowStatus' to 'active(1)' (for static rows) or
        'createAndGo(4)' (for dynamic rows),
        'xcmGenClientDataRequestID' (to a suitable client global ID),
        'xcmGenClientDataProductID' (to a suitable client product ID),
        'xcmGenClientDataLength' (to a suitable client data length)
        SIMULTANEOUSLY (in the same SNMP Set-Request PDU).
        Usage:  Conforming management agents SHALL NOT accept sets to
        'xcmGenClientDataRequestID',
        'xcmGenClientDataProductID', or
        'xcmGenClientDataLength'
        AFTER row creation (these objects are 'write-once').
        Usage:  To explicitly release this conceptual row, the client
        data owner SHALL set 'xcmGenClientDataRowStatus' to
        'notInService(2)' (for static rows) or 'destroy(6)' (for dynamic
        rows).
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'xcmGenClientDataSupportMaxCount' (limit object).
        See:    'RowStatus' in IETF SNMPv2 TC (RFC 1443/1903/2579).
        See:    'xcmHrDevMgmtCommandData' in XCMI HRX MIB and
                'xcmSecUserMgmtData' in XCMI Security MIB."
    ::= { xcmGenClientDataEntry 2 }
xcmGenClientDataRequestDate OBJECT-TYPE
    SYNTAX      DateAndTime
    MAX-ACCESS  read-only
    STATUS      current
    DESCRIPTION "
        The client data request date which uniquely timestamps the
        creation of this conceptual row in the 'xcmGenClientDataTable'.
        Usage:  This request date SHALL be set (to a suitable
        value) by conforming management agents during creation of each
        conceptual row in the 'xcmGenClientDataTable'.
        Usage:  Conforming implementations which have a source of time,
        SHALL set a meaningful value in this object.  ONLY those
        implementations which do NOT have a source of time, SHALL return
        the following DEFVAL."
    REFERENCE "
        See:    'xcmGenClientDataRowStatus'"
    DEFVAL      { '0000000000000000'H } 
    ::= { xcmGenClientDataEntry 3 }
xcmGenClientDataRequestID OBJECT-TYPE
    SYNTAX      XcmGlobalUniqueID
    MAX-ACCESS  read-create             
    STATUS      current
    DESCRIPTION "
        The client data owner request ID which uniquely identifies the
        creation of this conceptual row in the 'xcmGenClientDataTable'.
        Usage:  Conforming management stations, when they first create
        or activate rows in this table, SHALL set
        'xcmGenClientDataRowStatus' to 'active(1)' (for static rows) or
        'createAndGo(4)' (for dynamic rows),
        'xcmGenClientDataRequestID' (to a suitable client global ID),
        'xcmGenClientDataProductID' (to a suitable client product ID),
        'xcmGenClientDataLength' (to a suitable client data length)
        SIMULTANEOUSLY (in the same SNMP Set-Request PDU).
        Usage:  Conforming management agents SHALL NOT accept sets to
        'xcmGenClientDataRequestID',
        'xcmGenClientDataProductID', or
        'xcmGenClientDataLength'
        AFTER row creation (these objects are 'write-once')."
    REFERENCE "
        See:    'xcmGenClientDataRowStatus'"
    DEFVAL      { ''H }                 
    ::= { xcmGenClientDataEntry 4 }
xcmGenClientDataProductID OBJECT-TYPE
    SYNTAX      ProductID
    MAX-ACCESS  read-create             
    STATUS      current
    DESCRIPTION "
        The client data owner product ID corresponding to the current
        'owner' of this client data.
        Usage:  Conforming management stations, when they first create
        or activate rows in this table, SHALL set
        'xcmGenClientDataRowStatus' to 'active(1)' (for static rows) or
        'createAndGo(4)' (for dynamic rows),
        'xcmGenClientDataRequestID' (to a suitable client global ID),
        'xcmGenClientDataProductID' (to a suitable client product ID),
        'xcmGenClientDataLength' (to a suitable client data length)
        SIMULTANEOUSLY (in the same SNMP Set-Request PDU).
        Usage:  Conforming management agents SHALL NOT accept sets to
        'xcmGenClientDataRequestID',
        'xcmGenClientDataProductID', or
        'xcmGenClientDataLength'
        AFTER row creation (these objects are 'write-once')."
    REFERENCE "
        See:    'xcmGenClientDataRowStatus'
        See:    'ProductID' in IETF Host Resources MIB (RFC 2790)."
    DEFVAL      { zeroDotZero }   
    ::= { xcmGenClientDataEntry 5 }
xcmGenClientDataLength OBJECT-TYPE
    SYNTAX      Cardinal32
    MAX-ACCESS  read-create             
    STATUS      current
    DESCRIPTION "
        The client data length requested/granted for this
        conceptual row in the 'xcmGenClientDataTable'.
        Usage:  Conforming implementations NEED NOT support maximum
        client data length greater than 1 octet.
        Usage:  Conforming management stations, when they first create
        or activate rows in this table, SHALL set
        'xcmGenClientDataRowStatus' to 'active(1)' (for static rows) or
        'createAndGo(4)' (for dynamic rows),
        'xcmGenClientDataRequestID' (to a suitable client global ID),
        'xcmGenClientDataProductID' (to a suitable client product ID),
        'xcmGenClientDataLength' (to a suitable client data length)
        SIMULTANEOUSLY (in the same SNMP Set-Request PDU).
        Usage:  Conforming management agents SHALL NOT accept sets to
        'xcmGenClientDataRequestID',
        'xcmGenClientDataProductID', or
        'xcmGenClientDataLength'
        AFTER row creation (these objects are 'write-once')."
    REFERENCE "
        See:    'xcmGenClientDataRowStatus'"
    DEFVAL      { 0 }                   
    ::= { xcmGenClientDataEntry 6 }
xcmGenClientDataString OBJECT-TYPE
    SYNTAX      OCTET STRING (SIZE (0..255))
    MAX-ACCESS  read-create
    STATUS      current
    DESCRIPTION "
        The client data string currently set into this conceptual
        row in the 'xcmGenClientDataTable'.
        Usage:  Conforming implementations NEED NOT support maximum
        client data length greater than 1 octet.
        Usage:  This data string NEED NOT be set (to a suitable
        value) by the client data owner, in the same PDU which creates
        each conceptual row in the 'xcmGenClientDataTable'."
    REFERENCE "
        See:    'xcmGenClientDataRowStatus'"
    DEFVAL      { ''H }                 
    ::= { xcmGenClientDataEntry 7 }
--
--
--
xcmGenTrapClient            OBJECT IDENTIFIER ::= { xcmGeneralMIB 13 }
--
--
xcmGenTrapClientSimple OBJECT-IDENTITY
    STATUS      current
    DESCRIPTION "
        This subtree is current.  Subordinate objects are leaf objects."
    ::= { xcmGenTrapClient 1 }
xcmGenTrapClientEntryCount OBJECT-TYPE
    SYNTAX      Counter32
    MAX-ACCESS  read-only
    STATUS      current
    DESCRIPTION "
        The count of entries (rows) which are currently in the 'active'
        state in 'xcmGenTrapClientTable'."
    ::= { xcmGenTrapClientSimple 1 }
xcmGenTrapClientSupportMaxCount OBJECT-TYPE
    SYNTAX      Cardinal32
    MAX-ACCESS  read-only
    STATUS      current
    DESCRIPTION "
        The maximum number of simultaneous entries (rows) supported
        for the 'xcmGenTrapClientTable'.
        Usage:  The value zero ('0') represents 'no limit'."
    DEFVAL      { 0 }                   
    ::= { xcmGenTrapClientSimple 2 }
--
--
xcmGenTrapClientTable OBJECT-TYPE
    SYNTAX      SEQUENCE OF XcmGenTrapClientEntry
    MAX-ACCESS  not-accessible
    STATUS      current
    DESCRIPTION "
        A table of SNMP trap clients (management stations or proxies)
        registered for trap delivery from this host system.
        Usage:  SNMP version/transport independent trap registration.
        Usage:  Conforming management stations SHALL create at
        least one subordinate row in the 'xcmGenTrapViewTable' for each
        trap client that they register in the 'xcmGenTrapClientTable'.
        Conforming management agents SHOULD interpret a dangling row in
        the 'xcmGenTrapClientTable' (no children) as 'NO traps in view'
        (existing implementations of both clients and devices are known
        to consider dangling rows invalid).  To register for all device
        traps, use a single view of 'iso(1).org(3).dod(6).internet(1)'.
        Usage:  Conforming management agents SHALL delete any
        rows in the 'xcmGenTrapViewTable' which were subordinate to a
        deleted row in the 'xcmGenTrapClientTable'."
    REFERENCE "
        See:    Party group in Historic SNMPv2 Party MIB (RFC 1447)."
    ::= { xcmGenTrapClient 2 }
xcmGenTrapClientEntry OBJECT-TYPE
    SYNTAX      XcmGenTrapClientEntry
    MAX-ACCESS  not-accessible
    STATUS      current
    DESCRIPTION "
        An entry for an SNMP trap client (management station or proxy)
        registered for trap delivery from this host system."
    INDEX       { xcmGenTrapClientSNMPDomain,
                  xcmGenTrapClientSNMPAddress }
    ::= { xcmGenTrapClientTable 1 }
XcmGenTrapClientEntry ::= SEQUENCE {
        xcmGenTrapClientSNMPDomain      XcmGenSNMPDomain,
        xcmGenTrapClientSNMPAddress     OCTET STRING,
        xcmGenTrapClientRowStatus       RowStatus,
        xcmGenTrapClientIndex           Ordinal32,
        xcmGenTrapClientRowPersistence  XcmGenRowPersistence,
        xcmGenTrapClientSNMPVersion     XcmGenSNMPVersion,
        xcmGenTrapClientSNMPCommunity   OCTET STRING
    }
xcmGenTrapClientSNMPDomain OBJECT-TYPE
    SYNTAX      XcmGenSNMPDomain
    MAX-ACCESS  not-accessible
    STATUS      current
    DESCRIPTION "
        This object is used to specify the transport domain (address
        and name space) which SHALL be used by this management agent
        for SNMP protocol traffic (transmission of SNMP traps),
        in the version specified by 'xcmGenTrapClientSNMPVersion',
        to the trap client (management station or proxy).
        This object is also used to allow the 'xcmGenTrapClientTable' to
        be used with any URI scheme (e.g., 'mailto:') for notifications,
        by specifying 'uriNotifyDomain'."
    REFERENCE "
        See:    'xcmGenBaseSNMP[Domain|Version]Support'.
        See:    'XcmGenSNMPDomain' textual convention in the
                XCMI General TC.
        See:    'snmp...Domain' object identifiers in the
                IETF SNMPv2 Transport Mappings (RFC 1449/1906)."
    ::= { xcmGenTrapClientEntry 1 }
xcmGenTrapClientSNMPAddress OBJECT-TYPE
    SYNTAX      OCTET STRING (SIZE (0..255))
    MAX-ACCESS  not-accessible
    STATUS      current
    DESCRIPTION "
        This object is used to specify the transport address (below
        SNMP) which SHALL be used by this management agent to deliver
        SNMP traps to the trap client (management station or proxy).
        Usage:  This transport address usually consists of an underlying
        network layer address with a suffixed transport selector.
        Usage:  This object is of type 'XcmFixedLocaleDisplayString'."
    REFERENCE "
        See:    'xcmGenBaseSNMP[Domain|Version]Support'.
        See:    'SnmpUDPAddress' (IP addr, UDP port - Internet),
                'SNMPOSIAddress' (len, NSAP addr, TSelector - OSI),
                'SNMPNBPAddress' (object, type, zone - AppleTalk), and
                'SNMPIPXAddress' (net no, MAC addr, socket - NetWare)
                textual conventions in the
                IETF SNMPv2 Transport Mappings (RFC 1449/1906).
        See:    'XcmSNMPNetbiosAddress' (MAC addr, port - NetBIOS)
                textual conventions in the
                XCMI Comms Config TC.
        See:    'XcmSnmpIPHostnameAddress' textual convention in the
                XCMI Comms Config TC."
    ::= { xcmGenTrapClientEntry 2 }
xcmGenTrapClientRowStatus OBJECT-TYPE
    SYNTAX      RowStatus
    MAX-ACCESS  read-create
    STATUS      current
    DESCRIPTION "
        This object manages the row status of this conceptual row in
        the 'xcmGenTrapClientTable'.
        Usage:  It is conformant to implement this object as read-only,
        however, conforming management agents are STRONGLY RECOMMENDED
        to support at least read-write access to this object.
        Usage:  Conforming management stations, when they first create
        new rows in this table, SHALL set
        'xcmGenTrapClientRowStatus' (to 'createAndGo'),
        'xcmGenTrapClientRowPersistence' (if not 'volatile'),
        'xcmGenTrapClientSNMPVersion' (if not 'snmpV1Community'), and
        'xcmGenTrapClientSNMPCommunity' (if not the current managed
        system default in 'xcmGenBaseSNMPTrapCommunity')
        SIMULTANEOUSLY (in the same SNMP Set-Request PDU).
        Usage:  Conforming management agents SHALL NOT accept sets to
        'xcmGenTrapClientRowPersistence',
        'xcmGenTrapClientSNMPVersion', or
        'xcmGenTrapClientSNMPCommunity'
        AFTER row creation (these objects are 'write-once').
        Usage:  Conforming implementations which support dynamic rows
        SHALL support 'createAndGo' and 'destroy' writes to this
        'xcmGenTrapClientRowStatus' row status object; and
        SHALL set the 'xcmGenTrapClientGroup' bit in
        'xcmGenBaseGroupCreateSupport' in the 'xcmGenBaseTable'.
        Usage:  Conforming management agents SHOULD NOT support
        'notInService(2)', 'notReady(3)', or 'createAndWait(5)'.
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'xcmGenTrapClientSupportMaxCount' (limit object).
        See:    'RowStatus' in IETF SNMPv2 TC (RFC 1443/1903/2579).
        See:    'xcmHrDevMgmtCommandData' in XCMI HRX MIB and
                'xcmSecUserMgmtData' in XCMI Security MIB."
    ::= { xcmGenTrapClientEntry 3 }
xcmGenTrapClientIndex OBJECT-TYPE
    SYNTAX      Ordinal32
    MAX-ACCESS  read-only
    STATUS      current
    DESCRIPTION "
        A unique value ASSIGNED by this host system to identify this
        conceptual row in the 'xcmGenTrapClientTable'.
        This object is used to specify the unique client index which was
        chosen FOR the trap client registered in this conceptual row
        (management station or proxy) at row creation and which SHALL be
        used by the trap client to create any associated conceptual
        rows in the 'xcmGenTrapViewTable'.
        Usage:  Conforming management agents NEED NOT preserve the
        value of this object across power cycles for 'nonvolatile' rows
        in the 'xcmGenTrapClientTable', but SHALL preserve the
        configured associations with (any) subordinate rows in the
        'xcmGenTrapViewTable'."
    ::= { xcmGenTrapClientEntry 4 }
xcmGenTrapClientRowPersistence OBJECT-TYPE
    SYNTAX      XcmGenRowPersistence
    MAX-ACCESS  read-create             
    STATUS      current
    DESCRIPTION "
        This object is used to specify the persistence of this
        conceptual row in the 'xcmGenTrapClientTable' (and associated
        conceptual rows in the 'xcmGenTrapViewTable').
        Usage:  It is conformant to implement this object as read-only,
        however, conforming management agents are STRONGLY RECOMMENDED
        to support at least read-write access to this object.
        Usage:  Conforming management stations, when they first create
        new rows in this table, SHALL set
        'xcmGenTrapClientRowStatus' (to 'createAndGo'),
        'xcmGenTrapClientRowPersistence' (if not 'volatile'),
        'xcmGenTrapClientSNMPVersion' (if not 'snmpV1Community'), and
        'xcmGenTrapClientSNMPCommunity' (if not the current managed
        system default in 'xcmGenBaseSNMPTrapCommunity')
        SIMULTANEOUSLY (in the same SNMP Set-Request PDU).
        Usage:  Conforming management agents SHALL NOT accept sets to
        'xcmGenTrapClientRowPersistence',
        'xcmGenTrapClientSNMPVersion', or
        'xcmGenTrapClientSNMPCommunity'
        AFTER row creation (these objects are 'write-once').
        Usage:  Dynamically created rows SHALL be given 'volatile'
        or 'nonvolatile' persistence.
        Usage:  Conforming management agents SHALL support
        'volatile' (lost across power cycles).
        Usage:  Conforming management agents are STRONGLY RECOMMENDED to
        support 'nonvolatile' (preserved across power cycles),
        but NEED NOT support any other levels of persistence."
    DEFVAL      { volatile }            
    ::= { xcmGenTrapClientEntry 5 }
xcmGenTrapClientSNMPVersion OBJECT-TYPE
    SYNTAX      XcmGenSNMPVersion
    MAX-ACCESS  read-create             
    STATUS      current
    DESCRIPTION "
        This object is used to specify the SNMP version (RFC 1157, RFC
        1905, etc) which SHALL be used by this management agent
        for SNMP protocol traffic (transmission of SNMP traps),
        in the domain specified by 'xcmGenTrapClientSNMPDomain',
        to the trap client (management station or proxy).
        Usage:  Conforming management stations, when they first create
        new rows in this table, SHALL set
        'xcmGenTrapClientRowStatus' (to 'createAndGo'),
        'xcmGenTrapClientRowPersistence' (if not 'volatile'),
        'xcmGenTrapClientSNMPVersion' (if not 'snmpV1Community'), and
        'xcmGenTrapClientSNMPCommunity' (if not the current managed
        system default in 'xcmGenBaseSNMPTrapCommunity')
        SIMULTANEOUSLY (in the same SNMP Set-Request PDU).
        Usage:  Conforming management agents SHALL NOT accept sets to
        'xcmGenTrapClientRowPersistence',
        'xcmGenTrapClientSNMPVersion', or
        'xcmGenTrapClientSNMPCommunity'
        AFTER row creation (these objects are 'write-once')."
    REFERENCE "
        See:    'xcmGenBaseSNMP[Domain|Version]Support'."
    DEFVAL      { snmpV1Community }     
    ::= { xcmGenTrapClientEntry 6 }
xcmGenTrapClientSNMPCommunity OBJECT-TYPE
    SYNTAX      OCTET STRING (SIZE (0..64))
    MAX-ACCESS  read-create             
    STATUS      current
    DESCRIPTION "
        This object is used to specify the 'trap community name' used
        in all SNMPv1c and SNMPv2c 'Inform|Trap' PDUs
        which SHALL be generated by this SNMP management agent,
        in the domain specified by 'xcmGenTrapClientSNMPDomain',
        to the trap client (management station or proxy).
        Note:   XCMI-defined community name objects support 64 octets
        maximum length and configurable charsets, for consistency with
        the 'snmpCommunityName' object defined in the SNMP Community MIB
        defined in RFC 2576 (March 2000).
        Note:   Products MAY ship with a market-specific factory default
        locale with a charset other than 'utf-8', eg, in Japan a product
        might factory default to 'shift-jis(17)' or 'iso-2022-jp(39)'.
        Such products MUST implement the 'xcmGenFixedLocalizationTable',
        to prevent ambiguity about the factory default charset.
        Usage:  For best interworking with the ('utf-8' charset ONLY)
        closely related 'snmpCommunitySecurityName' object in RFC 2576,
        conforming management stations and management agents SHOULD NOT
        configure community names longer than 32 octets.
        Usage:  For best interworking with third-party applications,
        conforming management stations and management agents SHOULD NOT
        configure empty (zero-length or all spaces) community names.
        Usage:  Conforming management stations, when they first create
        new rows in this table, SHALL set
        'xcmGenTrapClientRowStatus' (to 'createAndGo'),
        'xcmGenTrapClientRowPersistence' (if not 'volatile'),
        'xcmGenTrapClientSNMPVersion' (if not 'snmpV1Community'), and
        'xcmGenTrapClientSNMPCommunity' (if not the current managed
        system default in 'xcmGenBaseSNMPTrapCommunity')
        SIMULTANEOUSLY (in the same SNMP Set-Request PDU).
        Usage:  Conforming management agents SHALL NOT accept sets to
        'xcmGenTrapClientRowPersistence',
        'xcmGenTrapClientSNMPVersion', or
        'xcmGenTrapClientSNMPCommunity'
        AFTER row creation (these objects are 'write-once').
        Usage:  This object SHALL be set by all XCMI conforming
        SNMP trap generators (managed host systems) to the default value
        of 'xcmGenBaseSNMPTrapCommunity', when NOT supplied by the
        requesting SNMP trap client (management station or proxy) at
        the time of row creation.
        Usage:  This object is of type 'XcmFixedLocaleDisplayString'
        (see DESCRIPTION of 'xcmGenBaseSNMPReadCommunity' above).
        If 'xcmGenLocalizationTable' or 'xcmGenFixedLocalizationTable'
        are not implemented on this host system, then the charset SHALL
        be 'utf-8(106)', ISO 10646-1 in 'UTF-8' stream encoding.
        Usage:  All XCMI conforming management agents SHALL allow
        any defined character in the configured charset of this object.
        All XCMI conforming management stations SHOULD NOT write control
        characters or other non-display characters into this object.
        WARNING:  Changing the configured 'trap community name' of an
        SNMP trap client registration will cause a COMPLETE loss of
        communications unless the associated SNMP management station
        (client) ALSO changes over to the new 'trap community name'!!!"
    REFERENCE "
        See:    SNMPv1c (RFC 1157) and SNMPv2c (RFC 1905).
        See:    'Coexistence between SNMPv1, SNMPv2, and SNMPv3'
                RFC 2576, March 2000.
        See:    'xcmGenBaseSNMPTrapCommunity'."
    ::= { xcmGenTrapClientEntry 7 }
--
--
--
xcmGenTrapView              OBJECT IDENTIFIER ::= { xcmGeneralMIB 14 }
--
--
xcmGenTrapViewSimple OBJECT-IDENTITY
    STATUS      current
    DESCRIPTION "
        This subtree is current.  Subordinate objects are leaf objects."
    ::= { xcmGenTrapView 1 }
xcmGenTrapViewEntryCount OBJECT-TYPE
    SYNTAX      Counter32
    MAX-ACCESS  read-only
    STATUS      current
    DESCRIPTION "
        The count of entries (rows) which are currently in the 'active'
        state in 'xcmGenTrapViewTable'."
    ::= { xcmGenTrapViewSimple 1 }
xcmGenTrapViewSupportMaxCount OBJECT-TYPE
    SYNTAX      Cardinal32
    MAX-ACCESS  read-only
    STATUS      current
    DESCRIPTION "
        The maximum number of simultaneous entries (rows) supported
        for the 'xcmGenTrapViewTable'.
        Usage:  The value zero ('0') represents 'no limit'."
    DEFVAL      { 0 }                   
    ::= { xcmGenTrapViewSimple 2 }
--
--
xcmGenTrapViewTable OBJECT-TYPE
    SYNTAX      SEQUENCE OF XcmGenTrapViewEntry
    MAX-ACCESS  not-accessible
    STATUS      current
    DESCRIPTION "
        A table of SNMP trap object subtrees (ie, trap scopes)
        registered for trap delivery from this host system to the
        associated trap client (management station or proxy).
        Usage:  SNMP version/transport independent trap registration.
        Usage:  Conforming management stations SHALL create at
        least one subordinate row in the 'xcmGenTrapViewTable' for each
        trap client that they register in the 'xcmGenTrapClientTable'.
        Conforming management agents SHOULD interpret a dangling row in
        the 'xcmGenTrapClientTable' (no children) as 'NO traps in view'
        (existing implementations of both clients and devices are known
        to consider dangling rows invalid).  To register for all device
        traps, use a single view of 'iso(1).org(3).dod(6).internet(1)'.
        Usage:  Conforming management agents SHALL delete any
        rows in the 'xcmGenTrapViewTable' which were subordinate to a
        deleted row in the 'xcmGenTrapClientTable'."
    REFERENCE "
        See:    View group in Historic SNMPv2 Party MIB (RFC 1447)."
    ::= { xcmGenTrapView 2 }
xcmGenTrapViewEntry OBJECT-TYPE
    SYNTAX      XcmGenTrapViewEntry
    MAX-ACCESS  not-accessible
    STATUS      current
    DESCRIPTION "
        An entry for an SNMP trap object subtree (ie, trap scope)
        registered for trap delivery from this host system to the
        associated trap client (management station or proxy)."
    INDEX       { xcmGenTrapClientIndex,
                  xcmGenTrapViewObjectSubtree }
    ::= { xcmGenTrapViewTable 1 }
XcmGenTrapViewEntry ::= SEQUENCE {
        xcmGenTrapViewObjectSubtree     OBJECT IDENTIFIER,
        xcmGenTrapViewRowStatus         RowStatus,
        xcmGenTrapViewNotifySeverity    XcmGenNotifySeverityFilter,
        xcmGenTrapViewNotifyTraining    XcmGenNotifyTrainingFilter
    }
xcmGenTrapViewObjectSubtree OBJECT-TYPE
    SYNTAX      OBJECT IDENTIFIER
    MAX-ACCESS  not-accessible
    STATUS      current
    DESCRIPTION "
        This object is used to specify the object subtree (within MIBs)
        which is 'in scope' for this trap view."
    ::= { xcmGenTrapViewEntry 1 }
xcmGenTrapViewRowStatus OBJECT-TYPE
    SYNTAX      RowStatus
    MAX-ACCESS  read-create
    STATUS      current
    DESCRIPTION "
        This object manages the row status of this conceptual row in
        the 'xcmGenTrapViewTable'.
        Usage:  Conforming implementations which support dynamic rows
        SHALL support 'createAndGo' and 'destroy' writes to this
        'xcmGenTrapViewRowStatus' row status object; and
        SHALL set the 'xcmGenTrapViewGroup' bit in
        'xcmGenBaseGroupCreateSupport' in the 'xcmGenBaseTable'.
        Usage:  Conforming management agents SHOULD NOT support
        'notInService(2)', 'notReady(3)', or 'createAndWait(5)'.
        Usage:  See section 3.4 'Secure Modes of Operation' and section
        3.5 'Secure SNMP Get/Set Requests' in XCMI Security TC, for
        details of secure modes of access to this row status object."
    REFERENCE "
        See:    'xcmGenBaseGroupCreateSupport' in 'xcmGenBaseTable'.
        See:    'xcmGenTrapViewSupportMaxCount' (limit object).
        See:    'RowStatus' in IETF SNMPv2 TC (RFC 1443/1903/2579).
        See:    'xcmHrDevMgmtCommandData' in XCMI HRX MIB and
                'xcmSecUserMgmtData' in XCMI Security MIB."
    ::= { xcmGenTrapViewEntry 2 }
xcmGenTrapViewNotifySeverity OBJECT-TYPE
    SYNTAX      XcmGenNotifySeverityFilter
    MAX-ACCESS  read-create
    STATUS      current
    DESCRIPTION "
        This object is used to specify the notification severity filter
        used to 'screen' notifications 'in scope' for this trap view.
        Usage:  Individual trap definitions MAY further constrain which
        notifications are 'in scope'."
    REFERENCE "
        See:    'prtAlertSeverityLevel' in IETF Printer MIB (RFC 1759).
        See:    'XcmGenNotifySeverityFilter' in XCMI General TC.
        See:    'xcmGenBaseNotifySeveritySupport'."
    DEFVAL      { 15 }                  
    ::= { xcmGenTrapViewEntry 3 }
xcmGenTrapViewNotifyTraining OBJECT-TYPE
    SYNTAX      XcmGenNotifyTrainingFilter
    MAX-ACCESS  read-create
    STATUS      current
    DESCRIPTION "
        This object is used to specify the notification training filter
        used to 'screen' notifications 'in scope' for this trap view.
        Usage:  Individual trap definitions MAY further constrain which
        notifications are 'in scope'."
    REFERENCE "
        See:    'prtAlertTrainingLevel' in IETF Printer MIB (RFC 1759).
        See:    'XcmGenNotifyTrainingFilter' in XCMI General TC.
        See:    'xcmGenBaseNotifyTrainingSupport'."
    DEFVAL      { 60 }                  
    ::= { xcmGenTrapViewEntry 4 }
--
xcmGenMessageMap            OBJECT IDENTIFIER ::= { xcmGeneralMIB 15 }
xcmGenMessageMapTable OBJECT-TYPE
    SYNTAX      SEQUENCE OF XcmGenMessageMapEntry
    MAX-ACCESS  not-accessible
    STATUS      current
    DESCRIPTION "
        A table of message string labels for the current contents
        of static (agent-generated) message string objects, in all
        MIBs implemented by this host system.
        Usage:  Exposes the server's message catalog for indirect search
        via source message object OIDs, yielding message string labels.
        Usage:  Supports reliable translation by clients (managers) of
        static (agent-generated) message strings, INDEPENDENT of the
        current language/country/charset of the message strings on the
        managed host system in the conventional MIB objects.
        Conformance:  XCMI conforming management agents SHALL
        support SNMP Get requests to the 'xcmGenMessageMapTable'
        (ie, agents must respond to valid explicit EXACT requests).
        When 'xcmGenMessageMapTable' is currently 'hidden' via
        'xcmGenBaseGroupWalkHidden', XCMI conforming management agents
        SHALL skip over 'xcmGenMessageMapTable' to the next
        lexicographically higher object for GetNext or GetBulk requests
        - 'xcmGenMessageMapTable' SHOULD be invisible to MIB walks,
        to avoid undesirable performance degradation with third-party
        network management stations and other monitoring tools."
    REFERENCE "
        See:    'XcmGenMessageMapStringLabel' in XCMI General TC."
    ::= { xcmGenMessageMap 2 }
xcmGenMessageMapEntry OBJECT-TYPE
    SYNTAX      XcmGenMessageMapEntry
    MAX-ACCESS  not-accessible
    STATUS      current
    DESCRIPTION "
        A entry for a message string label for the current contents
        of a static (agent-generated) message string object, in some
        MIB implemented by this host system.
        Conformance:  XCMI conforming management agents SHALL
        support SNMP Get requests to the 'xcmGenMessageMapTable'
        (ie, agents must respond to valid explicit EXACT requests).
        When 'xcmGenMessageMapTable' is currently 'hidden' via
        'xcmGenBaseGroupWalkHidden', XCMI conforming management agents
        SHALL skip over 'xcmGenMessageMapTable' to the next
        lexicographically higher object for GetNext or GetBulk requests
        - 'xcmGenMessageMapTable' SHOULD be invisible to MIB walks,
        to avoid undesirable performance degradation with third-party
        network management stations and other monitoring tools."
    INDEX       { xcmGenMessageMapStringIndexOID }
    ::= { xcmGenMessageMapTable 1 }
XcmGenMessageMapEntry ::= SEQUENCE {
        xcmGenMessageMapStringIndexOID  OBJECT IDENTIFIER,
        xcmGenMessageMapStringLabel     XcmGenMessageMapStringLabel
    }
xcmGenMessageMapStringIndexOID OBJECT-TYPE
    SYNTAX      OBJECT IDENTIFIER
    MAX-ACCESS  not-accessible
    STATUS      current
    DESCRIPTION "
        This object is used to specify the fully qualified object
        identifer (w/ instance suffix) of a message string object,
        which contains a Xerox registered standard or experimental
        message string value associated with the current message string
        label specified in 'xcmGenMessageMapStringLabel'."
    REFERENCE "
        See:    'XcmGenMessageMapStringLabel' in XCMI General TC."
    ::= { xcmGenMessageMapEntry 1 }
xcmGenMessageMapStringLabel OBJECT-TYPE
    SYNTAX      XcmGenMessageMapStringLabel
    MAX-ACCESS  read-only
    STATUS      current
    DESCRIPTION "
        This object is used to specify a Xerox standard or experiemental
        message string label associated with the current value of the
        message string pointed to by 'xcmGenMessageMapStringIndexOID'.
        Usage:  Experimental message string labels SHOULD NOT be used in
        shipping versions of Xerox-branded products or services.  They
        exist solely to facilitate rapid product development cycles.
        Usage:  All Xerox message string label values SHALL
        be specified using display (NOT space) characters from the IANA
        registered charset 'utf-8' (ie, the UTF-8 octet-stream encoding
        of ISO-10646 UCS-4, described in RFC 2279).
        Usage:  All Xerox message string label values SHALL
        contain no more than 64 UTF-8 display characters AND no more
        than 128 total octets (in some scripts, less than 64 characters
        in UTF-8 octet-stream encoding).
        Note:   New or refined message label syntaxes MAY be defined in
        future versions of the XCMI General TC."
    REFERENCE "
        See:    'XcmGenMessageMapStringLabel' in XCMI General TC."
    ::= { xcmGenMessageMapEntry 2 }
--
xcmGenMessageText           OBJECT IDENTIFIER ::= { xcmGeneralMIB 16 }
xcmGenMessageTextTable OBJECT-TYPE
    SYNTAX      SEQUENCE OF XcmGenMessageTextEntry
    MAX-ACCESS  not-accessible
    STATUS      current
    DESCRIPTION "
        A table of message string translations for all target locales
        of static (agent-generated) message string objects, in various
        known (agent-supported) source message locales.
        Usage:  Exposes the server's message catalog for indirect search
        via source message object OIDs, yielding target string values.
        Usage:  Supports reliable translation by servers (agents) of
        static (agent-generated) message strings, INDEPENDENT of the
        current language/country/charset of the message strings on the
        managed host system in the conventional MIB objects.
        Conformance:  XCMI conforming management agents SHALL
        support SNMP Get requests to the 'xcmGenMessageTextTable'
        (ie, agents must respond to valid explicit EXACT requests).
        When 'xcmGenMessageTextTable' is currently 'hidden' via
        'xcmGenBaseGroupWalkHidden', XCMI conforming management agents
        SHALL skip over 'xcmGenMessageTextTable' to the next
        lexicographically higher object for GetNext or GetBulk requests
        - 'xcmGenMessageTextTable' SHOULD be invisible to MIB walks,
        to avoid undesirable performance degradation with third-party
        network management stations and other monitoring tools."
    REFERENCE "
        See:    'xcmGenMessageTextTable'"
    ::= { xcmGenMessageText 2 }
xcmGenMessageTextEntry OBJECT-TYPE
    SYNTAX      XcmGenMessageTextEntry
    MAX-ACCESS  not-accessible
    STATUS      current
    DESCRIPTION "
        An entry for a message string translation for one target locale
        of a static (agent-generated) message string object, in some
        MIB implemented by this host system.
        Conformance:  XCMI conforming management agents SHALL
        support SNMP Get requests to the 'xcmGenMessageTextTable'
        (ie, agents must respond to valid explicit EXACT requests).
        When 'xcmGenMessageTextTable' is currently 'hidden' via
        'xcmGenBaseGroupWalkHidden', XCMI conforming management agents
        SHALL skip over 'xcmGenMessageTextTable' to the next
        lexicographically higher object for GetNext or GetBulk requests
        - 'xcmGenMessageTextTable' SHOULD be invisible to MIB walks,
        to avoid undesirable performance degradation with third-party
        network management stations and other monitoring tools."
    REFERENCE "
        See:    'xcmGenMessageMapTable'"
    INDEX       { xcmGenMessageTextStringIndexOID,
                  xcmGenMessageTextTargetLocale }
    ::= { xcmGenMessageTextTable 1 }
XcmGenMessageTextEntry ::= SEQUENCE {
        xcmGenMessageTextStringIndexOID OBJECT IDENTIFIER,
        xcmGenMessageTextTargetLocale   Ordinal32,
        xcmGenMessageTextTargetString   XcmNamedLocaleUtf8String
    }
xcmGenMessageTextStringIndexOID OBJECT-TYPE
    SYNTAX      OBJECT IDENTIFIER
    MAX-ACCESS  not-accessible
    STATUS      current
    DESCRIPTION "
        This object is used to specify the fully qualified object
        identifer (w/ instance suffix) of a message string object,
        which contains a Xerox registered standard or experimental
        message string value equivalent to the target message string
        translation specified in 'xcmGenMessageTextTargetString'.
        The locale of this source message string is immaterial."
    REFERENCE "
        See:    'xcmGenMessageTextTargetLocale'
        See:    'xcmGenMessageTextTargetString'"
    ::= { xcmGenMessageTextEntry 1 }
xcmGenMessageTextTargetLocale OBJECT-TYPE
    SYNTAX      Ordinal32
    MAX-ACCESS  not-accessible
    STATUS      current
    DESCRIPTION "
        This object is used to specify the locale (language/country),
        as a value of 'xcmGenLocalizationIndex', of the message string
        translation in 'xcmGenMessageTextTargetString'."
    REFERENCE "
        See:    'xcmGenMessageTextStringIndexOID'
        See:    'xcmGenMessageTextTargetString'"
    ::= { xcmGenMessageTextEntry 2 }
xcmGenMessageTextTargetString OBJECT-TYPE
    SYNTAX      XcmNamedLocaleUtf8String (SIZE (0..255))
    MAX-ACCESS  read-only
    STATUS      current
    DESCRIPTION "
        This object is used to specify a translated Xerox registered
        message string value associated with the current value of the
        message string pointed to by 'xcmGenMessageMapStringIndexOID',
        in the locale specified by 'xcmGenMessageTextTargetLocale'.
        Usage:  All Xerox registered message string values SHALL
        contain no more than 128 UTF-8 display characters AND no more
        than 255 total octets (in some scripts, less than 128 characters
        in UTF-8 octet-stream encoding)."
    REFERENCE "
        See:    'xcmGenMessageTextStringIndexOID'
        See:    'xcmGenMessageTextTargetLocale'"
    ::= { xcmGenMessageTextEntry 3 }
--
--
--
--
xcmGenNotifyRule            OBJECT IDENTIFIER ::= { xcmGeneralMIB 17 }
--
--
xcmGenNotifyRuleSimple OBJECT-IDENTITY
    STATUS      current
    DESCRIPTION "
        This subtree is current.  Subordinate objects are leaf objects."
    ::= { xcmGenNotifyRule 1 }
xcmGenNotifyRuleEntryCount OBJECT-TYPE
    SYNTAX      Counter32
    MAX-ACCESS  read-only
    STATUS      current
    DESCRIPTION "
        The count of entries (rows) which are currently in the 'active'
        state in 'xcmGenNotifyRuleTable'."
    ::= { xcmGenNotifyRuleSimple 1 }
xcmGenNotifyRuleSupportMaxCount OBJECT-TYPE
    SYNTAX      Cardinal32
    MAX-ACCESS  read-only
    STATUS      current
    DESCRIPTION "
        The maximum number of simultaneous entries (rows) supported
        for the 'xcmGenNotifyRuleTable'.
        Usage:  The value zero ('0') represents 'no limit'."
    DEFVAL      { 0 }                   
    ::= { xcmGenNotifyRuleSimple 2 }
--
--
xcmGenNotifyRuleTable OBJECT-TYPE
    SYNTAX      SEQUENCE OF XcmGenNotifyRuleEntry
    MAX-ACCESS  not-accessible
    STATUS      current
    DESCRIPTION "
        A table of notification rules (recipient/event lists)
        registered for event delivery from this host system.
        Note:   In this MIB, the term 'notification rule' is equivalent
        to the term 'Subscription object' in IPP Notifications.
        Usage:  Conforming management agents SHALL NOT accept sets to
        any other columnar object in 'xcmGenNotifyRuleTable' when
        'xcmGenNotifyRuleRowStatus' is 'active'.
        Dynamic rows must be deleted (with 'destroy') and then recreated
        (with 'createAndGo') with new columnar values.
        Static rows must be released (with 'notInService') and then
        then reallocated (with 'active') with new columnar values.
        Thus only a row status transition to 'active' indicates a new
        notification registration by a conforming management station.
        Usage:  Conforming management agents SHALL delete any
        rows in the 'xcmGenNotifyDetailTable' which were subordinate to
        a deleted row in the 'xcmGenNotifyRuleTable'."
    REFERENCE "
        See:    Section 5 'Subscription Object' and
                Section 5.3 'Subscription Template Attributes' and
                section 5.4 'Subscription Description Attributes' in
                IPP Notify (draft-ietf-ipp-not-spec-06.txt)."
    ::= { xcmGenNotifyRule 2 }
xcmGenNotifyRuleEntry OBJECT-TYPE
    SYNTAX      XcmGenNotifyRuleEntry
    MAX-ACCESS  not-accessible
    STATUS      current
    DESCRIPTION "
        An entry for a notification rule (recipient/event list)
        registered for event delivery from this host system."
    INDEX       { xcmGenNotifyRuleIndex }
    ::= { xcmGenNotifyRuleTable 1 }
XcmGenNotifyRuleEntry ::= SEQUENCE {
        xcmGenNotifyRuleIndex           Ordinal32,
        xcmGenNotifyRuleRowStatus       RowStatus,
        xcmGenNotifyRuleRowPersistence  XcmGenRowPersistence,
        xcmGenNotifyRuleRecipientURI    XcmFixedLocaleDisplayString,
        xcmGenNotifyRuleEventNames      XcmFixedLocaleDisplayString,
        xcmGenNotifyRuleEventDelay      Cardinal32,
        xcmGenNotifyRuleSeverityFilter  XcmGenNotifySeverityFilter,
        xcmGenNotifyRuleTrainingFilter  XcmGenNotifyTrainingFilter,
        xcmGenNotifyRuleCharset         IANACharset,
        xcmGenNotifyRuleNaturalLanguage DisplayString,
        xcmGenNotifyRuleSequenceNumber  Cardinal32
    }
xcmGenNotifyRuleIndex OBJECT-TYPE
    SYNTAX      Ordinal32
    MAX-ACCESS  not-accessible
    STATUS      current
    DESCRIPTION "
        A unique value used by this host system to identify this
        conceptual row in the 'xcmGenNotifyRuleTable'."
    REFERENCE "
        See:    Section 5.4.1 'notify-subscription-id' in IPP Notify."
    ::= { xcmGenNotifyRuleEntry 1 }
xcmGenNotifyRuleRowStatus OBJECT-TYPE
    SYNTAX      RowStatus
    MAX-ACCESS  read-create
    STATUS      current
    DESCRIPTION "
        This object is used to display the status of this conceptual row
        in the 'xcmGenNotifyRuleTable'.
        Usage:  This object MAY be used to create ('createAndGo') and
        delete ('destroy') dynamic rows in the 'xcmGenNotifyRuleTable'.
        Also used to enable ('active') and disable ('notInService')
        static rows in the 'xcmGenNotifyRuleTable'.
        Usage:  Conforming management agents SHOULD NOT support the
        intermediate values 'notReady(3)' or 'createAndWait(5)'.
        Usage:  See section 3.4 'Secure Modes of Operation' and section
        3.5 'Secure SNMP Get/Set Requests' in XCMI Security TC, for
        details of secure modes of access to this row status object."
    REFERENCE "
        See:    Section 11 'Operations for Notification' in IPP Notify.
        See:    'RowStatus' in IETF SNMPv2 TC (RFC 1443/1903/2579).
        See:    'xcmHrDevMgmtCommandData' in XCMI HRX MIB and
                'xcmSecUserMgmtData' in XCMI Security MIB."
    ::= { xcmGenNotifyRuleEntry 2 }
xcmGenNotifyRuleRowPersistence OBJECT-TYPE
    SYNTAX      XcmGenRowPersistence
    MAX-ACCESS  read-create
    STATUS      current
    DESCRIPTION "
        This object is used to specify the persistence of this
        conceptual row in the 'xcmGenNotifyRuleTable' (and associated
        conceptual rows in the 'xcmGenNotifyRuleDetailTable').
        Usage:  Dynamically created rows SHALL be given 'volatile'
        or 'nonvolatile' persistence.
        Usage:  Conforming management agents SHALL NOT accept sets to
        'xcmGenNotifyRuleRowPersistence'
        AFTER row creation (this object is 'write-once').
        Usage:  Conforming management agents SHALL support
        'volatile' (lost across power cycles), but NEED NOT support any
        other levels of persistence."
    REFERENCE "
        See:    Section 5.3.7 'notify-lease-duration' in IPP Notify.
        See:    Section 5.4.3 'lease-expiration-time' in IPP Notify."
    DEFVAL      { volatile }            
    ::= { xcmGenNotifyRuleEntry 3 }
xcmGenNotifyRuleRecipientURI OBJECT-TYPE
    SYNTAX      XcmFixedLocaleDisplayString (SIZE (0..255))
    MAX-ACCESS  read-create
    STATUS      current
    DESCRIPTION "
        This object is used to specify a single recipient URI (Uniform
        Resource Identifier, per Generic URI Syntax, RFC 2396) for event
        delivery for this notification rule (list of events), eg,
        - 'mailto:joe@sample.com' (Email)
        - 'mailto:VOICE=+3940226338@samplevoice.com' (Voice Mail)
        - 'mailto:FAX=+1.800.5553000/T33S=6377@sampleserv.com' (IFax)
        - 'ftp://machine.sample.com/pub/event_logs' (FTP logging)
        Usage:  'ftp:' and 'http:' URLs specify paths for event logs.
        Usage:  MAY include parameters for SNMP and other URL schemes
        (eg, 'snmp://machine.sample.com;version=2c;community=public'
        for SNMPv2c delivery with community-name of 'public').
        Usage:  For additional recipients, use 'notifyRecipientURI'
        notify details in the 'xcmGenNotifyRuleDetailTable'."
    REFERENCE "
        See:    Section 5.3.1 'notify-recipient-uri' in IPP Notify.
        See:    Generic URI Syntax (RFC 2396).
        See:    The 'mailto:' URL Scheme (RFC 2368).
        See:    Minimal PSTN address in Internet Mail (RFC 2303).
        See:    Minimal FAX address in Internet Mail (RFC 2304)."
    DEFVAL      { ''H }                 
    ::= { xcmGenNotifyRuleEntry 4 }
xcmGenNotifyRuleEventNames OBJECT-TYPE
    SYNTAX      XcmFixedLocaleDisplayString (SIZE (0..255))
    MAX-ACCESS  read-create
    STATUS      current
    DESCRIPTION "
        This object is used to specify the subscribed events for this
        notification rule, as a comma-delimited list of (standard)
        keywords or (vendor or site-specific) names.
        Usage:  Keywords of IPP 'notify-events' and SNMP traps and
        and SNMP state/alert enumeration keywords are interoperable
        (eg, 'lowPaper,jammed' from IETF HR MIB, RFC 2790).
    `   Usage:  Standard keywords MAY be scoped with their source, eg,
        'notify-events.job-stopped,hrPrinterDetectedErrorState.jammed',
        for clarity.
        Usage:  Conforming management stations and management agents
        SHALL prefix non-standard names with 'x-' for compatibility."
    REFERENCE "
        See:    Section 5.3.2 'notify-events' in IPP Notify.
        See:    TRAP-TYPE and NOTIFICATION-TYPE names in IETF/XCMI MIBs.
        See:    'hrDeviceStatus' in IETF HR MIB (RFC 2790).
        See:    'xcmHrDevInfoXStatus' in XCMI HRX MIB.
        See:    'xcmHrDevInfoConditions' in XCMI HRX MIB.
        See:    'hrPrinterDetectedErrorState' in IETF HR MIB (RFC 2790).
        See:    'prtAlertCode' in IETF Printer MIB (RFC 1759)."
    DEFVAL      { ''H }                 
    ::= { xcmGenNotifyRuleEntry 5 }
xcmGenNotifyRuleEventDelay OBJECT-TYPE
    SYNTAX      Cardinal32
    MAX-ACCESS  read-create
    STATUS      current
    DESCRIPTION "
        This object is used to specify a delay timer in seconds for
        event delivery that rate-limits (buffers) frequent events.
        This timer is the minimum number of seconds between events
        delivered for this notification rule ('xcmGenNotifyRuleIndex').
        Usage:  Conforming management agents (network devices) SHOULD
        support server-side buffering of events for interoperability
        (and improved performance) via 'xcmGenNotifyRuleEventDelay'.
        Usage:  Conforming management stations (recipients) SHOULD
        support client-side buffering of events for interoperability
        (and not depend on this 'xcmGenNotifyRuleEventDelay' object)."
    REFERENCE "
        See:    Section 5.3.8 'notify-time-interval' in IPP Notify."
    DEFVAL      { 0 }                   
    ::= { xcmGenNotifyRuleEntry 6 }
xcmGenNotifyRuleSeverityFilter OBJECT-TYPE
    SYNTAX      XcmGenNotifySeverityFilter
    MAX-ACCESS  read-create
    STATUS      current
    DESCRIPTION "
        This object is used to specify the notification severity filter
        used to 'screen' notifications for event delivery.
        Usage:  Notification details MAY further constrain which
        notifications are 'in scope'."
    REFERENCE "
        See:    'prtAlertSeverityLevel' in IETF Printer MIB (RFC 1759).
        See:    'XcmGenNotifySeverityFilter' in XCMI General TC.
        See:    'xcmGenBaseNotifySeveritySupport' in XCMI General MIB."
    DEFVAL      { 15 }                  
    ::= { xcmGenNotifyRuleEntry 7 }
xcmGenNotifyRuleTrainingFilter OBJECT-TYPE
    SYNTAX      XcmGenNotifyTrainingFilter
    MAX-ACCESS  read-create
    STATUS      current
    DESCRIPTION "
        This object is used to specify the notification training filter
        used to 'screen' notifications for event delivery.
        Usage:  Notification details MAY further constrain which
        notifications are 'in scope'."
    REFERENCE "
        See:    'prtAlertTrainingLevel' in IETF Printer MIB (RFC 1759).
        See:    'XcmGenNotifyTrainingFilter' in XCMI General TC.
        See:    'xcmGenBaseNotifyTrainingSupport' in XCMI General MIB."
    DEFVAL      { 60 }                  
    ::= { xcmGenNotifyRuleEntry 8 }
xcmGenNotifyRuleCharset OBJECT-TYPE
    SYNTAX      IANACharset
    MAX-ACCESS  read-create
    STATUS      current
    DESCRIPTION "
        This object is used to specify the notification charset
        used for notification text in event messages, specified as an
        IANA registered charset identifier, eg, 'MIBenum' value
        (per RFC 2978).
        Usage:  If 'xcmGenNotifyRuleCharset' is 'other(1)', then the
        value of 'xcmGenFixedLocalizationIndex' SHALL be used for a
        notification rule locale specifier for charset."
    REFERENCE "
        See:    Section 4.1.7 'charset' and section 4.4.17
               'charset-configured' in IPP/1.1 (RFC 2911).
        See:    Section 5.3.5 'notify-charset' in IPP Notify.
        See:    IANA Charset Registration Procedures (RFC 2978).
        See:    Codes for Representation of Names of Charsets, ISO 3166
        See:    Codes for Representation of Names of Countries, ISO 639"
    DEFVAL      { other }               
    ::= { xcmGenNotifyRuleEntry 9 }
xcmGenNotifyRuleNaturalLanguage OBJECT-TYPE
    SYNTAX      DisplayString
    MAX-ACCESS  read-create
    STATUS      current
    DESCRIPTION "
        This object is used to specify the notification natural language
        used for notification text in event messages, specified as an
        IETF 'language tag' (per RFC 3066).
        Usage:  If 'xcmGenNotifyRuleNaturalLanguage' is empty, then the
        value of 'xcmGenFixedLocalizationIndex' SHALL be used for a
        notification rule locale specifier for natural language."
    REFERENCE "
        See:    Section 4.1.8 'naturalLanguage' and section 4.4.19
               'natural-language-configured' in IPP/1.1 (RFC 2911).
        See:    Section 5.3.6 'notify-natural-language' in IPP Notify.
        See:    IETF Tags for Identification of Languages (RFC 3066).
        See:    Codes for Representation of Names of Languages, ISO 3166
        See:    Codes for Representation of Names of Countries, ISO 639"
    DEFVAL      { ''H }                 
    ::= { xcmGenNotifyRuleEntry 10 }
xcmGenNotifyRuleSequenceNumber OBJECT-TYPE
    SYNTAX      Cardinal32
    MAX-ACCESS  read-only
    STATUS      current
    DESCRIPTION "
        This object is used to specify the notification sequence number
        last used for event delivery for this notification rule.
        Usage:  Conforming management agents SHOULD include the value
        of 'xcmGenNotifyRuleSequenceNumber' in all event messages."
    REFERENCE "
        See:    Section 5.4.2 'notify-sequence-number' in IPP Notify."
    DEFVAL      { 0 }                   
    ::= { xcmGenNotifyRuleEntry 11 }
--
--
--
--
xcmGenNotifyDetail          OBJECT IDENTIFIER ::= { xcmGeneralMIB 18 }
--
--
xcmGenNotifyDetailSimple OBJECT-IDENTITY
    STATUS      current
    DESCRIPTION "
        This subtree is current.  Subordinate objects are leaf objects."
    ::= { xcmGenNotifyDetail 1 }
xcmGenNotifyDetailEntryCount OBJECT-TYPE
    SYNTAX      Counter32
    MAX-ACCESS  read-only
    STATUS      current
    DESCRIPTION "
        The count of entries (rows) which are currently in the 'active'
        state in 'xcmGenNotifyDetailTable'."
    ::= { xcmGenNotifyDetailSimple 1 }
xcmGenNotifyDetailSupportMax OBJECT-TYPE
    SYNTAX      Cardinal32
    MAX-ACCESS  read-only
    STATUS      current
    DESCRIPTION "
        The maximum number of simultaneous entries (rows) supported
        for the 'xcmGenNotifyDetailTable'.
        Usage:  The value zero ('0') represents 'no limit'."
    DEFVAL      { 0 }                   
    ::= { xcmGenNotifyDetailSimple 2 }
--
--
xcmGenNotifyDetailTable OBJECT-TYPE
    SYNTAX      SEQUENCE OF XcmGenNotifyDetailEntry
    MAX-ACCESS  not-accessible
    STATUS      current
    DESCRIPTION "
        A 'sparse' table of notification detail information for
        notification rules configured on this host system,
        augmenting the basic entries in the 'xcmGenNotifyTable'.
        Usage:  UNLIKE the 'xcmGenOptionTable' in the XCMI General MIB
        (which is a unique exception), this table of 'dictionary-based'
        notify details is used with DIRECT create/update operations."
    REFERENCE "
        See:    Section 5 'Subscription Object' and
                Section 5.3 'Subscription Template Attributes' and
                section 5.4 'Subscription Description Attributes' in
                IPP Notify (draft-ietf-ipp-not-spec-06.txt)."
    ::= { xcmGenNotifyDetail 2 }
xcmGenNotifyDetailEntry OBJECT-TYPE
    SYNTAX      XcmGenNotifyDetailEntry
    MAX-ACCESS  not-accessible
    STATUS      current
    DESCRIPTION "
        An entry of notification detail information for one of the
        notification rules configured on this host system,
        augmenting the basic entry in the 'xcmGenNotifyTable'."
    INDEX       { xcmGenNotifyRuleIndex,
                  xcmGenNotifyDetailType,
                  xcmGenNotifyDetailIndex }
    ::= { xcmGenNotifyDetailTable 1 }
XcmGenNotifyDetailEntry ::= SEQUENCE {
        xcmGenNotifyDetailType          XcmGenNotifyDetailType,
        xcmGenNotifyDetailIndex         Ordinal32,
        xcmGenNotifyDetailRowStatus     RowStatus,
        xcmGenNotifyDetailString        XcmFixedLocaleDisplayString
    }
xcmGenNotifyDetailType OBJECT-TYPE
    SYNTAX      XcmGenNotifyDetailType
    MAX-ACCESS  not-accessible
    STATUS      current
    DESCRIPTION "
        The type of notify detail stored in this conceptual row
        in 'xcmGenNotifyDetailTable'.
        Usage:  Conforming XCMI management stations and agents SHALL
        encode notify details as UTF-8 strings (like SLPv2, RFC 2608).
        - Integers SHALL be encoded as (signed) decimal strings.
        - Booleans SHALL be encoded as 'true' or 'false' strings.
        - Strings SHALL be encoded as UTF-8 character strings.
        - Binary data (e.g., 'userCertificate') SHALL be stored
        in SLPv2 opaque encoding (leading '\FF' and escaped octets).
        Usage:  Conformant implementations MUST encrypt passwords, keys,
        and other security information in 'xcmGenNotifyDetailString'."
    REFERENCE "
        See:    Section 5 'Subscription Object' and
                Section 5.3 'Subscription Template Attributes' and
                section 5.4 'Subscription Description Attributes' in
                IPP Notify (draft-ietf-ipp-not-spec-06.txt).
        See:    Section 5 'Service Attributes' (encoding rules) in
                Service Location Protocol v2 (RFC 2608)."
    ::= { xcmGenNotifyDetailEntry 1 }
xcmGenNotifyDetailIndex OBJECT-TYPE
    SYNTAX      Ordinal32
    MAX-ACCESS  not-accessible
    STATUS      current
    DESCRIPTION "
        A unique value used by this host system to identify this
        conceptual row in the 'xcmGenNotifyDetailTable', OR a common
        value shared across a set of related conceptual rows (with
        different values of 'xcmGenNotifyDetailType'."
    ::= { xcmGenNotifyDetailEntry 2 }
xcmGenNotifyDetailRowStatus OBJECT-TYPE
    SYNTAX      RowStatus
    MAX-ACCESS  read-create
    STATUS      current
    DESCRIPTION "
        This object is used to display the status of this conceptual row
        in the 'xcmGenNotifyDetailTable'.
        Usage:  This object MAY be used to create ('createAndGo') and
        delete ('destroy') dynamic rows in 'xcmGenNotifyDetailTable'.
        Also used to enable ('active') and disable ('notInService')
        static rows in the 'xcmGenNotifyTable'.
        Usage:  Conforming management agents SHOULD NOT support the
        intermediate values 'notReady(3)' or 'createAndWait(5)'.
        Usage:  See section 3.4 'Secure Modes of Operation' and section
        3.5 'Secure SNMP Get/Set Requests' in XCMI Security TC, for
        details of secure modes of access to this row status object."
    REFERENCE "
        See:    Section 11 'Operations for Notification' in IPP Notify.
        See:    'RowStatus' in IETF SNMPv2 TC (RFC 1443/1903/2579).
        See:    'xcmHrDevMgmtCommandData' in XCMI HRX MIB and
                'xcmSecUserMgmtData' in XCMI Security MIB."
    ::= { xcmGenNotifyDetailEntry 3 }
xcmGenNotifyDetailString OBJECT-TYPE
    SYNTAX      XcmFixedLocaleDisplayString (SIZE (0..255))
    MAX-ACCESS  read-create
    STATUS      current
    DESCRIPTION "
        The string notify detail value stored in this conceptual row
        in 'xcmGenNotifyDetailTable'.
        Usage:  Conforming XCMI management stations and agents SHALL
        encode notify details as UTF-8 strings (like SLPv2, RFC 2608).
        - Integers SHALL be encoded as (signed) decimal strings.
        - Booleans SHALL be encoded as 'true' or 'false' strings.
        - Strings SHALL be encoded as UTF-8 character strings.
        - Binary data (e.g., 'userCertificate') SHALL be stored
        in SLPv2 opaque encoding (leading '\FF' and escaped octets).
        Usage:  Conformant implementations MUST encrypt passwords, keys,
        and other security information in 'xcmGenNotifyDetailString'."
    REFERENCE "
        See:    Section 5 'Subscription Object' and
                Section 5.3 'Subscription Template Attributes' and
                section 5.4 'Subscription Description Attributes' in
                IPP Notify (draft-ietf-ipp-not-spec-06.txt).
        See:    Section 5 'Service Attributes' (encoding rules) in
                Service Location Protocol v2 (RFC 2608)."
    DEFVAL      { ''H }                 
    ::= { xcmGenNotifyDetailEntry 4 }
--
--
xcmGeneralMIBConformance
             OBJECT IDENTIFIER ::= { xcmGeneralMIB 2 }
xcmGeneralMIBGroups
             OBJECT IDENTIFIER ::= { xcmGeneralMIBConformance 2 }
--
--
xcmGeneralMIBCompliance MODULE-COMPLIANCE
    STATUS      current
    DESCRIPTION "
        The compliance statements for SNMP management agents that
        implement the General MIB."
    MODULE 
    MANDATORY-GROUPS {
        xcmGenBaseGroup,
        xcmGenTrapClientGroup,
        xcmGenTrapViewGroup
    }
    GROUP       xcmGenCurrentLocalizationGroup
    DESCRIPTION "
        This group controls the localization of dynamic string objects
        of type 'InternationalDisplayString' in legacy MIBs.
        Implementation of this group is conditionally mandatory, ie,
        mandatory for all systems which support MIB objects with type
        'InternationalDisplayString'
        and optional for all other systems."
    GROUP       xcmGenLocalizationGroup
    DESCRIPTION "
        This group declares supported localizations for string objects
        of type 'InternationalDisplayString' in legacy MIBs and
        of type 'XcmFixedLocaleDisplayString'
        or 'Xcm[Fixed|Mamed]LocaleUtf8String' in XCMI MIBs.
        Implementation of this group is conditionally mandatory, ie,
        mandatory for all systems which support MIB objects with type
        'InternationalDisplayString', 'XcmFixedLocaleDisplayString',
        'XcmFixedLocaleUtf8String', or 'XcmNamedLocaleUtf8String'
        and optional for all other systems."
    GROUP       xcmGenCodeIndexedStringGroup
    DESCRIPTION "
        Implementation of this group is conditionally mandatory:
        Mandatory for all systems which implement MIB objects of type
        'CodeIndexedStringIndex' or implement the
        'xcmGenCodedCharSetGroup'."
    GROUP       xcmGenCodedCharSetGroup
    DESCRIPTION "
        Implementation of this group is conditionally mandatory:
        Mandatory for all systems which implement MIB objects of type
        'CodeIndexedStringIndex' or implement the
        'xcmGenCodeIndexedStringGroup'."
    GROUP       xcmGenFixedLocalizationGroup
    DESCRIPTION "
        This group controls the localization of static string objects
        of type 'XcmFixedLocaleDisplayString'
        or 'Xcm[Fixed|Mamed]LocaleUtf8String' in XCMI MIBs.
        Implementation of this group is conditionally mandatory, ie,
        mandatory for all systems which support MIB objects with type
        'XcmFixedLocaleDisplayString',
        'XcmFixedLocaleUtf8String', or 'XcmNamedLocaleUtf8String'
        and optional for all other systems."
    GROUP       xcmGenLockGroup
    DESCRIPTION "
        Implementation of this group is conditionally mandatory, ie,
        mandatory for systems which support advisory contention
        locks, and optional for all other systems.
        Implementation of this group is conditionally mandatory,
        however it SHALL be implemented by systems which
        implement the 'xcmGenReconfGroup' and 'xcmGenOptionGroup'."
    GROUP       xcmGenReconfGroup
    DESCRIPTION "
        Implementation of this group is conditionally mandatory, ie,
        mandatory for systems which support tree structured
        atomic reconfiguration, and optional for all other systems.
        Implementation of this group is conditionally mandatory,
        however it SHALL be implemented by systems which
        implement the 'xcmGenOptionGroup'.
        Usage:  Systems which implement the 'xcmGenReconfGroup'
        and 'xcmGenOptionGroup' SHALL also implement
        the 'xcmGenLockGroup' (for advisory contention locks)."
    GROUP       xcmGenOptionGroup
    DESCRIPTION "
        Implementation of this group is conditionally mandatory, ie,
        mandatory for systems which support tree structured
        atomic reconfiguration, and optional for all other systems.
--
        Implementation of this group is conditionally mandatory,
        however it SHALL be implemented by systems which
        implement the 'xcmGenReconfGroup'.
--
        Usage:  Systems which implement the 'xcmGenReconfGroup'
        and 'xcmGenOptionGroup' SHALL also implement
        the 'xcmGenLockGroup' (for advisory contention locks)."
    GROUP       xcmGenClientDataGroup
    DESCRIPTION "
        Implementation of this group is conditionally mandatory, ie,
        mandatory for systems which support 'client data' for remote
        management stations, and optional for all other systems.
        Usage:  Conforming implementations SHALL preserve active
        'client data' objects across management agent power cycles."
    GROUP       xcmGenMessageMapGroup
    DESCRIPTION "
        Implementation of this group is conditionally mandatory, ie,
        mandatory for systems which implement message label lookups
        of agent-supplied strings and optional for all other systems."
    GROUP       xcmGenMessageTextGroup
    DESCRIPTION "
        Implementation of this group is conditionally mandatory, ie,
        mandatory for systems which implement message translations
        of agent-supplied strings and optional for all other systems."
    GROUP       xcmGenNotifyRuleGroup
    DESCRIPTION "
        Implementation of this group is conditionally mandatory, ie,
        mandatory for systems which implement event notification via
        non-SNMP delivery methods and optional for all other systems.
        Note:   Systems implementing the Notify Rule group
        SHALL implement the Notify Detail group.
        Note:   The Notify Rule group is functionally equivalent to
        the Trap Client group for non-SNMP event delivery methods."
    GROUP       xcmGenNotifyDetailGroup
    DESCRIPTION "
        Implementation of this group is conditionally mandatory, ie,
        mandatory for systems which implement event notification via
        non-SNMP delivery methods and optional for all other systems.
        Note:   Systems implementing the Notify Detail group
        SHALL implement the Notify Rule group.
        Note:   The Notify Detail group is functionally equivalent to
        the Trap View group for non-SNMP event delivery methods."
    OBJECT      xcmGenBaseSNMPReadCommunity
    SYNTAX      OCTET STRING (SIZE (0..1))
    MIN-ACCESS  read-only
    DESCRIPTION "
        It is conformant to implement this object as read-only.
        Usage:  All XCMI conforming management agents are
        STRONGLY RECOMMENDED to support an authenticated SNMP SetRequest
        to this object, changing the system 'read community name'
        (for best interworking with third-party management stations)."
    OBJECT      xcmGenBaseSNMPWriteCommunity
    SYNTAX      OCTET STRING (SIZE (0..1))
    MIN-ACCESS  read-only
    DESCRIPTION "
        It is conformant to implement this object as read-only.
        Usage:  All XCMI conforming management agents are
        STRONGLY RECOMMENDED to support an authenticated SNMP SetRequest
        to this object, changing the system 'write community name'
        (for best interworking with third-party management stations)."
    OBJECT      xcmGenBaseSNMPTrapCommunity
    SYNTAX      OCTET STRING (SIZE (0..1))
    MIN-ACCESS  read-only
    DESCRIPTION "
        It is conformant to implement this object as read-only.
        Usage:  All XCMI conforming management agents are
        STRONGLY RECOMMENDED to support an authenticated SNMP SetRequest
        to this object, changing the system 'trap community name'
        (for best interworking with third-party management stations)."
    OBJECT      xcmGenBaseGroupWalkHidden
    MIN-ACCESS  read-only
    DESCRIPTION "
        It is conformant to implement this object as read-only.
        XCMI conforming management agents NEED NOT support changing of
        MIB walk 'hidden' groups by remote management stations."
    OBJECT      xcmGenCurrentLocalizationIndex 
    MIN-ACCESS  read-only
    DESCRIPTION "
        It is conformant to implement this object as read-only"
    OBJECT      xcmGenCurrLocalizationRowStatus
    SYNTAX      INTEGER { active(1) }   
    MIN-ACCESS  read-only
    DESCRIPTION "
        It is conformant to implement this object as read-only, and
        only one of the enumerated values for the 'RowStatus' textual
        convention need be supported, specifically:  active(1)."
    OBJECT      xcmGenLocalizationRowStatus
    SYNTAX      INTEGER { active(1) }   
    MIN-ACCESS  read-only
    DESCRIPTION "
        It is conformant to implement this object as read-only, and
        only one of the enumerated values for the 'RowStatus' textual
        convention need be supported, specifically:  active(1)."
    OBJECT      xcmGenLocalizationASCIIName 
    MIN-ACCESS  read-only
    DESCRIPTION "
        It is conformant to implement this object as read-only"
    OBJECT      xcmGenLocalizationName 
    MIN-ACCESS  read-only
    DESCRIPTION "
        It is conformant to implement this object as read-only"
    OBJECT      xcmGenLocalizationLanguage 
    MIN-ACCESS  read-only
    DESCRIPTION "
        It is conformant to implement this object as read-only"
    OBJECT      xcmGenLocalizationCountry 
    MIN-ACCESS  read-only
    DESCRIPTION "
        It is conformant to implement this object as read-only"
    OBJECT      xcmGenLocalizationCharSet 
    MIN-ACCESS  read-only
    DESCRIPTION "
        It is conformant to implement this object as read-only"
    OBJECT      xcmGenCodeIndexedStringRowStat
    SYNTAX      INTEGER { active(1) }   
    MIN-ACCESS  read-only
    DESCRIPTION "
        It is conformant to implement this object as read-only, and
        only one of the enumerated values for the 'RowStatus' textual
        convention need be supported, specifically:  active(1)."
    OBJECT      xcmGenCodeIndexedStringData 
    SYNTAX      OCTET STRING (SIZE (0..32))
    MIN-ACCESS  read-only
    DESCRIPTION "
        It is conformant to implement this object as read-only, and
        only 32 octets maximum string length need be supported."
    OBJECT      xcmGenCodedCharSetRowStatus
    SYNTAX      INTEGER { active(1) }   
    MIN-ACCESS  read-only
    DESCRIPTION "
        It is conformant to implement this object as read-only, and
        only one of the enumerated values for the 'RowStatus' textual
        convention need be supported, specifically:  active(1)."
    OBJECT      xcmGenCodedCharSetASCIIName 
    MIN-ACCESS  read-only
    DESCRIPTION "
        It is conformant to implement this object as read-only"
    OBJECT      xcmGenFixedLocalizationIndex 
    MIN-ACCESS  read-only
    DESCRIPTION "
        It is conformant to implement this object as read-only"
    OBJECT      xcmGenFixedLocalizationRowStat
    SYNTAX      INTEGER { active(1) }   
    MIN-ACCESS  read-only
    DESCRIPTION "
        It is conformant to implement this object as read-only, and
        only one of the enumerated values for the 'RowStatus' textual
        convention need be supported, specifically:  active(1)."
    OBJECT      xcmGenLockRowStatus
    SYNTAX      INTEGER {               
        active(1),
        notInService(2)
        }
    MIN-ACCESS  read-write
    DESCRIPTION "
        It is conformant to implement this object as read-write, and
        only two of the enumerated values for the 'RowStatus' textual
        convention need be supported, specifically:
        active(1) and notInService(2)."
    OBJECT      xcmGenLockOwnerString
    SYNTAX      OCTET STRING (SIZE (0..32))
    MIN-ACCESS  read-write
    DESCRIPTION "
        It is conformant to implement this object as read-write, and
        only 32 octets maximum string length need be supported."
    OBJECT      xcmGenLockOwnerSubtree
    MIN-ACCESS  read-write
    DESCRIPTION "
        It is conformant to implement this object as read-write."
    OBJECT      xcmGenLockOwnerTimer
    MIN-ACCESS  read-write
    DESCRIPTION "
        It is conformant to implement this object as read-write."
    OBJECT      xcmGenReconfRowStatus
    SYNTAX      INTEGER {               
        active(1),
        notInService(2)
        }
    MIN-ACCESS  read-write
    DESCRIPTION "
        It is conformant to implement this object as read-write, and
        only two of the enumerated values for the 'RowStatus' textual
        convention need be supported, specifically:
        active(1) and notInService(2)."
    OBJECT      xcmGenReconfOptionIndex
    MIN-ACCESS  read-write
    DESCRIPTION "
        It is conformant to implement this object as read-write."
    OBJECT      xcmGenReconfOptionState
    MIN-ACCESS  read-write
    DESCRIPTION "
        It is conformant to implement this object as read-write."
    OBJECT      xcmGenOptionRowStatus
    SYNTAX      INTEGER {               
        active(1),
        notInService(2)
        }
    MIN-ACCESS  read-write
    DESCRIPTION "
        It is conformant to implement this object as read-write, and
        only two of the enumerated values for the 'RowStatus' textual
        convention need be supported, specifically:
        active(1) and notInService(2)."
    OBJECT      xcmGenOptionTypeOID
    MIN-ACCESS  read-write
    DESCRIPTION "
        It is conformant to implement this object as read-write."
    OBJECT      xcmGenOptionValueSyntax
    MIN-ACCESS  read-write
    DESCRIPTION "
        It is conformant to implement this object as read-write."
    OBJECT      xcmGenOptionValueInteger
    MIN-ACCESS  read-write
    DESCRIPTION "
        It is conformant to implement this object as read-write."
    OBJECT      xcmGenOptionValueOID
    MIN-ACCESS  read-write
    DESCRIPTION "
        It is conformant to implement this object as read-write."
    OBJECT      xcmGenOptionValueString
    SYNTAX      OCTET STRING (SIZE (0..32))
    MIN-ACCESS  read-write
    DESCRIPTION "
        It is conformant to implement this object as read-write, and
        only 32 octets maximum string length need be supported."
    OBJECT      xcmGenOptionValueLocalization
    MIN-ACCESS  read-write
    DESCRIPTION "
        It is conformant to implement this object as read-write."
    OBJECT      xcmGenOptionValueCodedCharSet
    MIN-ACCESS  read-write
    DESCRIPTION "
        It is conformant to implement this object as read-write."
    OBJECT      xcmGenOptionNextIndex
    MIN-ACCESS  read-write
    DESCRIPTION "
        It is conformant to implement this object as read-write."
    OBJECT      xcmGenOptionPreviousIndex
    MIN-ACCESS  read-write
    DESCRIPTION "
        It is conformant to implement this object as read-write."
    OBJECT      xcmGenOptionFamilyIndex
    MIN-ACCESS  read-write
    DESCRIPTION "
        It is conformant to implement this object as read-write."
    OBJECT      xcmGenClientDataRowStatus
    SYNTAX      INTEGER {               
        active(1),
        notInService(2)
        }
    MIN-ACCESS  read-write
    DESCRIPTION "
        It is conformant to implement this object as read-write, and
        only two of the enumerated values for the 'RowStatus' textual
        convention need be supported, specifically:
        active(1) and notInService(2)."
    OBJECT      xcmGenClientDataRequestID
    MIN-ACCESS  read-write
    DESCRIPTION "
        It is conformant to implement this object as read-write."
    OBJECT      xcmGenClientDataProductID
    MIN-ACCESS  read-write
    DESCRIPTION "
        It is conformant to implement this object as read-write."
    OBJECT      xcmGenClientDataLength
    SYNTAX      INTEGER (0..1)
    MIN-ACCESS  read-write
    DESCRIPTION "
        It is conformant to implement this object as read-write, and
        only 1 octet maximum client data length need be supported."
    OBJECT      xcmGenClientDataString
    SYNTAX      OCTET STRING (SIZE (0..1))
    MIN-ACCESS  read-write
    DESCRIPTION "
        It is conformant to implement this object as read-write, and
        only 1 octet maximum client data length need be supported."
--  DESCRIPTION "
--      textual convention need be supported."
--  DESCRIPTION "
--      only 32 octets maximum string length need be supported."
    OBJECT      xcmGenTrapClientRowStatus
    SYNTAX      INTEGER { active(1) }   
    MIN-ACCESS  read-only
    DESCRIPTION "
        Usage:  It is conformant to implement this object as read-only,
        however, conforming management agents are STRONGLY RECOMMENDED
        to support at least read-write access to this object."
    OBJECT      xcmGenTrapClientRowPersistence
    SYNTAX      INTEGER {
        volatile(3)                     
    }
    MIN-ACCESS  read-only
    DESCRIPTION "
        Usage:  It is conformant to implement this object as read-only,
        however, conforming management agents are STRONGLY RECOMMENDED
        to support at least read-write access to this object.
        Usage:  Conforming management agents SHALL support
        'volatile' (lost across power cycles).
        Usage:  Conforming management agents are STRONGLY RECOMMENDED to
        support 'nonvolatile' (preserved across power cycles),
        but NEED NOT support any other levels of persistence."
    OBJECT      xcmGenTrapClientSNMPVersion
    SYNTAX      INTEGER {
        unknown(1),                     
        other(2),                       
        snmpV1Community(3)
    }
    MIN-ACCESS  read-only
    DESCRIPTION "
        It is conformant to implement this object as read-only, and only
        those specified enumerated values for the 'XcmGenSNMPVersion'
        textual convention need be supported,
        specifically:  snmpV1Community(3)."
    OBJECT      xcmGenTrapClientSNMPCommunity
    SYNTAX      OCTET STRING (SIZE (0..1))
    MIN-ACCESS  read-only
    DESCRIPTION "
        It is conformant to implement this object as read-only, and
        only 1 octet maximum string length need be supported.
        XCMI conforming management agents NEED NOT support changing of
        SNMP community strings by remote management stations."
    OBJECT      xcmGenTrapViewRowStatus
    SYNTAX      INTEGER { active(1) }   
    MIN-ACCESS  read-only
    DESCRIPTION "
        It is conformant to implement this object as read-only, and only
        those specified enumerated values for the 'RowStatus' textual
        convention need be supported, specifically:  active(1)."
    OBJECT      xcmGenTrapViewNotifySeverity
    MIN-ACCESS  read-only
    DESCRIPTION "
        It is conformant to implement this object as read-only."
    OBJECT      xcmGenTrapViewNotifyTraining
    MIN-ACCESS  read-only
    DESCRIPTION "
        It is conformant to implement this object as read-only."
    OBJECT      xcmGenMessageMapStringLabel
    SYNTAX      XcmGenMessageMapStringLabel (SIZE (0..64))
    DESCRIPTION "
        It is conformant to implement this object as read-only, and
        only 64 octets maximum string length need be supported."
    OBJECT      xcmGenMessageTextTargetString
    SYNTAX      XcmNamedLocaleUtf8String (SIZE (0..64))
    DESCRIPTION "
        It is conformant to implement this object as read-only, and
        only 64 octets maximum string length need be supported."
    OBJECT      xcmGenNotifyRuleRowStatus
    SYNTAX      INTEGER { active(1) }   
    MIN-ACCESS  read-only
    DESCRIPTION "
        It is conformant to implement this object as read-only, and
        only one of the enumerated values for the 'RowStatus' textual
        convention need be supported, specifically:  active(1)."
    OBJECT      xcmGenNotifyRuleRowPersistence
    SYNTAX      INTEGER {
        volatile(3)                     
    }
    MIN-ACCESS  read-only
    DESCRIPTION "
        It is conformant to implement this object as read-only, and
        only one of the enumerated values for the 'xcmGenRowPersistence'
        textual convention need be supported,
        specifically:  volatile(3)."
    OBJECT      xcmGenNotifyRuleRecipientURI
    MIN-ACCESS  read-only
    DESCRIPTION "
        It is conformant to implement this object as read-only."
    OBJECT      xcmGenNotifyRuleEventNames
    MIN-ACCESS  read-only
    DESCRIPTION "
        It is conformant to implement this object as read-only."
    OBJECT      xcmGenNotifyRuleEventDelay
    MIN-ACCESS  read-only
    DESCRIPTION "
        It is conformant to implement this object as read-only."
    OBJECT      xcmGenNotifyRuleSeverityFilter
    MIN-ACCESS  read-only
    DESCRIPTION "
        It is conformant to implement this object as read-only."
    OBJECT      xcmGenNotifyRuleTrainingFilter
    MIN-ACCESS  read-only
    DESCRIPTION "
        It is conformant to implement this object as read-only."
    OBJECT      xcmGenNotifyRuleCharset
    MIN-ACCESS  read-only
    DESCRIPTION "
        It is conformant to implement this object as read-only."
    OBJECT      xcmGenNotifyRuleNaturalLanguage
    MIN-ACCESS  read-only
    DESCRIPTION "
        It is conformant to implement this object as read-only."
    OBJECT      xcmGenNotifyDetailRowStatus
    SYNTAX      INTEGER { active(1) }   
    MIN-ACCESS  read-only
    DESCRIPTION "
        It is conformant to implement this object as read-only, and
        only one of the enumerated values for the 'RowStatus' textual
        convention need be supported, specifically:  active(1)."
    OBJECT      xcmGenNotifyDetailString
    MIN-ACCESS  read-only
    DESCRIPTION "
        It is conformant to implement this object as read-only."
    ::= { xcmGeneralMIBConformance 3 }
--
--
xcmGenBaseGroup OBJECT-GROUP
    OBJECTS {
        xcmGenBaseRowStatus,
        xcmGenBaseSystemHrDeviceIndex,
        xcmGenBaseGroupSupport,
        xcmGenBaseGroupCreateSupport,
        xcmGenBaseGroupUpdateSupport,
        xcmGenBaseClientDataMaxSupport,
        xcmGenBaseOptionSyntaxSupport,
        xcmGenBaseReconfStateSupport,
        xcmGenBaseSNMPDomainSupport,
        xcmGenBaseSNMPTrapSupport,
        xcmGenBaseSNMPVersionSupport,
        xcmGenBaseSNMPReadCommunity,
        xcmGenBaseSNMPWriteCommunity,
        xcmGenBaseSNMPTrapCommunity,
        xcmGenBaseGroupWalkHidden,
        xcmGenBaseNotifySchemeSupport,
        xcmGenBaseNotifySeveritySupport,
        xcmGenBaseNotifyTrainingSupport,
        xcmGenBaseSystem1284DeviceId, 
        xcmGenBaseSNMPWarningTrapSupport
    }
    STATUS      current
    DESCRIPTION "
        General Base Group (XCMI General MIB capabilities)"
    ::= { xcmGeneralMIBGroups 1 }
xcmGenCurrentLocalizationGroup OBJECT-GROUP
    OBJECTS { 
        xcmGenCurrentLocalizationIndex,
        xcmGenCurrLocalizationRowStatus
    }
    STATUS  current
    DESCRIPTION "
        Current Localization Group (dynamic locales)"
    ::= { xcmGeneralMIBGroups 3 }
xcmGenLocalizationGroup OBJECT-GROUP
    OBJECTS {
        xcmGenLocalizationRowStatus,
        xcmGenLocalizationASCIIName,
        xcmGenLocalizationName,
        xcmGenLocalizationLanguage,
        xcmGenLocalizationCountry,
        xcmGenLocalizationCharSet
    }
    STATUS  current
    DESCRIPTION "
        General Localization Group (supported dynamic/static locales)"
    ::= { xcmGeneralMIBGroups 4 }
xcmGenCodeIndexedStringGroup OBJECT-GROUP
    OBJECTS { 
        xcmGenCodeIndexedStringRowStat,
        xcmGenCodeIndexedStringData
    }
    STATUS  current
    DESCRIPTION "
        Code Indexed String Group (charset conversions)"
    ::= { xcmGeneralMIBGroups 5 }
xcmGenCodedCharSetGroup OBJECT-GROUP
    OBJECTS {
        xcmGenCodedCharSetRowStatus,
        xcmGenCodedCharSetASCIIName
    }
    STATUS  current
    DESCRIPTION "
        Coded Character Set Group (supported IANA-registered charsets)"
    ::= { xcmGeneralMIBGroups 6 }
xcmGenFixedLocalizationGroup OBJECT-GROUP
    OBJECTS {
        xcmGenFixedLocalizationIndex,
        xcmGenFixedLocalizationRowStat
    }
    STATUS      current
    DESCRIPTION "
        Fixed Localization Group (static locales)"
    ::= { xcmGeneralMIBGroups 7 }
xcmGenLockGroup OBJECT-GROUP
    OBJECTS {
        xcmGenLockSupportMaxTimer,
        xcmGenLockCurrentMaxTimer,
        xcmGenLockCurrentLockCount,
        xcmGenLockHighestLockIndex,
        xcmGenLockSupportMaxCount,
        xcmGenLockRowStatus,
        xcmGenLockOwnerString,
        xcmGenLockOwnerSubtree,
        xcmGenLockOwnerTimer
    }
    STATUS      current
    DESCRIPTION "
        General Lock Group (advisory contention locks)
        Implementation of this group is STRONGLY RECOMMENDED."
    ::= { xcmGeneralMIBGroups 8 }
xcmGenReconfGroup OBJECT-GROUP
    OBJECTS {
        xcmGenReconfActivations,
        xcmGenReconfEntryCount,
        xcmGenReconfSupportMaxCount,
        xcmGenReconfRowStatus,
        xcmGenReconfOptionIndex,
        xcmGenReconfOptionState,
        xcmGenReconfErrorIndex,
        xcmGenReconfErrorStatus
    }
    STATUS      current
    DESCRIPTION "
        General Reconf Group (reconfiguration requests)"
    ::= { xcmGeneralMIBGroups 9 }
xcmGenOptionGroup OBJECT-GROUP
    OBJECTS {
        xcmGenOptionEntryCount,
        xcmGenOptionSupportMaxCount,
        xcmGenOptionRowStatus,
        xcmGenOptionTypeOID,
        xcmGenOptionValueSyntax,
        xcmGenOptionValueInteger,
        xcmGenOptionValueOID,
        xcmGenOptionValueString,
        xcmGenOptionValueLocalization,
        xcmGenOptionValueCodedCharSet,
        xcmGenOptionNextIndex,
        xcmGenOptionPreviousIndex,
        xcmGenOptionFamilyIndex
    }
    STATUS      current
    DESCRIPTION "
        General Option Group (reconfiguration options)"
    ::= { xcmGeneralMIBGroups 10 }
xcmGenClientDataGroup OBJECT-GROUP
    OBJECTS {
        xcmGenClientDataEntryCount,
        xcmGenClientDataLastIndex,
        xcmGenClientDataSupportMaxCount,
        xcmGenClientDataRowStatus,
        xcmGenClientDataRequestDate,
        xcmGenClientDataRequestID,
        xcmGenClientDataProductID,
        xcmGenClientDataLength,
        xcmGenClientDataString
    }
    STATUS      current
    DESCRIPTION "
        Client Data Group (network device installs/upgrades)"
    ::= { xcmGeneralMIBGroups 11 }
xcmGenTrapClientGroup OBJECT-GROUP
    OBJECTS {
        xcmGenTrapClientEntryCount,
        xcmGenTrapClientSupportMaxCount,
        xcmGenTrapClientRowStatus,
        xcmGenTrapClientIndex,
        xcmGenTrapClientRowPersistence,
        xcmGenTrapClientSNMPVersion,
        xcmGenTrapClientSNMPCommunity
    }
    STATUS      current
    DESCRIPTION "
        Trap Client Group (trap destination domains/addresses)"
    ::= { xcmGeneralMIBGroups 13 }
xcmGenTrapViewGroup OBJECT-GROUP
    OBJECTS {
        xcmGenTrapViewEntryCount,
        xcmGenTrapViewSupportMaxCount,
        xcmGenTrapViewRowStatus,
        xcmGenTrapViewNotifySeverity,
        xcmGenTrapViewNotifyTraining
    }
    STATUS      current
    DESCRIPTION "
        Trap View Group (trap requested object subtrees)"
    ::= { xcmGeneralMIBGroups 14 }
xcmGenMessageMapGroup OBJECT-GROUP
    OBJECTS {
        xcmGenMessageMapStringLabel
    }
    STATUS      current
    DESCRIPTION "
        Message Map Group (message labels for client localization)"
    ::= { xcmGeneralMIBGroups 15 }
xcmGenMessageTextGroup OBJECT-GROUP
    OBJECTS {
        xcmGenMessageTextTargetString
    }
    STATUS      current
    DESCRIPTION "
        Message Text Group (message lookups for agent localization)"
    ::= { xcmGeneralMIBGroups 16 }
xcmGenNotifyRuleGroup OBJECT-GROUP
    OBJECTS {
        xcmGenNotifyRuleEntryCount,
        xcmGenNotifyRuleSupportMaxCount,
        xcmGenNotifyRuleRowStatus,
        xcmGenNotifyRuleRowPersistence,
        xcmGenNotifyRuleRecipientURI,
        xcmGenNotifyRuleEventNames,
        xcmGenNotifyRuleEventDelay,
        xcmGenNotifyRuleSeverityFilter,
        xcmGenNotifyRuleTrainingFilter,
        xcmGenNotifyRuleCharset,
        xcmGenNotifyRuleNaturalLanguage,
        xcmGenNotifyRuleSequenceNumber
    }
    STATUS      current
    DESCRIPTION "
        Notify Rule Group (notification client URI and event names)"
    ::= { xcmGeneralMIBGroups 17 }
xcmGenNotifyDetailGroup OBJECT-GROUP
    OBJECTS {
        xcmGenNotifyDetailEntryCount,
        xcmGenNotifyDetailSupportMax,
        xcmGenNotifyDetailRowStatus,
        xcmGenNotifyDetailString
    }
    STATUS      current
    DESCRIPTION "
        Notify Detail Group (notification additional details)"
    ::= { xcmGeneralMIBGroups 18 }
xcmHrTC OBJECT-IDENTITY -- MODULE-IDENTITY
    STATUS   current
    DESCRIPTION
        "Version:    6.001.pub
        The TC module for textual conventions, enumerated types, OIDs,
        and other volatile elements of the companion Host Resources
        Extensions MIB ('xcmHrMIB'), which supports extended
        configuration and management of various host resources for
        network accessible host systems.  These modules augment and
        extend the original IETF Host Resources MIB (RFC 2790).
        Usage:  This MIB module introduces support for the 'realization'
        of both 'physical' and 'logical' devices, consistent with ISO
        DPA (Document Printing Application), ISO/IEC 10175, as reflected
        in the object 'xcmHrDevInfoRealization'.
        Note:   Conforming implementations SHALL NOT 'bubble up' status
        from 'physical' devices to associated 'logical' devices.  All
        devices SHALL report their own status ONLY.
        See:    Section 9 'Supplement' in XCMI Extensions to IETF Host
        Resources TC, for implementation guidance for this TC module.
        Copyright (C) 1995-2009 Xerox Corporation. All Rights Reserved."
    ::= { xeroxCommonMIB 52 }
--
--
--
--
--
--
xcmHrDeviceTypes OBJECT-IDENTITY
    STATUS      current
    DESCRIPTION
        "The root of all additional device types defined in HRX TC."
    ::= { xcmHrTC 2 }
xcmHrDeviceHostSystem OBJECT-IDENTITY
    STATUS      current
    DESCRIPTION
        "Host system device type - manufacturer independent.
        For host systems which instrument multiple devices and
        support MIBs with tables INDEXed by 'hrDeviceIndex', the single
        'xcmHrDeviceHostSystem' device represents the 'root' device
        which MAY be used to manage overall host system defaults,
        configuration, status, etc."
    REFERENCE
        "See:   'xcmHrDeviceHostSystemHistory' in this XCMI HRX TC."
    ::= { xcmHrDeviceTypes 101 }
xcmHrDeviceScanner OBJECT-IDENTITY
    STATUS      current
    DESCRIPTION
        "Scanner device type - manufacturer independent.
        An 'xcmHrDeviceScanner' device with 'xcmHrDevInfoRealization' of
        'physical' is a 'real' input device (eg, a 'scan channel' on a
        multifunction printer).
        An 'xcmHrDeviceScanner' device with 'xcmHrDevInfoRealization' of
        'logical' is a 'virtual' input device (eg, a 'personality' of a
        'scan channel' on a multifunction printer)."
    REFERENCE
        "See:   'xcmHrDeviceScannerHistory' in this XCMI HRX TC."
    ::= { xcmHrDeviceTypes 102 }
xcmHrDeviceCopier OBJECT-IDENTITY
    STATUS      current
    DESCRIPTION
        "Copier device type - manufacturer independent.
        An 'xcmHrDeviceCopier' device with 'xcmHrDevInfoRealization' of
        'physical' is a 'real' I/O device (eg, a 'copier' on a
        multifunction printer).
        An 'xcmHrDeviceCopier' device with 'xcmHrDevInfoRealization' of
        'logical' is a 'virtual' I/O device (eg, a 'personality' of a
        'copier' on a multifunction printer)."
    REFERENCE
        "See:   'xcmHrDeviceCopierHistory' in this XCMI HRX TC."
    ::= { xcmHrDeviceTypes 103 }
xcmHrDeviceFax OBJECT-IDENTITY
    STATUS      current
    DESCRIPTION
        "Fax device type - manufacturer independent.
         xcmHrDeviceFax is maintained for legacy products.  It is 
         recommended that the hrDeviceType is explicitly defined using
         xcmHrDeviceEmbeddedFax, xcmHrDeviceServerFax or
         xcmHrDeviceInternetFax.
        An 'xcmHrDeviceFax' device with 'xcmHrDevInfoRealization' of
        'physical' is a 'real' I/O device (eg, a 'fax channel' on a
        multifunction printer).
        An 'xcmHrDeviceFax' device with 'xcmHrDevInfoRealization' of
        'logical' is a 'virtual' I/O device (eg, a 'personality' of a
        'fax channel' on a multifunction printer)."
    REFERENCE
        "See:   'xcmHrDeviceFaxHistory' in this XCMI HRX TC."
    ::= { xcmHrDeviceTypes 104 }
xcmHrDeviceMailbox OBJECT-IDENTITY
    STATUS      current
    DESCRIPTION
        "Mailbox device type - manufacturer independent.
        An 'xcmHrDeviceMailbox' device is a 'multi-bin' output device,
        with each 'bin' assigned to a user, group, account, etc, and
        (optionally) physical security associated with each 'bin'.
        An 'xcmHrDeviceMailbox' device with 'xcmHrDevInfoRealization' of
        'physical' is a 'real' output device (eg, a 'tower mailbox' on
        a high-end printer).
        An 'xcmHrDeviceMailbox' device with 'xcmHrDevInfoRealization' of
        'logical' is a 'virtual' output device (eg, a 'personality' of a
        'tower mailbox' on a high-end printer).
        An 'xcmHrDeviceMailbox' device with 'xcmHrDevInfoRealization' of
        'logical' MAY also indicate the current configuration of a
        'physical' device of type 'xcmHrDeviceMailboxSorter'."
    REFERENCE
        "See:   'xcmHrDeviceMailboxSorter' and 'xcmHrDeviceSorter'."
    ::= { xcmHrDeviceTypes 105 }
xcmHrDeviceFinisher OBJECT-IDENTITY
    STATUS      current
    DESCRIPTION
        "Finisher device type - manufacturer independent.
        An 'xcmHrDeviceFinisher' device is an output finishing device.
        An 'xcmHrDeviceFinisher' device with 'xcmHrDevInfoRealization'
        of 'physical' is a 'real' output device (eg, a 'stapler'
        on a high-end printer).
        An 'xcmHrDeviceFinisher' device with 'xcmHrDevInfoRealization'
        of 'logical' is a 'virtual' output device (eg, a 'personality'
        of a 'stapler' on a high-end printer)."
    ::= { xcmHrDeviceTypes 106 }
xcmHrDeviceFeeder OBJECT-IDENTITY
    STATUS      current
    DESCRIPTION
        "Feeder device type - manufacturer independent.
        An 'xcmHrDeviceFeeder' device is an input device.
        An 'xcmHrDeviceFeeder' device with 'xcmHrDevInfoRealization'
        of 'physical' is a 'real' output device (eg, a 'high-capacity
        feeder' on a high-end printer).
        An 'xcmHrDeviceFeeder' device with 'xcmHrDevInfoRealization'
        of 'logical' is a 'virtual' output device (eg, a 'personality'
        of a 'high-capacity feeder' on a high-end printer)."
    ::= { xcmHrDeviceTypes 107 }
xcmHrDeviceSorter OBJECT-IDENTITY
    STATUS      current
    DESCRIPTION
        "Sorter device type - manufacturer independent.
        An 'xcmHrDeviceSorter' device is a 'multi-bin' output device,
        with each 'bin' assigned to a copy of the current job, and
        NO physical security associated with each 'bin'.
        An 'xcmHrDeviceSorter' device with 'xcmHrDevInfoRealization' of
        'physical' is a 'real' output device (eg, a '10-bin sorter' on
        a mid-range printer).
        An 'xcmHrDeviceSorter' device with 'xcmHrDevInfoRealization' of
        'logical' is a 'virtual' output device (eg, a 'personality' of a
        '10-bin sorter' on a mid-range printer).
        An 'xcmHrDeviceSorter' device with 'xcmHrDevInfoRealization' of
        'logical' MAY also indicate the current configuration of a
        'physical' device of type 'xcmHrDeviceMailboxSorter'."
    REFERENCE
        "See:   'xcmHrDeviceMailboxSorter' and 'xcmHrDeviceMailbox'."
    ::= { xcmHrDeviceTypes 108 }
xcmHrDeviceMailboxSorter OBJECT-IDENTITY
    STATUS      current
    DESCRIPTION
        "MailboxSorter device type - manufacturer independent.
        An 'xcmHrDeviceMailboxSorter' is a 'multi-bin' output device,
        which MAY be configured as either a 'mailbox' or a 'sorter',
        by a system adminstrator or by default product configuration.
        An 'xcmHrDeviceMailboxSorter' with 'xcmHrDevInfoRealization' of
        'physical' is a 'real' output device and associated with
        associated with exactly two 'logical' output devices of types
        'xcmHrDeviceMailbox' and 'xcmHrDeviceSorter' - one of these
        'logical' devices MAY be 'running' (currently configured) - at
        least one SHALL be 'down' (NOT currently configured)."
    ::= { xcmHrDeviceTypes 109 }
xcmHrDevicePrintAppliance OBJECT-IDENTITY
    STATUS      current
    DESCRIPTION
        "Print appliance device type - manufacturer independent.
        An 'xcmHrDevicePrintAppliance' is a network printing appliance
        with 'xcmHrDevInfoRealization' of 'physical'.
        An 'xcmHrDevicePrintAppliance' SHALL statically and/or actively
        discover available network printers and SHOULD advertise them
        as supported output devices, using rows in 'hrDeviceTable' of
        IETF HR MIB (RFC 2790) and 'prtGeneralTable' of the Printer MIB
        (RFC 1759 or successor), with 'hrDeviceType' set to
        'hrDevicePrinter'.
        An 'xcmHrDevicePrintAppliance' SHALL NOT use 'hrDeviceIndex' of
        '1' (first row) for an 'hrDevicePrinter' row, because a network
        printing appliance is an enhanced spooler and NOT a printer."
    REFERENCE
        "See:   'hrDevicePrinter' in IETF Host Resources MIB (RFC 2790).
        See:    'xcmHrDevicePrinterHistory' in this XCMI HRX TC."
    ::= { xcmHrDeviceTypes 110 }
xcmHrDeviceMarker OBJECT-IDENTITY
    STATUS      current
    DESCRIPTION
        "Marker Engine device type - manufacturer independent.
        An 'xcmHrDeviceMarker' device with 'xcmHrDevInfoRealization' 
        of 'physical' is a 'real' output device (eg, the 
        'marking engine' on a multifunction printer or copier).  The 
        marking engine is the module that accepts a print ready image 
        and physical media as input and outputs physical media with a 
        physical representation of the print ready input image.  The 
        'xcmHrDeviceMarker' is a 
        single module within a group of modules that cumulatively are 
        represented by 'hrDevicePrinter'. The marker shall represent the
        whole marker as a single physical unit and should maintain a 
        single entry in the 'hrDeviceTable' for all products that 
        support a single marking engine regardless of internal engine
        mark points. 
        (e.g. B&W, Highlight Color and Full Color Presses shall have a 
        single entry in 'hrDeviceTable'). Multiple entries of 
        'xcmHrDeviceMarker' may exist in the 'hrDeviceTable' if the 
        system supports multiple print engines whether chained, in     
        parallel or in any other configuration.   
        An 'xcmHrDeviceMarker' SHALL NOT use 'hrDeviceIndex' of
        '1' (first row).  The index 1 is reserved for an 
        'hrDevicePrinter' row." 
    ::= { xcmHrDeviceTypes 111 }
xcmHrDeviceFinisherBFM OBJECT-IDENTITY
    STATUS      current
    DESCRIPTION
        "Basic Finisher Module device type - manufacturer independent.
        An 'xcmHrDeviceFinisherBFM' device is a basic output finishing
        device. An 'xcmHrDeviceFinisherBFM' device with 
        'xcmHrDevInfoRealization' of 'physical' is a 'real' output 
        device (eg, a 'stapler' on a high-end printer).
        An 'xcmHrDeviceFinisherBFM' device with 
        'xcmHrDevInfoRealization' of 'logical' is a 'virtual' output 
        device (eg, a 'personality' of a 'stapler' on a high-end 
        printer)."
    ::= { xcmHrDeviceTypes 112 }
xcmHrDeviceFinisherMFF OBJECT-IDENTITY
    STATUS      current
    DESCRIPTION
        "Multi-Function Finisher device type - manufacturer 
         independent.
        An 'xcmHrDeviceFinisherMFF' device is a multi-function output 
         finishing device. An 'xcmHrDeviceFinisherMFF' device with 
         'xcmHrDevInfoRealization' of 'physical' is a 'real' output 
         device (eg, a 'saddle stitcher', 'C-Folder', 'Z-Folder', 
         'Hole Puncher' on a high-end printer).
        An 'xcmHrDeviceFinisherMFF' device with 
         'xcmHrDevInfoRealization' of 'logical' is a 'virtual' output 
         device (eg, a 'personality' of a 'saddle stitcher', 
         'C-Folder', 'Z-Folder', 'Hole Puncher' on a 
        high-end printer)."
    ::= { xcmHrDeviceTypes 113 }
xcmHrDeviceFinisherXIM OBJECT-IDENTITY
    STATUS      current
    DESCRIPTION
         "eXternal Interface Module Finisher device type.
        An 'xcmHrDeviceFinisherXIM' device is a hardware interface 
        used to pass media from a Xerox printing device to a 3rd party
        finishing devices. The 'xcmHrDeviceFinihserXIM' may or may not 
        contain its own output trays or finishing capabilities.
        An 'xcmHrDeviceFinisherXIM' device with 
        'xcmHrDevInfoRealization' of 'physical' is a 'real' output 
        device (e.g., an 'output bridge' on a high-end printer)."
    ::= { xcmHrDeviceTypes 114 }
xcmHrDeviceFinisher3rdParty OBJECT-IDENTITY
    STATUS      current
    DESCRIPTION
         "3rd Party Finisher device type - manufacturer independent.
        An 'xcmHrDeviceFinisher3rdParty' device is an output finishing 
        device. An 'xcmHrDeviceFinisher3rdParty' device with 
        'xcmHrDevInfoRealization'
        of 'physical' is a 'real' output device (eg, a 'stapler' on 
        a high-end printer). An 'xcmHrDeviceFinisher3rdParty' device 
        with 'xcmHrDevInfoRealization' of 'logical' is a 'virtual' 
        output device (eg, a 'personality' of a 'stapler' on a high-end
        printer)."
    ::= { xcmHrDeviceTypes 115 }
xcmHrDevicePaymentInterface OBJECT-IDENTITY
    STATUS      current
    DESCRIPTION
        "Payment Interface device type - manufacturer independent.
        An 'xcmHrDevicePaymentInterface' device is an payment 
        authorization device.
        An 'xcmHrDevicePaymentInterface' device with 
        'xcmHrDevInfoRealization' of 'physical' is a 'real' point of 
        purchase validation device (eg, a 'coin operated', 'smart card' 
        or other form of point of purchase payment for services 
        rendered on a multi-function printer or copier).
        An 'xcmHrDevicePaymentInterface' device with 
        'xcmHrDevInfoRealization' of 'logical' is a 'virtual' point 
        of purchase validation device (eg, a software service that 
        accepts payment through the Web or some other form of remote 
        point of purchase payment for services rendered on a 
        multi-function printer or copier)."
    ::= { xcmHrDeviceTypes 116 }
xcmHrDeviceInterposer OBJECT-IDENTITY
    STATUS      current
    DESCRIPTION
        "Interposer device type - manufacturer independent.
        An 'xcmHrDeviceInterposer' device is an input device which 
        physically resides downstream of the print engine amongst 
        finishing modules.
        An 'xcmHrDeviceInterposer' device with 
        'xcmHrDevInfoRealization' of 'physical' is a 'real' input 
        device (eg, a 'high-capacity Interposing feeder' that 
        physically resides amongst finishing modules
        on a high-end printer).
        An 'xcmHrDeviceInterposer' device with 
        'xcmHrDevInfoRealization' of 'logical' is a 'virtual' 
        input device (eg, a 'personality' of a 
        'high-capacity Interposing feeder' that physically resides 
        amongst finishing modules on a high-end printer). 
        Interposers are essentially feeders that are placed 
        downstream of the print engine paper path and upstream of 
        finishing devices.  Interposer fed media is not marked by the
        print engine; instead media fed from an interposer is inserted 
        before, between or after marked pages.  The media constitutes 
        covers, separators etc."  
    ::= { xcmHrDeviceTypes 117 }
xcmHrDeviceInternetFax OBJECT-IDENTITY
    STATUS      current
    DESCRIPTION
        "Internet Fax device type - manufacturer independent.
 A local Fax service which sends and/or receives faxes
 over the internet"
    REFERENCE
        "See:   'xcmHrDeviceFax' in this XCMI HRX TC."
    ::= { xcmHrDeviceTypes 118 }
xcmHrDeviceServerFax OBJECT-IDENTITY
    STATUS      current
    DESCRIPTION
        "Server Fax device type - manufacturer independent.
 A Fax service which works with a server on the network
 to send and/or receive faxes over a remote modem and
 phone lines"
    REFERENCE
        "See:   'xcmHrDeviceFax' in this XCMI HRX TC."
    ::= { xcmHrDeviceTypes 119 }
xcmHrDeviceEmbeddedFax OBJECT-IDENTITY
    STATUS      current
    DESCRIPTION
        "Embedded Fax device type - manufacturer independent. 
         A local fax service which sends and/or receives fax 
         directly over a modem and phone lines."
    REFERENCE
        "See:   'xcmHrDeviceFax' in this XCMI HRX TC."
    ::= { xcmHrDeviceTypes 120 }
xcmHrDeviceForeignInterface OBJECT-IDENTITY 
    STATUS      current 
    DESCRIPTION 
        "Foreign Interface device type - manufacturer independent. 
         A physical connection provided by a device for the purpose 
         of connecting an external accessory. This accessory may 
         be capable of tracking data (e.g. Auditron) or may enable/ 
         disable device operation (e.g. card reader, coin operator, 
         etc.). This device type shall only be used when the device 
         cannot detect the type of external accessory that is 
         physically connected. If the device can detect the type of 
         external accessory which can be physically connected, 
         then the appropriate device type for that interface should 
         be used instead. (e.g. xcmHrDevicePaymentInterface, 
         xcmHrDeviceSecurityInterface, or 
         xcmHrDeviceAccountingInterface" 
    ::= { xcmHrDeviceTypes 121 } 
xcmHrDeviceSecurityInterface OBJECT-IDENTITY 
    STATUS      current 
    DESCRIPTION 
        "Security device type - manufacturer independent. 
         A physical connection provided by a device for the purpose 
         of connecting an external security-related accessory. This 
         accessory may consist of a card reader or biometric device 
         which would restrict access to a machine to only authorized 
         users." 
    ::= { xcmHrDeviceTypes 122 } 
xcmHrDeviceAccountingInterface OBJECT-IDENTITY 
    STATUS      current 
    DESCRIPTION 
        "Accounting device type - manufacturer independent. 
         A physical connection provided by a device for the purpose 
         of connecting an external accounting-related accessory. This 
         accessory would provide the capability to track machine 
         usage but would not restrict access to the machine as would 
         an accessory defined by type xcmHrDevicePaymentInterface." 
    ::= { xcmHrDeviceTypes 123 } 
xcmHrDeviceFeederSFM OBJECT-IDENTITY 
    STATUS      current 
    DESCRIPTION 
        "Feeder device type - Xerox Substraite Feeding Module 
        An 'xcmHrDeviceFeederSFM' device is an input device. 
        An 'xcmHrDeviceFeederSFM' device with 
        'xcmHrDevInfoRealization' of 'physical' is a 'real' output 
        device (eg, a 'high-capacity feeder' on a high-end printer). 
        An 'xcmHrDeviceFeeder' device with 'xcmHrDevInfoRealization' 
        of 'logical' is a 'virtual' output device (eg, a 'personality' 
        of a 'high-capacity feeder' on a high-end printer)." 
    ::= { xcmHrDeviceTypes 124 } 
xcmHrDeviceFeederLFF OBJECT-IDENTITY 
    STATUS      current 
    DESCRIPTION 
        "Feeder device type - Xerox Large Format Feeder. 
        An 'xcmHrDeviceFeederLFF' device is an input device. 
        An 'xcmHrDeviceFeeder' device with 'xcmHrDevInfoRealization' 
        of 'physical' is a 'real' output device (eg, a 'high-capacity 
        large format feeder' on a high-end printer). 
        An 'xcmHrDeviceFeeder' device with 'xcmHrDevInfoRealization' 
        of 'logical' is a 'virtual' output device (eg, a 'personality' 
        of a 'high-capacity large format feeder' 
        on a high-end printer)." 
    ::= { xcmHrDeviceTypes 125 } 
xcmHrDeviceScannerADF OBJECT-IDENTITY 
    STATUS      current 
    DESCRIPTION 
        "Scanner device type - manufacturer independent automatic 
         document feeding scanner.  An 'xcmHrDeviceScannerADF' device 
         with 'xcmHrDevInfoRealization' of 'physical' is a 'real' input 
         device (eg, a 'scan channel' on a multifunction printer). 
         An 'xcmHrDeviceScannerADF' device with 
         'xcmHrDevInfoRealization' of 'logical' is a 'virtual' input 
         device (eg, a 'personality' of a 'scan channel' on a 
         multifunction printer)." 
    REFERENCE 
        "See:   'xcmHrDeviceScannerHistory' in this XCMI HRX TC." 
    ::= { xcmHrDeviceTypes 126 } 
xcmHrDeviceScannerPlaten OBJECT-IDENTITY 
    STATUS      current 
    DESCRIPTION 
        "Scanner device type -  manufacturer independent platen glass 
         scanner. An 'xcmHrDeviceScannerPlaten' device with 
         'xcmHrDevInfoRealization' of 'physical' is a 'real' input 
         device (eg, a 'scan channel' on a multifunction printer). 
        An 'xcmHrDeviceScannerPlaten' device with 
        'xcmHrDevInfoRealization' of 'logical' is a 'virtual' input 
        device (eg, a 'personality' of a 'scan channel' on a 
        multifunction printer)." 
    REFERENCE 
        "See:   'xcmHrDeviceScannerHistory' in this XCMI HRX TC." 
    ::= { xcmHrDeviceTypes 127 } 
xcmHrDeviceColorScanningCard OBJECT-IDENTITY 
    STATUS      current 
    DESCRIPTION 
        "An xcmHrDeviceColorScanningCard is a physical card that allows 
         for scanning of color, or monochrome, images from the printer
         to a remote device."
    ::= { xcmHrDeviceTypes 128 } 
--
--
--
xcmHrDeviceHostSystemHistory OBJECT-IDENTITY
    STATUS      current
    DESCRIPTION
        "Host system history device type - manufacturer independent."
    REFERENCE
        "See:   'xcmHrDeviceHostSystem' in this XCMI HRX TC."
    ::= { xcmHrDeviceTypes 151 }
xcmHrDeviceScannerHistory OBJECT-IDENTITY
    STATUS      current
    DESCRIPTION
        "Scanner history device type - manufacturer independent."
    REFERENCE
        "See:   'xcmHrDeviceScanner' in this XCMI HRX TC."
    ::= { xcmHrDeviceTypes 152 }
xcmHrDeviceCopierHistory OBJECT-IDENTITY
    STATUS      current
    DESCRIPTION
        "Copier history device type - manufacturer independent."
    REFERENCE
        "See:   'xcmHrDeviceCopier' in this XCMI HRX TC."
    ::= { xcmHrDeviceTypes 153 }
xcmHrDeviceFaxHistory OBJECT-IDENTITY
    STATUS      current
    DESCRIPTION
        "Fax history device type - manufacturer independent."
    REFERENCE
        "See:   'xcmHrDeviceFax' in this XCMI HRX TC."
    ::= { xcmHrDeviceTypes 154 }
xcmHrDevicePrinterHistory OBJECT-IDENTITY
    STATUS      current
    DESCRIPTION
        "Printer history device type - manufacturer independent."
    REFERENCE
        "See:   'hrDevicePrinter' in the IETF HR MIB."
    ::= { xcmHrDeviceTypes 55 }         
xcmHrCruXerographicModule OBJECT-IDENTITY
    STATUS      current
    DESCRIPTION
        "CRU xerographic module - manufacturer independent.
        An 'xcmHrCruXerographicModule' device is a customer
        replaceable unit, with 'xcmHrDevInfoRealization' of 'physical'."
    ::= { xcmHrDeviceTypes 201 }
xcmHrCruFuserModule OBJECT-IDENTITY
    STATUS      current
    DESCRIPTION
        "CRU fuser module - manufacturer independent.
        An 'xcmHrCruFuserModule' device is a customer
        replaceable unit, with 'xcmHrDevInfoRealization' of 'physical'."
    ::= { xcmHrDeviceTypes 202 }
xcmHrCruTonerBottleModule OBJECT-IDENTITY
    STATUS      current
    DESCRIPTION
        "CRU toner bottle module - manufacturer independent.
        An 'xcmHrCruTonerBottleModule' device is a customer
        replaceable unit, with 'xcmHrDevInfoRealization' of 'physical'."
    ::= { xcmHrDeviceTypes 203 }
xcmHrCruCollectorBottleModule OBJECT-IDENTITY
    STATUS      current
    DESCRIPTION
        "CRU (developer) collector bottle - manufacturer independent.
        An 'xcmHrCruCollectorBottleModule' device is a customer
        replaceable unit, with 'xcmHrDevInfoRealization' of 'physical'."
    ::= { xcmHrDeviceTypes 204 }
xcmHrCruTrayFeedHeadModule OBJECT-IDENTITY
    STATUS      current
    DESCRIPTION
        "CRU tray feed head module - manufacturer independent.
        An 'xcmHrCruTrayFeedHeadModule' device is a customer
        replaceable unit, with 'xcmHrDevInfoRealization' of 'physical'."
    ::= { xcmHrDeviceTypes 205 }
xcmHrCruAdfFeedHeadModule OBJECT-IDENTITY
    STATUS      current
    DESCRIPTION
        "CRU ADF feed head module - manufacturer independent.
        An 'xcmHrCruAdfFeedHeadModule' device is a customer
        replaceable unit, with 'xcmHrDevInfoRealization' of 'physical'.
        Note:   ADF is an acronym for 'automatic document feeder'."
    ::= { xcmHrDeviceTypes 206 }
xcmHrCruFuserWebModule OBJECT-IDENTITY
    STATUS      current
    DESCRIPTION
        "CRU fuser web module - manufacturer independent.
        An 'xcmHrCruFuserWebModule' device is a customer
        replaceable unit, with 'xcmHrDevInfoRealization' of 'physical'.
        Note:   A 'fuser web' is an oil-soaked fiber roll in a fuser,
        which prevents toner from getting on the fuser roll.  The 'fuser
        web' device would normally be replaced several times before the
        actual fuser device ('xcmHrCRUFuserModule') is replaced."
    ::= { xcmHrDeviceTypes 207 }
xcmHrCruFilterModule OBJECT-IDENTITY
    STATUS      current
    DESCRIPTION
        "CRU filter module - manufacturer independent.
        An 'xcmHrCruFilterModule' device is a customer replaceable 
        filter or filter unit, with 'xcmHrDevInfoRealization' of
        'physical'."
    ::= { xcmHrDeviceTypes 208 }
xcmHrCruCleanerUnitModule OBJECT-IDENTITY
    STATUS      current
    DESCRIPTION
        "CRU cleaner unit module - manufacturer independent.
        An 'xcmHrCruCleanerUnitModule' device is a customer
        replaceable cleaner unit, with 'xcmHrDevInfoRealization' of
        'physical' (eg, a belt cleaner or a photoreceptor cleaner)."
    REFERENCE
        "See:   'cleanerUnit' in 'PrtMarkerSuppliesTypeTC' in
                the Printer MIB v2."
    ::= { xcmHrDeviceTypes 209 }
xcmHrCruTransferUnitModule OBJECT-IDENTITY
    STATUS      current
    DESCRIPTION
        "CRU transfer unit module - manufacturer independent.
        An 'xcmHrCruTransferUnitModule' device is a customer
        replaceable transfer unit, with 'xcmHrDevInfoRealization' of
        'physical'."
    REFERENCE
        "See:   'transferUnit' in 'PrtMarkerSuppliesTypeTC' in
                the Printer MIB v2."
    ::= { xcmHrDeviceTypes 210 }
xcmHrCruTransferRollerModule OBJECT-IDENTITY
    STATUS      current
    DESCRIPTION
        "CRU transfer roller module - manufacturer independent.
        An 'xcmHrCruTransferRollerModule' device is a customer
        replaceable transfer roller, with 'xcmHrDevInfoRealization' of
        'physical' (eg, a biased transfer roller)."
    REFERENCE
        "See:   'transferUnit' in 'PrtMarkerSuppliesTypeTC' in
                the Printer MIB v2."
    ::= { xcmHrDeviceTypes 211 }
xcmHrCruPFPFeedRollModule OBJECT-IDENTITY
    STATUS      current
    DESCRIPTION
        "CRU Paper Feed Platform module - manufacturer independent.
        An 'xcmHrCruPaperFeedModule' device is a customer
        replaceable unit, with 'xcmHrDevInfoRealization' of 'physical'."
    ::= { xcmHrDeviceTypes 212 }
xcmHrCruPFPRetardRollModule OBJECT-IDENTITY
    STATUS    current
    DESCRIPTION
        "CRU PFP Retard Roll module - manufacturer independent.
        An 'xcmHrCruPFPRetardRollModule' device is a customer 
        replaceable unit, with 'xcmHrDevInfoRealization' of 'physical'."
    ::= { xcmHrDeviceTypes 213 }
xcmHrDeviceUSBPort  OBJECT-IDENTITY 
 STATUS current 
 DESCRIPTION 
  "The device type identifier used for a
  Universal Serial Bus port." 
 ::= { xcmHrDeviceTypes 250 } 
xcmHrDeviceFlashDIMMFileStore  OBJECT-IDENTITY 
 STATUS current 
 DESCRIPTION 
         "The device type identifier used for a Flash DIMM that contains
          a file system that is used to store files such as font files. 
          opposed to a Flash DIMM that contains a boot loader."
 ::= { xcmHrDeviceTypes 260 } 
xcmHrDeviceFlashDIMMBootLoader  OBJECT-IDENTITY 
 STATUS current 
 DESCRIPTION 
         "The device type identifier used for a Flash DIMM that contains
          the boot loader for a device. Files may or may not be stored o
          this device. As opposed to a Flash DIMM that contains a file 
          store system." 
 ::= { xcmHrDeviceTypes 261 } 
xcmHrDeviceFlashDrive  OBJECT-IDENTITY 
        STATUS current 
        DESCRIPTION 
         "The device type identifier used for a Flash Drive for a device
          Files may or may not be stored on this device. As opposed to a
          Flash DIMM that contains a file store system or a bootloader."
        ::= { xcmHrDeviceTypes 262 } 
xcmHrAdminServiceTypes OBJECT-IDENTITY
    STATUS      current
    DESCRIPTION
        "The root of all host system management service types (classes)
        defined in the Host Resources Extensions TC."
    REFERENCE
        "See:   'XcmSecPosixVerbs' and 'xcmSecServiceTypeOID'
                in XCMI Security TC/MIB."
    ::= { xcmHrTC 3 }
xcmHrAdminObjectService OBJECT-IDENTITY
    STATUS      current
    DESCRIPTION
        "The host system object management service."
    REFERENCE
        "See:   'xcmSysAdminObject...' in XCMI System Admin MIB.
        See:    'XcmSecPosixVerbs' and 'xcmSecServiceTypeOID'
                in XCMI Security TC/MIB."
    ::= { xcmHrAdminServiceTypes 1 }
xcmHrAdminServerService OBJECT-IDENTITY
    STATUS      current
    DESCRIPTION
        "The host system server management service."
    REFERENCE
        "See:   'xcmSysAdminServer...' in XCMI System Admin MIB,
                'hrSW[Running|Installed]Table' in IETF HR MIB, and
                'xcmHrSW[Running|Installed]ExtTable' in XCMI HRX MIB.
        See:    'XcmSecPosixVerbs' and 'xcmSecServiceTypeOID'
                in XCMI Security TC/MIB."
    ::= { xcmHrAdminServiceTypes 2 }
xcmHrAdminDeviceService OBJECT-IDENTITY
    STATUS      current
    DESCRIPTION
        "The host system device management service."
    REFERENCE
        "See:   'xcmSysAdminDevice...' in XCMI System Admin MIB,
                'hrDeviceTable' in IETF HR MIB, and
                'xcmHrDev[Info|Help|Mgmt|Power|Traffic|Calendar]Table'
                in XCMI HRX MIB.
        See:    'XcmSecPosixVerbs' and 'xcmSecServiceTypeOID'
                in XCMI Security TC/MIB."
    ::= { xcmHrAdminServiceTypes 3 }
xcmHrAdminJobService OBJECT-IDENTITY
    STATUS      current
    DESCRIPTION
        "The host system job management service."
    REFERENCE
        "See:   'xcmSysAdminJob...' in XCMI System Admin MIB, and
                'xcmJob[...]Table' in XCMI Job Monitoring MIB.
        See:    'XcmSecPosixVerbs' and 'xcmSecServiceTypeOID'
                in XCMI Security TC/MIB."
    ::= { xcmHrAdminServiceTypes 4 }
xcmHrAdminDocService OBJECT-IDENTITY
    STATUS      current
    DESCRIPTION
        "The host system document management service."
    REFERENCE
        "See:   'xcmSysAdminDoc...' in XCMI System Admin MIB, and
                'xcmDoc[...]Table' in XCMI Job Monitoring MIB.
        See:    'XcmSecPosixVerbs' and 'xcmSecServiceTypeOID'
                in XCMI Security TC/MIB."
    ::= { xcmHrAdminServiceTypes 5 }
xcmHrAdminSecurityService OBJECT-IDENTITY
    STATUS      current
    DESCRIPTION
        "The host system security management service."
    REFERENCE
        "See:   'xcmSysAdminSecurity...' in XCMI System Admin MIB.
        See:    'XcmSecPosixVerbs' and 'xcmSecServiceTypeOID'
                in XCMI Security TC/MIB."
    ::= { xcmHrAdminServiceTypes 6 }
xcmHrAdminCommsService OBJECT-IDENTITY
    STATUS      current
    DESCRIPTION
        "The host system communications management service."
    REFERENCE
        "See:   'xcmSysAdminComms...' in XCMI System Admin MIB and
                XCMI Comms Config and Comms Engine MIBs.
        See:    'XcmSecPosixVerbs' and 'xcmSecServiceTypeOID'
                in XCMI Security TC/MIB."
    ::= { xcmHrAdminServiceTypes 7 }
xcmHrAdminDeviceOperationTypes OBJECT-IDENTITY
    STATUS      current
    DESCRIPTION
        "The root of all host resources admin device operation types
        defined in the Host Resources Extensions TC.
        Usage:  The following OIDs support access control for the simple
        device admin operations defined in 'XcmHrDevMgmtCommandRequest'
        and used in 'xcmHrDevMgmtCommandRequest' in the XCMI HRX MIB,
        via 'xcmSec[Master|Policy]VerbTypeOID' in the XCMI Security MIB,
        WITHOUT requiring implementation of the XCMI System Admin MIB."
    REFERENCE
        "See:   'xcmSec[Master|Policy]VerbTypeOID' in
                XCMI Security MIB."
    ::= { xcmHrTC 4 }
xcmHrAdminDeviceNone            OBJECT IDENTIFIER
    ::= { xcmHrAdminDeviceOperationTypes 1 }
xcmHrAdminDeviceStartup         OBJECT IDENTIFIER
    ::= { xcmHrAdminDeviceOperationTypes 2 }
xcmHrAdminDeviceResetWarning    OBJECT IDENTIFIER
    ::= { xcmHrAdminDeviceOperationTypes 3 }
xcmHrAdminDeviceTest            OBJECT IDENTIFIER
    ::= { xcmHrAdminDeviceOperationTypes 4 }
xcmHrAdminDeviceShutdown        OBJECT IDENTIFIER
    ::= { xcmHrAdminDeviceOperationTypes 5 }
xcmHrAdminDeviceQuiesce         OBJECT IDENTIFIER
    ::= { xcmHrAdminDeviceOperationTypes 6 }
xcmHrAdminDeviceResetCounters   OBJECT IDENTIFIER
    ::= { xcmHrAdminDeviceOperationTypes 7 }
xcmHrAdminDeviceResetWarm       OBJECT IDENTIFIER
    ::= { xcmHrAdminDeviceOperationTypes 8 }
xcmHrAdminDeviceResetCold       OBJECT IDENTIFIER
    ::= { xcmHrAdminDeviceOperationTypes 9 }
xcmHrAdminDeviceResetFactory    OBJECT IDENTIFIER
    ::= { xcmHrAdminDeviceOperationTypes 10 }
xcmHrAdminDeviceFlushInput      OBJECT IDENTIFIER
    ::= { xcmHrAdminDeviceOperationTypes 11 }
xcmHrAdminDeviceFlushOutput     OBJECT IDENTIFIER
    ::= { xcmHrAdminDeviceOperationTypes 12 }
xcmHrAdminDeviceFlushInOut      OBJECT IDENTIFIER
    ::= { xcmHrAdminDeviceOperationTypes 13 }
xcmHrAdminDeviceManage          OBJECT IDENTIFIER
    ::= { xcmHrAdminDeviceOperationTypes 14 }
xcmHrAdminDeviceRefresh         OBJECT IDENTIFIER
    ::= { xcmHrAdminDeviceOperationTypes 15 }
xcmHrAdminDeviceWarmUp          OBJECT IDENTIFIER
    ::= { xcmHrAdminDeviceOperationTypes 16 }
xcmHrAdminDeviceCoolDown        OBJECT IDENTIFIER
    ::= { xcmHrAdminDeviceOperationTypes 17 }
xcmHrAdminDeviceEnergySave      OBJECT IDENTIFIER
    ::= { xcmHrAdminDeviceOperationTypes 18 }
xcmHrAdminDeviceWakeUp          OBJECT IDENTIFIER
    ::= { xcmHrAdminDeviceOperationTypes 19 }
xcmHrAdminDevicePowerToReady    OBJECT IDENTIFIER
    ::= { xcmHrAdminDeviceOperationTypes 20 }
xcmHrAdminDevicePowerToStandby  OBJECT IDENTIFIER
    ::= { xcmHrAdminDeviceOperationTypes 21 }
xcmHrAdminDevicePowerToSleep    OBJECT IDENTIFIER
    ::= { xcmHrAdminDeviceOperationTypes 22 }
--
--
XcmHrDevCalendarDayOfWeek ::= TEXTUAL-CONVENTION
    STATUS      current
    DESCRIPTION
        "The day of week when the command specified in a conceptual
        row in the 'xcmHrDevCalendarTable' SHALL be invoked."
    SYNTAX      INTEGER {
        monday(1),
        tuesday(2),
        wednesday(3),
        thursday(4),
        friday(5),
        saturday(6),
        sunday(7),
        everyDay(8),                    
        businessOpenDay(9),             
        businessClosedDay(10),          
        businessHoliday(11)             
    }
XcmHrDevCalendarTimeOfDay ::= TEXTUAL-CONVENTION
    STATUS      current
    DESCRIPTION
        "The time of day when the command specified in a conceptual
        row in the 'xcmHrDevCalendarTable' SHALL be invoked, specified
        as hours (0..23) multiplied by 100, added to minutes (0..59),
        added to a constant bias of 10000 (avoids an index value of zero
        in 'xcmHrDevCalendarTimeOfDay')."
    SYNTAX      INTEGER (10000..12359)
XcmHrDevDetailType ::= TEXTUAL-CONVENTION
    STATUS      current
    DESCRIPTION
        "The type of the device detail information specified
        in this conceptual row in the 'xcmHrDevDetailTable'.
        Usage:  Conforming management stations and management agents
        SHALL implement specified semantics for device detail types."
--
--
--
--
--
--
--
--
--
--
--
--
--
--
--
--
--
--
--
--
--         "Embedded Fax Card Memory (Mb)")
--
--
--
--
--
--
--
--
--
--
--
--
--
--
--
--               "+" or "-"> <hours from UTC,  
    REFERENCE
        "See:   'xcmHrDevDetailUnitClass' and
                'xcmHrDevDetailUnit' for syntax of device detail."
    SYNTAX      INTEGER {
        other(1),
        unknown(2),
        deviceName(3),
        deviceAlias(4),
        deviceType(5),
        deviceDescription(6),
        deviceID(7),
        deviceTree(8),
        deviceContext(9),
        deviceManufacturer(10),
        deviceModel(11),
        deviceSerialNumber(12),
        deviceVendor(13),
        deviceVersion(14),
        deviceServiceByCustomer(15),
        deviceReplaceByCustomer(16),
        deviceServicePlanName(17),
        deviceServicePlanPassword(18),
        deviceReplaceByWarranty(19),
        deviceLifetimeUsage(20),
        deviceReorderLifetimeLimit(21),
        deviceWarningLifetimeLimit(22),
        deviceReplaceLifetimeLimit(23),
        deviceMaximumLifetimeLimit(24),
        deviceDaysUntilReorderMsg(25),
        deviceDaysUntilWarningMsg(26),
        deviceDaysUntilReplaceMsg(27),
        deviceDaysUntilMaximumMsg(28),
        deviceLifetimeMsgDisplay(29),
        deviceAccountingUsage(30),
        deviceReorderOnDate(31),
        deviceWarningOnDate(32),
        deviceReplaceOnDate(33),
        deviceMaximumOnDate(34),
        deviceLifetimeErrorCount(35),
        deviceLifetimeErrorLimit(36),
        deviceLifetimeWarningCount(37),
        deviceLifetimeWarningLimit(38),
        deviceTriggerDaysForReorder(41),
        deviceTriggerDaysForWarning(42),
        deviceTriggerDaysForReplace(43),
        deviceTriggerDaysForMaximum(44),
        deviceReorderMsgSentDate(51),
        deviceWarningMsgSentDate(52),
        deviceReplaceMsgSentDate(53),
        deviceMaximumMsgSentDate(54),
        deviceReorderToVendorDate(55),
        deviceReorderConfirmDate(56),
        deviceReplaceDate(57),
        deviceReplaceSystemUsage(58),
        deviceReplaceWithGeneric(59),
        deviceHelpName(60),
        deviceHelpAddress(61),
        deviceHelpDescription(62),
        deviceHelpLocation(63),
        deviceHelpURI(64),
        deviceTranslatorSupport(71),
        deviceTranslatorReady(72),
        deviceInitialValueJobSupport(73),
        deviceInitialValueDocSupport(74),
        deviceMultipleDocSupport(75),
        deviceCancelDocSupport(76),
        deviceForeignJobsVisible(77),
        deviceInitialValueJobDefault(78),
        deviceInitialValueDocDefault(79),
        deviceInputMaxSpeedTrafficUnit(80),
        deviceInputMaxSpeedTimeUnit(81),
        deviceInputMaxSpeed(82),
        deviceOutputMaxSpeedTrafficUnit(83),
        deviceOutputMaxSpeedTimeUnit(84),
        deviceOutputMaxSpeed(85),
        deviceFeedResolutionSupport(86),
        deviceXFeedResolutionSupport(87),
        deviceSchedulerSupport(88),
        deviceSchedulerReady(89),
        devicePhysicalNameSupport(90),
        devicePhysicalNameReady(91),
        deviceLogicalNameSupport(92),
        deviceLogicalNameReady(93),
        devicePhysicalIndexSupport(94),
        devicePhysicalIndexReady(95),
        deviceLogicalIndexSupport(96),
        deviceLogicalIndexReady(97),
        deviceJobServiceDeviceIndex(98),
        deviceJobHistoryDeviceIndex(99),
        deviceFontIndexSupport(100),
        deviceFontIndexReady(101),
        deviceResourceIndexSupport(102),
        deviceResourceIndexReady(103),
        devicePowerModeName(110),
        devicePowerModeType(111),
        devicePowerModeDescription(112),
        devicePowerModeSupport(113),
        devicePowerTimeUnit(114),
        devicePowerWarmerSupport(115),
        devicePowerCoolerSupport(116),
        devicePowerWarmerDelay(117),
        devicePowerWarmerDuration(118),
        devicePowerCoolerDelay(119),
        devicePowerCoolerDuration(120),
        devicePowerWarmerTrigger(121),
        devicePowerCoolerTrigger(122),
        deviceNextWarmerModeIndex(123),
        deviceNextCoolerModeIndex(124),
        deviceEnergyStarSuspendMode(125),
        deviceProcessorFrwID(130),
        deviceNetworkIfIndex(140),
        deviceDiskStorageAccess(160),
        deviceDiskStorageMedia(161),
        deviceDiskStorageRemovable(162),
        deviceDiskStorageCapacity(163),
        deviceMemorySize(170),
        deviceConfigurationSetting(180), 
        deviceTimezone(181),
        deviceJobIncompleteTimeout(191),
        deviceJobProgrammingTimeout(192),
        deviceJobHoldDeleteTimeout(193),
        deviceJobPauseResumeTimeout(194),
        deviceGuestJobPolicy(200),
        deviceAlienJobPolicy(201),
        deviceEventLogFullPolicy(202),
        deviceJobLogFullPolicy(203),
        deviceRequestLogFullPolicy(204),
        deviceUniversalProductCode(210),
        deviceModelName(211),
        deviceModelDescription(212),
        deviceModelNumber(213),
        deviceManufacturerURI(220),
        deviceModelURI(221),
        deviceServiceUsage(230),
        deviceDeltaServiceUsage(231),
        deviceRolloverValue(232),
        deviceCPMenuControl(235),
        deviceUsageWarningThreshold(240),
        deviceLifetimeAvgCoverage(250),
        deviceLifeRemainingPercent(251),
        deviceRemainingImpressions(252),
        deviceSuppliesClass(253),
        deviceSupplyUnit(254),
        deviceSuppliesMaxCapacity(255),
        deviceSuppliesCurrentLevel(256),
        deviceInstallDate(260),
        deviceStatus(270),
        deviceFaxCountry(280),
        deviceFaxDialType(281),
        deviceInstallationKeyCSVPrintSubmission(500),
        deviceFeatureInstallationKeyAvailability(501),
        deviceFeatureInstallationKeyDisablement(502),
        deviceFeatureInstallationKeyDate(503)
    }
XcmHrDevDetailUnitClass ::= TEXTUAL-CONVENTION
    STATUS      current
    DESCRIPTION
        "The value unit class of the device detail information specified
        in this conceptual row in the 'xcmHrDevDetailTable'.
        Usage:  Used to select a textual convention for specifying the
        units of this device detail value.
        Usage:  Some of the value unit class enumerations specify that
        the actual unit is REQUIRED to be selected in '...DetailUnit'
        and REQUIRE '...DetailValueString' contains a value in units
        (and are commented as such below).
        Usage:  Some of the value unit class enumerations specify the
        actual unit DIRECTLY and REQUIRE that '...DetailUnit' be zero
        and REQUIRE '...DetailValueString' contains a value in the
        named textual convention (or a bit-mask derived from it)
        (and are commented as such below).
        Usage:  Some of the value unit class enumerations specify that
        '...DetailValueString' SHALL contain a bit-mask which is
        formed via the bit-wise OR of '2**(n)', where (n) is each
        selected enumerated value in the named textual convention.
        (see 'xcmGenBaseSNMPDomainSupport' object in XCMI General MIB)."
    SYNTAX      INTEGER {
        other(1),
        unknown(2),
        classGenOptionValueSyntax(3),   
        classDateAndTime(4),            
        classHrDevCalendarDayOfWeek(5), 
        classHrDevCalendarTimeOfDay(6), 
        classHrDevMgmtCommandRequest(7),
        classHrDevPowerTimeUnit(8),     
        classHrDevTrafficUnit(9),       
        classRowPersistence(10),        
        classRowPersistenceMask(11),    
        classLogFullPolicy(12),         
        classLogFullPolicyMask(13),     
        classHrDevInfoStatus(14),       
        classHrDevInfoStatusMask(15),   
        classHrDevInfoXStatus(16),      
        classHrDpaState(17),            
        classHrDpaConditions(18),       
        classHrDpaAvailability(19),     
        classHrDpaObjectClassSupport(20), 
        classHrDpaJobValidateSupport(21), 
        classJMJobState(22),            
        classJMJobStateMask(23),        
        classSecGuestJobPolicy(24),     
        classSecGuestJobPolicyMask(25), 
        classSecPosixRights(26),        
        classSecPosixVerbs(27),         
        classSvcMonJobConfirmSupport(28), 
        classSvcMonAttachmentPDLSupport(29) 
    }
XcmHrDevInfoRealization ::= TEXTUAL-CONVENTION
    STATUS      current
    DESCRIPTION
        "An extended device type (or device 'realization'),
        used by system administrators and end users of this device.
        Usage:  The use of either 'other' or 'unknown' is uninformative
        and SHOULD be avoided by conforming implementations.
      * 'physical' - 'real' device installed on this managed system;
      * 'logical' - 'virtual' device configured on this managed system;
      * 'logicalAndPhysical' - 'combined' device (from ISO DPA ??)."
    REFERENCE
        "See:   'hrDeviceType' in the basic Device Group of the
        IETF Host Resources MIB (RFC 2790).
        See:    Section 9.4 'Printer Object attributes' of ISO DPA
        (Document Printing Application) ISO/IEC 10175 (Final Text, March
        1996) for a discussion of 'printer realizations' of 'physical',
        'logical', and 'logical-and-physical' types (the latter unique
        to DPA)."
    SYNTAX      INTEGER {
        other(1),                       
        unknown(2),                     
        physical(11),                   
        logical(12),                    
        logicalAndPhysical(13)          
    }
XcmHrDevInfoStatus ::= TEXTUAL-CONVENTION
    STATUS      current
    DESCRIPTION
        "The current operational state of the device
        described by this row of the table.  A value
        'unknown(1)' indicates that the current state of the
        device is unknown.  'running(2)' indicates that the
        device is up and running and that no unusual error
        conditions are known.  The 'warning(3)' state
        indicates that agent has been informed of an
        unusual error condition by the operational software
        (eg, a disk device driver) but that the device is
        still 'operational'.  An example would be a high
        number of soft errors on a disk.  A value of
        'testing(4)', indicates that the device is not
        available for use because it is in the testing
        state.  The state of 'down(5)' is used only when the
        agent has been informed that the device is not
        available for any use.
        Usage:  Conforming implementations SHALL NOT 'bubble up' status
        from 'physical' devices to associated 'logical' devices.  All
        devices SHALL report their own status ONLY.
        Usage:  Devices in the 'down' state SHOULD NOT be accepting new
        work (or still processing old work).  Devices in the 'running'
        state SHOULD be prepared to accept new work.
        Usage:  The use of the state 'unknown' is uninformative
        and SHOULD be avoided by conforming implementations.
        Usage:  This is a textual convention representation of the
        'hrDeviceStatus' enumeration in the IETF Host Resources MIB
        (RFC 2790), rewritten from SMIv1 style (RFCs 1155 and 1212) into
        SMIv2 style (RFCs 1902/2578, 1903/2579, and 1904/2580)."
    REFERENCE
        "See:   'hrDeviceStatus' in the basic Device Group of the
        IETF Host Resources MIB (RFC 2790).
        See:    'xcmHrDevInfoXStatus', 'xcmHrDevInfoConditions', and
        'xcmHrDevInfoXConditions' in the Host Resources Extensions MIB."
    SYNTAX      INTEGER {
        unknown(1),                     
        running(2),                     
        warning(3),                     
        testing(4),                     
        down(5)                         
    }
XcmHrDevInfoXStatus ::= TEXTUAL-CONVENTION
    STATUS      current
    DESCRIPTION
        "An extended device status, used by system administrators
        and end users of this device (here, read 'state' for 'status').
        Usage:  Conforming implementations SHALL NOT 'bubble up' status
        from 'physical' devices to associated 'logical' devices.  All
        devices SHALL report their own status ONLY.
        Usage:  Exactly one enumeration of extended device status
        SHALL be defined, with ranges for each basic device type (eg,
        'hrDevicePrinter').  The legal range for extended device status
        for a given device type (either defined by RFC 2790 or by this
        MIB) is found by multiplying the final arc of the the device
        type OID by 100 - the result is the device specific range base -
        the end of the device specific range is 99 larger.  These device
        specific extended device status values SHALL be reissued
        periodically in the 'XcmHrDevInfoXStatus' textual convention."
    REFERENCE
        "See:   Section 9.4.9 'Printer-state' of ISO DPA
        (Document Printing Application) ISO/IEC 10175 (Final Text,
        18 May 1995) for a discussion of the printer states used here.
        Note that the DPA state 'connecting-to-printer' has no meaning
        in the context of a 'physical' printer device, but only in the
        context of an intermediate DP-Server presenting a 'logical'
        printer device.
        See:    'hrPrinterStatus' and 'hrPrinterDetectedErrorState' in
        the IETF Host Resources MIB (RFC 2790) for related discussion.
        See:    'hrDeviceStatus' in the basic Device Group of the
        IETF Host Resources MIB (RFC 2790).
        See:    'xcmHrDevInfoConditions' and 'xcmHrDevInfoXConditions'
        in the Host Resources Extensions MIB."
    SYNTAX      INTEGER {
        commonNone(0),
        commonOther(1),
        commonUnknown(2),
        commonLast(99),
        otherNone(100),
        unknownNone(200),
        processorNone(300),
        networkNone(400),
        printerNone(500),               
        printerOther(501),              
        printerUnknown(502),            
        printerIdle(503),               
        printerPrinting(504),           
        printerNeedsAttention(505),     
        printerPaused(506),             
        printerShutdown(507),           
        printerJobStartWait(508),       
        printerJobEndWait(509),         
        printerNeedsKeyOperator(510),   
        printerJobPasswordWait(511),    
        printerTimedOut(512),           
        printerConnectingToPrinter(513),
        diskStorageNone(600),
        videoNone(1000),
        audioNone(1100),
        coprocessorNone(1200),
        keyboardNone(1300),
        modemNone(1400),
        parallelPortNone(1500),
        pointingNone(1600),
        serialPortNone(1700),
        tapeNone(1800),
        clockNone(1900),
        volatileMemoryNone(2000),
        nonVolatileMemoryNone(2100),
        hostSystemNone(10100),
        scannerNone(10200),
        copierNone(10300),
        faxNone(10400),
        mailboxNone(10500),
        markerNone(11100),
        finisherBFMNone(11200),
        finisherMFFNone(11300),
        finisherXIMNone(11400),
        finisher3rdPartyNone(11500),
        paymentInterfaceNone(11600),
        interposerNone(11700),
        internetFaxNone(11800),
        serverFaxNone(11900),
        embeddedFaxNone(12000),
 foreignInterfaceNone(12100),
        securityInterfaceNone(12200),
        accountingInterfaceNone(12300), 
        cruNone(20000),                 
        cruOther(20001),                
        cruUnknown(20002),              
        cruReady(20003),                
        cruReorder(20004),              
        cruReplace(20005),              
        cruFault(20006),                
        reserved(40000)                 
    }
XcmHrDevInfoConditions ::= TEXTUAL-CONVENTION
    STATUS      current
    DESCRIPTION
        "A relatively generic description of the current 'conditions'
        of this device, specified in a bit-mask.
              1 : startupInProgress             
              2 : resetWarningInProgresss       
              4 : testInProgress                
              8 : shutdownInProgress            
             16 : quiesceInProgress             
             32 : resetCountersInProgress       
             64 : resetWarmInProgress           
            128 : resetColdInProgress           
            256 : resetFactoryInProgress        
            512 : flushInputInProgress          
           1024 : flushOutputInProgress         
           2048 : flushInOutInProgress          
           4096 : manageInProgress              
        The above basic 'conditions' record the original intent of the
        current command, when it results in delayed state transitions
        before arriving at the 'target' state.  They augment the state
        information available from 'hrDeviceStatus'.
           8192 : warmUpDelayInProgress         
          16384 : warmUpCycleInProgress         
          32768 : readyMode                     
          65536 : coolDownDelayInProgress       
         131072 : coolDownCycleInProgress       
         262144 : standbyMode                   
         524288 : energySaveDelayInProgress     
        1048576 : energySaveCycleInProgress     
        2097152 : sleepMode                     
        4194304 : wakeUpDelayInProgress         
        8388608 : wakeUpCycleInProgress         
       16777216 : powerToReadyInProgress        
       33554432 : powerToStandbyInProgress      
       67108864 : powerToSleepInProgress        
        The above optional 'conditions' record the progress of device
        'warm up', 'cool down', 'energy save', and 'wake up' power mgmt
        cycles and also define the device 'readyMode', 'standbyMode',
        and 'sleepMode' qualifiers to the generic 'hrDeviceStatus' of
        'running(2)', 'warning(3)', or 'testing(4)' (but NOT 'down(5)').
        See the power management cycle feature support and feature time
        objects in the Device Power Group of the Host Resources Ext MIB.
        Usage:  It is desirable that the implementor report 'conditions'
        of all devices corresponding to conceptual rows in the
        'hrDeviceTable' as accurately as feasible.  'Conditions' occur
        within or across 'states' in a finite state machine (FSM)
        implementation of a device.  They represent both short term and
        long term conditions.
        Usage:  A device with 'hrDeviceStatus' of 'running(2)' might
        have 'xcmHrDevInfoConditions' of 'quiesceInProgress', indicating
        that the device will soon transition to 'hrDeviceStatus' of
        'down(5)'.
        Usage:  A multi-bit example of 'xcmHrDevInfoConditions' is
        'quiesceInProgress' concurrently with 'standbyMode', ie, the
        device has previously 'cooled down' and will soon transition
        from 'hrDeviceStatus' of 'running(2)' to 'down(5)'."
    REFERENCE
        "See:   'hrDeviceStatus' in the basic Device Group of the
        IETF Host Resources MIB (RFC 2790).
        See:    'xcmHrDevInfoXStatus' and 'xcmHrDevInfoXConditions'
        in the Host Resources Extensions MIB."
    SYNTAX      INTEGER (0..2147483647)  
XcmHrDevInfoXConditions ::= TEXTUAL-CONVENTION
    STATUS      current
    DESCRIPTION
        "A device specific description of the extended 'conditions'
        of this device, specified in a bit-mask.
        Usage:  For FUTURE expansion.
        Usage:  Exactly one bit mask of extended device conditions SHALL
        be defined for each basic device type (eg, 'hrDevicePrinter').
        These device specific extended device conditions values SHALL be
        reissued periodically in the 'XcmHrDevInfoXConditions' textual
        convention.  These device specific extended device conditions
        are mutually exclusive and 'overloaded' in the single reporting
        object 'xcmHrDevInfoXConditions'."
    REFERENCE
        "See:   'hrDeviceStatus' in the basic Device Group of the
        IETF Host Resources MIB (RFC 2790).
        See:    'xcmHrDevInfoXStatus' and 'xcmHrDevInfoConditions'
        in the Host Resources Extensions MIB."
    SYNTAX      INTEGER (0..2147483647)  
XcmHrDeviceStatusType ::= TEXTUAL-CONVENTION
    STATUS      current
    DESCRIPTION
        "Used to describe the device status.
        Usage: used in xcmHrDetailTable for supplies.
        Required because supplies are not in the
        hrDeviceTable and therefore hrDeviceStatus
        cannot be used.
        Modeled after hrDeviceStatus where 2=running, 
        3=warning and 5=down."
    SYNTAX      INTEGER {
        unknown(1),
        ok(2),
        supplyReorder(3), 
        supplyReplace(5),
 supplyMissing(6)
    }  
XcmHrDevMgmtCommandRequest ::= TEXTUAL-CONVENTION
    STATUS      current
    DESCRIPTION
        "A write of this type by an (authorized) management station
        invokes a command for this device.
        A read of this type always returns the command currently in
        progress or last completed.
        It is mandatory that a conforming management agent ensure that
        the contents of this object remain 'in bounds' - an undefined
        value SHALL be replaced by 'none' - ie, although rejected with
        error in the SetResponse PDU, this object SHALL NOT contain any
        such undefined value.  At system initialization, this object
        SHALL contain 'none'.
      * 'none' - NO action(s) SHALL be taken, except to clear
        '...CommandData' and set '...CommandStatus' to 'noError'.
      * 'test' or 'manage' - the associated '...CommandData' object
        SHOULD/SHALL be specified in the same SetRequest PDU.
      * all other commands - the associated '...CommandData' object
        MAY be specified in the same SetRequest PDU.
      * 'startup', 'resetWarm', 'resetCold', or 'resetFactory' - the
        final state SHALL be 'running' (after cycle completes) - the
        sequence of states SHOULD be 'down' -> 'testing' -> 'running' -
        the final power mode SHALL be 'ready'.
      * 'startup' - this device SHALL transition from the 'down' state
        to the 'running' state and 'ready' power mode.
      * 'resetWarning' - this device SHALL transition from the 'warning'
        state to the 'running' state (because a management station has
        acknowledged the management agent's previous warning).
      * 'test' - this device SHALL transition immediately (ie, without
        attempting graceful quiesce) to the 'testing' state; it is a
        local matter (ie, device specific) how this command is
        processed; however, '...CommandData' SHOULD be specified.
      * 'shutdown' - this device SHALL transition immediately (ie,
        without attempting graceful quiesce) to the 'down' state and
        'off' power mode.
      * 'quiesce' - this device MAY transition gracefully to the 'down'
        state, or it MAY choose to treat a 'quiesce' as 'shutdown'.
      * 'resetCounters' - all device counters SHALL be reset to zero and
        the device SHALL remain in the same state and power mode.
      * 'resetWarm' - a device 'warm restart' SHALL be performed (ie,
        without a power cycle reset).
      * 'resetCold' - a device 'cold restart' SHALL be performed (ie,
        with a power cycle reset).
      * 'resetFactory' - all factory defaults SHALL be restored, and a
        device 'cold restart' SHALL be performed (ie, with a power cycle
        reset).
      * 'flushInput' - all device input (in progress or internally
        queued) SHALL be gracefully flushed.
      * 'flushOutput' - all device output (in progress or internally
        queued) SHALL be gracefully flushed.
      * 'flushInOut' - all device input and output output (in progress
        or internally queued) SHALL be gracefully flushed.
      * 'manage' - it is a local matter (ie, device specific) how this
        command is processed; however, '...CommandData' SHALL be
        specified.
      * 'refresh' - the device SHALL promptly read all of its manageable
        configuration parameters, but SHALL NOT perform a reset.
      * 'warmUp' - the device SHALL transition from the 'standby' mode
        to the 'ready' mode - invalid from any other power mode
        (optional command for remote device power management).
      * 'coolDown' - the device SHALL transition from the 'ready' mode
        to the 'standby' mode - invalid from any other power mode
        (optional command for remote device power management).
      * 'energySave' - the device SHALL transition from the 'standby'
        mode to the 'sleep' mode - invalid from any other power mode
        (optional command for remote device power management).
      * 'wakeUp' - the device SHALL transition from the 'sleep'
        mode to the 'standby' mode - invalid from any other power mode
        (optional command for remote device power management).
      * 'powerToReady' - the device SHALL transition from the 'standby'
        mode or the 'sleep' mode to the 'ready' mode
        (optional command for remote device power management).
      * 'powerToStandby' - the device SHALL transition from the 'ready'
        mode or the 'sleep' mode to the 'standby' mode
        (optional command for remote device power management).
      * 'powerToSleep' - the device SHALL transition from the 'ready'
        mode or the 'standby' mode to the 'sleep' mode
        (optional command for remote device power management).
        Note:   All of the POSIX and XCMI device level operations are
        taken from the POSIX System Admin std (IEEE 1387.4) and aligned
        with the high-end XCMI System Admin MIB."
    REFERENCE
        "See:   'dot5Commands' in IEEE 802.5 Token Ring MIB (RFC 1748)
        and 'hrDeviceStatus' in IETF Host Resources MIB (RFC 2790).
        Compare:    'ifOperStatus' (current) and 'ifAdminStatus'
        (desired) in the Interfaces Group of IETF MIB-II (RFC 1213);
        'RowStatus' textual convention in IETF SMIv2 (RFC 1902/2578).
        See:    Section 4 'Print Utilities' (pages 71 to 212) of
                POSIX Sys Admin (IEEE 1387.4 / Draft 8, October 1994).
        See:    OBJECT clause in MODULE-COMPLIANCE macro of
                XCMI Ext to Host Resources MIB, for compliance info.
        See:    Section 3.4 'XCMI Standard Tagged Management Data' and
                Section 3.5 'Simple Device Management Requests' in
                XCMI Ext to Host Resources TC.
        See:    Section 3.5.3 'Secure Simple Device Mgmt Requests' in
                XCMI Security TC."
    SYNTAX      INTEGER {
        none(1),                        
        startup(2),                     
        resetWarning(3),                
        test(4),                        
        shutdown(5),                    
        quiesce(6),                     
        resetCounters(7),               
        resetWarm(8),                   
        resetCold(9),                   
        resetFactory(10),               
        flushInput(11),                 
        flushOutput(12),                
        flushInOut(13),                 
        manage(14),                     
        refresh(15),                    
        warmUp(16),                     
        coolDown(17),                   
        energySave(18),                 
        wakeUp(19),                     
        powerToReady(20),               
        powerToStandby(21),             
        powerToSleep(22),               
        deviceCreate(1301),             
        deviceDelete(1302),             
        deviceList(1303),               
        deviceSet(1304),                
        deviceClean(1305),              
        deviceDisable(1306),            
        deviceEnable(1307),             
        devicePause(1308),              
        deviceResume(1309),             
        deviceShutdown(1310),           
        deviceQueueList(1311),          
        deviceJobCreate(1312),          
        deviceManage(2301),             
        deviceRestart(2302),            
        deviceInstall(2321),            
        deviceUpgrade(2322),            
        deviceBackup(2323),             
        deviceRestore(2324),            
        deviceConfigure(2325),          
        deviceDiagnose(2326),           
        deviceResetCounters(2331),      
        deviceResetWarm(2332),          
        deviceResetCold(2333),          
        deviceResetFactory(2334),       
        deviceFormat(2335),             
        deviceRefresh(2336),            
        deviceLogin(2341),              
        deviceLogout(2342),             
        deviceDiskOverwrite(2343),      
        entityCreate(1901),             
        entityDelete(1902),             
        entityList(1903),               
        entitySet(1904),                
        entityClean(1905),              
        entityDisable(1906),            
        entityEnable(1907),             
        entityPause(1908),              
        entityResume(1909),             
        entityShutdown(1910),           
        entityQueueList(1911),          
        entityJobCreate(1912),          
        entityManage(2901),             
        entityRestart(2902),            
        entityInstall(2921),            
        entityUpgrade(2922),            
        entityBackup(2923),             
        entityRestore(2924),            
        entityConfigure(2925),          
        entityDiagnose(2926),           
        entityResetCounters(2931),      
        entityResetWarm(2932),          
        entityResetCold(2933),          
        entityResetFactory(2934),       
        entityFormat(2935),             
        entityRefresh(2936),            
        entityLogin(2941),              
        entityLogout(2942)              
    }
XcmHrDevMgmtCommandData ::= TEXTUAL-CONVENTION
    STATUS      current
    DESCRIPTION
        "A write of this type specifies:  a) a 'test' command subtype
        and any accompanying 'test' device specific data; or b) a
        'manage' command subtype and any accompanying 'manage' device
        specific data; or c) device specific data accompanying any
        other command.
        A read of this type always returns the data (if any) which
        accompanied the current or last completed command."
    REFERENCE
        "See:   Section 4 'Print Utilities' (pages 71 to 212) of
                POSIX Sys Admin (IEEE 1387.4 / Draft 8, October 1994).
        See:    'hrDeviceStatus' in the Device group of the
                IETF Host Resources MIB (RFC 2790).
        See:    Section 3.4 'XCMI Standard Tagged Management Data' and
                Section 3.5 'Simple Device Management Requests' in
                XCMI Ext to Host Resources TC.
        See:    Section 3.5.3 'Secure Simple Device Mgmt Requests' in
                XCMI Security TC."
    SYNTAX      OCTET STRING (SIZE (0..255))
XcmHrDevMgmtCommandDataTag ::= TEXTUAL-CONVENTION
    STATUS      current
    DESCRIPTION
        "XCMI device management commands are passed as enumerated types
        in 'xcmHrDevMgmtCommandRequest' in the XCMI HRX MIB.
        Other XCMI management commands are passed as enumerated types in
        'xcmCommsMgmtCommandRequest', 'xcmSimpleJobMgmtOperation', etc,
        in the XCMI Comms Engine, Simple Job Mgmt, and other MIBs.
        XCMI management commands MAY also require one or more arguments
        (in addition to any specific variable bindings of MIB objects).
        Required arguments are passed as 'tagged string arguments' in
        'xcmHrDevMgmtCommandData', 'xcmSimpleJobMgmtData', etc.
        Each 'tagged string argument' substring is of the form:
            'TT=value:'
        where:
            'TT'        two-character 'tag', naming argument type
            '='         literal equal sign, beginning argument value
            'value'     human-readable string, encoding argument value
            ':'         literal colon, terminating argument value
        XCMI conforming management stations SHALL terminate ALL
        'tagged string argument' substrings properly with colon (':').
        XCMI standard 'tagged string arguments' MAY pass colon (':')
        in their 'value' by escaping it with backslash ('\').  XCMI
        conforming management agents SHALL interpret backslash
        followed by ANY other character as the literal value of the
        second character (ie, backslash is permitted, and is NOT
        restricted to certain following characters).
        XCMI standard 'tags' for data in 'tagged string arguments',
        (in 'xcmHrDevMgmtCommandData', 'xcmSimpleJobMgmtData', etc)
        are as follows:
      * SC  [Sub-Command - domain-specific, must be FIRST tag present]
      * OI  [Object Identifier - no object mapping]
      * OV  [Object Value - no object mapping]
      * DT  [Date and Time - no object mapping]
      * NI  [Noise Information - no object mapping]
      * SI  [Sequence Identifier - no object mapping]
      * AI  'xcmSecAccountIndex'
      * AN  'xcmSecAccountName'
      * AC  'xcmSecAccountPasscode'
      * AW  'xcmSecAccountPassword'
      * UI  'xcmSecUserIndex'
      * UN  'xcmSecUserName'
      * UC  'xcmSecUserPasscode'
      * UW  'xcmSecUserPassword'
      * ZD  'sysDescr'
      * ZI  'sysObjectID'
      * ZS  'sysServices'
      * IX  'ifIndex'
      * ID  'ifDescr'
      * IY  'ifType'
      * IM  'ifMtu'
      * IS  'ifSpeed'
      * IP  'ifPhysAddress'
      * IZ  'ifSpecific'
      * ZA  'hrSystemDate'
      * ZL  'hrSystemInitialLoadDevice'
      * ZP  'hrSystemInitialLoadParameters'
      * ZM  'hrSystemMaxProcesses'
      * SX  'hrStorageIndex'
      * SY  'hrStorageType'
      * SD  'hrStorageDescr'
      * SU  'hrStorageAllocationUnits'
      * SS  'hrStorageSize'
      * DX  'hrDeviceIndex'
      * DY  'hrDeviceType'
      * DD  'hrDeviceDescr'
      * DI  'hrDeviceID'
      * PI  'hrProcessorFrwID'
      * NI  'hrNetworkIfIndex'
      * KA  'hrDiskStorageAccess'
      * KM  'hrDiskStorageMedia'
      * KR  'hrDiskStorageRemoveble'
      * KC  'hrDiskStorageCapacity'
      * XX  'hrPartitionIndex'
      * XL  'hrPartitionLabel'
      * XI  'hrPartitionID'
      * XS  'hrPartitionSize'
      * XF  'hrPartitionFSIndex'
      * FX  'hrFSIndex'
      * FM  'hrFSMountPoint'
      * FR  'hrFSRemoteMountPoint'
      * FY  'hrFSType'
      * FA  'hrFSAccess'
      * FB  'hrFSBootable'
      * FS  'hrFSStorageIndex'
      * RO  'hrSWOSIndex'
      * RX  'hrSWRunIndex'
      * RN  'hrSWRunName'
      * RI  'hrSWRunID'
      * RF  'hrSWRunPath'
      * RP  'hrSWRunParameters'
      * RY  'hrSWRunType'
      * WX  'hrSWInstalledIndex'
      * WN  'hrSWInstalledName'
      * WI  'hrSWInstalledID'
      * WY  'hrSWInstalledType'
      * CN  [Color Name - no object mapping]
      * CV  [Color Value - no object mapping]
      * CO  [Community Name Ordinal - no direct object mapping]
      * CR  'xcmGenBaseSNMPReadCommunity'
      * CW  'xcmGenBaseSNMPWriteCommunity'
      * CT  'xcmGenBaseSNMPTrapCommunity'
      * JA  'xcmJobSubmittingApplication'
      * JC  'xcmJobClientId'
      * JD  'xcmDocName'
      * JF  'xcmDocFileName'
      * JH  'jobHoldSet' in 'xcmJobStateReasons'
      * JM  'xcmJobMessageFromAdministrator'
      * JN  'xcmJobName'
      * JO  'xcmJobOwner'
      * JP  'xcmJobPriority'
      * JR  'xcmJobRetentionPeriod'
      * JS  'xcmJobServiceType'
      * JT  'xcmJobProcessAfter'
      * JU  'xcmJobComment'
      * JW  ['system job' standard type - no object mapping]
      * JX  ['system job' extended type - no object mapping]
        XCMI standard 'system job' types for use in 'JW' arguments
        (in 'xcmHrDevMgmtCommandData' and 'xcmSimpleJobMgmtData') and
        for the value of 'xcmJobName' (unless 'JN' tag is specified)
        are as follows:
      * ACCT    (basic) accounting report
      * AEXT    (extended) accounting report
      * CONF    (basic) system configuration report
      * CEXT    (extended) system configuration report
      * CMEM    (installed) memory configuration report
      * CMSR    media (supported and ready) configuration report
      * CNET    network interfaces configuration report
      * COPT    (installed) optional devices configuration report
      * CPDL    (JCL and/or PDL) interpreters configuration report
      * CPRO    network protocols configuration report
      * CSWI    (installed) software configuration report
      * DEMO    (basic) demo job
      * DEXT    (extended) demo job
      * FONT    (basic) fonts report
      * FEXT    (extended) fonts report
      * FPCL    (installed) HP PCL fonts report
      * FPSX    (installed) Adobe PostScript fonts report
      * LIST    list tree of disk directories (but NOT contents)
      * LALL    list tree of disk directories (including all files)
      * LDIR    list (specific) disk directory
      * LERR    list system error file
      * LLOG    list system log file
      * LFIL    list (specific) file
      * MENU    (basic) local UI menu tree report
      * MEXT    (extended) local UI menu tree report
      * RSRC    (basic) document resources report
      * REXT    (extended) document resources report
      * TEST    (basic) system test
      * TEXT    (extended) system test
      * TMEM    (installed) memory verfication test report
      * TNET    network interfaces verification test report
      * TOPT    (installed) optional devices test report
      * TPAT    print test pattern (especially for printers and copiers)
      * TPDL    (JCL and/or PDL) interpreters system test report
      * TPRO    network protocols verification test report
      * TSWI    (installed) software verfication test report
      * TCAC    print automatic color chart (auto calibration)
      * TCBC    print balance chart (manual calibration)
      * TCCC    print corrected color chart (color calibration)
      * TCSC    scan automatic color chart (auto calibration)
      * TCTC    print tone chart (manual calibration)
      * TCUC    print uncorrected color chart (color calibration)
      * TCBV    set balance values (manual calibration)
      * TCTV    set tone values (manual calibration)
      * USER    (basic) configured users report
      * UEXT    (extended) configured users report
        The above XCMI standard 'tags' MAY be extended in the future."
    REFERENCE
        "See:   Section 4 'Print Utilities' (pages 71 to 212) of
                POSIX Sys Admin (IEEE 1387.4 / Draft 8, October 1994).
        See:    'hrDeviceStatus' in the Device group of the
                IETF Host Resources MIB (RFC 2790).
        See:    Section 3.4 'XCMI Standard Tagged Management Data' and
                Section 3.5 'Simple Device Management Requests' in
                XCMI Ext to Host Resources TC.
        See:    Section 3.5.3 'Secure Simple Device Mgmt Requests' in
                XCMI Security TC."
    SYNTAX      OCTET STRING (SIZE (2))
XcmHrDevPowerModeType ::= TEXTUAL-CONVENTION
    STATUS      current
    DESCRIPTION
        "A device power mode type, used by system administrators
        of this device for power management details.
        Usage:  Used in 'devicePowerModeType' Device Detail, to clearly
        identify the referenced power mode (without resort to strings)."
    SYNTAX      INTEGER {
        other(1),                       
        unknown(2),                     
        readyMode(3),                   
        standbyMode(4),                 
        sleepMode(5),                   
        offMode(6)                      
    }
XcmHrDevPowerTimeUnit ::= TEXTUAL-CONVENTION
    STATUS      current
    DESCRIPTION
        "A device power cycle time unit, used by system administrators
        of this device for power management cycle times.
        Usage:  Used to scale the values in the Device Power group, for
        convenience and (optional) high resolution."
    SYNTAX      INTEGER {
        other(1),                       
        unknown(2),                     
        microsecond(3),                 
        millisecond(4),                 
        second(5),                      
        kilosecond(6),                  
        megasecond(7),                  
        minute(8),                      
        hour(9),                        
        day(10),                        
        week(11),                       
        month(12),                      
        year(13)                        
    }
XcmHrDevTrafficUnit ::= TEXTUAL-CONVENTION
    STATUS      current
    DESCRIPTION
        "The type of traffic unit used to measure input and/or output
        traffic for this device.
        Usage:  The use of either 'other' or 'unknown' is uninformative
        and SHOULD be avoided by conforming implementations.
        Usage:  'mediaImage' - SHOULD be used ONLY for softcopy
                INPUT page images (scan, copy, fax, etc.).
                'mediaImpression' - SHOULD be used ONLY for hardcopy
                OUTPUT page impressions (print, copy, fax, etc.)
                'mediaSheet' - SHOULD be used ONLY for hardcopy
                OUTPUT and does NOT always equal output pages
                (e.g., duplex or N-up printing)."
    SYNTAX      INTEGER {
        other(1),                       
        unknown(2),                     
        binaryBit(11),                  
        binaryNibble(12),               
        binaryOctet(13),                
        binaryLine(14),                 
        textCharacter(15),              
        textWord(16),                   
        textLine(17),                   
        textSentence(18),               
        textParagraph(19),              
        mediaBlock(20),                 
        mediaSector(21),                
        mediaRow(22),                   
        mediaColumn(23),                
        mediaPacket(24),                
        mediaCell(25),                  
        mediaImage(26),                 
        mediaImpression(27),            
        mediaSheet(28),                 
        lengthInch(29),                 
        lengthFoot(30),                 
        lengthYard(31),                 
        lengthMile(32),                 
        lengthMicrometer(33),           
        lengthMillimeter(34),           
        lengthCentimeter(35),           
        lengthMeter(36),                
        lengthKilometer(37),            
        volumeMicroliter(38),           
        volumeMilliliter(39),           
        volumeLiter(40),                
        volumeKiloliter(41),            
        weightMicrogram(42),            
        weightMilligram(43),            
        weightGram(44),                 
        weightKilogram(45),             
        areaSqInch(50),                 
        areaSqFoot(51),                 
        areaSqYard(52),                 
        areaSqMile(53),                 
        areaSqMicrometer(54),           
        areaSqMillimeter(55),           
        areaSqCentimeter(56),           
        areaSqMeter(57),                
        areaSqKilometer(58),            
        areaSheet(59),                  -- Area in "sheets" 
        media100Image(60),              
        media100Impression(61),         
        media100Sheet(62),              
        length100Foot(63),              
        length100Meter(64),             
        area100SqFoot(65),              
        area10SqMeter(66),              
        area100Sheet(67),               
        document(68),                   
--      The area of a "sheet" is defined as the area in square meters 
        inkStick(100),                   
        totalItemsConsumed(101) 
    }
XcmHrGroupSupport ::= TEXTUAL-CONVENTION
    STATUS      current
    DESCRIPTION
        "The terse conformance statement of ALL mandatory, conditionally
        mandatory, and optional IETF Host Resources MIB (RFC 2790)
        and XCMI Ext to Host Resources MIB objects which are
        supported by this management agent implementation (ie, version)
        on this host system, specified in a bit-mask.
        The current set of values (which MAY be extended in the future)
        is given below:
              1 : hrSystemGroup                 
              2 : hrStorageGroup                
              4 : hrDeviceGroup                 
              8 : hrSWRunGroup                  
             16 : hrSWRunPerfGroup              
             32 : hrSWInstalledGroup            
             64 : xcmHrDevInfoGroup             
            128 : xcmHrDevHelpGroup             
            256 : xcmHrDevMgmtGroup             
            512 : xcmHrDevPowerGroup            
           1024 : xcmHrDevTrafficGroup          
           2048 : xcmHrSystemFaultGroup         
           4096 : xcmHrGeneralGroup             
           8192 : xcmHrDevCalendarGroup         
          16384 : xcmHrSWRunGroup               
          32768 : xcmHrSWInstalledGroup         
          65536 : xcmHrDevDetailGroup           
         131072 : xcmHrStorageExtGroup          
         262144 : xcmHrStorageDetailGroup       
         524288 : xcmHrDevCoverGroup            
        1048576 : xcmHrDevAlertGroup            
        2097152 : xcmHrConsoleScreenGroup       
        4194304 : xcmHrConsoleTabGroup          
       33554432 : hrProcessorTable              
       67108864 : hrNetworkTable                
      134217728 : hrPrinterTable                
      268435456 : hrDiskStorageTable            
      536870912 : hrPartitionTable              
     1073741824 : hrFSTable                     
        Usage:  Conforming management agents SHALL accurately
        report their support for IETF Host Resources MIB (RFC 2790)
        and XCMI Ext to Host Resources MIB object groups."
    SYNTAX      INTEGER (0..2147483647)  
XcmHrSWRunXStatus ::= TEXTUAL-CONVENTION
    STATUS      current
    DESCRIPTION
        "An extended software status, used by system administrators and
        end users of this software (here, read 'state' for 'status').
        Note:   This extended software status is present for future
        extensions."
    REFERENCE
        "See:   'hrSWRunStatus' in the basic Software Running Group
        of the IETF Host Resources MIB (RFC 2790)."
    SYNTAX      INTEGER {
        none(0),
        other(1),
        unknown(2)
    }
XcmHrStorageDetailType ::= TEXTUAL-CONVENTION
    STATUS      current
    DESCRIPTION
        "The type of the storage detail information specified
        in this conceptual row in the 'xcmHrStorageDetailTable'.
        Usage:  Used to describe system-, program-, or thread-level
        memory allocations/reservations.
        Usage:  'hrStorageEntry' and (optionally) 'xcmHrStorageEntry'
        MAY be referenced via 'xcmSecServiceHrStorageIndex' in the
        Service group of the XCMI Security MIB.
        Usage:  Conforming management stations and management agents
        SHALL implement specified semantics for storage detail types."
--
--
--
--
--
    REFERENCE
        "See:   'xcmHrStorageDetailUnit' for units of storage detail."
    SYNTAX      INTEGER {
        other(1),
        unknown(2),
        storageName(3),                 
        storageAlias(4),                
        storageType(5),                 
        storageDescription(6),          
        storageAllocationUnits(7),      
        storageTree(8),                 
        storageContext(9),              
        storageInputBuffer(10),         
        storageOutputBuffer(11),        
        storageImageBuffer(12),         
        storageMarkerBuffer(13),        
        storagePageBuffer(14),          
        storageTranslationBuffer(15),   
        storageWorkingBuffer(16),       
        storageFontCache(20),           
        storageFormCache(21),           
        storageLogoCache(22),           
        storageMacroCache(23),          
        storageStyleCache(24),          
        storageHeapMemory(30),          
        storagePrefixMemory(31),        
        storageStackMemory(32),         
        storageWorkingMemory(33),       
        storageBaseAddress(40),         
        storageWordSize(41),            
        storagePageSize(42)             
    }
XcmHrStorageRealization ::= TEXTUAL-CONVENTION
    STATUS      current
    DESCRIPTION
        "An extended storage type (or storage 'realization'),
        used by system administrators and end users of this storage.
        Usage:  The use of either 'other' or 'unknown' is uninformative
        and SHOULD be avoided by conforming implementations.
      * 'physicalSystem' - 'real' memory installed on a 'system'
        whose product is found via 'xcmHrStorageProductDeviceIndex' and
        whose CPU is found via 'xcmHrStoragePlatformDeviceIndex' and
        whose self is found via 'xcmHrStorageMatchingDeviceIndex';
      * 'physicalProgram' - 'real' memory assigned to a 'program'
        (memory which is 'pinned' and is NOT paged to disk storage)
        whose program is found via 'xcmHrStorageSWRunIndex';
      * 'physicalThread' - 'real' memory assigned to a 'thread'
        (memory which is 'pinned' and is NOT paged to disk storage)
        whose program/thread is found via 'xcmHrStorageSWRunIndex';
      * 'logicalSystem' - 'virtual' memory assigned to a 'system'
        (memory which is NOT 'pinned' and MAY be paged to disk storage)
        whose product is found via 'xcmHrStorageProductDeviceIndex' and
        whose CPU is found via 'xcmHrStoragePlatformDeviceIndex' and
        whose self is found via 'xcmHrStorageMatchingDeviceIndex';
      * 'logicalProgram' - 'virtual' memory assigned to a 'program'
        (memory which is NOT 'pinned' and MAY be paged to disk storage)
        whose program is found via 'xcmHrStorageSWRunIndex';
      * 'logicalThread' - 'virtual' memory assigned to a 'thread'
        (memory which is NOT 'pinned' and MAY be paged to disk storage)
        whose program/thread is found via 'xcmHrStorageSWRunIndex'."
    REFERENCE
        "See:   'XcmHrDevInfoRealization' textual convention in
                the XCMI Ext to Host Resources TC.
        See:    'xcmHrDevInfoRealization' in the Device Info group of
                the XCMI Ext to Host Resources MIB."
    SYNTAX      INTEGER {
        other(1),                       
        unknown(2),                     
        physicalSystem(10),             
        physicalProgram(11),            
        physicalThread(12),             
        logicalSystem(20),              
        logicalProgram(21),             
        logicalThread(22)               
    }
XcmHrDpaAvailability ::= TEXTUAL-CONVENTION
    STATUS      current
    DESCRIPTION
        "The generic availability of this system, device, service, etc."
    REFERENCE
        "See:   Section 9.1.6.6 '[Generic attribute] Availability' and
                Annex A 'id-val-availability-...'
                in DPA (ISO/IEC 10175-1 Final Text, March 1996)."
    SYNTAX      INTEGER {
        high(1),
        normal(2),
        low(3),
        none(5),
        unknown(6)
    }
XcmHrDpaConditions ::= TEXTUAL-CONVENTION
    STATUS      current
    DESCRIPTION
        "The generic conditions (ie, state reasons) of this system,
        device, service, etc, specified in a bit-mask.
              1 : cleanedByOperator             
              2 : cleanedBySystem               
              4 : disabledByOperator            
              8 : disabledBySystem              
             16 : pausedByOperator              
             32 : pausedBySystem                
             64 : shutdownByOperator            
            128 : shutdownBySystem              
            256 : diagnosedByOperator           
            512 : diagnosedBySystem             
           1024 : resetByOperator               
           2048 : resetBySystem                 
           4096 : startedByOperator             
           8192 : startedBySystem               
          65536 : activeCopy                    
         131072 : activePrint                   
         262144 : activeScan                    
         524288 : activeFaxReceive              
        1048576 : activeFaxSend                 
        2097152 : activeFileReceive             
        4194304 : activeFileSend                
        8388608 : activeMailReceive             
       16777216 : activeMailSend                
       33554432 : activeImageProcess            
       67108864 : activeOCR                     
      134217728 : activeDistribute              
        Usage:  The above 'conditions' augment the service state in
        'xcmSvcMonService[Current|Previous]State' and the service mgmt
        information in 'xcmSvcMonServiceMgmt[Operation|InProgress]'.
        Usage:  Conforming management agents SHALL report all
        'conditions' of entities accurately.  'Conditions' occur within
        or across 'states' in a finite state machine implementation of a
        system, device, service, etc.
        Usage:  A service with 'xcmSvcMonServiceCurrentState' of
        'ready(1)' might have 'xcmSvcMonServiceConditions' of
        'disabledByOperator', indicating that the service will not
        accept new jobs.
        Usage:  Multi-bit examples of 'xcmSvcMonServiceConditions' are
        'disabledByOperator' concurrently with 'pausedByOperator' and
        'activePrint' concurrently with 'activeMailSend'."
    REFERENCE
        "See:   Section 9.5.4 'Server-state',
                section 9.1.6.4 '[Generic attribute] State', and
                Annex A 'id-val-state-...'
                in DPA (ISO/IEC 10175-1 Final Text, March 1996).
        See:    Section D.2.3 'Server State Transitions'
                in DPA Mgmt Service (ISO 10175-3 Draft, October 1996).
        See:    Section 4 'Printing Utilities - Command Line Interface'
                in POSIX DPA Client (IEEE 1387.4, October 1994)."
    SYNTAX      INTEGER (0..2147483647)  
XcmHrDpaJobValidateSupport ::= TEXTUAL-CONVENTION
    STATUS      current
    DESCRIPTION
        "The job validation support of this system, service, etc,
        specified in a bit-mask.
        The current set of values (which MAY be extended in the future)
        is given below:
              1 : validateAndProcess    
              2 : validateSubmitOnly    
              4 : validateSyntaxOnly    
              8 : validateSemanticsOnly 
             16 : validateLocalOnly     
             32 : validateDistributed   
             64 : validateCreateLocal   
            128 : validateCreateRemote  
        Usage:  Conforming management agents SHALL accurately
        report their support for job validation modes."
    REFERENCE
        "See:   Section 9.5.10 'Job-validates-supported' (server),
                section 9.2.4.12 'Job-validate' (job), and
                Annex A 'id-val-job-validate-...'
                in DPA (ISO/IEC 10175-1 Final Text, March 1996)."
    SYNTAX      INTEGER (0..2147483647)  
XcmHrDpaObjectClassSupport ::= TEXTUAL-CONVENTION
    STATUS      current
    DESCRIPTION
        "The object class support of this system, service, etc,
        specified in a bit-mask.
        The current set of values (which MAY be extended in the future)
        is given below:
              1 : generic                       
              2 : job                           
              4 : printer                       
              8 : server                        
             16 : medium                        
             32 : font                          
            256 : transferMethod                
            512 : deliveryMethod                
           1024 : auxiliarySheet                
           2048 : finishing                     
           4096 : output                        
           8192 : imposition                    
          16384 : scheduler                     
          32768 : document                      
          65536 : resource                      
         131072 : initialValueJob               
         262144 : initialValueDocument          
         524288 : resourceContext               
        1048576 : auxiliarySheetPackage         
       16777216 : deviceHostSystem              
       33554432 : deviceScanner                 
       67108864 : deviceCopier                  
      134217728 : deviceFax                     
      268435456 : deviceMailbox                 
      536870912 : deviceFinisher                
     1073741824 : deviceCRU                     
        Usage:  Conforming management agents SHALL accurately
        report their support for object classes (ISO DPA and XCMI)."
    REFERENCE
        "See:   Section 9.5.5 'Object-classes-supported' (server),
                section 9.1.6.1 'Object-class' (system),
                Annex A 'id-oc-...'
                in DPA (ISO/IEC 10175-1 Final Text, March 1996)."
    SYNTAX      INTEGER (0..2147483647)  
XcmHrDpaState ::= TEXTUAL-CONVENTION
    STATUS      current
    DESCRIPTION
        "The generic state of this object (system, device, service,
        etc.).  The following standard values are defined (in section
        9.1.6.4 'State' of ISO 10175-1):
      * 'ready' - This object is ready to be used without human
        intervention.
      * 'onRequest' - This object requires human intervention in order
        to be used.
      * 'unavailable' - This object is NOT available for use even with
        human intervention.
      * 'unknown' - This state of this object is NOT known.
      * 'busy' - This object is temporarily inaccessible due to dynamic
        constraints, but will become 'ready' without human intervention.
      * 'initializing' - This object is being initialized (and is
        therefore temporarily inaccessible).
      * 'terminating' - This object is being terminated (and is
        therefore permanently inaccessible)."
    REFERENCE
        "See:   Section 9.1.6.4 '[Generic attribute] State' and
                Annex A 'id-val-state-...'
                in DPA (ISO/IEC 10175-1 Final Text, March 1996)."
    SYNTAX      INTEGER {
        ready(1),
        onRequest(2),
        unavailable(3),
        unknown(4),
        busy(5),
        initializing(6),
        terminating(7)
    }
XcmHrSuppliesClassTC ::= TEXTUAL-CONVENTION
    STATUS    current
    DESCRIPTION
       "The type of a supply."
    SYNTAX    INTEGER {
       other(1),
       unknown(2),
       replenishable(3),     
       customerReplacable(4),
       serviceReplacable(5), 
       rarelyReplaced(6),    
       notReplacable(7)      
    }
XcmHrDetailTableEnumTC ::= TEXTUAL-CONVENTION
    STATUS    current
    DESCRIPTION
       "The table referenced by a row in the xcmHrDetail
       table.  Add additional tables as details are
       required."
    SYNTAX    INTEGER {
       suppliesTable(1),        
       markerSuppliesTable(2),  
       finisherSuppliesTable(3) 
    }
XcmHrConsoleDefaultService ::= TEXTUAL-CONVENTION
    STATUS      current
    DESCRIPTION
        "The default service shown on the console user interface."
    SYNTAX      INTEGER {
        copyService(1),
        scanService(2),
        faxService(3),
        printService(4)
    }
--
--
--
xCmHrDummy          OBJECT IDENTIFIER ::= { xcmHrTC 999 }
xCmHrDevCalendarDayOfWeek OBJECT-TYPE
    SYNTAX      XcmHrDevCalendarDayOfWeek
    MAX-ACCESS  not-accessible
    STATUS      current
    DESCRIPTION "Dummy - DO NOT USE"
    ::= { xCmHrDummy 1 }
xCmHrDevCalendarTimeOfDay OBJECT-TYPE
    SYNTAX      XcmHrDevCalendarTimeOfDay
    MAX-ACCESS  not-accessible
    STATUS      current
    DESCRIPTION "Dummy - DO NOT USE"
    ::= { xCmHrDummy 2 }
xCmHrDevDetailType OBJECT-TYPE
    SYNTAX      XcmHrDevDetailType
    MAX-ACCESS  not-accessible
    STATUS      current
    DESCRIPTION "Dummy - DO NOT USE"
    ::= { xCmHrDummy 3 }
xCmHrDevDetailUnitClass OBJECT-TYPE
    SYNTAX      XcmHrDevDetailUnitClass
    MAX-ACCESS  not-accessible
    STATUS      current
    DESCRIPTION "Dummy - DO NOT USE"
    ::= { xCmHrDummy 4 }
xCmHrDevInfoRealization OBJECT-TYPE
    SYNTAX      XcmHrDevInfoRealization
    MAX-ACCESS  not-accessible
    STATUS      current
    DESCRIPTION "Dummy - DO NOT USE"
    ::= { xCmHrDummy 5 }
xCmHrDevInfoStatus OBJECT-TYPE
    SYNTAX      XcmHrDevInfoStatus
    MAX-ACCESS  not-accessible
    STATUS      current
    DESCRIPTION "Dummy - DO NOT USE"
    ::= { xCmHrDummy 6 }
xCmHrDevInfoXStatus OBJECT-TYPE
    SYNTAX      XcmHrDevInfoXStatus
    MAX-ACCESS  not-accessible
    STATUS      current
    DESCRIPTION "Dummy - DO NOT USE"
    ::= { xCmHrDummy 7 }
xCmHrDevInfoConditions OBJECT-TYPE
    SYNTAX      XcmHrDevInfoConditions
    MAX-ACCESS  not-accessible
    STATUS      current
    DESCRIPTION "Dummy - DO NOT USE"
    ::= { xCmHrDummy 8 }
xCmHrDevInfoXConditions OBJECT-TYPE
    SYNTAX      XcmHrDevInfoXConditions
    MAX-ACCESS  not-accessible
    STATUS      current
    DESCRIPTION "Dummy - DO NOT USE"
    ::= { xCmHrDummy 9 }
xCmHrDevMgmtCommandRequest OBJECT-TYPE
    SYNTAX      XcmHrDevMgmtCommandRequest
    MAX-ACCESS  not-accessible
    STATUS      current
    DESCRIPTION "Dummy - DO NOT USE"
    ::= { xCmHrDummy 10 }
xCmHrDevMgmtCommandData OBJECT-TYPE
    SYNTAX      XcmHrDevMgmtCommandData
    MAX-ACCESS  not-accessible
    STATUS      current
    DESCRIPTION "Dummy - DO NOT USE"
    ::= { xCmHrDummy 11 }
xCmHrDevMgmtCommandDataTag OBJECT-TYPE
    SYNTAX      XcmHrDevMgmtCommandDataTag
    MAX-ACCESS  not-accessible
    STATUS      current
    DESCRIPTION "Dummy - DO NOT USE"
    ::= { xCmHrDummy 12 }
xCmHrDevPowerModeType OBJECT-TYPE
    SYNTAX      XcmHrDevPowerModeType
    MAX-ACCESS  not-accessible
    STATUS      current
    DESCRIPTION "Dummy - DO NOT USE"
    ::= { xCmHrDummy 13 }
xCmHrDevPowerTimeUnit OBJECT-TYPE
    SYNTAX      XcmHrDevPowerTimeUnit
    MAX-ACCESS  not-accessible
    STATUS      current
    DESCRIPTION "Dummy - DO NOT USE"
    ::= { xCmHrDummy 14 }
xCmHrDevTrafficUnit OBJECT-TYPE
    SYNTAX      XcmHrDevTrafficUnit
    MAX-ACCESS  not-accessible
    STATUS      current
    DESCRIPTION "Dummy - DO NOT USE"
    ::= { xCmHrDummy 15 }
xCmHrGroupSupport OBJECT-TYPE
    SYNTAX      XcmHrGroupSupport
    MAX-ACCESS  not-accessible
    STATUS      current
    DESCRIPTION "Dummy - DO NOT USE"
    ::= { xCmHrDummy 16 }
xCmHrSWRunXStatus OBJECT-TYPE
    SYNTAX      XcmHrSWRunXStatus
    MAX-ACCESS  not-accessible
    STATUS      current
    DESCRIPTION "Dummy - DO NOT USE"
    ::= { xCmHrDummy 17 }
xCmHrStorageDetailType OBJECT-TYPE
    SYNTAX      XcmHrStorageDetailType
    MAX-ACCESS  not-accessible
    STATUS      current
    DESCRIPTION "Dummy - DO NOT USE"
    ::= { xCmHrDummy 18 }
xCmHrStorageRealization OBJECT-TYPE
    SYNTAX      XcmHrStorageRealization
    MAX-ACCESS  not-accessible
    STATUS      current
    DESCRIPTION "Dummy - DO NOT USE"
    ::= { xCmHrDummy 19 }
xCmHrDpaAvailability OBJECT-TYPE
    SYNTAX      XcmHrDpaAvailability
    MAX-ACCESS  not-accessible
    STATUS      current
    DESCRIPTION "Dummy - DO NOT USE"
    ::= { xCmHrDummy 20 }
xCmHrDpaConditions OBJECT-TYPE
    SYNTAX      XcmHrDpaConditions
    MAX-ACCESS  not-accessible
    STATUS      current
    DESCRIPTION "Dummy - DO NOT USE"
    ::= { xCmHrDummy 21 }
xCmHrDpaJobValidateSupport OBJECT-TYPE
    SYNTAX      XcmHrDpaJobValidateSupport
    MAX-ACCESS  not-accessible
    STATUS      current
    DESCRIPTION "Dummy - DO NOT USE"
    ::= { xCmHrDummy 22 }
xCmHrDpaObjectClassSupport OBJECT-TYPE
    SYNTAX      XcmHrDpaObjectClassSupport
    MAX-ACCESS  not-accessible
    STATUS      current
    DESCRIPTION "Dummy - DO NOT USE"
    ::= { xCmHrDummy 23 }
xCmHrDpaState OBJECT-TYPE
    SYNTAX      XcmHrDpaState
    MAX-ACCESS  not-accessible
    STATUS      current
    DESCRIPTION "Dummy - DO NOT USE"
    ::= { xCmHrDummy 24 }
xCmHrDetailTableEnumTC OBJECT-TYPE
    SYNTAX      XcmHrDetailTableEnumTC
    MAX-ACCESS  not-accessible
    STATUS      current
    DESCRIPTION "Dummy - DO NOT USE"
    ::= { xCmHrDummy 25 }
xCmHrSuppliesClassTC OBJECT-TYPE
    SYNTAX      XcmHrSuppliesClassTC
    MAX-ACCESS  not-accessible
    STATUS      current
    DESCRIPTION "Dummy - DO NOT USE"
    ::= { xCmHrDummy 26 }
xCmHrConsoleDefaultService OBJECT-TYPE
    SYNTAX      XcmHrConsoleDefaultService
    MAX-ACCESS  not-accessible
    STATUS      current
    DESCRIPTION "Dummy - DO NOT USE"
    ::= { xCmHrDummy 27 }
xcmHrMIB OBJECT-IDENTITY -- MODULE-IDENTITY
    STATUS   current
    DESCRIPTION
        "Version:   5.602.pub
        The MIB module for extended configuration and management of
        various host resources for network accessible host systems.
        This module augments and extends the original IETF Host
        Resources MIB (RFC 2790).
        Usage:  This MIB module introduces support for the 'realization'
        of both 'physical' and 'logical' devices, consistent with the
        Document Printing Application (DPA), ISO/IEC 10175, as reflected
        in the object 'xcmHrDevInfoRealization'.
        Note:   Conforming implementations SHALL NOT 'bubble up' status
        from 'physical' devices to associated 'logical' devices.  All
        devices SHALL report their own status ONLY.
        See:    Section 9 'Supplement' in XCMI Extensions to IETF Host
        Resources TC, for implementation guidance for this MIB module.
        Copyright (C) 1995-2006 Xerox Corporation. All Rights Reserved."
    ::= { xeroxCommonMIB 53 }
xcmHrZeroDummy OBJECT IDENTIFIER ::= { zeroDotZero 53 }
--
--
--
xcmHrGeneral        OBJECT IDENTIFIER ::= { xcmHrMIB 9 }
xcmHrGeneralTable OBJECT-TYPE
    SYNTAX      SEQUENCE OF XcmHrGeneralEntry
    MAX-ACCESS  not-accessible
    STATUS      current
    DESCRIPTION
        "A table of general counters and information for ease of use of
        the XCMI Ext to IETF Host Resources MIB and the
        IETF Host Resources MIB (RFC 2790) on this host system.
        Usage:  The ONLY valid row in the 'xcmHrGeneralTable'
        SHALL have an 'xcmHrGeneralIndex' of one ('1')."
    ::= { xcmHrGeneral 2 }
xcmHrGeneralEntry OBJECT-TYPE
    SYNTAX      XcmHrGeneralEntry
    MAX-ACCESS  not-accessible
    STATUS      current
    DESCRIPTION
        "An entry of general counters and information for ease of use of
        the XCMI Ext to IETF Host Resources MIB and the
        IETF Host Resources MIB (RFC 2790) on this host system.
        Usage:  The ONLY valid row in the 'xcmHrGeneralTable'
        SHALL have an 'xcmHrGeneralIndex' of one ('1')."
    INDEX       { xcmHrGeneralIndex }
    ::= { xcmHrGeneralTable 1 }
XcmHrGeneralEntry ::= SEQUENCE {
        xcmHrGeneralIndex               Ordinal32,
        xcmHrGeneralRowStatus           RowStatus,
        xcmHrGeneralVersionID           ProductID,
        xcmHrGeneralVersionDate         DateAndTime,
        xcmHrGeneralGroupSupport        XcmHrGroupSupport,
        xcmHrGeneralStorageLast         Cardinal32,
        xcmHrGeneralDeviceLast          Cardinal32,
        xcmHrGeneralFSLast              Cardinal32,
        xcmHrGeneralSWRunLast           Cardinal32,
        xcmHrGeneralSWInstalledLast     Cardinal32,
        xcmHrGeneralSystemFaultLast     Cardinal32,
        xcmHrGeneralCreateSupport       XcmHrGroupSupport,
        xcmHrGeneralUpdateSupport       XcmHrGroupSupport 
    }
--
--
xcmHrGeneralIndex OBJECT-TYPE
    SYNTAX      Ordinal32
    MAX-ACCESS  not-accessible
    STATUS      current
    DESCRIPTION
        "A unique value used by this host system to identify this
        conceptual row in the 'xcmHrGeneralTable'.
        Usage:  The ONLY valid row in the 'xcmHrGeneralTable'
        SHALL have an 'xcmHrGeneralIndex' of one ('1')."
    ::= { xcmHrGeneralEntry 1 }
xcmHrGeneralRowStatus OBJECT-TYPE
    SYNTAX      RowStatus
    MAX-ACCESS  read-only
    STATUS      current
    DESCRIPTION
        "This object is used to display status of the ONLY valid
        conceptual row in the 'xcmHrGeneralTable'.
        Usage:  'xcmHrGeneralRowStatus' is 'read-only' because
        the ONLY valid conceptual row SHALL NOT be deleted."
    ::= { xcmHrGeneralEntry 2 }
xcmHrGeneralVersionID OBJECT-TYPE
    SYNTAX      ProductID
    MAX-ACCESS  read-only
    STATUS      current
    DESCRIPTION
        "The software product ID of the SNMP sub-agent which implements
        the IETF Host Resources MIB (RFC 2790) and XCMI Extensions to
        Host Resources MIB on this host system.
        Usage:  This object SHALL specify the software product ID of an
        SNMP sub-agent (possibly also found in a conceptual row in the
        'hrSWRunTable' and/or 'hrSWInstalledTable' in the IETF HR MIB).
        This object SHALL NOT specify a particular release of the IETF
        HR MIB, the XCMI HRX MIB, or the whole host system product.
        Note:   Contrast with 'sysObjectID' for the whole SNMP agent in
        the IETF MIB-II (RFC 1213) and 'hrDeviceID' for the whole device
        (or whole product, in the case of 'xcmHrDevice...') in the IETF
        Host Resources MIB (RFC 2790)."
    REFERENCE
        "See:   'hrSW[Installed|Run]ID' in the Software Installed and
                Software Running groups of the IETF HR MIB (RFC 2790)."
    DEFVAL      { zeroDotZero }   
    ::= { xcmHrGeneralEntry 3 }
xcmHrGeneralVersionDate OBJECT-TYPE
    SYNTAX      DateAndTime
    MAX-ACCESS  read-only
    STATUS      current
    DESCRIPTION
        "The software build date of the SNMP sub-agent which implements
        the IETF Host Resources MIB (RFC 2790) and XCMI Extensions to
        Host Resources MIB on this host system.
        Usage:  This object SHALL specify the BUILD date of the SNMP
        sub-agent software (not available elsewhere in IETF/XCMI MIBs).
        This object SHALL NOT specify the INSTALL date of the SNMP
        sub-agent software on this host system, nor the RESET date.
        Note:   Contrast with 'hrSWInstalledDate' in the Software
        Installed group of the IETF Host Resources MIB (RFC 2790), and
        'xcmHrDevInfoResetDate' in the Device Info group of the XCMI
        Host Resources Extensions MIB."
    REFERENCE
        "See:   'hrSW[Installed|Run]ID' in the Software Installed and
                Software Running groups of the IETF HR MIB (RFC 2790)."
    DEFVAL      { '0000000000000000'H } 
    ::= { xcmHrGeneralEntry 4 }
xcmHrGeneralGroupSupport OBJECT-TYPE
    SYNTAX      XcmHrGroupSupport
    MAX-ACCESS  read-only
    STATUS      current
    DESCRIPTION
        "The terse conformance statement of ALL mandatory, conditionally
        mandatory, and optional IETF Host Resources MIB (RFC 2790)
        and XCMI Ext to IETF Host Resources MIB objects which are
        supported by this management agent implementation (ie, version)
        on this host system, specified in a bit-mask.
        Usage:  Conforming management agents SHALL accurately
        report their support for IETF Host Resources MIB (RFC 2790)
        and XCMI Ext to IETF Host Resources MIB object groups."
    DEFVAL      { 71 }                  
    ::= { xcmHrGeneralEntry 5 }
xcmHrGeneralStorageLast OBJECT-TYPE
    SYNTAX      Cardinal32
    MAX-ACCESS  read-only
    STATUS      current
    DESCRIPTION
        "The last entry index (regardless of its current state) in
        the 'hrStorageTable' of the IETF Host Resources MIB,
        on this host system.
        Usage:  The last entry index explicitly bounds the valid range
        of 'hrStorageIndex'."
    DEFVAL      { 0 }                   
    ::= { xcmHrGeneralEntry 6 }
xcmHrGeneralDeviceLast OBJECT-TYPE
    SYNTAX      Cardinal32
    MAX-ACCESS  read-only
    STATUS      current
    DESCRIPTION
        "The last entry index (regardless of its current state) in
        the 'hrDeviceTable' of the IETF Host Resources MIB,
        on this host system.
        Usage:  The last entry index explicitly bounds the valid range
        of 'hrDeviceIndex'."
    DEFVAL      { 0 }                   
    ::= { xcmHrGeneralEntry 7 }
xcmHrGeneralFSLast OBJECT-TYPE
    SYNTAX      Cardinal32
    MAX-ACCESS  read-only
    STATUS      current
    DESCRIPTION
        "The last entry index (regardless of its current state) in
        the 'hrFSTable' of the IETF Host Resources MIB,
        on this host system.
        Usage:  The last entry index explicitly bounds the valid range
        of 'hrFSIndex'."
    DEFVAL      { 0 }                   
    ::= { xcmHrGeneralEntry 8 }
xcmHrGeneralSWRunLast OBJECT-TYPE
    SYNTAX      Cardinal32
    MAX-ACCESS  read-only
    STATUS      current
    DESCRIPTION
        "The last entry index (regardless of its current state) in
        the 'hrSWRunTable' of the IETF Host Resources MIB,
        on this host system.
        Usage:  The last entry index explicitly bounds the valid range
        of 'hrSWRunIndex'."
    DEFVAL      { 0 }                   
    ::= { xcmHrGeneralEntry 9 }
xcmHrGeneralSWInstalledLast OBJECT-TYPE
    SYNTAX      Cardinal32
    MAX-ACCESS  read-only
    STATUS      current
    DESCRIPTION
        "The last entry index (regardless of its current state) in
        the 'hrSWInstalledTable' of the IETF Host Resources MIB,
        on this host system.
        Usage:  The last entry index explicitly bounds the valid range
        of 'hrSWInstalledIndex'."
    DEFVAL      { 0 }                   
    ::= { xcmHrGeneralEntry 10 }
xcmHrGeneralSystemFaultLast OBJECT-TYPE
    SYNTAX      Cardinal32
    MAX-ACCESS  read-only
    STATUS      current
    DESCRIPTION
        "The last entry index (regardless of its current state) in
        the 'xcmHrSystemFaultTable' of this XCMI Ext to Host Resources
        MIB, on this host system.
        Usage:  The last entry index explicitly bounds the valid range
        of 'xcmHrSystemFaultIndex'."
    DEFVAL      { 0 }                   
    ::= { xcmHrGeneralEntry 11 }
xcmHrGeneralCreateSupport OBJECT-TYPE
    SYNTAX      XcmHrGroupSupport
    MAX-ACCESS  read-only
    STATUS      current
    DESCRIPTION
        "The terse conformance statement of ALL mandatory, conditionally
        mandatory, and optional IETF Host Resources MIB (RFC 2790)
        and XCMI Ext to IETF Host Resources MIB objects which are
        supported for dynamic row creation (via '...RowStatus')
        by this management agent implementation (ie, version)
        on this host system, specified in a bit-mask.
        Usage:  Conforming management agents SHALL accurately
        report their support for IETF Host Resources MIB (RFC 2790)
        and XCMI Ext to IETF Host Resources MIB object groups."
    DEFVAL      { 0 }                   
    ::= { xcmHrGeneralEntry 12 }
xcmHrGeneralUpdateSupport OBJECT-TYPE
    SYNTAX      XcmHrGroupSupport
    MAX-ACCESS  read-only
    STATUS      current
    DESCRIPTION
        "The terse conformance statement of ALL mandatory, conditionally
        mandatory, and optional IETF Host Resources MIB (RFC 2790)
        and XCMI Ext to IETF Host Resources MIB objects which are
        supported for existing row update (via SNMP Set-Request PDUs)
        by this management agent implementation (ie, version)
        on this host system, specified in a bit-mask.
        Usage:  Conforming management agents SHALL accurately
        report their support for IETF Host Resources MIB (RFC 2790)
        and XCMI Ext to IETF Host Resources MIB object groups."
    DEFVAL      { 0 }                   
    ::= { xcmHrGeneralEntry 13 }
--
xcmHrDevInfo        OBJECT IDENTIFIER ::= { xcmHrMIB 3 }
xcmHrDevInfoTable OBJECT-TYPE
    SYNTAX      SEQUENCE OF XcmHrDevInfoEntry
    MAX-ACCESS  not-accessible
    STATUS      current
    DESCRIPTION
        "A 'sparse' table containing device info objects for
        installed and (possibly) active devices on this host system,
        augmenting the basic entries in the 'hrDeviceTable' of the
        IETF Host Resources MIB (RFC 2790).
        Usage:  Although this group is Mandatory in this MIB module,
        this table is 'sparse' because conforming management agents
        need NOT implement an entry in 'xcmHrDevInfoTable' for ALL of
        the installed (and instrumented) devices in 'hrDeviceTable'.
        Usage:  Conforming management agents SHALL implement an
        entry in 'xcmHrDevInfoTable' for the following device types
        (if they are installed devices in 'hrDeviceTable'):
        'hrDevicePrinter' (from IETF Host Resource MIB, RFC 2790); and
        'xcmHrDeviceHostSystem', 'xcmHrDeviceScanner',
        'xcmHrDeviceCopier', 'xcmHrDeviceFax', and 'xcmHrDeviceMailbox'
        (from XCMI HRX TC)."
    ::= { xcmHrDevInfo 2 }
xcmHrDevInfoEntry OBJECT-TYPE
    SYNTAX      XcmHrDevInfoEntry
    MAX-ACCESS  not-accessible
    STATUS      current
    DESCRIPTION
        "A 'sparse' entry containing device info objects for
        an installed and (possibly) active device on this host system,
        augmenting a basic entry in the 'hrDeviceTable' of the
        IETF Host Resources MIB (RFC 2790)."
    INDEX       { hrDeviceIndex }
    ::= { xcmHrDevInfoTable 1 }
XcmHrDevInfoEntry ::= SEQUENCE {
        xcmHrDevInfoRowStatus           RowStatus,
        xcmHrDevInfoName                XcmFixedLocaleDisplayString,
        xcmHrDevInfoSerialNumber        XcmFixedLocaleDisplayString,
        xcmHrDevInfoRealization         XcmHrDevInfoRealization,
        xcmHrDevInfoXStatus             XcmHrDevInfoXStatus,
        xcmHrDevInfoConditions          XcmHrDevInfoConditions,
        xcmHrDevInfoXConditions         XcmHrDevInfoXConditions,
        xcmHrDevInfoInstallDate         DateAndTime,
        xcmHrDevInfoResetDate           DateAndTime,
        xcmHrDevInfoNextDeviceIndex     Cardinal32,
        xcmHrDevInfoPreviousDeviceIndex Cardinal32,
        xcmHrDevInfoPhysicalDeviceIndex Cardinal32,
        xcmHrDevInfoPriority            INTEGER (0..100),
        xcmHrDevInfoXeroxAssetTagNumber XcmFixedLocaleDisplayString,
        xcmHrDevInfoCustomerAssetNumber XcmFixedLocaleDisplayString,
        xcmHrDevInfoPagePackPIN         OCTET STRING,
        xcmHrDevInfoPagePackReset       INTEGER (1..2), 
        xcmHrDevInfoPagePackTimer       Integer32 (-2..2147483647) 
    }
xcmHrDevInfoRowStatus OBJECT-TYPE
    SYNTAX      RowStatus
    MAX-ACCESS  read-create
    STATUS      current
    DESCRIPTION
        "This object manages the row status of this conceptual row in
        the 'xcmHrDevInfoTable' and ALSO manages the row status
        of the associated conceptual row in the 'hrDeviceTable'
        of the IETF Host Resources MIB (RFC 2790).
        Usage:  Conforming implementations which support static rows
        SHALL support 'active' and 'notInService' writes to this
        'xcmHrDevInfoRowStatus' row status object; and
        SHALL clear the 'xcmHrDevInfoGroup' bit in
        'xcmHrGeneralCreateSupport' in the 'xcmHrGeneralTable'.
        Usage:  Conforming implementations which support dynamic rows
        SHALL support 'createAndGo' and 'destroy' writes to this
        'xcmHrDevInfoRowStatus' row status object; and
        SHALL set the 'xcmHrDevInfoGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevInfoEntry 1 }
xcmHrDevInfoName OBJECT-TYPE
    SYNTAX      XcmFixedLocaleDisplayString (SIZE (0..255))
    MAX-ACCESS  read-create
    STATUS      current
    DESCRIPTION
        "Human-readable device name, used by system administrators
        and end users to identify this device for systems management.
        Usage:  This device name SHALL be the one normally used in a
        CLI/GUI/API for control of this system or device
        (eg, 'showstopper.sample.com' or 'showstopper.sample.com/lpt1:')
        Usage:  Conforming management agents, which ALSO implement the
        the Printer MIB v2, SHALL set 'xcmHrDevInfoName'
        to the SAME value as 'prtGeneralPrinterName' for the SAME
        'hrDevicePrinter' row (i.e., the values of these two objects
        SHALL be interlocked)."
    REFERENCE
        "See:   'hrDeviceDescr' in the Device group of the
                IETF Host Resources MIB (RFC 2790)."
    DEFVAL      { ''H }                 
    ::= { xcmHrDevInfoEntry 2 }
xcmHrDevInfoSerialNumber OBJECT-TYPE
    SYNTAX      XcmFixedLocaleDisplayString (SIZE (0..255))
    MAX-ACCESS  read-create
    STATUS      current
    DESCRIPTION
        "Human-readable serial number, used by system administrators
        and end users to identify this device for systems management.
        Usage:  Conforming management agents, which ALSO implement the
        the Printer MIB v2, SHALL set 'xcmHrDevInfoSerialNumber'
        to the SAME value as 'prtGeneralSerialNumber' for the SAME
        'hrDevicePrinter' row (i.e., the values of these two objects
        SHALL be interlocked)."
    REFERENCE
        "See:   'hrDeviceDescr' in the Device group of the
                IETF Host Resources MIB (RFC 2790)."
    DEFVAL      { ''H }                 
    ::= { xcmHrDevInfoEntry 3 }
xcmHrDevInfoRealization OBJECT-TYPE
    SYNTAX      XcmHrDevInfoRealization
    MAX-ACCESS  read-create
    STATUS      current
    DESCRIPTION
        "An extended device type (or device 'realization'),
        used by system administrators and end users of this device."
    REFERENCE
        "See:   'hrDeviceType' in the Device group of the
                IETF Host Resources MIB (RFC 2790).
        See:    Section 9.4 (pages 181 to 184) of DPA (Document Printing
        Application) ISO/IEC 10175 (Final Text, March 1996) for a
        discussion of 'printer realizations' of 'physical', 'logical',
        and 'logical-and-physical' types (the latter peculiar to DPA)."
    DEFVAL      { physical }            
    ::= { xcmHrDevInfoEntry 4 }
xcmHrDevInfoXStatus OBJECT-TYPE
    SYNTAX      XcmHrDevInfoXStatus
    MAX-ACCESS  read-only
    STATUS      current
    DESCRIPTION
        "An extended device status, used by system administrators
        and end users of this device (here, read 'state' for 'status').
        Usage:  Conforming implementations SHALL NOT 'bubble up' status
        from 'physical' devices to associated 'logical' devices.  All
        devices SHALL report their own status ONLY.
        Usage:  Exactly one enumeration of extended device status
        SHALL be defined, with ranges for each basic device type (eg,
        'hrDevicePrinter').  The legal range for extended device status
        for a given device type (either defined by RFC 2790 or by this
        MIB) is found by multiplying the final arc of the the device
        type OID by 100 - the result is the device specific range base -
        the end of the device specific range is 99 larger.  These device
        specific extended device status values SHALL be reissued
        periodically in the 'XcmHrDevInfoXStatus' textual convention."
    REFERENCE
        "See:   Section 9.4.9 'Printer-state' (page 185) of DPA
        (Document Printing Application) ISO/IEC 10175 (Final Text,
        March 1996) for a discussion of the printer states used here.
        Note that the DPA state 'connecting-to-printer' has no meaning
        in the context of a 'physical' printer device, but only in the
        context of an intermediate DP-Server presenting a 'logical'
        printer device.
        See:    'hrPrinterStatus' and 'hrPrinterDetectedErrorState' in
                IETF Host Resources MIB (RFC 2790).
        See:    'hrDeviceStatus' in the Device group of the
                IETF Host Resources MIB (RFC 2790).
        See:    'xcmHrDevInfoConditions' and 'xcmHrDevInfoXConditions'
                in the Host Resources Extensions MIB."
    ::= { xcmHrDevInfoEntry 5 }
xcmHrDevInfoConditions OBJECT-TYPE
    SYNTAX      XcmHrDevInfoConditions
    MAX-ACCESS  read-only
    STATUS      current
    DESCRIPTION
        "A relatively generic description of the current 'conditions'
        of this device, specified in a bit-mask.
        Usage:  It is desirable that the implementor report 'conditions'
        of all devices corresponding to conceptual rows in the
        'hrDeviceTable' as accurately as feasible.  'Conditions' occur
        within or across 'states' in a finite state machine (FSM)
        implementation of a device.  They represent both short term and
        long term conditions."
    REFERENCE
        "See:   'hrDeviceStatus' in the Device group of the
                IETF Host Resources MIB (RFC 2790).
        See:    'xcmHrDevInfoXStatus' and 'xcmHrDevInfoXConditions'
                in the Host Resources Extensions MIB."
    DEFVAL      { 0 }                   
    ::= { xcmHrDevInfoEntry 6 }
xcmHrDevInfoXConditions OBJECT-TYPE
    SYNTAX      XcmHrDevInfoXConditions
    MAX-ACCESS  read-only
    STATUS      current
    DESCRIPTION
        "A device specific description of the extended 'conditions'
        of this device, specified in a bit-mask.
        Usage:  For FUTURE expansion.
        Usage:  Exactly one bit mask of extended device conditions SHALL
        be defined for each basic device type (eg, 'hrDevicePrinter').
        These device specific extended device conditions values SHALL be
        reissued periodically in the 'XcmHrDevInfoXConditions' textual
        convention.  These device specific extended device conditions
        are mutually exclusive and 'overloaded' in the single reporting
        object 'xcmHrDevInfoXConditions'."
    REFERENCE
        "See:   'hrDeviceStatus' in the Device group of the
                IETF Host Resources MIB (RFC 2790).
        See:    'xcmHrDevInfoXStatus' and 'xcmHrDevInfoConditions'
                in the Host Resources Extensions MIB."
    DEFVAL      { 0 }                   
    ::= { xcmHrDevInfoEntry 7 }
xcmHrDevInfoInstallDate OBJECT-TYPE
    SYNTAX      DateAndTime
    MAX-ACCESS  read-create
    STATUS      current
    DESCRIPTION
        "The date of the most recent install or upgrade of the device
        represented by this conceptual row in the 'hrDeviceTable'."
    REFERENCE
        "See:   'hrDeviceDescr' in the Device group of the
                IETF Host Resources MIB (RFC 2790)."
    DEFVAL      { '0000000000000000'H } 
    ::= { xcmHrDevInfoEntry 8 }
xcmHrDevInfoResetDate OBJECT-TYPE
    SYNTAX      DateAndTime
    MAX-ACCESS  read-only
    STATUS      current
    DESCRIPTION
        "The date of the most recent auto or managed reset of the device
        represented by this conceptual row in the 'hrDeviceTable'."
    REFERENCE
        "See:   'hrDeviceDescr' in the Device group of the
                IETF Host Resources MIB (RFC 2790)."
    DEFVAL      { '0000000000000000'H } 
    ::= { xcmHrDevInfoEntry 9 }
--
--
xcmHrDevInfoNextDeviceIndex OBJECT-TYPE
    SYNTAX      Cardinal32
    MAX-ACCESS  read-create
    STATUS      current
    DESCRIPTION
        "The value of 'hrDeviceIndex' corresponding to:
        a) the next associated row in the 'hrDeviceTable'; or
        b) zero if this is the last associated conceptual row in a
        given set; or
        c) zero if this conceptual row is NOT part of a set."
    REFERENCE
        "See:   'hrDeviceIndex' in the Device group of the
                IETF Host Resources MIB (RFC 2790)."
    DEFVAL      { 0 }                   
    ::= { xcmHrDevInfoEntry 10 }
xcmHrDevInfoPreviousDeviceIndex OBJECT-TYPE
    SYNTAX      Cardinal32
    MAX-ACCESS  read-create
    STATUS      current
    DESCRIPTION
        "The value of 'hrDeviceIndex' corresponding to:
        a) the previous associated row in the 'hrDeviceTable'; or
        b) zero if this is the first associated conceptual row in a
        given set; or
        c) zero if this conceptual row is NOT part of a set."
    REFERENCE
        "See:   'hrDeviceIndex' in the Device group of the
                IETF Host Resources MIB (RFC 2790)."
    DEFVAL      { 0 }                   
    ::= { xcmHrDevInfoEntry 11 }
xcmHrDevInfoPhysicalDeviceIndex OBJECT-TYPE
    SYNTAX      Cardinal32
    MAX-ACCESS  read-create
    STATUS      current
    DESCRIPTION
        "The value of 'hrDeviceIndex' corresponding to the directly
        associated conceptual row in the 'hrDeviceTable' representing:
        a) the first underlying 'physical' device (if any), if this
        row has 'xcmHrDevInfoRealization' of 'logical'; or
        b) the first subordinate 'physical' device (if any), if this
        row has 'xcmHrDevInfoRealization' of 'physical' or
        'logicalAndPhysical'; or
        c) zero if there is no underlying or subordinate 'physical'
        device associated with this row (ie, this device)."
    REFERENCE
        "See:   'hrDeviceIndex' in the Device group of the
                IETF Host Resources MIB (RFC 2790)."
    DEFVAL      { 0 }                   
    ::= { xcmHrDevInfoEntry 12 }
xcmHrDevInfoPriority OBJECT-TYPE
    SYNTAX      INTEGER (0..100)
    MAX-ACCESS  read-create
    STATUS      current
    DESCRIPTION
        "The current priority of this device.
        Usage:  The scheduling priority of this device, where '0'
        is unspecified (default), '1' is lowest, and '100' is highest."
    REFERENCE
        "See:   'xcmSvcMonServicePriority'
                in XCMI Service Monitoring MIB."
    DEFVAL      { 0 }                   
    ::= { xcmHrDevInfoEntry 13 }
    xcmHrDevInfoXeroxAssetTagNumber OBJECT-TYPE
        SYNTAX      XcmFixedLocaleDisplayString (SIZE (0..31))
        MAX-ACCESS  read-create
        STATUS      current
        DESCRIPTION
            "Human-readable, alpha-numeric ID used by Xerox and Xerox 
            managed service providers to uniquely identify a device 
            ACROSS back-end financial, printer management, asset 
            management, and help desk system applications. The Asset Tag
            Number is an infra- structure management de facto standard 
            for asset identification for use by Xerox and Xerox managed 
            service providers.
         Usage:  Conforming management agents SHALL set 
             'xcmHrDevInfoXeroxAssetTagNumber' to the SAME value as 
            entered at a device's local UI, at a device's web UI 
            interface, and as shown on the device's configuration 
            sheet."
        REFERENCE
            "See:   'hrDeviceDescr' in the Device group of the
                IETF Host Resources MIB (RFC 2790)."
        DEFVAL { ''H }            
    ::= { xcmHrDevInfoEntry 14 }
    xcmHrDevInfoCustomerAssetNumber OBJECT-TYPE
        SYNTAX      XcmFixedLocaleDisplayString (SIZE (0..31))
        MAX-ACCESS  read-create
        STATUS      current
        DESCRIPTION
            "Human-readable, alpha-numeric ID used by customers of 
            Xerox. This ID is used system administrators and their 
            designated managed service providers to uniquely identify a 
            device for customers' internal financial management, printer
            management, asset management, and help desk system 
            applications. 
           Usage:  Conforming management agents SHALL set 
             'xcmHrDevInfoCustomerAssetNumber' to the SAME value as 
            entered at a device's local UI, at a device's web UI 
            interface, and as shown on the device's configuration 
            sheet."
        REFERENCE
             "See:   'hrDeviceDescr' in the Device group of the
                     IETF Host Resources MIB (RFC 2790)."
        DEFVAL      { ''H }         
     ::= { xcmHrDevInfoEntry 15 }
    xcmHrDevInfoPagePackPIN OBJECT-TYPE
        SYNTAX      OCTET STRING (SIZE (0..31))
        MAX-ACCESS  read-create
        STATUS      current
        DESCRIPTION
            "An alpha-numeric ID used by Xerox and Xerox authorized
            resellers to enable devices to use a PagePack model 
            of device distribution. PagePack is a cost per page
            contract model - which includes consumables, supplies
            and service - on both printer and multifunction systems
            The PIN number is used to change a device from 
            purchased consumables device to a PagePack device.
            Usage: The device may return a NULL string or the word 
            'authorized' if the PIN value has been sent and the
            device does not want to expose the value to
            the PIN to unauthorized viewing. If no PIN has been
            sent or this functionality is not supported then a 
            NULL string is returned "
        REFERENCE
            "See:   'XcmSvcMonServiceType' in 'Service Monitoring TC'."
        DEFVAL      { ''H }         
     ::= { xcmHrDevInfoEntry 16 }
xcmHrDevInfoPagePackReset OBJECT-TYPE 
        SYNTAX      INTEGER (1..2) 
        MAX-ACCESS  read-create 
        STATUS      current 
        DESCRIPTION 
            "An enumeration used to get and set the page pack settings. 
            Usage: The device will return enabled when page pack 
            has been enabled and return disabled when page pack 
            has been disabled.
                enabled  (1)
                disabled (2) 
            " 
        REFERENCE 
            "See:   'xcmHrDevInfoPagePackPIN' in this mib." 
        DEFVAL      { 2 }         
     ::= { xcmHrDevInfoEntry 17 } 
xcmHrDevInfoPagePackTimer OBJECT-TYPE 
        SYNTAX      Integer32 (-2..2147483647) 
        MAX-ACCESS  read-create 
        STATUS      current 
        DESCRIPTION 
            "An timer value for page pack. 
            Usage: The value (-1) means timer not enabled 
             and a value 0..2147483647 means the timer has been 
             enabled" 
        REFERENCE 
            "See:   'xcmHrDevInfoPagePackPIN' in this mib." 
        DEFVAL      { -1 }         
     ::= { xcmHrDevInfoEntry 18 } 
xcmHrDevInfoV1EventOID OBJECT-IDENTITY
    STATUS      current
    DESCRIPTION
        "The value of the enterprise-specific OID in an SNMPv1 trap sent
        whenever a device status variable changes.
        See SNMPv2 trap definition 'xcmHrDevInfoV2Event'
        below for 'special semantics'."
    ::= { xcmHrDevInfo 1 }
xcmHrDevInfoV2EventPrefix
    OBJECT IDENTIFIER ::= { xcmHrDevInfoV1EventOID 0 }
xcmHrDevInfoV2Event NOTIFICATION-TYPE
    OBJECTS {
        hrDeviceIndex,
        hrDeviceStatus,
        xcmHrDevInfoXStatus,
        xcmHrDevInfoConditions,
        xcmHrDevInfoXConditions
    }
    STATUS      current
    DESCRIPTION
        "This trap is sent whenever 'hrDeviceStatus' and/or
        'xcmHrDevInfo[XStatus|Conditions|XConditions]' changes.
        Note:   The variable-bindings of this trap have been chosen to
        specify a complete device status change while keeping
        trap messages reasonably concise (generally a few hundred octets
        at most).
        This notification has the following special semantics:
            o   The device's 'hrDeviceIndex' field
                value SHALL be appended to this trap object ID,
                as a BER binary OID suffix.
        This trap OID qualifier allows device management/monitoring
        applications to limit the alerts they receive to ones generated
        by devices of interest."
    ::= { xcmHrDevInfoV2EventPrefix 1 }
--
--          "This trap is sent whenever 'hrDeviceStatus' and/or
--          above for 'special semantics'."
--
--
--
--
xcmHrDevHelp        OBJECT IDENTIFIER ::= { xcmHrMIB 4 }
xcmHrDevHelpTable OBJECT-TYPE
    SYNTAX      SEQUENCE OF XcmHrDevHelpEntry
    MAX-ACCESS  not-accessible
    STATUS      current
    DESCRIPTION
        "A 'sparse' table containing device help objects for
        installed and (possibly) active devices on this host system,
        augmenting the basic entries in the 'hrDeviceTable' of the
        IETF Host Resources MIB (RFC 2790)."
    REFERENCE
        "See:   'hrProcessorTable', 'hrNetworkTable', 'hrPrinterTable'
                in the IETF Host Resources MIB (RFC 2790)."
    ::= { xcmHrDevHelp 2 }
xcmHrDevHelpEntry OBJECT-TYPE
    SYNTAX      XcmHrDevHelpEntry
    MAX-ACCESS  not-accessible
    STATUS      current
    DESCRIPTION
        "A 'sparse' entry containing device help objects for
        an installed and (possibly) active device on this host system,
        augmenting a basic entry in the 'hrDeviceTable' of the
        IETF Host Resources MIB (RFC 2790)."
    INDEX       { hrDeviceIndex }
    ::= { xcmHrDevHelpTable 1 }
XcmHrDevHelpEntry ::= SEQUENCE {
        xcmHrDevHelpRowStatus           RowStatus,
        xcmHrDevHelpOperatorMessage     XcmFixedLocaleDisplayString,
        xcmHrDevHelpProblemMessage      XcmFixedLocaleDisplayString,
        xcmHrDevHelpCommsAddressIndex   Cardinal32
    }
xcmHrDevHelpRowStatus OBJECT-TYPE
    SYNTAX      RowStatus
    MAX-ACCESS  read-create
    STATUS      current
    DESCRIPTION
        "This object manages the row status of this conceptual row in
        the 'xcmHrDevHelpTable'.
        Usage:  Conforming implementations which support static rows
        SHALL support 'active' and 'notInService' writes to this
        'xcmHrDevHelpRowStatus' row status object; and
        SHALL clear the 'xcmHrDevHelpGroup' bit in
        'xcmHrGeneralCreateSupport' in the 'xcmHrGeneralTable'.
        Usage:  Conforming implementations which support dynamic rows
        SHALL support 'createAndGo' and 'destroy' writes to this
        'xcmHrDevHelpRowStatus' row status object; and
        SHALL set the 'xcmHrDevHelpGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevHelpEntry 1 }
xcmHrDevHelpOperatorMessage OBJECT-TYPE
    SYNTAX      XcmFixedLocaleDisplayString (SIZE (0..255))
    MAX-ACCESS  read-create
    STATUS      current
    DESCRIPTION
        "Human-readable operator message, used by system operators and
        system administrators to display an operator message for end
        users of this device.
        For example, 'Out to lunch - back at 1pm'."
    REFERENCE
        "See:   'hrDeviceDescr' in the Device group of the
                IETF Host Resources MIB (RFC 2790)."
    DEFVAL      { ''H }                 
    ::= { xcmHrDevHelpEntry 2 }
xcmHrDevHelpProblemMessage OBJECT-TYPE
    SYNTAX      XcmFixedLocaleDisplayString (SIZE (0..255))
    MAX-ACCESS  read-create
    STATUS      current
    DESCRIPTION
        "Human-readable problem message, used by system operators and
        system administrators to display a problem message for end
        users of this device.
        For example, 'Toner low - only small jobs accepted'."
    REFERENCE
        "See:   'hrDeviceDescr' in the Device group of the
                IETF Host Resources MIB (RFC 2790)."
    DEFVAL      { ''H }                 
    ::= { xcmHrDevHelpEntry 3 }
xcmHrDevHelpCommsAddressIndex OBJECT-TYPE
    SYNTAX      Cardinal32
    MAX-ACCESS  read-create
    STATUS      current
    DESCRIPTION
        "The value of 'xcmCommsAddressIndex' corresponding to the first
        associated conceptual row in the 'xcmCommsAddressTable', or zero
        if this 'xcmHrDevHelpEntry' does NOT require such information.
        This 'chain' of address entries provides device help contact
        info for end users of this device.
        For example, 'system operator' or 'supplies' contact info."
    REFERENCE
        "See:   Comms Address group of the XCMI Comms Engine MIB, for
        details of specification of device help contact info.
        See:    'XcmSecUserRole' in XCMI Security TC, for appropriate
        values for 'xcmCommsAddressUserRole'.
        See:    'sysContact' in the IETF MIB-II (RFC 1213), for details
        of specification of 'simple' host system contact info."
    DEFVAL      { 0 }                   
    ::= { xcmHrDevHelpEntry 4 }
--
--
--
xcmHrDevMgmt        OBJECT IDENTIFIER ::= { xcmHrMIB 5 }
xcmHrDevMgmtTable OBJECT-TYPE
    SYNTAX      SEQUENCE OF XcmHrDevMgmtEntry
    MAX-ACCESS  not-accessible
    STATUS      current
    DESCRIPTION
        "A 'sparse' table containing management control objects for
        installed and (possibly) active devices on this host system,
        augmenting the basic entries in the 'hrDeviceTable' of the
        IETF Host Resources MIB (RFC 2790)."
    REFERENCE
        "See:   'hrProcessorTable', 'hrNetworkTable', 'hrPrinterTable'
                in the IETF Host Resources MIB (RFC 2790).
        See:    'xcmSysAdminRequestTable' in XCMI System Admin MIB and
                'xcmSecUserTable' in XCMI Security MIB."
    ::= { xcmHrDevMgmt 2 }
xcmHrDevMgmtEntry OBJECT-TYPE
    SYNTAX      XcmHrDevMgmtEntry
    MAX-ACCESS  not-accessible
    STATUS      current
    DESCRIPTION
        "A 'sparse' entry containing management control objects for
        an installed and (possibly) active device on this host system,
        augmenting a basic entry in the 'hrDeviceTable' of the
        IETF Host Resources MIB (RFC 2790)."
    INDEX       { hrDeviceIndex }
    ::= { xcmHrDevMgmtTable 1 }
XcmHrDevMgmtEntry ::= SEQUENCE {
        xcmHrDevMgmtRowStatus           RowStatus,
        xcmHrDevMgmtCommandRequest      XcmHrDevMgmtCommandRequest,
        xcmHrDevMgmtCommandData         XcmHrDevMgmtCommandData,
        xcmHrDevMgmtCommandStatus       XcmGenSNMPv2ErrorStatus,
        xcmHrDevMgmtUserPassword        OCTET STRING,
        xcmHrDevMgmtOperatorPassword    OCTET STRING,
        xcmHrDevMgmtAdminPassword       OCTET STRING,
        xcmHrDevMgmtCommandInProgress   TruthValue,
        xcmHrDevMgmtUserName            OCTET STRING,
        xcmHrDevMgmtOperatorName        OCTET STRING,
        xcmHrDevMgmtAdminName           OCTET STRING, 
        xcmHrDevMgmtCustomPassword      OCTET STRING 
} 
xcmHrDevMgmtRowStatus OBJECT-TYPE
    SYNTAX      RowStatus
    MAX-ACCESS  read-create
    STATUS      current
    DESCRIPTION
        "This object manages the row status of this conceptual row in
        the 'xcmHrDevMgmtTable'.
        Usage:  Conforming implementations which support static rows
        SHALL support 'active' and 'notInService' writes to this
        'xcmHrDevMgmtRowStatus' row status object; and
        SHALL clear the 'xcmHrDevMgmtGroup' bit in
        'xcmHrGeneralCreateSupport' in the 'xcmHrGeneralTable'.
        Usage:  Conforming implementations which support dynamic rows
        SHALL support 'createAndGo' and 'destroy' writes to this
        'xcmHrDevMgmtRowStatus' row status object; and
        SHALL set the 'xcmHrDevMgmtGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevMgmtEntry 1 }
xcmHrDevMgmtCommandRequest OBJECT-TYPE
    SYNTAX      XcmHrDevMgmtCommandRequest
    MAX-ACCESS  read-create
    STATUS      current
    DESCRIPTION
        "The most recent device management command request
        specified for this conceptual row in the 'xcmHrDevMgmtTable'.
        Usage:  Conforming management agents SHALL 'reject' any
        SNMP Set-Request to 'xcmHrDevMgmtCommand[Request|Data]'
        while another management operation is already in progress
        (ie, while 'xcmHrDevMgmtCommandInProgress' is 'true'),
        with 'badValue' (SNMPv1) or 'inconsistentValue' (SNMPv2/v3).
        Usage:  Conforming management stations SHALL set
        'xcmHrDevMgmtCommandRequest' (mgmt operation) and
        'xcmHrDevMgmtCommandData' (mgmt arguments)
        SIMULTANEOUSLY (in the same SNMP Set-Request PDU)."
    REFERENCE
        "See:   Section 4 'Print Utilities' (pages 71 to 212) of
                POSIX Sys Admin (IEEE 1387.4 / Draft 8, October 1994).
        See:    'hrDeviceStatus' in the Device group of the
                IETF Host Resources MIB (RFC 2790).
        See:    OBJECT clause in MODULE-COMPLIANCE macro of
                XCMI Ext to Host Resources MIB, for compliance info.
        See:    'XcmHrDevMgmtCommandDataTag' textual convention,
                Section 3.4 'XCMI Standard Tagged Management Data', and
                Section 3.5 'Simple Device Management Requests' in
                XCMI Ext to Host Resources TC.
        See:    Section 3.5.3 'Secure Simple Device Mgmt Requests' in
                XCMI Security TC.
        See:    'xcmHrDevMgmtCommand[Data|Status|InProgress]'"
    DEFVAL      { none }                
    ::= { xcmHrDevMgmtEntry 2 }
xcmHrDevMgmtCommandData OBJECT-TYPE
    SYNTAX      XcmHrDevMgmtCommandData (SIZE (0..255))
    MAX-ACCESS  read-create
    STATUS      current
    DESCRIPTION
        "The most recent device management command data (if any)
        specified for this conceptual row in the 'xcmHrDevMgmtTable'.
        Usage:  Conforming management agents SHALL 'reject' any
        SNMP Set-Request to 'xcmHrDevMgmtCommand[Request|Data]'
        while another management operation is already in progress
        (ie, while 'xcmHrDevMgmtCommandInProgress' is 'true'),
        with 'badValue' (SNMPv1) or 'inconsistentValue' (SNMPv2/v3).
        Usage:  Conforming management stations SHALL set
        'xcmHrDevMgmtCommandRequest' (mgmt operation) and
        'xcmHrDevMgmtCommandData' (mgmt arguments)
        SIMULTANEOUSLY (in the same SNMP Set-Request PDU).
        Usage:  Conformant implementations MUST encrypt passwords, keys,
        and other security information stored in this string object."
    REFERENCE
        "See:   Section 4 'Print Utilities' (pages 71 to 212) of
                POSIX Sys Admin (IEEE 1387.4 / Draft 8, October 1994).
        See:    'hrDeviceStatus' in the Device group of the
                IETF Host Resources MIB (RFC 2790).
        See:    'XcmHrDevMgmtCommandDataTag' textual convention,
                Section 3.4 'XCMI Standard Tagged Management Data', and
                Section 3.5 'Simple Device Management Requests' in
                XCMI Ext to Host Resources TC.
        See:    Section 3.5.3 'Secure Simple Device Mgmt Requests' in
                XCMI Security TC.
        See:    'xcmHrDevMgmtCommand[Request|Status|InProgress]'"
    DEFVAL      { ''H }                 
    ::= { xcmHrDevMgmtEntry 3 }
xcmHrDevMgmtCommandStatus OBJECT-TYPE
    SYNTAX      XcmGenSNMPv2ErrorStatus
    MAX-ACCESS  read-only
    STATUS      current
    DESCRIPTION
        "The simple device management error status associated with
        this conceptual row in 'xcmHrDevMgmtTable'.
        Usage:  Conforming management agents SHALL set this
        object to the value returned in an SNMP Set-Response PDU when
        a simple device management operation is 'accepted', ie, when
        'xcmHrDevMgmtCommandInProgress' goes from 'false' to 'true'.
        Usage:  Conforming management agents SHALL set this
        object to the value of the completion status of the (possibly
        deferred) simple device management operation, when
        'xcmHrDevMgmtCommandInProgress' goes from 'true' to 'false'."
    REFERENCE
        "See:   Section 4 'Print Utilities' (pages 71 to 212) of
                POSIX Sys Admin (IEEE 1387.4 / Draft 8, October 1994).
        See:    'hrDeviceStatus' in the Device group of the
                IETF Host Resources MIB (RFC 2790).
        See:    'XcmHrDevMgmtCommandDataTag' textual convention,
                Section 3.4 'XCMI Standard Tagged Management Data', and
                Section 3.5 'Simple Device Management Requests' in
                XCMI Ext to Host Resources TC.
        See:    Section 3.5.3 'Secure Simple Device Mgmt Requests' in
                XCMI Security TC.
        See:    'xcmHrDevMgmtCommand[Operation|Data|InProgress]'"
    ::= { xcmHrDevMgmtEntry 4 }
xcmHrDevMgmtUserPassword OBJECT-TYPE
    SYNTAX      OCTET STRING (SIZE (0..255))
    MAX-ACCESS  read-create
    STATUS      current
    DESCRIPTION
        "A protected end user password for this device.
        Usage:  Conformant implementations MUST encrypt passwords, keys,
        and other security information stored in this string object.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'end user password' in this object.
        Usage:  Conforming management stations and management agents
        SHOULD support authentication of SNMP SetRequests via values of
        'xcmHrDevMgmt[User|Operator|Admin]Password' in ciphertext
        (ie, encrypted) written in 'xcmHrDevMgmtCommandData'.
        Usage:  Conforming management stations MAY support client-side
        authentication of user roles and rights via checking values of
        'xcmHrDevMgmt[User|Operator|Admin]Password' presented in client
        applications (eg, install tools).  WARNING:  Such authentication
        mechanisms do NOT protect managed systems from attack by other
        SNMP client applications that do NOT perform such client-side
        authentication and are thus inherently weak."
    REFERENCE
        "See:   'xcmHrDevMgmt[Operator|Admin]Password'
        See:    Section 3.5.2 'Secure Password Change Requests' in
                XCMI Security TC.
        See:    'xcmSysAdminRequestTable' in XCMI System Admin MIB and
                'xcmSecUserTable' in XCMI Security MIB.
        See:    Both the X/Open PSIS (Printing Systems Interoperability
        Specification) and the new Part 3 'Systems Management' of DPA
        (ISO/IEC 10175) use the simple three-role scheme specified here.
        In Appendix D 'Roles of Users' (pages 108 to 109) of Printer MIB
        v1 (RFC 1759), Jay Martin provided an excellent discussion of
        a number of user 'role models', including the following ones:
        User (USER) - A person or application that submits print jobs to
        the printer; typically viewed as the 'end user' within the
        overall printing environment.
        Operator (OP) - A person responsible for maintaining a printer
        on a day-to-day basis, including such tasks as filling empty
        media trays, emptying full output trays, replacing toner
        cartridges, etc.
        System Manager (MGR) - A person responsible for configuration
        and troubleshooting of components involved in the overall
        printing environment, including printers, print queues and
        network connectivity issues.  This person is typically
        responsible for ensuring the overall operational integrity of
        the print system components, and is typically viewed as the
        central point of coordination among all other Role Models."
    DEFVAL      { ''H }                 
    ::= { xcmHrDevMgmtEntry 5 }
xcmHrDevMgmtOperatorPassword OBJECT-TYPE
    SYNTAX      OCTET STRING (SIZE (0..255))
    MAX-ACCESS  read-create
    STATUS      current
    DESCRIPTION
        "A protected system operator password for this device.
        Usage:  Conformant implementations MUST encrypt passwords, keys,
        and other security information stored in this string object.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'operator password' in this object.
        Usage:  Conforming management stations and management agents
        SHOULD support authentication of SNMP SetRequests via values of
        'xcmHrDevMgmt[User|Operator|Admin]Password' in ciphertext
        (ie, encrypted) written in 'xcmHrDevMgmtCommandData'.
        Usage:  Conforming management stations MAY support client-side
        authentication of user roles and rights via checking values of
        'xcmHrDevMgmt[User|Operator|Admin]Password' presented in client
        applications (eg, install tools).  WARNING:  Such authentication
        mechanisms do NOT protect managed systems from attack by other
        SNMP client applications that do NOT perform such client-side
        authentication and are thus inherently weak."
    REFERENCE
        "See:   'xcmHrDevMgmt[User|Admin]Password'
        See:    Section 3.5.2 'Secure Password Change Requests' in
                XCMI Security TC.
        See:    'xcmSysAdminRequestTable' in XCMI System Admin MIB and
                'xcmSecUserTable' in XCMI Security MIB."
    DEFVAL      { ''H }                 
    ::= { xcmHrDevMgmtEntry 6 }
xcmHrDevMgmtAdminPassword OBJECT-TYPE
    SYNTAX      OCTET STRING (SIZE (0..255))
    MAX-ACCESS  read-create
    STATUS      current
    DESCRIPTION
        "A protected system administrator password for this device.
        Usage:  Conformant implementations MUST encrypt passwords, keys,
        and other security information stored in this string object.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'administrator password' in this object.
        Usage:  Conforming management stations and management agents
        SHOULD support authentication of SNMP SetRequests via values of
        'xcmHrDevMgmt[User|Operator|Admin]Password' in ciphertext
        (ie, encrypted) written in 'xcmHrDevMgmtCommandData'.
        Usage:  Conforming management stations MAY support client-side
        authentication of user roles and rights via checking values of
        'xcmHrDevMgmt[User|Operator|Admin]Password' presented in client
        applications (eg, install tools).  WARNING:  Such authentication
        mechanisms do NOT protect managed systems from attack by other
        SNMP client applications that do NOT perform such client-side
        authentication and are thus inherently weak."
    REFERENCE
        "See:   'xcmHrDevMgmt[User|Operator]Password'
        See:    Section 3.5.2 'Secure Password Change Requests' in
                XCMI Security TC.
        See:    'xcmSysAdminRequestTable' in XCMI System Admin MIB and
                'xcmSecUserTable' in XCMI Security MIB."
    DEFVAL      { ''H }                 
    ::= { xcmHrDevMgmtEntry 7 }
xcmHrDevMgmtCommandInProgress OBJECT-TYPE
    SYNTAX      TruthValue
    MAX-ACCESS  read-only
    STATUS      current
    DESCRIPTION
        "The device management in progress status associated with
        this conceptual row in 'xcmHrDevMgmtTable'.
        Usage:  Conforming management agents SHALL 'reject' any
        SNMP Set-Request to 'xcmHrDevMgmtCommand[Request|Data]'
        while another management operation is already in progress
        (ie, while 'xcmHrDevMgmtCommandInProgress' is 'true'),
        with 'badValue' (SNMPv1) or 'inconsistentValue' (SNMPv2/v3)."
    REFERENCE
        "See:   Section 4 'Print Utilities' (pages 71 to 212) of
                POSIX Sys Admin (IEEE 1387.4 / Draft 8, October 1994).
        See:    'hrDeviceStatus' in the Device group of the
                IETF Host Resources MIB (RFC 2790).
        See:    'XcmHrDevMgmtCommandDataTag' textual convention,
                Section 3.4 'XCMI Standard Tagged Management Data', and
                Section 3.5 'Simple Device Management Requests' in
                XCMI Ext to Host Resources TC.
        See:    Section 3.5.3 'Secure Simple Device Mgmt Requests' in
                XCMI Security TC.
        See:    'xcmHrDevMgmtCommand[Request|Data|Status]'"
    DEFVAL      { false }               
    ::= { xcmHrDevMgmtEntry 8 }
xcmHrDevMgmtUserName OBJECT-TYPE
    SYNTAX      OCTET STRING (SIZE (0..255))
    MAX-ACCESS  read-create
    STATUS      current
    DESCRIPTION
        "A protected end user Name for this device.
        Usage:  Conformant implementations MUST encrypt passwords, keys,
        and other security information stored in this string object.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'end user Name' in this object.
        Usage:  Conforming management stations and management agents
        SHOULD support authentication of SNMP SetRequests via values of
        'xcmHrDevMgmt[User|Operator|Admin]Name' in ciphertext
        (ie, encrypted) written in 'xcmHrDevMgmtCommandData'.
        Usage:  Conforming management stations MAY support client-side
        authentication of user roles and rights via checking values of
        'xcmHrDevMgmt[User|Operator|Admin]Name' presented in client
        applications (eg, install tools).  WARNING:  Such authentication
        mechanisms do NOT protect managed systems from attack by other
        SNMP client applications that do NOT perform such client-side
        authentication and are thus inherently weak."
    REFERENCE
        "See:   'xcmHrDevMgmt[Operator|Admin]Name'
         See:    Section 3.5.2 'Secure Password Change Requests' in
                 XCMI Security TC.
         See:    'xcmSysAdminRequestTable' in XCMI System Admin MIB and
                 'xcmSecUserTable' in XCMI Security MIB.
         See:    Both the X/Open PSIS (Printing Systems Interoperability
         Specification) and the new Part 3 'Systems Management' of DPA
         (ISO/IEC 10175) use the simple three-role scheme specified here
         In Appendix D 'Roles of Users' (pages 108 to 109) of Printer MI
         v1 (RFC 1759), Jay Martin provided an excellent discussion of
         a number of user 'role models', including the following ones:
        User (USER) - A person or application that submits print jobs to
        the printer; typically viewed as the 'end user' within the
        overall printing environment.
        Operator (OP) - A person responsible for maintaining a printer
        on a day-to-day basis, including such tasks as filling empty
        media trays, emptying full output trays, replacing toner
        cartridges, etc.
        System Manager (MGR) - A person responsible for configuration
        and troubleshooting of components involved in the overall
        printing environment, including printers, print queues and
        network connectivity issues.  This person is typically
        responsible for ensuring the overall operational integrity of
        the print system components, and is typically viewed as the
        central point of coordination among all other Role Models."
    DEFVAL      { ''H }                 
    ::= { xcmHrDevMgmtEntry 9 }
xcmHrDevMgmtOperatorName OBJECT-TYPE
    SYNTAX      OCTET STRING (SIZE (0..255))
    MAX-ACCESS  read-create
    STATUS      current
    DESCRIPTION
        "A protected system operator Name for this device.
        Usage:  Conformant implementations MUST encrypt passwords, keys,
        and other security information stored in this string object.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'operator Name' in this object.
        Usage:  Conforming management stations and management agents
        SHOULD support authentication of SNMP SetRequests via values of
        'xcmHrDevMgmt[User|Operator|Admin]Name' in ciphertext
        (ie, encrypted) written in 'xcmHrDevMgmtCommandData'.
        Usage:  Conforming management stations MAY support client-side
        authentication of user roles and rights via checking values of
        'xcmHrDevMgmt[User|Operator|Admin]Name' presented in client
        applications (eg, install tools).  WARNING:  Such authentication
        mechanisms do NOT protect managed systems from attack by other
        SNMP client applications that do NOT perform such client-side
        authentication and are thus inherently weak."
    REFERENCE
        "See:   'xcmHrDevMgmt[User|Admin]Name'
         See:    Section 3.5.2 'Secure Password Change Requests' in
                 XCMI Security TC.
         See:    'xcmSysAdminRequestTable' in XCMI System Admin MIB and
                 'xcmSecUserTable' in XCMI Security MIB."
    DEFVAL      { ''H }                 
    ::= { xcmHrDevMgmtEntry 10 }
xcmHrDevMgmtAdminName OBJECT-TYPE
    SYNTAX      OCTET STRING (SIZE (0..255))
    MAX-ACCESS  read-create
    STATUS      current
    DESCRIPTION
        "A protected system administrator Name for this device.
        Usage:  Conformant implementations MUST encrypt passwords, keys,
        and other security information stored in this string object.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'administrator Name' in this object.
        Usage:  Conforming management stations and management agents
        SHOULD support authentication of SNMP SetRequests via values of
        'xcmHrDevMgmt[User|Operator|Admin]Name' in ciphertext
        (ie, encrypted) written in 'xcmHrDevMgmtCommandData'.
        Usage:  Conforming management stations MAY support client-side
        authentication of user roles and rights via checking values of
        'xcmHrDevMgmt[User|Operator|Admin]Name' presented in client
        applications (eg, install tools).  WARNING:  Such authentication
        mechanisms do NOT protect managed systems from attack by other
        SNMP client applications that do NOT perform such client-side
        authentication and are thus inherently weak."
    REFERENCE
        "See:   'xcmHrDevMgmt[User|Operator]Name'
         See:    Section 3.5.2 'Secure Password Change Requests' in
                 XCMI Security TC.
         See:    'xcmSysAdminRequestTable' in XCMI System Admin MIB and
                 'xcmSecUserTable' in XCMI Security MIB."
    DEFVAL      { ''H }                 
    ::= { xcmHrDevMgmtEntry 11 }
xcmHrDevMgmtCustomPassword OBJECT-TYPE 
    SYNTAX      OCTET STRING (SIZE (0..255)) 
    MAX-ACCESS  read-create 
    STATUS      current 
    DESCRIPTION 
        "A protected PDL password for this device. 
        Usage:  Conformant implementations MUST encrypt passwords, keys,
        and other security information stored in this string object. 
        Usage:  All XCMI conforming management agents: a) SHOULD always 
        return an encoded string in response to an SNMP GetRequest of 
        this object; b) SHALL NOT return the contents of this object in 
        cleartext (ie, unencrypted) in response to an SNMP GetRequest; 
        c) SHOULD support (ie, accept) an unencoded SNMP SetRequest 
        changing the system 'custom password' in this object. 
        Usage:  Conforming management stations and management agents 
        SHOULD support authentication of SNMP SetRequests via values of 
        'xcmHrDevMgmt[User|Operator|Admin|Custom]Password' in 
        written cleartext in 'xcmHrDevMgmtCommandData'. 
        Usage:  Conforming management stations MAY support client-side 
        authentication of user roles and rights via checking values of 
        'xcmHrDevMgmt[User|Operator|Admin|Custom]Password' presented in 
        client applications (eg, install tools).  WARNING:  Such 
        mechanisms do NOT protect managed systems from attack by other 
        authentication SNMP client applications that do NOT perform such
        client-side authentication and are thus inherently weak." 
    REFERENCE 
        "See:   'xcmHrDevMgmt[User|Operator|Admin]Password' 
        See:    Section 3.5.2 'Secure Password Change Requests' in 
                XCMI Security TC. 
        See:    'xcmSysAdminRequestTable' in XCMI System Admin MIB and 
                'xcmSecUserTable' in XCMI Security MIB." 
    DEFVAL      { ''H }                 
    ::= { xcmHrDevMgmtEntry 12 } 
xcmHrDevMgmtV1EventOID OBJECT-IDENTITY
    STATUS      current
    DESCRIPTION
        "The value of the enterprise-specific OID in an SNMPv1 trap sent
        whenever an 'xcmHrDevMgmtCommandRequest' completes.
        See SNMPv2 trap definition 'xcmHrDevMgmtV2Event'
        below for 'special semantics'."
    ::= { xcmHrDevMgmt 1 }
xcmHrDevMgmtV2EventPrefix
    OBJECT IDENTIFIER ::= { xcmHrDevMgmtV1EventOID 0 }
xcmHrDevMgmtV2Event NOTIFICATION-TYPE
    OBJECTS {
        hrDeviceIndex,
        hrDeviceStatus,
        xcmHrDevInfoXStatus,
        xcmHrDevInfoConditions,
        xcmHrDevInfoXConditions,
        xcmHrDevMgmtCommandRequest,
        xcmHrDevMgmtCommandStatus
    }
    STATUS      current
    DESCRIPTION
        "This trap is sent whenever an 'XcmHrDevMgmtCommandRequest'
        completes, ie, when 'xcmHrDevMgmtCommandStatus' becomes the
        completed operation status and 'XcmHrDevMgmtCommandInProgress'
        goes from 'true' to 'false'.
        Note:   The variable-bindings of this trap have been chosen to
        specify a complete management operation result while keeping
        trap messages reasonably concise (generally a few hundred octets
        at most).
        This notification has the following special semantics:
            o   The device's 'hrDeviceIndex' field
                value SHALL be appended to this trap object ID,
                as a BER binary OID suffix.
        This trap OID qualifier allows device management/monitoring
        applications to limit the alerts they receive to ones generated 
        by requests they have submitted."
    ::= { xcmHrDevMgmtV2EventPrefix 1 }
--
--          "This trap is sent when an 'XcmHrDevMgmtCommandRequest'
--          above for 'special semantics'."
--
--
--
xcmHrDevPower       OBJECT IDENTIFIER ::= { xcmHrMIB 6 }
xcmHrDevPowerTable OBJECT-TYPE
    SYNTAX      SEQUENCE OF XcmHrDevPowerEntry
    MAX-ACCESS  not-accessible
    STATUS      current
    DESCRIPTION
        "A 'sparse' table containing power management cycle objects for
        installed and (possibly) active devices on this host system,
        augmenting the basic entries in the 'hrDeviceTable' of the
        IETF Host Resources MIB (RFC 2790)."
    REFERENCE
        "See:   'hrProcessorTable', 'hrNetworkTable', 'hrPrinterTable'
                in the IETF Host Resources MIB (RFC 2790)."
    ::= { xcmHrDevPower 2 }
xcmHrDevPowerEntry OBJECT-TYPE
    SYNTAX      XcmHrDevPowerEntry
    MAX-ACCESS  not-accessible
    STATUS      current
    DESCRIPTION
        "A 'sparse' entry containing power management cycle objects for
        an installed and (possibly) active device on this host system,
        augmenting a basic entry in the 'hrDeviceTable' of the
        IETF Host Resources MIB (RFC 2790)."
    INDEX       { hrDeviceIndex }
    ::= { xcmHrDevPowerTable 1 }
XcmHrDevPowerEntry ::= SEQUENCE {
        xcmHrDevPowerRowStatus          RowStatus,
        xcmHrDevPowerWarmUpSupport      PresentOnOff,
        xcmHrDevPowerCoolDownSupport    PresentOnOff,
        xcmHrDevPowerEnergySaveSupport  PresentOnOff,
        xcmHrDevPowerTimeUnit           XcmHrDevPowerTimeUnit,
        xcmHrDevPowerWarmUpDelay        Integer32,
        xcmHrDevPowerWarmUpDuration     Integer32,
        xcmHrDevPowerCoolDownDelay      Integer32,
        xcmHrDevPowerCoolDownDuration   Integer32,
        xcmHrDevPowerEnergySaveDelay    Integer32,
        xcmHrDevPowerEnergySaveDuration Integer32,
        xcmHrDevPowerWakeUpSupport      PresentOnOff,
        xcmHrDevPowerWakeUpDelay        Integer32,
        xcmHrDevPowerWakeUpDuration     Integer32,
        xcmHrDevPowerShutdownDelay      Integer32,
        xcmHrDevPowerShutdownDuration   Integer32,
        xcmHrDevPowerStartupDelay       Integer32,
        xcmHrDevPowerStartupDuration    Integer32
    }
xcmHrDevPowerRowStatus OBJECT-TYPE
    SYNTAX      RowStatus
    MAX-ACCESS  read-create
    STATUS      current
    DESCRIPTION
        "This object manages the row status of this conceptual row in
        the 'xcmHrDevPowerTable'.
        Usage:  Conforming implementations which support static rows
        SHALL support 'active' and 'notInService' writes to this
        'xcmHrDevPowerRowStatus' row status object; and
        SHALL clear the 'xcmHrDevPowerGroup' bit in
        'xcmHrGeneralCreateSupport' in the 'xcmHrGeneralTable'.
        Usage:  Conforming implementations which support dynamic rows
        SHALL support 'createAndGo' and 'destroy' writes to this
        'xcmHrDevPowerRowStatus' row status object; and
        SHALL set the 'xcmHrDevPowerGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevPowerEntry 1 }
xcmHrDevPowerWarmUpSupport OBJECT-TYPE
    SYNTAX      PresentOnOff
    MAX-ACCESS  read-create
    STATUS      current
    DESCRIPTION
        "A device 'warm up' feature support management object,
        used by system administrators of this device.
        Usage:  This object specifies the support present (if any) for
        a device 'warm up' feature ('standbyMode' to 'readyMode').
        For example, a photocopier might want to 'warm up' (as a system)
        (to 'readyMode') some time after a user presses a button.
      * 'other(1)'
        - DEPRECATED - SHALL NOT be used by conforming implementations
      * 'on(3)'
        - device 'warm up' feature is present and enabled
        both '...WarmUpDelay' and '...WarmUpDuration' are used
        - if '...WarmUpDelay' is zero,
        then 'warm up' cycle begins immediately after trigger event
        - if '...WarmUpDelay' is non-zero,
        then 'warm up' cycle is delayed for specified time
        - if '...WarmUpDuration' is zero,
        then 'warm up' cycle completes immediately after initiation
        - if '...WarmUpDuration' is non-zero,
        then 'warm up' cycle requires specified time to complete
      * 'off(4)'
        - device 'warm up' feature is present but disabled
        both '...WarmUpDelay' and '...WarmUpDuration' NOT used
      * 'notPresent(5)'
        - device 'warm up' feature NOT present on this host system
        both '...WarmUpDelay' and '...WarmUpDuration' NOT used"
    REFERENCE
        "See:   'xcmHrDevPowerWarmUp[Delay|Duration]'"
    DEFVAL      { notPresent }          
    ::= { xcmHrDevPowerEntry 2 }
xcmHrDevPowerCoolDownSupport OBJECT-TYPE
    SYNTAX      PresentOnOff
    MAX-ACCESS  read-create
    STATUS      current
    DESCRIPTION
        "A device 'cool down' feature support management object,
        used by system administrators of this device.
        Usage:  This object specifies the support present (if any) for
        a device 'cool down' feature ('readyMode' to 'standbyMode').
        For example, a printer might want to 'cool down' a motor
        (to 'standbyMode') some time after the last page printed.
      * 'other(1)'
        - DEPRECATED - SHALL NOT be used by conforming implementations
      * 'on(3)'
        - device 'cool down' feature is present and enabled
        both '...CoolDownDelay' and '...CoolDownDuration' are used
        - if '...CoolDownDelay' is zero,
        then 'cool down' cycle begins immediately after trigger event
        - if '...CoolDownDelay' is non-zero,
        then 'cool down' cycle is delayed for specified time
        - if '...CoolDownDuration' is zero,
        then 'cool down' cycle completes immediately after initiation
        - if '...CoolDownDuration' is non-zero,
        then 'cool down' cycle requires specified time to complete
      * 'off(4)'
        - device 'cool down' feature is present but disabled
        both '...CoolDownDelay' and '...CoolDownDuration' NOT used
      * 'notPresent(5)'
        - device 'cool down' feature NOT present on this host system
        both '...CoolDownDelay' and '...CoolDownDuration' NOT used"
    REFERENCE
        "See:   'xcmHrDevPowerCoolDown[Delay|Duration]'"
    DEFVAL      { notPresent }          
    ::= { xcmHrDevPowerEntry 3 }
xcmHrDevPowerEnergySaveSupport OBJECT-TYPE
    SYNTAX      PresentOnOff
    MAX-ACCESS  read-create
    STATUS      current
    DESCRIPTION
        "A device 'energy save' feature support management object,
        used by system administrators of this device.
        Usage:  This object specifies the support present (if any) for
        a device 'energy save' feature ('standbyMode' to 'sleepMode').
        For example, a printer might want to 'energy save' transition
        (to 'sleepMode') some time after the last 'cool down'
        (to 'standbyMode') completion.
      * 'other(1)'
        - DEPRECATED - SHALL NOT be used by conforming implementations
      * 'on(3)'
        - device 'energy save' feature is present and enabled
        both '...EnergySaveDelay' and '...EnergySaveDuration' are used
        - if '...EnergySaveDelay' is zero,
        then 'energy save' cycle begins immediately after trigger event
        - if '...EnergySaveDelay' is non-zero,
        then 'energy save' cycle is delayed for specified time
        - if '...EnergySaveDuration' is zero,
        then 'energy save' cycle completes immediately after initiation
        - if '...EnergySaveDuration' is non-zero,
        then 'energy save' cycle requires specified time to complete
      * 'off(4)'
        - device 'energy save' feature is present but disabled
        both '...EnergySaveDelay' and '...EnergySaveDuration' NOT used
      * 'notPresent(5)'
        - device 'energy save' feature NOT present on this host system
        both '...EnergySaveDelay' and '...EnergySaveDuration' NOT used"
    REFERENCE
        "See:   'xcmHrDevPowerEnergySave[Delay|Duration]'"
    DEFVAL      { notPresent }          
    ::= { xcmHrDevPowerEntry 4 }
xcmHrDevPowerTimeUnit OBJECT-TYPE
    SYNTAX      XcmHrDevPowerTimeUnit
    MAX-ACCESS  read-create
    STATUS      current
    DESCRIPTION
        "A device power cycle time unit, used by system administrators
        of this device for power management cycle times.
        Usage:  Used to scale the values in the Device Power group, for
        convenience and (optional) high resolution."
    DEFVAL      { unknown }             
    ::= { xcmHrDevPowerEntry 5 }
xcmHrDevPowerWarmUpDelay OBJECT-TYPE
    SYNTAX      Integer32
    MAX-ACCESS  read-create
    STATUS      current
    DESCRIPTION
        "A device 'warm up' feature delay time,
        or zero if none, used by system administrators of this device.
        Usage:  The time delay after last 'warm up' trigger event
        (eg, arrival of a job, some local user action, etc)
        before the 'warm up' cycle will begin (to power 'readyMode'
        in 'xcmHrDevInfoConditions')."
    REFERENCE
        "See:   'xcmHrDevPowerWarmUpSupport' for feature details
        and     'xcmHrDevPowerTimeUnit' for time unit
        and     'xcmHrDevInfoConditions' for device 'mode' conditions"
    DEFVAL      { 0 }                   
    ::= { xcmHrDevPowerEntry 6 }
xcmHrDevPowerWarmUpDuration OBJECT-TYPE
    SYNTAX      Integer32
    MAX-ACCESS  read-create
    STATUS      current
    DESCRIPTION
        "A device 'warm up' feature duration,
        or zero if none, used by system administrators of this device.
        Usage:  The time after last 'warm up' initiation
        before the 'warm up' will complete (to power 'readyMode'
        in 'xcmHrDevInfoConditions')."
    REFERENCE
        "See:   'xcmHrDevPowerWarmUpSupport' for feature details
        and     'xcmHrDevPowerTimeUnit' for time unit
        and     'xcmHrDevInfoConditions' for device 'mode' conditions"
    DEFVAL      { 0 }                   
    ::= { xcmHrDevPowerEntry 7 }
xcmHrDevPowerCoolDownDelay OBJECT-TYPE
    SYNTAX      Integer32
    MAX-ACCESS  read-create
    STATUS      current
    DESCRIPTION
        "A device 'cool down' feature delay time,
        or zero if none, used by system administrators of this device.
        Usage:  The time delay after last 'cool down' trigger event
        (eg, completion of a job, some local user action, etc)
        before the 'cool down' cycle will begin (to power 'standbyMode'
        in 'xcmHrDevInfoConditions')."
    REFERENCE
        "See:   'xcmHrDevPowerCoolDownSupport' for feature details
        and     'xcmHrDevPowerTimeUnit' for time unit
        and     'xcmHrDevInfoConditions' for device 'mode' conditions"
    DEFVAL      { 0 }                   
    ::= { xcmHrDevPowerEntry 8 }
xcmHrDevPowerCoolDownDuration OBJECT-TYPE
    SYNTAX      Integer32
    MAX-ACCESS  read-create
    STATUS      current
    DESCRIPTION
        "A device 'cool down' feature duration,
        or zero if none, used by system administrators of this device.
        Usage:  The time after last 'cool down' initiation
        before the 'cool down' will complete (to power 'standbyMode'
        in 'xcmHrDevInfoConditions')."
    REFERENCE
        "See:   'xcmHrDevPowerCoolDownSupport' for feature details
        and     'xcmHrDevPowerTimeUnit' for time unit
        and     'xcmHrDevInfoConditions' for device 'mode' conditions"
    DEFVAL      { 0 }                   
    ::= { xcmHrDevPowerEntry 9 }
xcmHrDevPowerEnergySaveDelay OBJECT-TYPE
    SYNTAX      Integer32
    MAX-ACCESS  read-create
    STATUS      current
    DESCRIPTION
        "A device 'energy save' feature delay time,
        or zero if none, used by system administrators of this device.
        Usage:  The time delay after last 'energy save' trigger event
        (eg, completion of the last 'cool down' cycle to 'standbyMode')
        before the 'energy save' cycle will begin (to power 'sleepMode'
        in 'xcmHrDevInfoConditions')."
    REFERENCE
        "See:   'xcmHrDevPowerEnergySaveSupport' for feature details
        and     'xcmHrDevPowerTimeUnit' for time unit
        and     'xcmHrDevInfoConditions' for device 'mode' conditions"
    DEFVAL      { 0 }                   
    ::= { xcmHrDevPowerEntry 10 }
xcmHrDevPowerEnergySaveDuration OBJECT-TYPE
    SYNTAX      Integer32
    MAX-ACCESS  read-create
    STATUS      current
    DESCRIPTION
        "A device 'energy save' feature duration,
        or zero if none, used by system administrators of this device.
        Usage:  The time after last 'energy save' initiation
        before the 'energy save' will complete (to power 'sleepMode'
        in 'xcmHrDevInfoConditions')."
    REFERENCE
        "See:   'xcmHrDevPowerEnergySaveSupport' for feature details
        and     'xcmHrDevPowerTimeUnit' for time unit
        and     'xcmHrDevInfoConditions' for device 'mode' conditions"
    DEFVAL      { 0 }                   
    ::= { xcmHrDevPowerEntry 11 }
xcmHrDevPowerWakeUpSupport OBJECT-TYPE
    SYNTAX      PresentOnOff
    MAX-ACCESS  read-create
    STATUS      current
    DESCRIPTION
        "A device 'wake up' feature support management object,
        used by system administrators of this device.
        Usage:  This object specifies the support present (if any) for
        a device 'wake up' feature ('sleepMode' to 'standbyMode').
        For example, a photocopier might want to 'wake up' (as a system)
        (to 'standbyMode') some time after a user presses a button.
      * 'other(1)'
        - DEPRECATED - SHALL NOT be used by conforming implementations
      * 'on(3)'
        - device 'wake up' feature is present and enabled
        both '...WakeUpDelay' and '...WakeUpDuration' are used
        - if '...WakeUpDelay' is zero,
        then 'wake up' cycle begins immediately after trigger event
        - if '...WakeUpDelay' is non-zero,
        then 'wake up' cycle is delayed for specified time
        - if '...WakeUpDuration' is zero,
        then 'wake up' cycle completes immediately after initiation
        - if '...WakeUpDuration' is non-zero,
        then 'wake up' cycle requires specified time to complete
      * 'off(4)'
        - device 'wake up' feature is present but disabled
        both '...WakeUpDelay' and '...WakeUpDuration' NOT used
      * 'notPresent(5)'
        - device 'wake up' feature NOT present on this host system
        both '...WakeUpDelay' and '...WakeUpDuration' NOT used"
    REFERENCE
        "See:   'xcmHrDevPowerWakeUp[Delay|Duration]'"
    DEFVAL      { notPresent }          
    ::= { xcmHrDevPowerEntry 12 }
xcmHrDevPowerWakeUpDelay OBJECT-TYPE
    SYNTAX      Integer32
    MAX-ACCESS  read-create
    STATUS      current
    DESCRIPTION
        "A device 'wake up' feature delay time,
        or zero if none, used by system administrators of this device.
        Usage:  The time delay after last 'wake up' trigger event
        (eg, arrival of a job, some local user action, etc)
        before the 'wake up' cycle will begin (to power 'standbyMode'
        in 'xcmHrDevInfoConditions')."
    REFERENCE
        "See:   'xcmHrDevPowerWakeUpSupport' for feature details
        and     'xcmHrDevPowerTimeUnit' for time unit
        and     'xcmHrDevInfoConditions' for device 'mode' conditions"
    DEFVAL      { 0 }                   
    ::= { xcmHrDevPowerEntry 13 }
xcmHrDevPowerWakeUpDuration OBJECT-TYPE
    SYNTAX      Integer32
    MAX-ACCESS  read-create
    STATUS      current
    DESCRIPTION
        "A device 'wake up' feature duration,
        or zero if none, used by system administrators of this device.
        Usage:  The time after last 'wake up' initiation
        before the 'wake up' will complete (to power 'standbyMode'
        in 'xcmHrDevInfoConditions')."
    REFERENCE
        "See:   'xcmHrDevPowerWakeUpSupport' for feature details
        and     'xcmHrDevPowerTimeUnit' for time unit
        and     'xcmHrDevInfoConditions' for device 'mode' conditions"
    DEFVAL      { 0 }                   
    ::= { xcmHrDevPowerEntry 14 }
xcmHrDevPowerShutdownDelay OBJECT-TYPE
    SYNTAX      Integer32
    MAX-ACCESS  read-create
    STATUS      current
    DESCRIPTION
        "A device 'shutdown' feature delay time,
        or zero if none, used by system administrators of this device.
        Usage:  The time delay after last 'shutdown' trigger event
        (eg, completion of the last 'energy save' cycle to 'sleepMode')
        before the 'shutdown' cycle will begin (to power 'offMode'
        in 'xcmHrDevInfoConditions' and 'down' in 'hrDeviceStatus')."
    REFERENCE
        "See:   'xcmHrDevPowerTimeUnit' for time unit
        and     'xcmHrDevInfoConditions' for device 'mode' conditions"
    DEFVAL      { 0 }                   
    ::= { xcmHrDevPowerEntry 15 }
xcmHrDevPowerShutdownDuration OBJECT-TYPE
    SYNTAX      Integer32
    MAX-ACCESS  read-create
    STATUS      current
    DESCRIPTION
        "A device 'shutdown' feature duration,
        or zero if none, used by system administrators of this device.
        Usage:  The time after last 'shutdown' initiation
        before the 'shutdown' cycle will complete (to power 'offMode'
        in 'xcmHrDevInfoConditions' and 'down' in 'hrDeviceStatus')."
    REFERENCE
        "See:   'xcmHrDevPowerTimeUnit' for time unit
        and     'xcmHrDevInfoConditions' for device 'mode' conditions"
    DEFVAL      { 0 }                   
    ::= { xcmHrDevPowerEntry 16 }
xcmHrDevPowerStartupDelay OBJECT-TYPE
    SYNTAX      Integer32
    MAX-ACCESS  read-create
    STATUS      current
    DESCRIPTION
        "A device 'startup' feature delay time,
        or zero if none, used by system administrators of this device.
        Usage:  The time delay after last 'startup' trigger event
        (eg, 'xcmHrDevCalendarCommandRequest' or local user action)
        before the 'startup' cycle will begin (to power 'readyMode'
        in 'xcmHrDevInfoConditions' and 'running' in 'hrDeviceStatus')."
    REFERENCE
        "See:   'xcmHrDevPowerTimeUnit' for time unit
        and     'xcmHrDevInfoConditions' for device 'mode' conditions"
    DEFVAL      { 0 }                   
    ::= { xcmHrDevPowerEntry 17 }
xcmHrDevPowerStartupDuration OBJECT-TYPE
    SYNTAX      Integer32
    MAX-ACCESS  read-create
    STATUS      current
    DESCRIPTION
        "A device 'startup' feature duration,
        or zero if none, used by system administrators of this device.
        Usage:  The time after last 'startup' initiation
        before the 'startup' cycle will complete (to power 'readyMode'
        in 'xcmHrDevInfoConditions' and 'running' in 'hrDeviceStatus')."
    REFERENCE
        "See:   'xcmHrDevPowerTimeUnit' for time unit
        and     'xcmHrDevInfoConditions' for device 'mode' conditions"
    DEFVAL      { 0 }                   
    ::= { xcmHrDevPowerEntry 18 }
--
--
xcmHrDevTraffic     OBJECT IDENTIFIER ::= { xcmHrMIB 7 }
xcmHrDevTrafficTable OBJECT-TYPE
    SYNTAX      SEQUENCE OF XcmHrDevTrafficEntry
    MAX-ACCESS  not-accessible
    STATUS      current
    DESCRIPTION
        "A 'sparse' table containing traffic information objects for
        installed and (possibly) active devices on this host system,
        augmenting the basic entries in the 'hrDeviceTable' of the
        IETF Host Resources MIB (RFC 2790)."
    REFERENCE
        "See:   'hrProcessorTable', 'hrNetworkTable', 'hrPrinterTable'
                in the IETF Host Resources MIB (RFC 2790)."
    ::= { xcmHrDevTraffic 2 }
xcmHrDevTrafficEntry OBJECT-TYPE
    SYNTAX      XcmHrDevTrafficEntry
    MAX-ACCESS  not-accessible
    STATUS      current
    DESCRIPTION
        "A 'sparse' entry containing traffic information objects for
        an installed and (possibly) active device on this host system,
        augmenting a basic entry in the 'hrDeviceTable' of the
        IETF Host Resources MIB (RFC 2790)."
    INDEX       { hrDeviceIndex }
    ::= { xcmHrDevTrafficTable 1 }
XcmHrDevTrafficEntry ::= SEQUENCE {
        xcmHrDevTrafficRowStatus        RowStatus,
        xcmHrDevTrafficInputSupport     PresentOnOff,
        xcmHrDevTrafficOutputSupport    PresentOnOff,
        xcmHrDevTrafficInputUnit        XcmHrDevTrafficUnit,
        xcmHrDevTrafficOutputUnit       XcmHrDevTrafficUnit,
        xcmHrDevTrafficInputCount       Counter32,
        xcmHrDevTrafficOutputCount      Counter32,
        xcmHrDevTrafficInputMaxSize     Cardinal32,
        xcmHrDevTrafficOutputMaxSize    Cardinal32,
        xcmHrDevTrafficInputTimeout     Integer32,
        xcmHrDevTrafficOutputTimeout    Integer32
    }
xcmHrDevTrafficRowStatus OBJECT-TYPE
    SYNTAX      RowStatus
    MAX-ACCESS  read-create
    STATUS      current
    DESCRIPTION
        "This object manages the row status of this conceptual row in
        the 'xcmHrDevTrafficTable'.
        Usage:  Conforming implementations which support static rows
        SHALL support 'active' and 'notInService' writes to this
        'xcmHrDevTrafficRowStatus' row status object; and
        SHALL clear the 'xcmHrDevTrafficGroup' bit in
        'xcmHrGeneralCreateSupport' in the 'xcmHrGeneralTable'.
        Usage:  Conforming implementations which support dynamic rows
        SHALL support 'createAndGo' and 'destroy' writes to this
        'xcmHrDevTrafficRowStatus' row status object; and
        SHALL set the 'xcmHrDevTrafficGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevTrafficEntry 1 }
xcmHrDevTrafficInputSupport OBJECT-TYPE
    SYNTAX      PresentOnOff
    MAX-ACCESS  read-create
    STATUS      current
    DESCRIPTION
        "A device input traffic support management object,
        used by system administrators of this device.
        Usage:  This object specifies the support present (if any)
        for device input traffic (I/O).
        For example, a ROM only supports input traffic (ie, reads).
      * 'other(1)'
        - DEPRECATED - SHALL NOT be used by conforming implementations
      * 'on(3)'
        - device 'input I/O' feature is present and enabled
        and '...InputTimeout' is meaningful
        - if '...InputTimeout' is zero,
        then 'input I/O' cycle MAY proceed for an infinite time
        - if '...InputTimeout' is non-zero,
        then 'input I/O' cycle is limited to the specified time
      * 'off(4)'
        - device 'input I/O' feature is present but disabled
        and '...InputTimeout' is ignored
      * 'notPresent(5)'
        - device 'input I/O' feature NOT present on this host system
        and '...InputTimeout' is ignored"
    REFERENCE
        "See:   'xcmHrDevTrafficInputTimeout'."
    DEFVAL      { notPresent }          
    ::= { xcmHrDevTrafficEntry 2 }
xcmHrDevTrafficOutputSupport OBJECT-TYPE
    SYNTAX      PresentOnOff
    MAX-ACCESS  read-create
    STATUS      current
    DESCRIPTION
        "A device output traffic support management object,
        used by system administrators of this device.
        Usage:  This object specifies the support present (if any)
        for device output traffic (I/O).
        For example, a ROM does NOT support output traffic (ie, writes).
      * 'other(1)'
        - DEPRECATED - SHALL NOT be used by conforming implementations
      * 'on(3)'
        - device 'output I/O' feature is present and enabled
        and '...OutputTimeout' is meaningful
        - if '...OutputTimeout' is zero,
        then 'output I/O' cycle MAY proceed for an infinite time
        - if '...OutputTimeout' is non-zero,
        then 'output I/O' cycle is limited to the specified time
      * 'off(4)'
        - device 'output I/O' feature is present but disabled
        and '...OutputTimeout' is ignored
      * 'notPresent(5)'
        - device 'output I/O' feature NOT present on this host system
        and '...OutputTimeout' is ignored"
    REFERENCE
        "See:   'xcmHrDevTrafficOutputTimeout'."
    DEFVAL      { notPresent }          
    ::= { xcmHrDevTrafficEntry 3 }
xcmHrDevTrafficInputUnit OBJECT-TYPE
    SYNTAX      XcmHrDevTrafficUnit
    MAX-ACCESS  read-create
    STATUS      current
    DESCRIPTION
        "A device input unit, used by system administrators
        of this device for input traffic counters.
        Usage:  For example, a disk drive might use 'mediaBlock'.
        Usage:  Thanks to XCMI WG members for stimulating the following
        discussion.  There are three reasonable ways for using the
        'xcmHrDevTraffic[Input|Output]Unit' objects:  a) 'read-only' and
        set up by the management agent according to the sole appropriate
        (fixed) units at time of row creation; b) 'write-once' by the
        management station, at time of row creation (possibly selecting
        from among several possible valid units); and c) 'write-many' by
        the management station (to dynamically request the management
        agent to 'convert' the 'xcmHrDevTraffic[Input|Output]Count'
        objects into the appropriate units).  Conforming implementations
        need NOT support more than one of the above three scenarios.
        Usage:  'mediaImage' - SHOULD be used ONLY for softcopy
                INPUT page images (scan, copy, fax, etc.).
                'mediaImpression' - SHOULD be used ONLY for hardcopy
                OUTPUT page impressions (print, copy, fax, etc.)
                'mediaSheet' - SHOULD be used ONLY for hardcopy
                OUTPUT and does NOT always equal output pages
                (e.g., duplex or N-up printing)."
    DEFVAL      { unknown }             
    ::= { xcmHrDevTrafficEntry 4 }
xcmHrDevTrafficOutputUnit OBJECT-TYPE
    SYNTAX      XcmHrDevTrafficUnit
    MAX-ACCESS  read-create
    STATUS      current
    DESCRIPTION
        "A device output unit, used by system administrators
        of this device for output traffic counters.
        Usage:  For example, a terminal might use 'textLine'.
        Usage:  'mediaImage' - SHOULD be used ONLY for softcopy
                INPUT page images (scan, copy, fax, etc.).
                'mediaImpression' - SHOULD be used ONLY for hardcopy
                OUTPUT page impressions (print, copy, fax, etc.)
                'mediaSheet' - SHOULD be used ONLY for hardcopy
                OUTPUT and does NOT always equal output pages
                (e.g., duplex or N-up printing)."
    DEFVAL      { unknown }             
    ::= { xcmHrDevTrafficEntry 5 }
xcmHrDevTrafficInputCount OBJECT-TYPE
    SYNTAX      Counter32
    MAX-ACCESS  read-only
    STATUS      current
    DESCRIPTION
        "A device input traffic count, used by system administrators
        and end users of this device.
        Usage:  Although no default value ('DEFVAL' clause) is permitted
        (by IETF SMIv2) for this counter, conforming host systems SHALL
        zero this counter upon conceptual row creation."
    REFERENCE
        "See:   'hrDeviceErrors' in the Device group of the
                IETF Host Resources MIB (RFC 2790)."
    ::= { xcmHrDevTrafficEntry 6 }
xcmHrDevTrafficOutputCount OBJECT-TYPE
    SYNTAX      Counter32
    MAX-ACCESS  read-only
    STATUS      current
    DESCRIPTION
        "A device output traffic count, used by system administrators
        and end users of this device.
        Usage:  Although no default value ('DEFVAL' clause) is permitted
        (by IETF SMIv2) for this counter, conforming host systems SHALL
        zero this counter upon conceptual row creation."
    REFERENCE
        "See:   'hrDeviceErrors' in the Device group of the
            IETF Host Resources MIB (RFC 2790)."
    ::= { xcmHrDevTrafficEntry 7 }
xcmHrDevTrafficInputMaxSize OBJECT-TYPE
    SYNTAX      Cardinal32
    MAX-ACCESS  read-create
    STATUS      current
    DESCRIPTION
        "A device input maximum size, or zero if infinite,
        used by system administrators and end users of this device.
        Usage:  It is device specific how (or if) this limit object is
        used (eg, disk with 'xcmHrDevTrafficInputUnit' of 'mediaBlock'
        might limit block count of a single disk read to '50')."
    DEFVAL      { 0 }                   
    ::= { xcmHrDevTrafficEntry 8 }
xcmHrDevTrafficOutputMaxSize OBJECT-TYPE
    SYNTAX      Cardinal32
    MAX-ACCESS  read-create
    STATUS      current
    DESCRIPTION
        "A device output maximum size, or zero if infinite,
        used by system administrators and end users of this device.
        Usage:  It is device specific how (or if) this limit object is
        used (eg, disk with 'xcmHrDevTrafficOutputUnit' of 'mediaBlock'
        might limit block count of a single disk write to '50')."
    DEFVAL      { 0 }                   
    ::= { xcmHrDevTrafficEntry 9 }
xcmHrDevTrafficInputTimeout OBJECT-TYPE
    SYNTAX      Integer32
    UNITS       "seconds"
    MAX-ACCESS  read-create
    STATUS      current
    DESCRIPTION
        "A device input traffic timeout (in seconds),
        or zero if none, used by system administrators of this device.
        Usage:  This object specifies the timeout to be used (if any)
        for device input traffic (I/O).
        For example, a disk drive might want to timeout disk reads."
    REFERENCE
        "See:   'xcmHrDevTrafficInputSupport' for feature details
        and     'xcmHrDevInfoConditions' for device 'mode' conditions"
    DEFVAL      { 0 }                   
    ::= { xcmHrDevTrafficEntry 10 }
xcmHrDevTrafficOutputTimeout OBJECT-TYPE
    SYNTAX      Integer32
    UNITS       "seconds"
    MAX-ACCESS  read-create
    STATUS      current
    DESCRIPTION
        "A device output traffic timeout (in seconds),
        or zero if none, used by system administrators of this device.
        Usage:  This object specifies the timeout to be used (if any)
        for device output traffic (I/O).
        For example, a terminal might want to timeout screen writes."
    REFERENCE
        "See:   'xcmHrDevTrafficOutputSupport' for feature details
        and     'xcmHrDevInfoConditions' for device 'mode' conditions"
    DEFVAL      { 0 }                   
    ::= { xcmHrDevTrafficEntry 11 }
--
--
xcmHrSystemFault    OBJECT IDENTIFIER ::= { xcmHrMIB 8 }
xcmHrSystemFaultTable OBJECT-TYPE
    SYNTAX      SEQUENCE OF XcmHrSystemFaultEntry
    MAX-ACCESS  not-accessible
    STATUS      current
    DESCRIPTION
        "A table of the system faults which have been recorded
        (logged) on this host system.
        Usage:  Conforming implementations SHALL ensure that this
        table contains (up to) a product specific number of the most
        'recent' faults on this host system.
        Usage:  Conforming implementations which also implement Device
        Alert group, SHALL record in 'xcmHrDevAlertTable'
        each persistent system fault when it occurs and is recorded
        in 'xcmHrSystemFaultTable'.
        Usage:  Conforming implementations MAY 'age' older entries out
        of 'xcmHrSystemFaultTable' (by an algorithm outside the scope of
        XCMI specifications)."
    ::= { xcmHrSystemFault 2 }
xcmHrSystemFaultEntry OBJECT-TYPE
    SYNTAX      XcmHrSystemFaultEntry
    MAX-ACCESS  not-accessible
    STATUS      current
    DESCRIPTION
        "An entry for a system fault which has been recorded
        (logged) on this host system."
    INDEX       { xcmHrSystemFaultIndex }
    ::= { xcmHrSystemFaultTable 1 }
XcmHrSystemFaultEntry ::= SEQUENCE {
        xcmHrSystemFaultIndex           Ordinal32,
        xcmHrSystemFaultRowStatus       RowStatus,
        xcmHrSystemFaultCode            Integer32,
        xcmHrSystemFaultString          XcmFixedLocaleDisplayString,
        xcmHrSystemFaultReferenceOID    OBJECT IDENTIFIER,
        xcmHrSystemFaultHrDeviceIndex   Cardinal32,
        xcmHrSystemFaultDate            DateAndTime
    }
--
--
xcmHrSystemFaultIndex OBJECT-TYPE
    SYNTAX      Ordinal32
    MAX-ACCESS  not-accessible
    STATUS      current
    DESCRIPTION
        "A unique value used by this host system to identify this
        conceptual row in the 'xcmHrSystemFaultTable'.
        Usage:  Conforming implementations SHALL NOT 'reuse' values of
        'xcmHrSystemFaultIndex' until its' 32-bit value wraps.  Even in
        the case of eventual wrap, the entries SHALL be strictly
        sequenced by the associated value of 'xcmHrSystemFaultDate'.
        Usage:  Conforming implementations are strongly encouraged to
        preserve the last used value of 'xcmHrSystemFaultIndex' across
        system power cycles."
    ::= { xcmHrSystemFaultEntry 1 }
xcmHrSystemFaultRowStatus OBJECT-TYPE
    SYNTAX      RowStatus
    MAX-ACCESS  read-create
    STATUS      current
    DESCRIPTION
        "This object is used to create (by management agent) and delete
        (by management station and/or management agent) individual
        conceptual rows in the 'xcmHrSystemFaultTable'.
        Usage:  Conforming implementations which support static rows
        SHALL support 'active' and 'notInService' writes to this
        'xcmHrSystemFaultRowStatus' row status object; and
        SHALL clear the 'xcmHrSystemFaultGroup' bit in
        'xcmHrGeneralCreateSupport' in the 'xcmHrGeneralTable'.
        Usage:  Conforming implementations which support dynamic rows
        SHALL support 'createAndGo' and 'destroy' writes to this
        'xcmHrSystemFaultRowStatus' row status object; and
        SHALL set the 'xcmHrSystemFaultGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrSystemFaultEntry 2 }
xcmHrSystemFaultCode OBJECT-TYPE
    SYNTAX      Integer32
    MAX-ACCESS  read-only
    STATUS      current
    DESCRIPTION
        "Encoded fault code of the system fault which is
        recorded in this conceptual row in the 'xcmHrSystemFaultTable'."
    DEFVAL      { 0 }                   
    ::= { xcmHrSystemFaultEntry 3 }
xcmHrSystemFaultString OBJECT-TYPE
    SYNTAX      XcmFixedLocaleDisplayString (SIZE (0..255))
    MAX-ACCESS  read-only
    STATUS      current
    DESCRIPTION
        "Human-readable fault string of the system fault which is
        recorded in this conceptual row in the 'xcmHrSystemFaultTable'."
    DEFVAL      { ''H }                 
    ::= { xcmHrSystemFaultEntry 4 }
xcmHrSystemFaultReferenceOID OBJECT-TYPE
    SYNTAX      OBJECT IDENTIFIER
    MAX-ACCESS  read-only
    STATUS      current
    DESCRIPTION
        "An (optional) unambiguous system object reference
        (which MAY include instance suffix information),
        used by system administrators and end users to qualify
        this system fault.
        Usage:  Since this system object reference is specified
        as an object identifier, it MAY be taken from any IETF, Xerox,
        third- party, or product-specific MIB, or it MAY simply be any
        IETF SMIv2-style 'autonomous type'."
    DEFVAL      { zeroDotZero }   
    ::= { xcmHrSystemFaultEntry 5 }
xcmHrSystemFaultHrDeviceIndex OBJECT-TYPE
    SYNTAX      Cardinal32
    MAX-ACCESS  read-only
    STATUS      current
    DESCRIPTION
        "An (optional) device index (ie, value of 'hrDeviceIndex'),
        used by system administrators and end users to qualify
        this system fault."
    REFERENCE
        "See:   'hrDeviceIndex' and 'hrDeviceType' objects in the
        IETF Host Resources MIB (RFC 2790)."
    DEFVAL      { 0 }                   
    ::= { xcmHrSystemFaultEntry 6 }
xcmHrSystemFaultDate OBJECT-TYPE
    SYNTAX      DateAndTime
    MAX-ACCESS  read-only
    STATUS      current
    DESCRIPTION
        "The time stamp for the system fault which is
        recorded in this conceptual row in the 'xcmHrSystemFaultTable'."
    DEFVAL      { '0000000000000000'H } 
    ::= { xcmHrSystemFaultEntry 7 }
--
--
xcmHrDevCalendar    OBJECT IDENTIFIER ::= { xcmHrMIB 10 }
xcmHrDevCalendarTable OBJECT-TYPE
    SYNTAX      SEQUENCE OF XcmHrDevCalendarEntry
    MAX-ACCESS  not-accessible
    STATUS      current
    DESCRIPTION
        "A 'sparse' table containing calendar management objects for
        installed and (possibly) active devices on this host system,
        augmenting the basic entries in the 'hrDeviceTable' of the
        IETF Host Resources MIB (RFC 2790)."
    ::= { xcmHrDevCalendar 2 }
xcmHrDevCalendarEntry OBJECT-TYPE
    SYNTAX      XcmHrDevCalendarEntry
    MAX-ACCESS  not-accessible
    STATUS      current
    DESCRIPTION
        "A 'sparse' entry containing calendar management objects for
        an installed and (possibly) active device on this host system,
        augmenting a basic entry in the 'hrDeviceTable' of the
        IETF Host Resources MIB (RFC 2790)."
    INDEX       { hrDeviceIndex,
                  xcmHrDevCalendarDayOfWeek,
                  xcmHrDevCalendarTimeOfDay }
    ::= { xcmHrDevCalendarTable 1 }
XcmHrDevCalendarEntry ::= SEQUENCE {
        xcmHrDevCalendarDayOfWeek       XcmHrDevCalendarDayOfWeek,
        xcmHrDevCalendarTimeOfDay       XcmHrDevCalendarTimeOfDay,
        xcmHrDevCalendarRowStatus       RowStatus,
        xcmHrDevCalendarExplicitDate    DateAndTime,
        xcmHrDevCalendarCommandRequest  XcmHrDevMgmtCommandRequest,
        xcmHrDevCalendarCommandData     XcmHrDevMgmtCommandData
    }
xcmHrDevCalendarDayOfWeek OBJECT-TYPE
    SYNTAX      XcmHrDevCalendarDayOfWeek
    MAX-ACCESS  not-accessible
    STATUS      current
    DESCRIPTION
        "The day of week when the command specified in this conceptual
        row in the 'xcmHrDevCalendarTable' SHALL be invoked."
    ::= { xcmHrDevCalendarEntry 1 }
xcmHrDevCalendarTimeOfDay OBJECT-TYPE
    SYNTAX      XcmHrDevCalendarTimeOfDay
    MAX-ACCESS  not-accessible
    STATUS      current
    DESCRIPTION
        "The time of day when the command specified in this conceptual
        row in the 'xcmHrDevCalendarTable' SHALL be invoked, specified
        as hours (0..23) multiplied by 100, added to minutes (0..59),
        added to a constant bias of 10000 (avoids an index value of zero
        in 'xcmHrDevCalendarTimeOfDay')."
    ::= { xcmHrDevCalendarEntry 2 }
xcmHrDevCalendarRowStatus OBJECT-TYPE
    SYNTAX      RowStatus
    MAX-ACCESS  read-create
    STATUS      current
    DESCRIPTION
        "This object manages the row status of this conceptual row in
        the 'xcmHrDevCalendarTable'.
        Usage:  Conforming implementations which support static rows
        SHALL support 'active' and 'notInService' writes to this
        'xcmHrDevCalendarRowStatus' row status object; and
        SHALL clear the 'xcmHrDevCalendarGroup' bit in
        'xcmHrGeneralCreateSupport' in the 'xcmHrGeneralTable'.
        Usage:  Conforming implementations which support dynamic rows
        SHALL support 'createAndGo' and 'destroy' writes to this
        'xcmHrDevCalendarRowStatus' row status object; and
        SHALL set the 'xcmHrDevCalendarGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevCalendarEntry 3 }
xcmHrDevCalendarExplicitDate OBJECT-TYPE
    SYNTAX      DateAndTime
    MAX-ACCESS  read-create
    STATUS      current
    DESCRIPTION
        "The explicit date when the command specified in this conceptual
        row in the 'xcmHrDevCalendarTable' SHALL be invoked.
        Usage:  When 'xcmHrDevCalendarExplicitDate' is used, the value
        of 'xcmHrDevCalendarDayOfWeek' SHALL be 'everyDay' and the value
        of 'xcmHrDevCalendarTimeOfDay' SHALL be arbitrary (to provide
        uniqueness for this conceptual row)."
    DEFVAL      { '0000000000000000'H } 
    ::= { xcmHrDevCalendarEntry 4 }
xcmHrDevCalendarCommandRequest OBJECT-TYPE
    SYNTAX      XcmHrDevMgmtCommandRequest
    MAX-ACCESS  read-create
    STATUS      current
    DESCRIPTION
        "The management command request specified in this conceptual
        row in the 'xcmHrDevCalendarTable', which SHALL be invoked based
        on 'xcmHrDevCalendarDayOfWeek', 'xcmHrDevCalendarTimeOfDay', and
        (optionally) 'xcmHrDevCalendarExplicitDate'."
    REFERENCE
        "See:   'hrDeviceStatus' in the Device group of the
                IETF Host Resources MIB (RFC 2790).
        See:    'xcmHrDevCalendarCommandData'"
    DEFVAL      { none }                
    ::= { xcmHrDevCalendarEntry 5 }
xcmHrDevCalendarCommandData OBJECT-TYPE
    SYNTAX      XcmHrDevMgmtCommandData
    MAX-ACCESS  read-create
    STATUS      current
    DESCRIPTION
        "The management command data specified in this conceptual
        row in the 'xcmHrDevCalendarTable', which SHALL be invoked based
        on 'xcmHrDevCalendarDayOfWeek', 'xcmHrDevCalendarTimeOfDay', and
        (optionally) 'xcmHrDevCalendarExplicitDate'.
        Usage:  Conformant implementations MUST encrypt passwords, keys,
        and other security information stored in this string object."
    REFERENCE
        "See:   Security Config, Account, and User groups in
                XCMI Security MIB.
        See:    Section 6.6 'Security in DPA' (pages 38 to 39) of
                DPA (ISO 10175-1 / Final Text, March 1996).
        See:    'hrDeviceStatus' in the Device group of the
                IETF Host Resources MIB (RFC 2790).
        See:    'xcmHrDevCalendarCommandRequest'"
    DEFVAL      { ''H }                 
    ::= { xcmHrDevCalendarEntry 6 }
--
--
xcmHrSWRun          OBJECT IDENTIFIER ::= { xcmHrMIB 11 }
xcmHrSWRunTable OBJECT-TYPE
    SYNTAX      SEQUENCE OF XcmHrSWRunEntry
    MAX-ACCESS  not-accessible
    STATUS      current
    DESCRIPTION
        "A 'sparse' table containing software info objects for
        loaded and (possibly) active software on this host system,
        augmenting the basic entries in the 'hrSWRunTable' of the
        IETF Host Resources MIB (RFC 2790)."
    ::= { xcmHrSWRun 2 }
xcmHrSWRunEntry OBJECT-TYPE
    SYNTAX      XcmHrSWRunEntry
    MAX-ACCESS  not-accessible
    STATUS      current
    DESCRIPTION
        "A 'sparse' entry containing software info objects for
        loaded and (possibly) active software on this host system,
        augmenting a basic entry in the 'hrSWRunTable' of the
        IETF Host Resources MIB (RFC 2790)."
    INDEX       { hrSWRunIndex }
    ::= { xcmHrSWRunTable 1 }
XcmHrSWRunEntry ::= SEQUENCE {
        xcmHrSWRunRowStatus             RowStatus,
        xcmHrSWRunAdminName             XcmFixedLocaleDisplayString,
        xcmHrSWRunXStatus               XcmHrSWRunXStatus,
        xcmHrSWRunRowCreateDate         DateAndTime,
        xcmHrSWRunPhysicalDeviceIndex   Cardinal32,
        xcmHrSWRunLogicalDeviceIndex    Cardinal32,
        xcmHrSWRunNextIndex             Cardinal32,
        xcmHrSWRunPreviousIndex         Cardinal32
    }
xcmHrSWRunRowStatus OBJECT-TYPE
    SYNTAX      RowStatus
    MAX-ACCESS  read-create
    STATUS      current
    DESCRIPTION
        "This object manages the row status of this conceptual row in
        the 'xcmHrSWRunTable' and ALSO manages the row status
        of the associated conceptual row in the 'hrSWRunTable'
        of the IETF Host Resources MIB.
        Usage:  Conforming implementations which support static rows
        SHALL support 'active' and 'notInService' writes to this
        'xcmHrSWRunRowStatus' row status object; and
        SHALL clear the 'xcmHrSWRunGroup' bit in
        'xcmHrGeneralCreateSupport' in the 'xcmHrGeneralTable'.
        Usage:  Conforming implementations which support dynamic rows
        SHALL support 'createAndGo' and 'destroy' writes to this
        'xcmHrSWRunRowStatus' row status object; and
        SHALL set the 'xcmHrSWRunGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrSWRunEntry 1 }
xcmHrSWRunAdminName OBJECT-TYPE
    SYNTAX      XcmFixedLocaleDisplayString (SIZE (0..255))
    MAX-ACCESS  read-create
    STATUS      current
    DESCRIPTION
        "Human-readable software name, used by system administrators
        and end users to identify this software for systems management.
        Usage:  This software name SHALL be the one normally used in a
        CLI/GUI/API for control of this software.
        Note:   The 'hrSWRunName' object in 'hrSWRunTable'
        of the IETF Host Resources MIB (RFC 2790) has MANDATORY content
        of 'manufacturer, revision, and the name by which [the software]
        is commonly known'.  Thus, conforming implementations SHALL NOT
        set a 'simple name' into 'hrSWRunName'.  Therefore, this
        'xcmHrSWRunAdminName' object is needed for management."
    REFERENCE
        "See:   'hrSWRunName' in the Software Running Group
        of the IETF Host Resources MIB (RFC 2790)."
    DEFVAL      { ''H }                 
    ::= { xcmHrSWRunEntry 2 }
xcmHrSWRunXStatus OBJECT-TYPE
    SYNTAX      XcmHrSWRunXStatus
    MAX-ACCESS  read-only
    STATUS      current
    DESCRIPTION
        "An extended software status, used by system administrators and
        end users of this software (here, read 'state' for 'status').
        Note:   This extended software status is present for future
        extensions."
    REFERENCE
        "See:   'hrSWRunStatus' in the Software Running Group
        of the IETF Host Resources MIB (RFC 2790)."
    ::= { xcmHrSWRunEntry 3 }
xcmHrSWRunRowCreateDate OBJECT-TYPE
    SYNTAX      DateAndTime
    MAX-ACCESS  read-only
    STATUS      current
    DESCRIPTION
        "The date and time when this conceptual row was created."
    DEFVAL      { '0000000000000000'H } 
    ::= { xcmHrSWRunEntry 4 }
xcmHrSWRunPhysicalDeviceIndex OBJECT-TYPE
    SYNTAX      Cardinal32
    MAX-ACCESS  read-create
    STATUS      current
    DESCRIPTION
        "The value of 'hrDeviceIndex' corresponding to the first
        associated conceptual row in the 'hrDeviceTable' representing
        a supported and (possibly) ready 'physical' device, which has
        'xcmHrDevInfoRealization' of 'physical' or 'logicalAndPhysical',
        or zero, if there is no supported and subordinate 'physical'
        device associated with this row (ie, this running software)."
    REFERENCE
        "See:   'hrDeviceIndex' in the Device group of the
                IETF Host Resources MIB (RFC 2790).
        See:    Section 9.5.6 'Physical-printers-supported' of
                DPA (ISO 10175-1, Final Text, March 1996)."
    DEFVAL      { 0 }                   
    ::= { xcmHrSWRunEntry 5 }
xcmHrSWRunLogicalDeviceIndex OBJECT-TYPE
    SYNTAX      Cardinal32
    MAX-ACCESS  read-create
    STATUS      current
    DESCRIPTION
        "The value of 'hrDeviceIndex' corresponding to the first
        associated conceptual row in the 'hrDeviceTable' representing
        a supported and (possibly) ready 'logical' device, which has
        'xcmHrDevInfoRealization' of 'logical' or 'logicalAndPhysical',
        or zero, if there is no supported and subordinate 'logical'
        device associated with this row (ie, this running software)."
    REFERENCE
        "See:   'hrDeviceIndex' in the Device group of the
                IETF Host Resources MIB (RFC 2790).
        See:    Section 9.5.8 'Logical-printers-supported' of
                DPA (ISO 10175-1, Final Text, March 1996)."
    DEFVAL      { 0 }                   
    ::= { xcmHrSWRunEntry 6 }
xcmHrSWRunNextIndex OBJECT-TYPE
    SYNTAX      Cardinal32
    MAX-ACCESS  read-create
    STATUS      current
    DESCRIPTION
        "The value of 'hrSWRunIndex' corresponding to the next
        associated row in the 'hrSWRunTable', or zero if this is
        the last associated conceptual row in a given set."
    DEFVAL      { 0 }                   
    ::= { xcmHrSWRunEntry 7 }
xcmHrSWRunPreviousIndex OBJECT-TYPE
    SYNTAX      Cardinal32
    MAX-ACCESS  read-create
    STATUS      current
    DESCRIPTION
        "The value of 'hrSWRunIndex' corresponding to the previous
        associated row in the 'hrSWRunTable', or zero if this is
        the first associated conceptual row in a given set."
    DEFVAL      { 0 }                   
    ::= { xcmHrSWRunEntry 8 }
--
--
xcmHrSWInstalled    OBJECT IDENTIFIER ::= { xcmHrMIB 12 }
xcmHrSWInstalledTable OBJECT-TYPE
    SYNTAX      SEQUENCE OF XcmHrSWInstalledEntry
    MAX-ACCESS  not-accessible
    STATUS      current
    DESCRIPTION
        "A 'sparse' table containing software info objects for
        installed and (possibly) active software on this host system,
        augmenting the basic entries in the 'hrSWInstalledTable' of the
        IETF Host Resources MIB (RFC 2790)."
    ::= { xcmHrSWInstalled 2 }
xcmHrSWInstalledEntry OBJECT-TYPE
    SYNTAX      XcmHrSWInstalledEntry
    MAX-ACCESS  not-accessible
    STATUS      current
    DESCRIPTION
        "A 'sparse' entry containing software info objects for
        installed and (possibly) active software on this host system,
        augmenting a basic entry in the 'hrSWInstalledTable' of the
        IETF Host Resources MIB (RFC 2790)."
    INDEX       { hrSWInstalledIndex }
    ::= { xcmHrSWInstalledTable 1 }
XcmHrSWInstalledEntry ::= SEQUENCE {
        xcmHrSWInstalledRowStatus       RowStatus,
        xcmHrSWInstalledAdminName       XcmFixedLocaleDisplayString,
        xcmHrSWInstalledXStatus         XcmHrSWRunXStatus,
        xcmHrSWInstalledRowCreateDate   DateAndTime,
        xcmHrSWInstalledPhysicalIndex   Cardinal32,
        xcmHrSWInstalledLogicalIndex    Cardinal32,
        xcmHrSWInstalledNextIndex       Cardinal32,
        xcmHrSWInstalledPreviousIndex   Cardinal32
    }
xcmHrSWInstalledRowStatus OBJECT-TYPE
    SYNTAX      RowStatus
    MAX-ACCESS  read-create
    STATUS      current
    DESCRIPTION
        "This object manages the row status of this conceptual row in
        the 'xcmHrSWInstalledTable' and ALSO manages the row status
        of the associated conceptual row in the 'hrSWInstalledTable'
        of the IETF Host Resources MIB (RFC 2790).
        Usage:  Conforming implementations which support static rows
        SHALL support 'active' and 'notInService' writes to this
        'xcmHrSWInstalledRowStatus' row status object; and
        SHALL clear the 'xcmHrSWInstalledGroup' bit in
        'xcmHrGeneralCreateSupport' in the 'xcmHrGeneralTable'.
        Usage:  Conforming implementations which support dynamic rows
        SHALL support 'createAndGo' and 'destroy' writes to this
        'xcmHrSWInstalledRowStatus' row status object; and
        SHALL set the 'xcmHrSWInstalledGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrSWInstalledEntry 1 }
xcmHrSWInstalledAdminName OBJECT-TYPE
    SYNTAX      XcmFixedLocaleDisplayString (SIZE (0..255))
    MAX-ACCESS  read-create
    STATUS      current
    DESCRIPTION
        "Human-readable software name, used by system administrators
        and end users to identify this software for systems management.
        Usage:  This software name SHALL be the one normally used in a
        CLI/GUI/API for control of this software.
        Note:   The 'hrSWInstalledName' object in 'hrSWInstalledTable'
        of the IETF Host Resources MIB (RFC 2790) has MANDATORY content
        of 'manufacturer, revision, and the name by which [the software]
        is commonly known'.  Thus, conforming implementations SHALL NOT
        set a 'simple name' into 'hrSWInstalledName'.  Therefore, this
        'xcmHrSWInstalledAdminName' object is needed for management."
    REFERENCE
        "See:   'hrSWInstalledName' in the Software Installed Group
        of the IETF Host Resources MIB (RFC 2790)."
    DEFVAL      { ''H }                 
    ::= { xcmHrSWInstalledEntry 2 }
xcmHrSWInstalledXStatus OBJECT-TYPE
    SYNTAX      XcmHrSWRunXStatus
    MAX-ACCESS  read-only
    STATUS      current
    DESCRIPTION
        "An extended software status, used by system administrators and
        end users of this software (here, read 'state' for 'status').
        Note:   This extended software status is present for future
        extensions."
    REFERENCE
        "See:   'hrSWRunStatus' in the Software Running Group
        of the IETF Host Resources MIB (RFC 2790)."
    ::= { xcmHrSWInstalledEntry 3 }
xcmHrSWInstalledRowCreateDate OBJECT-TYPE
    SYNTAX      DateAndTime
    MAX-ACCESS  read-only
    STATUS      current
    DESCRIPTION
        "The date and time when this conceptual row was created."
    DEFVAL      { '0000000000000000'H } 
    ::= { xcmHrSWInstalledEntry 4 }
xcmHrSWInstalledPhysicalIndex OBJECT-TYPE
    SYNTAX      Cardinal32
    MAX-ACCESS  read-create
    STATUS      current
    DESCRIPTION
        "The value of 'hrDeviceIndex' corresponding to the first
        associated conceptual row in the 'hrDeviceTable' representing
        a supported and (possibly) ready 'physical' device, which has
        'xcmHrDevInfoRealization' of 'physical' or 'logicalAndPhysical',
        or zero, if there is no supported and subordinate 'physical'
        device associated with this row (ie, this installed software)."
    REFERENCE
        "See:   'hrDeviceIndex' in the Device group of the
                IETF Host Resources MIB (RFC 2790).
        See:    Section 9.5.6 'Physical-printers-supported' of
                DPA (ISO 10175-1, Final Text, March 1996)."
    DEFVAL      { 0 }                   
    ::= { xcmHrSWInstalledEntry 5 }
xcmHrSWInstalledLogicalIndex OBJECT-TYPE
    SYNTAX      Cardinal32
    MAX-ACCESS  read-create
    STATUS      current
    DESCRIPTION
        "The value of 'hrDeviceIndex' corresponding to the first
        associated conceptual row in the 'hrDeviceTable' representing
        a supported and (possibly) ready 'logical' device, which has
        'xcmHrDevInfoRealization' of 'logical' or 'logicalAndPhysical',
        or zero, if there is no supported and subordinate 'logical'
        device associated with this row (ie, this installed software)."
    REFERENCE
        "See:   'hrDeviceIndex' in the Device group of the
                IETF Host Resources MIB (RFC 2790).
        See:    Section 9.5.8 'Logical-printers-supported' of
                DPA (ISO 10175-1, Final Text, March 1996)."
    DEFVAL      { 0 }                   
    ::= { xcmHrSWInstalledEntry 6 }
xcmHrSWInstalledNextIndex OBJECT-TYPE
    SYNTAX      Cardinal32
    MAX-ACCESS  read-create
    STATUS      current
    DESCRIPTION
        "The value of 'hrSWInstalledIndex' corresponding to the next
        associated row in the 'hrSWInstalledTable', or zero if this is
        the last associated conceptual row in a given set."
    DEFVAL      { 0 }                   
    ::= { xcmHrSWInstalledEntry 7 }
xcmHrSWInstalledPreviousIndex OBJECT-TYPE
    SYNTAX      Cardinal32
    MAX-ACCESS  read-create
    STATUS      current
    DESCRIPTION
        "The value of 'hrSWInstalledIndex' corresponding to the previous
        associated row in the 'hrSWInstalledTable', or zero if this is
        the first associated conceptual row in a given set."
    DEFVAL      { 0 }                   
    ::= { xcmHrSWInstalledEntry 8 }
--
--
xcmHrDevDetail      OBJECT IDENTIFIER ::= { xcmHrMIB 13 }
xcmHrDevDetailTable OBJECT-TYPE
    SYNTAX      SEQUENCE OF XcmHrDevDetailEntry
    MAX-ACCESS  not-accessible
    STATUS      current
    DESCRIPTION
        "A 'sparse' table containing device detail information for
        installed and (possibly) active devices on this host system,
        augmenting the basic entries in the 'hrDeviceTable' of the
        IETF Host Resources MIB (RFC 2790).
        Usage:  UNLIKE the 'xcmGenOptionTable' in the XCMI General MIB
        (which is a unique exception), this table of 'dictionary-based'
        device details is used with DIRECT create/update operations."
    REFERENCE
        "See:   'hrProcessorTable', 'hrNetworkTable', 'hrPrinterTable'
                in the IETF Host Resources MIB (RFC 2790)."
    ::= { xcmHrDevDetail 2 }
xcmHrDevDetailEntry OBJECT-TYPE
    SYNTAX      XcmHrDevDetailEntry
    MAX-ACCESS  not-accessible
    STATUS      current
    DESCRIPTION
        "A 'sparse' entry containing device detail information for
        an installed and (possibly) active device on this host system,
        augmenting a basic entry in the 'hrDeviceTable' of the
        IETF Host Resources MIB (RFC 2790).
        Usage:  An entry in this table MAY be used to store specialized
        information for a device, such as 'lifetime' information for a
        CRU ('customer replaceable unit'), eg, a paper tray feed head."
    INDEX       { hrDeviceIndex,
                  xcmHrDevDetailType,
                  xcmHrDevDetailIndex }
    ::= { xcmHrDevDetailTable 1 }
XcmHrDevDetailEntry ::= SEQUENCE {
        xcmHrDevDetailType              XcmHrDevDetailType,
        xcmHrDevDetailIndex             Ordinal32,
        xcmHrDevDetailRowStatus         RowStatus,
        xcmHrDevDetailUnitClass         XcmHrDevDetailUnitClass,
        xcmHrDevDetailUnit              Cardinal32,
        xcmHrDevDetailValueInteger      Integer32,
        xcmHrDevDetailValueOID          OBJECT IDENTIFIER,
        xcmHrDevDetailValueString       OCTET STRING, 
        xcmHrDevDetailDescription       XcmFixedLocaleDisplayString 
    }
xcmHrDevDetailType OBJECT-TYPE
    SYNTAX      XcmHrDevDetailType
    MAX-ACCESS  read-only
    STATUS      current
    DESCRIPTION
        "The type of the device detail information specified
        in this conceptual row in the 'xcmHrDevDetailTable'."
    ::= { xcmHrDevDetailEntry 1 }
xcmHrDevDetailIndex OBJECT-TYPE
    SYNTAX      Ordinal32
    MAX-ACCESS  read-only
    STATUS      current
    DESCRIPTION
        "A unique value used by this host system to identify this
        conceptual row in the 'xcmHrDevDetailTable', OR a common
        value shared across a set of related conceptual rows (with
        different values of 'xcmHrDevDetailType'.
        Usage:  For device detail types which are single-valued, this
        index SHALL be used to correlate related single-valued details.
        Usage:  For device detail types which are multi-valued, this
        index SHALL be used to enumerate lists of multi-valued details."
    ::= { xcmHrDevDetailEntry 2 }
xcmHrDevDetailRowStatus OBJECT-TYPE
    SYNTAX      RowStatus
    MAX-ACCESS  read-create
    STATUS      current
    DESCRIPTION
        "This object manages the row status of this conceptual row in
        in the 'xcmHrDevDetailTable'.
        Usage:  Conforming implementations which support static rows
        SHALL support 'active' and 'notInService' writes to this
        'xcmHrDevDetailRowStatus' row status object; and
        SHALL clear the 'xcmHrDevDetailGroup' bit in
        'xcmHrGeneralCreateSupport' in the 'xcmHrGeneralTable'.
        Usage:  Conforming implementations which support dynamic rows
        SHALL support 'createAndGo' and 'destroy' writes to this
        'xcmHrDevDetailRowStatus' row status object; and
        SHALL set the 'xcmHrDevDetailGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevDetailEntry 3 }
xcmHrDevDetailUnitClass OBJECT-TYPE
    SYNTAX      XcmHrDevDetailUnitClass
    MAX-ACCESS  read-create
    STATUS      current
    DESCRIPTION
        "The value unit class of the detail information specified
        in this conceptual row in the 'xcmHrDevDetailTable'.
        Usage:  Used to select a textual convention for specifying the
        value unit of this device detail.
        Usage:  The 'xcmHrDevDetail[UnitClass|Class]' objects
        are used to specify the value syntax AND the value unit of the
        'xcmHrDevDetail[Integer|OID|String]' value objects."
    REFERENCE
        "See:   'xcmHrDevDetailUnit'"
    DEFVAL      { unknown }             
    ::= { xcmHrDevDetailEntry 4 }
xcmHrDevDetailUnit OBJECT-TYPE
    SYNTAX      Cardinal32
    MAX-ACCESS  read-create
    STATUS      current
    DESCRIPTION
        "The value unit of the detail information specified
        in this conceptual row in the 'xcmHrDevDetailTable'.
        Usage:  Used to select an enumerated choice from a textual
        convention to specify the value unit of this device detail.
        Usage:  The 'xcmHrDevDetail[UnitClass|Class]' objects
        are used to specify the value syntax AND the value unit of the
        'xcmHrDevDetail[Integer|OID|String]' value objects."
    REFERENCE
        "See:   'xcmHrDevDetailUnitClass'"
    DEFVAL      { 0 }                   
    ::= { xcmHrDevDetailEntry 5 }
xcmHrDevDetailValueInteger OBJECT-TYPE
    SYNTAX      Integer32
    MAX-ACCESS  read-create
    STATUS      current
    DESCRIPTION
        "A device detail value integer,
        used by system administrators and end users to specify
        the current value for a device detail
        with a base value syntax of 'INTEGER'."
    REFERENCE
        "See:   'xcmHrDevDetailValueOID' and
                'xcmHrDevDetailValueString'
        See:    'xcmHrDevDetailUnitClass' and
                'xcmHrDevDetailUnit' for syntax of detail value"
    DEFVAL      { 0 }                   
    ::= { xcmHrDevDetailEntry 6 }
xcmHrDevDetailValueOID OBJECT-TYPE
    SYNTAX      OBJECT IDENTIFIER
    MAX-ACCESS  read-create
    STATUS      current
    DESCRIPTION
        "A device detail value OID (object identifier),
        used by system administrators and end users to specify
        the current value for a device detail
        with a base value syntax of 'OBJECT IDENTIFIER'."
    REFERENCE
        "See:   'xcmHrDevDetailValueInteger' and
                'xcmHrDevDetailValueString'
        See:    'xcmHrDevDetailUnitClass' and
                'xcmHrDevDetailUnit' for syntax of detail value"
    DEFVAL      { zeroDotZero }   
    ::= { xcmHrDevDetailEntry 7 }
xcmHrDevDetailValueString OBJECT-TYPE
    SYNTAX      OCTET STRING (SIZE (0..255))
    MAX-ACCESS  read-create
    STATUS      current
    DESCRIPTION
        "A device detail value string,
        used by system administrators and end users to specify
        the current value for a device detail
        with a base value syntax of 'OCTET STRING'.
        Usage:  This object is of type 'XcmFixedLocaleDisplayString'.
        Usage:  Conformant implementations MUST encrypt passwords, keys,
        and other security information stored in this string object."
    REFERENCE
        "See:   'xcmHrDevDetailValueInteger' and
                'xcmHrDevDetailValueOID'
        See:    'xcmHrDevDetailUnitClass' and
                'xcmHrDevDetailUnit' for syntax of detail value"
    DEFVAL      { ''H }                 
    ::= { xcmHrDevDetailEntry 8 }
xcmHrDevDetailDescription OBJECT-TYPE 
    SYNTAX      XcmFixedLocaleDisplayString (SIZE (0..255)) 
    MAX-ACCESS  read-create 
    STATUS      current 
    DESCRIPTION 
       "This object is used to provide a description of the 
       detail. It is NOT expected to be parsed by the management
       application." 
 ::= { xcmHrDevDetailEntry 9 } 
xcmHrDevDetailV1EventOID OBJECT-IDENTITY
    STATUS      current
    DESCRIPTION
        "The value of the enterprise-specific OID in an SNMPv1 trap sent
        whenever a device detail usage or time limit is reached.
        See SNMPv2 trap definition 'xcmHrDevDetailV2Event'
        below for 'special semantics'."
    ::= { xcmHrDevDetail 1 }
xcmHrDevDetailV2EventPrefix
    OBJECT IDENTIFIER ::= { xcmHrDevDetailV1EventOID 0 }
xcmHrDevDetailV2Event NOTIFICATION-TYPE
    OBJECTS {
        hrDeviceIndex,
        xcmHrDevDetailType,
        xcmHrDevDetailIndex
    }
    STATUS      current
    DESCRIPTION
        "This trap is sent when 'xcmHrDevDetailIndex' is shared
        between a counter detail and a limit detail which are
        specified in 'xcmHrDevDetailValueInteger', OR
        when 'xcmHrDevDetailValueString' specifies a trigger date.
        Note:   The variable-bindings of this trap have been chosen to
        specify a complete device status change while keeping
        trap messages reasonably concise (generally a few hundred octets
        at most).
        This notification has the following special semantics:
            o   The detail's 'hrDeviceIndex' value,
                the detail's 'xcmHrDevDetailType' value, and
                the detail's 'xcmHrDevDetailIndex' value
                SHALL be appended to this trap object ID,
                as a BER binary OID suffix.
        This trap OID qualifier allows device management/monitoring
        applications to limit the alerts they receive to ones generated
        by device details of interest."
    ::= { xcmHrDevDetailV2EventPrefix 1 }
--
--          "This trap is sent when 'xcmHrDevDetailIndex' is shared
--          above for 'special semantics'."
--
--
xcmHrStorage        OBJECT IDENTIFIER ::= { xcmHrMIB 14 }
xcmHrStorageTable OBJECT-TYPE
    SYNTAX      SEQUENCE OF XcmHrStorageEntry
    MAX-ACCESS  not-accessible
    STATUS      current
    DESCRIPTION
        "A 'sparse' table containing storage info objects for
        'logical' or 'physical' storage elements on this host system,
        augmenting the basic entries in the 'hrStorageTable' of the
        IETF Host Resources MIB (RFC 2790)."
    ::= { xcmHrStorage 2 }
xcmHrStorageEntry OBJECT-TYPE
    SYNTAX      XcmHrStorageEntry
    MAX-ACCESS  not-accessible
    STATUS      current
    DESCRIPTION
        "A 'sparse' entry containing storage info objects for
        a 'logical' or 'physical' storage element on this host system,
        augmenting a basic entry in the 'hrStorageTable' of the
        IETF Host Resources MIB (RFC 2790)."
    INDEX       { hrStorageIndex }
    ::= { xcmHrStorageTable 1 }
XcmHrStorageEntry ::= SEQUENCE {
        xcmHrStorageRowStatus           RowStatus,
        xcmHrStorageRealization         XcmHrStorageRealization,
        xcmHrStorageStatus              XcmHrDevInfoStatus,
        xcmHrStorageProductDeviceIndex  Cardinal32,
        xcmHrStoragePlatformDeviceIndex Cardinal32,
        xcmHrStoragePagingDeviceIndex   Cardinal32,
        xcmHrStorageMatchingDeviceIndex Cardinal32,
        xcmHrStorageSWRunIndex          Cardinal32,
        xcmHrStorageSWInstalledIndex    Cardinal32,
        xcmHrStorageNextIndex           Cardinal32,
        xcmHrStoragePreviousIndex       Cardinal32,
        xcmHrStoragePhysicalIndex       Cardinal32
    }
xcmHrStorageRowStatus OBJECT-TYPE
    SYNTAX      RowStatus
    MAX-ACCESS  read-create
    STATUS      current
    DESCRIPTION
        "This object manages the row status of this conceptual row in
        the 'xcmHrStorageTable' and ALSO manages the row status
        of the associated conceptual row in the 'hrStorageTable'
        of the IETF Host Resources MIB (RFC 2790).
        Usage:  Conforming implementations which support static rows
        SHALL support 'active' and 'notInService' writes to this
        'xcmHrStorageRowStatus' row status object; and
        SHALL clear the 'xcmHrStorageGroup' bit in
        'xcmHrGeneralCreateSupport' in the 'xcmHrGeneralTable'.
        Usage:  Conforming implementations which support dynamic rows
        SHALL support 'createAndGo' and 'destroy' writes to this
        'xcmHrStorageRowStatus' row status object; and
        SHALL set the 'xcmHrStorageGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrStorageEntry 1 }
xcmHrStorageRealization OBJECT-TYPE
    SYNTAX      XcmHrStorageRealization
    MAX-ACCESS  read-create
    STATUS      current
    DESCRIPTION
        "An extended storage type (or storage 'realization'),
        used by system administrators and end users of this storage.
        Usage:  The use of either 'other' or 'unknown' is uninformative
        and SHOULD be avoided by conforming implementations."
    REFERENCE
        "See:   'XcmHrDevInfoRealization' textual convention in
                the XCMI Ext to Host Resources TC.
        See:    'xcmHrDevInfoRealization' in the Device Info group of
                the XCMI Ext to Host Resources MIB."
    DEFVAL      { physicalSystem }      
    ::= { xcmHrStorageEntry 2 }
xcmHrStorageStatus OBJECT-TYPE
    SYNTAX      XcmHrDevInfoStatus
    MAX-ACCESS  read-only
    STATUS      current
    DESCRIPTION
        "A storage status, used by system administrators
        and end users of this storage (here, read 'state' for 'status').
        Usage:  Conforming implementations SHALL NOT 'bubble up' status
        from 'physical' storage to associated 'logical' storage.  All
        storage SHALL report its own status ONLY."
    REFERENCE
        "See:   'XcmHrDevInfoStatus' textual convention in
                the XCMI Ext to Host Resources TC.
        See:    'hrDeviceStatus' in the Device group of
                the IETF Host Resources MIB (RFC 2790)."
    DEFVAL      { unknown }             
    ::= { xcmHrStorageEntry 3 }
xcmHrStorageProductDeviceIndex OBJECT-TYPE
    SYNTAX      Cardinal32
    MAX-ACCESS  read-create
    STATUS      current
    DESCRIPTION
        "The value of 'hrDeviceIndex' corresponding to the product
        associated conceptual row in the 'hrDeviceTable' representing
        the product (container) device (eg, of type 'hrDevicePrinter'),
        which uses this storage."
    REFERENCE
        "See:   'hrDeviceIndex' in the Device group of the
                IETF Host Resources MIB (RFC 2790)."
    DEFVAL      { 0 }                   
    ::= { xcmHrStorageEntry 4 }
xcmHrStoragePlatformDeviceIndex OBJECT-TYPE
    SYNTAX      Cardinal32
    MAX-ACCESS  read-create
    STATUS      current
    DESCRIPTION
        "The value of 'hrDeviceIndex' corresponding to the platform
        associated conceptual row in the 'hrDeviceTable' representing
        the CPU device (of type 'hrDeviceProcessor'),
        which manages this storage."
    REFERENCE
        "See:   'hrDeviceIndex' in the Device group of the
                IETF Host Resources MIB (RFC 2790)."
    DEFVAL      { 0 }                   
    ::= { xcmHrStorageEntry 5 }
xcmHrStoragePagingDeviceIndex OBJECT-TYPE
    SYNTAX      Cardinal32
    MAX-ACCESS  read-create
    STATUS      current
    DESCRIPTION
        "The value of 'hrDeviceIndex' corresponding to the paging
        associated conceptual row in the 'hrDeviceTable' representing
        the paging device (usually of type 'hrDeviceDiskStorage'),
        which provides secondary storage for swapping of this storage."
    REFERENCE
        "See:   'hrDeviceIndex' in the Device group of the
                IETF Host Resources MIB (RFC 2790).
        See:    'storagePageSize' in the
                'XcmHrStorageDetailType' textual convention in
                the XCMI Ext to Host Resources TC."
    DEFVAL      { 0 }                   
    ::= { xcmHrStorageEntry 6 }
xcmHrStorageMatchingDeviceIndex OBJECT-TYPE
    SYNTAX      Cardinal32
    MAX-ACCESS  read-create
    STATUS      current
    DESCRIPTION
        "The value of 'hrDeviceIndex' corresponding to the matching
        associated conceptual row in the 'hrDeviceTable' representing
        the matching device (eg, of type 'hrDeviceDiskStorage'),
        which corresponds to this storage."
    REFERENCE
        "See:   'hrDeviceIndex' in the Device group of the
                IETF Host Resources MIB (RFC 2790)."
    DEFVAL      { 0 }                   
    ::= { xcmHrStorageEntry 7 }
xcmHrStorageSWRunIndex OBJECT-TYPE
    SYNTAX      Cardinal32
    MAX-ACCESS  read-create
    STATUS      current
    DESCRIPTION
        "The value of 'hrSWRunIndex' corresponding to the superior
        associated conceptual row in the 'hrSWRunTable'
        representing the running software which manages this storage."
    REFERENCE
        "See:   'hrSWRunIndex' in the Software Running group
                of the IETF Host Resources MIB (RFC 2790)."
    DEFVAL      { 0 }                   
    ::= { xcmHrStorageEntry 8 }
xcmHrStorageSWInstalledIndex OBJECT-TYPE
    SYNTAX      Cardinal32
    MAX-ACCESS  read-create
    STATUS      current
    DESCRIPTION
        "The value of 'hrSWInstalledIndex' corresponding to the superior
        associated conceptual row in the 'hrSWInstalledTable'
        representing the installed software which manages this storage."
    REFERENCE
        "See:   'hrSWInstalledIndex' in the Software Installed group
                of the IETF Host Resources MIB (RFC 2790)."
    DEFVAL      { 0 }                   
    ::= { xcmHrStorageEntry 9 }
xcmHrStorageNextIndex OBJECT-TYPE
    SYNTAX      Cardinal32
    MAX-ACCESS  read-create
    STATUS      current
    DESCRIPTION
        "The value of 'hrStorageIndex' corresponding to:
        a) the next associated row in the 'hrStorageTable'; or
        b) zero if this is the last associated conceptual row in a
        given set; or
        c) zero if this conceptual row is NOT part of a set."
    REFERENCE
        "See:   'hrStorageIndex' in the Storage group of the
                IETF Host Resources MIB (RFC 2790)."
    DEFVAL      { 0 }                   
    ::= { xcmHrStorageEntry 10 }
xcmHrStoragePreviousIndex OBJECT-TYPE
    SYNTAX      Cardinal32
    MAX-ACCESS  read-create
    STATUS      current
    DESCRIPTION
        "The value of 'hrStorageIndex' corresponding to:
        a) the previous associated row in the 'hrStorageTable'; or
        b) zero if this is the first associated conceptual row in a
        given set; or
        c) zero if this conceptual row is NOT part of a set."
    REFERENCE
        "See:   'hrStorageIndex' in the Storage group of the
                IETF Host Resources MIB (RFC 2790)."
    DEFVAL      { 0 }                   
    ::= { xcmHrStorageEntry 11 }
xcmHrStoragePhysicalIndex OBJECT-TYPE
    SYNTAX      Cardinal32
    MAX-ACCESS  read-create
    STATUS      current
    DESCRIPTION
        "The value of 'hrStorageIndex' corresponding to the directly
        associated conceptual row in the 'hrStorageTable' representing:
        a) the first underlying 'physical' storage (if any), if this
        row has 'xcmHrStorageRealization' of 'logical...'; or
        b) the first subordinate 'physical' storage (if any), if this
        row has 'xcmHrStorageRealization' of 'physical...'; or
        c) zero if there is no underlying or subordinate 'physical'
        storage associated with this row (ie, this storage)."
    REFERENCE
        "See:   'hrStorageIndex' in the Storage group of the
                IETF Host Resources MIB (RFC 2790)."
    DEFVAL      { 0 }                   
    ::= { xcmHrStorageEntry 12 }
--
--
xcmHrStorageDetail  OBJECT IDENTIFIER ::= { xcmHrMIB 15 }
xcmHrStorageDetailTable OBJECT-TYPE
    SYNTAX      SEQUENCE OF XcmHrStorageDetailEntry
    MAX-ACCESS  not-accessible
    STATUS      current
    DESCRIPTION
        "A 'sparse' table containing storage detail information for
        'logical' or 'physical' storage elements on this host system,
        augmenting a basic entry in the 'hrStorageTable' of the
        IETF Host Resources MIB (RFC 2790).
        Usage:  UNLIKE the 'xcmGenOptionTable' in the XCMI General MIB
        (which is a unique exception), this table of 'dictionary-based'
        storage details is used with DIRECT create/update operations."
    ::= { xcmHrStorageDetail 2 }
xcmHrStorageDetailEntry OBJECT-TYPE
    SYNTAX      XcmHrStorageDetailEntry
    MAX-ACCESS  not-accessible
    STATUS      current
    DESCRIPTION
        "A 'sparse' entry containing storage detail information for
        a 'logical' or 'physical' storage element on this host system,
        augmenting a basic entry in the 'hrStorageTable' of the
        IETF Host Resources MIB (RFC 2790)."
    INDEX       { hrStorageIndex,
                  xcmHrStorageDetailType,
                  xcmHrStorageDetailIndex }
    ::= { xcmHrStorageDetailTable 1 }
XcmHrStorageDetailEntry ::= SEQUENCE {
        xcmHrStorageDetailType          XcmHrStorageDetailType,
        xcmHrStorageDetailIndex         Ordinal32,
        xcmHrStorageDetailRowStatus     RowStatus,
        xcmHrStorageDetailUnitClass     XcmHrDevDetailUnitClass,
        xcmHrStorageDetailUnit          Cardinal32,
        xcmHrStorageDetailValueInteger  Integer32,
        xcmHrStorageDetailValueOID      OBJECT IDENTIFIER,
        xcmHrStorageDetailValueString   OCTET STRING
    }
xcmHrStorageDetailType OBJECT-TYPE
    SYNTAX      XcmHrStorageDetailType
    MAX-ACCESS  not-accessible
    STATUS      current
    DESCRIPTION
        "The type of the storage detail information specified
        in this conceptual row in the 'xcmHrStorageDetailTable'."
    ::= { xcmHrStorageDetailEntry 1 }
xcmHrStorageDetailIndex OBJECT-TYPE
    SYNTAX      Ordinal32
    MAX-ACCESS  not-accessible
    STATUS      current
    DESCRIPTION
        "A unique value used by this host system to identify this
        conceptual row in the 'xcmHrStorageDetailTable', OR a common
        value shared across a set of related conceptual rows (with
        different values of 'xcmHrStorageDetailType'.
        Usage:  For storage detail types which are single-valued, this
        index SHALL be used to correlate related single-valued details.
        Usage:  For storage detail types which are multi-valued, this
        index SHALL be used to enumerate lists of multi-valued details."
    ::= { xcmHrStorageDetailEntry 2 }
xcmHrStorageDetailRowStatus OBJECT-TYPE
    SYNTAX      RowStatus
    MAX-ACCESS  read-create
    STATUS      current
    DESCRIPTION
        "This object manages the row status of this conceptual row in
        in the 'xcmHrStorageDetailTable'.
        Usage:  Conforming implementations which support static rows
        SHALL support 'active' and 'notInService' writes to this
        'xcmHrStorageDetailRowStatus' row status object; and
        SHALL clear the 'xcmHrStorageDetailGroup' bit in
        'xcmHrGeneralCreateSupport' in the 'xcmHrGeneralTable'.
        Usage:  Conforming implementations which support dynamic rows
        SHALL support 'createAndGo' and 'destroy' writes to this
        'xcmHrStorageDetailRowStatus' row status object; and
        SHALL set the 'xcmHrStorageDetailGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrStorageDetailEntry 3 }
xcmHrStorageDetailUnitClass OBJECT-TYPE
    SYNTAX      XcmHrDevDetailUnitClass
    MAX-ACCESS  read-create
    STATUS      current
    DESCRIPTION
        "The value unit class of the detail information specified
        in this conceptual row in the 'xcmHrStorageDetailTable'.
        Usage:  Used to select a textual convention for specifying the
        value unit of this storage detail.
        Usage:  The 'xcmHrStorageDetail[UnitClass|Class]' objects
        are used to specify the value syntax AND the value unit of the
        'xcmHrStorageDetail[Integer|OID|String]' value objects."
    REFERENCE
        "See:   'xcmHrStorageDetailUnit'"
    DEFVAL      { unknown }             
    ::= { xcmHrStorageDetailEntry 4 }
xcmHrStorageDetailUnit OBJECT-TYPE
    SYNTAX      Cardinal32
    MAX-ACCESS  read-create
    STATUS      current
    DESCRIPTION
        "The value unit of the detail information specified
        in this conceptual row in the 'xcmHrStorageDetailTable'.
        Usage:  Used to select an enumerated choice from a textual
        convention to specify the value unit of this storage detail.
        Usage:  The 'xcmHrStorageDetail[UnitClass|Class]' objects
        are used to specify the value syntax AND the value unit of the
        'xcmHrStorageDetail[Integer|OID|String]' value objects."
    REFERENCE
        "See:   'xcmHrStorageDetailUnitClass'"
    DEFVAL      { 0 }                   
    ::= { xcmHrStorageDetailEntry 5 }
xcmHrStorageDetailValueInteger OBJECT-TYPE
    SYNTAX      Integer32
    MAX-ACCESS  read-create
    STATUS      current
    DESCRIPTION
        "A storage detail value integer,
        used by system administrators and end users to specify
        the current value for a storage detail
        with a base value syntax of 'INTEGER'."
    REFERENCE
        "See:   'xcmHrStorageDetailValueOID' and
                'xcmHrStorageDetailValueString'
        See:    'xcmHrStorageDetailUnitClass' and
                'xcmHrStorageDetailUnit' for syntax of detail value"
    DEFVAL      { 0 }                   
    ::= { xcmHrStorageDetailEntry 6 }
xcmHrStorageDetailValueOID OBJECT-TYPE
    SYNTAX      OBJECT IDENTIFIER
    MAX-ACCESS  read-create
    STATUS      current
    DESCRIPTION
        "A storage detail value OID (object identifier),
        used by system administrators and end users to specify
        the current value for a storage detail
        with a base value syntax of 'OBJECT IDENTIFIER'."
    REFERENCE
        "See:   'xcmHrStorageDetailValueInteger' and
                'xcmHrStorageDetailValueString'
        See:    'xcmHrStorageDetailUnitClass' and
                'xcmHrStorageDetailUnit' for syntax of detail value"
    DEFVAL      { zeroDotZero }   
    ::= { xcmHrStorageDetailEntry 7 }
xcmHrStorageDetailValueString OBJECT-TYPE
    SYNTAX      OCTET STRING (SIZE (0..255))
    MAX-ACCESS  read-create
    STATUS      current
    DESCRIPTION
        "A storage detail value string,
        used by system administrators and end users to specify
        the current value for a storage detail
        with a base value syntax of 'OCTET STRING'.
        Usage:  This object is of type 'XcmFixedLocaleDisplayString'.
        Usage:  Conformant implementations MUST encrypt passwords, keys,
        and other security information stored in this string object."
    REFERENCE
        "See:   'xcmHrStorageDetailValueInteger' and
                'xcmHrStorageDetailValueOID'
        See:    'xcmHrStorageDetailUnitClass' and
                'xcmHrStorageDetailUnit' for syntax of detail value"
    DEFVAL      { ''H }                 
    ::= { xcmHrStorageDetailEntry 8 }
--
--
xcmHrDevCover       OBJECT IDENTIFIER ::= { xcmHrMIB 16 }
xcmHrDevCoverTable OBJECT-TYPE
    SYNTAX      SEQUENCE OF XcmHrDevCoverEntry
    MAX-ACCESS  not-accessible
    STATUS      current
    DESCRIPTION
        "A 'sparse' table containing cover and/or interlock info for
        installed and (possibly) active devices on this host system,
        augmenting the basic entries in the 'hrDeviceTable' of the
        IETF Host Resources MIB (RFC 2790)."
    REFERENCE
        "See:   'prtCoverTable' in the Printer MIB."
    ::= { xcmHrDevCover 2 }
xcmHrDevCoverEntry OBJECT-TYPE
    SYNTAX      XcmHrDevCoverEntry
    MAX-ACCESS  not-accessible
    STATUS      current
    DESCRIPTION
        "A 'sparse' entry containing cover and/or interlock info for
        an installed and (possibly) active device on this host system,
        augmenting a basic entry in the 'hrDeviceTable' of the
        IETF Host Resources MIB (RFC 2790)."
    INDEX       { hrDeviceIndex,
                  xcmHrDevCoverIndex }
    ::= { xcmHrDevCoverTable 1 }
XcmHrDevCoverEntry ::= SEQUENCE {
        xcmHrDevCoverIndex              Ordinal32,
        xcmHrDevCoverRowStatus          RowStatus,
        xcmHrDevCoverName               XcmFixedLocaleDisplayString,
        xcmHrDevCoverDescription        XcmFixedLocaleDisplayString,
        xcmHrDevCoverTypeCover          TruthValue,
        xcmHrDevCoverStatusOpen         TruthValue
    }
xcmHrDevCoverIndex OBJECT-TYPE
    SYNTAX      Ordinal32
    MAX-ACCESS  not-accessible
    STATUS      current
    DESCRIPTION
        "A unique value used by this host system to identify this
        conceptual row in the 'xcmHrDevCoverTable'."
    ::= { xcmHrDevCoverEntry 1 }
xcmHrDevCoverRowStatus OBJECT-TYPE
    SYNTAX      RowStatus
    MAX-ACCESS  read-create
    STATUS      current
    DESCRIPTION
        "This object manages the row status of this conceptual row in
        the 'xcmHrDevCoverTable'.
        Usage:  Conforming implementations which support static rows
        SHALL support 'active' and 'notInService' writes to this
        'xcmHrDevCoverRowStatus' row status object; and
        SHALL clear the 'xcmHrDevCoverGroup' bit in
        'xcmHrGeneralCreateSupport' in the 'xcmHrGeneralTable'.
        Usage:  Conforming implementations which support dynamic rows
        SHALL support 'createAndGo' and 'destroy' writes to this
        'xcmHrDevCoverRowStatus' row status object; and
        SHALL set the 'xcmHrDevCoverGroup' bit in
        'xcmHrGeneralCreateSupport' in the 'xcmHrGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevCoverEntry 2 }
xcmHrDevCoverName OBJECT-TYPE
    SYNTAX      XcmFixedLocaleDisplayString (SIZE (0..255))
    MAX-ACCESS  read-create
    STATUS      current
    DESCRIPTION
        "Human-readable name of this device cover or interlock
        specified in this conceptual row in the 'xcmHrDevCoverTable'.
        Usage:  This name SHALL be locally unambiguous (if specified)
        on this managed host system and SHALL be the one normally used
        in a CLI/GUI/API for identification of this device cover or
        interlock (eg, 'Cover1').
        Usage:  The the Printer MIB combines the name of a
        device cover or device interlock with the description, in one
        object - 'xcmHrDevCover[Name|Description]' add clarity."
    REFERENCE
        "See:   'xcmHrDevCoverDescription' (below).
        See:    'prtCoverDescription' in the Printer MIB."
    DEFVAL      { ''H }                 
    ::= { xcmHrDevCoverEntry 3 }
xcmHrDevCoverDescription OBJECT-TYPE
    SYNTAX      XcmFixedLocaleDisplayString (SIZE (0..255))
    MAX-ACCESS  read-create
    STATUS      current
    DESCRIPTION
        "Human-readable description of this device cover or interlock
        specified in this conceptual row in the 'xcmHrDevCoverTable'.
        Usage:  This description MAY contain the manufacturer's name,
        the color, the physical location, etc, of this device cover or
        interlock (eg, 'Top front blue cover').
        Usage:  The the Printer MIB combines the name of a
        device cover or device interlock with the description, in one
        object - 'xcmHrDevCover[Name|Description]' add clarity."
    REFERENCE
        "See:   'xcmHrDevCoverName' (above).
        See:    'prtCoverDescription' in the Printer MIB."
    DEFVAL      { ''H }                 
    ::= { xcmHrDevCoverEntry 4 }
xcmHrDevCoverTypeCover OBJECT-TYPE
    SYNTAX      TruthValue
    MAX-ACCESS  read-create
    STATUS      current
    DESCRIPTION
        "The type of the device cover or interlock
        specified in this conceptual row in the 'xcmHrDevCoverTable'.
      * 'true' - this is a device cover conceptual row;
      * 'false' - this is a device interlock conceptual row.
        Usage:  The the Printer MIB combines the identity of
        cover versus interlock with the status of open versus closed, in
        one object - 'xcmHrDevCover[TypeCover|StatusOpen]' add clarity."
    REFERENCE
        "See:   'xcmHrDevCoverStatusOpen' (below).
        See:    'prtCoverStatus' in the Printer MIB."
    DEFVAL      { true }                
    ::= { xcmHrDevCoverEntry 5 }
xcmHrDevCoverStatusOpen OBJECT-TYPE
    SYNTAX      TruthValue
    MAX-ACCESS  read-create             
    STATUS      current
    DESCRIPTION
        "The status of the device cover or interlock
        specified in this conceptual row in the 'xcmHrDevCoverTable'.
      * 'true' - this cover/interlock is currently open;
      * 'false' - this cover/interlock is currently closed.
        Usage:  The the Printer MIB combines the choice of
        cover versus interlock with the status of open versus closed, in
        one object - 'xcmHrDevCover[TypeCover|StatusOpen]' add clarity."
    REFERENCE
        "See:   'xcmHrDevCoverTypeCover' (above).
        See:    'prtCoverStatus' in the Printer MIB."
    DEFVAL      { false }               
    ::= { xcmHrDevCoverEntry 6 }
--
--
xcmHrDevAlert       OBJECT IDENTIFIER ::= { xcmHrMIB 17 }
xcmHrDevAlertTable OBJECT-TYPE
    SYNTAX      SEQUENCE OF XcmHrDevAlertEntry
    MAX-ACCESS  not-accessible
    STATUS      current
    DESCRIPTION
        "A table of the device alerts which have been generated and
        recorded on this host system.
        Certain devices can be associated with specific alert tables 
        defined industry wide for the specific device.  This general 
        alert table is designed to work with these other alert tables.  
        At this time, the only device specific alert table is 
        prtAlertTable in the printer MIB.  See xcmHrDevAlertCodeInteger 
        and xcmHrDevAlertDevAlertIndex for connections to the device 
        specific alert table.
        Usage:  Conforming implementations SHALL ensure that this
        table contains (up to) a product-specific number of the most
        'recent' device alerts on this host system.
        Usage:  When an event occurs that should be reported through the
        Alert table, the implementation SHALL create an alert for each 
        device impacted by the event.  This SHOULD include all logical 
        devices containing the impacted device.  All such alerts SHALL 
        have the same index 'xcmHrDevAlertIndex.'
        Usage:  If the hrDeviceIndex is an hrDevicePrinter, then the 
        product SHALL also generate an alert in the IETF 
        'prtAlertTable.' The index 'prtAlertIndex' for the associated 
        printer alert table
        entry SHALL be returned in 'xcmHrDevAlertDevAlertIndex' for the 
        'hrDevicePrinter' index.  Management tools can use the value of 
        'xcmHrDevAlertDevAlertIndex' to associate printer alerts with 
        alerts in this table.
        Usage:  Conforming implementations which also implement the
        System Fault group SHALL record in 'xcmHrSystemFaultTable'
        each persistent system fault when it occurs and is recorded
        in 'xcmHrDevAlertTable'.
        Usage:  Conforming implementations MAY 'age' older entries out
        of 'xcmHrDevAlertTable' based on algorithms which depend on the 
        age of the entry and the particular alert.  When the number of 
        alerts in the table exceeds the product-specific maximum number 
        of alerts, the oldest non-critical alert SHALL be removed.  If 
        there are no non-critical alerts, then the oldest critical alert
        SHALL be removed."
    REFERENCE
        "See:   'prtAlertTable' in the Printer MIB."
    ::= { xcmHrDevAlert 2 }
xcmHrDevAlertEntry OBJECT-TYPE
    SYNTAX      XcmHrDevAlertEntry
    MAX-ACCESS  not-accessible
    STATUS      current
    DESCRIPTION
        "An entry for a device alert which has been generated and
        recorded on this host system."
    REFERENCE
        "See:   'prtAlertEntry' in the Printer MIB."
    INDEX       { hrDeviceIndex,
                  xcmHrDevAlertIndex }
    ::= { xcmHrDevAlertTable 1 }
XcmHrDevAlertEntry ::= SEQUENCE {
        xcmHrDevAlertIndex              Ordinal32,
        xcmHrDevAlertRowStatus          RowStatus,
        xcmHrDevAlertSeverityLevel      XcmGenNotifySeverityFilter,
        xcmHrDevAlertTrainingLevel      XcmGenNotifyTrainingFilter,
        xcmHrDevAlertCodeInteger        Integer32,
        xcmHrDevAlertCodeString         XcmFixedLocaleDisplayString,
        xcmHrDevAlertDescription        XcmFixedLocaleDisplayString,
        xcmHrDevAlertReferenceOID       OBJECT IDENTIFIER,
        xcmHrDevAlertDateAndTime        DateAndTime,
        xcmHrDevAlertTitle              XcmFixedLocaleDisplayString,
        xcmHrDevAlertHelpReference      OCTET STRING,
        xcmHrDevAlertReferenceIndex     Integer32,
        xcmHrDevAlertReferenceLocation  Integer32,
        xcmHrDevAlertDevAlertIndex      Integer32,
        xcmHrDevAlertPriority           Integer32
    }
--
--
xcmHrDevAlertIndex OBJECT-TYPE
    SYNTAX      Ordinal32
    MAX-ACCESS  not-accessible
    STATUS      current
    DESCRIPTION
        "A unique value used by this host system to identify this
        conceptual row in the 'xcmHrDevAlertTable'.
        Usage:  Conforming implementations SHALL NOT 'reuse' values of
        'xcmHrDevAlertIndex' until its' 32-bit value wraps.  Even in
        the case of eventual wrap, the entries SHALL be strictly
        sequenced by the associated value of 'xcmHrDevAlertDateAndTime.'
        Usage: When an event causes an alert on several devices, all 
        such alerts SHALL have the same 'xcmHrDevAlertIndex.'  
        Usage:  Conforming implementations are strongly encouraged to
        preserve the last used value of 'xcmHrDevAlertIndex' across
        system power cycles."
    ::= { xcmHrDevAlertEntry 1 }
xcmHrDevAlertRowStatus OBJECT-TYPE
    SYNTAX      RowStatus
    MAX-ACCESS  read-create
    STATUS      current
    DESCRIPTION
        "This object is used to create (by management agent) and delete
        (by management station and/or management agent) individual
        conceptual rows in the 'xcmHrDevAlertTable'.
        Usage:  Management stations can not create rows in the alert 
        table. Conforming implementations SHALL support 'active' and 
        'notInService' writes to this 'xcmHrDevAlertRowStatus' row 
        status object; and SHALL clear the 'xcmHrDevAlertGroup' bit in
        'xcmHrGeneralCreateSupport' in the 'xcmHrGeneralTable'.
        Usage:  Conforming implementations MAY support dynamic row
        deletion via 'destroy(6)'.  This allows management stations to 
        delete any any obsolete unary non-critical alerts."
    REFERENCE
        "See:   'xcmHrGeneralCreateSupport' in 'xcmHrGeneralTable'.
        See:    'RowStatus' in IETF SNMPv2 TC (RFC 1443/1903/2579).
        See:    'xcmHrDevMgmtCommandData' in XCMI HRX MIB and
                'xcmSecUserMgmtData' in XCMI Security MIB."
    ::= { xcmHrDevAlertEntry 2 }
xcmHrDevAlertSeverityLevel OBJECT-TYPE
    SYNTAX      XcmGenNotifySeverityFilter
    MAX-ACCESS  read-only
    STATUS      current
    DESCRIPTION
        "Device-specific severity level for the device alert which
        is recorded in this conceptual row in the 'xcmHrDevAlertTable'.
        Usage:  Conforming management agents SHALL set one bit
        (specific severity level) or zero bits (no severity level
        reported) in this object."
    REFERENCE
        "See:   'prtAlertSeverityLevel' in the Printer MIB.
        See:    'XcmGenNotifySeverityFilter' in XCMI General TC and
                'xcmGenTrapViewNotifySeverity' in XCMI General MIB."
    DEFVAL      { 0 }                   
    ::= { xcmHrDevAlertEntry 3 }
xcmHrDevAlertTrainingLevel OBJECT-TYPE
    SYNTAX      XcmGenNotifyTrainingFilter
    MAX-ACCESS  read-only
    STATUS      current
    DESCRIPTION
        "Device-specific training level for the device alert which
        is recorded in this conceptual row in the 'xcmHrDevAlertTable'.
        Usage:  Conforming management agents SHALL set one bit
        (specific training level) or zero bits (no training level
        reported) in this object."
    REFERENCE
        "See:   'prtAlertTrainingLevel' in the Printer MIB.
        See:    'XcmGenNotifyTrainingFilter' in XCMI General TC and
                'xcmGenTrapViewNotifyTraining' in XCMI General MIB."
    DEFVAL      { 0 }                   
    ::= { xcmHrDevAlertEntry 4 }
xcmHrDevAlertCodeInteger OBJECT-TYPE
    SYNTAX      Integer32
    MAX-ACCESS  read-only
    STATUS      current
    DESCRIPTION
        "Device-specific code for the device alert which is recorded in
        this conceptual row in the 'xcmHrDevAlertTable'.
        Usage: Conforming implementations SHALL use the values specified
        in any device-specific alert table.  For devices of type 
        'hrDevicePrinter', this value SHALL be the same as the 
        'PrtAlertCodeTC' returned in 'prtAlertCode.'
        The value of 0 means that no code has been assigned to this 
alert. 
        This value is intended for internal use by management 
applications
        rather than for human display.  It should not be confused with
        'xcmHrDevAlertCodeString;' the two values are generally NOT the
        same and there is no assumed mapping from one to the other.
        All values in the range 1..99999 are reserved for definition 
        within a device specific MIB.  Values 100000..199999 will be 
        defined within this MIB in future versions.  Individual products
        may define values 200000 and larger."
    REFERENCE
        "See:   'prtAlertCode' in the Printer MIB."
    DEFVAL      { 0 }                   
    ::= { xcmHrDevAlertEntry 5 }
xcmHrDevAlertCodeString OBJECT-TYPE
    SYNTAX      XcmFixedLocaleDisplayString (SIZE (0..255))
    MAX-ACCESS  read-only
    STATUS      current
    DESCRIPTION
        "Product-specific 'reportable alert code' string for the device
        alert which is recorded in this conceptual row in the
        'xcmHrDevAlertTable'.
        This is a product-specific value used in documentation when 
        describing this alert.
        Usage:  This value is intended for human display, and typically 
        contains an alphanumeric code or keyword phrase.  It should not
        be confused with 'xcmHrDevAlertCodeInteger;' the two values are
        generally NOT the same and there is no assumed mapping from one
        to the other.
        Usage:  Often this string is not translated since it has no 
        specific meaning."
    DEFVAL      { ''H }                 
    ::= { xcmHrDevAlertEntry 6 }
xcmHrDevAlertDescription OBJECT-TYPE
    SYNTAX      XcmFixedLocaleDisplayString (SIZE (0..255))
    MAX-ACCESS  read-only
    STATUS      current
    DESCRIPTION
        "Human-readable alert description for the device alert which
        is recorded in this conceptual row in the 'xcmHrDevAlertTable'.
        Usage:  This is a human-readable string, not intended for
        machine parsing.  Management stations SHOULD obtain the
        alert-specific fault code and severity level from the
        'xcmHrDevAlertCodeString' and 'xcmHrDevAlertSeverityLevel' and 
        the current status from 'hrDeviceStatus' objects rather than 
        trying to interpret this string.
        Implementators are strongly encouraged to include in this       
        description:
            - a description of the problem,
            - a description of the corrective action or a statement
              that no corrective action is required,
            - a description of the impact on device operations.
        Implementors SHOULD NOT include in this description a
        statement of the current operating state of the device,
        since the device state may be changed by some other event
        unrelated to this alert, making any such statement invalid.
        A statement such as 'Device operation may continue' or 'This
        problem must be corrected before the device can resume
        operation' is acceptable.
        Usage:  Conforming implementations SHALL provide BOTH
        detailed 'xcmHrDevAlertDescription' AND terse
        'xcmHrDevAlertTitle' descriptions for each critical
        alert and for each alert which requires human intervention.
        Implementations MAY provide the same text for both strings.
        Usage:  Implementations SHALL provide localized translations
        of this string via the 'xcmGenMessageTextTable.'
        Usage:  For devices of type 'hrDevicePrinter', this SHOULD
        be the same description provided in 'prtAlertDescription' in
        the IETF Printer MIB alert table.  Implementations MAY choose
        to make these descriptions different in order to differentiate
        between IETF-only and XCMI-aware management applications."
    REFERENCE
        "See:   'prtAlertDescription' in the Printer MIB."
    DEFVAL      { ''H }                 
    ::= { xcmHrDevAlertEntry 7 }
xcmHrDevAlertReferenceOID OBJECT-TYPE
    SYNTAX      OBJECT IDENTIFIER
    MAX-ACCESS  read-only
    STATUS      current
    DESCRIPTION
        "An (optional) unambiguous system object reference
        (which MAY include an object instance qualifier suffix),
        used to specify supplemental information for this device alert.
        Usage:  Since this system object reference is specified as an
        ASN.1 object identifier, it MAY be taken from any IETF, Xerox,
        third-party, or product-specific MIB, or it MAY simply be any
        IETF SMIv2-style 'autonomous type'.
        Usage:  If 'xcmHrDevAlertReferenceIndex' is greater than 0,
        then it is an index into a table referenced by 
        'xcmHrDevAlertReferenceOID.'
        Usage:  Devices of type 'hrDevicePrinter' SHALL set
        'xcmHrDevAlertReferenceOID' to the OID of the table or group
        referred to by 'prtAlertGroup' in the IETF printer alert
        table.  (This may be a table or group in the host resources
        MIB, printer MIB, finisher MIB, or other MIB as enumerated
        by 'PrtAlertGroupTC'.)
        Note: Given the flexibility this object provides, the 
        information is only valuable to the Management Station if the 
        OID is a well known OID."
    REFERENCE
        "See:   'prtAlertGroup', 'prtAlertGroupIndex' and 
'prtAlertLocation'
                in the Printer MIB.
        See:    'xcmHrSystemFaultReferenceOID' in XCMI HRX MIB."
    DEFVAL      { zeroDotZero }   
    ::= { xcmHrDevAlertEntry 8 }
xcmHrDevAlertDateAndTime OBJECT-TYPE
    SYNTAX      DateAndTime
    MAX-ACCESS  read-only
    STATUS      current
    DESCRIPTION
        "The date and time stamp for the device alert which
        is recorded in this conceptual row in the 'xcmHrDevAlertTable'."
    REFERENCE
        "See:   'prtAlertTime' in the Printer MIB.
        See:    'hrSystemDate' in IETF Host Resources MIB (RFC 2790)."
    DEFVAL      { '0000000000000000'H } 
    ::= { xcmHrDevAlertEntry 9 }
xcmHrDevAlertTitle OBJECT-TYPE
    SYNTAX      XcmFixedLocaleDisplayString (SIZE (0..16))
    MAX-ACCESS  read-only
    STATUS      current
    DESCRIPTION
       "A terse description of the problem or corrective action 
        associated with the device alert which is recorded in this 
        conceptual row in the 'xcmHrDevAlertTable'.
        Usage:  This is a human-readable string, not intended for
        machine parsing.  This message should be constructed for
        display in a navigation tree or other contexts where the
        management station's user interface may have strict limits on
        message length and complexity.  The message should identify
        the general type and area of the alert but omit most details
        in the interest of brevity, e.g. 'tray empty' or 'replace
        toner' but not 'load A4 Transparency in top tray' or 'replace
        cyan toner cartridge.'  Implementations are strongly
        encouraged to supply more detailed information in
        'xcmHrDevAlertDescription' but may simply supply the same
        text for both strings.
        Usage:  Conforming implementations SHALL provide both detailed 
        'xcmHrDevAlertDescription' and terse 'xcmHrDevAlertTitle' 
        descriptions for each critical alert and for each alert which 
        requires human intervention.
        Usage:  Implementations SHALL provide localized translations
        of this string via the 'xcmGenMessageTextTable.'"
    REFERENCE
        "See:   'xcmHrDevAlertDescription' which contains both a 
                description of the alert and the repair plan.
        See:    'xcmHrDevAlertCodeString' which contains an alert code 
                used in product documentation.
        See:    'xcmHrDevAlertHelpReference' which contains an alert 
                code used by a management station to locate help."
    DEFVAL      { ''H } 
    ::= { xcmHrDevAlertEntry 10 }
xcmHrDevAlertHelpReference OBJECT-TYPE
    SYNTAX      OCTET STRING (SIZE (0..255))
    MAX-ACCESS  read-only
    STATUS      current
   DESCRIPTION
       "A key into a help reference.  This key is intended for machine 
        usage as either a key into a database or as part of a path name 
        to additional information.
       Usage:  This string may be used by a management station to 
       construct the complete URL or pathname of a file which may be 
       stored on the management station, the managed device, a 
       customer's server or a Xerox web server.  The mechanism by which 
       the URL or pathname should be constructed, including any 
       requested localization, is product- and application- dependent.
       For example, if the device returns a string containing two path
       components <product-name>/<info-path>, a host-based management
       application might construct either the pathname 
       '<install-dir>/<product-name>/<info-path>.<locale>' or 
       '<install-dir>/<locale>/<product-name>/<info-path>' depending
       on how the author wanted to organize and distribute help files
       for various products and locales.  A web-based application with 
       knowledge of the managed device's embedded web server might be 
       able to construct the URL 
       'http://<device-address>/alert-info/<product-name>/<info-path>'
       and request a specific localization via the HTTP 'accept-
       language' and 'accept-charset' headers.
       Usage:  Implementors SHALL use only the US-ASCII alphanumeric 
       characters 'A'-'Z', 'a'-'z', '0'-'9' and the punctuation marks 
       underscore ('_'), hyphen ('-'), and forward slash ('/').  The
       first and last characters must be alphanumeric.
       Implementors should note that some hosts distinguish between
       upper- and lower-case letters in pathnames and others don't.
       Therefore, different help paths should differ by more than just
       letter case, and product documentation MUST accurately reflect
       the strings returned in 'xcmHrDevAlertHelpReference', including
       letter case.
       Rationale:  Limiting the character set in this way ensures that 
       the string can be used to construct a valid pathname or URL on   
       the widest variety of host systems.  Note that the file name is  
       not localized (although the contents may be) and not generally   
       displayed for users, so there is little need to support 
       characters outside of this basic US-ASCII set."
    REFERENCE
        "See:   'xcmHrDevAlertDescription' which contains both a 
                description of the alert and the repair plan.
        See:    'xcmHrDevAlertCodeString' which contains an alert code 
                used in product documentation.
        See:    'xcmHrDevAlertDescription' which contains a description 
                and repair actions."
    DEFVAL      { ''H } 
    ::= { xcmHrDevAlertEntry 11 }
    xcmHrDevAlertReferenceIndex OBJECT-TYPE
    SYNTAX      Integer32
    MAX-ACCESS  read-create
    STATUS      current
    DESCRIPTION
        "An (optional) index into a system table used to specify
        supplemental information for this device alert.
        Usage:  When xcmHrDevAlertReferenceOID is a table, 
        xcmHrDevAlertReferenceIndex can be an index into that table.  
        Note:  If the ReferenceOID table has multiple indices, the 
        management table must recognize the table and must know which 
        index is given by this ReferenceIndex.
        Usage:  Use -1 if no index is required."
    REFERENCE
        "See:   'prtAlertGroupIndex' in the Printer MIB.
        See:    'xcmHrDevAlertReferenceOID'."
    DEFVAL      { -1 }   
    ::= { xcmHrDevAlertEntry 12 }
xcmHrDevAlertReferenceLocation OBJECT-TYPE
    SYNTAX      Integer32
    MAX-ACCESS  read-create
    STATUS      current
    DESCRIPTION
        "A product-specific refinement of the source of an alert.
        The value 'unknown(-2)' indicates that the device has no
        additional information to provide."
    REFERENCE
        "See:   'prtAlertGroupLocation' in the Printer MIB.
        See:    'xcmHrDevAlertReferenceOID'.
        See:    'xcmHrDevAlertReferenceIndex'."
    DEFVAL      { -2 }   
    ::= { xcmHrDevAlertEntry 13 }
xcmHrDevAlertDevAlertIndex OBJECT-TYPE
    SYNTAX      Integer32
    MAX-ACCESS  read-create
    STATUS      current
    DESCRIPTION
        "An index into a device-specific alert table.
        When 'hrDeviceIndex' is of type 'hrDevicePrinter', then this
        field SHALL be the value of 'prtAlertIndex' for the same alert."
    REFERENCE
        "See:   'prtAlertIndex' in the Printer MIB."
    DEFVAL      { 0 }   
    ::= { xcmHrDevAlertEntry 14 }
xcmHrDevAlertPriority OBJECT-TYPE
    SYNTAX      Integer32
    MAX-ACCESS  read-create
    STATUS      current
    DESCRIPTION
        "A sorting hint for user interfaces displaying device alerts.
        Usage:  this field allows a device to suggest, for instance,
        that the 'replace fuser' alert should be displayed before the
        'close door' alert in a list or navigation tree.
        Alert priorities are ordinal numbers, with 1 indicating the
        highest priority for display.  A value of zero means 'no
        priority hint available'."
    REFERENCE
        "See:   'prtAlertIndex' in the Printer MIB."
    DEFVAL      { 0 }   
    ::= { xcmHrDevAlertEntry 15 }
xcmHrDevAlertLastAlertIndex       OBJECT-TYPE
    SYNTAX      Cardinal32
    MAX-ACCESS  read-only
    STATUS      current
    DESCRIPTION
        "The value of 'xcmHrDevAlertIndex' for the most recently-added
        alert (critical or non-critical) in the alert table.  This value
        only reflects the most recently added alert; if the alert is 
        subsequently cleared, the value of 'xcmHrDevAlertAllEvents' 
        SHALL NOT be changed as a result.  Compliant implementations
        SHALL report zero if no alerts have been added to the table.
        A management tool may use the fact that this value has not 
        changed to avoid checking for new alerts.
        Note that the value of this object will 'wrap' when the first
        alert is added to the table after 'xcmHrDevAlertIndex'
        has reached 2**32 - 1 and 'wrapped' to 1."
    ::= { xcmHrDevAlert 3 }
xcmHrDevAlertLastCriticalAlertIndex OBJECT-TYPE
    SYNTAX      Cardinal32
    MAX-ACCESS  read-only
    STATUS      current
    DESCRIPTION
        "The value of 'xcmHrDevAlertIndex' for the most recently-added
        critical alert in the alert table.  This value only reflects the
        most recently added alert; if the alert is subsequently cleared,
        the value of 'xcmHrDevAlertLastCriticalAlertIndex' SHALL NOT be
        changed as a result.  Compliant implementations SHALL report
        zero if no critical alerts have been added to the table.
        A management tool may use the fact that this value has not 
        changed to avoid checking for new critical alerts.
        Note that the value of this object will 'wrap' when the first
        critical alert is added to the table after 'xcmHrDevAlertIndex'
        has reached 2**32 - 1 and 'wrapped' to 1."
    ::= { xcmHrDevAlert 4 }
--
--
xcmHrDevAlertV1EventOID OBJECT-IDENTITY
    STATUS      current
    DESCRIPTION
        "The value of the enterprise-specific OID in an SNMPv1 trap sent
        whenever a device alert row transitions to 'active' row status
        or (optionally) transitions to 'notInService' row status in
        'xcmHrDevAlertTable'.
        See SNMPv2 trap definition 'xcmHrDevAlertV2Event'
        below for 'special semantics'."
    ::= { xcmHrDevAlert 1 }
xcmHrDevAlertV2EventPrefix
    OBJECT IDENTIFIER ::= { xcmHrDevAlertV1EventOID 0 }
xcmHrDevAlertV2Event NOTIFICATION-TYPE
    OBJECTS {
        xcmHrDevAlertRowStatus,
        xcmHrDevAlertSeverityLevel,
        xcmHrDevAlertTrainingLevel,
        xcmHrDevAlertCodeInteger,
        xcmHrDevAlertCodeString
    }
    STATUS      current
    DESCRIPTION
        "This trap is sent whenever a device alert row transitions
        to 'active' row status or (optionally) transitions to
        'notInService' row status in 'xcmHrDevAlertTable'.
        This trap is sent when requested by a prior subscription.
        Note:   The variable-bindings of this trap have been chosen to
        specify a complete device alert event while keeping
        trap messages reasonably concise (generally a few hundred octets
        at most).
        This notification has the following special semantics:
            o   The device's 'hrDeviceIndex' field
                value SHALL be appended to this trap object ID,
                as a BER binary OID suffix.
        This trap OID qualifier allows device management/monitoring
        applications to limit the alerts they receive to ones generated
        by devices of interest.
        Systems MAY add other variable-bindings from any MIB."
    ::= { xcmHrDevAlertV2EventPrefix 1 }
--
--          "This trap is sent whenever a device alert row transitions
--          above for 'special semantics'."
--
--
xcmHrConsoleScreen  OBJECT IDENTIFIER ::= { xcmHrMIB 18 }
xcmHrConsoleScreenTable OBJECT-TYPE
    SYNTAX      SEQUENCE OF XcmHrConsoleScreenEntry
    MAX-ACCESS  not-accessible
    STATUS      current
    DESCRIPTION
        "A table containing system local console screen (page) info for
        an installed local user interface console on this host system."
    REFERENCE
        "See:   'prtConsoleDisplayBufferTable' and
                'prtConsoleLightTable' in the Printer MIB."
    ::= { xcmHrConsoleScreen 2 }
xcmHrConsoleScreenEntry OBJECT-TYPE
    SYNTAX      XcmHrConsoleScreenEntry
    MAX-ACCESS  not-accessible
    STATUS      current
    DESCRIPTION
        "An entry containing system local console screen (page) info for
        an installed local user interface console on this host system.
        Usage:  Conforming management agents SHOULD report local console
        info via 'hrDeviceIndex' for 'hrDevicePrinter' - consistent with
        'prtConsoleDisplayBufferTable' in the Printer MIB -
        or 'hrDeviceIndex' for 'xcmHrDeviceHostSystem' in XCMI HRX TC."
    INDEX       { hrDeviceIndex,
                  xcmHrConsoleScreenIndex }
    ::= { xcmHrConsoleScreenTable 1 }
XcmHrConsoleScreenEntry ::= SEQUENCE {
        xcmHrConsoleScreenIndex        Ordinal32,
        xcmHrConsoleScreenName         XcmFixedLocaleDisplayString,
        xcmHrConsoleScreenDescription  XcmFixedLocaleDisplayString,
        xcmHrConsoleScreenParentIndex  Cardinal32,
        xcmHrConsoleScreenPriority     INTEGER (0..100),
        xcmHrConsoleScreenTabCount     Cardinal32
    }
xcmHrConsoleScreenIndex OBJECT-TYPE
    SYNTAX      Ordinal32
    MAX-ACCESS  not-accessible
    STATUS      current
    DESCRIPTION
        "A unique value used by this host system to identify this
        conceptual row in the 'xcmHrConsoleScreenTable'."
    ::= { xcmHrConsoleScreenEntry 1 }
xcmHrConsoleScreenName OBJECT-TYPE
    SYNTAX      XcmFixedLocaleDisplayString (SIZE (0..255))
    MAX-ACCESS  read-only
    STATUS      current
    DESCRIPTION
        "Human-readable name of this local console screen (page),
        used by system administrators and end users to identify this
        screen for systems management.
        Usage:  Conforming management agents SHOULD NOT report the same
        value of 'xcmHrConsoleScreenName' for different screens (pages).
        Screens (pages) are always uniquely labelled by their indices of
        'xcmHrDeviceIndex' and 'xcmHrConsoleScreenIndex'."
    DEFVAL      { ''H }                 
    ::= { xcmHrConsoleScreenEntry 2 }
xcmHrConsoleScreenDescription OBJECT-TYPE
    SYNTAX      XcmFixedLocaleDisplayString (SIZE (0..255))
    MAX-ACCESS  read-only
    STATUS      current
    DESCRIPTION
        "Human-readable description of this local console screen."
    DEFVAL      { ''H }                 
    ::= { xcmHrConsoleScreenEntry 3 }
xcmHrConsoleScreenParentIndex OBJECT-TYPE
    SYNTAX      Cardinal32
    MAX-ACCESS  read-only
    STATUS      current
    DESCRIPTION
        "Parent console screen index associated with this local console
        screen (page), or zero (if none).
        Usage:  Value of 'xcmHrConsoleScreenIndex' for parent screen.
        This object MAY be used to report tree or forest relationships
        between local console screens.  Trees have a single root screen.
        Forests have two or more root screens (w/ no parent screen)."
    DEFVAL      { 0 }                   
    ::= { xcmHrConsoleScreenEntry 4 }
xcmHrConsoleScreenPriority OBJECT-TYPE
    SYNTAX      INTEGER (0..100)
    MAX-ACCESS  read-write
    STATUS      current
    DESCRIPTION
        "The display priority of this local console screen (page).
        Usage:  The display priority of this screen (page), where '0'
        is unspecified (default), '1' is lowest, and '100' is highest.
        When two screens (pages) have equal priority, the first (lowest)
        value of 'xcmHrConsoleScreenIndex' (lexicographical order)
        SHALL have the highest display priority."
    REFERENCE
        "See:   'xcmHrDevInfoPriority' in XCMI Ext to Host Resources MIB
                'xcmJobPriority' in XCMI Job Mon MIB.
                'xcmSvcMonServicePriority' in XCMI Svc Mon MIB."
    DEFVAL      { 0 }                   
    ::= { xcmHrConsoleScreenEntry 5 }
xcmHrConsoleScreenTabCount OBJECT-TYPE
    SYNTAX      Cardinal32
    MAX-ACCESS  read-only
    STATUS      current
    DESCRIPTION
        "Number of tabs (buttons) on this local console screen (page).
        Usage:  Conforming management agents SHALL report values
        of 'xcmHrConsoleTabIndex' that are less than or equal to the
        value of 'xcmHrConsoleScreenTabCount' for the SAME value of
        'xcmHrConsoleScreenIndex' (enclosing screen)."
    DEFVAL      { 0 }                   
    ::= { xcmHrConsoleScreenEntry 6 }
--
--
xcmHrConsoleTab     OBJECT IDENTIFIER ::= { xcmHrMIB 19 }
xcmHrConsoleTabTable OBJECT-TYPE
    SYNTAX      SEQUENCE OF XcmHrConsoleTabEntry
    MAX-ACCESS  not-accessible
    STATUS      current
    DESCRIPTION
        "A table containing system local console tab (button) info for
        an installed local user interface console on this host system."
    REFERENCE
        "See:   'prtConsoleDisplayBufferTable' and
                'prtConsoleLightTable' in the Printer MIB."
    ::= { xcmHrConsoleTab 2 }
xcmHrConsoleTabEntry OBJECT-TYPE
    SYNTAX      XcmHrConsoleTabEntry
    MAX-ACCESS  not-accessible
    STATUS      current
    DESCRIPTION
        "An entry containing system local console tab (button) info for
        an installed local user interface console on this host system.
        Usage:  Conforming management agents SHOULD report local console
        info via 'hrDeviceIndex' for 'hrDevicePrinter' - consistent with
        'prtConsoleDisplayBufferTable' in the Printer MIB -
        or 'hrDeviceIndex' for 'xcmHrDeviceHostSystem' in XCMI HRX TC."
    INDEX       { hrDeviceIndex,
                  xcmHrConsoleScreenIndex,
                  xcmHrConsoleTabIndex }
    ::= { xcmHrConsoleTabTable 1 }
XcmHrConsoleTabEntry ::= SEQUENCE {
        xcmHrConsoleTabIndex            Ordinal32,
        xcmHrConsoleTabName             XcmFixedLocaleDisplayString,
        xcmHrConsoleTabDescription      XcmFixedLocaleDisplayString,
        xcmHrConsoleTabScreenIndex      Cardinal32,
        xcmHrConsoleTabPriority         INTEGER (0..100)
    }
xcmHrConsoleTabIndex OBJECT-TYPE
    SYNTAX      Ordinal32
    MAX-ACCESS  not-accessible
    STATUS      current
    DESCRIPTION
        "A unique value used by this host system to identify this
        conceptual row in the 'xcmHrConsoleTabTable'."
    ::= { xcmHrConsoleTabEntry 1 }
xcmHrConsoleTabName OBJECT-TYPE
    SYNTAX      XcmFixedLocaleDisplayString (SIZE (0..255))
    MAX-ACCESS  read-only
    STATUS      current
    DESCRIPTION
        "Human-readable name of this local console tab (button),
        within the enclosing local console screen (page),
        used by system administrators and end users to identify this
        tab for systems management.
        Usage:  Conforming management agents MAY report the same
        value of 'xcmHrConsoleTabName' for different tabs (buttons).
        Tabs (buttons) are always uniquely labelled by their indices of
        'xcmHrDeviceIndex', 'xcmHrConsoleScreenIndex', and
        'xcmHrConsoleTabIndex'."
    DEFVAL      { ''H }                 
    ::= { xcmHrConsoleTabEntry 2 }
xcmHrConsoleTabDescription OBJECT-TYPE
    SYNTAX      XcmFixedLocaleDisplayString (SIZE (0..255))
    MAX-ACCESS  read-only
    STATUS      current
    DESCRIPTION
        "Human-readable description of this local console tab (button),
        within the enclosing local console screen (page)."
    DEFVAL      { ''H }                 
    ::= { xcmHrConsoleTabEntry 3 }
xcmHrConsoleTabScreenIndex OBJECT-TYPE
    SYNTAX      Cardinal32
    MAX-ACCESS  read-only
    STATUS      current
    DESCRIPTION
        "New local console screen selected by this local console tab
        (button).
        Usage:  Value of 'xcmHrConsoleScreenIndex' for the new screen."
    DEFVAL      { 0 }                   
    ::= { xcmHrConsoleTabEntry 4 }
xcmHrConsoleTabPriority OBJECT-TYPE
    SYNTAX      INTEGER (0..100)
    MAX-ACCESS  read-write
    STATUS      current
    DESCRIPTION
        "The display priority of this local console tab (button)
        within the enclosing local console screen (page).
        Usage:  The display priority of this tab (button), where '0'
        is unspecified (default), '1' is lowest, and '100' is highest.
        When two tabs (buttons) have equal priority, the first (lowest)
        value of 'xcmHrConsoleTabIndex' (lexicographical order), for
        the SAME value of 'xcmHrConsoleScreenIndex' (enclosing screen),
        SHALL have the highest display priority."
    REFERENCE
        "See:   'xcmHrDevInfoPriority' in XCMI Ext to Host Resources MIB
                'xcmJobPriority' in XCMI Job Mon MIB.
                'xcmSvcMonServicePriority' in XCMI Svc Mon MIB."
    DEFVAL      { 0 }                   
    ::= { xcmHrConsoleTabEntry 5 }
--
--
xcmHrSupplies OBJECT IDENTIFIER ::= { xcmHrMIB 20 }
xcmHrSuppliesTable OBJECT-TYPE
    SYNTAX SEQUENCE OF XcmHrSuppliesEntry
    MAX-ACCESS not-accessible
    STATUS current
    DESCRIPTION
        "A table containing information on all supplies for the
        managed system.
        Usage: Rows of the table are created by the agent.
        Certain values in the rows can be set by a management
        tool."
    ::= { xcmHrSupplies 1 }
xcmHrSuppliesEntry OBJECT-TYPE
    SYNTAX XcmHrSuppliesEntry
    MAX-ACCESS not-accessible
    STATUS current
    DESCRIPTION
        "See xcmHrSuppliesTable"
    INDEX { xcmHrSuppliesIndex }
    ::= { xcmHrSuppliesTable 1 }
XcmHrSuppliesEntry ::= SEQUENCE {
    xcmHrSuppliesIndex Ordinal32,
    xcmHrSuppliesReferenceOID OBJECT IDENTIFIER,
    xcmHrSuppliesType AutonomousType,
    xcmHrSuppliesClass XcmHrSuppliesClassTC,
    xcmHrSuppliesDescr OCTET STRING,
    xcmHrSuppliesPartNumber OCTET STRING
     }
xcmHrSuppliesIndex OBJECT-TYPE
    SYNTAX     Ordinal32 (1..65535)
    MAX-ACCESS not-accessible
    STATUS     current
    DESCRIPTION
       "A unique value used by the agent to identify this
       supply.  Although these values may change due to a
       major reconfiguration of the device (e.g. the
       addition of new finishing module to the printer),
       values SHOULD remain stable across successive printer
       power cycles."
    ::= { xcmHrSuppliesEntry 1 }
xcmHrSuppliesReferenceOID OBJECT-TYPE
    SYNTAX      OBJECT IDENTIFIER
    MAX-ACCESS  read-only
    STATUS      current
    DESCRIPTION
       "A system object reference (which SHALL include an
       object instance qualifier suffix), used to specify an
       object in another table related to this supply.
       Usage: If the supply also appears in the
       prtMarkerSuppliesTable, then this referenceOID SHALL
       be the OID for the prtMarkerSuppliesDescription for
       this supply.
       Usage: If the supply also appears in the
       finSupplyTable, then this referenceOID SHALL be the
       OID for the finSupplyDescription for this supply.
       Usage: If the supply also appears in some other table
       (such as a scanner supplies table), then this
       referenceOID SHALL be the OID for the description
       column for this supply if a description column
       exists.  Otherwise it SHALL be the first column of
       the other table as the reference OID.
       Usage: If the supply does not appear in any other
       table, then this referenceOID SHALL be the OID for
       hrDeviceDescr for the physical device requiring or
       using this supply.
       Usage: If no physical device in the hrDeviceTable
       requires the supply, then the hrDeviceTable is not
       complete.
       Note: Given the flexibility this object provides, the
       information is only valuable to the Management
       Station if the OID is a well-known OID.
       Note:  This object has no default value since it must
       be filled in."
     ::= { xcmHrSuppliesEntry 2 }
xcmHrSuppliesType OBJECT-TYPE
    SYNTAX     AutonomousType
    MAX-ACCESS read-only
    STATUS     current
    DESCRIPTION
       "An indication of the type of device.  Use device
       type OIDs."
     ::= { xcmHrSuppliesEntry 3 }
xcmHrSuppliesClass OBJECT-TYPE
    SYNTAX      XcmHrSuppliesClassTC
    MAX-ACCESS  read-only
    STATUS      current
    DESCRIPTION
       "This object describes how this type is replaced.  Values
       range from 'it never breaks' to 'untrained user'.  A
       value of 'Unknown(2)' should never be used.  Use the
       least restrictive type if it is not clear.  For example,
       if a part is usually replaced by service, but a customer
       can order it and replace it on their own, then the supply
       would be 'CustomerReplaceable(4)'."
 ::= { xcmHrSuppliesEntry 4 }
xcmHrSuppliesDescr OBJECT-TYPE
    SYNTAX      OCTET STRING
    MAX-ACCESS  read-only
    STATUS      current
    DESCRIPTION
       "A description of this supply. This name MUST match the
       name of the supply as it will be exposed on
       www.xerox.com, within the printer's web UI, within the
       printer's local UI and within all configuration pages
       that can be generated by the printer."
 ::= { xcmHrSuppliesEntry 5 }
xcmHrSuppliesPartNumber OBJECT-TYPE
    SYNTAX      OCTET STRING
    MAX-ACCESS  read-only
    STATUS      current
    DESCRIPTION
       "The part number used to order this supply.  This part
       number may depend on the location of the machine.  If no
       part number is associated with this supply, then the
       value will be blank (null)."
 ::= { xcmHrSuppliesEntry 6 }
xcmHrDetailTable OBJECT-TYPE
    SYNTAX SEQUENCE OF XcmHrDetailEntry
    MAX-ACCESS not-accessible
    STATUS current
    DESCRIPTION
       "A 'sparse' table containing detail information for
       rows of other SNMP tables'
       Usage: Rows of the table are created by the agent.
       Certain values in the rows can be set by a management
       tool.
       Usage:  OSI ASN.1 encoding rules (ISO 8825) and IETF
       SNMP rules REQUIRE that when object identifiers
       (OIDs) are used as table indices, the first arc (sub-
       identifier) of each object identifier MUST be
       preceded by the count of arcs (sub- identifiers) in
       the object identifier (see 'Mapping of the
       INDEX clause' in SNMPv2-SMI, RFC 2578), unless the
       index is rightmost (low-order) and specified with the
       IMPLIED keyword.  Thus, the xcmHrDetailTableIndex
       index of xcmHrDetailEntry MUST be preceded by an arcs
       count in SNMP request/response PDUs.
       So, if we wanted the Total Black Impressions using
       the third xcmHrSupplies row (lets assume that is the
       toner cartridge) we would do an SNMP Get on the
       object
       1.3.6.1.4.1.253.8.51.1.3.1.7.1.1.3.20.34
       Because 1.3.6.1.4.1.253.8.51.1.3.1.7 is the OID of
       xcmHrDetailValueInteger.  1 is the enumeration for
       the xcmHrSuppliesTable.  3 is the index into the
       xcmHrSupplies table for this cartridge (and there is
       1 arcs there).  20 is the detail type for lifetime
       usage.  And 34 is the index from table 22 of the XMIG
       for 'Total Black Impressions'.  "
 ::= { xcmHrSupplies 2 }
xcmHrDetailEntry OBJECT-TYPE
    SYNTAX XcmHrDetailEntry
    MAX-ACCESS not-accessible
    STATUS current
    DESCRIPTION
       "See xcmHrDetailTable"
    INDEX { xcmHrDetailTableRef, xcmHrDetailTableIndex,
       xcmHrDetailType, xcmHrDetailIndex }
 ::= { xcmHrDetailTable 1 }
 XcmHrDetailEntry ::= SEQUENCE {
    xcmHrDetailTableRef XcmHrDetailTableEnumTC,
    xcmHrDetailTableIndex OBJECT IDENTIFIER,
    xcmHrDetailType XcmHrDevDetailType,
    xcmHrDetailIndex Ordinal32,
    xcmHrDetailUnitClass XcmHrDevDetailUnitClass,
    xcmHrDetailUnit Cardinal32,
    xcmHrDetailValueInteger Integer32,
    xcmHrDetailValueOID OBJECT IDENTIFIER,
    xcmHrDetailValueString OCTET STRING,
    xcmHrDetailDescription XcmFixedLocaleDisplayString
 }
xcmHrDetailTableRef OBJECT-TYPE
    SYNTAX      XcmHrDetailTableEnumTC
    MAX-ACCESS  not-accessible
    STATUS      current
    DESCRIPTION
       "This object is used to identify the table that this
       detail is qualifying.
       Usage: To provide additional information
       on supplies that are defined in the xcmHrSuppliesTable,
       prtMarkerSuppliesTable or finSupplyTable."
 ::= { xcmHrDetailEntry 1 }
xcmHrDetailTableIndex OBJECT-TYPE
    SYNTAX      OBJECT IDENTIFIER
    MAX-ACCESS  not-accessible
    STATUS      current
    DESCRIPTION
       "This object is used to provide the index of the
       specific row in the table referenced by
       xcmHrDetailTableRef.
       Usage: To identify a supply in the
       xcmHrSuppliesTable, use the single octet
       xcmHrSuppliesIndex.
       Usage: To identify a supply in the
       prtMarkerSuppliesTable, use the single octet
       prtMarkerSuppliesIndex.
       Usage: To identify a supply in the
       finSupplyTable, use the single octet
       finSupplyIndex."
 ::= { xcmHrDetailEntry 2 }
xcmHrDetailType OBJECT-TYPE
    SYNTAX      XcmHrDevDetailType
    MAX-ACCESS  not-accessible
    STATUS      current
    DESCRIPTION
       "The type of the detail information specified in this
       row of the table."
 ::= { xcmHrDetailEntry 3 }
xcmHrDetailIndex OBJECT-TYPE
    SYNTAX      Ordinal32
    MAX-ACCESS  not-accessible
    STATUS      current
    DESCRIPTION
       "This object supports details which have multiple
       values and can also be used to correlate related
       values of different types.
       Usage:  For distinct detail types which are related,
       this index SHALL be equal for related detail values.
       Usage:  For detail types which are multi-valued, this
       index SHALL be used to enumerate the list of details."
 ::= { xcmHrDetailEntry 4 }
xcmHrDetailUnitClass OBJECT-TYPE
    SYNTAX      XcmHrDevDetailUnitClass
    MAX-ACCESS  read-only
    STATUS      current
    DESCRIPTION
       "The value/unit class of the detail information
       specified in this row of the table.
       Usage: Used to select a textual convention for
       specifying the value unit of this device detail.
       Usage: Also used to specify which of
       xcmHrDetailValue[Integer|OID|String] are used to
       contain the detail value.
       Usage: Typically the value of xcmHrDetailUnitClass is
       listed explicitly in the description of the
       XcmHrDevDetailType enumeration. In that case, the
       agent SHALL populate this object with the listed
       enumeration and a management tool does not have to
       check this object to determine the unit class."
    DEFVAL      { unknown }        
 ::= { xcmHrDetailEntry 5 }
xcmHrDetailUnit OBJECT-TYPE
    SYNTAX      Cardinal32
    MAX-ACCESS  read-write
    STATUS      current
    DESCRIPTION
       "This object makes explicit the units in which this
       detail value is being specified.
       Usage:  Used to select an enumerated choice from a
       textual convention to specify the value unit of this
       device detail.  The specific textual convention is
       identified by xcmHrDetailUnitClass.
       "
    DEFVAL      { 0 }            
 ::= { xcmHrDetailEntry 6 }
xcmHrDetailValueInteger OBJECT-TYPE
    SYNTAX      Integer32
    MAX-ACCESS  read-write
    STATUS      current
    DESCRIPTION
       "The current value for a device detail with a base
       value syntax 'INTEGER'. "
 ::= { xcmHrDetailEntry 7 }
xcmHrDetailValueOID OBJECT-TYPE
    SYNTAX      OBJECT IDENTIFIER
    MAX-ACCESS  read-write
    STATUS      current
    DESCRIPTION
       "The current value for a device detail with a base
       value syntax 'OID'. "
 ::= { xcmHrDetailEntry 8 }
xcmHrDetailValueString OBJECT-TYPE
    SYNTAX      OCTET STRING
    MAX-ACCESS  read-write
    STATUS      current
    DESCRIPTION
       "The current value for a device detail with a base
       value syntax 'STRING'.
       This object is also used to provide secondary
       information when the base value syntax is 'INTEGER'
       or 'OID'.  Typically this is a string version of the
       value of the detail."
 ::= { xcmHrDetailEntry 9 }
xcmHrDetailDescription OBJECT-TYPE
    SYNTAX      XcmFixedLocaleDisplayString (SIZE (0..255))
    MAX-ACCESS  read-write
    STATUS      current
    DESCRIPTION
       "This object is used to provide a description of the
       detail."
 ::= { xcmHrDetailEntry 10 }
--
--
xcmHrConsole  OBJECT IDENTIFIER ::= { xcmHrMIB 21 }
xcmHrConsoleTable OBJECT-TYPE
    SYNTAX      SEQUENCE OF XcmHrConsoleEntry
    MAX-ACCESS  not-accessible
    STATUS      current
    DESCRIPTION
        "A table containing system local console information for
        an installed local user interface console on this host system."
    REFERENCE
        "See:   'prtConsoleDisplayBufferTable' and
                'prtConsoleLightTable' in the Printer MIB."
    ::= { xcmHrConsole 2 }
xcmHrConsoleEntry OBJECT-TYPE
    SYNTAX      XcmHrConsoleEntry
    MAX-ACCESS  not-accessible
    STATUS      current
    DESCRIPTION
        "An entry containing system local console information for
        an installed local user interface console on this host system.
        Usage:  Conforming management agents SHOULD report local console
        info via 'hrDeviceIndex' for 'hrDevicePrinter' - consistent with
        'prtConsoleDisplayBufferTable' in the Printer MIB -
        or 'hrDeviceIndex' for 'xcmHrDeviceHostSystem' in XCMI HRX TC."
    INDEX       { hrDeviceIndex,
                  xcmHrConsoleIndex }
    ::= { xcmHrConsoleTable 1 }
XcmHrConsoleEntry ::= SEQUENCE {
        xcmHrConsoleIndex          Ordinal32,
        xcmHrConsoleDefaultService XcmHrConsoleDefaultService,
        xcmHrConsoleBrightness     Integer32,
        xcmHrConsoleContrast       Integer32,
        xcmHrConsoleAccessibility  TruthValue,
        xcmHrConsoleAutoClearTime  Integer32,
        xcmHrConsoleInsertTimeout  Integer32,
        xcmHrConsoleTray1Timeout   Integer32,
        xcmHrConsoleTray2nTimeout  Integer32,
        xcmHrConsoleLoadTimeout    Integer32,
        xcmHrConsoleSoundVolume    Integer32,
        xcmHrConsoleSoundDuration  Integer32 
    }
xcmHrConsoleIndex OBJECT-TYPE
    SYNTAX      Ordinal32
    MAX-ACCESS  not-accessible
    STATUS      current
    DESCRIPTION
        "A unique value used by this host system to identify this
        conceptual row in the 'xcmHrConsoleTable'."
    ::= { xcmHrConsoleEntry 1 }
xcmHrConsoleDefaultService OBJECT-TYPE
    SYNTAX      XcmHrConsoleDefaultService
    MAX-ACCESS  read-create
    STATUS      current
    DESCRIPTION
        "The default service shown on the console user interface.
         This is used to change the meaning of the Green Button 
         on the front panel of many devices."
    DEFVAL      { copyService }                 
    ::= { xcmHrConsoleEntry 2 }
xcmHrConsoleBrightness OBJECT-TYPE
    SYNTAX      Integer32
    MAX-ACCESS  read-create
    STATUS      current
    DESCRIPTION
        "The console brightness level. Often this a number from
         1 to 10 where 1 is dimmest and 10 is brightest."
    DEFVAL      { 5 }
    ::= { xcmHrConsoleEntry 3 }
xcmHrConsoleContrast OBJECT-TYPE
    SYNTAX      Integer32
    MAX-ACCESS  read-create
    STATUS      current
    DESCRIPTION
        "The console contrast level. Often this a number from
         1 to 10 where 1 is least contrast and 10 is most contrast."
    DEFVAL      { 5 }
    ::= { xcmHrConsoleEntry 4 }
xcmHrConsoleAccessibility OBJECT-TYPE
    SYNTAX      TruthValue
    MAX-ACCESS  read-create
    STATUS      current
    DESCRIPTION
        "Turns On/off control panel accessibility mode. When On,
         value=true, the console does not timeout and key 
         repeating is off. When Off, value=false, the console panel 
         times out after specified period of no activity and key 
         repeating is on."
    DEFVAL      { false }
    ::= { xcmHrConsoleEntry 5 }
xcmHrConsoleAutoClearTime OBJECT-TYPE
    SYNTAX      Integer32
    MAX-ACCESS  read-create
    STATUS      current
    DESCRIPTION
        "The automatic clear timeout for the console. Often this a numbe
         0 to 120 where 0 is console never times out and 120 means the
         console times out after 120 seconds of no activity."
    DEFVAL      { 60 }
    ::= { xcmHrConsoleEntry 6 }
xcmHrConsoleInsertTimeout OBJECT-TYPE
    SYNTAX      Integer32
    MAX-ACCESS  read-create
    STATUS      current
    DESCRIPTION
        "The insertion timeout for console prompts. Often this a number
         0, 60 or -1 where 0 is console never prompts, 60 means the
         console prompts the user for 60 seconds than stops and -1 
         means the console prompt is displayed for an infinite 
         amount of time."
    DEFVAL      { 60 }
    ::= { xcmHrConsoleEntry 7 }
xcmHrConsoleTray1Timeout OBJECT-TYPE
    SYNTAX      Integer32
    MAX-ACCESS  read-create
    STATUS      current
    DESCRIPTION
        "The insertion timeout for console prompts for tray 1 events. 
         Often this a number 0, 60 or -1 where 0 is console never 
         prompts, 60 means the console prompts the user for 60 seconds 
         than stops and -1 means the console prompt is displayed for 
         an infinite amount of time."
    DEFVAL      { 60 }
    ::= { xcmHrConsoleEntry 8 }
xcmHrConsoleTray2nTimeout OBJECT-TYPE
    SYNTAX      Integer32
    MAX-ACCESS  read-create
    STATUS      current
    DESCRIPTION
        "The insertion timeout in seconds for console prompts for 
         trays 2 through n events. Often this a number 0, 60 or -1 
         where 0 is console never prompts, 60 means the console prompts 
         the user for 1 minute than stops and -1 means the console 
         prompt is displayed for an infinite amount of time."
    DEFVAL      { 60 }
    ::= { xcmHrConsoleEntry 9 }
xcmHrConsoleLoadTimeout OBJECT-TYPE
    SYNTAX      Integer32
    MAX-ACCESS  read-create
    STATUS      current
    DESCRIPTION
        "The amount of time in minutes the system waits for before 
         using the   default media source for the device."
    DEFVAL      { 60 }
    ::= { xcmHrConsoleEntry 10 }
xcmHrConsoleSoundVolume OBJECT-TYPE
    SYNTAX      Integer32
    MAX-ACCESS  read-create
    STATUS      current
    DESCRIPTION
        "The console sound volume control. This is often used to control
         how loud the fax modem telephone line sound is. This is often a
         number 0 through 10 where 0 is console sounds are off, 
         1 is the lowest volume and 10 is the highest volume."
    DEFVAL      { 2 }
    ::= { xcmHrConsoleEntry 11 }
xcmHrConsoleSoundDuration OBJECT-TYPE
    SYNTAX      Integer32
    MAX-ACCESS  read-create
    STATUS      current
    DESCRIPTION
        "The console sound duration. This is often used to control how
         long the sound will last when the fax modem telephone line soun
         is on. This is often a number 1 through 255 where 1 means the 
         console sounds are on for 1 second and 255 means the console  
         sounds are on for 255 seconds."
    DEFVAL      { 15 }
    ::= { xcmHrConsoleEntry 12 } 
--
--
xcmHrGenericParamGroup OBJECT IDENTIFIER ::= { xcmHrMIB 22 }
xcmHrGenericParamName OBJECT-TYPE
    SYNTAX      OCTET STRING (SIZE (0..255))
    MAX-ACCESS  read-create
    STATUS      current
    DESCRIPTION "
        This object provides a name of a parameter that can be
        returned and modified by SNMP.
        Usage: Conforming management agents SHALL 'reject' any SNMP
        Set-request to xcmHrGenericParamName if the parameter name 
        is invalid, with 'bad Value' error. 
        Usage:  Conforming management stations can set 
        'xcmHrGenericParamName', i.e. the parameter name and
        'xcmHrGenericParamValue', i.e. the parameter value
        SIMULTANEOUSLY in the same SNMP Set-Request PDU using a 
        BULK-SET request. The order in the BULK-SET must be
        'xcmHrGenericParamName', followed by 
        'xcmHrGenericParamValue'"
    DEFVAL      { ''H }
    ::= { xcmHrGenericParamGroup 1 }
xcmHrGenericParamValue OBJECT-TYPE
    SYNTAX      OCTET STRING (SIZE (0..255))
    MAX-ACCESS  read-create
    STATUS      current
    DESCRIPTION "
        This object provides a value for a parameter that can be
        returned and modified by SNMP. To get a parameter value
        the manager will need to SET 'xcmHrGenericParamName'
        to inform the agent what parameter value is desired.
        Then a GET request on this object will return 
        the value for the parameter requested.
        Usage:  Conformant implementations MUST encrypt passwords, keys,
        and other security information in SET requests made to this 
        object.
        Usage:  Conformant implementations MUST NOT return passwords, 
        keys, and other security information in response to GET requests
        made to this object.
        Usage:  Conforming management stations can set 
        'xcmHrGenericParamValue', i.e. the parameter value and
        'xcmHrGenericParamName', i.e. the parameter name
        SIMULTANEOUSLY in the same SNMP Set-Request PDU using a 
        BULK-SET request. The order in the BULK-SET must be
        'xcmHrGenericParamName', followed by 
        'xcmHrGenericParamValue'"
    DEFVAL      { ''H }
    ::= { xcmHrGenericParamGroup 2 }
--
--
xcmHrMIBConformance OBJECT IDENTIFIER ::= { xcmHrMIB 2 }
xcmHrMIBGroups      OBJECT IDENTIFIER ::= { xcmHrMIBConformance 2 }
--
--
xcmHrMIBCompliance MODULE-COMPLIANCE
    STATUS      current
    DESCRIPTION
        "The compliance statements for SNMP management agents that
        implement the Host Resources Extensions MIB."
    MODULE 
    MANDATORY-GROUPS {
        xcmHrGeneralGroup,
        xcmHrSuppliesGroup,
        xcmHrDevInfoGroup
    }
    GROUP       xcmHrDevHelpGroup
    DESCRIPTION
        "Implementation of this group is DEPRECATED (as of XCMI v4.1)
        and conforming implementations SHOULD use 'deviceHelp...'
        details in 'xcmHrDevDetailTable' instead.
        Usage:  Conforming management agents which implement this
        group SHALL also implement the Comms Address group
        of the XCMI Comms Engine MIB and SHALL use 'XcmSecUserRole'
        values from XCMI Security TC in 'xcmCommsAddressUserRole'.
        Note:   'sysContact' in IETF MIB-II (RFC 1213) provides a
        low-cost alternative for systems which do NOT implement
        complex device help (contact) info via SNMP."
    GROUP       xcmHrDevMgmtGroup
    DESCRIPTION
        "Implementation of this group is conditionally mandatory, ie,
        mandatory for systems which implement simple device
        management via SNMP, and optional for all other systems."
    GROUP       xcmHrDevPowerGroup
    DESCRIPTION
        "Implementation of this group is conditionally mandatory, ie,
        mandatory for systems which implement device power profile
        management via SNMP, and optional for all other systems.
        Note:   Systems are free to decompose the hierarchy of their
        hardware containment to any depth via 'hrDeviceTable' and
        and 'xcmHrDev[Info|Power]Table' entries, in order to manage
        their power profiles at any granularity."
    GROUP       xcmHrDevTrafficGroup
    DESCRIPTION
        "Implementation of this group is conditionally mandatory, ie,
        mandatory for systems which implement device traffic
        statistics via SNMP, and optional for all other systems."
    GROUP       xcmHrSystemFaultGroup
    DESCRIPTION
        "Implementation of this group is conditionally mandatory, ie,
        mandatory for systems which implement persistent system
        fault logs via SNMP, and optional for all other systems."
    GROUP       xcmHrDevCalendarGroup
    DESCRIPTION
        "Implementation of this group is conditionally mandatory, ie,
        mandatory for systems which implement device calendar
        management via SNMP, and optional for all other systems."
    GROUP       xcmHrSWRunGroup
    DESCRIPTION
        "Implementation of this group is conditionally mandatory, ie,
        mandatory for systems which support running software
        extensions via SNMP, and optional for all other systems.
        Usage:  Conforming management agents which implement this
        group SHALL also implement the Software Running
        group of the IETF Host Resources MIB (RFC 2790)
        and MAY also support secure 'service' configuration
        via the XCMI Security MIB."
    GROUP       xcmHrSWInstalledGroup
    DESCRIPTION
        "Implementation of this group is conditionally mandatory, ie,
        mandatory for systems which support installed software
        extensions via SNMP, and optional for all other systems.
        Usage:  Conforming management agents which implement this
        group SHALL also implement the Software Installed
        group of the IETF Host Resources MIB (RFC 2790)
        and MAY also support secure 'service' configuration
        via the XCMI Security MIB."
    GROUP       xcmHrDevDetailGroup
    DESCRIPTION
        "Implementation of this group is conditionally mandatory, ie,
        mandatory for systems which implement device detail info
        via SNMP, and optional for all other systems."
    GROUP       xcmHrStorageGroup
    DESCRIPTION
        "Implementation of this group is conditionally mandatory, ie,
        mandatory for systems which support storage extensions info
        via SNMP, and optional for all other systems.
        Usage:  Conforming management agents which implement this
        group SHALL also implement the Storage
        group of the IETF Host Resources MIB (RFC 2790)
        and MAY also support secure 'service' configuration
        via the XCMI Security MIB."
    GROUP       xcmHrStorageDetailGroup
    DESCRIPTION
        "Implementation of this group is conditionally mandatory, ie,
        mandatory for systems which implement storage detail info
        via SNMP, and optional for all other systems."
    GROUP       xcmHrDevCoverGroup
    DESCRIPTION
        "Implementation of this group is conditionally mandatory, ie,
        mandatory for systems which implement device cover and/or
        interlock info via SNMP, and optional for all other systems."
    GROUP       xcmHrDevAlertGroup
    DESCRIPTION
        "Implementation of this group is conditionally mandatory, ie,
        mandatory for systems which implement device alerts
        via SNMP, and optional for all other systems."
    GROUP       xcmHrConsoleScreenGroup
    DESCRIPTION
        "Implementation of this group is conditionally mandatory, ie,
        mandatory for systems which implement system local console
        management via SNMP, and optional for all other systems."
    GROUP       xcmHrConsoleTabGroup
    DESCRIPTION
        "Implementation of this group is conditionally mandatory, ie,
        mandatory for systems which implement system local console
        management via SNMP, and optional for all other systems."
    GROUP       xcmHrConsoleGroup
    DESCRIPTION
        "Implementation of this group is conditionally mandatory, ie,
        mandatory for systems which implement local console
        management via SNMP, and optional for all other systems."
    OBJECT      xcmHrGeneralRowStatus
    SYNTAX      INTEGER { active(1) }   
    DESCRIPTION
        "It is conformant to implement this object as read-only, and
        only one of the enumerated values for the 'RowStatus' textual
        convention need be supported, specifically:  active(1)."
    OBJECT      xcmHrDevInfoRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevInfoName
    SYNTAX      XcmFixedLocaleDisplayString (SIZE (0..32))
    MIN-ACCESS  read-only
    DESCRIPTION
        "It is conformant to implement this object as read-only, and
        only 32 octets maximum string length need be supported."
    OBJECT      xcmHrDevInfoSerialNumber
    SYNTAX      XcmFixedLocaleDisplayString (SIZE (0..32))
    MIN-ACCESS  read-only
    DESCRIPTION
        "It is conformant to implement this object as read-only, and
        only 32 octets maximum string length need be supported."
    OBJECT      xcmHrDevInfoRealization
    MIN-ACCESS  read-only
    DESCRIPTION
        "It is conformant to implement this object as read-only."
    OBJECT      xcmHrDevInfoInstallDate
    MIN-ACCESS  read-only
    DESCRIPTION
        "It is conformant to implement this object as read-only."
    OBJECT      xcmHrDevInfoNextDeviceIndex
    MIN-ACCESS  read-only
    DESCRIPTION
        "It is conformant to implement this object as read-only."
    OBJECT      xcmHrDevInfoPreviousDeviceIndex
    MIN-ACCESS  read-only
    DESCRIPTION
        "It is conformant to implement this object as read-only."
    OBJECT      xcmHrDevInfoPhysicalDeviceIndex
    MIN-ACCESS  read-only
    DESCRIPTION
        "It is conformant to implement this object as read-only."
    OBJECT      xcmHrDevHelpRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevHelpOperatorMessage
    SYNTAX      XcmFixedLocaleDisplayString (SIZE (0..32))
    MIN-ACCESS  read-only
    DESCRIPTION
        "It is conformant to implement this object as read-only, and
        only 32 octets maximum string length need be supported."
    OBJECT      xcmHrDevHelpProblemMessage
    SYNTAX      XcmFixedLocaleDisplayString (SIZE (0..32))
    MIN-ACCESS  read-only
    DESCRIPTION
        "It is conformant to implement this object as read-only, and
        only 32 octets maximum string length need be supported."
    OBJECT      xcmHrDevHelpCommsAddressIndex
    MIN-ACCESS  read-only
    DESCRIPTION
        "It is conformant to implement this object as read-only."
    OBJECT      xcmHrDevMgmtRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevMgmtCommandRequest
    SYNTAX      INTEGER {
        none(1),                        
        startup(2),                     
        resetWarning(3),                
        shutdown(5),                    
        resetCounters(7),               
        resetWarm(8),                   
        resetCold(9),                   
        resetFactory(10),               
        deviceDisable(1306),            
        deviceEnable(1307),             
        devicePause(1308),              
        deviceResume(1309),             
        deviceShutdown(1310),           
        deviceResetCounters(2331),      
        deviceResetWarm(2332),          
        deviceResetCold(2333),          
        deviceResetFactory(2334)        
    }
    DESCRIPTION
        "It is conformant to implement this object as follows:
        only the above subset of operations need be supported."
    OBJECT      xcmHrDevMgmtCommandData
    SYNTAX      XcmHrDevMgmtCommandData (SIZE (0..1))
    DESCRIPTION
        "It is conformant to implement this object as follows:
        only 1 octet maximum string length need be supported.
        Usage:  Conformant implementations MUST encrypt passwords, keys,
        and other security information stored in this string object."
    OBJECT      xcmHrDevMgmtUserPassword
    SYNTAX      OCTET STRING (SIZE (0..32))
    MIN-ACCESS  read-only
    DESCRIPTION
        "It is conformant to implement this object as read-only, and
        only 32 octets maximum string length need be supported.
        Usage:  Conformant implementations MUST encrypt passwords, keys,
        and other security information stored in this string object."
    OBJECT      xcmHrDevMgmtOperatorPassword
    SYNTAX      OCTET STRING (SIZE (0..32))
    MIN-ACCESS  read-only
    DESCRIPTION
        "It is conformant to implement this object as read-only, and
        only 32 octets maximum string length need be supported.
        Usage:  Conformant implementations MUST encrypt passwords, keys,
        and other security information stored in this string object."
    OBJECT      xcmHrDevMgmtAdminPassword
    SYNTAX      OCTET STRING (SIZE (0..32))
    MIN-ACCESS  read-only
    DESCRIPTION
        "It is conformant to implement this object as read-only, and
        only 32 octets maximum string length need be supported.
        Usage:  Conformant implementations MUST encrypt passwords, keys,
        and other security information stored in this string object."
    OBJECT      xcmHrDevPowerRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevPowerWarmUpSupport
    MIN-ACCESS  read-only
    DESCRIPTION
        "It is conformant to implement this object as read-only."
    OBJECT      xcmHrDevPowerCoolDownSupport
    MIN-ACCESS  read-only
    DESCRIPTION
        "It is conformant to implement this object as read-only."
    OBJECT      xcmHrDevPowerEnergySaveSupport
    MIN-ACCESS  read-only
    DESCRIPTION
        "It is conformant to implement this object as read-only."
    OBJECT      xcmHrDevPowerTimeUnit
    MIN-ACCESS  read-only
    DESCRIPTION
        "It is conformant to implement this object as read-only."
    OBJECT      xcmHrDevPowerWarmUpDelay
    MIN-ACCESS  read-only
    DESCRIPTION
        "It is conformant to implement this object as read-only."
    OBJECT      xcmHrDevPowerWarmUpDuration
    MIN-ACCESS  read-only
    DESCRIPTION
        "It is conformant to implement this object as read-only."
    OBJECT      xcmHrDevPowerCoolDownDelay
    MIN-ACCESS  read-only
    DESCRIPTION
        "It is conformant to implement this object as read-only."
    OBJECT      xcmHrDevPowerCoolDownDuration
    MIN-ACCESS  read-only
    DESCRIPTION
        "It is conformant to implement this object as read-only."
    OBJECT      xcmHrDevPowerEnergySaveDelay
    MIN-ACCESS  read-only
    DESCRIPTION
        "It is conformant to implement this object as read-only."
    OBJECT      xcmHrDevPowerEnergySaveDuration
    MIN-ACCESS  read-only
    DESCRIPTION
        "It is conformant to implement this object as read-only."
    OBJECT      xcmHrDevPowerWakeUpSupport
    MIN-ACCESS  read-only
    DESCRIPTION
        "It is conformant to implement this object as read-only."
    OBJECT      xcmHrDevPowerWakeUpDelay
    MIN-ACCESS  read-only
    DESCRIPTION
        "It is conformant to implement this object as read-only."
    OBJECT      xcmHrDevPowerWakeUpDuration
    MIN-ACCESS  read-only
    DESCRIPTION
        "It is conformant to implement this object as read-only."
    OBJECT      xcmHrDevPowerShutdownDelay
    MIN-ACCESS  read-only
    DESCRIPTION
        "It is conformant to implement this object as read-only."
    OBJECT      xcmHrDevPowerShutdownDuration
    MIN-ACCESS  read-only
    DESCRIPTION
        "It is conformant to implement this object as read-only."
    OBJECT      xcmHrDevPowerStartupDelay
    MIN-ACCESS  read-only
    DESCRIPTION
        "It is conformant to implement this object as read-only."
    OBJECT      xcmHrDevPowerStartupDuration
    MIN-ACCESS  read-only
    DESCRIPTION
        "It is conformant to implement this object as read-only."
    OBJECT      xcmHrDevTrafficRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevTrafficInputSupport
    MIN-ACCESS  read-only
    DESCRIPTION
        "It is conformant to implement this object as read-only."
    OBJECT      xcmHrDevTrafficOutputSupport
    MIN-ACCESS  read-only
    DESCRIPTION
        "It is conformant to implement this object as read-only."
    OBJECT      xcmHrDevTrafficInputUnit
    MIN-ACCESS  read-only
    DESCRIPTION
        "It is conformant to implement this object as read-only."
    OBJECT      xcmHrDevTrafficOutputUnit
    MIN-ACCESS  read-only
    DESCRIPTION
        "It is conformant to implement this object as read-only."
    OBJECT      xcmHrDevTrafficInputMaxSize
    MIN-ACCESS  read-only
    DESCRIPTION
        "It is conformant to implement this object as read-only."
    OBJECT      xcmHrDevTrafficOutputMaxSize
    MIN-ACCESS  read-only
    DESCRIPTION
        "It is conformant to implement this object as read-only."
    OBJECT      xcmHrDevTrafficInputTimeout
    MIN-ACCESS  read-only
    DESCRIPTION
        "It is conformant to implement this object as read-only."
    OBJECT      xcmHrDevTrafficOutputTimeout
    MIN-ACCESS  read-only
    DESCRIPTION
        "It is conformant to implement this object as read-only."
    OBJECT      xcmHrSystemFaultRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrSystemFaultString
    SYNTAX      XcmFixedLocaleDisplayString (SIZE (0..1))
    DESCRIPTION
        "It is conformant to implement this object as read-only, and
        only 1 octet maximum string length need be supported."
    OBJECT      xcmHrDevCalendarRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevCalendarExplicitDate
    MIN-ACCESS  read-only
    DESCRIPTION
        "It is conformant to implement this object as read-only."
    OBJECT      xcmHrDevCalendarCommandRequest
    MIN-ACCESS  read-only
    DESCRIPTION
        "It is conformant to implement this object as read-only."
    OBJECT      xcmHrDevCalendarCommandData
    SYNTAX      XcmHrDevMgmtCommandData (SIZE (0..1))
    MIN-ACCESS  read-only
    DESCRIPTION
        "It is conformant to implement this object as read-only, and
        only 1 octet maximum string length need be supported.
        Usage:  Conformant implementations MUST encrypt passwords, keys,
        and other security information stored in this string object."
    OBJECT      xcmHrSWRunRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrSWRunAdminName
    SYNTAX      XcmFixedLocaleDisplayString (SIZE (0..32))
    MIN-ACCESS  read-only
    DESCRIPTION
        "It is conformant to implement this object as read-only, and
        only 32 octets maximum string length need be supported."
    OBJECT      xcmHrSWRunPhysicalDeviceIndex
    MIN-ACCESS  read-only
    DESCRIPTION
        "It is conformant to implement this object as read-only."
    OBJECT      xcmHrSWRunLogicalDeviceIndex
    MIN-ACCESS  read-only
    DESCRIPTION
        "It is conformant to implement this object as read-only."
    OBJECT      xcmHrSWRunNextIndex
    MIN-ACCESS  read-only
    DESCRIPTION
        "It is conformant to implement this object as read-only."
    OBJECT      xcmHrSWRunPreviousIndex
    MIN-ACCESS  read-only
    DESCRIPTION
        "It is conformant to implement this object as read-only."
    OBJECT      xcmHrSWInstalledRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrSWInstalledAdminName
    SYNTAX      XcmFixedLocaleDisplayString (SIZE (0..32))
    MIN-ACCESS  read-only
    DESCRIPTION
        "It is conformant to implement this object as read-only, and
        only 32 octets maximum string length need be supported."
    OBJECT      xcmHrSWInstalledPhysicalIndex
    MIN-ACCESS  read-only
    DESCRIPTION
        "It is conformant to implement this object as read-only."
    OBJECT      xcmHrSWInstalledLogicalIndex
    MIN-ACCESS  read-only
    DESCRIPTION
        "It is conformant to implement this object as read-only."
    OBJECT      xcmHrSWInstalledNextIndex
    MIN-ACCESS  read-only
    DESCRIPTION
        "It is conformant to implement this object as read-only."
    OBJECT      xcmHrSWInstalledPreviousIndex
    MIN-ACCESS  read-only
    DESCRIPTION
        "It is conformant to implement this object as read-only."
    OBJECT      xcmHrDevDetailRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevDetailUnitClass
    MIN-ACCESS  read-only
    DESCRIPTION
        "It is conformant to implement this object as read-only."
    OBJECT      xcmHrDevDetailUnit
    MIN-ACCESS  read-only
    DESCRIPTION
        "It is conformant to implement this object as read-only."
    OBJECT      xcmHrDevDetailValueInteger
    MIN-ACCESS  read-only
    DESCRIPTION
        "It is conformant to implement this object as read-only."
    OBJECT      xcmHrDevDetailValueOID
    MIN-ACCESS  read-only
    DESCRIPTION
        "It is conformant to implement this object as read-only."
    OBJECT      xcmHrDevDetailValueString
    SYNTAX      OCTET STRING (SIZE (0..1))
    MIN-ACCESS  read-only
    DESCRIPTION
        "It is conformant to implement this object as read-only, and
        only 1 octet maximum string length need be supported.
        Usage:  Conformant implementations MUST encrypt passwords, keys,
        and other security information stored in this string object."
    OBJECT      xcmHrStorageRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrStorageRealization
    MIN-ACCESS  read-only
    DESCRIPTION
        "It is conformant to implement this object as read-only."
    OBJECT      xcmHrStorageProductDeviceIndex
    MIN-ACCESS  read-only
    DESCRIPTION
        "It is conformant to implement this object as read-only."
    OBJECT      xcmHrStoragePlatformDeviceIndex
    MIN-ACCESS  read-only
    DESCRIPTION
        "It is conformant to implement this object as read-only."
    OBJECT      xcmHrStorageMatchingDeviceIndex
    MIN-ACCESS  read-only
    DESCRIPTION
        "It is conformant to implement this object as read-only."
    OBJECT      xcmHrStorageSWRunIndex
    MIN-ACCESS  read-only
    DESCRIPTION
        "It is conformant to implement this object as read-only."
    OBJECT      xcmHrStorageSWInstalledIndex
    MIN-ACCESS  read-only
    DESCRIPTION
        "It is conformant to implement this object as read-only."
    OBJECT      xcmHrStorageNextIndex
    MIN-ACCESS  read-only
    DESCRIPTION
        "It is conformant to implement this object as read-only."
    OBJECT      xcmHrStoragePreviousIndex
    MIN-ACCESS  read-only
    DESCRIPTION
        "It is conformant to implement this object as read-only."
    OBJECT      xcmHrStoragePhysicalIndex
    MIN-ACCESS  read-only
    DESCRIPTION
        "It is conformant to implement this object as read-only."
    OBJECT      xcmHrStorageDetailRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrStorageDetailUnitClass
    MIN-ACCESS  read-only
    DESCRIPTION
        "It is conformant to implement this object as read-only."
    OBJECT      xcmHrStorageDetailUnit
    MIN-ACCESS  read-only
    DESCRIPTION
        "It is conformant to implement this object as read-only."
    OBJECT      xcmHrStorageDetailValueInteger
    MIN-ACCESS  read-only
    DESCRIPTION
        "It is conformant to implement this object as read-only."
    OBJECT      xcmHrStorageDetailValueOID
    MIN-ACCESS  read-only
    DESCRIPTION
        "It is conformant to implement this object as read-only."
    OBJECT      xcmHrStorageDetailValueString
    SYNTAX      OCTET STRING (SIZE (0..1))
    MIN-ACCESS  read-only
    DESCRIPTION
        "It is conformant to implement this object as read-only, and
        only 1 octet maximum string length need be supported.
        Usage:  Conformant implementations MUST encrypt passwords, keys,
        and other security information stored in this string object."
    OBJECT      xcmHrDevCoverRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevCoverName
    SYNTAX      XcmFixedLocaleDisplayString (SIZE (0..32))
    MIN-ACCESS  read-only
    DESCRIPTION
        "It is conformant to implement this object as read-only, and
        only 32 octets maximum string length need be supported."
    OBJECT      xcmHrDevCoverDescription
    SYNTAX      XcmFixedLocaleDisplayString (SIZE (0..32))
    MIN-ACCESS  read-only
    DESCRIPTION
        "It is conformant to implement this object as read-only, and
        only 32 octets maximum string length need be supported."
    OBJECT      xcmHrDevCoverTypeCover
    MIN-ACCESS  read-only
    DESCRIPTION
        "It is conformant to implement this object as read-only."
    OBJECT      xcmHrDevCoverStatusOpen
    MIN-ACCESS  read-only
    DESCRIPTION
        "It is conformant to implement this object as read-only."
    OBJECT      xcmHrDevAlertRowStatus
    SYNTAX      INTEGER { active(1) }   
    MIN-ACCESS  read-only
    DESCRIPTION
        "It is conformant to implement this object as read-only, and
        only one of the enumerated values for the 'RowStatus' textual
        convention need be supported, specifically:  active(1)."
    OBJECT      xcmHrDevAlertCodeString
    SYNTAX      XcmFixedLocaleDisplayString (SIZE (0..1))
    DESCRIPTION
        "It is conformant to implement this object as read-only, and
        only 1 octet maximum string length need be supported."
    OBJECT      xcmHrDevAlertDescription
    SYNTAX      XcmFixedLocaleDisplayString (SIZE (0..32))
    DESCRIPTION
        "It is conformant to implement this object as read-only, and
        only 32 octets maximum string length need be supported."
    OBJECT      xcmHrConsoleScreenName
    SYNTAX      XcmFixedLocaleDisplayString (SIZE (0..32))
    DESCRIPTION
        "It is conformant to implement this object as read-only, and
        only 32 octets maximum string length need be supported."
    OBJECT      xcmHrConsoleScreenDescription
    SYNTAX      XcmFixedLocaleDisplayString (SIZE (0..32))
    DESCRIPTION
        "It is conformant to implement this object as read-only, and
        only 32 octets maximum string length need be supported."
    OBJECT      xcmHrConsoleTabName
    SYNTAX      XcmFixedLocaleDisplayString (SIZE (0..32))
    DESCRIPTION
        "It is conformant to implement this object as read-only, and
        only 32 octets maximum string length need be supported."
    OBJECT      xcmHrConsoleTabDescription
    SYNTAX      XcmFixedLocaleDisplayString (SIZE (0..32))
    DESCRIPTION
        "It is conformant to implement this object as read-only, and
        only 32 octets maximum string length need be supported."
    OBJECT      xcmHrConsoleDefaultService
    MIN-ACCESS  read-only
    DESCRIPTION
        "It is conformant to implement this object as read-only."
    OBJECT      xcmHrConsoleBrightness
    MIN-ACCESS  read-only
    DESCRIPTION
        "It is conformant to implement this object as read-only."
    OBJECT      xcmHrConsoleContrast
    MIN-ACCESS  read-only
    DESCRIPTION
        "It is conformant to implement this object as read-only."
    OBJECT      xcmHrConsoleAccessibility
    MIN-ACCESS  read-write
    DESCRIPTION
        "It is conformant to implement this object as read-only."
    OBJECT      xcmHrConsoleAutoClearTime
    MIN-ACCESS  read-only
    DESCRIPTION
        "It is conformant to implement this object as read-only."
    OBJECT      xcmHrConsoleInsertTimeout
    MIN-ACCESS  read-only
    DESCRIPTION
        "It is conformant to implement this object as read-only."
    OBJECT      xcmHrConsoleTray1Timeout
    MIN-ACCESS  read-only
    DESCRIPTION
        "It is conformant to implement this object as read-only."
    OBJECT      xcmHrConsoleTray2nTimeout
    MIN-ACCESS  read-only
    DESCRIPTION
        "It is conformant to implement this object as read-only."
    OBJECT      xcmHrConsoleLoadTimeout
    MIN-ACCESS  read-only
    DESCRIPTION
        "It is conformant to implement this object as read-only."
    OBJECT      xcmHrConsoleSoundVolume
    MIN-ACCESS  read-only
    DESCRIPTION
        "It is conformant to implement this object as read-only."
    OBJECT      xcmHrConsoleSoundDuration
    MIN-ACCESS  read-only
    DESCRIPTION
        "It is conformant to implement this object as read-only."
    ::= { xcmHrMIBConformance 3 }
--
--
xcmHrGeneralGroup OBJECT-GROUP
    OBJECTS {
        xcmHrGeneralRowStatus,
        xcmHrGeneralVersionID,
        xcmHrGeneralVersionDate,
        xcmHrGeneralGroupSupport,
        xcmHrGeneralStorageLast,
        xcmHrGeneralDeviceLast,
        xcmHrGeneralFSLast,
        xcmHrGeneralSWRunLast,
        xcmHrGeneralSWInstalledLast,
        xcmHrGeneralSystemFaultLast,
        xcmHrGeneralCreateSupport,
        xcmHrGeneralUpdateSupport
    }
    STATUS      current
    DESCRIPTION
        "The Host Resources Extensions MIB General Group"
    ::= { xcmHrMIBGroups 9 }
xcmHrDevInfoGroup OBJECT-GROUP
    OBJECTS {
        xcmHrDevInfoRowStatus,
        xcmHrDevInfoName,
        xcmHrDevInfoSerialNumber,
        xcmHrDevInfoRealization,
        xcmHrDevInfoXStatus,
        xcmHrDevInfoConditions,
        xcmHrDevInfoXConditions,
        xcmHrDevInfoInstallDate,
        xcmHrDevInfoResetDate,
        xcmHrDevInfoNextDeviceIndex,
        xcmHrDevInfoPreviousDeviceIndex,
        xcmHrDevInfoPhysicalDeviceIndex,
        xcmHrDevInfoPriority
    }
    STATUS      current
    DESCRIPTION
        "The Host Resources Extensions MIB Device Info Group"
    ::= { xcmHrMIBGroups 3 }
xcmHrDevHelpGroup OBJECT-GROUP
    OBJECTS {
        xcmHrDevHelpRowStatus,
        xcmHrDevHelpOperatorMessage,
        xcmHrDevHelpProblemMessage,
        xcmHrDevHelpCommsAddressIndex
    }
    STATUS      current
    DESCRIPTION
        "The Host Resources Extensions MIB Device Help Group
        Implementation of this group is DEPRECATED (as of XCMI v4.1)
        and conforming implementations SHOULD use 'deviceHelp...'
        details in 'xcmHrDevDetailTable' instead."
    ::= { xcmHrMIBGroups 4 }
xcmHrDevMgmtGroup OBJECT-GROUP
    OBJECTS {
        xcmHrDevMgmtRowStatus,
        xcmHrDevMgmtCommandRequest,
        xcmHrDevMgmtCommandData,
        xcmHrDevMgmtCommandStatus,
        xcmHrDevMgmtUserPassword,
        xcmHrDevMgmtOperatorPassword,
        xcmHrDevMgmtAdminPassword,
        xcmHrDevMgmtCommandInProgress,
        xcmHrDevMgmtUserName, 
        xcmHrDevMgmtOperatorName,
        xcmHrDevMgmtAdminName
    }
    STATUS      current
    DESCRIPTION
        "The Host Resources Extensions MIB Device Mgmt Group"
    ::= { xcmHrMIBGroups 5 }
xcmHrDevPowerGroup OBJECT-GROUP
    OBJECTS {
        xcmHrDevPowerRowStatus,
        xcmHrDevPowerWarmUpSupport,
        xcmHrDevPowerCoolDownSupport,
        xcmHrDevPowerEnergySaveSupport,
        xcmHrDevPowerTimeUnit,
        xcmHrDevPowerWarmUpDelay,
        xcmHrDevPowerWarmUpDuration,
        xcmHrDevPowerCoolDownDelay,
        xcmHrDevPowerCoolDownDuration,
        xcmHrDevPowerEnergySaveDelay,
        xcmHrDevPowerEnergySaveDuration,
        xcmHrDevPowerWakeUpSupport,
        xcmHrDevPowerWakeUpDelay,
        xcmHrDevPowerWakeUpDuration,
        xcmHrDevPowerShutdownDelay,
        xcmHrDevPowerShutdownDuration,
        xcmHrDevPowerStartupDelay,
        xcmHrDevPowerStartupDuration
    }
    STATUS      current
    DESCRIPTION
        "The Host Resources Extensions MIB Device Power Group"
    ::= { xcmHrMIBGroups 6 }
xcmHrDevTrafficGroup OBJECT-GROUP
    OBJECTS {
        xcmHrDevTrafficRowStatus,
        xcmHrDevTrafficInputSupport,
        xcmHrDevTrafficOutputSupport,
        xcmHrDevTrafficInputUnit,
        xcmHrDevTrafficOutputUnit,
        xcmHrDevTrafficInputCount,
        xcmHrDevTrafficOutputCount,
        xcmHrDevTrafficInputMaxSize,
        xcmHrDevTrafficOutputMaxSize,
        xcmHrDevTrafficInputTimeout,
        xcmHrDevTrafficOutputTimeout
    }
    STATUS      current
    DESCRIPTION
        "The Host Resources Extensions MIB Device Traffic Group"
    ::= { xcmHrMIBGroups 7 }
xcmHrSystemFaultGroup OBJECT-GROUP
    OBJECTS {
        xcmHrSystemFaultRowStatus,
        xcmHrSystemFaultCode,
        xcmHrSystemFaultString,
        xcmHrSystemFaultReferenceOID,
        xcmHrSystemFaultHrDeviceIndex,
        xcmHrSystemFaultDate
    }
    STATUS      current
    DESCRIPTION
        "The Host Resources Extensions MIB System Fault Group"
    ::= { xcmHrMIBGroups 8 }
xcmHrDevCalendarGroup OBJECT-GROUP
    OBJECTS {
        xcmHrDevCalendarRowStatus,
        xcmHrDevCalendarExplicitDate,
        xcmHrDevCalendarCommandRequest,
        xcmHrDevCalendarCommandData
    }
    STATUS      current
    DESCRIPTION
        "The Host Resources Extensions MIB Device Calendar Group"
    ::= { xcmHrMIBGroups 10 }
xcmHrSWRunGroup OBJECT-GROUP
    OBJECTS {
        xcmHrSWRunRowStatus,
        xcmHrSWRunAdminName,
        xcmHrSWRunXStatus,
        xcmHrSWRunRowCreateDate,
        xcmHrSWRunPhysicalDeviceIndex,
        xcmHrSWRunLogicalDeviceIndex,
        xcmHrSWRunNextIndex,
        xcmHrSWRunPreviousIndex
    }
    STATUS      current
    DESCRIPTION
        "The Host Resources Extensions MIB Software Running Ext Group"
    ::= { xcmHrMIBGroups 11 }
xcmHrSWInstalledGroup OBJECT-GROUP
    OBJECTS {
        xcmHrSWInstalledRowStatus,
        xcmHrSWInstalledAdminName,
        xcmHrSWInstalledXStatus,
        xcmHrSWInstalledRowCreateDate,
        xcmHrSWInstalledPhysicalIndex,
        xcmHrSWInstalledLogicalIndex,
        xcmHrSWInstalledNextIndex,
        xcmHrSWInstalledPreviousIndex
    }
    STATUS      current
    DESCRIPTION
        "The Host Resources Extensions MIB Software Installed Ext Group"
    ::= { xcmHrMIBGroups 12 }
xcmHrDevDetailGroup OBJECT-GROUP
    OBJECTS {
        xcmHrDevDetailType,
        xcmHrDevDetailIndex,
        xcmHrDevDetailRowStatus,
        xcmHrDevDetailUnitClass,
        xcmHrDevDetailUnit,
        xcmHrDevDetailValueInteger,
        xcmHrDevDetailValueOID,
        xcmHrDevDetailValueString
    }
    STATUS      current
    DESCRIPTION
        "The Host Resources Extensions MIB Device Detail Group"
    ::= { xcmHrMIBGroups 13 }
xcmHrStorageGroup OBJECT-GROUP
    OBJECTS {
        xcmHrStorageRowStatus,
        xcmHrStorageRealization,
        xcmHrStorageStatus,
        xcmHrStorageProductDeviceIndex,
        xcmHrStoragePlatformDeviceIndex,
        xcmHrStoragePagingDeviceIndex,
        xcmHrStorageMatchingDeviceIndex,
        xcmHrStorageSWRunIndex,
        xcmHrStorageSWInstalledIndex,
        xcmHrStorageNextIndex,
        xcmHrStoragePreviousIndex,
        xcmHrStoragePhysicalIndex
    }
    STATUS      current
    DESCRIPTION
        "The Host Resources Extensions MIB Storage Ext Group"
    ::= { xcmHrMIBGroups 14 }
xcmHrStorageDetailGroup OBJECT-GROUP
    OBJECTS {
        xcmHrStorageDetailRowStatus,
        xcmHrStorageDetailUnitClass,
        xcmHrStorageDetailUnit,
        xcmHrStorageDetailValueInteger,
        xcmHrStorageDetailValueOID,
        xcmHrStorageDetailValueString
    }
    STATUS      current
    DESCRIPTION
        "The Host Resources Extensions MIB Storage Detail Group"
    ::= { xcmHrMIBGroups 15 }
xcmHrDevCoverGroup OBJECT-GROUP
    OBJECTS {
        xcmHrDevCoverRowStatus,
        xcmHrDevCoverName,
        xcmHrDevCoverDescription,
        xcmHrDevCoverTypeCover,
        xcmHrDevCoverStatusOpen
    }
    STATUS      current
    DESCRIPTION
        "The Host Resources Extensions MIB Device Cover Group"
    ::= { xcmHrMIBGroups 16 }
xcmHrDevAlertGroup OBJECT-GROUP
    OBJECTS {
        xcmHrDevAlertRowStatus,
        xcmHrDevAlertSeverityLevel,
        xcmHrDevAlertTrainingLevel,
        xcmHrDevAlertCodeInteger,
        xcmHrDevAlertCodeString,
        xcmHrDevAlertDescription,
        xcmHrDevAlertReferenceOID,
        xcmHrDevAlertDateAndTime,
        xcmHrDevAlertTitle,
        xcmHrDevAlertHelpReference,
        xcmHrDevAlertReferenceIndex,
        xcmHrDevAlertReferenceLocation,
        xcmHrDevAlertDevAlertIndex      
    }
    STATUS      current
    DESCRIPTION
        "The Host Resources Extensions MIB Device Alert Group"
    ::= { xcmHrMIBGroups 17 }
xcmHrConsoleScreenGroup OBJECT-GROUP
    OBJECTS {
        xcmHrConsoleScreenName,
        xcmHrConsoleScreenDescription,
        xcmHrConsoleScreenParentIndex,
        xcmHrConsoleScreenPriority,
        xcmHrConsoleScreenTabCount
    }
    STATUS      current
    DESCRIPTION
        "The Host Resources Extensions MIB Console Screen Group"
    ::= { xcmHrMIBGroups 18 }
xcmHrConsoleTabGroup OBJECT-GROUP
    OBJECTS {
        xcmHrConsoleTabName,
        xcmHrConsoleTabDescription,
        xcmHrConsoleTabScreenIndex,
        xcmHrConsoleTabPriority
    }
    STATUS      current
    DESCRIPTION
        "The Host Resources Extensions MIB Console Tab Group"
    ::= { xcmHrMIBGroups 19 }
xcmHrSuppliesGroup OBJECT-GROUP
    OBJECTS {
    xcmHrSuppliesReferenceOID,
    xcmHrSuppliesType,
    xcmHrSuppliesClass,
    xcmHrSuppliesDescr,
    xcmHrSuppliesPartNumber 
    }
    STATUS      current
    DESCRIPTION
        "The Host Resources Extensions MIB Supplies Group"
    ::= { xcmHrMIBGroups 20 }
xcmHrDetailGroup OBJECT-GROUP
    OBJECTS {
    xcmHrDetailUnitClass,
    xcmHrDetailUnit,
    xcmHrDetailValueInteger,
    xcmHrDetailValueOID,
    xcmHrDetailValueString,
    xcmHrDetailDescription
 }
    STATUS      current
    DESCRIPTION
        "The Host Resources Extensions MIB Detail Group"
    ::= { xcmHrMIBGroups 21 }
xcmHrConsoleGroup OBJECT-GROUP
    OBJECTS {
        xcmHrConsoleDefaultService,
        xcmHrConsoleBrightness,
        xcmHrConsoleContrast,
        xcmHrConsoleAccessibility,
        xcmHrConsoleAutoClearTime,
        xcmHrConsoleInsertTimeout,
        xcmHrConsoleTray1Timeout,
        xcmHrConsoleTray2nTimeout,
        xcmHrConsoleLoadTimeout,
        xcmHrConsoleSoundVolume,
        xcmHrConsoleSoundDuration
    }
    STATUS      current
    DESCRIPTION
        "The Host Resources Extensions MIB Console Group"
    ::= { xcmHrMIBGroups 22 }
xcmPrintTC OBJECT-IDENTITY -- MODULE-IDENTITY
    STATUS   current
    DESCRIPTION "
        Version: 6.004.pub
        XCMI Extensions to Printer MIB Textual Conventions.
        This Module provides Xerox extensions of the IETF Printer MIB.
        Copyright (C) 1997-2013 Xerox Corporation. All Rights Reserved."
    ::= { xeroxCommonMIB 54 }
--
--
--
--
XcmPrtAuxSheetContent ::= TEXTUAL-CONVENTION
    STATUS      current
    DESCRIPTION "
        Auxiliary sheets are added by the printing system and
        are not part of the actual print job. Examples include
        error pages and banner pages.
        This textual convention is used to specify the information
        content of auxiliary sheets."
    SYNTAX INTEGER {
                other(1),
                unknown(2),
                notSpecified(3),
                concise(5),              
                verbose(6)               
                }
XcmPrtAuxSheetType ::= TEXTUAL-CONVENTION
    STATUS      current
    DESCRIPTION "
        Auxiliary sheets are added by the printing system and
        are not part of the actual print job.
        This attribute uniquely identifies an auxiliary-sheet,
        which includes the types jobErrorSheet and printerStartupSheet.
        'printerStartupSheet' is a sheet printed shortly after power-up
        when the device is ready.  Typical startup pages include test
        patterns and/or printer configuration information.
        'jobErrorSheet' is a sheet printed with error messages
        generated during the printing of a job-result-set that is to be
        printed with the hardcopy output of that job-result-set, and
        should be printed on an ending sheet of the job-result-set, or
        some similar sheet.  These sheets are not
        a part of any job-copy.  If no error messages have been
        generated, the device need not print an extra page.
        The default for this page type should be 'On'.
        The following Auxiliary-sheet-package types can be specified 
        either for a job component (job result set or job copy) or
        document (document result set or document copy).
        For now, only the jobSetStart package has been enumerated.   
        'jobSetStart' - Auxiliary-sheet starts each result-set
                        Sometimes referred to as a jobBanner sheet
        'jobSetEnd'   - Auxiliary-sheet at the end of a result set "
    REFERENCE   "
        ISO/IEC 10175-1:1996(E)
        Section 9.10.2.2: Delivery-methods for hardcopy output logs
        Section 9.11.1:   Auxiliary-sheet-package identifier"
    SYNTAX INTEGER {
                other(-1),
                unknown(-2),
                notSpecified(-3),
                jobSetStart(1),
                jobSetEnd(2),
                printerStartupSheet(101),
                jobErrorSheet(102)
                }
XcmPrtChannelType ::= TEXTUAL-CONVENTION
    STATUS      current
    DESCRIPTION "
        This enumeration indicates the type of channel that is
        receiving jobs.
        This enumeration is being added to the IETF Printer MIB.
        This is an IETF type 2 enum."
    SYNTAX INTEGER {
                       other(1),
                       chSerialPort(3),
                       chParallelPort(4),
                       chIEEE1284Port(5),
                       chSCSIPort(6),
                       chAppleTalkPAP(7),
                           --
                           --
                       chLPDServer(8),
                           --
                       chNetwareRPrinter(9),
                           --
                           --
                           --
                           --
                           --
                        chNetwarePServer(10),
                           --
                           --
                           --
                           --
                           --
                           --
                       chPort9100(11),
                       chAppSocket(12),
                       chFTP(13),         
                       chTFTP(14),        
                       chDLCLLCPort(15),
                       chIBM3270(16),     
                       chIBM5250(17),     
                       chFax(18),
                       chIEEE1394(19),
                       chTransport1(20),
                           -- in RFC 1700 or current "Assigned
                           -- Numbers" RFC. This RFC should also be
                       chCPAP(21),      
                       chPCPrint(26),   
                       chServerMessageBlock(27),
                           --
                           --
                       chPSM(28),       
                       chSystemObjectManager(31), 
                       chDECLAT(32),
                           --
                           --
                           --
                           --
                       chNPAP(33),
                       chUSB(34),    
                       chIRDA(35),   
                       chPrintXChange(36), 
                       chPortTCP(37),
                           -- A unidirectional "raw" TCP
                           --
                           --
                       chBidirPortTCP(38),
                           --
                       chUNPP(39),
                       chAppleTalkADSP(40),
                       chPortSPX(41),
                           --
                           --
                           --
                           --
                           --
                           -- There must be exactly one "Net" and
                           -- one "Node" and one "Socket" entry. A
                       chPortHTTP(42),
                       chNDPS(43)
                           --
                           --
                }
XcmPrtGroupSupport ::= TEXTUAL-CONVENTION
    STATUS      current
    DESCRIPTION "
        The terse conformance statement of ALL mandatory, conditionally
        mandatory, and optional Printer MIB Extension object groups,
        specified in a bit-mask.
        The current set of values (which may be extended in the future)
        is given below:
              1 : xcmPrtBaseGroup                    
              2 : xcmPrtGeneralGroup                 
              4 : xcmPrtInputGroup                   
              8 : xcmPrtOutputGroup                  
             16 : xcmPrtChannelGroup                 
             32 : xcmPrtInterpreterGroup             
             64 : xcmPrtInputAliasGroup              
            128 : xcmPrtGeneralAuxSheetGroup         
            256 : xcmPrtGeneralProdSpecificGroup     
            512 : xcmPrtAuxPackageGroup              
           1024 : xcmPrtChannelProdSpecificGroup     
           2048 : xcmPrtInterpProdSpecificGroup      
           4096 : xcmPrtInterpPCLGroup               
           8192 : xcmPrtInterpPCLProdSpecificGroup   
          16384 : xcmPrtMediumTypeSupportedGroup     
          32768 : xcmPrtGeneralInstalledOptionsGroup 
        Usage:  Conforming management agents shall ALWAYS accurately
        report their support for XCMI Printer MIB Extensions
        object groups."
    SYNTAX      INTEGER (0..2147483647)  
XcmPrtIETFPrintMIBGroupSupport ::= TEXTUAL-CONVENTION
    STATUS      current
    DESCRIPTION "
        The terse conformance statement of ALL mandatory, conditionally
        mandatory, and optional IETF Printer MIB object groups,
        specified in a bit-mask.
        The current set of values (which may be extended in the future)
        is given below:
              1 : prtGeneralGroup               
              2 : prtResponsiblePartyGroup      
              4 : prtInputGroup                 
              8 : prtExtendedInputGroup         
             16 : prtInputMediaGroup            
             32 : prtOutputGroup                
             64 : prtExtendedOutputGroup        
            128 : prtOutputDimensionsGroup      
            256 : prtOutputFeaturesGroup        
            512 : prtMarkerGroup                
           1024 : prtMarkerSuppliesGroup        
           2048 : prtMarkerColorantGroup        
           4096 : prtMediaPathGroup             
           8192 : prtChannelGroup               
          16384 : prtInterpreterGroup           
          32768 : prtConsoleGroup               
          65536 : prtAlertTableGroup            
         131072 : prtAuxiliarySheetGroup        
         262144 : prtInputSwitchingGroup        
        Usage:  Conforming management agents shall ALWAYS accurately
        report their support for IETF Printer MIB object groups."
    REFERENCE   "See: IETF Printer MIB"
    SYNTAX      INTEGER (0..2147483647)  
XcmPrtInterpreterLangFamily ::= TEXTUAL-CONVENTION
    STATUS      current
    DESCRIPTION "
        This enumeration indicates the type of interpreter that is
        receiving jobs.
        This enumeration is being added to the IETF Printer MIB.
        This value is an IETF type 2 enumeration."
    SYNTAX INTEGER {
              other(1),
              unknown(2),
              langPCL(3),      
              langHPGL(4),     
              langPJL(5),      
              langPS(6),       
              langIPDS(7),     
              langPPDS(8),     
              langEscapeP(9),  
              langEpson(10),
              langDDIF(11),    
              langInterpress(12),
              langISO6429(13), 
              langLineData(14),
              langMODCA(15),   
              langREGIS(16),   
              langSCS(17),     
              langSPDL(18),    
              langTEK4014(19), 
              langPDS(20),
              langIGP(21),     
              langCodeV(22),   
              langDSCDSE(23),  
              langWPS(24),     
              langLN03(25),    
              langCCITT(26),
              langQUIC(27),    
              langCPAP(28),    
              langDecPPL(29),  
              langSimpleText(30),
              langNPAP(31),    
              langDOC(32),     
              langimPress(33), 
              langPinwriter(34),
              langNPDL(35),    
              langNEC201PL(36),
              langAutomatic(37),
              langPages(38),   
              langLIPS(39),    
              langTIFF(40),    
              langDiagnostic(41),
              langPSPrinter(42),
              langCaPSL(43),   
              langEXCL(44),    
              langLCDS(45),    
              langXES(46),     
              langPCLXL(47),   
              langART(48),     
                               -- Technical reference manual: "ART IV
                               -- Reference Manual", No F33M.
              langTIPSI(49),   
              langPrescribe(50),
                               -- "PRESCRIBE II Programming Manual"
              langLinePrinter(51),
              langIDP(52),     
              langXJCL(53),    
                               -- "ART IV Reference Manual", No F33M.
              langPDF(54),     
              langRPDL(55),    
                               -- Technical manual "RPDL command
                               -- reference" No.307029
              langIntermecIPL(56),
                               -- Technical Manual: "IPL Programmers
                               -- Reference Manual"
              langUBIFingerprint(57),
                               -- Reference Manual: "UBI Fingerprint
                               -- 7.1", No. 1-960434-00
              langUBIDirectProtocol(58)
                               -- Programmers guide: " UBI Direct
                               -- Protocol", No. 1-960419-00
          }
XcmPrtMediaTypeErrorPolicy ::= TEXTUAL-CONVENTION
    STATUS      current
    DESCRIPTION "
        Controls interpreter behavior when the requested Media Type
        is not currently available.
        * The values 'other' and 'unknown' are deprecated for
          conforming implementations.
        * 'abortJob' will cause the interpreter to abort the job
          with an appropriate error condition.
        * 'ignore' will cause the job to be printed on the default
          media as specified by xcmPrtInterpInputIndexDefault OR
          xcmPrtInterpPaperSizeDefault OR any available media
          deemed appropriate by the implementation.
          No adjustment will be made to the image size.
          Exact semantics of this setting are product specific.
        * 'interactWithOperator' will cause the printer to interact
          with the operator to determine what to do. For example,
          display a message at the operator console requesting the
          desired media. The semantics of this policy vary among
          different products and environments.
        * 'ignoreAfterTimeout' will cause the job to be ignored
          same as 'ignore' above, but not till after
          xcmPrtInterpErrorPolicyTimeout expires."
    REFERENCE "
        See: XcmPrtPageSizeErrorPolicy"
    SYNTAX INTEGER {
                other(1),
                unknown(2),
                notSpecified(3),
                abortJob(4),
                ignore(5),
                interactWithOperator(6),
                ignoreAfterTimeout(11)
                }
XcmPrtMediumClassType ::= TEXTUAL-CONVENTION
    STATUS      current
    DESCRIPTION "
        Paper size classes for a printer."
    SYNTAX INTEGER {
                other (1),
                unknown(2),
                notSpecified(3),
                northAmerica(4),
                iso(5),
                jis(6)
                }
XcmPrtMediumSize ::= TEXTUAL-CONVENTION
    STATUS      current
    DESCRIPTION "
        This attribute specifies the size of this medium by means of a
        pre-defined value.  The medium size specified in this manner may
        be one of the standard sizes to which object identifiers have
        been assigned in ISO/IEC 10175 (DPA), or another applicable
        standard, or for which a value has been created.
        Enumerations for DPA defined medium sizes are derived by adding
        1000 to the ISO/IEC 10175 enumerations.
        XCMI defined enumerations start at 10."
    REFERENCE   "ISO/IEC 10175-1:1996(E), Section 9.6.5: Medium-size"
    SYNTAX INTEGER {
                other(1),
                unknown(2),
                notSpecified(3),
                mediumSize13x18(10),       
                naLetter(1000),            
                naLegal(1001),             
                na10x13Envelope(1002),     
                na9x12Envelope(1003),      
                naNumber10Envelope(1004),  
                na7x9Envelope(1005),       
                na9x11Envelope(1006),      
                na10x14Envelope(1007),     
                naNumber9Envelope(1008),   --
                na6x9Envelope(1009),       
                na10x15Envelope(1010),     
                a(1011),                   
                b(1012),                   
                c(1013),                   
                d(1014),                   
                e(1015),                   
                monarchEnvelope(1016),     
                isoA0(1020),               
                isoA1(1021),               
                isoA2(1022),               
                isoA3(1023),               
                isoA4(1024),               
                isoA5(1025),               
                isoA6(1026),               
                isoA7(1027),               
                isoA8(1028),               
                isoA9(1029),               
                isoA10(1030),              
                isoB0(1040),               
                isoB1(1041),               
                isoB2(1042),               
                isoB3(1043),               
                isoB4(1044),               
                isoB5(1045),               
                isoB6(1046),               
                isoB7(1047),               
                isoB8(1048),               
                isoB9(1049),               
                isoB10(1050),              
                isoC3(1063),               
                isoC4(1064),               
                isoC5(1065),               
                isoC6(1066),               
                isoDesignatedLong(1067),   
                jisB0(1080),               
                jisB1(1081),               
                jisB2(1082),               
                jisB3(1083),               
                jisB4(1084),               
                jisB5(1085),               
                jisB6(1086),               
                jisB7(1087),               
                jisB8(1088),               
                jisB9(1089),               
                jisB10(1090),              
                executive(1100),            
                folio(1101),                
                invoice(1102),              
                ledger(1103),  
                quarto(1104)                
                }
XcmPrtOutputOffsetStackingType ::= TEXTUAL-CONVENTION
    STATUS      current
    DESCRIPTION "
        Offset stacking types further refining that specified by
        the object prtOutputOffsetStacking in the Printer MIB.
        - offsetOnJob means that each job is offset but copies within
          the job are not offset.
        - offsetOnJobAndCopy means that there is an offset on job and
          copy boundaries."
    REFERENCE "Printer MIB prtOutputOffsetStacking object"
    SYNTAX INTEGER {
                other(1),
                unknown(2),
                notSpecified(3),
                noOffset(4),
                offsetOnJob(5),
                offsetOnJobandCopy(6)
                }
XcmPrtOutputStaplePosition ::= TEXTUAL-CONVENTION
    STATUS      current
    DESCRIPTION "
        This Textual Convention enumerates possible staple positions.
        The staple positions enumerated are relative to the
        physical layout of the finishing device.  
        The observer is on the front side of the finisher which
        is defined as for sheets passing through the finisher.
        The 'front' side is the side from which staples are pushed.
        The physical corners of the finishing device are specified
        by designating the corner of the finisher where a portrait
        long-edge fed sheet with english/left-to-right text is stapled
        as staplePosCorner1, and then the other corners are numbered
        in a counter-clockwise direction with the observer on the
        front side of the finisher.  
        'staplePosCorner1', 'staplePosCorner2', 'staplePosCorner3', and
        'staplePosCorner4' indicate a single staple in the specified
        corner.  This object does not specify the angle of the staple,
        e.g. 90, 45 or zero degrees.
        'stapleEdge...' indicates multiple staples on the edge
        specified.  'stapleEdge12' is the edge which include Corner1
        and Corner2.
        The current set of values (which may be extended in the future)
        is given below:
              1 : staplePosCorner1                
              2 : staplePosCorner2                
              4 : staplePosCorner3                
              8 : staplePosCorner4                
             16 : stapleEdge12                    
             32 : stapleEdge23                    
             64 : stapleEdge34                    
            128 : stapleEdge14                    -- 2**7"
    REFERENCE "
        See: 'xcmPrtOutputStaplePosDefault'
        See: 'xcmPrtOutputStaplePosSupported'"
    SYNTAX  INTEGER(0..255)
XcmPrtPageSizeErrorPolicy ::= TEXTUAL-CONVENTION
    STATUS      current
    DESCRIPTION "
        Controls interpreter behavior when the requested Page Size
        is not currently available.
        * The values 'other' and 'unknown' are deprecated for
          conforming implementations.
        * 'abortJob' will cause the interpreter to abort the job
          with an appropriate error condition.
        * 'ignore' will cause the job to be printed on the default
          media as specified by xcmPrtInterpInputIndexDefault OR
          xcmPrtInterpPaperSizeDefault OR any available media
          deemed appropriate by the implementation.
          No adjustment will be made to the image size.
          Exact semantics of this setting are product specific.
        * 'interactWithOperator' will cause the printer to interact
          with the operator to determine what to do. For example,
          display a message at the operator console requesting the
          desired media. The semantics of this policy vary among
          different products and environments.
        * 'useNearestAndAdjust' will cause the job to be printed on
          the nearest available media (as described below). The
          interpreter will adjust the image size (by scaling and
          centering) to fit.
        * 'useNextLargerAndAdjust' will cause the job to be printed
          on the next larger available media (as described below). 
          The interpreter will adjust the image size (by scaling and 
          centering) to fit.
        * 'useNearest' will cause the job to be printed on
          the nearest available media (as described below).
          No adjustment will be made to the image size.
        * 'useNextLarger' will cause the job to be printed on
          the next larger available media (as described below). 
          No adjustment will be made to the image size.
        * 'ignoreAfterTimeout' will cause the job to be ignored
          same as ignore' above, but not till after
          xcmPrtInterpErrorPolicyTimeout expires.
        In the above descriptions, nearest size is defined as the
        one closest in area to the requested size. The next larger
        size is the one that is at least as large as the requested
        size in both width and height and is smallest in area.
        To adjust the page means to scale the page image (if 
        necessary) to fit the medium, then center the image on
        the medium."
    REFERENCE "
        PostScript Language Reference Manual, second edition,
        Adobe Systems Incorporated, pp 239-249.
        See: XcmPrtMediaTypeErrorPolicy"
    SYNTAX INTEGER {
                other(1),
                unknown(2),
                notSpecified(3),
                abortJob(4),
                ignore(5),
                interactWithOperator(6),
                useNearestAndAdjust(7),
                useNextLargerAndAdjust(8),
                useNearest(9),
                useNextLarger(10),
                ignoreAfterTimeout(11)
                }
XcmPrtPCLFontSource ::= TEXTUAL-CONVENTION
    STATUS      current
    DESCRIPTION "
        "
    REFERENCE "
        See: PJL Technical Reference Manual- FONTSOURCE"
    SYNTAX INTEGER {
               other(1),
               unknown(2),
               notSpecified(3),
               internal(20),     
               romSimm1(41),     
               romSimm2(42),     
               romSimm3(43),     
               romSimm4(44),     
               romSimm5(45),     
               romSimm6(46),     
               romSimm7(47),     
               romSimm8(48),     
               romSimm9(49),     
               cartridge1(61),   
               cartridge2(62),   
               cartridge3(63),   
               cartridge4(64),   
               cartridge5(65),   
               cartridge6(66),   
               cartridge7(67),   
               cartridge8(68),   
               cartridge9(69),   
               permanentSoft(80) 
               }
XcmPrtPlex ::= TEXTUAL-CONVENTION
    STATUS      current
    DESCRIPTION "
        This Textual Convention enumerates plex modes which may
        be supported by a printer or interpreter.  A plex mode
        specifies whether pages are to be printed one-sided or
        two-sided, as well as the content orientation between
        consecutive pages.
        For the XcmPrtPlex TC, the following definitions apply:
          'one-sided' - Print on only one side of each sheet.
          'two-sided' - Print on both sides of each sheet.
          'simplex' - The document pages are to be oriented so as to
               condition them for one-sided printing.
          'long-edge-bind'  - The document pages are to be oriented so
               as to condition them for two-sided printing, bound along
               the length (the longer edge) of the physical page.
          'short-edge-bind' - The document pages are to be oriented so
               as to condition them for two-sided printing, bound along
               the width (the shorter edge) of the physical page. 
        XcmPrtPlex's representation is bit-encoded, so that a device
        may show multiple plex modes supported.  The value zero shall
        mean notSpecified.
        The following XcmPrtPlex values and meanings are defined:
        0x001 simplex, one-sided
        0X002 simplex, two-sided
        0x010 long-edge-bind,  one-sided
        0x020 long-edge-bind,  two-sided
        0x040 short-edge-bind, one-sided
        0x080 short-edge-bind, two-sided
        The following describes the relationship of the xcmPrtPlex
        modes to DPA, PostScript and PCL.
        DPA:
        In DPA, Plex specifies whether the page images of the
        output document are to be conditioned for (eventual) one-sided
        or two-sided printing, and also specifies whether the
        relative orientation between consecutive page-images is to
        be altered.
        In DPA, the Plex modes specified are named 'Simplex', 'Duplex'
        and 'Tumble'.  However, 'Duplex' would more accurately be named
        bindLongEdge, and 'Tumble' would more accurately be named
        bindShortEdge.
        As written in DPA, 'Whether the images are portrait or
        landscape, the binding edge is parallel to: the y axis for
        'duplex', and the x axis for 'tumble'.  This last observation
        is important for understanding when to use 'tumble'.  If the
        binding edge of the document is along the y-axis, the plex is
        'duplex', whether the orientation is portrait or landscape, and
        if the binding-edge is along the x-axis, the plex is 'tumble',
        whether the orientation is portrait or landscape.
        In DPA, a separate attribute, 'Sides', specifies 1-sided or
        2-sided printing.
        In DPA, the value of this attribute may also be used by the
        presentation processes of some document formats to determine
        whether or not to print certain designated pages 
        (e.g. the extra blank pages needed in two-sided printing to
        cause sections to begin on the righthand side of a book, or
        recto page).
        The following enumerations are relevant to DPA:
        simplexOneSided,       simplexTwoSided,
        bindLongEdgeOneSided,  bindLongEdgeTwoSided,
        bindShortEdgeOneSided, bindShortEdgeTwoSided.
        PostScript:
        In PostScript, the keys 'duplex' and 'tumble' are booleans
        which specify relative orientation between consecutive pages,
        and to the number of sides printed.   
        If 'Duplex' is False, pages are printed 1-sided, i.e. 'simplex'.
        If 'Duplex' is True,  pages are printed 2-sided.
        (For most PostScript interpreters, only when 'Duplex' is set to
        True) 'Tumble' specifies how the page images on opposite
        sides of a sheet are oriented with respect to each other.  
        If 'Tumble' is False, the default user spaces of the two pages
        are oriented such that the highest value of y in the two spaces
        lie along the same edge of the media.  Informally, a Tumble
        value of False produces output suitable for binding on the left
        or right.  When the default user space is set to a portrait
        'pagesize', setting Tumble to false is the same as using the
        XcmPrtPlex attribute longEdgeBind.  When the default user space
        is set to a landscape 'pagesize', setting Tumble to false is the
        same as using the XcmPrtPlex attribute shortEdgeBind.
        If 'Tumble' is True,  the default user spaces of the two pages
        are oriented such that the highest value of y in the two spaces
        lie along opposite edges of the media. Informally, a Tumble
        value of True produces output suitable for binding on the top
        or bottom.  When the default user space is set to a landscape
        'pagesize', setting Tumble to true is the same as using the
        XcmPrtPlex attribute shortEdgeBind.  When the default user space
        is set to a landscape 'pagesize', setting Tumble to true is the
        same as using the XcmPrtPlex attribute longEdgeBind.
        The following XcmPrtPlex enumerations are
        relevant to PostScript:
            bindLongEdgeOneSided,  bindLongEdgeTwoSided,
            bindShortEdgeOneSided, bindShortEdgeTwoSided.
        Typically (ie, for a Portrait default user space):
        OneSided      maps to the duplex boolean set to false
        TwoSided      maps to the duplex boolean set to true
        bindEdgeLong  maps to the tumble boolean set to false
        bindEdgeShort maps to the tumble boolean set to true
        PCL:
        In PCL, the attributes simplex, duplex long-edge-binding, and
        duplex short-edge-binding, along with content orientation,
        landscape or portrait, detail the number of sides to be printed,
        content orientation, and relative orientation between
        consecutive pages.  The PCL model matches that of DPA.
        The following XcmPrtPlex enumerations are relevant to PCL:
        simplexOneSided, bindLongEdgeTwoSided, bindShortEdgeTwoSided."
    REFERENCE "
        See: ISO/IEC 10175-1:1996(E)
             Section 9.3.2.16.2: Plex
             Section 9.3.2.19:   Sides
        See: PostScript Language Reference Manual (2nd Edition)
             - PageSize, Duplex, Tumble
        See: PCL 5 Printer Language Technical Reference Manual
             Simplex/Duplex Print Command"
    SYNTAX INTEGER (0..255)
XcmPrtPrintQuality ::= TEXTUAL-CONVENTION
    STATUS      current
    DESCRIPTION "
        These attributes specify the output quality of the printed
        document.  Some printers have programmatically controlled output
        quality.  This attribute allows the user to specify the level of
        output quality desired from printers.
        The following standard values are defined:
        - 'draft'  means lowest quality available on the printer.
          Uses include increasing the printer's speed and saving
          toner.
        - 'normal' means normal or intermediate quality on the printer. 
        - 'high'   means highest quality available on the printer."
    REFERENCE "
        ISO/IEC 10175-1:1996(E)
        Section 9.3.2.17:  Print-quality"
    SYNTAX INTEGER {
                other(1),
                unknown(2),
                notSpecified(3),
                draft(4),
                normal(5),
                high(6)
                }
XcmPrtPrintScreen ::= TEXTUAL-CONVENTION
    STATUS      current
    DESCRIPTION "
        This Textual-Convention enumerates special modes for 80
        character screen dumps onto A4 size paper, which is usually
        77 characters wide.  This function is useful when printing the
        80 characters per line width of computer displays.
        The PrintScreen mode enables characters to be printed as shown 
        on the display when PrintScreen is executed from the host.
        When mode850 or mode852 is set, the following is done:
            - Symbol set value changed to PC-850 or PC-852.
              with the current Symbol set value being stored.
            - A4 size horizontal printable area expanded to being 80
              characters wide.
        When the special mode is returned to Off, the following is done:
            - Symbol set value returned to the stored SymbolSet Value.
            - A4 size horizontal printable area returned to being 77
              characters."
    SYNTAX INTEGER {
                other(1),
                unknown(2),
                notSpecified(3),
                off(4),
                mode850(5),
                mode852(6)
                }
XcmPrtTraySwitch ::= TEXTUAL-CONVENTION
    STATUS      current
    DESCRIPTION "
        This Textual-Convention enumerates which tray switching
        declaration mechanism is used."
    REFERENCE "
        See:  xcmPrtInterpTraySwitch
        See:  xcmPrtInputNextPrtInputIndex
        See:  xcmPrtInputAliasTable"
    SYNTAX INTEGER {
                other(1),
                unknown(2),
                notSpecified(3),
                off(4),
                useXcmPrtInputNextPrtInputIndex(5),
                useXcmPrtInputAliasTable(6)
                }
--
--
XcmPrtGeneralMonoPrintOpt ::= TEXTUAL-CONVENTION
    STATUS      current
    DESCRIPTION "
        These attributes specify the printing performance /
        economy mode setting."
    REFERENCE "
        See: Phaser 7750 User Guide... for more information "
    SYNTAX INTEGER {
                other(1),
                optimizeForSpeed(3),
                optimizeForEconomy(4),
                notPresent(5)
                }
--
--
XcmPrtOutputPunchPosition ::= TEXTUAL-CONVENTION
    STATUS      current
    DESCRIPTION "
        This Textual Convention enumerates possible punch positions.
        The punch positions enumerated are the number of punch 
        positions that can be supported by the finishing device.
         punchPos2Hole  is used to indicate a two-hole punch option.
         punchPos3Hole  is used to indicate a three-hole punch option.
         punchPos4Hole  is used to indicate a four-hole punch option.
        The current set of values (which may be extended in the future)
        is given below:
              1 : punchPos2Hole                
              2 : punchPos3Hole                
              4 : punchPos4Hole                -- 2**2"
    REFERENCE "
        See: xcmPrtOutputPunchPosSupported"
    SYNTAX  INTEGER(0..255)
--
--
XcmPrtInputTraysConfiguration ::= TEXTUAL-CONVENTION
    STATUS      current
    DESCRIPTION "
           This Textual Convention identifies all possible input tray 
           combinations for a print device."
    REFERENCE "
       See the xcmPrtInputTraysConfiguration object definition for 
       16prtx.txt for more details."
    SYNTAX    INTEGER {
        undefined(0),
        oneTray(1),
        twoTrays(2),
        threeTrays(3),
        fourTrays(4),
        fiveTrays(5),
        sixTrays(6),
        threeTraysAndOneHCF(7),  
        fourTraysAndOneHCF(8),
        fiveTraysAndOneHCF (9),
        threeTraysAndOneBypass(10),
        fourTraysAndOneBypass(11),
        fiveTraysAndOneBypass(12),
        threeTraysAndOneBypassAndOneHCF(13),  
        fourTraysAndOneBypassAndOneHCF(14),
        fiveTraysAndOneBypassAndOneHCF(15),
        oneFeederWithTwoTrays(16),  
        twoFeedersWithFourTrays(17),
        oneFeederWithFourTrays(18),
        twoFeedersWithEightTrays(19)
 }
--
--
XcmPrtFinisherDFAType ::= TEXTUAL-CONVENTION
    STATUS      current
    DESCRIPTION 
        "This collection of enumerations indicate the posssible types 
        of Finisher DFA modules that could be installed within a 
        print device."
    SYNTAX INTEGER {
                other(1),
                notInstalled(2),
                dfaFinisher(3),
                sbm(4)
                }
XcmPrtHighCapacityFeederType ::= TEXTUAL-CONVENTION
    STATUS      current
    DESCRIPTION 
        "This collection of enumerations indicate the posssible types 
        of High Capacity Feeders that could be installed within a 
        print device."
    SYNTAX INTEGER {
                other(1),
                notInstalled(2),
                hcf(3),
                hcfOversized(4),
                hcfOversized2Trays(5)
                }
XcmPrtHolePunchUnitType ::= TEXTUAL-CONVENTION
    STATUS      current
    DESCRIPTION 
        "This collection of enumerations indicate the posssible types 
        of Hole Punch Units that could be installed within a print 
        device."
    SYNTAX INTEGER {
                other(1),
                notInstalled(2),
                punch2HoleSheet(3),
                punch2HoleNASheet(4),
                punch2HoleEUSheet(5),
                punch3HoleNASheet(6),
                punch4HoleSheet(7),
                punch4HoleEUSheet(8),
                punch4HoleSwedishSheet(9),
                punch2And3HoleNAStack(10),
                punch2And4HoleEUStack(11),
                punch2HoleStack(12),
                punch2HoleNAStack(13),
                punch2HoleEUStack(14),
                punch3HoleStack(15),
                punch3HoleNAStack(16),
                punch4HoleStack(17),
                punch4HoleEUStack(18),
                punch4HoleSwedishStack(19),
                punch5HoleNASheet(20),
                punch2And3And5HoleNASheet(21),
                punch2And3HoleStack(22),
                punch2And4HoleStack(23),
                punch2And3And4HoleStack(24)
                }
XcmPrtFaxOutType ::= TEXTUAL-CONVENTION
    STATUS      current
    DESCRIPTION 
        "This collection of enumerations indicate the posssible types 
        of Fax Out Units that could be installed within a print device."
    SYNTAX INTEGER {
                other(1),
         notPresent(2),
                installed(3),
                faxWithsip(4),
                faxLanAndIp(5)
                }
XcmPrtPhaserModuleType ::= TEXTUAL-CONVENTION
    STATUS      current
    DESCRIPTION 
        "This collection of enumerations indicate the posssible types 
        of configurations for a Phaser print device."
    SYNTAX INTEGER {
                other(1),
                notSpecified(2),
         b(3),
         n(4),
         dn(5),
         dt(6),
         dx(7),
         gx(8),
         dp(9),
         dxf(10)
                }
XcmPrtPrintEngineType ::= TEXTUAL-CONVENTION
    STATUS      current
    DESCRIPTION 
        "This collection of enumerations indicate the posssible types 
        of print engine configurations that could be supported by a
        print device."
    SYNTAX INTEGER {
                other(1),
         single(2),
         dual(3)
                }
XcmPrtAsciiJobTicketType ::= TEXTUAL-CONVENTION
    STATUS      current
    DESCRIPTION 
        "This collection of enumerations indicate the posssible types 
        of ASCII Job Tickets that could be supported by a print 
        device."
    SYNTAX INTEGER {
                other(1),
         notPresent(2),
         asciiJobTicketRequired(3),
         asciiJobTicketAllowed(4)
                }
XcmPrtAuthenticationModeType ::= TEXTUAL-CONVENTION
    STATUS      current
    DESCRIPTION 
        "This collection of enumerations indicate the posssible types 
        of Authentication Modes that could be supported by a print 
        device."
    SYNTAX INTEGER {
                other(1),
         notPresent(2),
         commonAccessCardPiv(3),
         s3(4),
         pin(5),
         password(6),
         smartCard(7)
                }
XcmPrtHoldForAuthenModeType ::= TEXTUAL-CONVENTION
    STATUS      current
    DESCRIPTION 
        "This collection of enumerations indicate the posssible types 
        of Hold for Authentication Modes that could be supported by a
        print device."
    SYNTAX INTEGER {
                other(1),
         notPresent(2),
         pin(3),
         userId(4)
                }
XcmPrtAccountingSystemType ::= TEXTUAL-CONVENTION
    STATUS      current
    DESCRIPTION 
        "This collection of enumerations indicate the posssible types 
        of Accounting Systems that could be supported by a print
        device."
    SYNTAX INTEGER {
                other(1),
         notPresent(2),
         standard(3),
         network(4),
         accountingGreenUserOnly(5),
         accountingGreenAccountOnly(6),
         accountingGreenBillingOnly(7),
         accountingGreenUserAndAccount(8),
         accountingGreenAll(9)
                }
--
--
--
xCmPrintTCDummy     OBJECT IDENTIFIER ::= { xcmPrintTC 999 }
xCmPrtTCAuxSheetContent OBJECT-TYPE
    SYNTAX      XcmPrtAuxSheetContent
    MAX-ACCESS  not-accessible
    STATUS      current
    DESCRIPTION "Dummy - DO NOT USE"
    ::= { xCmPrintTCDummy 1 }
xCmPrtTCXcmPrtAuxSheetType OBJECT-TYPE
    SYNTAX      XcmPrtAuxSheetType
    MAX-ACCESS  not-accessible
    STATUS      current
    DESCRIPTION "Dummy - DO NOT USE"
    ::= { xCmPrintTCDummy 2 }
xCmPrtTCTCChannelType OBJECT-TYPE
    SYNTAX      XcmPrtChannelType
    MAX-ACCESS  not-accessible
    STATUS      current
    DESCRIPTION "Dummy - DO NOT USE"
    ::= { xCmPrintTCDummy 3 }
xCmPrtTCGroupSupport OBJECT-TYPE
    SYNTAX      XcmPrtGroupSupport
    MAX-ACCESS  not-accessible
    STATUS      current
    DESCRIPTION "Dummy - DO NOT USE"
    ::= { xCmPrintTCDummy 4 }
xCmPrtTCIETFPrintMIBGroupSupport OBJECT-TYPE
    SYNTAX      XcmPrtIETFPrintMIBGroupSupport
    MAX-ACCESS  not-accessible
    STATUS      current
    DESCRIPTION "Dummy - DO NOT USE"
    ::= { xCmPrintTCDummy 5 }
xCmPrtTCInterpreterLangFamily OBJECT-TYPE
    SYNTAX      XcmPrtInterpreterLangFamily
    MAX-ACCESS  not-accessible
    STATUS      current
    DESCRIPTION "Dummy - DO NOT USE"
    ::= { xCmPrintTCDummy 6 }
xCmPrtTCMediaTypeErrorPolicy OBJECT-TYPE
    SYNTAX      XcmPrtMediaTypeErrorPolicy
    MAX-ACCESS  not-accessible
    STATUS      current
    DESCRIPTION "Dummy - DO NOT USE"
    ::= { xCmPrintTCDummy 7 }
xCmPrtTCMediumClassType OBJECT-TYPE
    SYNTAX      XcmPrtMediumClassType
    MAX-ACCESS  not-accessible
    STATUS      current
    DESCRIPTION "Dummy - DO NOT USE"
    ::= { xCmPrintTCDummy 8 }
xCmPrtTCMediumSize OBJECT-TYPE
    SYNTAX      XcmPrtMediumSize
    MAX-ACCESS  not-accessible
    STATUS      current
    DESCRIPTION "Dummy - DO NOT USE"
    ::= { xCmPrintTCDummy 9 }
xCmPrtTCOutputOffsetStackingType OBJECT-TYPE
    SYNTAX      XcmPrtOutputOffsetStackingType
    MAX-ACCESS  not-accessible
    STATUS      current
    DESCRIPTION "Dummy - DO NOT USE"
    ::= { xCmPrintTCDummy 10 }
xCmPrtOutputStaplePosition OBJECT-TYPE
    SYNTAX      XcmPrtOutputStaplePosition
    MAX-ACCESS  not-accessible
    STATUS      current
    DESCRIPTION "Dummy - DO NOT USE"
    ::= { xCmPrintTCDummy 11 }
xCmPrtTCPageSizeErrorPolicy OBJECT-TYPE
    SYNTAX      XcmPrtPageSizeErrorPolicy
    MAX-ACCESS  not-accessible
    STATUS      current
    DESCRIPTION "Dummy - DO NOT USE"
    ::= { xCmPrintTCDummy 12 }
xCmPrtTCPCLFontSource OBJECT-TYPE
    SYNTAX      XcmPrtPCLFontSource
    MAX-ACCESS  not-accessible
    STATUS      current
    DESCRIPTION "Dummy - DO NOT USE"
    ::= { xCmPrintTCDummy 13 }
xCmPrtTCPlex OBJECT-TYPE
    SYNTAX      XcmPrtPlex
    MAX-ACCESS  not-accessible
    STATUS      current
    DESCRIPTION "Dummy - DO NOT USE"
    ::= { xCmPrintTCDummy 14 }
xCmPrtTCPrintQuality OBJECT-TYPE
    SYNTAX      XcmPrtPrintQuality
    MAX-ACCESS  not-accessible
    STATUS      current
    DESCRIPTION "Dummy - DO NOT USE"
    ::= { xCmPrintTCDummy 15 }
xCmPrtTCPrintScreen OBJECT-TYPE
    SYNTAX      XcmPrtPrintScreen
    MAX-ACCESS  not-accessible
    STATUS      current
    DESCRIPTION "Dummy - DO NOT USE"
    ::= { xCmPrintTCDummy 16 }
xCmPrtTCTraySwitch OBJECT-TYPE
    SYNTAX      XcmPrtTraySwitch
    MAX-ACCESS  not-accessible
    STATUS      current
    DESCRIPTION "Dummy - DO NOT USE"
    ::= { xCmPrintTCDummy 17 }
xCmPrtTCGeneralMonoPrintOpt OBJECT-TYPE
    SYNTAX      XcmPrtGeneralMonoPrintOpt
    MAX-ACCESS  not-accessible
    STATUS      current
    DESCRIPTION "Dummy - DO NOT USE"
    ::= { xCmPrintTCDummy 18 }
xCmPrtOutputPunchPosition OBJECT-TYPE
    SYNTAX      XcmPrtOutputPunchPosition
    MAX-ACCESS  not-accessible
    STATUS      current
    DESCRIPTION "Dummy - DO NOT USE"
    ::= { xCmPrintTCDummy 19 }
xCmPrtInputTraysConfiguration OBJECT-TYPE
    SYNTAX      XcmPrtInputTraysConfiguration
    MAX-ACCESS  not-accessible
    STATUS      current
    DESCRIPTION "Dummy - DO NOT USE"
    ::= { xCmPrintTCDummy 20 }
xcmPrintMIB OBJECT-IDENTITY -- MODULE-IDENTITY
    STATUS   current
    DESCRIPTION "
        Version: 6.006.pub
        Xerox XCMI Extension to IETF Printer MIB Module.
        This Module provides extension to the IETF Printer MIB.
        Copyright (C) 1997-2013 Xerox Corporation. All Rights Reserved."
    ::= { xeroxCommonMIB 55 }
--
--
xcmPrtBase                OBJECT IDENTIFIER ::= { xcmPrintMIB 1 }
xcmPrtGeneral             OBJECT IDENTIFIER ::= { xcmPrintMIB 5 }
xcmPrtDriverOptions       OBJECT IDENTIFIER ::= { xcmPrintMIB 6 }
--
xcmPrtInput               OBJECT IDENTIFIER ::= { xcmPrintMIB 8 }
xcmPrtOutput              OBJECT IDENTIFIER ::= { xcmPrintMIB 9 }
xcmPrtChannel             OBJECT IDENTIFIER ::= { xcmPrintMIB 14 }
xcmPrtInterpreter         OBJECT IDENTIFIER ::= { xcmPrintMIB 15 }
xcmPrtInputAlias          OBJECT IDENTIFIER ::= { xcmPrintMIB 50 }
xcmPrtAuxSheet            OBJECT IDENTIFIER ::= { xcmPrintMIB 52 }
xcmPrtAuxPackage          OBJECT IDENTIFIER ::= { xcmPrintMIB 60 }
xcmPrtMediumTypeSupported OBJECT IDENTIFIER ::= { xcmPrintMIB 75 }
xcmPrtInterpPCL           OBJECT IDENTIFIER ::= { xcmPrintMIB 70 }
--
--
--
xcmPrtBaseTable OBJECT-TYPE
    SYNTAX      SEQUENCE OF XcmPrtBaseEntry
    MAX-ACCESS  not-accessible
    STATUS      current
    DESCRIPTION
        "A table of general counters and information for ease of use of
        the XCMI Extension to IETF Printer MIB Module and the
        IETF Printer MIB on this host system.
        Usage:  The ONLY valid row in the 'xcmPrtBaseTable'
        shall ALWAYS have an 'xcmPrtBaseIndex' of one ('1')."
    ::= { xcmPrtBase 2 }
xcmPrtBaseEntry OBJECT-TYPE
    SYNTAX      XcmPrtBaseEntry
    MAX-ACCESS  not-accessible
    STATUS      current
    DESCRIPTION
        "An entry of general counters and information for ease of use of
        the XCMI Extension to IETF Printer MIB Module and the
        IETF Printer MIB on this host system.
        Usage:  The ONLY valid row in the 'xcmPrtBaseTable'
        shall ALWAYS have an 'xcmPrtBaseIndex' of one ('1')."
    INDEX       { xcmPrtBaseIndex }
    ::= { xcmPrtBaseTable 1 }
XcmPrtBaseEntry ::= SEQUENCE {
        xcmPrtBaseIndex                Ordinal32,
        xcmPrtBaseRowStatus            RowStatus,
        xcmPrtBaseGroupSupport         XcmPrtGroupSupport,
        xcmPrtBaseUpdateSupport        XcmPrtGroupSupport,
        xcmPrtBaseCreateSupport        XcmPrtGroupSupport,
        xcmPrtBaseIETFMIBGroupSupport  XcmPrtIETFPrintMIBGroupSupport,
        xcmPrtBaseIETFMIBUpdateSupport XcmPrtIETFPrintMIBGroupSupport,
        xcmPrtBaseIETFMIBCreateSupport XcmPrtIETFPrintMIBGroupSupport
    }
xcmPrtBaseIndex OBJECT-TYPE
    SYNTAX      Ordinal32
    MAX-ACCESS  not-accessible
    STATUS      current
    DESCRIPTION
        "A unique value used by this host system to identify this
        conceptual row in the 'xcmPrtBaseTable'.
        Usage:  The ONLY valid row in the 'xcmPrtBaseTable'
        shall ALWAYS have an 'xcmPrtBaseIndex' of one ('1')."
    ::= { xcmPrtBaseEntry 1 }
xcmPrtBaseRowStatus OBJECT-TYPE
    SYNTAX      RowStatus
    MAX-ACCESS  read-only
    STATUS      current
    DESCRIPTION
        "This object is used to display status of the ONLY valid
        conceptual row in the 'xcmPrtBaseTable'.
        Usage:  'xcmPrtBaseRowStatus' is 'read-only' because
        the ONLY valid conceptual row shall NOT be deleted."
    ::= { xcmPrtBaseEntry 2 }
xcmPrtBaseGroupSupport OBJECT-TYPE
    SYNTAX      XcmPrtGroupSupport
    MAX-ACCESS  read-only
    STATUS      current
    DESCRIPTION "
        The terse conformance statement of ALL mandatory, conditionally
        mandatory, and optional module objects which are
        supported by this management agent implementation (ie, version)
        on this host system, specified in a bit-mask."
    DEFVAL      { 0 }                  
    ::= { xcmPrtBaseEntry 3 }
xcmPrtBaseUpdateSupport OBJECT-TYPE
    SYNTAX      XcmPrtGroupSupport
    MAX-ACCESS  read-only
    STATUS      current
    DESCRIPTION "
        The terse conformance statement of ALL mandatory, conditionally
        mandatory, and optional module objects which are
        supported for existing row update (via SNMP Set-Request PDUs)
        by this management agent implementation (ie, version)
        on this host system, specified in a bit-mask."
    DEFVAL      { 0 }                   
    ::= { xcmPrtBaseEntry 4 }
xcmPrtBaseCreateSupport OBJECT-TYPE
    SYNTAX      XcmPrtGroupSupport
    MAX-ACCESS  read-only
    STATUS      current
    DESCRIPTION "
        The terse conformance statement of ALL mandatory, conditionally
        mandatory, and optional module objects which are
        supported for dynamic row creation (via '...RowStatus')
        by this management agent implementation (ie, version)
        on this host system, specified in a bit-mask."
    DEFVAL      { 0 }                   
    ::= { xcmPrtBaseEntry 5 }
xcmPrtBaseIETFMIBGroupSupport OBJECT-TYPE
    SYNTAX      XcmPrtIETFPrintMIBGroupSupport
    MAX-ACCESS  read-only
    STATUS      current
    DESCRIPTION "
        The terse conformance statement of ALL mandatory, conditionally
        mandatory, and optional module objects in the IETF Printer MIB
        which are supported by this management agent
        implementation (ie, version) on this host system,
        specified in a bit-mask."
    REFERENCE   "See: IETF Printer MIB"
    DEFVAL      { 127525 }  
    ::= { xcmPrtBaseEntry 6 }
xcmPrtBaseIETFMIBUpdateSupport OBJECT-TYPE
    SYNTAX      XcmPrtIETFPrintMIBGroupSupport
    MAX-ACCESS  read-only
    STATUS      current
    DESCRIPTION "
        The terse conformance statement of ALL mandatory, conditionally
        mandatory, and optional module objects in the IETF Printer MIB
        supported for existing row update (via SNMP Set-Request PDUs)
        by this management agent implementation (ie, version)
        on this host system, specified in a bit-mask."
    REFERENCE   "See: IETF Printer MIB"
    DEFVAL      { 0 }                   
    ::= { xcmPrtBaseEntry 7 }
xcmPrtBaseIETFMIBCreateSupport OBJECT-TYPE
    SYNTAX      XcmPrtIETFPrintMIBGroupSupport
    MAX-ACCESS  read-only
    STATUS      current
    DESCRIPTION "
        The terse conformance statement of ALL mandatory, conditionally
        mandatory, and optional module objects in the IETF Printer MIB
        supported for dynamic row creation (via '...RowStatus')
        by this management agent implementation (ie, version)
        on this host system, specified in a bit-mask.
        Currently there are no groups within the IETF Printer MIB which
        provide for dynamic row creation, and this object shall always
        return '0'.  Dynamic row creation is provided to these groups
        through the XCMI Extension to IETF Printer MIB Module, but
        CreateSupport should be reflected in xcmPrtBaseCreateSupport.
        This object is included for completeness."
    REFERENCE   "See: IETF Printer MIB"
    DEFVAL      { 0 }                   
    ::= { xcmPrtBaseEntry 8 }
--
--
--
xcmPrtGeneralTable OBJECT-TYPE
    SYNTAX      SEQUENCE OF XcmPrtGeneralEntry
    MAX-ACCESS  not-accessible
    STATUS      current
    DESCRIPTION "
        A table of general information per printer.
        This table augments the prtGeneralTable."
    ::= { xcmPrtGeneral 1 }
xcmPrtGeneralEntry OBJECT-TYPE
    SYNTAX      XcmPrtGeneralEntry
    MAX-ACCESS  not-accessible
    STATUS      current
    DESCRIPTION "
        An entry exists in this table for each device entry in the
        hostmib device table whose type is printer."
    AUGMENTS { prtGeneralEntry }
    ::= { xcmPrtGeneralTable 1 }
XcmPrtGeneralEntry ::= SEQUENCE {
    xcmPrtGeneralRowStatus            RowStatus,
    xcmPrtGeneralAuxSheetPackage      Cardinal32,
    xcmPrtGeneralManualFeedTimeout    Integer32,
    xcmPrtGeneralInputAutoSwitch      PresentOnOff,
    xcmPrtGeneralOutputAutoSwitch     PresentOnOff,
    xcmPrtGeneralMediumClassDefault   XcmPrtMediumClassType,
    xcmPrtGeneralDarknessLevels       Cardinal32,
    xcmPrtGeneralDarknessLevelNorm    Cardinal32,
    xcmPrtGeneralDarknessLevelDflt    Integer32,
    xcmPrtGeneralHexDumpEnable        PresentOnOff,
    xcmPrtGeneralTonerLowStop         PresentOnOff,
    xcmPrtGeneralStartupPage          PresentOnOff,
    xcmPrtGeneralBannerPage           PresentOnOff,
    xcmPrtGeneralEndBannerPage        PresentOnOff,
    xcmPrtGeneralTrayLowWarning       PresentOnOff, 
    xcmPrtGeneralScanlineCompaction   PresentOnOff,
    xcmPrtGeneralMonoPrintOptimization XcmPrtGeneralMonoPrintOpt,
    xcmPrtGeneralInstalledFeeder    OCTET STRING (SIZE(0..255)),
    xcmPrtGeneralInstalledFinisher  OCTET STRING (SIZE(0..255)),
    xcmPrtGeneralInstalledAnalogFax OCTET STRING (SIZE(0..255))
    }
xcmPrtGeneralRowStatus OBJECT-TYPE
    SYNTAX      RowStatus
    MAX-ACCESS  read-create
    STATUS      current
    DESCRIPTION "
        Manages the status of this conceptual row in the
        xcmPrtGeneralTable."
    ::= { xcmPrtGeneralEntry 1 }
xcmPrtGeneralAuxSheetPackage OBJECT-TYPE
    SYNTAX      Cardinal32
    MAX-ACCESS  read-create
    STATUS      current
    DESCRIPTION "
        This object is an index into the xcmPrtAuxPackageTable.
        This table is used to enable or disable printing of
        auxiliary sheets at the printer box level.
        The value zero shall mean not specified."
    REFERENCE "
        See: xcmPrtInterpAuxSheetPackage
        See: xcmPrtChannelAuxSheetPackage
        See: xcmPrtGeneralAuxSheetGroup - xcmPrtGeneralStartupPage
        See: xcmPrtGeneralAuxSheetGroup - xcmPrtGeneralBannerPage
        See: xcmPrtGeneralAuxSheetGroup - xcmPrtGeneralEndBannerPage"
    DEFVAL { 0 } 
    ::= { xcmPrtGeneralEntry 2 }
xcmPrtGeneralManualFeedTimeout OBJECT-TYPE
    SYNTAX      Integer32
    UNITS       "Seconds"
    MAX-ACCESS  read-create
    STATUS      current
    DESCRIPTION "
        The duration in seconds after which the printer shall either:
        (a) switch to another input subunit, if the value of
            prtInputNextIndex is non-zero and prtGeneralAutoSwitch is on
        or
        (b) abort any job waiting for manually fed input, if the value
            value of prtInputNextIndex is zero or prtGeneralAutoSwitch
            is off or notPresent.
        The event which causes the printer to enter the waiting state
        is product specific.
        A value of (-1) implies 'other' or 'infinite' which translates
        to 'this input subunit doesn't support manual feed'.
        A value of (-2) implies 'unknown'."
    REFERENCE "
        This object copied from the April 1996 Printer MIB 
        prtInputManualFeedTimeout object.  This object is currently
        in the prtInputTable.  The XCMI WG will push in June 1996 to 
        move this object the prtGeneralTable as done here."
    DEFVAL { -1 } 
    ::= { xcmPrtGeneralEntry 3 }
xcmPrtGeneralInputAutoSwitch OBJECT-TYPE
    SYNTAX      PresentOnOff
    MAX-ACCESS  read-create
    STATUS      current
    DESCRIPTION "
        Indicates the state of the auto input switching feature.
        The value notPresent indicates the feature is not currently
        supported. Exact behavior of this feature is product specific."
    REFERENCE "
        This object copied from the April 1996 Printer MIB 
        prtInputAutoSwitch object.  This object is currently
        in the prtInputTable.  The XCMI WG will push in June 1996, 
        to move this object the prtGeneralTable as done here."
    DEFVAL { notPresent }
    ::= { xcmPrtGeneralEntry 4 }
xcmPrtGeneralOutputAutoSwitch OBJECT-TYPE
    SYNTAX      PresentOnOff
    MAX-ACCESS  read-create
    STATUS      current
    DESCRIPTION "
        Indicates the state of the auto output tray switching feature.
        The value notPresent indicates the feature is not currently
        supported.  Exact behavior of this feature is product specific."
    DEFVAL { notPresent }
    ::= { xcmPrtGeneralEntry 5 }
xcmPrtGeneralMediumClassDefault OBJECT-TYPE
    SYNTAX      XcmPrtMediumClassType
    MAX-ACCESS  read-create
    STATUS      current
    DESCRIPTION "
        This object sets the default medium size class for the printer.
        This object sets the medium size for printer management
        functions such as printing the configuration sheet.
        It may affect any media related object, such as form length."
    DEFVAL { unknown }
    ::= { xcmPrtGeneralEntry 6 }
xcmPrtGeneralDarknessLevels OBJECT-TYPE
    SYNTAX      Cardinal32
    MAX-ACCESS  read-create
    STATUS      current
    DESCRIPTION "
        This value indicates the maximum number of darkness levels
        supported by this printer.
        The level settings range from 1 to xcmPrtGeneralDarknessLevels
        where 1 represents the lightest level and
        xcmPrtGeneralDarknessLevels represents the darkest level.
        The value 1 implies no user settables.
        The value 0 means unspecified.
        The selection of a darkness levels specifies that the
        printer shall process the page images so that they appear
        either 'lighter' or 'darker'."
    DEFVAL { 0 } 
    ::= { xcmPrtGeneralEntry 7 }
xcmPrtGeneralDarknessLevelNorm OBJECT-TYPE
    SYNTAX      Cardinal32
    MAX-ACCESS  read-create
    STATUS      current
    DESCRIPTION "
        The normal setting for the darkness printing object.
        The value 0 means unspecified."
    DEFVAL { 0 } 
    ::= { xcmPrtGeneralEntry 8 }
xcmPrtGeneralDarknessLevelDflt OBJECT-TYPE
    SYNTAX      Integer32
    MAX-ACCESS  read-create
    STATUS      current
    DESCRIPTION "
        The default setting for the density printing option.
        The value (-2) indicates unknown.
        The value (-4) indicates the auto setting."
    REFERENCE "
        See: PJL Technical Reference Manual - DENSITY"
    DEFVAL { -2 } 
    ::= { xcmPrtGeneralEntry 9 }
xcmPrtGeneralHexDumpEnable OBJECT-TYPE
    SYNTAX      PresentOnOff
    MAX-ACCESS  read-create
    STATUS      current
    DESCRIPTION "
        This object controls whether the printer is in a special
        diagnostic mode wherein all received print data is printed in
        hexadecimal format.
        Whether a reset or power-cycles turns xcmPrtGeneralHexDumpEnable
        to Off is product dependent."
    REFERENCE "
        See: Printer MIB prtInterpreterLangFamily - langDiagnostic(41)"
    DEFVAL { notPresent }
    ::= { xcmPrtGeneralEntry 10 }
xcmPrtGeneralTonerLowStop  OBJECT-TYPE
    SYNTAX      PresentOnOff
    MAX-ACCESS  read-create
    STATUS      current
    DESCRIPTION "
        Indicates the action taken when a low toner condition exists.
        'on' indicates that the printer will stop printing when then
        toner is low
        'off' indicates that printing will continue when the toner is
        low
        'notPresent' indicates that the printer has no selectable
        option for action under a low toner condition."  
    DEFVAL  {notPresent}
    ::= { xcmPrtGeneralEntry 13 }
--
--
--
--
--
xcmPrtGeneralStartupPage OBJECT-TYPE
        SYNTAX      PresentOnOff
        MAX-ACCESS  read-create
        STATUS      current
        DESCRIPTION "
            Used to enable or disable printing a startup page. If
            enabled, a startup page will be printed shortly after
            power-up, when the device is ready. Typical startup
            pages include test patterns and/or printer configuration
            information.
            Usage:  Conforming management agents, which ALSO implement
            the the Printer MIB v2, SHALL set 'xcmPrtGeneralStartupPage'
            to the SAME value as 'prtAuxiliarySheetStartupPage' (i.e.,
            the values of these two objects SHALL be interlocked)."
        REFERENCE "
            This object copied directly from the April 1996 version of
            the Printer MIB's prtGeneralStartupPage object."
        DEFVAL { notPresent }
        ::= { xcmPrtGeneralEntry 11 }
xcmPrtGeneralBannerPage OBJECT-TYPE
        SYNTAX      PresentOnOff
        MAX-ACCESS  read-create
        STATUS      current
        DESCRIPTION "
            Used to enable or disable printing banner pages at the
            beginning of jobs. This is a master switch which applies
            to all jobs, regardless of interpreter.
            Usage:  Conforming management agents, which ALSO implement
            the the Printer MIB v2, SHALL set 'xcmPrtGeneralBannerPage'
            to the SAME value as 'prtAuxiliarySheetBannerPage' (i.e.,
            the values of these two objects SHALL be interlocked)."
        REFERENCE "
            This object copied directly from the April 1996 version of
            the Printer MIB's prtGeneralBannerPage object."
        DEFVAL { notPresent }
        ::= { xcmPrtGeneralEntry 12 }
xcmPrtGeneralEndBannerPage OBJECT-TYPE
        SYNTAX      PresentOnOff
        MAX-ACCESS  read-create
        STATUS      current
        DESCRIPTION "
            Used to enable or disable printing banner pages at the
            end of jobs. This is a master switch which applies
            to all jobs, regardless of interpreter."
        DEFVAL { notPresent }
        ::= { xcmPrtGeneralEntry 14 }
xcmPrtGeneralTrayLowWarning  OBJECT-TYPE
       SYNTAX      PresentOnOff
       MAX-ACCESS  read-create
       STATUS      current
       DESCRIPTION "
           Indicates the action taken when a input tray paper condition 
           'on' indicates that the printer will report the warning over 
              the user interfaces: Control Panel, CWIS, SNMP, etc.
           'off' indicates that printing will not report the warning
           'notPresent' indicates that the printer has no selectable
              option for a low paper condition."  
       DEFVAL  {notPresent}
       ::= { xcmPrtGeneralEntry 15 }
--
--
--
--
xcmPrtGeneralScanlineCompaction OBJECT-TYPE
    SYNTAX      PresentOnOff
    MAX-ACCESS  read-create
    STATUS      current
    DESCRIPTION "
        This object enables a printing mode wherein the printer
        compresses selected scanlines of raster image data as they are
        received and holds them in compressed form until they are to
        be printed.  This allows particular jobs to be processed with
        less memory, but often reduced performance as well.  
        On some Printers, turning this feature Off is referred to as
        'PerformanceEnhancement'.  
        When xcmInterpPageProtect is set to Off,
        some complex jobs may not print successfully with minimum
        memory.  The ScanlineCompaction feature enables printing some
        complex jobs without resorting to reserving additional memory
        by turning on the PageProtect option or installing additional
        memory."
    REFERENCE "
        See: xcmPrtInterpPageProtect
        See: DocuPrint 4517 Network Laser Printers User Guide, Pg. D-12"
    DEFVAL { notPresent }
    ::= { xcmPrtGeneralEntry 50 }
--
--
xcmPrtGeneralMonoPrintOptimization OBJECT-TYPE
    SYNTAX      XcmPrtGeneralMonoPrintOpt
    MAX-ACCESS  read-create
    STATUS      current
    DESCRIPTION "
        This object enables a printing mode wherein the printer
        can be set to either one of two modes overall. 
        Mode 1 is Optimized for Speed,
        Mode 2 is Optimized for Economy.
        This setting affects the overall performance of the
        printer and thus affects all print quality modes."
    REFERENCE "
        See: Phaser 7750 User Guide... for more information"
    DEFVAL { notPresent }
    ::= { xcmPrtGeneralEntry 51 }
--
--
--
--
xcmPrtGeneralInstalledFeeder OBJECT-TYPE
    SYNTAX      OCTET STRING (SIZE(0..255))
    MAX-ACCESS  read-only
    STATUS      current
    DESCRIPTION "
        This object uniquely specifies the currently installed Feeder 
        hardware. Its purpose is to allow clients to determine via a 
        single MIB object the number and type of input trays and feeding
        options available, based exclusively on the feeder that is 
        installed."
    DEFVAL { "none" }
    ::= { xcmPrtGeneralEntry 70 }
xcmPrtGeneralInstalledFinisher OBJECT-TYPE
    SYNTAX      OCTET STRING (SIZE(0..255))
    MAX-ACCESS  read-only
    STATUS      current
    DESCRIPTION "
        This object uniquely specifies the currently installed Finisher 
        hardware. Its purpose is to allow clients to determine via a 
        single MIB object the number and type of output trays and 
        finishing options available, based exclusively on the finisher 
        that is installed."
    DEFVAL { "none" }
    ::= { xcmPrtGeneralEntry 71 }
xcmPrtGeneralInstalledAnalogFax OBJECT-TYPE
    SYNTAX      OCTET STRING (SIZE(0..255))
    MAX-ACCESS  read-only
    STATUS      current
    DESCRIPTION "
        This object uniquely specifies the currently installed analog 
        fax card. Its purpose is to allow clients to determine via a 
        single MIB object whether an analog fax card is installed, and 
        the options that are available based on the fax card that is 
        installed."
    DEFVAL { "none" }
    ::= { xcmPrtGeneralEntry 72 }
--
--
xcmPrtGeneralConsoleLocalizationV1EventOID OBJECT-IDENTITY
    STATUS      current
    DESCRIPTION
        "The value of the enterprise-specific OID in an SNMPv1 
         trap sent whenever 'prtConsoleLocalization' in the 
         industry standard printer mib is updated.
         See SNMPv2 trap definition 
         'xcmPrtGeneralConsoleLocalizationV2Event'
         below."
    ::= { xcmPrtGeneral 2 } 
xcmPrtGeneralConsoleLocalizationV2EventPrefix
 OBJECT IDENTIFIER ::= 
 { xcmPrtGeneralConsoleLocalizationV1EventOID 0 }
xcmPrtGeneralConsoleLocalizationV2Event NOTIFICATION-TYPE
    OBJECTS {
        prtConsoleLocalization,
        prtLocalizationLanguage,
        prtLocalizationCountry,
        prtLocalizationCharacterSet
    }
    STATUS      current
    DESCRIPTION
        "This trap is sent when the value for prtConsoleLocalization 
         in the industry standard printer MIB gets updated.
         Note:   The variable-bindings of this trap have been chosen to
         allow for updated prtConsoleLocalization information to be 
         provided while keeping trap messages reasonably concise  
         (generally a few hundred octets at most)."
    ::= { xcmPrtGeneralConsoleLocalizationV2EventPrefix 1 }
--
--
--
--
--
--
--
--
xcmPrtDrvrHwdOptStapler OBJECT-TYPE
    SYNTAX      PresentOnOff
    MAX-ACCESS  read-only
    STATUS      current
    DESCRIPTION
        "Object that indicates if a Stapler Unit is installed within
         the print device."
    ::= { xcmPrtDriverOptions 1 }
xcmPrtDrvrHwdOptDuplexUnit OBJECT-TYPE
    SYNTAX      PresentOnOff
    MAX-ACCESS  read-only
    STATUS      current
    DESCRIPTION
        "Object that indicates if a Duplex Unit is installed within
         the print device."
    ::= { xcmPrtDriverOptions 2 }
xcmPrtDrvrHwdOptPhaserBookletMaker OBJECT-TYPE
    SYNTAX      PresentOnOff
    MAX-ACCESS  read-only
    STATUS      current
    DESCRIPTION
        "Object that indicates if a Booklet Maker Module is installed
         within the Phaser print device."
    ::= { xcmPrtDriverOptions 3 }
xcmPrtDrvrHwdOptEnvelopeTray OBJECT-TYPE
    SYNTAX      PresentOnOff
    MAX-ACCESS  read-only
    STATUS      current
    DESCRIPTION
        "Object that indicates if an Envelope Tray is installed within
         the print device."
    ::= { xcmPrtDriverOptions 4 }
xcmPrtDrvrHwdOptCoilPunchUnit OBJECT-TYPE
    SYNTAX      PresentOnOff
    MAX-ACCESS  read-only
    STATUS      current
    DESCRIPTION
        "Object that indicates if a Coil Punch Unit is installed
         within the print device."
    ::= { xcmPrtDriverOptions 5 }
xcmPrtDrvrHwdOptFinisherDFA OBJECT-TYPE
    SYNTAX      XcmPrtFinisherDFAType
    MAX-ACCESS  read-only
    STATUS      current
    DESCRIPTION
        "Object that indicates the type of Finisher DFA that is 
        installed within the print device."
    ::= { xcmPrtDriverOptions 6 }
xcmPrtDrvrHwdOptHighCapacityFeeder OBJECT-TYPE
    SYNTAX      XcmPrtHighCapacityFeederType
    MAX-ACCESS  read-only
    STATUS      current
    DESCRIPTION
        "Object that indicates the type of High Capacity Feeder that
        is installed within the print device."
    ::= { xcmPrtDriverOptions 7 }
xcmPrtDriverOutputDeliveryUnit OBJECT-TYPE
    SYNTAX      OCTET STRING (SIZE(0..255))
    MAX-ACCESS  read-only
    STATUS      current
    DESCRIPTION
        "Object used to indicate the type of Output Delivery Units that
         are installed within the print device. The contents of this
         object shall expose a string of valid Output Delivery Unit name
         which are seperated by a comma. Valid Output Delivery Unit type
         include: 
            'notInstalled'
            'installed'
            'phStacker'
            'phAdvanced'
            'phProfessional'
            'offsetCatchTray'
            'simpleCatchTray'
            'outputBin500Support'
            'octMailbox'
            'sctMailbox'
            'octMailboxStapler'
            'sctMailboxStapler'
            'basicOfficeFinisher'
            'officeFinisher'
            'advancedOfficeFinisher'
            'standardFinisher'
            'professionalFinisher'
            'dClassFinisher'
            'dBookletMaker'
            'dBookletMakerFold'
            'd3ClassFinisher'
            'd3ClassFinisherHcs'
            'sbm'
            'standardMff'
            'professionalMff'
            'bfm'
            'ftm'
            'bfmBfm'
            'bfmBfmFtm'
            'hcs'
            'ehcs'
            'hvf'
            'hvfBm'
            'bTypeFinisher'
            'cTypeFinisher'
            'cTypeFinisherBookletMaker'
            'phProfessional2'
            'dfaCompliant'
            'hcss'
            'dClassFinisherAdvanced'
            'dClassFinisherProfessional'
            'dClassFinisherProduction'
            'cClassFinisherAdvanced'
            'cClassFinisherProfessional'
            'sbmFolder'
            'standardFinisherMain'
            'standardFinisherSb'
            'dfaCompliantMain'
            'dfaCompliantSb'
            'dfaCompliantCustom'
            'ehcs80'
            'ehcss80'
            'hcsDfa'
            'hcsHcs'
            'hcsHcsDfa'
            'D3ClassFinisherHcsHcs'
            'css'
            'professionalPlusMff'
            'bfmFtm'
            'aTypeFinisher'
            'typeSb'
            'typeSbBookletMaker'
            'professionalMffMohican'
            'ftms'
            'bfmFtms'
            'ftmsFtms'
            'bfmFtmsFtms'
            'bfmBfmFtms'
            'dFold'
            'mainTray'
        An example: dClassFinisherProduction,dBookletMaker"
    ::= { xcmPrtDriverOptions 8 }
xcmPrtDrvrHwdOptHardDrive OBJECT-TYPE
    SYNTAX      PresentOnOff
    MAX-ACCESS  read-only
    STATUS      current
    DESCRIPTION
        "Object that indicates if a Hard Drive is installed within
         the print device."
    ::= { xcmPrtDriverOptions 9 }
xcmPrtDrvrHwdOptHolePunchUnit OBJECT-TYPE
    SYNTAX      XcmPrtHolePunchUnitType
    MAX-ACCESS  read-only
    STATUS      current
    DESCRIPTION
        "Object used to indicate the type of Hole Punch Unit that is 
         installed within the print device."
    ::= { xcmPrtDriverOptions 10 }
xcmPrtDriverInputPaperTrays OBJECT-TYPE
    SYNTAX      OCTET STRING (SIZE(0..255))
    MAX-ACCESS  read-only
    STATUS      current
    DESCRIPTION
        "Object used to indicate the type of Paper Trays that are
         installed within the print device. The contents of this
         object shall expose a string of valid Paper Tray names which
         are seperated by a comma. Valid paper tray types include:      
            'notInstalled'
            'traysInstalled'
            '1Tray'
            '2Trays'
            '3Trays'
            '3TraysHighCapacity'
            '4Trays'
            '4TraysHighCapacityTandemTray'
            '5Trays'
            '6Trays'
            'extraTraysNotInstalled'
            '1ExtraTray'
            '2ExtraTrays'
            '3ExtraTrays'
            '4ExtraTrays'
            '5TraysHighCapacityTandemTray'
            '6TraysHighCapacity'
            '6TraysHighCapacityTandemTray'
         An example: 6Trays,2ExtraTrays"
    ::= { xcmPrtDriverOptions 11 }
xcmPrtDrvrHwdOptInserterUnit OBJECT-TYPE
    SYNTAX      PresentOnOff
    MAX-ACCESS  read-only
    STATUS      current
    DESCRIPTION
        "Object that indicates if an Inserter Unit is installed
         within the print device."
    ::= { xcmPrtDriverOptions 12 }
xcmPrtDrvrHwdOptJobAccountingFdi OBJECT-TYPE
    SYNTAX      PresentOnOff
    MAX-ACCESS  read-only
    STATUS      current
    DESCRIPTION
        "Object that indicates if a Job Accounting FDI Unit is
         installedthe print device."
    ::= { xcmPrtDriverOptions 13 }
xcmPrtDrvrHwdOptFaxOut OBJECT-TYPE
    SYNTAX      XcmPrtFaxOutType
    MAX-ACCESS  read-only
    STATUS      current
    DESCRIPTION
        "Object that indicates if a Fax Out Unit is installed within
         the print device."
    ::= { xcmPrtDriverOptions 14 }
xcmPrtDrvrHwdOptMemoryInMBs OBJECT-TYPE
    SYNTAX      Integer32
    MAX-ACCESS  read-only
    STATUS      current
    DESCRIPTION
        "Object that indicates the size of physical memory in units
         of Megabytes installed within the print device. A value of 
         zero indicates that no memory is installed."
    ::= { xcmPrtDriverOptions 15 }
xcmPrtDrvrHwdOptOutputBinSide OBJECT-TYPE
    SYNTAX      PresentOnOff
    MAX-ACCESS  read-only
    STATUS      current
    DESCRIPTION
        "Object that indicates if a Side Output Bin is installed
         within the print device."
    ::= { xcmPrtDriverOptions 16 }
xcmPrtDrvrHwdOptOutputBinCenter OBJECT-TYPE
    SYNTAX      PresentOnOff
    MAX-ACCESS  read-only
    STATUS      current
    DESCRIPTION
        "Object that indicates if a Center Output Bin is installed
         within the print device."
    ::= { xcmPrtDriverOptions 17 }
xcmPrtDrvrHwdOptPhaserModule OBJECT-TYPE
    SYNTAX      XcmPrtPhaserModuleType
    MAX-ACCESS  read-only
    STATUS      current
    DESCRIPTION
        "Object that indentifies the configuration of the Phaser
         print device."
    ::= { xcmPrtDriverOptions 18 }
xcmPrtDrvrHwdOptPrintEngine OBJECT-TYPE
    SYNTAX      XcmPrtPrintEngineType
    MAX-ACCESS  read-only
    STATUS      current
    DESCRIPTION
        "Object that indicates if the print device contains a single
         print engine or has two print engines."
    ::= { xcmPrtDriverOptions 19 }
xcmPrtDrvrHwdOptSquareFoldTrimmer OBJECT-TYPE
    SYNTAX      PresentOnOff
    MAX-ACCESS  read-only
    STATUS      current
    DESCRIPTION
        "Object that indicates if a Square Fold Trimmer Unit is
         installed within the print device."
    ::= { xcmPrtDriverOptions 20 }
xcmPrtDrvrHwdOptTriFold OBJECT-TYPE
    SYNTAX      PresentOnOff
    MAX-ACCESS  read-only
    STATUS      current
    DESCRIPTION
        "Object that indicates if a Tri-Fold Unit is installed within
         the print device."
    ::= { xcmPrtDriverOptions 21 }
xcmPrtDrvrFntCollation OBJECT-TYPE
    SYNTAX      PresentOnOff
    MAX-ACCESS  read-only
    STATUS      current
    DESCRIPTION
        "Object that indicates if the Collation function is supported 
        by the print device."
    ::= { xcmPrtDriverOptions 50 }
xcmPrtDrvrFntAsciiJobTicket OBJECT-TYPE
    SYNTAX      XcmPrtAsciiJobTicketType
    MAX-ACCESS  read-only
    STATUS      current
    DESCRIPTION
        "Object that indicates if an ACSII Job Ticket function is
        supported by the print device."
    ::= { xcmPrtDriverOptions 51 }
xcmPrtDrvrFntAuthenticationMode OBJECT-TYPE
    SYNTAX      XcmPrtAuthenticationModeType
    MAX-ACCESS  read-only
    STATUS      current
    DESCRIPTION
        "Object that indicates the type of Authentication Mode 
        function that is supported by the print device."
    ::= { xcmPrtDriverOptions 52 }
xcmPrtDrvrFntHoldForAuthenMode OBJECT-TYPE
    SYNTAX      XcmPrtHoldForAuthenModeType
    MAX-ACCESS  read-only
    STATUS      current
    DESCRIPTION
        "Object that indicates the type of Hold for Authentication
        Mode function that is supported by the print device."
    ::= { xcmPrtDriverOptions 53 }
xcmPrtDrvrFntEnhancedImageQualityMode OBJECT-TYPE
    SYNTAX      PresentOnOff
    MAX-ACCESS  read-only
    STATUS      current
    DESCRIPTION
        "Object that indicates if the Enhanced Image Quality function
        is supported by the print device."
    ::= { xcmPrtDriverOptions 54 }
xcmPrtDrvrFntProductivityPack OBJECT-TYPE
    SYNTAX      PresentOnOff
    MAX-ACCESS  read-only
    STATUS      current
    DESCRIPTION
        "Object that indicates if the Productivity Pack function
        is supported by the print device."
    ::= { xcmPrtDriverOptions 55 }
xcmPrtDrvrFntJobStorage OBJECT-TYPE
    SYNTAX      PresentOnOff
    MAX-ACCESS  read-only
    STATUS      current
    DESCRIPTION
        "Object that indicates if the Job Storage software function
        is supported by the print device."
    ::= { xcmPrtDriverOptions 56 }
xcmPrtDrvrFntJobAccountingSystem OBJECT-TYPE
    SYNTAX      XcmPrtAccountingSystemType
    MAX-ACCESS  read-only
    STATUS      current
    DESCRIPTION
        "Object that indicates the type of Job Accounting System that
        is supported by the print device."
    ::= { xcmPrtDriverOptions 57 }
--
--
--
xcmPrtInputTable OBJECT-TYPE
    SYNTAX      SEQUENCE OF XcmPrtInputEntry
    MAX-ACCESS  not-accessible
    STATUS      current
    DESCRIPTION "
        This table logically augments the Printer MIB's prtInputTable."
    ::= { xcmPrtInput 1 }
xcmPrtInputEntry OBJECT-TYPE
    SYNTAX      XcmPrtInputEntry
    MAX-ACCESS  not-accessible
    STATUS      current
    DESCRIPTION "
        Entries may exist for each entry in the prtInputTable."
    AUGMENTS { prtInputEntry }
    ::= { xcmPrtInputTable 1 }
XcmPrtInputEntry ::= SEQUENCE {
    xcmPrtInputRowStatus            RowStatus,
    xcmPrtInputNextPrtInputIndex    Integer32,
    xcmPrtInputUseCustomSize        PresentOnOff,
    xcmPrtInputCustDimFeedDirDecl   Integer32,
    xcmPrtInputCustDimXFeedDirDecl  Integer32, 
    xcmPrtInputTrayPriority         Integer32
    }
xcmPrtInputRowStatus OBJECT-TYPE
    SYNTAX      RowStatus
    MAX-ACCESS  read-create
    STATUS      current
    DESCRIPTION "
        Manages the status of this conceptual row
        in the xcmPrtInputTable."
    ::= { xcmPrtInputEntry 1 }
xcmPrtInputNextPrtInputIndex OBJECT-TYPE
    SYNTAX      Integer32
    MAX-ACCESS  read-create
    STATUS      current
    DESCRIPTION "
        The value of prtInputIndex corresponding to the input subunit
        which will be used when this input subunit is emptied.
        The value of zero indicates that auto input switching will not
        occur when this input subunit is emptied.
        Two different mechanisms for input tray switching,
        xcmPrtNextPrtInputIndex and xcmPrtInputAliasGroup, are provided.
        A device agent may make use of one or the other, none, or both. 
        Use the model that fits best for the given application.
        Usage:  Conforming management agents, which ALSO implement the
        the Printer MIB v2, SHALL set 'xcmPrtInputNextPrtInputIndex'
        to the SAME value as 'prtInputNextIndex' (i.e., the values of
        these two objects SHALL be interlocked)."
    REFERENCE "
        See: xcmPrtInputAliasGroup
        See: xcmPrtInterpTraySwitch"
    DEFVAL { 0 }
    ::= { xcmPrtInputEntry 2 }
xcmPrtInputUseCustomSize OBJECT-TYPE
    SYNTAX      PresentOnOff
    MAX-ACCESS  read-create
    STATUS      current
    DESCRIPTION "
        Specifies how this input subunit determines the paper size to
        use.
        If the value is 'Off' this input subunit uses the paper size
        automatically sensed by the subunit.
        If the value is 'On' this input subunit uses the custom
        dimensions provided by xcmPrtInputCustDimFeedDirDecl and
        xcmPrtInputCustDimXFeedDirDecl."
    REFERENCE "
        See: xcmPrtInputCustDimFeedDirDecl
        See: xcmPrtInputCustDimXFeedDirDecl"
    DEFVAL { other } 
    ::= { xcmPrtInputEntry 3 }
xcmPrtInputCustDimFeedDirDecl OBJECT-TYPE
    SYNTAX      Integer32
    MAX-ACCESS  read-create
    STATUS      current
    DESCRIPTION "
        Provides the dimension, in the feed direction, of the media in
        this input subunit, when the value of xcmPrtInputUseCustomSize
        is set to 'On'.
        When xcmPrtInputUseCustomSize is set to On, this value is copied
        to prtInputMediaDimFeedDirDeclared and
        prtInputMediaDimFeedDirChosen."
    REFERENCE "
        See: xcmPrtInputUseCustomSize
        See: xcmPrtInputCustDimXFeedDirDecl"
    DEFVAL { 0 }
    ::= { xcmPrtInputEntry 4 }
xcmPrtInputCustDimXFeedDirDecl OBJECT-TYPE
    SYNTAX      Integer32
    MAX-ACCESS  read-create
    STATUS      current
    DESCRIPTION "
        Provides the dimension, in the feed direction, of the media in
        this input subunit, when the value of xcmPrtInputUseCustomSize
        is set to 'On'.
        When xcmPrtInputUseCustomSize is set to 'On', this value is
        copied to prtInputMediaDimFeedDirDeclared and
        prtInputMediaDimFeedDirChosen."
    REFERENCE "
        See: xcmPrtInputUseCustomSize
        See: xcmPrtInputCustDimFeedDirDecl"
    DEFVAL { 0 }
    ::= { xcmPrtInputEntry 5 }
xcmPrtInputTrayPriority OBJECT-TYPE
    SYNTAX      Integer32
    MAX-ACCESS  read-create
    STATUS      current
    DESCRIPTION "
        The current priority of this tray.  This value/mechanism
        is independent of xcmPrtNextPrtInputIndex and
        xcmPrtInputAliasGroup.
        Usage:  The priority of this device, where '0' is
        unspecified (default), '1' is lowest, and '100' is highest."
    REFERENCE "
        See: xcmPrtNextPrtInputIndex
        See: xcmPrtInputAliasGroup"
    DEFVAL { 0 }                   
    ::= { xcmPrtInputEntry 6 }
--
--
xcmPrtInputTrayTable OBJECT-TYPE
    SYNTAX      SEQUENCE OF XcmPrtInputTrayEntry
    MAX-ACCESS  not-accessible
    STATUS      current
    DESCRIPTION "
        This table logically augments the Printer MIB's Input Group."
    ::= { xcmPrtInput 2 }
xcmPrtInputTrayEntry OBJECT-TYPE
    SYNTAX      XcmPrtInputTrayEntry
    MAX-ACCESS  not-accessible
    STATUS      current
    DESCRIPTION "
        Entries may exist for each unique hrDeviceIndex entry in the 
        prtInputTable."
    INDEX  { hrDeviceIndex }
    ::= { xcmPrtInputTrayTable 1 }
XcmPrtInputTrayEntry ::= SEQUENCE {
    xcmPrtInputTraysRowStatus        RowStatus,
    xcmPrtInputTraysInstalled        Integer32,
    xcmPrtInputTraysConfiguration    XcmPrtInputTraysConfiguration  
    }
xcmPrtInputTraysRowStatus OBJECT-TYPE
    SYNTAX      RowStatus
    MAX-ACCESS  read-create
    STATUS      current
    DESCRIPTION "
        Manages the status of this conceptual row
        in the xcmPrtInputTrayTable."
    ::= { xcmPrtInputTrayEntry 1 }
xcmPrtInputTraysInstalled OBJECT-TYPE
    SYNTAX      Integer32
    MAX-ACCESS  read-create
    STATUS      current
    DESCRIPTION "
       The number of printer input trays installed on this device. This 
       is read-only on devices that are able to determine this value at 
       The value is read-write on devices that do not know how many inpu
       trays are installed on the device.
       The value reported must match the number of rows in prtInputTable
       for each unique hrDeviceIndex in that table.
       Input trays for finisher units are not reported by this value."
    DEFVAL { 1 }  
    ::= { xcmPrtInputTrayEntry 2 }
xcmPrtInputTraysConfiguration OBJECT-TYPE
    SYNTAX   XcmPrtInputTraysConfiguration  
    MAX-ACCESS  read-only
    STATUS      current
    DESCRIPTION "
        This single object represents the input tray configuration 
        for the entire machine. The value exposed by this object 
        will be utilized by Xerox print driver software and the 
        Microsoft OS."
    DEFVAL { undefined }  
    ::= { xcmPrtInputTrayEntry 3 }
--
--
xcmPrtOutputTable OBJECT-TYPE
    SYNTAX      SEQUENCE OF XcmPrtOutputEntry
    MAX-ACCESS  not-accessible
    STATUS      current
    DESCRIPTION "
        This table logically augments the prtOutputTable in the
        Printer MIB."
    ::= { xcmPrtOutput 1 }
xcmPrtOutputEntry OBJECT-TYPE
    SYNTAX      XcmPrtOutputEntry
    MAX-ACCESS  not-accessible
    STATUS      current
    DESCRIPTION "
        Entries may exist for each entry in the prtOutputTable."
    AUGMENTS { prtOutputEntry }
    ::= { xcmPrtOutputTable 1 }
XcmPrtOutputEntry ::= SEQUENCE {
    xcmPrtOutputRowStatus           RowStatus,
    xcmPrtOutputNextIndex           Integer32,
    xcmPrtOutputPassword            OCTET STRING (SIZE(0..255)),
    xcmPrtOutputOffsetStackingType  XcmPrtOutputOffsetStackingType,
    xcmPrtOutputTrayTimeoutSupport  PresentOnOff,
    xcmPrtOutputTrayTimeout         Cardinal32,
    xcmPrtOutputStaple              PresentOnOff,
    xcmPrtOutputStaplePosSupported  XcmPrtOutputStaplePosition,
    xcmPrtOutputStapleDefault       PresentOnOff,
    xcmPrtOutputStaplePosDefault    XcmPrtOutputStaplePosition,
    xcmPrtOutputPunch               PresentOnOff,
    xcmPrtOutputPunchDefault        PresentOnOff,  
    xcmPrtOutputPunchPosSupported   XcmPrtOutputPunchPosition,
    xcmPrtOutputBookletFoldStaple   PresentOnOff
    }
xcmPrtOutputRowStatus OBJECT-TYPE
    SYNTAX      RowStatus
    MAX-ACCESS  read-create
    STATUS      current
    DESCRIPTION "
        Manages the status of this conceptual row in the
        xcmPrtOutputTable."
    ::= { xcmPrtOutputEntry 1 }
xcmPrtOutputNextIndex OBJECT-TYPE
    SYNTAX      Integer32
    MAX-ACCESS  read-create
    STATUS      current
    DESCRIPTION "
        The value of prtOutputIndex corresponding to the output subunit
        which will be used when this output subunit is filled.
        A value of zero(0) indicates that auto output switching will not
        occur when this output subunit is filled."
    DEFVAL { 0 }
    ::= { xcmPrtOutputEntry 2 }
xcmPrtOutputPassword OBJECT-TYPE
    SYNTAX      OCTET STRING (SIZE(0..255))
    MAX-ACCESS  read-create
    STATUS      current
    DESCRIPTION "
        This object is used as the password for an Output Tray, e.g. an
        output mailbox.  It is the value that must be entered to open
        the output tray."
    REFERENCE   "See: prtOutputSecurity."
    DEFVAL { ''H }
    ::= { xcmPrtOutputEntry 3 }
xcmPrtOutputOffsetStackingType OBJECT-TYPE
    SYNTAX      XcmPrtOutputOffsetStackingType
    MAX-ACCESS  read-create
    STATUS      current
    DESCRIPTION "
        This object further refines the type of offset stacking from
        that specified by the object prtOutputOffsetStacking in the
        Printer MIB."
    REFERENCE "
        See: prtOutputOffsetStacking
        See: xcmPrtInterpOffsetStackingType"
    DEFVAL { notSpecified }
    ::= { xcmPrtOutputEntry 4 }
xcmPrtOutputTrayTimeoutSupport OBJECT-TYPE
    SYNTAX      PresentOnOff
    MAX-ACCESS  read-create
    STATUS      current
    DESCRIPTION "
        Determines whether the printer should wait before sending
        the printed output to another output destination when the 
        selected or default destination is full.
        'On' indicates that would should wait as specified by
        xcmPrtOutputTrayTimeout.
        'Off' indicates this feature is off and should immediately
        seek to send the printed output to another destination.
        The value 'other' shall mean not specified."
    REFERENCE "See: xcmPrtOutputTrayTimeout"
    DEFVAL { other } 
    ::= { xcmPrtOutputEntry 5 }
xcmPrtOutputTrayTimeout OBJECT-TYPE
    SYNTAX      Cardinal32
    UNITS       "Seconds"
    MAX-ACCESS  read-create
    STATUS      current
    DESCRIPTION "
        Determines how long the printer should wait before sending
        the printed output to another output destination when the 
        selected or default destination is full.
        A value of (0) implies 'other' or 'infinite' which translates
        to this input subunit does not support this feature."
    DEFVAL { 0 } 
    ::= { xcmPrtOutputEntry 6 }
--
--
--
xcmPrtOutputStaple  OBJECT-TYPE
    SYNTAX      PresentOnOff
    MAX-ACCESS  read-create
    STATUS      current
    DESCRIPTION "
        This object declares whether the printer has the ability to
        staple multi-page documents delivered to the specified output
        destination, and whether this ability is currently turned on.
        'on' indicates stapling is supported to this output destination,
        and that it is turned on.
        'off' indicates this printer supports stapling to this output
        destination, but that it is turned off.  If a job calls for a
        staple, none will be given.
        'notPresent' indicates that this printer does not support
        stapling to this output destination.
        The value 'other' shall mean not specified."
    REFERENCE "
        See: 'xcmPrtOutputStapleDefault
        See: 'xcmPrtOutputStaplePosSupported'
        See: 'xcmPrtOutputStaplePosDefault'"
    DEFVAL { other } 
    ::= { xcmPrtOutputEntry 100 }
xcmPrtOutputStaplePosSupported OBJECT-TYPE
    SYNTAX      XcmPrtOutputStaplePosition
    MAX-ACCESS  read-create
    STATUS      current
    DESCRIPTION "
        This object declares the stapling positions supported."
    REFERENCE "
        See: 'xcmPrtOutputStaple'
        See: 'xcmPrtOutputStapleDefault'
        See: 'xcmPrtOutputStaplePosDefault'"
    DEFVAL { 0 }  
    ::= { xcmPrtOutputEntry 101 }
xcmPrtOutputStapleDefault  OBJECT-TYPE
    SYNTAX      PresentOnOff
    MAX-ACCESS  read-create
    STATUS      current
    DESCRIPTION "
        This object declares for the cases where the job-stream does not
        specify whether to staple a particular job, whether the printer
        should apply the default staple specified in
        xcmPrtOutputStaplePosDefault for this output destination.
        'on' indicates the staple default feature is supported
        for this output destination, and that a job not specifying
        whether to staple should be supplied a staple per the
        'xcmPrtOutputStaplePosDefault' object.
        If stapling is disabled, the document will not be stapled.
        'off' indicates the staple default feature is supported
        for this output destination, but that it is turned off.  Jobs
        not specifying whether to staple, will not be stapled.
        'notPresent' indicates the staple default feature is not
        supported.  Jobs not specifying whether to staple, will not
        be stapled.
        The value 'other' shall mean not specified."
    REFERENCE "
        See: 'xcmPrtOutputStaple
        See: 'xcmPrtOutputStaplePosSupported'
        See: 'xcmPrtOutputStaplePosDefault'"
    DEFVAL { other } 
    ::= { xcmPrtOutputEntry 102 }
xcmPrtOutputStaplePosDefault OBJECT-TYPE
    SYNTAX      XcmPrtOutputStaplePosition
    MAX-ACCESS  read-create
    STATUS      current
    DESCRIPTION "
        This object controls the default staple position to be used
        when stapling is enabled, and the job-stream does not specify
        whether to staple the particular job or the job-stream
        specifies to apply a staple, but does not specify where.
        Only one staple position may be declared.
        The value of zero indicates a default of not staple."
    REFERENCE "
        See: 'xcmPrtOutputStaple'
        See: 'xcmPrtOutputStapleDefault'
        See: 'xcmPrtOutputStaplePosSupported'"
    DEFVAL { 0 }  
    ::= { xcmPrtOutputEntry 103 }
xcmPrtOutputPunch  OBJECT-TYPE
    SYNTAX      PresentOnOff
    MAX-ACCESS  read-create
    STATUS      current
    DESCRIPTION "
        This object declares whether the printer has the ability to
        punch holes in documents delivered to the specified output
        destination, and whether this ability is currently turned on.
        'on' indicates hole punching is supported to this output
        destination and that it is turned on
        'off'  indicates this printer supports hole punching to this
        output destination, but that it is turned off.  If a job calls
        for punched output, no punching will occur.
        'not Present'  indicates that this printer does not support
        hole punching."
    DEFVAL  { notPresent}
    ::= {xcmPrtOutputEntry  104}
xcmPrtOutputPunchDefault  OBJECT-TYPE
    SYNTAX      PresentOnOff
    MAX-ACCESS  read-create
    STATUS      current
    DESCRIPTION "
        This object declares whether the printer will punch the job
        when the print stream does not specify a punch requirement.
        'on' indicates hole punching is supported to this output
        destination and that the job will be punched if the data
        stream contains no job punch information
        'off'  indicates this printer supports hole punching to this
        output destination, and that the job will not be punched if
        the data stream contains no job punch information
        'not Present'  indicates that this printer does not support
        hole punching."
    DEFVAL  { notPresent}
    ::= {xcmPrtOutputEntry  105}
--
--
xcmPrtOutputPunchPosSupported  OBJECT-TYPE
     SYNTAX      XcmPrtOutputPunchPosition
      MAX-ACCESS  read-create
      STATUS      current
      DESCRIPTION "
          This object declares the punch positions supported."
      REFERENCE "
          See: 'xcmPrtOutputPunch'"
      DEFVAL  { 0 } 
      ::= {xcmPrtOutputEntry  106}
xcmPrtOutputBookletFoldStaple OBJECT-TYPE
      SYNTAX      PresentOnOff
      MAX-ACCESS  read-create
      STATUS      current
      DESCRIPTION "
          This object declares whether the device has the ability to
          fold and or staple booklet documents delivered to the specifie
          output destination, and whether this ability is currently turn
          on  indicates booklet folding and/or stapling is supported to 
          output destination and that it is turned on.
          off  indicates booklet folding and/or stapling is supported to
          but that it is turned off. If a job calls for a
          booklet folding and/or staple, none will be given.
          notPresent  indicates booklet folding and/or stapling is
          not supported.
          The value  other  shall mean not specified."
      DEFVAL  { notPresent } 
      ::= { xcmPrtOutputEntry  107 }
--
--
xcmPrtChannelTable OBJECT-TYPE
    SYNTAX      SEQUENCE OF XcmPrtChannelEntry
    MAX-ACCESS  not-accessible
    STATUS      current
    DESCRIPTION "
        This table logically augments Printer MIB's prtChannelTable."
    ::= { xcmPrtChannel 1 }
xcmPrtChannelEntry OBJECT-TYPE
    SYNTAX      XcmPrtChannelEntry
    MAX-ACCESS  not-accessible
    STATUS      current        
    DESCRIPTION "
        An entry exists corresponding to each entry in the
        prtChannelTable."
    AUGMENTS    { prtChannelEntry }
    ::= { xcmPrtChannelTable 1 }
XcmPrtChannelEntry ::= SEQUENCE {
    xcmPrtChannelRowStatus          RowStatus,
    xcmPrtChannelEOJTimeout         Cardinal32,
    xcmPrtChannelAuxSheetPackage    Cardinal32,
    xcmPrtChannelSpoolingEnable     PresentOnOff,
    xcmPrtChannelLangSensing        PresentOnOff,
    xcmPrtChannelBinaryPostScript   PresentOnOff,
    xcmPrtChannelAutoJobEnd         PresentOnOff,
    xcmPrtChannelBinaryPostScriptZ  PresentOnOff
    }
xcmPrtChannelRowStatus OBJECT-TYPE
    SYNTAX      RowStatus
    MAX-ACCESS  read-create
    STATUS      current
    DESCRIPTION "
        Manages the status of this conceptual row in the
        xcmPrtChannelTable."
    ::= { xcmPrtChannelEntry 1 }
xcmPrtChannelEOJTimeout OBJECT-TYPE
    SYNTAX      Cardinal32
    UNITS       "Seconds"
    MAX-ACCESS  read-create
    STATUS      current
    DESCRIPTION "
        Defines the number of  seconds that the channel waits before
        timing out. For example, this may be used for the parallel
        channel.
        The value zero means infinite or no timeout on the channel."
    DEFVAL { 0 } 
    ::= { xcmPrtChannelEntry 2 }
xcmPrtChannelAuxSheetPackage OBJECT-TYPE
    SYNTAX      Cardinal32
    MAX-ACCESS  read-create
    STATUS      current
    DESCRIPTION "
        This object is an index into the xcmPrtAuxPackageTable.
        This table is used to enable or disable printing of
        auxiliary sheets by this channel.
        The value zero shall mean not specified."
    REFERENCE "
        See: xcmPrtGeneralAuxSheetPackage
        See: xcmPrtInterpAuxSheetPackage"
    DEFVAL { 0 } 
    ::= { xcmPrtChannelEntry 3 }
xcmPrtChannelSpoolingEnable OBJECT-TYPE
    SYNTAX      PresentOnOff
    MAX-ACCESS  read-create
    STATUS      current
    DESCRIPTION "
        This object controls spooling to a large data store such as a
        hard disk.
        When set to On, data received and waiting to be processed from
        any port is spooled onto the large data store and later
        retrieved for processing.  This allows the printer to receive 
        the data more rapidly, thus freeing the data source sooner.
        It may also increase throughput by having the next job's print
        data already local for processing.
        When set to Off, the spooling feature is disabled.
        Data received is not spooled to the large data store, and is
        accepted by the printer only as needed for printing.  
        You may want to disable this spooling feature if spooling is
        already done outside the printer; having the spooling done on
        the printer as well, may not add value, and may create error
        recovery and queue monitoring difficulties.
        The value 'other' shall mean not specified."
    REFERENCE "
        DocuPrint 4517 Network Laser Printers User Guide, pg. D-5."
    DEFVAL { other }  
    ::= { xcmPrtChannelEntry 4 }
xcmPrtChannelLangSensing OBJECT-TYPE
    SYNTAX      PresentOnOff
    MAX-ACCESS  read-create
    STATUS      current
    DESCRIPTION "
        This object indicates whether the channel supports detection of
        the input PDL language type, and if so, whether the feature is
        enabled.
        Currently, the prtChannelDefaultPageDescLangIndex points to the
        Page Description Language Interpreter for this channel.  One of
        the PDL types enumerated in the prtInterpreterLangFamily object
        is langAutomatic(37), to be used for automatic PDL sensing;
        however, if the language sensing fails there is no fallback
        language for the channel.
        Conforming implementations shall use xcmPrtChannelLangSensing
        for each channel and deprecate use of the langAutomatic(37) enum
        in favor of the literal default language in the
        prtInterpreterLangFamily object.
        The value 'other' shall mean not specified."
    REFERENCE "
        See: Printer MIB prtInterpreterLangFamily"
    DEFVAL { other }  
    ::= { xcmPrtChannelEntry 5 }
xcmPrtChannelBinaryPostScript OBJECT-TYPE
    SYNTAX      PresentOnOff
    MAX-ACCESS  read-create
    STATUS      current
    DESCRIPTION "
        If 'On' PostScript received over this channel is
        processed as pure binary data.
        If 'Off' PostScript is interpretted as ASCII or TBCP data.
        The value 'other' shall mean not specified."
    REFERENCE "
        See: Printer MIB prtInterpreterLangFamily
        See: xcmPrtChannelBinaryPostScriptZ"
    DEFVAL { other }  
    ::= { xcmPrtChannelEntry 6 }
--
--
--
xcmPrtChannelAutoJobEnd OBJECT-TYPE
    SYNTAX      PresentOnOff
    MAX-ACCESS  read-create
    STATUS      current
    DESCRIPTION "
        Controls automatic ending of a print job that does not finish
        printing.
        When 'On', after the current print job has paused long enough
        to exceed the xcmPrtChannelEOJTimeout interval,
        the current print job will be stopped.
        When 'Off', the print job does not end after the timeout
        interval.  Instead, the printer waits to continue until another
        print job is received on any port.  A partial page will remain
        unprinted until the next print job is received.  The current
        job will then be stopped.
        The value 'other' shall indicate not specified."
    REFERENCE "
        See: xcmPrtChannelEOJTimeout
        See: Xerox 4517+ User Guide
        See: Xerox 4505  User Guide"
    DEFVAL { other } 
    ::= { xcmPrtChannelEntry 80 }
xcmPrtChannelBinaryPostScriptZ OBJECT-TYPE
    SYNTAX      PresentOnOff
    MAX-ACCESS  read-create
    STATUS      current
    DESCRIPTION "
        If 'On' PostScript received over this channel is
        processed as pure binary data.
        If 'Off' PostScript is interpretted as ASCII or TBCP data.
        The value 'other' shall mean not specified.
        Devices should NOT implement this object, should instead
        implement the equivalent object xcmPrtChannelBinaryPostScript.
        This xcmPrtChannelBinaryPostScriptZ object appears for
        backward compatibility support only, since some few devices
        implemented the object at this OID.  Clients/managers wishing
        to support those devices should try to access both objects
        (which generally can be done with a single SNMP message packet
        combining requests for both object OIDs) and use whichever
        object is present in the device."
    REFERENCE "
        See: xcmPrtChannelBinaryPostScript
        See: Printer MIB prtInterpreterLangFamily"
    DEFVAL { other }  
    ::= { xcmPrtChannelEntry 81 }
--
--
--
xcmPrtInterpreterTable OBJECT-TYPE
    SYNTAX      SEQUENCE OF XcmPrtInterpreterEntry
    MAX-ACCESS  not-accessible
    STATUS      current
    DESCRIPTION "
        This table logically augments the Printer MIB's
        prtInterpreterTable."
    ::= { xcmPrtInterpreter 1 }
xcmPrtInterpreterEntry OBJECT-TYPE
    SYNTAX      XcmPrtInterpreterEntry
    MAX-ACCESS  not-accessible
    STATUS      current        
    DESCRIPTION "
        An entry exists corresponding to each entry in the
        prtInterpreterTable."
    AUGMENTS    { prtInterpreterEntry }
    ::= { xcmPrtInterpreterTable 1 }
XcmPrtInterpreterEntry ::= SEQUENCE {
    xcmPrtInterpRowStatus           RowStatus,
    xcmPrtInterpAuxSheetPackage     Cardinal32,
    xcmPrtInterpContextSaving       PresentOnOff,
    xcmPrtInterpEdgeEnhancement     PresentOnOff,
    xcmPrtInterpFontIndexDefault    Integer32,
    xcmPrtInterpGrayLevels          Cardinal32,
    xcmPrtInterpGrayLevelDefault    Cardinal32,
    xcmPrtInterpJamRecovery         PresentOnOff,
    xcmPrtInterpJobCopiesDefault    Ordinal32,
    xcmPrtInterpLineWrap            PresentOnOff,
    xcmPrtInterpMediumSizeDefault   XcmPrtMediumSize,
    xcmPrtInterpPageProtect         PresentOnOff,
    xcmPrtInterpPageProtectSize     XcmPrtMediumSize,
    xcmPrtInterpPageSizeErrorPolicy XcmPrtPageSizeErrorPolicy,
    xcmPrtInterpPlexSupported       XcmPrtPlex,
    xcmPrtInterpPlexDefault         XcmPrtPlex,
    xcmPrtInterpPrintEdgeToEdge     PresentOnOff,
    xcmPrtInterpPrintQuality        XcmPrtPrintQuality,
    xcmPrtInterpPrtInputIndexDflt   Cardinal32,
    xcmPrtInterpPrtOutputIndexDflt  Cardinal32,
    xcmPrtInterpResFeedDirDefault   Cardinal32,
    xcmPrtInterpResXFeedDirDefault  Cardinal32,
    xcmPrtInterpResIPResIndex       Cardinal32,
    xcmPrtInterpResIPResIndexDflt   Cardinal32,
    xcmPrtInterpTextFormLength      Cardinal32,
    xcmPrtInterpTimeoutJob          Cardinal32,
    xcmPrtInterpTimeoutPage         Cardinal32,
    xcmPrtInterpInputAliasIndexDflt Cardinal32,
    xcmPrtInterpTraySwitch          XcmPrtTraySwitch,
    xcmPrtInterpMediumTypeDefault
                       XcmFixedLocaleDisplayString (SIZE(0..255)),
    xcmPrtInterpMediaTypeErrPolicy  XcmPrtMediaTypeErrorPolicy,
    xcmPrtInterpErrorPolicyTimeout  Cardinal32,
    xcmPrtInterpLineTerm            PresentOnOff,
    xcmPrtInterpEnhancedResolution  PresentOnOff,
    xcmPrtInterpAutoContinue        PresentOnOff,
    xcmPrtInterpEnvFeederSize       XcmPrtMediumSize,
    xcmPrtInterpManualFeedPgSize    XcmPrtMediumSize,
    xcmPrtInterpOffsetStackingType  XcmPrtOutputOffsetStackingType,
    xcmPrtInterpProcessBarcodes     PresentOnOff
    }
xcmPrtInterpRowStatus OBJECT-TYPE
    SYNTAX      RowStatus
    MAX-ACCESS  read-create
    STATUS      current
    DESCRIPTION "
        Manages the status of this conceptual row in the
        xcmPrtInterpreterTable."  
    ::= { xcmPrtInterpreterEntry 1 }
xcmPrtInterpAuxSheetPackage OBJECT-TYPE
    SYNTAX      Cardinal32
    MAX-ACCESS  read-create
    STATUS      current
    DESCRIPTION "
        This object is an index into the xcmPrtAuxPackageTable.
        This table is used to enable or disable printing of
        auxiliary sheets by this interpreter.
        The value zero shall mean not specified."
    REFERENCE "
        See: xcmPrtGeneralAuxSheetPackage
        See: xcmPrtChannelAuxSheetPackage"
    DEFVAL { 0 } 
    ::= { xcmPrtInterpreterEntry 2 }
xcmPrtInterpContextSaving OBJECT-TYPE
    SYNTAX      PresentOnOff
    MAX-ACCESS  read-create
    STATUS      current
    DESCRIPTION "
        Enables reserving memory for saving permanently downloaded fonts
        and macros, when the printer switches between this and another
        interpreter.  The effect is to save the memory for a subsequent
        job using this interpreter.
        When set to Off, all permanently downloaded fonts and macros are
        cleared from memory when switching PDLs.  They must be
        downloaded again when the printer switches back to using the
        current PDL.
        When set to On, permanently downloaded fonts and macros are
        stored in printer memory.  You eliminate the time to download
        them again when the printer switches back to the current PDL.
        In PCL, this is referred to as Resource Savings.
        The value 'other' shall mean not specified."
    REFERENCE "
        DocuPrint 4517 Network Laser Printers User Guide, Pg. D-16."
    DEFVAL { other }  
    ::= { xcmPrtInterpreterEntry 3 }
xcmPrtInterpEdgeEnhancement OBJECT-TYPE
    SYNTAX      PresentOnOff
    MAX-ACCESS  read-create
    STATUS      current
    DESCRIPTION "
        Specifies whether the printer should perform EdgeEnhancement of
        the image of the printed document for this interpreter.
        The value 'other' shall mean not specified."
    DEFVAL { other } 
    ::= { xcmPrtInterpreterEntry 4 }
xcmPrtInterpFontIndexDefault OBJECT-TYPE
    SYNTAX      Integer32
    MAX-ACCESS  read-create
    STATUS      current
    DESCRIPTION "
        The value of xcmFontIndex corresponding to the xcmFontEntry
        which represents the default font for this Interpreter.
        A value of (-1) means 'other'.
        A value of (-2) means 'unknown'.
        A value of (-3) means 'notPresent'.
        A value of 'other' (-3) should be used for those
        interpreters which have no default font (e.g. PostScript).
        For agents that choose not to implement the Resources MIB,
        this object specifies the ID of the default font.  This use
        of this object is significant only to the specific product."
    DEFVAL { -2 } 
    ::= { xcmPrtInterpreterEntry 5 }
xcmPrtInterpGrayLevels OBJECT-TYPE
    SYNTAX      Cardinal32
    MAX-ACCESS  read-create
    STATUS      current
    DESCRIPTION "
        This object describes the gray levels supported by this
        interpreter.  This may represent gray levels within a color
        plane.
        The value zero means not specified for this interpreter."
    DEFVAL { 0 } 
    ::= { xcmPrtInterpreterEntry 6 }
xcmPrtInterpGrayLevelDefault OBJECT-TYPE
    SYNTAX      Cardinal32
    MAX-ACCESS  read-create
    STATUS      current
    DESCRIPTION "
        This object controls the number of gray scales for this
        interpreter.
        The value zero means not specified for this interpreter."
    REFERENCE "See: xcmPrtInterpGrayLevels"
    DEFVAL { 0 } 
    ::= { xcmPrtInterpreterEntry 7 }
xcmPrtInterpJamRecovery OBJECT-TYPE
    SYNTAX  PresentOnOff
    MAX-ACCESS  read-create
    STATUS      current
    DESCRIPTION "
        This object controls how the printer recovers from a paper jam.
        When set to On, the printer reprints any pages in the printer at
        the time of the jam, after the jam has been cleared.  The
        printer does this by using a portion of memory to store print
        data.  This may slow throughput.
        When set to Off, some pages may be lost after the jam has been
        cleared.  The print job must be re-sent, specifying those pages
        that did not print as a result of the paper jam.
        The value 'other' shall mean not specified."
    REFERENCE "
        DocuPrint 4517 Network Laser Printers User Guide, Pg. D-9."
    DEFVAL { other }  
    ::= { xcmPrtInterpreterEntry 8 }
xcmPrtInterpJobCopiesDefault OBJECT-TYPE
    SYNTAX      Ordinal32
    MAX-ACCESS  read-create
    STATUS      current
    DESCRIPTION "
        This defines the default number of job copies to be printed
        by this interpreter.
        If set incorrectly, this object may cause difficulties at
        customer sites.  Agent developers should consider making this
        object read-only, permanently set to one copy."
    REFERENCE "
          See: ISO/IEC 10175-1:1996(E)
               - Section 9.2.2.1: Results-profile job-copies
          See: PJL Technical Reference Manual - COPIES
          See: PCL 5 Printer Language Technical Reference Manual
               - Number of Copies Command"
    DEFVAL { 1 } 
    ::= { xcmPrtInterpreterEntry 9 }
xcmPrtInterpLineWrap OBJECT-TYPE
    SYNTAX      PresentOnOff
    MAX-ACCESS  read-create
    STATUS      current
    DESCRIPTION "
        This object controls whether long lines are wrapped or
        truncated.
        If On,  long lines wrap to the next line.
        If Off, long lines are truncated.
        Note the meaning of 'long' depends on the orientation and the
        current page size.
        The value 'other' shall mean not specified."
    REFERENCE "
        Adobe PostScript Language Reference Manual Supplement."
    DEFVAL { other }  
    ::= { xcmPrtInterpreterEntry 10 }
xcmPrtInterpMediumSizeDefault OBJECT-TYPE
    SYNTAX      XcmPrtMediumSize
    MAX-ACCESS  read-create
    STATUS      current
    DESCRIPTION "
        This object specifies the default medium size for an
        interpreter.  It is used if no medium size is specified.
        For PCL, this object sets the General PJL Environment variable
        'Paper'.
        The xcmPrtInterpMediumSizeDefault object may be affected by
        setting the xcmPrtGeneralMediumClassDefault object."
    REFERENCE "
        See: PCL 5 Printer Language Technical Reference Manual
        See: PJL Technical Reference Manual - PAPER
        See: xcmPrtGeneralMediumClassDefault"
    DEFVAL { notSpecified }
    ::= { xcmPrtInterpreterEntry 11 }
xcmPrtInterpPageProtect OBJECT-TYPE
    SYNTAX      PresentOnOff
    MAX-ACCESS  read-create
    STATUS      current
    DESCRIPTION "
        This object enables reserving sufficient memory for printing
        complex pages, thus avoiding Page Too Complex errors.
        The amount of memory reserved is implementation specific.
        When this feature is turned on, printer performance may
        be slowed.
        The value 'other' shall mean not specified."
    REFERENCE "
        DocuPrint 4517 Network Laser Printers User Guide, Pg. D-11."
    DEFVAL { other } 
    ::= { xcmPrtInterpreterEntry 12 }
xcmPrtInterpPageProtectSize OBJECT-TYPE
    SYNTAX      XcmPrtMediumSize
    MAX-ACCESS  read-create
    STATUS      current
    DESCRIPTION "
        This object sets the PageSize to be used by this interpreter
        in reserving sufficient memory for printing complex pages,
        thus avoiding Page Too Complex Errors.
        The actual amount of memory to be reserved as a function of the
        specified page size is implementation specific. When this
        feature is turned on, printer performance may be slowed.
        In PCL, this object supports the General PJL Environment
        Variable 'PAGEPROTECT'.  This object the sets the page
        protection configuration.
        The page protection feature reserves a block of printer memory
        to prevent printer overrun errors when formatting very dense
        or complex images.  This variable may be set to any legal
        value at any time, regardless of the current amount of free
        memory or the currently set resolution.
        When a job is sent, if there is not enough memory to print
        correctly with the current resolution and page protection
        configuration, the system temporarily overrides the resolution
        and/or page protect values to run the job.
        When the page protection status is changed, memory may be
        reconfigured, and all downloaded fonts, PCL macros, and
        PostScript dictionaries may be lost.
        The value notSpecified shall also mean Off."
    REFERENCE "
        See: Printer Job Language Technical Reference Manual
             - General PJL Environment Variable 'PAGEPROTECT'"
    DEFVAL { notSpecified } 
    ::= { xcmPrtInterpreterEntry 13 }
xcmPrtInterpPageSizeErrorPolicy OBJECT-TYPE
    SYNTAX      XcmPrtPageSizeErrorPolicy
    MAX-ACCESS  read-create
    STATUS      current
    DESCRIPTION "
        Controls interpreter behavior when the requested Page Size
        is not currently available."
    REFERENCE "
        See: xcmPrtInterpMediaTypeErrPolicy
        See: xcmPrtInterpErrorPolicyTimeout"
    DEFVAL { notSpecified }
    ::= { xcmPrtInterpreterEntry 14 }
xcmPrtInterpPlexSupported OBJECT-TYPE
    SYNTAX      XcmPrtPlex
    MAX-ACCESS  read-create
    STATUS      current
    DESCRIPTION "
        This object specifies the Plex modes supported by this
        interpreter.  These Plex modes specify the relative
        orientations between consecutive pages, and capabilities of
        printing one-side, two-sided or both.  "
    DEFVAL { 0 } 
    ::= { xcmPrtInterpreterEntry 15 }
xcmPrtInterpPlexDefault OBJECT-TYPE
    SYNTAX      XcmPrtPlex
    MAX-ACCESS  read-create
    STATUS      current
    DESCRIPTION "
        This object specifies the default plex for this interpreter.
        The device shall set no more than one bit.
        The value zero shall indicate not specified."
    REFERENCE "See: xcmPrtInterpPlexSupported"
    DEFVAL { 0 } 
    ::= { xcmPrtInterpreterEntry 16 }
xcmPrtInterpPrintEdgeToEdge OBJECT-TYPE
    SYNTAX      PresentOnOff
    MAX-ACCESS  read-create
    STATUS      current
    DESCRIPTION "
        Enables edge to edge printing for interpreters that try to
        enforce a coordinate system that is offset from the edge of the
        paper, e.g., PCL.
        When On,  jobs are printed to the edge of the paper.
        When Off, jobs are printed in normal printable area of page.
        The value 'other' shall mean not specified."
    DEFVAL { other } 
    ::= { xcmPrtInterpreterEntry 17 }
xcmPrtInterpPrintQuality OBJECT-TYPE
    SYNTAX      XcmPrtPrintQuality
    MAX-ACCESS  read-create
    STATUS      current
    DESCRIPTION "
        Sets the default output quality of the printed document for this
        interpreter.  Some printers have programmatically controlled
        output quality."
    DEFVAL { normal }
    ::= { xcmPrtInterpreterEntry 18 }
xcmPrtInterpPrtInputIndexDflt OBJECT-TYPE
    SYNTAX      Cardinal32
    MAX-ACCESS  read-create
    STATUS      current
    DESCRIPTION "
        Sets the default input source for the interpreter.
        It is the index to the prtInputGroup.
        The value zero means not specified."
    DEFVAL { 0 } 
    ::= { xcmPrtInterpreterEntry 19 }
xcmPrtInterpPrtOutputIndexDflt OBJECT-TYPE
    SYNTAX      Cardinal32
    MAX-ACCESS  read-create
    STATUS      current
    DESCRIPTION "
        The value of the index of the default Output bin for this
        interpreter.  If specified, this object overrides the box level
        object prtOutputDefaultIndex.
        The value zero means unspecified."
    REFERENCE "See: Printer MIB prtOutputDefaultIndex"
    DEFVAL { 0 } 
    ::= { xcmPrtInterpreterEntry 20 }
xcmPrtInterpResFeedDirDefault OBJECT-TYPE
    SYNTAX      Cardinal32
    MAX-ACCESS  read-create
    STATUS      current
    DESCRIPTION "
        This object specifies for this interpreter, the default
        resolution in the Feed direction in 10000 units of measure
        specified by prtMarkerAddressabilityUnit for this interpreter.
        A related object is the Printer MIB
        prtInterpreterFeedAddressability object which describes the 
        maximum interpreter addressability in the feed direction.
        The value zero shall mean not specified.
        If this object has a value other than unspecified, this object
        takes precedence over xcmPrtInterpFeedResIndexDefault."
    REFERENCE "See: Printer MIB prtInterpreterFeedAddressability"
    DEFVAL { 0 } 
    ::= { xcmPrtInterpreterEntry 21 }
xcmPrtInterpResXFeedDirDefault OBJECT-TYPE
    SYNTAX      Cardinal32
    MAX-ACCESS  read-create
    STATUS      current
    DESCRIPTION "
        This object specifies for this interpreter, the default
        resolution in the Cross Feed direction in 10000 units of measure
        specified by prtMarkerAddressabilityUnit for this interpreter.
        A related object is the Printer MIB
        prtInterpreterFeedAddressability object which describes the 
        maximum interpreter addressability in the cross feed direction.
        The value zero means unspecified.
        If this object has a value other than unspecified, this object 
        takes precedence over xcmPrtInterpFeedResIndexDefault."
    REFERENCE "See: Printer MIB prtInterpreterXFeedAddressability"
    DEFVAL { 0 } 
    ::= { xcmPrtInterpreterEntry 22 }
xcmPrtInterpResIPResIndex OBJECT-TYPE
    SYNTAX     Cardinal32
    MAX-ACCESS read-create
    STATUS     current
    DESCRIPTION "
        This object shall provide an index into the xcmIPResTable.
        The xcmIPResTable shall be used to list available resolutions
        supported by this interpreter.  Each row includes objects
        for Feed Resolution (pixels per inch), XFeed Resolution
        (pixels per inch), Bits Per Pixel Supported, and Number of
        Color Planes Supported.
        The value zero means unspecified."
    DEFVAL { 0 } 
    ::= { xcmPrtInterpreterEntry 23 }
xcmPrtInterpResIPResIndexDflt OBJECT-TYPE
    SYNTAX      Cardinal32
    MAX-ACCESS  read-create
    STATUS      current
    DESCRIPTION "
        This object which is a pointer into the xcmIPResTable sets the
        print resolution for this interpreter.
        The value zero means unspecified."
    DEFVAL { 0 } 
    ::= { xcmPrtInterpreterEntry 24 }
xcmPrtInterpTextFormLength OBJECT-TYPE
    SYNTAX      Cardinal32
    MAX-ACCESS  read-create
    STATUS      current
    DESCRIPTION "
        This object sets the maximum number of lines per page for a text
        file that is being printed using this interpreter.
        For PCL Interpreters, this object provides the General PJL
        Environment Variable FORMLINES.  This variable is tied to both
        the PJL Environment Variables PAPER and ORIENTATION.  If the
        value of either of those variables is changed, then the
        FORMLINES variable automatically is updated to maintain the
        same line spacing.
        The value zero means not specified."
    REFERENCE "
        See: PJL Technical Reference Manual - FORMLINES"
    DEFVAL { 0 } 
    ::= { xcmPrtInterpreterEntry 25 }
xcmPrtInterpTimeoutJob OBJECT-TYPE
    SYNTAX      Cardinal32
    UNITS       "Seconds"
    MAX-ACCESS  read-create
    STATUS      current
    DESCRIPTION "
        This object sets how long printer will wait for correct end of
        job from the interpreter.
        This setting lets you adjust how long the printer will wait to
        receive the data it needs to complete a job before terminating
        it prematurely.
        The value zero means infinite."
    DEFVAL { 0 } 
    ::= { xcmPrtInterpreterEntry 26 }
xcmPrtInterpTimeoutPage OBJECT-TYPE
    SYNTAX      Cardinal32
    UNITS       "Seconds"
    MAX-ACCESS  read-create
    STATUS      current
    DESCRIPTION "
        This object sets how long printer will wait for correct end of
        page from the interpreter.
        If, for example, a print job contains a page without the correct
        end of page code, the job will stall.  This setting lets you
        adjust how long the printer will wait to receive the data it
        needs to complete a page before terminating it prematurely.
        The value zero means infinite."
    DEFVAL { 0 } 
::= { xcmPrtInterpreterEntry 27 }
xcmPrtInterpInputAliasIndexDflt OBJECT-TYPE
    SYNTAX      Cardinal32
    MAX-ACCESS  read-create
    STATUS      current
    DESCRIPTION "
        Sets the default input tray alias for this interpreter.
        It is the xcmPrtInputAliasIndex to the xcmPrtInputAlias table.
        The value zero means 'not specified'."
    REFERENCE   " See: xcmPrtInputAliasTable"
    DEFVAL { 0 } 
    ::= { xcmPrtInterpreterEntry 28 }
xcmPrtInterpTraySwitch OBJECT-TYPE
    SYNTAX      XcmPrtTraySwitch
    MAX-ACCESS  read-create
    STATUS      current
    DESCRIPTION "
        This object declares for this interpreter the tray switching
        declaration mechanism used.
        Note: The tray switching declaration mechanisms do not specify
        how or when or whether a printer switches back to using an
        earlier emptied tray after that tray is refilled.
        For example, assume a printer is set up to first use
        Tray 1, then when emptied Tray 2, then Tray 3.
        If just after tray 1 becomes empty and the printer switches
        to Tray 2, the operator refills Tray 1; the printer may
        select which tray to pull the next sheet from using a variety
        of algorithms:
        - The printer may switch back immediately to use tray 1.
          This may be particularly appropriate if tray 1 is the
          high capacity feeder.
        - The printer may pull sheets from tray 2 until it is
          empty and then switch back to tray 1.
        - The printer may pull sheets from tray 2 until it is
          empty and then continue to tray 3, before switching
          back to tray 1.
        Again, implementation of how the input tray switching
        programs behave when empty trays are refilled is considered
        printer specific."
    REFERENCE "
        See:  xcmPrtInputNextPrtInputIndex
        See:  xcmPrtInputAliasGroup"
    DEFVAL { notSpecified }
    ::= { xcmPrtInterpreterEntry 29 }
xcmPrtInterpMediumTypeDefault OBJECT-TYPE
    SYNTAX      XcmFixedLocaleDisplayString (SIZE(0..255))
    MAX-ACCESS  read-create
    STATUS      current
    DESCRIPTION "
        Specifies the paper type used to print a page if no paper
        type is specified by the software application
        Typical paper types could include Plain, Preprinted, etc."
    DEFVAL { ''H } 
    ::= { xcmPrtInterpreterEntry 30 }
xcmPrtInterpMediaTypeErrPolicy OBJECT-TYPE
    SYNTAX      XcmPrtMediaTypeErrorPolicy
    MAX-ACCESS  read-create
    STATUS      current
    DESCRIPTION "
        Controls interpreter behavior when the requested Media Type
        is not currently available."
    REFERENCE "
        See: xcmPrtInterpPageSizeErrorPolicy
        See: xcmPrtInterpErrorPolicyTimeout"
    DEFVAL { notSpecified }
    ::= { xcmPrtInterpreterEntry 31 }
xcmPrtInterpErrorPolicyTimeout OBJECT-TYPE
    SYNTAX      Cardinal32
    UNITS       "Seconds"
    MAX-ACCESS  read-create
    STATUS      current
    DESCRIPTION "
        Provides the timeout for ErrorPolicy enumerations
        requiring one, e.g. 'ignoreAfterTimeout'
        The value zero shall mean infinite or not supported."
    REFERENCE "
        See: xcmPrtInterpPageSizeErrorPolicy
        See: xcmPrtInterpMediaTypeErrPolicy"
    DEFVAL { 0 }
    ::= { xcmPrtInterpreterEntry 32 }
xcmPrtInterpLineTerm OBJECT-TYPE
    SYNTAX      PresentOnOff
    MAX-ACCESS  read-create
    STATUS      current
    DESCRIPTION "
        Enables adding a Carriage Return after every Line Feed.
        The value 'On' indicates that a Carriage Return will be 
        added after every Line Feed.
        Usage example:  This is a useful feature when printing text
        jobs via PCL through a standard queue in UNIX.
        The value 'other' shall mean not specified."
    DEFVAL { other }  
    ::= { xcmPrtInterpreterEntry 33 }
xcmPrtInterpEnhancedResolution OBJECT-TYPE
    SYNTAX      PresentOnOff
    MAX-ACCESS  read-create
    STATUS      current
    DESCRIPTION "
        This  value determines whether the value of
        prtMarkerAddressabilityFeedDir and
        prtMarkerAddressabilityXFeedDir is generated directly or
        generated by enhancing a lower resolution
        via interpolation techniques.
        The value 'other' shall mean not specified."
    DEFVAL { other }  
    ::= { xcmPrtInterpreterEntry 34 }
--
--
--
xcmPrtInterpAutoContinue OBJECT-TYPE
    SYNTAX      PresentOnOff
    MAX-ACCESS  read-create
    STATUS      current
    DESCRIPTION "
        This object controls whether the printer resumes printing after
        a system error occurs.
        When set to Off, the printer does not automatically resume.
        Manual intervention must occur for the printer to resume.
        When set to On, the printer automatically resumes operation
        after certain system errors.  The On setting is useful in a
        networked environment.
        The value 'other' shall mean not specified."
    REFERENCE "
        DocuPrint 4517 Network Laser Printers User Guide, Pg. D-3."
    DEFVAL { other }  
    ::= { xcmPrtInterpreterEntry 50 }
xcmPrtInterpEnvFeederSize OBJECT-TYPE
    SYNTAX      XcmPrtMediumSize
    MAX-ACCESS  read-create
    STATUS      current
    DESCRIPTION "
        This object informs the printer what size of envelope is
        currently loaded in the envelope feeder.  Because the input tray
        feeding envelopes may not have a size sensor, this setting is
        required so that the printer is able to know when the size of
        envelope requested for printing is different than that loaded.
        When the sizes do not match, and xcmPrtInterpPageSizeErrorPolicy
        is set to Off, the printer displays a message asking for a
        change of envelope size.
        The XcmPrtPaperSize selected should be that of an envelope."
    REFERENCE "
        DocuPrint 4517 Network Laser Printers User Guide, Pg. D-16."
    DEFVAL { notSpecified }
    ::= { xcmPrtInterpreterEntry 51 }
xcmPrtInterpManualFeedPgSize OBJECT-TYPE
    SYNTAX      XcmPrtMediumSize
    MAX-ACCESS  read-create
    STATUS      current
    DESCRIPTION "
        This object sets the default medium size of the manual input
        tray for this interpreter."
    REFERENCE "
        DocuPrint 4517 Network Laser Printers User Guide, Pg. D-10."
    DEFVAL { notSpecified }
    ::= { xcmPrtInterpreterEntry 52 }
xcmPrtInterpOffsetStackingType OBJECT-TYPE
    SYNTAX      XcmPrtOutputOffsetStackingType
    MAX-ACCESS  read-create
    STATUS      current
    DESCRIPTION "
        This object further refines the type of offset stacking from
        that specified by the object prtOutputOffsetStacking in the
        Printer MIB.
        Printers who need to specify OffsetStackingType by
        interpreter shall set this object to 'other'.
        To specify OffsetStackingType by interpreter, use the
        object xcmPrtOutputOffsetStackingType."
    REFERENCE "
        See: prtOutputOffsetStacking.
        See: xcmPrtOutputOffsetStackingType"
    DEFVAL { notSpecified }
    ::= { xcmPrtInterpreterEntry 53 }
xcmPrtInterpProcessBarcodes OBJECT-TYPE
    SYNTAX      PresentOnOff
    MAX-ACCESS  read-create
    STATUS      current
    DESCRIPTION "
 Specifies whether the 'extra' barcode processing within 
 the interpreter should be used."
    DEFVAL { other }  
    ::= { xcmPrtInterpreterEntry 54 }
--
--
xcmPrtInputAliasTable OBJECT-TYPE
    SYNTAX      SEQUENCE OF XcmPrtInputAliasEntry
    MAX-ACCESS  not-accessible
    STATUS      current
    DESCRIPTION "
        This table defines one or more aliases for input sub-units
        defined in the Input Group."
    ::= { xcmPrtInputAlias 1 }
xcmPrtInputAliasEntry OBJECT-TYPE
    SYNTAX      XcmPrtInputAliasEntry
    MAX-ACCESS  not-accessible
    STATUS      current        
    DESCRIPTION "
        One or more entries may exist corresponding to each entry
        in the prtInputTable."
    INDEX { hrDeviceIndex, prtInterpreterIndex, xcmPrtInputAliasIndex }
    ::= { xcmPrtInputAliasTable 1 }
XcmPrtInputAliasEntry ::= SEQUENCE {
    xcmPrtInputAliasIndex     Cardinal32,
    xcmPrtInputAliasRowStatus RowStatus,
    xcmPrtInputAliasName
                XcmFixedLocaleDisplayString (SIZE(0..63)),
    xcmPrtInputAliasSwitchProgram  DisplayString (SIZE(0..255))
    }
xcmPrtInputAliasIndex OBJECT-TYPE
    SYNTAX      Cardinal32
    MAX-ACCESS  not-accessible
    STATUS      current
    DESCRIPTION "
        A unique value used to identify this row in the 
        xcmPrtInputAliasTable."
    ::= { xcmPrtInputAliasEntry 1 }
xcmPrtInputAliasRowStatus OBJECT-TYPE
    SYNTAX      RowStatus
    MAX-ACCESS  read-create
    STATUS      current
    DESCRIPTION "
        Manages the status of this conceptual row in the
        xcmPrtInputAliasTable."
    ::= { xcmPrtInputAliasEntry 2 }
xcmPrtInputAliasName OBJECT-TYPE
    SYNTAX      XcmFixedLocaleDisplayString (SIZE(0..63))
    MAX-ACCESS  read-create
    STATUS      current
    DESCRIPTION "
        Defines an alternate name for the input source.  This is in
        addition to the prtInputName from the Input Group.  Typical
        usage is to map an interpreter specific name to the sub-unit
        name in the Input Group, e.g., PCL's 'upper' to the device
        input name 'main'."
    DEFVAL { ''H } 
    ::= { xcmPrtInputAliasEntry 3 }
xcmPrtInputAliasSwitchProgram OBJECT-TYPE
    SYNTAX      DisplayString (SIZE(0..255))
    MAX-ACCESS  read-create
    STATUS      current
    DESCRIPTION "
        The input tray switching program for this 'InputAliasName'
        presented in a '.' separated list of prtInputIndex values.
        For example, the string '1.4.3' indicates start with the
        input tray represented by prtInputIndex 1, if it becomes
        empty switch to prtInputIndex 4, when it becomes empty
        switch to prtInputIndex 3, if it becomes empty then wait
        for operator intervention.
        An empty string shall indicate unspecified."
    DEFVAL { ''H } 
    ::= { xcmPrtInputAliasEntry 4 }
--
--
--
xcmPrtInterpPCLTable OBJECT-TYPE
    SYNTAX      SEQUENCE OF XcmPrtInterpPCLEntry
    MAX-ACCESS  not-accessible
    STATUS      current
    DESCRIPTION "
        This table is an extension to the prtInterpPCLTable."
    ::= { xcmPrtInterpPCL 1 }
xcmPrtInterpPCLEntry OBJECT-TYPE
    SYNTAX      XcmPrtInterpPCLEntry
    MAX-ACCESS  not-accessible
    STATUS      current        
    DESCRIPTION "
        An entry exists corresponding to each entry in the
        xcmPrtInterpPCLTable."
    INDEX       { hrDeviceIndex, prtInterpreterIndex }
    ::= { xcmPrtInterpPCLTable 1 }
XcmPrtInterpPCLEntry ::= SEQUENCE {
    xcmPrtInterpPCLRowStatus         RowStatus,
    xcmPrtInterpPCLFontSourceDflt    XcmPrtPCLFontSource,
    xcmPrtInterpPCLFontNumberDflt    Cardinal32,
    xcmPrtInterpPCLPitchNumerator    Cardinal32,
    xcmPrtInterpPCLPitchDenominator  Cardinal32,
    xcmPrtInterpPCLPtSizeNumerator   Cardinal32,
    xcmPrtInterpPCLPtSizeDenominatr  Cardinal32,
    xcmPrtInterpPCLPrintScreen    XcmPrtPrintScreen
    }
xcmPrtInterpPCLRowStatus OBJECT-TYPE
    SYNTAX      RowStatus
    MAX-ACCESS  read-create
    STATUS      current
    DESCRIPTION "
        Manages the status of this conceptual row in the
        xcmPrtInterpPCLTable."
    ::= { xcmPrtInterpPCLEntry 1 }
xcmPrtInterpPCLFontSourceDflt OBJECT-TYPE
    SYNTAX      XcmPrtPCLFontSource
    MAX-ACCESS  read-create
    STATUS      current
    DESCRIPTION "
        This object provides the PCL-specific PJL variable 'FONTSOURCE'.
        'FONTSOURCE' specifies the device location of the default font
        in PCL."
    REFERENCE "
        See: PJL Technical Reference Manual- FONTSOURCE"
    DEFVAL { notSpecified }
    ::= { xcmPrtInterpPCLEntry 2 }
xcmPrtInterpPCLFontNumberDflt OBJECT-TYPE
    SYNTAX      Cardinal32
    MAX-ACCESS  read-create
    STATUS      current
    DESCRIPTION "
        This object provides the PCL-specific PJL variable 'FONTNUMBER'.
        In PCL, 'FONTNUMBER' specifies the ID of the default font within
        the default FONTSOURCE."
    REFERENCE "
        See: PJL Technical Reference Manual - FONTNUMBER"
    DEFVAL { 0 } 
    ::= { xcmPrtInterpPCLEntry 3 }
xcmPrtInterpPCLPitchNumerator OBJECT-TYPE
    SYNTAX      Cardinal32
    MAX-ACCESS  read-create
    STATUS      current
    DESCRIPTION "
        This object along with xcmPrtInterpPCLPitchDenominator sets 
        the default for the PCL-specific PJL variable  'PITCH.
        These two object sets the default pitch size for the PCL default
        font defined in xcmPrtInterpreterPCLFontNumberDflt.
        This variable only applies when the default font specified is
        a scalable fixed pitch font.
        A value of zero shall mean not specified."
    REFERENCE "
        See: PCL 5 Printer Language Technical Reference Manual
        See: PJL Technical Reference Manual - PITCH
        See: xcmPrtInterpPCLPitchDenominator"
    DEFVAL { 0 } 
    ::= { xcmPrtInterpPCLEntry 4 }
xcmPrtInterpPCLPitchDenominator OBJECT-TYPE
    SYNTAX      Cardinal32
    MAX-ACCESS  read-create
    STATUS      current
    DESCRIPTION "
        This object along with xcmPrtInterpPCLPitchNumerator sets 
        the default for the PCL-specific PJL variable 'PITCH'.
        These two object sets the default pitch size for the PCL default
        font defined in xcmPrtInterpreterPCLFontNumberDflt.
        The PITCH variable only applies when the default font specified
        is a scalable fixed pitch font.
        A value of zero shall mean not specified.
        It is expected that a typical application will set 
        xcmPrtInterpPCLPitchDenominator to 100."
    REFERENCE "
        See: PCL 5 Printer Language Technical Reference Manual
        See: PJL Technical Reference Manual - PITCH
        See: xcmPrtInterpPCLPitchNumerator"
    DEFVAL { 100 }
    ::= { xcmPrtInterpPCLEntry 5 }
xcmPrtInterpPCLPtSizeNumerator OBJECT-TYPE
    SYNTAX      Cardinal32
    MAX-ACCESS  read-create
    STATUS      current
    DESCRIPTION "
        This object along with xcmPrtInterpPCLPtSizeDenominatr sets the
        default for the PCL-specific PJL variable 'PTSIZE'.
        The PTSIZE variable only applies when the FONTNUMBER setting
        specifies a scalable proportionally-spaced font.
        The size is in units of printer's points, which units are here
        considered to be exactly 1/72 of an inch.
        The value zero shall mean not specified."
    REFERENCE "
        See: PJL Technical Reference Manual - PTSIZE
        See: PCL 5 Printer Language Technical Reference Manual
        See: xcmPrtInterpPCLPtSizeDenominatr"
    DEFVAL { 0 } 
    ::= { xcmPrtInterpPCLEntry 6 }
xcmPrtInterpPCLPtSizeDenominatr OBJECT-TYPE
    SYNTAX      Cardinal32
    MAX-ACCESS  read-create
    STATUS      current
    DESCRIPTION "
        This object along with xcmPrtInterpPCLPtSizeNumerator sets the
        default for the PCL-specific PJL variable 'PTSIZE'.
        The PTSIZE variable only applies when the FONTNUMBER setting
        specifies a scalable proportionally-spaced font.
        The value zero shall mean not specified.
        It is expected that a typical application will set this object
        to the value 4.  For example, if the denominator is set to 4,
        describe a PtSize of 8.5, xcmPrtInterpPCLPtSizeNominator must
        be set to 34."
    REFERENCE "
        See: PCL 5 Printer Language Technical Reference Manual
        See: PJL Technical Reference Manual - PTSIZE
        See: xcmPrtInterpPCLPtSizeNumerator"
    DEFVAL { 4 } 
    ::= { xcmPrtInterpPCLEntry 7 }
--
--
xcmPrtInterpPCLPrintScreen OBJECT-TYPE
    SYNTAX      XcmPrtPrintScreen
    MAX-ACCESS  read-create
    STATUS      current
    DESCRIPTION "
        This object sets a special mode for 80 character screen dumps."
    DEFVAL { off }
    ::= { xcmPrtInterpPCLEntry 50 }
--
xcmPrtAuxPackageTable OBJECT-TYPE
    SYNTAX      SEQUENCE OF XcmPrtAuxPackageEntry
    MAX-ACCESS  not-accessible
    STATUS      current
    DESCRIPTION "
        This table lists Auxiliary Sheets enabled for this printer."
    ::= { xcmPrtAuxPackage 1 }
xcmPrtAuxPackageEntry OBJECT-TYPE
    SYNTAX      XcmPrtAuxPackageEntry
    MAX-ACCESS  not-accessible
    STATUS      current        
    DESCRIPTION "
        An entry exists corresponding to each entry in the
        xcmPrtAuxPackageTable."
    INDEX       { hrDeviceIndex, xcmPrtAuxPackageIndex }
    ::= { xcmPrtAuxPackageTable 1 }
XcmPrtAuxPackageEntry ::= SEQUENCE {
    xcmPrtAuxPackageIndex             Cardinal32,
    xcmPrtAuxPackageRowStatus         RowStatus,
    xcmPrtAuxPackageType              XcmPrtAuxSheetType,
    xcmPrtAuxPackageContent           XcmPrtAuxSheetContent,
    xcmPrtAuxPackagePrtInputIndex     Cardinal32,
    xcmPrtAuxPackageNext              Cardinal32
    }
xcmPrtAuxPackageIndex OBJECT-TYPE
    SYNTAX      Cardinal32
    MAX-ACCESS  not-accessible
    STATUS      current
    DESCRIPTION "
        A unique value used by the printer to identify this
        Auxiliary Sheet."
    ::= { xcmPrtAuxPackageEntry 1 }
xcmPrtAuxPackageRowStatus OBJECT-TYPE
    SYNTAX      RowStatus
    MAX-ACCESS  read-create
    STATUS      current
    DESCRIPTION "
        Manages the status of this conceptual row in the
        xcmPrtAuxPackageTable."
    ::= { xcmPrtAuxPackageEntry 2 }
xcmPrtAuxPackageType OBJECT-TYPE
    SYNTAX      XcmPrtAuxSheetType
    MAX-ACCESS  read-create
    STATUS      current
    DESCRIPTION "
        Specifies the Auxiliary Sheet type associated with this row.
        Note: DEFVAL commented out due to the negative enum
        definition in 15prtxtc being illegal in strict SMIv1
        (see section 3.2.1.1 of RFC 1155)."
    ::= { xcmPrtAuxPackageEntry 3 }
xcmPrtAuxPackageContent OBJECT-TYPE
    SYNTAX      XcmPrtAuxSheetContent
    MAX-ACCESS  read-create
    STATUS      current
    DESCRIPTION "
        Specifies the information content of this auxiliary sheet.
    The value zero shall mean notSpecified."
    DEFVAL { notSpecified }
    ::= { xcmPrtAuxPackageEntry 4 }
xcmPrtAuxPackagePrtInputIndex OBJECT-TYPE
    SYNTAX      Cardinal32
    MAX-ACCESS  read-create
    STATUS      current
    DESCRIPTION "
        Specifies the input tray the printer shall use in
        printing this auxiliary sheet.
    The value zero shall mean notSpecified."
    DEFVAL { 0 } 
    ::= { xcmPrtAuxPackageEntry 5 }
xcmPrtAuxPackageNext OBJECT-TYPE
    SYNTAX      Cardinal32
    MAX-ACCESS  read-create
    STATUS      current
    DESCRIPTION "
        Provides the index of the next Auxiliary Sheet
        declared for this printer.  This provides a linking
        mechanism to group auxiliary pages.  The last
        auxiliary page to be declared will set this
        xcmPrtAuxPackageNext object to zero, meaning no further
        sheets.
        The value zero shall mean notPresent."
    DEFVAL { 0 } 
    ::= { xcmPrtAuxPackageEntry 6 }
--
--
--
xcmPrtMedmTypeSupTable OBJECT-TYPE
    SYNTAX      SEQUENCE OF XcmPrtMedmTypeSupEntry
    MAX-ACCESS  not-accessible
    STATUS      current
    DESCRIPTION "
        A table of specific and general medium 'types' which are
        associated with this host system."
    ::= { xcmPrtMediumTypeSupported 2 }
xcmPrtMedmTypeSupEntry OBJECT-TYPE
    SYNTAX      XcmPrtMedmTypeSupEntry
    MAX-ACCESS  not-accessible
    STATUS      current
    DESCRIPTION "
        An entry for a specific or general medium 'types' which
        is associated with this host system."
    INDEX       { hrDeviceIndex, xcmPrtMedmTypeSupIndex }
    ::= { xcmPrtMedmTypeSupTable 1 }
XcmPrtMedmTypeSupEntry ::= SEQUENCE {
    xcmPrtMedmTypeSupIndex          Ordinal32,
    xcmPrtMedmTypeSupRowStatus      RowStatus,
    xcmPrtMedmTypeSupRowPersistence XcmGenRowPersistence,
    xcmPrtMedmTypeSupName
                XcmFixedLocaleDisplayString (SIZE(0..255)),
    xcmPrtMedmTypeSupFuserTemp      Integer32,
    xcmPrtMedmTypeSupPaperType      OCTET STRING(SIZE(0..255)),
    xcmPrtMedmTypeSupPDLString      OCTET STRING(SIZE(0..255)),
    xcmPrtMedmTypeSupFuserHide      TruthValue
    }
xcmPrtMedmTypeSupIndex OBJECT-TYPE
    SYNTAX      Ordinal32
    MAX-ACCESS  not-accessible
    STATUS      current
    DESCRIPTION "
        A unique value used to identify this medium type supported."
    ::= { xcmPrtMedmTypeSupEntry 1 }
xcmPrtMedmTypeSupRowStatus OBJECT-TYPE
    SYNTAX      RowStatus
    MAX-ACCESS  read-create
    STATUS      current
    DESCRIPTION "
        Manages the status of this conceptual row in the 
        'xcmPrtMedmTypeSupTable'."
    ::= { xcmPrtMedmTypeSupEntry 2 }
xcmPrtMedmTypeSupRowPersistence OBJECT-TYPE
    SYNTAX      XcmGenRowPersistence
    MAX-ACCESS  read-create
    STATUS      current
    DESCRIPTION "
        Indicates persistence of this row, from the given enumeration."
    DEFVAL { unknown }
    ::= { xcmPrtMedmTypeSupEntry 3 }
xcmPrtMedmTypeSupName OBJECT-TYPE
    SYNTAX      XcmFixedLocaleDisplayString (SIZE (0..255))
    MAX-ACCESS  read-create
    STATUS      current
    DESCRIPTION "
        Named 'type' of this medium instance. This can be the name of 
        the media type provided by a user."
    REFERENCE   "
        See: prtInputMediaType"
    DEFVAL { ''H }
    ::= { xcmPrtMedmTypeSupEntry 4 }
xcmPrtMedmTypeSupFuserTemp OBJECT-TYPE
    SYNTAX      Integer32
    MAX-ACCESS  read-create
    STATUS      current
    DESCRIPTION "
        Indicates the relative fuser temperature for this medium type.
        The range is 1 - 100.  A value to '50' indciates the 'normal'
        fuser temperature.  Values higher than 50 indicate higher fuser
        temperatures.  Values lower than 50 indicate lower fuser
        temperatures.
        The value to use is device specific."
    DEFVAL { 50 }
    ::= { xcmPrtMedmTypeSupEntry 5 }
xcmPrtMedmTypeSupPaperType OBJECT-TYPE
    SYNTAX      OCTET STRING (SIZE (0..255))
    MAX-ACCESS  read-create
    STATUS      current
    DESCRIPTION "
        The paper type for this xcmPrtMedmTypeSupName."
    REFERENCE   "
        See: prtInputMediaType"
    DEFVAL { ''H }
    ::= { xcmPrtMedmTypeSupEntry 6 }
xcmPrtMedmTypeSupPDLString OBJECT-TYPE
    SYNTAX      OCTET STRING (SIZE (0..255))
    MAX-ACCESS  read-create
    STATUS      current
    DESCRIPTION "
        The string used in the print stream for this 
         xcmPrtMedmTypeSupName."
    REFERENCE   "
        See: prtInputMediaType"
    DEFVAL { ''H }
    ::= { xcmPrtMedmTypeSupEntry 7 }
xcmPrtMedmTypeSupFuserHide OBJECT-TYPE
    SYNTAX      TruthValue
    MAX-ACCESS  read-create
    STATUS      current
    DESCRIPTION "
        Indicates if the custom type has to be hidden in host drivers. 
        True means the media type is not displayed. 
        False means the media type can be selected for a print job"
    DEFVAL { false }
    ::= { xcmPrtMedmTypeSupEntry 8 }
--
--
xcmPrtMIBConformance OBJECT IDENTIFIER ::= { xcmPrintMIB 2 }
--
--
xcmPrtMIBCompliance MODULE-COMPLIANCE
    STATUS      current
    DESCRIPTION "
        The compliance statement for agents that implement the
        printer MIB extension module."
    MODULE 
    MANDATORY-GROUPS { xcmPrtBaseGroup }
    --
    --
    GROUP       xcmPrtGeneralGroup
    DESCRIPTION "
        Implementation of this group is conditionally mandatory."
    GROUP       xcmPrtGeneralAuxSheetGroup
    DESCRIPTION "
        Implementation of this group is conditionally mandatory."
    GROUP       xcmPrtGeneralProdSpecificGroup
    DESCRIPTION "
        Implementation of this group is conditionally mandatory."
    GROUP       xcmPrtInputGroup
    DESCRIPTION "
        Implementation of this group is conditionally mandatory."
    GROUP       xcmPrtOutputGroup
    DESCRIPTION "
        Implementation of this group is conditionally mandatory."
    GROUP       xcmPrtOutputFinishingGroup
    DESCRIPTION "
        Implementation of this group is conditionally mandatory."
    GROUP       xcmPrtChannelGroup
    DESCRIPTION "
        Implementation of this group is conditionally mandatory."
    GROUP       xcmPrtChannelProdSpecificGroup
    DESCRIPTION "
        Implementation of this group is optional."
    GROUP       xcmPrtInterpreterGroup
    DESCRIPTION "
        Implementation of this group is conditionally mandatory."
    GROUP       xcmPrtInterpProdSpecificGroup
    DESCRIPTION "
        Implementation of this group is conditionally mandatory."
    GROUP       xcmPrtInputAliasGroup
    DESCRIPTION "
        Implementation of this group is conditionally mandatory."
    GROUP       xcmPrtAuxPackageGroup
    DESCRIPTION "
        Implementation of this group is conditionally mandatory."
    GROUP       xcmPrtMediumTypeSupportedGroup
    DESCRIPTION "
        Implementation of this group is conditionally mandatory."
    GROUP       xcmPrtInterpPCLGroup
    DESCRIPTION "
        Implementation of this group is conditionally mandatory."
    GROUP       xcmPrtInterpPCLProdSpecificGroup
    DESCRIPTION "
        Implementation of this group is conditionally mandatory."
    --
    --
    OBJECT      xcmPrtBaseRowStatus
    SYNTAX      INTEGER { active(1) }  
    DESCRIPTION "
        It is conformant to implement this object as read-only, and
        only one of the enumerated values for the 'RowStatus' textual
        convention need be supported, specifically:  active(1)."
    --
    --
    OBJECT      xcmPrtGeneralRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtGeneralAuxSheetPackage 
    MIN-ACCESS  read-only
    DESCRIPTION "It is conformant to implement this object read-only."
    OBJECT      xcmPrtGeneralManualFeedTimeout
    MIN-ACCESS  read-only
    DESCRIPTION "It is conformant to implement this object read-only."
    OBJECT      xcmPrtGeneralInputAutoSwitch
    MIN-ACCESS  read-only
    DESCRIPTION "It is conformant to implement this object read-only."
    OBJECT      xcmPrtGeneralOutputAutoSwitch
    MIN-ACCESS  read-only
    DESCRIPTION "It is conformant to implement this object read-only."
    OBJECT      xcmPrtGeneralMediumClassDefault
    MIN-ACCESS  read-only
    DESCRIPTION "It is conformant to implement this object read-only."
    OBJECT      xcmPrtGeneralDarknessLevels
    MIN-ACCESS  read-only
    DESCRIPTION "It is conformant to implement this object read-only."
    OBJECT      xcmPrtGeneralDarknessLevelNorm
    MIN-ACCESS  read-only
    DESCRIPTION "It is conformant to implement this object read-only."
    OBJECT      xcmPrtGeneralDarknessLevelDflt
    MIN-ACCESS  read-only
    DESCRIPTION "It is conformant to implement this object read-only."
    OBJECT      xcmPrtGeneralHexDumpEnable
    MIN-ACCESS  read-only
    DESCRIPTION "It is conformant to implement this object read-only."
    OBJECT      xcmPrtGeneralTonerLowStop
    MIN-ACCESS  read-only
    DESCRIPTION "It is conformant to implement this object read-only."
    --
    --
    OBJECT      xcmPrtGeneralStartupPage
    MIN-ACCESS  read-only
    DESCRIPTION "It is conformant to implement this object read-only."
    OBJECT      xcmPrtGeneralBannerPage
    MIN-ACCESS  read-only
    DESCRIPTION "It is conformant to implement this object read-only."
    OBJECT      xcmPrtGeneralEndBannerPage
    MIN-ACCESS  read-only
    DESCRIPTION "It is conformant to implement this object read-only."
    OBJECT      xcmPrtGeneralTrayLowWarning 
    MIN-ACCESS  read-only
    DESCRIPTION "It is conformant to implement this object read-only."
    --
    --
    OBJECT      xcmPrtGeneralScanlineCompaction
    MIN-ACCESS  read-only
    DESCRIPTION "It is conformant to implement this object read-only."
    OBJECT      xcmPrtGeneralMonoPrintOptimization 
    MIN-ACCESS  read-only
    DESCRIPTION "It is conformant to implement this object read-only."
    --
    --
    OBJECT      xcmPrtInputRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtInputNextPrtInputIndex
    MIN-ACCESS  read-only
    DESCRIPTION "It is conformant to implement this object read-only."
    --
    --
    OBJECT      xcmPrtOutputRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtOutputNextIndex
    MIN-ACCESS  read-only
    DESCRIPTION "It is conformant to implement this object read-only."
    OBJECT      xcmPrtOutputPassword
    SYNTAX      OCTET STRING (SIZE(0..16))
    MIN-ACCESS  read-only
    DESCRIPTION "It is conformant to implement this object read-only."
    OBJECT      xcmPrtOutputOffsetStackingType
    MIN-ACCESS  read-only
    DESCRIPTION "It is conformant to implement this object read-only."
    OBJECT      xcmPrtOutputTrayTimeoutSupport
    MIN-ACCESS  read-only
    DESCRIPTION "It is conformant to implement this object read-only."
    OBJECT      xcmPrtOutputTrayTimeout
    MIN-ACCESS  read-only
    DESCRIPTION "It is conformant to implement this object read-only."
    --
    --
    OBJECT      xcmPrtOutputStaple
    MIN-ACCESS  read-only
    DESCRIPTION "It is conformant to implement this object read-only."
    OBJECT      xcmPrtOutputStaplePosSupported
    MIN-ACCESS  read-only
    DESCRIPTION "It is conformant to implement this object read-only."
    OBJECT      xcmPrtOutputStapleDefault
    MIN-ACCESS  read-only
    DESCRIPTION "It is conformant to implement this object read-only."
    OBJECT      xcmPrtOutputStaplePosDefault
    MIN-ACCESS  read-only
    DESCRIPTION "It is conformant to implement this object read-only."
    OBJECT      xcmPrtOutputPunch
    MIN-ACCESS  read-only
    DESCRIPTION "It is conformant to implement this object read-only."
    OBJECT      xcmPrtOutputPunchDefault
    MIN-ACCESS  read-only
    DESCRIPTION "It is conformant to implement this object read-only."
    OBJECT      xcmPrtOutputPunchPosSupported  
    MIN-ACCESS  read-only
    DESCRIPTION "It is conformant to implement this object read-only."
    OBJECT      xcmPrtOutputBookletFoldStaple
    MIN-ACCESS  read-only
    DESCRIPTION "It is conformant to implement this object read-only."
    --
    --
    OBJECT      xcmPrtChannelRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtChannelEOJTimeout
    MIN-ACCESS  read-only
    DESCRIPTION "It is conformant to implement this object read-only."
    OBJECT      xcmPrtChannelAuxSheetPackage
    MIN-ACCESS  read-only
    DESCRIPTION "It is conformant to implement this object read-only."
    OBJECT      xcmPrtChannelSpoolingEnable
    MIN-ACCESS  read-only
    DESCRIPTION "It is conformant to implement this object read-only."
    OBJECT      xcmPrtChannelLangSensing
    MIN-ACCESS  read-only
    DESCRIPTION "It is conformant to implement this object read-only."
    OBJECT      xcmPrtChannelBinaryPostScript
    MIN-ACCESS  read-only
    DESCRIPTION "It is conformant to implement this object read-only."
    --
    --
    OBJECT      xcmPrtChannelAutoJobEnd
    MIN-ACCESS  read-only
    DESCRIPTION "It is conformant to implement this object read-only."
    OBJECT      xcmPrtChannelBinaryPostScriptZ
    MIN-ACCESS  read-only
    DESCRIPTION "It is conformant to implement this object read-only."
    --
    --
    OBJECT      xcmPrtInterpRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtInterpAuxSheetPackage
    MIN-ACCESS  read-only
    DESCRIPTION "It is conformant to implement this object read-only."
    OBJECT      xcmPrtInterpContextSaving
    MIN-ACCESS  read-only
    DESCRIPTION "It is conformant to implement this object read-only."
    OBJECT      xcmPrtInterpEdgeEnhancement
    MIN-ACCESS  read-only
    DESCRIPTION "It is conformant to implement this object read-only."
    OBJECT      xcmPrtInterpFontIndexDefault
    MIN-ACCESS  read-only
    DESCRIPTION "It is conformant to implement this object read-only."
    OBJECT      xcmPrtInterpGrayLevels
    MIN-ACCESS  read-only
    DESCRIPTION "It is conformant to implement this object read-only."
    OBJECT      xcmPrtInterpGrayLevelDefault
    MIN-ACCESS  read-only
    DESCRIPTION "It is conformant to implement this object read-only."
    OBJECT      xcmPrtInterpJamRecovery
    MIN-ACCESS  read-only
    DESCRIPTION "It is conformant to implement this object read-only."
    OBJECT      xcmPrtInterpJobCopiesDefault
    MIN-ACCESS  read-only
    DESCRIPTION "It is conformant to implement this object read-only."
    OBJECT      xcmPrtInterpLineWrap
    MIN-ACCESS  read-only
    DESCRIPTION "It is conformant to implement this object read-only."
    OBJECT      xcmPrtInterpMediumSizeDefault
    MIN-ACCESS  read-only
    DESCRIPTION "It is conformant to implement this object read-only."
    OBJECT      xcmPrtInterpPageProtect
    MIN-ACCESS  read-only
    DESCRIPTION "It is conformant to implement this object read-only."
    OBJECT      xcmPrtInterpPageProtectSize
    MIN-ACCESS  read-only
    DESCRIPTION "It is conformant to implement this object read-only."
    OBJECT      xcmPrtInterpPageSizeErrorPolicy
    MIN-ACCESS  read-only
    DESCRIPTION "It is conformant to implement this object read-only."
    OBJECT      xcmPrtInterpPlexSupported
    MIN-ACCESS  read-only
    DESCRIPTION "It is conformant to implement this object read-only."
    OBJECT      xcmPrtInterpPlexDefault
    MIN-ACCESS  read-only
    DESCRIPTION "It is conformant to implement this object read-only."
    OBJECT      xcmPrtInterpPrintEdgeToEdge
    MIN-ACCESS  read-only
    DESCRIPTION "It is conformant to implement this object read-only."
    OBJECT      xcmPrtInterpPrintQuality
    MIN-ACCESS  read-only
    DESCRIPTION "It is conformant to implement this object read-only."
    OBJECT      xcmPrtInterpPrtInputIndexDflt
    MIN-ACCESS  read-only
    DESCRIPTION "It is conformant to implement this object read-only."
    OBJECT      xcmPrtInterpPrtOutputIndexDflt
    MIN-ACCESS  read-only
    DESCRIPTION "It is conformant to implement this object read-only."
    OBJECT      xcmPrtInterpResFeedDirDefault
    MIN-ACCESS  read-only
    DESCRIPTION "It is conformant to implement this object read-only."
    OBJECT      xcmPrtInterpResXFeedDirDefault
    MIN-ACCESS  read-only
    DESCRIPTION "It is conformant to implement this object read-only."
    OBJECT      xcmPrtInterpResIPResIndex
    MIN-ACCESS  read-only
    DESCRIPTION "It is conformant to implement this object read-only."
    OBJECT      xcmPrtInterpResIPResIndexDflt
    MIN-ACCESS  read-only
    DESCRIPTION "It is conformant to implement this object read-only."
    OBJECT      xcmPrtInterpTextFormLength
    MIN-ACCESS  read-only
    DESCRIPTION "It is conformant to implement this object read-only."
    OBJECT      xcmPrtInterpTimeoutJob
    MIN-ACCESS  read-only
    DESCRIPTION "It is conformant to implement this object read-only."
    OBJECT      xcmPrtInterpTimeoutPage
    MIN-ACCESS  read-only
    DESCRIPTION "It is conformant to implement this object read-only."
    OBJECT      xcmPrtInterpInputAliasIndexDflt
    MIN-ACCESS  read-only
    DESCRIPTION "It is conformant to implement this object read-only."
    OBJECT      xcmPrtInterpTraySwitch
    MIN-ACCESS  read-only
    DESCRIPTION "It is conformant to implement this object read-only."
    OBJECT      xcmPrtInterpMediumTypeDefault
    SYNTAX      XcmFixedLocaleDisplayString (SIZE(0..16))
    MIN-ACCESS  read-only
    DESCRIPTION "It is conformant to implement this object read-only."
    OBJECT      xcmPrtInterpMediaTypeErrPolicy
    MIN-ACCESS  read-only
    DESCRIPTION "It is conformant to implement this object read-only."
    OBJECT      xcmPrtInterpErrorPolicyTimeout
    MIN-ACCESS  read-only
    DESCRIPTION "It is conformant to implement this object read-only."
    OBJECT      xcmPrtInterpLineTerm
    MIN-ACCESS  read-only
    DESCRIPTION "It is conformant to implement this object read-only."
    OBJECT      xcmPrtInterpEnhancedResolution
    MIN-ACCESS  read-only
    DESCRIPTION "It is conformant to implement this object read-only."
    --
    --
    OBJECT      xcmPrtInterpAutoContinue
    MIN-ACCESS  read-only
    DESCRIPTION "It is conformant to implement this object read-only."
    OBJECT      xcmPrtInterpEnvFeederSize
    MIN-ACCESS  read-only
    DESCRIPTION "It is conformant to implement this object read-only."
    OBJECT      xcmPrtInterpManualFeedPgSize
    MIN-ACCESS  read-only
    DESCRIPTION "It is conformant to implement this object read-only."
    OBJECT      xcmPrtInterpOffsetStackingType
    MIN-ACCESS  read-only
    DESCRIPTION "It is conformant to implement this object read-only."
    OBJECT      xcmPrtInterpProcessBarcodes
    MIN-ACCESS  read-only
    DESCRIPTION "It is conformant to implement this object read-only."
    --
    --
    OBJECT      xcmPrtInputAliasRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtInputAliasName
    MIN-ACCESS  read-only
    DESCRIPTION "It is conformant to implement this object read-only."
    OBJECT      xcmPrtInputAliasSwitchProgram
    MIN-ACCESS  read-only
    DESCRIPTION "It is conformant to implement this object read-only."
    --
    --
    OBJECT      xcmPrtInterpPCLRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtInterpPCLFontSourceDflt
    MIN-ACCESS  read-only
    DESCRIPTION "It is conformant to implement this object read-only."
    OBJECT      xcmPrtInterpPCLFontNumberDflt
    MIN-ACCESS  read-only
    DESCRIPTION "It is conformant to implement this object read-only."
    OBJECT      xcmPrtInterpPCLPitchNumerator
    MIN-ACCESS  read-only
    DESCRIPTION "It is conformant to implement this object read-only."
    OBJECT      xcmPrtInterpPCLPitchDenominator
    MIN-ACCESS  read-only
    DESCRIPTION "It is conformant to implement this object read-only."
    OBJECT      xcmPrtInterpPCLPtSizeNumerator
    MIN-ACCESS  read-only
    DESCRIPTION "It is conformant to implement this object read-only."
    OBJECT      xcmPrtInterpPCLPtSizeDenominatr
    MIN-ACCESS  read-only
    DESCRIPTION "It is conformant to implement this object read-only."
    --
    --
    OBJECT      xcmPrtInterpPCLPrintScreen
    MIN-ACCESS  read-only
    DESCRIPTION "It is conformant to implement this object read-only."
    --
    --
    OBJECT      xcmPrtAuxPackageRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtAuxPackageType
    MIN-ACCESS  read-only
    DESCRIPTION "It is conformant to implement this object read-only."
    OBJECT      xcmPrtAuxPackageContent
    MIN-ACCESS  read-only
    DESCRIPTION "It is conformant to implement this object read-only."
    OBJECT      xcmPrtAuxPackagePrtInputIndex
    MIN-ACCESS  read-only
    DESCRIPTION "It is conformant to implement this object read-only."
    OBJECT      xcmPrtAuxPackageNext
    MIN-ACCESS  read-only
    DESCRIPTION "It is conformant to implement this object read-only."
    --
    --
    OBJECT      xcmPrtMedmTypeSupRowStatus
    SYNTAX      INTEGER { active(1) }  
    MIN-ACCESS  read-only
    DESCRIPTION "
        It is conformant to implement this object as read-only, and
        only one of the enumerated values for the 'RowStatus' textual
        convention need be supported, specifically:  active(1)."
    OBJECT      xcmPrtMedmTypeSupRowPersistence
    MIN-ACCESS  read-only
    DESCRIPTION "It is conformant to implement this object read-only."
    OBJECT      xcmPrtMedmTypeSupName
    SYNTAX      XcmFixedLocaleDisplayString (SIZE(0..16))
    MIN-ACCESS  read-only
    DESCRIPTION "
        It is conformant to implement this object read-only
        and with a reduced string length."
    OBJECT      xcmPrtMedmTypeSupFuserTemp
    MIN-ACCESS  read-only
    DESCRIPTION "It is conformant to implement this object read-only."
    OBJECT      xcmPrtMedmTypeSupPaperType
    MIN-ACCESS  read-only
    DESCRIPTION "It is conformant to implement this object read-only."
    OBJECT      xcmPrtMedmTypeSupPDLString
    MIN-ACCESS  read-only
    DESCRIPTION "It is conformant to implement this object read-only."
    OBJECT      xcmPrtMedmTypeSupFuserHide
    MIN-ACCESS  read-only
    DESCRIPTION "It is conformant to implement this object read-only."
    ::= { xcmPrtMIBConformance 1 }
xcmPrtMIBGroups OBJECT IDENTIFIER ::= { xcmPrtMIBConformance 2 }
xcmPrtBaseGroup OBJECT-GROUP
    OBJECTS {   xcmPrtBaseRowStatus,
                xcmPrtBaseGroupSupport,
                xcmPrtBaseUpdateSupport,
                xcmPrtBaseCreateSupport,
                xcmPrtBaseIETFMIBGroupSupport,
                xcmPrtBaseIETFMIBUpdateSupport,
                xcmPrtBaseIETFMIBCreateSupport
                }
    STATUS      current
    DESCRIPTION "
        The general printer group extension."
    ::= { xcmPrtMIBGroups 1 }
xcmPrtGeneralGroup OBJECT-GROUP
    OBJECTS {   xcmPrtGeneralRowStatus,
                xcmPrtGeneralAuxSheetPackage,
                xcmPrtGeneralManualFeedTimeout,
                xcmPrtGeneralInputAutoSwitch,
                xcmPrtGeneralOutputAutoSwitch,
                xcmPrtGeneralMediumClassDefault,
                xcmPrtGeneralDarknessLevels,
                xcmPrtGeneralDarknessLevelNorm,
                xcmPrtGeneralDarknessLevelDflt,
                xcmPrtGeneralHexDumpEnable
                }
    STATUS      current
    DESCRIPTION "
        The general printer group extension."
    ::= { xcmPrtMIBGroups 5 }
xcmPrtDriverOptionsGroup OBJECT-GROUP
    OBJECTS {   xcmPrtDrvrHwdOptStapler,
                xcmPrtDrvrHwdOptDuplexUnit,
                xcmPrtDrvrHwdOptPhaserBookletMaker,
                xcmPrtDrvrHwdOptEnvelopeTray,
                xcmPrtDrvrHwdOptCoilPunchUnit,
                xcmPrtDrvrHwdOptFinisherDFA,
                xcmPrtDrvrHwdOptHighCapacityFeeder,
                xcmPrtDriverOutputDeliveryUnit,
                xcmPrtDrvrHwdOptHardDrive,
                xcmPrtDrvrHwdOptHolePunchUnit,
                xcmPrtDriverInputPaperTrays,
                xcmPrtDrvrHwdOptInserterUnit,
                xcmPrtDrvrHwdOptJobAccountingFdi,
                xcmPrtDrvrHwdOptFaxOut,
                xcmPrtDrvrHwdOptMemoryInMBs,
                xcmPrtDrvrHwdOptOutputBinSide,
                xcmPrtDrvrHwdOptOutputBinCenter,
                xcmPrtDrvrHwdOptPhaserModule,
                xcmPrtDrvrHwdOptPrintEngine,
                xcmPrtDrvrHwdOptSquareFoldTrimmer,
                xcmPrtDrvrHwdOptTriFold,   
                xcmPrtDrvrFntCollation,
                xcmPrtDrvrFntAsciiJobTicket,
                xcmPrtDrvrFntAuthenticationMode,
                xcmPrtDrvrFntHoldForAuthenMode,
                xcmPrtDrvrFntEnhancedImageQualityMode,
                xcmPrtDrvrFntProductivityPack,
                xcmPrtDrvrFntJobStorage,
                xcmPrtDrvrFntJobAccountingSystem
                }
    STATUS      current
    DESCRIPTION "
        The printer driver options group extension."
    ::= { xcmPrtMIBGroups 6 }
xcmPrtInputGroup OBJECT-GROUP
    OBJECTS {   xcmPrtInputRowStatus,
                xcmPrtInputNextPrtInputIndex,
                xcmPrtInputUseCustomSize,
                xcmPrtInputCustDimFeedDirDecl,
                xcmPrtInputCustDimXFeedDirDecl,
                xcmPrtInputTrayPriority
                }
    STATUS      current
    DESCRIPTION "
        The input group extension."
    ::= { xcmPrtMIBGroups 8 }
xcmPrtOutputGroup OBJECT-GROUP
    OBJECTS {   xcmPrtOutputRowStatus,
                xcmPrtOutputNextIndex,
                xcmPrtOutputPassword,
                xcmPrtOutputOffsetStackingType,
                xcmPrtOutputTrayTimeoutSupport,
                xcmPrtOutputTrayTimeout
                }
    STATUS      current
    DESCRIPTION "
        The output group extension."
    ::= { xcmPrtMIBGroups 9 }
xcmPrtChannelGroup OBJECT-GROUP
    OBJECTS {   xcmPrtChannelRowStatus, 
                xcmPrtChannelEOJTimeout,
                xcmPrtChannelAuxSheetPackage,
                xcmPrtChannelSpoolingEnable,
                xcmPrtChannelLangSensing,
                xcmPrtChannelBinaryPostScript
                }
    STATUS      current
    DESCRIPTION "
        The Channel group extension."
    ::= { xcmPrtMIBGroups 14 }
xcmPrtInterpreterGroup OBJECT-GROUP
    OBJECTS {   xcmPrtInterpRowStatus,
                xcmPrtInterpAuxSheetPackage,
                xcmPrtInterpContextSaving,
                xcmPrtInterpEdgeEnhancement,
                xcmPrtInterpFontIndexDefault, 
                xcmPrtInterpGrayLevels,
                xcmPrtInterpGrayLevelDefault,
                xcmPrtInterpJamRecovery,
                xcmPrtInterpJobCopiesDefault,
                xcmPrtInterpLineWrap,
                xcmPrtInterpMediumSizeDefault,
                xcmPrtInterpPageProtect,
                xcmPrtInterpPageProtectSize,
                xcmPrtInterpPageSizeErrorPolicy,
                xcmPrtInterpPlexSupported,
                xcmPrtInterpPlexDefault,
                xcmPrtInterpPrintEdgeToEdge,
                xcmPrtInterpPrintQuality,
                xcmPrtInterpPrtInputIndexDflt,
                xcmPrtInterpPrtOutputIndexDflt,
                xcmPrtInterpResFeedDirDefault,
                xcmPrtInterpResXFeedDirDefault,
                xcmPrtInterpResIPResIndex,
                xcmPrtInterpResIPResIndexDflt,
                xcmPrtInterpTextFormLength,
                xcmPrtInterpTimeoutJob,
                xcmPrtInterpTimeoutPage,
                xcmPrtInterpInputAliasIndexDflt,
                xcmPrtInterpTraySwitch,
                xcmPrtInterpMediumTypeDefault,
                xcmPrtInterpMediaTypeErrPolicy,
                xcmPrtInterpErrorPolicyTimeout,
                xcmPrtInterpLineTerm,
                xcmPrtInterpEnhancedResolution
                }
    STATUS      current
    DESCRIPTION "
        The interpreter group extension."
    ::= { xcmPrtMIBGroups 15 }
xcmPrtInputAliasGroup OBJECT-GROUP
    OBJECTS {   xcmPrtInputAliasRowStatus,
                xcmPrtInputAliasName,
                xcmPrtInputAliasSwitchProgram
                }
    STATUS      current
    DESCRIPTION "
        The Input Alias group."
    ::= { xcmPrtMIBGroups 50 }
xcmPrtOutputFinishingGroup OBJECT-GROUP
    OBJECTS {   xcmPrtOutputStaple,
                xcmPrtOutputStaplePosSupported,
                xcmPrtOutputStapleDefault,
                xcmPrtOutputStaplePosDefault,
                xcmPrtOutputPunch,
                xcmPrtOutputPunchDefault,
  xcmPrtOutputPunchPosSupported,
  xcmPrtOutputBookletFoldStaple
                }
    STATUS      current
    DESCRIPTION "
        The Output Finishing group."
    ::= { xcmPrtMIBGroups 51 }
xcmPrtGeneralAuxSheetGroup OBJECT-GROUP
    OBJECTS {   xcmPrtGeneralStartupPage,
                xcmPrtGeneralBannerPage,
                xcmPrtGeneralEndBannerPage,
                xcmPrtGeneralTrayLowWarning 
                }
    STATUS      current
    DESCRIPTION "
        The General Auxiliary Sheet group."
    ::= { xcmPrtMIBGroups 52 }
xcmPrtGeneralProdSpecificGroup OBJECT-GROUP
    OBJECTS {   xcmPrtGeneralScanlineCompaction,
                xcmPrtGeneralTonerLowStop,
  xcmPrtGeneralMonoPrintOptimization 
                }
    STATUS      current
    DESCRIPTION "
        The general printer product specific group."
    ::= { xcmPrtMIBGroups 55 }
xcmPrtAuxPackageGroup OBJECT-GROUP
    OBJECTS {   xcmPrtAuxPackageRowStatus,
                xcmPrtAuxPackageType,
                xcmPrtAuxPackageContent,
                xcmPrtAuxPackagePrtInputIndex,
                xcmPrtAuxPackageNext
                }
    STATUS      current
    DESCRIPTION "
        The Auxiliary Package group."
    ::= { xcmPrtMIBGroups 60 }
xcmPrtChannelProdSpecificGroup OBJECT-GROUP
    OBJECTS {   xcmPrtChannelAutoJobEnd,
                xcmPrtChannelBinaryPostScriptZ
                }
    STATUS      current
    DESCRIPTION "
        The Channel group extension for prod specific objects."
    ::= { xcmPrtMIBGroups 64 }
xcmPrtInterpProdSpecificGroup OBJECT-GROUP
    OBJECTS {   xcmPrtInterpAutoContinue,
                xcmPrtInterpOffsetStackingType,
                xcmPrtInterpEnvFeederSize,
                xcmPrtInterpManualFeedPgSize,
      xcmPrtInterpProcessBarcodes     
                }
    STATUS      current
    DESCRIPTION "
        The interpreter group extension."
    ::= { xcmPrtMIBGroups 65 }
xcmPrtInterpPCLGroup OBJECT-GROUP
    OBJECTS {   xcmPrtInterpPCLRowStatus, 
                xcmPrtInterpPCLFontSourceDflt,
                xcmPrtInterpPCLFontNumberDflt,
                xcmPrtInterpPCLPitchNumerator,
                xcmPrtInterpPCLPitchDenominator,
                xcmPrtInterpPCLPtSizeNumerator,
                xcmPrtInterpPCLPtSizeDenominatr
                }
    STATUS      current
    DESCRIPTION "
        The Interpreter PCL group."
    ::= { xcmPrtMIBGroups 70 }
xcmPrtInterpPCLProdSpecificGroup OBJECT-GROUP
    OBJECTS {   xcmPrtInterpPCLPrintScreen }
    STATUS      current
    DESCRIPTION "
        The Interpreter PCL Product Specific group."
    ::= { xcmPrtMIBGroups 71 }
xcmPrtMediumTypeSupportedGroup OBJECT-GROUP
    OBJECTS {   xcmPrtMedmTypeSupRowStatus,
                xcmPrtMedmTypeSupRowPersistence,
                xcmPrtMedmTypeSupName,
                xcmPrtMedmTypeSupFuserTemp,
                xcmPrtMedmTypeSupPaperType,
                xcmPrtMedmTypeSupPDLString,
                xcmPrtMedmTypeSupFuserHide
                }
    STATUS      current
    DESCRIPTION "
        The Medium Type Supported group."
    ::= { xcmPrtMIBGroups 75 }
xcmRsrcTC OBJECT-IDENTITY -- MODULE-IDENTITY
    STATUS   current
    DESCRIPTION "
        XCMI Document Resources MIB Textual Conventions,
        Version 5.10.pub.
        Copyright (C) 1997-2002 Xerox Corporation. All Rights Reserved."
    ::= { xeroxCommonMIB 56 }
XcmRsrcGroupSupport ::= TEXTUAL-CONVENTION
        STATUS          current
        DESCRIPTION
                "Indicators for each primary object group of the
                Document Resources MIB, used to indicate which groups
                are supported by this host system, specified by a
                bit-mask:
                    1 : xcmRsrcGeneral  
                    2 : xcmRsrcInfo   
                    4 : xcmFontInfo     
                    8 : xcmFontPCLInfo  -- 2**3 : PCL font group"
        SYNTAX  INTEGER (0..2147483647)
XcmRsrcType ::= TEXTUAL-CONVENTION
        STATUS          current
        DESCRIPTION
                "The type of this resource, from the given enumeration."
        SYNTAX  INTEGER {
                other(1),
                unknown(2),
                font(3),
                logo(4),
                form(5),
                image(6)
              }
XcmRsrcPersistence ::= TEXTUAL-CONVENTION
        STATUS          current
        DESCRIPTION
                "Describes the persistence of this resource.
                Permanent, or resident, resources are built into the
                device and cannot be removed.  They may, for example,
                be in ROM, or on hard disk with read-only access.
                (Note that HP PCL considers a resource to be 'permanent'
                if it persists across jobs, but such resources are not
                necessarily permanent by the definition used here.)
                Nonvolatile resources may be removed by appropriate
                action, but otherwise persist indefinitely, including
                across device power cycles.  They may, for example, be
                on hard disk, or in a ROM cartridge.  (The type of
                action required to remove the resource, e.g. file
                deletion or ROM cartridge removal, can generally be
                deduced from the hrStorageType of the storage device
                containing the resource.)
                Volatile resources are lost across device power cycles.
                They are typically in RAM.
                Reference: 'xcmRsrcHrStorageIndex' in this Resources
                MIB; and 'hrStorageType' in IETF Host Resources MIB
                (RFC 1514, September 1993) on page 8 (which directly
                relate to the actual level of 'persistence')."
        SYNTAX  INTEGER {
                other(1),
                unknown(2),
                volatile(3),    
                nonvolatile(4), 
                permanent(5)    
              }
XcmFontType ::= TEXTUAL-CONVENTION
        STATUS          current
        DESCRIPTION
                "The representation type or format of this font,
                from the given enumeration."
        SYNTAX  INTEGER {
                other(1),
                unknown(2),
                psType1(3),  
                psType3(4),  
                psType0(5),  
                psType42(6),  
                psCIDType0(7),  
                psCIDType1(8),  
                psCIDType2(9),  
                pclSoftFont(10),  
                pclIntellifont(11),  
                xeroxICF(12),  
                psType14(13),  -- Adobe PostScript Type 14 ("Chameleon"
                               -- font - "tunings" to a "master" font)
                psType2(14)  
               }
XcmFontSpacing ::= TEXTUAL-CONVENTION
        STATUS          current
        DESCRIPTION
                "The kind of spacing of the characters in this font,
                from the given enumeration."
        SYNTAX  INTEGER {
                other(1),
                unknown(2),
                fixedSpacing(3),
                proportionalSpacing(4)
               }
XcmFontPCLStyle ::= TEXTUAL-CONVENTION
        STATUS          current
        DESCRIPTION
                "The style of the font, from the given enumeration.
                See: 'PCL 5 Printer Language Technical Reference
                Manual' and 'PCL 5 Comparision Guide' by
                Hewlett-Packard Corporation."
        SYNTAX  INTEGER {
                other(1),
                unknown(2),
                upright(3),
                italic(4),
                condensed(5),
                condensedItalic(6),
                compressed(7),
                expanded(8),
                outline(9),
                inline(10),
                shadowed(11),
                outlineShadowed(12)
              }
XcmFontPCLStrokeWeight ::= TEXTUAL-CONVENTION
        STATUS          current
        DESCRIPTION
                "The PCL stroke weight of the font, from the given
                enumeration.
                These enumeration values are generally equal to the
                usual PCL stroke weight values + 10.
                See: 'PCL 5 Printer Language Technical Reference
                Manual' and 'PCL 5 Comparision Guide' by
                Hewlett-Packard Corporation."
        SYNTAX  INTEGER {
                other(1),
                unknown(2),
                ultraThin(3),
                extraThin(4),
                thin(5),
                extraLight(6),
                light(7),
                demiLight(8),
                semiLight(9),
                medium(10),
                semiBold(11),
                demiBold(12),
                bold(13),
                extraBold(14),
                black(15),
                extraBlack(16),
                ultraBlack(17)
              }
--
--
xCmRsrcDummy OBJECT IDENTIFIER ::= { xcmRsrcTC 999 }
xCmRsrcGroupSupport OBJECT-TYPE
    SYNTAX      XcmRsrcGroupSupport
    MAX-ACCESS  not-accessible
    STATUS      current
    DESCRIPTION "Dummy object - DO NOT USE"
    ::= { xCmRsrcDummy 1 }
xCmRsrcType OBJECT-TYPE
    SYNTAX      XcmRsrcType
    MAX-ACCESS  not-accessible
    STATUS      current
    DESCRIPTION "Dummy object - DO NOT USE"
    ::= { xCmRsrcDummy 2 }
xCmRsrcPersistence OBJECT-TYPE
    SYNTAX      XcmRsrcPersistence
    MAX-ACCESS  not-accessible
    STATUS      current
    DESCRIPTION "Dummy object - DO NOT USE"
    ::= { xCmRsrcDummy 3 }
xCmFontType OBJECT-TYPE
    SYNTAX      XcmFontType
    MAX-ACCESS  not-accessible
    STATUS      current
    DESCRIPTION "Dummy object - DO NOT USE"
    ::= { xCmRsrcDummy 4 }
xCmFontSpacing OBJECT-TYPE
    SYNTAX      XcmFontSpacing
    MAX-ACCESS  not-accessible
    STATUS      current
    DESCRIPTION "Dummy object - DO NOT USE"
    ::= { xCmRsrcDummy 5 }
xCmFontPCLStyle OBJECT-TYPE
    SYNTAX      XcmFontPCLStyle
    MAX-ACCESS  not-accessible
    STATUS      current
    DESCRIPTION "Dummy object - DO NOT USE"
    ::= { xCmRsrcDummy 6 }
xCmFontPCLStrokeWeight OBJECT-TYPE
    SYNTAX      XcmFontPCLStrokeWeight
    MAX-ACCESS  not-accessible
    STATUS      current
    DESCRIPTION "Dummy object - DO NOT USE"
    ::= { xCmRsrcDummy 7 }
xcmRsrcMIB OBJECT-IDENTITY -- MODULE-IDENTITY
    STATUS   current
    DESCRIPTION "
        XCMI Document Resources MIB,
        Version 5.12.pub.
        Copyright (C) 1997-2002 Xerox Corporation. All Rights Reserved."
    ::= { xeroxCommonMIB 57 }
--
--
xcmRsrcGeneral OBJECT IDENTIFIER ::= { xcmRsrcMIB 1 }
--
--
--
xcmRsrcGeneralTable OBJECT-TYPE
        SYNTAX          SEQUENCE OF XcmRsrcGeneralEntry
        MAX-ACCESS      not-accessible
        STATUS          current
        DESCRIPTION
                "A table of general counters and summary information for
                ease of use of the overall Document Resources MIB on
                this host system.
                This Document Resources General table has exactly one
                row, with an xcmRsrcGeneralIndex value of 1."
        ::= { xcmRsrcGeneral 1 }
xcmRsrcGeneralEntry OBJECT-TYPE
        SYNTAX          XcmRsrcGeneralEntry
        MAX-ACCESS      not-accessible
        STATUS          current
        DESCRIPTION
                "A row entry of general counters and summary information
                for ease of use of the overall Document Resources MIB on
                this host system.
                The Document Resources General table has exactly one row
                entry, with an xcmRsrcGeneralIndex value of 1."
        INDEX { xcmRsrcGeneralIndex }
        ::= { xcmRsrcGeneralTable 1 }
XcmRsrcGeneralEntry ::= SEQUENCE {
        xcmRsrcGeneralIndex             Ordinal32,
        xcmRsrcGeneralRowStatus         RowStatus,
        xcmRsrcGeneralGroupSupport      XcmRsrcGroupSupport,
        xcmRsrcGeneralCreateSupport     XcmRsrcGroupSupport,
        xcmRsrcGeneralUpdateSupport     XcmRsrcGroupSupport,
        xcmRsrcGeneralRsrcTypeAccept    OCTET STRING,
        xcmRsrcGeneralFontTypeAccept    OCTET STRING,
        xcmRsrcGeneralRsrcTypeSupport   OCTET STRING,
        xcmRsrcGeneralFontTypeSupport   OCTET STRING
        }
xcmRsrcGeneralIndex OBJECT-TYPE
        SYNTAX          Ordinal32
        MAX-ACCESS      not-accessible
        STATUS          current
        DESCRIPTION
                "An identifier of this conceptual row in the
                xcmRsrcGeneralTable.
                The xcmRsrcGeneralTable has exactly one row, with an
                xcmRsrcGeneralIndex value of 1."
        ::= { xcmRsrcGeneralEntry 1 }
xcmRsrcGeneralRowStatus OBJECT-TYPE
        SYNTAX          RowStatus
        MAX-ACCESS      read-only
        STATUS          current
        DESCRIPTION
                "Displays the status of this conceptual row in the
                xcmRsrcGeneralTable.
                The xcmRsrcGeneralTable has exactly one row, with an
                xcmRsrcGeneralIndex value of 1."
        ::= { xcmRsrcGeneralEntry 2 }
xcmRsrcGeneralGroupSupport OBJECT-TYPE
        SYNTAX          XcmRsrcGroupSupport
        MAX-ACCESS      read-only
        STATUS          current
        DESCRIPTION
                "Indicates which object groups of the Document Resources
                MIB are supported by this host system, specified in a
                bit-mask."
        DEFVAL          { 2 }   
        ::= { xcmRsrcGeneralEntry 3 }
xcmRsrcGeneralCreateSupport OBJECT-TYPE
        SYNTAX          XcmRsrcGroupSupport
        MAX-ACCESS      read-only
        STATUS          current
        DESCRIPTION
                "Indicates which object groups of the Document Resources
                MIB are supported by this host system for dynamic row
                creation (via '...RowStatus'), specified in a bit-mask."
        DEFVAL          { 0 }  
        ::= { xcmRsrcGeneralEntry 4 }
xcmRsrcGeneralUpdateSupport OBJECT-TYPE
        SYNTAX          XcmRsrcGroupSupport
        MAX-ACCESS      read-only
        STATUS          current
        DESCRIPTION
                "Indicates which object groups of the Document Resources
                MIB are supported by this host system for existing row
                update (via SNMP Set-Request PDUs), specified in a
                bit-mask."
        DEFVAL          { 0 } 
        ::= { xcmRsrcGeneralEntry 5 }
xcmRsrcGeneralRsrcTypeAccept OBJECT-TYPE
        SYNTAX          OCTET STRING (SIZE (0..32))   
        MAX-ACCESS      read-only
        STATUS          current
        DESCRIPTION
                "Indicates all of the document resource types which are
                accepted for dynamic delivery to and use by this host
                system, specified in a bit-array.
                Usage:  This bit-array is constructed from the set of
                supported values from 'XcmRsrcType', used as powers of 2
                with big-endian rules - the high-order bit of the first
                octet corresponds to a resource type of '0' (reserved)
                - the low-order bit of the first octet corresponds to a
                resource type of '7'.
                Similar to the BITS pseudotype defined in IETF SMIv2
                (RFC 2578), which has the same bit ordering rules but
                requires definitions for contiguous enumerated bits."
        REFERENCE
                "See:   'XcmRsrcType' in XCMI Document Resources TC;
                        'hrPrinterDetectedErrorState' in IETF
                            Host Resources MIB (RFC 1514/2790);
                        Section 7.1.4 'The BITS construct' in IETF
                            SMIv2 (RFC 2578);
                        Section 8 'Serialization using the BER' in IETF
                            Transport Mappings for SNMPv2 (RFC 1908)."
        ::= { xcmRsrcGeneralEntry 6 }
xcmRsrcGeneralFontTypeAccept OBJECT-TYPE
        SYNTAX          OCTET STRING (SIZE (0..64))   
        MAX-ACCESS      read-only
        STATUS          current
        DESCRIPTION
                "Indicates all of the font types which are accepted for
                dynamic delivery to and use by this host system,
                specified in a bit-array.
                Usage:  This bit-array is constructed from the set of
                supported values from 'XcmFontType', used as powers of 2
                with big-endian rules - the high-order bit of the first
                octet corresponds to a font type of '0' (reserved)
                - the low-order bit of the first octet corresponds to a
                font type of '7'.
                Similar to the BITS pseudotype defined in IETF SMIv2
                (RFC 2578), which has the same bit ordering rules but
                requires definitions for contiguous enumerated bits."
        REFERENCE
                "See:   'XcmFontType' in XCMI Document Resources TC;
                        'hrPrinterDetectedErrorState' in IETF
                            Host Resources MIB (RFC 1514/2790);
                        Section 7.1.4 'The BITS construct' in IETF
                            SMIv2 (RFC 2578);
                        Section 8 'Serialization using the BER' in IETF
                            Transport Mappings for SNMPv2 (RFC 1908)."
        ::= { xcmRsrcGeneralEntry 7 }
xcmRsrcGeneralRsrcTypeSupport OBJECT-TYPE
        SYNTAX          OCTET STRING (SIZE (0..32))   
        MAX-ACCESS      read-only
        STATUS          current
        DESCRIPTION
                "Indicates all of the document resource types which are
                supported for use by this host system, specified in a
                bit-array.
                Usage:  This bit-array is constructed from the set of
                supported values from 'XcmRsrcType', used as powers of 2
                with big-endian rules - the high-order bit of the first
                octet corresponds to a resource type of '0' (reserved)
                - the low-order bit of the first octet corresponds to a
                resource type of '7'.
                Similar to the BITS pseudotype defined in IETF SMIv2
                (RFC 2578), which has the same bit ordering rules but
                requires definitions for contiguous enumerated bits."
        REFERENCE
                "See:   'XcmRsrcType' in XCMI Document Resources TC;
                        'hrPrinterDetectedErrorState' in IETF
                            Host Resources MIB (RFC 1514/2790);
                        Section 7.1.4 'The BITS construct' in IETF
                            SMIv2 (RFC 2578);
                        Section 8 'Serialization using the BER' in IETF
                            Transport Mappings for SNMPv2 (RFC 1908)."
        ::= { xcmRsrcGeneralEntry 8 }
xcmRsrcGeneralFontTypeSupport OBJECT-TYPE
        SYNTAX          OCTET STRING (SIZE (0..64))   
        MAX-ACCESS      read-only
        STATUS          current
        DESCRIPTION
                "Indicates all of the font types which are supported for
                use by this host system, specified in a bit-array.
                Usage:  This bit-array is constructed from the set of
                supported values from 'XcmFontType', used as powers of 2
                with big-endian rules - the high-order bit of the first
                octet corresponds to a font type of '0' (reserved)
                - the low-order bit of the first octet corresponds to a
                font type of '7'.
                Similar to the BITS pseudotype defined in IETF SMIv2
                (RFC 2578), which has the same bit ordering rules but
                requires definitions for contiguous enumerated bits."
        REFERENCE
                "See:   'XcmFontType' in XCMI Document Resources TC;
                        'hrPrinterDetectedErrorState' in IETF
                            Host Resources MIB (RFC 1514/2790);
                        Section 7.1.4 'The BITS construct' in IETF
                            SMIv2 (RFC 2578);
                        Section 8 'Serialization using the BER' in IETF
                            Transport Mappings for SNMPv2 (RFC 1908)."
        ::= { xcmRsrcGeneralEntry 9 }
--
--
xcmRsrcInfo OBJECT IDENTIFIER ::= { xcmRsrcMIB 3 }
--
--
xcmRsrcTable OBJECT-TYPE
        SYNTAX          SEQUENCE OF XcmRsrcEntry
        MAX-ACCESS      not-accessible
        STATUS          current
        DESCRIPTION
                "This table should contain an entry for each unique
                resource available in the printer or multi-functional
                device."
        ::= { xcmRsrcInfo 1 }
xcmRsrcEntry OBJECT-TYPE
        SYNTAX          XcmRsrcEntry
        MAX-ACCESS      not-accessible
        STATUS          current
        DESCRIPTION
                "Entries exist in the table for each available
                resource on each present device."
        INDEX { hrDeviceIndex, xcmRsrcIndex }
        ::= { xcmRsrcTable 1 }
XcmRsrcEntry ::= SEQUENCE {
        xcmRsrcIndex                    Ordinal32,
        xcmRsrcRowStatus                RowStatus,
        xcmRsrcType                     XcmRsrcType,
        xcmRsrcInterpreterLangFamily    XcmPrtInterpreterLangFamily,
        xcmRsrcName                     CodeIndexedStringIndex,
        xcmRsrcDescription              CodeIndexedStringIndex,
        xcmRsrcCopyright                CodeIndexedStringIndex,
        xcmRsrcPersistence              XcmRsrcPersistence,
        xcmRsrcHrStorageIndex           Cardinal32,
        xcmRsrcSizeHigh                 Integer64High,
        xcmRsrcSizeLow                  Integer64Low,
        xcmRsrcID                       CodeIndexedStringIndex,
        xcmRsrcVersion                  CodeIndexedStringIndex
        }
xcmRsrcIndex OBJECT-TYPE
        SYNTAX          Ordinal32
        MAX-ACCESS      not-accessible
        STATUS          current
        DESCRIPTION
                "A unique value for each available resource on each
                present device. These values may change upon addition
                and deletion of a resource; however, index values should
                not change for existing resources at least within a
                power cycle; and index values should not be re-used for
                different resources at least within a power cycle."
        ::= { xcmRsrcEntry 1 }
xcmRsrcRowStatus OBJECT-TYPE
        SYNTAX          RowStatus
        MAX-ACCESS      read-create
        STATUS          current
        DESCRIPTION
                "Manages the status of this conceptual row in the
                xcmRsrcTable.
                Note that the status of a row in the table should
                reflect the status of the corresponding resource, not
                actually drive the status of the resource; in
                particular, removing a row from the table should not
                itself cause the removal of the corresponding resource
                from the device."
        ::= { xcmRsrcEntry 2 }
xcmRsrcType OBJECT-TYPE
        SYNTAX          XcmRsrcType
        MAX-ACCESS      read-create
        STATUS          current
        DESCRIPTION
                "The type of this resource, from the given
                enumeration."
        DEFVAL          { unknown }
        ::= { xcmRsrcEntry 3 }
xcmRsrcInterpreterLangFamily OBJECT-TYPE
        SYNTAX          XcmPrtInterpreterLangFamily
        MAX-ACCESS      read-create
        STATUS          current
        DESCRIPTION
                "The print interpreter language or other family
                of imaging mechanism with which this resource is
                associated, from the given enumeration."
        DEFVAL          { other }
        ::= { xcmRsrcEntry 4 }
xcmRsrcName OBJECT-TYPE
        SYNTAX          CodeIndexedStringIndex
        MAX-ACCESS      read-create
        STATUS          current
        DESCRIPTION
                "The resource name, the human-readable name usually
                used to identify the resource by and to the device.
                Being of type CodeIndexedString, the resource name may
                be present in multiple character sets, although it will
                commonly be present in only one preferred character
                set, e.g. only in ASCII for the name of a PostScript
                font.
                For a font resource, the resource name is the name of
                the font, the deliverable resource which informs how
                to image the included set of characters. The font is
                generally named in accord with the page description
                language or other imaging mechanism with which the
                font is associated. Often but not always, the font's
                name is the same as or similar to the name of the
                font's typeface, its design.
                Typical PostScript font names include 'Helvetica' (i.e.
                the medium, upright version) and 'Times-BoldItalic'.
                Typical PCL font names include 'Courier10' or
                'TmsRmn'.  However, it should be noted that PCL font
                names are normally just comments, not used for machine
                identification of the font resource."
        DEFVAL          { 0 }  
        ::= { xcmRsrcEntry 5 }
xcmRsrcDescription OBJECT-TYPE
        SYNTAX          CodeIndexedStringIndex
        MAX-ACCESS      read-create
        STATUS          current
        DESCRIPTION
                "A description of the resource, as complete as
                practical, including resource type and sub-type and
                other significant attributes.  For example,
                'PostScript Type 1 font for Times Bold Italic'."
        DEFVAL          { 0 }  
        ::= { xcmRsrcEntry 6 }
xcmRsrcCopyright OBJECT-TYPE
        SYNTAX          CodeIndexedStringIndex
        MAX-ACCESS      read-create
        STATUS          current
        DESCRIPTION
                "A human readable copyright message for the resource,
                e.g. as may be required by the resource's licensor.
                May also be null, or indicate that no rights are
                claimed, e.g. 'public domain'."
        DEFVAL          { 0 }  
        ::= { xcmRsrcEntry 7 }
xcmRsrcPersistence OBJECT-TYPE
        SYNTAX          XcmRsrcPersistence
        MAX-ACCESS      read-create
        STATUS          current
        DESCRIPTION
                "The persistence of this resource, from the given
                enumeration."
        DEFVAL          { unknown }
        ::= { xcmRsrcEntry 8 }
xcmRsrcHrStorageIndex OBJECT-TYPE
        SYNTAX          Cardinal32  
        MAX-ACCESS      read-create
        STATUS          current
        DESCRIPTION
                "The hrStorageIndex of the storage device or other
                storage resource which contains this document resource.
                A hrStorageIndex points to a hrStorageEntry in the
                hrStorageTable in the Host Resource MIB.  Each
                hrStorageEntry is a sequence of hrStorageIndex,
                hrStorageType, hrStorageDescr,
                hrStorageAllocationUnits, hrStorageSize, hrStorageUsed,
                hrStorageAllocationFailures.  The hrStorageType
                includes hrStorageOther, hrStorageRam,
                hrStorageVirtualMemory, hrStorageFixedDisk,
                hrStorageRemovableDisk, hrStorageFloppyDisk.
                A 0 index value indicates no hrStorageEntry."
        REFERENCE
                "See: 'hrStorageIndex' in IETF Host Resources MIB (RFC
                1514, September 1993) on page 8 - which indexes the
                Host Resources Storage Group (mandatory for all host
                systems in HR MIB)."
        DEFVAL          { 0 }  
        ::= { xcmRsrcEntry 9 }
xcmRsrcSizeHigh OBJECT-TYPE
        SYNTAX          Integer64High
        MAX-ACCESS      read-create
        STATUS          current
        DESCRIPTION
                "The high-order part of the data storage size of this
                document resource itself, in units of bytes.  A
                xcmRsrcSizeHigh value of -1 indicates unknown size."
        DEFVAL          { -1 }  
        ::= { xcmRsrcEntry 10 }
xcmRsrcSizeLow OBJECT-TYPE
        SYNTAX          Integer64Low
        MAX-ACCESS      read-create
        STATUS          current
        DESCRIPTION
                "The low-order part of the data storage size of this
                document resource itself, in units of bytes.  A
                xcmRsrcSizeHigh value of -1 indicates unknown size."
        DEFVAL          { 0 }  
        ::= { xcmRsrcEntry 11 }
xcmRsrcID OBJECT-TYPE
        SYNTAX          CodeIndexedStringIndex
        MAX-ACCESS      read-create
        STATUS          current
        DESCRIPTION
                "An ID, or identifier, for the resource, complementary
                to the resource name, as appropriate to the resource
                type and sub-type.  For example, for a PostScript font
                or PCL font, this resource ID would be the PostScript or
                PCL font ID.  Where the ID is inherently an integer or
                other number, e.g. as for a PCL font ID, it is
                nonetheless represented here as a string, e.g. '253'."
        DEFVAL          { 0 }  
        ::= { xcmRsrcEntry 12 }
xcmRsrcVersion OBJECT-TYPE
        SYNTAX          CodeIndexedStringIndex
        MAX-ACCESS      read-create
        STATUS          current
        DESCRIPTION
                "The version of the resource, as appropriate to the
                resource type and sub-type.  Where the version is
                inherently an integer or other number, it is nonetheless
                represented here as a string, e.g. '3'."
        DEFVAL          { 0 }  
        ::= { xcmRsrcEntry 13 }
--
--
xcmRsrcV1EventOID OBJECT-IDENTITY
    STATUS      current
    DESCRIPTION
        "The value of the enterprise-specific OID in an SNMPv1 trap sent
        whenever a resource entry or a subordinate entry changes.
        See SNMPv2 trap definition 'xcmRsrcV2Event' below
        for 'special semantics'."
    ::= { xcmRsrcInfo 2 }
xcmRsrcV2EventPrefix
    OBJECT IDENTIFIER ::= { xcmRsrcV1EventOID 0 }
xcmRsrcV2Event NOTIFICATION-TYPE
    OBJECTS {
        xcmRsrcRowStatus
    }
    STATUS      current
    DESCRIPTION
        "This trap is sent whenever ANY object in a resource entry
        or in a subordinate entry changes.
        This notification has the following special semantics:
            o   Any resource entry object (e.g. 'xcmRsrcPersistence'
                in the Resource table) whose value has changed SHOULD
                also be added to this trap's variable-bindings.
            o   Any subordinate entry object (e.g. 'xcmFontRowStatus'
                in the Font table) whose value has changed MAY
                also be added to this trap's variable-bindings.
        The above special semantics permit optimizations by agreement
        between SNMP manager and SNMP agent implementers."
    ::= { xcmRsrcV2EventPrefix 1 }
--
--          "This trap is sent whenever ANY object in a resource entry
--          for 'special semantics'."
--
--
xcmFontInfo OBJECT IDENTIFIER ::= { xcmRsrcMIB 4 }
--
--
xcmFontTable OBJECT-TYPE
        SYNTAX          SEQUENCE OF XcmFontEntry
        MAX-ACCESS      not-accessible
        STATUS          current
        DESCRIPTION
                "This table should contain an entry for each unique
                font available in the device. If a font is available
                to multiple interpreters, there should be multiple
                entries for that font, one per interpreter."
        ::= { xcmFontInfo 1 }
xcmFontEntry OBJECT-TYPE
        SYNTAX          XcmFontEntry
        MAX-ACCESS      not-accessible
        STATUS          current
        DESCRIPTION
                "Entries exist in the table for each font
                available to an interpreter in the device."
        INDEX { hrDeviceIndex, xcmRsrcIndex }
        ::= { xcmFontTable 1 }
XcmFontEntry ::= SEQUENCE {
        xcmFontRowStatus                RowStatus,
        xcmFontType                     XcmFontType,
        xcmFontPointsMinNumerator       Integer32,
        xcmFontPointsMaxNumerator       Integer32,
        xcmFontPointsDenominator        Integer32,
        xcmFontSpacing                  XcmFontSpacing,
        xcmFontCharSet                  IANACharset
        }
xcmFontRowStatus OBJECT-TYPE
        SYNTAX          RowStatus
        MAX-ACCESS      read-create
        STATUS          current
        DESCRIPTION
                "Manages the status of this conceptual row in the
                xcmFontTable."
        ::= { xcmFontEntry 1 }
xcmFontType OBJECT-TYPE
        SYNTAX          XcmFontType
        MAX-ACCESS      read-create
        STATUS          current
        DESCRIPTION
                "The type of this font, from the given enumeration."
        DEFVAL          { unknown }
        ::= { xcmFontEntry 2 }
xcmFontPointsMinNumerator OBJECT-TYPE
        SYNTAX          Integer32
        MAX-ACCESS      read-create
        STATUS          current
        DESCRIPTION
                "The numerator of a fraction indicating the body size,
                or the minimum of the supported range of body sizes,
                of the font.  The size is in units of printer's points,
                which units are here considered to be exactly 1/72 of
                an inch.  Values of -1 indicate 'infinite,' while
                values of -2 indicate 'unknown.'"
        DEFVAL          { -2 }  
        ::= { xcmFontEntry 3 }
xcmFontPointsMaxNumerator OBJECT-TYPE
        SYNTAX          Integer32
        MAX-ACCESS      read-create
        STATUS          current
        DESCRIPTION
                "The numerator of a fraction indicating the body size,
                or the maximum of the supported range of body sizes,
                of the font.  The size is in units of printer's points,
                which units are here considered to be exactly 1/72 of
                an inch.  Values of -1 indicate 'infinite,' while
                values of -2 indicate 'unknown.'"
        DEFVAL          { -2 }  
        ::= { xcmFontEntry 4 }
xcmFontPointsDenominator OBJECT-TYPE
        SYNTAX          Integer32
        MAX-ACCESS      read-create
        STATUS          current
        DESCRIPTION
                "The denominator of both minimum and maximum body size.
                The denominator is typically chosen to give a
                convenient scale and precision for expressing the
                sizes.  Values of -1 indicate 'infinite,' while values
                of -2 indicate 'unknown.'"
        DEFVAL          { -2 }  
        ::= { xcmFontEntry 5 }
xcmFontSpacing OBJECT-TYPE
        SYNTAX          XcmFontSpacing
        MAX-ACCESS      read-create
        STATUS          current
        DESCRIPTION
                "The kind of spacing of the characters in this font,
                from the given enumeration."
        DEFVAL          { unknown }
        ::= { xcmFontEntry 6 }
xcmFontCharSet OBJECT-TYPE
        SYNTAX          IANACharset
        MAX-ACCESS      read-create
        STATUS          current
        DESCRIPTION
                "The character set of this font resource.  The value is
                the enum for the IANA-registered coded character set,
                per the IANACharset textual-convention in the Printer
                MIB (RFC 1759).  For more info. about character sets and
                coded character sets, see RFCs 2277 and 2278."
        DEFVAL          { other }  
        ::= { xcmFontEntry 7 }
--
--
xcmFontPCLInfo OBJECT IDENTIFIER ::= { xcmRsrcMIB 5 }
--
--
xcmFontPCLTable OBJECT-TYPE
        SYNTAX          SEQUENCE OF XcmFontPCLEntry
        MAX-ACCESS      not-accessible
        STATUS          current
        DESCRIPTION
                "This table should contain an entry for each unique
                font available in the device. If a font is available
                to multiple interpreters, there should be multiple
                entries for that font here, one entry per interpreter."
        ::= { xcmFontPCLInfo 1 }
xcmFontPCLEntry OBJECT-TYPE
        SYNTAX          XcmFontPCLEntry
        MAX-ACCESS      not-accessible
        STATUS          current
        DESCRIPTION
                "Entries exist in the table for each PCL font."
        INDEX { hrDeviceIndex, xcmRsrcIndex }
        ::= { xcmFontPCLTable 1 }
XcmFontPCLEntry ::= SEQUENCE {
        xcmFontPCLRowStatus             RowStatus,
        xcmFontPCLTypefaceValue         Integer32,
        xcmFontPCLSymbolSetValue        Integer32,
        xcmFontPCLStyle                 XcmFontPCLStyle,
        xcmFontPCLPitchMinNumerator     Integer32,
        xcmFontPCLPitchMaxNumerator     Integer32,
        xcmFontPCLPitchDenominator      Integer32,
        xcmFontPCLStrokeWeight          XcmFontPCLStrokeWeight
        }
xcmFontPCLRowStatus OBJECT-TYPE
        SYNTAX          RowStatus
        MAX-ACCESS      read-create
        STATUS          current
        DESCRIPTION
                "Manages the status of this conceptual row in the
                xcmFontPCLTable."
        ::= { xcmFontPCLEntry 1 }
xcmFontPCLTypefaceValue OBJECT-TYPE
        SYNTAX          Integer32
        MAX-ACCESS      read-create
        STATUS          current
        DESCRIPTION
                "The integer value specifying the PCL 'typeface'
                (really family) of the font. For example, 3 normally
                indicates Courier, 4 indicates 'Helv'.
                A value of -1 indicates unknown typeface value."
        REFERENCE
                "See: 'PCL 5 Printer Language Technical Reference
                Manual' and 'PCL 5 Comparision Guide' by
                Hewlett-Packard Corporation."
        DEFVAL          { -1 }  
        ::= { xcmFontPCLEntry 2 }
xcmFontPCLSymbolSetValue OBJECT-TYPE
        SYNTAX          Integer32
        MAX-ACCESS      read-create
        STATUS          current
        DESCRIPTION
                "The integer value specifying the PCL symbol set of
                the font. For example, 21 normally indicates ASCII,
                277 indicates the HP Roman-8 set.
                A value of -1 indicates unknown symbol set value."
        REFERENCE
                "See: 'PCL 5 Printer Language Technical Reference
                Manual' and 'PCL 5 Comparision Guide' by
                Hewlett-Packard Corporation."
        DEFVAL          { -1 }  
        ::= { xcmFontPCLEntry 3 }
xcmFontPCLStyle OBJECT-TYPE
        SYNTAX          XcmFontPCLStyle
        MAX-ACCESS      read-create
        STATUS          current
        DESCRIPTION
                "The style of the font, from the given enumeration."
        REFERENCE
                "See: 'PCL 5 Printer Language Technical Reference
                Manual' and 'PCL 5 Comparision Guide' by
                Hewlett-Packard Corporation."
        DEFVAL          { unknown }
        ::= { xcmFontPCLEntry 4 }
xcmFontPCLPitchMinNumerator OBJECT-TYPE
        SYNTAX          Integer32
        MAX-ACCESS      read-create
        STATUS          current
        DESCRIPTION
                "The numerator of a fraction indicating the pitch, or
                the minimum of the supported range of pitches, of the
                font.  The pitch is in units of characters per inch.
                Values of -1 indicate 'infinite,' while values of -2
                indicate 'unknown.'"
        DEFVAL          { -2 }  
        ::= { xcmFontPCLEntry 5 }
xcmFontPCLPitchMaxNumerator OBJECT-TYPE
        SYNTAX          Integer32
        MAX-ACCESS      read-create
        STATUS          current
        DESCRIPTION
                "The numerator of a fraction indicating the pitch, or
                the maximum of the supported range of pitches, of the
                font.  The pitch is in units of characters per inch.
                Values of -1 indicate 'infinite,' while values of -2
                indicate 'unknown.'"
        DEFVAL          { -2 }  
        ::= { xcmFontPCLEntry 6 }
xcmFontPCLPitchDenominator OBJECT-TYPE
        SYNTAX          Integer32
        MAX-ACCESS      read-create
        STATUS          current
        DESCRIPTION
                "The denominator of both minimum and maximum pitch.
                The denominator is typically chosen to give a
                convenient scale and precision for expressing the
                pitches.  Values of -1 indicate 'infinite,' while
                values of -2 indicate 'unknown.'"
        DEFVAL          { -2 }  
        ::= { xcmFontPCLEntry 7 }
xcmFontPCLStrokeWeight OBJECT-TYPE
        SYNTAX          XcmFontPCLStrokeWeight
        MAX-ACCESS      read-create
        STATUS          current
        DESCRIPTION
                "The PCL stroke weight of the font, from the given
                enumeration."
        REFERENCE
                "See: 'PCL 5 Printer Language Technical Reference
                Manual' and 'PCL 5 Comparision Guide' by
                Hewlett-Packard Corporation."
        DEFVAL          { unknown }
        ::= { xcmFontPCLEntry 8 }
--
--
xcmRsrcMIBConformance
                   OBJECT IDENTIFIER ::= { xcmRsrcMIB 2 }
xcmRsrcMIBGroups
                   OBJECT IDENTIFIER ::= { xcmRsrcMIBConformance 2 }
--
--
xcmRsrcMIBCompliance MODULE-COMPLIANCE
    STATUS     current
    DESCRIPTION
        "The compliance statement for SNMP management agents that
        implement the XCMI Document Resources MIB."
    MODULE 
    MANDATORY-GROUPS {
        xcmRsrcGeneralGroup,
        xcmRsrcInfoGroup
    }
    --
    --
    GROUP       xcmFontInfoGroup
    DESCRIPTION "
        This Group is Conditionally Mandatory, i.e. mandatory for
        those devices which manage font-specific attributes of
        resources over the network."
    GROUP       xcmFontPCLGroup
    DESCRIPTION "
        This Group is Conditionally Mandatory, i.e. mandatory for
        those devices which manage PCL-specific attributes of font
        resources over the network."
    --
    --
    --
    --
    OBJECT      xcmRsrcRowStatus
    SYNTAX      INTEGER { active(1) }  
    MIN-ACCESS  read-only
    DESCRIPTION
        "It is conformant to implement this object as read-only, and
        only one of the enumerated values for the 'RowStatus' textual
        convention need be supported, specifically:  active(1)."
    OBJECT      xcmRsrcType
    MIN-ACCESS  read-only
    DESCRIPTION
        "It is conformant to implement this object as read-only."
    OBJECT      xcmRsrcInterpreterLangFamily
    MIN-ACCESS  read-only
    DESCRIPTION
        "It is conformant to implement this object as read-only."
    OBJECT      xcmRsrcName
    MIN-ACCESS  read-only
    DESCRIPTION
        "It is conformant to implement this object as read-only."
    OBJECT      xcmRsrcDescription
    MIN-ACCESS  read-only
    DESCRIPTION
        "It is conformant to implement this object as read-only."
    OBJECT      xcmRsrcCopyright
    MIN-ACCESS  read-only
    DESCRIPTION
        "It is conformant to implement this object as read-only."
    OBJECT      xcmRsrcPersistence
    MIN-ACCESS  read-only
    DESCRIPTION
        "It is conformant to implement this object as read-only."
    OBJECT      xcmRsrcHrStorageIndex
    MIN-ACCESS  read-only
    DESCRIPTION
        "It is conformant to implement this object as read-only."
    OBJECT      xcmRsrcSizeHigh
    MIN-ACCESS  read-only
    DESCRIPTION
        "It is conformant to implement this object as read-only."
    OBJECT      xcmRsrcSizeLow
    MIN-ACCESS  read-only
    DESCRIPTION
        "It is conformant to implement this object as read-only."
    OBJECT      xcmRsrcID
    MIN-ACCESS  read-only
    DESCRIPTION
        "It is conformant to implement this object as read-only."
    OBJECT      xcmRsrcVersion
    MIN-ACCESS  read-only
    DESCRIPTION
        "It is conformant to implement this object as read-only."
    --
    --
    OBJECT      xcmFontRowStatus
    SYNTAX      INTEGER { active(1) }  
    MIN-ACCESS  read-only
    DESCRIPTION
        "It is conformant to implement this object as read-only, and
        only one of the enumerated values for the 'RowStatus' textual
        convention need be supported, specifically:  active(1)."
    OBJECT      xcmFontType
    MIN-ACCESS  read-only
    DESCRIPTION
        "It is conformant to implement this object as read-only."
    OBJECT      xcmFontPointsMinNumerator
    MIN-ACCESS  read-only
    DESCRIPTION
        "It is conformant to implement this object as read-only."
    OBJECT      xcmFontPointsMaxNumerator
    MIN-ACCESS  read-only
    DESCRIPTION
        "It is conformant to implement this object as read-only."
    OBJECT      xcmFontPointsDenominator
    MIN-ACCESS  read-only
    DESCRIPTION
        "It is conformant to implement this object as read-only."
    OBJECT      xcmFontSpacing
    MIN-ACCESS  read-only
    DESCRIPTION
        "It is conformant to implement this object as read-only."
    OBJECT      xcmFontCharSet
    MIN-ACCESS  read-only
    DESCRIPTION
        "It is conformant to implement this object as read-only."
    --
    --
    OBJECT      xcmFontPCLRowStatus
    SYNTAX      INTEGER { active(1) }  
    MIN-ACCESS  read-only
    DESCRIPTION
        "It is conformant to implement this object as read-only, and
        only one of the enumerated values for the 'RowStatus' textual
        convention need be supported, specifically:  active(1)."
    OBJECT      xcmFontPCLTypefaceValue
    MIN-ACCESS  read-only
    DESCRIPTION
        "It is conformant to implement this object as read-only."
    OBJECT      xcmFontPCLSymbolSetValue
    MIN-ACCESS  read-only
    DESCRIPTION
        "It is conformant to implement this object as read-only."
    OBJECT      xcmFontPCLStyle
    MIN-ACCESS  read-only
    DESCRIPTION
        "It is conformant to implement this object as read-only."
    OBJECT      xcmFontPCLPitchMinNumerator
    MIN-ACCESS  read-only
    DESCRIPTION
        "It is conformant to implement this object as read-only."
    OBJECT      xcmFontPCLPitchMaxNumerator
    MIN-ACCESS  read-only
    DESCRIPTION
        "It is conformant to implement this object as read-only."
    OBJECT      xcmFontPCLPitchDenominator
    MIN-ACCESS  read-only
    DESCRIPTION
        "It is conformant to implement this object as read-only."
    OBJECT      xcmFontPCLStrokeWeight
    MIN-ACCESS  read-only
    DESCRIPTION
        "It is conformant to implement this object as read-only."
    ::= { xcmRsrcMIBConformance 1 }
--
--
xcmRsrcGeneralGroup OBJECT-GROUP
    OBJECTS {
        xcmRsrcGeneralRowStatus,
        xcmRsrcGeneralGroupSupport,
        xcmRsrcGeneralCreateSupport,
        xcmRsrcGeneralUpdateSupport,
        xcmRsrcGeneralRsrcTypeAccept,
        xcmRsrcGeneralFontTypeAccept,
        xcmRsrcGeneralRsrcTypeSupport,
        xcmRsrcGeneralFontTypeSupport
    }
    STATUS  current
    DESCRIPTION
        "The Resources MIB General Group."
    ::= { xcmRsrcMIBGroups 1 }
xcmRsrcInfoGroup OBJECT-GROUP
    OBJECTS {
        xcmRsrcRowStatus,
        xcmRsrcType,
        xcmRsrcInterpreterLangFamily,
        xcmRsrcName,
        xcmRsrcDescription,
        xcmRsrcCopyright,
        xcmRsrcPersistence,
        xcmRsrcHrStorageIndex,
        xcmRsrcSizeHigh,
        xcmRsrcSizeLow,
        xcmRsrcID,
        xcmRsrcVersion
    }
    STATUS  current
    DESCRIPTION
        "The Document Resources MIB (Generic) Resources Group."
    ::= { xcmRsrcMIBGroups 3 }
xcmFontInfoGroup OBJECT-GROUP
    OBJECTS {
        xcmFontRowStatus,
        xcmFontType,
        xcmFontPointsMinNumerator,
        xcmFontPointsMaxNumerator,
        xcmFontPointsDenominator,
        xcmFontSpacing,
        xcmFontCharSet
    }
    STATUS  current
    DESCRIPTION
        "The Resources MIB (General) Fonts Group."
    ::= { xcmRsrcMIBGroups 4 }
xcmFontPCLGroup OBJECT-GROUP
    OBJECTS {
        xcmFontPCLRowStatus,
        xcmFontPCLTypefaceValue,
        xcmFontPCLSymbolSetValue,
        xcmFontPCLStyle,
        xcmFontPCLPitchMinNumerator,
        xcmFontPCLPitchMaxNumerator,
        xcmFontPCLPitchDenominator,
        xcmFontPCLStrokeWeight
    }
    STATUS  current
    DESCRIPTION
        "The Resources MIB PCL Fonts Group."
    ::= { xcmRsrcMIBGroups 5 }
xcmJobMonTC OBJECT-IDENTITY -- MODULE-IDENTITY
    STATUS   current
        DESCRIPTION "
            File:     40jobtc.dfm, .mib, .pdf, .txt
            Version:  5.11.pub
            This textual-convention module defines textual-
            conventions for use with the Job Monitoring MIB,
            module:  XEROX-JOB-MONITORING-MIB.  Also the explanatory
            material with this module explains the Job Monitoring
            MIB.  These textual-conventions and explanations are in
            a separate module from the Job Monitoring MIB, so that
            they may be republished when additional enums are added
            or more explanatory material is added without needing to
            republish the Job Monitoring MIB, thus increasing the
            stability of the Job Monitoring MIB.
            Copyright 1996-2002 Xerox Corporation. All Rights Reserved."
        ::= { xeroxCommonMIB 58 }
XcmJMJobServiceTypeOID ::= TEXTUAL-CONVENTION
    STATUS     current
    DESCRIPTION
        "Specifies the type of service to which the job has been
        submitted.  The service type is represented as a single OID,
        rather than as an OID for a source-type and an OID for a
        destination-type, so that more general and arbitrary service
        types can be created, such as services with more than one
        destination type, or ones with only a source or only a
        destination."
    SYNTAX     OBJECT IDENTIFIER
--
--
xcmJobServiceTypesOID OBJECT-IDENTITY
    STATUS     current
    DESCRIPTION
        "The root of all job service type OIDs defined in the Job
        Monitoring MIB TC.  Also use these same OIDs for Xerox
        extensions to ISO DPA."
    ::= { xcmJobMonTC 2 }
xcmJobServiceScanToFileOID OBJECT-IDENTITY
    STATUS     current
    DESCRIPTION
        "Scan-to-file
        The scan-to-file job service scans one or more documents and
        stores the result in one or more (1) local files, (2) files
        in a distributed file system or (3) files in a document
        repository, depending on the prescriptive instructions submitted
        with the job service request."
    ::= { xcmJobServiceTypesOID 1 }
xcmJobServiceScanToPrintOID OBJECT-IDENTITY
    STATUS     current
    DESCRIPTION
        "Scan-to-print
        The scan-to-print job service scans one or more documents and
        prints the results on a local printer or on a network
        printer, depending on the prescriptive instructions submitted
        with the job service request."
    REFERENCE
        "See:   'xcmJobServiceCopyOID' below"
    ::= { xcmJobServiceTypesOID 2 }
xcmJobServiceScanToFaxOID OBJECT-IDENTITY
    STATUS     current
    DESCRIPTION
        "Scan-to-fax
        The scan-to-fax job service scans one or more documents and
        faxes the results using a local fax or on a network
        fax, depending on the prescriptive instructions submitted
        with the job service request."
    ::= { xcmJobServiceTypesOID 3 }
xcmJobServiceScanToMailListOID OBJECT-IDENTITY
    STATUS     current
    DESCRIPTION
        "Scan-to-mail-list
        The scan-to-mail-list job service scans one or more documents
        and distributes the results using the distribution list
        specified by the prescriptive instructions submitted
        with the job service request."
    ::= { xcmJobServiceTypesOID 4 }
xcmJobServiceFaxToFileOID OBJECT-IDENTITY
    STATUS     current
    DESCRIPTION
        "Fax-to-file
        The fax-to-file job service accepts one or more documents via
        inbound fax and stores the result in one or more: (1) local
        files, (2) files in a distributed file system or (3) files in a
        document repository, depending on the prescriptive instructions
        submitted with the job service request."
    ::= { xcmJobServiceTypesOID 5 }
xcmJobServiceFaxToPrintOID OBJECT-IDENTITY
    STATUS     current
    DESCRIPTION
        "Fax-to-print
        The fax-to-print job service accepts one or more documents via
        inbound fax and prints the results on a local printer or on a
        network printer, depending on the prescriptive instructions
        submitted with the job service request."
    ::= { xcmJobServiceTypesOID 6 }
xcmJobServiceFaxToMailListOID OBJECT-IDENTITY
    STATUS     current
    DESCRIPTION
        "Fax-to-mail-list
        The fax-to-mail-list job service accepts one or more documents
        via inbound fax and distributes the results using the
        distribution list specified by the prescriptive instructions
        submitted with the job service request."
    ::= { xcmJobServiceTypesOID 7 }
xcmJobServicePrintOID OBJECT-IDENTITY
    STATUS     current
    DESCRIPTION
        "Print
        The print job service accepts one or more documents submitted
        with the job print service request, referenced from the job
        request in a distributed file system or document repository
        and prints on a network printer, depending on the prescriptive
        instructions submitted with the job service request."
    ::= { xcmJobServiceTypesOID 8 }
xcmJobServiceFileToFaxOID OBJECT-IDENTITY
    STATUS     current
    DESCRIPTION
        "File-to-fax
        The file-to-fax job service accepts one or more documents
        submitted with the job print service request, referenced from
        the job request in a distributed file system or document
        repository and faxes the results using a local fax or on a
        network fax, depending on the prescriptive instructions
        submitted with the job service request."
    ::= { xcmJobServiceTypesOID 9 }
xcmJobServiceFileToMailListOID OBJECT-IDENTITY
    STATUS     current
    DESCRIPTION
        "File-to-mail-list
        The file-to-mail-list job service accepts one or more documents
        submitted with the job service request, referenced from the job
        request in a distributed file system or document repository
        and distributes the results using the distribution
        list specified by the prescriptive instructions submitted
        with the job service request.  The file-to-mail-list service
        permits a user to compose a compound job whose sub-job produces
        a file, such as a scan-to-file, and whose subsequent sub-jobs
        use the file as input, such as a sub-job to file-to-mail-list
        and a second (parallel) sub-job to print from the same file."
    ::= { xcmJobServiceTypesOID 10 }
xcmJobServiceCopyOID OBJECT-IDENTITY
    STATUS     current
    DESCRIPTION
        "Copy
        The copy job service reads images (via xerography, scanner,
        etc.) and writes (prints) those images (with a pipeline delay of
        zero or more images) on a local marker sub-unit (copy service
        need NOT write a disk or other secondary storage file of the
        copy images).  Compare with 'xcmJobServiceScanToPrint' (strictly
        used for digital scanners - scan to print service shall ALWAYS
        write a disk or other secondary storage file of the whole
        document, i.e., the set of copy images).
        The key distinction, from an Image Processing point of is that,
        for a copy (or local copy) job the IIT (input - scan) and IOT
        (output - marker) are WELL-TUNED with respect to each other to
        produce the best quality and the best performance.
        Whereas for ScantoPrint the target IOT (or the its capabilities)
        are not assumed to be known at the time scanning and in order to
        achieve best quality, there is often an additional  step of
        image processing that the systems needs to go through (often
        called Image Interoperability Services).
        Usage:  A copy job service shall ALWAYS expose
        an 'xcmHrDeviceCopier' (scanner and marker are invisible)
        in the IETF HR MIB, XCMI HRX MIB, and XCMI Job Monitoring MIB.
        Usage:  A scan to print job service shall ALWAYS expose
        an 'xcmHrDeviceScanner' and an 'hrDevicePrinter' (marker)
        in the IETF HR MIB, XCMI HRX MIB, and XCMI Job Monitoring MIB."
    REFERENCE
        "See:   'xcmJobServiceScanToPrintOID' above"
    ::= { xcmJobServiceTypesOID 11 }
xcmJobServiceFileToFileOID OBJECT-IDENTITY
    STATUS     current
    DESCRIPTION
        "File-to-file
        The file-to-file job service accepts one or more documents
        submitted with the job print service request, referenced from
        the job request in a distributed file system or document
        repository and stores the result in one or more: (1) local
        files, (2) files in a distributed file system or (3) files in a
        document repository, depending on the prescriptive instructions
        submitted with the job service request.
        The initial intent of this job service is support the transfer
        of a file to a device's hard drive.  When the file transfer is
        complete, the file-to-file job is complete.  It is expected that
        a user will eventually process the file from the device hard
        drive, but that action starts a new job.  This service might be
        used in the processing of a secure-print action."
    ::= { xcmJobServiceTypesOID 12 }
XcmJMJobState ::= TEXTUAL-CONVENTION
    STATUS     current
    DESCRIPTION
        "A job may be in any of the states defined by this textual-
         convention.
        The Xerox Job model is a refinement of the ISO DPA standard and
        generalizes to non-printing devices.  The textual definitions
        given here are an abbreviation of the full specification of the
        semantics of the job states given in the Xerox Job Model
        specification.  Agent implementers of this MIB need to refer to
        the Xerox Job Model specification in addition to this textual
        convention.
        Traps shall be generated when a job performs a job
        state transition.  In order to reduce network traffic, it is
        recommended, but not required, that an implementation suppress
        traps for self-loops.  The xcmJobPreviousState can be used to
        detect self-loops and suppress self-loop traps by not sending
        traps when the value of the xcmJobPreviousState is the same as
        the value of the xcmJobCurrentState.
        When a job is in the processing state,
        the state of the assigned device(s) is needed to fully
        represent the state of the job.  In addition, the
        job-state-reasons attributes provides additional, more abstract,
        user feedback about what is happening to the job when the job
        is in many of its states.  See the Xerox Job Model
        Specification, Phase 1 or later for the specification of which
        job-state-reasons values may be used with which job states..
        ISO DPA:   Job-current-state
        Standard values are defined for the current-job-state and
        previous-job-state attributes of the DPA job object, as follows:
        unknown           The job state is not known, or is
                          indeterminate, or is not returned by the
                          operation.  (id-val-job-state-unknown)
        creating          The job has been created on the server by
                          the create-job sub-operation of the Submit
                          request, but a Submit request with neither (1)
                          a TRUE value for the job-submission-complete
                          component of the SubmitArgument nor (2) a TRUE
                          value for the job-process-before-completely-
                          specified (long jobs) job attribute has not
                          yet been received and no document has started
                          processing.  The job maybe in the process
                          of being checked by the server for
                          attributes, defaults being applied, a
                          device being selected, etc.
                          [Renamed from ISO DPA pre-processing state,
                          but kept the same enum code, since the
                          semantics are identical.] (id-val-job-
                          state-pre-processing)
NOTE: The Xerox Job Model transitory state: evaluate-hold shall not be
visible to requesters, and therefore is not in the Job Monitoring MIB.
        held              The job is waiting to be released for
                          scheduling for any number of reasons as
                          specified by the value of the job's job-
                          state-reasons attribute.  (id-val-job-
                          state-held)
                          See the Xerox Job Model Specification, Phase 1
                          or later for the specification of which
                          job-state-reasons values may be used when the
                          job is in the held state.
        pending           The job is
                          waiting to start processing on a device and
                          has no shared system resources assigned to it
                          yet.  (id-val-job-state-pending)
[The ISO DPA processing and printing states have been combined into a
single job state, called processing, which includes any device activity,
so that the job life cycle can be used for all kinds of jobs, not just
printing jobs, and have the same life cycle.  The printing state is
DEPRECATED. In addition, the difference between the ISO DPA processing
state and printing state was one of user feed back only.  The standard
specified no differences in job state transitions between the processing
and printing states.  Therefore, ISO DPA should have used the device-
state-of-devices-assigned mechanism to provide the user feedback
distinction between the processing and printing states.  In fact,
neither Novell's NDPS nor IBM's PSM DPA products implement the printing
state, only the processing state.  Only Printxchange implements the
printing state (as well as the processing state).  So we will propose to
ISO DPA that the DPA printing state be deprecated.
[For convenience in understanding the difference between ISO DPA and the
Job Monitoring MIB (and the Xerox Job Model), the ISO DPA processing and
printing specifications are given here first, followed by the new
(Xerox) definition of processing which incorporates the semantics of the
ISO DPA processing and printing states, and extends these semantics to
sub-jobs.]
[ISO DPA processing specification:  The server is processing the job, or
has made the job ready for printing, but the output device is not yet
printing it, either because the job hasn't reached the output device or
because the job is queued in the output device or some other spooler,
awaiting the output device to print it.]
[ISO DPA printing state specification which is DEPRECATED by the Job
Monitoring MIB:  The server has completed processing the job and the
output device is currently printing the job on at least one printer.
That is, a print engine is either printing pages of the job, or failing
in its attempt to print pages of the job because of some wait state,
such as, start-wait, end-wait, needs-attention, etc.  The complete job
state includes the detailed status represented in the printers' printer-
state attribute(s).]
[The following Xerox definition of the 'processing' job state combines
the ISO DPA processing and printing states into a single state, called
'processing', which can be used with any kind of device:
        processing        The server is:
                          (1) processing the job, or
                          (2) has made the job ready for processing, but
                          the device is not yet processing it, either:
                            (a) because the job hasn't reached the
                                device or
                            (b) because the job is queued in the device
                                or some other spooler, awaiting the
                                device to process it
                          or
                          (3) has completed processing the job and the
                          device is currently processing (printing,
                          scanning, sending-fax, receiving-fax,
                          sending-e-mail, filing, or retrieving) the job
                          on at least one device. That is, a device is
                          either performing input-output of the job, or
                          failing in its attempt to perform input-output
                          of the job because of some wait state, such
                          as, start-wait, end-wait, needs-attention,
                          etc.
                          Additional information about the job's current
                          state is also given in the job's
                          job-state-reasons attribute for when the job
                          is in any of its states, including processing.
                          See the Xerox Job Model for which values of
                          the job's job-state-reasons attribute may be
                          used when the job is in the processing state.
                          NOTE: DPA does not yet have any
                          job-state-reasons defined for the
                          processing/printing states.
                          (id-val-job-state-processing)]
        paused            The job has been paused as a result of a
                          PauseJob request.
                          NOTE: The Xerox Job Model has renamed the
                          PauseJob and ResumeJob operations to HoldJob
                          and ReleaseJob and has changed the semantics
                          to put the job back into the held state,
                          with the job-hold attribute set to TRUE
                          and the job-hold-set value added to the
                          job-state-reasons attribute instead of putting
                          into the paused state.  So the paused state
                          remains only for use with ISO DPA systems that
                          have implemented the paused state.
                          (id-val-job-state-paused)
        interrupted       The job was interrupted by the InterruptJob
                          request for an intervening job, and shall
                          resume processing automatically once the
                          intervening job has completed.  The
                          interrupted job may relinquish shared
                          resources and devices to the interrupting job,
                          but not to other jobs.
                          (id-val-job-state-interrupted)
        terminating       The job has been cancelled by a CancelJob
                          request or aborted by the server and is in
                          the process of terminating.  The job's job-
                          state-reasons attribute contains the
                          reasons that the job is being terminated.
                          (id-val-job-state-terminating)
        retained          The job is being retained at the server as
                          a result of the job's job-retention-period
                          being non-zero. The job has (1) completed
                          successfully or with warnings or errors,
                          (2) been aborted while [processing] printing
                          by the server, or (3) been cancelled by the
                          CancelJob request before or during
                          processing.  The job's job-state-reasons
                          attribute contains the reasons that the job
                          has been retained.
                          While in the retained state, all of the
                          job's document data (and resources, if any)
                          shall be retained by the server; thus a job
                          in the retained state [could be resubmitted
                          using the Resubmit request in ISO DPA
                          Part 3.].  ResubmitJob shall create a new job
                          object instance and assign a new
                          job-identifier.  See the Xerox Job Model spec.
                          (id-val-job-state-retained)
        completed         The job has either:
                              (1) completed successfully or with
                                  warnings or errors,
                              (2) been aborted by the server while
                                  processing, or
                              (3) been cancelled by the CancelJob
                                  request,
                            AND the job's:
                              (1) job-retention-period was zero or
                                  has expired, or
                              (2) job-discard-time has arrived.
                          OR a ResubmitJob operation has been issued
                             which forces the old job to the completed
                             state and makes a new job object instance
                             with a new job identifier.  See the Xerox
                             Job Model specification.
                          The job's job-state-reasons attribute
                          contains the reason(s) that the job has
                          been completed.
                          While in the completed state, a job's
                          document data (and resources if any) need
                          not be retained by the server; thus a job
                          in the completed state could not be
                          resubmitted. The length of time that a job
                          may be in this state, before transitioning
                          to unknown, is implementation-dependent.
                          However, servers that implement the
                          completed job-state shall retain, as a
                          minimum, the following attributes for any
                          job in the completed state: job-identifier,
                          job-owner, job-name, current-job-state,
                          devices-assigned, and job-state-reasons, plus
                          as a Xerox extension, the accounting
                          attributes:
                          xcmJobAccountingUserName,
                          xcmJobAccountingInformation,
                          xcmJobStartedProcessingTime,
                          xcmJobImpressionsCompleted,
                          xcmJobMediaSheetsCompleted,
                          xcmJobCompletionTime, xcmJobWorkUnitType
                          XcmHrDevTrafficUnit,
                          and xcmJobUnitsOfWorkCompleted
                          so that an accounting management application
                          can copy the accounting data from the MIB
                          before the job is deleted from the MIB.
                          Jobs that have been moved to the OPTIONAL
                          'Job History' device SHALL be in the
                          'completed' state (or 'aborted' or 'canceled'
                          states with the PWG Job Mon MIB).
                          (id-val-job-state-completed)
                This is a type 2 enum."
    SYNTAX     INTEGER {
                   other(1),
                   unknown(2),       
                   created(3),       
                   pending(6),
                   processing(7),    
                   interrupted(8),
                   retained(11),
                   held(12),
                   paused(13),       
                   terminating(14),
                   completed(17),
                   printing(18)      
               }
XcmJMJobStateReasons ::= TEXTUAL-CONVENTION
    STATUS     current
    DESCRIPTION
        "This representation is bit-encoded, so that multiple reasons
        can occur at once.  Each bit corresponds to an ISO DPA OID for
        the same reason.  The MIB enum value is given by:
                value = 2 ** (last arc of DPA id-val-reasons-xxx OID -1)
                id-val-reasons-documents-needed = 1.0.10175.1.6.19.1
        See the Xerox Job Model Specification, Phase 1 or later for the
        specification of which job-state-reasons values may be used with
        which job states.
        ISO DPA:   Job-state-reasons
        This attribute identifies the reason or reasons that the job is
        in the held, [processing,] terminating, retained, or completed
        state.  The server shall indicate the particular reason(s) by
        setting the value of the job-state-reasons attribute.  When the
        job is not in any of these states, the server shall set the
        value of the job-state-reasons attribute to the empty set.
        The following standard values are defined:
        jobIncoming                       0x1
            The job has been accepted by the server or device, but the
            server or device is expecting (1) additional operations from
            the client to finish creating the job and/or (2) is
            accessing/accepting document data.
            NOTE - this reason has been renamed from the ISO DPA
            'documents-needed' to the IPP 'job-incoming' which has been
            generalized to include the condition before the job has been
            closed by the client.  (id-val-reasons-documents-needed)
        jobHoldSet                        0x2
            The value of the job's job-hold attribute is TRUE.  (id-val-
            reasons-job-hold-set)
        jobProcessAfterSpecified          0x4
            The value of the job's job-process-after attribute has
            specified a time specification that has not yet occurred.
            Renamed from ISO DPA job-print-after-specified.  (id-val-
            reasons-job-process-after-specified)
        requiredResourcesNotReady         0x8
            At least one of the resources needed by the job, such as
            media, fonts, resource objects, etc., is not ready on any of
            the physical device's for which the job is a candidate.
            (id-val-reasons-required-resources-not-ready)
        successfulCompletion              0x10
            The job completed successfully.  (id-val-reasons-successful
            completion)
        completedWithWarnings             0x20
            The job completed with warnings.  (id-val-reasons-completed-
            with-warnings)
        completedWithErrors               0x40
            The job completed with errors (and possibly warnings too).
            (id-val-reasons-completed-with-errors)
        cancelledByUser                   0x80
            The job was cancelled by the user using the CancelJob
            request.  (id-val-reasons-cancelled-by-user)
        cancelledByOperator               0x100
            The job was cancelled by the operator using the CancelJob
            request.  (id-val-reasons-cancelled-by-operator)
        abortedBySystem                   0x200
            The job was aborted by the system.  (id-val-reasons-aborted-
            by-system)
        logfilePending                    0x400
            The job's logfile is pending file transfer.  (id-val-
            reasons-logfile-pending)
        logfileTransferring               0x800
            The job's logfile is being transferred.  (id-val-reasons-
            logfile-transferring)
        The following bits are from IPP (and start at the high end of
        the bits definitions):
        jobOutgoing                       0x40000000
            Configuration 2 only:  The server is transmitting the job to
            the device.
        The remaining bits are reserved for future standardization and
        shall not be used by conforming implementations.
This is the equivalent of a type 2 enum."
    SYNTAX      INTEGER(0..2147483647)  
XcmJMJobXStateReasons ::= TEXTUAL-CONVENTION
    STATUS     current
    DESCRIPTION
        "This representation is bit-encoded, so that multiple reasons
        can occur at once.  Each bit corresponds to a Xerox OID for
        the same Xerox extension to the ISO DPA job state reason.
        In a DPA protocol, the DPA and Xerox OID can be intermixed.
        But in a bit encoded SNMP information object, we need to
        keep the bit encodings separate.
        The MIB enum value is given by:
            value = 2 ** (last arc of Xerox xid-val-reasons-xxx OID)
            xid-val-reasons-cascaded = 1.2.840.113550.1.6.19.0
            The last arc is shown in parens in the description.
        ISO DPA:   Job-state-reasons
        This attribute identifies the reason or reasons that the job is
        in the held, [processing] terminating,
        retained, or completed state.  The server shall indicate the
        particular reason(s) by setting the value of the
        job-state-reasons [xcmJobStateReasons, xcmJobXStateReasons,
        and xcmX2StateReasons objects] attribute.  When the job is not
        in any of these states, the server shall set the value of the
        job-state-reasons attribute to the empty set.
        The following values are defined as Xerox extensions.  The
        specification is copied from the Xerox Job Model, Phase 1,
        updated to version 0.67, 12/20/96.
        NOTE: In the Xerox Job Model, the acronym JSP stands for Job
        Service Provider.  In ISO DPA and this MIB the term server is
        used equivalently to JSP.
        The extensions defined by Printxchange:
        cascaded                          0x1
            (0) After the outbound gateway retrieves all job and
            document attributes and data, it stores the information into
            a spool directory.  Once it has done this, it sends the
            supervisor a job-processing event with this job-state-reason
            which tells the supervisor to transition to a new job state.
        deletedByAdministrator            0x2
            (1) The administrator has issued a Delete operation on the
            job or a Clean operation on the server or queue containing
            the job; therefore the job may have been cancelled before or
            during processing, and will have no retention-period or
            completion-period.
        discardTimeArrived                0x4
            (2) The job has been deleted (cancelled with the job-
            retention-period set to 0) due to the fact that the time
            specified by the job's job-discard-time has arrived [if the
            job had already completed, the only action that would have
            occurred is that the job-retention-period would be set to 0
            and the job is deleted].
        postprintFailed                   0x8
            (3) The post-processing agent failed while trying to log
            accounting attributes for the job; therefore the job has
            been placed into retained state for a system-defined period
            of time (Printxchange, 5 minutes), so the administrator can
            examine it, resubmit it, etc.  The post-processing agent is
            a plug-and-play mechanism which the system and the customer
            uses to add functionality that is executed after a job has
            finished processing.
        submissionInterrupted             0x10
            (4) Indicates that the job was not completely submitted for
            the following reasons: (1) the server has crashed before the
            job was closed by the client.  The server shall put the job
            into the completed state (and shall not process the job).
            (2) the server or the document transfer method has crashed
            in some non-recoverable way before the document data was
            entirely transferred to the server.  The server shall put
            the job into the completed state (and shall not process the
            job). (3) the client crashed or failed to close the job
            before the time-out period (Printxchange, 20 minutes). The
            server shall close the job and put the job into the held
            state with job-state-reasons of submission-interrupted and
            job-hold-set and with the job's job-hold attribute set to
            TRUE.  The user may release the job for scheduling by
            issuing the ReleaseJob operation.
        maxJobFaultCountExceeded          0x20
            (5) The job has been faulted and returned by the server
            several times and that the job-fault-count exceeded the
            device's (or server's, if not defined for the device) cfg-
            max-job-fault-count.  The job is automatically put into the
            held state regardless of the hold-jobs-interrupted-by-
            device-failure attribute. This job-state-reasons value is
            used in conjunction with the job-interrupted-by-device-
            failure value.
        Job timed-out while processing (optional):
        Implementation option:  The following values of job-state-
        reasons are derived from ISO DPA printer states for use when the
        system moves a processing job to the held state because a site-
        settable time-out condition was exceeded while the job was in
        the processing state:
        devicesNeedAttentionTimeOut       0x40
            (6) One or more document transforms that the job is using
            needs human intervention in order for the job to make
            progress, but the human intervention did not occur within
            the site-settable time-out value and the JSP has
            transitioned the job to the held state.
        needsKeyOperatorTimeOut           0x80
            (7) One or more devices or document transforms that the job
            is using need a specially trained operator (who may need a
            key to unlock the device and gain access) in order for the
            job to make progress, but the key operator intervention did
            not occur within the site-settable time-out value and the
            JSP has transitioned the job to the held state.
        jobStartWaitTimeOut               0x100
            (8) The JSP has stopped the job at the beginning of
            processing to await human action, such as installing a
            special cartridge or special non-standard media, but the job
            was not resumed within the site-settable time-out value and
            the JSP has transitioned the job to the held state.
            Normally, the job is resumed by means outside the job model,
            such as some local function on the device.
        jobEndWaitTimeOut                 0x200
            (9) The JSP has stopped the job at the end of processing to
            await human action, such as removing a special cartridge or
            restoring standard media, but the job was not resumed within
            the site-settable time-out value and the JSP has
            transitioned the job to the retained state.  Normally, the
            job is resumed by means outside the job model, such as some
            local function on the device, whereupon the job shall
            transition immediately to the terminating state.
        jobPasswordWaitTimeOut            0x400
            DEPRECATED: (10) The JSP has stopped the job at the
            beginning of processing to await input of the job's
            password, but the human intervention did not occur within
            the site-settable time-out value and the JSP has
            transitioned the job to the held state.  Normally, the
            password is input and the job is resumed by means outside
            the job model, such as some local function on the device.
            This value is DEPRECATED because the JSP shall move Secure
            Jobs from processing to held when they are the next to run
            and set the jobPasswordWait job-state-reason, so that the
            device is not blocked.
        deviceTimedOut                    0x800
            (11) A device that the job was using has not responded in a
            period specified by the device's site-settable device-
            timeout-period attribute (In ISO DPA the printer's printer-
            timeout-period attribute).
        connectingToDeviceTimeOut         0x1000
            (12) The JSP is attempting to connect to one or more devices
            which may be dial-up, polled, or queued, and so may be busy
            with traffic from other systems, but JSP was unable to
            connect to the device within the site-settable time-out
            value and the JSP has transitioned the job to the held state
        Reasons used when the job is in processing state:
        The following values for the job-state-reasons attribute have
        been added by the Job Model team to give requesters feedback
        about the job when the job is in the processing state:
        transferring                      0x2000
            (13) The job is being transferred to a down stream server or
            device.
        queueInDevice                     0x4000
            (14) The job has been queued in a down stream server or
            device.
        jobCleanup                        0x8000
            (15) The JSP is performing cleanup activity as part of
            ending normal processing.
        processingToStopPoint             0x10000
            (16) The requester has issued an InterruptJob operation and
            the JSP is processing up until the specified stop point
            occurs.
        Other reasons added by the Xerox Job Model:
        The following values for the job's job-state-reasons attribute
        have been added by the Xerox Job Model team:
        jobPasswordWait                   0x20000
            (17) Either:
            (1) The JSP has selected the Secure Job to be next to
            process, but instead of assigning resources and starting the
            job processing, the JSP has transitioned the job to the held
            state to await entry of a password (and dispatched another
            job, if there is one) OR
            (2) the JSP has interpreted (ripped) the Secure Job and the
            marker is scheduled separately, so that the JSP transitions
            the job to the held state to await entry of a password (and
            dispatched another job, if there is one).
            The user resumes the job either locally or by issuing a
            ReleaseJob supplying a job-password=secret-code input
            parameter that SHALL match the job's job-password attribute.
        validating                        0x40000
            (18) The job is validating the job after a CreateJob
            operation.  The job state may be creating, held, pending, or
            processing.
        queueHeld                         0x80000
            (19) The operator has held the entire queue by means outside
            the scope of the Job model.
        jobProofWait                      0x100000
            (20) The job has produced a single proof copy and is in the
            held state waiting for the requester to issue the ReleaseJob
            operation to release the job to print normally, obeying the
            job-copies and copy-count job and document attributes that
            were originally submitted.
        heldForDiagnostics                0x200000
            (21) The system is running intrusive diagnostics, so the all
            jobs are being held.
        serviceOffLine                    0x400000
            (22) The service/document transform is off-line and
            accepting no jobs.  All pending jobs are put into the held
            state.  This could be true if its input is impaired or
            broken.
        noSpaceOnServer                   0x800000
            (23) The job is held because there is no room on the server
            to store all of the job.  For example, there is no room for
            the document data or a scan-to-file job.
        pinRequired                       0x1000000
            (24) The device requires that a pin be entered in order to
            proceed, because the PIN was not supplied with the document
            or job.
        exceededAccountLimit              0x2000000
            (25) The account for which this job is drawn has exceeded
            its limit.  This condition should be detected before the job
            is scheduled so that the user does not wait until his/her
            job is scheduled only to find that the account is overdrawn.
            This condition may also occur while the job is processing
            either as processing begins or part way through processing.
            An overdraft mechanism should be included to be user-
            friendly, so as to minimize the chances that the job cannot
            finish or that media is wasted.  For example, the JSP should
            finish the current copy for a job with collated document
            copies, rather than stopping in the middle of the current
            document copy.
        jobHeldForRetry                   0x4000000
            (26) The job encountered some errors that the JSP could not
            recover from with its normal retry procedures, but the error
            is worth trying the job later, such as phone number busy or
            remote file system in-accessible.  For such a situation, the
            JSP shall add the held-for-retry value to the job's job-
            state-reasons attribute and transition the job from the
            processing to the held (via the evaluate-hold internal
            momentary state), rather than to the retained state.
        The remaining bits are reserved for future standardization and
        shall not be used by conforming implementations.
        This is the equivalent of a type 2 enum."
    SYNTAX      INTEGER(0..2147483647)  
XcmJMJobX2StateReasons ::= TEXTUAL-CONVENTION
    STATUS     current
    DESCRIPTION
        "This representation is bit-encoded, so that multiple reasons
        can occur at once.  Each bit corresponds to a Xerox OID for
        the same Xerox extension to the ISO DPA job state reason.
        In a DPA protocol, the DPA and Xerox OID can be intermixed.
        But in a bit encoded SNMP information object, we need to
        keep the bit encodings separate.  XcmJMJobX2StateReasons
        provides an additional 31 bits for Xerox extensions in addition
        to the 31 bits provided for by XcmJMJobXStateReasons.
        The MIB enum value is given by:
            value = 2 ** (last arc of Xerox xid-val-reasons-xxx OID -30)
            xid-val-reasons-xxx = 1.2.840.113550.1.6.19.30
        jobPrinting                       0x1
        (30) At least one of the output device to which the job is
            assigned is marking media. This value is useful for servers
            and output devices which spend a great deal of time
            processing (1) when no marking is happening and then want to
            show that marking is now happening or (2) when the job is in
            the process of being canceled or aborted while the job
            remains in the 'processing' state, but the marking has not
            yet stopped so that impression or sheet counts are still
            increasing for the job.
            This job-state-reason value is defined in the PWG Job
            Monitoring MIB and IPP.  It has been generalized here for
            jobs that use more than one device.
            This job-state-reason value should be used instead of the
            'printing' which has been deprecated in this MIB (and is
            recommended against in ISO DPA in a corrigenda).
        jobInterpreting                   0x2
            (31) The job is interpreting document data.
            This job-state-reason value is defined in the PWG Job
            Monitoring MIB and IPP.  It has been generalized here for
            jobs that use more than one device and for devices that can
            be interpreting more than one job at a time.
        jobScanning                       0x4
            (32) At least one of the input devices to which the job is
            assigned is scanning document data.
        jobFaxReceiving                   0x8
            (33) At least one of the FAX devices to which the job is
            assigned is receiving FAX document data.
        jobFaxSending                     0x10
            (34) At least one of the FAX devices to which the job is
            assigned is sending FAX document data.
        jobFileReceiving                  0x20
            (35) The job is receiving files or document data.
        jobFileSending                    0x40
            (36) The job is sending files or document data.
        jobMailReceiving                  0x80
            (37) The job is receiving electronic mail document data.
        jobMailSending                    0x100
            (38) The job is sending electronic mail document data.
            value = 2 ** (30 - last arc of PSIS pid-val-reasons-xxx OID)
            pid-val-reasons-cancelled-by-shutdown =
                1.2.826.0.1050.8.1.6.19.0
        NOTE: the Xerox extensions to DPA work from right to left and
        X/Open PSIS extensions work from left to right, avoiding the
        sign bit.
        The remaining bits (in the middle) are reserved for future
        standardization and shall not be used by conforming
        implementations.
        The following PSIS bits are defined using the PSIS extensions to
        ISO DPA starting with the left-most bit, not counting the sign
        bit.  These definitions are taken from the August 28, 1995,
        version 5.0 of the X/Open PSIS specification.  [Text in brackets
        indicates additions and clarifications made for the Job
        Monitoring MIB.]
        cancelledByShutdown               0x40000000
            the job was cancelled because the server or device was
            shutdown before completing the job.  The job shall be placed
            in the pending state [if the job was not started, else the
            job shall be placed in the terminating state].
        deviceUnavailable                 0x20000000
            This job was aborted by the system because the device is
            currently unable to accept jobs.  This reason [shall be]
            used in conjunction with the reason aborted-by-system. The
            job shall be placed in the pending state.
        wrongDevice                        0x10000000
            This job was aborted by the system because the device is
            unable to handle this particular job; the spooler should try
            another device.  This reason [shall be] used in conjunction
            with the reason aborted-by-system.  The job shall be pending
            if the queue contains other physical devices that the job
            could process on, and the spooler is capable of not sending
            the job back to a physical device that has rejected the job
            for this job-state-reasons value.  Otherwise, [the job]
            shall be retained.
        badJob                            0x8000000
            This job was aborted by the system because this job has a
            major problem[, such as an ill-formed PDL]; the spooler
            should not even try another printer.  This reason [shall be]
            used in conjunction with the reason aborted-by-system. The
            job shall be placed in the [terminating] state.
        jobInterruptedByDeviceFailure     0x4000000
            The device or supervisor failed while the job was
            [processing/]printing.  The spooler is keeping the job in
            the held state until an operator can determine what to do
            with the job.
        This is the equivalent of a type 2 enum."
    SYNTAX      INTEGER(0..2147483647)  
XcmJMDocType ::= TEXTUAL-CONVENTION
    STATUS     current
    DESCRIPTION
        "Jobs contain contained-documents.  Contained-documents may be
        printable, font, or resource objects.  This had
        been deleted due to object deletions from 41jobmon.mib, but
        has been restored along with those objects.
        ISO DPA:   Document-type
        The following standard values are defined:
        printable    Specifies that this document is to be printed on
                     the assigned printer.  (id-val-document-type-
                     printable)
        font         Specifies that this document is a font resource
                     which may be required by one or more of the
                     printable documents associated with the print-
                     job.  See the font object class.  (id-val-
                     document-type-font)
        resource     Specifies that this document contains resource
                     data, of some type other than font, which may be
                     required to print one or more of the printable
                     documents associated with the print-job.  See
                     the resource object class.  (id-val-document-
                     type-resource)
        This is a type 2 enum."
    SYNTAX     INTEGER {
                   other(1),
                   unknown(2),
                   printable(3),    
                   font(4),         
                   resource(5)      
               }
XcmJMDocFileNameType ::= TEXTUAL-CONVENTION
    STATUS     current
    DESCRIPTION
        "The type of file name syntax from which a document is
        obtained for an output job, such as print, or for which a
        document is produced for an input job, such as scan-
        to-file.  The file name syntax types are taken from ISO DPA
        for the DistinguishedNameStringSyntax data type.  This had
        been deleted due to object deletions from 41jobmon.mib, but
        has been restored along with those objects.
        ISO DPA:   distinguished-name-syntax
        The following standard values are defined:
        automatic   server recognizes the syntax
        X-500       ISO 9594 Directory Service
        XFN         X/OPEN Federated Names
        DCE         Distributed Computing Environment
                    includes X.500 and CDS
        CDS         Cell Directory Service - part of DCE
        NIS         Network Information Service
        DNS         Domain Name Service
        DEC-NS      Digital Name Service
        Internet-mail Internet Mail address
        XNS         Xerox Network System
        Bindery     Bindery
                    example: FILE_SERVER_NAME\OBJECT_NAME
        NDS         Novell Directory Service
                    example: .objectName.container.organization or
                    .cn=objectName.ou=container.o=organization
        URL         HTTP Universal Resource Locator
                    examples:
                    http://www.organization-name.org/homepage.htm
                    ftp://ftp-out.external.hp.com/snmpmib/dpa/dpa-00.doc
        POSIX       POSIX file name (ISO 9945-1)  
        UNIX        UNIX(TM) file name
        OS/2        OS/2 file name
        PC-DOS      PC DOS file name
        NT          NT file name
        MVS         MVS file name
        VM          VM file name
        OS/400      OS/400 file name
        VMS         VMS file name
        UNC         Microsoft Universal Name Convention
                    example:
                    \\fileservername\volume\filepath\filename.ext
        NetWare     NetWare file path name
                    example: servername\volume\filepath\filename.ext
        This is a type 2 enum."
    SYNTAX     INTEGER {
                   other(1),
                   unknown(2),
                   fntAutomatic(3),
                   fntX500(4),
                   fntXFN(5),
                   fntDCE(6),
                   fntCDS(7),
                   fntNIS(8),
                   fntDNS(9),
                   fntDECNS(10),
                   fntInternetMail(11),
                   fntXNS(12),
                   fntBindery(13),
                   fntNDS(14),        
                   fntURL(15),        
                   fntPOSIX(23),    
                   fntUNIX(24),
                   fntOS2(25),
                   fntPCDOS(26),
                   fntNT(27),
                   fntMVS(28),
                   fntVM(29),
                   fntOS400(30),
                   fntVMS(31),
                   fntUNC(32),        
                   fntNetWare(33)     
               }
XcmJMDocState ::= TEXTUAL-CONVENTION
    STATUS     current
    DESCRIPTION
        "The following standard values are defined for the state of
        contained-documents:
        transferPending
            The server has created the document object, but the data
            transfer of the document data has not started or completed
            (id-val-document-state-transfer-pending)
        pending
            The server has received the document data and the document
            is waiting for processing to begin.  The job may already be
            in the processing state, if the job's job-scheduling
            attribute is not after-complete (see the current-job-state
            and job-scheduling job attributes.  (id-val-document-state-
            pending)
        processing
            The server has started processing this document, or has made
            the document ready for processing by a device, but the
            device is not yet processing it, either because the document
            hasn't reached the device or because the document is queued
            in the device or some other spooler, awaiting the device to
            process it, or the device has finished processingthe
            document and some additional processing is needed, such as
            image processing after scanning.  (id-val-document-state-
            processing)
        printing
            The server has completed processing the document and the
            output device is currently printing the document on at least
            one printer. That is, a print engine is either printing
            pages of the document, or failing in its attempt to print
            pages of the document because of some wait state, such as,
            start-wait, end-wait, needs-attention, etc.  The complete
            document state includes the detailed status represented in
            the devices' device-state attribute(s).
        NOTE: Other job-service-type-specific states will be added in
        the future, such as scanning.
        completed
            The server has completed this document.  The job may still
            be in the processing state, or may be in the retained state.
            The job shall move to the retained state when all documents
            are completed (id-val-document-state-completed)
        This is a type 2 enum."
    SYNTAX     INTEGER {
                   other(1),
                   unknown(2),
                   transferPending(3),
                   pending(4),
                   processing(5),
                   completed(6),
                   printing(7)
               }
XcmJMDocOutputMethod ::= TEXTUAL-CONVENTION
    STATUS     current
    DESCRIPTION
        "This object is bit coded, so that multiple document output
        requests may be made for the document.  Each bit corresponds to
        one of the ISO DPA output OIDs.
        ISO DPA:   Output
        This attribute identifies the output processing for the media
        on which the document is to be printed.
        The following standard values are defined.  The value of the
        bit is given by the formula:
           bit value = 2 ** (last OID arc)
           id-val-output-page-collate = 1.0.10175.1.6.115.0
        pageCollate                       0x1
            This value specifies that the pages of a document are to be
            in sequence, when multiple copies of the document are
            specified by the copy-count attribute (possibly up to some
            implementation-defined maximum number of copies). Whether
            this effect is achieved by placing copies of the document in
            multiple output bins or in the same output bin with
            implementation-defined document separation is
            implementation-dependent. Also whether it is achieved by
            making multiple passes over the document or by using an
            output sorter is implementation-dependent.
            Either pageCollate or noPageCollate shall be set, but not
            both.  If both pageCollate and noPageCollate are set, the
            noPageCollate value shall be ignored.  (id-val-output-page-
            collate)
        noPageCollate                     0x2
            This value specifies that the copies of the pages of a
            document are to follow one another when multiple copies are
            specified by the copy-count attribute. That is, if 3 copies
            are specified, three copies of page 1 are printed then three
            copies of page 2, etc., and no collating of these pages is
            desired. This may be useful in some implementations where
            multiple copies requires re-interpretation of the document
            format and the document contains some compute intensive
            pages (such as images)  (id-val-output-no page-collate)
        decollate                         0x10
            The parts of a multi-part form are to be separated and
            sorted into stacks for each part.
        Either decollate or noDecollate shall be set, but not both.  If
        both decollate and noDecollate are set, the noDecollate value
        shall be ignored.  (id-val-output-decollate)
        noDecollate                       0x20
            The parts of a multi-part form are to remain intact  (id-
            val-output-no decollate)
        burst                             0x40
            Continuous media is to be separated into individual sheets,
            generally by bursting along perforations.
        Either burst or noBurst shall be set, but not both.  If both
        burst and noBurst are set, the noBurst value shall be ignored.
        (id-val-output-burst)
        noBurst                           0x80
            Continuous media is to remain continuous, no bursting is
            desired  (id-val-output-no burst)
        stackingDefault                   0x400
            A site-defined output-stacking operation is to be applied
            (id-val-output-stacking-default)
        This is the equivalent of a type 2 enum."
    SYNTAX    INTEGER(0..65535)
XcmJMGroupSupport ::= TEXTUAL-CONVENTION
    STATUS      current
    DESCRIPTION
        "The terse conformance statement of ALL mandatory, conditionally
        mandatory, and optional XCMI Job Monitoring MIB groups
        supported by this management agent implementation (i.e.,
        version) on this host system, specified in a bit-mask.
        The current set of values (which may be extended in the future)
        is given below:
              1 : xcmJMBaseGroup                   
              2 : xcmJMJobGenBasicGroup            
              4 : xcmJMDevicesAssignedGroup        
              8 : xcmJMClientIdMapGroup            
             32 : xcmJMJobGenExtGroup              
            128 : xcmJMDocGenBasicGroup            
            256 : xcmJMDocPrintExtGroup            
            512 : xcmJMJobGenSpoolingBasicGroup    
           1024 : xcmJMJobGenSpoolingExtGroup      
           2048 : xcmJMJobGenAccountingBasicGroup  
           4096 : xcmJMMediaConsumedGroup          
           8192 : xcmJMColorImpsConsumedGroup      
          16384 : xcmJMJobAlertGroup               
          32768 : xcmJMDocAlertGroup               
          65536 : xcmJMJobImpsByMediumSizeGroup    
        Note: The following had been deprecated, but have been made
        current starting with version 4.00: xcmJMJobGenExtGroup,
        xcmJMJobGenSpoolingBasicGroup, xcmJMJobGenAccountingBasicGroup,
        xcmJMMediaConsumedGroup, and xcmJMJobImpsByMediumSizeGroup.
        The following had been deleted, but are restored as of version
        4.01: xcmJMDocGenBasicGroup, xcmJMDocPrintExtGroup,
        xcmJMJobGenSpoolingExtGroup, xcmJMColorImpsConsumedGroup,
        and xcmJMDocAlertGroup.
        The following were deleted in v2.51:
        xcmJMJobStateMsgGroup and xcmJMJobTreeBasicGroup.
        Usage:  Conforming management agents shall ALWAYS accurately
        report their support for XCMI Job Monitoring MIB groups."
    SYNTAX        INTEGER(0..2147483647)  
XcmJMImpsCountType ::= TEXTUAL-CONVENTION
    STATUS      current                
    DESCRIPTION "
        The recognized impression counting types for impressions
        produced by the jobs.
        The following standard values are defined for the count-type.
        total count
                Count all impressions.
        black and white count
                Count impressions requiring only black colorant.
        highlight color count
                Count impressions requiring black plus one other
                colorant.
        full color count
                Count impressions requiring 3 or more colorants.
        one visible color count
                Count impressions for which one visible color is
                printed.  This is determined when a printer driver
                converts a document to PDL formatted data.  This is
                related in a specific accounting method rather than
                consumed colorants.  The differentiation between a
                'one visible color' impression from an impression of
                another type is device dependent, i.e., a device might
                consider 'one visible', 'black and white', and
                'highlight' to be three different types.
        limited visible color count
                Count impressions for which multiple visible colors are
                printed, but when the impression should not be
                considered 'full color'.  This is determined when a
                printer driver converts a document to PDL formatted
                data.  This is related in a specific accounting method
                rather than consumed colorants.  The choice of a number
                of colors that differentiates a 'limited color'
                impression from a 'full color' (or other type of)
                impression is device dependent.
        one colorant count
               Count impressions on which any one colorant is used,
                whether black or any other color.
        two colorant count
                Count impressions on which any two colorants are used,
                whether or not black is used.
        three colorant count
                Count impressions on which any three colorants are
                used, whether or not black is used.
        four colorant count
                Count impressions on which any four colorants are used,
                whether or not black is used.
     NOTE: Other count-type may be added in the future according to
           the requirements of accounting services."
    SYNTAX INTEGER {
                other(1),
                totalCount(4),
                blackAndWhiteCount(5),
                highlightColorCount(6),
                fullColorCount(7),
                oneVisibleColorCount(11),
                limitedVisibleColorCount(19),
                oneColorantCount(21),
                twoColorantCount(22),
                threeColorantCount(23),
                fourColorantCount(24)
                }
XcmJMMediumType ::= TEXTUAL-CONVENTION
    STATUS     current             
    DESCRIPTION
        "The recognized types of media.
        NOTE: For this MIB, these values are enums, instead of
        strings.  This departure from the IETF Printer MIB where
        medium-types are strings is so that the medium types can be more
        easily localized.  Also the xcmJMMediaConsumedGroup accounting
        group also has the media names as string values so that
        accounting systems can use either the enum type or the medium
        name.
        ISO DPA:   Medium-type
        This attribute identifies the type of this medium. (e.g.
        stationery, envelope, transparency, etc.)
        The following standard values are defined:
        stationery
            Separately cut sheets of an opaque material  (id-val-medium-
            type-stationery)Sometimes called 'standard'.
        transparency
            Separately cut sheets of a transparent material  (id-val-
            medium-type-transparency)
        envelope
            Envelopes that can be used for conventional mailing purposes
            (id-val-medium-type-envelope)
        envelopePlain
            Envelopes that are not pre-printed and have no windows  (id-
            val-medium-type-envelope-plain)
        envelopeWindow
            Envelopes that have windows for addressing purposes  (id-
            val-medium-type-envelope-window)
        continuousLong
            Continuously connected sheets of an opaque material
            connected along the long edge  (id-val-medium-type-
            continuous-long)
        continuousShort
            Continuously connected sheets of an opaque material
            connected along the short edge  (id-val-medium-type-
            continuous-short)
        tabStock
            Media with tabs  (id-val-medium-type-tab)
        multiPartForm
            Form medium composed of multiple layers not pre-attached to
            one another;  each sheet may be drawn separately from an
            input source  (id-val-medium-multi-part-form)
        labels
            Label-stock  (id-val-medium-labels)
        multiLayer
            Form medium composed of multiple layers which are pre-
            attached to one another, e.g. for use with impact printers
            (id-val-medium-type-multi-layer).
        The following are additional types that are being proposed to
        ISO DPA and so continue with the same enum and OID assignments:
        prePrinted
            pre-printed medium, other than letterhead
        letterhead
            pre-printed letterhead
        coverStock
            cover medium
        The following are additional types that are orthogonal to media-
        type and so will not be proposed to ISO DPA as additional media-
        type.  Instead, these will be proposed as separate attributes of
        the medium object.
        Therefore, they will be assigned as Xerox extension bits for use
        in the Job Monitoring MIB:
        drilled
            Medium with holes. (Corresponds to the existing ISO DPA
            medium-holes attribute)
        coated
            Medium with some coating. (Will be proposed to ISO DPA as a
            separate medium object attribute, possibly Boolean).
        recycled
            recycled medium.  (Will be proposed to ISO DPA as a separate
            medium object attribute, possibly Boolean).
        heavyWeight
            heavy-weight medium.  (Corresponds to the existing ISO DPA
            medium-weight attribute).
        This is a type 2 enum."
    SYNTAX     INTEGER {
                   other(1),
                   unknown(2),
                   stationery(3),       -- sometimes called "standard"
                   transparency(4),
                   envelope(5),         
                   envelopePlain(6),    
                   continuousLong(7),
                   continuousShort(8),
                   tabStock(9),
                   multiPartForm(10),
                   labels(11),
                   envelopeWindow(12),  
                   multiLayer(13),
                   prePrinted(14),
                   letterhead(15),
                   coverStock(16),
                   drilled(100),
                   coated(101),
                   recycled(102),
                   heavyWeight(103)
               }
--
--
--
xCmJobMonTCDummy     OBJECT IDENTIFIER ::= { xcmJobMonTC 999 }
xCmJobMonTCJobServiceTypeOID OBJECT-TYPE
    SYNTAX      XcmJMJobServiceTypeOID
    MAX-ACCESS  not-accessible
    STATUS      current
    DESCRIPTION "Dummy - DO NOT USE"
    ::= { xCmJobMonTCDummy 1 }
xCmJobMonTCJobState OBJECT-TYPE
    SYNTAX      XcmJMJobState
    MAX-ACCESS  not-accessible
    STATUS      current
    DESCRIPTION "Dummy - DO NOT USE"
    ::= { xCmJobMonTCDummy 2 }
xCmJobMonTCJobStateReasons OBJECT-TYPE
    SYNTAX      XcmJMJobStateReasons
    MAX-ACCESS  not-accessible
    STATUS      current
    DESCRIPTION "Dummy - DO NOT USE"
    ::= { xCmJobMonTCDummy 3 }
xCmJobMonTCJobXStateReasons OBJECT-TYPE
    SYNTAX      XcmJMJobXStateReasons
    MAX-ACCESS  not-accessible
    STATUS      current
    DESCRIPTION "Dummy - DO NOT USE"
    ::= { xCmJobMonTCDummy 4 }
xCmJobMonTCJobX2StateReasons OBJECT-TYPE
    SYNTAX      XcmJMJobX2StateReasons
    MAX-ACCESS  not-accessible
    STATUS      current
    DESCRIPTION "Dummy - DO NOT USE"
    ::= { xCmJobMonTCDummy 5 }
xCmJobMonTCDocType OBJECT-TYPE
    SYNTAX      XcmJMDocType
    MAX-ACCESS  not-accessible
    STATUS      current
    DESCRIPTION "Dummy - DO NOT USE"
    ::= { xCmJobMonTCDummy 6 }
xCmJobMonTCDocFileNameType OBJECT-TYPE
    SYNTAX      XcmJMDocFileNameType
    MAX-ACCESS  not-accessible
    STATUS      current
    DESCRIPTION "Dummy - DO NOT USE"
    ::= { xCmJobMonTCDummy 7 }
xCmJobMonTCDocState OBJECT-TYPE
    SYNTAX      XcmJMDocState
    MAX-ACCESS  not-accessible
    STATUS      current
    DESCRIPTION "Dummy - DO NOT USE"
    ::= { xCmJobMonTCDummy 8 }
xCmJobMonTCDocOutputMethod OBJECT-TYPE
    SYNTAX      XcmJMDocOutputMethod
    MAX-ACCESS  not-accessible
    STATUS      current
    DESCRIPTION "Dummy - DO NOT USE"
    ::= { xCmJobMonTCDummy 9 }
xCmJobMonTCGroupSupport OBJECT-TYPE
    SYNTAX      XcmJMGroupSupport
    MAX-ACCESS  not-accessible
    STATUS      current
    DESCRIPTION "Dummy - DO NOT USE"
    ::= { xCmJobMonTCDummy 10 }
xCmJobMonTCImpsCountType OBJECT-TYPE
    SYNTAX      XcmJMImpsCountType
    MAX-ACCESS  not-accessible
    STATUS      current                
    DESCRIPTION "Dummy - DO NOT USE"
    ::= { xCmJobMonTCDummy 11 }
xCmJobMonTCMediumType OBJECT-TYPE
    SYNTAX      XcmJMMediumType
    MAX-ACCESS  not-accessible
    STATUS      current                
    DESCRIPTION "Dummy - DO NOT USE"
    ::= { xCmJobMonTCDummy 12 }
xcmJobMonMIB OBJECT-IDENTITY -- MODULE-IDENTITY
    STATUS   current
        DESCRIPTION "
            File:     41jobmon.dfm, .mib, .txt, .pdf
            Version:  4.03.pub
            This MIB specifies job and document objects for
            monitoring print jobs, including accounting, of print
            jobs.  This MIB does not provide for management and
            control of print jobs, such as cancelling or modifying
            them.  If job control is desired, another MIB that
            augments this one should be developed.
            The groups in this MIB are arranged so that an
            additional MIB may be developed that supports monitoring
            of multifunction jobs (print, scan, FAX, etc.),
            including scan-only jobs.  Such a MIB is intended to
            augment this MIB.  See the companion Job Monitoring MIB
            textual conventions module: XEROX-JOB-MONITORING-TC for
            the textual conventions and for an explanation of the
            use of this MIB (see file 40jobtc.txt).
            The specification for many of the objects in this MIB is
            taken directly from the ISO 10175 Document Printing
            Application (DPA) standard, clause 9.2, Job Attributes
            and clause 9.3, Document Attributes.  Such direct
            inclusions are explicitly indicated.  However, this MIB
            is intended to be used with non-DPA implementations, so
            only a small set of general DPA attributes have been
            included in the Job Monitoring MIB.  In addition, a
            single print-centric group is included.  Finally, some
            of the ISO DPA specifications have been generalized so
            that they may be used with non-print job services.  For
            example, changing the names and descriptions from
            'printer' to 'device'.  All such changes to ISO DPA text
            are indicated inside square brackets to make it clear
            how this Job Monitoring MIB differs from ISO DPA.
            Copyright 1996-2002 Xerox Corporation. All Rights Reserved.
        REFERENCES
            See 40jobtc.txt for the conformance requirements and
            textual conventions for use with this MIB module."
        ::= { xeroxCommonMIB 59 }
xcmJobZeroDummy OBJECT IDENTIFIER ::= { zeroDotZero 59 }
-- NOTE - The term "Mandatory" in this MIB, as in all MIBs, means that
-- The term "Conditionally Mandatory" in this MIB,
xcmJobMonBase        OBJECT IDENTIFIER ::= { xcmJobMonMIB 1 }
xcmJobMonBaseTable OBJECT-TYPE
    SYNTAX      SEQUENCE OF XcmJobMonBaseEntry
    MAX-ACCESS  not-accessible
    STATUS      current
    DESCRIPTION
        "A table of general counters and capabilities for ease of use
        of the XCMI Job Monitoring MIB on this host system.
        Usage:  The ONLY valid row in the 'xcmJobMonBaseTable'
        shall ALWAYS have an 'xcmJobMonBaseIndex' of one ('1')."
    ::= { xcmJobMonBase 2 }
xcmJobMonBaseEntry OBJECT-TYPE
    SYNTAX      XcmJobMonBaseEntry
    MAX-ACCESS  not-accessible
    STATUS      current
    DESCRIPTION
        "An entry of general counters and capabilities for ease of use
        of the XCMI Job Monitoring MIB on this host system.
        Usage:  The ONLY valid row in the 'xcmJobMonBaseTable'
        shall ALWAYS have an 'xcmJobMonBaseIndex' of one ('1')."
    INDEX       { xcmJobMonBaseIndex }
    ::= { xcmJobMonBaseTable 1 }
XcmJobMonBaseEntry ::= SEQUENCE {
        xcmJobMonBaseIndex             Ordinal32,
        xcmJobMonBaseRowStatus         RowStatus,
        xcmJobMonBaseVersionID         ProductID,
        xcmJobMonBaseVersionDate       DateAndTime,
        xcmJobMonBaseGroupSupport      XcmJMGroupSupport,
        xcmJobMonBaseCreateSupport     XcmJMGroupSupport,
        xcmJobMonBaseUpdateSupport     XcmJMGroupSupport
    }
xcmJobMonBaseIndex OBJECT-TYPE
    SYNTAX      Ordinal32
    MAX-ACCESS  not-accessible
    STATUS      current
    DESCRIPTION
        "A unique value used by this host system to identify this
        conceptual row in the 'xcmJobMonBaseTable'.
        Usage:  The ONLY valid row in the 'xcmJobMonBaseTable'
        shall ALWAYS have an 'xcmJobMonBaseIndex' of one ('1')."
    ::= { xcmJobMonBaseEntry 1 }
xcmJobMonBaseRowStatus OBJECT-TYPE
    SYNTAX      RowStatus
    MAX-ACCESS  read-only
    STATUS      current
    DESCRIPTION
        "This object is used to display status of the ONLY valid
        conceptual row in the 'xcmJobMonBaseTable'.
        Usage:  'xcmJobMonBaseRowStatus' is 'read-only' because
        the ONLY valid conceptual row shall NOT be deleted."
    ::= { xcmJobMonBaseEntry 2 }
xcmJobMonBaseVersionID OBJECT-TYPE
    SYNTAX      ProductID
    MAX-ACCESS  read-only
    STATUS      current
    DESCRIPTION
        "The software product ID of the SNMP sub-agent which implements
        the XCMI Job Monitoring MIB on this host system.
        Usage:  This object shall specify the software product ID of an
        SNMP sub-agent (possibly also found in a conceptual row in the
        'hrSWRunTable' and/or 'hrSWInstalledTable' in the IETF HR MIB).
        This object shall NOT specify a particular release of the XCMI
        Job Monitoring MIB, or the whole host system product.
        Note:   Contrast with 'sysObjectID' for the whole SNMP agent in
        the IETF MIB-II (RFC 1213) and 'hrDeviceID' for the whole device
        (or whole product, in the case of 'xcmHrDevice...') in the IETF
        Host Resources MIB (RFC 1514)."
    REFERENCE
        "See:   'hrSW[Installed|Run]ID' in the Software Installed and
                Software Running groups of the IETF HR MIB (RFC 1514)."
    DEFVAL      { zeroDotZero }   
    ::= { xcmJobMonBaseEntry 3 }
xcmJobMonBaseVersionDate OBJECT-TYPE
    SYNTAX      DateAndTime
    MAX-ACCESS  read-only
    STATUS      current
    DESCRIPTION
        "The software build date of the SNMP sub-agent which implements
        the XCMI Job Monitoring MIB on this host system.
        Usage:  This object shall specify the BUILD date of the SNMP
        sub-agent software (not available elsewhere in IETF/XCMI MIBs).
        This object shall NOT specify the INSTALL date of the SNMP
        sub-agent software on this host system, nor the RESET date.
        Note:   Contrast with 'hrSWInstalledDate' in the Software
        Installed group of the IETF Host Resources MIB (RFC 1514), and
        'xcmHrDevInfoResetDate' in the Device Info group of the XCMI
        Host Resources Extensions MIB."
    REFERENCE
        "See:   'hrSW[Installed|Run]ID' in the Software Installed and
                Software Running groups of the IETF HR MIB (RFC 1514)."
    DEFVAL      { '0000000000000000'H } 
    ::= { xcmJobMonBaseEntry 4 }
xcmJobMonBaseGroupSupport OBJECT-TYPE
    SYNTAX      XcmJMGroupSupport
    MAX-ACCESS  read-only
    STATUS      current
    DESCRIPTION
        "The terse conformance statement of ALL mandatory, conditionally
        mandatory, and optional XCMI Job Monitoring MIB groups
        supported by this management agent implementation (i.e.,
        version)  on this host system, specified in a bit-mask.
        Usage:  Conforming management agents shall ALWAYS accurately
        report their support for XCMI Job Monitoring MIB groups."
    DEFVAL { 3 }                  
    ::= { xcmJobMonBaseEntry 5 }
xcmJobMonBaseCreateSupport OBJECT-TYPE
    SYNTAX      XcmJMGroupSupport
    MAX-ACCESS  read-only
    STATUS      current
    DESCRIPTION
        "The terse conformance statement of ALL mandatory, conditionally
        mandatory, and optional XCMI Job Monitoring MIB groups
        supported for dynamic row creation (via '...RowStatus')
        by this management agent implementation (i.e., version)
        on this host system, specified in a bit-mask.
        Usage:  Conforming management agents shall ALWAYS accurately
        report their support for XCMI Job Monitoring MIB groups."
    DEFVAL      { 0 }                   
    ::= { xcmJobMonBaseEntry 6 }
xcmJobMonBaseUpdateSupport OBJECT-TYPE
    SYNTAX      XcmJMGroupSupport
    MAX-ACCESS  read-only
    STATUS      current
    DESCRIPTION
        "The terse conformance statement of ALL mandatory, conditionally
        mandatory, and optional XCMI Job Monitoring MIB groups
        supported for existing row update (via SNMP Set-Request PDUs)
        by this management agent implementation (i.e., version)
        on this host system, specified in a bit-mask.
        Usage:  Conforming management agents shall ALWAYS accurately
        report their support for XCMI Job Monitoring MIB groups."
    DEFVAL      { 0 }                   
    ::= { xcmJobMonBaseEntry 7 }
--
xcmJobGenBasic  OBJECT IDENTIFIER ::= { xcmJobMonMIB 6 }
xcmJobGenBasicTable OBJECT-TYPE
    SYNTAX     SEQUENCE OF XcmJobGenBasicEntry
    MAX-ACCESS not-accessible
    STATUS     current
    DESCRIPTION
        "A table of general mandatory job information per (logical or
        physical) device that is independent of the type of device
        (printer, scanner, fax, ...) and that does not require a
        spooling implementation (though a spooling implementation shall
        also implement this group, in which case spooled jobs shall also
        appear in the job table).
        Job information applies to the job as a whole or to all its
        documents.  The specification for most objects is taken
        directly from the ISO 10175 Document Printing Application (DPA)
        standard clause 9.2, Job Attributes.  However, this MIB is
        intended to be used with non-DPA implementations, so only a
        small set of general DPA attributes have been included here."
    ::= { xcmJobGenBasic 1}
xcmJobGenBasicEntry OBJECT-TYPE
    SYNTAX     XcmJobGenBasicEntry
    MAX-ACCESS not-accessible
    STATUS     current
    DESCRIPTION
        "An entry exists in this table for each job in the device,
         no matter what the state of the job is.  Each device is
         represented as a separate device entry in the Host Resources
         MIB device table as a device of type 'printer',
         'scanner', 'fax', ....  The management station references each
         job using the xcmJobIdentifierOnSystem assigned by the
         system (printer, server, supervisor, spooler) that
         accepted the job submission (by some other protocol)."
    INDEX { hrDeviceIndex, xcmJobIdentifierOnSystem }
    ::= { xcmJobGenBasicTable 1 }
XcmJobGenBasicEntry ::= SEQUENCE {
    xcmJobIdentifierOnSystem     DisplayString,            
    xcmJobIdentifierUpstream     DisplayString,            
    xcmJobClientId               OCTET STRING,             
    xcmJobServiceType            XcmJMJobServiceTypeOID,   
    xcmJobName                   CodeIndexedStringIndex,   
    xcmJobOwner                  CodeIndexedStringIndex,   
    xcmJobSourceChannelType      XcmPrtChannelType,        
    xcmJobSubmittedLocaleIndex   Cardinal32,               
    xcmJobCurrentState           XcmJMJobState,            
    xcmJobStateReasons           XcmJMJobStateReasons,     
    xcmJobXStateReasons          XcmJMJobXStateReasons,    
    xcmJobX2StateReasons         XcmJMJobX2StateReasons    
}
xcmJobIdentifierOnSystem OBJECT-TYPE
    SYNTAX     DisplayString (SIZE(0..255))          
    MAX-ACCESS read-only
    STATUS     current
    DESCRIPTION
        "The job identifier generated on the system that the agent is
        instrumenting.  The job identifier is generated by the job
        service provider when it accepts a submit job request from a job
        service requester using whatever job submission protocol that
        the job service provider supports.
        This job identifier is for each job and sub job submitted.  The
        job service provider promote a simple job request to a compound
        job, if the job service needs access to multiple devices, such
        as a scanner and a printer or to two printers, or to a printer
        and a fax.  See the textual conventions for a more complete
        description of compound jobs.
        The xcmJobIdentifierOnSystem is used as one of the indexes into
        each job and document table, along with the HrDeviceIndex from
        the Host Resources MIB which is an index value for each
        different job service instance (analogous to each instance of a
        logical printer in ISO DPA).
        NOTE: Different jobs on different systems may have the same job
        identifier.  Additional information is needed to make the job
        identifier unique in the network, such as the server or system
        component name.
        See also xcmJobIdentifierUpstream in this group.
        ISO DPA:  Job-identifier
        This attribute provides the job-identifier for this job on the
        server.  The server shall generate a job-identifier value that
        is unique on that server, but need not be unique across the
        distributed environment.  [In other words, the server's name
        need not be part of the job-identifier.]
        The value of the job-identifier attribute shall be returned by
        the server as part of the PrintResult in the first Print
        operation for the job (see 8.2.1).  The client shall pass its
        value as part of the PrintArgument in subsequent Print
        operations for the same job."
    REFERENCE
        "See note on maximum length of trap var bind that
        xcmJobIdentifierOnSystem contributes to:
        'xcmJobV2AlertPrefixNew' in the Job Alert Group of this MIB."
    ::= { xcmJobGenBasicEntry 1 }
xcmJobIdentifierUpstream OBJECT-TYPE
    SYNTAX     DisplayString (SIZE(0..255))   
    MAX-ACCESS read-only
    STATUS     current
    DESCRIPTION
        "Uniquely identifies the job on the immediately upstream
        client, server or device as generated by that client, server or
        device.  The server or device is specified by hrDeviceIndex.
        For an agent representing a spooling system, this object is the
        identifier generated by the submitting client and hrDeviceIndex
        identifies a logical device.
        NOTE: Since multiple clients may each generate the same
        identifier for the job, the xcmJobIdentifierUpstream is not
        necessarily unique on the server.  Client implementers are
        encouraged to generate client job ids that are unique.
        In some cases, the xcmJobSourceChannelType may help to
        disambiguate client job ids.
        NOTE: This object in this MIB is a generalization of the
        corresponding ISO DPA attribute: job-identifier-on-client
        which is printer-centric.
        ISO DPA:  Job-identifier-on-client[-upstream]
        This attribute provides the job-identifier for this job to
        uniquely identify the job on the client submitting the job, and
        the value shall be assigned by that client.
        The client shall supply the value of the job-identifier-on-
        client[-upstream] attribute at the time that the client submits
        the job to the server, if such client has its own job-identifier
        for the job.
        NOTE - This attribute is intended for jobs submitted from
        legacy servers which have their own job-identifier for the job.
        If a job passes through a chain of servers between the client
        initiating the job and the output device, the value of the job
        attribute job-identifier-on-client shall be the value of the
        job's job-identifier on the immediate upstream server and the
        value of the job attribute job-identifier-on-printer[-device]
        shall be the value of the job's job-identifier on the immediate
        downstream server or printer.
        NOTE - A job has attributes for identifying itself on the
        current server, on the immediate upstream server (where the job
        came from), and on the immediate downstream server or printer
        (where the job went). These attributes are
            job-identifier               [job-identifier-on-system]
            job-identifier-on-client     [job-identifier-upstream]
            job-identifier-on-printer    [job-identifier-downstream]
        respectively."
    DEFVAL { ''H }                      
    ::= { xcmJobGenBasicEntry 2 }
xcmJobClientId OBJECT-TYPE
    SYNTAX     OCTET STRING(SIZE(0..255))
    MAX-ACCESS read-only
    STATUS     current
    DESCRIPTION
        "A client end system supplies the 'xcmJobClientId' attribute
        to clearly identify jobs which that client has submitted to the
        server.  This attribute is used as one of the indices into the
        ClientIdMap table.  There are two types of job-submitting
        clients:
          1. XCMI-conforming job submitting clients
          2. non-XCMI-conforming job submitting clients
        For XCMI-conforming job submitting clients, the 'xcmJobClientId'
        shall be a globally unique job id.  This globally unique job id
        shall be a textual string representation in standard dotted
        decimal form of an OID (used in traps related to this job
        generated by this host system).  See XcmGlobalUniqueID in the
        Xerox General textual conventions in 06gentc.mib for a
        description of the contents required for XCMI-conforming job
        submitting clients.
        For non-XCMI-conforming job submitting clients, the job id may
        be any textual string and may not necessarily be unique, even if
        the job submitter is a strictly conforming ISO DPA client.
        ISO DPA:   Job-client-id
        This attribute supplies a human-readable descriptor for the
        job.  This descriptor may be printed by the server on auxiliary
        sheets to help identify the user's printed output, and
        discriminate between different jobs.
        Use and treatment of this attribute is implementation and site
        specific.
        If the client specifies the value of the job attribute job-
        client-id, no server shall change it.  If the client does not
        specify the value of the job attribute job-client-id, the first
        server shall set it to the value of the job attribute job-
        identifier, so that no downstream server shall change it. These
        rules ensure that if an implementation prints the value of the
        job-client-id on an auxiliary sheet, it has a value that is
        meaningful to the client originally submitting the job, no
        matter how many servers the job passes through.
        For example, client A submits a job to server B and does not
        specify a value for the job attribute job-client-id.  Server B
        assigns a job-identifier of 123 to the job, and forwards this
        job to server C.  Server C assigns a job-identifier of 456 to
        the job and forwards this job to printer D.  Printer D is not a
        DPA server, but it has its own queue and assigns a job-id of
        789 to the job. The following table shows the value of the
        relevant job attributes in the two servers B and C:
                   job-         job-          job-          job-
                   client-id    identifier-   identifier    identifier-
                                on-client                   on-printer
                   -------
        server B   123          unspecified   123           456
        server C   123          123           456           789*
        * If printer D did not assign a job-id to its jobs, then the
        value of the job attribute job-identifier-on-printer for server
        C would be unspecified."
    REFERENCE
        "See note on maximum length of trap var bind that
        xcmJobClientId contributes to:
        'xcmJobV2AlertPrefixNew' in the Job Alert Group of this MIB."
    ::= { xcmJobGenBasicEntry 3 }
xcmJobServiceType OBJECT-TYPE
    SYNTAX     XcmJMJobServiceTypeOID
    MAX-ACCESS read-only
    STATUS     current
    DESCRIPTION
        "Job-service-type (ISO DPA extension)
        This attribute specifies the type of the service to which this
        job was submitted.  The value of this object is filled in by the
        job service provider, not by the job service requester,
        depending on the service-name-requested (instance) parameter
        supplied by the job service requester in the create-job
        operation.
        The value is an OBJECT IDENTIFIER, so the implementers, third
        parties, and customers can add their own service types.  Values
        are scan-to-file, scan-to-print, print, etc.
        NOTE - the Host Resources Extension MIB defines OIDs for device
        types, which are closely related to job-service-types.  However,
        job-service-types are related to one or more device types."
    DEFVAL { zeroDotZero }        
    ::= { xcmJobGenBasicEntry 4 }
xcmJobName OBJECT-TYPE
    SYNTAX     CodeIndexedStringIndex
    MAX-ACCESS read-only
    STATUS     current
    DESCRIPTION
        "ISO DPA:  Job-name
        This attribute supplies a human readable string for the print-
        job. This string is used for naming the print-job in human-
        readable 'free-form' fashion.
        This attribute is intended for enabling a user or the user's
        application to convey a job name that may be printed on a start
        sheet, returned in a ListObjectAttributes result, or used in
        notification or logging messages.
        If this attribute is not specified, no job name is assumed, but
        implementation specific defaults are allowed, such as the value
        of the document-name attribute of the first document in the
        job."
    DEFVAL { 0 }                        
    ::= { xcmJobGenBasicEntry 5 }
xcmJobOwner OBJECT-TYPE
    SYNTAX     CodeIndexedStringIndex
    MAX-ACCESS read-only
    STATUS     current
    DESCRIPTION
        "ISO DPA:  Job-owner
        This attribute supplies the name of the human owner of the
        print-job.
        The value of job-owner will often be the same as job-
        originator. The job-owner will be different from job-originator
        when the job has been submitted by the originator on behalf of
        the owner. This attribute is not to take the place of the
        security parameters or the access-and-accounting attributes.
        If this attribute is not specified, the value of user-name or
        job-originator should be used for any circumstances which
        require a value for job-owner."
    DEFVAL { 0 }                        
    ::= { xcmJobGenBasicEntry 6 }
xcmJobSourceChannelType OBJECT-TYPE
    SYNTAX     XcmPrtChannelType
    MAX-ACCESS read-only
    STATUS     current
    DESCRIPTION
        "Job-source-channel-type (ISO DPA extension)
        This attribute specifies the type of channel that is receiving
        the job from the input device.  See XCMI Printer Extensions TC
        for values defined by the Printer MIB (RFC 1759)."
    DEFVAL { other }                    
    ::= { xcmJobGenBasicEntry 7 }
xcmJobSubmittedLocaleIndex OBJECT-TYPE
    SYNTAX     Cardinal32
    MAX-ACCESS read-only
    STATUS     current
    DESCRIPTION
        "Job-submitted-locale (ISO DPA extension)
        This object is the locale (country, territory, and language)
        index into the xcmGenLocalizationTable specifying the locale of
        the submitting user.  This object permits a management station
        to determine the exact coded character set that the submitting
        client used, in case the code conversion that the agent might
        perform to a different coded character set is not sufficient.
        This object also allows the system and the accounting package to
        determine the language that the submitting user used for
        selecting media.
        NOTE: ISO DPA has an operation-locale attribute which is passed
        as common arguments of every ISO DPA operation.  ISO DPA should
        be amended to indicate that the server may copy the
        operation-locale attribute to the job object, so that the server
        can remember the locale that the client specified.  Then an
        agent could copy the value of the coded character set from the
        job's operation-locale attribute in order to return as the value
        of xcmJobSubmittedLocaleIndex."
    DEFVAL { 0 }                        
    ::= { xcmJobGenBasicEntry 8 }
xcmJobCurrentState OBJECT-TYPE
    SYNTAX     XcmJMJobState
    MAX-ACCESS read-only
    STATUS     current
    DESCRIPTION
        "ISO DPA:  Current-job-state
        This attribute identifies the current state of the job
        (pending, processing, held, etc.)
        Print clients and DP-Servers shall be prepared to receive all
        the standard job states.  DP-Servers are not required to
        generate all job states, only those which are appropriate for
        the particular implementation.
        It is not conformant for an agent to return the unknown value
        if the job's state can be determined.
        If a server implementation or policy is to start processing
        documents before the last Print request (with a TRUE value for
        the job-submission-complete parameter) and the value of the
        job's job-scheduling attribute is not after-complete, the
        server shall change the job's current-job-state from pre-
        processing [building] directly to the processing state when the
        server begins processing any of the job's documents."
    DEFVAL { unknown }                  
    ::= { xcmJobGenBasicEntry 9 }
xcmJobStateReasons OBJECT-TYPE
    SYNTAX     XcmJMJobStateReasons
    MAX-ACCESS read-only
    STATUS     current
    DESCRIPTION
        "This object is bit-encoded, so that multiple reasons can occur
        at once.  Each bit corresponds to an ISO DPA OID for the same
        reason.  See textual conventions.
        ISO DPA:   Job-state-reasons
        This attribute identifies the reason or reasons that the job is
        in the held, terminating, retained, or completed state.  The
        server shall indicate the particular reason(s) by setting the
        value of the job-state-reasons attribute.  When the job is not
        in any of these states, the server shall set the value of the
        job-state-reasons attribute to the empty set."
    DEFVAL { 0 }                        
    ::= { xcmJobGenBasicEntry 10 }
xcmJobXStateReasons OBJECT-TYPE
    SYNTAX     XcmJMJobXStateReasons
    MAX-ACCESS read-only
    STATUS     current
    DESCRIPTION
        "This object is bit-encoded, so that multiple reasons can occur
        at once.  Each bit corresponds to a Xerox extension OID for the
        same reason.  See textual conventions.
        ISO DPA:   Job-state-reasons (extended with Xerox OIDs)
        This attribute identifies the reason or reasons that the job is
        in the held, [processing,] terminating,
        retained, or completed state.  The server shall indicate the
        particular reason(s) by setting the value of the
        job-state-reasons attribute.  When the job is not in any of
        these states, the server shall set the value of the
        job-state-reasons attribute to the empty set.
        See the Xerox Job Model Specification for the specification of
        which reasons can be used in which job states."
    DEFVAL { 0 }                        
    ::= { xcmJobGenBasicEntry 11 }
xcmJobX2StateReasons OBJECT-TYPE
    SYNTAX     XcmJMJobX2StateReasons
    MAX-ACCESS read-only
    STATUS     current
    DESCRIPTION
        "This object is bit-encoded, so that multiple reasons can occur
        at once.  Each bit corresponds to a second set of 31 Xerox
        extension OIDs for the same reason.  See textual conventions.
        ISO DPA:   Job-state-reasons (extended with Xerox OIDs)
        This attribute identifies the reason or reasons that the job is
        in the held, [processing,] terminating,
        retained, or completed state.  The server shall indicate the
        particular reason(s) by setting the value of the
        job-state-reasons attribute.  When the job is not in any of
        these states, the server shall set the value of the
        job-state-reasons attribute to the empty set.
        See the Xerox Job Model Specification for the specification of
        which reasons can be used in which job states."
    DEFVAL { 0 }                        
    ::= { xcmJobGenBasicEntry 12 }
--
--
-- implementer wishes to expose the state of such software "engines" to
--
--
--
xcmDevicesAssigned  OBJECT IDENTIFIER ::= { xcmJobMonMIB 7 }
xcmDevicesAssignedTable OBJECT-TYPE
    SYNTAX     SEQUENCE OF XcmDevicesAssignedEntry
    MAX-ACCESS not-accessible
    STATUS     current                 
    DESCRIPTION
        "This table contains the hrDeviceIndex values and states of the
        device(s) to which this job has been assigned, if the job has
        been assigned to a physical device by the job service provider.
        If the job service provider has not (yet) assigned the job to a
        device, there shall not be any rows in this table for the job.
        Some implementations assign jobs to physical devices when the
        job is submitted which is called early binding.  Other
        implementations delay assigning jobs to physical devices until
        the physical device is ready to accept another job which is
        called late binding.  Late binding is used when load balancing
        between several physical devices.
        NOTE: Some systems may assign a job to more than one
        device and progress part of the job on each.  Therefore, the
        device state is represented as a table.  For example, print
        systems that only assign a job to a single printer, need only
        implement a single row of this table.  As another example,
        multifunction devices/systems that scan and print, in
        order to implement a copy service may either:
          1. assign a simple job to at least two devices: a scanner and
             a printer or
          2. create a compound job with a single device assigned to each
             contained sub-job."
    ::= { xcmDevicesAssigned 1 }
xcmDevicesAssignedEntry OBJECT-TYPE
    SYNTAX     XcmDevicesAssignedEntry
    MAX-ACCESS not-accessible
    STATUS     current                 
    DESCRIPTION
        "Entries may exist in the table for each device index whose
        device type is 'printer', 'scanner', etc. and for each job.
        See Host Resources MIB and the XCMI Host Resources Extension MIB
        where OIDs are assigned for device types."
    INDEX { hrDeviceIndex, xcmJobIdentifierOnSystem,
            xcmDevicesAssignedHrDeviceIndex }
    ::= { xcmDevicesAssignedTable 1 }
XcmDevicesAssignedEntry ::= SEQUENCE {
    xcmDevicesAssignedHrDeviceIndex   Ordinal32,           
    xcmDeviceStateOfDevicesAssigned   XcmHrDevInfoXStatus, 
    xcmJobIdentifierDownstream        DisplayString        
}
xcmDevicesAssignedHrDeviceIndex OBJECT-TYPE
    SYNTAX     Ordinal32
    MAX-ACCESS not-accessible
    STATUS     current                 
    DESCRIPTION
        "The hrDeviceIndex of one of the [physical] devices (printers,
        scanners, FAX, etc.  to which the job has been assigned.
        For devices and systems that ensure that
        jobs are not lost across crashes and power cycles, these index
        values shall remain stable across successive device power
        cycles.  However, if a (low-end) device is not ensuring that job
        are persistent across crashes and power cycles, these index
        values need not remain stable across such crashes or power
        cycles.
        The representation of the assigned device(s)is an
        index into the Host Resources MIB device table, rather than
        being the distinguished name of the physical printer as in the
        ISO DPA printers-assigned attribute.
            NOTE - The name of the physical printer [or scanner] is
            contained in the XCMI Host Resources Extension MIB table for
            this device.
        ISO DPA:   Printers-assigned
        This attribute identifies the physical [devices] printer or
        printers to which this job has been assigned, if any.
        When the job is first submitted and the server has not yet
        assigned any printers to the job, the [table] shall be empty.
        If the server intends to use a single printer for the job, and
        the server has assigned a printer to the job, [each row] shall
        contain just that [device].
        If a server has split the job into multiple pieces and assigned
        each piece to a different printer, the table shall contain n
        rows, one for each assigned device. A job with multiple
        job-result-sets is an example of a job that would be easy to
        split into multiple pieces.
        A table with no elements shall be
        returned if this attribute is supported, but this job has not
        yet been assigned to any physical printers [or other devices].
        The number of rows in the table for this attribute shall
        be the same as the number of rows in the table for the
        associated job attribute printer-state-of-printers-assigned
        [number of rows for the xcmDeviceStateOfDevicesAssigned table].
        In addition, the ith element of each of these associated
        attributes shall be a value that pertains to the printer named
        by the ith element of printers-assigned.
        The printers-assigned value shall not be the same as the printer
        requested by the user if the job's printer-name-requested
        attribute specified a logical printer that supports one or more
        different physical printers.  The printers-assigned value might
        differ also if the job has been re-assigned by an operator to
        ensure successful completion of the job, allowing the user to
        find out where a job has been re-assigned (when necessary).
        The value of the job's printers-assigned attribute shall remain
        after the job has completed, so that users can determine the
        physical printer(s) on which the job was printed."
    ::= { xcmDevicesAssignedEntry 1 }
xcmDeviceStateOfDevicesAssigned OBJECT-TYPE
    SYNTAX     XcmHrDevInfoXStatus
    MAX-ACCESS read-only
    STATUS     current                 
    DESCRIPTION
        "For the MIB, the object applies to scanners, Faxes, etc., as
        well as printers.  For job services that are purely software or
        that have software document transforms that the implementation
        wishes to expose the state of the software 'engine' may also
        include rows in this table.  The purpose of the
        xcmDeviceStateOfDevicesAssigned is to give more detailed
        information about the state of a job when the job is in the
        processing state.  Consequently, the value of this object shall
        reflect the state of the device only when the job is in the
        processing state.  When the job is in any other state, the value
        of the xcmDeviceStateOfDevicesAssigned object shall be
        'unknown'.
        Changes of the values of xcmDeviceStateOfDevicesAssigned
        shall generate a trap.  Since the value of this object
        shall change only when the job is in the processing state, traps
        shall only be generated for changes in
        xcmDeviceStateOfDevicesAssigned  while the job is in the
        processing state.  Therefore, the
        xcmDeviceStateOfDevicesAssigned object shall not generate a trap
        when the job is not in the processing state.
        NOTE: the xcmDeviceStateOfDevicesAssigned is a duplicate of an
        object in the Host Resources Extension MIB.  But since that
        object is in an optional group, xcmDeviceStateOfDevicesAssigned
        is duplicated in this deprecated table, so that implementers are
        not forced to implement the entire optional group in the HRX
        MIB, such to get this state of the device that is part of the
        overall job state.
        NOTE: This group and table has been DEPRECATED, because
        some devices can be processing more than one
        job at a time.  However, if the device stops, only one of those
        jobs is actually affected.  So the deviceStopped bit in the
        PWG Job Monitoring MIB should be used (on a per job basis)
        to indicate that the device has a problem.
        ISO DPA:   Printer-state-of-printers-assigned
        This attribute identifies the current state of each assigned
        [device] printer. This attribute gives the client access to
        information within each assigned printer.  Because this
        attribute contains a value that is updated within the printer,
        the server may choose to update the value of this attribute only
        when a client [or management station] queries its value.
        See the [devices-assigned] printers-assigned attribute for the
        correspondence between elements of this attribute and those of
        [devices-assigned] printers-assigned."
    ::= { xcmDevicesAssignedEntry 2 }
xcmJobIdentifierDownstream OBJECT-TYPE
    SYNTAX     DisplayString (SIZE(0..255))
    MAX-ACCESS read-only
    STATUS     current                 
    DESCRIPTION
        "Uniquely identifies the job(s) on the immediately downstream
        server or device as generated by that server or device that this
        system has submitted in order to perform this job.  The
        downstream server or device is specified by its own value of
        hrDeviceIndex.  For an agent representing a spooling system,
        this object is the identifier generated by that spooling system
        and hrDeviceIndex identifies a logical device.
        NOTE: This object in this MIB is a generalization of the
        corresponding ISO DPA attribute: job-identifier-on-printer which
        is printer-centric.
        ISO DPA:  job-identifier-on-printer
        This attribute provides the job-identifier for this job to
        uniquely identify it on the printer or next server downstream,
        and it shall be assigned by that printer or server.
        The value of the job-identifier-on-printer attribute shall be
        the job-identifier that the printer or the next server
        downstream generates at the time the server submits the job to
        the printer or the next server downstream.  If the printer or
        the next server downstream does not generate its own job
        identifier, the server shall leave the value of this attribute
        unspecified.
        NOTE - This attribute is intended for jobs submitted to other
        servers, such as a gateway to a legacy server, or to printers
        which have their own internal queue and assign their own job
        identifiers."
    DEFVAL { ''H }                      
    ::= { xcmDevicesAssignedEntry 3 }
--
--
--
--
--
--
xcmClientIdMap  OBJECT IDENTIFIER ::= { xcmJobMonMIB 8 }
xcmClientIdMapTable OBJECT-TYPE
    SYNTAX     SEQUENCE OF XcmClientIdMapEntry
    MAX-ACCESS not-accessible
    STATUS     current
    DESCRIPTION
        "A table that maps 1) job identifiers generated by the client
        that submitted the job to 2) job identifiers generated by the
        server that accepted the job."
    ::= { xcmClientIdMap 1}
xcmClientIdMapEntry OBJECT-TYPE
    SYNTAX     XcmClientIdMapEntry
    MAX-ACCESS not-accessible
    STATUS     current
    DESCRIPTION
        "Entries exist in this table for each device entry in the
        Host Resources MIB device table whose type is 'printer',
        'scanner', 'fax', etc.  Such a device may represent a logical, a
        physical, or a logical-and-physical device, as specified in the
        xcmHrDevInfoRealiszation object in the Host Resources Extension
        MIB.
        The Host Resources Extension MIB has OIDs added for use in
        hrDeviceType.
        NOTE - The map table is indexed by both the xcmJobClientId
        (which the submitting job service requester may,
        optionally, supply to identify the job or the client or user
        that submitted the job) and the xcmJobIdentifierOnSystem (which
        the accepting job service provider shall supply to
        uniquely identifier the job on the accepting system.  Thus
        the job service provider guarantees that each map entry
        has a unique pair of indices."
    INDEX { xcmJobClientId, xcmJobIdentifierOnSystem }
    ::= { xcmClientIdMapTable 1 }
XcmClientIdMapEntry ::= SEQUENCE {
    xcmClientIdMapHrDeviceIndex   Ordinal32          
}
xcmClientIdMapHrDeviceIndex OBJECT-TYPE
    SYNTAX     Ordinal32             
    MAX-ACCESS read-only
    STATUS     current
    DESCRIPTION
        "The device index from the Host Resources MIB, so that the
         client can determine to which (logical or physical) device this
         job has been submitted."
    ::= { xcmClientIdMapEntry 2 }  
--
xcmJobGenExt  OBJECT IDENTIFIER ::= { xcmJobMonMIB 10 }
xcmJobGenExtTable OBJECT-TYPE
    SYNTAX     SEQUENCE OF XcmJobGenExtEntry
    MAX-ACCESS not-accessible
    STATUS     current                 
    DESCRIPTION
        "A table of general job information per (logical or
        physical) device that is independent of the type of device and
        that does not require a spooling implementation (though a
        spooling implementation shall also implement this group, in
        which case spooled jobs shall also appear in the job table).
        Job information applies to the job as a whole or to all its
        documents.  The specification for most objects is taken directly
        from the ISO 10175 Document Printing Application (DPA) standard
        clause 9.2, Job Attributes.    However, this MIB is
        intended to be used with non-DPA implementations, so only a
        small set of general DPA attributes have been included here."
    ::= { xcmJobGenExt 1}
xcmJobGenExtEntry OBJECT-TYPE
    SYNTAX     XcmJobGenExtEntry
    MAX-ACCESS not-accessible
    STATUS     current                 
    DESCRIPTION
        "An entry exists in this table for each job in the device,
         no matter what the state of the job is.  Each device is
         represented as a separate device entry in the Host Resources
         MIB device table as a device of type 'printer', 'scanner',
         'fax', etc.
         The management station references each job using
         the xcmJobIdentifierOnSystem assigned by this (logical
         for spooling or physical for non-spooling) device that
         accepted the job submission (by some other protocol).
         This table augments the Job General Basic
         table in this MIB."
    AUGMENTS { xcmJobGenBasicEntry }
    ::= { xcmJobGenExtTable 1 }
XcmJobGenExtEntry ::= SEQUENCE {
    xcmJobOriginator              CodeIndexedStringIndex,
    xcmJobSubmittingApplication   CodeIndexedStringIndex,
    xcmJobComment                 CodeIndexedStringIndex,
    xcmJobCopies                  Ordinal32,
    xcmJobCopiesCompleted         Counter32,
    xcmJobOutputBinIndex          Integer32,
    xcmJobServiceNameRequested    CodeIndexedStringIndex,
    xcmJobPreviousState           XcmJMJobState,
    xcmJobEstimatedCompletionTime DateAndTime,
    xcmJobSubmissionTime          DateAndTime,
    xcmJobPagesCompleted          Counter32,
    xcmJobOctetsCompletedHigh     Cardinal64High,
    xcmJobOctetsCompletedLow      Cardinal64Low,
    xcmJobErrorCount              Counter32,
    xcmJobWarningCount            Counter32,
    xcmJobProcessingTime          Counter32,
    xcmJobNumberOfDocuments       Cardinal32,
    xcmJobAuthorizationUserName   CodeIndexedStringIndex
}
xcmJobOriginator OBJECT-TYPE
    SYNTAX     CodeIndexedStringIndex
    MAX-ACCESS read-only
    STATUS     current                 
    DESCRIPTION
        "ISO DPA:  Job-originator
        This attribute supplies the name of the human or programmatic
        originator of the print-job.
        If this attribute is not specified, no value for job originator
        is assumed, but implementation specific defaults are allowed.
        NOTE - This attribute may be different from job-owner (1) when
        a program submits the print-job on behalf of a user or (2) when
        an operator must resubmit a misprinted job on behalf of the
        original job owner.  However, an operation to resubmit a print-
        job is outside the scope of this part of ISO/IEC 10175."
    DEFVAL { 0 }                        
    ::= { xcmJobGenExtEntry 1 }
xcmJobSubmittingApplication OBJECT-TYPE
    SYNTAX     CodeIndexedStringIndex
    MAX-ACCESS read-only
    STATUS     current                 
    DESCRIPTION
        "ISO DPA:  (ISO DPA extension)
        This attribute supplies the name of the programmatic
        originator of the print-job, i.e., name of the program
        that submitted the job on behalf of the end-user.
        If this attribute is not specified, no value for job
        programmatic originator is assumed, but implementation-specific
        defaults are allowed."
    DEFVAL { 0 }                        
    ::= { xcmJobGenExtEntry 2 }
xcmJobComment OBJECT-TYPE
    SYNTAX     CodeIndexedStringIndex
    MAX-ACCESS read-only
    STATUS     current                 
    DESCRIPTION
        "ISO DPA:  Job-comment
        This attribute supplies an arbitrary human-readable text string
        associated with the print-job.
        This attribute is intended for enabling a user to convey a text
        string that may be printed on a job start sheet, for example,
        in an implementation-dependent manner."
    DEFVAL { 0 }                        
    ::= { xcmJobGenExtEntry 3 }
xcmJobCopies OBJECT-TYPE
    SYNTAX     Ordinal32
    MAX-ACCESS read-only
    STATUS     current                 
    DESCRIPTION
        "For the MIB:  this object is generalized so that it applies
        to scanning as well as printing.
        ISO DPA:  job-copies (an element of results-profile attribute)
        Total number of job copies in the job, i.e., number of job
        copies summed across the job-result-sets.  If a job contains
        documents A, B, C, a job-copies value of 2 results in:
        A, B, C, A, B, C.  See ISO DPA results-profile attribute
        description for the specification of a job result set and
        the definition of job-copies.
        NOTE - In ISO DPA, job-copies is a separate value for each job
        result set, not the summation.  But it didn't seem worth the
        effort to make job-copies a table since not many systems support
        multiple job results sets for a single job."
    DEFVAL { 1 }                        
    ::= { xcmJobGenExtEntry 4 }
xcmJobCopiesCompleted OBJECT-TYPE
    SYNTAX     Counter32
    MAX-ACCESS read-only
    STATUS     current                 
    DESCRIPTION
        "For the MIB:  this object is generalized so that it applies
        to scanning as well as printing.
        ISO DPA:  Job-copies-completed
        This attribute indicates the number of job-copies of the job
        that the printer(s) have completed printing.  The server shall
        not reset its value during the processing of multiple print-job
        results that are part of the same job (see the results-profile
        job attribute).  Since this attribute is intended to measure
        the progress of a job, the value shall include repeated job-
        copies due to multiple print-job results for the same job.
        The accuracy of this value is implementation-dependent. It is
        expected that the value reported is never greater than the
        actual value.  This attribute may not be supported for all
        printers and all page description languages.
        The value of this attribute shall be 0 if printing has not
        started for this job."
    ::= { xcmJobGenExtEntry 5 }
xcmJobOutputBinIndex OBJECT-TYPE
    SYNTAX     Integer32
    MAX-ACCESS read-only
    STATUS     current                 
    DESCRIPTION
        "ISO DPA:  output-bin
        Special MIB definition:  specifies the index of the output
        subunit table for the job.
        NOTE - ISO DPA allows the output-bin to be specified
        differently for each job result set in a job.  However, it
        doesn't seem worth the effort to make output-bin a table, since
        multiple job-result-sets is an unlikely feature to be supported
        and/or used, especially with different output-bins."
    DEFVAL { 0 }                        
    ::= { xcmJobGenExtEntry 6 }
xcmJobServiceNameRequested OBJECT-TYPE
    SYNTAX     CodeIndexedStringIndex
    MAX-ACCESS read-only
    STATUS     current                 
    DESCRIPTION
        "Specifies the job service name instance on which the job is
        to be processed as specified by the job service requester when
        the job was submitted.
        NOTE: this object has been generalized for use in this MIB from
        ISO DPA where the attribute is only a logical or physical
        printer, not a job service instance, such as a scan-to-file
        service instance.
        ISO DPA: Printer-name-requested
        This attribute identifies the printer to be used for printing
        the job.  The client shall specify the value of this attribute
        with the first invocation of the Print operation for the print-
        job as the explicit printer-name component of the
        PrintArgument, rather than as an attribute (see 8.2.1.1).
        NOTES
        1.  To cause a server to select a printer according to other
        attributes, the System Administrator should define a logical
        printer that supports ALL of the physical printers supported by
        the server.
        2.  For the server that supports only a single printer, the
        logical printer name may be the same as the server name, as
        long as they cannot be confused for each other in the name
        service directory.
        3.  Initial-value-job objects should have the value of their
        printer-name-requested attribute specified as an empty value in
        order to indicate that no printer-name is defaulted."
    DEFVAL { 0 }                        
    ::= { xcmJobGenExtEntry 7 }
xcmJobPreviousState OBJECT-TYPE
    SYNTAX     XcmJMJobState
    MAX-ACCESS read-only
    STATUS     current                 
    DESCRIPTION
        "This object permits the management application to display
        the previous job state to the user without having to monitor
        all job state changes.  For example, when a job completes,
        the previous state indicates what the job was doing just before
        completing.  If the job was printing, then the completion
        was normal.  If the previous state was terminating, then the
        completion was abnormal.  Another example, is when a job is
        paused.  The xcmJobPreviousState indicates the state that the
        job was in when the job was paused.
        ISO DPA:  job-previous-state
        This attribute identifies the state of the job (pending,
        processing, held, etc.) before the last change of job state.
        Standard values are defined in the specification for the
        current-job-state [xcmJobCurrentState] job-status attribute.
        See textual-conventions."
    DEFVAL { unknown }                  
    ::= { xcmJobGenExtEntry 8 }
xcmJobEstimatedCompletionTime OBJECT-TYPE
    SYNTAX     DateAndTime
    MAX-ACCESS read-only
    STATUS     current                 
    DESCRIPTION
        "Job Monitoring MIB: If the estimated completion time is
        unknown, the agent should return the DEFVAL.  This object
        is a 'best efforts' object, so any estimate based on any data
        such as the octet-count or the number of pages (perhaps obtained
        from the PostScript commenting conventions up front) is far
        preferable than returning the DEFVAL.  A learning algorithm
        based on recent job sizes and their times could be used.
        ISO DPA:  Estimated-completion-time
        This attribute indicates the estimated time by which this job
        will be completed.
        The time to complete one job is dependent on the time required
        to complete all other jobs that the scheduling algorithm
        determines must be printed before this job may be printed. The
        time to complete each individual job may depend on when on-
        request resources are available. The time to print each
        individual job is dependent on the characteristics of the
        document formats in which the individual documents of the job
        are encoded and on the complexities and other characteristics
        of  the documents themselves.
        This attribute is highly implementation-dependent.  The
        estimated-completion-time may be easy to calculate for some
        combinations of document formats and scheduling algorithms. It
        may be impossible to calculate for other combinations.  It is
        recommended that, where possible, document creators provide
        system hints to the print system (perhaps appropriately encoded
        in document format headers) that help the print system
        understand which features of the document formats the document
        will be exercising."
    DEFVAL      { '0000000000000000'H } 
    ::= { xcmJobGenExtEntry 9 }
xcmJobSubmissionTime OBJECT-TYPE
    SYNTAX     DateAndTime
    MAX-ACCESS read-only
    STATUS     current                 
    DESCRIPTION
        "ISO DPA:  Submission-time
        This attribute indicates the time at which the latest Print
        request for this job was accepted by the server.
        An implementation that can tell time shall return a valid value
        for this object.  Only a device that cannot tell time shall
        return the DEFVAL."
    DEFVAL      { '0000000000000000'H } 
    ::= { xcmJobGenExtEntry 10 }
xcmJobPagesCompleted OBJECT-TYPE
    SYNTAX     Counter32
    MAX-ACCESS read-only
    STATUS     current                 
    DESCRIPTION
        "For the MIB:  this object is generalized so that it applies
        to scanning as well as printing.
        ISO DPA:  Pages-completed
        This attribute indicates the number of pages of the job that
        the printer(s) have completed printing.
        NOTE - The number of source pages, impressions and sheets of
        media may differ.  The following examples illustrate how they
        may differ when attributes, rather than the document contents,
        control the printing. If number-up is 0 or 1, there is one
        source page per impression, and if number-up is 2, there are
        two source pages per impression.  If sides is 1, there is one
        impression per sheet of media, but if sides is 2, there are two
        impressions per sheet of media. By inference, if number-up is 4
        and sides is 2, there are 4 source pages per impression and 8
        source pages per sheet of media.
        The server shall not reset its value during the processing of
        multiple copies of documents or the job.  Since this attribute
        is intended to measure the progress of a job, the value shall
        include repeated pages due to multiple copies.  When the job
        completes, this attribute should contain the value of the total
        number of source pages that the printer processed for the
        print-job.
        The accuracy of this value is implementation-dependent. It is
        expected that the value reported is never greater than the
        actual value.  This attribute may not be supported for all
        printers and all page description languages.
        The value of this attribute shall be 0 if printing has not
        started for this job. "
    ::= { xcmJobGenExtEntry 11 }
xcmJobOctetsCompletedHigh OBJECT-TYPE
    SYNTAX     Cardinal64High
    MAX-ACCESS read-only
    STATUS     current                 
    DESCRIPTION
        "For the Job Monitoring MIB:  two objects are used to represent
        a full 62-bit value.  The sign bit of each half is not used.
        This object is generalized for use with input devices as well.
        ISO DPA:  Octets-completed [high 31 bits]
        This attribute indicates the number of octets of the job that
        the printer(s) [devices(s)] have completed printing
        [processing].  The server shall not
        reset its value during the processing of multiple copies of
        documents or the job.  Since this attribute is intended to
        measure the progress of a job, the value shall include repeated
        pages due to multiple copies.
        The accuracy of this value is implementation-dependent. It may
        be approximated by the number of octets conveyed to the
        printer [device]. This attribute may not be supported for all
        printers and all page description languages.
        The value of this attribute shall be 0 if the device has not
        started this job."
    DEFVAL { 0 }                        
    ::= { xcmJobGenExtEntry 12 }
xcmJobOctetsCompletedLow OBJECT-TYPE
    SYNTAX     Cardinal64Low
    MAX-ACCESS read-only
    STATUS     current                 
    DESCRIPTION
        "ISO DPA:  Octets-completed [low 31 bits]
        See explanation of xcmJobOctetsCompletedHigh."
    DEFVAL { 0 }                        
    ::= { xcmJobGenExtEntry 13 }
xcmJobErrorCount OBJECT-TYPE
    SYNTAX     Counter32
    MAX-ACCESS read-only
    STATUS     current                 
    DESCRIPTION
        "ISO DPA:  Error-count
        This attribute provides the number of error events occurring
        while processing the job."
    ::= { xcmJobGenExtEntry 14 }
xcmJobWarningCount OBJECT-TYPE
    SYNTAX     Counter32
    MAX-ACCESS read-only
    STATUS     current                 
    DESCRIPTION
        "ISO DPA:  Warning-count
        This attribute provides the number of warning events occurring
        while processing the job."
    ::= { xcmJobGenExtEntry 15 }
xcmJobProcessingTime OBJECT-TYPE
    SYNTAX     Counter32
    UNITS      "seconds"
    MAX-ACCESS read-only
    STATUS     current                 
    DESCRIPTION
        "ISO DPA:  Processing-time
        This attribute indicates how long an individual job has been
        processing [in seconds]."
    ::= { xcmJobGenExtEntry 16 }
xcmJobNumberOfDocuments OBJECT-TYPE
    SYNTAX     Cardinal32
    MAX-ACCESS read-only
    STATUS     current                 
    DESCRIPTION
        "ISO DPA:  Number-of-documents
        This attribute indicates the number of documents in the job.
        The number indicates how many Print operations that specified a
        document (of any document-type have been submitted for
        printing until job submission has been completed; at that point
        this attribute shall then indicate the total number of
        printable documents, fonts, and resource objects submitted by
        the client in the job.  If the first Print operation does not
        contain a first-document component (see 8.2.1), the value of
        this attribute shall be 0.
        The server shall count fonts and resource objects passed to the
        server by means of Print operation invocations, as documents
        for the purposes of this attribute."
    DEFVAL { 0 }                        
    ::= { xcmJobGenExtEntry 17 }
xcmJobAuthorizationUserName OBJECT-TYPE
    SYNTAX     CodeIndexedStringIndex
    MAX-ACCESS read-only
    STATUS     current                 
    DESCRIPTION
        "The user's name for authorization purposes.  The value of
        xcmJobAuthorizationUserName may be the same or may be different
        than the value of the xcmJobAccountingUserName object, depending
        on the security system and the accounting system being used.
        ISO DPA:   User-name
        This attribute specifies the name of the user requesting access
        to print [or other] service operations.  The usage of
        this attribute may be mandatory, depending upon the local
        security policy used."
    REFERENCE
        "See XCMI security MIB (62sectc.txt and 63sec.txt)."
    DEFVAL { 0 }                        
    ::= { xcmJobGenExtEntry 18 }
--
--
xcmDocGenBasic  OBJECT IDENTIFIER ::= { xcmJobMonMIB 12 }
xcmDocGenBasicTable OBJECT-TYPE
    SYNTAX     SEQUENCE OF XcmDocGenBasicEntry
    MAX-ACCESS not-accessible
    STATUS     current
    DESCRIPTION
        "A table of general mandatory document information that is per
        document which in turn is per job and which in turn is per
        (logical or physical) device and is independent of the type of
        device (printer, scanner, fax, ...) and that does not require a
        spooling implementation (though a spooling implementations shall
        also implement this group, in which case spooled jobs shall also
        appear in the job table).
        Document information applies to an individual document contained
        in a job.  The specification for most objects is taken directly
        from the ISO 10175 Document Printing Application (DPA) standard
        clause 9.3, Document Attributes.    However, this MIB is
        intended to be used with non-DPA implementations, so only a
        small set of general DPA attributes have been included here."
    ::= { xcmDocGenBasic 1}
xcmDocGenBasicEntry OBJECT-TYPE
    SYNTAX     XcmDocGenBasicEntry
    MAX-ACCESS not-accessible
    STATUS     current
    DESCRIPTION
        "An entry exists in this table for each document in each job,
         no matter what the state of the job is.  Each printer is
         represented as a separate device entry in the Host Resources
         MIB device table as a device of type 'printer', 'scanner', o
         'fax', etc.  The management station references each job using
         the xcmJobIdentifierOnSystem assigned by this (logical
         for spooling or physical for non-spooling) device that
         accepted the job submission (by some other protocol)."
    INDEX { hrDeviceIndex, xcmJobIdentifierOnSystem,
            xcmDocSequenceNumber }
    ::= { xcmDocGenBasicTable 1 }
XcmDocGenBasicEntry ::= SEQUENCE {
    xcmDocSequenceNumber  Ordinal32,                    
    xcmDocName            CodeIndexedStringIndex,       
    xcmDocFileName        CodeIndexedStringIndex,       
    xcmDocFileNameType    XcmJMDocFileNameType,         
    xcmDocType            XcmJMDocType,                 
    xcmDocFormat          XcmPrtInterpreterLangFamily,  
    xcmDocFormatVariants  CodeIndexedStringIndex,       
    xcmDocFormatVersion   CodeIndexedStringIndex,       
    xcmDocOctetCount      Cardinal32,                   
    xcmDocState           XcmJMDocState                 
}
xcmDocSequenceNumber OBJECT-TYPE
    SYNTAX     Ordinal32
    MAX-ACCESS read-only
    STATUS     current
    DESCRIPTION
        "For the MIB, a row shall not exist in this table if the job
        does not (yet) have any documents.  A 32-bit index is required,
        since the ISO DPA has a 2**31-1 maximum-value integer for the
        document-sequence-number attribute.
        ISO DPA:   Document-sequence-number
        This attribute specifies the number of this document in
        relation to the set of documents in this job. The first
        document in the job is numbered 1.
        The document-sequence-number is not passed as an input
        attribute in the print operation.  Documents are assumed to be
        submitted in order (i.e., document number 1 followed by
        document number 2, etc.).
        [If the job service requester does not submit a document on the
        first create-job call, no document row shall be added to this
        table.  The rest of this ISO DPA paragraph does not apply:]
        A server shall return a value of 0 for this attribute if the
        first Print operation has not submitted a document (e.g., the
        first-document element is omitted in the create-job element of
        the Print operation).
        If a document is cancelled in a multi-document job, the
        document-sequence numbers of the other documents shall not
        change."
    ::= { xcmDocGenBasicEntry 1 }
xcmDocName OBJECT-TYPE
    SYNTAX     CodeIndexedStringIndex
    MAX-ACCESS read-only
    STATUS     current
    DESCRIPTION
        "For the MIB, the single xcmDocName object is both the document
        name for scan-to-file and the document name for file-to-print.
        ISO DPA:   Document-name
        This attribute supplies a human readable string for the
        document. This string is used for naming the document in a
        human-readable 'free-form' fashion.
        This attribute is intended for enabling a user or the user's
        application to convey a document name that may be printed on a
        start sheet, returned in a ListObjectAttributes result, or used
        in notification or logging messages.
        If this attribute is not specified, no document name is
        assumed, but implementation specific defaults are allowed, such
        as the simple-name part of the value of the document-file-name
        attribute.  It is suggested, however, that the server not
        supply additional text for this attribute when printing its
        value (e.g. on a start sheet).  This string only has meaning to
        the clients and can therefore take several forms, e.g. the name
        of a mail folder, name of a revisable document, the file
        specification minus the file path, the title of a document,
        etc."
    ::= { xcmDocGenBasicEntry 2 }
xcmDocFileName OBJECT-TYPE
    SYNTAX     CodeIndexedStringIndex
    MAX-ACCESS read-only
    STATUS     current
    DESCRIPTION
        "For the MIB, the single xcmDocFileName object is both the
        document file name for scan-to-file and the document file name
        for file-to-print.  If this attribute is specified for a
        scan-to-print job, the result of the scan is also copied to the
        file specified by xcmDocFileName as a side-effect of the
        scan-to-print operation.
        ISO DPA:   Document-file-name
        This attribute specifies the file name of the document, if the
        document came from a file.
        The file name may include the full path to the file, in which
        case the name-syntax element of the DistinguishedNameString
        data type shall specify the syntax of the file name.  If the
        document did not come from a file, the client should not
        specify this attribute."
    ::= { xcmDocGenBasicEntry 3 }
xcmDocFileNameType OBJECT-TYPE
    SYNTAX     XcmJMDocFileNameType
    MAX-ACCESS read-only
    STATUS     current
    DESCRIPTION
        "The type of file name syntax from which a document is
        obtained for an output job, such as print, or for which a
        document is produced for an input job, such as scan-
        to-file.  The file name syntax types are taken from ISO DPA
        for the DistinguishedNameStringSyntax data type.
        ISO DPA:   distinguished-name-syntax data type, name-syntax
        element.  See textual-conventions."
    ::= { xcmDocGenBasicEntry 4 }
xcmDocType OBJECT-TYPE
    SYNTAX     XcmJMDocType
    MAX-ACCESS read-only
    STATUS     current
    DESCRIPTION
        "ISO DPA:  Document-type
        This attribute indicates that the document being passed by the
        current Print abstract-operation is either a printable
        document, a font, or a resource.
        How resources are managed during the printing process is
        necessarily dependent on the characteristics of the server and
        printer implementations. These methods are considered
        implementation-specific, and shall not be dictated by ISO/IEC
        10175.  In particular, ISO/IEC 10175 does not require that
        resources be passed in advance of the documents that use them;
        i.e., resources may be passed to the server in any order within
        the job, subject only to the requirement that the resources be
        present at the server before processing begins on the documents
        that use them."
    ::= { xcmDocGenBasicEntry 5 }
xcmDocFormat OBJECT-TYPE
    SYNTAX     XcmPrtInterpreterLangFamily
    MAX-ACCESS read-only
    STATUS     current
    DESCRIPTION
        "The interpreter language family enum value registered by IANA
        is used according to the Printer MIB (RFC 1759).  See
        prtInterpreterLangFamily.  For the Job Monitoring
        MIB, an index into the prtInterpreterTable is not used, since
        the exact format of the document need not conform exactly to one
        of the printer's intepreters and, furthermore, the device need
        not even be a printer (so that the Printer MIB need not be used
        for non-printers).
        For scan-to-file jobs, the xcmDocFormat object specifies the
        document format desired as a result of the scan.
        ISO DPA:   Document-format
        This attribute identifies the overall print document format
        used for the document.  It consists of three elements, a
        document-format, a document-format-variants and a document-
        format-version. The latter two elements are optional.
        The document-format element identifies a particular family of
        document formats, of which there may exist several versions or
        variants.  The document-format-variants and document-format-
        version elements identify a specific instance of a document
        format. The variant refers to a particular functional subset of
        a format. For example, the format PostScript has variants of
        level 1 and level 2, and the format PCL has several variants,
        including PCL4 and PCL5.  The version distinguishes among
        successive releases of the same basic format and variant. For
        example, successive versions of Xerox Interpress include
        versions 2.0, 2.1, 3.0, 3.1, etc."
    ::= { xcmDocGenBasicEntry 6 }
xcmDocFormatVariants OBJECT-TYPE
    SYNTAX     CodeIndexedStringIndex
    MAX-ACCESS read-only
    STATUS     current
    DESCRIPTION
        "For scan-to-file jobs, the xcmDocFormatVariants object
        specifies the document format variant desired as a result of the
        scan.
        ISO DPA:   Document-format-variants
        The document-format-variants and document-format-version
        elements identify a specific instance of a document format. The
        variant refers to a particular functional subset of a format.
        For example, the format PostScript has variants of level 1 and
        level 2, and the format PCL has several variants, including
        PCL4 and PCL5.
        The document-format-variants element consists of a single
        text string.  If it is necessary to identify more than one
        variant, the respective variant values shall all be contained
        in the document-format-variants element, separated from one
        another by commas.
        If the client omits the document-format-variants or document-
        format-version elements, the server may supply a format-
        specific default which will restrict the outcome of the rules
        described in the next paragraph. This rule shall not cause a
        job to fail in validation if it would have succeeded with the
        rules of the next paragraph.
        If the client omits the document-format-variants element, the
        server shall print the document if the requested printer's
        document-formats-supported attribute contains a DocFormat
        which differs from the specified document-format only in the
        value of its document-format-variants.  If the
        document-format-variants is omitted from the printer
        document-formats-supported attribute, the printer shall accept
        documents with any variant of the specified format. Similar
        rules apply if the document-format-version element is omitted.
        If the client omits the document-format-variants or document-
        format-version elements, the server may supply a format-
        specific default. Such a default shall be one that could have
        matched a document-format according to the rules of the
        preceding paragraph.
        Proprietary values for the document-format, document-format-
        variants, and document-format-version elements are assigned by
        the owners of those formats.  Annex F contains a set of
        document-formats and variants for various commercially
        available formats and variants that are currently in common
        use."
    ::= { xcmDocGenBasicEntry 7 }
xcmDocFormatVersion OBJECT-TYPE
    SYNTAX     CodeIndexedStringIndex
    MAX-ACCESS read-only
    STATUS     current
    DESCRIPTION
        "For scan-to-file jobs, the xcmDocFormatVersion object specifies
        the document format version desired as a result of the scan.
        ISO DPA:   Document-format-version
        The version distinguishes among successive releases of the same
        basic format and variant. For example, successive versions of
        Xerox Interpress include versions 2.0, 2.1, 3.0, 3.1, etc."
    ::= { xcmDocGenBasicEntry 8 }
xcmDocOctetCount OBJECT-TYPE
    SYNTAX     Cardinal32
    MAX-ACCESS read-only
    STATUS     current
    DESCRIPTION
        "For the MIB, the value of the xcmDocOctetCount is used for both
        scan-to-file and file-to-print jobs.  In the case of
        scan-to-file jobs, the value starts at 0 and counts the number
        of octets scanned.
        ISO DPA:   Octet-count
        This attribute specifies the size of the document in octets."
    ::= { xcmDocGenBasicEntry 9 }
xcmDocState OBJECT-TYPE
    SYNTAX     XcmJMDocState
    MAX-ACCESS read-only
    STATUS     current
    DESCRIPTION
        "For the MIB, if the document is being
        scanned and printed in the same simple job, the xcmDocState
        object represents the state of the document being printed, since
        level 1 scan-to-print jobs must scan directly to the printer.
        ISO DPA:   Document-state
        This attribute identifies the current state of the document
        [whether being scanned or printed.]."
    ::= { xcmDocGenBasicEntry 10 }
--
--
xcmDocPrintExt  OBJECT IDENTIFIER ::= { xcmJobMonMIB 13 }
xcmDocPrintExtTable OBJECT-TYPE
    SYNTAX     SEQUENCE OF XcmDocPrintExtEntry
    MAX-ACCESS not-accessible
    STATUS     current
    DESCRIPTION
        "A table of print-centric document information which
        is per document which in turn is per job and which in turn is
        per (logical or physical) printer.  Document information applies
        to an individual document contained in the job.  The
        specification for most objects is taken directly from the ISO
        10175 Document Printing Application (DPA) standard clause 9.3,
        Document Attributes and is print-centric.    However, this MIB
        is intended to be used with non-DPA implementations, so only a
        small set of general DPA attributes have been included here."
    ::= { xcmDocPrintExt 1}
xcmDocPrintExtEntry OBJECT-TYPE
    SYNTAX     XcmDocPrintExtEntry
    MAX-ACCESS not-accessible
    STATUS     current
    DESCRIPTION
        "An entry exists in this table for each job in the device,
         no matter what the state of the job is.  Each printer is
         represented as a separate device entry in the Host Resources
         MIB device table as a device of type 'printer'.
         The management station references each job using
         the xcmJobIdentifierOnSystem assigned by this (logical
         for spooling or physical for non-spooling) device that
         accepted the job submission (by some other protocol).
         The management station accesses each document in the job using
         the xcmDocSequenceNumber from the xcmDocGenBasicTable.
         This table extends (for print jobs only) the
         Document General Basic table in this MIB."
    INDEX { hrDeviceIndex, xcmJobIdentifierOnSystem,
            xcmDocSequenceNumber }
    ::= { xcmDocPrintExtTable 1 }
XcmDocPrintExtEntry ::= SEQUENCE {
    xcmDocPrintDefaultMediumName InternationalDisplayString,
    xcmDocPrintDefaultInputIndex Cardinal16,              
    xcmDocPrintFinishing         InternationalDisplayString,
    xcmDocPrintOutputMethod      XcmJMDocOutputMethod,    
    xcmDocPrintNumberUp          InternationalDisplayString,
    xcmDocPrintSides             INTEGER(1..2),           
    xcmDocPrintCopyCount         Cardinal32,              
    xcmDocPrintCopiesCompleted   Counter32                
}
xcmDocPrintDefaultMediumName OBJECT-TYPE
    SYNTAX     InternationalDisplayString (SIZE(0..255))
    MAX-ACCESS read-only
    STATUS     current
    DESCRIPTION
        "The value of this object is the name of the medium
        that is the default medium for this
        document.  A null string indicates that neither the
        submitting client, nor the system, nor the printer has
        specified a default medium for this document.
        NOTE: This attribute that is supplied by the job service
        requester is localizable by the job service provider, since the
        job service provider must understand and support the specified
        value.
        ISO DPA:   Default-medium
        This attribute identifies a medium that the server shall use as
        the medium default for the pages of the document that require a
        specification.
        Standard values are defined in the specification of the medium-
        identifier medium attribute.
        If the page-media-select attribute is specified (either by the
        client or by a server default, i.e., the page-media-select
        attribute of the initial-value-job object specified by the
        logical or physical printer), then the server shall use the
        page-media-select value to override the default-medium
        specification on a page by page basis.
        The default-medium attribute may contain a value of id-val-
        generic-none (see DPA 9.1.2) indicating that the server shall
        not use a default medium.  Instead, the server shall rely on
        lower precedence document attributes (such as default-input-
        tray) for the media specification.
        If the document data, itself, specifies media, such
        specification shall override the default-medium attribute on a
        page by page basis.  If the document data specifies media which
        are not also values of media-used, then a printer may receive a
        document which requires media that are not ready. In such a
        case, an implementation may either abort the document or try
        printing the document on some alternative medium, such as the
        default medium.
        A client has numerous ways to specify the media to be used when
        printing a document and different document pages can be
        specified in different ways. The client can specify the media
        in the document contents or with attributes. Some attributes
        override the document contents, and other attributes may be
        overridden by the document contents. In addition, the client
        can specify the media by name or by the input-tray containing
        it.
        Before printing each page of a document, the server determines
        the medium or input-tray for that page by finding the first
        condition in the list of numbered steps below that is
        satisfied. For this discussion, either the medium or the input-
        tray is sufficient information:
        a)  If page-media-select has a medium value for the current
        page, use that medium, regardless of document contents and
        other attributes.
        b)  If input-tray-select has a value, use that tray.
        c)  If the document contents specify a medium, and that medium
        is the same as the value of one of the original-medium elements
        in the media-substitution attribute, then use the corresponding
        substitution-medium in the media-substitution attribute.
        d)  If the document contents specify a medium, use that medium.
        e)  If the document contents specify an input-tray, use that
        input-tray.
        f)  If the default-medium has a value, and the document format
        interpreter allows its use, and that medium is the same as the
        value of one of the original-medium elements in media-
        substitution attribute, then use the corresponding
        substitution-medium in the media-substitution attribute.
        g)  If the default-medium has a value and the document format
        interpreter allows its use, use the default-medium.
        h)  If the default-input-tray has a value and the document
        format interpreter allows its use, use the default-input-tray.
        i)  Use the medium or input-tray selected by the document
        format processor in the printer. This selection is
        implementation-dependent."
    ::= { xcmDocPrintExtEntry 1 }
xcmDocPrintDefaultInputIndex OBJECT-TYPE
    SYNTAX     Cardinal16
    MAX-ACCESS read-only
    STATUS     current
    DESCRIPTION
        "The value of this object is the index of the input sub-unit in
        the prtInputTable in the printer MIB that is the default input
        tray for this document.  An index value of 0 indicates that
        neither the submitting client, the print server, nor printer
        has specified a default input tray for this document.
        The Printer MIB (RFC 1759) requires that input sub-unit indices
        remain stable across successive device power cycles.
        ISO DPA:   Default-input-tray
        This attribute identifies an input-tray that the server shall
        use as the input-tray default for the pages of the document
        that require a specification.
        The correspondence between the simple-name of an input-tray
        (alphanumeric or numeric) and the actual tray in the printer is
        printer-dependent, and a tray named by such a simple-name may
        also have an OBJECT IDENTIFIER that names it as well.
        A server may try to convert a simple-name received from a
        client to one of the server's OIDs, depending on
        implementation. However, a server shall always return an input-
        tray as an OID to the client if the server identifies the
        input-tray using an OID.
        Examples: The simple-name strings: envelope, top, 2, or 02, or
        the OID value: id-val-input-tray-top.
        If the default-medium attribute is specified (either by the
        client or by a server default, i.e., the default-medium
        attribute of the initial-value-job object specified by the
        logical or physical printer), then the server shall use the
        default-medium value and shall ignore the default-input-tray
        attribute, if specified.  If the page-media-select attribute is
        specified (either by the client or by a server default, i.e.,
        the page-media-select attribute of the initial-value-job object
        specified by the logical or physical printer), then the server
        shall use the page-media-select value to override the default-
        input-tray specification on a page by page basis.
        If the document data, itself, specifies media or input trays,
        such specification shall override the default-input-tray
        attribute on a page by page basis.  If the document data
        specifies media or input-trays which are not also values of
        media-used or input-trays-used, respectively, then a printer
        may receive a document which requires media or input-trays
        which are not ready. In such a case, an implementation may
        either abort the document or try printing the document using
        some alternative input-tray, such as the default input-tray.
        The following standard values are defined:
        top             The top input tray in the printer.  (id-
                        val-input-tray-top)
        middle          The middle input tray in the printer.  (id-
                        val-input-tray-middle)
        bottom          The bottom input tray in the printer.  (id-
                        val-input-tray-bottom)
        envelope        The envelope input tray in the printer.
                        (id-val-input-tray-envelope)
        manual          The manual feed input tray in the printer.
                        (id-val-input-tray-manual)
        large-capacity  The large capacity input tray in the
                        printer.  (id-val-input-tray-large-
                        capacity)
        main            The main input tray  (id-val-input-tray-
                        main)
        side            The side input tray  (id-val-input-tray-
                        side)"
    ::= { xcmDocPrintExtEntry 2 }
xcmDocPrintFinishing OBJECT-TYPE
    SYNTAX     InternationalDisplayString (SIZE(0..255))
    MAX-ACCESS read-only
    STATUS     current
    DESCRIPTION
        "Specifies finishing to be performed on the document.
        NOTE: This attribute that is supplied by the job service
        requester is localizable by the job service provider, since the
        job service provider must understand and support the specified
        value."
    ::= { xcmDocPrintExtEntry 3 }
xcmDocPrintOutputMethod OBJECT-TYPE
    SYNTAX     XcmJMDocOutputMethod
    MAX-ACCESS read-only
    STATUS     current
    DESCRIPTION
        "This object is bit coded, so that multiple document output
        requests may be made for the document.  Each bit corresponds to
        one of the ISO DPA output OIDs.  See XcmJMDocOutputMethod
        textual convention for the algorithm that maps DPA OIDs to bits.
        ISO DPA:   Output
        This attribute identifies the output processing for the media
        on which the document is to be printed."
    ::= { xcmDocPrintExtEntry 4 }
xcmDocPrintNumberUp OBJECT-TYPE
    SYNTAX     InternationalDisplayString (SIZE(0..255))
    MAX-ACCESS read-only
    STATUS     current
    DESCRIPTION
        "For the MIB: this object is specified as a text string which
        can be a number, e.g., '2' meaning the number of logical pages
        per side, or a name, e.g., 'simple-2-up' meaning an imposition
        object in the system that specifies 2 logical pages per side.
        NOTE: This attribute that is supplied by the job service
        requester is localizable by the job service provider, since the
        job service provider must understand and support the specified
        value.
        ISO DPA: number-up (excerpted)
        This attribute specifies the number of source page-images to
        impose upon a single instance of a selected medium. The
        attribute can be specified either by a number directly or by
        naming an imposition object which specifies some particular
        number-up imposition.
        In general, only certain all-numeric text values are valid for
        this attribute, depending upon the server and printer
        implementations to which the print-request is directed.  A
        text value of '0' or 'none' shall suppress any server default
        number up, if any.
        This attribute primarily controls the translation, scaling and
        rotation of page images, but a site may choose to add
        embellishments, such as borders to each logical page. A site may
        even choose to add an attribute to control the presence or
        characteristics of such embellishments.
        The following standard text values are defined:
          '0'  This value suppresses any number-up operation or its
               embellishments.
          '1'  This value specifies that 1 logical page is to be imaged
               on one surface of the medium, possibly with
               embellishments.
          '2'  This value specifies that 2 logical pages are to be
               imaged on one surface of the medium, possibly with
               embellishments.
          '4'  This value specifies that 4 logical pages are to be
               imaged on one surface of the medium, possibly with
               embellishments.
        NOTE - The value '0' or 'none' specifies that no convenience
        imposition functions shall be performed; '0' or 'none' is needed
        to suppress any special number-up operation because a value of
        '1' or 'simple-1-up' for some sites may cause the server to
        alter the placement, or size of the page image, or to add
        embellishments, such as borders or to rotate the page depending
        on content-orientation.
        See ISO DPA number-up description for further details on the
        semantics of number-up, including figures."
    ::= { xcmDocPrintExtEntry 5 }
xcmDocPrintSides OBJECT-TYPE
    SYNTAX     INTEGER(1..2)
    MAX-ACCESS read-only
    STATUS     current
    DESCRIPTION
        "NOTE - The xcmDocPrintSides attribute is for print jobs.  A
        scanner-specific object, xcmDocScanSides is needed to be
        added when scanning is supported, so that input and output sides
        can be specified independently.
        ISO DPA:   Sides
        This attribute specifies the number of printable surfaces of
        the medium to be imaged."
    ::= { xcmDocPrintExtEntry 6 }
xcmDocPrintCopyCount OBJECT-TYPE
    SYNTAX     Cardinal32
    MAX-ACCESS read-only
    STATUS     current
    DESCRIPTION
        "ISO DPA:  Copy-count
        This attribute specifies the number of copies of the documents,
        or of the selected pages of the document, to be printed.
        A value of 1 for copy-count shall generate a single human
        perceptible copy of the electronic document.  If a value of 0
        is supplied [by the job service requester and is supported by
        the job service provider], the job may be processed normally,
        but no print output shall be produced or the server shall return
        an unsupported-attribute-value AttributeError [to the job
        service requester, if a copy-count of 0 is not supported]."
    ::= { xcmDocPrintExtEntry 7 }
xcmDocPrintCopiesCompleted OBJECT-TYPE
    SYNTAX     Counter32
    MAX-ACCESS read-only
    STATUS     current
    DESCRIPTION
        "For the MIB: on job recovery after power failure or a crash,
        the value of xcmDocPrintCopiesCompleted may be set to a lower
        value which would normally violate the SNMP constraints of a
        Counter32 type.
        ISO DPA:  Copies-completed
        This attribute indicates the number of complete copies of this
        document that have been printed.
        Some printers print multiple copies of each individual page of
        a document, completing the printing of all copies at the same
        time, printing as many of these pages as necessary to satisfy
        the copy count. The value of copies-completed is 0 if printing
        has not started for this document."
    ::= { xcmDocPrintExtEntry 8 }
--
--
xcmJobGenSpoolingBasic  OBJECT IDENTIFIER ::= { xcmJobMonMIB 14 }
xcmJobGenSpoolingBasicTable OBJECT-TYPE
    SYNTAX     SEQUENCE OF XcmJobGenSpoolingBasicEntry
    MAX-ACCESS not-accessible
    STATUS     current                 
    DESCRIPTION
        "A table of general job information per
        (logical or physical) device that is independent of the type of
        device (printer, scanner, fax, ...) but does require spooling
        of job (and document) instructions, but not necessarily of
        document-content data.
        Job information applies to the job as a whole or to all its
        documents.  The specification for most objects is taken directly
        from the ISO 10175 Document Printing Application (DPA) standard
        clause 9.2, Job Attributes.    However, this MIB is
        intended to be used with non-DPA implementations, so only a
        small set of general DPA attributes have been included here."
    ::= { xcmJobGenSpoolingBasic 1}
xcmJobGenSpoolingBasicEntry OBJECT-TYPE
    SYNTAX     XcmJobGenSpoolingBasicEntry
    MAX-ACCESS not-accessible
    STATUS     current                 
    DESCRIPTION
        "An entry exists in this table for each job in the device,
         no matter what the state of the job is.  Each device is
         represented as a separate device entry in the Host Resources
         MIB device table as a device of type 'printer', 'scanner',
         'fax', etc.  The management station references each job using
         the xcmJobIdentifierOnSystem assigned by this logical
         (for spooling) device that accepted the job submission
         (by some other protocol)."
    AUGMENTS { xcmJobGenBasicEntry }
    ::= { xcmJobGenSpoolingBasicTable 1 }
XcmJobGenSpoolingBasicEntry ::= SEQUENCE {
    xcmJobNumberOfJobResultSets  Ordinal32,
    xcmJobPriority               INTEGER(0..100),
    xcmJobTotalOctetsHigh        Cardinal64High,
    xcmJobTotalOctetsLow         Cardinal64Low,
    xcmJobInterveningJobs        Integer32
}
xcmJobNumberOfJobResultSets OBJECT-TYPE
    SYNTAX     Ordinal32
    MAX-ACCESS read-only
    STATUS     current                 
    DESCRIPTION
        "ISO DPA:  number-of-job-result-sets
        The hardcopy output of a print-job consists of one or more job
        sets, each of which may be specified to be delivered to, or
        held for, one particular recipient who is not necessarily the
        job creator.  Each job set may be specified to contain one or
        more job copies.  Each job copy shall contain one or more
        copies of each of the documents specified by means of the Print
        operations that compose the job.
        For example, consider the following job being submitted:
            results-profile: {delivery-address=Jones, job-copies=1},
                             {delivery-address=Smith, job-copies=2}
            documentA with copy-count=1
            documentB with copy-count=2
        +-------------------------------------------------------------+
        | +----------------------------+                              |
        | | +-------------+            |                              |
        | | | document A  |            |                              |
        | | +-------------+            |                              |
        | | | document B  |  job copy  |  job result set #1 for Jones |
        | | +-------------+            |                              |
        | | | document B  |            |                              |
        | | +-------------+            |                              |
        | +----------------------------+                              |
        +-------------------------------------------------------------+
        +-------------------------------------------------------------+
        | +----------------------------+                              |
        | | +-------------+            |                              |
        | | | document A  |            |                              |
        | | +-------------+            |                              |
        | | | document B  |  job copy  |                              |
        | | +-------------+            |                              |
        | | | document B  |            |                              |
        | | +-------------+            |                              |
        | +----------------------------+                              |
                                          job result set #2 for Smith |
        | +----------------------------+                              |
        | | +-------------+            |                              |
        | | | document A  |            |                              |
        | | +-------------+            |                              |
        | | | document B  |  job copy  |                              |
        | | +-------------+            |                              |
        | | | document B  |            |                              |
        | | +-------------+            |                              |
        | +----------------------------+                              |
        +-------------------------------------------------------------+"
    DEFVAL { 1 }                        
    ::= { xcmJobGenSpoolingBasicEntry 1 }
xcmJobPriority OBJECT-TYPE
    SYNTAX     INTEGER(0..100)
    MAX-ACCESS read-only
    STATUS     current                 
    DESCRIPTION
        "For the MIB:  A value of 0 means that the priority was not
         specified by the job service requester and the system did not
         specify a default value.
        ISO DPA:  Job-priority
        This attribute specifies a priority for scheduling the print-
        job. It is used by servers that employ a priority-based
        scheduling algorithm.
        A higher value specifies a higher priority. The value 1 is
        defined to indicate the lowest possible priority (a job which a
        priority-based scheduling algorithm shall pass over in favor
        of higher priority jobs). The value 100 is defined to indicate
        the highest possible priority. Priority is expected to be
        evenly or 'normally' distributed across this range. The mapping
        of vendor-defined priority over this range is implementation-
        specific.
        [The following DPA sentence is covered by the value of 0, since
        the DPA range is 1..100.  A value of 0 returned by an SNMP agent
        indicates the same semantics as ISO DPA returning the job object
        without the job-priority attribute present:]
        The omission of this attribute implies that the user
        places no constraints concerning priority on the scheduling of
        the print-job."
    DEFVAL { 0 }                        
    ::= { xcmJobGenSpoolingBasicEntry 2 }
xcmJobTotalOctetsHigh OBJECT-TYPE
    SYNTAX     Cardinal64High
    MAX-ACCESS read-only
    STATUS     current                 
    DESCRIPTION
        "For the Job Monitoring MIB:  two objects are used to represent
        a full 62-bit value.  The sign bit of each half is not used.
        This object is generalized for use with input devices as well.
        ISO DPA:  Total-job-octets [high 31 bits]
        This attribute indicates the size of the job in octets,
        including document and job copies.
        The server may update the value of this attribute after each
        document has been transferred to the server or the server may
        provide this value after all documents have been transferred to
        the server, depending on implementation.  In other words, while
        the job is in the pre-processing [building] state and when the
        job is in the held state with the job-state-reasons containing a
        document-needed value, the value of the total-job-octets job
        status attribute depends on implementation and may not
        correctly reflect the size of the job.
        In computing this value, the server shall include the
        multiplicative factors contributed by the (1) copy-count
        document attribute, (2) the results-profile.job-copies job
        attribute element and (3) multiple values of the results-
        profile job attribute, independent of whether the printer can
        process multiple copies of the job or document without making
        multiple passes over the job or document data and independent
        of the value of the output document attribute (page-collate vs.
        no-page-collate).  Thus the server computation is independent
        of the printer implementation and shall be:
        a)  Document contribution:  Multiply each copy-count by the
        size of the document in octets.
        b)  Add each document contribution together
        c)  Job result contribution:  Multiply the job size by the
        number job-copies in the result set.
        d)  Add each job result contribution together
        e)  Multiply the value by the number of values in the job's
        result-profile attribute."
    DEFVAL { 0 }                        
    ::= { xcmJobGenSpoolingBasicEntry 3 }
xcmJobTotalOctetsLow OBJECT-TYPE
    SYNTAX     Cardinal64Low
    MAX-ACCESS read-only
    STATUS     current                 
    DESCRIPTION
        "ISO DPA:  Total-job-octets [low 31 bits]
        This attribute indicates the size of the job in octets,
        including document and job copies.  See xcmJobTotalOctetsHigh
        for the specification."
    DEFVAL { 0 }                        
    ::= { xcmJobGenSpoolingBasicEntry 4 }
xcmJobInterveningJobs OBJECT-TYPE
    SYNTAX     Integer32
    MAX-ACCESS read-only
    STATUS     current                 
    DESCRIPTION
        "The number of jobs that are expected to complete before this
        job is completed according to the implementation's queuing and
        processing algorithm if no other jobs were to be submitted.  In
        other words, this value is the job's queue position.  The agent
        SHALL return a value of 0 for this object when there are no
        other jobs that are expected to complete before this job.
        A value of (-2) shall be used when the number of intervening
        jobs is unknown.
        NOTE the ISO DPA language does not include the case when
        multiple jobs are in the 'processing' (or printing) state:
        ISO DPA:  Intervening-jobs
        This attribute indicates the number of other jobs to be
        processed before this job may be scheduled for processing.  The
        server shall set the value of this attribute to 0 when the job
        begins processing."
    DEFVAL { -2 }                       
    ::= { xcmJobGenSpoolingBasicEntry 5 }
--
--
xcmJobGenSpoolingExt  OBJECT IDENTIFIER ::= { xcmJobMonMIB 15 }
xcmJobGenSpoolingExtTable OBJECT-TYPE
    SYNTAX     SEQUENCE OF XcmJobGenSpoolingExtEntry
    MAX-ACCESS not-accessible
    STATUS     current
    DESCRIPTION
        "A table of general extended job information per device
        that is independent of the type of device but that does require
        a spooling implementation.
        Job information applies to the job as a whole or to all its
        documents.  The specification for each object is taken directly
        from the ISO 10175 Document Printing Application (DPA) standard
        clause 9.2, Job Attributes.    However, this MIB is
        intended to be used with non-DPA implementations, so only a
        small set of general DPA attributes have been included here."
    ::= { xcmJobGenSpoolingExt 1}
xcmJobGenSpoolingExtEntry OBJECT-TYPE
    SYNTAX     XcmJobGenSpoolingExtEntry
    MAX-ACCESS not-accessible
    STATUS     current
    DESCRIPTION
        "An entry exists in this table for each job in the (logical)
         device, no matter what the state of the job is.  Each device is
         represented as a separate device entry in the Host Resources
         MIB device table as a device of type 'printer', 'scanner',
         'fax', etc.
         The management station references each job using
         the xcmJobIdentifierOnSystem assigned by this (logical) device
         that accepted the job submission (by some other protocol).
         This table augments the Job General Basic
         table in this MIB."
    AUGMENTS { xcmJobGenBasicEntry }
    ::= { xcmJobGenSpoolingExtTable 1 }
XcmJobGenSpoolingExtEntry ::= SEQUENCE {
    xcmJobProcessAfter            DateAndTime,            
    xcmJobDeadlineTime            DateAndTime,            
    xcmJobDiscardTime             DateAndTime,            
    xcmJobRetentionPeriod         Cardinal32,             
    xcmJobMessageToOperator       CodeIndexedStringIndex, 
    xcmJobMessageFromOperator     CodeIndexedStringIndex, 
    xcmJobMessageFromAdministrator
                                  CodeIndexedStringIndex, 
    xcmJobPageCount               Cardinal32              
}
xcmJobProcessAfter OBJECT-TYPE
    SYNTAX     DateAndTime
    MAX-ACCESS read-only
    STATUS     current
    DESCRIPTION
        "Specifies the calendar date and time of day after which the
        server is to process the job on the specified device.  The
        server shall hold the job in the held state until the specified
        date and time.
        NOTE: In this MIB, this object applies to any type of job, not
        just print jobs and so this object is a generalization of the
        ISO DPA attribute which is only for print jobs.
        ISO DPA: Job-print-after
        This attribute specifies the calendar date and time of day
        after which the print-job shall become a candidate to be
        scheduled for printing [processing].
        If the value of this attribute is in the future, the server
        shall set the value of the job's current-job-state to held and
        add the job-print-after-specified value to the job's job-state-
        reasons attribute and shall not schedule the print-job for
        printing until the specified date and time has passed.  When
        the specified date and time arrives, the server shall remove
        the job-print-after-specified value from the job's job-state-
        reason attribute and, if no other reasons remain, shall change
        the job's current-job-state to pending so that the job becomes
        a candidate for being scheduled on printer(s).
        [For purposes of this MIB, the agent shall return the DEFVAL
        if the job did not specify this attribute and disregard the next
        paragraph.]
        The server shall assign an empty value (see DPA 9.1.2) to the
        job-print-after attribute when no print after time has been
        assigned, so that the job shall be a candidate for scheduling
        immediately."
    DEFVAL      { '0000000000000000'H } 
    ::= { xcmJobGenSpoolingExtEntry 1 }
xcmJobDeadlineTime OBJECT-TYPE
    SYNTAX     DateAndTime
    MAX-ACCESS read-only
    STATUS     current
    DESCRIPTION
        "ISO DPA:  job-deadline-time
        This attribute specifies the calendar date and time of day by
        which the user desires the print-job to be completed.  This
        attribute is treated as a scheduling hint only.  If the
        specified deadline time arrives before completion of the job,
        the server shall generate the error-past-deadline event for the
        job, but the current-job-state shall not be changed. This
        attribute is intended for use by servers that implement some
        form of deadline scheduling.
        [For purposes of this MIB, the agent shall return the DEFVAL
        if the job did not specify this attribute and disregard the next
        paragraph.]
        The server shall assign an empty value (see DPA 9.1.2) to the
        job-deadline-time attribute when there is no deadline for the
        job."
    DEFVAL      { '0000000000000000'H } 
    ::= { xcmJobGenSpoolingExtEntry 3 }
xcmJobDiscardTime OBJECT-TYPE
    SYNTAX     DateAndTime
    MAX-ACCESS read-only
    STATUS     current
    DESCRIPTION
        "ISO DPA:  job-discard-time
        This attribute specifies the calendar date and time of day at
        which the print-job should be discarded, whether or not the job
        has printed.
        If this attribute is supported and the discard time has not
        arrived, the server shall retain job and document attributes and
        status; the server is not required to retain job document files
        if the job has completed processing and has exceeded the job's
        job-retention-period. When the job-discard-time arrives, the
        server shall set the job's job-retention-period to zero and
        shall perform a CancelJob operation on the specified job.
        Whether or not the print-job is discarded if the
        error-past-discard event occurs while the job is being printed
        is implementation-dependent.
        [For purposes of this MIB, the agent shall return the DEFVAL
        if the job did not specify this attribute and disregard the next
        paragraph.]
        The server shall assign an empty value (see DPA 9.1.2) to the
        job-discard-time attribute when there is no discard time for the
        job."
    DEFVAL      { '0000000000000000'H } 
    ::= { xcmJobGenSpoolingExtEntry 4 }
xcmJobRetentionPeriod OBJECT-TYPE
    SYNTAX     Cardinal32
    UNITS      "seconds"
    MAX-ACCESS read-only
    STATUS     current
    DESCRIPTION
        "ISO DPA:  job-retention-period
        This attribute specifies the minimum period [in seconds] of time
        following the completion of job processing that the
        server shall keep job attributes, document attributes, and
        document data.  The server may keep these attributes and data
        longer than the value of the job-retention-period attribute.
        Job-retention-period specifies a lower bound on how long job
        attributes, document attributes and document data shall be
        retained by a server after printing [processing] has completed,
        whilst job-discard-time sets an upper bound on retention of the
        job and document attributes independent of whether the job is
        ever scheduled for, starts or completes printing [processing].
        In addition to providing status information to a user after a
        job has completed printing [processing, the job-retention-period
        also provides the mechanism for retaining job's document data
        after it has been printed [processed], so that the job may be
        printed [processed] again, possibly with modified attributes,
        such as the job-copies component of the job-results attribute.
        However, the mechanism to reprint the job is outside the scope
        of this part of ISO/IEC 10175.  [See ResubmitJob in Part 3.]"
    ::= { xcmJobGenSpoolingExtEntry 5 }
xcmJobMessageToOperator OBJECT-TYPE
    SYNTAX     CodeIndexedStringIndex
    MAX-ACCESS read-only
    STATUS     current
    DESCRIPTION
        "ISO DPA:  job-message-to-operator
        This attribute carries a message from the user to the operator
        to indicate something about the processing of this print-job.
        This message, unlike the job-start-message, is not necessarily
        related to other job-scheduling attributes.  The server shall
        make this message available to the operator when the job has
        been accepted."
    ::= { xcmJobGenSpoolingExtEntry 6 }
xcmJobMessageFromOperator OBJECT-TYPE
    SYNTAX     CodeIndexedStringIndex
    MAX-ACCESS read-only
    STATUS     current
    DESCRIPTION
        "Xerox extension to ISO DPA:  job-message-from-operator
        This attribute carries a message from the operator to the user
        to indicate something about the processing of this print-job.
        What additional notification methods are used, if any, in
        addition to providing a value for this job attribute depends on
        implementation."
    ::= { xcmJobGenSpoolingExtEntry 7 }
xcmJobMessageFromAdministrator OBJECT-TYPE
    SYNTAX     CodeIndexedStringIndex
    MAX-ACCESS read-only
    STATUS     current
    DESCRIPTION
        "ISO DPA:  Job-message-from-administrator
        This attribute provides a message from an operator, system
        administrator or 'intelligent' process to indicate to the user
        the reasons for modification or other management action taken
        on a job."
    ::= { xcmJobGenSpoolingExtEntry 8 }
xcmJobPageCount OBJECT-TYPE
    SYNTAX     Cardinal32
    MAX-ACCESS read-only
    STATUS     current
    DESCRIPTION
        "ISO DPA:  Job-page-count
        This attribute contains the number of source pages in the job
        that the server expects to image. The server shall compute this
        value by the following procedure:
        a)  For each document in the job object, multiply the value
        of document's page-count attribute by the value of its copy-
        count attribute and call the result document-set-page-count.
        b)  Add up all the document-set-page-counts from the previous
        step and call this sum the job-copy-page-count.
        c)  For each job-result-set, multiply the value of job-copy-
        page-count from the previous step by the value of job-copies
        element of the job-result-set and call the result job-result-
        set-page-count.
        d)  Add up all the job-result-set-page-counts from the
        previous step and set this sum into the job-page-count
        attribute.
        The value of this attribute is a measure of the amount of
        computation involved.
        The accuracy of this value is dependent on the accuracy of the
        page-count attribute in each document.  If some documents have
        a page-count value of 0, the server may set the value of this
        attribute to 0 and not use it for scheduling."
    ::= { xcmJobGenSpoolingExtEntry 9 }
--
--
xcmJobGenAccountingBasic  OBJECT IDENTIFIER ::= { xcmJobMonMIB 16 }
xcmJobGenAccountingBasicTable OBJECT-TYPE
    SYNTAX     SEQUENCE OF XcmJobGenAccountingBasicEntry
    MAX-ACCESS not-accessible
    STATUS     current                 
    DESCRIPTION
        "A table of general job accounting
        information per (logical if spooling or physical if not
        spooling) device that is independent of the type of device
        (printer, scanner, fax, ...).
        Job information applies to the job as a whole or to all its
        documents.  The specification for most objects is taken directly
        from the ISO 10175 Document Printing Application (DPA) standard
        clause 9.2, Job Attributes.  However, this MIB is
        intended to be used with non-DPA implementations, so only a
        small set of general DPA attributes have been included here."
    ::= { xcmJobGenAccountingBasic 1}
xcmJobGenAccountingBasicEntry OBJECT-TYPE
    SYNTAX     XcmJobGenAccountingBasicEntry
    MAX-ACCESS not-accessible
    STATUS     current                 
    DESCRIPTION
        "An entry exists in this table for each job in the device,
         no matter what the state of the job is.  Each device is
         represented as a separate device entry in the Host Resources
         MIB device table as a device of type 'printer', 'scanner',
         'fax', etc.  The management station references each job using
         the xcmJobIdentifierOnSystem assigned by this logical
         (for spooling) or physical (not spooling) device that accepted
         the job submission (by some other protocol)."
    AUGMENTS { xcmJobGenBasicEntry }
    ::= { xcmJobGenAccountingBasicTable 1 }
XcmJobGenAccountingBasicEntry ::= SEQUENCE {
    xcmJobAccountingBasicRowStatus RowStatus,
    xcmJobAccountingUserName     CodeIndexedStringIndex,
    xcmJobAccountingInformation  OCTET STRING,
    xcmJobStartedProcessingTime  DateAndTime,
    xcmJobImpressionsCompleted   Counter32,
    xcmJobMediaSheetsCompleted   Counter32,
    xcmJobCompletionTime         DateAndTime,
    xcmJobWorkUnitType           XcmHrDevTrafficUnit,
    xcmJobUnitsOfWorkCompleted   Counter32
}
xcmJobAccountingBasicRowStatus OBJECT-TYPE
    SYNTAX      RowStatus
    MAX-ACCESS  read-write
    STATUS      current                 
    DESCRIPTION "
        Manages the status of this conceptual row in the
        xcmJobGenAccountingBasicTable.  When an accounting program
        has copied the data from this row into an accounting system,
        the accounting program should set destroy into this object
        in order to delete this row and all related xcmJob.,
        and xcmXxxConsumed. rows, in order to
        indicate that this accounting and job information is no
        longer needed to be retained by the SNMP agent."
    ::= { xcmJobGenAccountingBasicEntry 1 }
xcmJobAccountingUserName OBJECT-TYPE
    SYNTAX     CodeIndexedStringIndex
    MAX-ACCESS read-only
    STATUS     current                 
    DESCRIPTION
        "This attribute specifies the name of the user for accounting
        purposes.  See xcmJobOriginator, xcmJobOwner, and
        xcmJobAuthorizationUserName for additional
        user names for other purposes (and whose values may be
        different).  An agent may return the same value for all four
        attributes, if the printer or service does not support all
        four concepts.
        NOTE: There is no corresponding ISO DPA attribute (but there
        should be).  Often the xcmJobAuthorizationUserName will be the
        same as xcmJobAccountingUserName."
    DEFVAL { 0 }                        
    ::= { xcmJobGenAccountingBasicEntry 2 }
xcmJobAccountingInformation OBJECT-TYPE
    SYNTAX     OCTET STRING(SIZE(0..255))
    MAX-ACCESS read-only
    STATUS     current                 
    DESCRIPTION
        "This object is intended as an accounting identifier, so
        that a user can indicate to which account this job should
        be charged.  A user can have any number of accounts.  For
        example, a lawyer might charge each customer separately.
        The value can be text, binary, or encrypted.
        ISO DPA:  Accounting-information
        This attribute specifies information required by accounting
        services (e.g. the account to be charged for any services
        rendered).
        Accounting information is intended to be interpreted by an
        accounting system, and may be opaque to the print service."
    DEFVAL { ''H }                      
    ::= { xcmJobGenAccountingBasicEntry 3 }
xcmJobStartedProcessingTime OBJECT-TYPE
    SYNTAX     DateAndTime
    MAX-ACCESS read-only
    STATUS     current                 
    DESCRIPTION
        "The time at which the job started to be processed by the
        intended device (printed, scanned, faxed, etc.).
        NOTE: For use with this MIB, this attribute has been generalized
        to be used with any device, whereas the corresponding ISO DPA
        attribute is only started printing.
        A conforming implementation shall return an actual date and
        time, rather than the DEFVAL, unless the implementation cannot
        tell time.
        ISO DPA: Started-printing-time
        This attribute indicates the time at which this job started
        printing [processing]."
    DEFVAL      { '0000000000000000'H } 
    ::= { xcmJobGenAccountingBasicEntry 4 }
xcmJobImpressionsCompleted OBJECT-TYPE
    SYNTAX     Counter32
    MAX-ACCESS read-only
    STATUS     current                 
    DESCRIPTION
        "If no impressions are completed, this value shall remain 0.
        ISO DPA:  Impressions-completed
        This attribute indicates the number of impressions that the
        printer engine(s) have placed on the media for the job. See the
        note in the pages-completed attribute for the relationship of
        the pages-completed, impressions-completed and media-sheets-
        completed attributes.
        The server shall not reset its value during the processing of
        multiple copies of documents or the job.  Since this attribute
        is intended to measure the progress of a job, the value shall
        include repeated pages due to multiple copies. When the job
        completes, this attribute should contain the value of the total
        number of impressions that the printer made for the print-job.
        The accuracy of this value is implementation-dependent. It is
        expected that the value reported is never greater than the
        actual value.  This attribute may not be supported for all
        printers and all page description languages.
        The value of this attribute shall be 0 if printing [processing]
        has not started for this job."
    ::= { xcmJobGenAccountingBasicEntry 5 }
xcmJobMediaSheetsCompleted OBJECT-TYPE
    SYNTAX     Counter32
    MAX-ACCESS read-only
    STATUS     current                 
    DESCRIPTION
        "If no media sheets are completed, this value shall remain 0.
        ISO DPA:  Media-sheets-completed
        This attribute indicates the number of sheets of media that the
        printer(s) have completed printing for the job. See the note in
        the pages-completed attribute for the relationship of the
        pages-completed, impressions-completed and media-sheets-
        completed attributes.
        The server shall not reset its value during the processing of
        multiple copies of documents or the job.  Since this attribute
        is intended to measure the progress of a job, the value shall
        include repeated pages due to multiple copies. When the job
        completes, this attribute should contain the value of the total
        number of sheets of media used for the print-job.
        The accuracy of this value is implementation-dependent. It is
        expected that the value reported is never greater than the
        actual value.  This attribute may not be supported for all
        printers and all page description languages.
        The value of this attribute shall be 0 if printing has not
        started for this job."
    ::= { xcmJobGenAccountingBasicEntry 6 }
xcmJobCompletionTime OBJECT-TYPE
    SYNTAX     DateAndTime
    MAX-ACCESS read-only
    STATUS     current                 
    DESCRIPTION
        "A conforming implementation shall return an actual date and
        time, rather than the DEFVAL, unless the implementation cannot
        tell time.
        ISO DPA:  Completion-time
        This attribute indicates the time at which this job completed.
        Providing this time is useful for jobs which are retained after
        printing."
    DEFVAL      { '0000000000000000'H } 
    ::= { xcmJobGenAccountingBasicEntry 7 }
xcmJobWorkUnitType OBJECT-TYPE
    SYNTAX     XcmHrDevTrafficUnit
    MAX-ACCESS read-only
    STATUS     current                 
    DESCRIPTION
        "Xerox extension
        This attribute indicates the type of work that is being
        accounted for.  It shall be different from pages, sheets, or
        impressions, which already have their own objects."
    DEFVAL { unknown }                  
    ::= { xcmJobGenAccountingBasicEntry 8 }
xcmJobUnitsOfWorkCompleted OBJECT-TYPE
    SYNTAX     Counter32
    MAX-ACCESS read-only
    STATUS     current                 
    DESCRIPTION
        "Xerox extension:
        The number of work units completed.  See xcmJobWorkUnitType to
        determine what is being counted."
    ::= { xcmJobGenAccountingBasicEntry 9 }
--
--
xcmMediaConsumed  OBJECT IDENTIFIER ::= { xcmJobMonMIB 17 }
xcmMediaConsumedTable OBJECT-TYPE
    SYNTAX     SEQUENCE OF XcmMediaConsumedEntry
    MAX-ACCESS not-accessible
    STATUS     current                 
    DESCRIPTION
        "This table contains pairs of media indexes and the number of
        sheets of that media consumed by this job."
    ::= { xcmMediaConsumed 1 }
xcmMediaConsumedEntry OBJECT-TYPE
    SYNTAX     XcmMediaConsumedEntry
    MAX-ACCESS not-accessible
    STATUS     current                 
    DESCRIPTION
        "Entries may exist in the table for each device index in the
        Host Resource MIB whose device type is `printer', 'fax', etc.,
        and for each job."
    INDEX { hrDeviceIndex, xcmJobIdentifierOnSystem,
            xcmMediaConsumedIndex }
    ::= { xcmMediaConsumedTable 1 }
XcmMediaConsumedEntry ::= SEQUENCE {
    xcmMediaConsumedIndex         Ordinal16,
    xcmMediaConsumedRowStatus     RowStatus,
    xcmMediaConsumedType          XcmJMMediumType,
    xcmMediaConsumedName          CodeIndexedStringIndex,
    xcmMediaConsumedSheetCount    Counter32
}
xcmMediaConsumedIndex OBJECT-TYPE
    SYNTAX     Ordinal16
    MAX-ACCESS not-accessible
    STATUS     current                 
    DESCRIPTION
        "A unique value used by the device to identify this medium
        entry in this job.  For devices and systems that ensure that
        jobs are not lost across crashes and power cycles, these
        values shall remain stable across successive device power
        cycles.  However, if a (low-end) device is not ensuring that job
        are persistent across crashes and power cycles, these index
        values need not remain stable across such crashes or power
        cycles."
    ::= { xcmMediaConsumedEntry 1 }
xcmMediaConsumedRowStatus OBJECT-TYPE
    SYNTAX      RowStatus
    MAX-ACCESS  read-write
    STATUS      current                 
    DESCRIPTION
        "Manages the status of this conceptual row in the
        xcmMediaConsumedTable.  When an accounting program
        has copied the data from this row into an accounting system,
        the accounting program should delete this row in order to
        indicate that this accounting information is no longer needed
        to be retained by the SNMP agent.
        Since the accounting data may be of interest to end-users,
        the accounting program may want to wait for some period before
        deleting the row.
        If the accounting table becomes filled up so that the agent is
        unable to add new entries, a device may either refuse to accept
        new jobs, so that the valuable revenue stream is not lost, or
        may remove the oldest entry in the display and add the new
        job's accounting data."
    ::= { xcmMediaConsumedEntry 2 }
xcmMediaConsumedType OBJECT-TYPE
    SYNTAX     XcmJMMediumType
    MAX-ACCESS read-only
    STATUS     current                 
    DESCRIPTION
        "This attribute indicates the medium type that has been consumed
        by the device(s) for this job, e.g. stationery, envelope,
        transparency, etc."
    DEFVAL { unknown }                  
    ::= { xcmMediaConsumedEntry 3 }
xcmMediaConsumedName OBJECT-TYPE
    SYNTAX     CodeIndexedStringIndex
    MAX-ACCESS read-only
    STATUS     current                 
    DESCRIPTION
        "This attribute indicates the name of the medium that has been
        consumed by the device(s) for this job, e.g. letter-white,
        iso-a4-white, iso-a4-blanc, monarch-envelope,
        iso-a4-transparent, etc.
        ISO DPA assigns OIDs to medium names, but also allows the SA to
        define new media using text strings.  Hence, the object in this
        MIB is a text string, so that the SA can define additional
        medium names as needed."
    DEFVAL { 0 }                        
    ::= { xcmMediaConsumedEntry 4 }
xcmMediaConsumedSheetCount OBJECT-TYPE
    SYNTAX     Counter32
    MAX-ACCESS read-only
    STATUS     current                 
    DESCRIPTION
        "This attribute indicates the number of sheets of the medium
        that have been consumed by the device(s) for this job."
    ::= { xcmMediaConsumedEntry 5 }
--
--
xcmColorImpsConsumed  OBJECT IDENTIFIER ::= { xcmJobMonMIB 18 }
xcmColorImpsConsumedTable OBJECT-TYPE
    SYNTAX     SEQUENCE OF XcmColorImpsConsumedEntry
    MAX-ACCESS not-accessible
    STATUS     current
    DESCRIPTION
        "This table contains pairs of colorant indexes and the number
        of impressions of that colorant consumed by this job."
    ::= { xcmColorImpsConsumed 1 }
xcmColorImpsConsumedEntry OBJECT-TYPE
    SYNTAX     XcmColorImpsConsumedEntry
    MAX-ACCESS not-accessible
    STATUS     current
    DESCRIPTION
        "Entries may exist in the table for each device index whose
        device type is 'printer', 'fax', etc. and for each job."
    INDEX { hrDeviceIndex, xcmJobIdentifierOnSystem,
            xcmColorImpsConsumedIndex }
    ::= { xcmColorImpsConsumedTable 1 }
XcmColorImpsConsumedEntry ::= SEQUENCE {
    xcmColorImpsConsumedIndex           Ordinal16, 
    xcmColorImpsConsumedRowStatus       RowStatus, 
    xcmColorImpsConsumedTypeIndex       Ordinal16, 
    xcmColorImpsConsumedCount           Counter32  
}
xcmColorImpsConsumedIndex OBJECT-TYPE
    SYNTAX     Ordinal16
    MAX-ACCESS not-accessible
    STATUS     current
    DESCRIPTION
        "A unique value used by the printer to identify this colorant
        entry for this job.  For devices and systems that ensure that
        jobs are not lost across crashes and power cycles, these
        values shall remain stable across successive device power
        cycles.
        However, if a (low-end) device is not ensuring that job are
        persistent across crashes and power cycles, these index values
        need not remain stable across such crashes or power cycles."
    ::= { xcmColorImpsConsumedEntry 1 }
xcmColorImpsConsumedRowStatus OBJECT-TYPE
    SYNTAX      RowStatus
    MAX-ACCESS  read-write
    STATUS      current
    DESCRIPTION
        "Manages the status of this conceptual row in the
        xcmColorImpsConsumedTable.  When an accounting program
        has copied the data from this row into an accounting system,
        the accounting program should delete this row in order to
        indicate that this accounting information is no longer needed
        to be retained by the SNMP agent."
    ::= { xcmColorImpsConsumedEntry 2 }
xcmColorImpsConsumedTypeIndex OBJECT-TYPE
    SYNTAX     Ordinal16
    MAX-ACCESS read-only
    STATUS     current
    DESCRIPTION
        "This attribute indicates one of the colorant type (index into
        the prtColorantsTable in the Printer MIB) that have been
        consumed by the printer(s) for this print job."
    ::= { xcmColorImpsConsumedEntry 3 }
xcmColorImpsConsumedCount OBJECT-TYPE
    SYNTAX     Counter32
    MAX-ACCESS read-only
    STATUS     current
    DESCRIPTION
        "This attribute indicates the number of impressions that have
        been consumed by the printer(s) for this print job and this
        colorant.  For implementations that make a separate impression
        for each colorant used shall increment this count once for
        each colorant, so that the total number of
        xcmColorImpsConsumedCount for the job will be a multiple of the
        xcmJobImpressionsCompleted value."
    ::= { xcmColorImpsConsumedEntry 4 }
--
--
--
--
xcmJobImpsByMediumSize  OBJECT IDENTIFIER ::= { xcmJobMonMIB 21 }
xcmJobImpsByMediumSizeTable OBJECT-TYPE
    SYNTAX      SEQUENCE OF XcmJobImpsByMediumSizeEntry
    MAX-ACCESS  not-accessible
    STATUS      current                 
    DESCRIPTION
        "This table contains tuples of medium size, count-type,
        and the number of impressions counted by count-type on that
        medium consumed by this job."
    ::= { xcmJobImpsByMediumSize 1 }
xcmJobImpsByMediumSizeEntry OBJECT-TYPE
    SYNTAX      XcmJobImpsByMediumSizeEntry
    MAX-ACCESS  not-accessible
    STATUS      current                 
    DESCRIPTION
        "This entry has one tuple of medium size, count-type,
        and the number of impressions counted by count-type on that
        medium consumed by this job."
    INDEX   { hrDeviceIndex,
              xcmJobIdentifierOnSystem,
              xcmJobImpsByMediumSizeIndex }
    ::= { xcmJobImpsByMediumSizeTable 1 }
XcmJobImpsByMediumSizeEntry ::= SEQUENCE {
    xcmJobImpsByMediumSizeIndex        Ordinal16,
    xcmJobImpsByMediumSizeRowStatus    RowStatus,
    xcmJobImpsByMediumSizeMediumSize   XcmPrtMediumSize,
    xcmJobImpsByMediumSizeCountType    XcmJMImpsCountType,
    xcmJobImpsByMediumSizeCount        Counter32,
    xcmJobImpsByMediumSizeCountQuality XcmPrtPrintQuality
    }
xcmJobImpsByMediumSizeIndex OBJECT-TYPE
    SYNTAX     Ordinal16
    MAX-ACCESS not-accessible
    STATUS     current                 
    DESCRIPTION
        "A unique value used by the device to identify this
        impressions-by-medium-size entry in this job.  For devices and
        systems that ensure that jobs are not lost across crashes and
        power cycles, these values shall remain stable across successive
        device power cycles.  However, if a (low-end) device is not
        ensuring that job are persistent across crashes and power
        cycles, these index values need not remain stable across such
        crashes or power cycles."
    ::= { xcmJobImpsByMediumSizeEntry 1 }
xcmJobImpsByMediumSizeRowStatus OBJECT-TYPE
    SYNTAX      RowStatus
    MAX-ACCESS  read-write
    STATUS      current                 
    DESCRIPTION
        "Manages the status of this conceptual row in the
        xcmJobImpsByMediumSizeTable.  When an accounting program
        has copied the data from this row into an accounting system,
        the accounting program should delete this row in order to
        indicate that this accounting information is no longer needed
        to be retained by the SNMP agent.
        Since the accounting data may be of interest to end-users,
        the accounting program may want to wait for some period before
        deleting the row.
        If the accounting table becomes filled up so that the agent is
        unable to add new entries, a device may either refuse to accept
        new jobs, so that the valuable revenue stream is not lost, or
        may remove the oldest entry in the display and add the new
        job's accounting data."
    ::= { xcmJobImpsByMediumSizeEntry 2 }
xcmJobImpsByMediumSizeMediumSize OBJECT-TYPE
    SYNTAX     XcmPrtMediumSize
    MAX-ACCESS read-only
    STATUS     current                 
    DESCRIPTION
        "This attribute indicates the medium size that has been produced
        by the device(s) for this job, e.g. naLetter(1000), isoA4(1024),
        jisB4(1084), etc."
    DEFVAL { unknown }                  
    ::= { xcmJobImpsByMediumSizeEntry 3 }
xcmJobImpsByMediumSizeCountType OBJECT-TYPE
    SYNTAX     XcmJMImpsCountType
    MAX-ACCESS read-only
    STATUS     current                 
    DESCRIPTION
        "This attribute indicates the count-type that is how to count
        impressions produced by the device(s) for this job, e.g.
        blackAndWhiteCount, highlightColorCount, fullColorCount,
        etc."
    DEFVAL { totalCount }               
    ::= { xcmJobImpsByMediumSizeEntry 4 }
xcmJobImpsByMediumSizeCount OBJECT-TYPE
    SYNTAX     Counter32
    MAX-ACCESS read-only
    STATUS     current                 
    DESCRIPTION
        "This attribute indicates the number of impressions by medium
        size, count-type, and quality-type for the job, which are
        specified respectively by xcmJobImpsByMediumSizeMediumSize,
        xcmJobImpsByMediumSizeCountType, and
        xcmJobImpsByMediumSizeCountQuality."
    ::= { xcmJobImpsByMediumSizeEntry 5 }
xcmJobImpsByMediumSizeCountQuality OBJECT-TYPE
    SYNTAX     XcmPrtPrintQuality
    MAX-ACCESS read-only
    STATUS     current
    DESCRIPTION
        "This attribute indicates the quality-type used for counting
        impressions produced by the device(s) for this job, e.g., draft,
        normal, high, etc."
    REFERENCE "
        xcmPrtInterpPrintQuality, from 16prtx.mib"
    DEFVAL { normal }      
    ::= { xcmJobImpsByMediumSizeEntry 6 }
--
--
--
xcmJobAlert  OBJECT IDENTIFIER ::= { xcmJobMonMIB 19 }
xcmJobV1AlertNew OBJECT-IDENTITY
    STATUS     current
    DESCRIPTION
        "The value of the enterprise-specific OID in an SNMPv1 trap sent
        whenever the state of a job changes."
    REFERENCE
        "See SNMPv2 'xcmJobV2AlertNew' trap definitions below for
        'special semantics'."
    ::= { xcmJobAlert 4 }
xcmJobV2AlertPrefixNew OBJECT IDENTIFIER ::= { xcmJobV1AlertNew 0 }
xcmJobV2AlertNew NOTIFICATION-TYPE
    OBJECTS { hrDeviceIndex, xcmJobIdentifierOnSystem }
    STATUS  current                    
    DESCRIPTION
        "This trap is sent whenever the state of a job changes.  The
        'state of a job' is comprised by the aggregate values of the
        xcmJobCurrentState, xcmJobPriority, xcmJobStateReasons,
        xcmJobXStateReasons, xcmJobX2StateReasons,
        xcmDevicesAssigned and xcmDeviceStateOfDevicesAssigned
        fields of the job's table entries:  This notification is
        sent whenever any of these values changes with the following
        exceptions:
        1. Changes in xcmDeviceStateOfDevicesAssigned shall only
        generate traps when the job is in the processing state
        (NOTE - xcmJMDevicesAssignedGroup is deprecated)
        2. Changes in xcmJobStateReasons, xcmJobXStateReasons, and
        xcmJobX2StateReasons shall only generate traps when the job is
        in the processing state (rare).  The normal polling cycle will
        pick up any changes while the job is not in the processing
        state.  Since most changes in reasons also accompany a job state
        change, the chances that a change in a reason will have to wait
        for the normal polling cycle is very small.  For example, a
        requester further modifies a held job adding more reasons for it
        to be held will have to wait for the polling cycle, since the
        job does not change state (remaining in the held state).
        NOTE - the hrDeviceIndex is included for convenience, even
        though the Printer MIB (RFC 1759) doesn't include hrDeviceIndex
        in its traps.  Then the management station doesn't have to parse
        the received varBind OIDs on a trap in order to discover which
        device trapped.
        NOTE - the addition of an entire row to the job tables
        corresponds to the acceptance of another job by the server.  The
        state of the job changes from unknown to a specific value
        (usually pending).  Therefore, the agent shall generate a trap
        when a job is accepted (so that the management station can
        display the newly arrived job in a timely fashion).
        Similarly when the server removes a job because the job has been
        in the completed state for a sufficient time or the job has been
        deleted by a Delete operation, the SNMP agent shall reflect
        that removal by removing the row from the job tables, and shall
        generate a trap (since the state of the job has changed to
        non-existent).
        The IETF Printer MIB maintains a table which serves as a sort
        of 'audit-trail' of recent alerts.  There is no need for such
        a table here, since the job's tables will serve virtually the
        same purpose.
        As with all SNMP notifications, critical applications cannot
        completely rely upon delivery:  some amount of polling is
        recommended.
        The variable-bindings of this trap have been chosen to give the
        minimum of information:  the xcmJobIdentifierOnSystem
        value and hrDeviceIndex are provided.  With these an application
        is able to obtain the full job table entry.  An application has
        to look at the job tables anyway.  The time of the alert is
        returned as part of any SNMP trap.
        The hrDeviceIndex maps one-to-one with the PWG Job Mon
        jmGeneralJobSetIndex.  (The PWG Job Mon does not require the
        Host Resources MIB, so the name of the primary index for all PWG
        Job Mon tables is not hrDeviceIndex, but serves the same
        purpose of allowing multiple instances in a single device or
        server.
        The Job Alert's special semantics is covered by U.S. patent
        5778183.
        This notification has the following special semantics:
            o  If the job's xcmJobClientId field is not empty,
               its value will also be appended to trap object ID.
               NOTE: If the format of the xcmJobClientId is dotted
               decimal representation, then it will be encoded as a BER
               binary OID appended to the trap object ID.
               NOTE: The BER binary OID shall not include the ASN.1/BER
               tag of 6 indicating an OID and shall not include the
               ASN.1/BER length field in octets of the OID.
        This trap OID qualifier allows job-submission and monitoring
        applications to limit the alerts they receive to ones generated
        by jobs which they have submitted.
        NOTE: The sum of the trap var bind values must be less than can
        fit into a PDU on any transport, roughly 540 octets on some
        transports.  Thus implementers are warned to minimize the length
        of the xcmJobClientId and xcmJobIdentifierOnSystem objects."
    ::= { xcmJobV2AlertPrefixNew 1 }
--
--         "This trap is sent whenever a job changes state."
--
--
xcmDocAlert  OBJECT IDENTIFIER ::= { xcmJobMonMIB 20 }
xcmDocV1AlertNew OBJECT-IDENTITY
    STATUS     current
    DESCRIPTION
        "The value of the enterprise-specific OID in an SNMPv1 trap sent
        whenever the state of a document changes."
    REFERENCE
        "See SNMPv2 'xcmDocV2AlertNew' trap definitions below for
        'special semantics'."
    ::= { xcmDocAlert 4 }
xcmDocV2AlertPrefixNew  OBJECT IDENTIFIER ::= { xcmDocV1AlertNew 0 }
xcmDocV2AlertNew NOTIFICATION-TYPE
    OBJECTS { hrDeviceIndex, xcmJobIdentifierOnSystem,
              xcmDocSequenceNumber }
    STATUS current                    
    DESCRIPTION
        "This trap is sent whenever the state of one of the documents in
        a job changes.  The state of a single document is represented in
        the xcmDocGenBasicTable column: xcmDocState.
        The job's xcmJobIdentifierOnSystem and the document's
        xcmDocSequenceNumber are included in the trap's variable
        bindings; these can be used to reference the document's
        xcmDocGenBasicTable entry.
        NOTE - the addition of an entire row to the document tables
        corresponds to the acceptance of another document (in a job) by
        the server.  The state of the document changes from unknown to a
        specific value (usually transfer pending).  Therefore, the agent
        generates a trap when a document (within a job) is accepted (so
        that the management station can display the newly arrived
        document in a timely fashion).
        This notification has the following special semantics:
            1  The agent shall append the document's job's
               xcmJobClientId to the trap object ID, if the document's
               job's xcmJobClientId field is not empty.
               NOTE: If the format of the xcmJobClientId is dotted
               decimal representation, then it will be encoded as a BER
               binary OID appended to the trap object ID.
               NOTE: The BER binary OID shall not include the ASN.1/BER
               tag of 6 indicating an OID and shall not include the
               ASN.1/BER length field in octets of the OID.
            2  The agent shall append the value of the document's
               xcmDocSequenceNumber field to the trap object ID.
        These trap OID qualifiers allow job-submission and monitoring
        applications to specify exactly which alerts they are interested
        in and to limit the alerts they receive to ones generated by
        jobs or jobs and documents that they have submitted.
        NOTE: The sum of the trap var bind values must be less than can
        fit into a PDU on any transport, roughly 540 octets on some
        transports.  Thus implementers are warned to minimize the length
        of the xcmJobClientId and xcmJobIdentifierOnSystem objects."
    ::= { xcmDocV2AlertPrefixNew 1 }
--
--         "This trap is sent whenever a document (in a job) changes
--         state."
xcmJobMonMIBConformance  OBJECT IDENTIFIER ::= { xcmJobMonMIB 2 }
xcmJobMonCompliance MODULE-COMPLIANCE
    STATUS current
    DESCRIPTION
        "The mandatory compliance statement for the agents that
        implement the XCMI Job Monitoring MIB, i.e., all the mandatory
        groups.
        NOTE: These two groups are CONDITIONALLY MANDATORY as far as
        XCMI Conformance is concerned.  But if the conditions are
        satisfied (traps and/or SJMM), then these groups MUST be
        implemented, making them effectively MANDATORY."
    MODULE 
    MANDATORY-GROUPS { xcmJMBaseGroup,
                       xcmJMJobGenBasicGroup }
-- DESCRIPTION  "
--     objects."
    OBJECT       xcmJobIdentifierUpstream
    SYNTAX       DisplayString (SIZE(0..32))
    DESCRIPTION  ""
    OBJECT       xcmJobClientId
    SYNTAX       OCTET STRING (SIZE(0..32))
    DESCRIPTION  ""
--     DESCRIPTION  "Deprecated"
--     DESCRIPTION  "Deprecated"
    ::= { xcmJobMonMIBConformance 1 }
--
--
xcmJobMonMIBGroups  OBJECT IDENTIFIER ::= { xcmJobMonMIBConformance 3 }
xcmJMBaseGroup OBJECT-GROUP                 
    OBJECTS {    xcmJobMonBaseRowStatus,
                 xcmJobMonBaseVersionID,
                 xcmJobMonBaseVersionDate,
                 xcmJobMonBaseGroupSupport,
                 xcmJobMonBaseCreateSupport,
                 xcmJobMonBaseUpdateSupport  }
    STATUS       current
    DESCRIPTION
        "The conditionally mandatory Job Monitoring Base group,
        i.e., SHALL be implemented if implementing traps and/or SJMM."
    ::= { xcmJobMonMIBGroups 1 }   
xcmJMJobGenBasicGroup OBJECT-GROUP          
    OBJECTS {    xcmJobIdentifierOnSystem,
                 xcmJobIdentifierUpstream,
                 xcmJobClientId,
                 xcmJobServiceType,
                 xcmJobName,
                 xcmJobOwner,
                 xcmJobSourceChannelType,
                 xcmJobSubmittedLocaleIndex,
                 xcmJobCurrentState,
                 xcmJobStateReasons,
                 xcmJobXStateReasons,
                 xcmJobX2StateReasons
 }
    STATUS    current
    DESCRIPTION
        "The conditionally mandatory Job General Basic group,
        i.e., SHALL be implemented if implementing traps and/or SJMM."
    ::= { xcmJobMonMIBGroups 6 }   
xcmJMDevicesAssignedGroup OBJECT-GROUP                    
    OBJECTS {    xcmDeviceStateOfDevicesAssigned,
                 xcmJobIdentifierDownstream
 }
    STATUS    current                 
    DESCRIPTION
        "The deprecated Devices Assigned group."
    ::= { xcmJobMonMIBGroups 7 }
xcmJMClientIdMapGroup OBJECT-GROUP                        
    OBJECTS {    xcmClientIdMapHrDeviceIndex }
    STATUS    current
    DESCRIPTION
        "The optional client id map group - applies to all jobs."
    ::= { xcmJobMonMIBGroups 8 }
xcmJMJobGenExtGroup OBJECT-GROUP           
    OBJECTS {    xcmJobOriginator,
                 xcmJobSubmittingApplication,
                 xcmJobComment,
                 xcmJobCopies,
                 xcmJobCopiesCompleted,
                 xcmJobOutputBinIndex,
                 xcmJobServiceNameRequested,
                 xcmJobPreviousState,
                 xcmJobEstimatedCompletionTime,
                 xcmJobSubmissionTime,
                 xcmJobPagesCompleted,
                 xcmJobOctetsCompletedHigh,
                 xcmJobOctetsCompletedLow,
                 xcmJobErrorCount,
                 xcmJobWarningCount,
                 xcmJobProcessingTime,
                 xcmJobNumberOfDocuments,
                 xcmJobAuthorizationUserName }
    STATUS    current                 
    DESCRIPTION
        "The Job General Extended group."
    ::= { xcmJobMonMIBGroups 10 }
xcmJMDocGenBasicGroup OBJECT-GROUP 
    OBJECTS {    xcmDocSequenceNumber,
                 xcmDocName,
                 xcmDocFileName,
                 xcmDocFileNameType,
                 xcmDocType,
                 xcmDocFormat,
                 xcmDocFormatVariants,
                 xcmDocFormatVersion,
                 xcmDocOctetCount,
                 xcmDocState }
    STATUS    current
    DESCRIPTION
        "The document information group."
    ::= { xcmJobMonMIBGroups 12 }
xcmJMDocPrintExtGroup OBJECT-GROUP      
    OBJECTS {    xcmDocPrintDefaultMediumName,
                 xcmDocPrintDefaultInputIndex,
                 xcmDocPrintFinishing,
                 xcmDocPrintOutputMethod,
                 xcmDocPrintNumberUp,
                 xcmDocPrintSides,
                 xcmDocPrintCopyCount,
                 xcmDocPrintCopiesCompleted }
    STATUS    current
    DESCRIPTION
        "The Document Print-centric group."
    ::= { xcmJobMonMIBGroups 13 }
xcmJMJobGenSpoolingBasicGroup OBJECT-GROUP  
    OBJECTS {    xcmJobNumberOfJobResultSets,
                 xcmJobPriority,
                 xcmJobTotalOctetsHigh,
                 xcmJobTotalOctetsLow,
                 xcmJobInterveningJobs }
    STATUS    current                 
    DESCRIPTION
        "The Job General Spooling Basic group."
    ::= { xcmJobMonMIBGroups 14 }
xcmJMJobGenSpoolingExtGroup OBJECT-GROUP    
    OBJECTS {    xcmJobProcessAfter,
                 xcmJobDeadlineTime,
                 xcmJobDiscardTime,
                 xcmJobRetentionPeriod,
                 xcmJobMessageToOperator,
                 xcmJobMessageFromOperator,
                 xcmJobMessageFromAdministrator,
                 xcmJobPageCount }
    STATUS    current
    DESCRIPTION
        "The Job General Spooling Extended group."
    ::= { xcmJobMonMIBGroups 15 }
xcmJMJobGenAccountingBasicGroup OBJECT-GROUP  
    OBJECTS {    xcmJobAccountingBasicRowStatus,
                 xcmJobAccountingUserName,
                 xcmJobAccountingInformation,
                 xcmJobStartedProcessingTime,
                 xcmJobImpressionsCompleted,
                 xcmJobMediaSheetsCompleted,
                 xcmJobCompletionTime,
                 xcmJobWorkUnitType,
                 xcmJobUnitsOfWorkCompleted }
    STATUS    current                 
    DESCRIPTION
        "The Job General Accounting Basic group."
    ::= { xcmJobMonMIBGroups 16 }
xcmJMMediaConsumedGroup OBJECT-GROUP      
    OBJECTS {    xcmMediaConsumedRowStatus,
                 xcmMediaConsumedType,
                 xcmMediaConsumedName,
                 xcmMediaConsumedSheetCount }
    STATUS    current                 
    DESCRIPTION
        "The media consumed group."
    ::= { xcmJobMonMIBGroups 17 }
xcmJMColorImpsConsumedGroup OBJECT-GROUP          
    OBJECTS {    xcmColorImpsConsumedRowStatus,
                 xcmColorImpsConsumedTypeIndex,
                 xcmColorImpsConsumedCount }
    STATUS    current
    DESCRIPTION
        "The optional color impressions consumed group."
    ::= { xcmJobMonMIBGroups 18 }
xcmJMJobImpsByMediumSizeGroup OBJECT-GROUP  
    OBJECTS {    xcmJobImpsByMediumSizeRowStatus,
                 xcmJobImpsByMediumSizeMediumSize,
                 xcmJobImpsByMediumSizeCountType,
                 xcmJobImpsByMediumSizeCount,
                 xcmJobImpsByMediumSizeCountQuality   }
    STATUS       current              
    DESCRIPTION "The Job Impressions by Medium Size group."
    ::= { xcmJobMonMIBGroups 21 }
--         "The conditionally mandatory job alert group defines no
--         objects and so has to be commented out in order to compile."
--         "The conditionally mandatory doc alert group defines no
--         objects and so has to be commented out in order to compile."
xcmSimpleJobMgmtTC OBJECT-IDENTITY -- MODULE-IDENTITY
    STATUS   current
    DESCRIPTION
        "Version:   5.10.pub
        Textual Conventions companion to the XCMI Simple Job Mgmt MIB,
        the MIB module for performing lightweight management of jobs
        in network accessible host systems.
        See:    Document Printing Application - Part 1: Abstract Service
                (ISO/IEC 10175-1 / Final Text, March 1996).
        See:    POSIX System Administration - Part 4: Print Interfaces
                (IEEE 1387.4 / Draft 8, October 1994).
        See:    OSI Reference Model - Part 1:  Basic Reference Model
                (CCITT X.200:1992 | ISO 7498-1:1992).
        Copyright (C) 1997-2002 Xerox Corporation. All Rights Reserved."
    ::= { xeroxCommonMIB 75 }
--
--
XcmSimpleJobMgmtGroupSupport ::= TEXTUAL-CONVENTION
    STATUS      current
    DESCRIPTION
        "The terse conformance statement of ALL mandatory, conditionally
        mandatory, and optional XCMI Simple Job Mgmt MIB groups
        supported by this management agent implementation (ie, version)
        on this host system, specified in a bit-mask.
        The current set of values (which may be extended in the future)
        is given below:
              1 : simpleJobBaseGroup
              2 : simpleJobMgmtGroup
              4 : simpleJobInterceptGroup
        Usage:  Conforming management agents shall ALWAYS accurately
        report their support for XCMI Simple Job Mgmt MIB groups."
    SYNTAX      INTEGER (0..2147483647)  
XcmSimpleJobMgmtOperation ::= TEXTUAL-CONVENTION
    STATUS      current
    DESCRIPTION
        "The simple job management operation associated with
        this conceptual row in the 'xcmSimpleJobMgmtTable'
        and the 'xcmJobGenBasicTable' (XCMI Job Monitoring MIB), OR
        this conceptual row in the 'xcmSimpleJobInterceptTable'
        and the 'xcmJobClientId' object (XCMI Job Monitoring MIB).
        Note:   The enum of '0' (zero) in this textual convention is
        illegal in strict SMIv1 (see section 3.2.1.1 of RFC 1155), so
        this TC must be converted to an integer range for pure SMIv1."
    REFERENCE
        "See:   Section 4 'Print Utilities' (pages 71 to 212) of
                POSIX Sys Admin (IEEE 1387.4 / Draft 8, October 1994).
        See:    OBJECT clauses in MODULE-COMPLIANCE macro of
                XCMI Simple Job Mgmt MIB, for compliance info."
    SYNTAX      INTEGER {
        none(0),                        
        other(1),                       
        unknown(2),                     
        jobCreate(1401),                
        jobDelete(1402),                
        jobList(1403),                  
        jobSet(1404),                   
        jobPause(1408),                 
        jobResume(1409),                
        jobInterrupt(1411),             
        jobModify(1412),                
        jobPromote(1413),               
        jobRemove(1414),                
        jobResubmit(1415),              
        jobManage(2401),                
        docDelete(1502),                
        docList(1503),                  
        docSet(1504),                   
        docModify(1512),                
        docRemove(1514),                
        docManage(2501)                 
    }
XcmSimpleJobMgmtData ::= TEXTUAL-CONVENTION
    STATUS      current
    DESCRIPTION
        "The simple job management data associated with
        this conceptual row in the 'xcmSimpleJobMgmtTable'
        and the 'xcmJobGenBasicTable' (XCMI Job Monitoring MIB), OR
        this conceptual row in the 'xcmSimpleJobInterceptTable'
        and the 'xcmJobClientId' object (XCMI Job Monitoring MIB)."
    REFERENCE
        "See:   Security Config, Account, and User groups in
                XCMI Security MIB.
        See:    Section 6.6 'Security in DPA' (pages 38 to 39) of
                DPA (ISO 10175-1 / Final Text, March 1996).
        See:    Section 4 'Print Utilities' (pages 71 to 212) of
                POSIX Sys Admin (IEEE 1387.4 / Draft 8, October 1994).
        See:    OBJECT clauses in MODULE-COMPLIANCE macro of
                XCMI Simple Job Mgmt MIB, for compliance info."
    SYNTAX      OCTET STRING (SIZE (0..255))
--
--
--
xCmSimpleJobDummy   OBJECT IDENTIFIER ::= { xcmSimpleJobMgmtTC 999 }
xCmSimpleJobMgmtGroupSupport OBJECT-TYPE
    SYNTAX      XcmSimpleJobMgmtGroupSupport
    MAX-ACCESS  not-accessible
    STATUS      current
    DESCRIPTION "Dummy - DO NOT USE"
    ::= { xCmSimpleJobDummy 1 }
xCmSimpleJobMgmtOperation OBJECT-TYPE
    SYNTAX      XcmSimpleJobMgmtOperation
    MAX-ACCESS  not-accessible
    STATUS      current
    DESCRIPTION "Dummy - DO NOT USE"
    ::= { xCmSimpleJobDummy 2 }
xCmSimpleJobMgmtData OBJECT-TYPE
    SYNTAX      XcmSimpleJobMgmtData
    MAX-ACCESS  not-accessible
    STATUS      current
    DESCRIPTION "Dummy - DO NOT USE"
    ::= { xCmSimpleJobDummy 3 }
xcmSimpleJobMgmtMIB OBJECT-IDENTITY -- MODULE-IDENTITY
    STATUS   current
    DESCRIPTION
        "Version:   5.10.pub
        The MIB module for performing lightweight management of jobs
        in network accessible host systems.
        See:    Document Printing Application - Part 1: Abstract Service
                (ISO 10175-1 / Final Text, March 1996).
        See:    POSIX System Administration - Part 4: Print Interfaces
                (IEEE 1387.4 / Draft 8, October 1994).
        See:    OSI Reference Model - Part 1:  Basic Reference Model
                (CCITT X.200:1992 | ISO 7498-1:1992).
        Copyright (C) 1997-2002 Xerox Corporation. All Rights Reserved."
    ::= { xeroxCommonMIB 76 }
--
xcmSimpleJobBase        OBJECT IDENTIFIER ::= { xcmSimpleJobMgmtMIB 1 }
xcmSimpleJobBaseTable OBJECT-TYPE
    SYNTAX      SEQUENCE OF XcmSimpleJobBaseEntry
    MAX-ACCESS  not-accessible
    STATUS      current
    DESCRIPTION
        "A table of general counters and capabilities for ease of use
        of the XCMI Simple Job Mgmt MIB on this host system.
        Usage:  The ONLY valid row in the 'xcmSimpleJobBaseTable'
        shall ALWAYS have an 'xcmSimpleJobBaseIndex' of one ('1')."
    ::= { xcmSimpleJobBase 2 }
xcmSimpleJobBaseEntry OBJECT-TYPE
    SYNTAX      XcmSimpleJobBaseEntry
    MAX-ACCESS  not-accessible
    STATUS      current
    DESCRIPTION
        "An entry of general counters and capabilities for ease of use
        of the XCMI Simple Job Mgmt MIB on this host system.
        Usage:  The ONLY valid row in the 'xcmSimpleJobBaseTable'
        shall ALWAYS have an 'xcmSimpleJobBaseIndex' of one ('1')."
    INDEX       { xcmSimpleJobBaseIndex }
    ::= { xcmSimpleJobBaseTable 1 }
XcmSimpleJobBaseEntry ::= SEQUENCE {
        xcmSimpleJobBaseIndex           Ordinal32,
        xcmSimpleJobBaseRowStatus       RowStatus,
        xcmSimpleJobBaseGroupSupport    XcmSimpleJobMgmtGroupSupport,
        xcmSimpleJobBaseCreateSupport   XcmSimpleJobMgmtGroupSupport,
        xcmSimpleJobBaseUpdateSupport   XcmSimpleJobMgmtGroupSupport
    }
xcmSimpleJobBaseIndex OBJECT-TYPE
    SYNTAX      Ordinal32
    MAX-ACCESS  not-accessible
    STATUS      current
    DESCRIPTION
        "A unique value used by this host system to identify this
        conceptual row in the 'xcmSimpleJobBaseTable'.
        Usage:  The ONLY valid row in the 'xcmSimpleJobBaseTable'
        shall ALWAYS have an 'xcmSimpleJobBaseIndex' of one ('1')."
    ::= { xcmSimpleJobBaseEntry 1 }
xcmSimpleJobBaseRowStatus OBJECT-TYPE
    SYNTAX      RowStatus
    MAX-ACCESS  read-only
    STATUS      current
    DESCRIPTION
        "This object is used to display status of the ONLY valid
        conceptual row in the 'xcmSimpleJobBaseTable'.
        Usage:  'xcmSimpleJobBaseRowStatus' is 'read-only' because
        the ONLY valid conceptual row shall NOT be deleted."
    ::= { xcmSimpleJobBaseEntry 2 }
xcmSimpleJobBaseGroupSupport OBJECT-TYPE
    SYNTAX      XcmSimpleJobMgmtGroupSupport
    MAX-ACCESS  read-only
    STATUS      current
    DESCRIPTION
        "The terse conformance statement of ALL mandatory, conditionally
        mandatory, and optional XCMI Simple Job Mgmt MIB groups
        supported by this management agent implementation (ie, version)
        on this host system, specified in a bit-mask.
        Usage:  Conforming management agents shall ALWAYS accurately
        report their support for XCMI Simple Job Mgmt MIB groups."
    DEFVAL      { 3 }                   
    ::= { xcmSimpleJobBaseEntry 3 }
xcmSimpleJobBaseCreateSupport OBJECT-TYPE
    SYNTAX      XcmSimpleJobMgmtGroupSupport
    MAX-ACCESS  read-only
    STATUS      current
    DESCRIPTION
        "The terse conformance statement of ALL mandatory, conditionally
        mandatory, and optional XCMI Simple Job Mgmt MIB groups
        supported for dynamic row creation (via '...RowStatus')
        by this management agent implementation (ie, version)
        on this host system, specified in a bit-mask.
        Usage:  Conforming management agents shall ALWAYS accurately
        report their support for XCMI Simple Job Mgmt MIB groups."
    DEFVAL      { 0 }                   
    ::= { xcmSimpleJobBaseEntry 4 }
xcmSimpleJobBaseUpdateSupport OBJECT-TYPE
    SYNTAX      XcmSimpleJobMgmtGroupSupport
    MAX-ACCESS  read-only
    STATUS      current
    DESCRIPTION
        "The terse conformance statement of ALL mandatory, conditionally
        mandatory, and optional XCMI Simple Job Mgmt MIB groups
        supported for existing row update (via SNMP Set-Request PDUs)
        by this management agent implementation (ie, version)
        on this host system, specified in a bit-mask.
        Usage:  Conforming management agents shall ALWAYS accurately
        report their support for XCMI Simple Job Mgmt MIB groups."
    DEFVAL      { 2 }                   
    ::= { xcmSimpleJobBaseEntry 5 }
--
--
--
--
--
xcmSimpleJobMgmt        OBJECT IDENTIFIER ::= { xcmSimpleJobMgmtMIB 3 }
xcmSimpleJobMgmtTable OBJECT-TYPE
    SYNTAX      SEQUENCE OF XcmSimpleJobMgmtEntry
    MAX-ACCESS  not-accessible
    STATUS      current
    DESCRIPTION
        "A table which augments the 'xcmJobGenBasicTable' in the
        XCMI Job Monitoring MIB, to support simple job management
        of jobs on this host system."
    ::= { xcmSimpleJobMgmt 2 }
xcmSimpleJobMgmtEntry OBJECT-TYPE
    SYNTAX      XcmSimpleJobMgmtEntry
    MAX-ACCESS  not-accessible
    STATUS      current
    DESCRIPTION
        "An entry which augments an 'xcmJobGenBasicEntry' in the
        XCMI Job Monitoring MIB, to support simple job management
        of a job on this host system."
    AUGMENTS { xcmJobGenBasicEntry }
    ::= { xcmSimpleJobMgmtTable 1 }
XcmSimpleJobMgmtEntry ::= SEQUENCE {
        xcmSimpleJobMgmtOperation       XcmSimpleJobMgmtOperation,
        xcmSimpleJobMgmtData            XcmSimpleJobMgmtData,
        xcmSimpleJobMgmtStatus          XcmGenSNMPv2ErrorStatus,
        xcmSimpleJobMgmtInProgress      TruthValue
    }
--
--
xcmSimpleJobMgmtOperation OBJECT-TYPE
    SYNTAX      XcmSimpleJobMgmtOperation
    MAX-ACCESS  read-write
    STATUS      current
    DESCRIPTION
        "The simple job management operation specified for
        this conceptual row in the 'xcmSimpleJobMgmtTable'
        and the 'xcmJobGenBasicTable' (XCMI Job Monitoring MIB).
        Usage:  Conforming management agents SHALL 'reject' any
        SNMP Set-Operation to 'xcmSimpleJobMgmt[Operation|Data]'
        while another management operation is already in progress
        (ie, while 'xcmSimpleJobMgmtInProgress' is 'true'),
        with 'badValue' (SNMPv1) or 'inconsistentValue' (SNMPv2/v3).
        Usage:  Conforming management stations SHALL set
        'xcmSimpleJobMgmtOperation' (mgmt operation) and
        'xcmSimpleJobMgmtData' (mgmt arguments)
        SIMULTANEOUSLY (in the same SNMP Set-Operation PDU).
        Usage:  Performing 'delete' (system operator) shall ALWAYS force
        'xcmJobCurrentState' to 'completed(17)' immediately,
        and MAY affect 'xcmJobAccountingBasicRowStatus'.
        Usage:  Performing 'remove' (user cancel) shall ALWAYS force
        'xcmJobCurrentState' to 'completed(17)' in a timely fashion,
        but shall NOT affect 'xcmJobAccountingBasicRowStatus'."
    REFERENCE
        "See:   Section 4 'Print Utilities' (pages 71 to 212) of
                POSIX Sys Admin (IEEE 1387.4 / Draft 8, October 1994).
        See:    OBJECT clauses in MODULE-COMPLIANCE macro of
                XCMI Simple Job Mgmt MIB, for compliance info."
    ::= { xcmSimpleJobMgmtEntry 1 }
xcmSimpleJobMgmtData OBJECT-TYPE
    SYNTAX      XcmSimpleJobMgmtData (SIZE (0..255))
    MAX-ACCESS  read-write
    STATUS      current
    DESCRIPTION
        "The simple job management data specified for
        this conceptual row in the 'xcmSimpleJobMgmtTable'
        and the 'xcmJobGenBasicTable' (XCMI Job Monitoring MIB).
        Usage:  Conforming management agents SHALL 'reject' any
        SNMP Set-Operation to 'xcmSimpleJobMgmt[Operation|Data]'
        while another management operation is already in progress
        (ie, while 'xcmSimpleJobMgmtInProgress' is 'true'),
        with 'badValue' (SNMPv1) or 'inconsistentValue' (SNMPv2/v3).
        Usage:  Conforming management stations SHALL set
        'xcmSimpleJobMgmtOperation' (mgmt operation) and
        'xcmSimpleJobMgmtData' (mgmt arguments)
        SIMULTANEOUSLY (in the same SNMP Set-Operation PDU)."
    REFERENCE
        "See:   Security Config, Account, and User groups in
                XCMI Security MIB.
        See:    Section 6.6 'Security in DPA' (pages 38 to 39) of
                DPA (ISO 10175-1 / Final Text, March 1996).
        See:    Section 4 'Print Utilities' (pages 71 to 212) of
                POSIX Sys Admin (IEEE 1387.4 / Draft 8, October 1994).
        See:    OBJECT clauses in MODULE-COMPLIANCE macro of
                XCMI Simple Job Mgmt MIB, for compliance info."
    DEFVAL      { ''H }                 
    ::= { xcmSimpleJobMgmtEntry 2 }
xcmSimpleJobMgmtStatus OBJECT-TYPE
    SYNTAX      XcmGenSNMPv2ErrorStatus
    MAX-ACCESS  read-only
    STATUS      current
    DESCRIPTION
        "The simple job management error status associated with
        this conceptual row in 'xcmSimpleJobMgmtTable'.
        Usage:  Conforming management agents shall ALWAYS set this
        object to the value returned in an SNMP Set-Response PDU when
        a simple job management operation is 'accepted', ie, when
        'xcmSimpleJobMgmtInProgress' goes from 'false' to 'true'.
        Usage:  Conforming management agents shall ALWAYS set this
        object to the value of the completion status of the (possibly
        deferred) simple job management operation, when
        'xcmSimpleJobMgmtInProgress' goes from 'true' to 'false'."
    REFERENCE
        "See:   'xcmSimpleJobMgmt[Operation|Data|InProgress]'"
    ::= { xcmSimpleJobMgmtEntry 3 }
xcmSimpleJobMgmtInProgress OBJECT-TYPE
    SYNTAX      TruthValue
    MAX-ACCESS  read-only
    STATUS      current
    DESCRIPTION
        "The simple job management in progress status associated with
        this conceptual row in 'xcmSimpleJobMgmtTable'.
        Usage:  Conforming management agents SHALL 'reject' any
        SNMP Set-Operation to 'xcmSimpleJobMgmt[Operation|Data]'
        while another management operation is already in progress
        (ie, while 'xcmSimpleJobMgmtInProgress' is 'true'),
        with 'badValue' (SNMPv1) or 'inconsistentValue' (SNMPv2/v3)."
    REFERENCE
        "See:   'xcmSimpleJobMgmt[Operation|Data|Status]'"
    DEFVAL      { false }               
    ::= { xcmSimpleJobMgmtEntry 4 }
xcmSimpleJobMgmtV1EventOID OBJECT-IDENTITY
    STATUS      current
    DESCRIPTION
        "The value of the enterprise-specific OID in an SNMPv1 trap sent
        whenever an 'xcmSimpleJobMgmtOperation' completes.
        See SNMPv2 trap definition 'xcmSimpleJobMgmtV2Event'
        below for 'special semantics'."
    ::= { xcmSimpleJobMgmt 1 }
xcmSimpleJobMgmtV2EventPrefix
    OBJECT IDENTIFIER ::= { xcmSimpleJobMgmtV1EventOID 0 }
xcmSimpleJobMgmtV2Event NOTIFICATION-TYPE
    OBJECTS {
        hrDeviceIndex,
        xcmJobIdentifierOnSystem,
        xcmSimpleJobMgmtOperation,
        xcmSimpleJobMgmtStatus
    }
    STATUS      current
    DESCRIPTION
        "This trap is sent whenever an 'XcmSimpleJobMgmtOperation'
        completes, ie, when 'xcmSimpleJobMgmtStatus' becomes a
        completed operation status and 'XcmSimpleJobMgmtInProgress'
        goes from 'true' to 'false'.
        Note:  The 'hrDeviceIndex' is included for convenience, even
        though the IETF Printer MIB doesn't include 'hrDeviceIndex'
        in its traps.  Then the management station doesn't have to parse
        the received varBind OIDs on a trap in order to discover which 
        device trapped.
        Note:   The variable-bindings of this trap have been chosen to
        specify a complete job management operation result while keeping
        trap messages reasonably concise (generally a few hundred octets
        at most).
        This notification has the following special semantics:
            o   If the job's 'xcmJobClientId' field is non-empty and
                it is a valid 'XcmGlobalUniqueID' representation, its
                value shall ALWAYS be appended to this trap object ID,
                as a BER binary OID suffix.
                Note:   The BER binary OID suffix shall NOT include the
                BER tag of 6 indicating an OID and shall NOT include the
                BER length field in octets of the OID suffix.
        This trap OID qualifier allows job-submission and job-monitoring
        applications to limit the alerts they receive to ones generated 
        by jobs which they have submitted.
        Note:   The sum of the trap varBind values must be less than
        can fit into a PDU on any transport, roughly 540 octets on some
        transports.  Thus implementors are warned to minimize the length
        of the 'xcmJobClientId' and 'xcmJobIdentifierOnSystem' objects."
    ::= { xcmSimpleJobMgmtV2EventPrefix 1 }
--
--          "This trap is sent when an 'XcmSimpleJobMgmtOperation'
--          above for 'special semantics'."
--
--
--
xcmSimpleJobIntercept   OBJECT IDENTIFIER ::= { xcmSimpleJobMgmtMIB 4 }
xcmSimpleJobInterceptTable OBJECT-TYPE
    SYNTAX      SEQUENCE OF XcmSimpleJobInterceptEntry
    MAX-ACCESS  not-accessible
    STATUS      current
    DESCRIPTION
        "A table which is indexed by the future 'xcmJobClientId' in the
        XCMI Job Monitoring MIB, to support simple job intercept
        requests for upstream jobs (off this host system)."
    ::= { xcmSimpleJobIntercept 2 }
xcmSimpleJobInterceptEntry OBJECT-TYPE
    SYNTAX      XcmSimpleJobInterceptEntry
    MAX-ACCESS  not-accessible
    STATUS      current
    DESCRIPTION
        "An entry which is indexed by the future 'xcmJobClientId' in the
        XCMI Job Monitoring MIB, to support a simple job intercept
        request for an upstream job (off this host system)."
    INDEX       { xcmSimpleJobInterceptClientId }
    ::= { xcmSimpleJobInterceptTable 1 }
XcmSimpleJobInterceptEntry ::= SEQUENCE {
        xcmSimpleJobInterceptClientId   XcmFixedLocaleDisplayString,
        xcmSimpleJobInterceptRowStatus  RowStatus,
        xcmSimpleJobInterceptOperation  XcmSimpleJobMgmtOperation,
        xcmSimpleJobInterceptData       XcmSimpleJobMgmtData,
        xcmSimpleJobInterceptStatus     XcmGenSNMPv2ErrorStatus,
        xcmSimpleJobInterceptInProgress TruthValue
    }
--
--
xcmSimpleJobInterceptClientId OBJECT-TYPE
    SYNTAX      XcmFixedLocaleDisplayString (SIZE (0..128)) 
    MAX-ACCESS  read-only
    STATUS      current
    DESCRIPTION
        "A unique value used by this host system to identify this
        conceptual row in the 'xcmSimpleJobInterceptTable'.
        Usage:  The future value of 'xcmJobClientId' from the XCMI Job
        Monitoring MIB which uniquely identifies this client's job.
        Usage:  XCMI conforming management agents MAY choose to REJECT
        any attempt at row creation in the 'xcmSimpleJobInterceptTable'
        which specifies a value for 'xcmSimpleJobInterceptClientId' that
        does NOT conform to the 'XcmGlobalUniqueID' format (therefore
        cannot be appended onto the trap OID for any job-related traps).
        Usage:  XCMI conforming management agents MAY choose to ACCEPT
        any attempt at row creation in the 'xcmSimpleJobInterceptTable'
        which specifies a value for 'xcmSimpleJobInterceptClientId' that
        is nonetheless unique in the scope of the managed system (but
        not append it onto the trap OID for any job-related traps).
        Usage:  XCMI conforming management stations (ie, clients) shall
        ALWAYS submit an 'xcmJobClientId' in 'XcmGlobalUniqueID' format.
        XCMI conforming management agents (ie, servers and devices)
        shall ALWAYS append such an 'xcmJobClientId' onto the trap OID
        for any job-related traps.
        Usage:  Non-XCMI conforming management stations (ie, clients)
        MAY submit a non-unique 'xcmJobClientId', although they may be
        otherwise strictly conformant DPA (ISO 10175) clients."
    ::= { xcmSimpleJobInterceptEntry 1 }
xcmSimpleJobInterceptRowStatus OBJECT-TYPE
    SYNTAX      RowStatus
    MAX-ACCESS  read-create
    STATUS      current
    DESCRIPTION
        "This object is used to create and destroy individual conceptual
        rows in 'xcmSimpleJobInterceptTable'."
    ::= { xcmSimpleJobInterceptEntry 2 }
xcmSimpleJobInterceptOperation OBJECT-TYPE
    SYNTAX      XcmSimpleJobMgmtOperation
    MAX-ACCESS  read-create
    STATUS      current
    DESCRIPTION
        "The simple job intercept operation specified for
        this conceptual row in the 'xcmSimpleJobInterceptTable'
        and the 'xcmJobClientId' object (XCMI Job Monitoring MIB).
        Usage:  Conforming management agents SHALL 'reject' any
        SNMP Set-Operation to 'xcmSimpleJobIntercept[Operation|Data]'
        while another management operation is already in progress
        (ie, while 'xcmSimpleJobInterceptInProgress' is 'true'),
        with 'badValue' (SNMPv1) or 'inconsistentValue' (SNMPv2/v3).
        Usage:  Conforming management stations SHALL set
        'xcmSimpleJobInterceptOperation' (mgmt operation) and
        'xcmSimpleJobInterceptData' (mgmt arguments)
        SIMULTANEOUSLY (in the same SNMP Set-Operation PDU)."
    REFERENCE
        "See:   Section 4 'Print Utilities' (pages 71 to 212) of
                POSIX Sys Admin (IEEE 1387.4 / Draft 8, October 1994).
        See:    OBJECT clauses in MODULE-COMPLIANCE macro of
                XCMI Simple Job Mgmt MIB, for compliance info."
    ::= { xcmSimpleJobInterceptEntry 3 }
xcmSimpleJobInterceptData OBJECT-TYPE
    SYNTAX      XcmSimpleJobMgmtData (SIZE (0..255))
    MAX-ACCESS  read-create
    STATUS      current
    DESCRIPTION
        "The simple job intercept data specified for
        this conceptual row in the 'xcmSimpleJobInterceptTable'
        and the 'xcmJobClientId' object (XCMI Job Monitoring MIB).
        Usage:  Conforming management agents SHALL 'reject' any
        SNMP Set-Operation to 'xcmSimpleJobIntercept[Operation|Data]'
        while another management operation is already in progress
        (ie, while 'xcmSimpleJobInterceptInProgress' is 'true'),
        with 'badValue' (SNMPv1) or 'inconsistentValue' (SNMPv2/v3).
        Usage:  Conforming management stations SHALL set
        'xcmSimpleJobInterceptOperation' (mgmt operation) and
        'xcmSimpleJobInterceptData' (mgmt arguments)
        SIMULTANEOUSLY (in the same SNMP Set-Operation PDU)."
    REFERENCE
        "See:   Security Config, Account, and User groups in
                XCMI Security MIB.
        See:    Section 6.6 'Security in DPA' (pages 38 to 39) of
                DPA (ISO 10175-1 / Final Text, March 1996).
        See:    Section 4 'Print Utilities' (pages 71 to 212) of
                POSIX Sys Admin (IEEE 1387.4 / Draft 8, October 1994).
        See:    OBJECT clauses in MODULE-COMPLIANCE macro of
                XCMI Simple Job Mgmt MIB, for compliance info."
    DEFVAL      { ''H }                 
    ::= { xcmSimpleJobInterceptEntry 4 }
xcmSimpleJobInterceptStatus OBJECT-TYPE
    SYNTAX      XcmGenSNMPv2ErrorStatus
    MAX-ACCESS  read-only
    STATUS      current
    DESCRIPTION
        "The simple job intercept error status associated with
        this conceptual row in 'xcmSimpleJobInterceptTable'.
        Usage:  Conforming management agents shall ALWAYS set this
        object to the value returned in an SNMP Set-Response PDU when
        a simple job intercept operation is 'accepted', ie, when
        'xcmSimpleJobInterceptInProgress' goes from 'false' to 'true'.
        Usage:  Conforming management agents shall ALWAYS set this
        object to the value of the completion status of the (possibly
        deferred) simple job intercept operation, when
        'xcmSimpleJobInterceptInProgress' goes from 'true' to 'false'."
    REFERENCE
        "See:   'xcmSimpleJobIntercept[Operation|Data|InProgress]'"
    ::= { xcmSimpleJobInterceptEntry 5 }
xcmSimpleJobInterceptInProgress OBJECT-TYPE
    SYNTAX      TruthValue
    MAX-ACCESS  read-only
    STATUS      current
    DESCRIPTION
        "The simple job intercept in progress status associated with
        this conceptual row in 'xcmSimpleJobInterceptTable'.
        Usage:  Conforming management agents SHALL 'reject' any
        SNMP Set-Operation to 'xcmSimpleJobIntercept[Operation|Data]'
        while another management operation is already in progress
        (ie, while 'xcmSimpleJobInterceptInProgress' is 'true'),
        with 'badValue' (SNMPv1) or 'inconsistentValue' (SNMPv2/v3)."
    REFERENCE
        "See:   'xcmSimpleJobIntercept[Operation|Data|Status]'"
    DEFVAL      { false }               
    ::= { xcmSimpleJobInterceptEntry 6 }
xcmSimpleJobInterceptV1EventOID OBJECT-IDENTITY
    STATUS      current
    DESCRIPTION
        "The value of the enterprise-specific OID in an SNMPv1 trap sent
        whenever an 'xcmSimpleJobInterceptOperation' completes.
        See SNMPv2 trap definition 'xcmSimpleJobInterceptV2Event'
        below for 'special semantics'."
    ::= { xcmSimpleJobIntercept 1 }
xcmSimpleJobInterceptV2EventPrefix
    OBJECT IDENTIFIER ::= { xcmSimpleJobInterceptV1EventOID 0 }
xcmSimpleJobInterceptV2Event NOTIFICATION-TYPE
    OBJECTS {
        xcmSimpleJobInterceptClientId,
        xcmSimpleJobInterceptOperation,
        xcmSimpleJobInterceptStatus
    }
    STATUS      current
    DESCRIPTION
        "This trap is sent whenever an 'XcmSimpleJobInterceptOperation'
        completes.
        Note:   The variable-bindings of this trap have been chosen to
        specify a complete job intercept operation result while keeping
        trap messages reasonably concise (generally a few hundred octets
        at most).
        This notification has the following special semantics:
            o   If 'xcmSimpleJobInterceptClientId' is non-empty and
                it is a valid 'XcmGlobalUniqueID' representation, its
                value shall ALWAYS be appended to this trap object ID,
                as a BER binary OID suffix.
                Note:   The BER binary OID suffix shall NOT include the
                BER tag of 6 indicating an OID and shall NOT include the
                BER length field in octets of the OID suffix.
        This trap OID qualifier allows job-submission and job-monitoring
        applications to limit the alerts they receive to ones generated 
        by jobs which they have submitted.
        Note:   The sum of the trap varBind values must be less than
        can fit into a PDU on any transport, roughly 540 octets on some
        transports.  Thus implementors are warned to minimize the length
        of the 'xcmJobClientId' and 'xcmJobIdentifierOnSystem' objects."
    ::= { xcmSimpleJobInterceptV2EventPrefix 1 }
--
--          "This trap is sent when an 'XcmSimpleJobInterceptOperation'
--          above for 'special semantics'."
--
--
xcmSimpleJobMgmtMIBConformance
    OBJECT IDENTIFIER ::= { xcmSimpleJobMgmtMIB 2 }
xcmSimpleJobMgmtMIBGroups
    OBJECT IDENTIFIER ::= { xcmSimpleJobMgmtMIBConformance 2 }
--
--
xcmSimpleJobMgmtMIBCompliance MODULE-COMPLIANCE
    STATUS      current
    DESCRIPTION
        "The compliance statements for SNMP intercept agents that
        implement the Simple Job Mgmt MIB."
    MODULE 
    MANDATORY-GROUPS {
        xcmSimpleJobBaseGroup,
        xcmSimpleJobMgmtGroup
    }
    GROUP       xcmSimpleJobInterceptGroup
    DESCRIPTION
        "Implementation of this group is conditionally mandatory, ie,
        mandatory for systems which support simple job intercept
        via the defined extensions to the XCMI Job Monitoring MIB
        and optional for all other systems."
--      "Implementation of this group is conditionally mandatory, ie,
--      and optional for all other systems."
--      "Implementation of this group is conditionally mandatory, ie,
--      and optional for all other systems."
    OBJECT      xcmSimpleJobMgmtOperation
    SYNTAX      INTEGER {
        none(0),                        
        other(1),                       
        unknown(2),                     
        jobPause(1408),                 
        jobResume(1409),                
        jobRemove(1414)                 
    }
    DESCRIPTION
        "It is conformant to implement this object as follows:
        only the above subset of operations need be supported."
    OBJECT      xcmSimpleJobMgmtData
    SYNTAX      XcmSimpleJobMgmtData (SIZE (0..1))
    DESCRIPTION
        "It is conformant to implement this object as follows:
        only 1 octet maximum string length need be supported."
    OBJECT      xcmSimpleJobInterceptOperation
    SYNTAX      INTEGER {
        none(0),                        
        other(1),                       
        unknown(2),                     
        jobPause(1408),                 
        jobResume(1409),                
        jobRemove(1414)                 
    }
    DESCRIPTION
        "It is conformant to implement this object as follows:
        only the above subset of operations need be supported."
    OBJECT      xcmSimpleJobInterceptData
    SYNTAX      XcmSimpleJobMgmtData (SIZE (0..1))
    DESCRIPTION
        "It is conformant to implement this object as follows:
        only 1 octet maximum string length need be supported."
    ::= { xcmSimpleJobMgmtMIBConformance 3 }
--
--
xcmSimpleJobBaseGroup OBJECT-GROUP
    OBJECTS {
        xcmSimpleJobBaseRowStatus,
        xcmSimpleJobBaseGroupSupport,
        xcmSimpleJobBaseCreateSupport,
        xcmSimpleJobBaseUpdateSupport
    }
    STATUS      current
    DESCRIPTION
        "The Simple Job Base Group"
    ::= { xcmSimpleJobMgmtMIBGroups 1 }
xcmSimpleJobMgmtGroup OBJECT-GROUP
    OBJECTS {
        xcmSimpleJobMgmtOperation,
        xcmSimpleJobMgmtData,
        xcmSimpleJobMgmtStatus,
        xcmSimpleJobMgmtInProgress
    }
    STATUS      current
    DESCRIPTION
        "The Simple Job Mgmt Group"
    ::= { xcmSimpleJobMgmtMIBGroups 3 }
xcmSimpleJobInterceptGroup OBJECT-GROUP
    OBJECTS {
        xcmSimpleJobInterceptClientId,
        xcmSimpleJobInterceptRowStatus,
        xcmSimpleJobInterceptOperation,
        xcmSimpleJobInterceptData,
        xcmSimpleJobInterceptStatus,
        xcmSimpleJobInterceptInProgress
    }
    STATUS      current
    DESCRIPTION
        "The Simple Job Intercept Group"
    ::= { xcmSimpleJobMgmtMIBGroups 4 }
xcmJmxMIB OBJECT-IDENTITY -- MODULE-IDENTITY
    STATUS   current
    DESCRIPTION
        "Version:   5.401.pub
        The MIB module for job administration and job notifications for
        systems that implement the PWG Job Monitoring MIB (RFC 2707).
        See: Section 7 'Conformance Requirements and Implementers Guide'
        of the XCMI Job Monitoring TC (40jobtc.txt) for implementation
        and conformance guidance for the PWG Job Monitoring MIB
        (RFC 2707) and for mapping to the XCMI Job Monitoring MIB.
        Copyright (C) 2001-2002 Xerox Corporation. All Rights Reserved."
    ::= { xeroxCommonMIB 83 }
--
--
XcmJmxGroupSupport ::= TEXTUAL-CONVENTION
    STATUS      current
    DESCRIPTION
        "The terse conformance statement of ALL mandatory, conditionally
        mandatory, and optional PWG Job Monitoring MIB (RFC 2707)
        and XCMI Ext to PWG Job Monitoring MIB objects which are
        supported by this management agent implementation (i.e.,
        version) on this host system, specified in a bit-mask.
        The current set of values (which may be extended in the future)
        is given below:
              1 : jmGeneralGroup                
              2 : jmJobIDGroup                  
              4 : jmJobGroup                    
              8 : jmAttributeGroup              
             16 : jmxGeneralGroup               
             32 : jmxJobAdminGroup              
             64 : jmxJobTrapsGroup              
            128 : jmxJobOperationTrapsGroup     
        Usage:  Conforming management agents shall ALWAYS accurately
        report their support for PWG Job Monitoring MIB (RFC 2707)
        and XCMI Ext to PWG Job Monitoring MIB object groups."
    SYNTAX      INTEGER (0..2147483647)  
XcmJmxJobAdminOperation ::= TEXTUAL-CONVENTION
    STATUS      current
    DESCRIPTION
        "The current or most recent administrative operation on this job
        (submitted via SNMP, IPP, or any other job control protocol)."
    REFERENCE
        "See:   Section 3.3 'Job Operations'
                in IPP Model and Semantics [RFC-2911].
        See:    Section 4 'Job Operations'
                in IPP Job and Printer Admin Operations [IPP-ADMIN].
        See:    'xcmHrDevMgmtCommandDataTag' textual convention,
                Section 3.4 'XCMI Standard Tagged Management Data', and
                Section 3.5 'Simple Device Management Requests' in
                XCMI Host Resources Ext TC (for security issues).
        See:    Section 3.5.3 'Secure Simple Device Mgmt Requests' in
                XCMI Security TC (for security issues).
        See:    'xcmJmxJobAdmin[Status|InProgress]'"
    SYNTAX      INTEGER {
        other(1),
        unknown(2),
        cancelJob(3),                   
        holdJob(4),                     
        releaseJob(5),                  
        restartJob(6),                  
        reprocessJob(7),                
        suspendJob(8),                  
        resumeJob(9),                   
        promoteJob(10)                  
    }
XcmJmxJobAccntSupport ::= TEXTUAL-CONVENTION
    STATUS    current
    DESCRIPTION
        "Presence and configuration of a Job Accounting on the device.
         Note: This enumeration may be extended for more granularity in
         the future."
    SYNTAX    INTEGER {
                  other(1),
                  on(3),
                  off(4),
                  notPresent(5)
                  }
--
--
xcmJmxMIBObjects        OBJECT IDENTIFIER ::= { xcmJmxMIB 1 }
--
xcmJmxGeneral           OBJECT IDENTIFIER ::= { xcmJmxMIBObjects 1 }
xcmJmxGeneralTable OBJECT-TYPE
    SYNTAX      SEQUENCE OF XcmJmxGeneralEntry
    MAX-ACCESS  not-accessible
    STATUS      current
    DESCRIPTION
        "A table of general counters and information for ease of use of
        the XCMI Ext to PWG Job Monitoring MIB and the
        PWG Job Monitoring MIB (RFC 2707) on this host system.
        Usage:  The ONLY valid row in the 'xcmJmxGeneralTable'
        shall ALWAYS have an 'xcmJmxGeneralIndex' of one ('1')."
    ::= { xcmJmxGeneral 2 }
xcmJmxGeneralEntry OBJECT-TYPE
    SYNTAX      XcmJmxGeneralEntry
    MAX-ACCESS  not-accessible
    STATUS      current
    DESCRIPTION
        "An entry of general counters and information for ease of use of
        the XCMI Ext to PWG Job Monitoring MIB and the
        PWG Job Monitoring MIB (RFC 2707) on this host system.
        Usage:  The ONLY valid row in the 'xcmJmxGeneralTable'
        shall ALWAYS have an 'xcmJmxGeneralIndex' of one ('1')."
    INDEX       { xcmJmxGeneralIndex }
    ::= { xcmJmxGeneralTable 1 }
XcmJmxGeneralEntry ::= SEQUENCE {
        xcmJmxGeneralIndex              Ordinal32,
        xcmJmxGeneralGroupSupport       XcmJmxGroupSupport,
        xcmJmxGeneralJobCreatedCount    Counter32,
        xcmJmxGeneralJobCompletedCount  Counter32,
        xcmJmxGeneralJobOperationCount  Counter32,
        xcmJmxGeneralJobTrapCount       Counter32,
        xcmJmxGeneralJobAccntSupport    XcmJmxJobAccntSupport
    }
xcmJmxGeneralIndex OBJECT-TYPE
    SYNTAX      Ordinal32
    MAX-ACCESS  not-accessible
    STATUS      current
    DESCRIPTION
        "A unique value used by this host system to identify this
        conceptual row in the 'xcmJmxGeneralTable'.
        Usage:  The ONLY valid row in the 'xcmJmxGeneralTable'
        shall ALWAYS have an 'xcmJmxGeneralIndex' of one ('1')."
    ::= { xcmJmxGeneralEntry 1 }
xcmJmxGeneralGroupSupport OBJECT-TYPE
    SYNTAX      XcmJmxGroupSupport
    MAX-ACCESS  read-only
    STATUS      current
    DESCRIPTION
        "The terse conformance statement of ALL mandatory, conditionally
        mandatory, and optional PWG Job Monitoring MIB (RFC 2707)
        and XCMI Ext to PWG Job Monitoring MIB objects which are
        supported by this management agent implementation (i.e.,
        version) on this host system, specified in a bit-mask.
        Usage:  Conforming management agents shall ALWAYS accurately
        report their support for PWG Job Monitoring MIB (RFC 2707)
        and XCMI Ext to PWG Job Monitoring MIB object groups."
    DEFVAL      { 31 }                  
    ::= { xcmJmxGeneralEntry 2 }
xcmJmxGeneralJobCreatedCount OBJECT-TYPE
    SYNTAX      Counter32
    MAX-ACCESS  read-only
    STATUS      current
    DESCRIPTION
        "Total number of jobs that have been created on this
        managed system.  The managed system MAY preserve this count
        across initializations and resets.
        Usage: If the value of this counter is not preserved across 
        initializations and resets, then it SHALL be set to zero upon
        system initialization or reset.
        Usage: A managed system SHALL return zero if the number of jobs 
created is not known."
    ::= { xcmJmxGeneralEntry 3 }
xcmJmxGeneralJobCompletedCount OBJECT-TYPE
    SYNTAX      Counter32
    MAX-ACCESS  read-only
    STATUS      current
    DESCRIPTION
        "Total number of jobs that have completed on this
        managed system. The managed system MAY preserve this count
        across initializations and resets.
        Usage: If the value of this counter is not preserved across
        initializations and resets, then it SHALL be set to zero upon
        system initialization or reset.
        Usage: A managed system SHALL return zero if the number of jobs
        created is not known."
    ::= { xcmJmxGeneralEntry 4 }
xcmJmxGeneralJobOperationCount OBJECT-TYPE
    SYNTAX      Counter32
    MAX-ACCESS  read-only
    STATUS      current
    DESCRIPTION
        "Total number of job operations that have been executed on this
        managed system. The managed system MAY preserve this count
        across initializations and resets.
        Usage: If the value of this counter is not preserved across
        initializations and resets, then it SHALL be set to zero upon
        system initialization or reset.
        Usage: A managed system SHALL return zero if the number of jobs
        created is not known."
    ::= { xcmJmxGeneralEntry 5 }
xcmJmxGeneralJobTrapCount OBJECT-TYPE
    SYNTAX      Counter32
    MAX-ACCESS  read-only
    STATUS      current
    DESCRIPTION
        "Total number of job traps that have been sent from this
        managed system. The managed system MAY preserve this count
        across initializations and resets.
        Usage: If the value of this counter is not preserved across
        initializations and resets, then it SHALL be set to zero upon
        system initialization or reset.
        Usage: A managed system SHALL return zero if the number of jobs
        created is not known."
    ::= { xcmJmxGeneralEntry 6 }
xcmJmxGeneralJobAccntSupport OBJECT-TYPE
    SYNTAX      XcmJmxJobAccntSupport
    MAX-ACCESS  read-write
    STATUS      current
    DESCRIPTION
        "This is a way to turn the Job Accounting in the
        device on and off when the printer supports the
        PWG job accounting mib. If the job accounting within the
        device is off then the group support will report no
        no group supported. If job accounting is on then the 
        appropriate groups will be reported as supported."
    DEFVAL      { on }                  
    ::= { xcmJmxGeneralEntry 7 }
--
xcmJmxJobAdmin          OBJECT IDENTIFIER ::= { xcmJmxMIBObjects 2 }
xcmJmxJobAdminTable OBJECT-TYPE
    SYNTAX      SEQUENCE OF XcmJmxJobAdminEntry
    MAX-ACCESS  not-accessible
    STATUS      current
    DESCRIPTION
        "A table containing job operation requests for control
        of jobs on this host system."
    REFERENCE
        "See:   'jmJobTable' in Job Monitoring MIB [RFC-2707]."
    ::= { xcmJmxJobAdmin 1 }
xcmJmxJobAdminEntry OBJECT-TYPE
    SYNTAX      XcmJmxJobAdminEntry
    MAX-ACCESS  not-accessible
    STATUS      current
    DESCRIPTION
        "An entry containing a job operation request for control
        of a job on this host system."
    AUGMENTS    { jmJobEntry }
    ::= { xcmJmxJobAdminTable 1 }
XcmJmxJobAdminEntry ::= SEQUENCE {
        xcmJmxJobAdminOperation            XcmJmxJobAdminOperation,
        xcmJmxJobAdminStatus               XcmGenSNMPv2ErrorStatus,
        xcmJmxJobAdminInProgress           TruthValue
    }
xcmJmxJobAdminOperation OBJECT-TYPE
    SYNTAX      XcmJmxJobAdminOperation
    MAX-ACCESS  read-write
    STATUS      current
    DESCRIPTION
        "The current or most recent administrative operation on this job
        (submitted via SNMP, IPP, or any other job control protocol).
        Usage:  Conforming management agents shall ALWAYS 'reject' any
        SNMP Set-Request to 'xcmJmxJobAdminOperation'
        while another job operation request is already in progress
        (i.e., while 'xcmJmxJobAdminInProgress' is 'true'),
        with 'badValue' (SNMPv1) or 'inconsistentValue' (SNMPv2/v3)."
    REFERENCE
        "See:   Section 3.3 'Job Operations'
                in IPP Model and Semantics [RFC-2911].
        See:    Section 4 'Job Operations'
                in IPP Job and Printer Admin Operations [IPP-ADMIN].
        See:    'xcmHrDevMgmtCommandDataTag' textual convention,
                Section 3.4 'XCMI Standard Tagged Management Data', and
                Section 3.5 'Simple Device Management Requests' in
                XCMI Host Resources Ext TC (for security issues).
        See:    Section 3.5.3 'Secure Simple Device Mgmt Requests' in
                XCMI Security TC (for security issues).
        See:    'xcmJmxJobAdmin[Status|InProgress]'"
    DEFVAL      { unknown }             
    ::= { xcmJmxJobAdminEntry 1 }
xcmJmxJobAdminStatus OBJECT-TYPE
    SYNTAX      XcmGenSNMPv2ErrorStatus
    MAX-ACCESS  read-only
    STATUS      current
    DESCRIPTION
        "The job operation error status associated with
        this conceptual row in 'xcmJmxJobAdminTable'.
        Usage:  Conforming management agents shall ALWAYS set this
        object to the value returned in an SNMP Set-Response PDU when
        a job operation request is 'accepted', ie, when
        'xcmJmxJobAdminInProgress' goes from 'false' to 'true'.
        Usage:  Conforming management agents shall ALWAYS set this
        object to the value of the completion status of the (possibly
        deferred) job operation request, when
        'xcmJmxJobAdminInProgress' goes from 'true' to 'false'."
    REFERENCE
        "See:   'xcmJmxJobAdmin[Operation|InProgress]'"
    ::= { xcmJmxJobAdminEntry 2 }
xcmJmxJobAdminInProgress OBJECT-TYPE
    SYNTAX      TruthValue
    MAX-ACCESS  read-only
    STATUS      current
    DESCRIPTION
        "The job operation in progress status associated with
        this conceptual row in 'xcmJmxJobAdminTable'.
        'true' if job operation is in progress; otherwise, 'false'.
        Usage:  Conforming management agents shall ALWAYS 'reject' any
        SNMP Set-Request to 'xcmJmxJobAdminOperation'
        while another job operation request is already in progress
        (i.e., while 'xcmJmxJobAdminInProgress' is 'true'),
        with 'badValue' (SNMPv1) or 'inconsistentValue' (SNMPv2/v3)."
    REFERENCE
        "See:   'xcmJmxJobAdmin[Operation|Status]'"
    DEFVAL      { false }               
    ::= { xcmJmxJobAdminEntry 3 }
--
--
xcmJmxMIBNotifications  OBJECT IDENTIFIER ::= { xcmJmxMIB 2 }
--
xcmJmxJobOperationV1Enterprise OBJECT-IDENTITY
    STATUS      current
    DESCRIPTION
        "The value of the enterprise-specific OID in an SNMPv1 trap
        for a Job operation complete event sent by this managed system."
    ::= { xcmJmxMIBNotifications 1 }
xcmJmxJobOperationV2TrapPrefix
    OBJECT IDENTIFIER ::= { xcmJmxJobOperationV1Enterprise 0 }
xcmJmxJobOperationV2Trap NOTIFICATION-TYPE
    OBJECTS {
        jmJobState,
        jmJobStateReasons1,
        xcmJmxJobAdminOperation,
        xcmJmxJobAdminStatus
    }
    STATUS      current
    DESCRIPTION
        "This SMIv2 trap corresponds to a Job operation complete event.
        The values of 'jmGeneralJobSetIndex' and 'jmJobIndex' for
        use with 'jmJobTable' for this Job are conveyed in the
        instance qualifier (OID suffix) of 'jmJobOperation'.
        Additional variable-bindings MAY be appended to this trap:
        - Systems with the Host Resources MIB (RFC 2790) MAY add
          'hrSystemDate'
          (compare to IPP 'printer-current-time')
        - Systems MAY add other variable-bindings from any MIB"
    REFERENCE
        "See:   'xcmJmxJobAdminOperation' in this MIB."
    ::= { xcmJmxJobOperationV2TrapPrefix 1 }
xcmJmxJobStateV1Enterprise OBJECT-IDENTITY
    STATUS      current
    DESCRIPTION
        "The value of the enterprise-specific OID in an SNMPv1 trap
        for a Job state changed event sent by this managed system."
    ::= { xcmJmxMIBNotifications 2 }
xcmJmxJobStateV2TrapPrefix
    OBJECT IDENTIFIER ::= { xcmJmxJobStateV1Enterprise 0 }
xcmJmxJobStateV2Trap NOTIFICATION-TYPE
    OBJECTS {
        jmJobState,
        jmJobStateReasons1
    }
    STATUS      current
    DESCRIPTION
        "This SMIv2 trap corresponds to IPP 'job-state-changed' event.
        The values of 'jmGeneralJobSetIndex' and 'jmJobIndex' for
        use with 'jmJobTable' for this Job are conveyed in the
        instance qualifier (OID suffix) of 'jmJobState'.
        Additional variable-bindings MAY be appended to this trap:
        - Systems with the Host Resources MIB (RFC 2790) MAY add
          'hrSystemDate'
          (compare to IPP 'printer-current-time')
        - Systems MAY add other variable-bindings from any MIB"
    REFERENCE
        "See:   Section 5.3.2 'notify-events' in [IPP-NOT]."
    ::= { xcmJmxJobStateV2TrapPrefix 1 }
xcmJmxJobCreatedV1Enterprise OBJECT-IDENTITY
    STATUS      current
    DESCRIPTION
        "The value of the enterprise-specific OID in an SNMPv1 trap
        for a Job created event sent by this managed system."
    ::= { xcmJmxMIBNotifications 3 }
xcmJmxJobCreatedV2TrapPrefix
    OBJECT IDENTIFIER ::= { xcmJmxJobCreatedV1Enterprise 0 }
xcmJmxJobCreatedV2Trap NOTIFICATION-TYPE
    OBJECTS {
        jmJobState,
        jmJobStateReasons1,
        jmNumberOfInterveningJobs
    }
    STATUS      current
    DESCRIPTION
        "This SMIv2 trap corresponds to IPP 'job-created' event."
    REFERENCE
        "See:   Section 5.3.2 'notify-events' in [IPP-NOT]."
    ::= { xcmJmxJobCreatedV2TrapPrefix 1 }
xcmJmxJobCompletedV1Enterprise OBJECT-IDENTITY
    STATUS      current
    DESCRIPTION
        "The value of the enterprise-specific OID in an SNMPv1 trap
        for a Job completed event sent by this managed system."
    ::= { xcmJmxMIBNotifications 4 }
xcmJmxJobCompletedV2TrapPrefix
    OBJECT IDENTIFIER ::= { xcmJmxJobCompletedV1Enterprise 0 }
xcmJmxJobCompletedV2Trap NOTIFICATION-TYPE
    OBJECTS {
        jmJobState,
        jmJobStateReasons1,
        jmJobKOctetsProcessed,
        jmJobImpressionsCompleted
    }
    STATUS      current
    DESCRIPTION
        "This SMIv2 trap corresponds to IPP 'job-completed' event."
    REFERENCE
        "See:   Section 5.3.2 'notify-events' in [IPP-NOT]."
    ::= { xcmJmxJobCompletedV2TrapPrefix 1 }
xcmJmxJobStoppedV1Enterprise OBJECT-IDENTITY
    STATUS      current
    DESCRIPTION
        "The value of the enterprise-specific OID in an SNMPv1 trap
        for a Job stopped event sent by this managed system."
    ::= { xcmJmxMIBNotifications 5 }
xcmJmxJobStoppedV2TrapPrefix
    OBJECT IDENTIFIER ::= { xcmJmxJobStoppedV1Enterprise 0 }
xcmJmxJobStoppedV2Trap NOTIFICATION-TYPE
    OBJECTS {
        jmJobState,
        jmJobStateReasons1,
        jmJobKOctetsProcessed,
        jmJobImpressionsCompleted
    }
    STATUS      current
    DESCRIPTION
        "This SMIv2 trap corresponds to IPP 'job-stopped' event."
    REFERENCE
        "See:   Section 5.3.2 'notify-events' in [IPP-NOT]."
    ::= { xcmJmxJobStoppedV2TrapPrefix 1 }
xcmJmxJobConfigV1Enterprise OBJECT-IDENTITY
    STATUS      current
    DESCRIPTION
        "The value of the enterprise-specific OID in an SNMPv1 trap
        for a Job config changed event sent by this managed system."
    ::= { xcmJmxMIBNotifications 6 }
xcmJmxJobConfigV2TrapPrefix
    OBJECT IDENTIFIER ::= { xcmJmxJobConfigV1Enterprise 0 }
xcmJmxJobConfigV2Trap NOTIFICATION-TYPE
    OBJECTS {
        jmJobState,
        jmJobStateReasons1,
        jmNumberOfInterveningJobs
    }
    STATUS      current
    DESCRIPTION
        "This SMIv2 trap corresponds to IPP 'job-config-changed' event."
    REFERENCE
        "See:   Section 5.3.2 'notify-events' in [IPP-NOT]."
    ::= { xcmJmxJobConfigV2TrapPrefix 1 }
xcmJmxJobProgressV1Enterprise OBJECT-IDENTITY
    STATUS      current
    DESCRIPTION
        "The value of the enterprise-specific OID in an SNMPv1 trap
        for a Job progress event sent by this managed system."
    ::= { xcmJmxMIBNotifications 7 }
xcmJmxJobProgressV2TrapPrefix
    OBJECT IDENTIFIER ::= { xcmJmxJobProgressV1Enterprise 0 }
xcmJmxJobProgressV2Trap NOTIFICATION-TYPE
    OBJECTS {
        jmJobKOctetsPerCopyRequested,
        jmJobKOctetsProcessed,
        jmJobImpressionsPerCopyRequested,
        jmJobImpressionsCompleted
    }
    STATUS      current
    DESCRIPTION
        "This SMIv2 trap corresponds to an IPP 'job-progress' event."
    REFERENCE
        "See:   Section 5.3.2 'notify-events' in [IPP-NOT]."
    ::= { xcmJmxJobProgressV2TrapPrefix 1 }
--
--
xcmJmxMIBConformance    OBJECT IDENTIFIER ::= { xcmJmxMIB 3 }
--
--
xcmJmxMIBCompliance MODULE-COMPLIANCE
    STATUS  current
    DESCRIPTION
        "The compliance statement for agents that implement this
        Job Admin MIB."
    MODULE 
    MANDATORY-GROUPS { xcmJmxGeneralGroup }
--      "Implementation of this group is CONDITIONALLY MANDATORY;
--      mandatory for systems which send Job traps via SNMP."
--      "Implementation of this group is CONDITIONALLY MANDATORY;
--      send Job traps via SNMP."
--      "It is conformant to implement this object with only the above
--      convention supported."
    ::= { xcmJmxMIBConformance 1 }
xcmJmxMIBObjectGroups   OBJECT IDENTIFIER ::= { xcmJmxMIBConformance 2 }
xcmJmxGeneralGroup OBJECT-GROUP
    OBJECTS {
        xcmJmxGeneralGroupSupport,
        xcmJmxGeneralJobCreatedCount,
        xcmJmxGeneralJobCompletedCount,
        xcmJmxGeneralJobOperationCount,
        xcmJmxGeneralJobTrapCount
    }
    STATUS  current
    DESCRIPTION
        "The general group."
    ::= { xcmJmxMIBObjectGroups 1 }
xcmJmxJobAdminGroup OBJECT-GROUP
    OBJECTS {
        xcmJmxJobAdminOperation,
        xcmJmxJobAdminStatus,
        xcmJmxJobAdminInProgress
    }
    STATUS  current
    DESCRIPTION
        "The job administration group."
    ::= { xcmJmxMIBObjectGroups 2 }
xcmJmxMIBTrapGroups     OBJECT IDENTIFIER ::= { xcmJmxMIBConformance 3 }
--          "The job event notification group."
--          "The job operation event notification group."
xcmCommsEngineTC OBJECT-IDENTITY -- MODULE-IDENTITY
    STATUS   current
    DESCRIPTION
        "Version:   5.10.pub
        The TC module for textual conventions, enumerated types, OIDs,
        and other volatile elements of the companion Communications
        Engine MIB, which supports detailed protocol stack graphing,
        and active management of communications protocol stacks,
        communications end system applications, communications
        intermediate systems, and communications gateways for network
        accessible host systems.
        Copyright (C) 1995-2002 Xerox Corporation. All Rights Reserved."
    ::= { xeroxCommonMIB 60 }
--
--
XcmCommsMgmtCommandRequest ::= TEXTUAL-CONVENTION
    STATUS      current
    DESCRIPTION
        "A write to this object by an (authorized) management station
        SHALL invokes a command for this protocol entity.
        A read of this object SHALL return the command currently in
        progress or last completed.
        It is mandatory that a conforming management agent ensure that
        the contents of this object remain 'in bounds' - an undefined
        value SHALL be replaced by 'none' - ie, although rejected with
        error in the SetResponse PDU, this object SHALL NOT contain any
        such undefined value.  At system initialization, this object
        SHALL contain 'none'.
      * 'none' - NO action(s) SHALL be taken, except agent SHALL clear
        '...CommandData' and set '...CommandStatus' to 'noError'.
      * 'test' or 'manage' - the associated '...CommandData' object
        SHALL be specified in the same SetRequest PDU.
      * all other commands - the associated '...CommandData' object
        MAY be specified in the same SetRequest PDU.
      * 'disable' - this protocol SHALL transition immediately (ie,
        without attempting graceful quiesce) to the 'inoperative' state.
      * 'enable', 'resetWarm', 'resetCold', or 'resetFactory' - the
        final state SHALL be either 'closed' or 'opened'.
      * 'test' - this protocol SHALL transition immediately to the
        'testing' state; otherwise, it is a local matter (ie, protocol
        specific) how this command is processed; however, the associated
        '...CommandData' object SHALL be specified.
      * 'enable' - it is a local matter (ie, protocol specific) whether
        the final state SHALL be 'closed' or 'opened'; however, if
        'closed' results, an 'open' SHALL yield 'opened'.
      * 'close', 'recover', or 'open' - this protocol SHALL make a 'best
        effort' to make an orderly transition to the requested final
        state.
      * 'quiesce' - this protocol SHALL make a 'best effort' to make a
        graceful transition to the 'closed' state.
      * 'resetCounters' - all comms counters SHALL be reset to zero.
      * 'resetWarm' - a comms 'warm restart' SHALL be performed.
      * 'resetCold' - a comms 'cold restart' SHALL be performed (ie, a
        power cycle reset).
      * 'resetFactory' - all factory defaults SHALL be restored, and a
        comms 'cold restart' SHALL be performed (ie, a power cycle
        reset).
      * 'flushInput' - all comms input (in progress or internally
        queued) SHALL be gracefully flushed
      * 'flushOutput' - all comms output (in progress or internally
        queued) SHALL be gracefully flushed
      * 'flushInOut' - all comms input and output output (in progress
        or internally queued) SHALL be gracefully flushed
      * 'manage' - it is a local matter (ie, product specific) how this
        command is processed; however, the associated '...CommandData'
        object SHALL be specified.
        Note:   All of the POSIX and XCMI comms level operations are
        taken from the POSIX System Admin std (IEEE 1387.4) and aligned
        with the high-end XCMI System Admin MIB."
    REFERENCE
        "See:   'dot5Commands' in IEEE 802.5 Token Ring MIB (RFC 1748).
        Compare:    'ifOperStatus' (current) and 'ifAdminStatus'
        (desired) in the Interfaces Group of IETF MIB-II (RFC 1213);
        'RowStatus' textual convention in IETF SMIv2 (RFC 1902/2578)."
    SYNTAX      INTEGER {
        none(1),
        disable(2),                     
        test(3),                        
        enable(4),                      
        close(5),                       
        recover(6),                     
        open(7),                        
        quiesce(8),                     
        resetCounters(9),               
        resetWarm(10),                  
        resetCold(11),                  
        resetFactory(12),               
        flushInput(13),                 
        flushOutput(14),                
        flushInOut(15),                 
        manage(16),                     
        commsCreate(1701),              
        commsDelete(1702),              
        commsList(1703),                
        commsSet(1704),                 
        commsClean(1705),               
        commsDisable(1706),             
        commsEnable(1707),              
        commsPause(1708),               
        commsResume(1709),              
        commsShutdown(1710),            
        commsManage(2701),              
        commsRestart(2702),             
        commsInstall(2721),             
        commsUpgrade(2722),             
        commsBackup(2723),              
        commsRestore(2724),             
        commsConfigure(2725),           
        commsDiagnose(2726),            
        commsResetCounters(2731),       
        commsResetWarm(2732),           
        commsResetCold(2733),           
        commsResetFactory(2734),        
        commsLogin(2741),               
        commsLogout(2742)               
    }
XcmCommsMgmtCommandData ::= TEXTUAL-CONVENTION
    STATUS      current
    DESCRIPTION
        "A write to this object specifies:  a) a 'test' command subtype
        and any accompanying 'test' protocol specific data; or b) a
        'manage' command subtype and any accompanying 'manage' protocol
        specific data; or c) protocol specific data accompanying any
        other command.
        A read of this object SHALL return the data (if any) which
        accompanied the current or last completed command.
        Note:   Conforming implementations are STRONGLY encouraged to
        consider support of encrypted password writes in this object."
    REFERENCE
        "See:   Appropriate standards for protocol specific tests"
    SYNTAX      OCTET STRING (SIZE (0..255))
XcmCommsMgmtState ::= TEXTUAL-CONVENTION
    STATUS      current
    DESCRIPTION
        "A relatively generic description of the current state of
        this communications entity.
        Usage:  It is desirable that the implementor report the states
        of all stack layers corresponding to conceptual rows in the
        'xcmCommsStackTable' accurately.  The use of the value 'unknown'
        SHOULD NOT be the general case, unless the host system has NO
        local instrumentation of the stack layers (such as the DMTF DMI,
        Desktop Management Interface) - when ANY local instrumentation
        of the stack layers is available, the implementor SHOULD
        accurately report stack layer states."
    SYNTAX      INTEGER {
        other(1),                       
        unknown(2),                     
        inoperative(3),                 
        testing(4),                     
        closed(5),                      
        closing(6),                     
        opening(7),                     
        recovering(8),                  
        opened(9)                       
    }
XcmCommsMgmtConditions ::= TEXTUAL-CONVENTION
    STATUS      current
    DESCRIPTION
        "A relatively generic description of the current conditions of
        this communications entity.
        The definition of 'conditions' is partially entity specific
        and is NOT completely amenable to generalization.  However, a
        base set of values (which MAY be extended for each entity type)
        is given below:
              1 : disableInProgress                  (normally NOT used)
              2 : testInProgress                              (optional)
              4 : enableInProgress
              8 : closeInProgress
             16 : recoverInProgress                           (optional)
             32 : openInProgress
             64 : quiesceInProgress                           (optional)
            128 : resetCountersInProgress            (normally NOT used)
            256 : resetWarmInProgress                 (current defaults)
            512 : resetColdInProgress                 (current defaults)
           1024 : resetFactoryInProgress              (factory defaults)
           2048 : manageInProgress                            (optional)
           4096 : incomingTestInProgress                      (optional)
           8192 : outgoingTestInProgress                      (optional)
          16384 : incomingAuthorizeInProgress                 (optional)
          32768 : outgoingAuthorizeInProgress                 (optional)
          65536 : incomingFlowControlInProgress               (optional)
         131072 : outgoingFlowControlInProgress               (optional)
        The above basic 'conditions' remember the original intent of the
        current command, when it results in several state transitions
        before arriving at the 'final' state.  They augment the state
        info available from a variable of type 'XcmCommsMgmtState',
        by graphing the 'progress' of a command through the states.
        Usage:  It is desirable that the implementor report 'conditions'
        of all stack layers corresponding to conceptual rows in the
        'xcmCommsStackTable' accurately.  'Conditions' occur within or
        across 'states' in a finite state machine (FSM) implementation
        of a communications entity.  They represent both transient and
        long term constraints and circumstances."
    SYNTAX      INTEGER (0..2147483647)  
XcmCommsStackPosition ::= TEXTUAL-CONVENTION
    STATUS      current
    DESCRIPTION
        "A relatively generic description of the current
        position of this protocol entity (ie, this layer) in a protocol
        stack.
        Composed of one or more of the following position descriptors,
        arithmetically added together:
        bottom      :  1
        middle      :  2
        top         :  4
        lowerMux    :  8
        upperMux    : 16
        Usage:  A conceptual row in 'xcmCommsStackTable', which occupies
        a 'bottom' position in a protocol stack AND has a corresponding
        row in the 'xcmCommsStackXrefTable', SHOULD have valid
        references in 'xcmCommsStackXrefIfIndex' (to IETF MIB-II) and
        'xcmCommsStackXrefHrCommDevIndex' (to IETF Host Resources MIB).
        Usage:  A conceptual row in 'xcmCommsStackTable' which occupies
        a 'lowerMux' and/or an 'upperMux' position in a protocol stack
        SHALL have one (or two) valid corresponding conceptual
        rows in the 'xcmCommsMuxTable', as the conventionally used
        'xcmStack[Lower|Upper]StackIndex' objects take on zero values
        for multiplexors (thus breaking the graph of the stack layers,
        without the use of the 'xcmCommsMuxTable').
        Note:   In many real open systems which are internet attached,
        IETF IP (connectionless mode) network layer has a position of:
        a)  'middle' - neither top nor bottom;
        b)  'lowerMux' - above both OSI LLC (ISO 8802-2) and OSI CONP
            (CCITT X.25 over LAPB) datalinks; and
        c)  'upperMux' - below both IETF TCP (connection mode) and
            IETF UDP (connectionless mode) transports."
    SYNTAX      INTEGER {
        bottom(1),                      
        middle(2),                      
        top(4),                         
        bottomAndTop(5),                
        lowerMux(8),                    
        bottomLowerMux(9),              
        middleLowerMux(10),             
        topLowerMux(12),                
        upperMux(16),                   
        bottomUpperMux(17),             
        middleUpperMux(18),             
        topUpperMux(20),                
        bottomBothMux(25),              
        middleBothMux(26),              
        topBothMux(28)                  
    }
XcmCommsStackExtPurpose ::= TEXTUAL-CONVENTION
    STATUS      current
    DESCRIPTION
        "A relatively generic description of the current
        purpose of this stack layer/sublayer during normal operation.
        Usage:  Please note that 'layerInterWorkingUnit' would correctly
        describe:  a datalink MAC sublayer bridge (eg, IEEE 802.1D); a
        network layer relay (X.25 backbone switch); a network layer
        gateway (eg, X.25 <--> Telex IWU); or a transport layer gateway
        (eg, OSI COTP over X.25 <--> OSI COTP over OSI CLNP).
        Also note that 'systemInterWorkingUnit' would correctly describe
        an application layer gateway (eg, X/Open XDPA <--> Novell NDPS,
        for print services based on DPA, ISO 10175)."
    SYNTAX      INTEGER {
        other(1),                       
        unknown(2),                     
        layerOther(11),                 
        layerDataTransfer(12),          
        layerManagement(13),            
        layerSecurity(14),              
        layerInterWorkingUnit(15),      
        systemOther(16),
        systemDataTransfer(17),         
        systemManagement(18),           
        systemSecurity(19),             
        systemInterWorkingUnit(20)      
    }
XcmCommsStackExtRole ::= TEXTUAL-CONVENTION
    STATUS      current
    DESCRIPTION
        "A relatively generic description of the current
        role of this stack layer/sublayer during normal operation.
        Usage:  The values 'peer', 'primary', and 'secondary' are
        standard roles for non-application layer protocols.  The value
        'multicaster' indicates a role of multicast host (ie, all remote
        systems would play roles of 'secondary').  The values 'client'
        and 'server', which are analogous to 'primary' and 'secondary',
        are normally used to refer to application layer protocols, along
        with 'peer' (eg, IBM SNA APPC applications)."
    SYNTAX      INTEGER {
        other(1),                       
        unknown(2),                     
        peer(11),                       
        primary(12),                    
        secondary(13),                  
        multicaster(14),                
        client(15),                     
        server(16)                      
    }
XcmCommsStackExtSuite ::= TEXTUAL-CONVENTION
    STATUS      current
    DESCRIPTION
        "The current protocol suite of this protocol entity
        (stack layer or sublayer)."
    SYNTAX      INTEGER {
        other(1),                       
        unknown(2),                     
        osilan(11),                     
        osiman(12),                     
        osiwan(13),                     
        internet(14),                   
        ibmsna(15),                     
        ibmbisync(16),                  
        decnet(17),                     
        appletalk(18),                  
        netware(19),                    
        vines(20),                      
        lantastic(21),                  
        lanserver(22),                  
        lanmanager(23),                 
        ntas(24),                       
        netbios(25),                    
        netbeui(26),                    
        serial(27),                     
        parallel(28),                   
        directPrint(29),                
        usb(30)                         
    }
XcmCommsStackExtSuiteVersion ::= TEXTUAL-CONVENTION
    STATUS      current
    DESCRIPTION
        "The current protocol suite version of this protocol entity
        (stack layer or sublayer).
        Usage:  The following enumeration is used to unambiguously
        identify a specific protocol suite version (or generic version),
        without resort to textual strings.
        Note:   The following enumeration values are composed of two
        N-digit elements (left-to-right):
        a)  First, the two-digit enumeration value of the protocol suite
            (from 'XcmCommsStackExtSuite'); and
        b)  Second, a unique four-digit identifier."
    SYNTAX      INTEGER {
        other(1),                       
        unknown(2),                     
        osilanVersions(110101),         
        osimanVersions(120101),         
        osiwanVersions(130101),         
        internetVersions(140101),       
        ibmsnaVersions(150101),         
        ibmbisyncVersions(160101),      
        decnetVersions(170101),         
        appletalkVersions(180101),      
        appletalkPhase1(181999),        
        appletalkPhase2(182999),        
        netwareVersions(190101),        
        netware2x(192999),              
        netware3x(193999),              
        netware4x(194999),              
        vinesVersions(200101),          
        lantasticVersions(210101),      
        lanserverVersions(220101),      
        lanmanagerVersions(230101),     
        ntasVersions(240101),           
        netbiosVersions(250101),        
        netbeuiVersions(260101),        
        serialVersions(270101),         
        parallelVersions(280101),       
        directPrintVersions(290101),    
        usbVersions(300101)             
    }
XcmCommsStackExtLayer ::= TEXTUAL-CONVENTION
    STATUS      current
    DESCRIPTION
        "The closest approximate layer in the OSI Reference Model
        (CCITT X.200 | ISO 7498) to the current behavior
        of this stack layer or sublayer.
        Usage:  Note that this value MAY NOT be strictly
        accurate.  A number of legacy proprietary protocol suites use
        unusual and irregular names for their protocols (eg, frequent
        assignment of relatively simplistic transport protocols to the
        OSI Reference Model session layer in some protocol suites).
        Note:   The following enumeration values are biased by ten (10),
        for ease of use, from the original OSI Reference Model."
    SYNTAX      INTEGER {
        other(1),                       
        unknown(2),                     
        physical(11),
        datalink(12),
        network(13),
        transport(14),
        session(15),
        presentation(16),
        application(17)
    }
XcmCommsStackExtProtocol ::= TEXTUAL-CONVENTION
    STATUS      current
    DESCRIPTION
        "The specific protocol (within a given protocol suite) currently
        configured for this stack layer or sublayer.
        Usage:  The following enumeration is used to unambiguously
        identify a specific protocol (within a given protocol suite),
        without resort to textual strings.
        Note:   The following enumeration values are composed of three
        two-digit elements (left-to-right):
        a)  First, the two-digit enumeration value of the protocol suite
            (from 'XcmCommsStackExtSuite');
        b)  Second, the two-digit enumeration value of the OSI Reference
            Model layer (from 'XcmCommsStackExtLayer'); and
        c)  Third, a unique two-digit identifier."
    SYNTAX      INTEGER {
        other(1),                       
        unknown(2),                     
        osilanSuite(110101),            
        osilan8023PMD(111103),          
        osilan8024PMD(111104),          
        osilan8025PMD(111105),          
        osilanFDDIPMD(111107),          
        osilan80211PMD(111108),         
        osilan8023PHY(111113),          
        osilan8024PHY(111114),          
        osilan8025PHY(111115),          
        osilanFDDIPHY(111117),          
        osilan80211PHY(111118),         
        osilan8023MAC(111203),          
        osilan8024MAC(111204),          
        osilan8025MAC(111205),          
        osilanFDDIMAC(111207),          
        osilan80211MAC(111208),         
        osilan8025SMT(111215),          
        osilanFDDISMT(111217),          
        osilan80211SMT(111218),         
        osilan8022LLC(111221),          
        osilan8022LLCSNAP(111222),      
        osilan8021BLMMP(111232),        
        osilan8021DBRG(111234),         
        osilan80210SDE(111241),         
        osimanSuite(120101),            
        osiman8026PMD(121106),          
        osiman8026PHY(121116),          
        osiman8026MAC(121206),          
        osiman8026SMT(121216),          
        osiwanSuite(130101),            
        osiwanHdlcABM(131201),          
        osiwanHdlcARM(131202),          
        osiwanHdlcNRM(131203),          
        osiwanHdlcABME(131211),         
        osiwanHdlcARME(131212),         
        osiwanHdlcNRME(131213),         
        osiwanHdlcLAPB(131221),         
        osiwanHdlcLAPD(131224),         
        osiwanFax(131241),              
        osiwanPSTN(131251),             
        osiwanISDN(131261),             
        osiwanCLNP(131301),             
        osiwanCONP(131302),             
        osiwanESIS(131303),             
        osiwanISIS(131304),             
        osiwanCLTP(131401),             
        osiwanCOTP(131402),             
        osiwanCLSP(131501),             
        osiwanCOSP(131502),             
        osiwanCLPP(131601),             
        osiwanCOPP(131602),             
        osiwanACSE(131701),             
        osiwanRTSE(131702),             
        osiwanROSE(131703),             
        osiwanCCR(131704),              
        osiwanDPA(131713),              
        osiwanFTAM(131714),             
        osiwanVT(131716),               
        osiwanMHS(131740),              
        osiwanDS(131750),               
        osiwanDAP(131751),              
        osiwanDSP(131752),              
        osiwanMgmt(131770),             
        osiwanCMIP(131771),             
        osiwanSec(131780),              
        internetSuite(140101),          
        internetSLIP(141201),           
        internetPPP(141202),            
        internetIP(141301),             
        internetICMP(141302),           
        internetARP(141303),            
        internetDHCP(141304),           
        internetBOOTP(141305),          
        internetRARP(141306),           
        internetIPv6(141310),           
        internetUDP(141401),            
        internetTCP(141402),            
        internetPing(141404),           
        internetSSL3(141405),           
        internetTLS(141406),            
        internetRaw(141501),            
        internetIPP(141502),            
        internetLPR(141503),            
        internetFTP(141504),            
        internetSMTP(141505),           
        internetTelnet(141506),         
        internetDNS(141507),            
        internetTFTP(141508),           
        internetHTTP(141509),           
        internetSNMP(141510),           
        internetSNMPv1(141511),         
        internetSNMPv2(141512),         
        internetSNMPv3(141513),         
        internetPOP3(141514),           
        internetIMAP4(141515),          
        internetFax(141516),            
        internetWINS(141519),           
        internetSunOncSuite(141520),    
        internetSunOncNIS(141521),      
        internetSunOncPlusNIS(141522),  
        internetSunOncRPC(141523),      
        internetSunOncPlusRPC(141524),  
        internetSunTiRPC(141525),       
        internetOsfDceSuite(141530),    
        internetOsfDceCDS(141531),      
        internetOsfDceRPC(141532),      
        internetOsfDceKerberos(141533), 
        internetOsfDmeSuite(141540),    
        internetLDAP(141551),           
        internetCLDAP(141552),          
        internetSalutation(141561),     
        internetUpnpSuite(141570),      
        internetUpnpSSDP(141571),       
        internetUpnpGENA(141572),       
        internetSLP(141591),            
        internetSLPv1(141592),          
        internetSLPv2(141593),          
        ibmsnaSuite(150101),            
        ibmsnaSDLC(151201),             
        ibmsnaDLC(151211),              
        ibmsnaDLS(151221),              
        ibmsnaPC(151301),               
        ibmsnaTC(151401),               
        ibmsnaDFC(151501),              
        ibmsnaCSC(151502),              
        ibmsnaPUNS(151503),             
        ibmsnaLUNS(151504),             
        ibmsnaPS(151601),               
        ibmsna3270PS(151602),           
        ibmsna5250PS(151603),           
        ibmsnaRJE(151604),              
        ibmsnaAPPC(151605),             
        ibmbisyncSuite(160101),         
        ibmbisyncDLC(161201),           
        ibmbisyncPS(161601),            
        ibmbisync3270PS(161602),        
        ibmbisync5250PS(161603),        
        ibmbisyncRJE(161604),           
        decnetSuite(170101),            
        appletalkSuite(180101),         
        appletalkLLAP(181201),          
        appletalkELAP(181202),          
        appletalkTLAP(181203),          
        appletalkDDP(181301),           
        appletalkAARP(181303),          
        appletalkATP(181401),           
        appletalkADSP(181402),          
        appletalkRTMP(181403),          
        appletalkAEP(181404),           
        appletalkASP(181501),           
        appletalkZIP(181502),           
        appletalkPAP(181503),           
        appletalkNBP(181507),           
        appletalkSNMP(181510),          
        appletalkSNMPv1(181511),        
        appletalkSNMPv2(181512),        
        appletalkSNMPv3(181513),        
        appletalkAFP(181601),           
        netwareSuite(190101),           
        netwareIPX(191301),             
        netwareSPX(191402),             
        netwareRIP(191403),             
        netwareEcho(191404),            
        netwareNCP(191501),             
        netwareNetbios(191502),         
        netwarePServer(191503),         
        netwareFServer(191504),         
        netwareMHS(191505),             
        netwareBindery(191507),         
        netwareNDS(191508),             
        netwareRPrinter(191509),        
        netwareSNMP(191510),            
        netwareSNMPv1(191511),          
        netwareSNMPv2(191512),          
        netwareSNMPv3(191513),          
        netwareSAP(191591),             
        vinesSuite(200101),             
        vinesVIP(201301),               
        vinesVICP(201302),              
        vinesVARP(201303),              
        vinesIP(201311),                
        vinesICMP(201312),              
        vinesARP(201313),               
        vinesVRTP(201314),              
        vinesVIPC(201401),              
        vinesVSPP(201402),              
        vinesUDP(201411),               
        vinesTCP(201412),               
        vinesNetRPC(201501),            
        vinesSocket(201502),            
        vinesNetbios(201503),           
        vinesPrint(201701),             
        vinesFiling(201702),            
        vinesMail(201703),              
        vinesStreetTalk(201704),        
        lantasticSuite(210101),         
        lanserverSuite(220101),         
        lanmanagerSuite(230101),        
        ntasSuite(240101),              
        netbiosSuite(250101),           
        netbiosNBP(251501),             
        netbiosSNMP(251510),            
        netbiosSNMPv1(251511),          
        netbiosSNMPv2(251512),          
        netbiosSNMPv3(251513),          
        netbiosIntEndNode(251520),      
        netbiosIntNameServer(251521),   
        netbiosIntDistServer(251522),   
        netbiosSAP(251591),             
        netbiosSMB(251701),             
        netbiosPClient(251702),         
        netbiosPServer(251703),         
        netbiosFClient(251704),         
        netbiosFServer(251705),         
        netbeuiSuite(260101),           
        netbeuiDatalink(261201),        
        netbeuiLLC(261221),             
        netbeuiDLC(261231),             
        serialSuite(270101),            
        parallelSuite(280101),          
        directPrintSuite(290101),       
        usbSuite(300101)                
    }
XcmCommsAddressExtForm ::= TEXTUAL-CONVENTION
    STATUS      current
    DESCRIPTION
        "The current address form of this protocol entity."
    SYNTAX      INTEGER {
        other(1),                       
        unknown(2),                     
        postal(11),                     
        voice(12),                      
        telex(13),                      
        fax(14),                        
        packet(15),                     
        email(16),                      
        fullName(17),                   
        relName(18)                     
    }
XcmCommsAddressExtScope ::= TEXTUAL-CONVENTION
    STATUS      current
    DESCRIPTION
        "The current address scope of this protocol entity."
    SYNTAX      INTEGER {
        other(1),                       
        unknown(2),                     
        subnet(11),                     
        region(12),                     
        network(13),                    
        universe(14)                    
    }
XcmCommsAddressExtFanout ::= TEXTUAL-CONVENTION
    STATUS      current
    DESCRIPTION
        "The current address fan out of this protocol entity."
    SYNTAX      INTEGER {
        other(1),                       
        unknown(2),                     
        unicast(11),                    
        multicast(12),                  
        broadcast(13),                  
        universe(14),                   
        unicastMask(15),                
        multicastMask(16),              
        broadcastMask(17),              
        universeMask(18)                
    }
XcmCommsEngineGroupSupport ::= TEXTUAL-CONVENTION
    STATUS      current
    DESCRIPTION
        "The terse conformance statement of ALL mandatory, conditionally
        mandatory, and optional XCMI Comms Engine MIB object groups
        supported by this management agent implementation (ie, version)
        on this host system, specified in a bit-mask.
        The current set of values (which MAY be extended in the future)
        is given below:
              1 : commsEngineGroup            
              2 : commsEngineExtGroup         
              4 : commsStackGroup             
              8 : commsStackExtGroup          
             16 : commsStackXrefGroup         
             32 : commsMuxGroup               
             64 : commsMuxExtGroup            
            128 : commsAddressGroup           
            256 : commsAddressExtGroup        
            512 : commsTrafficGroup           
           1024 : commsAccessGroup            
           2048 : commsMgmtGroup              
        Usage:  Conforming management agents SHALL accurately
        report their support for XCMI Comms Engine MIB object groups."
    SYNTAX      INTEGER (0..2147483647)  
--
--
--
xCmCommsEngineDummy OBJECT IDENTIFIER ::= { xcmCommsEngineTC 999 }
xCmCommsMgmtCommandRequest OBJECT-TYPE
    SYNTAX      XcmCommsMgmtCommandRequest
    MAX-ACCESS  not-accessible
    STATUS      current
    DESCRIPTION "Dummy - DO NOT USE"
    ::= { xCmCommsEngineDummy 1 }
xCmCommsMgmtCommandData OBJECT-TYPE
    SYNTAX      XcmCommsMgmtCommandData
    MAX-ACCESS  not-accessible
    STATUS      current
    DESCRIPTION "Dummy - DO NOT USE"
    ::= { xCmCommsEngineDummy 2 }
xCmCommsMgmtState OBJECT-TYPE
    SYNTAX      XcmCommsMgmtState
    MAX-ACCESS  not-accessible
    STATUS      current
    DESCRIPTION "Dummy - DO NOT USE"
    ::= { xCmCommsEngineDummy 3 }
xCmCommsMgmtConditions OBJECT-TYPE
    SYNTAX      XcmCommsMgmtConditions
    MAX-ACCESS  not-accessible
    STATUS      current
    DESCRIPTION "Dummy - DO NOT USE"
    ::= { xCmCommsEngineDummy 4 }
xCmCommsStackPosition OBJECT-TYPE
    SYNTAX      XcmCommsStackPosition
    MAX-ACCESS  not-accessible
    STATUS      current
    DESCRIPTION "Dummy - DO NOT USE"
    ::= { xCmCommsEngineDummy 5 }
xCmCommsStackExtPurpose OBJECT-TYPE
    SYNTAX      XcmCommsStackExtPurpose
    MAX-ACCESS  not-accessible
    STATUS      current
    DESCRIPTION "Dummy - DO NOT USE"
    ::= { xCmCommsEngineDummy 6 }
xCmCommsStackExtRole OBJECT-TYPE
    SYNTAX      XcmCommsStackExtRole
    MAX-ACCESS  not-accessible
    STATUS      current
    DESCRIPTION "Dummy - DO NOT USE"
    ::= { xCmCommsEngineDummy 7 }
xCmCommsStackExtSuite OBJECT-TYPE
    SYNTAX      XcmCommsStackExtSuite
    MAX-ACCESS  not-accessible
    STATUS      current
    DESCRIPTION "Dummy - DO NOT USE"
    ::= { xCmCommsEngineDummy 8 }
xCmCommsStackExtSuiteVersion OBJECT-TYPE
    SYNTAX      XcmCommsStackExtSuiteVersion
    MAX-ACCESS  not-accessible
    STATUS      current
    DESCRIPTION "Dummy - DO NOT USE"
    ::= { xCmCommsEngineDummy 9 }
xCmCommsStackExtLayer OBJECT-TYPE
    SYNTAX      XcmCommsStackExtLayer
    MAX-ACCESS  not-accessible
    STATUS      current
    DESCRIPTION "Dummy - DO NOT USE"
    ::= { xCmCommsEngineDummy 10 }
xCmCommsStackExtProtocol OBJECT-TYPE
    SYNTAX      XcmCommsStackExtProtocol
    MAX-ACCESS  not-accessible
    STATUS      current
    DESCRIPTION "Dummy - DO NOT USE"
    ::= { xCmCommsEngineDummy 11 }
xCmCommsAddressExtForm OBJECT-TYPE
    SYNTAX      XcmCommsAddressExtForm
    MAX-ACCESS  not-accessible
    STATUS      current
    DESCRIPTION "Dummy - DO NOT USE"
    ::= { xCmCommsEngineDummy 12 }
xCmCommsAddressExtScope OBJECT-TYPE
    SYNTAX      XcmCommsAddressExtScope
    MAX-ACCESS  not-accessible
    STATUS      current
    DESCRIPTION "Dummy - DO NOT USE"
    ::= { xCmCommsEngineDummy 13 }
xCmCommsAddressExtFanout OBJECT-TYPE
    SYNTAX      XcmCommsAddressExtFanout
    MAX-ACCESS  not-accessible
    STATUS      current
    DESCRIPTION "Dummy - DO NOT USE"
    ::= { xCmCommsEngineDummy 14 }
xCmCommsEngineGroupSupport OBJECT-TYPE
    SYNTAX      XcmCommsEngineGroupSupport
    MAX-ACCESS  not-accessible
    STATUS      current
    DESCRIPTION "Dummy - DO NOT USE"
    ::= { xCmCommsEngineDummy 15 }
xcmCommsEngineMIB OBJECT-IDENTITY -- MODULE-IDENTITY
    STATUS   current
    DESCRIPTION
        "Version:   5.11.pub
        The MIB module for detailed protocol stack graphing, and active
        management of communications protocol stacks, communications end
        system applications, communications intermediate systems, and
        communications gateways for network accessible host systems.
        Usage:  Note that throughout this MIB module, the INDEX clauses
        referring to 'hrDeviceIndex' for the 'hrDeviceTable' (Devices
        Group) of the Host Resources MIB (RFC 2790) SHALL
        specify host system CPUs (ie, 'hrDeviceProcessor') and SHALL NOT
        specify ANY other 'hrDeviceType'.
        Usage:  The object 'xcmCommsStackXrefHrCommDevIndex' in  the
        Comms Stack Xref Group of this MIB MAY be used to specify
        (for 'bottom' protocol stack layers) the corresponding value of
        'hrDeviceIndex' for network, modem, serial port, and parallel
        port devices.  And the object 'xcmCommsStackXrefIfIndex' MAY be
        used to specify the value of 'ifIndex' for the corresponding
        entry in the MIB-II 'ifTable' (ie, 'network interfaces').
        Copyright (C) 1995-2002 Xerox Corporation. All Rights Reserved."
    ::= { xeroxCommonMIB 61 }
xcmCommsEngineZeroDummy OBJECT IDENTIFIER ::= { zeroDotZero 61 }
--
--
--
xcmCommsEngine          OBJECT IDENTIFIER ::= { xcmCommsEngineMIB 3 }
xcmCommsEngineTable OBJECT-TYPE
    SYNTAX      SEQUENCE OF XcmCommsEngineEntry
    MAX-ACCESS  not-accessible
    STATUS      current
    DESCRIPTION
        "A table of the communications engines installed and (possibly)
        running on platforms (ie, CPUs) on this host system."
    ::= { xcmCommsEngine 2 }
xcmCommsEngineEntry OBJECT-TYPE
    SYNTAX      XcmCommsEngineEntry
    MAX-ACCESS  not-accessible
    STATUS      current
    DESCRIPTION
        "An entry for a communications engine installed and (possibly)
        running on a platform (ie, CPU) on this host system.
        Usage:  Note that values of 'hrDeviceIndex' used to reference
        entries in the 'xcmCommsEngineTable' SHALL reference
        entries in the 'hrDeviceTable' with 'hrDeviceType' equal to
        'hrDeviceProcessor' (representing host system CPUs and therefore
        also having corresponding entries in the 'hrProcessorTable')."
    INDEX       { hrDeviceIndex }
    ::= { xcmCommsEngineTable 1 }
XcmCommsEngineEntry ::= SEQUENCE {
        xcmCommsEngineRowStatus         RowStatus,
        xcmCommsEngineName              XcmFixedLocaleDisplayString,
        xcmCommsEngineStackLast         Cardinal32,
        xcmCommsEngineMuxLast           Cardinal32,
        xcmCommsEngineAddressLast       Cardinal32,
        xcmCommsEngineMgmtLast          Cardinal32,
        xcmCommsEngineGroupSupport      XcmCommsEngineGroupSupport,
        xcmCommsEngineCreateSupport     XcmCommsEngineGroupSupport,
        xcmCommsEngineUpdateSupport     XcmCommsEngineGroupSupport
    }
--
--
xcmCommsEngineRowStatus OBJECT-TYPE
    SYNTAX      RowStatus
    MAX-ACCESS  read-only
    STATUS      current
    DESCRIPTION
        "This object is used to create and delete individual conceptual
        rows in the 'xcmCommsEngineTable'."
    ::= { xcmCommsEngineEntry 1 }
xcmCommsEngineName OBJECT-TYPE
    SYNTAX      XcmFixedLocaleDisplayString (SIZE (0..255))
    MAX-ACCESS  read-only
    STATUS      current
    DESCRIPTION
        "Human-readable name, used by system administrators
        and end users to identify this communications engine
        for systems management.
        Usage:  This name SHOULD be the one normally used in a
        command shell for control of this communications engine."
    DEFVAL      { ''H }                 
    ::= { xcmCommsEngineEntry 2 }
xcmCommsEngineStackLast OBJECT-TYPE
    SYNTAX      Cardinal32
    MAX-ACCESS  read-only
    STATUS      current
    DESCRIPTION
        "The last entry index (regardless of its current state) in
        the 'xcmCommsStackTable' of this communications engine,
        on this host system.
        Usage:  The last entry index explicitly bounds the valid range
        of 'xcmCommsStackIndex'."
    DEFVAL      { 0 }                   
    ::= { xcmCommsEngineEntry 3 }
xcmCommsEngineMuxLast OBJECT-TYPE
    SYNTAX      Cardinal32
    MAX-ACCESS  read-only
    STATUS      current
    DESCRIPTION
        "The last entry index (regardless of its current state) in
        the 'xcmCommsMuxTable' of this communications engine,
        on this host system.
        Usage:  The last entry index explicitly bounds the valid range
        of 'xcmCommsMuxIndex'."
    DEFVAL      { 0 }                   
    ::= { xcmCommsEngineEntry 4 }
xcmCommsEngineAddressLast OBJECT-TYPE
    SYNTAX      Cardinal32
    MAX-ACCESS  read-only
    STATUS      current
    DESCRIPTION
        "The last entry index (regardless of its current state) in
        the 'xcmCommsAddressTable' of this communications engine,
        on this host system.
        Usage:  The last entry index explicitly bounds the valid range
        of 'xcmCommsAddressIndex'."
    DEFVAL      { 0 }                   
    ::= { xcmCommsEngineEntry 6 }
xcmCommsEngineMgmtLast OBJECT-TYPE
    SYNTAX      Cardinal32
    MAX-ACCESS  read-only
    STATUS      current
    DESCRIPTION
        "The last entry index (regardless of its current state) in
        the 'xcmCommsMgmtTable' of this communications engine,
        on this host system.
        Usage:  The last entry index explicitly bounds the valid range
        of 'xcmCommsMgmtIndex'."
    DEFVAL      { 0 }                   
    ::= { xcmCommsEngineEntry 7 }
xcmCommsEngineGroupSupport OBJECT-TYPE
    SYNTAX      XcmCommsEngineGroupSupport
    MAX-ACCESS  read-only
    STATUS      current
    DESCRIPTION
        "The terse conformance statement of ALL mandatory, conditionally
        mandatory, and optional XCMI Comms Engine MIB object groups
        supported by this management agent implementation (ie, version)
        on this host system, specified in a bit-mask.
        Usage:  Conforming management agents SHALL accurately
        report their support for XCMI Comms Engine MIB object groups."
    DEFVAL      { 1 }                   
    ::= { xcmCommsEngineEntry 8 }
xcmCommsEngineCreateSupport OBJECT-TYPE
    SYNTAX      XcmCommsEngineGroupSupport
    MAX-ACCESS  read-only
    STATUS      current
    DESCRIPTION
        "The terse conformance statement of ALL mandatory, conditionally
        mandatory, and optional XCMI Comms Engine MIB object groups
        supported for dynamic row creation (via '...RowStatus')
        by this management agent implementation (ie, version)
        on this host system, specified in a bit-mask.
        Usage:  Conforming management agents SHALL accurately
        report their support for XCMI Comms Engine MIB object groups."
    DEFVAL      { 0 }                   
    ::= { xcmCommsEngineEntry 9 }
xcmCommsEngineUpdateSupport OBJECT-TYPE
    SYNTAX      XcmCommsEngineGroupSupport
    MAX-ACCESS  read-only
    STATUS      current
    DESCRIPTION
        "The terse conformance statement of ALL mandatory, conditionally
        mandatory, and optional XCMI Comms Engine MIB object groups
        supported for existing row update (via SNMP Set-Request PDUs)
        by this management agent implementation (ie, version)
        on this host system, specified in a bit-mask.
        Usage:  Conforming management agents SHALL accurately
        report their support for XCMI Comms Engine MIB object groups."
    DEFVAL      { 0 }                   
    ::= { xcmCommsEngineEntry 10 }
--
--
xcmCommsEngineExt       OBJECT IDENTIFIER ::= { xcmCommsEngineMIB 4 }
xcmCommsEngineExtTable OBJECT-TYPE
    SYNTAX      SEQUENCE OF XcmCommsEngineExtEntry
    MAX-ACCESS  not-accessible
    STATUS      current
    DESCRIPTION
        "A 'sparse' table which augments 'xcmCommsEngineTable' with
        additional useful information."
    ::= { xcmCommsEngineExt 2 }
xcmCommsEngineExtEntry OBJECT-TYPE
    SYNTAX      XcmCommsEngineExtEntry
    MAX-ACCESS  not-accessible
    STATUS      current
    DESCRIPTION
        "A 'sparse' entry which augments 'xcmCommsEngineEntry' with
        additional useful information."
    INDEX       { hrDeviceIndex }
    ::= { xcmCommsEngineExtTable 1 }
XcmCommsEngineExtEntry ::= SEQUENCE {
        xcmCommsEngineExtRowStatus      RowStatus,
        xcmCommsEngineExtState          XcmCommsMgmtState,
        xcmCommsEngineExtConditions     XcmCommsMgmtConditions,
        xcmCommsEngineExtVersionID      ProductID,
        xcmCommsEngineExtVersionDate    DateAndTime,
        xcmCommsEngineExtMgmtIndex      Cardinal32,
        xcmCommsEngineExtOwnerOID       OBJECT IDENTIFIER
    }
--
--
xcmCommsEngineExtRowStatus OBJECT-TYPE
    SYNTAX      RowStatus
    MAX-ACCESS  read-only
    STATUS      current
    DESCRIPTION
        "This object is used to create and delete individual conceptual
        rows in the 'xcmCommsEngineExtTable'."
    ::= { xcmCommsEngineExtEntry 1 }
xcmCommsEngineExtState OBJECT-TYPE
    SYNTAX      XcmCommsMgmtState
    MAX-ACCESS  read-only
    STATUS      current
    DESCRIPTION
        "A relatively generic description of the current state of
        this communications entity."
    DEFVAL      { inoperative }         
    ::= { xcmCommsEngineExtEntry 2 }
xcmCommsEngineExtConditions OBJECT-TYPE
    SYNTAX      XcmCommsMgmtConditions
    MAX-ACCESS  read-only
    STATUS      current
    DESCRIPTION
        "A relatively generic description of the current conditions of
        this communications entity."
    DEFVAL      { 0 }                   
    ::= { xcmCommsEngineExtEntry 4 }
xcmCommsEngineExtVersionID OBJECT-TYPE
    SYNTAX      ProductID
    MAX-ACCESS  read-only
    STATUS      current
    DESCRIPTION
        "The software product ID of the SNMP sub-agent which implements
        the XCMI Comms Engine MIB on this host system.
        Usage:  This object SHALL specify the software product ID of an
        SNMP sub-agent (possibly also found in a conceptual row in the
        'hrSWRunTable' and/or 'hrSWInstalledTable' in the IETF HR MIB).
        This object SHALL NOT specify a particular release of the XCMI
        Comms Engine MIB, or the whole host system product.
        Note:   Contrast with 'sysObjectID' for the whole SNMP agent in
        the IETF MIB-II (RFC 1213) and 'hrDeviceID' for the whole device
        (or whole product, in the case of 'xcmHrDevice...') in the IETF
        Host Resources MIB (RFC 2790)."
    REFERENCE
        "See:   'hrSW[Installed|Run]ID' in the Software Installed and
                Software Running groups of the IETF HR MIB (RFC 2790)."
    DEFVAL      { zeroDotZero }   
    ::= { xcmCommsEngineExtEntry 5 }
xcmCommsEngineExtVersionDate OBJECT-TYPE
    SYNTAX      DateAndTime
    MAX-ACCESS  read-only
    STATUS      current
    DESCRIPTION
        "The software build date of the SNMP sub-agent which implements
        the XCMI Comms Engine MIB on this host system.
        Usage:  This object SHALL specify the BUILD date of the SNMP
        sub-agent software (not available elsewhere in IETF/XCMI MIBs).
        This object SHALL NOT specify the INSTALL date of the SNMP
        sub-agent software on this host system, nor the RESET date.
        Note:   Contrast with 'hrSWInstalledDate' in the Software
        Installed group of the IETF Host Resources MIB (RFC 2790), and
        'xcmHrDevInfoResetDate' in the Device Info group of the XCMI
        Host Resources Extensions MIB."
    REFERENCE
        "See:   'hrSW[Installed|Run]ID' in the Software Installed and
                Software Running groups of the IETF HR MIB (RFC 2790)."
    DEFVAL      { '0000000000000000'H } 
    ::= { xcmCommsEngineExtEntry 6 }
--
--
xcmCommsEngineExtMgmtIndex OBJECT-TYPE
    SYNTAX      Cardinal32
    MAX-ACCESS  read-only
    STATUS      current
    DESCRIPTION
        "The value of 'xcmCommsMgmtIndex' corresponding to a directly
        associated conceptual row in the 'xcmCommsMgmtTable', or zero
        if this 'managed entity' does NOT require such information."
    DEFVAL      { 0 }                   
    ::= { xcmCommsEngineExtEntry 7 }
--
--
xcmCommsEngineExtOwnerOID OBJECT-TYPE
    SYNTAX      OBJECT IDENTIFIER
    MAX-ACCESS  read-only
    STATUS      current
    DESCRIPTION
        "The OID (object identifier) of the conceptual row or simple
        object which represents some 'owner entity' associated with
        this entry in the 'xcmCommsEngineExtTable'."
    DEFVAL      { zeroDotZero }   
    ::= { xcmCommsEngineExtEntry 8 }
--
--
xcmCommsStack           OBJECT IDENTIFIER ::= { xcmCommsEngineMIB 5 }
xcmCommsStackTable OBJECT-TYPE
    SYNTAX      SEQUENCE OF XcmCommsStackEntry
    MAX-ACCESS  not-accessible
    STATUS      current
    DESCRIPTION
        "A table containing information on the relationships between
        the multiple stack layers or sublayers (ie, protocol entities)
        comprising the (possibly) running 'protocol stacks' on this host
        system.  In particular, it contains information about which
        stack layer runs 'above' and 'below' which other stack layer."
    ::= { xcmCommsStack 2 }
xcmCommsStackEntry OBJECT-TYPE
    SYNTAX      XcmCommsStackEntry
    MAX-ACCESS  not-accessible
    STATUS      current
    DESCRIPTION
        "An entry for a stack layer in a protocol stack installed
        and (possibly) running on this host system."
    INDEX       { hrDeviceIndex, xcmCommsStackIndex }
    ::= { xcmCommsStackTable 1 }
XcmCommsStackEntry ::= SEQUENCE {
        xcmCommsStackIndex              Ordinal32,
        xcmCommsStackRowStatus          RowStatus,
        xcmCommsStackTypeOID            OBJECT IDENTIFIER,
        xcmCommsStackName               XcmFixedLocaleDisplayString,
        xcmCommsStackPosition           XcmCommsStackPosition,
        xcmCommsStackLowerStackIndex    Cardinal32,
        xcmCommsStackUpperStackIndex    Cardinal32,
        xcmCommsStackAddressIndex       Cardinal32,
        xcmCommsStackOptionIndex        Cardinal32,
        xcmCommsStackLowerMuxIndex      Cardinal32,
        xcmCommsStackUpperMuxIndex      Cardinal32
    }
--
--
xcmCommsStackIndex OBJECT-TYPE
    SYNTAX      Ordinal32
    MAX-ACCESS  not-accessible
    STATUS      current
    DESCRIPTION
        "A unique value used by this host system to identify this
        conceptual row in the 'xcmCommsStackTable'."
    ::= { xcmCommsStackEntry 1 }
xcmCommsStackRowStatus OBJECT-TYPE
    SYNTAX      RowStatus
    MAX-ACCESS  read-only
    STATUS      current
    DESCRIPTION
        "This object is used to create and delete individual conceptual
        rows in the 'xcmCommsStackTable'."
    ::= { xcmCommsStackEntry 2 }
xcmCommsStackTypeOID OBJECT-TYPE
    SYNTAX      OBJECT IDENTIFIER
    MAX-ACCESS  read-only
    STATUS      current
    DESCRIPTION
        "An unambiguous stack layer type,
        used by system administrators and end users to identify
        the type of this stack layer.
        Usage:  Since this unambiguous stack layer type is specified
        as an object identifier, it MAY be taken from any IETF, Xerox,
        third- party, or product-specific MIB, or it MAY simply be any
        IETF SMIv2-style 'autonomous type'.
        Usage:  Suitable values for this unambiguous stack layer type
        are specified in the companion XCMI Comms Config TC (eg,
        'xcmCONetwareIPX')."
    DEFVAL      { zeroDotZero }   
    ::= { xcmCommsStackEntry 3 }
xcmCommsStackName OBJECT-TYPE
    SYNTAX      XcmFixedLocaleDisplayString (SIZE (0..255))
    MAX-ACCESS  read-only
    STATUS      current
    DESCRIPTION
        "Human-readable name, used by system administrators
        and end users to identify this stack layer
        for systems management.
        Usage:  This name SHOULD be the one normally used in a
        command shell for control of this stack layer."
    DEFVAL      { ''H }                 
    ::= { xcmCommsStackEntry 4 }
xcmCommsStackPosition OBJECT-TYPE
    SYNTAX      XcmCommsStackPosition
    MAX-ACCESS  read-only
    STATUS      current
    DESCRIPTION
        "A relatively generic description of the current position of
        this protocol entity (ie, this layer) in this protocol stack.
        Usage:  A conceptual row in 'xcmCommsStackTable', which occupies
        a 'bottom' position in a protocol stack AND has a corresponding
        row in the 'xcmCommsStackXrefTable', SHOULD have valid
        references in 'xcmCommsStackXrefIfIndex' (to IETF MIB-II) and
        'xcmCommsStackXrefHrCommDevIndex' (to IETF Host Resources MIB).
        Usage:  A conceptual row in 'xcmCommsStackTable' which occupies
        a 'lowerMux' and/or an 'upperMux' position in a protocol stack
        SHALL have one (or two) valid corresponding conceptual
        rows in the 'xcmCommsMuxTable', as the conventionally used
        'xcmCommsStack[Lower|Upper]StackIndex' objects take on zero
        values for multiplexors (thus breaking the graph of the stack
        layers, without the use of the 'xcmCommsMuxTable')."
    DEFVAL      { bottom }              
    ::= { xcmCommsStackEntry 5 }
--
--
xcmCommsStackLowerStackIndex OBJECT-TYPE
    SYNTAX      Cardinal32
    MAX-ACCESS  read-only
    STATUS      current
    DESCRIPTION
        "The value of 'xcmCommsStackIndex' corresponding to a next
        lower associated conceptual row in the 'xcmCommsStackTable', or
        zero if this stack layer's position is either 'bottom' or
        'lowerMux'."
    DEFVAL      { 0 }                   
    ::= { xcmCommsStackEntry 6 }
xcmCommsStackUpperStackIndex OBJECT-TYPE
    SYNTAX      Cardinal32
    MAX-ACCESS  read-only
    STATUS      current
    DESCRIPTION
        "The value of 'xcmCommsStackIndex' corresponding to a next
        higher associated conceptual row in the 'xcmCommsStackTable', or
        zero if this stack layer's position is either 'upperMux' or
        sometimes 'top' (see usage note below).
        Usage:  Only for protocol entities whose current purpose is
        either 'layerInterWorkingUnit' (ie, relays or gateways) or
        'systemInterWorkingUnit' (ie, application gateways), it is
        permitted that the stack layer whose current position is 'top'
        have an upper layer index pointing to the peer entity (also in a
        'top' position) which comprises the 'other half' of a relay or
        gateway between two different address domains (ie, an active
        protocol conversion relay) - that is the graphed protocol stack
        is an inverted 'U'."
    DEFVAL      { 0 }                   
    ::= { xcmCommsStackEntry 7 }
xcmCommsStackAddressIndex OBJECT-TYPE
    SYNTAX      Cardinal32
    MAX-ACCESS  read-only
    STATUS      current
    DESCRIPTION
        "The value of 'xcmCommsAddressIndex' corresponding to the first
        associated conceptual row in the 'xcmCommsAddressTable', or zero
        if this 'owner entity' does NOT require such information."
    DEFVAL      { 0 }                   
    ::= { xcmCommsStackEntry 8 }
xcmCommsStackOptionIndex OBJECT-TYPE
    SYNTAX      Cardinal32
    MAX-ACCESS  read-only
    STATUS      current
    DESCRIPTION
        "The value of 'xcmCommsOptionIndex' corresponding to the first
        associated conceptual row in the 'xcmCommsOptionTable', or zero
        if this stack layer does NOT require such information."
    DEFVAL      { 0 }                   
    ::= { xcmCommsStackEntry 9 }
--
--
xcmCommsStackLowerMuxIndex OBJECT-TYPE
    SYNTAX      Cardinal32
    MAX-ACCESS  read-only
    STATUS      current
    DESCRIPTION
        "The value of 'xcmCommsMuxIndex' corresponding to the first
        associated conceptual row in the 'xcmCommsMuxTable', or zero
        if this stack layer's position is NOT 'lowerMux'."
    DEFVAL      { 0 }                   
    ::= { xcmCommsStackEntry 10 }
xcmCommsStackUpperMuxIndex OBJECT-TYPE
    SYNTAX      Cardinal32
    MAX-ACCESS  read-only
    STATUS      current
    DESCRIPTION
        "The value of 'xcmCommsMuxIndex' corresponding to the first
        associated conceptual row in the 'xcmCommsMuxTable', or zero
        if this stack layer's position is NOT 'upperMux'."
    DEFVAL      { 0 }                   
    ::= { xcmCommsStackEntry 11 }
--
--
xcmCommsStackExt        OBJECT IDENTIFIER ::= { xcmCommsEngineMIB 6 }
xcmCommsStackExtTable OBJECT-TYPE
    SYNTAX      SEQUENCE OF XcmCommsStackExtEntry
    MAX-ACCESS  not-accessible
    STATUS      current
    DESCRIPTION
        "A 'sparse' table which augments 'xcmCommsStackTable' with
        additional useful information."
    ::= { xcmCommsStackExt 2 }
xcmCommsStackExtEntry OBJECT-TYPE
    SYNTAX      XcmCommsStackExtEntry
    MAX-ACCESS  not-accessible
    STATUS      current
    DESCRIPTION
        "A 'sparse' entry which augments 'xcmCommsStackEntry' with
        additional useful information."
    INDEX       { hrDeviceIndex, xcmCommsStackIndex }
    ::= { xcmCommsStackExtTable 1 }
XcmCommsStackExtEntry ::= SEQUENCE {
        xcmCommsStackExtRowStatus       RowStatus,
        xcmCommsStackExtState           XcmCommsMgmtState,
        xcmCommsStackExtConditions      XcmCommsMgmtConditions,
        xcmCommsStackExtPurpose         XcmCommsStackExtPurpose,
        xcmCommsStackExtRole            XcmCommsStackExtRole,
        xcmCommsStackExtSuite           XcmCommsStackExtSuite,
        xcmCommsStackExtSuiteVersion    XcmCommsStackExtSuiteVersion,
        xcmCommsStackExtLayer           XcmCommsStackExtLayer,
        xcmCommsStackExtProtocol        XcmCommsStackExtProtocol,
        xcmCommsStackExtMgmtIndex       Cardinal32,
        xcmCommsStackExtOwnerOID        OBJECT IDENTIFIER
    }
--
--
xcmCommsStackExtRowStatus OBJECT-TYPE
    SYNTAX      RowStatus
    MAX-ACCESS  read-only
    STATUS      current
    DESCRIPTION
        "This object is used to create and delete individual conceptual
        rows in the 'xcmCommsStackExtTable'."
    ::= { xcmCommsStackExtEntry 1 }
xcmCommsStackExtState OBJECT-TYPE
    SYNTAX      XcmCommsMgmtState
    MAX-ACCESS  read-only
    STATUS      current
    DESCRIPTION
        "A relatively generic description of the current state of
        this communications entity."
    DEFVAL      { inoperative }         
    ::= { xcmCommsStackExtEntry 2 }
xcmCommsStackExtConditions OBJECT-TYPE
    SYNTAX      XcmCommsMgmtConditions
    MAX-ACCESS  read-only
    STATUS      current
    DESCRIPTION
        "A relatively generic description of the current conditions of
        this communications entity."
    DEFVAL      { 0 }                   
    ::= { xcmCommsStackExtEntry 3 }
xcmCommsStackExtPurpose OBJECT-TYPE
    SYNTAX      XcmCommsStackExtPurpose
    MAX-ACCESS  read-only
    STATUS      current
    DESCRIPTION
        "A relatively generic description of the current purpose of
        this stack layer during normal operation."
    DEFVAL      { unknown }             
    ::= { xcmCommsStackExtEntry 4 }
xcmCommsStackExtRole OBJECT-TYPE
    SYNTAX      XcmCommsStackExtRole
    MAX-ACCESS  read-only
    STATUS      current
    DESCRIPTION
        "A relatively generic description of the current role of
        this stack layer during normal operation."
    DEFVAL      { unknown }             
    ::= { xcmCommsStackExtEntry 5 }
xcmCommsStackExtSuite OBJECT-TYPE
    SYNTAX      XcmCommsStackExtSuite
    MAX-ACCESS  read-only
    STATUS      current
    DESCRIPTION
        "The current protocol suite of this protocol entity
        (stack layer or sublayer)."
    DEFVAL      { unknown }             
    ::= { xcmCommsStackExtEntry 6 }
xcmCommsStackExtSuiteVersion OBJECT-TYPE
    SYNTAX      XcmCommsStackExtSuiteVersion
    MAX-ACCESS  read-only
    STATUS      current
    DESCRIPTION
        "The current protocol suite version of this protocol entity
        (stack layer or sublayer)."
    DEFVAL      { unknown }             
    ::= { xcmCommsStackExtEntry 7 }
xcmCommsStackExtLayer OBJECT-TYPE
    SYNTAX      XcmCommsStackExtLayer
    MAX-ACCESS  read-only
    STATUS      current
    DESCRIPTION
        "The closest approximate layer in the OSI Reference Model
        (CCITT X.200 | ISO 7498) to the current behavior
        of this stack layer or sublayer."
    DEFVAL      { unknown }             
    ::= { xcmCommsStackExtEntry 8 }
xcmCommsStackExtProtocol OBJECT-TYPE
    SYNTAX      XcmCommsStackExtProtocol
    MAX-ACCESS  read-only
    STATUS      current
    DESCRIPTION
        "The specific protocol (within a given protocol suite) currently
        configured for this stack layer or sublayer."
    DEFVAL      { unknown }             
    ::= { xcmCommsStackExtEntry 9 }
--
--
xcmCommsStackExtMgmtIndex OBJECT-TYPE
    SYNTAX      Cardinal32
    MAX-ACCESS  read-only
    STATUS      current
    DESCRIPTION
        "The value of 'xcmCommsMgmtIndex' corresponding to the directly
        associated conceptual row in the 'xcmCommsMgmtTable', or zero
        if this 'managed entity' does NOT require such information."
    DEFVAL      { 0 }                   
    ::= { xcmCommsStackExtEntry 10 }
--
--
xcmCommsStackExtOwnerOID OBJECT-TYPE
    SYNTAX      OBJECT IDENTIFIER
    MAX-ACCESS  read-only
    STATUS      current
    DESCRIPTION
        "The OID (object identifier) of the conceptual row or simple
        object which represents some 'owner entity' associated with
        this entry in the 'xcmCommsStackExtTable'.
        Usage:  A Printer Channel, for example, might choose to specify
        the OID of some conceptual row in the 'prtChannelTable'."
    REFERENCE
        "See:   'prtChannelTable' in Printer MIB (RFC 1759)"
    DEFVAL      { zeroDotZero }   
    ::= { xcmCommsStackExtEntry 11 }
--
--
xcmCommsStackXref       OBJECT IDENTIFIER ::= { xcmCommsEngineMIB 7 }
xcmCommsStackXrefTable OBJECT-TYPE
    SYNTAX      SEQUENCE OF XcmCommsStackXrefEntry
    MAX-ACCESS  not-accessible
    STATUS      current
    DESCRIPTION
        "A table containing optional cross reference information for
        the multiple stack layers or sublayers (ie, protocol entities)
        comprising the (possibly) running 'protocol stacks' on this host
        system."
    ::= { xcmCommsStackXref 2 }
xcmCommsStackXrefEntry OBJECT-TYPE
    SYNTAX      XcmCommsStackXrefEntry
    MAX-ACCESS  not-accessible
    STATUS      current
    DESCRIPTION
        "An entry for a stack layer in a protocol stack installed
        and (possibly) running on this host system."
    INDEX       { hrDeviceIndex, xcmCommsStackIndex }
    ::= { xcmCommsStackXrefTable 1 }
XcmCommsStackXrefEntry ::= SEQUENCE {
        xcmCommsStackXrefRowStatus      RowStatus,
        xcmCommsStackXrefLayerMgmtIndex Cardinal32,
        xcmCommsStackXrefLayerSecIndex  Cardinal32,
        xcmCommsStackXrefLayerIWUIndex  Cardinal32,
        xcmCommsStackXrefHrSWRunIndex   Cardinal32,
        xcmCommsStackXrefHrSWInsIndex   Cardinal32,
        xcmCommsStackXrefIfIndex        Cardinal32,
        xcmCommsStackXrefHrCommDevIndex Cardinal32
    }
--
--
xcmCommsStackXrefRowStatus OBJECT-TYPE
    SYNTAX      RowStatus
    MAX-ACCESS  read-only
    STATUS      current
    DESCRIPTION
        "This object is used to create and delete individual conceptual
        rows in the 'xcmCommsStackXrefTable'."
    ::= { xcmCommsStackXrefEntry 1 }
--
--
xcmCommsStackXrefLayerMgmtIndex OBJECT-TYPE
    SYNTAX      Cardinal32
    MAX-ACCESS  read-only
    STATUS      current
    DESCRIPTION
        "The value of 'xcmCommsStackIndex' corresponding to the
        one-to-one associated conceptual row in the 'xcmCommsStackTable'
        which has 'xcmCommsStackExtPurpose' of 'layerManagement',
        or zero if this this stack layer has no associated layer
        management entity."
    DEFVAL      { 0 }                   
    ::= { xcmCommsStackXrefEntry 2 }
xcmCommsStackXrefLayerSecIndex OBJECT-TYPE
    SYNTAX      Cardinal32
    MAX-ACCESS  read-only
    STATUS      current
    DESCRIPTION
        "The value of 'xcmCommsStackIndex' corresponding to the
        one-to-one associated conceptual row in the 'xcmCommsStackTable'
        which has 'xcmCommsStackExtPurpose' of 'layerSecurity',
        or zero if this this stack layer has no associated layer
        security entity."
    DEFVAL      { 0 }                   
    ::= { xcmCommsStackXrefEntry 3 }
xcmCommsStackXrefLayerIWUIndex OBJECT-TYPE
    SYNTAX      Cardinal32
    MAX-ACCESS  read-only
    STATUS      current
    DESCRIPTION
        "The value of 'xcmCommsStackIndex' corresponding to the
        one-to-one associated conceptual row in the 'xcmCommsStackTable'
        which has 'xcmCommsStackExtPurpose' of 'layerInterWorkingUnit',
        or zero if this this stack layer has no associated layer
        relay entity."
    DEFVAL      { 0 }                   
    ::= { xcmCommsStackXrefEntry 4 }
xcmCommsStackXrefHrSWRunIndex OBJECT-TYPE
    SYNTAX      Cardinal32
    MAX-ACCESS  read-only
    STATUS      current
    DESCRIPTION
        "The value of 'hrSWRunIndex' corresponding to the directly
        associated conceptual row in the 'hrSWRunTable' of the
        Host Resources MIB (RFC 2790), or zero if 'hrSWRunTable'
        is NOT implemented."
    DEFVAL      { 0 }                   
    ::= { xcmCommsStackXrefEntry 5 }
xcmCommsStackXrefHrSWInsIndex OBJECT-TYPE
    SYNTAX      Cardinal32
    MAX-ACCESS  read-only
    STATUS      current
    DESCRIPTION
        "The value of 'hrSWInstalledIndex' corresponding to the directly
        associated conceptual row in the 'hrSWInstalledTable' of the
        Host Resources MIB (RFC 2790), or zero if 'hrSWInstalledTable'
        is NOT implemented."
    DEFVAL      { 0 }                   
    ::= { xcmCommsStackXrefEntry 6 }
--
--
xcmCommsStackXrefIfIndex OBJECT-TYPE
    SYNTAX      Cardinal32
    MAX-ACCESS  read-only
    STATUS      current
    DESCRIPTION
        "The value of 'ifIndex' corresponding to the directly
        associated conceptual row in the 'ifTable' (Interfaces Group)
        of the MIB-II (RFC 1213), or zero if the position of this
        stack layer is NOT 'bottom' (ie, this stack layer does NOT
        represent a physical 'network interface').
        Usage:  This is partially a convenience object, since given the
        value of 'hrDeviceIndex' for an 'hrDeviceNetwork' type device,
        the corresponding 'ifIndex' is found in the mandatory entry in
        the 'hrNetworkTable'.  However, note that for 'hrDeviceModem',
        'hrDeviceSerialPort', and 'hrDeviceParallelPort' devices, the
        'xcmCommsStackXrefIfIndex' object is a NECESSITY for support of
        this communications engine MIB."
    REFERENCE
        "See:   'xcmCommsStackPosition' and the 'InterfaceIndex'
        textual convention in Evolution of the Interfaces Group of
        MIB-II (RFC 1573)."
    DEFVAL      { 0 }                   
    ::= { xcmCommsStackXrefEntry 7 }
xcmCommsStackXrefHrCommDevIndex OBJECT-TYPE
    SYNTAX      Cardinal32
    MAX-ACCESS  read-only
    STATUS      current
    DESCRIPTION
        "The value of 'hrDeviceIndex' corresponding to the directly
        associated conceptual rows in the 'hrDeviceTable' and (possibly)
        'hrNetworkTable' of the Host Resources MIB (RFC 2790), or zero
        if the position of this stack layer is NOT 'bottom' (ie, this
        stack layer does NOT represent a physical 'network interface').
        Usage:  Note that for 'hrDeviceModem', 'hrDeviceSerialPort', and
        'hrDeviceParallelPort' devices, there is NO corresponding entry
        in the 'hrNetworkTable', a subtle difference between MIB-II (RFC
        1213) and the Host Resources MIB (RFC 2790)."
    REFERENCE
        "See:   'xcmCommsStackPosition' and the 'hrDeviceIndex'
        of the Devices Group of the Host Resources MIB (RFC 2790)."
    DEFVAL      { 0 }                   
    ::= { xcmCommsStackXrefEntry 8 }
--
--
xcmCommsMux             OBJECT IDENTIFIER ::= { xcmCommsEngineMIB 8 }
xcmCommsMuxTable OBJECT-TYPE
    SYNTAX      SEQUENCE OF XcmCommsMuxEntry
    MAX-ACCESS  not-accessible
    STATUS      current
    DESCRIPTION
        "A table containing information on the relationships between
        the multiple stack layers or sublayers (ie, protocol entities)
        participating in a 'upper' or 'lower' multiplexor (ie, the
        simultaneous adjacency of two or more 'upper' or 'lower'
        stack layers with a single instance of a 'base' stack layer),
        eg, IP (a 'base' stack layer) operating below both TCP and UDP
        (the 'adjacent' stack layers)."
    ::= { xcmCommsMux 2 }
xcmCommsMuxEntry OBJECT-TYPE
    SYNTAX      XcmCommsMuxEntry
    MAX-ACCESS  not-accessible
    STATUS      current
    DESCRIPTION
        "An entry for a 'base' stack layer participating in an 'upper'
        or 'lower' multiplexor."
    INDEX       { hrDeviceIndex, xcmCommsMuxIndex }
    ::= { xcmCommsMuxTable 1 }
XcmCommsMuxEntry ::= SEQUENCE {
        xcmCommsMuxIndex                Ordinal32,
        xcmCommsMuxRowStatus            RowStatus,
        xcmCommsMuxNextIndex            Cardinal32,
        xcmCommsMuxPreviousIndex        Cardinal32,
        xcmCommsMuxOptionIndex          Cardinal32,
        xcmCommsMuxBaseStackIndex       Ordinal32,
        xcmCommsMuxAdjacentStackIndex   Ordinal32
    }
--
--
xcmCommsMuxIndex OBJECT-TYPE
    SYNTAX      Ordinal32
    MAX-ACCESS  not-accessible
    STATUS      current
    DESCRIPTION
        "A unique value used by this host system to identify this
        conceptual row in the 'xcmCommsMuxTable'."
    ::= { xcmCommsMuxEntry 1 }
xcmCommsMuxRowStatus OBJECT-TYPE
    SYNTAX      RowStatus
    MAX-ACCESS  read-only
    STATUS      current
    DESCRIPTION
        "This object is used to create and delete individual conceptual
        rows in the 'xcmCommsMuxTable'."
    ::= { xcmCommsMuxEntry 2 }
--
--
xcmCommsMuxNextIndex OBJECT-TYPE
    SYNTAX      Cardinal32
    MAX-ACCESS  read-only
    STATUS      current
    DESCRIPTION
        "The value of 'xcmCommsMuxIndex' corresponding to a next
        associated conceptual row in the 'xcmCommsMuxTable', or zero
        if this is the last associated conceptual row in a given set."
    DEFVAL      { 0 }                   
    ::= { xcmCommsMuxEntry 3 }
xcmCommsMuxPreviousIndex OBJECT-TYPE
    SYNTAX      Cardinal32
    MAX-ACCESS  read-only
    STATUS      current
    DESCRIPTION
        "The value of 'xcmCommsMuxIndex' corresponding to a previous
        associated conceptual row in the 'xcmCommsMuxTable', or zero
        if this is the first associated conceptual row in a given set."
    DEFVAL      { 0 }                   
    ::= { xcmCommsMuxEntry 4 }
xcmCommsMuxOptionIndex OBJECT-TYPE
    SYNTAX      Cardinal32
    MAX-ACCESS  read-only
    STATUS      current
    DESCRIPTION
        "The value of 'xcmCommsOptionIndex' corresponding to the first
        associated conceptual row in the 'xcmCommsOptionTable', or zero
        if this multiplexor entry does NOT require such information."
    DEFVAL      { 0 }                   
    ::= { xcmCommsMuxEntry 5 }
--
--
xcmCommsMuxBaseStackIndex OBJECT-TYPE
    SYNTAX      Ordinal32
    MAX-ACCESS  read-only
    STATUS      current
    DESCRIPTION
        "The value of 'xcmCommsStackIndex' corresponding to the base
        associated conceptual row in the 'xcmCommsStackTable'."
    ::= { xcmCommsMuxEntry 6 }
xcmCommsMuxAdjacentStackIndex OBJECT-TYPE
    SYNTAX      Ordinal32
    MAX-ACCESS  read-only
    STATUS      current
    DESCRIPTION
        "The value of 'xcmCommsStackIndex' corresponding to the adjacent
        associated conceptual row in the 'xcmCommsStackTable'."
    ::= { xcmCommsMuxEntry 7 }
--
--
xcmCommsMuxExt          OBJECT IDENTIFIER ::= { xcmCommsEngineMIB 9 }
xcmCommsMuxExtTable OBJECT-TYPE
    SYNTAX      SEQUENCE OF XcmCommsMuxExtEntry
    MAX-ACCESS  not-accessible
    STATUS      current
    DESCRIPTION
        "A 'sparse' table which augments 'xcmCommsMuxTable' with
        additional useful information."
    ::= { xcmCommsMuxExt 2 }
xcmCommsMuxExtEntry OBJECT-TYPE
    SYNTAX      XcmCommsMuxExtEntry
    MAX-ACCESS  not-accessible
    STATUS      current
    DESCRIPTION
        "A 'sparse' entry which augments 'xcmCommsMuxEntry' with
        additional useful information."
    INDEX       { hrDeviceIndex, xcmCommsMuxIndex }
    ::= { xcmCommsMuxExtTable 1 }
XcmCommsMuxExtEntry ::= SEQUENCE {
        xcmCommsMuxExtRowStatus         RowStatus,
        xcmCommsMuxExtState             XcmCommsMgmtState,
        xcmCommsMuxExtConditions        XcmCommsMgmtConditions,
        xcmCommsMuxExtMgmtIndex         Cardinal32,
        xcmCommsMuxExtAddressIndex      Cardinal32,
        xcmCommsMuxExtOwnerOID          OBJECT IDENTIFIER
    }
--
--
xcmCommsMuxExtRowStatus OBJECT-TYPE
    SYNTAX      RowStatus
    MAX-ACCESS  read-only
    STATUS      current
    DESCRIPTION
        "This object is used to create and delete individual conceptual
        rows in the 'xcmCommsMuxExtTable'."
    ::= { xcmCommsMuxExtEntry 1 }
xcmCommsMuxExtState OBJECT-TYPE
    SYNTAX      XcmCommsMgmtState
    MAX-ACCESS  read-only
    STATUS      current
    DESCRIPTION
        "A relatively generic description of the current state of
        this communications entity."
    DEFVAL      { inoperative }         
    ::= { xcmCommsMuxExtEntry 2 }
xcmCommsMuxExtConditions OBJECT-TYPE
    SYNTAX      XcmCommsMgmtConditions
    MAX-ACCESS  read-only
    STATUS      current
    DESCRIPTION
        "A relatively generic description of the current conditions of
        this communications entity."
    DEFVAL      { 0 }                   
    ::= { xcmCommsMuxExtEntry 3 }
--
--
xcmCommsMuxExtMgmtIndex OBJECT-TYPE
    SYNTAX      Cardinal32
    MAX-ACCESS  read-only
    STATUS      current
    DESCRIPTION
        "The value of 'xcmCommsMgmtIndex' corresponding to the directly
        associated conceptual row in the 'xcmCommsMgmtTable', or zero
        if this 'managed entity' does NOT require such information."
    DEFVAL      { 0 }                   
    ::= { xcmCommsMuxExtEntry 4 }
xcmCommsMuxExtAddressIndex OBJECT-TYPE
    SYNTAX      Cardinal32
    MAX-ACCESS  read-only
    STATUS      current
    DESCRIPTION
        "The value of 'xcmCommsAddressIndex' corresponding to the first
        associated conceptual row in the 'xcmCommsAddressTable', or zero
        if this 'owner entity' does NOT require such information."
    DEFVAL      { ''H }                 
    ::= { xcmCommsMuxExtEntry 5 }
--
--
xcmCommsMuxExtOwnerOID OBJECT-TYPE
    SYNTAX      OBJECT IDENTIFIER
    MAX-ACCESS  read-only
    STATUS      current
    DESCRIPTION
        "The OID (object identifier) of the conceptual row or simple
        object which represents some 'owner entity' associated with
        this entry in the 'xcmCommsMuxExtTable'."
    DEFVAL      { zeroDotZero }   
    ::= { xcmCommsMuxExtEntry 6 }
--
--
xcmCommsAddress         OBJECT IDENTIFIER ::= { xcmCommsEngineMIB 10 }
xcmCommsAddressTable OBJECT-TYPE
    SYNTAX      SEQUENCE OF XcmCommsAddressEntry
    MAX-ACCESS  not-accessible
    STATUS      current
    DESCRIPTION
        "A table containing information on unicast, multicast, and
        broadcast addresses (remote/local) known to this host system."
    ::= { xcmCommsAddress 2 }
xcmCommsAddressEntry OBJECT-TYPE
    SYNTAX      XcmCommsAddressEntry
    MAX-ACCESS  not-accessible
    STATUS      current
    DESCRIPTION
        "An entry containing information on one unicast, multicast, or
        broadcast address (remote/local) known to this host system."
    INDEX       { hrDeviceIndex, xcmCommsAddressIndex }
    ::= { xcmCommsAddressTable 1 }
XcmCommsAddressEntry ::= SEQUENCE {
        xcmCommsAddressIndex            Ordinal32,
        xcmCommsAddressRowStatus        RowStatus,
        xcmCommsAddressTypeOID          OBJECT IDENTIFIER,
        xcmCommsAddressUserRole         Integer32,
        xcmCommsAddressName             XcmFixedLocaleDisplayString,
        xcmCommsAddressCanonical        OCTET STRING,
        xcmCommsAddressNextIndex        Cardinal32,
        xcmCommsAddressPreviousIndex    Cardinal32,
        xcmCommsAddressOptionIndex      Cardinal32
    }
--
--
xcmCommsAddressIndex OBJECT-TYPE
    SYNTAX      Ordinal32
    MAX-ACCESS  not-accessible
    STATUS      current
    DESCRIPTION
        "A unique value used by this host system to identify this
        conceptual row in the 'xcmCommsAddressTable'."
    ::= { xcmCommsAddressEntry 1 }
xcmCommsAddressRowStatus OBJECT-TYPE
    SYNTAX      RowStatus
    MAX-ACCESS  read-create
    STATUS      current
    DESCRIPTION
        "This object is used to create and delete individual conceptual
        rows in the 'xcmCommsAddressTable'."
    ::= { xcmCommsAddressEntry 2 }
xcmCommsAddressTypeOID OBJECT-TYPE
    SYNTAX      OBJECT IDENTIFIER
    MAX-ACCESS  read-create
    STATUS      current
    DESCRIPTION
        "An unambiguous address type,
        used by system administrators and end users to identify
        the type of this address.
        Usage:  Since this unambiguous address type is specified
        as an object identifier, it MAY be taken from any IETF, Xerox,
        third- party, or product-specific MIB, or it MAY simply be any
        IETF SMIv2-style 'autonomous type'.
        Usage:  Suitable values for this unambiguous address type
        are specified in the companion XCMI Comms Config TC (eg,
        'xcmCONetwareIPX')."
    DEFVAL      { zeroDotZero }   
    ::= { xcmCommsAddressEntry 3 }
xcmCommsAddressUserRole OBJECT-TYPE
    SYNTAX      Integer32
    MAX-ACCESS  read-create
    STATUS      current
    DESCRIPTION
        "An unambiguous address user role,
        used by system administrators and end users to identify
        the user role of this address.
        Usage:  This unambiguous address user role is specified by a
        value defined in the textual convention 'XcmSecUserRole' in the
        XCMI Security/AAA TC.
        Usage:  This unambiguous address user role is weakly typed here
        to avoid cyclic compilation dependencies between XCMI MIBs.
        Usage:  A chain of 'xcmCommsAddressEntry' objects MAY be pointed
        to by 'xcmDevHelpCommsAddressIndex' in the Device Help group of
        the XCMI Ext to IETF Host Resources MIB.  In this case, the
        'xcmCommsAddressTypeOID' object MAY contain values such as
        'xcmCOOsiwanPSTNAddress' (analog phone number),
        'xcmCOOsiwanFaxAddress' (fax phone number), etc,
        taken from the XCMI Comms Config TC.
        In this case, the 'xcmCommsAddressUserRole' object MAY be used
        to specify the role of the system admin, system operator, etc
        (whose name is specified by 'xcmCommsAddressName',
        address format is specified by 'xcmCommsAddressTypeOID',
        and actual address is specified by 'xcmCommsAddressCanonical')."
    REFERENCE
        "See:   'XcmSecUserRole' in the XCMI Security/AAA TC.
        See:    'xcmDevHelpCommsAddressIndex' in the
                XCMI Ext to IETF Host Resources MIB."
    ::= { xcmCommsAddressEntry 4 }
xcmCommsAddressName OBJECT-TYPE
    SYNTAX      XcmFixedLocaleDisplayString (SIZE (0..255))
    MAX-ACCESS  read-create
    STATUS      current
    DESCRIPTION
        "Human-readable name, used by system administrators
        and end users to identify this protocol entity.
        Usage:  This name SHOULD be the one normally used in a
        command shell for control of this protocol entity.
        Usage:  When a chain of 'xcmCommsAddressEntry' objects is
        pointed to by 'xcmHrDevHelpCommsAddressIndex' in the Device Help
        group of the XCMI Ext to IETF Host Resources MIB (see the
        'xcmCommsAddressUserRole' object above) special semantics apply.
        In this case, the 'xcmCommsAddressName' object MAY be used
        to specify the name of the system admin, system operator, etc
        (whose role is specified by 'xcmCommsAddressUserRole',
        address format is specified by 'xcmCommsAddressTypeOID',
        and actual address is specified by 'xcmCommsAddressCanonical')."
    DEFVAL      { ''H }                 
    ::= { xcmCommsAddressEntry 5 }
xcmCommsAddressCanonical OBJECT-TYPE
    SYNTAX      OCTET STRING (SIZE (0..255))
    MAX-ACCESS  read-create
    STATUS      current
    DESCRIPTION
        "The current canonical address of this protocol entity."
    ::= { xcmCommsAddressEntry 6 }
--
--
xcmCommsAddressNextIndex OBJECT-TYPE
    SYNTAX      Cardinal32
    MAX-ACCESS  read-create
    STATUS      current
    DESCRIPTION
        "The value of 'xcmCommsAddressIndex' corresponding to a next
        associated conceptual row in the 'xcmCommsAddressTable', or zero
        if this is the last associated conceptual row in a given set.
        Usage:  A locally administered 'directory' MAY be searched
        and/or managed via use of the 'xcmCommsAddressNextIndex'
        and the 'xcmCommsAddressPreviousIndex' objects referenced
        from each base protocol entity (ie, stack layer)."
    DEFVAL      { 0 }                   
    ::= { xcmCommsAddressEntry 7 }
xcmCommsAddressPreviousIndex OBJECT-TYPE
    SYNTAX      Cardinal32
    MAX-ACCESS  read-create
    STATUS      current
    DESCRIPTION
        "The value of 'xcmCommsAddressIndex' corresponding to a previous
        associated conceptual row in the 'xcmCommsAddressTable', or zero
        if this is the first associated conceptual row in a given set."
    DEFVAL      { 0 }                   
    ::= { xcmCommsAddressEntry 8 }
xcmCommsAddressOptionIndex OBJECT-TYPE
    SYNTAX      Cardinal32
    MAX-ACCESS  read-create
    STATUS      current
    DESCRIPTION
        "The value of 'xcmCommsOptionIndex' corresponding to the first
        associated conceptual row in the 'xcmCommsOptionTable', or zero
        if this address entry does NOT require such information."
    DEFVAL      { ''H }                 
    ::= { xcmCommsAddressEntry 9 }
--
--
xcmCommsAddressExt      OBJECT IDENTIFIER ::= { xcmCommsEngineMIB 11 }
xcmCommsAddressExtTable OBJECT-TYPE
    SYNTAX      SEQUENCE OF XcmCommsAddressExtEntry
    MAX-ACCESS  not-accessible
    STATUS      current
    DESCRIPTION
        "A 'sparse' table which augments 'xcmCommsAddressTable' with
        additional useful information."
    ::= { xcmCommsAddressExt 2 }
xcmCommsAddressExtEntry OBJECT-TYPE
    SYNTAX      XcmCommsAddressExtEntry
    MAX-ACCESS  not-accessible
    STATUS      current
    DESCRIPTION
        "A 'sparse' entry which augments 'xcmCommsAddressEntry' with
        additional useful information."
    INDEX       { hrDeviceIndex, xcmCommsAddressIndex }
    ::= { xcmCommsAddressExtTable 1 }
XcmCommsAddressExtEntry ::= SEQUENCE {
        xcmCommsAddressExtRowStatus     RowStatus,
        xcmCommsAddressExtState         XcmCommsMgmtState,
        xcmCommsAddressExtConditions    XcmCommsMgmtConditions,
        xcmCommsAddressExtForm          XcmCommsAddressExtForm,
        xcmCommsAddressExtScope         XcmCommsAddressExtScope,
        xcmCommsAddressExtFanout        XcmCommsAddressExtFanout,
        xcmCommsAddressExtMgmtIndex     Cardinal32,
        xcmCommsAddressExtOwnerOID      OBJECT IDENTIFIER
    }
--
--
xcmCommsAddressExtRowStatus OBJECT-TYPE
    SYNTAX      RowStatus
    MAX-ACCESS  read-create
    STATUS      current
    DESCRIPTION
        "This object is used to create and delete individual conceptual
        rows in the 'xcmCommsAddressExtTable'."
    ::= { xcmCommsAddressExtEntry 1 }
xcmCommsAddressExtState OBJECT-TYPE
    SYNTAX      XcmCommsMgmtState
    MAX-ACCESS  read-only
    STATUS      current
    DESCRIPTION
        "A relatively generic description of the current state of
        this communications entity."
    DEFVAL      { inoperative }         
    ::= { xcmCommsAddressExtEntry 2 }
xcmCommsAddressExtConditions OBJECT-TYPE
    SYNTAX      XcmCommsMgmtConditions
    MAX-ACCESS  read-only
    STATUS      current
    DESCRIPTION
        "A relatively generic description of the current conditions of
        this communications entity."
    DEFVAL      { 0 }                   
    ::= { xcmCommsAddressExtEntry 3 }
xcmCommsAddressExtForm OBJECT-TYPE
    SYNTAX      XcmCommsAddressExtForm
    MAX-ACCESS  read-create
    STATUS      current
    DESCRIPTION
        "The current address form of this protocol entity."
    DEFVAL      { unknown }             
    ::= { xcmCommsAddressExtEntry 4 }
xcmCommsAddressExtScope OBJECT-TYPE
    SYNTAX      XcmCommsAddressExtScope
    MAX-ACCESS  read-create
    STATUS      current
    DESCRIPTION
        "The current address scope of this protocol entity."
    DEFVAL      { unknown }             
    ::= { xcmCommsAddressExtEntry 5 }
xcmCommsAddressExtFanout OBJECT-TYPE
    SYNTAX      XcmCommsAddressExtFanout
    MAX-ACCESS  read-create
    STATUS      current
    DESCRIPTION
        "The current address fan out of this protocol entity."
    DEFVAL      { unknown }             
    ::= { xcmCommsAddressExtEntry 6 }
--
--
xcmCommsAddressExtMgmtIndex OBJECT-TYPE
    SYNTAX      Cardinal32
    MAX-ACCESS  read-create
    STATUS      current
    DESCRIPTION
        "The value of 'xcmCommsMgmtIndex' corresponding to the directly
        associated conceptual row in the 'xcmCommsMgmtTable', or zero
        if this 'managed entity' does NOT require such information."
    DEFVAL      { ''H }                 
    ::= { xcmCommsAddressExtEntry 7 }
--
--
xcmCommsAddressExtOwnerOID OBJECT-TYPE
    SYNTAX      OBJECT IDENTIFIER
    MAX-ACCESS  read-create
    STATUS      current
    DESCRIPTION
        "The OID (object identifier) of the conceptual row or simple
        object which represents some 'owner entity' associated with
        this entry in the 'xcmCommsAddressExtTable'."
    DEFVAL      { zeroDotZero }   
    ::= { xcmCommsAddressExtEntry 8 }
--
--
xcmCommsTraffic         OBJECT IDENTIFIER ::= { xcmCommsEngineMIB 12 }
xcmCommsTrafficTable OBJECT-TYPE
    SYNTAX      SEQUENCE OF XcmCommsTrafficEntry
    MAX-ACCESS  not-accessible
    STATUS      current
    DESCRIPTION
        "A table containing input and output traffic counters for
        stack layers."
    ::= { xcmCommsTraffic 2 }
xcmCommsTrafficEntry OBJECT-TYPE
    SYNTAX      XcmCommsTrafficEntry
    MAX-ACCESS  not-accessible
    STATUS      current
    DESCRIPTION
        "An entry containing input and output traffic counters for
        this stack layer."
    INDEX       { hrDeviceIndex, xcmCommsStackIndex }
    ::= { xcmCommsTrafficTable 1 }
XcmCommsTrafficEntry ::= SEQUENCE {
        xcmCommsTrafficRowStatus        RowStatus,
        xcmCommsTrafficInputUnit        XcmHrDevTrafficUnit,
        xcmCommsTrafficOutputUnit       XcmHrDevTrafficUnit,
        xcmCommsTrafficInputCount       Counter32,
        xcmCommsTrafficOutputCount      Counter32,
        xcmCommsTrafficInputErrors      Counter32,
        xcmCommsTrafficOutputErrors     Counter32
    }
--
--
xcmCommsTrafficRowStatus OBJECT-TYPE
    SYNTAX      RowStatus
    MAX-ACCESS  read-only
    STATUS      current
    DESCRIPTION
        "This object is used to create and delete individual conceptual
        rows in the 'xcmCommsTrafficTable'."
    ::= { xcmCommsTrafficEntry 1 }
xcmCommsTrafficInputUnit OBJECT-TYPE
    SYNTAX      XcmHrDevTrafficUnit
    MAX-ACCESS  read-only
    STATUS      current
    DESCRIPTION
        "A layer input unit, used by system administrators
        and end users of this layer for traffic counters."
    DEFVAL      { unknown }             
    ::= { xcmCommsTrafficEntry 2 }
xcmCommsTrafficOutputUnit OBJECT-TYPE
    SYNTAX      XcmHrDevTrafficUnit
    MAX-ACCESS  read-only
    STATUS      current
    DESCRIPTION
        "A layer output unit, used by system administrators
        and end users of this layer for traffic counters."
    DEFVAL      { unknown }             
    ::= { xcmCommsTrafficEntry 3 }
xcmCommsTrafficInputCount OBJECT-TYPE
    SYNTAX      Counter32
    MAX-ACCESS  read-only
    STATUS      current
    DESCRIPTION
        "A layer input traffic count, used by system administrators
        and end users of this layer.
        Usage:  Although no default value ('DEFVAL' clause) is permitted
        (by IETF SMIv2) for this counter, conforming host systems SHALL
        zero this counter upon conceptual row creation."
    ::= { xcmCommsTrafficEntry 4 }
xcmCommsTrafficOutputCount OBJECT-TYPE
    SYNTAX      Counter32
    MAX-ACCESS  read-only
    STATUS      current
    DESCRIPTION
        "A layer output traffic count, used by system administrators
        and end users of this layer.
        Usage:  Although no default value ('DEFVAL' clause) is permitted
        (by IETF SMIv2) for this counter, conforming host systems SHALL
        zero this counter upon conceptual row creation."
    ::= { xcmCommsTrafficEntry 5 }
xcmCommsTrafficInputErrors OBJECT-TYPE
    SYNTAX      Counter32
    MAX-ACCESS  read-only
    STATUS      current
    DESCRIPTION
        "A layer input errors count, used by system administrators
        and end users of this layer.
        Usage:  Although no default value ('DEFVAL' clause) is permitted
        (by IETF SMIv2) for this counter, conforming host systems SHALL
        zero this counter upon conceptual row creation."
    ::= { xcmCommsTrafficEntry 6 }
xcmCommsTrafficOutputErrors OBJECT-TYPE
    SYNTAX      Counter32
    MAX-ACCESS  read-only
    STATUS      current
    DESCRIPTION
        "A layer output errors count, used by system administrators
        and end users of this layer.
        Usage:  Although no default value ('DEFVAL' clause) is permitted
        (by IETF SMIv2) for this counter, conforming host systems SHALL
        zero this counter upon conceptual row creation."
    ::= { xcmCommsTrafficEntry 7 }
--
--
xcmCommsAccess          OBJECT IDENTIFIER ::= { xcmCommsEngineMIB 13 }
xcmCommsAccessTable OBJECT-TYPE
    SYNTAX      SEQUENCE OF XcmCommsAccessEntry
    MAX-ACCESS  not-accessible
    STATUS      current
    DESCRIPTION
        "A table containing current, high-water mark, and maximum
        permitted values for both connection (or association) and
        message (or datagram) ports at the upper sides (ie, service
        provider interfaces) of stack layers."
    ::= { xcmCommsAccess 2 }
xcmCommsAccessEntry OBJECT-TYPE
    SYNTAX      XcmCommsAccessEntry
    MAX-ACCESS  not-accessible
    STATUS      current
    DESCRIPTION
        "A table containing current, high-water mark, and maximum
        permitted values for both connection (or association) and
        message (or datagram) ports at the upper side (ie, service
        provider interface) of this stack layer."
    INDEX       { hrDeviceIndex, xcmCommsStackIndex }
    ::= { xcmCommsAccessTable 1 }
XcmCommsAccessEntry ::= SEQUENCE {
        xcmCommsAccessRowStatus         RowStatus,
        xcmCommsAccessConnectPorts      Gauge32,
        xcmCommsAccessHighConnectPorts  Gauge32,
        xcmCommsAccessMaxConnectPorts   Cardinal32,
        xcmCommsAccessDatagramPorts     Gauge32,
        xcmCommsAccessHighDatagramPorts Gauge32,
        xcmCommsAccessMaxDatagramPorts  Cardinal32
    }
--
--
xcmCommsAccessRowStatus OBJECT-TYPE
    SYNTAX      RowStatus
    MAX-ACCESS  read-only
    STATUS      current
    DESCRIPTION
        "This object is used to create and delete individual conceptual
        rows in the 'xcmCommsAccessTable'."
    ::= { xcmCommsAccessEntry 1 }
xcmCommsAccessConnectPorts OBJECT-TYPE
    SYNTAX      Gauge32
    MAX-ACCESS  read-only
    STATUS      current
    DESCRIPTION
        "The current number of connection (or association) ports open at
        the upper side (ie, service provider interface) of this layer."
    DEFVAL      { 0 }                   
    ::= { xcmCommsAccessEntry 2 }
xcmCommsAccessHighConnectPorts OBJECT-TYPE
    SYNTAX      Gauge32
    MAX-ACCESS  read-only
    STATUS      current
    DESCRIPTION
        "The highest number of connection (or association) ports open at
        the upper side (ie, service provider interface) of this layer."
    DEFVAL      { 0 }                   
    ::= { xcmCommsAccessEntry 3 }
xcmCommsAccessMaxConnectPorts OBJECT-TYPE
    SYNTAX      Cardinal32
    MAX-ACCESS  read-only
    STATUS      current
    DESCRIPTION
        "The maximum number of connection (or association) ports
        permitted at the upper side (ie, service provider interface)
        of this layer."
    DEFVAL      { 0 }                   
    ::= { xcmCommsAccessEntry 4 }
xcmCommsAccessDatagramPorts OBJECT-TYPE
    SYNTAX      Gauge32
    MAX-ACCESS  read-only
    STATUS      current
    DESCRIPTION
        "The current number of message (or datagram) ports open at
        the upper side (ie, service provider interface) of this layer."
    DEFVAL      { 0 }                   
    ::= { xcmCommsAccessEntry 5 }
xcmCommsAccessHighDatagramPorts OBJECT-TYPE
    SYNTAX      Gauge32
    MAX-ACCESS  read-only
    STATUS      current
    DESCRIPTION
        "The highest number of message (or datagram) ports open at
        the upper side (ie, service provider interface) of this layer."
    DEFVAL      { 0 }                   
    ::= { xcmCommsAccessEntry 6 }
xcmCommsAccessMaxDatagramPorts OBJECT-TYPE
    SYNTAX      Cardinal32
    MAX-ACCESS  read-only
    STATUS      current
    DESCRIPTION
        "The maximum number of message (or datagram) ports permitted at
        the upper side (ie, service provider interface) of this layer."
    DEFVAL      { 0 }                   
    ::= { xcmCommsAccessEntry 7 }
--
--
xcmCommsMgmt            OBJECT IDENTIFIER ::= { xcmCommsEngineMIB 14 }
xcmCommsMgmtTable OBJECT-TYPE
    SYNTAX      SEQUENCE OF XcmCommsMgmtEntry
    MAX-ACCESS  not-accessible
    STATUS      current
    DESCRIPTION
        "A table containing additional management control objects for
        installed and (possibly) active entities on this host system and
        supporting detailed and extensible 'states' and 'conditions'."
    ::= { xcmCommsMgmt 2 }
xcmCommsMgmtEntry OBJECT-TYPE
    SYNTAX      XcmCommsMgmtEntry
    MAX-ACCESS  not-accessible
    STATUS      current
    DESCRIPTION
        "An entry containing additional management control objects for
        installed and (possibly) active entity on this host system and
        supporting detailed and extensible 'states' and 'conditions'."
    INDEX       { hrDeviceIndex, xcmCommsMgmtIndex }
    ::= { xcmCommsMgmtTable 1 }
XcmCommsMgmtEntry ::= SEQUENCE {
        xcmCommsMgmtIndex               Ordinal32,
        xcmCommsMgmtRowStatus           RowStatus,
        xcmCommsMgmtCommandRequest      XcmCommsMgmtCommandRequest,
        xcmCommsMgmtCommandData         XcmCommsMgmtCommandData,
        xcmCommsMgmtCommandStatus       XcmGenSNMPv2ErrorStatus,
        xcmCommsMgmtCommandInProgress   TruthValue
    }
--
--
xcmCommsMgmtIndex OBJECT-TYPE
    SYNTAX      Ordinal32
    MAX-ACCESS  not-accessible
    STATUS      current
    DESCRIPTION
        "A unique value used by this host system to identify this
        conceptual row in the 'xcmCommsMgmtTable'."
    ::= { xcmCommsMgmtEntry 1 }
xcmCommsMgmtRowStatus OBJECT-TYPE
    SYNTAX      RowStatus
    MAX-ACCESS  read-create
    STATUS      current
    DESCRIPTION
        "This object is used to create and delete individual conceptual
        rows in the 'xcmCommsMgmtTable'."
    ::= { xcmCommsMgmtEntry 2 }
xcmCommsMgmtCommandRequest OBJECT-TYPE
    SYNTAX      XcmCommsMgmtCommandRequest
    MAX-ACCESS  read-create
    STATUS      current
    DESCRIPTION
        "The most recent comms management command request
        specified for this conceptual row in the 'xcmCommsMgmtTable'.
        Usage:  Conforming management agents SHALL 'reject' any
        SNMP Set-Request to 'xcmCommsMgmtCommand[Request|Data]'
        while another management operation is already in progress
        (ie, while 'xcmCommsMgmtCommandInProgress' is 'true'),
        with 'badValue' (SNMPv1) or 'inconsistentValue' (SNMPv2/v3).
        Usage:  Conforming management stations SHALL set
        'xcmCommsMgmtCommandRequest' (mgmt operation) and
        'xcmCommsMgmtCommandData' (mgmt arguments)
        SIMULTANEOUSLY (in the same SNMP Set-Request PDU)."
    REFERENCE
        "See:   'xcmCommsMgmtCommand[Data|Status|InProgress]'"
    DEFVAL      { none }                
    ::= { xcmCommsMgmtEntry 3 }
xcmCommsMgmtCommandData OBJECT-TYPE
    SYNTAX      XcmCommsMgmtCommandData (SIZE (0..255))
    MAX-ACCESS  read-create
    STATUS      current
    DESCRIPTION
        "The most recent comms management command data (if any)
        specified for this conceptual row in the 'xcmCommsMgmtTable'.
        Usage:  Conforming management agents SHALL 'reject' any
        SNMP Set-Request to 'xcmCommsMgmtCommand[Request|Data]'
        while another management operation is already in progress
        (ie, while 'xcmCommsMgmtCommandInProgress' is 'true'),
        with 'badValue' (SNMPv1) or 'inconsistentValue' (SNMPv2/v3).
        Usage:  Conforming management stations SHALL set
        'xcmCommsMgmtCommandRequest' (mgmt operation) and
        'xcmCommsMgmtCommandData' (mgmt arguments)
        SIMULTANEOUSLY (in the same SNMP Set-Request PDU).
        Usage:  Conformant implementations MUST encrypt passwords, keys,
        and other security information stored in this string object."
    REFERENCE
        "See:   'xcmCommsMgmtCommand[Request|Status|InProgress]'"
    DEFVAL      { ''H }                 
    ::= { xcmCommsMgmtEntry 4 }
xcmCommsMgmtCommandStatus OBJECT-TYPE
    SYNTAX      XcmGenSNMPv2ErrorStatus
    MAX-ACCESS  read-only
    STATUS      current
    DESCRIPTION
        "The simple comms management error status associated with
        this conceptual row in 'xcmCommsMgmtTable'.
        Usage:  Conforming management agents SHALL set this
        object to the value returned in an SNMP Set-Response PDU when
        a simple comms management operation is 'accepted', ie, when
        'xcmCommsMgmtCommandInProgress' goes from 'false' to 'true'.
        Usage:  Conforming management agents SHALL set this
        object to the value of the completion status of the (possibly
        deferred) simple comms management operation, when
        'xcmCommsMgmtCommandInProgress' goes from 'true' to 'false'."
    REFERENCE
        "See:   'xcmCommsMgmtCommand[Request|Data|InProgress]'"
    ::= { xcmCommsMgmtEntry 5 }
xcmCommsMgmtCommandInProgress OBJECT-TYPE
    SYNTAX      TruthValue
    MAX-ACCESS  read-only
    STATUS      current
    DESCRIPTION
        "The comms management in progress status associated with
        this conceptual row in 'xcmCommsMgmtTable'.
        Usage:  Conforming management agents SHALL 'reject' any
        SNMP Set-Request to 'xcmCommsMgmtCommand[Request|Data]'
        while another management operation is already in progress
        (ie, while 'xcmCommsMgmtCommandInProgress' is 'true'),
        with 'badValue' (SNMPv1) or 'inconsistentValue' (SNMPv2/v3)."
    REFERENCE
        "See:   'xcmCommsMgmtCommand[Request|Data|Status]'"
    DEFVAL      { false }               
    ::= { xcmCommsMgmtEntry 6 }
--
--
xcmCommsEngineMIBConformance
    OBJECT IDENTIFIER ::= { xcmCommsEngineMIB 2 }
xcmCommsEngineMIBGroups
    OBJECT IDENTIFIER ::= { xcmCommsEngineMIBConformance 2 }
--
--
xcmCommsEngineMIBCompliance MODULE-COMPLIANCE
    STATUS      current
    DESCRIPTION
        "The compliance statements for SNMP management agents that
        implement the Comms Engine MIB."
    MODULE 
    MANDATORY-GROUPS {
        xcmCommsEngineGroup
    }
    GROUP       xcmCommsEngineExtGroup
    DESCRIPTION
        "Implementation of this group is optional for all systems."
    GROUP       xcmCommsStackGroup
    DESCRIPTION
        "Implementation of this group is conditionally mandatory, ie,
        mandatory for systems which implement stack layer graphing
        via SNMP."
    GROUP       xcmCommsStackExtGroup
    DESCRIPTION
        "Implementation of this group is optional for all systems."
    GROUP       xcmCommsStackXrefGroup
    DESCRIPTION
        "Implementation of this group is optional for all systems."
    GROUP       xcmCommsMuxGroup
    DESCRIPTION
        "Implementation of this group is conditionally mandatory, ie,
        mandatory for systems which implement stack layer graphing
        via SNMP."
    GROUP       xcmCommsMuxExtGroup
    DESCRIPTION
        "Implementation of this group is optional for all systems."
    GROUP       xcmCommsAddressGroup
    DESCRIPTION
        "Implementation of this group is conditionally mandatory, ie,
        mandatory for systems which implement address directories
        via SNMP."
    GROUP       xcmCommsAddressExtGroup
    DESCRIPTION
        "Implementation of this group is optional for all systems."
    GROUP       xcmCommsTrafficGroup
    DESCRIPTION
        "Implementation of this group is optional for all systems."
    GROUP       xcmCommsAccessGroup
    DESCRIPTION
        "Implementation of this group is optional for all systems."
    GROUP       xcmCommsMgmtGroup
    DESCRIPTION
        "Implementation of this group is optional for all systems."
    OBJECT      xcmCommsEngineRowStatus
    SYNTAX      INTEGER { active(1) }   
    DESCRIPTION
        "It is conformant to implement this object as read-only, and
        only one of the enumerated values for the 'RowStatus' textual
        convention need be supported, specifically:  active(1)."
    OBJECT      xcmCommsEngineName
    SYNTAX      XcmFixedLocaleDisplayString (SIZE (0..32))
    DESCRIPTION
        "It is conformant to implement this object as read-only, and
        only 32 octets maximum string length need be supported."
    OBJECT      xcmCommsEngineExtRowStatus
    SYNTAX      INTEGER { active(1) }   
    DESCRIPTION
        "It is conformant to implement this object as read-only, and
        only one of the enumerated values for the 'RowStatus' textual
        convention need be supported, specifically:  active(1)."
    OBJECT      xcmCommsStackRowStatus
    SYNTAX      INTEGER { active(1) }   
    DESCRIPTION
        "It is conformant to implement this object as read-only, and
        only one of the enumerated values for the 'RowStatus' textual
        convention need be supported, specifically:  active(1)."
    OBJECT      xcmCommsStackName
    SYNTAX      XcmFixedLocaleDisplayString (SIZE (0..32))
    DESCRIPTION
        "It is conformant to implement this object as read-only, and
        only 32 octets maximum string length need be supported."
    OBJECT      xcmCommsStackExtRowStatus
    SYNTAX      INTEGER { active(1) }   
    DESCRIPTION
        "It is conformant to implement this object as read-only, and
        only one of the enumerated values for the 'RowStatus' textual
        convention need be supported, specifically:  active(1)."
    OBJECT      xcmCommsStackXrefRowStatus
    SYNTAX      INTEGER { active(1) }   
    DESCRIPTION
        "It is conformant to implement this object as read-only, and
        only one of the enumerated values for the 'RowStatus' textual
        convention need be supported, specifically:  active(1)."
    OBJECT      xcmCommsMuxRowStatus
    SYNTAX      INTEGER { active(1) }   
    DESCRIPTION
        "It is conformant to implement this object as read-only, and
        only one of the enumerated values for the 'RowStatus' textual
        convention need be supported, specifically:  active(1)."
    OBJECT      xcmCommsMuxExtRowStatus
    SYNTAX      INTEGER { active(1) }   
    DESCRIPTION
        "It is conformant to implement this object as read-only, and
        only one of the enumerated values for the 'RowStatus' textual
        convention need be supported, specifically:  active(1)."
    OBJECT      xcmCommsAddressRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsAddressTypeOID
    MIN-ACCESS  read-only
    DESCRIPTION
        "It is conformant to implement this object as read-only."
    OBJECT      xcmCommsAddressUserRole
    MIN-ACCESS  read-only
    DESCRIPTION
        "It is conformant to implement this object as read-only."
    OBJECT      xcmCommsAddressName
    SYNTAX      XcmFixedLocaleDisplayString (SIZE (0..32))
    MIN-ACCESS  read-only
    DESCRIPTION
        "It is conformant to implement this object as read-only, and
        only 32 octets maximum string length need be supported."
    OBJECT      xcmCommsAddressCanonical
    SYNTAX      OCTET STRING (SIZE (0..32))
    MIN-ACCESS  read-only
    DESCRIPTION
        "It is conformant to implement this object as read-only, and
        only 32 octets maximum string length need be supported."
    OBJECT      xcmCommsAddressNextIndex
    MIN-ACCESS  read-only
    DESCRIPTION
        "It is conformant to implement this object as read-only."
    OBJECT      xcmCommsAddressPreviousIndex
    MIN-ACCESS  read-only
    DESCRIPTION
        "It is conformant to implement this object as read-only."
    OBJECT      xcmCommsAddressOptionIndex
    MIN-ACCESS  read-only
    DESCRIPTION
        "It is conformant to implement this object as read-only."
    OBJECT      xcmCommsAddressExtRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsAddressExtForm
    MIN-ACCESS  read-only
    DESCRIPTION
        "It is conformant to implement this object as read-only."
    OBJECT      xcmCommsAddressExtScope
    MIN-ACCESS  read-only
    DESCRIPTION
        "It is conformant to implement this object as read-only."
    OBJECT      xcmCommsAddressExtFanout
    MIN-ACCESS  read-only
    DESCRIPTION
        "It is conformant to implement this object as read-only."
    OBJECT      xcmCommsAddressExtMgmtIndex
    MIN-ACCESS  read-only
    DESCRIPTION
        "It is conformant to implement this object as read-only."
    OBJECT      xcmCommsAddressExtOwnerOID
    MIN-ACCESS  read-only
    DESCRIPTION
        "It is conformant to implement this object as read-only."
    OBJECT      xcmCommsTrafficRowStatus
    SYNTAX      INTEGER { active(1) }   
    DESCRIPTION
        "It is conformant to implement this object as read-only, and
        only one of the enumerated values for the 'RowStatus' textual
        convention need be supported, specifically:  active(1)."
    OBJECT      xcmCommsAccessRowStatus
    SYNTAX      INTEGER { active(1) }   
    DESCRIPTION
        "It is conformant to implement this object as read-only, and
        only one of the enumerated values for the 'RowStatus' textual
        convention need be supported, specifically:  active(1)."
    OBJECT      xcmCommsMgmtRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsMgmtCommandRequest
    MIN-ACCESS  read-only
    DESCRIPTION
        "It is conformant to implement this object as read-only."
    OBJECT      xcmCommsMgmtCommandData
    SYNTAX      XcmCommsMgmtCommandData (SIZE (0..32))
    MIN-ACCESS  read-only
    DESCRIPTION
        "It is conformant to implement this object as read-only, and
        only 32 octets maximum string length need be supported.
        Usage:  Conformant implementations MUST encrypt passwords, keys,
        and other security information stored in this string object."
    ::= { xcmCommsEngineMIBConformance 3 }
--
--
xcmCommsEngineMIBHelpCompliance MODULE-COMPLIANCE
    STATUS      current
    DESCRIPTION
        "The compliance statements for SNMP management agents that
        implement a subset of the Comms Engine MIB, for the sole purpose
        of supporting extended 'contact' information per device, via
        the Device Help group of the XCMI Ext to Host Resources MIB.
        Usage:  See 'Usage' paragraphs in the DESCRIPTION sub-clauses of
        the following OBJECT clauses for additional usage details."
    MODULE 
    MANDATORY-GROUPS {
        xcmCommsEngineGroup,
        xcmCommsAddressGroup
    }
    GROUP       xcmCommsAddressExtGroup
    DESCRIPTION
        "Implementation of this group is optional for all systems."
    GROUP       xcmCommsMgmtGroup
    DESCRIPTION
        "Implementation of this group is optional for all systems."
    OBJECT      xcmCommsEngineRowStatus
    SYNTAX      INTEGER { active(1) }   
    DESCRIPTION
        "It is conformant to implement this object as read-only, and
        only one of the enumerated values for the 'RowStatus' textual
        convention need be supported, specifically:  active(1)."
    OBJECT      xcmCommsEngineName
    SYNTAX      XcmFixedLocaleDisplayString (SIZE (0..32))
    DESCRIPTION
        "It is conformant to implement this object as read-only, and
        only 32 octets maximum string length need be supported."
    OBJECT      xcmCommsAddressRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsAddressTypeOID
    MIN-ACCESS  read-only
    DESCRIPTION
        "It is conformant to implement this object as read-only.
        Usage:  Suitable values for this unambiguous address type
        are specified in the XCMI Comms Config TC, for use with
        the Device Help group of the XCMI Ext to Host Resources MIB
        (eg, 'xcmCOOsiwanPSTNAddress' - analog phone number)."
    OBJECT      xcmCommsAddressUserRole
    MIN-ACCESS  read-only
    DESCRIPTION
        "It is conformant to implement this object as read-only.
        Usage:  Suitable values for this unambiguous address user role
        are specified in the XCMI Security TC, in the textual convention
        'XcmSecUserRole' (system/technician/end user), for use with
        the Device Help group of the XCMI Ext to Host Resources MIB
        (eg, 'systemSuppliesSource' - device supplies contact info)."
    OBJECT      xcmCommsAddressName
    SYNTAX      XcmFixedLocaleDisplayString (SIZE (0..32))
    MIN-ACCESS  read-only
    DESCRIPTION
        "It is conformant to implement this object as read-only, and
        only 32 octets maximum string length need be supported.
        Usage:  This object SHALL contain the human-readable 'common'
        name of a person (or business entity), eg 'John J Wellingtion',
        and NOT the user 'login' name, eg 'jwellington', for use with
        the Device Help group of the XCMI Ext to Host Resources MIB."
    OBJECT      xcmCommsAddressCanonical
    SYNTAX      OCTET STRING (SIZE (0..32))
    MIN-ACCESS  read-only
    DESCRIPTION
        "It is conformant to implement this object as read-only, and
        only 32 octets maximum string length need be supported.
        Usage:  This object SHALL contain the 'canonical' (standardized)
        form of the electronic (eg, Fax) or hardcopy (eg, postal)
        'address' of the person (or business entity) identified in the
        above 'xcmCommsAddressName' object."
    OBJECT      xcmCommsAddressNextIndex
    MIN-ACCESS  read-only
    DESCRIPTION
        "It is conformant to implement this object as read-only.
        Usage:  This object SHALL contain the index of the next
        extended 'contact' info row in the 'xcmCommsAddressTable', or
        zero, if this is the last row in the set which is currently
        associated with a given managed device, for use with
        the Device Help group of the XCMI Ext to Host Resources MIB."
    OBJECT      xcmCommsAddressPreviousIndex
    MIN-ACCESS  read-only
    DESCRIPTION
        "It is conformant to implement this object as read-only.
        Usage:  This object SHALL contain the index of the previous
        extended 'contact' info row in the 'xcmCommsAddressTable', or
        zero, if this is the first row in the set which is currently
        associated with a given managed device, for use with
        the Device Help group of the XCMI Ext to Host Resources MIB."
    OBJECT      xcmCommsAddressOptionIndex
    MIN-ACCESS  read-only
    DESCRIPTION
        "It is conformant to implement this object as read-only.
        Usage:  This object SHALL contain zero, for use with
        the Device Help group of the XCMI Ext to Host Resources MIB."
    OBJECT      xcmCommsAddressExtRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsAddressExtForm
    MIN-ACCESS  read-only
    DESCRIPTION
        "It is conformant to implement this object as read-only."
    OBJECT      xcmCommsAddressExtScope
    MIN-ACCESS  read-only
    DESCRIPTION
        "It is conformant to implement this object as read-only."
    OBJECT      xcmCommsAddressExtFanout
    MIN-ACCESS  read-only
    DESCRIPTION
        "It is conformant to implement this object as read-only."
    OBJECT      xcmCommsAddressExtMgmtIndex
    MIN-ACCESS  read-only
    DESCRIPTION
        "It is conformant to implement this object as read-only."
    OBJECT      xcmCommsAddressExtOwnerOID
    MIN-ACCESS  read-only
    DESCRIPTION
        "It is conformant to implement this object as read-only."
    OBJECT      xcmCommsMgmtRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsMgmtCommandRequest
    MIN-ACCESS  read-only
    DESCRIPTION
        "It is conformant to implement this object as read-only."
    OBJECT      xcmCommsMgmtCommandData
    SYNTAX      XcmCommsMgmtCommandData (SIZE (0..32))
    MIN-ACCESS  read-only
    DESCRIPTION
        "It is conformant to implement this object as read-only, and
        only 32 octets maximum string length need be supported.
        Usage:  Conformant implementations MUST encrypt passwords, keys,
        and other security information stored in this string object."
    ::= { xcmCommsEngineMIBConformance 4 }
--
--
xcmCommsEngineGroup OBJECT-GROUP
    OBJECTS {
        xcmCommsEngineRowStatus,
        xcmCommsEngineName,
        xcmCommsEngineStackLast,
        xcmCommsEngineMuxLast,
        xcmCommsEngineAddressLast,
        xcmCommsEngineMgmtLast,
        xcmCommsEngineGroupSupport,
        xcmCommsEngineCreateSupport,
        xcmCommsEngineUpdateSupport
    }
    STATUS      current
    DESCRIPTION
        "Comms Engine Group (Comms Engines)."
    ::= { xcmCommsEngineMIBGroups 3 }
xcmCommsEngineExtGroup OBJECT-GROUP
    OBJECTS {
        xcmCommsEngineExtRowStatus,
        xcmCommsEngineExtState,
        xcmCommsEngineExtConditions,
        xcmCommsEngineExtVersionID,
        xcmCommsEngineExtVersionDate,
        xcmCommsEngineExtMgmtIndex,
        xcmCommsEngineExtOwnerOID
    }
    STATUS      current
    DESCRIPTION
        "Comms Engine Ext Group (Comms Engines)."
    ::= { xcmCommsEngineMIBGroups 4 }
xcmCommsStackGroup OBJECT-GROUP
    OBJECTS {
        xcmCommsStackRowStatus,
        xcmCommsStackTypeOID,
        xcmCommsStackName,
        xcmCommsStackPosition,
        xcmCommsStackLowerStackIndex,
        xcmCommsStackUpperStackIndex,
        xcmCommsStackAddressIndex,
        xcmCommsStackOptionIndex,
        xcmCommsStackLowerMuxIndex,
        xcmCommsStackUpperMuxIndex
    }
    STATUS      current
    DESCRIPTION
        "Comms Stack Group (Stack Layers)."
    ::= { xcmCommsEngineMIBGroups 5 }
xcmCommsStackExtGroup OBJECT-GROUP
    OBJECTS {
        xcmCommsStackExtRowStatus,
        xcmCommsStackExtState,
        xcmCommsStackExtConditions,
        xcmCommsStackExtPurpose,
        xcmCommsStackExtRole,
        xcmCommsStackExtSuite,
        xcmCommsStackExtSuiteVersion,
        xcmCommsStackExtLayer,
        xcmCommsStackExtProtocol,
        xcmCommsStackExtMgmtIndex,
        xcmCommsStackExtOwnerOID
    }
    STATUS      current
    DESCRIPTION
        "Comms Stack Ext Group (Stack Layers)."
    ::= { xcmCommsEngineMIBGroups 6 }
xcmCommsStackXrefGroup OBJECT-GROUP
    OBJECTS {
        xcmCommsStackXrefRowStatus,
        xcmCommsStackXrefLayerMgmtIndex,
        xcmCommsStackXrefLayerSecIndex,
        xcmCommsStackXrefLayerIWUIndex,
        xcmCommsStackXrefHrSWRunIndex,
        xcmCommsStackXrefHrSWInsIndex,
        xcmCommsStackXrefIfIndex,
        xcmCommsStackXrefHrCommDevIndex
    }
    STATUS      current
    DESCRIPTION
        "Comms Stack Xref Group (Stack Layers)."
    ::= { xcmCommsEngineMIBGroups 7 }
xcmCommsMuxGroup OBJECT-GROUP
    OBJECTS {
        xcmCommsMuxRowStatus,
        xcmCommsMuxNextIndex,
        xcmCommsMuxPreviousIndex,
        xcmCommsMuxOptionIndex,
        xcmCommsMuxBaseStackIndex,
        xcmCommsMuxAdjacentStackIndex
    }
    STATUS      current
    DESCRIPTION
        "Comms Mux Group (Multiplexors)."
    ::= { xcmCommsEngineMIBGroups 8 }
xcmCommsMuxExtGroup OBJECT-GROUP
    OBJECTS {
        xcmCommsMuxExtRowStatus,
        xcmCommsMuxExtState,
        xcmCommsMuxExtConditions,
        xcmCommsMuxExtMgmtIndex,
        xcmCommsMuxExtAddressIndex,
        xcmCommsMuxExtOwnerOID
    }
    STATUS      current
    DESCRIPTION
        "Comms Mux Ext Group (Multiplexors)."
    ::= { xcmCommsEngineMIBGroups 9 }
xcmCommsAddressGroup OBJECT-GROUP
    OBJECTS {
        xcmCommsAddressRowStatus,
        xcmCommsAddressTypeOID,
        xcmCommsAddressUserRole,
        xcmCommsAddressName,
        xcmCommsAddressCanonical,
        xcmCommsAddressNextIndex,
        xcmCommsAddressPreviousIndex,
        xcmCommsAddressOptionIndex
    }
    STATUS      current
    DESCRIPTION
        "Comms Address Group (Directories)."
    ::= { xcmCommsEngineMIBGroups 10 }
xcmCommsAddressExtGroup OBJECT-GROUP
    OBJECTS {
        xcmCommsAddressExtRowStatus,
        xcmCommsAddressExtState,
        xcmCommsAddressExtConditions,
        xcmCommsAddressExtForm,
        xcmCommsAddressExtScope,
        xcmCommsAddressExtFanout,
        xcmCommsAddressExtMgmtIndex,
        xcmCommsAddressExtOwnerOID
    }
    STATUS      current
    DESCRIPTION
        "Comms Address Ext Group (Directories)."
    ::= { xcmCommsEngineMIBGroups 11 }
xcmCommsTrafficGroup OBJECT-GROUP
    OBJECTS {
        xcmCommsTrafficRowStatus,
        xcmCommsTrafficInputUnit,
        xcmCommsTrafficOutputUnit,
        xcmCommsTrafficInputCount,
        xcmCommsTrafficOutputCount,
        xcmCommsTrafficInputErrors,
        xcmCommsTrafficOutputErrors
    }
    STATUS      current
    DESCRIPTION
        "Comms Traffic Group (Stack Layer Traffic Counters)."
    ::= { xcmCommsEngineMIBGroups 12 }
xcmCommsAccessGroup OBJECT-GROUP
    OBJECTS {
        xcmCommsAccessRowStatus,
        xcmCommsAccessConnectPorts,
        xcmCommsAccessHighConnectPorts,
        xcmCommsAccessMaxConnectPorts,
        xcmCommsAccessDatagramPorts,
        xcmCommsAccessHighDatagramPorts,
        xcmCommsAccessMaxDatagramPorts
    }
    STATUS      current
    DESCRIPTION
        "Comms Access Group (Stack Layer Access Counters)."
    ::= { xcmCommsEngineMIBGroups 13 }
xcmCommsMgmtGroup OBJECT-GROUP
    OBJECTS {
        xcmCommsMgmtRowStatus,
        xcmCommsMgmtCommandRequest,
        xcmCommsMgmtCommandData,
        xcmCommsMgmtCommandStatus,
        xcmCommsMgmtCommandInProgress
    }
    STATUS      current
    DESCRIPTION
        "Comms Mgmt Group (State Management)."
    ::= { xcmCommsEngineMIBGroups 14 }
xcmCommsConfigTC OBJECT-IDENTITY -- MODULE-IDENTITY
    STATUS   current
    DESCRIPTION
        "Version:   6.001.pub
        The TC module for textual conventions, enumerated types, OIDs,
        and other volatile elements of the companion Communications
        Config MIB, which supports active configuration discovery of
        communications end system applications, communications
        intermediate systems, and communications gateways for network
        accessible host systems.
        Copyright (C) 1996-2007 Xerox Corporation. All Rights Reserved."
    ::= { xeroxCommonMIB 63 }
--
--
--
--
--
xcmSnmpNetbiosDomain OBJECT-IDENTITY
    STATUS      current
    DESCRIPTION
        "The SNMP over NetBIOS transport domain.  The corresponding
        transport address is of type 'XcmSnmpNetbiosAddress'."
    ::= { xcmCommsConfigTC 3 }
XcmSnmpNetbiosAddress ::= TEXTUAL-CONVENTION
    STATUS      current
    DESCRIPTION
        "The canonical NetBIOS transport address.  The corresponding
        SNMP over NetBIOS transport domain is 'xcmSnmpNetbiosDomain'.
        The canonical NetBIOS transport address
        (registered as a NetBIOS session layer name via 'AddName'):
            Octets      Contents        Encoding
            ----
              1-12      MAC-address     ASCII hexadecimal (uppercase)
                        [IEEE 802.x]        ('0'-'9', 'A'-'F')
             13-14      XCMI-reserved   ASCII decimal zeros
                        [XCMI future]       ('0' - 0x30)
             15-16      NetBIOS-port    binary network-byte order
                        [XCMI std port]     (high-order byte first)
        "
    SYNTAX  OCTET STRING (SIZE (16))
xcmSnmpIPHostnameDomain OBJECT-IDENTITY
    STATUS      current
    DESCRIPTION
        "The transport domain for SNMP over UDP when 
         using host name instead of IP address.  The corresponding
         transport address is of type 'XcmSnmpIPHostnameAddress'."
    ::= { xcmCommsConfigTC 5 }
XcmSnmpIPHostnameAddress ::= TEXTUAL-CONVENTION
    STATUS      current
    DESCRIPTION
        "The transport address.  The corresponding
        transport domain is 'xcmSnmpIPHostnameDomain'.
            Octets      Contents            Encoding
            ----
              1         Host Name Length    unsigned char 0-255
              2-n       FQDN                
              n+1, n+2  UDP Port                                "
    SYNTAX  OCTET STRING (SIZE (255))
--
--
--
--
XcmCommsConfigGroupSupport ::= TEXTUAL-CONVENTION
    STATUS      current
    DESCRIPTION
        "The terse conformance statement of ALL mandatory, conditionally
        mandatory, and optional XCMI Comms Config MIB object groups
        supported by this management agent implementation (ie, version)
        on this host system, specified in a bit-mask.
        The current set of values (which MAY be extended in the future)
        is given below:
              1 : commsConfigGroup            
              2 : commsOptionGroup            
              4 : commsDirRecordGroup         
              8 : commsDirAttributeGroup      
             16 : commsDirStringGroup         
             32 : commsProtocolGroup          
        Usage:  Conforming management agents SHALL accurately
        report their support for XCMI Comms Config MIB object groups."
    SYNTAX      INTEGER (0..2147483647)  
XcmCommsDirRecordType ::= TEXTUAL-CONVENTION
    STATUS      current
    DESCRIPTION
        "The type of the directory record specified
        in this conceptual row in the 'xcmCommsDirRecordTable'.
        Usage:  Directory records of type 'recordXxxGroup' SHALL
        contain only 'xxxIndex' directory attributes (ie, pointers to
        individual 'recordXxx' directory records)."
    SYNTAX      INTEGER {
        other(1),                       
        unknown(2),                     
        top(10),                        
        recordService(100),             
        recordServiceGroup(101),        
        recordAccount(200),             
        recordAccountGroup(201),        
        recordDepartment(300),          
        recordDepartmentGroup(301),     
        recordMailbox(400),             
        recordMailboxGroup(401),        
        recordResource(500),            
        recordResourceGroup(501),       
        recordSpeedDial(600),           
        recordSpeedDialGroup(601),      
        recordUser(700),                
        recordUserGroup(701),           
        recordButtonDial(800),          
        recordButtonDialGroup(801),     
        recordRepository(900),          
        recordRepositoryGroup(901)      
    }
XcmCommsDirAttributeType ::= TEXTUAL-CONVENTION
    STATUS      current
    DESCRIPTION
        "A directory attribute type, used to identify this
        integer-valued directory attribute, which MAY have a matching
        string-valued directory attribute in 'xcmCommsDirStringTable'.
        Usage:   When directory attribute type indicates integer-valued,
        the value of 'xcmCommsDirAttributeValue' SHALL be the
        actual value of this directory attribute.
        Usage:   When directory attribute type indicates string-valued,
        the value of 'xcmCommsDirAttributeValue' SHALL be zero,
        EXCEPT for a directory attribute type of 'protocolTyped...',
        when the protocol type SHALL be specified as the integer value.
        The actual string-valued attribute SHALL be specified in
        an exactly matching row of 'xcmCommsDirStringTable'.
        Usage:  Matching directory attributes (string-valued)
        SHALL be specified in an exactly matching row of
        'xcmCommsDirStringTable'.  Matching rows have EXACTLY the SAME
        values of 'xcmCommsDirRecordType', 'xcmCommsDirRecordIndex',
        'xcmCommsDirAttributeType', and 'xcmCommsDirAttributeIndex'.
        Usage:  Parallel directory attributes (peers of this one)
        SHALL be specified in parallel (NOT matching) rows of
        'xcmCommsDirAttributeTable' (integer-valued attributes) or
        'xcmCommsDirStringTable' (string-valued attributes).  Parallel
        rows have EXACTLY the SAME values of 'xcmCommsDirRecordType',
        'xcmCommsDirRecordIndex', and 'xcmCommsDirAttributeIndex',
        but MUST have a DIFFERENT value of 'xcmCommsDirAttributeType'.
        Usage:   When directory attribute type is 'protocolTyped...' the
        particular protocol layer SHALL be specified by placing a
        a value from the enumeration 'XcmCommsStackExtProtocol' in
        'xcmCommsDirAttributeValue' for this row."
    REFERENCE
        "See:   'xcmCommsDirAttributeType' in the XCMI Comms Config MIB
                'XcmCommsStackExtProtocol' in the XCMI Comms Engine TC."
    SYNTAX      INTEGER {
        other(1),
        unknown(2),
        --
        parentRecordType(10),           
        parentRecordIndex(11),          
        parentGroupRecordType(12),      
        parentGroupRecordIndex(13),     
        peerRecordType(20),             
        peerRecordIndex(21),            
        peerGroupRecordType(22),        
        peerGroupRecordIndex(23),       
        childRecordType(30),            
        childRecordIndex(31),           
        childGroupRecordType(32),       
        childGroupRecordIndex(33),      
        --
        serviceIndex(100),              
        serviceGroupIndex(101),         
        servicePosixRights(102),        
        servicePosixVerbs(103),         
        serviceType(110),               
        serviceSkill(111),              
        serviceScope(112),              
        servicePhysicalDeviceIndex(120),
        serviceLogicalDeviceIndex(121), 
        serviceExternalDeviceIndex(122),
        serviceSWRunIndex(123),         
        serviceSWInstalledIndex(124),   
        serviceStorageIndex(125),       
        servicePriority(130),           
        serviceLifetimeUsage(140),          
        serviceLifetimeUnitClass(141),      
        serviceLifetimeUnit(142),           
        serviceLifetimeLimit(143),          
        serviceLifetimeErrorCount(144),     
        serviceLifetimeErrorLimit(145),     
        serviceLifetimeWarningCount(146),   
        serviceLifetimeWarningLimit(147),   
        --
        serviceName(150),               
        serviceFullName(151),           
        serviceCode(152),               
        servicePassword(153),           
        servicePasscode(154),           
        serviceAlias(155),              
        serviceLoginDate(156),          
        serviceLogoutDate(157),         
        serviceDescription(160),        
        serviceLocation(161),           
        serviceTypeOID(162),            
        serviceProductID(163),          
        serviceLanguageConfigured(170), 
        serviceLanguageSupported(171),  
        serviceCharsetConfigured(172),  
        serviceCharsetSupported(173),   
        serviceTree(180),               
        serviceContext(181),            
        serviceVolume(182),             
        servicePath(183),               
        --
        accountIndex(200),              
        accountGroupIndex(201),         
        accountPosixRights(202),        
        accountPosixVerbs(203),         
        accountRole(210),               
        accountSkill(211),              
        accountScope(212),              
        accountLifetimeUsage(240),          
        accountLifetimeUnitClass(241),      
        accountLifetimeUnit(242),           
        accountLifetimeLimit(243),          
        accountLifetimeErrorCount(244),     
        accountLifetimeErrorLimit(245),     
        accountLifetimeWarningCount(246),   
        accountLifetimeWarningLimit(247),   
        --
        accountName(250),               
        accountFullName(251),           
        accountCode(252),               
        accountPassword(253),           
        accountPasscode(254),           
        accountAlias(255),              
        accountLoginDate(256),          
        accountLogoutDate(257),         
        accountDescription(260),        
        accountLocation(261),           
        --
        departmentIndex(300),           
        departmentGroupIndex(301),      
        --
        departmentName(350),            
        departmentFullName(351),        
        departmentCode(352),            
        departmentDescription(360),     
        departmentLocation(361),        
        --
        mailboxIndex(400),              
        mailboxGroupIndex(401),         
        --
        mailboxName(450),               
        mailboxFullName(451),           
        mailboxCode(452),               
        mailboxDescription(460),        
        mailboxLocation(461),           
        --
        resourceIndex(500),             
        resourceGroupIndex(501),        
        resourcePosixRights(502),       
        resourcePosixVerbs(503),        
        resourceType(510),              
        resourceSkill(511),             
        resourceScope(512),             
        resourceLifetimeUsage(540),         
        resourceLifetimeUnitClass(541),     
        resourceLifetimeUnit(542),          
        resourceLifetimeLimit(543),         
        resourceLifetimeErrorCount(544),    
        resourceLifetimeErrorLimit(545),    
        resourceLifetimeWarningCount(546),  
        resourceLifetimeWarningLimit(547),  
        --
        resourceName(550),              
        resourceFullName(551),          
        resourceCode(552),              
        resourcePassword(553),          
        resourcePasscode(554),          
        resourceAlias(555),             
        resourceLoginDate(556),         
        resourceLogoutDate(557),        
        resourceDescription(560),       
        resourceLocation(561),          
        --
        speedDialIndex(600),            
        speedDialGroupIndex(601),       
        --
        speedDialName(650),             
        speedDialFullName(651),         
        speedDialCode(652),             
        speedDialDescription(660),      
        speedDialLocation(661),         
        --
        userIndex(700),                 
        userGroupIndex(701),            
        userPosixRights(702),           
        userPosixVerbs(703),            
        userRole(710),                  
        userSkill(711),                 
        userScope(712),                 
        userLifetimeUsage(740),             
        userLifetimeUnitClass(741),         
        userLifetimeUnit(742),              
        userLifetimeLimit(743),             
        userLifetimeErrorCount(744),        
        userLifetimeErrorLimit(745),        
        userLifetimeWarningCount(746),      
        userLifetimeWarningLimit(747),      
        --
        userName(750),                  
        userFullName(751),              
        userCode(752),                  
        userPassword(753),              
        userPasscode(754),              
        userAlias(755),                 
        userLoginDate(756),             
        userLogoutDate(757),            
        userDescription(760),           
        userLocation(761),              
        --
        buttonDialIndex(800),           
        buttonDialGroupIndex(801),      
        --
        buttonDialName(850),            
        buttonDialFullName(851),        
        buttonDialCode(852),            
        buttonDialDescription(860),     
        buttonDialLocation(861),        
        --
        repositoryIndex(900),           
        repositoryGroupIndex(901),      
        repositoryPosixRights(902),     
        repositoryPosixVerbs(903),      
        repositorySkill(911),           
        repositoryScope(912),           
        --
        repositoryName(950),            
        repositoryFullName(951),        
        repositoryCode(952),            
        repositoryPassword(953),        
        repositoryPasscode(954),        
        repositoryAlias(955),           
        repositoryLoginDate(956),       
        repositoryLogoutDate(957),      
        repositoryDescription(960),     
        repositoryLocation(961),        
        --
        --
        protocolType(1000),             
        protocolPurpose(1001),          
        protocolRole(1002),             
        protocolSuite(1003),            
        protocolLayer(1004),            
        protocolDeviceIndex(1010),      
        protocolInterfaceIndex(1011),   
        protocolPriority(1030),         
        protocolConnectorType(1510),    
        protocolConnectorAdaptive(1511),
        protocolSignalType(1512),       
        protocolSignalAdaptive(1513),   
        protocolCableType(1514),        
        protocolCableAdaptive(1515),    
        protocolFrameType(1520),        
        protocolFrameAdaptive(1521),    
        protocolMinFrameSize(1522),     
        protocolMaxFrameSize(1523),     
        protocolSpeed(1530),            
        protocolSpeedAdaptive(1531),    
        protocolMinSpeed(1532),         
        protocolMaxSpeed(1533),         
        protocolBidirectional(1534),    
        protocolDirection(1535),        
        protocolFlowControl(1536),      
        protocolMaxConnections(1537),   
        protocolInputTimeout(1540),     
        protocolInputFlowWindow(1541),  
        protocolInputPrime(1542),       
        protocolMinInputChars(1543),    
        protocolMaxInputChars(1544),    
        protocolOutputTimeout(1550),    
        protocolOutputFlowWindow(1551), 
        protocolOutputPrime(1552),      
        protocolMinOutputChars(1553),   
        protocolMaxOutputChars(1554),   
        protocolMaxRetries(1560),       
        protocolRetryInterval(1561),    
        protocolPollInterval(1562),     
        protocolListen(1570),           
        protocolListenSocket(1571),     
        protocolListenInterval(1572),   
        protocolSpool(1580),            
        protocolMaxSpool(1581),         
        protocolJobTimeout(1582),       
        protocolAutoSwitch(1583),       
        protocolBinaryPS(1584),         
        protocolDefaultPDL(1585),       
        protocolSendStartTime(1590),    
        protocolSendEndTime(1591),      
        protocolReceiveStartTime(1592), 
        protocolReceiveEndTime(1593),   
        protocolSendLineNumber(1600),   
        protocolSendCoverSheet(1601),   
        protocolSendHeader(1602),       
        protocolSendConfirmPrint(1603), 
        protocolSendManual(1604),       
        protocolSendSecurity(1605),     
        protocolSendStoreTime(1606),    
        protocolSendResolution(1610),   
        protocolSendErrorCorrection(1611),      
        protocolReceiveLineNumber(1620),
        protocolReceiveCoverSheet(1621),
        protocolReceiveFooter(1622),    
        protocolReceiveToMemory(1623),  
        protocolReceiveManual(1624),    
        protocolReceiveSecurity(1625),  
        protocolReceiveAutoReduce(1626),
        protocolReceiveOverflow(1627),  
        protocolReceiveCollate(1628),   
        protocolReceiveResolution(1630),
        protocolReceiveErrorCorrection(1631),   
        --
        --
        protocolTypedName(2000),                
        protocolTypedFullName(2001),            
        protocolTypedPassword(2002),            
        protocolTypedHostName(2003),            
        protocolTypedQueueName(2004),           
        protocolTypedServerName(2005),          
        protocolTypedDescription(2006),         
        protocolTypedLocation(2007),            
        protocolTypedAddress(2010),             
        protocolTypedBroadcastAddress(2011),    
        protocolTypedListenAddress(2012),       
        protocolTypedMulticastAddress(2013),    
        protocolTypedConfirmAddress(2014),      
        protocolTypedConfirmURL(2015),          
        protocolTypedAcceptAddress(2020),       
        protocolTypedAcceptSubnet(2021),        
        protocolTypedRejectAddress(2022),       
        protocolTypedRejectSubnet(2023),        
        protocolTypedURC(2030),                 
        protocolTypedURI(2031),                 
        protocolTypedURL(2032),                 
        protocolTypedURN(2033),                 
        protocolTypedDeviceName(2040),          
        reserved(3000)
    }
XcmCommsLDAPAttributeType ::= TEXTUAL-CONVENTION
    STATUS      current
    DESCRIPTION
        "The type of LDAP attribute stored in this communications,
        device, or service detail conceptual row.
        Usage:  Conforming XCMI management stations and agents SHALL
        encode LDAP attributes as UTF-8 strings (like SLPv2, RFC 2608).
        - Integers SHALL be encoded as (signed) decimal strings.
        - Booleans SHALL be encoded as 'true' or 'false' strings.
        - Binary data (e.g., 'userCertificate') SHALL be stored
        in SLPv2 opaque encoding (leading '\FF' and escaped octets)."
    REFERENCE
        "See:   'xcmCOInternetLDAPAttributeStr'
                in XCMI Comms Config TC.
        See:    'systemDirectoryLDAPObjectClass' and
                'systemDirectoryLDAPAttribute' in XCMI Svc Mon TC.
        See:    Section 5 'Service Attributes' in
                Service Location Protocol v2 (RFC 2608).
        See:    Section 9 'Attribute Types' in
                COSINE and Internet X.500 Schema (RFC 1274).
        See:    Section 5 'Attribute Types' in
                Summary of X.500:1996 User Schema for LDAPv3 (RFC 2256).
        See:    Section 9.1 'Attribute Types' in
                Definition of inetOrgPerson LDAP Class (RFC 2798)."
    SYNTAX      INTEGER {
        other(1),
        unknown(2),
        commonName(3),                  
        surname(4),                     
        serialNumber(5),                
        country(6),                     
        city(7),                        
        state(8),                       
        streetAddress(9),               
        org(10),                        
        orgUnit(11),                    
        title(12),                      
        description(13),                
        searchGuide(14),                
        businessCategory(15),           
        postalAddress(16),              
        postalCode(17),                 
        postOfficeBox(18),              
        office(19),                     
        telephoneNumber(20),            
        telexNumber(21),                
        teletexTerminal(22),            
        faxNumber(23),                  
        x121Address(24),                
        isdnNumber(25),                 
        registeredAddress(26),          
        destinationIndicator(27),       
        preferredDeliveryMethod(28),    
        presentationAddress(29),        
        supportedContext(30),           
        member(31),                     
        owner(32),                      
        role(33),                       
        seeAlso(34),                    
        userPassword(35),               
        userCertificate(36),            
        caCertificate(37),              
        authorityRevocationList(38),    
        certificateRevocationList(39),  
        crossCertificatePair(40),       
        name(41),                       
        givenName(42),                  
        initials(43),                   
        generationQualifier(44),        -- generation (e.g., "IInd")
        x500UniqueIdentifier(45),       
        dnQualifier(46),                
        enhancedSearchGuide(47),        
        protocolInformation(48),        
        distinguishedName(49),          
        uniqueMember(50),               
        houseIdentifier(51),            
        supportedAlgorithms(52),        
        deltaRevocationList(53),        
        dmdName(54),                    
        uid(101),                       
        textEncodedORAddress(102),      
        mail(103),                      
        info(104),                      
        favoriteDrink(105),             
        roomNumber(106),                
        photo(107),                     
        userClass(108),                 
        host(109),                      
        manager(110),                   
        documentIdentifier(111),        
        documentTitle(112),             
        documentVersion(113),           
        documentAuthor(114),            
        documentLocation(115),          
        homePhone(116),                 
        secretary(117),                 
        otherMailbox(118),              
        domainComponent(121),           
        associatedDomain(127),          
        associatedName(128),            
        homePostalAddress(129),         
        personalTitle(130),             
        mobile(131),                    
        pager(132),                     
        friendlyCountry(133),           
        uniqueIdentifier(134),          
        orgStatus(135),                 
        buildingName(138),              
        personalSignature(143),         
        audio(145),                     
        documentPublisher(146),         
        carLicense(201),                
        departmentNumber(202),          
        displayName(203),               
        employeeNumber(204),            
        employeeType(205),              
        jpegPhoto(206),                 
        preferredLanguage(207),         
        userSMIMECertificate(208),      
        userPKCS12(209),                
        labeledURI(300)                 
    }
--
--
xcmCOSpecialTypes OBJECT-IDENTITY
    STATUS      current
    DESCRIPTION
        "The root of all special comms option types defined in
        the Comms Config TC."
    ::= { xcmCommsConfigTC 4 }
xcmCOSpecialLabel OBJECT-IDENTITY
    STATUS      current
    DESCRIPTION
        "Human-readable name for the following configuration subtree,
        specified in 'xcmCommsOptionsValueString'.
        Usage:  To label tree vertices (eg, for client GUI)."
    ::= { xcmCOSpecialTypes 1 }
xcmCOSpecialImport OBJECT-IDENTITY
    STATUS      current
    DESCRIPTION
        "The 'xcmCommsOptionIndex' of an 'imported' configuration
        subtree, specified in 'xcmCommsOptionValueInteger'.
        Usage:  To import a section of common config from elsewhere.
        All comms configuration options in the 'imported' subtree SHALL
        be 'imported' and THEN any dependent options found via the
        current 'xcmCommsOptionFamilyIndex' chain SHALL be treated as
        though they logically 'followed' the 'imported' configuration
        subtree.
        Usage:  This row SHALL be logically 're-typed' by inheritance
        from the first imported row (eg, 'xcmCOOsilanEthernet'), but
        ONLY for the 'scoping' of dependent options which are found via
        the current 'xcmCommsOptionFamilyIndex' chain (eg, a dependent
        option for 'xcmCOOsilanEthernetFrameOverride').
        Usage:  The pointer specified in 'xcmCommsOptionValueInteger'
        SHALL be used to evaluate the 'imported' configuration substree
        and THEN any 'local' options SHALL be evaluated from the current
        'xcmCommsOptionFamilyIndex' chain.
        Usage:  As would normally be true of any option, this row SHALL
        NOT affect the 'scoping' of independent options found via the
        current 'xcmCommsOptionNextIndex' chain (eg, the next protocol
        within a given protocol suite configuration subtree)."
    ::= { xcmCOSpecialTypes 2 }
xcmCOSpecialRemark OBJECT-IDENTITY
    STATUS      current
    DESCRIPTION
        "Human-readable remark for the following configuration subtree,
        specified in 'xcmCommsOptionsValueString'.
        Usage:  To comment tree vertices (eg, for client GUI)."
    ::= { xcmCOSpecialTypes 3 }
xcmCOSpecialAddress OBJECT-IDENTITY
    STATUS      current
    DESCRIPTION
        "Human-readable canonical address for the protocol specified in
        'xcmCommsOptionValueOID' (eg, 'xcmCOInternetIP') is specified
        in 'xcmCommsOptionsValueString' (eg, '19.242.128.21').
        Usage:  'Overloads' protocol types to yield protocol addresses."
    ::= { xcmCOSpecialTypes 4 }
xcmCOSpecialState OBJECT-IDENTITY
    STATUS      current
    DESCRIPTION
        "The current state of the communications protocol specified
        in 'xcmCommsOptionValueOID' (eg, 'xcmCOInternetIP') is specified
        in 'xcmCommsOptionsValueInteger' (eg, 'opened(9)').
        Usage:  'Overloads' protocol types to yield protocol entity
        states."
    REFERENCE
        "See:   'XcmCommsMgmtState' in XCMI Comms Engine TC."
    ::= { xcmCOSpecialTypes 5 }
xcmCOSpecialConditions OBJECT-IDENTITY
    STATUS      current
    DESCRIPTION
        "The current conditions of the communications protocol specified
        in 'xcmCommsOptionValueOID' (eg, 'xcmCOInternetIP') is specified
        in 'xcmCommsOptionsValueInteger' (eg, 'openInProgress').
        Usage:  'Overloads' protocol types to yield protocol entity
        conditions."
    REFERENCE
        "See:   'XcmCommsMgmtConditions' in XCMI Comms Engine TC."
    ::= { xcmCOSpecialTypes 6 }
xcmCOSpecialName OBJECT-IDENTITY
    STATUS      current
    DESCRIPTION
        "Human-readable directory name for the directory specified in
        'xcmCommsOptionValueOID' (eg, 'xcmCOInternetDNS') is specified
        in 'xcmCommsOptionsValueString' (eg, 'showstopper.sample.com').
        Usage:  'Overloads' directory types to yield directory names."
    ::= { xcmCOSpecialTypes 7 }
xcmCOSpecialSupportedInteger OBJECT-IDENTITY
    STATUS      current
    DESCRIPTION
        "Integer-encoded supported value for the option specified in
        'xcmCommsOptionValueOID' (eg, 'xcmCOOsilanFrameType') is found
        in 'xcmCommsOptionsValueInteger' (eg, 'mac(3)').
        Usage:  'Overloads' option types to yield options supported."
    ::= { xcmCOSpecialTypes 8 }
xcmCOSpecialSupportedString OBJECT-IDENTITY
    STATUS      current
    DESCRIPTION
        "String-encoded supported value for the option specified in
        'xcmCommsOptionValueOID' (eg, 'xcmCOAppletalkNBPType') is found
        in 'xcmCommsOptionsValueString' (eg, 'LaserPrinter').
        Usage:  'Overloads' option types to yield options supported."
    ::= { xcmCOSpecialTypes 9 }
xcmCOSpecialAcceptAddress OBJECT-IDENTITY
    STATUS      current
    DESCRIPTION
        "Human-readable 'accept' address for the protocol specified in
        'xcmCommsOptionValueOID' (eg, 'xcmCOInternetIP') is specified
        in 'xcmCommsOptionsValueString' (eg, '19.242.128.21').
        Usage:  'Overloads' protocol types to yield protocol specific
        addresses of remote entities at this protocol layer,
        from which incoming datagrams and/or connections SHALL
        be accepted.
        Usage:  Address format is the protocol specific canonical
        format defined for this protocol type as defined elsewhere in
        this XCMI Comms Config TC."
    ::= { xcmCOSpecialTypes 10 }
xcmCOSpecialAcceptSubnet OBJECT-IDENTITY
    STATUS      current
    DESCRIPTION
        "Human-readable 'accept' subnet for the protocol specified in
        'xcmCommsOptionValueOID' (eg, 'xcmCOInternetIP') is specified
        in 'xcmCommsOptionsValueString' (eg, '19.242.255.255' as might
        be specified in an 'xcmCOInternetIPSubnetMask' comms option).
        Usage:  'Overloads' protocol types to yield protocol specific
        subnet masks of remote entities at this protocol layer,
        from which incoming datagrams and/or connections SHALL
        be accepted.
        Usage:  Subnet mask format is the protocol specific canonical
        format defined for this protocol type as defined elsewhere in
        this XCMI Comms Config TC."
    ::= { xcmCOSpecialTypes 11 }
xcmCOSpecialRejectAddress OBJECT-IDENTITY
    STATUS      current
    DESCRIPTION
        "Human-readable 'reject' address for the protocol specified in
        'xcmCommsOptionValueOID' (eg, 'xcmCOInternetIP') is specified
        in 'xcmCommsOptionsValueString' (eg, '19.242.128.21').
        Usage:  'Overloads' protocol types to yield protocol specific
        addresses of remote entities at this protocol layer,
        from which incoming datagrams and/or connections SHALL
        be rejected.
        Usage:  Address format is the protocol specific canonical
        format defined for this protocol type as defined elsewhere in
        this XCMI Comms Config TC."
    ::= { xcmCOSpecialTypes 12 }
xcmCOSpecialRejectSubnet OBJECT-IDENTITY
    STATUS      current
    DESCRIPTION
        "Human-readable 'reject' subnet for the protocol specified in
        'xcmCommsOptionValueOID' (eg, 'xcmCOInternetIP') is specified
        in 'xcmCommsOptionsValueString' (eg, '19.242.255.255' as might
        be specified in an 'xcmCOInternetIPSubnetMask' comms option).
        Usage:  'Overloads' protocol types to yield protocol specific
        subnet masks of remote entities at this protocol layer,
        from which incoming datagrams and/or connections SHALL
        be rejected.
        Usage:  Subnet mask format is the protocol specific canonical
        format defined for this protocol type as defined elsewhere in
        this XCMI Comms Config TC."
    ::= { xcmCOSpecialTypes 13 }
xcmCOSpecialMaxRequestRetries OBJECT-IDENTITY
    STATUS      current
    DESCRIPTION
        "The maximum request retries for the communications protocol
        specified in 'xcmCommsOptionValueOID' (eg, 'xcmCOInternetDNS')
        is specified in 'xcmCommsOptionsValueInteger' (eg, '4' retries).
        Usage:  A value of zero indicates that the request SHALL ONLY be
        attempted once (no retries) before being considered a failure.
        Usage:  'Overloads' protocol types to yield protocol request
        retry limits."
    ::= { xcmCOSpecialTypes 14 }
xcmCOSpecialRequestTimeout OBJECT-IDENTITY
    STATUS      current
    DESCRIPTION
        "The request timeout for the communications protocol
        specified in 'xcmCommsOptionValueOID' (eg, 'xcmCOInternetDNS')
        is specified in 'xcmCommsOptionsValueInteger' (eg, '3' seconds).
        Usage:  A value of zero indicates that the request timeout is a
        local system default (and NOT reported/configured).
        Usage:  'Overloads' protocol types to yield protocol request
        timeout limits."
    ::= { xcmCOSpecialTypes 15 }
xcmCOSpecialSecurity OBJECT-IDENTITY
    STATUS      current
    DESCRIPTION
        "The security protocol (datalink, network, transport layer, etc)
        specified in 'xcmCommsOptionValueOID' (eg, 'xcmCOInternetTLS')
        is enabled and disabled by 'xcmCommsOptionsValueInteger'.
        Usage:  'Overloads' protocol types to configure security for
        datalink, network, transport, and application layer protocols."
    ::= { xcmCOSpecialTypes 16 }
--
--
xcmCOOsilanSuite
    OBJECT IDENTIFIER ::= { xcmCommsConfigTC 11 }
xcmCOOsilanPhysicals
    OBJECT IDENTIFIER ::= { xcmCOOsilanSuite 1100 }
xcmCOOsilanConnectorType        
    OBJECT IDENTIFIER ::= { xcmCOOsilanPhysicals 1 }
xcmCOOsilanConnectorOverride    
    OBJECT IDENTIFIER ::= { xcmCOOsilanConnectorType 1 }
xcmCOOsilanConnectorDetected    
    OBJECT IDENTIFIER ::= { xcmCOOsilanConnectorType 2 }
xcmCOOsilanConnectorAdaptive    
    OBJECT IDENTIFIER ::= { xcmCOOsilanConnectorType 3 }
xcmCOOsilanSignalType           
    OBJECT IDENTIFIER ::= { xcmCOOsilanPhysicals 2 }
    --
    --
    --
    --
    --
    --
    --
    --
xcmCOOsilanSignalOverride       
    OBJECT IDENTIFIER ::= { xcmCOOsilanSignalType 1 }
xcmCOOsilanSignalDetected       
    OBJECT IDENTIFIER ::= { xcmCOOsilanSignalType 2 }
xcmCOOsilanSignalAdaptive       
    OBJECT IDENTIFIER ::= { xcmCOOsilanSignalType 3 }
    -- If true is selected "autodetect" signal type has been selected
xcmCOOsilanSignalSupport        
    OBJECT IDENTIFIER ::= { xcmCOOsilanSignalType 4 }
xcmCOOsilanSignalCapability        
    OBJECT IDENTIFIER ::= { xcmCOOsilanSignalType 5 }
xcmCOOsilanCableType            
    OBJECT IDENTIFIER ::= { xcmCOOsilanPhysicals 3 }
xcmCOOsilanCableOverride        
    OBJECT IDENTIFIER ::= { xcmCOOsilanCableType 1 }
xcmCOOsilanCableDetected        
    OBJECT IDENTIFIER ::= { xcmCOOsilanCableType 2 }
xcmCOOsilanCableAdaptive        
    OBJECT IDENTIFIER ::= { xcmCOOsilanCableType 3 }
xcmCOOsilanCableSupport         
    OBJECT IDENTIFIER ::= { xcmCOOsilanCableType 4 }
xcmCOOsilanDatalinks
    OBJECT IDENTIFIER ::= { xcmCOOsilanSuite 1200 }
xcmCOOsilanFrameType            
    OBJECT IDENTIFIER ::= { xcmCOOsilanSuite 1201 }
xcmCOOsilanFrameOverride        
    OBJECT IDENTIFIER ::= { xcmCOOsilanFrameType 1 }
xcmCOOsilanFrameDetected        
    OBJECT IDENTIFIER ::= { xcmCOOsilanFrameType 2 }
xcmCOOsilanFrameAdaptive        
    OBJECT IDENTIFIER ::= { xcmCOOsilanFrameType 3 }
xcmCOOsilanEthernet             
    OBJECT IDENTIFIER ::= { xcmCOOsilanSuite 1203 }
xcmCOOsilanTokenBus             
    OBJECT IDENTIFIER ::= { xcmCOOsilanSuite 1204 }
xcmCOOsilanTokenRing            
    OBJECT IDENTIFIER ::= { xcmCOOsilanSuite 1205 }
xcmCOOsilanFDDI                 
    OBJECT IDENTIFIER ::= { xcmCOOsilanSuite 1207 }
xcmCOOsilanEthernetType         
    OBJECT IDENTIFIER ::= { xcmCOOsilanEthernet 1 }
xcmCOOsilanEthernetDevice
    OBJECT IDENTIFIER ::= { xcmCOOsilanEthernet 2 }
xcmCOOsilanEthernetDeviceName
    OBJECT IDENTIFIER ::= { xcmCOOsilanEthernetDevice 1 }
xcmCOOsilanEthernetSpeed
    OBJECT IDENTIFIER ::= { xcmCOOsilanEthernet 3 }
xcmCOOsilanEthernetSpeedOverride
    OBJECT IDENTIFIER ::= { xcmCOOsilanEthernetSpeed 1 }
xcmCOOsilanEthernetSpeedDetected
    OBJECT IDENTIFIER ::= { xcmCOOsilanEthernetSpeed 2 }
xcmCOOsilanEthernetSpeedAdaptive
    OBJECT IDENTIFIER ::= { xcmCOOsilanEthernetSpeed 3 }
xcmCOOsilanEthernetSpeedSupport
    OBJECT IDENTIFIER ::= { xcmCOOsilanEthernetSpeed 4 }
xcmCOOsilanEthernetMinSpeed
    OBJECT IDENTIFIER ::= { xcmCOOsilanEthernetSpeed 5 }
xcmCOOsilanEthernetMaxSpeed
    OBJECT IDENTIFIER ::= { xcmCOOsilanEthernetSpeed 6 }
xcmCOOsilanEthernetMaxFrameSize
    OBJECT IDENTIFIER ::= { xcmCOOsilanEthernet 4 }
xcmCOOsilanEthernetInterface
    OBJECT IDENTIFIER ::= { xcmCOOsilanEthernet 5 }
xcmCOOsilanEthernetMACAddress
    OBJECT IDENTIFIER ::= { xcmCOOsilanEthernet 6 }
xcmCOOsilanTokenRingType        
    OBJECT IDENTIFIER ::= { xcmCOOsilanTokenRing 1 }
xcmCOOsilanTokenRingDevice
    OBJECT IDENTIFIER ::= { xcmCOOsilanTokenRing 2 }
xcmCOOsilanTokenRingDeviceName
    OBJECT IDENTIFIER ::= { xcmCOOsilanTokenRingDevice 1 }
xcmCOOsilanTokenRingSpeed
    OBJECT IDENTIFIER ::= { xcmCOOsilanTokenRing 3 }
xcmCOOsilanTokenRingSpeedOverride
    OBJECT IDENTIFIER ::= { xcmCOOsilanTokenRingSpeed 1 }
xcmCOOsilanTokenRingSpeedDetected
    OBJECT IDENTIFIER ::= { xcmCOOsilanTokenRingSpeed 2 }
xcmCOOsilanTokenRingSpeedAdaptive
    OBJECT IDENTIFIER ::= { xcmCOOsilanTokenRingSpeed 3 }
xcmCOOsilanTokenRingSpeedSupport
    OBJECT IDENTIFIER ::= { xcmCOOsilanTokenRingSpeed 4 }
xcmCOOsilanTokenRingMinSpeed
    OBJECT IDENTIFIER ::= { xcmCOOsilanTokenRingSpeed 5 }
xcmCOOsilanTokenRingMaxSpeed
    OBJECT IDENTIFIER ::= { xcmCOOsilanTokenRingSpeed 6 }
xcmCOOsilanTokenRingMaxFrameSize
    OBJECT IDENTIFIER ::= { xcmCOOsilanTokenRing 4 }
xcmCOOsilanTokenRingInterface
    OBJECT IDENTIFIER ::= { xcmCOOsilanTokenRing 5 }
xcmCOOsilanTokenRingMACAddress
    OBJECT IDENTIFIER ::= { xcmCOOsilanTokenRing 6 }
xcmCOOsilanTokenRingSSR         
    OBJECT IDENTIFIER ::= { xcmCOOsilanTokenRing 11 }
xcmCOOsilanTokenRingSSRAllRoute 
    OBJECT IDENTIFIER ::= { xcmCOOsilanTokenRing 12 }
xcmCOOsilanTokenRingSSRSingleRR 
    OBJECT IDENTIFIER ::= { xcmCOOsilanTokenRing 13 }
xcmCOOsilanTokenRingSSRAdaptive 
    OBJECT IDENTIFIER ::= { xcmCOOsilanTokenRing 14 }
xcmCOOsilanTokenRingMACOverride 
    OBJECT IDENTIFIER ::= { xcmCOOsilanTokenRing 21 }
--
--
xcmCOOsiwanSuite
    OBJECT IDENTIFIER ::= { xcmCommsConfigTC 13 }
xcmCOOsiwanPhysicals
    OBJECT IDENTIFIER ::= { xcmCOOsiwanSuite 1100 }
xcmCOOsiwanConnectorType        
    OBJECT IDENTIFIER ::= { xcmCOOsiwanPhysicals 1 }
xcmCOOsiwanConnectorOverride    
    OBJECT IDENTIFIER ::= { xcmCOOsiwanConnectorType 1 }
xcmCOOsiwanConnectorDetected    
    OBJECT IDENTIFIER ::= { xcmCOOsiwanConnectorType 2 }
xcmCOOsiwanConnectorAdaptive    
    OBJECT IDENTIFIER ::= { xcmCOOsiwanConnectorType 3 }
xcmCOOsiwanSignalType           
    OBJECT IDENTIFIER ::= { xcmCOOsiwanPhysicals 2 }
xcmCOOsiwanSignalOverride       
    OBJECT IDENTIFIER ::= { xcmCOOsiwanSignalType 1 }
xcmCOOsiwanSignalDetected       
    OBJECT IDENTIFIER ::= { xcmCOOsiwanSignalType 2 }
xcmCOOsiwanSignalAdaptive       
    OBJECT IDENTIFIER ::= { xcmCOOsiwanSignalType 3 }
xcmCOOsiwanSignalSupport        
    OBJECT IDENTIFIER ::= { xcmCOOsiwanSignalType 4 }
xcmCOOsiwanLineNumber           
    OBJECT IDENTIFIER ::= { xcmCOOsiwanPhysicals 4 }
xcmCOOsiwanSendManual           
    OBJECT IDENTIFIER ::= { xcmCOOsiwanPhysicals 5 }
xcmCOOsiwanReceiveManual        
    OBJECT IDENTIFIER ::= { xcmCOOsiwanPhysicals 6 }
xcmCOOsiwanRingsBeforeAnswer    
    OBJECT IDENTIFIER ::= { xcmCOOsiwanPhysicals 7 }
xcmCOOsiwanErrorCorrection      
    OBJECT IDENTIFIER ::= { xcmCOOsiwanPhysicals 8 }
xcmCOOsiwanDirection            
    OBJECT IDENTIFIER ::= { xcmCOOsiwanPhysicals 9 }
xcmCOOsiwanSendStartTime        
    OBJECT IDENTIFIER ::= { xcmCOOsiwanPhysicals 10 }
xcmCOOsiwanSendEndTime          
    OBJECT IDENTIFIER ::= { xcmCOOsiwanPhysicals 11 }
xcmCOOsiwanReceiveStartTime     
    OBJECT IDENTIFIER ::= { xcmCOOsiwanPhysicals 12 }
xcmCOOsiwanReceiveEndTime       
    OBJECT IDENTIFIER ::= { xcmCOOsiwanPhysicals 13 }
xcmCOOsiwanRingerVolume         
    OBJECT IDENTIFIER ::= { xcmCOOsiwanPhysicals 20 }
xcmCOOsiwanMonitorVolume        
    OBJECT IDENTIFIER ::= { xcmCOOsiwanPhysicals 21 }
xcmCOOsiwanAlarmVolume          
    OBJECT IDENTIFIER ::= { xcmCOOsiwanPhysicals 22 }
xcmCOOsiwanKeyboardVolume       
    OBJECT IDENTIFIER ::= { xcmCOOsiwanPhysicals 23 }
xcmCOOsiwanDatalinks
    OBJECT IDENTIFIER ::= { xcmCOOsiwanSuite 1200 }
xcmCOOsiwanFax                  
    OBJECT IDENTIFIER ::= { xcmCOOsiwanSuite 1241 }
xcmCOOsiwanPSTN                 
    OBJECT IDENTIFIER ::= { xcmCOOsiwanSuite 1251 }
xcmCOOsiwanISDN                 
    OBJECT IDENTIFIER ::= { xcmCOOsiwanSuite 1261 }
xcmCOOsiwanFaxAddress
    OBJECT IDENTIFIER ::= { xcmCOOsiwanFax 1 }
xcmCOOsiwanFaxDevice
    OBJECT IDENTIFIER ::= { xcmCOOsiwanFax 2 }
xcmCOOsiwanFaxDeviceName
    OBJECT IDENTIFIER ::= { xcmCOOsiwanFaxDevice 1 }
xcmCOOsiwanFaxSpeed
    OBJECT IDENTIFIER ::= { xcmCOOsiwanFax 3 }
xcmCOOsiwanFaxSpeedOverride
    OBJECT IDENTIFIER ::= { xcmCOOsiwanFaxSpeed 1 }
xcmCOOsiwanFaxSpeedDetected
    OBJECT IDENTIFIER ::= { xcmCOOsiwanFaxSpeed 2 }
xcmCOOsiwanFaxSpeedAdaptive
    OBJECT IDENTIFIER ::= { xcmCOOsiwanFaxSpeed 3 }
xcmCOOsiwanFaxSpeedSupport
    OBJECT IDENTIFIER ::= { xcmCOOsiwanFaxSpeed 4 }
xcmCOOsiwanFaxMinSpeed
    OBJECT IDENTIFIER ::= { xcmCOOsiwanFaxSpeed 5 }
xcmCOOsiwanFaxMaxSpeed
    OBJECT IDENTIFIER ::= { xcmCOOsiwanFaxSpeed 6 }
xcmCOOsiwanFaxInterface
    OBJECT IDENTIFIER ::= { xcmCOOsiwanFax 5 }
xcmCOOsiwanFaxAcceptAddress     
    OBJECT IDENTIFIER ::= { xcmCOOsiwanFax 11 }
xcmCOOsiwanFaxRejectAddress     
    OBJECT IDENTIFIER ::= { xcmCOOsiwanFax 12 }
xcmCOOsiwanFaxSendCoverSheet    
    OBJECT IDENTIFIER ::= { xcmCOOsiwanFax 20 }
xcmCOOsiwanFaxSendHeader        
    OBJECT IDENTIFIER ::= { xcmCOOsiwanFax 21 }
xcmCOOsiwanFaxSendManual        
    OBJECT IDENTIFIER ::= { xcmCOOsiwanFax 22 }
xcmCOOsiwanFaxSendSecurity      
    OBJECT IDENTIFIER ::= { xcmCOOsiwanFax 23 }
xcmCOOsiwanFaxMaxRetries        
    OBJECT IDENTIFIER ::= { xcmCOOsiwanFax 24 }
xcmCOOsiwanFaxRetryInterval     
    OBJECT IDENTIFIER ::= { xcmCOOsiwanFax 25 }
xcmCOOsiwanFaxSendStoreTime     
    OBJECT IDENTIFIER ::= { xcmCOOsiwanFax 26 }
xcmCOOsiwanFaxMaxOriginalLength 
    OBJECT IDENTIFIER ::= { xcmCOOsiwanFax 27 }
xcmCOOsiwanFaxReceiveCoverSheet 
    OBJECT IDENTIFIER ::= { xcmCOOsiwanFax 30 }
xcmCOOsiwanFaxReceiveFooter     
    OBJECT IDENTIFIER ::= { xcmCOOsiwanFax 31 }
xcmCOOsiwanFaxReceiveToMemory   
    OBJECT IDENTIFIER ::= { xcmCOOsiwanFax 32 }
xcmCOOsiwanFaxReceiveManual     
    OBJECT IDENTIFIER ::= { xcmCOOsiwanFax 33 }
xcmCOOsiwanFaxReceiveSecurity   
    OBJECT IDENTIFIER ::= { xcmCOOsiwanFax 34 }
xcmCOOsiwanFaxReceiveAutoReduce 
    OBJECT IDENTIFIER ::= { xcmCOOsiwanFax 35 }
xcmCOOsiwanFaxReceiveOverflow   
    OBJECT IDENTIFIER ::= { xcmCOOsiwanFax 36 }
xcmCOOsiwanFaxReceiveCollate    
    OBJECT IDENTIFIER ::= { xcmCOOsiwanFax 37 }
xcmCOOsiwanFaxG3                
    OBJECT IDENTIFIER ::= { xcmCOOsiwanFax 40 }
xcmCOOsiwanFaxG4                
    OBJECT IDENTIFIER ::= { xcmCOOsiwanFax 41 }
xcmCOOsiwanFaxLineSwitching     
    OBJECT IDENTIFIER ::= { xcmCOOsiwanFax 42 }
xcmCOOsiwanFaxMaxSpeedDial      
    OBJECT IDENTIFIER ::= { xcmCOOsiwanFax 43 }
xcmCOOsiwanPSTNAddress          
    OBJECT IDENTIFIER ::= { xcmCOOsiwanPSTN 1 }
xcmCOOsiwanISDNAddress          
    OBJECT IDENTIFIER ::= { xcmCOOsiwanISDN 1 }
xcmCOOsiwanTransports
    OBJECT IDENTIFIER ::= { xcmCOOsiwanSuite 1400 }
xcmCOOsiwanApplications
    OBJECT IDENTIFIER ::= { xcmCOOsiwanSuite 1700 }
xcmCOOsiwanDPA                          
    OBJECT IDENTIFIER ::= { xcmCOOsiwanSuite 1713 }
xcmCOOsiwanFTAM                         
    OBJECT IDENTIFIER ::= { xcmCOOsiwanSuite 1714 }
xcmCOOsiwanVT                           
    OBJECT IDENTIFIER ::= { xcmCOOsiwanSuite 1716 }
xcmCOOsiwanMHS                          
    OBJECT IDENTIFIER ::= { xcmCOOsiwanSuite 1740 }
xcmCOOsiwanDS                           
    OBJECT IDENTIFIER ::= { xcmCOOsiwanSuite 1750 }
xcmCOOsiwanDAP                          
    OBJECT IDENTIFIER ::= { xcmCOOsiwanSuite 1751 }
xcmCOOsiwanDSP                          
    OBJECT IDENTIFIER ::= { xcmCOOsiwanSuite 1752 }
xcmCOOsiwanMgmt                         
    OBJECT IDENTIFIER ::= { xcmCOOsiwanSuite 1770 }
xcmCOOsiwanCMIP                         
    OBJECT IDENTIFIER ::= { xcmCOOsiwanSuite 1771 }
xcmCOOsiwanSecurity                     
    OBJECT IDENTIFIER ::= { xcmCOOsiwanSuite 1780 }
--
--
xcmCOInternetSuite
    OBJECT IDENTIFIER ::= { xcmCommsConfigTC 14 }
xcmCOInternetDatalinks
    OBJECT IDENTIFIER ::= { xcmCOInternetSuite 1200 }
xcmCOInternetSLIP               
    OBJECT IDENTIFIER ::= { xcmCOInternetSuite 1201 }
xcmCOInternetPPP                
    OBJECT IDENTIFIER ::= { xcmCOInternetSuite 1202 }
xcmCOInternetTransports
    OBJECT IDENTIFIER ::= { xcmCOInternetSuite 1400 }
xcmCOInternetIP                 
    OBJECT IDENTIFIER ::= { xcmCOInternetSuite 1301 }
xcmCOInternetICMP               
    OBJECT IDENTIFIER ::= { xcmCOInternetSuite 1302 }
xcmCOInternetARP                
    OBJECT IDENTIFIER ::= { xcmCOInternetSuite 1303 }
xcmCOInternetDHCP               
    OBJECT IDENTIFIER ::= { xcmCOInternetSuite 1304 }
xcmCOInternetBOOTP              
    OBJECT IDENTIFIER ::= { xcmCOInternetSuite 1305 }
xcmCOInternetBOOTPBroadcastEnabled
   OBJECT IDENTIFIER ::= { xcmCOInternetBOOTP 1}
xcmCOInternetRARP               
    OBJECT IDENTIFIER ::= { xcmCOInternetSuite 1306 }
xcmCOInternetIPv6               
    OBJECT IDENTIFIER ::= { xcmCOInternetSuite 1310 }
xcmCOInternetUDP                
    OBJECT IDENTIFIER ::= { xcmCOInternetSuite 1401 }
xcmCOInternetTCP                
    OBJECT IDENTIFIER ::= { xcmCOInternetSuite 1402 }
xcmCOInternetPing               
    OBJECT IDENTIFIER ::= { xcmCOInternetSuite 1404 }
xcmCOInternetSSL3               
    OBJECT IDENTIFIER ::= { xcmCOInternetSuite 1405 }
xcmCOInternetTLS                
    OBJECT IDENTIFIER ::= { xcmCOInternetSuite 1406 }
xcmCOInternetICMPv6               
    OBJECT IDENTIFIER ::= { xcmCOInternetSuite 1410 }
xcmCOInternetSSL3Port               
    OBJECT IDENTIFIER ::= { xcmCOInternetSSL3 1 }
xcmCOInternetSSL3CipherStrength        
    OBJECT IDENTIFIER ::= { xcmCOInternetSSL3 2 }
xcmCOInternetIPAddress          
    OBJECT IDENTIFIER ::= { xcmCOInternetIP 1 }
xcmCOInternetIPv6Address          
    OBJECT IDENTIFIER ::= { xcmCOInternetIPv6 1 }
xcmCOInternetIPSocketAddress    
    OBJECT IDENTIFIER ::= { xcmCOInternetIPAddress 1 }
xcmCOInternetIPv6SocketAddress    
    OBJECT IDENTIFIER ::= { xcmCOInternetIPv6Address 1 }
xcmCOInternetIPv6ManuallyAssignedAddress
    OBJECT IDENTIFIER ::= { xcmCOInternetIPv6Address 2 }
xcmCOInternetIPv6DHCPv6AssignedAddress
    OBJECT IDENTIFIER ::= { xcmCOInternetIPv6Address 3 }
xcmCOInternetIPv6LinkLocalAddress
    OBJECT IDENTIFIER ::= { xcmCOInternetIPv6Address 4 }
xcmCOInternetIPv6StatelessAddress
    OBJECT IDENTIFIER ::= { xcmCOInternetIPv6Address 5 }
xcmCOInternetIPv6RandomAddress
    OBJECT IDENTIFIER ::= { xcmCOInternetIPv6Address 6 }
xcmCOInternetIPv6AutomaticAddressing
    OBJECT IDENTIFIER ::= { xcmCOInternetIPv6Address 7 }
xcmCOInternetIPv6EUI64InterfaceId
    OBJECT IDENTIFIER ::= { xcmCOInternetIPv6 2 }
xcmCOInternetIPv6RouterAdvertisementAddressPrefix
    OBJECT IDENTIFIER ::= { xcmCOInternetIPv6 3 }
xcmCOInternetIPv6DefaultGateway         
    OBJECT IDENTIFIER ::= { xcmCOInternetIPv6 4 }
xcmCOInternetIPv6HostName               
    OBJECT IDENTIFIER ::= { xcmCOInternetIPv6 5 }
xcmCOInternetIPSubnetMask       
    OBJECT IDENTIFIER ::= { xcmCOInternetIP 2 }
xcmCOInternetIPAddressViaRARP   
    OBJECT IDENTIFIER ::= { xcmCOInternetIP 3 }
xcmCOInternetIPDefaultGateway   
    OBJECT IDENTIFIER ::= { xcmCOInternetIP 4 }
xcmCOInternetIPAddressSource    
    OBJECT IDENTIFIER ::= { xcmCOInternetIP 5 }
xcmCOInternetIPDatalinks        
    OBJECT IDENTIFIER ::= { xcmCOInternetIP 12 }
xcmCOInternetIPHostName         
    OBJECT IDENTIFIER ::= { xcmCOInternetIP 50 }
xcmCOInternetIPAutoIPAddress 
OBJECT IDENTIFIER ::= { xcmCOInternetIP 51 }
xcmCOInternetIPAutoEnable          
    OBJECT IDENTIFIER ::= { xcmCOInternetIP 60 }
xcmCOInternetIPBcastCache
   OBJECT IDENTIFIER ::= { xcmCOInternetIP 61 }
xcmCOInternetIPInstall
   OBJECT IDENTIFIER ::= { xcmCOInternetIP 62 }
xcmCOInternetIPSec   
    OBJECT IDENTIFIER ::= { xcmCOInternetIP 70 }
xcmCOInternetIPBCacheEnabled     
    OBJECT IDENTIFIER ::= { xcmCOInternetIPBcastCache 1 }
xcmCOInternetIPBCacheAddress1    
    OBJECT IDENTIFIER ::= { xcmCOInternetIPBcastCache 2 }
xcmCOInternetIPBCacheAddress2    
    OBJECT IDENTIFIER ::= { xcmCOInternetIPBcastCache 3 }
xcmCOInternetIPBCacheAddress3    
    OBJECT IDENTIFIER ::= { xcmCOInternetIPBcastCache 4 }
xcmCOInternetIPBCacheAddress4    
    OBJECT IDENTIFIER ::= { xcmCOInternetIPBcastCache 5 }
xcmCOInternetIPInstallSelect       
   OBJECT IDENTIFIER ::= { xcmCOInternetIPInstall 1 }
xcmCOInternetIPAllSubnetsLocal     
   OBJECT IDENTIFIER ::= { xcmCOInternetIPInstall 2 }
--
--
xcmCOInternetDHCPClassID        
    OBJECT IDENTIFIER ::= { xcmCOInternetDHCP 1 }
xcmCOInternetDHCPLeaseTime      
    OBJECT IDENTIFIER ::= { xcmCOInternetDHCP 2 }
xcmCOInternetDHCPRequestTimeout 
    OBJECT IDENTIFIER ::= { xcmCOInternetDHCP 3 }
xcmCOInternetDHCPServer 
    OBJECT IDENTIFIER ::= { xcmCOInternetDHCP 4 }
--
--
--
--
xcmCOInternetDHCPOptionGet      
    OBJECT IDENTIFIER ::= { xcmCOInternetDHCP 10 }
xcmCOInternetDHCPOptionSet      
    OBJECT IDENTIFIER ::= { xcmCOInternetDHCP 11 }
--
--
xcmCODHCPGetSubnetMask          
    OBJECT IDENTIFIER ::= { xcmCOInternetDHCPOptionGet 1 }
xcmCODHCPGetSubnetTimeOffset    
    OBJECT IDENTIFIER ::= { xcmCOInternetDHCPOptionGet 2 }
xcmCODHCPGetRouter              
    OBJECT IDENTIFIER ::= { xcmCOInternetDHCPOptionGet 3 }
xcmCODHCPGetTPTimeServer        
    OBJECT IDENTIFIER ::= { xcmCOInternetDHCPOptionGet 4 }
xcmCODHCPGetIEN116NameServer    
    OBJECT IDENTIFIER ::= { xcmCOInternetDHCPOptionGet 5 }
xcmCODHCPGetDNSNameServer       
    OBJECT IDENTIFIER ::= { xcmCOInternetDHCPOptionGet 6 }
xcmCODHCPGetLogServer           
    OBJECT IDENTIFIER ::= { xcmCOInternetDHCPOptionGet 7 }
xcmCODHCPGetCookieServer        
    OBJECT IDENTIFIER ::= { xcmCOInternetDHCPOptionGet 8 }
xcmCODHCPGetLPRServer           
    OBJECT IDENTIFIER ::= { xcmCOInternetDHCPOptionGet 9 }
xcmCODHCPGetImpressServer       
    OBJECT IDENTIFIER ::= { xcmCOInternetDHCPOptionGet 10 }
xcmCODHCPGetResourceLocServer   
    OBJECT IDENTIFIER ::= { xcmCOInternetDHCPOptionGet 11 }
xcmCODHCPGetHostName            
    OBJECT IDENTIFIER ::= { xcmCOInternetDHCPOptionGet 12 }
xcmCODHCPGetBootFileSize        
    OBJECT IDENTIFIER ::= { xcmCOInternetDHCPOptionGet 13 }
xcmCODHCPGetMeritDumpFile       
    OBJECT IDENTIFIER ::= { xcmCOInternetDHCPOptionGet 14 }
xcmCODHCPGetDNSDomainName       
    OBJECT IDENTIFIER ::= { xcmCOInternetDHCPOptionGet 15 }
xcmCODHCPGetSwapServer          
    OBJECT IDENTIFIER ::= { xcmCOInternetDHCPOptionGet 16 }
xcmCODHCPGetRootPath            
    OBJECT IDENTIFIER ::= { xcmCOInternetDHCPOptionGet 17 }
xcmCODHCPGetExtensionsPath      
    OBJECT IDENTIFIER ::= { xcmCOInternetDHCPOptionGet 18 }
--
--
xcmCODHCPGetIPForwarding        
    OBJECT IDENTIFIER ::= { xcmCOInternetDHCPOptionGet 19 }
xcmCODHCPGetNLSourceRouting     
    OBJECT IDENTIFIER ::= { xcmCOInternetDHCPOptionGet 20 }
xcmCODHCPGetNLPolicyFilter      
    OBJECT IDENTIFIER ::= { xcmCOInternetDHCPOptionGet 21 }
xcmCODHCPGetMaxIPDatagramSize   
    OBJECT IDENTIFIER ::= { xcmCOInternetDHCPOptionGet 22 }
xcmCODHCPGetIPDefaultTTL        
    OBJECT IDENTIFIER ::= { xcmCOInternetDHCPOptionGet 23 }
xcmCODHCPGetPathMTUAgeTimeout   
    OBJECT IDENTIFIER ::= { xcmCOInternetDHCPOptionGet 24 }
xcmCODHCPGetPathMTUPlateau      
    OBJECT IDENTIFIER ::= { xcmCOInternetDHCPOptionGet 25 }
--
--
xcmCODHCPGetInterfaceMTUSize    
    OBJECT IDENTIFIER ::= { xcmCOInternetDHCPOptionGet 26 }
xcmCODHCPGetAllSubnetsLocal     
    OBJECT IDENTIFIER ::= { xcmCOInternetDHCPOptionGet 27 }
xcmCODHCPGetBroadcastAddress    
    OBJECT IDENTIFIER ::= { xcmCOInternetDHCPOptionGet 28 }
xcmCODHCPGetMaskDiscovery       
    OBJECT IDENTIFIER ::= { xcmCOInternetDHCPOptionGet 29 }
xcmCODHCPGetMaskSupplier        
    OBJECT IDENTIFIER ::= { xcmCOInternetDHCPOptionGet 30 }
xcmCODHCPGetRouterDiscovery     
    OBJECT IDENTIFIER ::= { xcmCOInternetDHCPOptionGet 31 }
xcmCODHCPGetRouterSolAddress    
    OBJECT IDENTIFIER ::= { xcmCOInternetDHCPOptionGet 32 }
xcmCODHCPGetStaticRoute         
    OBJECT IDENTIFIER ::= { xcmCOInternetDHCPOptionGet 33 }
--
--
xcmCODHCPGetARPTrailer          
    OBJECT IDENTIFIER ::= { xcmCOInternetDHCPOptionGet 34 }
xcmCODHCPGetARPCacheTimeout     
    OBJECT IDENTIFIER ::= { xcmCOInternetDHCPOptionGet 35 }
xcmCODHCPGetEthernetFrameIEEE   
    OBJECT IDENTIFIER ::= { xcmCOInternetDHCPOptionGet 36 }
--
--
xcmCODHCPGetTCPDefaultTTL       
    OBJECT IDENTIFIER ::= { xcmCOInternetDHCPOptionGet 37 }
xcmCODHCPGetTCPKeepInterval     
    OBJECT IDENTIFIER ::= { xcmCOInternetDHCPOptionGet 38 }
xcmCODHCPGetTCPKeepGarbage      
    OBJECT IDENTIFIER ::= { xcmCOInternetDHCPOptionGet 39 }
--
--
xcmCODHCPGetNISDomainName       
    OBJECT IDENTIFIER ::= { xcmCOInternetDHCPOptionGet 40 }
xcmCODHCPGetNISNameServer       
    OBJECT IDENTIFIER ::= { xcmCOInternetDHCPOptionGet 41 }
xcmCODHCPGetNTPTimeServer       
    OBJECT IDENTIFIER ::= { xcmCOInternetDHCPOptionGet 42 }
xcmCODHCPGetVendorSpecific      
    OBJECT IDENTIFIER ::= { xcmCOInternetDHCPOptionGet 43 }
xcmCODHCPGetNetbiosNameServer   
    OBJECT IDENTIFIER ::= { xcmCOInternetDHCPOptionGet 44 }
xcmCODHCPGetNetbiosDistServer   
    OBJECT IDENTIFIER ::= { xcmCOInternetDHCPOptionGet 45 }
xcmCODHCPGetNetbiosNodeType     
    OBJECT IDENTIFIER ::= { xcmCOInternetDHCPOptionGet 46 }
xcmCODHCPGetNetbiosScope        
    OBJECT IDENTIFIER ::= { xcmCOInternetDHCPOptionGet 47 }
xcmCODHCPGetXWindowFontServer   
    OBJECT IDENTIFIER ::= { xcmCOInternetDHCPOptionGet 48 }
xcmCODHCPGetXWindowDisplayMgr   
    OBJECT IDENTIFIER ::= { xcmCOInternetDHCPOptionGet 49 }
xcmCODHCPGetNISPlusDomainName   
    OBJECT IDENTIFIER ::= { xcmCOInternetDHCPOptionGet 64 }
xcmCODHCPGetNISPlusNameServer   
    OBJECT IDENTIFIER ::= { xcmCOInternetDHCPOptionGet 65 }
xcmCODHCPGetMobileIPHomeAgent   
    OBJECT IDENTIFIER ::= { xcmCOInternetDHCPOptionGet 68 }
xcmCODHCPGetSMTPMailServer      
    OBJECT IDENTIFIER ::= { xcmCOInternetDHCPOptionGet 69 }
xcmCODHCPGetPOP3MailServer      
    OBJECT IDENTIFIER ::= { xcmCOInternetDHCPOptionGet 70 }
xcmCODHCPGetNNTPNewsServer      
    OBJECT IDENTIFIER ::= { xcmCOInternetDHCPOptionGet 71 }
xcmCODHCPGetWWWServer           
    OBJECT IDENTIFIER ::= { xcmCOInternetDHCPOptionGet 72 }
xcmCODHCPGetFingerServer        
    OBJECT IDENTIFIER ::= { xcmCOInternetDHCPOptionGet 73 }
xcmCODHCPGetIRCServer           
    OBJECT IDENTIFIER ::= { xcmCOInternetDHCPOptionGet 74 }
xcmCODHCPGetStreetTalkServer    
    OBJECT IDENTIFIER ::= { xcmCOInternetDHCPOptionGet 75 }
xcmCODHCPGetStreetTalkDAServer  
    OBJECT IDENTIFIER ::= { xcmCOInternetDHCPOptionGet 76 }
--
--
xcmCODHCPSetIPAddressRequest    
    OBJECT IDENTIFIER ::= { xcmCOInternetDHCPOptionSet 50 }
xcmCODHCPSetIPAddressLeaseTime  
    OBJECT IDENTIFIER ::= { xcmCOInternetDHCPOptionSet 51 }
xcmCODHCPSetOptionOverload      
    OBJECT IDENTIFIER ::= { xcmCOInternetDHCPOptionSet 52 }
xcmCODHCPGetMessageType         
    OBJECT IDENTIFIER ::= { xcmCOInternetDHCPOptionGet 53 }
xcmCODHCPGetServerID            
    OBJECT IDENTIFIER ::= { xcmCOInternetDHCPOptionGet 54 }
xcmCODHCPGetParameterRequest    
    OBJECT IDENTIFIER ::= { xcmCOInternetDHCPOptionGet 55 }
xcmCODHCPGetErrorMessage        
    OBJECT IDENTIFIER ::= { xcmCOInternetDHCPOptionGet 56 }
xcmCODHCPGetMaxMessageSize      
    OBJECT IDENTIFIER ::= { xcmCOInternetDHCPOptionGet 57 }
xcmCODHCPGetRenewT1Interval     
    OBJECT IDENTIFIER ::= { xcmCOInternetDHCPOptionGet 58 }
xcmCODHCPGetRebindT2Interval    
    OBJECT IDENTIFIER ::= { xcmCOInternetDHCPOptionGet 59 }
xcmCODHCPSetClassID             
    OBJECT IDENTIFIER ::= { xcmCOInternetDHCPOptionSet 60 }
xcmCODHCPSetClientID            
    OBJECT IDENTIFIER ::= { xcmCOInternetDHCPOptionSet 61 }
xcmCODHCPGetTFTPServerName      
    OBJECT IDENTIFIER ::= { xcmCOInternetDHCPOptionGet 66 }
xcmCODHCPGetBootFileName        
    OBJECT IDENTIFIER ::= { xcmCOInternetDHCPOptionGet 67 }
--
--
xcmCODHCPGetNDSNameServer       
    OBJECT IDENTIFIER ::= { xcmCOInternetDHCPOptionGet 85 }
xcmCODHCPGetNDSTreeName         
    OBJECT IDENTIFIER ::= { xcmCOInternetDHCPOptionGet 86 }
xcmCODHCPGetNDSContext          
    OBJECT IDENTIFIER ::= { xcmCOInternetDHCPOptionGet 87 }
xcmCOInternetUDPAddress         
    OBJECT IDENTIFIER ::= { xcmCOInternetUDP 1 }
xcmCOInternetUDPPort            
    OBJECT IDENTIFIER ::= { xcmCOInternetUDP 2 }
xcmCOInternetTCPAddress         
    OBJECT IDENTIFIER ::= { xcmCOInternetTCP 1 }
xcmCOInternetTCPPort            
    OBJECT IDENTIFIER ::= { xcmCOInternetTCP 2 }
xcmCOInternetTCPMaxSegmentSize 
    OBJECT IDENTIFIER ::= { xcmCOInternetTCP 3 }
xcmCOInternetApplications
    OBJECT IDENTIFIER ::= { xcmCOInternetSuite 1700 }
xcmCOInternetRaw                
    OBJECT IDENTIFIER ::= { xcmCOInternetSuite 1501 }
xcmCOInternetIPP                
    OBJECT IDENTIFIER ::= { xcmCOInternetSuite 1502 }
xcmCOInternetLPR                
    OBJECT IDENTIFIER ::= { xcmCOInternetSuite 1503 }
xcmCOInternetFTP                
    OBJECT IDENTIFIER ::= { xcmCOInternetSuite 1504 }
xcmCOInternetFTPPassiveMode 
    OBJECT IDENTIFIER ::= { xcmCOInternetFTP 1 }
xcmCOInternetSMTP               
    OBJECT IDENTIFIER ::= { xcmCOInternetSuite 1505 }
xcmCOInternetTelnet             
    OBJECT IDENTIFIER ::= { xcmCOInternetSuite 1506 }
xcmCOInternetDNS                
    OBJECT IDENTIFIER ::= { xcmCOInternetSuite 1507 }
xcmCOInternetTFTP               
    OBJECT IDENTIFIER ::= { xcmCOInternetSuite 1508 }
xcmCOInternetHTTP               
    OBJECT IDENTIFIER ::= { xcmCOInternetSuite 1509 }
xcmCOInternetSNMP               
    OBJECT IDENTIFIER ::= { xcmCOInternetSuite 1510 }
xcmCOInternetSNMPv1             
    OBJECT IDENTIFIER ::= { xcmCOInternetSuite 1511 }
xcmCOInternetSNMPv2             
    OBJECT IDENTIFIER ::= { xcmCOInternetSuite 1512 }
xcmCOInternetSNMPv3             
    OBJECT IDENTIFIER ::= { xcmCOInternetSuite 1513 }
xcmCOInternetSNMPVersion        
    OBJECT IDENTIFIER ::= { xcmCOInternetSNMP 1 }
xcmCOInternetSNMPAdminAddress   
    OBJECT IDENTIFIER ::= { xcmCOInternetSNMP 2 }
xcmCOInternetPOP3               
    OBJECT IDENTIFIER ::= { xcmCOInternetSuite 1514 }
xcmCOInternetIMAP4              
    OBJECT IDENTIFIER ::= { xcmCOInternetSuite 1515 }
xcmCOInternetFax                
    OBJECT IDENTIFIER ::= { xcmCOInternetSuite 1516 }
xcmCOInternetNTP                
    OBJECT IDENTIFIER ::= { xcmCOInternetSuite 1517}
xcmCOInternetSFTP                
    OBJECT IDENTIFIER ::= { xcmCOInternetSuite 1518}
xcmCOInternetWINS               
    OBJECT IDENTIFIER ::= { xcmCOInternetSuite 1519 }
xcmCOInternetSunOncSuite        
    OBJECT IDENTIFIER ::= { xcmCOInternetSuite 1520 }
xcmCOInternetSunOncNIS          
    OBJECT IDENTIFIER ::= { xcmCOInternetSuite 1521 }
xcmCOInternetSunOncPlusNIS      
    OBJECT IDENTIFIER ::= { xcmCOInternetSuite 1522 }
xcmCOInternetSunOncRPC          
    OBJECT IDENTIFIER ::= { xcmCOInternetSuite 1523 }
xcmCOInternetSunOncPlusRPC      
    OBJECT IDENTIFIER ::= { xcmCOInternetSuite 1524 }
xcmCOInternetSunTiRPC           
    OBJECT IDENTIFIER ::= { xcmCOInternetSuite 1525 }
xcmCOInternetHTTPS               
    OBJECT IDENTIFIER ::= { xcmCOInternetSuite 1526 }
xcmCOInternetOsfDceSuite        
    OBJECT IDENTIFIER ::= { xcmCOInternetSuite 1530 }
xcmCOInternetOsfDceCDS          
    OBJECT IDENTIFIER ::= { xcmCOInternetSuite 1531 }
xcmCOInternetOsfDceRPC          
    OBJECT IDENTIFIER ::= { xcmCOInternetSuite 1532 }
xcmCOInternetOsfDceKerberos     
    OBJECT IDENTIFIER ::= { xcmCOInternetSuite 1533 }
xcmCOInternetOsfDmeSuite        
    OBJECT IDENTIFIER ::= { xcmCOInternetSuite 1540 }
xcmCOInternetLDAP               
    OBJECT IDENTIFIER ::= { xcmCOInternetSuite 1551 }
xcmCOInternetCLDAP              
    OBJECT IDENTIFIER ::= { xcmCOInternetSuite 1552 }
xcmCOInternetSalutation         
    OBJECT IDENTIFIER ::= { xcmCOInternetSuite 1561 }
xcmCOInternetUpnpSuite          
    OBJECT IDENTIFIER ::= { xcmCOInternetSuite 1570 }
xcmCOInternetUpnpSSDP           
    OBJECT IDENTIFIER ::= { xcmCOInternetSuite 1571 }
xcmCOInternetUpnpGENA           
    OBJECT IDENTIFIER ::= { xcmCOInternetSuite 1572 }
xcmCOInternetSLP                
    OBJECT IDENTIFIER ::= { xcmCOInternetSuite 1591 }
xcmCOInternetSLPv1              
    OBJECT IDENTIFIER ::= { xcmCOInternetSuite 1592 }
xcmCOInternetSLPv2              
    OBJECT IDENTIFIER ::= { xcmCOInternetSuite 1593 }
--
--
xcmCOInternetWSDSuite           
    OBJECT IDENTIFIER ::= { xcmCOInternetSuite 1595 }
xcmCOInternetWSDiscovery        
    OBJECT IDENTIFIER ::= { xcmCOInternetWSDSuite 1 }
xcmCOInternetWSXResourcePort    
    OBJECT IDENTIFIER ::= { xcmCOInternetWSDSuite 2 }
xcmCOInternetWSDiscoveryMulticast  
    OBJECT IDENTIFIER ::= { xcmCOInternetWSDiscovery 1 }
xcmCOInternetWSDiscoveryPort    
    OBJECT IDENTIFIER ::= { xcmCOInternetWSDiscovery 2 }
xcmCOInternetWSPrintPort       
    OBJECT IDENTIFIER ::= { xcmCOInternetWSDSuite 3 }
xcmCOInternetWSScanPort        
    OBJECT IDENTIFIER ::= { xcmCOInternetWSDSuite 4 }
xcmCOInternetWSTransferPort       
    OBJECT IDENTIFIER ::= { xcmCOInternetWSDSuite 5 }
xcmCOInternetDeallocateAllDynamicResources   
    OBJECT IDENTIFIER ::= { xcmCOInternetSuite  1600}
xcmCOInternetDHCPv6               
    OBJECT IDENTIFIER ::= { xcmCOInternetSuite 1800 }
xcmCOInternetDHCPv6ConfigState    
    OBJECT IDENTIFIER ::= { xcmCOInternetDHCPv6 1 }
xcmCOInternetDNSv6                
    OBJECT IDENTIFIER ::= { xcmCOInternetSuite 1801 }
xcmCOInternetDNSv6DomainName      
    OBJECT IDENTIFIER ::= { xcmCOInternetDNSv6 1 }
xcmCOInternetDNSv6ServerAddress   
OBJECT IDENTIFIER ::= { xcmCOInternetDNSv6 2 }
xcmCOInternetDNSv6DynamicUpdate   
OBJECT IDENTIFIER ::= { xcmCOInternetDNSv6 3 }
xcmCOInternetDNSv6ResolutionPolicy    
    OBJECT IDENTIFIER ::= { xcmCOInternetDNSv6 4 }
xcmCOInternetIPv6DeallocateAllDynamicResources   
OBJECT IDENTIFIER ::= { xcmCOInternetSuite 1802}
xcmCOInternetSLPVersion         
    OBJECT IDENTIFIER ::= { xcmCOInternetSLP 1 }
xcmCOInternetRawHostName        
    OBJECT IDENTIFIER ::= { xcmCOInternetRaw 1 }
xcmCOInternetRawHostAddress     
    OBJECT IDENTIFIER ::= { xcmCOInternetRaw 2 }
xcmCOInternetRawListenSocket    
    OBJECT IDENTIFIER ::= { xcmCOInternetRaw 3 }
xcmCOInternetRawMaxClients      
    OBJECT IDENTIFIER ::= { xcmCOInternetRaw 4 }
xcmCOInternetRawAcceptAddress   
    OBJECT IDENTIFIER ::= { xcmCOInternetRaw 11 }
xcmCOInternetRawAcceptSubnet    
    OBJECT IDENTIFIER ::= { xcmCOInternetRaw 12 }
xcmCOInternetRawRejectAddress   
    OBJECT IDENTIFIER ::= { xcmCOInternetRaw 21 }
xcmCOInternetRawRejectSubnet    
    OBJECT IDENTIFIER ::= { xcmCOInternetRaw 22 }
xcmCOInternetRawSpool           
    OBJECT IDENTIFIER ::= { xcmCOInternetRaw 31 }
xcmCOInternetRawMaxSpool        
    OBJECT IDENTIFIER ::= { xcmCOInternetRaw 32 }
xcmCOInternetRawJobTimeout      
    OBJECT IDENTIFIER ::= { xcmCOInternetRaw 40 }
xcmCOInternetRawAutoSwitch      
    OBJECT IDENTIFIER ::= { xcmCOInternetRaw 41 }
xcmCOInternetRawBinaryPS        
    OBJECT IDENTIFIER ::= { xcmCOInternetRaw 42 }
xcmCOInternetRawDefaultPDL      
    OBJECT IDENTIFIER ::= { xcmCOInternetRaw 43 }
xcmCOInternetRawBidirectional      
    OBJECT IDENTIFIER ::= { xcmCOInternetRaw 44 }
xcmCOInternetIPPHostName        
    OBJECT IDENTIFIER ::= { xcmCOInternetIPP 1 }
xcmCOInternetIPPHostAddress     
    OBJECT IDENTIFIER ::= { xcmCOInternetIPP 2 }
xcmCOInternetIPPListenSocket    
    OBJECT IDENTIFIER ::= { xcmCOInternetIPP 3 }
xcmCOInternetIPPMaxClients      
    OBJECT IDENTIFIER ::= { xcmCOInternetIPP 4 }
xcmCOInternetIPPVersionString   
    OBJECT IDENTIFIER ::= { xcmCOInternetIPP 9 }
xcmCOInternetIPPAcceptAddress   
    OBJECT IDENTIFIER ::= { xcmCOInternetIPP 11 }
xcmCOInternetIPPAcceptSubnet    
    OBJECT IDENTIFIER ::= { xcmCOInternetIPP 12 }
xcmCOInternetIPPRejectAddress   
    OBJECT IDENTIFIER ::= { xcmCOInternetIPP 21 }
xcmCOInternetIPPRejectSubnet    
    OBJECT IDENTIFIER ::= { xcmCOInternetIPP 22 }
xcmCOInternetIPPSpool           
    OBJECT IDENTIFIER ::= { xcmCOInternetIPP 31 }
xcmCOInternetIPPMaxSpool        
    OBJECT IDENTIFIER ::= { xcmCOInternetIPP 32 }
xcmCOInternetIPPJobTimeout      
    OBJECT IDENTIFIER ::= { xcmCOInternetIPP 40 }
xcmCOInternetIPPAutoSwitch      
    OBJECT IDENTIFIER ::= { xcmCOInternetIPP 41 }
xcmCOInternetIPPBinaryPS        
    OBJECT IDENTIFIER ::= { xcmCOInternetIPP 42 }
xcmCOInternetIPPDefaultPDL      
    OBJECT IDENTIFIER ::= { xcmCOInternetIPP 43 }
xcmCOInternetIPPAuthScheme   
    OBJECT IDENTIFIER ::= { xcmCOInternetIPP 50 }
xcmCOInternetLPRHostName        
    OBJECT IDENTIFIER ::= { xcmCOInternetLPR 1 }
xcmCOInternetLPRHostAddress     
    OBJECT IDENTIFIER ::= { xcmCOInternetLPR 2 }
xcmCOInternetLPRListenSocket    
    OBJECT IDENTIFIER ::= { xcmCOInternetLPR 3 }
xcmCOInternetLPRMaxClients      
    OBJECT IDENTIFIER ::= { xcmCOInternetLPR 4 }
xcmCOInternetLPRAcceptAddress   
    OBJECT IDENTIFIER ::= { xcmCOInternetLPR 11 }
xcmCOInternetLPRAcceptSubnet    
    OBJECT IDENTIFIER ::= { xcmCOInternetLPR 12 }
xcmCOInternetLPRRejectAddress   
    OBJECT IDENTIFIER ::= { xcmCOInternetLPR 21 }
xcmCOInternetLPRRejectSubnet    
    OBJECT IDENTIFIER ::= { xcmCOInternetLPR 22 }
xcmCOInternetLPRSpool           
    OBJECT IDENTIFIER ::= { xcmCOInternetLPR 31 }
xcmCOInternetLPRMaxSpool        
    OBJECT IDENTIFIER ::= { xcmCOInternetLPR 32 }
xcmCOInternetLPRJobTimeout      
    OBJECT IDENTIFIER ::= { xcmCOInternetLPR 40 }
xcmCOInternetLPRAutoSwitch      
    OBJECT IDENTIFIER ::= { xcmCOInternetLPR 41 }
xcmCOInternetLPRBinaryPS        
    OBJECT IDENTIFIER ::= { xcmCOInternetLPR 42 }
xcmCOInternetLPRDefaultPDL      
    OBJECT IDENTIFIER ::= { xcmCOInternetLPR 43 }
xcmCOInternetSMTPHostName       
    OBJECT IDENTIFIER ::= { xcmCOInternetSMTP 1 }
xcmCOInternetSMTPHostAddress    
    OBJECT IDENTIFIER ::= { xcmCOInternetSMTP 2 }
xcmCOInternetSMTPListenSocket   
    OBJECT IDENTIFIER ::= { xcmCOInternetSMTP 3 }
xcmCOInternetSMTPMaxClients     
    OBJECT IDENTIFIER ::= { xcmCOInternetSMTP 4 }
xcmCOInternetSMTPAcceptAddress  
    OBJECT IDENTIFIER ::= { xcmCOInternetSMTP 11 }
xcmCOInternetSMTPAcceptSubnet   
    OBJECT IDENTIFIER ::= { xcmCOInternetSMTP 12 }
xcmCOInternetSMTPRejectAddress  
    OBJECT IDENTIFIER ::= { xcmCOInternetSMTP 21 }
xcmCOInternetSMTPRejectSubnet   
    OBJECT IDENTIFIER ::= { xcmCOInternetSMTP 22 }
xcmCOInternetSMTPSpool          
    OBJECT IDENTIFIER ::= { xcmCOInternetSMTP 31 }
xcmCOInternetSMTPMaxSpool       
    OBJECT IDENTIFIER ::= { xcmCOInternetSMTP 32 }
xcmCOInternetSMTPJobTimeout     
    OBJECT IDENTIFIER ::= { xcmCOInternetSMTP 40 }
xcmCOInternetSMTPAutoSwitch     
    OBJECT IDENTIFIER ::= { xcmCOInternetSMTP 41 }
xcmCOInternetSMTPBinaryPS       
    OBJECT IDENTIFIER ::= { xcmCOInternetSMTP 42 }
xcmCOInternetSMTPDefaultPDL     
    OBJECT IDENTIFIER ::= { xcmCOInternetSMTP 43 }
xcmCOInternetSMTPSubject        
    OBJECT IDENTIFIER ::= { xcmCOInternetSMTP 44 }
xcmCOInternetSMTPSignatureLine  
    OBJECT IDENTIFIER ::= { xcmCOInternetSMTP 45 }
xcmCOInternetSMTPUserName       
    OBJECT IDENTIFIER ::= { xcmCOInternetSMTP 47 }
xcmCOInternetSMTPPassword       
    OBJECT IDENTIFIER ::= { xcmCOInternetSMTP 48 }
xcmCOInternetSMTPMaxInputText   
    OBJECT IDENTIFIER ::= { xcmCOInternetSMTP 50 }
xcmCOInternetSMTPMaxInputAttach 
    OBJECT IDENTIFIER ::= { xcmCOInternetSMTP 51 }
xcmCOInternetSMTPMaxOutputText  
    OBJECT IDENTIFIER ::= { xcmCOInternetSMTP 52 }
xcmCOInternetSMTPMaxOutputAttach 
    OBJECT IDENTIFIER ::= { xcmCOInternetSMTP 53 }
xcmCOInternetSMTPConfirmRequest 
    OBJECT IDENTIFIER ::= { xcmCOInternetSMTP 54 }
xcmCOInternetSMTPConfirmReply   
    OBJECT IDENTIFIER ::= { xcmCOInternetSMTP 55 }
xcmCOInternetSMTPConfirmTimeout 
    OBJECT IDENTIFIER ::= { xcmCOInternetSMTP 56 }
xcmCOInternetSMTPFeatureReply   
    OBJECT IDENTIFIER ::= { xcmCOInternetSMTP 57 }
xcmCOInternetSMTPMailAddress    
    OBJECT IDENTIFIER ::= { xcmCOInternetSMTP 58 }
xcmCOInternetSMTPMaxInFragments 
    OBJECT IDENTIFIER ::= { xcmCOInternetSMTP 59 }
xcmCOInternetSMTPMaxOutFragments 
    OBJECT IDENTIFIER ::= { xcmCOInternetSMTP 60 }
xcmCOInternetSMTPMaxInAttachments 
    OBJECT IDENTIFIER ::= { xcmCOInternetSMTP 61 }
xcmCOInternetSMTPMaxOutAttachments 
    OBJECT IDENTIFIER ::= { xcmCOInternetSMTP 62 }
xcmCOInternetSMTPMaxInputSize   
    OBJECT IDENTIFIER ::= { xcmCOInternetSMTP 63 }
xcmCOInternetSMTPMaxOutputSize  
    OBJECT IDENTIFIER ::= { xcmCOInternetSMTP 64 }
xcmCOInternetSMTPReversePath  
    OBJECT IDENTIFIER ::= { xcmCOInternetSMTP 65 }
xcmCOInternetSMTPAutoServer 
   OBJECT IDENTIFIER ::= { xcmCOInternetSMTP 70 }
xcmCOInternetDNSDomainName      
    OBJECT IDENTIFIER ::= { xcmCOInternetDNS 1 }
xcmCOInternetDNSLanguage        
    OBJECT IDENTIFIER ::= { xcmCOInternetDNS 3 }
xcmCOInternetDNSCharset         
    OBJECT IDENTIFIER ::= { xcmCOInternetDNS 4 }
xcmCOInternetDNSServerName      
    OBJECT IDENTIFIER ::= { xcmCOInternetDNS 5 }
xcmCOInternetDNSServerAddress   
    OBJECT IDENTIFIER ::= { xcmCOInternetDNS 6 }
xcmCOInternetDNSServerResolvedAddress   
    OBJECT IDENTIFIER ::= { xcmCOInternetDNS 7 }
xcmCOInternetDNSServerTimeout   
    OBJECT IDENTIFIER ::= { xcmCOInternetDNS 8 }
xcmCOInternetDNSAppendDomainName   
    OBJECT IDENTIFIER ::= { xcmCOInternetDNS 9 }
xcmCOInternetDNSAppendParentDomains  
    OBJECT IDENTIFIER ::= { xcmCOInternetDNS 10 }
xcmCOInternetDNSDomainNameList   
    OBJECT IDENTIFIER ::= { xcmCOInternetDNS 11 }
xcmCOInternetDNSDynamicUpdate   
    OBJECT IDENTIFIER ::= { xcmCOInternetDNS 13 }
xcmCOInternetDNSUpdatePolicy    
    OBJECT IDENTIFIER ::= { xcmCOInternetDNS 14 }
xcmCOInternetDNSMulticastEnable  
    OBJECT IDENTIFIER ::= { xcmCOInternetDNS 30 }
xcmCOInternetIOSDiscoveryEnable 
    OBJECT IDENTIFIER ::= { xcmCOInternetDNS 31 }
xcmCOInternetHTTPAddressURL     
    OBJECT IDENTIFIER ::= { xcmCOInternetHTTP 1 }
xcmCOInternetHTTPAddressURI     
    OBJECT IDENTIFIER ::= { xcmCOInternetHTTP 2 }
xcmCOInternetHTTPAddressURN     
    OBJECT IDENTIFIER ::= { xcmCOInternetHTTP 3 }
xcmCOInternetHTTPVersionString  
    OBJECT IDENTIFIER ::= { xcmCOInternetHTTP 9 }
xcmCOInternetHTTPListenSocket   
    OBJECT IDENTIFIER ::= { xcmCOInternetHTTP 11 }
xcmCOInternetHTTPMaxClients     
    OBJECT IDENTIFIER ::= { xcmCOInternetHTTP 12 }
xcmCOInternetHTTPClientTimeout  
    OBJECT IDENTIFIER ::= { xcmCOInternetHTTP 13 }
xcmCOInternetHTTPStatusRefresh  
    OBJECT IDENTIFIER ::= { xcmCOInternetHTTP 14 }
xcmCOInternetHTTPAdminAddress  
    OBJECT IDENTIFIER ::= { xcmCOInternetHTTP 15 }
xcmCOInternetHTTPKeyUsrAddress  
    OBJECT IDENTIFIER ::= { xcmCOInternetHTTP 16 }
xcmCOInternetHTTPProxy   
    OBJECT IDENTIFIER ::= { xcmCOInternetHTTP 20 }
xcmCOInternetHTTPInfoFwd  
    OBJECT IDENTIFIER ::= { xcmCOInternetHTTP 25 }
xcmCOInternetHTTPProxyIPAddress  
    OBJECT IDENTIFIER ::= { xcmCOInternetHTTPProxy 1 }
xcmCOInternetHTTPProxyHostName  
    OBJECT IDENTIFIER ::= { xcmCOInternetHTTPProxy 2 }
xcmCOInternetHTTPProxyPortNumber   
    OBJECT IDENTIFIER ::= { xcmCOInternetHTTPProxy 3 }
xcmCOInternetHTTPProxyExceptions   
    OBJECT IDENTIFIER ::= { xcmCOInternetHTTPProxy 4 }
    --  It is the responsibility of the management tool to "get" 
    --     "set" the rows.
xcmCOInternetHTTPProxyServer      
    OBJECT IDENTIFIER ::= { xcmCOInternetHTTPProxy 5 }
xcmCOInternetHTTPProxyUserName   
    OBJECT IDENTIFIER ::= { xcmCOInternetHTTPProxy 6 }
xcmCOInternetHTTPProxyPassword  
    OBJECT IDENTIFIER ::= { xcmCOInternetHTTPProxy 7 }
xcmCOInternetHTTPProxyAutoDetect  
    OBJECT IDENTIFIER ::= { xcmCOInternetHTTPProxy 8 }
xcmCOInternetHTTPProxyShareSettings 
    OBJECT IDENTIFIER::= { xcmCOInternetHTTPProxy 9 }
xcmCOInternetHTTPProxyAuthValid 
    OBJECT IDENTIFIER::= { xcmCOInternetHTTPProxy 10 }
xcmCOInternetPOP3HostName       
    OBJECT IDENTIFIER ::= { xcmCOInternetPOP3 1 }
xcmCOInternetPOP3HostAddress    
    OBJECT IDENTIFIER ::= { xcmCOInternetPOP3 2 }
xcmCOInternetPOP3PollInterval   
    OBJECT IDENTIFIER ::= { xcmCOInternetPOP3 4 }
xcmCOInternetPOP3Subject        
    OBJECT IDENTIFIER ::= { xcmCOInternetPOP3 44 }
xcmCOInternetPOP3SignatureLine  
    OBJECT IDENTIFIER ::= { xcmCOInternetPOP3 45 }
xcmCOInternetPOP3UserName       
    OBJECT IDENTIFIER ::= { xcmCOInternetPOP3 47 }
xcmCOInternetPOP3Password       
    OBJECT IDENTIFIER ::= { xcmCOInternetPOP3 48 }
xcmCOInternetPOP3MaxInputText   
    OBJECT IDENTIFIER ::= { xcmCOInternetPOP3 50 }
xcmCOInternetPOP3MaxInputAttach 
    OBJECT IDENTIFIER ::= { xcmCOInternetPOP3 51 }
xcmCOInternetPOP3MaxOutputText  
    OBJECT IDENTIFIER ::= { xcmCOInternetPOP3 52 }
xcmCOInternetPOP3MaxOutputAttach 
    OBJECT IDENTIFIER ::= { xcmCOInternetPOP3 53 }
xcmCOInternetPOP3ConfirmRequest 
    OBJECT IDENTIFIER ::= { xcmCOInternetPOP3 54 }
xcmCOInternetPOP3ConfirmReply   
    OBJECT IDENTIFIER ::= { xcmCOInternetPOP3 55 }
xcmCOInternetPOP3ConfirmTimeout 
    OBJECT IDENTIFIER ::= { xcmCOInternetPOP3 56 }
xcmCOInternetPOP3FeatureReply   
    OBJECT IDENTIFIER ::= { xcmCOInternetPOP3 57 }
xcmCOInternetPOP3MailAddress    
    OBJECT IDENTIFIER ::= { xcmCOInternetPOP3 58 }
xcmCOInternetPOP3MaxInFragments 
    OBJECT IDENTIFIER ::= { xcmCOInternetPOP3 59 }
xcmCOInternetPOP3MaxOutFragments 
    OBJECT IDENTIFIER ::= { xcmCOInternetPOP3 60 }
xcmCOInternetPOP3MaxInAttachments 
    OBJECT IDENTIFIER ::= { xcmCOInternetPOP3 61 }
xcmCOInternetPOP3MaxOutAttachments 
    OBJECT IDENTIFIER ::= { xcmCOInternetPOP3 62 }
xcmCOInternetPOP3MaxInputSize   
    OBJECT IDENTIFIER ::= { xcmCOInternetPOP3 63 }
xcmCOInternetPOP3MaxOutputSize  
    OBJECT IDENTIFIER ::= { xcmCOInternetPOP3 64 }
xcmCOInternetIMAP4HostName      
    OBJECT IDENTIFIER ::= { xcmCOInternetIMAP4 1 }
xcmCOInternetIMAP4HostAddress   
    OBJECT IDENTIFIER ::= { xcmCOInternetIMAP4 2 }
xcmCOInternetIMAP4PollInterval  
    OBJECT IDENTIFIER ::= { xcmCOInternetIMAP4 4 }
xcmCOInternetIMAP4Subject       
    OBJECT IDENTIFIER ::= { xcmCOInternetIMAP4 44 }
xcmCOInternetIMAP4SignatureLine 
    OBJECT IDENTIFIER ::= { xcmCOInternetIMAP4 45 }
xcmCOInternetIMAP4UserName      
    OBJECT IDENTIFIER ::= { xcmCOInternetIMAP4 47 }
xcmCOInternetIMAP4Password      
    OBJECT IDENTIFIER ::= { xcmCOInternetIMAP4 48 }
xcmCOInternetIMAP4MaxInputText  
    OBJECT IDENTIFIER ::= { xcmCOInternetIMAP4 50 }
xcmCOInternetIMAP4MaxInputAttach 
    OBJECT IDENTIFIER ::= { xcmCOInternetIMAP4 51 }
xcmCOInternetIMAP4MaxOutputText 
    OBJECT IDENTIFIER ::= { xcmCOInternetIMAP4 52 }
xcmCOInternetIMAP4MaxOutputAttach 
    OBJECT IDENTIFIER ::= { xcmCOInternetIMAP4 53 }
xcmCOInternetIMAP4ConfirmRequest 
    OBJECT IDENTIFIER ::= { xcmCOInternetIMAP4 54 }
xcmCOInternetIMAP4ConfirmReply  
    OBJECT IDENTIFIER ::= { xcmCOInternetIMAP4 55 }
xcmCOInternetIMAP4ConfirmTimeout 
    OBJECT IDENTIFIER ::= { xcmCOInternetIMAP4 56 }
xcmCOInternetIMAP4FeatureReply  
    OBJECT IDENTIFIER ::= { xcmCOInternetIMAP4 57 }
xcmCOInternetIMAP4MailAddress   
    OBJECT IDENTIFIER ::= { xcmCOInternetIMAP4 58 }
xcmCOInternetIMAP4MaxInFragments 
    OBJECT IDENTIFIER ::= { xcmCOInternetIMAP4 59 }
xcmCOInternetIMAP4MaxOutFragments 
    OBJECT IDENTIFIER ::= { xcmCOInternetIMAP4 60 }
xcmCOInternetIMAP4MaxInAttachments 
    OBJECT IDENTIFIER ::= { xcmCOInternetIMAP4 61 }
xcmCOInternetIMAP4MaxOutAttachments 
    OBJECT IDENTIFIER ::= { xcmCOInternetIMAP4 62 }
xcmCOInternetIMAP4MaxInputSize   
    OBJECT IDENTIFIER ::= { xcmCOInternetIMAP4 63 }
xcmCOInternetIMAP4MaxOutputSize  
    OBJECT IDENTIFIER ::= { xcmCOInternetIMAP4 64 }
xcmCOInternetNTPHostName        
    OBJECT IDENTIFIER ::= { xcmCOInternetNTP 1 }
xcmCOInternetNTPHostAddress    
    OBJECT IDENTIFIER ::= { xcmCOInternetNTP 2 }
xcmCOInternetNTPv6HostAddress   
    OBJECT IDENTIFIER ::= { xcmCOInternetNTP 3 }
xcmCOInternetNTPPort            
    OBJECT IDENTIFIER ::= { xcmCOInternetNTP 4 }
xcmCOInternetNTPGMTOffset       
    OBJECT IDENTIFIER ::= { xcmCOInternetNTP 5 }
xcmCOInternetNTPPollInterval    
    OBJECT IDENTIFIER ::= { xcmCOInternetNTP 6 }
xcmCOInternetNTPSkewTime        
    OBJECT IDENTIFIER ::= { xcmCOInternetNTP 7 }
xcmCOInternetWINSDomainName     
    OBJECT IDENTIFIER ::= { xcmCOInternetWINS 1 }
xcmCOInternetWINSLanguage       
    OBJECT IDENTIFIER ::= { xcmCOInternetWINS 3 }
xcmCOInternetWINSCharset        
    OBJECT IDENTIFIER ::= { xcmCOInternetWINS 4 }
xcmCOInternetWINSServerName     
    OBJECT IDENTIFIER ::= { xcmCOInternetWINS 5 }
xcmCOInternetWINSServerAddress  
    OBJECT IDENTIFIER ::= { xcmCOInternetWINS 6 }
xcmCOInternetWINSServerSocket   
    OBJECT IDENTIFIER ::= { xcmCOInternetWINS 7 }
xcmCOInternetLDAPLanguage       
    OBJECT IDENTIFIER ::= { xcmCOInternetLDAP 3 }
xcmCOInternetLDAPCharset        
    OBJECT IDENTIFIER ::= { xcmCOInternetLDAP 4 }
xcmCOInternetLDAPServerName     
    OBJECT IDENTIFIER ::= { xcmCOInternetLDAP 5 }
xcmCOInternetLDAPServerAddress  
    OBJECT IDENTIFIER ::= { xcmCOInternetLDAP 6 }
xcmCOInternetLDAPServerSocket   
    OBJECT IDENTIFIER ::= { xcmCOInternetLDAP 7 }
xcmCOInternetLDAPPollInterval   
    OBJECT IDENTIFIER ::= { xcmCOInternetLDAP 8 }
xcmCOInternetLDAPBindDN         
    OBJECT IDENTIFIER ::= { xcmCOInternetLDAP 11 }
xcmCOInternetLDAPBindPassword   
    OBJECT IDENTIFIER ::= { xcmCOInternetLDAP 12 }
xcmCOInternetLDAPBaseDN         
    OBJECT IDENTIFIER ::= { xcmCOInternetLDAP 13 }
xcmCOInternetLDAPPrinterName    
    OBJECT IDENTIFIER ::= { xcmCOInternetLDAP 21 }
xcmCOInternetLDAPPrinterClass   
    OBJECT IDENTIFIER ::= { xcmCOInternetLDAP 22 }
xcmCOInternetLDAPAttributeName  
    OBJECT IDENTIFIER ::= { xcmCOInternetLDAP 31 }
xcmCOInternetLDAPAttributeType  
    OBJECT IDENTIFIER ::= { xcmCOInternetLDAP 32 }
xcmCOInternetLDAPAttributeInt   
    OBJECT IDENTIFIER ::= { xcmCOInternetLDAP 33 }
xcmCOInternetLDAPAttributeStr   
    OBJECT IDENTIFIER ::= { xcmCOInternetLDAP 34 }
xcmCOInternetLDAPMaxSearchResult 
    OBJECT IDENTIFIER ::= { xcmCOInternetLDAP 35 }
xcmCOInternetLDAPSearchTimeout  
    OBJECT IDENTIFIER ::= { xcmCOInternetLDAP 36 }
xcmCOInternetSSDPCacheTimeout   
    OBJECT IDENTIFIER ::= { xcmCOInternetUpnpSSDP 1 }
xcmCOInternetSSDPTimeToLive     
    OBJECT IDENTIFIER ::= { xcmCOInternetUpnpSSDP 2 }
xcmCOInternetSSDPServerVersion  
    OBJECT IDENTIFIER ::= { xcmCOInternetUpnpSSDP 3 }
xcmCOInternetSLPLanguage        
    OBJECT IDENTIFIER ::= { xcmCOInternetSLP 3 }
xcmCOInternetSLPCharset         
    OBJECT IDENTIFIER ::= { xcmCOInternetSLP 4 }
xcmCOInternetSLPServerName      
    OBJECT IDENTIFIER ::= { xcmCOInternetSLP 5 }
xcmCOInternetSLPServerAddress   
    OBJECT IDENTIFIER ::= { xcmCOInternetSLP 6 }
xcmCOInternetSLPServerSocket    
    OBJECT IDENTIFIER ::= { xcmCOInternetSLP 7 }
xcmCOInternetSLPPollInterval    
    OBJECT IDENTIFIER ::= { xcmCOInternetSLP 8 }
xcmCOInternetSLPMaxMulticastTime 
    OBJECT IDENTIFIER ::= { xcmCOInternetSLP 10 }
xcmCOInternetSLPDAFindStartWait  
    OBJECT IDENTIFIER ::= { xcmCOInternetSLP 11 }
xcmCOInternetSLPInitialRetryWait 
    OBJECT IDENTIFIER ::= { xcmCOInternetSLP 12 }
xcmCOInternetSLPMaxUnicastTime   
    OBJECT IDENTIFIER ::= { xcmCOInternetSLP 13 }
xcmCOInternetSLPDAHeartbeatTime  
    OBJECT IDENTIFIER ::= { xcmCOInternetSLP 14 }
xcmCOInternetSLPDAFindActiveWait 
    OBJECT IDENTIFIER ::= { xcmCOInternetSLP 15 }
xcmCOInternetSLPRegPassiveWait   
    OBJECT IDENTIFIER ::= { xcmCOInternetSLP 16 }
xcmCOInternetSLPRegActiveWait    
    OBJECT IDENTIFIER ::= { xcmCOInternetSLP 17 }
xcmCOInternetSLPCloseConnWait    
    OBJECT IDENTIFIER ::= { xcmCOInternetSLP 18 }
xcmCOInternetSLPCacheReplyTime   
    OBJECT IDENTIFIER ::= { xcmCOInternetSLP 20 }
xcmCOInternetSLPMaxRegLifetime   
    OBJECT IDENTIFIER ::= { xcmCOInternetSLP 21 }
xcmCOInternetSLPDAFindRetryWait  
    OBJECT IDENTIFIER ::= { xcmCOInternetSLP 22 }
xcmCOInternetSLPMaxDARequestTime 
    OBJECT IDENTIFIER ::= { xcmCOInternetSLP 23 }
xcmCOInternetSLPMulticastEnable  
    OBJECT IDENTIFIER ::= { xcmCOInternetSLP 30 }
xcmCOInternetSLPMulticastRadius  
    OBJECT IDENTIFIER ::= { xcmCOInternetSLP 31 }
xcmCOInternetSLPPathMTUSize      
    OBJECT IDENTIFIER ::= { xcmCOInternetSLP 32 }
xcmCOInternetSLPScopeName        
    OBJECT IDENTIFIER ::= { xcmCOInternetSLP 40 }
xcmCOInternetSLPScopeKey         
    OBJECT IDENTIFIER ::= { xcmCOInternetSLP 41 }
xcmCOInternetSLPAttributesEnable  
    OBJECT IDENTIFIER ::= { xcmCOInternetSLP 50 }
xcmCOInternetOsfDceKerberosRealm 
    OBJECT IDENTIFIER ::= { xcmCOInternetOsfDceKerberos 1 }
--
--
xcmCOAppletalkSuite
    OBJECT IDENTIFIER ::= { xcmCommsConfigTC 18 }
xcmCOAppletalkDatalinks
    OBJECT IDENTIFIER ::= { xcmCOAppletalkSuite 1200 }
xcmCOAppletalkLLAP              
    OBJECT IDENTIFIER ::= { xcmCOAppletalkSuite 1201 }
xcmCOAppletalkELAP              
    OBJECT IDENTIFIER ::= { xcmCOAppletalkSuite 1202 }
xcmCOAppletalkTLAP              
    OBJECT IDENTIFIER ::= { xcmCOAppletalkSuite 1203 }
xcmCOAppletalkPhase             
    OBJECT IDENTIFIER ::= { xcmCOAppletalkSuite 1211 }
xcmCOAppletalkTransports
    OBJECT IDENTIFIER ::= { xcmCOAppletalkSuite 1400 }
xcmCOAppletalkDDP               
    OBJECT IDENTIFIER ::= { xcmCOAppletalkSuite 1301 }
xcmCOAppletalkAARP              
    OBJECT IDENTIFIER ::= { xcmCOAppletalkSuite 1303 }
xcmCOAppletalkATP               
    OBJECT IDENTIFIER ::= { xcmCOAppletalkSuite 1401 }
xcmCOAppletalkADSP              
    OBJECT IDENTIFIER ::= { xcmCOAppletalkSuite 1402 }
xcmCOAppletalkRTMP              
    OBJECT IDENTIFIER ::= { xcmCOAppletalkSuite 1403 }
xcmCOAppletalkAEP               
    OBJECT IDENTIFIER ::= { xcmCOAppletalkSuite 1404 }
xcmCOAppletalkNBP               
    OBJECT IDENTIFIER ::= { xcmCOAppletalkSuite 1405 }
xcmCOAppletalkDDPAddress        
    OBJECT IDENTIFIER ::= { xcmCOAppletalkDDP 1 }
xcmCOAppletalkDDPSocketAddress  
    OBJECT IDENTIFIER ::= { xcmCOAppletalkDDPAddress 1 }
xcmCOAppletalkDDPDatalinks      
    OBJECT IDENTIFIER ::= { xcmCOAppletalkDDP 12 }
xcmCOAppletalkNBPHostName       
    OBJECT IDENTIFIER ::= { xcmCOAppletalkNBP 1 }
xcmCOAppletalkNBPLanguage       
    OBJECT IDENTIFIER ::= { xcmCOAppletalkNBP 3 }
xcmCOAppletalkNBPCharset        
    OBJECT IDENTIFIER ::= { xcmCOAppletalkNBP 4 }
xcmCOAppletalkNBPObject         
    OBJECT IDENTIFIER ::= { xcmCOAppletalkNBP 11 }
xcmCOAppletalkNBPType           
    OBJECT IDENTIFIER ::= { xcmCOAppletalkNBP 12 }
xcmCOAppletalkNBPZone           
    OBJECT IDENTIFIER ::= { xcmCOAppletalkNBP 13 }
xcmCOAppletalkNBPNetwork        
    OBJECT IDENTIFIER ::= { xcmCOAppletalkNBP 21 }
xcmCOAppletalkNBPNode           
    OBJECT IDENTIFIER ::= { xcmCOAppletalkNBP 22 }
xcmCOAppletalkNBPSocket         
    OBJECT IDENTIFIER ::= { xcmCOAppletalkNBP 23 }
xcmCOAppletalkNBPZoneToNetworks 
    OBJECT IDENTIFIER ::= { xcmCOAppletalkNBP 31 }
xcmCOAppletalkApplications
    OBJECT IDENTIFIER ::= { xcmCOAppletalkSuite 1700 }
xcmCOAppletalkASP               
    OBJECT IDENTIFIER ::= { xcmCOAppletalkSuite 1501 }
xcmCOAppletalkZIP               
    OBJECT IDENTIFIER ::= { xcmCOAppletalkSuite 1502 }
xcmCOAppletalkPAP               
    OBJECT IDENTIFIER ::= { xcmCOAppletalkSuite 1503 }
xcmCOAppletalkSNMP              
    OBJECT IDENTIFIER ::= { xcmCOAppletalkSuite 1510 }
xcmCOAppletalkSNMPv1            
    OBJECT IDENTIFIER ::= { xcmCOAppletalkSuite 1511 }
xcmCOAppletalkSNMPv2            
    OBJECT IDENTIFIER ::= { xcmCOAppletalkSuite 1512 }
xcmCOAppletalkSNMPv3            
    OBJECT IDENTIFIER ::= { xcmCOAppletalkSuite 1513 }
xcmCOAppletalkAFP               
    OBJECT IDENTIFIER ::= { xcmCOAppletalkSuite 1601 }
xcmCOAppletalkPS                
    OBJECT IDENTIFIER ::= { xcmCOAppletalkSuite 1602 }
xcmCOAppletalkPAPHostName       
    OBJECT IDENTIFIER ::= { xcmCOAppletalkPAP 1 }
xcmCOAppletalkPAPHostAddress    
    OBJECT IDENTIFIER ::= { xcmCOAppletalkPAP 2 }
xcmCOAppletalkPAPListenSocket   
    OBJECT IDENTIFIER ::= { xcmCOAppletalkPAP 3 }
xcmCOAppletalkPAPMaxClients     
    OBJECT IDENTIFIER ::= { xcmCOAppletalkPAP 4 }
xcmCOAppletalkPAPMaxPrinters    
    OBJECT IDENTIFIER ::= { xcmCOAppletalkPAP 5 }
xcmCOAppletalkPAPObject         
    OBJECT IDENTIFIER ::= { xcmCOAppletalkPAP 11 }
xcmCOAppletalkPAPType           
    OBJECT IDENTIFIER ::= { xcmCOAppletalkPAP 12 }
xcmCOAppletalkPAPZone           
    OBJECT IDENTIFIER ::= { xcmCOAppletalkPAP 13 }
xcmCOAppletalkPAPNetwork        
    OBJECT IDENTIFIER ::= { xcmCOAppletalkPAP 21 }
xcmCOAppletalkPAPNode           
    OBJECT IDENTIFIER ::= { xcmCOAppletalkPAP 22 }
xcmCOAppletalkPAPSpool          
    OBJECT IDENTIFIER ::= { xcmCOAppletalkPAP 31 }
xcmCOAppletalkPAPMaxSpool       
    OBJECT IDENTIFIER ::= { xcmCOAppletalkPAP 32 }
xcmCOAppletalkPAPJobTimeout     
    OBJECT IDENTIFIER ::= { xcmCOAppletalkPAP 40 }
xcmCOAppletalkPAPAutoSwitch     
    OBJECT IDENTIFIER ::= { xcmCOAppletalkPAP 41 }
xcmCOAppletalkPAPBinaryPS       
    OBJECT IDENTIFIER ::= { xcmCOAppletalkPAP 42 }
xcmCOAppletalkPAPDefaultPDL     
    OBJECT IDENTIFIER ::= { xcmCOAppletalkPAP 43 }
--
--
xcmCONetwareSuite
    OBJECT IDENTIFIER ::= { xcmCommsConfigTC 19 }
xcmCONetwareDatalinks
    OBJECT IDENTIFIER ::= { xcmCONetwareSuite 1200 }
xcmCONetwareTransports
    OBJECT IDENTIFIER ::= { xcmCONetwareSuite 1400 }
xcmCONetwareIPX                 
    OBJECT IDENTIFIER ::= { xcmCONetwareSuite 1301 }
xcmCONetwareIP                
OBJECT IDENTIFIER  ::= {xcmCONetwareSuite 1302}    
xcmCONetwareSPX                 
    OBJECT IDENTIFIER ::= { xcmCONetwareSuite 1402 }
xcmCONetwareRIP                 
    OBJECT IDENTIFIER ::= { xcmCONetwareSuite 1403 }
xcmCONetwareEcho                
    OBJECT IDENTIFIER ::= { xcmCONetwareSuite 1404 }
xcmCONetwareIPXAddress          
    OBJECT IDENTIFIER ::= { xcmCONetwareIPX 1 }
xcmCONetwareIPXSocketAddress    
    OBJECT IDENTIFIER ::= { xcmCONetwareIPXAddress 1 }
xcmCONetwareIPXDatalinks        
    OBJECT IDENTIFIER ::= { xcmCONetwareIPX 12 }
xcmCONetwareApplications
    OBJECT IDENTIFIER ::= { xcmCONetwareSuite 1700 }
xcmCONetwareNCP                 
    OBJECT IDENTIFIER ::= { xcmCONetwareSuite 1501 }
xcmCONetwareNetbios             
    OBJECT IDENTIFIER ::= { xcmCONetwareSuite 1502 }
xcmCONetwarePServer             
    OBJECT IDENTIFIER ::= { xcmCONetwareSuite 1503 }
xcmCONetwareFServer             
    OBJECT IDENTIFIER ::= { xcmCONetwareSuite 1504 }
xcmCONetwareMHS                 
    OBJECT IDENTIFIER ::= { xcmCONetwareSuite 1505 }
xcmCONetwareBindery             
    OBJECT IDENTIFIER ::= { xcmCONetwareSuite 1507 }
xcmCONetwareNDS                 
    OBJECT IDENTIFIER ::= { xcmCONetwareSuite 1508 }
xcmCONetwareRPrinter            
    OBJECT IDENTIFIER ::= { xcmCONetwareSuite 1509 }
xcmCONetwareSNMP                
    OBJECT IDENTIFIER ::= { xcmCONetwareSuite 1510 }
xcmCONetwareSNMPv1              
    OBJECT IDENTIFIER ::= { xcmCONetwareSuite 1511 }
xcmCONetwareSNMPv2              
    OBJECT IDENTIFIER ::= { xcmCONetwareSuite 1512 }
xcmCONetwareSNMPv3              
    OBJECT IDENTIFIER ::= { xcmCONetwareSuite 1513 }
xcmCONetwareSAP                 
    OBJECT IDENTIFIER ::= { xcmCONetwareSuite 1591 }
xcmCONetwareNDSIP                 
    OBJECT IDENTIFIER ::= { xcmCONetwareSuite 1600 }
xcmCONetwareNDSIPHostname        
    OBJECT IDENTIFIER ::= { xcmCONetwareNDSIP 1 }
xcmCONetwareNDSIPAddress                
    OBJECT IDENTIFIER ::= { xcmCONetwareNDSIP 2 }
xcmCONetwareNDSIPUseHostname          
    OBJECT IDENTIFIER ::= { xcmCONetwareNDSIP 3 }
xcmCONetwarePServerName         
    OBJECT IDENTIFIER ::= { xcmCONetwarePServer 1 }
xcmCONetwarePServerPassword     
    OBJECT IDENTIFIER ::= { xcmCONetwarePServer 2 }
xcmCONetwarePServerQueueName    
    OBJECT IDENTIFIER ::= { xcmCONetwarePServer 3 }
xcmCONetwarePServerPollInterval 
    OBJECT IDENTIFIER ::= { xcmCONetwarePServer 4 }
xcmCONetwarePServerFindFServer  
    OBJECT IDENTIFIER ::= { xcmCONetwarePServer 5 }
xcmCONetwarePServerMaxFServers  
    OBJECT IDENTIFIER ::= { xcmCONetwarePServer 6 }
xcmCONetwarePServerNotify       
    OBJECT IDENTIFIER ::= { xcmCONetwarePServer 7 }
xcmCONetwarePServerNotifyLocale 
    OBJECT IDENTIFIER ::= { xcmCONetwarePServerNotify 1 }
xcmCONetwarePServerMaxPrinters  
    OBJECT IDENTIFIER ::= { xcmCONetwarePServer 8 }
xcmCONetwarePServerSuspendPoll
OBJECT IDENTIFIER ::= { xcmCONetwarePServer 9 }
xcmCONetwarePServerSuspendPollInterval
OBJECT IDENTIFIER ::= { xcmCONetwarePServer 10 }
xcmCONetwarePServerSpool        
    OBJECT IDENTIFIER ::= { xcmCONetwarePServer 31 }
xcmCONetwarePServerMaxSpool     
    OBJECT IDENTIFIER ::= { xcmCONetwarePServer 32 }
xcmCONetwarePServerJobTimeout   
    OBJECT IDENTIFIER ::= { xcmCONetwarePServer 40 }
xcmCONetwarePServerAutoSwitch   
    OBJECT IDENTIFIER ::= { xcmCONetwarePServer 41 }
xcmCONetwarePServerBinaryPS     
    OBJECT IDENTIFIER ::= { xcmCONetwarePServer 42 }
xcmCONetwarePServerDefaultPDL   
    OBJECT IDENTIFIER ::= { xcmCONetwarePServer 43 }
xcmCONetwarePServerConfigTimeout 
    OBJECT IDENTIFIER ::= { xcmCONetwarePServer 50 }
xcmCONetwareRPrinterName        
    OBJECT IDENTIFIER ::= { xcmCONetwareRPrinter 1 }
xcmCONetwareRPrinterNumber      
    OBJECT IDENTIFIER ::= { xcmCONetwareRPrinter 2 }
xcmCONetwareRPrinterPollInterval 
    OBJECT IDENTIFIER ::= { xcmCONetwareRPrinter 3 }
xcmCONetwareRPrinterJobTimeout  
    OBJECT IDENTIFIER ::= { xcmCONetwareRPrinter 40 }
xcmCONetwareRPrinterAutoSwitch  
    OBJECT IDENTIFIER ::= { xcmCONetwareRPrinter 41 }
xcmCONetwareRPrinterBinaryPS    
    OBJECT IDENTIFIER ::= { xcmCONetwareRPrinter 42 }
xcmCONetwareRPrinterDefaultPDL  
    OBJECT IDENTIFIER ::= { xcmCONetwareRPrinter 43 }
xcmCONetwareFServerName         
    OBJECT IDENTIFIER ::= { xcmCONetwareFServer 1 }
xcmCONetwareFServerPassword     
    OBJECT IDENTIFIER ::= { xcmCONetwareFServer 2 }
xcmCONetwareFServerAddress      
    OBJECT IDENTIFIER ::= { xcmCONetwareFServer 3 }
xcmCONetwareBinderyLanguage     
    OBJECT IDENTIFIER ::= { xcmCONetwareBindery 3 }
xcmCONetwareBinderyCharset      
    OBJECT IDENTIFIER ::= { xcmCONetwareBindery 4 }
xcmCONetwareNDSTreeName         
    OBJECT IDENTIFIER ::= { xcmCONetwareNDS 1 }
xcmCONetwareNDSContext          
    OBJECT IDENTIFIER ::= { xcmCONetwareNDS 2 }
xcmCONetwareNDSLanguage         
    OBJECT IDENTIFIER ::= { xcmCONetwareNDS 3 }
xcmCONetwareNDSCharset          
    OBJECT IDENTIFIER ::= { xcmCONetwareNDS 4 }
xcmCONetwareSAPInterval         
    OBJECT IDENTIFIER ::= { xcmCONetwareSAP 1 }
xcmCONetwareSAPNumber           
    OBJECT IDENTIFIER ::= { xcmCONetwareSAP 2 }
xcmCONetwareSAPValueString      
    OBJECT IDENTIFIER ::= { xcmCONetwareSAP 3 }
xcmCONetwareSAPUnitName         
    OBJECT IDENTIFIER ::= { xcmCONetwareSAP 4 }
xcmCONetwareSAPFormatID         
    OBJECT IDENTIFIER ::= { xcmCONetwareSAP 5 }
xcmCONetwareSAPSuspend
OBJECT IDENTIFIER ::= { xcmCONetwareSAP 6 }
xcmCONetwareSAPSuspendInterval
OBJECT IDENTIFIER ::= { xcmCONetwareSAP 7 }
--
--
xcmCOVinesSuite
    OBJECT IDENTIFIER ::= { xcmCommsConfigTC 20 }
xcmCOVinesDatalinks
    OBJECT IDENTIFIER ::= { xcmCOVinesSuite 1200 }
xcmCOVinesTransports
    OBJECT IDENTIFIER ::= { xcmCOVinesSuite 1400 }
xcmCOVinesVIP                   
    OBJECT IDENTIFIER ::= { xcmCOVinesSuite 1301 }
xcmCOVinesVICP                  
    OBJECT IDENTIFIER ::= { xcmCOVinesSuite 1302 }
xcmCOVinesVARP                  
    OBJECT IDENTIFIER ::= { xcmCOVinesSuite 1303 }
xcmCOVinesIP                    
    OBJECT IDENTIFIER ::= { xcmCOVinesSuite 1311 }
xcmCOVinesICMP                  
    OBJECT IDENTIFIER ::= { xcmCOVinesSuite 1312 }
xcmCOVinesARP                   
    OBJECT IDENTIFIER ::= { xcmCOVinesSuite 1313 }
xcmCOVinesVRTP                  
    OBJECT IDENTIFIER ::= { xcmCOVinesSuite 1314 }
xcmCOVinesVIPC                  
    OBJECT IDENTIFIER ::= { xcmCOVinesSuite 1401 }
xcmCOVinesVSPP                  
    OBJECT IDENTIFIER ::= { xcmCOVinesSuite 1402 }
xcmCOVinesUDP                   
    OBJECT IDENTIFIER ::= { xcmCOVinesSuite 1411 }
xcmCOVinesTCP                   
    OBJECT IDENTIFIER ::= { xcmCOVinesSuite 1412 }
xcmCOVinesApplications
    OBJECT IDENTIFIER ::= { xcmCOVinesSuite 1700 }
xcmCOVinesNetRPC                
    OBJECT IDENTIFIER ::= { xcmCOVinesSuite 1501 }
xcmCOVinesSocket                
    OBJECT IDENTIFIER ::= { xcmCOVinesSuite 1502 }
xcmCOVinesNetbios               
    OBJECT IDENTIFIER ::= { xcmCOVinesSuite 1503 }
xcmCOVinesPrint                 
    OBJECT IDENTIFIER ::= { xcmCOVinesSuite 1701 }
xcmCOVinesFiling                
    OBJECT IDENTIFIER ::= { xcmCOVinesSuite 1702 }
xcmCOVinesMail                  
    OBJECT IDENTIFIER ::= { xcmCOVinesSuite 1703 }
xcmCOVinesStreetTalk            
    OBJECT IDENTIFIER ::= { xcmCOVinesSuite 1704 }
xcmCOVinesPrintName             
    OBJECT IDENTIFIER ::= { xcmCOVinesPrint 1 }
xcmCOVinesPrintPassword         
    OBJECT IDENTIFIER ::= { xcmCOVinesPrint 2 }
xcmCOVinesPrintPollInterval     
    OBJECT IDENTIFIER ::= { xcmCOVinesPrint 4 }
xcmCOVinesPrintMaxServers       
    OBJECT IDENTIFIER ::= { xcmCOVinesPrint 5 }
xcmCOVinesPrintServerName       
    OBJECT IDENTIFIER ::= { xcmCOVinesPrint 6 }
xcmCOVinesPrintSpool            
    OBJECT IDENTIFIER ::= { xcmCOVinesPrint 31 }
xcmCOVinesPrintMaxSpool         
    OBJECT IDENTIFIER ::= { xcmCOVinesPrint 32 }
xcmCOVinesPrintJobTimeout       
    OBJECT IDENTIFIER ::= { xcmCOVinesPrint 40 }
xcmCOVinesPrintAutoSwitch       
    OBJECT IDENTIFIER ::= { xcmCOVinesPrint 41 }
xcmCOVinesPrintBinaryPS         
    OBJECT IDENTIFIER ::= { xcmCOVinesPrint 42 }
xcmCOVinesPrintDefaultPDL       
    OBJECT IDENTIFIER ::= { xcmCOVinesPrint 43 }
xcmCOVinesStreetTalkLanguage    
    OBJECT IDENTIFIER ::= { xcmCOVinesStreetTalk 3 }
xcmCOVinesStreetTalkCharset     
    OBJECT IDENTIFIER ::= { xcmCOVinesStreetTalk 4 }
--
--
xcmCONetbiosSuite
    OBJECT IDENTIFIER ::= { xcmCommsConfigTC 25 }
xcmCONetbiosDatalinks
    OBJECT IDENTIFIER ::= { xcmCONetbiosSuite 1200 }
xcmCONetbiosTransports
    OBJECT IDENTIFIER ::= { xcmCONetbiosSuite 1400 }
xcmCONetbiosNBP                 
    OBJECT IDENTIFIER ::= { xcmCONetbiosSuite 1501 }
xcmCONetbiosSNMP                
    OBJECT IDENTIFIER ::= { xcmCONetbiosSuite 1510 }
xcmCONetbiosSNMPv1              
    OBJECT IDENTIFIER ::= { xcmCONetbiosSuite 1511 }
xcmCONetbiosSNMPv2              
    OBJECT IDENTIFIER ::= { xcmCONetbiosSuite 1512 }
xcmCONetbiosSNMPv3              
    OBJECT IDENTIFIER ::= { xcmCONetbiosSuite 1513 }
xcmCONetbiosIntEndNode           
    OBJECT IDENTIFIER ::= { xcmCONetbiosSuite 1520 }
xcmCONetbiosIntNameServer        
    OBJECT IDENTIFIER ::= { xcmCONetbiosSuite 1521 }
xcmCONetbiosIntDistServer        
    OBJECT IDENTIFIER ::= { xcmCONetbiosSuite 1522 }
xcmCONetbiosSAP                 
    OBJECT IDENTIFIER ::= { xcmCONetbiosSuite 1591 }
xcmCONetbiosApplications
    OBJECT IDENTIFIER ::= { xcmCONetbiosSuite 1700 }
xcmCONetbiosSMB                 
    OBJECT IDENTIFIER ::= { xcmCONetbiosSuite 1701 }
xcmCONetbiosSMBPClient          
    OBJECT IDENTIFIER ::= { xcmCONetbiosSuite 1702 }
xcmCONetbiosSMBPServer          
    OBJECT IDENTIFIER ::= { xcmCONetbiosSuite 1703 }
xcmCONetbiosSMBFClient          
    OBJECT IDENTIFIER ::= { xcmCONetbiosSuite 1704 }
xcmCONetbiosSMBFServer          
    OBJECT IDENTIFIER ::= { xcmCONetbiosSuite 1705 }
xcmCONetbiosSMBDomain          
    OBJECT IDENTIFIER ::= { xcmCONetbiosSuite 1706 }
xcmCONetbiosNBPName             
    OBJECT IDENTIFIER ::= { xcmCONetbiosNBP 1 }
xcmCONetbiosNBPGroupName        
    OBJECT IDENTIFIER ::= { xcmCONetbiosNBP 2 }
xcmCONetbiosNBPPassword         
    OBJECT IDENTIFIER ::= { xcmCONetbiosNBP 3 }
xcmCONetbiosNBPService          
    OBJECT IDENTIFIER ::= { xcmCONetbiosNBP 4 }
xcmCONetbiosNBPRemark           
    OBJECT IDENTIFIER ::= { xcmCONetbiosNBP 5 }
xcmCONetbiosNBPServiceRemark    
    OBJECT IDENTIFIER ::= { xcmCONetbiosNBP 6 }
xcmCONetbiosNBPIPCRemark        
    OBJECT IDENTIFIER ::= { xcmCONetbiosNBP 7 }
xcmCONetbiosNBPLanguage         
    OBJECT IDENTIFIER ::= { xcmCONetbiosNBP 8 }
xcmCONetbiosNBPCharset          
    OBJECT IDENTIFIER ::= { xcmCONetbiosNBP 9 }
xcmCONetbiosNBPOverNetbeui      
    OBJECT IDENTIFIER ::= { xcmCONetbiosNBP 11 }
xcmCONetbiosNBPOverInternet     
    OBJECT IDENTIFIER ::= { xcmCONetbiosNBP 12 }
xcmCONetbiosNBPOverNetware      
    OBJECT IDENTIFIER ::= { xcmCONetbiosNBP 13 }
xcmCONetbiosIntEndNodeAddress    
    OBJECT IDENTIFIER ::= { xcmCONetbiosIntEndNode 1 }
xcmCONetbiosIntEndNodeSource     
    OBJECT IDENTIFIER ::= { xcmCONetbiosIntEndNode 2 }
xcmCONetbiosIntNodeType         
    OBJECT IDENTIFIER ::= { xcmCONetbiosIntEndNode 3 }
xcmCONetbiosIntNodeTypeSource   
    OBJECT IDENTIFIER ::= { xcmCONetbiosIntEndNode 4 }
xcmCONetbiosIntNodeScope         
    OBJECT IDENTIFIER ::= { xcmCONetbiosIntEndNode 5 }
xcmCONetbiosIntNodeScopeSource   
    OBJECT IDENTIFIER ::= { xcmCONetbiosIntEndNode 6 }
xcmCONetbiosIntNameServerAddress 
    OBJECT IDENTIFIER ::= { xcmCONetbiosIntNameServer 1 }
xcmCONetbiosIntNameServerSource  
    OBJECT IDENTIFIER ::= { xcmCONetbiosIntNameServer 2 }
xcmCONetbiosIntDistServerAddress 
    OBJECT IDENTIFIER ::= { xcmCONetbiosIntDistServer 1 }
xcmCONetbiosIntDistServerSource  
    OBJECT IDENTIFIER ::= { xcmCONetbiosIntDistServer 2 }
xcmCONetbiosSAPInterval         
    OBJECT IDENTIFIER ::= { xcmCONetbiosSAP 1 }
xcmCONetbiosSMBPClientMaxConns  
    OBJECT IDENTIFIER ::= { xcmCONetbiosSMBPClient 4 }
xcmCONetbiosSMBPClientSpool     
    OBJECT IDENTIFIER ::= { xcmCONetbiosSMBPClient 31 }
xcmCONetbiosSMBPClientMaxSpool  
    OBJECT IDENTIFIER ::= { xcmCONetbiosSMBPClient 32 }
xcmCONetbiosSMBPClientJobTimeout 
    OBJECT IDENTIFIER ::= { xcmCONetbiosSMBPClient 40 }
xcmCONetbiosSMBPClientAutoSwitch 
    OBJECT IDENTIFIER ::= { xcmCONetbiosSMBPClient 41 }
xcmCONetbiosSMBPClientBinaryPS   
    OBJECT IDENTIFIER ::= { xcmCONetbiosSMBPClient 42 }
xcmCONetbiosSMBPClientDefaultPDL 
    OBJECT IDENTIFIER ::= { xcmCONetbiosSMBPClient 43 }
xcmCONetbiosSMBPServerMaxConns  
    OBJECT IDENTIFIER ::= { xcmCONetbiosSMBPServer 4 }
xcmCONetbiosSMBPServerSpool     
    OBJECT IDENTIFIER ::= { xcmCONetbiosSMBPServer 31 }
xcmCONetbiosSMBPServerMaxSpool  
    OBJECT IDENTIFIER ::= { xcmCONetbiosSMBPServer 32 }
xcmCONetbiosSMBPServerJobTimeout 
    OBJECT IDENTIFIER ::= { xcmCONetbiosSMBPServer 40 }
xcmCONetbiosSMBPServerAutoSwitch 
    OBJECT IDENTIFIER ::= { xcmCONetbiosSMBPServer 41 }
xcmCONetbiosSMBPServerBinaryPS   
    OBJECT IDENTIFIER ::= { xcmCONetbiosSMBPServer 42 }
xcmCONetbiosSMBPServerDefaultPDL 
    OBJECT IDENTIFIER ::= { xcmCONetbiosSMBPServer 43 }
xcmCONetbiosSMBFServerName      
    OBJECT IDENTIFIER ::= { xcmCONetbiosSMBFServer 1 }
--
--
xcmCONetbeuiSuite
    OBJECT IDENTIFIER ::= { xcmCommsConfigTC 26 }
xcmCONetbeuiDatalinks
    OBJECT IDENTIFIER ::= { xcmCONetbeuiSuite 1200 }
xcmCONetbeuiLLC                 
    OBJECT IDENTIFIER ::= { xcmCONetbeuiSuite 1201 }
xcmCONetbeuiDLC                 
    OBJECT IDENTIFIER ::= { xcmCONetbeuiSuite 1202 }
--
--
xcmCOSerialSuite
    OBJECT IDENTIFIER ::= { xcmCommsConfigTC 27 }
xcmCOSerialPhysical
    OBJECT IDENTIFIER ::= { xcmCOSerialSuite 1100 }
xcmCOSerialSignalType
    OBJECT IDENTIFIER ::= { xcmCOSerialSuite 1101 }
xcmCOSerialSignalOverride       
    OBJECT IDENTIFIER ::= { xcmCOSerialSignalType 1 }
xcmCOSerialSignalDetected       
    OBJECT IDENTIFIER ::= { xcmCOSerialSignalType 2 }
xcmCOSerialSignalAdaptive       
    OBJECT IDENTIFIER ::= { xcmCOSerialSignalType 3 }
xcmCOSerialSignalSupport        
    OBJECT IDENTIFIER ::= { xcmCOSerialSignalType 4 }
xcmCOSerialDevice
    OBJECT IDENTIFIER ::= { xcmCOSerialSuite 1102 }
xcmCOSerialDeviceName
    OBJECT IDENTIFIER ::= { xcmCOSerialDevice 1 }
xcmCOSerialSpeed
    OBJECT IDENTIFIER ::= { xcmCOSerialSuite 1103 }
xcmCOSerialSpeedOverride
    OBJECT IDENTIFIER ::= { xcmCOSerialSpeed 1 }
xcmCOSerialSpeedDetected
    OBJECT IDENTIFIER ::= { xcmCOSerialSpeed 2 }
xcmCOSerialSpeedAdaptive
    OBJECT IDENTIFIER ::= { xcmCOSerialSpeed 3 }
xcmCOSerialSpeedSupport
    OBJECT IDENTIFIER ::= { xcmCOSerialSpeed 4 }
xcmCOSerialMinSpeed
    OBJECT IDENTIFIER ::= { xcmCOSerialSpeed 5 }
xcmCOSerialMaxSpeed
    OBJECT IDENTIFIER ::= { xcmCOSerialSpeed 6 }
xcmCOSerialBidirectional
    OBJECT IDENTIFIER ::= { xcmCOSerialSuite 1104 }
xcmCOSerialInputTimeout         
    OBJECT IDENTIFIER ::= { xcmCOSerialSuite 1105 }
xcmCOSerialOutputTimeout
    OBJECT IDENTIFIER ::= { xcmCOSerialSuite 1106 }
xcmCOSerialConnectorType
    OBJECT IDENTIFIER ::= { xcmCOSerialSuite 1107 }
xcmCOSerialConnectorOverride    
    OBJECT IDENTIFIER ::= { xcmCOSerialConnectorType 1 }
xcmCOSerialConnectorDetected    
    OBJECT IDENTIFIER ::= { xcmCOSerialConnectorType 2 }
xcmCOSerialConnectorAdaptive    
    OBJECT IDENTIFIER ::= { xcmCOSerialConnectorType 3 }
xcmCOSerialMinInputChars        
    OBJECT IDENTIFIER ::= { xcmCOSerialSuite 1108 }
xcmCOSerialMaxInputChars        
    OBJECT IDENTIFIER ::= { xcmCOSerialSuite 1109 }
xcmCOSerialParity
    OBJECT IDENTIFIER ::= { xcmCOSerialSuite 1111 }
xcmCOSerialDataBits
    OBJECT IDENTIFIER ::= { xcmCOSerialSuite 1112 }
xcmCOSerialFlowControl
    OBJECT IDENTIFIER ::= { xcmCOSerialSuite 1113 }
xcmCOSerialStartBits
    OBJECT IDENTIFIER ::= { xcmCOSerialSuite 1114 }
xcmCOSerialStopBits
    OBJECT IDENTIFIER ::= { xcmCOSerialSuite 1115 }
xcmCOSerialInputPrime
    OBJECT IDENTIFIER ::= { xcmCOSerialSuite 1116 }
xcmCOSerialDTR                  
    OBJECT IDENTIFIER ::= { xcmCOSerialSuite 1121 }
xcmCOSerialDSR                  
    OBJECT IDENTIFIER ::= { xcmCOSerialSuite 1122 }
xcmCOSerialCTS                  
    OBJECT IDENTIFIER ::= { xcmCOSerialSuite 1123 }
xcmCOSerialRTS                  
    OBJECT IDENTIFIER ::= { xcmCOSerialSuite 1124 }
xcmCOSerialDatalinks
    OBJECT IDENTIFIER ::= { xcmCOSerialSuite 1200 }
xcmCOSerialProtocol
    OBJECT IDENTIFIER ::= { xcmCOSerialDatalinks 1 }
--
--
xcmCOParallelSuite
    OBJECT IDENTIFIER ::= { xcmCommsConfigTC 28 }
xcmCOParallelPhysical
    OBJECT IDENTIFIER ::= { xcmCOParallelSuite 1100 }
xcmCOParallelSignalType
    OBJECT IDENTIFIER ::= { xcmCOParallelSuite 1101 }
xcmCOParallelSignalOverride     
    OBJECT IDENTIFIER ::= { xcmCOParallelSignalType 1 }
xcmCOParallelSignalDetected     
    OBJECT IDENTIFIER ::= { xcmCOParallelSignalType 2 }
xcmCOParallelSignalAdaptive     
    OBJECT IDENTIFIER ::= { xcmCOParallelSignalType 3 }
xcmCOParallelSignalSupport      
    OBJECT IDENTIFIER ::= { xcmCOParallelSignalType 4 }
xcmCOParallelDevice
    OBJECT IDENTIFIER ::= { xcmCOParallelSuite 1102 }
xcmCOParallelDeviceName
    OBJECT IDENTIFIER ::= { xcmCOParallelDevice 1 }
xcmCOParallelDeviceID           
    OBJECT IDENTIFIER ::= { xcmCOParallelDevice 2 }
xcmCOParallelSpeed
    OBJECT IDENTIFIER ::= { xcmCOParallelSuite 1103 }
xcmCOParallelSpeedOverride
    OBJECT IDENTIFIER ::= { xcmCOParallelSpeed 1 }
xcmCOParallelSpeedDetected
    OBJECT IDENTIFIER ::= { xcmCOParallelSpeed 2 }
xcmCOParallelSpeedAdaptive
    OBJECT IDENTIFIER ::= { xcmCOParallelSpeed 3 }
xcmCOParallelSpeedSupport
    OBJECT IDENTIFIER ::= { xcmCOParallelSpeed 4 }
xcmCOParallelMinSpeed
    OBJECT IDENTIFIER ::= { xcmCOParallelSpeed 5 }
xcmCOParallelMaxSpeed
    OBJECT IDENTIFIER ::= { xcmCOParallelSpeed 6 }
xcmCOParallelBidirectional
    OBJECT IDENTIFIER ::= { xcmCOParallelSuite 1104 }
xcmCOParallelInputTimeout       
    OBJECT IDENTIFIER ::= { xcmCOParallelSuite 1105 }
xcmCOParallelOutputTimeout
    OBJECT IDENTIFIER ::= { xcmCOParallelSuite 1106 }
xcmCOParallelConnectorType
    OBJECT IDENTIFIER ::= { xcmCOParallelSuite 1107 }
xcmCOParallelConnectorOverride  
    OBJECT IDENTIFIER ::= { xcmCOParallelConnectorType 1 }
xcmCOParallelConnectorDetected  
    OBJECT IDENTIFIER ::= { xcmCOParallelConnectorType 2 }
xcmCOParallelConnectorAdaptive  
    OBJECT IDENTIFIER ::= { xcmCOParallelConnectorType 3 }
xcmCOParallelMinInputChars      
    OBJECT IDENTIFIER ::= { xcmCOParallelSuite 1108 }
xcmCOParallelMaxInputChars      
    OBJECT IDENTIFIER ::= { xcmCOParallelSuite 1109 }
xcmCOParallelParity
    OBJECT IDENTIFIER ::= { xcmCOParallelSuite 1111 }
xcmCOParallelDataBits
    OBJECT IDENTIFIER ::= { xcmCOParallelSuite 1112 }
xcmCOParallelFlowControl
    OBJECT IDENTIFIER ::= { xcmCOParallelSuite 1113 }
xcmCOParallelInputPrime
    OBJECT IDENTIFIER ::= { xcmCOParallelSuite 1116 }
xcmCOParallelHandshake
    OBJECT IDENTIFIER ::= { xcmCOParallelSuite 1117 }
xcmCOParallelDataStrobe
    OBJECT IDENTIFIER ::= { xcmCOParallelSuite 1118 }
xcmCOParallelDatalinks
    OBJECT IDENTIFIER ::= { xcmCOParallelSuite 1200 }
xcmCOParallelProtocol
    OBJECT IDENTIFIER ::= { xcmCOParallelDatalinks 1 }
--
--
xcmCODirectPrintSuite
    OBJECT IDENTIFIER ::= { xcmCommsConfigTC 29 }
xcmCODirectPrintPhysical
    OBJECT IDENTIFIER ::= { xcmCODirectPrintSuite 1100 }
xcmCODirectPrintDatalinks
    OBJECT IDENTIFIER ::= { xcmCODirectPrintSuite 1200 }
xcmCODirectPrintProtocol
    OBJECT IDENTIFIER ::= { xcmCODirectPrintDatalinks 1 }
    -- See: Adobe "Serial and Parallel Binary Communications Protocols"
--
--
xcmCOUsbSuite
    OBJECT IDENTIFIER ::= { xcmCommsConfigTC 30 }
xcmCOUsbPhysical
    OBJECT IDENTIFIER ::= { xcmCOUsbSuite 1100 }
xcmCOUsbDevice
    OBJECT IDENTIFIER ::= { xcmCOUsbSuite 1102 }
xcmCOUsbDeviceName
    OBJECT IDENTIFIER ::= { xcmCOUsbDevice 1 }
xcmCOUsbSpeed
    OBJECT IDENTIFIER ::= { xcmCOUsbSuite 1103 }
xcmCOUsbSpeedOverride
    OBJECT IDENTIFIER ::= { xcmCOUsbSpeed 1 }
xcmCOUsbSpeedDetected
    OBJECT IDENTIFIER ::= { xcmCOUsbSpeed 2 }
xcmCOUsbSpeedAdaptive
    OBJECT IDENTIFIER ::= { xcmCOUsbSpeed 3 }
xcmCOUsbSpeedSupport
    OBJECT IDENTIFIER ::= { xcmCOUsbSpeed 4 }
xcmCOUsbMinSpeed
    OBJECT IDENTIFIER ::= { xcmCOUsbSpeed 5 }
xcmCOUsbMaxSpeed
    OBJECT IDENTIFIER ::= { xcmCOUsbSpeed 6 }
xcmCOUsbBidirectional
    OBJECT IDENTIFIER ::= { xcmCOUsbSuite 1104 }
xcmCOUsbInputTimeout            
    OBJECT IDENTIFIER ::= { xcmCOUsbSuite 1105 }
xcmCOUsbOutputTimeout
    OBJECT IDENTIFIER ::= { xcmCOUsbSuite 1106 }
xcmCOUsbMinInputChars           
    OBJECT IDENTIFIER ::= { xcmCOUsbSuite 1108 }
xcmCOUsbMaxInputChars           
    OBJECT IDENTIFIER ::= { xcmCOUsbSuite 1109 }
xcmCOUsbDatalinks
    OBJECT IDENTIFIER ::= { xcmCOUsbSuite 1200 }
xcmCOUsbProtocol
    OBJECT IDENTIFIER ::= { xcmCOUsbDatalinks 1 }
--
--
--
xCmCommsConfigDummy OBJECT IDENTIFIER ::= { xcmCommsConfigTC 999 }
xCmSnmpNetbiosAddress OBJECT-TYPE
    SYNTAX      XcmSnmpNetbiosAddress
    MAX-ACCESS  not-accessible
    STATUS      current
    DESCRIPTION "Dummy - DO NOT USE"
    ::= { xCmCommsConfigDummy 1 }
xCmCommsConfigGroupSupport OBJECT-TYPE
    SYNTAX      XcmCommsConfigGroupSupport
    MAX-ACCESS  not-accessible
    STATUS      current
    DESCRIPTION "Dummy - DO NOT USE"
    ::= { xCmCommsConfigDummy 2 }
xCmCommsDirRecordType OBJECT-TYPE
    SYNTAX      XcmCommsDirRecordType
    MAX-ACCESS  not-accessible
    STATUS      current
    DESCRIPTION "Dummy - DO NOT USE"
    ::= { xCmCommsConfigDummy 3 }
xCmCommsDirAttributeType OBJECT-TYPE
    SYNTAX      XcmCommsDirAttributeType
    MAX-ACCESS  not-accessible
    STATUS      current
    DESCRIPTION "Dummy - DO NOT USE"
    ::= { xCmCommsConfigDummy 4 }
xCmCommsLDAPAttributeType OBJECT-TYPE
    SYNTAX      XcmCommsLDAPAttributeType
    MAX-ACCESS  not-accessible
    STATUS      current
    DESCRIPTION "Dummy - DO NOT USE"
    ::= { xCmCommsConfigDummy 5 }
xCmSnmpIPHostnameAddress OBJECT-TYPE
    SYNTAX      XcmSnmpIPHostnameAddress 
    MAX-ACCESS  not-accessible
    STATUS      current
    DESCRIPTION "Dummy - DO NOT USE"
    ::= { xCmCommsConfigDummy 6 }
xcmCommsConfigMIB OBJECT-IDENTITY -- MODULE-IDENTITY
    STATUS   current
    DESCRIPTION
        "Version:   5.11.pub
        The MIB module which supports active configuration discovery
        of communications protocol stacks, communications end system
        applications, communications intermediate systems, and
        communications gateways for network accessible host systems.
        Usage:  Note that throughout this MIB module, the INDEX clauses
        referring to 'hrDeviceIndex' for the 'hrDeviceTable' (Devices
        Group) of the Host Resources MIB (RFC 2790) SHALL
        specify host system CPUs (ie, 'hrDeviceProcessor') and shall NOT
        specify host system 'network interfaces', with entries in the
        'ifTable' (Interfaces Group) of MIB-II (RFC 1213).
        Copyright (C) 1996-2002 Xerox Corporation. All Rights Reserved."
    ::= { xeroxCommonMIB 64 }
xcmCommsConfigZeroDummy OBJECT IDENTIFIER ::= { zeroDotZero 64 }
--
--
--
xcmCommsConfig          OBJECT IDENTIFIER ::= { xcmCommsConfigMIB 3 }
xcmCommsConfigTable OBJECT-TYPE
    SYNTAX      SEQUENCE OF XcmCommsConfigEntry
    MAX-ACCESS  not-accessible
    STATUS      current
    DESCRIPTION
        "A table of the communications engines installed and (possibly)
        running on platforms (ie, CPUs) on this host system."
    ::= { xcmCommsConfig 2 }
xcmCommsConfigEntry OBJECT-TYPE
    SYNTAX      XcmCommsConfigEntry
    MAX-ACCESS  not-accessible
    STATUS      current
    DESCRIPTION
        "An entry for a communications engine installed and (possibly)
        running on a platform (ie, CPU) on this host system.
        Usage:  Note that values of 'hrDeviceIndex' used to reference
        entries in the 'xcmCommsEngineTable' SHALL reference
        entries in the 'hrDeviceTable' with 'hrDeviceType' equal to
        'hrDeviceProcessor' (representing host system CPUs and therefore
        also having corresponding entries in the 'hrProcessorTable')."
    INDEX       { hrDeviceIndex }
    ::= { xcmCommsConfigTable 1 }
XcmCommsConfigEntry ::= SEQUENCE {
        xcmCommsConfigRowStatus         RowStatus,
        xcmCommsConfigActiveOptionFirst Cardinal32,
        xcmCommsConfigActiveOptionLast  Cardinal32,
        xcmCommsConfigGroupSupport      XcmCommsConfigGroupSupport,
        xcmCommsConfigCreateSupport     XcmCommsConfigGroupSupport,
        xcmCommsConfigUpdateSupport     XcmCommsConfigGroupSupport
    }
--
--
xcmCommsConfigRowStatus OBJECT-TYPE
    SYNTAX      RowStatus
    MAX-ACCESS  read-only
    STATUS      current
    DESCRIPTION
        "This object displays the status of individual conceptual
        rows in the 'xcmCommsConfigTable'.
        Usage:  'xcmCommsConfigRowStatus' is 'read-only' because
        these conceptual rows shall NOT be deleted."
    ::= { xcmCommsConfigEntry 1 }
xcmCommsConfigActiveOptionFirst OBJECT-TYPE
    SYNTAX      Cardinal32
    MAX-ACCESS  read-only
    STATUS      current
    DESCRIPTION
        "The value of 'xcmCommsOptionIndex' corresponding to the first
        active configuration option (in 'xcmCommsOptionTable'), or zero
        if this communications engine does NOT require such information.
        Usage:  This 'chain' represents currently active configuration
        options of this communications engine."
    REFERENCE
        "See:   'xcmCommsConfigActiveOptionLast'"
    DEFVAL      { 0 }                   
    ::= { xcmCommsConfigEntry 2 }
xcmCommsConfigActiveOptionLast OBJECT-TYPE
    SYNTAX      Cardinal32
    MAX-ACCESS  read-only
    STATUS      current
    DESCRIPTION
        "The value of 'xcmCommsOptionIndex' corresponding to the last
        active configuration option (in 'xcmCommsOptionTable'), or zero
        if this communications engine does NOT require such information.
        Usage:  This 'chain' represents currently active configuration
        options of this communications engine.
        Usage:  The last entry index explicitly bounds the valid range
        of 'xcmCommsOptionIndex'.  This is the value of the numerically
        highest entry index, NOT necessarily the 'logically last' entry
        index in the structured tree in 'xcmCommsOptionTable'."
    REFERENCE
        "See:   'xcmCommsConfigActiveOptionFirst'"
    DEFVAL      { 0 }                   
    ::= { xcmCommsConfigEntry 3 }
xcmCommsConfigGroupSupport OBJECT-TYPE
    SYNTAX      XcmCommsConfigGroupSupport
    MAX-ACCESS  read-only
    STATUS      current
    DESCRIPTION
        "The terse conformance statement of ALL mandatory, conditionally
        mandatory, and optional XCMI Comms Config MIB object groups
        supported by this management agent implementation (ie, version)
        on this host system, specified in a bit-mask.
        Usage:  Conforming management agents SHALL accurately
        report their support for XCMI Comms Config MIB object groups."
    DEFVAL      { 1 }                   
    ::= { xcmCommsConfigEntry 4 }
xcmCommsConfigCreateSupport OBJECT-TYPE
    SYNTAX      XcmCommsConfigGroupSupport
    MAX-ACCESS  read-only
    STATUS      current
    DESCRIPTION
        "The terse conformance statement of ALL mandatory, conditionally
        mandatory, and optional XCMI Comms Config MIB object groups
        supported for dynamic row creation (via '...RowStatus')
        by this management agent implementation (ie, version)
        on this host system, specified in a bit-mask.
        Usage:  Conforming management agents SHALL accurately
        report their support for XCMI Comms Config MIB object groups."
    DEFVAL      { 0 }                   
    ::= { xcmCommsConfigEntry 5 }
xcmCommsConfigUpdateSupport OBJECT-TYPE
    SYNTAX      XcmCommsConfigGroupSupport
    MAX-ACCESS  read-only
    STATUS      current
    DESCRIPTION
        "The terse conformance statement of ALL mandatory, conditionally
        mandatory, and optional XCMI Comms Config MIB object groups
        supported for existing row update (via SNMP Set-Request PDUs)
        by this management agent implementation (ie, version)
        on this host system, specified in a bit-mask.
        Usage:  Conforming management agents SHALL accurately
        report their support for XCMI Comms Config MIB object groups."
    DEFVAL      { 0 }                   
    ::= { xcmCommsConfigEntry 6 }
--
--
xcmCommsOption          OBJECT IDENTIFIER ::= { xcmCommsConfigMIB 4 }
xcmCommsOptionTable OBJECT-TYPE
    SYNTAX      SEQUENCE OF XcmCommsOptionEntry
    MAX-ACCESS  not-accessible
    STATUS      current
    DESCRIPTION
        "A table containing information on installation, configuration,
        or other aspects of communications options on this host system."
    ::= { xcmCommsOption 2 }
xcmCommsOptionEntry OBJECT-TYPE
    SYNTAX      XcmCommsOptionEntry
    MAX-ACCESS  not-accessible
    STATUS      current
    DESCRIPTION
        "An entry containing information on installation, configuration,
        or other aspects of communications options on this host system."
    INDEX       { hrDeviceIndex, xcmCommsOptionIndex }
    ::= { xcmCommsOptionTable 1 }
XcmCommsOptionEntry ::= SEQUENCE {
        xcmCommsOptionIndex             Ordinal32,
        xcmCommsOptionRowStatus         RowStatus,
        xcmCommsOptionTypeOID           OBJECT IDENTIFIER,
        xcmCommsOptionValueSyntax       XcmGenOptionValueSyntax,
        xcmCommsOptionValueInteger      Integer32,
        xcmCommsOptionValueOID          OBJECT IDENTIFIER,
        xcmCommsOptionValueString       OCTET STRING,
        xcmCommsOptionValueLocalization Cardinal32,
        xcmCommsOptionValueCodedCharSet IANACharset,
        xcmCommsOptionNextIndex         Cardinal32,
        xcmCommsOptionPreviousIndex     Cardinal32,
        xcmCommsOptionFamilyIndex       Cardinal32
    }
--
--
xcmCommsOptionIndex OBJECT-TYPE
    SYNTAX      Ordinal32
    MAX-ACCESS  not-accessible
    STATUS      current
    DESCRIPTION
        "A unique value used by this host system to identify this
        conceptual row in the 'xcmCommsOptionTable'."
    ::= { xcmCommsOptionEntry 1 }
xcmCommsOptionRowStatus OBJECT-TYPE
    SYNTAX      RowStatus
    MAX-ACCESS  read-only
    STATUS      current
    DESCRIPTION
        "This object displays the status of individual conceptual
        rows in the 'xcmCommsOptionTable'."
    ::= { xcmCommsOptionEntry 2 }
xcmCommsOptionTypeOID OBJECT-TYPE
    SYNTAX      OBJECT IDENTIFIER
    MAX-ACCESS  read-only
    STATUS      current
    DESCRIPTION
        "An unambiguous communications option type,
        used by system administrators and end users to identify
        this communications option.
        Usage:  Since this communications option type is specified
        as an object identifier, it MAY be taken from any IETF, Xerox,
        third- party, or product-specific MIB, or it MAY simply be any
        IETF SMIv2-style 'autonomous type'."
    DEFVAL      { zeroDotZero }   
    ::= { xcmCommsOptionEntry 3 }
xcmCommsOptionValueSyntax OBJECT-TYPE
    SYNTAX      XcmGenOptionValueSyntax
    MAX-ACCESS  read-only
    STATUS      current
    DESCRIPTION
        "A communications option value syntax,
        used by system administrators and end users to specify
        the correct value syntax for this communications option.
        Usage:  This communications option value syntax is used to
        select which of the following three objects shall be used to
        contain the value of this communications option."
    DEFVAL      { unknown }             
    ::= { xcmCommsOptionEntry 4 }
xcmCommsOptionValueInteger OBJECT-TYPE
    SYNTAX      Integer32
    MAX-ACCESS  read-only
    STATUS      current
    DESCRIPTION
        "A communications option value integer,
        used by system administrators and end users to specify
        the current value for a communications option
        with a base value syntax of 'INTEGER'."
    REFERENCE
        "See:   'xcmCommsOptionValueSyntax' and 'xcmCommsOptionTypeOID'"
    DEFVAL      { 0 }                   
    ::= { xcmCommsOptionEntry 5 }
xcmCommsOptionValueOID OBJECT-TYPE
    SYNTAX      OBJECT IDENTIFIER
    MAX-ACCESS  read-only
    STATUS      current
    DESCRIPTION
        "A communications option value OID (object identifier),
        used by system administrators and end users to specify
        the current value for a communications option
        with a base value syntax of 'OBJECT IDENTIFIER'."
    REFERENCE
        "See:   'xcmCommsOptionValueSyntax' and 'xcmCommsOptionTypeOID'"
    DEFVAL      { zeroDotZero }   
    ::= { xcmCommsOptionEntry 6 }
xcmCommsOptionValueString OBJECT-TYPE
    SYNTAX      OCTET STRING (SIZE (0..255))
    MAX-ACCESS  read-only
    STATUS      current
    DESCRIPTION
        "A communications option value string,
        used by system administrators and end users to specify
        the current value for a communications option
        with a base value syntax of 'OCTET STRING'.
        Usage:  This object is of type 'XcmFixedLocaleDisplayString'
        (if 'xcmCommsOptionValueLocalization' is zero)
        or 'XcmNamedLocaleUtf8String'
        (if 'xcmCommsOptionValueLocalization' is non-zero).
        Usage:  Conformant implementations MUST encrypt passwords, keys,
        and other security information stored in this string object."
    REFERENCE
        "See:   'xcmCommsOptionValueSyntax' and 'xcmCommsOptionTypeOID'
        See:    'xcmGenFixedLocalizationIndex' in XCMI General MIB."
    DEFVAL      { ''H }                 
    ::= { xcmCommsOptionEntry 7 }
xcmCommsOptionValueLocalization OBJECT-TYPE
    SYNTAX      Cardinal32
    MAX-ACCESS  read-only
    STATUS      current
    DESCRIPTION
        "A communications option value localization,
        used by system administrators and end users to specify
        the ALTERNATE localization for a communications option
        (different from 'xcmGenFixedLocalizationIndex'), so that
        'xcmCommsOptionValueString' becomes 'XcmNamedLocaleUtf8String'.
        Usage:  For a communications option string to which POSIX-style
        localization (territory, language, character set) is applicable
        (non-keyword) this object MAY contain a suitable index value for
        'xcmGenLocalizationIndex' from the XCMI General MIB, or zero to
        indicate 'none'."
    REFERENCE
        "See:   'xcmCommsOptionValueSyntax' and 'xcmCommsOptionTypeOID'.
        See:    'xcmGenFixedLocalizationIndex' in XCMI General MIB."
    DEFVAL      { 0 }                   
    ::= { xcmCommsOptionEntry 8 }
xcmCommsOptionValueCodedCharSet OBJECT-TYPE
    SYNTAX      IANACharset
    MAX-ACCESS  read-only
    STATUS      current
    DESCRIPTION
        "A communications option value character set,
        used by system administrators and end users to specify
        the ALTERNATE character set for a communications option
        (different from 'xcmGenFixedLocalizationIndex'), so that
        'xcmCommsOptionValueString' is unambiguous.
        Usage:  XCMI conforming management agents shall ONLY allow
        Sets of this object to 'other' (none) or 'utf-8' (Unicode/
        ISO-10646 in the UTF-8 encoding, a proper superset of US-ASCII),
        for consistency with the Xerox Unicode Coherence Standard."
    REFERENCE
        "See:   'xcmCommsOptionValueSyntax' and 'xcmCommsOptionTypeOID'.
        See:    'IANACharset' in IETF Printer MIB (RFC 1759).
        See:    'xcmGenCodedCharSetTable' in XCMI General MIB."
    DEFVAL      { other }               
    ::= { xcmCommsOptionEntry 9 }
--
--
xcmCommsOptionNextIndex OBJECT-TYPE
    SYNTAX      Cardinal32
    MAX-ACCESS  read-only
    STATUS      current
    DESCRIPTION
        "The value of 'xcmCommsOptionIndex' corresponding to the next
        'chained' conceptual row in the 'xcmCommsOptionTable', or zero
        if this is the last associated conceptual row in a particular
        vertical 'chain' within a given set.
        Usage:  Generally, communications options (of similar or unlike
        type) are 'chained' vertically via '...[Next|Previous]Index'.
        But, in the case where particular communications options MUST
        be 'tightly coupled', they SHOULD be 'shelved' horizontally via
        '...[Family|Previous]Index' (eg, an IP address and an IP subnet
        mask)."
    REFERENCE
        "See:   'xcmCommsOption[Family|Previous]Index'"
    DEFVAL      { 0 }                   
    ::= { xcmCommsOptionEntry 10 }
xcmCommsOptionPreviousIndex OBJECT-TYPE
    SYNTAX      Cardinal32
    MAX-ACCESS  read-only
    STATUS      current
    DESCRIPTION
        "The value of 'xcmCommsOptionIndex' corresponding to a previous
        associated conceptual row in the 'xcmCommsOptionTable', or zero
        if this is the first associated conceptual row in a given set.
        Usage:  This object provides common 'backward' linkage for BOTH
        the 'xcmCommsOptionNextIndex' and 'xcmCommsOptionFamilyIndex'
        linkage objects.  A previous conceptual row MAY 'forward'
        reference this conceptual row via either '...NextIndex' or
        '...FamilyIndex' - ie, a given conceptual row MAY 'forward'
        reference EXACTLY zero, one, or two 'later' conceptual rows."
    REFERENCE
        "See:   'xcmCommsOption[Next|Family]Index'"
    DEFVAL      { 0 }                   
    ::= { xcmCommsOptionEntry 11 }
xcmCommsOptionFamilyIndex OBJECT-TYPE
    SYNTAX      Cardinal32
    MAX-ACCESS  read-only
    STATUS      current
    DESCRIPTION
        "The value of 'xcmCommsOptionIndex' corresponding to the next
        'family' conceptual row in the 'xcmCommsOptionTable', or zero
        if this is the last associated conceptual row in a particular
        horizontal 'shelf' (of 'family' members) within a given set.
        Usage:  Generally, communications options (of similar or unlike
        type) are 'chained' vertically via '...[Next|Previous]Index'.
        But, in the case where particular communications options MUST
        be 'tightly coupled', they SHOULD be 'shelved' horizontally via
        '...[Family|Previous]Index' (eg, an IP address and an IP subnet
        mask)."
    REFERENCE
        "See:   'xcmCommsOption[Next|Previous]Index'"
    DEFVAL      { 0 }                   
    ::= { xcmCommsOptionEntry 12 }
--
--
xcmCommsDirRecord       OBJECT IDENTIFIER ::= { xcmCommsConfigMIB 5 }
xcmCommsDirRecordTable OBJECT-TYPE
    SYNTAX      SEQUENCE OF XcmCommsDirRecordEntry
    MAX-ACCESS  not-accessible
    STATUS      current
    DESCRIPTION
        "A table containing directory records
        configured on this host system."
    ::= { xcmCommsDirRecord 2 }
xcmCommsDirRecordEntry OBJECT-TYPE
    SYNTAX      XcmCommsDirRecordEntry
    MAX-ACCESS  not-accessible
    STATUS      current
    DESCRIPTION
        "An entry for a directory record
        configured on this host system."
    INDEX       { xcmCommsDirRecordType,
                  xcmCommsDirRecordIndex }
    ::= { xcmCommsDirRecordTable 1 }
XcmCommsDirRecordEntry ::= SEQUENCE {
        xcmCommsDirRecordType           XcmCommsDirRecordType,
        xcmCommsDirRecordIndex          Ordinal32,
        xcmCommsDirRecordRowStatus      RowStatus,
        xcmCommsDirRecordKeyType        XcmCommsDirAttributeType,
        xcmCommsDirRecordKeyInteger     Integer32,
        xcmCommsDirRecordKeyString      XcmFixedLocaleUtf8String,
        xcmCommsDirRecordParentType     XcmCommsDirRecordType,
        xcmCommsDirRecordParentIndex    Cardinal32
    }
xcmCommsDirRecordType OBJECT-TYPE
    SYNTAX      XcmCommsDirRecordType
    MAX-ACCESS  not-accessible
    STATUS      current
    DESCRIPTION
        "A directory record type, used to uniquely identify this
        directory record (and all subordinate directory attributes),
        when combined with 'xcmCommsDirRecordIndex' (below)."
    ::= { xcmCommsDirRecordEntry 1 }
xcmCommsDirRecordIndex OBJECT-TYPE
    SYNTAX      Ordinal32
    MAX-ACCESS  not-accessible
    STATUS      current
    DESCRIPTION
        "A directory record index, used to uniquely identify this
        directory record (and all subordinate directory attributes),
        when combined with 'xcmCommsDirRecordType' (above).
        Usage:  This directory record index SHALL be unique for
        each record of a given type (value of 'xcmCommsDirRecordType'),
        but NEED NOT be unique for directory records of different types.
        This is to permit directory records of different types to start
        their numbering (value of 'xcmCommsDirRecordIndex') over from
        one ('1') and such usage is RECOMMENDED."
    ::= { xcmCommsDirRecordEntry 2 }
xcmCommsDirRecordRowStatus OBJECT-TYPE
    SYNTAX      RowStatus
    MAX-ACCESS  read-create
    STATUS      current
    DESCRIPTION
        "This object manages the row status of this conceptual row in
        the 'xcmCommsDirRecordTable'.
        Usage:  Conforming implementations which support static rows
        SHALL support 'active' and 'notInService' writes to this
        'xcmCommsDirRecordRowStatus' row status object; and
        SHALL clear the 'commsDirRecordGroup' bit in
        'xcmCommsConfigCreateSupport' in the 'xcmCommsConfigTable'.
        Usage:  Conforming implementations which support dynamic rows
        SHALL support 'createAndGo' and 'destroy' writes to this
        'xcmCommsDirRecordRowStatus' row status object; and
        SHALL set the 'commsDirRecordGroup' bit in
        'xcmCommsConfigCreateSupport' in the 'xcmCommsConfigTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmCommsConfigCreateSupport' in 'xcmCommsConfigTable'.
        See:    'RowStatus' in IETF SNMPv2 TC (RFC 1443/1903/2579).
        See:    'xcmHrDevMgmtCommandData' in XCMI HRX MIB and
                'xcmSecUserMgmtData' in XCMI Security MIB."
    ::= { xcmCommsDirRecordEntry 3 }
xcmCommsDirRecordKeyType OBJECT-TYPE
    SYNTAX      XcmCommsDirAttributeType
    MAX-ACCESS  read-create
    STATUS      current
    DESCRIPTION
        "A directory record key attribute type, used to specify a
        primary key attribute for sorting this directory record, or
        'unknown' if no primary key attribute is specified.
        Usage:  The 'Relative Distinguished Name' (RDN) of this
        directory record is the tuple of the directory record type, the
        key attribute type, and the key attribute value."
    REFERENCE
        "See:   'XcmCommsDirAttributeType' in the XCMI CC TC
                'xcmCommsDirAttributeType' in this XCMI CC MIB."
    DEFVAL      { unknown }             
    ::= { xcmCommsDirRecordEntry 4 }
xcmCommsDirRecordKeyInteger OBJECT-TYPE
    SYNTAX      Integer32
    MAX-ACCESS  read-create
    STATUS      current
    DESCRIPTION
        "A directory record key attribute integer value, used to specify
        a primary key attribute for sorting this directory record, or
        zero ('0') if no primary key attribute is specified.
        Usage:  The 'Relative Distinguished Name' (RDN) of this
        directory record is the tuple of the directory record type, the
        key attribute type, and the key attribute value."
    REFERENCE
        "See:   'xcmCommsDirRecordKeyType' in this XCMI CC MIB
                'xcmCommsDirAttributeValue' in this XCMI CC MIB."
    DEFVAL      { 0 }                   
    ::= { xcmCommsDirRecordEntry 5 }
xcmCommsDirRecordKeyString OBJECT-TYPE
    SYNTAX      XcmFixedLocaleUtf8String (SIZE (0..255))
    MAX-ACCESS  read-create
    STATUS      current
    DESCRIPTION
        "A directory record key attribute string value, used to specify
        a primary key attribute for sorting this directory record, or
        zero ('0') if no primary key attribute is specified.
        Usage:  String-valued directory attributes SHALL be
        specified as UTF-8 encoded Unicode (ISO 10646) strings.
        Usage:  The 'Relative Distinguished Name' (RDN) of this
        directory record is the tuple of the directory record type, the
        key attribute type, and the key attribute value."
    REFERENCE
        "See:   'xcmCommsDirRecordKeyType' in this XCMI CC MIB
                'xcmCommsDirStringValue' in this XCMI CC MIB."
    DEFVAL      { ''H }                 
    ::= { xcmCommsDirRecordEntry 6 }
xcmCommsDirRecordParentType OBJECT-TYPE
    SYNTAX      XcmCommsDirRecordType
    MAX-ACCESS  read-create
    STATUS      current
    DESCRIPTION
        "A parent directory record type, used to identify the parent
        directory record (superior to this directory record), or
        'unknown' if no parent directory record is specified.
        Usage:  Supports hierarchical directory structures.
        Usage:  The 'Fully Qualified Distinguished Name' (FQDN) of this
        directory record is the concatentation of the RDN (record key)
        of this directory record with the RDNs of all superior directory
        records to the 'top' (highest node)."
    REFERENCE
        "See:   'xcmCommsDirRecordType' in this XCMI CC MIB
                'xcmCommsDirRecordIndex' in this XCMI CC MIB."
    DEFVAL      { unknown }             
    ::= { xcmCommsDirRecordEntry 7 }
xcmCommsDirRecordParentIndex OBJECT-TYPE
    SYNTAX      Cardinal32
    MAX-ACCESS  read-create
    STATUS      current
    DESCRIPTION
        "A parent directory record index, used to identify the parent
        directory record (superior to this directory record), or
        zero ('0') if no parent directory record is specified.
        Usage:  Supports hierarchical directory structures.
        Usage:  The 'Fully Qualified Distinguished Name' (FQDN) of this
        directory record is the concatentation of the RDN (record key)
        of this directory record with the RDNs of all superior directory
        records to the 'top' (highest node)."
    REFERENCE
        "See:   'xcmCommsDirRecordType' in this XCMI CC MIB
                'xcmCommsDirRecordIndex' in this XCMI CC MIB."
    DEFVAL      { 0 }                   
    ::= { xcmCommsDirRecordEntry 8 }
--
--
xcmCommsDirAttribute    OBJECT IDENTIFIER ::= { xcmCommsConfigMIB 6 }
xcmCommsDirAttributeTable OBJECT-TYPE
    SYNTAX      SEQUENCE OF XcmCommsDirAttributeEntry
    MAX-ACCESS  not-accessible
    STATUS      current
    DESCRIPTION
        "A table containing integer-valued directory attributes
        configured on this host system.
        Usage:  Table contains an entry for all integer-valued and
        string-valued attributes configured on this host system."
    ::= { xcmCommsDirAttribute 2 }
xcmCommsDirAttributeEntry OBJECT-TYPE
    SYNTAX      XcmCommsDirAttributeEntry
    MAX-ACCESS  not-accessible
    STATUS      current
    DESCRIPTION
        "An entry for an integer-valued directory attribute
        configured on this host system."
    INDEX       { xcmCommsDirRecordType,
                  xcmCommsDirRecordIndex,
                  xcmCommsDirAttributeType,
                  xcmCommsDirAttributeIndex }
    ::= { xcmCommsDirAttributeTable 1 }
XcmCommsDirAttributeEntry ::= SEQUENCE {
        xcmCommsDirAttributeType        XcmCommsDirAttributeType,
        xcmCommsDirAttributeIndex       Ordinal32,
        xcmCommsDirAttributeRowStatus   RowStatus,
        xcmCommsDirAttributeValue       Integer32
    }
xcmCommsDirAttributeType OBJECT-TYPE
    SYNTAX      XcmCommsDirAttributeType
    MAX-ACCESS  not-accessible
    STATUS      current
    DESCRIPTION
        "A directory attribute type, used to uniquely identify this
        integer-valued directory attribute (and also any matching
        string-valued directory attribute in 'xcmCommsDirStringTable'),
        when combined with 'xcmCommsDirAttributeIndex' (below).
        Usage:   When directory attribute type indicates integer-valued,
        the value of 'xcmCommsDirAttributeValue' SHALL be the
        actual value of this directory attribute.
        Usage:   When directory attribute type indicates string-valued,
        the value of 'xcmCommsDirAttributeValue' SHALL be zero,
        EXCEPT for a directory attribute type of 'protocolTyped...',
        when the protocol type shall be specified as the integer value.
        The actual string-valued attribute SHALL be specified in
        an exactly matching row of 'xcmCommsDirStringTable'.
        Usage:  Matching directory attributes (string-valued)
        SHALL be specified in an exactly matching row of
        'xcmCommsDirStringTable'.  Matching rows have EXACTLY the SAME
        values of 'xcmCommsDirRecordType', 'xcmCommsDirRecordIndex',
        'xcmCommsDirAttributeType', and 'xcmCommsDirAttributeIndex'.
        Usage:  Parallel directory attributes (peers of this one)
        SHALL be specified in parallel (NOT matching) rows of
        'xcmCommsDirAttributeTable' (integer-valued attributes) or
        'xcmCommsDirStringTable' (string-valued attributes).  Parallel
        rows have EXACTLY the SAME values of 'xcmCommsDirRecordType',
        'xcmCommsDirRecordIndex', and 'xcmCommsDirAttributeIndex',
        but MUST have a DIFFERENT value of 'xcmCommsDirAttributeType'.
        Usage:   When directory attribute type is 'protocolTyped...' the
        particular protocol layer SHALL be specified by placing a
        a value from the enumeration 'XcmCommsStackExtProtocol' in
        'xcmCommsDirAttributeValue' for this row."
    REFERENCE
        "See:   'XcmCommsDirAttributeType' in the XCMI CC TC
                'XcmCommsStackExtProtocol' in the XCMI Comms Engine TC."
    ::= { xcmCommsDirAttributeEntry 1 }
xcmCommsDirAttributeIndex OBJECT-TYPE
    SYNTAX      Ordinal32
    MAX-ACCESS  not-accessible
    STATUS      current
    DESCRIPTION
        "A directory attribute index, used to uniquely identify this
        integer-valued directory attribute (and also any matching
        string-valued directory attribute in 'xcmCommsDirStringTable'),
        when combined with 'xcmCommsDirAttributeType' (above).
        Usage:  This directory attribute index SHALL be unique
        for each attribute subordinate to one directory record (ie, rows
        with EXACTLY the SAME values of 'xcmCommsDirRecordType' and
        'xcmCommsDirRecordIndex').  EXCEPT when two or more different
        directory attributes are 'parallel'; then they SHALL
        have EXACTLY the SAME value of 'xcmCommsDirAttributeIndex'.
        Example:  The following example illustrates the use of
        'parallel' directory attributes in a 'speed dial' entry.
        (Index values are shown in square brackets, for clarity.)
       [xcmCommsDirRecordType           = recordSpeedDial]
       [xcmCommsDirRecordIndex          = 1]
        xcmCommsDirRecordRowStatus      = active
        xcmCommsDirRecordKeyType        = userFullName (sort key)
        xcmCommsDirRecordKeyInteger     = 0 (unused)
        xcmCommsDirRecordKeyString      = 'Fred Flintstone' (sort key)
       [xcmCommsDirRecordType           = recordSpeedDial]
       [xcmCommsDirRecordIndex          = 1]
       [xcmCommsDirAttributeType        = userLocation]
       [xcmCommsDirAttributeIndex       = 1]
        xcmCommsDirAttributeRowStatus   = active
        xcmCommsDirAttributeValue       = 0 (unused)
        xcmCommsDirStringRowStatus      = active
        xcmCommsDirStringValue          = 'Bldg 705, H-18'
       [xcmCommsDirRecordType           = recordSpeedDial]
       [xcmCommsDirRecordIndex          = 1]
       [xcmCommsDirAttributeType        = protocolTypedAddress]
       [xcmCommsDirAttributeIndex       = 2]
        xcmCommsDirAttributeRowStatus   = active
        xcmCommsDirAttributeValue       = osiwanFax (FAX protocol type)
        xcmCommsDirStringRowStatus      = active
        xcmCommsDirStringValue          = '0+...' (FAX phone number)
       [xcmCommsDirRecordType           = recordSpeedDial]
       [xcmCommsDirRecordIndex          = 1]
       [xcmCommsDirAttributeType        = protocolPriority]
       [xcmCommsDirAttributeIndex       = 2] (parallel attribute)
        xcmCommsDirAttributeRowStatus   = active
        xcmCommsDirAttributeValue       = 100 (highest priority)
       [xcmCommsDirRecordType           = recordSpeedDial]
       [xcmCommsDirRecordIndex          = 1]
       [xcmCommsDirAttributeType        = protocolMaxRetries]
       [xcmCommsDirAttributeIndex       = 2] (parallel attribute)
        xcmCommsDirAttributeRowStatus   = active
        xcmCommsDirAttributeValue       = 3 (FAX max retries)
       [xcmCommsDirRecordType           = recordSpeedDial]
       [xcmCommsDirRecordIndex          = 1]
       [xcmCommsDirAttributeType        = protocolRetryInterval]
       [xcmCommsDirAttributeIndex       = 2] (parallel attribute)
        xcmCommsDirAttributeRowStatus   = active
        xcmCommsDirAttributeValue       = 10 (FAX retry interval)
       [xcmCommsDirRecordType           = recordSpeedDial]
       [xcmCommsDirRecordIndex          = 1]
       [xcmCommsDirAttributeType        = protocolTypedAddress]
       [xcmCommsDirAttributeIndex       = 3]
        xcmCommsDirAttributeRowStatus   = active
        xcmCommsDirAttributeValue       = osiwanFax (FAX protocol type)
        xcmCommsDirStringRowStatus      = active
        xcmCommsDirStringValue          = '0+...' (FAX phone number)
       [xcmCommsDirRecordType           = recordSpeedDial]
       [xcmCommsDirRecordIndex          = 1]
       [xcmCommsDirAttributeType        = protocolPriority]
       [xcmCommsDirAttributeIndex       = 3] (parallel attribute)
        xcmCommsDirAttributeRowStatus   = active
        xcmCommsDirAttributeValue       = 50 (medium priority)
       [xcmCommsDirRecordType           = recordSpeedDial]
       [xcmCommsDirRecordIndex          = 1]
       [xcmCommsDirAttributeType        = protocolTypedAddress]
       [xcmCommsDirAttributeIndex       = 4]
        xcmCommsDirAttributeRowStatus   = active
        xcmCommsDirAttributeValue       = internetSMTP (Email protocol)
        xcmCommsDirStringRowStatus      = active
        xcmCommsDirStringValue          = 'fflint@...' (Email address)
       [xcmCommsDirRecordType           = recordSpeedDial]
       [xcmCommsDirRecordIndex          = 1]
       [xcmCommsDirAttributeType        = protocolPriority]
       [xcmCommsDirAttributeIndex       = 4] (parallel attribute)
        xcmCommsDirAttributeRowStatus   = active
        xcmCommsDirAttributeValue       = 1 (lowest priority)
        Discussion:  This example shows a 'speed dial' directory record
        with a primary sort key (e.g., for local UI display ordering) of
        the destination user's full name ('userFullName').
        Also shown are four sets of 'parallel' directory attributes:
        a)  user location;
        b)  primary FAX destination (highest priority);
        c)  secondary FAX destination (medium priority);
        d)  tertiary Email destination (lowest priority).
        Usage:  Each 'parallel' directory attribute in a given set is
        correlated by the SAME value of 'xcmCommsDirAttributeIndex'."
    ::= { xcmCommsDirAttributeEntry 2 }
xcmCommsDirAttributeRowStatus OBJECT-TYPE
    SYNTAX      RowStatus
    MAX-ACCESS  read-create
    STATUS      current
    DESCRIPTION
        "This object manages the row status of this conceptual row in
        the 'xcmCommsDirAttributeTable'.
        Usage:  Conforming implementations which support static rows
        SHALL support 'active' and 'notInService' writes to this
        'xcmCommsDirAttributeRowStatus' row status object; and
        SHALL clear the 'commsDirAttributeGroup' bit in
        'xcmCommsConfigCreateSupport' in the 'xcmCommsConfigTable'.
        Usage:  Conforming implementations which support dynamic rows
        SHALL support 'createAndGo' and 'destroy' writes to this
        'xcmCommsDirAttributeRowStatus' row status object; and
        SHALL set the 'commsDirAttributeGroup' bit in
        'xcmCommsConfigCreateSupport' in the 'xcmCommsConfigTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmCommsConfigCreateSupport' in 'xcmCommsConfigTable'.
        See:    'RowStatus' in IETF SNMPv2 TC (RFC 1443/1903/2579).
        See:    'xcmHrDevMgmtCommandData' in XCMI HRX MIB and
                'xcmSecUserMgmtData' in XCMI Security MIB."
    ::= { xcmCommsDirAttributeEntry 3 }
xcmCommsDirAttributeValue OBJECT-TYPE
    SYNTAX      Integer32
    MAX-ACCESS  read-create
    STATUS      current
    DESCRIPTION
        "A directory attribute value, the contents of this
        integer-valued directory attribute, or zero if
        'xcmCommsDirAttributeType' indicates string-valued,
        and is NOT 'protocolTyped...'.
        Usage:   When directory attribute type is 'protocolTyped...' the
        particular protocol layer SHALL be specified by placing a
        a value from the enumeration 'XcmCommsStackExtProtocol' in
        'xcmCommsDirAttributeValue' for this row."
    REFERENCE
        "See:   'xcmCommsDirAttributeType' in this XCMI CC MIB
                'XcmCommsDirAttributeType' in the XCMI CC TC
                'XcmCommsStackExtProtocol' in the XCMI Comms Engine TC."
    DEFVAL      { 0 }                   
    ::= { xcmCommsDirAttributeEntry 4 }
--
--
xcmCommsDirString       OBJECT IDENTIFIER ::= { xcmCommsConfigMIB 7 }
xcmCommsDirStringTable OBJECT-TYPE
    SYNTAX      SEQUENCE OF XcmCommsDirStringEntry
    MAX-ACCESS  not-accessible
    STATUS      current
    DESCRIPTION
        "A table containing string-valued directory attributes
        configured on this host system.
        Usage:  Table contains an entry for ONLY string-valued and
        configured on this host system."
    ::= { xcmCommsDirString 2 }
xcmCommsDirStringEntry OBJECT-TYPE
    SYNTAX      XcmCommsDirStringEntry
    MAX-ACCESS  not-accessible
    STATUS      current
    DESCRIPTION
        "An entry containing string-valued directory attributes
        configured on this host system."
    INDEX       { xcmCommsDirRecordType,
                  xcmCommsDirRecordIndex,
                  xcmCommsDirAttributeType,
                  xcmCommsDirAttributeIndex }
    ::= { xcmCommsDirStringTable 1 }
XcmCommsDirStringEntry ::= SEQUENCE {
        xcmCommsDirStringRowStatus      RowStatus,
        xcmCommsDirStringValue          XcmFixedLocaleUtf8String
    }
xcmCommsDirStringRowStatus OBJECT-TYPE
    SYNTAX      RowStatus
    MAX-ACCESS  read-create
    STATUS      current
    DESCRIPTION
        "This object manages the row status of this conceptual row in
        the 'xcmCommsDirStringTable'.
        Usage:  Conforming implementations which support static rows
        SHALL support 'active' and 'notInService' writes to this
        'xcmCommsDirStringRowStatus' row status object; and
        SHALL clear the 'commsDirStringGroup' bit in
        'xcmCommsConfigCreateSupport' in the 'xcmCommsConfigTable'.
        Usage:  Conforming implementations which support dynamic rows
        SHALL support 'createAndGo' and 'destroy' writes to this
        'xcmCommsDirStringRowStatus' row status object; and
        SHALL set the 'commsDirStringGroup' bit in
        'xcmCommsConfigCreateSupport' in the 'xcmCommsConfigTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmCommsConfigCreateSupport' in 'xcmCommsConfigTable'.
        See:    'RowStatus' in IETF SNMPv2 TC (RFC 1443/1903/2579).
        See:    'xcmHrDevMgmtCommandData' in XCMI HRX MIB and
                'xcmSecUserMgmtData' in XCMI Security MIB."
    ::= { xcmCommsDirStringEntry 1 }
xcmCommsDirStringValue OBJECT-TYPE
    SYNTAX      XcmFixedLocaleUtf8String (SIZE (0..255))
    MAX-ACCESS  read-create
    STATUS      current
    DESCRIPTION
        "A directory attribute value, the contents of this
        string-valued directory attribute.
        Usage:  String-valued directory attributes SHALL be
        specified as UTF-8 encoded Unicode (ISO 10646) strings.
        Usage:   When directory attribute type is 'protocolTyped...' the
        particular protocol layer SHALL be specified by placing a
        a value from the enumeration 'XcmCommsStackExtProtocol' in
        'xcmCommsDirAttributeValue' for this row.
        Usage:  Conformant implementations MUST encrypt passwords, keys,
        and other security information stored in this string object."
    REFERENCE
        "See:   'xcmCommsDirAttributeType' in this XCMI CC MIB
                'XcmCommsDirAttributeType' in the XCMI CC TC."
    DEFVAL      { ''H }                 
    ::= { xcmCommsDirStringEntry 2 }
--
--
xcmCommsProtocol        OBJECT IDENTIFIER ::= { xcmCommsConfigMIB 8 }
xcmCommsProtocolTable OBJECT-TYPE
    SYNTAX      SEQUENCE OF XcmCommsProtocolEntry
    MAX-ACCESS  not-accessible
    STATUS      current
    DESCRIPTION
        "A table of available communications protocol suites and
        specific communications protocols on this host system."
    ::= { xcmCommsProtocol 2 }
xcmCommsProtocolEntry OBJECT-TYPE
    SYNTAX      XcmCommsProtocolEntry
    MAX-ACCESS  not-accessible
    STATUS      current
    DESCRIPTION
        "An entry for an available communications protocol suite or
        specific communications protocol on this host system."
    INDEX       { hrDeviceIndex, xcmCommsProtocolType }
    ::= { xcmCommsProtocolTable 1 }
XcmCommsProtocolEntry ::= SEQUENCE {
        xcmCommsProtocolType            XcmCommsStackExtProtocol,
        xcmCommsProtocolRowStatus       RowStatus
    }
--
--
xcmCommsProtocolType OBJECT-TYPE
    SYNTAX      XcmCommsStackExtProtocol
    MAX-ACCESS  not-accessible
    STATUS      current
    DESCRIPTION
        "The type of an available communications protocol suite or
        specific communications protocol on this host system.
        Usage:  To indicate that a communications protocol suite is
        available, use a suite value of 'XcmCommsStackExtProtocol',
        eg, 'internetSuite(140101)' for the Internet suite.
        Usage:  To indicate that a specific communications protocol is
        available, use a specific value of 'XcmCommsStackExtProtocol',
        eg, 'internetFTP(141504)' for the Internet FTP protocol."
    REFERENCE
        "See:   'XcmCommsStackExtProtocol' in XCMI Comms Engine TC.
        See:    'protocolType' enumeration and
                'protocolTyped[Name|Address]' enumerations in
                'XcmCommsDirAttributeType' in XCMI CC TC.
        See:    'xcmCommsDirAttributeType' in XCMI CC MIB."
    ::= { xcmCommsProtocolEntry 1 }
xcmCommsProtocolRowStatus OBJECT-TYPE
    SYNTAX      RowStatus
    MAX-ACCESS  read-only
    STATUS      current
    DESCRIPTION
        "This object displays the status of individual conceptual
        rows in the 'xcmCommsProtocolTable'."
    ::= { xcmCommsProtocolEntry 2 }
--
--
xcmCommsConfigMIBConformance
    OBJECT IDENTIFIER ::= { xcmCommsConfigMIB 2 }
xcmCommsConfigMIBGroups
    OBJECT IDENTIFIER ::= { xcmCommsConfigMIBConformance 2 }
--
--
xcmCommsConfigMIBCompliance MODULE-COMPLIANCE
    STATUS      current
    DESCRIPTION
        "The compliance statements for SNMP management agents that
        implement the Comms Config MIB."
    MODULE 
    MANDATORY-GROUPS {
        xcmCommsConfigGroup,
        xcmCommsOptionGroup
    }
    GROUP       xcmCommsDirRecordGroup
    DESCRIPTION
        "Implementation of this group is conditionally mandatory, ie,
        mandatory for systems which implement directories via SNMP."
    GROUP       xcmCommsDirAttributeGroup
    DESCRIPTION
        "Implementation of this group is conditionally mandatory, ie,
        mandatory for systems which implement directories via SNMP."
    GROUP       xcmCommsDirStringGroup
    DESCRIPTION
        "Implementation of this group is conditionally mandatory, ie,
        mandatory for systems which implement directories via SNMP."
    GROUP       xcmCommsProtocolGroup
    DESCRIPTION
        "Implementation of this group is conditionally mandatory, ie,
        mandatory for systems which support discovery of available
        communications suites and specific protocols via SNMP."
    OBJECT      xcmCommsConfigRowStatus
    SYNTAX      INTEGER { active(1) }   
    DESCRIPTION
        "It is conformant to implement this object as read-only, and
        only one of the enumerated values for the 'RowStatus' textual
        convention need be supported, specifically:  active(1)."
    OBJECT      xcmCommsOptionRowStatus
    SYNTAX      INTEGER { active(1) }   
    DESCRIPTION
        "It is conformant to implement this object as read-only, and
        only one of the enumerated values for the 'RowStatus' textual
        convention need be supported, specifically:  active(1)."
    OBJECT      xcmCommsOptionValueString
    SYNTAX      OCTET STRING (SIZE (0..32))
    DESCRIPTION
        "It is conformant to implement this object as read-only, and
        only 32 octets maximum string length need be supported.
        Usage:  Conformant implementations MUST encrypt passwords, keys,
        and other security information stored in this string object."
    OBJECT      xcmCommsDirRecordRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsDirRecordKeyType
    MIN-ACCESS  read-only
    DESCRIPTION
        "It is conformant to implement this object as read-only."
    OBJECT      xcmCommsDirRecordKeyInteger
    MIN-ACCESS  read-only
    DESCRIPTION
        "It is conformant to implement this object as read-only."
    OBJECT      xcmCommsDirRecordKeyString
    SYNTAX      XcmFixedLocaleUtf8String (SIZE (0..1))
    MIN-ACCESS  read-only
    DESCRIPTION
        "It is conformant to implement this object as read-only, and
        only 1 octet maximum string length need be supported."
    OBJECT      xcmCommsDirRecordParentType
    MIN-ACCESS  read-only
    DESCRIPTION
        "It is conformant to implement this object as read-only."
    OBJECT      xcmCommsDirRecordParentIndex
    MIN-ACCESS  read-only
    DESCRIPTION
        "It is conformant to implement this object as read-only."
    OBJECT      xcmCommsDirAttributeRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsDirAttributeValue
    MIN-ACCESS  read-only
    DESCRIPTION
        "It is conformant to implement this object as read-only."
    OBJECT      xcmCommsDirStringRowStatus
    SYNTAX      INTEGER { active(1) }   
    MIN-ACCESS  read-only
    DESCRIPTION
        "It is conformant to implement this object as read-only, and
        only one of the enumerated values for the 'RowStatus' textual
        convention need be supported, specifically:  active(1)."
    OBJECT      xcmCommsDirStringValue
    SYNTAX      XcmFixedLocaleUtf8String (SIZE (0..32))
    MIN-ACCESS  read-only
    DESCRIPTION
        "It is conformant to implement this object as read-only, and
        only 32 octets maximum string length need be supported.
        Usage:  Conformant implementations MUST encrypt passwords, keys,
        and other security information stored in this string object."
    ::= { xcmCommsConfigMIBConformance 3 }
--
--
xcmCommsConfigGroup OBJECT-GROUP
    OBJECTS {
        xcmCommsConfigRowStatus,
        xcmCommsConfigActiveOptionFirst,
        xcmCommsConfigActiveOptionLast,
        xcmCommsConfigGroupSupport,
        xcmCommsConfigCreateSupport,
        xcmCommsConfigUpdateSupport
    }
    STATUS      current
    DESCRIPTION
        "The Comms Config Group (Communications Configurations)."
    ::= { xcmCommsConfigMIBGroups 3 }
xcmCommsOptionGroup OBJECT-GROUP
    OBJECTS {
        xcmCommsOptionRowStatus,
        xcmCommsOptionTypeOID,
        xcmCommsOptionValueSyntax,
        xcmCommsOptionValueInteger,
        xcmCommsOptionValueOID,
        xcmCommsOptionValueString,
        xcmCommsOptionValueLocalization,
        xcmCommsOptionValueCodedCharSet,
        xcmCommsOptionNextIndex,
        xcmCommsOptionPreviousIndex,
        xcmCommsOptionFamilyIndex
    }
    STATUS      current
    DESCRIPTION
        "The Comms Option Group (Communications Configuration Options)."
    ::= { xcmCommsConfigMIBGroups 4 }
xcmCommsDirRecordGroup OBJECT-GROUP
    OBJECTS {
        xcmCommsDirRecordRowStatus,
        xcmCommsDirRecordKeyType,
        xcmCommsDirRecordKeyInteger,
        xcmCommsDirRecordKeyString,
        xcmCommsDirRecordParentType,
        xcmCommsDirRecordParentIndex
    }
    STATUS      current
    DESCRIPTION
        "Directory Record Group."
    ::= { xcmCommsConfigMIBGroups 5 }
xcmCommsDirAttributeGroup OBJECT-GROUP
    OBJECTS {
        xcmCommsDirAttributeRowStatus,
        xcmCommsDirAttributeValue
    }
    STATUS      current
    DESCRIPTION
        "Directory Attribute Group."
    ::= { xcmCommsConfigMIBGroups 6 }
xcmCommsDirStringGroup OBJECT-GROUP
    OBJECTS {
        xcmCommsDirStringRowStatus,
        xcmCommsDirStringValue
    }
    STATUS      current
    DESCRIPTION
        "Directory String Group."
    ::= { xcmCommsConfigMIBGroups 7 }
xcmCommsProtocolGroup OBJECT-GROUP
    OBJECTS {
        xcmCommsProtocolRowStatus
    }
    STATUS      current
    DESCRIPTION
        "Comms Protocol Group (available suites and protocols)."
    ::= { xcmCommsConfigMIBGroups 8 }
xcmSvcMonTC OBJECT-IDENTITY -- MODULE-IDENTITY
    STATUS   current
    DESCRIPTION
        "Version:   6.007.pub
        Textual Conventions companion to XCMI Service Monitoring MIB,
        the MIB module for basic configuration and active management
        of application services for network accessible host systems.
        See:    IETF Network Services Monitoring MIB
                (IETF RFC 1565, January 1994).
        See:    IETF Host Resources MIB
                (IETF RFC 2790, March 2000).
        See:    OSI Reference Model - Part 1:  Basic Reference Model
                (CCITT X.200:1992 | ISO 7498-1:1992).
        See:    OSI Reference Model - Part 4:  Systems Management
                (CCITT X.700:1992 | ISO 7498-4:1992).
        See:    Document Printing Application - Part 1: Abstract Service
                (ISO/IEC 10175-1 Final Text, March 1996).
        See:    POSIX System Administration - Part 4: Print Interfaces
                (IEEE 1387.4 / Draft 8, October 1994).
        Copyright (C) 1996-2005 Xerox Corporation. All Rights Reserved."
    ::= { xeroxCommonMIB 73 }
--
--
XcmSvcMonGroupSupport ::= TEXTUAL-CONVENTION
    STATUS      current
    DESCRIPTION
        "The terse conformance statement of ALL mandatory, conditionally
        mandatory, and optional XCMI Service Monitoring MIB groups
        supported by this management agent implementation (ie, version)
        on this host system, specified in a bit-mask.
        The current set of values (which MAY be extended in the future)
        is given below:
              1 : svcMonGeneralGroup            
              2 : svcMonQueueGroup              
              4 : svcMonQueueExtGroup           
              8 : svcMonServiceGroup            
             16 : svcMonServiceDetailGroup      
             32 : svcMonServiceMgmtGroup        
        Usage:  Conforming management agents SHALL accurately
        report their support for XCMI Service Monitoring MIB groups."
    SYNTAX      INTEGER (0..2147483647)  
XcmSvcMonJobConfirmSupport ::= TEXTUAL-CONVENTION
    STATUS      current
    DESCRIPTION
        "The support for handling job confirmation reports and/or job
        notifications on this host system, specified in a bit-mask.
        The current set of values (which MAY be extended in the future)
        is given below:
              1 : confirmOnError                
              2 : confirmOnWarning              
              4 : confirmOnAbort                
              8 : confirmOnCancel               
             16 : confirmOnComplete             
             32 : confirmOnReceive              
             64 : confirmOnDeliver              
            128 : confirmOnStateChange          
            256 : confirmOnStateReasonChange    
        Usage:  Conforming management agents SHALL accurately
        report their support for job confirmation reports."
    SYNTAX      INTEGER (0..2147483647)  
XcmSvcMonAttachmentPDLSupport ::= TEXTUAL-CONVENTION
    STATUS      current
    DESCRIPTION "
        This bit-mask defines a set of Page Description Languages
        which are acceptable for email attachments.
        The current set of values (which MAY be extended in the future)
        is given below:
              1 : attachmentTIFF            
              2 : attachmentPDF             
              4 : attachmentPS              
              8 : attachmentTXT             
             16 : attachmentPCL             
             32 : attachmentPRN             
             64 : attachmentJPG             
            128 : attachmentXPS             
            256 : attachmentPDFA            
        Usage:  The set of accepted attachment types is specified by 
            adding together the various PDL values."
    SYNTAX      INTEGER (0..2147483647)  
XcmSvcMonServiceMgmtOperation ::= TEXTUAL-CONVENTION
    STATUS      current
    DESCRIPTION
        "The most recent service management operation specified for
        this conceptual row in the 'xcmSvcMonServiceMgmtTable'.
        Usage:  The operations specified in this textual convention are
        derived from the 'object' and 'server' operations specified in
        the POSIX.3 standard.
        Note:   The enum of '0' (zero) in this textual convention is
        illegal in strict SMIv1 (see section 3.2.1.1 of RFC 1155), so
        this TC must be converted to an integer range for pure SMIv1."
    REFERENCE
        "See:   Section 4 'Print Utilities' (pages 71 to 212) of
                POSIX Sys Admin (IEEE 1387.4 / Draft 8, October 1994).
        See:    OBJECT clause in MODULE-COMPLIANCE macro of
                XCMI Service Monitoring MIB, for compliance info."
    SYNTAX      INTEGER {
        none(0),                        
        other(1),                       
        unknown(2),                     
        serviceCreate(1201),            
        serviceDelete(1202),            
        serviceList(1203),              
        serviceSet(1204),               
        serviceClean(1205),             
        serviceDisable(1206),           
        serviceEnable(1207),            
        servicePause(1208),             
        serviceResume(1209),            
        serviceShutdown(1210),          
        serviceManage(2201),            
        serviceRestart(2202),           
        serviceInstall(2221),           
        serviceUpgrade(2222),           
        serviceBackup(2223),            
        serviceRestore(2224),           
        serviceConfigure(2225),         
        serviceDiagnose(2226),          
        serviceResetCounters(2231),     
        serviceResetWarm(2232),         
        serviceResetCold(2233),         
        serviceResetFactory(2234),      
        serviceLogin(2241),             
        serviceLogout(2242)             
    }
XcmSvcMonServiceMgmtData ::= TEXTUAL-CONVENTION
    STATUS      current
    DESCRIPTION
        "The most recent simple service management data specified for
        this conceptual row in the 'xcmSvcMonServiceMgmtTable'.
        XCMI service management commands are passed as strings in 
        'xcmSvcMonServiceMgmtData' in the XCMI Service Monitoring MIB.
        XCMI management commands MAY also require one or more arguments
        (in addition to any specific variable bindings of MIB objects).
        Required arguments are passed as 'tagged string arguments' in
        'xcmSvcMonServiceMgmtData'.
        XCMI standard 'tags' for data in 'tagged string arguments',
        are specified in 'XcmHrDevMgmtCommandDataTag', or are as follows
      * DT  [Date and Time]
     XCMI standard 'system operation' types for use in 'SO' arguments
     (in 'xcmSvcMonServiceMgmtData') are as follows. The form of SO
     requests is 'SO=...'. This tagged data includes an extension
     to XcmHrDevMgmtCommandDataTag. 
     Each 'tagged string argument' substring is of the form:
               'TT=value:'
          where:
               'TT'     two-character 'tag', naming argument type
               '='      literal equal sign, beginning argument value
               'value'  human-readable string, encoding argument value
               ':'      literal colon, terminating argument value 
           Some tags require a qualifier.  For example, see 
           'CreatePublicFolder'.
   * SO (Service Operation - no object mapping)
   * TP (Type - no object mapping)
   * TM (Time - no object mapping)
   * FN (Filename - no object mapping)
   * CreatePublicFolder
   * DeleteAllPublicFiles
   * DeleteAllPublicFolders
   * DeletePublicFile
   * DeletePublicFolder
   * Disable
   * DiskOverwrite
   * S2DPrivateAccessPasswordOn
   * S2DPrivateAutoDeleteInterval
   * S2DPrivateAutoDeleteOn
   * S2DPrivateScanPasswordOn
   * S2DPublicAutoDeleteInterval
   * S2DPublicAutoDeleteOn
   * S2DPublicState
   * PrintCollationOff
   * PrintCollationOn
   * PrintMedia2ndSide
   * PrintMediaCardStock
   * PrintMediaColoredPaper
   * PrintMediaEnvelope
   * PrintMediaLabel
   * PrintMediaLetterhead
   * PrintMediaPlainPaper
   * PrintMediaPreprinted
   * PrintMediaPrepunched
   * PrintMediaSpecial
   * PrintMediaTransparency
   * PrintOrientationLandScape
   * PrintOrientationPortrait
   * PrintPlexOff
   * PrintPlexOn
   * PrintStaplingOff
   * PrintStaplingOn
        The above XCMI standard 'tags' MAY be extended in the future."
    REFERENCE
        "See:   Section 4 'Print Utilities' (pages 71 to 212) of
                POSIX Sys Admin (IEEE 1387.4 / Draft 8, October 1994).
        See:    OBJECT clause in MODULE-COMPLIANCE macro of
                XCMI Service Monitoring MIB, for compliance info.
        See:    Section 3.4 'XCMI Standard Tagged Management Data' and
                Section 3.5 'Simple Device Management Requests' in
                XCMI Ext to Host Resources TC.
        See:    Section 3.5.3 'Secure Simple Device Mgmt Requests' in
                XCMI Security TC."
    SYNTAX      OCTET STRING (SIZE (0..255))
XcmSvcMonServiceDetailClass ::= TEXTUAL-CONVENTION
    STATUS      current
    DESCRIPTION
        "A service detail class,
        used by system administrators and end users to specify
        the correct class for this service detail."
    SYNTAX      INTEGER {
        other(1),
        unknown(2),
        localOther(3),                  
        remoteOther(4),                 
        localAccountingServer(100),     
        localApplicationServer(101),    
        localDocumentServer(102),       
        localFileServer(103),           
        localLoggingServer(104),        
        localNameServer(105),           
        localNotificationServer(106),   
        localSecurityServer(107),       
        localMailServer(108),           
        localProtocolConfigurationServer(109),
        remoteAccountingServer(150),    
        remoteApplicationServer(151),   
        remoteDocumentServer(152),      
        remoteFileServer(153),          
        remoteLoggingServer(154),       
        remoteNameServer(155),          
        remoteNotificationServer(156),  
        remoteSecurityServer(157),      
        remoteMailServer(158),          
        remoteValidationServer(159),    
        localJobAccountingServer(200),  
        localJobLoggingServer(201),     
        localJobProcessingServer(202),  
        localJobTemplateServer(203),    
        remoteJobAccountingServer(250), 
        remoteJobLoggingServer(251),    
        remoteJobProcessingServer(252), 
        remoteJobTemplateServer(253),   
        localPhysicalRelay(301),        
        localDatalinkRelay(302),        
        localNetworkRelay(303),         
        localTransportRelay(304),       
        localSessionRelay(305),         
        localPresentationRelay(306),    
        localApplicationRelay(307),     
        remotePhysicalRelay(351),       
        remoteDatalinkRelay(352),       
        remoteNetworkRelay(353),        
        remoteTransportRelay(354),      
        remoteSessionRelay(355),        
        remotePresentationRelay(356),   
        remoteApplicationRelay(357),    
        localNetMgmtAgent(400),         
        localNetMgmtEventSource(401),   
        localNetMgmtEventTarget(402),   
        localNetMgmtProxy(403),         
        localNetMgmtStation(404),       
        remoteNetMgmtAgent(450),        
        remoteNetMgmtEventSource(451),  
        remoteNetMgmtEventTarget(452),  
        remoteNetMgmtProxy(453),        
        remoteNetMgmtStation(454),       
        remoteNetworkedHost(500),
        remoteDirectlyConnectHost(501),
        xeroxResourceService (562),
        wsPrintService (563),
        wsScanService (564),
        localAutomaticDiagnosticService(570),
        localDevice(600)
    }
XcmSvcMonServiceDetailType ::= TEXTUAL-CONVENTION
    STATUS      current
    DESCRIPTION
        "A system, service, or profile detail type,
        used by system administrators and end users to specify
        the correct type for this service detail.
        Usage:  Conforming management stations and management agents
        SHALL implement specified semantics for service detail types."
--
--
--
--
--
--
--
--
--
--
--
--
--
--
--
--
--      -   Current usage includes "update successful" or 
--      -    "update failed".
--      -   This value "update successful" is reset to '' 
--
--
--
--
--
--
--
--
--
--
--
--
--
--
--
--
--
--
--
--
--
--
--      - 0 (zero) indicates "no fax forwarding"
    REFERENCE
        "See:   'xcmSvcMonServiceDetailUnitClass' and
                'xcmSvcMonServiceDetailUnit' for syntax of detail."
    SYNTAX      INTEGER {
        other(1),
        unknown(2),
        systemOther(101),
        systemUnknown(102),
        systemServerTimeout(103),
        systemLoginCredentialsSource(104), 
        systemCertificateRequired(105),
        systemUseProxy(106),
        systemServiceTypeSupport(108),
        systemURI(109),
        systemOS(110),
        systemOSVersion(111),
        systemDescription(112),
        systemName(113),
        systemAddress(114),
        systemTree(115),
        systemContext(116),
        systemVolume(117),
        systemPath(118),
        systemCurrentLocale(119),
        systemProtocol(120),
        systemProtocolDetail(121),
        systemLoginName(122),
        systemLoginPassword(123),
        systemLoginDate(124),
        systemLogoutDate(125),
        systemAlias(126),
        systemLocation(127),
        systemOperatorMessage(128),
        systemProblemMessage(129),
        systemHelpName(130),
        systemHelpAddress(131),
        systemHelpDescription(132),
        systemHelpLocation(133),
        systemProtocolSecurity(135),
        systemAuthMethod(136),
        systemAuthSupport(137),
        systemState(140),
        systemConditions(141),
        systemAvailability(142),
        systemEnabled(143),
        systemPollingStartDate(150),
        systemPollingStartTime(151),
        systemPollingLastDate(152),
        systemPollingLastTime(153),
        systemPollingInterval(154),
        systemPollingEnabled(155),
        systemPhysicalNameSupport(160),
        systemPhysicalNameReady(161),
        systemLogicalNameSupport(162),
        systemLogicalNameReady(163),
        systemPhysicalIndexSupport(164),
        systemPhysicalIndexReady(165),
        systemLogicalIndexSupport(166),
        systemLogicalIndexReady(167),
        systemObjectClassSupport(170),
        systemEventSupport(171),
        systemJobValidateSupport(172),
        systemModifyDocSupport(173),
        systemTransferMethodSupport(174),
        systemLocaleSupport(175),
        systemPosixVerbsSupport(176),
        systemJobStateSupport(177),
        systemDeviceStatusSupport(179),
        systemDeviceXStatusSupport(180),
        systemTranslatorSupport(181),
        systemTranslatorReady(182),
        systemInitialValJobSupport(183),
        systemInitialValDocSupport(184),
        systemMultipleDocSupport(185),
        systemCancelDocSupport(186),
        systemForeignJobsVisible(187),
        systemJobConfirmEnabled(190),
        systemJobConfirmContent(191),
        systemJobConfirmSupport(192),
        systemJobConfirmPolicy(193),
        systemJobDefaultPDL(194),
        systemJobDefaultFeedResolution(195),
        systemJobDefaultXFeedResolution(196),
        systemJobDefaultDepthResolution(197),
        systemJobConfirmSheetColor(198),
        systemJobConfirmSheetType(199),
        systemFileSystemType(200),
        systemFilenameOther(201),
        systemFilenameUnknown(202),
        systemFilename(210),
        systemFilenameRoot(211),
        systemFilenameExtension(212),
        systemFilenameIncrement(213),
        systemFilenameWildcards(214),
        systemFilenameDefault(215),
        systemFilenameSoftLink(216),
        systemFilenameHardLink(217),
        systemFilenameConsole(218),
        systemFilenameDevice(219),
        systemFilenameDirectory(220),
        systemFilenameAccessRights(221),
        systemFileDateTime(222),
        systemFilePageCount(223),
        systemFaultLogFileURI(224),
        systemUsageLogFileURI(225),
        systemCustomPaperTypeFileURI(226),
        systemJobFinishingSupport(230),
        systemJobFinishingDefault(231),
        systemJobSidesSupport(232),
        systemJobSidesDefault(233),
        systemJobOrientationSupport(234),
        systemJobOrientationDefault(235),
        systemJobMediaSupport(236),
        systemJobMediaDefault(237),
        systemJobAttributeSupport(238),
        systemJobAttributeDefault(239),
        systemLifetimeUsage(240),
        systemLifetimeLimit(241),
        systemLifetimeErrorCount(242),
        systemLifetimeErrorLimit(243),
        systemLifetimeWarningCount(244),
        systemLifetimeWarningLimit(245),
        systemAccountingUsage(250),
        systemJobTemplateOther(251),
        systemJobTemplateUnknown(252),
        systemJobTemplateMaxStorage(260),
        systemJobTemplateMaxCount(261),
        systemJobTemplateCurrentCount(262),
        systemJobTemplateConfirmSheet(263),
        systemJobTemplateConfirmContent(264),
        systemJobTemplateConfirmSupport(265),
        systemJobTemplateConfirmPolicy(266),
        systemJobTemplateConfirmSheetColor(267),
        systemJobTemplateConfirmSheetType(268),
        systemJobTemplateAutoUpdate(269),
        systemJobTemplateStatus(270),
        systemJobCoverSheetEnabled(271),
        systemJobCoverSheetContent(272),
        systemJobCoverSheetContentKey(273),
        systemJobCoverSheetContentOID(274),
        systemJobCoverSheetContentText(275),
        systemJobErrorSheetEnabled(281),
        systemJobErrorSheetContent(282),
        systemJobErrorSheetContentKey(283),
        systemJobErrorSheetContentOID(284),
        systemJobErrorSheetContentText(285),
        systemJobReceiveContentKey(287),
        systemJobReceiveAttachmentType(288),
        systemJobShowSenderEnabled(291),
        systemJobShowSenderContent(292),
        systemJobShowSenderContentKey(293),
        systemJobShowSenderContentOID(294),
        systemJobShowSenderContentText(295),
        systemJobCopySenderEnabled(299),
        systemChannelOther(301),
        systemChannelUnknown(302),
        systemChannelDiagnostic(310),
        systemChannelFax(311),
        systemChannelFileTransfer(312),
        systemChannelImageProcess(313),
        systemChannelMail(314),
        systemChannelMultifunction(315), 
        systemChannelPrint(316),
        systemChannelScan(317),
        systemChannelOCR(318),
        systemChannelCopy(319),
        systemJobLogUserInformation (320),
        systemJobFrequency(322),
        systemJobDayOfWeek(323),
        systemJobDayOfMonth(324),
        systemJobTime(325),
        systemJobLtrA4Substitution(326),
        systemJobDefaultTray(327),
        systemJobPCLDraftMode(328),
        systemJobPrintQuality(329),
        systemJobIncompleteTimeout(331),
        systemJobProgrammingTimeout(332),
        systemJobHoldDeleteTimeout(333),
        systemJobPauseResumeTimeout(334),
        systemJobUserDefinedScrns(335),
        systemJobDefaultColorMode(336),
        systemJobDefaultOriginalType(337),
        systemJobAutoSuppression(338),
        systemJobCyanColorBalance(339),
        systemActivityReportEnabled(340),
        systemAccountingEnabled(341),
        systemLoggingEnabled(342),
        systemNotificationEnabled(343),
        systemPersonalName(344),
        systemJobMagentaColorBalance(345),
        systemJobYellowColorBalance(346),
        systemJobBlackColorBalance(347),
        systemDiskCapacityAvailable(348), 
        systemPriority(349),
        systemMailSubject(350),
        systemMailSignatureLine(351),
        systemMailMaxInputText(360),
        systemMailMaxInputAttach(361),
        systemMailMaxOutputText(362),
        systemMailMaxOutputAttach(363),
        systemMailConfirmRequest(364),
        systemMailConfirmReply(365),
        systemMailConfirmTimeout(366),
        systemMailFeatureReply(367),
        systemMailAddress(368),
        systemMailMaxInFragments(369),
        systemMailMaxOutFragments(370),
        systemMailMaxInAttachments(371),
        systemMailMaxOutAttachments(372),
        systemMailMaxInputSize(373),
        systemMailMaxOutputSize(374),
        systemMailSenderNetAuthSupport(375),
        systemMailSenderGuestAuthSupport(376),
        systemMailSenderNoAuthSupport(377),
        systemMailImageQualityType(378),
        systemMailOutputUsage(379),
        systemDirectoryMaxSearchResult(380),
        systemDirectorySearchTimeout(381),
        systemDirectoryLDAPServerType(382),
        systemDirectoryLDAPObjectClass(383),
        systemDirectoryLDAPAttribute(384),
        systemDirectoryLDAPSearchEnabled(385),
        systemDirectoryLocalSearchEnabled(386),
        systemDirectorySearchFilter(387),
        systemDirectorySearchSortKey(388),
        systemDirectoryAddressBookDefault(389),
        systemIncludeEventInteger(400),
        systemExcludeEventInteger(401),
        systemIncludeEventOID(402),
        systemExcludeEventOID(403),
        systemIncludeEventString(404),
        systemExcludeEventString(405),
        systemGuestJobPolicy(500),
        systemAlienJobPolicy(501),
        systemEventLogFullPolicy(502),
        systemJobLogFullPolicy(503),
        systemRequestLogFullPolicy(504),
        systemScriptName(510),
        systemConfigurationSetting(515), 
        systemValidationUserID(520),
        systemScanJobImageQualityType(550),
        systemScanJobOriginalType(551),
        systemBillingConfiguration(570),
        systemBillingSequenceNumber(571),
        autoDeleteEnabled(600),
        autoDeleteInterval(601),
        accessPasswordRequired(602),
        createPasswordRequired(603),
        scanMailboxName(604),
        systemColorPassword(610),
        faxSendOn(700),
        redialCount(701),
        redialTimeInterval(702),
        autoResendPolicy(703),
        autoResendCount(704),
        faxStartingRate(705),
        faxTransmissionHeader(706),
        faxReceiveOn(720),
        answerDelay(721),
        junkFaxPrevention(722),
        secureFaxOn(723),
        faxTransmissionReportOn(730),
        faxTransmissionReportType(731),
        faxReducedImageOn(732),
        faxAutoActivityReportOn(733),
        faxRule(740),
        faxRuleName(741),
        faxFileFormat(742),
 faxCountryCode(743),
 faxLineNumber(744),
 faxLineName(745),
 faxLineOptions(746),
 faxReceiveHeader(747)
    }
XcmSvcMonServiceType ::= TEXTUAL-CONVENTION
    STATUS      current
    DESCRIPTION
        "The explicit type of this system and/or end-user service."
    REFERENCE
        "See:   'xcmJobServiceType...' in XCMI Job Monitoring MIB
                'serviceType' in 'XcmCommsDirAttributeType' in
                XCMI Comms Config TC."
    SYNTAX      INTEGER {
        other(1),
        unknown(2),
        jobServiceScanToFile(101),
        jobServiceScanToPrint(102),
        jobServiceScanToFax(103),
        jobServiceScanToMailList(104),
        jobServiceFaxToFile(105),
        jobServiceFaxToPrint(106),
        jobServiceFaxToMailList(107),
        jobServicePrint(108),
        jobServiceFileToFax(109),
        jobServiceFileToMailList(110),
        jobServiceCopy(111),
        jobServiceFileToFile(112),
        jobServiceMultifunction(113),    
        jobServiceScanToInternetFax(114),
        jobServiceScanToServerFax(115),
        jobServiceScanToAnalogFax(116),
        jobServiceScanToNetworkFile(117), 
        jobServiceScanToHostFile(118),
        jobServiceScanToLocalFile(119),
        jobServicePrintToAnalogFax(120),
        jobServiceAnalogFax(121),
        jobServiceCapturePrintSaveReprintService(122),
        jobServiceScanFromApplication(123),
        adminObjectService(201),
        adminServerService(202),
        adminDeviceService(203),
        adminJobService(204),
        adminDocService(205),
        adminSecurityService(206),
        adminCommsService(207),
        systemServiceDiagnostic(300),
        systemServiceFax(301),
        systemServiceFileTransfer(302),
        systemServiceImageProcess(303),
        systemServiceMail(304),
        systemServiceMultifunction(305), 
        systemServicePrint(306),
        systemServiceScan(307),
        systemServiceOCR(308),
        systemServiceCopy(309),
        systemServiceAutoSoftwareUpgrade(310),
        systemServiceSoftwareUpgrade(311),
        systemBaseBusinessServices(312),
        localAccountingService(400),
        localApplicationService(401),
        localDocumentService(402),
        localFileService(403),
        localLoggingService(404),
        localNameService(405),
        localNotificationService(406),
        localSecurityService(407),
        localImmediateDiskOverwriteSecurityService(408),
        localOnDemandDiskOverwriteSecurityService(409),
        localDiskEncryptionSecurityService(410),
        localIDCardCopyService(411),
        localTieredBillingService(412),
        localOnDemandDiskOverwriteCompletionTime(413),
        localOnDemandDiskOverwriteCompletionStatus(414),
        localDeviceBillingService(415),
        remoteAccountingService(500),
        remoteApplicationService(501),
        remoteDocumentService(502),
        remoteFileService(503),
        remoteLoggingService(504),
        remoteNameService(505),
        remoteNotificationService(506),
        remoteSecurityService(507),
        remoteDeviceAuthenticationService(508),
        localECommerceService (550),
        -- "Printer Neighborhood"
        localDiscoveryService (560),
        localCBRService(561),
        webClientTemplateManagementService(600),
        webClientCustomUIService(601),
        webClientMetadataValidationService(602),
        automaticMeterReadService(603), 
        automaticSuppliesReplenishmentService(604), 
        automaticRemoteMonitoringService(605), 
        automaticRemoteDiagnosticService(606),
        automaticPagePackService(607),
        webServerTemplateManagementService(700),
        webServerCustomUIService(701),
        webServerMetadataValidationService(702),
        webServerBillingService(703),
        webServerSecurityConfigurationService(704),
        webServerProtocolConfigurationService(705),
        webServerServices(706),
        webServerMcAfeeSecurityService(707),
        webServerRemoteServicesConfigurationService(708)
    }
XcmSvcMonServiceStateDetail ::= TEXTUAL-CONVENTION
    STATUS      current
    DESCRIPTION
       "This TC represents a list of possible faults which further
        clarify the service status information exposed via the current 
 state, previous state, and conditions objects."
    SYNTAX      INTEGER {
        other(1),
        unknown(2),
        undefined3(3),
        undefined4(4),
        undefined5(5),
        undefined6(6),
        undefined7(7),
        requiredHardwareNotInstalled(8),
        requiredSoftwareNotInstalled(9),
        hardwareOptionNotEnabled(10),
        softwareOptionNotEnabled(11),
        rebootRequiredToEnableService(12),
        rebootRequiredToDisableService(13),
        serviceNotStarted(14),
        serviceNotConfigured(15),
        undefined16(16),
        undefined17(17),
        undefined18(18),
        undefined19(19),
        undefined20(20),
        undefined21(21),
        undefined22(22),
        undefined23(23),
        proxyModeOnly(24),
        notRegistered(25),
        registeredServiceNotEnabled(26),
        communicationFaultWithHost(27),
        communicationWithHostManuallyDisabled(28),
        rejectedByHostAlreadyRegistered(29),
        rejectedByHostInvalidSerialNo(30),
        registrationPending(31),
        deregistrationPending(32),
        internalError(33),
        requestPending(34),
        undefined35(35),
        undefined36(36),
        undefined37(37),
        undefined38(38),
        undefined39(39),
        criticalFaultImpactingService(40),
        nonCriticalFaultDegradingService(41),
        noFaultsImpactingService(42)
        }
XcmSvcMonSystemMailSenderNetAuthSupport ::= TEXTUAL-CONVENTION
    STATUS      current
    DESCRIPTION
        "The various values for the systemMailSenderNetAuthSupport
        attribute in the xcmHrDevDetailTable."
    SYNTAX      INTEGER {
        ldapNotEditable(1),       
        ldapEditableOnSuccess(2), 
        ldapEditableOnFailure(3), 
        ldapEditableOnEither(4),  
        nonLdapAuthNotEditable(5),
        nonLdapAuthEditable(6)    
    }
XcmImageQualityType ::= TEXTUAL-CONVENTION
    STATUS      current
    DESCRIPTION
        "Used to describe the different image quality types."
    SYNTAX      INTEGER {
        photo(1),
        text(2),
        phototext(3), 
        halftone(4),
        auto(5),
        newspaperMagazine(6),
        map(7)
    }
XcmOriginalType ::= TEXTUAL-CONVENTION
    STATUS      current
    DESCRIPTION
        "Used to describe the different original types."
    SYNTAX      INTEGER {
        none(0),
        printedOriginal(1),
        photocopiedOriginal(2),
        photograph(3),
        inkjetOriginal(4),
        solidInkOriginal(5)
    }
XcmOutputUsage ::= TEXTUAL-CONVENTION
    STATUS      current
    DESCRIPTION
        "Used to describe the ways that the output may be used."
    SYNTAX      INTEGER {
        sharingAndPrinting(1),
        highQualityPrinting(2),
        archivalRecord(3),
        ocr(4),
        custom(5),
        simpleScan(6)
    }
XcmLoginCredentialsSource ::= TEXTUAL-CONVENTION
    STATUS      current
    DESCRIPTION
        "Used to describe the Login Credentials source."
    SYNTAX      INTEGER {
        none(0),
        user(1),
        system(2),
        promptAlways(3),
        promptIfNeeded(4),
          --prompt if logged in user doesn't match name in template
        domainUser(5)
          --authenticated user and domain
    }
--
--
--
xCmSvcMonDummy   OBJECT IDENTIFIER ::= { xcmSvcMonTC 999 }
xCmSvcMonGroupSupport OBJECT-TYPE
    SYNTAX      XcmSvcMonGroupSupport
    MAX-ACCESS  not-accessible
    STATUS      current
    DESCRIPTION "Dummy - DO NOT USE"
    ::= { xCmSvcMonDummy 1 }
xCmSvcMonServiceMgmtOperation OBJECT-TYPE
    SYNTAX      XcmSvcMonServiceMgmtOperation
    MAX-ACCESS  not-accessible
    STATUS      current
    DESCRIPTION "Dummy - DO NOT USE"
    ::= { xCmSvcMonDummy 2 }
xCmSvcMonServiceMgmtData OBJECT-TYPE
    SYNTAX      XcmSvcMonServiceMgmtData
    MAX-ACCESS  not-accessible
    STATUS      current
    DESCRIPTION "Dummy - DO NOT USE"
    ::= { xCmSvcMonDummy 3 }
xCmSvcMonServiceDetailClass OBJECT-TYPE
    SYNTAX      XcmSvcMonServiceDetailClass
    MAX-ACCESS  not-accessible
    STATUS      current
    DESCRIPTION "Dummy - DO NOT USE"
    ::= { xCmSvcMonDummy 4 }
xCmSvcMonServiceDetailType OBJECT-TYPE
    SYNTAX      XcmSvcMonServiceDetailType
    MAX-ACCESS  not-accessible
    STATUS      current
    DESCRIPTION "Dummy - DO NOT USE"
    ::= { xCmSvcMonDummy 5 }
xCmSvcMonServiceType OBJECT-TYPE
    SYNTAX      XcmSvcMonServiceType
    MAX-ACCESS  not-accessible
    STATUS      current
    DESCRIPTION "Dummy - DO NOT USE"
    ::= { xCmSvcMonDummy 6 }
xCmSvcMonJobConfirmSupport OBJECT-TYPE
    SYNTAX      XcmSvcMonJobConfirmSupport
    MAX-ACCESS  not-accessible
    STATUS      current
    DESCRIPTION "Dummy - DO NOT USE"
    ::= { xCmSvcMonDummy 7 }
xCmSvcMonSystemMailSenderNetAuthSupport OBJECT-TYPE
    SYNTAX      XcmSvcMonSystemMailSenderNetAuthSupport
    MAX-ACCESS  not-accessible
    STATUS      current
    DESCRIPTION "Dummy - DO NOT USE"
    ::= { xCmSvcMonDummy 8 }
xCmSvcMonAttachmentPDLSupport OBJECT-TYPE
    SYNTAX      XcmSvcMonAttachmentPDLSupport
    MAX-ACCESS  not-accessible
    STATUS      current
    DESCRIPTION "Dummy - DO NOT USE"
    ::= { xCmSvcMonDummy 9 }
xCmImageQualityType OBJECT-TYPE
    SYNTAX      XcmImageQualityType
    MAX-ACCESS  not-accessible
    STATUS      current
    DESCRIPTION "Dummy - DO NOT USE"
    ::= { xCmSvcMonDummy 10 }
xCmOutputUsage OBJECT-TYPE
    SYNTAX      XcmOutputUsage
    MAX-ACCESS  not-accessible
    STATUS      current
    DESCRIPTION "Dummy - DO NOT USE"
    ::= { xCmSvcMonDummy 11 }
xCMLoginCredentialsSource  OBJECT-TYPE
    SYNTAX      XcmLoginCredentialsSource 
    MAX-ACCESS  not-accessible
    STATUS      current
    DESCRIPTION "Dummy - DO NOT USE"
    ::= { xCmSvcMonDummy 12 }
xcmSvcMonMIB OBJECT-IDENTITY -- MODULE-IDENTITY
    STATUS   current
    DESCRIPTION
        "Version:   5.502.pub
        The MIB module for basic configuration and active management
        of application services for network accessible host systems.
        See:    IETF Network Services Monitoring MIB
                (IETF RFC 1565, January 1994).
        See:    IETF Host Resources MIB
                (IETF RFC 2790, March 2000).
        See:    OSI Reference Model - Part 1:  Basic Reference Model
                (CCITT X.200:1992 | ISO 7498-1:1992).
        See:    OSI Reference Model - Part 4:  Systems Management
                (CCITT X.700:1992 | ISO 7498-4:1992).
        Copyright (C) 1996-2006 Xerox Corporation. All Rights Reserved."
    ::= { xeroxCommonMIB 74 }
xcmSvcMonZeroDummy OBJECT IDENTIFIER ::= { zeroDotZero 74 }
--
--
--
xcmSvcMonGeneral        OBJECT IDENTIFIER ::= { xcmSvcMonMIB 1 }
xcmSvcMonGeneralTable OBJECT-TYPE
    SYNTAX      SEQUENCE OF XcmSvcMonGeneralEntry
    MAX-ACCESS  not-accessible
    STATUS      current
    DESCRIPTION
        "A table of general counters and capabilities for ease of use
        of the XCMI Service Monitoring MIB on this host system.
        Usage:  The ONLY valid row in the 'xcmSvcMonGeneralTable'
        SHALL have an 'xcmSvcMonGeneralIndex' of one ('1')."
    ::= { xcmSvcMonGeneral 2 }
xcmSvcMonGeneralEntry OBJECT-TYPE
    SYNTAX      XcmSvcMonGeneralEntry
    MAX-ACCESS  not-accessible
    STATUS      current
    DESCRIPTION
        "An entry of general counters and capabilities for ease of use
        of the XCMI Service Monitoring MIB on this host system.
        Usage:  The ONLY valid row in the 'xcmSvcMonGeneralTable'
        SHALL have an 'xcmSvcMonGeneralIndex' of one ('1')."
    INDEX       { xcmSvcMonGeneralIndex }
    ::= { xcmSvcMonGeneralTable 1 }
XcmSvcMonGeneralEntry ::= SEQUENCE {
        xcmSvcMonGeneralIndex           Ordinal32,
        xcmSvcMonGeneralRowStatus       RowStatus,
        xcmSvcMonGeneralVersionID       ProductID,
        xcmSvcMonGeneralVersionDate     DateAndTime,
        xcmSvcMonGeneralGroupSupport    XcmSvcMonGroupSupport,
        xcmSvcMonGeneralCreateSupport   XcmSvcMonGroupSupport,
        xcmSvcMonGeneralUpdateSupport   XcmSvcMonGroupSupport
    }
xcmSvcMonGeneralIndex OBJECT-TYPE
    SYNTAX      Ordinal32
    MAX-ACCESS  not-accessible
    STATUS      current
    DESCRIPTION
        "A unique value used by this host system to identify this
        conceptual row in the 'xcmSvcMonGeneralTable'.
        Usage:  The ONLY valid row in the 'xcmSvcMonGeneralTable'
        SHALL have an 'xcmSvcMonGeneralIndex' of one ('1').
        Usage:  'xcmSvcMonGeneralRowStatus' is 'read-only' because
        the ONLY valid conceptual row SHALL NOT be deleted."
    ::= { xcmSvcMonGeneralEntry 1 }
xcmSvcMonGeneralRowStatus OBJECT-TYPE
    SYNTAX      RowStatus
    MAX-ACCESS  read-only
    STATUS      current
    DESCRIPTION
        "This object is used to display status of the ONLY valid
        conceptual row in the 'xcmSvcMonGeneralTable'.
        Usage:  'xcmSvcMonGeneralRowStatus' is 'read-only' because
        the ONLY valid conceptual row SHALL NOT be deleted."
    ::= { xcmSvcMonGeneralEntry 2 }
xcmSvcMonGeneralVersionID OBJECT-TYPE
    SYNTAX      ProductID
    MAX-ACCESS  read-only
    STATUS      current
    DESCRIPTION
        "The software product ID of the SNMP sub-agent which implements
        the XCMI Service Monitoring MIB on this host system.
        Usage:  This object SHALL specify the software product ID of an
        SNMP sub-agent (possibly also found in a conceptual row in the
        'hrSWRunTable' and/or 'hrSWInstalledTable' in the IETF HR MIB).
        This object SHALL NOT specify a particular release of the XCMI
        Service Monitoring MIB, or the whole host system product.
        Note:   Contrast with 'sysObjectID' for the whole SNMP agent in
        the IETF MIB-II (RFC 1213) and 'hrDeviceID' for the whole device
        (or whole product, in the case of 'xcmHrDevice...') in the IETF
        Host Resources MIB (RFC 2790)."
    REFERENCE
        "See:   'hrSW[Installed|Run]ID' in the Software Installed and
                Software Running groups of the IETF HR MIB (RFC 2790)."
    DEFVAL      { zeroDotZero }   
    ::= { xcmSvcMonGeneralEntry 3 }
xcmSvcMonGeneralVersionDate OBJECT-TYPE
    SYNTAX      DateAndTime
    MAX-ACCESS  read-only
    STATUS      current
    DESCRIPTION
        "The software build date of the SNMP sub-agent which implements
        the XCMI Service Monitoring MIB on this host system.
        Usage:  This object SHALL specify the BUILD date of the SNMP
        sub-agent software (not available elsewhere in IETF/XCMI MIBs).
        This object SHALL NOT specify the INSTALL date of the SNMP
        sub-agent software on this host system, nor the RESET date.
        Note:   Contrast with 'hrSWInstalledDate' in the Software
        Installed group of the IETF Host Resources MIB (RFC 2790), and
        'xcmHrDevInfoResetDate' in the Device Info group of the XCMI
        Host Resources Extensions MIB."
    REFERENCE
        "See:   'hrSW[Installed|Run]ID' in the Software Installed and
                Software Running groups of the IETF HR MIB (RFC 2790)."
    DEFVAL      { '0000000000000000'H } 
    ::= { xcmSvcMonGeneralEntry 4 }
xcmSvcMonGeneralGroupSupport OBJECT-TYPE
    SYNTAX      XcmSvcMonGroupSupport
    MAX-ACCESS  read-only
    STATUS      current
    DESCRIPTION
        "The terse conformance statement of ALL mandatory, conditionally
        mandatory, and optional XCMI Service Monitoring MIB groups
        supported by this management agent implementation (ie, version)
        on this host system, specified in a bit-mask.
        Usage:  Conforming management agents SHALL accurately
        report their support for XCMI Service Monitoring MIB groups."
    DEFVAL      { 1 }                   
    ::= { xcmSvcMonGeneralEntry 5 }
xcmSvcMonGeneralCreateSupport OBJECT-TYPE
    SYNTAX      XcmSvcMonGroupSupport
    MAX-ACCESS  read-only
    STATUS      current
    DESCRIPTION
        "The terse conformance statement of ALL mandatory, conditionally
        mandatory, and optional XCMI Service Monitoring MIB groups
        supported for dynamic row creation (via '...RowStatus')
        by this management agent implementation (ie, version)
        on this host system, specified in a bit-mask.
        Usage:  Conforming management agents SHALL accurately
        report their support for XCMI Service Monitoring MIB groups."
    DEFVAL      { 0 }                   
    ::= { xcmSvcMonGeneralEntry 6 }
xcmSvcMonGeneralUpdateSupport OBJECT-TYPE
    SYNTAX      XcmSvcMonGroupSupport
    MAX-ACCESS  read-only
    STATUS      current
    DESCRIPTION
        "The terse conformance statement of ALL mandatory, conditionally
        mandatory, and optional XCMI Service Monitoring MIB groups
        supported for existing row update (via SNMP Set-Request PDUs)
        by this management agent implementation (ie, version)
        on this host system, specified in a bit-mask.
        Usage:  Conforming management agents SHALL accurately
        report their support for XCMI Service Monitoring MIB groups."
    DEFVAL      { 0 }                   
    ::= { xcmSvcMonGeneralEntry 7 }
--
--
--
xcmSvcMonQueue          OBJECT IDENTIFIER ::= { xcmSvcMonMIB 3 }
xcmSvcMonQueueTable OBJECT-TYPE
    SYNTAX      SEQUENCE OF XcmSvcMonQueueEntry
    MAX-ACCESS  not-accessible
    STATUS      current
    DESCRIPTION
        "A table of the external job queues supported and (possibly)
        active, for some 'physical', 'logical', or 'logicalAndPhysical'
        device on this host system.
        Usage:  These externally visible job queues MAY actually be
        configured on external print/file servers (remote) or on the
        managed system itself (local).
        Usage:  For example, a 'logical printer' might support one or
        more external (network) job queues.
        Note:   The 'xcmJobGenBasicTable' in the XCMI Job Monitoring MIB
        (indexed by 'hrDeviceIndex' from the IETF Host Resources MIB)
        displays the unordered union of all jobs present in the (one or
        more) 'local' queues supported by each 'physical', 'logical', or
        'logicalAndPhysical' device on this host system.
        Note:   The XCMI Comms Engine MIB is indexed by devices of type
        'CPU', while the 'xcmSvcMonQueueTable' is indexed by application
        devices of type 'printer', 'fax', etc.
        Usage:  Throughout this specification, the term 'stable storage'
        refers to storage which is reliable over long durations (years)
        and is NOT destroyed by host system reboot (eg, battery-backed
        DRAM is 'stable storage' - while simple DRAM is NOT 'stable
        storage').  Examples of valid 'stable storage' include:  NVRAM,
        hard disk, EEPROM, etc.
        Usage:  Conforming implementations SHALL preserve active
        queue table objects across management agent power cycles,
        and SHALL implement one of the following two methods:
        1)  The agent SHALL store queue table objects directly in
            'stable storage'; or
        2)  The agent SHALL automatically checkpoint all active queue
            table objects to 'stable storage' with reasonable frequency
            (either due to a write to some queue table object, or upon
            expiration of a product-specific timeout).
        Usage:  Conforming implementations MAY (optionally) support
        one of the following two 'checkpoint protocols':
        1)  A client sends a 'Set' of 'xcmSvcMonQueueRowStatus' to
            'active(1)', to request that a 'checkpoint' be performed;
        2a) An agent which supports 'rapid checkpoint',
            completes the checkpoint to 'stable storage', and
            sends a 'SetResponse' with 'noError(0)';
            <or>
        2b) An agent which supports 'delayed checkpoint',
            changes 'xcmSvcMonQueueRowStatus' to 'notInService(2)',
            sends a 'SetResponse' with 'noError(0)',
            completes the checkpoint to 'stable storage', and
            changes 'xcmSvcMonQueueRowStatus' back to 'active(1)'."
    REFERENCE
        "See:   'xcmSvcMonQueueOnSystem', and
                'xcmSvcMonQueueRoutingIndex'.
        See:    'xcmHrDevInfoRealization' in XCMI Ext to Host Res MIB.
        See:    'xcmJobGenBasicTable' in XCMI Job Monitoring MIB."
    ::= { xcmSvcMonQueue 2 }
xcmSvcMonQueueEntry OBJECT-TYPE
    SYNTAX      XcmSvcMonQueueEntry
    MAX-ACCESS  not-accessible
    STATUS      current
    DESCRIPTION
        "An entry for an external job queue supported and (possibly)
        active, for some 'physical', 'logical', or 'logicalAndPhysical'
        device on this host system.
        Usage:  This externally visible job queue MAY actually be
        configured on an external print/file server (remote) or on the
        managed system itself (local)."
    REFERENCE
        "See:   'xcmSvcMonQueueOnSystem', and
                'xcmSvcMonQueueRoutingIndex'.
        See:    'xcmHrDevInfoRealization' in XCMI Ext to Host Res MIB.
        See:    'xcmJobGenBasicTable' in XCMI Job Monitoring MIB."
    INDEX       { hrDeviceIndex,
                  xcmSvcMonQueueIndex }
    ::= { xcmSvcMonQueueTable 1 }
XcmSvcMonQueueEntry ::= SEQUENCE {
        xcmSvcMonQueueIndex             Ordinal32,
        xcmSvcMonQueueRowStatus         RowStatus,
        xcmSvcMonQueueDomain            XcmCommsStackExtProtocol,
        xcmSvcMonQueuePath              XcmFixedLocaleDisplayString,
        xcmSvcMonQueueName              XcmFixedLocaleDisplayString,
        xcmSvcMonQueueOnSystem          TruthValue
    }
xcmSvcMonQueueIndex OBJECT-TYPE
    SYNTAX      Ordinal32
    MAX-ACCESS  read-only
    STATUS      current
    DESCRIPTION
        "A unique value used by this host system to identify this
        conceptual row in the 'xcmSvcMonQueueTable'.
        Usage:  This object SHALL be permanent (ie, preserved
        across all hardware resets)."
    ::= { xcmSvcMonQueueEntry 1 }
xcmSvcMonQueueRowStatus OBJECT-TYPE
    SYNTAX      RowStatus
    MAX-ACCESS  read-create
    STATUS      current
    DESCRIPTION
        "This object is used to create and delete individual conceptual
        rows in the 'xcmSvcMonQueueTable' and (optionally) in the
        'xcmSvcMonQueueExtTable' (if implementated on this system).
        Usage:  Conforming implementations which support static rows
        SHALL support 'active' and 'notInService' writes to this
        'xcmSvcMonQueueRowStatus' row status object; and
        SHALL clear the 'svcMonQueueGroup' bit in
        'xcmSvcMonGeneralCreateSupport' in the 'xcmSvcMonGeneralTable'.
        Usage:  Conforming implementations which support dynamic rows
        SHALL support 'createAndGo' and 'destroy' writes to this
        'xcmSvcMonQueueRowStatus' row status object; and
        SHALL set the 'svcMonQueueGroup' bit in
        'xcmSvcMonGeneralCreateSupport' in the 'xcmSvcMonGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmSvcMonGeneralCreateSupport' in
                'xcmSvcMonGeneralTable'.
        See:    'RowStatus' in IETF SNMPv2 TC (RFC 1443/1903/2579).
        See:    'xcmHrDevMgmtCommandData' in XCMI HRX MIB and
                'xcmSecUserMgmtData' in XCMI Security MIB."
    ::= { xcmSvcMonQueueEntry 2 }
xcmSvcMonQueueDomain OBJECT-TYPE
    SYNTAX      XcmCommsStackExtProtocol
    MAX-ACCESS  read-create
    STATUS      current
    DESCRIPTION
        "The queue namespace domain (directory protocol) for the queue
        path and queue name (eg, 'internetDNS', 'netwareNDS').
        Usage:  This queue namespace domain SHALL be a valid
        directory protocol enumeration from 'XcmCommsStackExtProtocol'
        in the XCMI Comms Engine TC.
        Usage:  When a remote management station (client) creates a row
        in 'xcmSvcMonQueueTable' (via 'xcmSvcMonQueueRowStatus'),
        this queue namespace domain SHALL be specified.
        Note:   For implementation efficiency, this object uses the
        integer 'XcmCommStackExtProtocol' values (from the XCMI Comms
        Engine MIB) rather than the equivalent 'XcmCO...' OID values
        (from the XCMI Comms Config MIB)."
    REFERENCE
        "See:   'xcmSvcMonQueue[Path|Name]'"
    DEFVAL      { unknown }             
    ::= { xcmSvcMonQueueEntry 3 }
xcmSvcMonQueuePath OBJECT-TYPE
    SYNTAX      XcmFixedLocaleDisplayString (SIZE (0..255))
    MAX-ACCESS  read-create
    STATUS      current
    DESCRIPTION
        "Human-readable queue path, used by system administrators
        and end-users to specify the 'full network path' of a file
        server (eg, Novell Bindery) or directory tree (eg, Novell NDS)
        which, when prefixed to the following 'xcmSvcMonQueueName'
        object, specifies a 'full network queue name' of this queue.
        Usage:  This queue path SHOULD be the one normally used in a
        command shell for control of this queue.
        Usage:  When a remote management station (client) creates a row
        in 'xcmSvcMonQueueTable' (via 'xcmSvcMonQueueRowStatus'),
        this queue path SHALL be specified."
    REFERENCE
        "See:   'xcmSvcMonQueue[Domain|Name]'"
    DEFVAL      { ''H }                 
    ::= { xcmSvcMonQueueEntry 4 }
xcmSvcMonQueueName OBJECT-TYPE
    SYNTAX      XcmFixedLocaleDisplayString (SIZE (0..255))
    MAX-ACCESS  read-create
    STATUS      current
    DESCRIPTION
        "Human-readable queue name, used by system administrators
        and end-users to specify the 'simple name' of this queue (or in
        the Novell NDS case, the context and simple name concatenated),
        which, when suffixed to the preceding 'xcmSvcMonQueuePath'
        object, specifies a 'full network queue name' of this queue.
        Usage:  This queue name SHOULD be the one normally used in a
        command shell for control of this queue.
        Usage:  When a remote management station (client) creates a row
        in 'xcmSvcMonQueueTable' (via 'xcmSvcMonQueueRowStatus'),
        this queue name SHALL be specified."
    REFERENCE
        "See:   'xcmSvcMonQueue[Domain|Path]'
        See:    'xcmJobGenBasicTable' in XCMI Job Monitoring MIB."
    DEFVAL      { ''H }                 
    ::= { xcmSvcMonQueueEntry 5 }
xcmSvcMonQueueOnSystem OBJECT-TYPE
    SYNTAX      TruthValue
    MAX-ACCESS  read-create
    STATUS      current
    DESCRIPTION
        "Specifies whether this queue is present on this host system
        (local) or is on another network system (remote)."
    REFERENCE
        "See:   'xcmSvcMonQueueRoutingIndex'."
    DEFVAL      { true }                
    ::= { xcmSvcMonQueueEntry 6 }
--
--
--
xcmSvcMonQueueExt       OBJECT IDENTIFIER ::= { xcmSvcMonMIB 4 }
xcmSvcMonQueueExtTable OBJECT-TYPE
    SYNTAX      SEQUENCE OF XcmSvcMonQueueExtEntry
    MAX-ACCESS  not-accessible
    STATUS      current
    DESCRIPTION
        "A table which augments 'xcmSvcMonQueueTable', with dynamic
        queue routing (forwarding), state, conditions, fault info,
        create date, lifetime jobs, and last connect date and jobs.
        Usage:  Conforming implementations SHALL preserve active
        queue table objects across management agent power cycles,
        and SHALL implement one of the following two methods:
        1)  The agent SHALL store queue table objects directly in
            'stable storage'; or
        2)  The agent SHALL automatically checkpoint all active queue
            table objects to 'stable storage' with reasonable frequency
            (either due to a write to some queue table object, or upon
            expiration of a product-specific timeout)."
    REFERENCE
        "See:   'xcmSvcMonQueueTable' in this MIB module."
    ::= { xcmSvcMonQueueExt 2 }
xcmSvcMonQueueExtEntry OBJECT-TYPE
    SYNTAX      XcmSvcMonQueueExtEntry
    MAX-ACCESS  not-accessible
    STATUS      current
    DESCRIPTION
        "An entry which augments 'xcmSvcMonQueueTable', with dynamic
        queue routing (forwarding), state, conditions, and fault info."
    REFERENCE
        "See:   'xcmSvcMonQueueTable' in this MIB module."
    AUGMENTS    { xcmSvcMonQueueEntry }
    ::= { xcmSvcMonQueueExtTable 1 }
XcmSvcMonQueueExtEntry ::= SEQUENCE {
        xcmSvcMonQueueRoutingIndex      Cardinal32,
        xcmSvcMonQueueState             XcmCommsMgmtState,
        xcmSvcMonQueueConditions        XcmCommsMgmtConditions,
        xcmSvcMonQueueFaultCount        Counter32,
        xcmSvcMonQueueFaultCode         Integer32,
        xcmSvcMonQueueFaultString       XcmFixedLocaleDisplayString,
        xcmSvcMonQueueRowCreateDate     DateAndTime,
        xcmSvcMonQueueRowTotalJobs      Counter32,
        xcmSvcMonQueueLastConnectDate   DateAndTime,
        xcmSvcMonQueueLastConnectJobs   Counter32
    }
xcmSvcMonQueueRoutingIndex OBJECT-TYPE
    SYNTAX      Cardinal32
    MAX-ACCESS  read-create
    STATUS      current
    DESCRIPTION
        "The (optional) routing index of this queue.
        Usage:  This (optional) routing index, for queue indirection
        mapping, specifies 'xcmSvcMonQueueIndex' for the NEXT queue
        closer to (or on) this host system, or zero if none.
        Usage:  It is common for more than one off-system (remote) queue
        to be forwarded to the same on-system (local) queue.  Multiple
        off-system (remote) entries in the 'xcmSvcMonQueueTable' (for a
        given device) MAY forward to the same on-system (local) entry."
    REFERENCE
        "See:   'xcmSvcMonQueueOnSystem'."
    DEFVAL      { 0 }                   
    ::= { xcmSvcMonQueueExtEntry 1 }
xcmSvcMonQueueState OBJECT-TYPE
    SYNTAX      XcmCommsMgmtState
    MAX-ACCESS  read-only
    STATUS      current
    DESCRIPTION
        "The current state of this queue.
        Usage:  This queue state specifies the operational state
        of the application service or the network communications path
        to this queue.
        Usage:  This queue state need NOT be reported for a
        'remote' queue (ie, 'xcmSvcMonQueueOnSystem' is 'false'),
        although in some cases (eg, Novell PServer), the state of
        (connectivity to) the 'remote' queue is known (and SHALL
        be reported) on the managed system.
        Usage:  This queue state SHALL be as reported in
        the XCMI Comms Config/Engine MIB objects for this queue."
    REFERENCE
        "See:   'XcmCommsMgmt[State|Conditions]' in XCMI Comms Engine.
        See:    'xcmSvcMonQueueConditions'"
    DEFVAL      { closed }              
    ::= { xcmSvcMonQueueExtEntry 2 }
xcmSvcMonQueueConditions OBJECT-TYPE
    SYNTAX      XcmCommsMgmtConditions
    MAX-ACCESS  read-only
    STATUS      current
    DESCRIPTION
        "The current conditions (ie, state reasons) of this queue.
        Usage:  These queue conditions qualify the operational state
        of the application service or the network communications path
        to this queue.
        Usage:  These queue conditions need NOT be reported for a
        'remote' queue (ie, 'xcmSvcMonQueueOnSystem' is 'false'),
        although in some cases (eg, Novell PServer), the state of
        (connectivity to) the 'remote' queue is known (and SHALL
        be reported) on the managed system.
        Usage:  These queue conditions SHALL be as reported in
        the XCMI Comms Config/Engine MIB objects for this queue."
    REFERENCE
        "See:   'XcmCommsMgmt[State|Conditions]' in XCMI Comms Engine.
        See:    'xcmSvcMonQueueState'"
    DEFVAL      { 0 }                   
    ::= { xcmSvcMonQueueExtEntry 3 }
xcmSvcMonQueueFaultCount OBJECT-TYPE
    SYNTAX      Counter32
    MAX-ACCESS  read-only
    STATUS      current
    DESCRIPTION
        "The current fault count of this queue.
        Usage:  This queue fault count qualifies the operational state
        of the application service or the network communications path
        to this queue.
        Usage:  This queue fault count need NOT be reported for a
        'remote' queue (ie, 'xcmSvcMonQueueOnSystem' is 'false'),
        although in some cases (eg, Novell PServer), the state of
        (connectivity to) the 'remote' queue is known (and SHALL
        be reported) on the managed system.
        Usage:  This queue fault count SHALL be as reported in
        any relevant device- or service-specific MIB for this queue.
        Usage:  Although no default value ('DEFVAL' clause) is permitted
        (by IETF SMIv2) for this counter, conforming host systems SHALL
        zero this counter upon conceptual row creation."
    REFERENCE
        "See:   'xcmSvcMonQueue[State|Conditions]'"
    ::= { xcmSvcMonQueueExtEntry 4 }
xcmSvcMonQueueFaultCode OBJECT-TYPE
    SYNTAX      Integer32
    MAX-ACCESS  read-only
    STATUS      current
    DESCRIPTION
        "Encoded current fault code of this queue.
        Usage:  This queue fault code qualifies the operational state
        of the application service or the network communications path
        to this queue.
        Usage:  This queue fault code need NOT be reported for a
        'remote' queue (ie, 'xcmSvcMonQueueOnSystem' is 'false'),
        although in some cases (eg, Novell PServer), the state of
        (connectivity to) the 'remote' queue is known (and SHALL
        be reported) on the managed system.
        Usage:  This queue fault code SHALL be as reported in
        any relevant device- or service-specific MIB for this queue."
    REFERENCE
        "See:   'xcmSvcMonQueue[State|Conditions]'"
    DEFVAL      { 0 }                   
    ::= { xcmSvcMonQueueExtEntry 5 }
xcmSvcMonQueueFaultString OBJECT-TYPE
    SYNTAX      XcmFixedLocaleDisplayString (SIZE (0..255))
    MAX-ACCESS  read-only
    STATUS      current
    DESCRIPTION
        "Human-readable current fault string of this queue.
        Usage:  This queue fault string qualifies the operational state
        of the application service or the network communications path
        to this queue.
        Usage:  This queue fault string need NOT be reported for a
        'remote' queue (ie, 'xcmSvcMonQueueOnSystem' is 'false'),
        although in some cases (eg, Novell PServer), the state of
        (connectivity to) the 'remote' queue is known (and SHALL
        be reported) on the managed system.
        Usage:  This queue fault string SHALL be as reported in
        any relevant device- or service-specific MIB for this queue."
    REFERENCE
        "See:   'xcmSvcMonQueue[State|Conditions]'"
    DEFVAL      { ''H }                 
    ::= { xcmSvcMonQueueExtEntry 6 }
xcmSvcMonQueueRowCreateDate OBJECT-TYPE
    SYNTAX      DateAndTime
    MAX-ACCESS  read-only
    STATUS      current
    DESCRIPTION
        "The date and time of creation of this conceptual row in the
        'xcmSvcMonQueueTable' (and 'xcmSvcMonQueueExtTable')."
    REFERENCE
        "See:   'xcmSvcMonQueueOnSystem'.
        See:    'xcmSvcMonQueueRowTotalJobs'"
    DEFVAL      { '0000000000000000'H } 
    ::= { xcmSvcMonQueueExtEntry 7 }
xcmSvcMonQueueRowTotalJobs OBJECT-TYPE
    SYNTAX      Counter32
    MAX-ACCESS  read-only
    STATUS      current
    DESCRIPTION
        "The total jobs completed for this remote/local external
        job queue, since 'xcmSvcMonQueueRowCreateDate'.
        Usage:  Although no default value ('DEFVAL' clause) is permitted
        (by IETF SMIv2) for this counter, conforming host systems SHALL
        zero this counter upon conceptual row creation."
    REFERENCE
        "See:   'xcmSvcMonQueueOnSystem'.
        See:    'xcmSvcMonQueueRowTotalJobs'"
    ::= { xcmSvcMonQueueExtEntry 8 }
xcmSvcMonQueueLastConnectDate OBJECT-TYPE
    SYNTAX      DateAndTime
    MAX-ACCESS  read-only
    STATUS      current
    DESCRIPTION
        "The date and time of last connect (and/or login) to this remote
        or local external job queue."
    REFERENCE
        "See:   'xcmSvcMonQueueOnSystem'.
        See:    'xcmSvcMonQueueLastConnectJobs'"
    DEFVAL      { '0000000000000000'H } 
    ::= { xcmSvcMonQueueExtEntry 9 }
xcmSvcMonQueueLastConnectJobs OBJECT-TYPE
    SYNTAX      Counter32
    MAX-ACCESS  read-only
    STATUS      current
    DESCRIPTION
        "The total jobs completed for this remote/local external
        job queue, since 'xcmSvcMonQueueLastConnectDate'.
        Usage:  Although no default value ('DEFVAL' clause) is permitted
        (by IETF SMIv2) for this counter, conforming host systems SHALL
        zero this counter upon conceptual row creation."
    REFERENCE
        "See:   'xcmSvcMonQueueOnSystem'.
        See:    'xcmSvcMonQueueRowTotalJobs'"
    ::= { xcmSvcMonQueueExtEntry 10 }
xcmSvcMonQueueExtV1EventOID OBJECT-IDENTITY
    STATUS      current
    DESCRIPTION
        "The value of the enterprise-specific OID in an SNMPv1 trap sent
        whenever 'xcmSvcMonQueue[State|Conditions|FaultCount]' changes.
        See SNMPv2 trap definition 'xcmSvcMonQueueExtV2Event'
        below for 'special semantics'."
    ::= { xcmSvcMonQueueExt 1 }
xcmSvcMonQueueExtV2EventPrefix
    OBJECT IDENTIFIER ::= { xcmSvcMonQueueExtV1EventOID 0 }
xcmSvcMonQueueExtV2Event NOTIFICATION-TYPE
    OBJECTS {
        xcmSvcMonQueueIndex,
        xcmSvcMonQueueOnSystem,
        xcmSvcMonQueueState,
        xcmSvcMonQueueConditions,
        xcmSvcMonQueueFaultCount,
        xcmSvcMonQueueFaultCode,
        xcmSvcMonQueueFaultString
    }
    STATUS      current
    DESCRIPTION
        "This is the definition of the SNMPv2 trap sent whenever
        'xcmSvcMonQueue[State|Conditions|FaultCount]' changes.
        Note:   The variable-bindings of this trap have been chosen to
        specify a complete associated queue status change while keeping
        trap messages reasonably concise (generally a few hundred octets
        at most).
        This notification has the following special semantics:
            o   The queue's 'xcmSvcMonQueueIndex' field
                value SHALL be appended to this trap object ID,
                as a BER binary OID suffix.
        This trap OID qualifier allows service management/monitoring
        applications to limit the alerts they receive to ones generated 
        by associated queues of interest."
    ::= { xcmSvcMonQueueExtV2EventPrefix 1 }
--
--          "This is the definition of the SNMPv1 trap sent whenever
--          above for 'special semantics'."
--
--
xcmSvcMonService        OBJECT IDENTIFIER ::= { xcmSvcMonMIB 5 }
xcmSvcMonServiceTable OBJECT-TYPE
    SYNTAX      SEQUENCE OF XcmSvcMonServiceEntry
    MAX-ACCESS  not-accessible
    STATUS      current
    DESCRIPTION
        "A table of the system and/or end-user services supported and
        (possibly) ready on this host system, and (possibly) associated
        with one or more 'physical', 'logical', or 'logicalAndPhysical'
        devices on this host system presenting job services and one or
        more external devices (for security, accounting, etc), attached
        to this host system."
    REFERENCE
        "See:   'xcmSecServiceTable' in XCMI Security MIB."
    ::= { xcmSvcMonService 2 }
xcmSvcMonServiceEntry OBJECT-TYPE
    SYNTAX      XcmSvcMonServiceEntry
    MAX-ACCESS  not-accessible
    STATUS      current
    DESCRIPTION
        "An entry for a system and/or end-user service supported and
        (possibly) ready on this host system, and (possibly) associated
        with one or more 'physical', 'logical', or 'logicalAndPhysical'
        devices on this host system presenting job services and one or
        more external devices (for security, accounting, etc), attached
        to this host system."
    REFERENCE
        "See:   'xcmSecServiceEntry' in XCMI Security MIB."
    INDEX       { xcmSvcMonServiceIndex }
    ::= { xcmSvcMonServiceTable 1 }
XcmSvcMonServiceEntry ::= SEQUENCE {
        xcmSvcMonServiceIndex           Ordinal32,
        xcmSvcMonServiceRowStatus       RowStatus,
        xcmSvcMonServiceName            XcmFixedLocaleDisplayString,
        xcmSvcMonServiceCurrentState    XcmHrDpaState,
        xcmSvcMonServicePreviousState   XcmHrDpaState,
        xcmSvcMonServiceConditions      XcmHrDpaConditions,
        xcmSvcMonServiceAvailability    XcmHrDpaAvailability,
        xcmSvcMonServicePhysicalDevice  Cardinal32,
        xcmSvcMonServiceLogicalDevice   Cardinal32,
        xcmSvcMonServiceExternalDevice  Cardinal32,
        xcmSvcMonServiceSWRun           Cardinal32,
        xcmSvcMonServiceSWInstalled     Cardinal32,
        xcmSvcMonServiceStorage         Cardinal32,
        xcmSvcMonServicePriority        INTEGER (0..100),
        xcmSvcMonServiceType            XcmSvcMonServiceType,
        xcmSvcMonServiceStateDetail     OCTET STRING (SIZE (0..64))
    }
xcmSvcMonServiceIndex OBJECT-TYPE
    SYNTAX      Ordinal32
    MAX-ACCESS  read-only
    STATUS      current
    DESCRIPTION
        "A unique value used by this host system to identify this
        conceptual row in the 'xcmSvcMonServiceTable'.
        Usage:  Conforming management stations and management agents
        SHALL ensure that 'xcmSvcMonServiceIndex' is equal to
        'xcmSecServiceIndex' for the same service (if the XCMI Security
        MIB is also implemented).
        Usage:  This object SHALL be permanent (ie, preserved
        across all hardware resets)."
    ::= { xcmSvcMonServiceEntry 1 }
xcmSvcMonServiceRowStatus OBJECT-TYPE
    SYNTAX      RowStatus
    MAX-ACCESS  read-create
    STATUS      current
    DESCRIPTION
        "This object is used to create and delete individual conceptual
        rows in the 'xcmSvcMonServiceTable' and (optionally) in the
        'xcmSvcMonServiceMgmtTable' (if implemented on this system).
        Usage:  Conforming management stations and management agents
        SHALL ensure that 'xcmSvcMonServiceIndex' is equal to
        'xcmSecServiceIndex' for the same service (if the XCMI Security
        MIB is also implemented).
        Usage:  Conforming implementations which support static rows
        SHALL support 'active' and 'notInService' writes to this
        'xcmSvcMonServiceRowStatus' row status object; and
        SHALL clear the 'svcMonServiceGroup' bit in
        'xcmSvcMonGeneralCreateSupport' in the 'xcmSvcMonGeneralTable'.
        Usage:  Conforming implementations which support dynamic rows
        SHALL support 'createAndGo' and 'destroy' writes to this
        'xcmSvcMonServiceRowStatus' row status object; and
        SHALL set the 'svcMonServiceGroup' bit in
        'xcmSvcMonGeneralCreateSupport' in the 'xcmSvcMonGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmSvcMonGeneralCreateSupport' in
                'xcmSvcMonGeneralTable'.
        See:    'RowStatus' in IETF SNMPv2 TC (RFC 1443/1903/2579).
        See:    'xcmHrDevMgmtCommandData' in XCMI HRX MIB and
                'xcmSecUserMgmtData' in XCMI Security MIB."
    ::= { xcmSvcMonServiceEntry 2 }
xcmSvcMonServiceName OBJECT-TYPE
    SYNTAX      XcmFixedLocaleDisplayString (SIZE (0..255))
    MAX-ACCESS  read-create
    STATUS      current
    DESCRIPTION
        "A human-readable name, used by system administrators
        and end-users to identify this service.
        Usage:  This name SHALL be either:
        a) the name normally used in a command shell for control of
        this service (eg, 'showstopper.sample.com/bin/scan2file'); or
        b) the local user-friendly service name (eg, 'ScanToFile').
        Usage:  Conforming implementations need NOT ensure that each
        'xcmSvcMonServiceEntry' has a non-empty (on the managed system)
        'xcmSvcMonServiceName' (ie, names support is optional), but
        a given 'xcmSvcMonServiceName' SHALL be found via the
        same value of 'xcmSecServiceIndex' on the same managed system
        (ie, service names SHALL be persistent)."
    REFERENCE
        "See:   Section 9.5.1 'Server-name'
                in DPA (ISO/IEC 10175-1 Final Text, March 1996).
        See:    'xcmHrDevInfoName' in XCMI Ext to Host Res MIB."
    DEFVAL      { ''H }                 
    ::= { xcmSvcMonServiceEntry 3 }
xcmSvcMonServiceCurrentState OBJECT-TYPE
    SYNTAX      XcmHrDpaState
    MAX-ACCESS  read-only
    STATUS      current
    DESCRIPTION
        "The current state of this system and/or end-user service.
        Usage:  The current DPA object generic state of a service."
    REFERENCE
        "See:   Section 9.5.4 'Server-state' and
                section 9.1.6.4 'State' (generic object state)
                in DPA (ISO/IEC 10175-1 Final Text, March 1996).
        See:    Section D.2.3 'Server State Transitions'
                in DPA Mgmt Service (ISO 10175-3 Draft, October 1996).
        See:    'hrDeviceStatus' in IETF Host Resources MIB (RFC 2790).
        See:    'xcmHrDevInfoXStatus' and 'xcmHrDevInfoConditions'
                in XCMI Ext to Host Resources MIB."
    DEFVAL      { unknown }             
    ::= { xcmSvcMonServiceEntry 4 }
xcmSvcMonServicePreviousState OBJECT-TYPE
    SYNTAX      XcmHrDpaState
    MAX-ACCESS  read-only
    STATUS      current
    DESCRIPTION
        "The previous state of this system and/or end-user service.
        Usage:  The previous DPA object generic state of a service."
    REFERENCE
        "See:   Section 9.5.4 'Server-state' and
                section 9.1.6.4 'State' (generic object state)
                in DPA (ISO/IEC 10175-1 Final Text, March 1996).
        See:    Section D.2.3 'Server State Transitions'
                in DPA Mgmt Service (ISO 10175-3 Draft, October 1996).
        See:    'hrDeviceStatus' in IETF Host Resources MIB (RFC 2790).
        See:    'xcmHrDevInfoXStatus' and 'xcmHrDevInfoConditions'
                in XCMI Ext to Host Resources MIB."
    DEFVAL      { unknown }             
    ::= { xcmSvcMonServiceEntry 5 }
xcmSvcMonServiceConditions OBJECT-TYPE
    SYNTAX      XcmHrDpaConditions
    MAX-ACCESS  read-only
    STATUS      current
    DESCRIPTION
        "The current conditions (ie, state reasons) of this system
        and/or end-user service."
    REFERENCE
        "See:   Section 9.5.4 'Server-state' and
                section 9.1.6.4 'State' (generic object state)
                in DPA (ISO/IEC 10175-1 Final Text, March 1996).
        See:    Section D.2.3 'Server State Transitions'
                in DPA Mgmt Service (ISO 10175-3 Draft, October 1996).
        See:    'hrDeviceStatus' in IETF Host Resources MIB (RFC 2790).
        See:    'xcmHrDevInfoXStatus' and 'xcmHrDevInfoConditions'
                in XCMI Ext to Host Resources MIB."
    DEFVAL      { 0 }                   
    ::= { xcmSvcMonServiceEntry 6 }
xcmSvcMonServiceAvailability OBJECT-TYPE
    SYNTAX      XcmHrDpaAvailability
    MAX-ACCESS  read-only
    STATUS      current
    DESCRIPTION
        "The availability of this system and/or end-user service."
    REFERENCE
        "See:   Section 9.1.6.6 '[Generic attribute] Availability' and
                Annex A 'id-val-availability-...'
                in DPA (ISO/IEC 10175-1 Final Text, March 1996)."
    DEFVAL      { unknown }             
    ::= { xcmSvcMonServiceEntry 7 }
xcmSvcMonServicePhysicalDevice OBJECT-TYPE
    SYNTAX      Cardinal32
    MAX-ACCESS  read-create
    STATUS      current
    DESCRIPTION
        "The value of 'hrDeviceIndex' corresponding to the first
        associated physical device row in the 'hrDeviceTable' in the
        Host Resources MIB (RFC 2790) and an (optional) associated row
        in 'xcmHrDevInfoTable' of the XCMI Ext to Host Resources MIB,
        or zero if none.
        Usage:  Conforming implementations SHALL ensure that
        physical devices underlying services are 'visible'."
    REFERENCE
        "See:   'hrDeviceIndex' in the Device group of
                IETF Host Resources MIB (RFC 2790).
        See:    'xcmHrDevInfoRealization' in the Device Info group of
                XCMI Ext to Host Resources MIB.
        See:    Section 9.4 (pages 181 to 184) of DPA (Document Printing
        Application) ISO/IEC 10175 (Final Text, March 1996) for a
        discussion of 'printer realizations' of 'physical', 'logical',
        and 'logical-and-physical' types (the latter peculiar to DPA)."
    DEFVAL      { 0 }                   
    ::= { xcmSvcMonServiceEntry 8 }
xcmSvcMonServiceLogicalDevice OBJECT-TYPE
    SYNTAX      Cardinal32
    MAX-ACCESS  read-create
    STATUS      current
    DESCRIPTION
        "The value of 'hrDeviceIndex' corresponding to the first
        associated logical device row in the 'hrDeviceTable' in the
        Host Resources MIB (RFC 2790) and an (optional) associated row
        in 'xcmHrDevInfoTable' of the XCMI Ext to Host Resources MIB,
        or zero if none.
        Usage:  Conforming implementations SHALL ensure that
        logical devices presenting services are 'visible'."
    REFERENCE
        "See:   'xcmSvcMonServicePhysicalDevice' above."
    DEFVAL      { 0 }                   
    ::= { xcmSvcMonServiceEntry 9 }
xcmSvcMonServiceExternalDevice OBJECT-TYPE
    SYNTAX      Cardinal32
    MAX-ACCESS  read-create
    STATUS      current
    DESCRIPTION
        "The value of 'hrDeviceIndex' corresponding to the first
        associated external device row in the 'hrDeviceTable' in the
        Host Resources MIB (RFC 2790) and an (optional) associated row
        in 'xcmHrDevInfoTable' of the XCMI Ext to Host Resources MIB,
        or zero if none.
        Usage:  Such an external device is termed a 'foreign attachment'
        and SHALL have 'xcmHrDevInfoRealization' of 'physical' in the
        Device Info group of the XCMI Ext to Host Resources MIB - such
        a device performs some security processing (any authentication,
        authorization, or accounting), job processing, job finishing, or
        other off-system activity, on behalf of this service."
    REFERENCE
        "See:   'hrDeviceIndex' in the Device group of
                IETF Host Resources MIB (RFC 2790)."
    DEFVAL      { 0 }                   
    ::= { xcmSvcMonServiceEntry 10 }
xcmSvcMonServiceSWRun OBJECT-TYPE
    SYNTAX      Cardinal32
    MAX-ACCESS  read-create
    STATUS      current
    DESCRIPTION
        "The value of 'hrSWRunIndex' corresponding to the first
        associated conceptual row in the 'hrSWRunTable' of the
        Host Resources MIB (RFC 2790) and an (optional) associated row
        in 'xcmHrSWRunTable' of the XCMI Ext to Host Resources MIB,
        or zero if none.
        Usage:  A 'chain' of one or more Software Running entries in
        the Host Resources MIB MAY be associated with this service.
        By convention, the FIRST of these entries SHALL represent
        the security functional unit of this service."
    REFERENCE
        "See:   'hrSWRunIndex' in the Software Running group of
                IETF Host Resources MIB (RFC 2790).
        See:    Software Running Extensions group of
                XCMI Ext to Host Resources MIB."
    DEFVAL      { 0 }                   
    ::= { xcmSvcMonServiceEntry 11 }
xcmSvcMonServiceSWInstalled OBJECT-TYPE
    SYNTAX      Cardinal32
    MAX-ACCESS  read-create
    STATUS      current
    DESCRIPTION
        "The value of 'hrSWInstalledIndex' corresponding to the first
        associated conceptual row in the 'hrSWInstalledTable' of the
        Host Resources MIB (RFC 2790) and an (optional) associated row
        in 'xcmHrSWInstalledTable' in XCMI Ext to Host Resources MIB,
        or zero if none.
        Usage:  A 'chain' of one or more Software Installed entries in
        the Host Resources MIB MAY be associated with a service.
        By convention, the FIRST of these entries SHALL represent
        the security functional unit of a service."
    REFERENCE
        "See:   'hrSWInstalledIndex' in the Software Installed group of
                IETF Host Resources MIB (RFC 2790).
        See:    Software Installed Extensions group of
                XCMI Ext to Host Resources MIB."
    DEFVAL      { 0 }                   
    ::= { xcmSvcMonServiceEntry 12 }
xcmSvcMonServiceStorage OBJECT-TYPE
    SYNTAX      Cardinal32
    MAX-ACCESS  read-create
    STATUS      current
    DESCRIPTION
        "The value of 'hrStorageIndex' corresponding to the first
        associated conceptual row in the 'hrStorageTable' of the
        Host Resources MIB (RFC 2790) and an (optional) associated row
        in 'xcmHrStorageTable' of the XCMI Ext to Host Resources MIB,
        or zero if none.
        Usage:  A 'chain' of one or more Storage entries in
        the Host Resources MIB MAY be associated with a service."
    REFERENCE
        "See:   'hrStorageIndex' in the Storage group of
                IETF Host Resources MIB (RFC 2790).
        See:    Storage Extensions group of
                XCMI Ext to Host Resources MIB."
    DEFVAL      { 0 }                   
    ::= { xcmSvcMonServiceEntry 13 }
xcmSvcMonServicePriority OBJECT-TYPE
    SYNTAX      INTEGER (0..100)
    MAX-ACCESS  read-create
    STATUS      current
    DESCRIPTION
        "The current priority of this system and/or end-user service.
        Usage:  The scheduling priority of this service, where '0'
        is unspecified (default), '1' is lowest, and '100' is highest."
    REFERENCE
        "See:   'xcmHrDevInfoPriority' in
                XCMI Ext to Host Resources MIB."
    DEFVAL      { 0 }                   
    ::= { xcmSvcMonServiceEntry 14 }
xcmSvcMonServiceType OBJECT-TYPE
    SYNTAX      XcmSvcMonServiceType
    MAX-ACCESS  read-create
    STATUS      current
    DESCRIPTION
        "The explicit type of this system and/or end-user service."
    DEFVAL      { unknown }             
    ::= { xcmSvcMonServiceEntry 15 }
xcmSvcMonServiceStateDetail OBJECT-TYPE
    SYNTAX      OCTET STRING (SIZE (0..64))   
    MAX-ACCESS  read-only
    STATUS      current
    DESCRIPTION
        "This object represents additional status details to further
         describe the current state of the service.
        Usage:  This bit-array is constructed from the set of
        supported values from 'XcmSvcMonServiceStateDetail', used as 
        powers of 2 with big-endian rules - the high-order bit of the
        first octet corresponds to a service state detail '0' (reserved)
        - the low-order bit of the first octet corresponds to a
        service state detail of '7'.
        Similar to the BITS pseudotype defined in IETF SMIv2
        (RFC 2578), which has the same bit ordering rules but
        requires definitions for contiguous enumerated bits."
        REFERENCE
                "See:   'XcmSvcMonServiceStateDetail' in XCMI Service
                          Monitor MIB TC;
                        Section 7.1.4 'The BITS construct' in the IETF 
                          Coexistence between Version 1, Version 2, and 
                          Version 3 of the Internet-standard Network
                          Management Framework SMIv2 (RFC 2578)"
     DEFVAL      { ''H }                 
        ::= { xcmSvcMonServiceEntry 16 }
xcmSvcMonServiceV1EventOID OBJECT-IDENTITY
    STATUS      current
    DESCRIPTION
        "The value of the enterprise-specific OID in an SNMPv1 trap sent
        whenever a service status changes.
        See SNMPv2 trap definition 'xcmSvcMonServiceV2Event'
        below for 'special semantics'."
    ::= { xcmSvcMonService 1 }
xcmSvcMonServiceV2EventPrefix
    OBJECT IDENTIFIER ::= { xcmSvcMonServiceV1EventOID 0 }
xcmSvcMonServiceV2Event NOTIFICATION-TYPE
    OBJECTS {
        xcmSvcMonServiceIndex,
        xcmSvcMonServiceCurrentState,
        xcmSvcMonServicePreviousState,
        xcmSvcMonServiceConditions
    }
    STATUS      current
    DESCRIPTION
        "This trap is sent whenever
        'XcmSvcMonService[CurrentState|Conditions]' changes.
        Note:   The variable-bindings of this trap have been chosen to
        specify a complete service status change while keeping
        trap messages reasonably concise (generally a few hundred octets
        at most).
        This notification has the following special semantics:
            o   The service's 'xcmSvcMonServiceIndex' field
                value SHALL be appended to this trap object ID,
                as a BER binary OID suffix.
        This trap OID qualifier allows service management/monitoring
        applications to limit the alerts they receive to ones generated 
        by services of interest."
    ::= { xcmSvcMonServiceV2EventPrefix 1 }
--
--          "This trap is sent whenever
--          above for 'special semantics'."
--
--
xcmSvcMonServiceDetail  OBJECT IDENTIFIER ::= { xcmSvcMonMIB 6 }
xcmSvcMonServiceDetailTable OBJECT-TYPE
    SYNTAX      SEQUENCE OF XcmSvcMonServiceDetailEntry
    MAX-ACCESS  not-accessible
    STATUS      current
    DESCRIPTION
        "A 'sparse' table containing service detail information for
        installed and (possibly) active services on this host system,
        augmenting the basic entries in the 'xcmSvcMonServiceTable'
        of the XCMI Service Monitoring MIB.
        Usage:  UNLIKE the 'xcmGenOptionTable' in the XCMI General MIB
        (which is a unique exception), this table of 'dictionary-based'
        service details is used with DIRECT create/update operations."
    ::= { xcmSvcMonServiceDetail 2 }
xcmSvcMonServiceDetailEntry OBJECT-TYPE
    SYNTAX      XcmSvcMonServiceDetailEntry
    MAX-ACCESS  not-accessible
    STATUS      current
    DESCRIPTION
        "A 'sparse' entry containing service detail information for
        an installed and (possibly) active service on this host system,
        augmenting a basic entry in the 'xcmSvcMonServiceTable'
        of the XCMI Service Monitoring MIB."
    INDEX       { xcmSvcMonServiceIndex,
                  xcmSvcMonServiceDetailClass,
                  xcmSvcMonServiceDetailType,
                  xcmSvcMonServiceDetailIndex }
    ::= { xcmSvcMonServiceDetailTable 1 }
XcmSvcMonServiceDetailEntry ::= SEQUENCE {
        xcmSvcMonServiceDetailClass     XcmSvcMonServiceDetailClass,
        xcmSvcMonServiceDetailType      XcmSvcMonServiceDetailType,
        xcmSvcMonServiceDetailIndex     Ordinal32,
        xcmSvcMonServiceDetailRowStatus RowStatus,
        xcmSvcMonServiceDetailUnitClass XcmHrDevDetailUnitClass,
        xcmSvcMonServiceDetailUnit      Cardinal32,
        xcmSvcMonServiceDetailInteger   Integer32,
        xcmSvcMonServiceDetailOID       OBJECT IDENTIFIER,
        xcmSvcMonServiceDetailString    OCTET STRING
    }
xcmSvcMonServiceDetailClass OBJECT-TYPE
    SYNTAX      XcmSvcMonServiceDetailClass
    MAX-ACCESS  not-accessible
    STATUS      current
    DESCRIPTION
        "A service detail class,
        used by system administrators and end users to specify
        the correct class for this service detail."
    ::= { xcmSvcMonServiceDetailEntry 1 }
xcmSvcMonServiceDetailType OBJECT-TYPE
    SYNTAX      XcmSvcMonServiceDetailType
    MAX-ACCESS  not-accessible
    STATUS      current
    DESCRIPTION
        "A service detail type,
        used by system administrators and end users to specify
        the correct type for this service detail."
    ::= { xcmSvcMonServiceDetailEntry 2 }
xcmSvcMonServiceDetailIndex OBJECT-TYPE
    SYNTAX      Ordinal32
    MAX-ACCESS  not-accessible
    STATUS      current
    DESCRIPTION
        "A unique value used by this host system to identify this
        conceptual row in the 'xcmSvcMonServiceDetailTable', OR a common
        value shared across a set of related conceptual rows (with
        different values of 'xcmSvcMonServiceDetailType'.
        Usage:  For service detail types which are single-valued, this
        index SHALL be used to correlate related single-valued details.
        Usage:  For service detail types which are multi-valued, this
        index SHALL be used to enumerate lists of multi-valued details."
    ::= { xcmSvcMonServiceDetailEntry 3 }
xcmSvcMonServiceDetailRowStatus OBJECT-TYPE
    SYNTAX      RowStatus
    MAX-ACCESS  read-create
    STATUS      current
    DESCRIPTION
        "This object is used to create and delete individual conceptual
        rows in the 'xcmSvcMonServiceDetailTable'.
        Usage:  Conforming implementations which support static rows
        SHALL support 'active' and 'notInService' writes to this
        'xcmSvcMonServiceDetailRowStatus' row status object; and
        SHALL clear the 'svcMonServiceDetailGroup' bit in
        'xcmSvcMonGeneralCreateSupport' in the 'xcmSvcMonGeneralTable'.
        Usage:  Conforming implementations which support dynamic rows
        SHALL support 'createAndGo' and 'destroy' writes to this
        'xcmSvcMonServiceDetailRowStatus' row status object; and
        SHALL set the 'svcMonServiceDetailGroup' bit in
        'xcmSvcMonGeneralCreateSupport' in the 'xcmSvcMonGeneralTable'.
        Usage:  Conforming implementations need NOT support dynamic row
        creation (via 'createAndGo(4)') nor dynamic row deletion (via
        'destroy(6)').
        Usage:  See section 3.4 'Secure Modes of Operation' and section
        3.5 'Secure SNMP Get/Set Requests' in XCMI Security TC, for
        details of secure modes of access to this row status object."
    REFERENCE
        "See:   'xcmSvcMonGeneralCreateSupport' in
                'xcmSvcMonGeneralTable'.
        See:    'RowStatus' in IETF SNMPv2 TC (RFC 1443/1903/2579).
        See:    'xcmHrDevMgmtCommandData' in XCMI HRX MIB and
                'xcmSecUserMgmtData' in XCMI Security MIB."
    ::= { xcmSvcMonServiceDetailEntry 4 }
xcmSvcMonServiceDetailUnitClass OBJECT-TYPE
    SYNTAX      XcmHrDevDetailUnitClass
    MAX-ACCESS  read-create
    STATUS      current
    DESCRIPTION
        "The value unit class of the detail information specified
        in this conceptual row in the 'xcmSvcMonServiceDetailTable'.
        Usage:  Used to select a textual convention for specifying the
        value unit of this service detail.
        Usage:  The 'xcmSvcMonServiceDetail[UnitClass|Class]' objects
        are used to specify the value syntax AND the value unit of the
        'xcmSvcMonServiceDetail[Integer|OID|String]' value objects."
    REFERENCE
        "See:   'xcmSvcMonServiceDetailUnit'"
    DEFVAL      { unknown }             
    ::= { xcmSvcMonServiceDetailEntry 5 }
xcmSvcMonServiceDetailUnit OBJECT-TYPE
    SYNTAX      Cardinal32
    MAX-ACCESS  read-create
    STATUS      current
    DESCRIPTION
        "The value unit of the detail information specified
        in this conceptual row in the 'xcmSvcMonServiceDetailTable'.
        Usage:  Used to select an enumerated choice from a textual
        convention to specify the value unit of this service detail.
        Usage:  The 'xcmSvcMonServiceDetail[UnitClass|Class]' objects
        are used to specify the value syntax AND the value unit of the
        'xcmSvcMonServiceDetail[Integer|OID|String]' value objects."
    REFERENCE
        "See:   'xcmSvcMonServiceDetailUnitClass'"
    DEFVAL      { 0 }                   
    ::= { xcmSvcMonServiceDetailEntry 6 }
xcmSvcMonServiceDetailInteger OBJECT-TYPE
    SYNTAX      Integer32
    MAX-ACCESS  read-create
    STATUS      current
    DESCRIPTION
        "A service detail value integer,
        used by system administrators and end users to specify
        the current value for a service detail
        with a base value syntax of 'INTEGER'."
    REFERENCE
        "See:   'xcmSvcMonServiceDetailOID' and
                'xcmSvcMonServiceDetailString'
        See:    'xcmSvcMonServiceDetailUnitClass' and
                'xcmSvcMonServiceDetailUnit' for syntax of detail value"
    DEFVAL      { 0 }                   
    ::= { xcmSvcMonServiceDetailEntry 7 }
xcmSvcMonServiceDetailOID OBJECT-TYPE
    SYNTAX      OBJECT IDENTIFIER
    MAX-ACCESS  read-create
    STATUS      current
    DESCRIPTION
        "A service detail value OID (object identifier),
        used by system administrators and end users to specify
        the current value for a service detail
        with a base value syntax of 'OBJECT IDENTIFIER'."
    REFERENCE
        "See:   'xcmSvcMonServiceDetailInteger' and
                'xcmSvcMonServiceDetailString'
        See:    'xcmSvcMonServiceDetailUnitClass' and
                'xcmSvcMonServiceDetailUnit' for syntax of detail value"
    DEFVAL      { zeroDotZero }   
    ::= { xcmSvcMonServiceDetailEntry 8 }
xcmSvcMonServiceDetailString OBJECT-TYPE
    SYNTAX      OCTET STRING (SIZE (0..255))
    MAX-ACCESS  read-create
    STATUS      current
    DESCRIPTION
        "A service detail value string,
        used by system administrators and end users to specify
        the current value for a service detail
        with a base value syntax of 'OCTET STRING'.
        Usage:  This object is of type 'XcmFixedLocaleDisplayString'.
        Usage:  Conformant implementations MUST encrypt passwords, keys,
        and other security information stored in this string object."
    REFERENCE
        "See:   'xcmSvcMonServiceDetailInteger' and
                'xcmSvcMonServiceDetailOID'
        See:    'xcmSvcMonServiceDetailUnitClass' and
                'xcmSvcMonServiceDetailUnit' for syntax of detail value"
    DEFVAL      { ''H }                 
    ::= { xcmSvcMonServiceDetailEntry 9 }
--
xcmSvcMonServiceMgmt    OBJECT IDENTIFIER ::= { xcmSvcMonMIB 7 }
xcmSvcMonServiceMgmtTable OBJECT-TYPE
    SYNTAX      SEQUENCE OF XcmSvcMonServiceMgmtEntry
    MAX-ACCESS  not-accessible
    STATUS      current
    DESCRIPTION
        "A table containing service management requests for control
        of system and/or end-user services on this host system."
    ::= { xcmSvcMonServiceMgmt 2 }
xcmSvcMonServiceMgmtEntry OBJECT-TYPE
    SYNTAX      XcmSvcMonServiceMgmtEntry
    MAX-ACCESS  not-accessible
    STATUS      current
    DESCRIPTION
        "An entry containing a service management request for control
        of a system and/or end-user service on this host system."
    AUGMENTS    { xcmSvcMonServiceEntry }
    ::= { xcmSvcMonServiceMgmtTable 1 }
XcmSvcMonServiceMgmtEntry ::= SEQUENCE {
   xcmSvcMonServiceMgmtOperation        XcmSvcMonServiceMgmtOperation,
   xcmSvcMonServiceMgmtData             XcmSvcMonServiceMgmtData,
   xcmSvcMonServiceMgmtStatus           XcmGenSNMPv2ErrorStatus,
   xcmSvcMonServiceMgmtInProgress       TruthValue,
   xcmSvcMonServiceMgmtRowStatus        RowStatus,
   xcmSvcMonServiceMgmtUserPassword     OCTET STRING,
   xcmSvcMonServiceMgmtOperatorPassword OCTET STRING,
   xcmSvcMonServiceMgmtAdminPassword    OCTET STRING
    }
xcmSvcMonServiceMgmtOperation OBJECT-TYPE
    SYNTAX      XcmSvcMonServiceMgmtOperation
    MAX-ACCESS  read-create
    STATUS      current
    DESCRIPTION
        "The most recent service management operation specified for
        this conceptual row in the 'xcmSvcMonServiceMgmtTable'.
        Usage:  Conforming management agents SHALL 'reject' any
        SNMP Set-Request to 'xcmSvcMonServiceMgmt[Operation|Data]'
        while another management operation is already in progress
        (ie, while 'xcmSvcMonServiceMgmtInProgress' is 'true'),
        with 'badValue' (SNMPv1) or 'inconsistentValue' (SNMPv2/v3).
        Usage:  Conforming management stations SHALL set
        'xcmSvcMonServiceMgmtOperation' (mgmt operation) and
        'xcmSvcMonServiceMgmtData' (mgmt arguments)
        SIMULTANEOUSLY (in the same SNMP Set-Request PDU)."
    REFERENCE
        "See:   Section 4 'Print Utilities' (pages 71 to 212) of
                POSIX Sys Admin (IEEE 1387.4 / Draft 8, October 1994).
        See:    OBJECT clause in MODULE-COMPLIANCE macro of
                XCMI Service Monitoring MIB, for compliance info."
    ::= { xcmSvcMonServiceMgmtEntry 1 }
xcmSvcMonServiceMgmtData OBJECT-TYPE
    SYNTAX      XcmSvcMonServiceMgmtData (SIZE (0..255))
    MAX-ACCESS  read-create
    STATUS      current
    DESCRIPTION
        "The most recent service management data specified for
        this conceptual row in the 'xcmSvcMonServiceMgmtTable'.
        Usage:  Conforming management agents SHALL 'reject' any
        SNMP Set-Request to 'xcmSvcMonServiceMgmt[Operation|Data]'
        while another management operation is already in progress
        (ie, while 'xcmSvcMonServiceMgmtInProgress' is 'true')
        with 'badValue' (SNMPv1) or 'inconsistentValue' (SNMPv2/v3).
        Usage:  Conforming management stations SHALL set
        'xcmSvcMonServiceMgmtOperation' (mgmt operation) and
        'xcmSvcMonServiceMgmtData' (mgmt arguments)
        SIMULTANEOUSLY (in the same SNMP Set-Request PDU).
        Usage:  Conformant implementations MUST encrypt passwords, 
        keys, and other security information stored in this string 
        object.
        Usage:  Management strings will be formatted as specified
        in the 'XcmHrDevMgmtCommandDataTag' textual convention. This
        means that the 'TT=value:' string format will be used with all
        management strings.
        Usage:  Strings that have been specified by XCMI are provided
        in the 'XcmSvcMonServiceMgmtData'."
    REFERENCE
        "See:   Section 4 'Print Utilities' (pages 71 to 212) of
                POSIX Sys Admin (IEEE 1387.4 / Draft 8, October 1994).
        See:    OBJECT clause in MODULE-COMPLIANCE macro of
                XCMI Service Monitoring MIB, for compliance info.
        See:    'XcmHrDevMgmtCommandDataTag' textual convention,
                Section 3.4 'XCMI Standard Tagged Management Data', and
                Section 3.5 'Simple Device Management Requests' in
                XCMI Ext to Host Resources TC.
        See:    Section 3.5.3 'Secure Simple Device Mgmt Requests' in
                XCMI Security TC."
    DEFVAL      { ''H }                 
    ::= { xcmSvcMonServiceMgmtEntry 2 }
xcmSvcMonServiceMgmtStatus OBJECT-TYPE
    SYNTAX      XcmGenSNMPv2ErrorStatus
    MAX-ACCESS  read-only
    STATUS      current
    DESCRIPTION
        "The service management error status associated with
        this conceptual row in 'xcmSvcMonServiceMgmtTable'.
        Usage:  Conforming management agents SHALL set this
        object to the value returned in an SNMP Set-Response PDU when
        a service management operation is 'accepted', ie, when
        'xcmSvcMonServiceMgmtInProgress' goes from 'false' to 'true'.
        Usage:  Conforming management agents SHALL set this
        object to the value of the completion status of the (possibly
        deferred) service management operation, when
        'xcmSvcMonServiceMgmtInProgress' goes from 'true' to 'false'."
    REFERENCE
        "See:   'xcmSvcMonServiceMgmt[Operation|Data|InProgress]'"
    ::= { xcmSvcMonServiceMgmtEntry 3 }
xcmSvcMonServiceMgmtInProgress OBJECT-TYPE
    SYNTAX      TruthValue
    MAX-ACCESS  read-only
    STATUS      current
    DESCRIPTION
        "The service management in progress status associated with
        this conceptual row in 'xcmSvcMonServiceMgmtTable'.
        Usage:  Conforming management agents SHALL 'reject' any
        SNMP Set-Request to 'xcmSvcMonServiceMgmt[Operation|Data]'
        while another management operation is already in progress
        (ie, while 'xcmSvcMonServiceMgmtInProgress' is 'true'),
        with 'badValue' (SNMPv1) or 'inconsistentValue' (SNMPv2/v3)."
    REFERENCE
        "See:   'xcmSvcMonServiceMgmt[Operation|Data|Status]'"
    DEFVAL      { false }               
    ::= { xcmSvcMonServiceMgmtEntry 4 }
  xcmSvcMonServiceMgmtRowStatus OBJECT-TYPE
      SYNTAX      RowStatus
      MAX-ACCESS  read-create
      STATUS      current
      DESCRIPTION
          "This object manages the row status of this conceptual row in
          the 'xcmSvcMonServiceMgmtTable'.
          Usage:  Conforming implementations which support static rows
          SHALL support 'active' and 'notInService' writes to this
          'xcmSvcMonServiceMgmtRowStatus' row status object; and
          SHALL clear the 'xcmSvcMonServiceMgmtGroup' bit in
          'xcmSvcMonGeneralCreateSupport' in the 
          'xcmSvcMonServiceGeneralTable'.
          Usage:  Conforming implementations which support dynamic rows
          SHALL support 'createAndGo' and 'destroy' writes to this
          'xcmSvcMonServiceMgmtRowStatus' row status object; and
          SHALL set the 'xcmSvcMonServiceMgmtGroup' bit in
          'xcmSvcMonGeneralCreateSupport' in the 
          'xcmSvcMonServiceGeneralTable'.
          Usage:  Conforming implementations need NOT support dynamic 
          row creation (via 'createAndGo(4)') nor dynamic row deletion 
          (via 'destroy(6)').
          Usage:  See section 3.4 'Secure Modes of Operation' and 
          section 3.5 'Secure SNMP Get/Set Requests' in XCMI Security 
          TC, for details of secure modes of access to this row status 
          object."
      REFERENCE
          "See: xcmSvcMonGeneralCreateSupport in the 
                xcmSvcMonServiceGeneralTable.
           See: RowStatus in IETF SNMPv2 TC (RFC 1443/1903/2579).
           See: xcmSvcMonServiceMgmtData in XCMI Service 
                Monitoring MIB."
      ::= { xcmSvcMonServiceMgmtEntry 5 }
xcmSvcMonServiceMgmtUserPassword OBJECT-TYPE
    SYNTAX      OCTET STRING (SIZE (0..255))
    MAX-ACCESS  read-create
    STATUS      current
    DESCRIPTION
        "A protected end user password for this device.
        Usage:  Conformant implementations MUST encrypt passwords, keys,
        and other security information stored in this string object.
        Usage:  When changing the [User|Operator|Admin] Password,
        conformant implementations MUST encrypt the NEW password that is
        submitted in 'xcmSvcMonServiceMgmtData'.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'end user password' that is used in this 
        object."
    REFERENCE
        "See:   'xcmSvcMonServiceMgmt[Operator|Admin]Password'
         See:    Section 3.5.2 'Secure Password Change Requests' in
                XCMI Security TC.
         See:    'xcmSysAdminRequestTable' in XCMI System Admin MIB and
                'xcmSecUserTable' in XCMI Security MIB."
    DEFVAL      { ''H }                 
    ::= { xcmSvcMonServiceMgmtEntry 6 }
xcmSvcMonServiceMgmtOperatorPassword OBJECT-TYPE
    SYNTAX      OCTET STRING (SIZE (0..255))
    MAX-ACCESS  read-create
    STATUS      current
    DESCRIPTION
        "A protected system operator password for this device.
        Usage:  Conformant implementations MUST encrypt passwords, keys,
        and other security information stored in this string object.
        Usage:  When changing the [User|Operator|Admin] Password,
        conformant implementations MUST encrypt the NEW password that is
        submitted in 'xcmSvcMonServiceMgmtData'.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'operator password' that is used in this 
        object."
    REFERENCE
        "See:   'xcmSvcMonServiceMgmt[User|Admin]Password'
         See:    Section 3.5.2 'Secure Password Change Requests' in
                XCMI Security TC.
         See:    'xcmSysAdminRequestTable' in XCMI System Admin MIB and
                'xcmSecUserTable' in XCMI Security MIB."
    DEFVAL      { ''H }                 
    ::= { xcmSvcMonServiceMgmtEntry 7 }
xcmSvcMonServiceMgmtAdminPassword OBJECT-TYPE
    SYNTAX      OCTET STRING (SIZE (0..255))
    MAX-ACCESS  read-create
    STATUS      current
    DESCRIPTION
        "A protected system administrator password for this device.
        Usage:  Conformant implementations MUST encrypt passwords, keys,
        and other security information stored in this string object.
        Usage:  When changing the [User|Operator|Admin] Password,
        conformant implementations MUST encrypt the NEW password that is
        submitted in 'xcmSvcMonServiceMgmtData'.
        Usage:  All XCMI conforming management agents: a) SHOULD always
        return a zero length string in response to an SNMP GetRequest of
        this object; b) SHALL NOT return the contents of this object in
        cleartext (ie, unencrypted) in response to an SNMP GetRequest;
        c) SHOULD support (ie, accept) an authenticated SNMP SetRequest
        changing the system 'administrator password' that is used in 
        this object."
    REFERENCE
        "See:   'xcmSvcMonServiceMgmt[User|Operator]Password'
         See:    Section 3.5.2 'Secure Password Change Requests' in
                XCMI Security TC.
         See:    'xcmSysAdminRequestTable' in XCMI System Admin MIB and
                'xcmSecUserTable' in XCMI Security MIB."
    DEFVAL      { ''H }                 
    ::= { xcmSvcMonServiceMgmtEntry 8 }
xcmSvcMonServiceMgmtV1EventOID OBJECT-IDENTITY
    STATUS      current
    DESCRIPTION
        "The value of the enterprise-specific OID in an SNMPv1 trap sent
        whenever an 'xcmSvcMonServiceMgmtOperation' completes.
        See SNMPv2 trap definition 'xcmSvcMonServiceMgmtV2Event'
        below for 'special semantics'."
    ::= { xcmSvcMonServiceMgmt 1 }
xcmSvcMonServiceMgmtV2EventPrefix
    OBJECT IDENTIFIER ::= { xcmSvcMonServiceMgmtV1EventOID 0 }
xcmSvcMonServiceMgmtV2Event NOTIFICATION-TYPE
    OBJECTS {
        xcmSvcMonServiceIndex,
        xcmSvcMonServiceMgmtOperation,
        xcmSvcMonServiceMgmtStatus
    }
    STATUS      current
    DESCRIPTION
        "This trap is sent whenever an 'XcmSvcMonServiceMgmtOperation'
        completes, ie, when 'xcmSvcMonServiceMgmtStatus' becomes the
        completed operation status and 'XcmSvcMonServiceMgmtInProgress'
        goes from 'true' to 'false'.
        Note:   The variable-bindings of this trap have been chosen to
        specify a complete management operation result while keeping
        trap messages reasonably concise (generally a few hundred octets
        at most).
        This notification has the following special semantics:
            o   The service's 'xcmSvcMonServiceIndex' field
                value SHALL be appended to this trap object ID,
                as a BER binary OID suffix.
        This trap OID qualifier allows service management/monitoring
        applications to limit the alerts they receive to ones generated 
        by requests they have submitted."
    ::= { xcmSvcMonServiceMgmtV2EventPrefix 1 }
--
--          "This trap is sent when an 'XcmSvcMonServiceMgmtOperation'
--          above for 'special semantics'."
--
--
xcmSvcMonMIBConformance
    OBJECT IDENTIFIER ::= { xcmSvcMonMIB 2 }
xcmSvcMonMIBGroups
    OBJECT IDENTIFIER ::= { xcmSvcMonMIBConformance 2 }
--
--
xcmSvcMonMIBCompliance MODULE-COMPLIANCE
    STATUS      current
    DESCRIPTION
        "The compliance statements for SNMP management agents that
        implement the Service Monitoring MIB."
    MODULE 
    MANDATORY-GROUPS {
        xcmSvcMonGeneralGroup
    }
    GROUP       xcmSvcMonQueueGroup
    DESCRIPTION
        "Implementation of this group is conditionally mandatory, ie,
        mandatory for systems which support external (network) job
        queues (print/fax/etc), on external print/file servers
        (remotely) and/or on the managed system itself (locally),
        and optional for all other systems.
        Note:   'read-only' implementation of this group is allowed,
        but it prevents the use of this group as a 'shared' resource
        between cooperating (remote) management stations and (local)
        management agents."
    GROUP       xcmSvcMonQueueExtGroup
    DESCRIPTION
        "Implementation of this group is conditionally mandatory, ie,
        mandatory for systems with routing (forwarding), state,
        conditions, or fault info for external (network) job
        queues (print/fax/etc), on external print/file servers
        (remotely) and/or on the managed system itself (locally),
        and optional for all other systems.
        Note:   'read-only' implementation of this group is allowed,
        but it prevents the use of this group as a 'shared' resource
        between cooperating (remote) management stations and (local)
        management agents."
    GROUP       xcmSvcMonServiceGroup
    DESCRIPTION
        "Implementation of this group is conditionally mandatory, ie,
        mandatory for systems which support service monitoring
        and optional for all other systems."
    GROUP       xcmSvcMonServiceDetailGroup
    DESCRIPTION
        "Implementation of this group is conditionally mandatory, ie,
        mandatory for systems which support service details
        and optional for all other systems.
        Note:   Systems implementing 'xcmSvcMonServiceDetailGroup'
                SHALL implement the 'xcmSvcMonServiceGroup'."
    GROUP       xcmSvcMonServiceMgmtGroup
    DESCRIPTION
        "Implementation of this group is conditionally mandatory, ie,
        mandatory for systems which support service management
        and optional for all other systems."
    OBJECT      xcmSvcMonQueueRowStatus
    SYNTAX      INTEGER { active(1) }   
    MIN-ACCESS  read-only
    DESCRIPTION
        "It is conformant to implement this object as read-only, and
        only one of the enumerated values for the 'RowStatus' textual
        convention need be supported, specifically:  active(1)."
    OBJECT      xcmSvcMonQueueDomain
    MIN-ACCESS  read-only
    DESCRIPTION
        "It is conformant to implement this object as read-only."
    OBJECT      xcmSvcMonQueuePath
    SYNTAX      XcmFixedLocaleDisplayString (SIZE (0..32))
    MIN-ACCESS  read-only
    DESCRIPTION
        "It is conformant to implement this object as read-only, and
        only 32 octets maximum string length need be supported."
    OBJECT      xcmSvcMonQueueName
    SYNTAX      XcmFixedLocaleDisplayString (SIZE (0..32))
    MIN-ACCESS  read-only
    DESCRIPTION
        "It is conformant to implement this object as read-only, and
        only 32 octets maximum string length need be supported."
    OBJECT      xcmSvcMonQueueOnSystem
    MIN-ACCESS  read-only
    DESCRIPTION
        "It is conformant to implement this object as read-only."
    OBJECT      xcmSvcMonQueueRoutingIndex
    MIN-ACCESS  read-only
    DESCRIPTION
        "It is conformant to implement this object as read-only."
    OBJECT      xcmSvcMonQueueFaultString
    SYNTAX      XcmFixedLocaleDisplayString (SIZE (0..1))
    DESCRIPTION
        "It is conformant to implement this object as read-only, and
        only 1 octet maximum string length need be supported."
    OBJECT      xcmSvcMonServiceRowStatus
    SYNTAX      INTEGER { active(1) }   
    MIN-ACCESS  read-only
    DESCRIPTION
        "It is conformant to implement this object as read-only, and
        only one of the enumerated values for the 'RowStatus' textual
        convention need be supported, specifically:  active(1)."
    OBJECT      xcmSvcMonServiceName
    SYNTAX      XcmFixedLocaleDisplayString (SIZE (0..32))
    MIN-ACCESS  read-only
    DESCRIPTION
        "It is conformant to implement this object as read-only, and
        only 32 octets maximum string length need be supported."
    OBJECT      xcmSvcMonServicePhysicalDevice
    MIN-ACCESS  read-only
    DESCRIPTION
        "It is conformant to implement this object as read-only."
    OBJECT      xcmSvcMonServiceLogicalDevice
    MIN-ACCESS  read-only
    DESCRIPTION
        "It is conformant to implement this object as read-only."
    OBJECT      xcmSvcMonServiceExternalDevice
    MIN-ACCESS  read-only
    DESCRIPTION
        "It is conformant to implement this object as read-only."
    OBJECT      xcmSvcMonServiceSWRun
    MIN-ACCESS  read-only
    DESCRIPTION
        "It is conformant to implement this object as read-only."
    OBJECT      xcmSvcMonServiceSWInstalled
    MIN-ACCESS  read-only
    DESCRIPTION
        "It is conformant to implement this object as read-only."
    OBJECT      xcmSvcMonServiceStorage
    MIN-ACCESS  read-only
    DESCRIPTION
        "It is conformant to implement this object as read-only."
    OBJECT      xcmSvcMonServiceDetailRowStatus
    SYNTAX      INTEGER { active(1) }   
    MIN-ACCESS  read-only
    DESCRIPTION
        "It is conformant to implement this object as read-only, and
        only one of the enumerated values for the 'RowStatus' textual
        convention need be supported, specifically:  active(1)."
    OBJECT      xcmSvcMonServiceDetailUnitClass
    MIN-ACCESS  read-only
    DESCRIPTION
        "It is conformant to implement this object as read-only."
    OBJECT      xcmSvcMonServiceDetailUnit
    MIN-ACCESS  read-only
    DESCRIPTION
        "It is conformant to implement this object as read-only."
    OBJECT      xcmSvcMonServiceDetailInteger
    MIN-ACCESS  read-only
    DESCRIPTION
        "It is conformant to implement this object as read-only."
    OBJECT      xcmSvcMonServiceDetailOID
    MIN-ACCESS  read-only
    DESCRIPTION
        "It is conformant to implement this object as read-only."
    OBJECT      xcmSvcMonServiceDetailString
    SYNTAX      OCTET STRING (SIZE (0..1))
    MIN-ACCESS  read-only
    DESCRIPTION
        "It is conformant to implement this object as read-only, and
        only 1 octet maximum string length need be supported.
        Usage:  Conformant implementations MUST encrypt passwords, keys,
        and other security information stored in this string object."
    OBJECT      xcmSvcMonServiceMgmtOperation
    SYNTAX      INTEGER {
        none(0),                        
        other(1),                       
        unknown(2),                     
        serviceDisable(1206),           
        serviceEnable(1207),            
        servicePause(1208),             
        serviceResume(1209)             
    }
    DESCRIPTION
        "It is conformant to implement this object as follows:
        only the above subset of operations need be supported."
    OBJECT      xcmSvcMonServiceMgmtData
    SYNTAX      XcmSvcMonServiceMgmtData (SIZE (0..1))
    DESCRIPTION
        "It is conformant to implement this object as follows:
        only 1 octet maximum string length need be supported.
        Usage:  Conformant implementations MUST encrypt passwords, keys,
        and other security information stored in this string object."
    ::= { xcmSvcMonMIBConformance 3 }
--
--
xcmSvcMonGeneralGroup OBJECT-GROUP
    OBJECTS {
        xcmSvcMonGeneralRowStatus,
        xcmSvcMonGeneralVersionID,
        xcmSvcMonGeneralVersionDate,
        xcmSvcMonGeneralGroupSupport,
        xcmSvcMonGeneralCreateSupport,
        xcmSvcMonGeneralUpdateSupport
    }
    STATUS      current
    DESCRIPTION
        "The Service Monitoring General Group."
    ::= { xcmSvcMonMIBGroups 1 }
xcmSvcMonQueueGroup OBJECT-GROUP
    OBJECTS {
        xcmSvcMonQueueIndex,
        xcmSvcMonQueueRowStatus,
        xcmSvcMonQueueDomain,
        xcmSvcMonQueuePath,
        xcmSvcMonQueueName,
        xcmSvcMonQueueOnSystem
    }
    STATUS      current
    DESCRIPTION
        "The Service Monitoring Associated Queue Group."
    ::= { xcmSvcMonMIBGroups 3 }
xcmSvcMonQueueExtGroup OBJECT-GROUP
    OBJECTS {
        xcmSvcMonQueueRoutingIndex,
        xcmSvcMonQueueState,
        xcmSvcMonQueueConditions,
        xcmSvcMonQueueFaultCount,
        xcmSvcMonQueueFaultCode,
        xcmSvcMonQueueFaultString,
        xcmSvcMonQueueRowCreateDate,
        xcmSvcMonQueueRowTotalJobs,
        xcmSvcMonQueueLastConnectDate,
        xcmSvcMonQueueLastConnectJobs
    }
    STATUS      current
    DESCRIPTION
        "The Service Monitoring Associated Queue Ext Group."
    ::= { xcmSvcMonMIBGroups 4 }
xcmSvcMonServiceGroup OBJECT-GROUP
    OBJECTS {
        xcmSvcMonServiceIndex,
        xcmSvcMonServiceRowStatus,
        xcmSvcMonServiceName,
        xcmSvcMonServiceCurrentState,
        xcmSvcMonServicePreviousState,
        xcmSvcMonServiceConditions,
        xcmSvcMonServiceAvailability,
        xcmSvcMonServicePhysicalDevice,
        xcmSvcMonServiceLogicalDevice,
        xcmSvcMonServiceExternalDevice,
        xcmSvcMonServiceSWRun,
        xcmSvcMonServiceSWInstalled,
        xcmSvcMonServiceStorage,
        xcmSvcMonServicePriority,
        xcmSvcMonServiceType,
        xcmSvcMonServiceStateDetail    
    }
    STATUS      current
    DESCRIPTION
        "The Service Monitoring Service Group."
    ::= { xcmSvcMonMIBGroups 5 }
xcmSvcMonServiceDetailGroup OBJECT-GROUP
    OBJECTS {
        xcmSvcMonServiceDetailRowStatus,
        xcmSvcMonServiceDetailUnitClass,
        xcmSvcMonServiceDetailUnit,
        xcmSvcMonServiceDetailInteger,
        xcmSvcMonServiceDetailOID,
        xcmSvcMonServiceDetailString
    }
    STATUS      current
    DESCRIPTION
        "The Service Monitoring Service Detail Group."
    ::= { xcmSvcMonMIBGroups 6 }
xcmSvcMonServiceMgmtGroup OBJECT-GROUP
    OBJECTS {
        xcmSvcMonServiceMgmtOperation,
        xcmSvcMonServiceMgmtData,
        xcmSvcMonServiceMgmtStatus,
        xcmSvcMonServiceMgmtInProgress
    }
    STATUS      current
    DESCRIPTION
        "The Service Monitoring Service Mgmt Group."
    ::= { xcmSvcMonMIBGroups 7 }
xcmPidTC OBJECT-IDENTITY -- MODULE-IDENTITY
    STATUS   current
    DESCRIPTION "
        XCMI Product ID Module,
        Version 6.038.pub
        Copyright (C) 1997-2013 Xerox Corporation. All Rights Reserved."
    ::= { xeroxCommonMIB 62 }
xcmPidProductIdentifiers OBJECT-IDENTITY
    STATUS      current
    DESCRIPTION
        "The root of all identifiers defined in this module."
    ::= { xcmPidTC 1 }
----------------------------------------------------------------
----------------------------------------------------------------
xcmPidDocuCentreSystems OBJECT-IDENTITY
    STATUS      current
    DESCRIPTION
        "Document Centre Systems product line identifier
                 (not a complete product identifier)."
    ::= { xcmPidProductIdentifiers 1 }
xcmPidDCS20 OBJECT-IDENTITY
    STATUS      current
    DESCRIPTION
        "Document Centre/System 20 product type identifier
                 (not a complete product identifier)."
    ::= { xcmPidDocuCentreSystems 1 }
xcmPidDCS20M1 OBJECT-IDENTITY
    STATUS      current
    DESCRIPTION
        "Document Centre/System 20 launch configuration model
                 identifier (not a complete product identifier)."
    ::= { xcmPidDCS20 1 }
            -- => SAP PID string = "111"
xcmPidDCS20M1V1 OBJECT-IDENTITY
    STATUS      current
    DESCRIPTION
        "Document Centre/System 20 launch configuration version,
                 and complete product identifier."
    ::= { xcmPidDCS20M1 1 }
xcmPidDCS35 OBJECT-IDENTITY
    STATUS      current
    DESCRIPTION
        "Document Centre/System 35 product type identifier
                 (not a complete product identifier)."
    ::= { xcmPidDocuCentreSystems 2 }
xcmPidDCS35M1 OBJECT-IDENTITY
    STATUS      current
    DESCRIPTION
        "Document Centre/System 35 launch configuration model
                 identifier (not a complete product identifier)."
    ::= { xcmPidDCS35 1 }
            -- => SAP PID string = "121"
xcmPidDCS35M1V1 OBJECT-IDENTITY
    STATUS      current
    DESCRIPTION
        "Document Centre/System 35 launch configuration version,
                 and complete product identifier."
    ::= { xcmPidDCS35M1 1 }
--
--
xcmPidDC220 OBJECT-IDENTITY
    STATUS      current
    DESCRIPTION
        "Document Centre 220 product type identifier
                 (not a complete product identifier)."
    ::= { xcmPidDocuCentreSystems 8 }
xcmPidDC220ST OBJECT-IDENTITY
    STATUS      current
    DESCRIPTION
        "Document Centre 220ST multi-function system
                 model identifier (not a complete product identifier)."
    ::= { xcmPidDC220 1 }
            -- => SAP PID string = "181"
xcmPidDC220STV3 OBJECT-IDENTITY
    STATUS      current
    DESCRIPTION
        "Document Centre 220ST multi-function system
                 second post-launch configuration version, and
                 complete product identifier."
    ::= { xcmPidDC220ST 3 }
xcmPidDC220STV4 OBJECT-IDENTITY
    STATUS      current
    DESCRIPTION
        "Document Centre 220ST multi-function system
                 third post-launch configuration version, and
                 complete product identifier."
    ::= { xcmPidDC220ST 4 }
xcmPidDC230 OBJECT-IDENTITY
    STATUS      current
    DESCRIPTION
        "Document Centre 230 product type identifier
                 (not a complete product identifier)."
    ::= { xcmPidDocuCentreSystems 3 }
xcmPidDC230ST OBJECT-IDENTITY
    STATUS      current
    DESCRIPTION
        "Document Centre 230ST multi-function system
                 model identifier (not a complete product identifier)."
    ::= { xcmPidDC230 1 }
            -- => SAP PID string = "131"
xcmPidDC230STV1 OBJECT-IDENTITY
    STATUS      current
    DESCRIPTION
        "Document Centre 230ST multi-function system
                 launch configuration version, and
                 complete product identifier."
    ::= { xcmPidDC230ST 1 }
xcmPidDC230STV2 OBJECT-IDENTITY
    STATUS      current
    DESCRIPTION
        "Document Centre 230ST multi-function system
                 first post-launch configuration version, and
                 complete product identifier."
    ::= { xcmPidDC230ST 2 }
xcmPidDC230STV3 OBJECT-IDENTITY
    STATUS      current
    DESCRIPTION
        "Document Centre 230ST multi-function system
                 second post-launch configuration version, and
                 complete product identifier."
    ::= { xcmPidDC230ST 3 }
xcmPidDC230STV4 OBJECT-IDENTITY
    STATUS      current
    DESCRIPTION
        "Document Centre 230ST multi-function system
                 third post-launch configuration version, and
                 complete product identifier."
    ::= { xcmPidDC230ST 4 }
xcmPidDC230STV5 OBJECT-IDENTITY
    STATUS      current
    DESCRIPTION
        "Document Centre 230ST multi-function system
                 fourth post-launch configuration version, and
                 complete product identifier."
    ::= { xcmPidDC230ST 5 }
xcmPidDC230LP OBJECT-IDENTITY
    STATUS      current
    DESCRIPTION
        "Document Centre 230LP laser printer
                 model identifier (not a complete product identifier)."
    ::= { xcmPidDC230 2 }
            -- => SAP PID string = "132"
xcmPidDC230LPV1 OBJECT-IDENTITY
    STATUS      current
    DESCRIPTION
        "Document Centre 230LP laser printer
                 launch configuration version, and
                 complete product identifier."
    ::= { xcmPidDC230LP 1 }
xcmPidDC230LPV2 OBJECT-IDENTITY
    STATUS      current
    DESCRIPTION
        "Document Centre 230LP laser printer
                 first post-launch configuration version, and
                 complete product identifier."
    ::= { xcmPidDC230LP 2 }
xcmPidDC230LPV3 OBJECT-IDENTITY
    STATUS      current
    DESCRIPTION
        "Document Centre 230LP laser printer
                 second post-launch configuration version, and
                 complete product identifier."
    ::= { xcmPidDC230LP 3 }
xcmPidDC230LPV4 OBJECT-IDENTITY
    STATUS      current
    DESCRIPTION
        "Document Centre 230LP laser printer
                 third post-launch configuration version, and
                 complete product identifier."
    ::= { xcmPidDC230LP 4 }
xcmPidDC230LPV5 OBJECT-IDENTITY
    STATUS      current
    DESCRIPTION
        "Document Centre 230LP laser printer
                 fourth post-launch configuration version, and
                 complete product identifier."
    ::= { xcmPidDC230LP 5 }
xcmPidDC230i OBJECT-IDENTITY
    STATUS      current
    DESCRIPTION
        "Document Centre 230i multi-function system
                 model identifier (not a complete product identifier)."
    ::= { xcmPidDocuCentreSystems 22 }
xcmPidDC230iST OBJECT-IDENTITY
    STATUS      current
    DESCRIPTION
        "Document Centre 230iST multi-function system
                 model identifier (not a complete product identifier)."
    ::= { xcmPidDC230i 1 }
            -- => SAP PID string = "1F1"
xcmPidDC230iSTV1 OBJECT-IDENTITY
    STATUS      current
    DESCRIPTION
        "Document Centre 230iST multi-function system
                 launch configuration version, and
                 complete product identifier."
    ::= { xcmPidDC230iST 1 }
xcmPidDC230iSTV2 OBJECT-IDENTITY
    STATUS      current
    DESCRIPTION
        "Document Centre 230iST multi-function system
                 first post-launch configuration version, and
                 complete product identifier."
    ::= { xcmPidDC230iST 2 }
--
--
xcmPidDC240 OBJECT-IDENTITY
    STATUS      current
    DESCRIPTION
        "Document Centre 240 product type identifier
                 (not a complete product identifier)."
    ::= { xcmPidDocuCentreSystems 5 }
xcmPidDC240ST OBJECT-IDENTITY
    STATUS      current
    DESCRIPTION
        "Document Centre 240ST multi-function system
                 model identifier (not a complete product identifier)."
    ::= { xcmPidDC240 1 }
            -- => SAP PID string = "151"
xcmPidDC240STV1 OBJECT-IDENTITY
    STATUS      current
    DESCRIPTION
        "Document Centre 240ST multi-function system launch 
          configuration version, and complete product identifier."
    ::= { xcmPidDC240ST 1 }
xcmPidDC240STV2 OBJECT-IDENTITY
    STATUS      current
    DESCRIPTION
        "Document Centre 240ST multi-function system
                 first post-launch configuration version, and
                 complete product identifier."
    ::= { xcmPidDC240ST 2 }
xcmPidDC240STV3 OBJECT-IDENTITY
    STATUS      current
    DESCRIPTION
        "Document Centre 240ST multi-function system
                 second post-launch configuration version, and
                 complete product identifier."
    ::= { xcmPidDC240ST 3 }
xcmPidDC255 OBJECT-IDENTITY
    STATUS      current
    DESCRIPTION
        "Document Centre 255 product type identifier
                 (not a complete product identifier)."
    ::= { xcmPidDocuCentreSystems 7 }
xcmPidDC255ST OBJECT-IDENTITY
    STATUS      current
    DESCRIPTION
        "Document Centre 255ST multi-function system
                 model identifier (not a complete product identifier)."
    ::= { xcmPidDC255 1 }
            -- => SAP PID string = "171"
xcmPidDC255STV1 OBJECT-IDENTITY
    STATUS      current
    DESCRIPTION
        "Document Centre 255ST multi-function system launch
          configuration version, and complete product identifier."
    ::= { xcmPidDC255ST 1 }
xcmPidDC255STV2 OBJECT-IDENTITY
    STATUS      current
    DESCRIPTION
        "Document Centre 255ST multi-function system
                 first post-launch configuration version, and
                 complete product identifier."
    ::= { xcmPidDC255ST 2 }
xcmPidDC255STV3 OBJECT-IDENTITY
    STATUS      current
    DESCRIPTION
        "Document Centre 255ST multi-function system
                 second post-launch configuration version, and
                 complete product identifier."
    ::= { xcmPidDC255ST 3 }
xcmPidDC255LP OBJECT-IDENTITY
    STATUS      current
    DESCRIPTION
        "Document Centre 255LP laser printer
                 model identifier (not a complete product identifier)."
    ::= { xcmPidDC255 2 }
            -- => SAP PID string = "172"
xcmPidDC255LPV1 OBJECT-IDENTITY
    STATUS      current
    DESCRIPTION
        "Document Centre 255LP laser printer launch configuration
                 version, and complete product identifier."
    ::= { xcmPidDC255LP 1 }
xcmPidDC255LPV2 OBJECT-IDENTITY
    STATUS      current
    DESCRIPTION
        "Document Centre 255LP laser printer
                 first post-launch configuration version, and
                 complete product identifier."
    ::= { xcmPidDC255LP 2 }
xcmPidDC255LPV3 OBJECT-IDENTITY
    STATUS      current
    DESCRIPTION
        "Document Centre 255LP laser printer
                 second post-launch configuration version, and
                 complete product identifier."
    ::= { xcmPidDC255LP 3 }
xcmPidDC265 OBJECT-IDENTITY
    STATUS      current
    DESCRIPTION
        "Document Centre 265 product type identifier
                 (not a complete product identifier)."
    ::= { xcmPidDocuCentreSystems 4 }
xcmPidDC265ST OBJECT-IDENTITY
    STATUS      current
    DESCRIPTION
        "Document Centre 265ST multi-function system
                 model identifier (not a complete product identifier)."
    ::= { xcmPidDC265 1 }
            -- => SAP PID string = "141"
xcmPidDC265STV1 OBJECT-IDENTITY
    STATUS      current
    DESCRIPTION
        "Document Centre 265ST multi-function system launch 
          configuration version, and complete product identifier."
    ::= { xcmPidDC265ST 1 }
xcmPidDC265STV2 OBJECT-IDENTITY
    STATUS      current
    DESCRIPTION
        "Document Centre 265ST multi-function system
                 first post-launch configuration version, and
                 complete product identifier."
    ::= { xcmPidDC265ST 2 }
xcmPidDC265STV3 OBJECT-IDENTITY
    STATUS      current
    DESCRIPTION
        "Document Centre 265ST multi-function system
                 second post-launch configuration version, and
                 complete product identifier."
    ::= { xcmPidDC265ST 3 }
xcmPidDC265LP OBJECT-IDENTITY
    STATUS      current
    DESCRIPTION
        "Document Centre 265LP laser printer
                 model identifier (not a complete product identifier)."
    ::= { xcmPidDC265 2 }
            -- => SAP PID string = "142"
xcmPidDC265LPV1 OBJECT-IDENTITY
    STATUS      current
    DESCRIPTION
        "Document Centre 265LP laser printer launch configuration
                 version, and complete product identifier."
    ::= { xcmPidDC265LP 1 }
xcmPidDC265LPV2 OBJECT-IDENTITY
    STATUS      current
    DESCRIPTION
        "Document Centre 265LP laser printer
                 first post-launch configuration version, and
                 complete product identifier."
    ::= { xcmPidDC265LP 2 }
xcmPidDC265LPV3 OBJECT-IDENTITY
    STATUS      current
    DESCRIPTION
        "Document Centre 265LP laser printer
                 second post-launch configuration version, and
                 complete product identifier."
    ::= { xcmPidDC265LP 3 }
--
--
xcmPidDC332 OBJECT-IDENTITY
    STATUS      current
    DESCRIPTION
        "Document Centre 332 product type identifier
                 (not a complete product identifier)."
    ::= { xcmPidDocuCentreSystems 9 }
xcmPidDC332ST OBJECT-IDENTITY
    STATUS      current
    DESCRIPTION
        "Document Centre 332ST multi-function system
                 model identifier (not a complete product identifier)."
    ::= { xcmPidDC332 1 }
            -- => SAP PID string = "191"
xcmPidDC332STV1 OBJECT-IDENTITY
    STATUS      current
    DESCRIPTION
        "Document Centre 332ST multi-function system
                 launch configuration version, and
                 complete product identifier."
    ::= { xcmPidDC332ST 1 }
xcmPidDC332STV2 OBJECT-IDENTITY
    STATUS      current
    DESCRIPTION
        "Document Centre 332ST multi-function system
                 first post-launch configuration version, and
                 complete product identifier."
    ::= { xcmPidDC332ST 2 }
--
--
xcmPidDC340 OBJECT-IDENTITY
    STATUS      current
    DESCRIPTION
        "Document Centre 340 product type identifier
                 (not a complete product identifier)."
    ::= { xcmPidDocuCentreSystems 6 }
xcmPidDC340ST OBJECT-IDENTITY
    STATUS      current
    DESCRIPTION
        "Document Centre 340ST multi-function system
                 model identifier (not a complete product identifier)."
    ::= { xcmPidDC340 1 }
            -- => SAP PID string = "161"
xcmPidDC340STV1 OBJECT-IDENTITY
    STATUS      current
    DESCRIPTION
        "Document Centre 340ST multi-function system
                 launch configuration version, and
                 complete product identifier."
    ::= { xcmPidDC340ST 1 }
xcmPidDC340STV2 OBJECT-IDENTITY
    STATUS      current
    DESCRIPTION
        "Document Centre 340ST multi-function system
                 first post-launch configuration version, and
                 complete product identifier."
    ::= { xcmPidDC340ST 2 }
--
--
xcmPidDC420 OBJECT-IDENTITY
    STATUS      current
    DESCRIPTION
        "Document Centre 420 product type identifier
                 (not a complete product identifier)."
    ::= { xcmPidDocuCentreSystems 19 }
xcmPidDC420ST OBJECT-IDENTITY
    STATUS      current
    DESCRIPTION
        "Document Centre 420ST multi-function system
                 model identifier (not a complete product identifier)."
    ::= { xcmPidDC420 1 }
            -- => SAP PID string = "1C1"
xcmPidDC420STV1 OBJECT-IDENTITY
    STATUS      current
    DESCRIPTION
        "Document Centre 420ST multi-function system
                 launch configuration version, and
                 complete product identifier."
    ::= { xcmPidDC420ST 1 }
xcmPidDC420STV2 OBJECT-IDENTITY
    STATUS      current
    DESCRIPTION
        "Document Centre 420ST multi-function system
                 first post-launch configuration version, and
                 complete product identifier."
    ::= { xcmPidDC420ST 2 }
--
--
xcmPidDC426 OBJECT-IDENTITY
    STATUS      current
    DESCRIPTION
        "Document Centre 426 multi-function system
                 model identifier (not a complete product identifier)."
    ::= { xcmPidDC420 2 }
            -- => SAP PID string = "1C2"
xcmPidDC426V1 OBJECT-IDENTITY
    STATUS      current
    DESCRIPTION
        "Document Centre 426 multi-function system
                 launch configuration version, and
                 complete product identifier."
    ::= { xcmPidDC426 1 }
xcmPidDC432 OBJECT-IDENTITY
    STATUS      current
    DESCRIPTION
        "Document Centre 432 product type identifier
                 (not a complete product identifier)."
    ::= { xcmPidDocuCentreSystems 20 }
xcmPidDC432ST OBJECT-IDENTITY
    STATUS      current
    DESCRIPTION
        "Document Centre 432ST multi-function system
                 model identifier (not a complete product identifier)."
    ::= { xcmPidDC432 1 }
            -- => SAP PID string = "1D1"
xcmPidDC432STV1 OBJECT-IDENTITY
    STATUS      current
    DESCRIPTION
        "Document Centre 432ST multi-function system
                 launch configuration version, and
                 complete product identifier."
    ::= { xcmPidDC432ST 1 }
xcmPidDC432STV2 OBJECT-IDENTITY
    STATUS      current
    DESCRIPTION
        "Document Centre 432ST multi-function system
                 first post-launch configuration version, and
                 complete product identifier."
    ::= { xcmPidDC432ST 2 }
xcmPidDC432STV3 OBJECT-IDENTITY
    STATUS      current
    DESCRIPTION
        "Document Centre 432ST multi-function system
                 second post-launch configuration version, and
                 complete product identifier."
    ::= { xcmPidDC432ST 3 }
xcmPidDC432STV4 OBJECT-IDENTITY
    STATUS      current
    DESCRIPTION
        "Document Centre 432ST multi-function system
                 third post-launch configuration version, and
                 complete product identifier."
    ::= { xcmPidDC432ST 4 }
xcmPidDC432STV5 OBJECT-IDENTITY
    STATUS      current
    DESCRIPTION
        "Document Centre 432ST multi-function system
                 fourth post-launch configuration version, and
                 complete product identifier."
    ::= { xcmPidDC432ST 5 }
xcmPidDC430 OBJECT-IDENTITY
    STATUS      current
    DESCRIPTION
        "Document Centre 430 multi-function system
                 model identifier (not a complete product identifier)."
    ::= { xcmPidDC432 2 }
            -- => SAP PID string = "1D2"
xcmPidDC430V1 OBJECT-IDENTITY
    STATUS      current
    DESCRIPTION
        "Document Centre 430 multi-function system
                 launch configuration version, and
                 complete product identifier."
    ::= { xcmPidDC430 1 }
xcmPidDC440 OBJECT-IDENTITY
    STATUS      current
    DESCRIPTION
        "Document Centre 440 product type identifier
                 (not a complete product identifier)."
    ::= { xcmPidDocuCentreSystems 21 }
xcmPidDC440ST OBJECT-IDENTITY
    STATUS      current
    DESCRIPTION
        "Document Centre 440ST multi-function system
                 model identifier (not a complete product identifier)."
    ::= { xcmPidDC440 1 }
            -- => SAP PID string = "1E1"
xcmPidDC440STV1 OBJECT-IDENTITY
    STATUS      current
    DESCRIPTION
        "Document Centre 440ST multi-function system
                 launch configuration version, and
                 complete product identifier."
    ::= { xcmPidDC440ST 1 }
xcmPidDC440STV2 OBJECT-IDENTITY
    STATUS      current
    DESCRIPTION
        "Document Centre 440ST multi-function system
                 first post-launch configuration version, and
                 complete product identifier."
    ::= { xcmPidDC440ST 2 }
xcmPidDC440STV3 OBJECT-IDENTITY
    STATUS      current
    DESCRIPTION
        "Document Centre 440ST multi-function system
                 second post-launch configuration version, and
                 complete product identifier."
    ::= { xcmPidDC440ST 3 }
--
--
xcmPidDC4XX OBJECT-IDENTITY
    STATUS      current
    DESCRIPTION
        "Document Centre 4XX product type identifier
                 (not a complete product identifier)."
    ::= { xcmPidDocuCentreSystems 17 }
xcmPidDC460 OBJECT-IDENTITY
    STATUS      current
    DESCRIPTION
        "Document Centre 460 multi-functional system
                 model identifier (not a complete product identifier)."
    ::= { xcmPidDC4XX 2 }
            -- => SAP PID string = "1A2"
xcmPidDC460V1 OBJECT-IDENTITY
    STATUS      current
    DESCRIPTION
        "Document Centre 460 multi-functional system launch
                configuration version, and complete product identifier."
    ::= { xcmPidDC460 1 }
--
--
xcmPidDC470 OBJECT-IDENTITY
    STATUS      current
    DESCRIPTION
        "Document Centre 470 multi-functional system
                 model identifier (not a complete product identifier)."
    ::= { xcmPidDC4XX 4 }
            -- => SAP PID string = "1A4"
xcmPidDC470V1 OBJECT-IDENTITY
    STATUS      current
    DESCRIPTION
        "Document Centre 470 multi-functional system launch
                configuration version, and complete product identifier."
    ::= { xcmPidDC470 1 }
--
--
xcmPidDC4YY OBJECT-IDENTITY
    STATUS      current
    DESCRIPTION
        "Document Centre 4YY product type identifier
                 (not a complete product identifier)."
    ::= { xcmPidDocuCentreSystems 23 }
xcmPidDC480 OBJECT-IDENTITY
    STATUS      current
    DESCRIPTION
        "Document Centre 480 multi-functional system
                 model identifier (not a complete product identifier)."
    ::= { xcmPidDC4YY 1 }
            -- => SAP PID string = "1G1"
xcmPidDC480V1 OBJECT-IDENTITY
    STATUS      current
    DESCRIPTION
        "Document Centre 480 multi-functional system, UNUSED
                version, and complete product identifier."
    ::= { xcmPidDC480 1 }
--
--
xcmPidDC425 OBJECT-IDENTITY
    STATUS      current
    DESCRIPTION
        "Document Centre 425 product type identifier
                 (not a complete product identifier)."
    ::= { xcmPidDocuCentreSystems 24 }
xcmPidDC425ST OBJECT-IDENTITY
    STATUS      current
    DESCRIPTION
        "Document Centre 425ST multi-functional system
                 model identifier (not a complete product identifier)."
    ::= { xcmPidDC425 1 }
            -- => SAP PID string = "1H1"
xcmPidDC425STV1 OBJECT-IDENTITY
    STATUS      current
    DESCRIPTION
        "Document Centre 425ST multi-functional system launch
                configuration version, and complete product identifier."
    ::= { xcmPidDC425ST 1 }
--
--
xcmPidDC555 OBJECT-IDENTITY
    STATUS      current
    DESCRIPTION
        "Document Centre 555 product type identifier
                 (not a complete product identifier)."
    ::= { xcmPidDocuCentreSystems 27 }
xcmPidDC555ST OBJECT-IDENTITY
    STATUS      current
    DESCRIPTION
        "Document Centre 555ST multi-functional system
                 model identifier (not a complete product identifier)."
    ::= { xcmPidDC555 1 }
            -- => SAP PID string = "1K1"
xcmPidDC555STV1 OBJECT-IDENTITY
    STATUS      current
    DESCRIPTION
        "Document Centre 555ST multi-functional system ECE pre-launch
                configuration version, and complete product identifier."
    ::= { xcmPidDC555ST 1 }
xcmPidDC555STV2 OBJECT-IDENTITY
    STATUS      current
    DESCRIPTION
        "Document Centre 555ST multi-functional system, 
                 launch configuration version, and
                 complete product identifier."
    ::= { xcmPidDC555ST 2 }
--
--
xcmPidDC535 OBJECT-IDENTITY
    STATUS  current
    DESCRIPTION
        "Document Centre 535 product type identifier
                 (not a complete product identifier)."
    ::= { xcmPidDocuCentreSystems 30 }
xcmPidDC535ST OBJECT-IDENTITY
    STATUS  current
    DESCRIPTION
        "Document Centre 535 multi-function system model identifier
                 (not a complete product identifier)."
    ::= { xcmPidDC535 1 }
            -- => SAP PID string = "1N1"
xcmPidDC535STV1 OBJECT-IDENTITY
    STATUS  current
    DESCRIPTION
        "Document Centre 535 multi-function system
                 ECE pre-launch configuration version, and
                 complete product identifier."
    ::= { xcmPidDC535ST 1 }
xcmPidDC535STV2 OBJECT-IDENTITY
    STATUS  current
    DESCRIPTION
        "Document Centre 535 multi-function system
                 launch configuration version, and
                 complete product identifier."
    ::= { xcmPidDC535ST 2 }
xcmPidDC545 OBJECT-IDENTITY
    STATUS  current
    DESCRIPTION
        "Document Centre 545 product type identifier
                 (not a complete product identifier)."
    ::= { xcmPidDocuCentreSystems 31 }
xcmPidDC545ST OBJECT-IDENTITY
    STATUS  current
    DESCRIPTION
        "Document Centre 545 multi-function system model identifier
                 (not a complete product identifier)."
    ::= { xcmPidDC545 1 }
            -- => SAP PID string = "1O1"
xcmPidDC545STV1 OBJECT-IDENTITY
    STATUS  current
    DESCRIPTION
        "Document Centre 545 multi-function system
                 ECE pre-launch configuration version, and
                 complete product identifier."
    ::= { xcmPidDC545ST 1 }
xcmPidDC545STV2 OBJECT-IDENTITY
    STATUS  current
    DESCRIPTION
        "Document Centre 545 multi-function system
                 launch configuration version, and
                 complete product identifier."
    ::= { xcmPidDC545ST 2 }
--
--
----------------------------------------------------------------
----------------------------------------------------------------
xcmPidWorkCentreMFSystems OBJECT-IDENTITY
    STATUS      current
    DESCRIPTION
        "WorkCentre and WorkCentrePro Systems product line identifier
                 (not a complete product identifier)."
    ::= { xcmPidProductIdentifiers 20 }
xcmPidWCPro OBJECT-IDENTITY
    STATUS      current
    DESCRIPTION
        "WorkCentrePro System product line identifier
                 (not a complete product identifier)."
    ::= { xcmPidWorkCentreMFSystems 1 }
xcmPidWCP32C OBJECT-IDENTITY
    STATUS      current
    DESCRIPTION
        "WorkCentrePro32C multi-function system identifier
                 (not a complete product identifier)."
    ::= { xcmPidWCPro 1 }
            -- => SAP PID string = "D11"
xcmPidWCP32CV1 OBJECT-IDENTITY
    STATUS      current
    DESCRIPTION
        "WorkCentrePro32C multi-function system,
                 launch configuration version #1, and
                 complete product identifier."
    ::= { xcmPidWCP32C 1 }
xcmPidWCP32CV2 OBJECT-IDENTITY
    STATUS      current
    DESCRIPTION
        "WorkCentrePro32C multi-function system,
                 launch configuration version #2, and
                 complete product identifier."
    ::= { xcmPidWCP32C 2 }
xcmPidWCP35 OBJECT-IDENTITY
    STATUS      current
    DESCRIPTION
        "WorkCentrePro35 multi-function system identifier
                 (not a complete product identifier)."
    ::= { xcmPidWCPro 2 }
            -- => SAP PID string = "D12"
xcmPidWCP35V1 OBJECT-IDENTITY
    STATUS      current
    DESCRIPTION
        "WorkCentrePro35 multi-function system,
                 launch configuration version #1, and
                 complete product identifier."
    ::= { xcmPidWCP35 1 }
xcmPidWCP35V2 OBJECT-IDENTITY
    STATUS      current
    DESCRIPTION
        "WorkCentrePro35 multi-function system,
                 launch configuration version #2, and
                 complete product identifier."
    ::= { xcmPidWCP35 2 }
xcmPidWCP40C OBJECT-IDENTITY
    STATUS      current
    DESCRIPTION
        "WorkCentrePro40C multi-function system identifier
                 (not a complete product identifier)."
    ::= { xcmPidWCPro 3 }
            -- => SAP PID string = "D13"
xcmPidWCP40CV1 OBJECT-IDENTITY
    STATUS      current
    DESCRIPTION
        "WorkCentrePro40C multi-function system,
                 launch configuration version #1, and
                 complete product identifier."
    ::= { xcmPidWCP40C 1 }
xcmPidWCP40CV2 OBJECT-IDENTITY
    STATUS      current
    DESCRIPTION
        "WorkCentrePro40C multi-function system,
                 launch configuration version #2, and
                 complete product identifier."
    ::= { xcmPidWCP40C 2 }
xcmPidWCP45 OBJECT-IDENTITY
    STATUS      current
    DESCRIPTION
     "WorkCentrePro45 multi-function system identifier
      (not a complete product identifier)."
    ::= { xcmPidWCPro 4 }
            -- => SAP PID string = "D14"
xcmPidWCP45V1 OBJECT-IDENTITY
    STATUS      current
    DESCRIPTION
        "WorkCentrePro45 multi-function system,
                 launch configuration version #1, and
                 complete product identifier."
    ::= { xcmPidWCP45 1 }
xcmPidWCP45V2 OBJECT-IDENTITY
    STATUS      current
    DESCRIPTION
        "WorkCentrePro45 multi-function system,
                 launch configuration version #2, and
                 complete product identifier."
    ::= { xcmPidWCP45 2 }
xcmPidWCP55 OBJECT-IDENTITY
    STATUS      current
    DESCRIPTION
        "WorkCentrePro55 multi-function system identifier
                 (not a complete product identifier)."
    ::= { xcmPidWCPro 5 }
            -- => SAP PID string = "D15"
xcmPidWCP55V1 OBJECT-IDENTITY
    STATUS      current
    DESCRIPTION
        "WorkCentrePro55 multi-function system,
                 launch configuration version #1, and
                 complete product identifier."
    ::= { xcmPidWCP55 1 }
xcmPidWCP55V2 OBJECT-IDENTITY
    STATUS      current
    DESCRIPTION
        "WorkCentrePro55 multi-function system,
                 launch configuration version #2, and
                 complete product identifier."
    ::= { xcmPidWCP55 2 }
--
--
xcmPidWCP165 OBJECT-IDENTITY
    STATUS      current
    DESCRIPTION
        "WorkCentre Pro 165 multi-function system identifier
                 (not a complete product identifier)."
    ::= { xcmPidWCPro 9 }
            -- => SAP PID string = "D19"
xcmPidWCP165V1 OBJECT-IDENTITY
    STATUS      current
    DESCRIPTION
        "WorkCentre Pro 165 multi-function system,
                 launch configuration version #1, and
                 complete product identifier."
    ::= { xcmPidWCP165 1 }
xcmPidWCP175 OBJECT-IDENTITY
    STATUS      current
    DESCRIPTION
        "WorkCentre Pro 175 multi-function system identifier
                 (not a complete product identifier)."
    ::= { xcmPidWCPro 17 }
            -- => SAP PID string = "D1A"
xcmPidWCP175V1 OBJECT-IDENTITY
    STATUS      current
    DESCRIPTION
        "WorkCentre Pro 175 multi-function system,
                 launch configuration version #1, and
                 complete product identifier."
    ::= { xcmPidWCP175 1 }
xcmPidWC265 OBJECT-IDENTITY
    STATUS      current
    DESCRIPTION
        "WorkCentre 265 multi-function system identifier
                 (not a complete product identifier)."
    ::= { xcmPidWCPro 22 }
            -- => SAP PID string = "D1F"
xcmPidWC265V1 OBJECT-IDENTITY
    STATUS      current
    DESCRIPTION
        "WorkCentre 265 multi-function system,
                 launch configuration version #1, and
                 complete product identifier."
    ::= { xcmPidWC265 1 }
--
xcmPidWC275 OBJECT-IDENTITY
    STATUS      current
    DESCRIPTION
        "WorkCentre 275 multi-function system identifier
                 (not a complete product identifier)."
    ::= { xcmPidWCPro 23 }
            -- => SAP PID string = "D1G"
xcmPidWC275V1 OBJECT-IDENTITY
    STATUS      current
    DESCRIPTION
        "WorkCentre 275 multi-function system,
                 launch configuration version #1, and
                 complete product identifier."
    ::= { xcmPidWC275 1 }
xcmPidWCP265 OBJECT-IDENTITY
    STATUS      current
    DESCRIPTION
        "WorkCentre Pro 265 multi-function system identifier
                 (not a complete product identifier)."
    ::= { xcmPidWCPro 24 }
            -- => SAP PID string = "D1H"
xcmPidWCP265V1 OBJECT-IDENTITY
    STATUS      current
    DESCRIPTION
        "WorkCentre Pro 265 multi-function system,
                 launch configuration version #1, and
                 complete product identifier."
    ::= { xcmPidWCP265 1 }
xcmPidWCP275 OBJECT-IDENTITY
    STATUS      current
    DESCRIPTION
        "WorkCentre Pro 275 multi-function system identifier
                 (not a complete product identifier)."
    ::= { xcmPidWCPro 25 }
            -- => SAP PID string = "D1I"
xcmPidWCP275V1 OBJECT-IDENTITY
    STATUS      current
    DESCRIPTION
        "WorkCentre Pro 275 multi-function system,
                 launch configuration version #1, and
                 complete product identifier."
    ::= { xcmPidWCP275 1 }
--
xcmPidWCPS265 OBJECT-IDENTITY
    STATUS      current
    DESCRIPTION
        "WorkCentre + PostScript 265 multi-function system identifier
                 (not a complete product identifier)."
    ::= { xcmPidWCPro 26 }
            -- => SAP PID string = "D1J"
xcmPidWCPS265V1 OBJECT-IDENTITY
    STATUS      current
    DESCRIPTION
        "WorkCentre + PostScript 265 multi-function system,
                 launch configuration version #1, and
                 complete product identifier."
    ::= { xcmPidWCPS265 1 }
--
xcmPidWCPS275 OBJECT-IDENTITY
    STATUS      current
    DESCRIPTION
        "WorkCentre + PostScript 275 multi-function system identifier
                 (not a complete product identifier)."
    ::= { xcmPidWCPro 27 }
            -- => SAP PID string = "D1K"
xcmPidWCPS275V1 OBJECT-IDENTITY
    STATUS      current
    DESCRIPTION
        "WorkCentre + PostScript 275 multi-function system,
                 launch configuration version #1, and
                 complete product identifier."
    ::= { xcmPidWCPS275 1 }
--
-- Patriot / Lexington branding is "WorkCentre" however 
xcmPidWC7655 OBJECT-IDENTITY
    STATUS      current
    DESCRIPTION
        "WorkCentre 7655 multi-function system identifier
                 (not a complete product identifier)."
    ::= { xcmPidWCPro 28 }
            -- => SAP PID string = "D1L"
xcmPidWC7655V1 OBJECT-IDENTITY
    STATUS      current
    DESCRIPTION
        "WorkCentre 7655 system identifier
         launch configuration version #1, and
         complete product identifier."
    ::= { xcmPidWC7655 1 }
--
-- Patriot / Lexington branding is "WorkCentre" however 
xcmPidWC7665 OBJECT-IDENTITY
    STATUS      current
    DESCRIPTION
        "WorkCentre 7665 system identifier
                 (not a complete product identifier)."
    ::= { xcmPidWCPro 29 }
            -- => SAP PID string = "D1M"
xcmPidWC7665V1 OBJECT-IDENTITY
    STATUS      current
    DESCRIPTION
        "WorkCentre 7665 system identifier
         launch configuration version #1, and
         complete product identifier."
    ::= { xcmPidWC7665 1 }
--
-- Patriot / Lexington branding is "WorkCentre" however 
xcmPidWC7675 OBJECT-IDENTITY
    STATUS      current
    DESCRIPTION
        "WorkCentre 7675 system identifier
                 (not a complete product identifier)."
    ::= { xcmPidWCPro 36 }
            -- => SAP PID string = "D1S"
xcmPidWC7675V1 OBJECT-IDENTITY
    STATUS      current
    DESCRIPTION
        "WorkCentre 7675 system identifier
         launch configuration version #1, and
         complete product identifier."
    ::= { xcmPidWC7675 1 }
--
--
--
--
--
--
--
--
--
--
xcmPidWCPC2128 OBJECT-IDENTITY
    STATUS      current
    DESCRIPTION
        "WorkCentre Pro C2128 multi-function system 
                 identifier (not a complete product identifier)."
    ::= { xcmPidWCPro 19 }
            -- => SAP PID string = "D1C"
xcmPidWCPC2128V1 OBJECT-IDENTITY
    STATUS      current
    DESCRIPTION
        "WorkCentre Pro C2128 multi-function system launch configuration
                 and version #1, and complete product identifier."
    ::= { xcmPidWCPC2128 1 }
xcmPidWCPC2636 OBJECT-IDENTITY
    STATUS      current
    DESCRIPTION
        "WorkCentre Pro C2636 multi-function system 
                 identifier (not a complete product identifier)."
    ::= { xcmPidWCPro 20 }
            -- => SAP PID string = "D1D"
xcmPidWCPC2636V1 OBJECT-IDENTITY
    STATUS      current
    DESCRIPTION
        "WorkCentre Pro C2636 multi-function system launch configuration
                 and version #1, and complete product identifier."
    ::= { xcmPidWCPC2636 1 }
xcmPidWCPC3545 OBJECT-IDENTITY
    STATUS      current
    DESCRIPTION
        "WorkCentre Pro C3545 multi-function system
                 identifier (not a complete product identifier)."
    ::= { xcmPidWCPro 21 }
            -- => SAP PID string = "D1E"
xcmPidWCPC3545V1 OBJECT-IDENTITY
    STATUS      current
    DESCRIPTION
        "WorkCentre Pro C3545 multi-function system launch configuration
                 and version #1, and complete product identifier."
    ::= { xcmPidWCPC3545 1 }
--
--
xcmPidWCMF OBJECT-IDENTITY
    STATUS      current
    DESCRIPTION
        "WorkCentre System identifier               
                 (not a complete product identifier)."
    ::= { xcmPidWorkCentreMFSystems 2 }
----------------------------------------------------------------
----------------------------------------------------------------
xcmPidWCMF3 OBJECT-IDENTITY
    STATUS      current
    DESCRIPTION
        "WorkCentrePro System product line identifier
                 (not a complete product identifier)."
    ::= { xcmPidWorkCentreMFSystems 3 }
--
--
xcmPidWCM35 OBJECT-IDENTITY
    STATUS      current
    DESCRIPTION
        "WorkCentre M35 multi-function system identifier
                (not a complete product identifier)."
    ::= { xcmPidWCMF 2 }
            -- => SAP PID string = "D22"
xcmPidWCM35V1 OBJECT-IDENTITY
    STATUS      current
    DESCRIPTION
        "WorkCentre M35 multi-function system, 
                 launch configuration version #1, and
                 complete product identifier."
    ::= { xcmPidWCM35 1 }
xcmPidWCM35V2 OBJECT-IDENTITY
    STATUS      current
    DESCRIPTION
        "WorkCentre M35 multi-function system,
                 launch configuration version #2, and
                 complete product identifier."
    ::= { xcmPidWCM35 2 }
xcmPidWCM45 OBJECT-IDENTITY
    STATUS      current
    DESCRIPTION
        "WorkCentre M45 multi-function system identifier
                (not a complete product identifier)."
    ::= { xcmPidWCMF 3 }
            -- => SAP PID string = "D23"
xcmPidWCM45V1 OBJECT-IDENTITY
    STATUS      current
    DESCRIPTION
        "WorkCentre M45 multi-function system, 
                 launch configuration version #1, and
                 complete product identifier."
    ::= { xcmPidWCM45 1 }
xcmPidWCM45V2 OBJECT-IDENTITY
    STATUS      current
    DESCRIPTION
        "WorkCentre M45 multi-function system,
                 launch configuration version #2, and
                 complete product identifier."
    ::= { xcmPidWCM45 2 }
xcmPidWCM55 OBJECT-IDENTITY
    STATUS      current
    DESCRIPTION
        "WorkCentre M55 multi-function system identifier
                (not a complete product identifier)."
    ::= { xcmPidWCMF 4 }
            -- => SAP PID string = "D24"
xcmPidWCM55V1 OBJECT-IDENTITY
    STATUS      current
    DESCRIPTION
        "WorkCentre M55 multi-function system, 
                 launch configuration version #1, and
                 complete product identifier."
    ::= { xcmPidWCM55 1 }
xcmPidWCM55V2 OBJECT-IDENTITY
    STATUS      current
    DESCRIPTION
        "WorkCentre M55 multi-function system,
                 launch configuration version #2, and
                 complete product identifier."
    ::= { xcmPidWCM55 2 }
xcmPidWCM165 OBJECT-IDENTITY
    STATUS      current
    DESCRIPTION
        "WorkCentre  M165 multi-function system identifier
                 (not a complete product identifier)."
    ::= { xcmPidWCMF 5 }
            -- => SAP PID string = "D25"
xcmPidWCM165V1 OBJECT-IDENTITY
    STATUS      current
    DESCRIPTION
        "WorkCentre  M165 multi-function system,
                 launch configuration version #1, and
                 complete product identifier."
    ::= { xcmPidWCM165 1 }
xcmPidWCM175 OBJECT-IDENTITY
    STATUS      current
    DESCRIPTION
        "WorkCentre  M175 multi-function system identifier
                 (not a complete product identifier)."
    ::= { xcmPidWCMF 6 }
            -- => SAP PID string = "D26"
xcmPidWCM175V1 OBJECT-IDENTITY
    STATUS      current
    DESCRIPTION
        "WorkCentre  M175 multi-function system,
                 launch configuration version #1, and
                 complete product identifier."
    ::= { xcmPidWCM175 1 }
--
--
xcmPidWCMPS35 OBJECT-IDENTITY
    STATUS      current
    DESCRIPTION
        "WorkCentre  M35 PostScript multi-function system identifier
                 (not a complete product identifier)."
    ::= { xcmPidWCMF 9 }
            -- => SAP PID string = "D29"
xcmPidWCMPS35V1 OBJECT-IDENTITY
    STATUS      current
    DESCRIPTION
        "WorkCentre  M35 PostScript multi-function system,
                 launch configuration version #1, and
                 complete product identifier."
    ::= { xcmPidWCMPS35 1 }
xcmPidWCMPS45 OBJECT-IDENTITY
    STATUS      current
    DESCRIPTION
        "WorkCentre  M45 PostScript multi-function system identifier
                 (not a complete product identifier)."
    ::= { xcmPidWCMF 17 }
            -- => SAP PID string = "D2A"
xcmPidWCMPS45V1 OBJECT-IDENTITY
    STATUS      current
    DESCRIPTION
        "WorkCentre  M45 PostScript multi-function system,
                 launch configuration version #1, and
                 complete product identifier."
    ::= { xcmPidWCMPS45 1 }
xcmPidWCMPS55 OBJECT-IDENTITY
    STATUS      current
    DESCRIPTION
        "WorkCentre  M55 PostScript multi-function system identifier
                 (not a complete product identifier)."
    ::= { xcmPidWCMF 18 }
            -- => SAP PID string = "D2B"
xcmPidWCMPS55V1 OBJECT-IDENTITY
    STATUS      current
    DESCRIPTION
        "WorkCentre  M55 PostScript multi-function system,
                 launch configuration version #1, and
                 complete product identifier."
    ::= { xcmPidWCMPS55 1 }
xcmPidWCMPS165 OBJECT-IDENTITY
    STATUS      current
    DESCRIPTION
        "WorkCentre  M165 PostScript multi-function system identifier
                 (not a complete product identifier)."
    ::= { xcmPidWCMF 19 }
            -- => SAP PID string = "D2C"
xcmPidWCMPS165V1 OBJECT-IDENTITY
    STATUS      current
    DESCRIPTION
        "WorkCentre  M165 PostScript multi-function system,
                 launch configuration version #1, and
                 complete product identifier."
    ::= { xcmPidWCMPS165 1 }
xcmPidWCMPS175 OBJECT-IDENTITY
    STATUS      current
    DESCRIPTION
        "WorkCentre  M175 PostScript multi-function system identifier
                 (not a complete product identifier)."
    ::= { xcmPidWCMF 20 }
            -- => SAP PID string = "D2D"
xcmPidWCMPS175V1 OBJECT-IDENTITY
    STATUS      current
    DESCRIPTION
        "WorkCentre  M175 PostScript multi-function system,
                 launch configuration version #1, and
                 complete product identifier."
    ::= { xcmPidWCMPS175 1 }
xcmPidWCPS232 OBJECT-IDENTITY
    STATUS      current
    DESCRIPTION
        "WorkCentre + PostScript 232 multi-function system identifier
                 (not a complete product identifier)."
    ::= { xcmPidWCMF 26 }
            -- => SAP PID string = "D2J"
xcmPidWCPS232V1 OBJECT-IDENTITY
    STATUS      current
    DESCRIPTION
        "WorkCentre + PostScript 232 multi-function system,
                 launch configuration version #1, and
                 complete product identifier."
    ::= { xcmPidWCPS232 1 }
xcmPidWCPS238 OBJECT-IDENTITY
    STATUS      current
    DESCRIPTION
        "WorkCentre + PostScript 238 multi-function system identifier
                 (not a complete product identifier)."
    ::= { xcmPidWCMF 27 }
            -- => SAP PID string = "D2K"
xcmPidWCPS238V1 OBJECT-IDENTITY
    STATUS      current
    DESCRIPTION
        "WorkCentre + PostScript 238 multi-function system,
                 launch configuration version #1, and
                 complete product identifier."
    ::= { xcmPidWCPS238 1 }
xcmPidWCPS245 OBJECT-IDENTITY
    STATUS      current
    DESCRIPTION
        "WorkCentre + PostScript 245 multi-function system identifier
                 (not a complete product identifier)."
    ::= { xcmPidWCMF 28 }
            -- => SAP PID string = "D2L"
xcmPidWCPS245V1 OBJECT-IDENTITY
    STATUS      current
    DESCRIPTION
        "WorkCentre + PostScript 245 multi-function system,
                 launch configuration version #1, and
                 complete product identifier."
    ::= { xcmPidWCPS245 1 }
xcmPidWCPS255 OBJECT-IDENTITY
    STATUS      current
    DESCRIPTION
        "WorkCentre + PostScript 255 multi-function system identifier
                 (not a complete product identifier)."
    ::= { xcmPidWCMF 29 }
            -- => SAP PID string = "D2M"
xcmPidWCPS255V1 OBJECT-IDENTITY
    STATUS      current
    DESCRIPTION
        "WorkCentre + PostScript 255 multi-function system,
                 launch configuration version #1, and
                 complete product identifier."
    ::= { xcmPidWCPS255 1 }
xcmPidWCP232 OBJECT-IDENTITY
    STATUS      current
    DESCRIPTION
        "WorkCentre Pro 232 multi-function system identifier
                 (not a complete product identifier)."
    ::= { xcmPidWCMF 30 }
            -- => SAP PID string = "D2N"
xcmPidWCP232V1 OBJECT-IDENTITY
    STATUS      current
    DESCRIPTION
        "WorkCentre Pro 232 multi-function system,
                 launch configuration version #1, and
                 complete product identifier."
    ::= { xcmPidWCP232 1 }
xcmPidWCP238 OBJECT-IDENTITY
    STATUS      current
    DESCRIPTION
        "WorkCentre Pro 238 multi-function system identifier
                 (not a complete product identifier)."
    ::= { xcmPidWCMF 31 }
            -- => SAP PID string = "D2O"
xcmPidWCP238V1 OBJECT-IDENTITY
    STATUS      current
    DESCRIPTION
        "WorkCentre Pro 238 multi-function system,
                 launch configuration version #1, and
                 complete product identifier."
    ::= { xcmPidWCP238 1 }
xcmPidWCP245 OBJECT-IDENTITY
    STATUS      current
    DESCRIPTION
        "WorkCentre Pro 245 multi-function system identifier
                 (not a complete product identifier)."
    ::= { xcmPidWCMF 32 }
            -- => SAP PID string = "D2P"
xcmPidWCP245V1 OBJECT-IDENTITY
    STATUS      current
    DESCRIPTION
        "WorkCentre Pro 245 multi-function system,
                 launch configuration version #1, and
                 complete product identifier."
    ::= { xcmPidWCP245 1 }
xcmPidWCP255 OBJECT-IDENTITY
    STATUS      current
    DESCRIPTION
        "WorkCentre Pro 255 multi-function system identifier
                 (not a complete product identifier)."
    ::= { xcmPidWCMF 33 }
            -- => SAP PID string = "D2Q"
xcmPidWCP255V1 OBJECT-IDENTITY
    STATUS      current
    DESCRIPTION
        "WorkCentre Pro 255 multi-function system,
                 launch configuration version #1, and
                 complete product identifier."
    ::= { xcmPidWCP255 1 }
xcmPidWC232 OBJECT-IDENTITY
    STATUS      current
    DESCRIPTION
        "WorkCentre 232 multi-function system identifier
                 (not a complete product identifier)."
    ::= { xcmPidWCMF 34 }
            -- => SAP PID string = "D2R"
xcmPidWC232V1 OBJECT-IDENTITY
    STATUS      current
    DESCRIPTION
        "WorkCentre 232 multi-function system,
                 launch configuration version #1, and
                 complete product identifier."
    ::= { xcmPidWC232 1 }
xcmPidWC238 OBJECT-IDENTITY
    STATUS      current
    DESCRIPTION
        "WorkCentre 238 multi-function system identifier
                 (not a complete product identifier)."
    ::= { xcmPidWCMF 35 }
            -- => SAP PID string = "D2S"
xcmPidWC238V1 OBJECT-IDENTITY
    STATUS      current
    DESCRIPTION
        "WorkCentre 238 multi-function system,
                 launch configuration version #1, and
                 complete product identifier."
    ::= { xcmPidWC238 1 }
xcmPidWC245 OBJECT-IDENTITY
    STATUS      current
    DESCRIPTION
        "WorkCentre 245 multi-function system identifier
                 (not a complete product identifier)."
    ::= { xcmPidWCMF 36 }
            -- => SAP PID string = "D2T"
xcmPidWC245V1 OBJECT-IDENTITY
    STATUS      current
    DESCRIPTION
        "WorkCentre 245 multi-function system,
                 launch configuration version #1, and
                 complete product identifier."
    ::= { xcmPidWC245 1 }
xcmPidWC255 OBJECT-IDENTITY
    STATUS      current
    DESCRIPTION
        "WorkCentre 255 multi-function system identifier
                 (not a complete product identifier)."
    ::= { xcmPidWCMF 37 }
            -- => SAP PID string = "D2U"
xcmPidWC255V1 OBJECT-IDENTITY
    STATUS      current
    DESCRIPTION
        "WorkCentre 255 multi-function system,
                 launch configuration version #1, and
                 complete product identifier."
    ::= { xcmPidWC255 1 }
--
--
xcmPidWCMF28 OBJECT-IDENTITY
    STATUS      current
    DESCRIPTION
        "Xerox WorkCentre M128 multi-function system identifier
                 (not a complete product identifier)."
    ::= { xcmPidWCMF 23 }
            -- => SAP PID string = "D2G"
xcmPidWCMFM28 OBJECT-IDENTITY
    STATUS      current
    DESCRIPTION
        "Xerox WorkCentre M128 multi-function system,
                 launch configuration version #1, and
                 complete product identifier."
    ::= { xcmPidWCMF28 1 }
--
--
--
xcmPidWorkCentre5135 OBJECT-IDENTITY
    STATUS      current
    DESCRIPTION
        "Xerox WorkCentre 5135 model identifier
                 (not a complete product identifier)."
    ::= { xcmPidWCMF 40 }
            -- => SAP PID string = "D2X"
--
--     -mf "Xerox" -mo "WorkCentre 5135"
xcmPidWorkCentre5135C1 OBJECT-IDENTITY
    STATUS      current
    DESCRIPTION
        "Xerox WorkCentre 5135 model and configuration 1 identifier
           (not a complete product identifier)."
    ::= { xcmPidWorkCentre5135 1 }
xcmPidWorkCentre5135C1V1 OBJECT-IDENTITY
    STATUS      current
    DESCRIPTION
        "Xerox WorkCentre 5135 launch model, configuration 1, 
           version 1.  A complete product identifier."
    ::= { xcmPidWorkCentre5135C1 1 }
xcmPidWorkCentre5135C1V2 OBJECT-IDENTITY
    STATUS      current
    DESCRIPTION
        "Xerox WorkCentre 5135 launch model, configuration 1, 
           version 2.  A complete product identifier."
    ::= { xcmPidWorkCentre5135C1 2 }
xcmPidWorkCentre5150 OBJECT-IDENTITY
    STATUS      current
    DESCRIPTION
        "Xerox WorkCentre 5150 model identifier
                 (not a complete product identifier)."
    ::= { xcmPidWCMF 41 }
            -- => SAP PID string = "D2Y"
--
--     -mf "Xerox" -mo "WorkCentre 5150"
xcmPidWorkCentre5150C1 OBJECT-IDENTITY
    STATUS      current
    DESCRIPTION
        "Xerox WorkCentre 5150 model and configuration 1 identifier
           (not a complete product identifier)."
    ::= { xcmPidWorkCentre5150 1 }
xcmPidWorkCentre5150C1V1 OBJECT-IDENTITY
    STATUS      current
    DESCRIPTION
        "Xerox WorkCentre 5150 launch model, configuration 1, 
           version 1.  A complete product identifier."
    ::= { xcmPidWorkCentre5150C1 1 }
xcmPidWorkCentre5150C1V2 OBJECT-IDENTITY
    STATUS      current
    DESCRIPTION
        "Xerox WorkCentre 5150 launch model, configuration 1, 
           version 2.  A complete product identifier."
    ::= { xcmPidWorkCentre5150C1 2 }
--
--
--
xcmPidWC5632 OBJECT-IDENTITY
    STATUS      current
    DESCRIPTION
        "WorkCentre 5632 multi-function system identifier
                 (not a complete product identifier)."
    ::= { xcmPidWCMF3 35 }
            -- => SAP PID string = "D3S"
--
--     -mf "Xerox" -mo "WorkCentre 5632"
xcmPidWC5632V1 OBJECT-IDENTITY
    STATUS      current
    DESCRIPTION
        "WorkCentre 5632 multi-function system,
                 launch configuration version #1, and
                 complete product identifier."
    ::= { xcmPidWC5632 1 }
--
--
--
--
xcmPidWC5638 OBJECT-IDENTITY
    STATUS      current
    DESCRIPTION
        "WorkCentre 5638 multi-function system identifier
                 (not a complete product identifier)."
    ::= { xcmPidWCMF3 37 }
            -- => SAP PID string = "D3U"
--
--     -mf "Xerox" -mo "WorkCentre 5638"
xcmPidWC5638V1 OBJECT-IDENTITY
    STATUS      current
    DESCRIPTION
        "WorkCentre 5638 multi-function system,
                 launch configuration version #1, and
                 complete product identifier."
    ::= { xcmPidWC5638 1 }
--
--
xcmPidWC5645 OBJECT-IDENTITY
    STATUS      current
    DESCRIPTION
        "WorkCentre 5645 multi-function system identifier
                 (not a complete product identifier)."
    ::= { xcmPidWCMF3 38 }
            -- => SAP PID string = "D3V"
--
--     -mf "Xerox" -mo "WorkCentre 5645"
xcmPidWC5645V1 OBJECT-IDENTITY
    STATUS      current
    DESCRIPTION
        "WorkCentre 5645 multi-function system,
                 launch configuration version #1, and
                 complete product identifier."
    ::= { xcmPidWC5645 1 }
--
--
xcmPidWC5655 OBJECT-IDENTITY
    STATUS      current
    DESCRIPTION
        "WorkCentre 5655 multi-function system identifier
                 (not a complete product identifier)."
    ::= { xcmPidWCMF3 39 }
            -- => SAP PID string = "D3W"
--
--     -mf "Xerox" -mo "WorkCentre 5655"
xcmPidWC5655V1 OBJECT-IDENTITY
    STATUS      current
    DESCRIPTION
        "WorkCentre 5655 multi-function system,
                 launch configuration version #1, and
                 complete product identifier."
    ::= { xcmPidWC5655 1 }
--
--
xcmPidWC5665 OBJECT-IDENTITY
    STATUS      current
    DESCRIPTION
        "WorkCentre 5665 multi-function system identifier
                 (not a complete product identifier)."
    ::= { xcmPidWCMF3 40 }
            -- => SAP PID string = "D3X"
--
--     -mf "Xerox" -mo "WorkCentre 5665"
xcmPidWC5665V1 OBJECT-IDENTITY
    STATUS      current
    DESCRIPTION
        "WorkCentre 5665 multi-function system,
                 launch configuration version #1, and
                 complete product identifier."
    ::= { xcmPidWC5665 1 }
--
--
xcmPidWC5675 OBJECT-IDENTITY
    STATUS      current
    DESCRIPTION
        "WorkCentre 5675 multi-function system identifier
                 (not a complete product identifier)."
    ::= { xcmPidWCMF3 41 }
            -- => SAP PID string = "D3Y"
--
--     -mf "Xerox" -mo "WorkCentre 5675"
xcmPidWC5675V1 OBJECT-IDENTITY
    STATUS      current
    DESCRIPTION
        "WorkCentre 5675 multi-function system,
                 launch configuration version #1, and
                 complete product identifier."
    ::= { xcmPidWC5675 1 }
--
--
--
----------------------------------------------------------------
----------------------------------------------------------------
xcmPidWCMF4 OBJECT-IDENTITY
    STATUS      current
    DESCRIPTION
        "Xerox WorkCentre System product line identifier
                 (not a complete product identifier)."
    ::= { xcmPidWorkCentreMFSystems 4 }
--
--
xcmPidWC5687 OBJECT-IDENTITY
    STATUS      current
    DESCRIPTION
        "Xerox WorkCentre 5687 multi-function system identifier
                 (not a complete product identifier)."
    ::= { xcmPidWCMF4 9 }
            -- => SAP PID string = "D49"
--
--     -mf "Xerox" -mo "WorkCentre 5687"
xcmPidWC5687V1 OBJECT-IDENTITY
    STATUS      current
    DESCRIPTION
        "Xerox WorkCentre 5687 multi-function system,
                 launch configuration version #1, and
                 complete product identifier."
    ::= { xcmPidWC5687 1 }
--
--
xcmPidWC5030 OBJECT-IDENTITY
    STATUS      current
    DESCRIPTION
        "Xerox WorkCentre 5030 multi-function system identifier
                 (not a complete product identifier)."
    ::= { xcmPidWCMF4 17 }
            -- => SAP PID string = "D4A"
--
--     -mf "Xerox" -mo "WorkCentre 5030"
xcmPidWC5030V1 OBJECT-IDENTITY
    STATUS      current
    DESCRIPTION
        "Xerox WorkCentre 5030 multi-function system,
                 launch configuration version #1, and
                 complete product identifier."
    ::= { xcmPidWC5030 1 }
xcmPidWC5030V2 OBJECT-IDENTITY
    STATUS      current
    DESCRIPTION
        "Xerox WorkCentre 5030 multi-function system,
                 launch configuration version #2, and
                 complete product identifier."
    ::= { xcmPidWC5030 2 }
xcmPidWC5050 OBJECT-IDENTITY
    STATUS      current
    DESCRIPTION
        "Xerox WorkCentre 5050 multi-function system identifier
                 (not a complete product identifier)."
    ::= { xcmPidWCMF4 18 }
            -- => SAP PID string = "D4B"
--
--     -mf "Xerox" -mo "WorkCentre 5050"
xcmPidWC5050V1 OBJECT-IDENTITY
    STATUS      current
    DESCRIPTION
        "Xerox WorkCentre 5050 multi-function system,
                 launch configuration version #1, and
                 complete product identifier."
    ::= { xcmPidWC5050 1 }
xcmPidWC5050V2 OBJECT-IDENTITY
    STATUS      current
    DESCRIPTION
        "Xerox WorkCentre 5050 multi-function system,
                 launch configuration version #2, and
                 complete product identifier."
    ::= { xcmPidWC5050 2 }
--
--
--
--
----------------------------------------------------------------
----------------------------------------------------------------
xcmPidWCMF5 OBJECT-IDENTITY
    STATUS      current
    DESCRIPTION
        "Xerox WorkCentre System product line identifier
                 (not a complete product identifier)."
    ::= { xcmPidWorkCentreMFSystems 5 }
--
xcmPidWC6400 OBJECT-IDENTITY
    STATUS      current
    DESCRIPTION
        "Xerox WorkCentre 6400 model identifier
           (not a complete product identifier)."
    ::= { xcmPidWCMF5 5 }
            -- => SAP PID string = "D55"
xcmPidWC6400S OBJECT-IDENTITY
    STATUS      current
    DESCRIPTION
        "Xerox WorkCentre 6400S 
           model and configuration identifier
           (not a complete product identifier)."
    ::= { xcmPidWC6400 1 }
--
--     -mf "Xerox" -mo "WorkCentre 6400S"
xcmPidWC6400Sv1 OBJECT-IDENTITY
    STATUS      current
    DESCRIPTION
        "Xerox WorkCentre 6400S 
            launch model, configuration, version 1. 
            A complete product identifier."
    ::= { xcmPidWC6400S 1 }
xcmPidWC6400Sv2 OBJECT-IDENTITY
    STATUS      current
    DESCRIPTION
        "Xerox WorkCentre 6400S 
            launch model, configuration, version 2. 
            A complete product identifier."
    ::= { xcmPidWC6400S 2 }
xcmPidWC6400X OBJECT-IDENTITY
    STATUS      current
    DESCRIPTION
        "Xerox WorkCentre 6400X 
           model and configuration identifier
           (not a complete product identifier)."
    ::= { xcmPidWC6400 2 }
--
--     -mf "Xerox" -mo "WorkCentre 6400X"
xcmPidWC6400Xv1 OBJECT-IDENTITY
    STATUS      current
    DESCRIPTION
        "Xerox WorkCentre 6400X 
            launch model, configuration, version 1. 
            A complete product identifier."
    ::= { xcmPidWC6400X 1 }
xcmPidWC6400Xv2 OBJECT-IDENTITY
    STATUS      current
    DESCRIPTION
        "Xerox WorkCentre 6400X  
            launch model, configuration, version 2. 
            A complete product identifier."
    ::= { xcmPidWC6400X 2 }
xcmPidWC6400XF OBJECT-IDENTITY
    STATUS      current
    DESCRIPTION
        "Xerox WorkCentre 6400XF 
           model and configuration identifier
           (not a complete product identifier)."
    ::= { xcmPidWC6400 3 }
--
--     -mf "Xerox" -mo "WorkCentre 6400XF"
xcmPidWC6400XFv1 OBJECT-IDENTITY
    STATUS      current
    DESCRIPTION
        "Xerox WorkCentre 6400XF 
            launch model, configuration, version 1. 
            A complete product identifier."
    ::= { xcmPidWC6400XF 1 }
xcmPidWC6400XFv2 OBJECT-IDENTITY
    STATUS      current
    DESCRIPTION
        "Xerox WorkCentre 6400XF 
            launch model, configuration, version 2. 
            A complete product identifier."
    ::= { xcmPidWC6400XF 2 }
--
--
--
xcmPidWorkCentre5735 OBJECT-IDENTITY
    STATUS      current
    DESCRIPTION
        "Xerox WorkCentre 5735 model identifier
                 (not a complete product identifier)."
    ::= { xcmPidWCMF5 29 }
            -- => SAP PID string = "D5M"
--
--     -mf "Xerox" -mo "WorkCentre 5735"
xcmPidWorkCentre5735C1 OBJECT-IDENTITY
    STATUS      current
    DESCRIPTION
        "Xerox WorkCentre 5735 model and configuration 1 identifier
           (not a complete product identifier)."
    ::= { xcmPidWorkCentre5735 1 }
xcmPidWorkCentre5735C1V1 OBJECT-IDENTITY
    STATUS      current
    DESCRIPTION
        "Xerox WorkCentre 5735 launch model, configuration 1, 
           version 1.  A complete product identifier."
    ::= { xcmPidWorkCentre5735C1 1 }
xcmPidWorkCentre5740 OBJECT-IDENTITY
    STATUS      current
    DESCRIPTION
        "Xerox WorkCentre 5740 model identifier
                 (not a complete product identifier)."
    ::= { xcmPidWCMF5 30 }
            -- => SAP PID string = "D5N"
--
--     -mf "Xerox" -mo "WorkCentre 5740"
xcmPidWorkCentre5740C1 OBJECT-IDENTITY
    STATUS      current
    DESCRIPTION
        "Xerox WorkCentre 5740 model and configuration 1 identifier
           (not a complete product identifier)."
    ::= { xcmPidWorkCentre5740 1 }
xcmPidWorkCentre5740C1V1 OBJECT-IDENTITY
    STATUS      current
    DESCRIPTION
        "Xerox WorkCentre 5740 launch model, configuration 1, 
           version 1.  A complete product identifier."
    ::= { xcmPidWorkCentre5740C1 1 }
xcmPidWorkCentre5745 OBJECT-IDENTITY
    STATUS      current
    DESCRIPTION
        "Xerox WorkCentre 5745 model identifier
                 (not a complete product identifier)."
    ::= { xcmPidWCMF5 31 }
            -- => SAP PID string = "D5O"
--
--     -mf "Xerox" -mo "WorkCentre 5745"
xcmPidWorkCentre5745C1 OBJECT-IDENTITY
    STATUS      current
    DESCRIPTION
        "Xerox WorkCentre 5745 model and configuration 1 identifier
           (not a complete product identifier)."
    ::= { xcmPidWorkCentre5745 1 }
xcmPidWorkCentre5745C1V1 OBJECT-IDENTITY
    STATUS      current
    DESCRIPTION
        "Xerox WorkCentre 5745 launch model, configuration 1, 
           version 1.  A complete product identifier."
    ::= { xcmPidWorkCentre5745C1 1 }
xcmPidWorkCentre5755 OBJECT-IDENTITY
    STATUS      current
    DESCRIPTION
        "Xerox WorkCentre 5755 model identifier
                 (not a complete product identifier)."
    ::= { xcmPidWCMF5 32 }
            -- => SAP PID string = "D5P"
--
--     -mf "Xerox" -mo "WorkCentre 5755"
xcmPidWorkCentre5755C1 OBJECT-IDENTITY
    STATUS      current
    DESCRIPTION
        "Xerox WorkCentre 5755 model and configuration 1 identifier
           (not a complete product identifier)."
    ::= { xcmPidWorkCentre5755 1 }
xcmPidWorkCentre5755C1V1 OBJECT-IDENTITY
    STATUS      current
    DESCRIPTION
        "Xerox WorkCentre 5755 launch model, configuration 1, 
           version 1.  A complete product identifier."
    ::= { xcmPidWorkCentre5755C1 1 }
xcmPidWorkCentre5765 OBJECT-IDENTITY
    STATUS      current
    DESCRIPTION
        "Xerox WorkCentre 5765 model identifier
                 (not a complete product identifier)."
    ::= { xcmPidWCMF5 33 }
            -- => SAP PID string = "D5Q"
--
--     -mf "Xerox" -mo "WorkCentre 5765"
xcmPidWorkCentre5765C1 OBJECT-IDENTITY
    STATUS      current
    DESCRIPTION
        "Xerox WorkCentre 5765 model and configuration 1 identifier
           (not a complete product identifier)."
    ::= { xcmPidWorkCentre5765 1 }
xcmPidWorkCentre5765C1V1 OBJECT-IDENTITY
    STATUS      current
    DESCRIPTION
        "Xerox WorkCentre 5765 launch model, configuration 1, 
           version 1.  A complete product identifier."
    ::= { xcmPidWorkCentre5765C1 1 }
xcmPidWorkCentre5775 OBJECT-IDENTITY
    STATUS      current
    DESCRIPTION
        "Xerox WorkCentre 5775 model identifier
                 (not a complete product identifier)."
    ::= { xcmPidWCMF5 34 }
            -- => SAP PID string = "D5R"
--
--     -mf "Xerox" -mo "WorkCentre 5775"
xcmPidWorkCentre5775C1 OBJECT-IDENTITY
    STATUS      current
    DESCRIPTION
        "Xerox WorkCentre 5775 model and configuration 1 identifier
           (not a complete product identifier)."
    ::= { xcmPidWorkCentre5775 1 }
xcmPidWorkCentre5775C1V1 OBJECT-IDENTITY
    STATUS      current
    DESCRIPTION
        "Xerox WorkCentre 5775 launch model, configuration 1, 
           version 1.  A complete product identifier."
    ::= { xcmPidWorkCentre5775C1 1 }
xcmPidWorkCentre5790 OBJECT-IDENTITY
    STATUS      current
    DESCRIPTION
        "Xerox WorkCentre 5790 model identifier
                 (not a complete product identifier)."
    ::= { xcmPidWCMF5 35 }
            -- => SAP PID string = "D5S"
--
--     -mf "Xerox" -mo "WorkCentre 5790"
xcmPidWorkCentre5790C1 OBJECT-IDENTITY
    STATUS      current
    DESCRIPTION
        "Xerox WorkCentre 5790 model and configuration 1 identifier
           (not a complete product identifier)."
    ::= { xcmPidWorkCentre5790 1 }
xcmPidWorkCentre5790C1V1 OBJECT-IDENTITY
    STATUS      current
    DESCRIPTION
        "Xerox WorkCentre 5790 launch model, configuration 1, 
           version 1.  A complete product identifier."
    ::= { xcmPidWorkCentre5790C1 1 }
--
--
----------------------------------------------------------------
----------------------------------------------------------------
xcmPidWCMF6 OBJECT-IDENTITY
    STATUS      current
    DESCRIPTION
        "Xerox WorkCentre System product line identifier
                 (not a complete product identifier)."
    ::= { xcmPidWorkCentreMFSystems 6 }
--
--
xcmPidWorkCentre3045B OBJECT-IDENTITY
    STATUS      current
    DESCRIPTION
        "Xerox WorkCentre 3045B model identifier
                 (not a complete product identifier)."
    ::= { xcmPidWCMF6 7 }
            -- => SAP PID string = "D67"
--
--     -mf "Xerox" -mo "WorkCentre 3045B"
xcmPidWorkCentre3045BC1 OBJECT-IDENTITY
    STATUS      current
    DESCRIPTION
        "Xerox WorkCentre 3045B model and configuration 1 identifier
           (not a complete product identifier)."
    ::= { xcmPidWorkCentre3045B 1 }
xcmPidWorkCentre3045BC1V1 OBJECT-IDENTITY
    STATUS      current
    DESCRIPTION
        "Xerox WorkCentre 3045B launch model, configuration 1, 
           version 1.  A complete product identifier."
    ::= { xcmPidWorkCentre3045BC1 1 }
--
--
xcmPidWorkCentre3045NI OBJECT-IDENTITY
    STATUS      current
    DESCRIPTION
        "Xerox WorkCentre 3045NI model identifier
                 (not a complete product identifier)."
    ::= { xcmPidWCMF6 9 }
            -- => SAP PID string = "D69"
--
--     -mf "Xerox" -mo "WorkCentre 3045NI"
xcmPidWorkCentre3045NIC1 OBJECT-IDENTITY
    STATUS      current
    DESCRIPTION
        "Xerox WorkCentre 3045NI model and configuration 1 identifier
           (not a complete product identifier)."
    ::= { xcmPidWorkCentre3045NI 1 }
xcmPidWorkCentre3045NIC1V1 OBJECT-IDENTITY
    STATUS      current
    DESCRIPTION
        "Xerox WorkCentre 3045NI launch model, configuration 1, 
           version 1.  A complete product identifier."
    ::= { xcmPidWorkCentre3045NIC1 1 }
--
--
xcmPidWorkCentre6605 OBJECT-IDENTITY
    STATUS      current
    DESCRIPTION
        "Xerox WorkCentre 6605 model identifier
           (not a complete product identifier)."
    ::= { xcmPidWCMF6 34 }
            -- => SAP PID string = "D6R"
--
--     -mf "Xerox" -mo "WorkCentre 6605"
xcmPidWorkCentre6605NC1 OBJECT-IDENTITY
    STATUS      current
    DESCRIPTION
        "Xerox WorkCentre 6605
           model and configuration 1 identifier
           (not a complete product identifier)."
    ::= { xcmPidWorkCentre6605 1 }
--
--     -mf "Xerox" -mo "WorkCentre 6605N"
xcmPidWorkCentre6605NC1V1 OBJECT-IDENTITY
    STATUS      current
    DESCRIPTION
        "Xerox WorkCentre 6605
            launch model, configuration 1, version 1.
            A complete product identifier."
    ::= { xcmPidWorkCentre6605NC1 1 }
xcmPidWorkCentre6605DNC2 OBJECT-IDENTITY
    STATUS      current
    DESCRIPTION
        "Xerox WorkCentre 6605
           model and configuration 2 identifier
           (not a complete product identifier)."
    ::= { xcmPidWorkCentre6605 2 }
--
--     -mf "Xerox" -mo "WorkCentre 6605DN"
xcmPidWorkCentre6605DNC2V1 OBJECT-IDENTITY
    STATUS      current
    DESCRIPTION
        "Xerox WorkCentre 6605
            launch model, configuration 2, version 1.
            A complete product identifier."
    ::= { xcmPidWorkCentre6605DNC2 1 }
--
--
----------------------------------------------------------------
----------------------------------------------------------------
xcmPidWCMF7 OBJECT-IDENTITY
    STATUS      current
    DESCRIPTION
        "Xerox WorkCentre System product line identifier
                 (not a complete product identifier)."
    ::= { xcmPidWorkCentreMFSystems 7 }
--
--
--
--
--
--
--
--
--
--
----------------------------------------------------------------
----------------------------------------------------------------
xcmPidDesktopDocuPrintPrinters OBJECT-IDENTITY
    STATUS      current
    DESCRIPTION
        "Desktop DocuPrint Printers product line identifier
                 (not a complete product identifier)."
    ::= { xcmPidProductIdentifiers 2 }
--
--
xcmPid4517 OBJECT-IDENTITY
    STATUS      current
    DESCRIPTION
        "Desktop DocuPrint 4517 product type identifier
                 (not a complete product identifier)."
    ::= { xcmPidDesktopDocuPrintPrinters 2 }
xcmPid4517PlusM1 OBJECT-IDENTITY
    STATUS      current
    DESCRIPTION
        "Desktop DocuPrint 4517+ launch configuration model identifier
                 (not a complete product identifier)."
    ::= { xcmPid4517 1 }
            -- => SAP PID string = "221"
xcmPid4517PlusM1V1 OBJECT-IDENTITY
    STATUS      current
    DESCRIPTION
        "Desktop DocuPrint 4517+ launch configuration model and version,
                 and complete product identifier."
    ::= { xcmPid4517PlusM1 1 }
xcmPidDocuPrintN17 OBJECT-IDENTITY
    STATUS      current
    DESCRIPTION
        "Desktop DocuPrint N17 launch configuration model
                 identifier (not a complete product identifier)."
    ::= { xcmPid4517 2 }
            -- => SAP PID string = "222"
xcmPidDocuPrintN17V1 OBJECT-IDENTITY
    STATUS      current
    DESCRIPTION
        "Desktop DocuPrint N17 launch configuration model and
                 version, and complete product identifier."
    ::= { xcmPidDocuPrintN17 1 }
--
--
xcmPidDocuPrintC55 OBJECT-IDENTITY
    STATUS      current
    DESCRIPTION
        "Desktop DocuPrint C55 product type identifier
                 (not a complete product identifier)."
    ::= { xcmPidDesktopDocuPrintPrinters 3 }
xcmPidDocuPrintC55M1 OBJECT-IDENTITY
    STATUS      current
    DESCRIPTION
        "Desktop DocuPrint C55 launch configuration model identifier
                 (not a complete product identifier)."
    ::= { xcmPidDocuPrintC55 1 }
            -- => SAP PID string = "231"
xcmPidDocuPrintC55M1V1 OBJECT-IDENTITY
    STATUS      current
    DESCRIPTION
        "Desktop DocuPrint C55 launch configuration model and version,
                 and complete product identifier."
    ::= { xcmPidDocuPrintC55M1 1 }
xcmPidDocuPrintC55M1V2 OBJECT-IDENTITY
    STATUS      current
    DESCRIPTION
        "Desktop DocuPrint C55 launch configuration model 
                 post-launch configuration version,
                 and complete product identifier."
    ::= { xcmPidDocuPrintC55M1 2 }
xcmPidDocuPrintNC60 OBJECT-IDENTITY
    STATUS      current
    DESCRIPTION
        "Desktop DocuPrint NC60 launch configuration model identifier
                 (not a complete product identifier)."
    ::= { xcmPidDocuPrintC55 2 }
            -- => SAP PID string = "232"
xcmPidDocuPrintNC60V1 OBJECT-IDENTITY
    STATUS      current
    DESCRIPTION
        "Desktop DocuPrint NC60 launch configuration model and version,
                 and complete product identifier."
    ::= { xcmPidDocuPrintNC60 1 }
--
--
xcmPidP1210 OBJECT-IDENTITY
    STATUS      current
    DESCRIPTION
        "Desktop DocuPrint P1210 product type identifier
                 (not a complete product identifier)."
    ::= { xcmPidDesktopDocuPrintPrinters 4 }
xcmPidP1210M1 OBJECT-IDENTITY
    STATUS      current
    DESCRIPTION
        "Desktop DocuPrint P1210 launch configuration model identifier
                 (not a complete product identifier)."
    ::= { xcmPidP1210 1 }
            -- => SAP PID string = "241"
xcmPidP1210M1V1 OBJECT-IDENTITY
    STATUS      current
    DESCRIPTION
        "Desktop DocuPrint P1210 launch configuration model and version,
                 and complete product identifier."
    ::= { xcmPidP1210M1 1 }
xcmPidP3400 OBJECT-IDENTITY
    STATUS      current
    DESCRIPTION
        "Xerox Phaser 3400 product type identifier
                 (not a complete product identifier)."
    ::= { xcmPidDesktopDocuPrintPrinters 5 }
xcmPidP3400M1 OBJECT-IDENTITY
    STATUS      current
    DESCRIPTION
        "Xerox Phaser 3400 launch configuration model identifier
                 (not a complete product identifier)."
    ::= { xcmPidP3400 1 }
            -- => SAP PID string = "251"
xcmPidP3400M1V1 OBJECT-IDENTITY
    STATUS      current
    DESCRIPTION
        "Xerox Phaser 3400 launch configuration model and version,
                 and complete product identifier."
    ::= { xcmPidP3400M1 1 }
----------------------------------------------------------------
----------------------------------------------------------------
xcmPidWorkGroupDocuPrintPrinters OBJECT-IDENTITY
    STATUS      current
    DESCRIPTION
        "WorkGroup & MidRange DocuPrint Printers product line identifier
                 (not a complete product identifier)."
    ::= { xcmPidProductIdentifiers 3 }
--
--
xcmPidDocuPrintNnn OBJECT-IDENTITY
    STATUS      current
    DESCRIPTION
        "WorkGroup DocuPrint Nnn product type identifier
                 (not a complete product identifier)."
    ::= { xcmPidWorkGroupDocuPrintPrinters 2 }
xcmPidDocuPrintN32 OBJECT-IDENTITY
    STATUS      current
    DESCRIPTION
        "WorkGroup DocuPrint N32 model identifier
                 (not a complete product identifier)."
    ::= { xcmPidDocuPrintNnn 1 }
            -- => SAP PID string = "321"
xcmPidDocuPrintN32V1 OBJECT-IDENTITY
    STATUS      current
    DESCRIPTION
        "WorkGroup DocuPrint N32 launch configuration version,
                 and complete product identifier."
    ::= { xcmPidDocuPrintN32 1 }
xcmPidDocuPrintN32V2 OBJECT-IDENTITY
    STATUS      current
    DESCRIPTION
        "WorkGroup DocuPrint N32 post-launch configuration version,
                 and complete product identifier."
    ::= { xcmPidDocuPrintN32 2 }
xcmPidDocuPrintN24 OBJECT-IDENTITY
    STATUS      current
    DESCRIPTION
        "WorkGroup DocuPrint N24 model identifier
                 (not a complete product identifier)."
    ::= { xcmPidDocuPrintNnn 2 }
            -- => SAP PID string = "322"
xcmPidDocuPrintN24V1 OBJECT-IDENTITY
    STATUS      current
    DESCRIPTION
        "WorkGroup DocuPrint N24 launch configuration version,
                 and complete product identifier."
    ::= { xcmPidDocuPrintN24 1 }
xcmPidDocuPrintN24V2 OBJECT-IDENTITY
    STATUS      current
    DESCRIPTION
        "WorkGroup DocuPrint N24 post-launch configuration version,
                 and complete product identifier."
    ::= { xcmPidDocuPrintN24 2 }
xcmPidDocuPrintN40 OBJECT-IDENTITY
    STATUS      current
    DESCRIPTION
        "WorkGroup DocuPrint N40 model identifier
                 (not a complete product identifier)."
    ::= { xcmPidDocuPrintNnn 3 }
            -- => SAP PID string = "323"
xcmPidDocuPrintN40V1 OBJECT-IDENTITY
    STATUS      current
    DESCRIPTION
        "WorkGroup DocuPrint N40 launch configuration version,
                 and complete product identifier."
    ::= { xcmPidDocuPrintN40 1 }
--   DP N24: {1.3.6.1.4.1.279.253.62.1.3.2.5.1}, "325"
--   DP N32: {1.3.6.1.4.1.279.253.62.1.3.2.4.1}, "324"
--   DP N40: {1.3.6.1.4.1.279.253.62.1.3.2.6.1}, "326"
xcmPidDocuPrintN2025 OBJECT-IDENTITY
    STATUS      current
    DESCRIPTION
        "WorkGroup DocuPrint N2025 model identifier
                 (not a complete product identifier)."
    ::= { xcmPidDocuPrintNnn 17 }
            -- => SAP PID string = "32A"
xcmPidDocuPrintN2025V1 OBJECT-IDENTITY
    STATUS      current
    DESCRIPTION
        "WorkGroup DocuPrint N2025 launch configuration version,
                 and complete product identifier."
    ::= { xcmPidDocuPrintN2025 1 }
xcmPidDocuPrintN2025V2 OBJECT-IDENTITY
    STATUS      current
    DESCRIPTION
        "WorkGroup DocuPrint N2025 first post-launch
                 configuration version, and complete
                 product identifier."
    ::= { xcmPidDocuPrintN2025 2 }
xcmPidDocuPrintN2125 OBJECT-IDENTITY
    STATUS      current
    DESCRIPTION
        "WorkGroup DocuPrint N2125 model identifier
                 (not a complete product identifier)."
    ::= { xcmPidDocuPrintNnn 18 }
            -- => SAP PID string = "32B"
xcmPidDocuPrintN2125V1 OBJECT-IDENTITY
    STATUS      current
    DESCRIPTION
        "WorkGroup DocuPrint N2125 launch configuration version,
                 and complete product identifier."
    ::= { xcmPidDocuPrintN2125 1 }
--
--
xcmPidDocuPrintN2425 OBJECT-IDENTITY
    STATUS      current
    DESCRIPTION
        "WorkGroup DocuPrint N2425 model identifier
                 (not a complete product identifier)."
    ::= { xcmPidDocuPrintNnn 19 }
            -- => SAP PID string = "32C"
xcmPidDocuPrintN2425V1 OBJECT-IDENTITY
    STATUS      current
    DESCRIPTION
        "WorkGroup DocuPrint N2425 launch configuration version,
                 and complete product identifier."
    ::= { xcmPidDocuPrintN2425 1 }
xcmPidDocuPrintN2825 OBJECT-IDENTITY
    STATUS      current
    DESCRIPTION
        "WorkGroup DocuPrint N2825 model identifier
                 (not a complete product identifier)."
    ::= { xcmPidDocuPrintNnn 20 }
            -- => SAP PID string = "32D"
xcmPidDocuPrintN2825V1 OBJECT-IDENTITY
    STATUS      current
    DESCRIPTION
        "WorkGroup DocuPrint N2825 launch configuration version,
                 and complete product identifier."
    ::= { xcmPidDocuPrintN2825 1 }
--
--
xcmPidDocuPrintN3225 OBJECT-IDENTITY
    STATUS      current
    DESCRIPTION
        "WorkGroup DocuPrint N3225 model identifier
                 (not a complete product identifier)."
    ::= { xcmPidDocuPrintNnn 21 }
            -- => SAP PID string = "32E"
xcmPidDocuPrintN3225V1 OBJECT-IDENTITY
    STATUS      current
    DESCRIPTION
        "WorkGroup DocuPrint N3225 launch configuration version,
                 and complete product identifier."
    ::= { xcmPidDocuPrintN3225 1 }
--
--
xcmPidDocuPrintN4025 OBJECT-IDENTITY
    STATUS      current
    DESCRIPTION
        "WorkGroup DocuPrint N4025 model identifier
                 (not a complete product identifier)."
    ::= { xcmPidDocuPrintNnn 22 }
            -- => SAP PID string = "32F"
xcmPidDocuPrintN4025V1 OBJECT-IDENTITY
    STATUS      current
    DESCRIPTION
        "WorkGroup DocuPrint N4025 launch configuration version,
                 and complete product identifier."
    ::= { xcmPidDocuPrintN4025 1 }
xcmPidDocuPrintN4025V2 OBJECT-IDENTITY
    STATUS      current
    DESCRIPTION
        "WorkGroup DocuPrint N4025 first post-launch
                 configuration version, and complete
                 product identifier."
    ::= { xcmPidDocuPrintN4025 2 }
xcmPidDocuPrintAyame35 OBJECT-IDENTITY
    STATUS      current           
    DESCRIPTION
        "WorkGroup DocuPrint Ayame35 model identifier
                 (not a complete product identifier)."
    ::= { xcmPidDocuPrintNnn 35 }
            -- => SAP PID string = "32S"
xcmPidDocuPrintAyame35V1 OBJECT-IDENTITY
    STATUS      current           
    DESCRIPTION
        "WorkGroup DocuPrint Ayame35 launch configuration version,
                 and complete product identifier."
    ::= { xcmPidDocuPrintAyame35 1 }
xcmPidDocuPrintN4525 OBJECT-IDENTITY
    STATUS      current
    DESCRIPTION
        "WorkGroup DocuPrint N4525 model identifier
                 (not a complete product identifier)."
    ::= { xcmPidDocuPrintNnn 36 }
            -- => SAP PID string = "32T"
xcmPidDocuPrintN4525V1 OBJECT-IDENTITY
    STATUS      current
    DESCRIPTION
        "WorkGroup DocuPrint N4525 launch configuration version,
                 and complete product identifier."
    ::= { xcmPidDocuPrintN4525 1 }
xcmPidPhaser5400 OBJECT-IDENTITY
    STATUS      current
    DESCRIPTION
        "WorkGroup Phaser 5400 model identifier
                 (not a complete product identifier)."
    ::= { xcmPidDocuPrintNnn 37 }
            -- => SAP PID string = "32U"
xcmPidPhaser5400V1 OBJECT-IDENTITY
    STATUS      current
    DESCRIPTION
        "WorkGroup Phaser 5400 launch configuration version,
                 and complete product identifier."
    ::= { xcmPidPhaser5400 1 }
--
--
xcmPidDocuPrintNCnn OBJECT-IDENTITY
    STATUS      current
    DESCRIPTION
        "WorkGroup DocuPrint NCnn Color Laser Printers product type
                 identifier (not a complete product identifier)."
    ::= { xcmPidWorkGroupDocuPrintPrinters 3 }
xcmPidDocuPrintNC70 OBJECT-IDENTITY
    STATUS      current
    DESCRIPTION
        "WorkGroup DocuPrint NC70 Color Laser Printer
                 model identifier (not a complete product identifier)."
    ::= { xcmPidDocuPrintNCnn 1 }
            -- => SAP PID string = "331"
xcmPidDocuPrintNC70V1 OBJECT-IDENTITY
    STATUS      current
    DESCRIPTION
        "WorkGroup DocuPrint NC70 Color Laser Printer
                 launch configuration version,
                 and complete product identifier."
    ::= { xcmPidDocuPrintNC70 1 }
xcmPidDocuPrintNC80 OBJECT-IDENTITY
    STATUS      current
    DESCRIPTION
        "WorkGroup DocuPrint NC80 Color Laser Printer
                 model identifier (not a complete product identifier)."
    ::= { xcmPidDocuPrintNCnn 2 }
            -- => SAP PID string = "332"
xcmPidDocuPrintNC80V1 OBJECT-IDENTITY
    STATUS      current
    DESCRIPTION
        "WorkGroup DocuPrint NC80 Color Laser Printer
                 launch configuration version,
                 and complete product identifier."
    ::= { xcmPidDocuPrintNC80 1 }
--
--
xcmPidXeroxPhaserPrinters OBJECT-IDENTITY
    STATUS      current
    DESCRIPTION
        "Xerox Phaser Printers product line identifier
                 (not a complete product identifier)."
    ::= { xcmPidProductIdentifiers 19 }
xcmPidPhaser3yyyFamily OBJECT-IDENTITY
    STATUS      current
    DESCRIPTION
        "Xerox Phaser 3yyy Family product line identifier
         (not a complete product identifier)."
    ::= { xcmPidXeroxPhaserPrinters 1 }
xcmPidPhaser3450 OBJECT-IDENTITY
    STATUS      current
    DESCRIPTION
      "Xerox Phaser 3450 Laser Printer model identifier
       (not a complete product identifier)."
    ::= { xcmPidPhaser3yyyFamily 1 }
            -- => SAP PID string = "C11"
xcmPidPhaser3450D OBJECT-IDENTITY
    STATUS      current
    DESCRIPTION
        "Xerox Phaser 3450D Laser Printer launch configuration model,
                  version, and complete product identifier."
    ::= { xcmPidPhaser3450 2 }
xcmPidPhaser3450DN OBJECT-IDENTITY
    STATUS      current
    DESCRIPTION
        "Xerox Phaser 3450DN Laser Printer launch configuration model,
                  version, and complete product identifier."
    ::= { xcmPidPhaser3450 3 }
xcmPidPhaser3450B OBJECT-IDENTITY
    STATUS      current
    DESCRIPTION
        "Xerox Phaser 3450B Laser Printer launch configuration model,
                  version, and complete product identifier."
    ::= { xcmPidPhaser3450 4 }
xcmPidPhaser3500 OBJECT-IDENTITY
    STATUS      current
    DESCRIPTION
        "Xerox Phaser 3500 Laser Printer model identifier
                 (not a complete product identifier)."
    ::= { xcmPidPhaser3yyyFamily 2 }
            -- => SAP PID string = "C12"
xcmPidPhaser3500b OBJECT-IDENTITY
    STATUS      current
    DESCRIPTION
        "Xerox Phaser 3500b (Base) Laser Printer launch 
   configuration model, version, and complete product identifier."
    ::= { xcmPidPhaser3500 1 }
xcmPidPhaser3500n OBJECT-IDENTITY
    STATUS      current
    DESCRIPTION
        "Xerox Phaser 3500n (Base+Network Card) Laser Printer launch 
   configuration model, version, and complete product identifier."
    ::= { xcmPidPhaser3500 2 }
xcmPidPhaser3150 OBJECT-IDENTITY
    STATUS      current
    DESCRIPTION
        "Xerox Phaser 3150 Laser Printer model identifier
                 (not a complete product identifier)."
    ::= { xcmPidPhaser3yyyFamily 3 }
            -- => SAP PID string = "C13"
xcmPidPhaser3150b OBJECT-IDENTITY
    STATUS      current
    DESCRIPTION
        "Xerox Phaser 3150b (Base) Laser Printer launch 
   configuration model, version, and complete product identifier."
    ::= { xcmPidPhaser3150 1 }
xcmPidPhaser3150n OBJECT-IDENTITY
    STATUS      current
    DESCRIPTION
        "Xerox Phaser 3150n (Base+Network Card) Laser Printer launch 
   configuration model, version, and complete product identifier."
    ::= { xcmPidPhaser3150 2 }
xcmPidPhaser3428 OBJECT-IDENTITY
    STATUS      current
    DESCRIPTION
        "Xerox Phaser 3428 Laser Printer model identifier
                 (not a complete product identifier)."
    ::= { xcmPidPhaser3yyyFamily 4 }
            -- => SAP PID string = "C14"
xcmPidPhaser3428v1 OBJECT-IDENTITY
    STATUS      current
    DESCRIPTION
        "Xerox Phaser 3428 Laser Printer launch configuration model,
                  version 1, and complete product identifier."
    ::= { xcmPidPhaser3428 1 }
xcmPidPhaser3124 OBJECT-IDENTITY
    STATUS      current
    DESCRIPTION
        "Xerox Phaser 3124 Laser Printer model identifier
                 (not a complete product identifier)."
    ::= { xcmPidPhaser3yyyFamily 5 }
            -- => SAP PID string = "C15"
xcmPidPhaser3124v1 OBJECT-IDENTITY
    STATUS      current
    DESCRIPTION
        "Xerox Phaser 3124 Laser Printer launch configuration model,
                  version 1, and complete product identifier."
    ::= { xcmPidPhaser3124 1 }
xcmPidPhaser3125 OBJECT-IDENTITY
    STATUS      current
    DESCRIPTION
        "Xerox Phaser 3125 Laser Printer model identifier
                 (not a complete product identifier)."
    ::= { xcmPidPhaser3yyyFamily 6 }
            -- => SAP PID string = "C16"
xcmPidPhaser3125v1 OBJECT-IDENTITY
    STATUS      current
    DESCRIPTION
        "Xerox Phaser 3125 Laser Printer launch configuration model,
                  version 1, and complete product identifier."
    ::= { xcmPidPhaser3125 1 }
xcmPidPhaser3250 OBJECT-IDENTITY
    STATUS      current
    DESCRIPTION
        "Xerox Phaser 3250 Laser Printer model identifier
                 (not a complete product identifier)."
    ::= { xcmPidPhaser3yyyFamily 8 }
            -- => SAP PID string = "C18"
xcmPidPhaser3250v1 OBJECT-IDENTITY
    STATUS      current
    DESCRIPTION
        "Xerox Phaser 3250 Printer launch configuration model,
                version 1, and complete product identifier."
    ::= { xcmPidPhaser3250 1 }
xcmPidPhaser3600 OBJECT-IDENTITY
    STATUS      current
    DESCRIPTION
        "Xerox Phaser 3600 model identifier
                 (not a complete product identifier)."
    ::= { xcmPidPhaser3yyyFamily 9 }
            -- => SAP PID string = "C19"
xcmPidPhaser3600v1 OBJECT-IDENTITY
    STATUS      current
    DESCRIPTION
        "Xerox Phaser 3600 launch configuration model,
                version 1, and complete product identifier."
    ::= { xcmPidPhaser3600 1 }
xcmPidPhaser3100MFP OBJECT-IDENTITY
    STATUS      current
    DESCRIPTION
        "Xerox Phaser 3100 4-in-1  model identifier
                 (not a complete product identifier)."
    ::= { xcmPidPhaser3yyyFamily 17 }
            -- => SAP PID string = "C1A"
xcmPidPhaser3100MFPv1 OBJECT-IDENTITY
    STATUS      current
    DESCRIPTION
        "Xerox Phaser 3100MFP launch configuration model,
                version 1, and complete product identifier."
    ::= { xcmPidPhaser3100MFP 1 }
xcmPidPhaser3100 OBJECT-IDENTITY
    STATUS      current
    DESCRIPTION
        "Xerox Phaser 3100 3-in-1 model identifier
                 (not a complete product identifier)."
    ::= { xcmPidPhaser3yyyFamily 18 }
            -- => SAP PID string = "C1B"
xcmPidPhaser3100v1 OBJECT-IDENTITY
    STATUS      current
    DESCRIPTION
        "Xerox Phaser 3100 launch configuration model,
                version 1, and complete product identifier."
    ::= { xcmPidPhaser3100 1 }
xcmPidPhaser3435 OBJECT-IDENTITY
    STATUS      current
    DESCRIPTION
        "Xerox Phaser 3435 35ppm A4 model identifier
                 (not a complete product identifier)."
    ::= { xcmPidPhaser3yyyFamily 19 }
            -- => SAP PID string = "C1C"
xcmPidPhaser3435v1 OBJECT-IDENTITY
    STATUS      current
    DESCRIPTION
        "Xerox Phaser 3435 launch configuration model,
                version 1, and complete product identifier."
    ::= { xcmPidPhaser3435 1 }
xcmPidPhaser3300MFP OBJECT-IDENTITY
    STATUS      current
    DESCRIPTION
        "Xerox Phaser 3300MFP model identifier
           (not a complete product identifier)."
    ::= { xcmPidPhaser3yyyFamily 20 }
            -- => SAP PID string = "C1D"
xcmPidPhaser3300MFPc1 OBJECT-IDENTITY
    STATUS      current
    DESCRIPTION
        "Xerox Phaser 3300MFP 
           model and configuration identifier
           (not a complete product identifier)."
    ::= { xcmPidPhaser3300MFP 1 }
xcmPidPhaser3300MFPc1v1 OBJECT-IDENTITY
    STATUS      current
    DESCRIPTION
        "Xerox Phaser 3300MFP 
            launch model, configuration, version 1. 
            A complete product identifier."
    ::= { xcmPidPhaser3300MFPc1 1 }
--
--
xcmPidPhaser3010 OBJECT-IDENTITY
    STATUS      current
    DESCRIPTION
        "Xerox Phaser 3010 model identifier
                 (not a complete product identifier)."
    ::= { xcmPidPhaser3yyyFamily 26 }
            -- => SAP PID string = "C1J"
--
--     -mf "Xerox" -mo "Phaser 3010"
xcmPidPhaser3010C1 OBJECT-IDENTITY
    STATUS      current
    DESCRIPTION
        "Xerox Phaser 3010 model and configuration 1 identifier
           (not a complete product identifier)."
    ::= { xcmPidPhaser3010 1 }
xcmPidPhaser3010C1V1 OBJECT-IDENTITY
    STATUS      current
    DESCRIPTION
        "Xerox Phaser 3010 launch model, configuration 1, 
           version 1.  A complete product identifier."
    ::= { xcmPidPhaser3010C1 1 }
--
--
xcmPidPhaser3040 OBJECT-IDENTITY
    STATUS      current
    DESCRIPTION
        "Xerox Phaser 3040 model identifier
                 (not a complete product identifier)."
    ::= { xcmPidPhaser3yyyFamily 28 }
            -- => SAP PID string = "C1L"
--
--     -mf "Xerox" -mo "Phaser 3040"
xcmPidPhaser3040C1 OBJECT-IDENTITY
    STATUS      current
    DESCRIPTION
        "Xerox Phaser 3040 model and configuration 1 identifier
           (not a complete product identifier)."
    ::= { xcmPidPhaser3040 1 }
xcmPidPhaser3040C1V1 OBJECT-IDENTITY
    STATUS      current
    DESCRIPTION
        "Xerox Phaser 3040 launch model, configuration 1, 
           version 1.  A complete product identifier."
    ::= { xcmPidPhaser3040C1 1 }
--
--
xcmPidPhaser4yyyFamily OBJECT-IDENTITY
    STATUS      current
    DESCRIPTION
        "Xerox Phaser 4yyy Family product line identifier
                 (not a complete product identifier)."
    ::= { xcmPidXeroxPhaserPrinters 2 }
xcmPidPhaser4400 OBJECT-IDENTITY
    STATUS      current
    DESCRIPTION
        "Xerox Phaser 4400 Laser Printer model identifier
                 (not a complete product identifier)."
    ::= { xcmPidPhaser4yyyFamily 1 }
            -- => SAP PID string = "C21"
xcmPidPhaser4400N OBJECT-IDENTITY
    STATUS      current
    DESCRIPTION
        "Xerox Phaser 4400N Laser Printer launch configuration model,
                  version, and complete product identifier."
    ::= { xcmPidPhaser4400 1 }
xcmPidPhaser4400DT OBJECT-IDENTITY
    STATUS      current
    DESCRIPTION
        "Xerox Phaser 4400DT Laser Printer launch configuration model,
                  version, and complete product identifier."
    ::= { xcmPidPhaser4400 2 }
xcmPidPhaser4400DX OBJECT-IDENTITY
    STATUS      current
    DESCRIPTION
        "Xerox Phaser 4400DX Laser Printer launch configuration model,
                  version, and complete product identifier."
    ::= { xcmPidPhaser4400 3 }
xcmPidPhaser4400B OBJECT-IDENTITY
    STATUS      current
    DESCRIPTION
        "Xerox Phaser 4400B Laser Printer launch configuration model,
                  version, and complete product identifier."
    ::= { xcmPidPhaser4400 4 }
xcmPidPhaser4500 OBJECT-IDENTITY
    STATUS      current
    DESCRIPTION
        "Xerox Phaser 4500 Laser Printer model identifier
                 (not a complete product identifier)."
    ::= { xcmPidPhaser4yyyFamily 2 }
            -- => SAP PID string = "C22"
xcmPidPhaser4500N OBJECT-IDENTITY
    STATUS      current
    DESCRIPTION
        "Xerox Phaser 4500N Laser Printer launch configuration model,
                  version, and complete product identifier."
    ::= { xcmPidPhaser4500 1 }
xcmPidPhaser4500DT OBJECT-IDENTITY
    STATUS      current
    DESCRIPTION
        "Xerox Phaser 4500DT Laser Printer launch configuration model,
                  version, and complete product identifier."
    ::= { xcmPidPhaser4500 2 }
xcmPidPhaser4500DX OBJECT-IDENTITY
    STATUS      current
    DESCRIPTION
        "Xerox Phaser 4500DX Laser Printer launch configuration model,
                  version, and complete product identifier."
    ::= { xcmPidPhaser4500 3 }
xcmPidPhaser4500B OBJECT-IDENTITY
    STATUS      current
    DESCRIPTION
        "Xerox Phaser 4500B Laser Printer launch configuration model,
                  version, and complete product identifier."
    ::= { xcmPidPhaser4500 4 }
xcmPidPhaser4510 OBJECT-IDENTITY
    STATUS      current
    DESCRIPTION
        "Xerox Phaser 4510 Laser Printer model identifier
                 (not a complete product identifier)."
    ::= { xcmPidPhaser4yyyFamily 3 }
            -- => SAP PID string = "C23"
xcmPidPhaser4510B OBJECT-IDENTITY
    STATUS      current
    DESCRIPTION
        "Xerox Phaser 4510B Laser Printer launch configuration model,
                  version, and complete product identifier."
    ::= { xcmPidPhaser4510 1 }
xcmPidPhaser4510N OBJECT-IDENTITY
    STATUS      current
    DESCRIPTION
        "Xerox Phaser 4510N Laser Printer launch configuration model,
                  version, and complete product identifier."
    ::= { xcmPidPhaser4510 2 }
xcmPidPhaser4510DT OBJECT-IDENTITY
    STATUS      current
    DESCRIPTION
        "Xerox Phaser 4510DT Laser Printer launch configuration model,
                  version, and complete product identifier."
    ::= { xcmPidPhaser4510 3 }
xcmPidPhaser4510DX OBJECT-IDENTITY
    STATUS      current
    DESCRIPTION
        "Xerox Phaser 4510DX Laser Printer launch configuration model,
                  version, and complete product identifier."
    ::= { xcmPidPhaser4510 4 }
--
--
xcmPidPhaser5yyyFamily OBJECT-IDENTITY
    STATUS      current
    DESCRIPTION
        "Xerox Phaser 5yyy Family product line identifier
                 (not a complete product identifier)."
    ::= { xcmPidXeroxPhaserPrinters 3 }
--
xcmPidPhaser5500 OBJECT-IDENTITY
    STATUS      current
    DESCRIPTION
        "Xerox Phaser 5500 Laser Printer model identifier
                 (not a complete product identifier)."
    ::= { xcmPidPhaser5yyyFamily 1 }
            -- => SAP PID string = "C31"
xcmPidPhaser5500B OBJECT-IDENTITY
    STATUS      current
    DESCRIPTION
        "Xerox Phaser 5500B Laser Printer launch configuration model,
                  version, and complete product identifier."
    ::= { xcmPidPhaser5500 1 }
xcmPidPhaser5500N OBJECT-IDENTITY
    STATUS      current
    DESCRIPTION
        "Xerox Phaser 5500N Laser Printer launch configuration model,
                  version, and complete product identifier."
    ::= { xcmPidPhaser5500 2 }
xcmPidPhaser5500DN OBJECT-IDENTITY
    STATUS      current
    DESCRIPTION
        "Xerox Phaser 5500DN Laser Printer launch configuration model,
                  version, and complete product identifier."
    ::= { xcmPidPhaser5500 3 }
xcmPidPhaser5500DT OBJECT-IDENTITY
    STATUS      current
    DESCRIPTION
        "Xerox Phaser 5500DT Laser Printer launch configuration model,
                  version, and complete product identifier."
    ::= { xcmPidPhaser5500 4 }
xcmPidPhaser5500DX OBJECT-IDENTITY
    STATUS      current
    DESCRIPTION
        "Xerox Phaser 5500DX Laser Printer launch configuration model,
                  version, and complete product identifier."
    ::= { xcmPidPhaser5500 5 }
xcmPidPhaser5550 OBJECT-IDENTITY
    STATUS      current
    DESCRIPTION
        "Xerox Phaser 5550 Laser Printer model identifier
                 (not a complete product identifier)."
    ::= { xcmPidPhaser5yyyFamily 2 }
            -- => SAP PID string = "C32"
xcmPidPhaser5550B OBJECT-IDENTITY
    STATUS      current
    DESCRIPTION
        "Xerox Phaser 5550B Laser Printer launch configuration model,
                  version, and complete product identifier."
    ::= { xcmPidPhaser5550 1 }
xcmPidPhaser5550N OBJECT-IDENTITY
    STATUS      current
    DESCRIPTION
        "Xerox Phaser 5550N Laser Printer launch configuration model,
                  version, and complete product identifier."
    ::= { xcmPidPhaser5550 2 }
xcmPidPhaser5550DN OBJECT-IDENTITY
    STATUS      current
    DESCRIPTION
        "Xerox Phaser 5550DN Laser Printer launch configuration model,
                  version, and complete product identifier."
    ::= { xcmPidPhaser5550 3 }
xcmPidPhaser5550DT OBJECT-IDENTITY
    STATUS      current
    DESCRIPTION
        "Xerox Phaser 5550DT Laser Printer launch configuration model,
                  version, and complete product identifier."
    ::= { xcmPidPhaser5550 4 }
xcmPidPhaser5335 OBJECT-IDENTITY
    STATUS      current
    DESCRIPTION
        "Xerox Phaser 5335 Laser Printer model identifier
                 (not a complete product identifier)."
    ::= { xcmPidPhaser5yyyFamily 3 }
            -- => SAP PID string = "C33"
xcmPidPhaser5335v1 OBJECT-IDENTITY
    STATUS      current
    DESCRIPTION
        "Xerox Phaser 5335 Laser Printer launch configuration model,
                  version, and complete product identifier."
    ::= { xcmPidPhaser5335 1 }
--
--
--
xcmPidPhaser6yyyFamily OBJECT-IDENTITY
    STATUS      current
    DESCRIPTION
        "Xerox Phaser 6yyy Family product line identifier
                 (not a complete product identifier)."
    ::= { xcmPidXeroxPhaserPrinters 4 }
--
xcmPidPhaser6100 OBJECT-IDENTITY
    STATUS      current
    DESCRIPTION
        "Xerox Phaser 6100 Laser Printer model identifier
                 (not a complete product identifier)."
    ::= { xcmPidPhaser6yyyFamily 2 }
            -- => SAP PID string = "C42"
xcmPidPhaser6100n OBJECT-IDENTITY
    STATUS      current
    DESCRIPTION
        "Xerox Phaser 6100n Laser Printer,
                  launch configuration model,
                  version, and complete product identifier."
    ::= { xcmPidPhaser6100 1 }
xcmPidPhaser6200 OBJECT-IDENTITY
    STATUS      current
    DESCRIPTION
        "Xerox Phaser 6200 Laser Printer model identifier
                 (not a complete product identifier)."
    ::= { xcmPidPhaser6yyyFamily 1 }
            -- => SAP PID string = "C41"
xcmPidPhaser6200B OBJECT-IDENTITY
    STATUS      current
    DESCRIPTION
        "Xerox Phaser 6200B Laser Printer launch configuration model,
                  version, and complete product identifier."
    ::= { xcmPidPhaser6200 1 }
xcmPidPhaser6200N OBJECT-IDENTITY
    STATUS      current
    DESCRIPTION
        "Xerox Phaser 6200N Laser Printer launch configuration model,
                  version, and complete product identifier."
    ::= { xcmPidPhaser6200 2 }
xcmPidPhaser6200DP OBJECT-IDENTITY
    STATUS      current
    DESCRIPTION
        "Xerox Phaser 6200DP Laser Printer launch configuration model,
                  version, and complete product identifier."
    ::= { xcmPidPhaser6200 3 }
xcmPidPhaser6200DX OBJECT-IDENTITY
    STATUS      current
    DESCRIPTION
        "Xerox Phaser 6200DX Laser Printer launch configuration model,
                  version, and complete product identifier."
    ::= { xcmPidPhaser6200 4 }
xcmPidPhaser6250 OBJECT-IDENTITY
    STATUS      current
    DESCRIPTION
        "Xerox Phaser 6250 Laser Printer model identifier
                 (not a complete product identifier)."
    ::= { xcmPidPhaser6yyyFamily 3 }
            -- => SAP PID string = "C43"
xcmPidPhaser6250B OBJECT-IDENTITY
    STATUS      current
    DESCRIPTION
        "Xerox Phaser 6250B Laser Printer,
                  the Base configuration (No Network, 128MB RAM)
                  launch configuration model,
                  version, and complete product identifier."
    ::= { xcmPidPhaser6250 1 }
xcmPidPhaser6250N OBJECT-IDENTITY
    STATUS      current
    DESCRIPTION
        "Xerox Phaser 6250N Laser Printer 
                  adds: Built-in 10/100 Ethernet, 256MB RAM, 
    Pipeline performance
                  launch configuration model,
                  version, and complete product identifier."
    ::= { xcmPidPhaser6250 2 }
xcmPidPhaser6250DP OBJECT-IDENTITY
    STATUS      current
    DESCRIPTION
        "Xerox Phaser 6250DP Laser Printer 
                  6250N + Auto Duplex, Photomode
                  launch configuration model,
                  version, and complete product identifier."
    ::= { xcmPidPhaser6250 3 }
xcmPidPhaser6250DT OBJECT-IDENTITY
    STATUS      current
    DESCRIPTION
        "Xerox Phaser 6250DT Laser Printer 
                  6250DP + Single Auxiliary Tray + 256 (512MB total)
                  launch configuration model,
                  version, and complete product identifier."
    ::= { xcmPidPhaser6250 5 }
xcmPidPhaser6250DX OBJECT-IDENTITY
    STATUS      current
    DESCRIPTION
        "Xerox Phaser 6250DX Laser Printer 
                  6250DT + Internal HD
                  launch configuration model,
                  version, and complete product identifier."
    ::= { xcmPidPhaser6250 4 }
--
xcmPidPhaser6300 OBJECT-IDENTITY
    STATUS      current
    DESCRIPTION
        "Xerox Phaser 6300 Laser Printer model identifier
                 (not a complete product identifier)."
    ::= { xcmPidPhaser6yyyFamily 4 }
            -- => SAP PID string = "C44"
xcmPidPhaser6300B OBJECT-IDENTITY
    STATUS      current
    DESCRIPTION
        "Xerox Phaser 6300B Laser Printer
                  launch configuration model,
                  version, and complete product identifier."
    ::= { xcmPidPhaser6300 1 }
xcmPidPhaser6300N OBJECT-IDENTITY
    STATUS      current
    DESCRIPTION
        "Xerox Phaser 6300N Laser Printer 
                  the Base configuration (Built-in 10/100 Ethernet, 128M
                  26ppm B&W/36ppm Color) launch configuration model,
                  version, and complete product identifier."
    ::= { xcmPidPhaser6300 2 }
xcmPidPhaser6300DN OBJECT-IDENTITY
    STATUS      current
    DESCRIPTION
        "Xerox Phaser 6300DN Laser Printer 
                  6300N + Auto Duplex
                  launch configuration model,
                  version, and complete product identifier."
    ::= { xcmPidPhaser6300 3 }
xcmPidPhaser6350 OBJECT-IDENTITY
    STATUS      current
    DESCRIPTION
        "Xerox Phaser 6350 Series Laser Printer model identifier
                 (not a complete product identifier)."
    ::= { xcmPidPhaser6yyyFamily 6 }
            -- => SAP PID string = "C46"
xcmPidPhaser6350DP OBJECT-IDENTITY
    STATUS      current
    DESCRIPTION
        "Xerox Phaser 6350DP Laser Printer 
                  6300DN + Photomode + 128MB (256MB total) + 36ppm B&W
                  launch configuration model,
                  version, and complete product identifier."
    ::= { xcmPidPhaser6350 1 }
xcmPidPhaser6350DT OBJECT-IDENTITY
    STATUS      current
    DESCRIPTION
        "Xerox Phaser 6350DT Laser Printer 
                  6350DP + Single Auxiliary Tray + 256MB (512MB total)
                  launch configuration model,
                  version, and complete product identifier."
    ::= { xcmPidPhaser6350 2 }
xcmPidPhaser6350DX OBJECT-IDENTITY
    STATUS      current
    DESCRIPTION
        "Xerox Phaser 6350DX Laser Printer 
                  6350DT + Internal HD
                  launch configuration model,
                  version, and complete product identifier."
    ::= { xcmPidPhaser6350 3 }
--
--
xcmPidPhaser6120 OBJECT-IDENTITY
    STATUS      current
    DESCRIPTION
        "Xerox Phaser 6120 Laser Printer model identifier
                 (not a complete product identifier)."
    ::= { xcmPidPhaser6yyyFamily 7 }
            -- => SAP PID string = "C47"
xcmPidPhaser6120b OBJECT-IDENTITY
    STATUS      current
    DESCRIPTION
        "Xerox Phaser 6120b (Base) Laser Printer launch 
   configuration model, version, and complete product identifier."
    ::= { xcmPidPhaser6120 1 }
xcmPidPhaser6120n OBJECT-IDENTITY
    STATUS      current
    DESCRIPTION
        "Xerox Phaser 6120n (Base+Network Card) Laser Printer launch 
   configuration model, version, and complete product identifier."
    ::= { xcmPidPhaser6120 2 }
--
xcmPidPhaser6360 OBJECT-IDENTITY
    STATUS      current
    DESCRIPTION
        "Xerox Phaser 6360 Color Laser Printer model identifier
                 (not a complete product identifier)."
    ::= { xcmPidPhaser6yyyFamily 8 }
            -- => SAP PID string = "C48"
xcmPidPhaser6360N OBJECT-IDENTITY
    STATUS      current
    DESCRIPTION
        "Xerox Phaser 6360N Color Laser Printer
                  launch configuration model,
                  version, and complete product identifier."
    ::= { xcmPidPhaser6360 1 }
xcmPidPhaser6360DN OBJECT-IDENTITY
    STATUS      current
    DESCRIPTION
        "Xerox Phaser 6360DN Color Laser Printer 
                  launch configuration model,
                  version, and complete product identifier."
    ::= { xcmPidPhaser6360 2 }
xcmPidPhaser6360DT OBJECT-IDENTITY
    STATUS      current
    DESCRIPTION
        "Xerox Phaser 6360DT Color Laser Printer 
                  launch configuration model,
                  version, and complete product identifier."
    ::= { xcmPidPhaser6360 3 }
xcmPidPhaser6360DX OBJECT-IDENTITY
    STATUS      current
    DESCRIPTION
        "Xerox Phaser 6360DX Color Laser Printer 
                  launch configuration model,
                  version, and complete product identifier."
    ::= { xcmPidPhaser6360 4 }
xcmPidPhaser6180 OBJECT-IDENTITY
    STATUS      current
    DESCRIPTION
        "Xerox Phaser 6180 Color Printer model identifier
                 (not a complete product identifier)."
    ::= { xcmPidPhaser6yyyFamily 9 }
            -- => SAP PID string = "C49"
xcmPidPhaser6180N OBJECT-IDENTITY
    STATUS      current
    DESCRIPTION
        "Xerox Phaser 6180N Color Printer
                  launch configuration model,
                  version, and complete product identifier."
    ::= { xcmPidPhaser6180 1 }
xcmPidPhaser6180DN OBJECT-IDENTITY
    STATUS      current
    DESCRIPTION
        "Xerox Phaser 6180DN Color Printer 
                  launch configuration model,
                  version, and complete product identifier."
    ::= { xcmPidPhaser6180 2 }
xcmPidPhaser6110N OBJECT-IDENTITY
    STATUS      current
    DESCRIPTION
        "Xerox Phaser 6110N Printer model identifier
                 (not a complete product identifier)."
    ::= { xcmPidPhaser6yyyFamily 17 }
            -- => SAP PID string = "C4A"
xcmPidPhaser6110Nv1 OBJECT-IDENTITY
    STATUS      current
    DESCRIPTION
        "Xerox Phaser 6110N Version 1 Printer
                  launch configuration model,
                  version, and complete product identifier."
    ::= { xcmPidPhaser6110N 1 }
xcmPidPhaser6115 OBJECT-IDENTITY
    STATUS      current
    DESCRIPTION
        "Xerox Phaser 6115 model identifier
                 (not a complete product identifier)."
    ::= { xcmPidPhaser6yyyFamily 18 }
            -- => SAP PID string = "C4B"
xcmPidPhaser6115N OBJECT-IDENTITY
    STATUS      current
    DESCRIPTION
        "Xerox Phaser 6115 Base launch configuration model,
                  version, and complete product identifier."
    ::= { xcmPidPhaser6115 1 }
xcmPidPhaser6115DN OBJECT-IDENTITY
    STATUS      current
    DESCRIPTION
        "Xerox Phaser 6115 Base + Duplex launch configuration 
            model, version, and complete product identifier."
    ::= { xcmPidPhaser6115 2 }
xcmPidPhaser6110MFP3 OBJECT-IDENTITY
    STATUS      current
    DESCRIPTION
        "Xerox Phaser 6110MFP3 Printer model identifier
                 (not a complete product identifier)."
    ::= { xcmPidPhaser6yyyFamily 19 }
            -- => SAP PID string = "C4C"
xcmPidPhaser6110MFP3v1 OBJECT-IDENTITY
    STATUS      current
    DESCRIPTION
        "Xerox Phaser 6110MFP3 Version 1 Printer
                  launch configuration model,
                  version, and complete product identifier."
    ::= { xcmPidPhaser6110MFP3 1 }
xcmPidPhaser6110MFP4 OBJECT-IDENTITY
    STATUS      current
    DESCRIPTION
        "Xerox Phaser 6110MFP4 Printer model identifier
                 (not a complete product identifier)."
    ::= { xcmPidPhaser6yyyFamily 20 }
            -- => SAP PID string = "C4D"
xcmPidPhaser6110MFP4v1 OBJECT-IDENTITY
    STATUS      current
    DESCRIPTION
        "Xerox Phaser 6110MFP4 Version 1 Printer
                  launch configuration model,
                  version, and complete product identifier."
    ::= { xcmPidPhaser6110MFP4 1 }
xcmPidPhaser6180MFP OBJECT-IDENTITY
    STATUS      current
    DESCRIPTION
        "Xerox Phaser 6180 Printer model identifier
                 (not a complete product identifier)."
    ::= { xcmPidPhaser6yyyFamily 21 }
            -- => SAP PID string = "C4E"
xcmPidPhaser6180MFPN OBJECT-IDENTITY
    STATUS      current
    DESCRIPTION
        "Xerox Phaser 6180 Printer (Network + 128MB RAM)
                  launch configuration model,
                  version, and complete product identifier."
    ::= { xcmPidPhaser6180MFP 1 }
xcmPidPhaser6180MFPDN OBJECT-IDENTITY
    STATUS      current
    DESCRIPTION
        "Xerox Phaser 6180 Printer (Network + 128MB RAM + Duplex)
                  launch configuration model,
                  version, and complete product identifier."
    ::= { xcmPidPhaser6180MFP 2 }
xcmPidPhaser6130 OBJECT-IDENTITY
    STATUS      current
    DESCRIPTION
        "Xerox Phaser 6130 model identifier
                 (not a complete product identifier)."
    ::= { xcmPidPhaser6yyyFamily 23 }
            -- => SAP PID string = "C4G"
xcmPidPhaser6130N OBJECT-IDENTITY
    STATUS      current
    DESCRIPTION
        "Xerox Phaser Color Printer 6130N
                  launch configuration model,
                  version, and complete product identifier."
    ::= { xcmPidPhaser6130 1 }
xcmPidPhaser6125 OBJECT-IDENTITY
    STATUS      current
    DESCRIPTION
        "Xerox Phaser 6125 model identifier
                 (not a complete product identifier)."
    ::= { xcmPidPhaser6yyyFamily 24 }
            -- => SAP PID string = "C4H"
xcmPidPhaser6125N OBJECT-IDENTITY
    STATUS      current
    DESCRIPTION
        "Xerox Phaser Color Printer 6125N
                  launch configuration model,
                  version, and complete product identifier."
    ::= { xcmPidPhaser6125 1 }
xcmPidPhaser6280 OBJECT-IDENTITY
    STATUS      current
    DESCRIPTION
        "Xerox Phaser 6280 Color Printer model identifier
                 (not a complete product identifier)."
    ::= { xcmPidPhaser6yyyFamily 25 }
            -- => SAP PID string = "C4I"
xcmPidPhaser6280N OBJECT-IDENTITY
    STATUS      current
    DESCRIPTION
        "Xerox Phaser 6280N Color Printer
           model and configuration identifier
           (not a complete product identifier)."
    ::= { xcmPidPhaser6280 1 }
xcmPidPhaser6280Nv1 OBJECT-IDENTITY
    STATUS      current
    DESCRIPTION
        "Xerox Phaser 6280N Color Printer 
            launch model, configuration, version 1. 
            A complete product identifier."
    ::= { xcmPidPhaser6280N 1 }
xcmPidPhaser6280DN OBJECT-IDENTITY
    STATUS      current
    DESCRIPTION
        "Xerox Phaser 6280DN Color Printer 
           model and configuration identifier
           (not a complete product identifier)."
    ::= { xcmPidPhaser6280 2 }
xcmPidPhaser6280DNv1 OBJECT-IDENTITY
    STATUS      current
    DESCRIPTION
        "Xerox Phaser 6280DN Color Printer 
            launch model, configuration, version 1. 
            A complete product identifier."
    ::= { xcmPidPhaser6280DN 1 }
xcmPidPhaser6280DT OBJECT-IDENTITY
    STATUS      current
    DESCRIPTION
        "Xerox Phaser 6280DT Color Printer 
           model and configuration identifier
           (not a complete product identifier)."
    ::= { xcmPidPhaser6280 3 }
xcmPidPhaser6280DTv1 OBJECT-IDENTITY
    STATUS      current
    DESCRIPTION
        "Xerox Phaser 6280DT Color Printer 
            launch model, configuration, version 1. 
            A complete product identifier."
    ::= { xcmPidPhaser6280DT 1 }
--
--
xcmPidPhaser6700 OBJECT-IDENTITY
    STATUS      current
    DESCRIPTION
        "Xerox Phaser 6700  model identifier
           (not a complete product identifier)."
    ::= { xcmPidPhaser6yyyFamily 30 }
            -- => SAP PID string = "C4N"
--
--     -mf "Xerox" -mo "Phaser 6700N"
--     -mf "Xerox" -mo "Phaser 6700DN"
--     -mf "Xerox" -mo "Phaser 6700DT"
--     -mf "Xerox" -mo "Phaser 6700DX"
-- Phaser 6700 Base Configuration 1 "N"
xcmPidPhaser6700C1 OBJECT-IDENTITY
    STATUS      current
    DESCRIPTION
        "Xerox Phaser 6700
           model and configuration 1 identifier
           (not a complete product identifier)."
    ::= { xcmPidPhaser6700 1 }
xcmPidPhaser6700C1V1 OBJECT-IDENTITY
    STATUS      current
    DESCRIPTION
        "Xerox Phaser 6700
            launch model, configuration 1, version 1.
            A complete product identifier."
    ::= { xcmPidPhaser6700C1 1 }
-- Phaser 6700 Configuration 2 "DN"
xcmPidPhaser6700C2 OBJECT-IDENTITY
    STATUS      current
    DESCRIPTION
        "Xerox Phaser 6700
           model and configuration 2 identifier
           (not a complete product identifier)."
    ::= { xcmPidPhaser6700 2 }
xcmPidPhaser6700C2V1 OBJECT-IDENTITY
    STATUS      current
    DESCRIPTION
        "Xerox Phaser 6700
            launch model, configuration 2, version 1.
            A complete product identifier."
    ::= { xcmPidPhaser6700C2 1 }
-- Phaser 6700 Configuration 3 "DT"
xcmPidPhaser6700C3 OBJECT-IDENTITY
    STATUS      current
    DESCRIPTION
        "Xerox Phaser 6700
           model and configuration 3 identifier
           (not a complete product identifier)."
    ::= { xcmPidPhaser6700 3 }
xcmPidPhaser6700C3V1 OBJECT-IDENTITY
    STATUS      current
    DESCRIPTION
        "Xerox Phaser 6700
            launch model, configuration 3, version 1.
            A complete product identifier."
    ::= { xcmPidPhaser6700C3 1 }
-- Phaser 6700 Configuration 4 "DX"
xcmPidPhaser6700C4 OBJECT-IDENTITY
    STATUS      current
    DESCRIPTION
        "Xerox Phaser 6700
           model and configuration 4 identifier
           (not a complete product identifier)."
    ::= { xcmPidPhaser6700 4 }
xcmPidPhaser6700C4V1 OBJECT-IDENTITY
    STATUS      current
    DESCRIPTION
        "Xerox Phaser 6700
            launch model, configuration 4, version 1.
            A complete product identifier."
    ::= { xcmPidPhaser6700C4 1 }
--
--
xcmPidWorkCentre6015B OBJECT-IDENTITY
    STATUS      current
    DESCRIPTION
        "Xerox WorkCentre 6015B  model identifier
           (not a complete product identifier)."
    ::= { xcmPidPhaser6yyyFamily 32 }
            -- => SAP PID string = "C4P"
--
--     -mf "Xerox" -mo "WorkCentre 6015B"
xcmPidWorkCentre6015BC1 OBJECT-IDENTITY
    STATUS      current
    DESCRIPTION
        "Xerox WorkCentre 6015B
           model and configuration 1 identifier
           (not a complete product identifier)."
    ::= { xcmPidWorkCentre6015B 1 }
xcmPidWorkCentre6015BC1V1 OBJECT-IDENTITY
    STATUS      current
    DESCRIPTION
        "Xerox WorkCentre 6015B
            launch model, configuration 1, version 1.
            A complete product identifier."
    ::= { xcmPidWorkCentre6015BC1 1 }
xcmPidPhaser6500 OBJECT-IDENTITY
    STATUS      current
    DESCRIPTION
        "Xerox Phaser 6500  model identifier
           (not a complete product identifier)."
    ::= { xcmPidPhaser6yyyFamily 33 }
            -- => SAP PID string = "C4Q"
--
--     -mf "Xerox" -mo "Phaser 6500"
-- Phaser 6500 Base Configuration 1 "N"
xcmPidPhaser6500C1 OBJECT-IDENTITY
    STATUS      current
    DESCRIPTION
        "Xerox Phaser 6500
           model and configuration 1 identifier
           (not a complete product identifier)."
    ::= { xcmPidPhaser6500 1 }
xcmPidPhaser6500C1V1 OBJECT-IDENTITY
    STATUS      current
    DESCRIPTION
        "Xerox Phaser 6500
            launch model, configuration 1, version 1.
            A complete product identifier."
    ::= { xcmPidPhaser6500C1 1 }
-- Phaser 6500 Configuration 2 "DN"
xcmPidPhaser6500C2 OBJECT-IDENTITY
    STATUS      current
    DESCRIPTION
        "Xerox Phaser 6500
           model and configuration 2 identifier
           (not a complete product identifier)."
    ::= { xcmPidPhaser6500 2 }
xcmPidPhaser6500C2V1 OBJECT-IDENTITY
    STATUS      current
    DESCRIPTION
        "Xerox Phaser 6500
            launch model, configuration 2, version 1.
            A complete product identifier."
    ::= { xcmPidPhaser6500C2 1 }
xcmPidWorkCentre6505 OBJECT-IDENTITY
    STATUS      current
    DESCRIPTION
        "Xerox WorkCentre 6505  model identifier
           (not a complete product identifier)."
    ::= { xcmPidPhaser6yyyFamily 34 }
            -- => SAP PID string = "C4R"
--
--     -mf "Xerox" -mo "WorkCentre 6505"
-- WorkCentre 6505 Base Configuration 1 "N"
xcmPidWorkCentre6505C1 OBJECT-IDENTITY
    STATUS      current
    DESCRIPTION
        "Xerox WorkCentre 6505
           model and configuration 1 identifier
           (not a complete product identifier)."
    ::= { xcmPidWorkCentre6505 1 }
xcmPidWorkCentre6505C1V1 OBJECT-IDENTITY
    STATUS      current
    DESCRIPTION
        "Xerox WorkCentre 6505
            launch model, configuration 1, version 1.
            A complete product identifier."
    ::= { xcmPidWorkCentre6505C1 1 }
-- WorkCentre 6505 Configuration 2 "D"
xcmPidWorkCentre6505C2 OBJECT-IDENTITY
    STATUS      current
    DESCRIPTION
        "Xerox WorkCentre 6505
           model and configuration 2 identifier
           (not a complete product identifier)."
    ::= { xcmPidWorkCentre6505 2 }
xcmPidWorkCentre6505C2V1 OBJECT-IDENTITY
    STATUS      current
    DESCRIPTION
        "Xerox WorkCentre 6505
            launch model, configuration 2, version 1.
            A complete product identifier."
    ::= { xcmPidWorkCentre6505C2 1 }
xcmPidPhaser6000 OBJECT-IDENTITY
    STATUS      current
    DESCRIPTION
        "Xerox Phaser 6000  model identifier
           (not a complete product identifier)."
    ::= { xcmPidPhaser6yyyFamily 35 }
            -- => SAP PID string = "C4S"
--
--     -mf "Xerox" -mo "Phaser 6000"
xcmPidPhaser6000C1 OBJECT-IDENTITY
    STATUS      current
    DESCRIPTION
        "Xerox Phaser 6000
           model and configuration 1 identifier
           (not a complete product identifier)."
    ::= { xcmPidPhaser6000 1 }
xcmPidPhaser6000C1V1 OBJECT-IDENTITY
    STATUS      current
    DESCRIPTION
        "Xerox Phaser 6000
            launch model, configuration 1, version 1.
            A complete product identifier."
    ::= { xcmPidPhaser6000C1 1 }
xcmPidWorkCentre6015 OBJECT-IDENTITY
    STATUS      current
    DESCRIPTION
        "Xerox WorkCentre 6015 model identifier
           (not a complete product identifier)."
    ::= { xcmPidPhaser6yyyFamily 36 }
            -- => SAP PID string = "C4T"
--
--     -mf "Xerox" -mo "WorkCentre 6015"
xcmPidWorkCentre6015C1 OBJECT-IDENTITY
    STATUS      current
    DESCRIPTION
        "Xerox WorkCentre 6015
           model and configuration 1 identifier
           (not a complete product identifier)."
    ::= { xcmPidWorkCentre6015 1 }
xcmPidWorkCentre6015C1V1 OBJECT-IDENTITY
    STATUS      current
    DESCRIPTION
        "Xerox WorkCentre 6015
            launch model, configuration 1, version 1.
            A complete product identifier."
    ::= { xcmPidWorkCentre6015C1 1 }
xcmPidWorkCentre6015C2 OBJECT-IDENTITY
    STATUS      current
    DESCRIPTION
        "Xerox WorkCentre 6015
           model and configuration 2 identifier
           (not a complete product identifier)."
    ::= { xcmPidWorkCentre6015 2 }
xcmPidWorkCentre6015C2V1 OBJECT-IDENTITY
    STATUS      current
    DESCRIPTION
        "Xerox WorkCentre 6015
            launch model, configuration 2, version 1.
            A complete product identifier."
    ::= { xcmPidWorkCentre6015C2 1 }
xcmPidPhaser6600 OBJECT-IDENTITY
    STATUS      current
    DESCRIPTION
        "Xerox Phaser 6600 model identifier
           (not a complete product identifier)."
    ::= { xcmPidPhaser6yyyFamily 37 }
            -- => SAP PID string = "C4U"
--
--     -mf "Xerox" -mo "Phaser 6600"
xcmPidPhaser6600NC1 OBJECT-IDENTITY
    STATUS      current
    DESCRIPTION
        "Xerox Phaser 6600
           model and configuration 1 identifier
           (not a complete product identifier)."
    ::= { xcmPidPhaser6600 1 }
--
--     -mf "Xerox" -mo "Phaser 6600N"
xcmPidPhaser6600NC1V1 OBJECT-IDENTITY
    STATUS      current
    DESCRIPTION
        "Xerox Phaser 6600
            launch model, configuration 1, version 1.
            A complete product identifier."
    ::= { xcmPidPhaser6600NC1 1 }
xcmPidPhaser6600DNC2 OBJECT-IDENTITY
    STATUS      current
    DESCRIPTION
        "Xerox Phaser 6600
           model and configuration 2 identifier
           (not a complete product identifier)."
    ::= { xcmPidPhaser6600 2 }
--
--     -mf "Xerox" -mo "Phaser 6600DN"
xcmPidPhaser6600DNC2V1 OBJECT-IDENTITY
    STATUS      current
    DESCRIPTION
        "Xerox Phaser 6600
            launch model, configuration 2, version 1.
            A complete product identifier."
    ::= { xcmPidPhaser6600DNC2 1 }
xcmPidPhaser7yyyFamily OBJECT-IDENTITY
    STATUS      current
    DESCRIPTION
        "Xerox Phaser 7yyy Family product line identifier
                 (not a complete product identifier)."
    ::= { xcmPidXeroxPhaserPrinters 5 }
xcmPidPhaser7300 OBJECT-IDENTITY
    STATUS      current
    DESCRIPTION
        "Xerox Phaser 7300 Laser Printer model identifier
                 (not a complete product identifier)."
    ::= { xcmPidPhaser7yyyFamily 1 }
            -- => SAP PID string = "C51"
xcmPidPhaser7300DN OBJECT-IDENTITY
    STATUS      current
    DESCRIPTION
        "Xerox Phaser 7300DN Laser Printer launch configuration model,
                  version, and complete product identifier."
    ::= { xcmPidPhaser7300 1 }
xcmPidPhaser7300N OBJECT-IDENTITY
    STATUS      current           
    DESCRIPTION
        "Xerox Phaser 7300N Laser Printer launch configuration model,
                  version, and complete product identifier."
    ::= { xcmPidPhaser7300 2 }
xcmPidPhaser7300DT OBJECT-IDENTITY
    STATUS      current
    DESCRIPTION
        "Xerox Phaser 7300DT Laser Printer launch configuration model,
                  version, and complete product identifier."
    ::= { xcmPidPhaser7300 3 }
xcmPidPhaser7300DX OBJECT-IDENTITY
    STATUS      current
    DESCRIPTION
        "Xerox Phaser 7300DX Laser Printer launch configuration model,
                  version, and complete product identifier."
    ::= { xcmPidPhaser7300 4 }
xcmPidPhaser7300B OBJECT-IDENTITY
    STATUS      current
    DESCRIPTION
        "Xerox Phaser 7300B Laser Printer launch configuration model,
                  version, and complete product identifier."
    ::= { xcmPidPhaser7300 5 }
--
xcmPidPhaser7400 OBJECT-IDENTITY
    STATUS      current
    DESCRIPTION
        "Xerox Phaser 7400 Laser Printer model identifier
                 (not a complete product identifier)."
    ::= { xcmPidPhaser7yyyFamily 2 }
            -- => SAP PID string = "C52"
xcmPidPhaser7400B OBJECT-IDENTITY
    STATUS      current
    DESCRIPTION
        "Xerox Phaser 7400B Laser Printer launch configuration model,
                  version, and complete product identifier."
    ::= { xcmPidPhaser7400 1 }
xcmPidPhaser7400N OBJECT-IDENTITY
    STATUS      current           
    DESCRIPTION
        "Xerox Phaser 7400N Laser Printer launch configuration model,
                  version, and complete product identifier."
    ::= { xcmPidPhaser7400 2 }
xcmPidPhaser7400DN OBJECT-IDENTITY
    STATUS      current
    DESCRIPTION
        "Xerox Phaser 7400DN Laser Printer launch configuration model,
                  version, and complete product identifier."
    ::= { xcmPidPhaser7400 3 }
xcmPidPhaser7400DT OBJECT-IDENTITY
    STATUS      current
    DESCRIPTION
        "Xerox Phaser 7400DT Laser Printer launch configuration model,
                  version, and complete product identifier."
    ::= { xcmPidPhaser7400 4 }
xcmPidPhaser7400DX OBJECT-IDENTITY
    STATUS      current
    DESCRIPTION
        "Xerox Phaser 7400DX Laser Printer launch configuration model,
                  version, and complete product identifier."
    ::= { xcmPidPhaser7400 5 }
xcmPidPhaser7400DXF OBJECT-IDENTITY
    STATUS      current
    DESCRIPTION
        "Xerox Phaser 7400DXF Laser Printer launch configuration model,
                  version, and complete product identifier."
    ::= { xcmPidPhaser7400 6 }
xcmPidPhaser7750 OBJECT-IDENTITY
    STATUS      current
    DESCRIPTION
        "Xerox Phaser 7750 Laser Printer model identifier
                 (not a complete product identifier)."
    ::= { xcmPidPhaser7yyyFamily 3 }
            -- => SAP PID string = "C53"
xcmPidPhaser7750B OBJECT-IDENTITY
    STATUS      current
    DESCRIPTION
        "Xerox Phaser 7750B Laser Printer launch configuration model,
                  version, and complete product identifier."
    ::= { xcmPidPhaser7750 1 }
xcmPidPhaser7750DN OBJECT-IDENTITY
    STATUS      current          
    DESCRIPTION
        "Xerox Phaser 7750DN Laser Printer launch configuration model,
                  version, and complete product identifier."
    ::= { xcmPidPhaser7750 2 }
xcmPidPhaser7750GX OBJECT-IDENTITY
    STATUS      current
    DESCRIPTION
        "Xerox Phaser 7750GX Laser Printer launch configuration model,
                  version, and complete product identifier."
    ::= { xcmPidPhaser7750 3 }
xcmPidPhaser7750DXF OBJECT-IDENTITY
    STATUS      current
    DESCRIPTION
        "Xerox Phaser 7750DXF Laser Printer launch configuration model,
                  version, and complete product identifier."
    ::= { xcmPidPhaser7750 4 }
xcmPidPhaser7760 OBJECT-IDENTITY
    STATUS      current
    DESCRIPTION
        "Xerox Phaser 7760 Laser Printer model identifier
                 (not a complete product identifier)."
    ::= { xcmPidPhaser7yyyFamily 4 }
            -- => SAP PID string = "C54"
xcmPidPhaser7760B OBJECT-IDENTITY
    STATUS      current
    DESCRIPTION
        "Xerox Phaser 7760B Laser Printer launch configuration model,
                  version, and complete product identifier."
    ::= { xcmPidPhaser7760 1 }
xcmPidPhaser7760DN OBJECT-IDENTITY
    STATUS      current          
    DESCRIPTION
        "Xerox Phaser 7760DN Laser Printer launch configuration model,
                  version, and complete product identifier."
    ::= { xcmPidPhaser7760 2 }
xcmPidPhaser7760GX OBJECT-IDENTITY
    STATUS      current
    DESCRIPTION
        "Xerox Phaser 7760GX Laser Printer launch configuration model,
                  version, and complete product identifier."
    ::= { xcmPidPhaser7760 3 }
xcmPidPhaser7760DX OBJECT-IDENTITY
    STATUS      current
    DESCRIPTION
        "Xerox Phaser 7760DX Laser Printer launch configuration model,
                  version, and complete product identifier."
    ::= { xcmPidPhaser7760 4 }
--
--
--
xcmPidPhaser7800 OBJECT-IDENTITY
    STATUS      current
    DESCRIPTION
        "Xerox Phaser 7800 Laser Printer model identifier
                 (not a complete product identifier)."
    ::= { xcmPidPhaser7yyyFamily 6 }
            -- => SAP PID string = "C56"
xcmPidPhaser7800NC1 OBJECT-IDENTITY
    STATUS      current
    DESCRIPTION
        "Xerox Phaser 7800N Laser Printer 
           model and configuration identifier
           (not a complete product identifier)."
    ::= { xcmPidPhaser7800 1 }
--
--     -mf "Xerox" -mo "Phaser 7800N"
xcmPidPhaser7800NC1V1 OBJECT-IDENTITY
    STATUS      current
    DESCRIPTION
        "Xerox Phaser 7800N Laser Printer 
            launch model, configuration, version 1. 
            A complete product identifier."
    ::= { xcmPidPhaser7800NC1 1 }
xcmPidPhaser7800DNC1 OBJECT-IDENTITY
    STATUS      current
    DESCRIPTION
        "Xerox Phaser 7800DN Laser Printer 
           model and configuration identifier
           (not a complete product identifier)."
    ::= { xcmPidPhaser7800 2 }
--
--     -mf "Xerox" -mo "Phaser 7800DN"
xcmPidPhaser7800DNC1V1 OBJECT-IDENTITY
    STATUS      current
    DESCRIPTION
        "Xerox Phaser 7800DN Laser Printer 
            launch model, configuration, version 1. 
            A complete product identifier."
    ::= { xcmPidPhaser7800DNC1 1 }
xcmPidPhaser7800GXC1 OBJECT-IDENTITY
    STATUS      current
    DESCRIPTION
        "Xerox Phaser 7800GX Laser Printer 
           model and configuration identifier
           (not a complete product identifier)."
    ::= { xcmPidPhaser7800 3 }
--
--     -mf "Xerox" -mo "Phaser 7800GX"
xcmPidPhaser7800GXC1V1 OBJECT-IDENTITY
    STATUS      current
    DESCRIPTION
        "Xerox Phaser 7800GX Laser Printer 
            launch model, configuration, version 1. 
            A complete product identifier."
    ::= { xcmPidPhaser7800GXC1 1 }
xcmPidPhaser7800DXC1 OBJECT-IDENTITY
    STATUS      current
    DESCRIPTION
        "Xerox Phaser 7800DX Laser Printer 
           model and configuration identifier
           (not a complete product identifier)."
    ::= { xcmPidPhaser7800 4 }
--
--     -mf "Xerox" -mo "Phaser 7800DX"
xcmPidPhaser7800DXC1V1 OBJECT-IDENTITY
    STATUS      current
    DESCRIPTION
        "Xerox Phaser 7800DX Laser Printer 
            launch model, configuration, version 1. 
            A complete product identifier."
    ::= { xcmPidPhaser7800DXC1 1 }
xcmPidPhaser7100 OBJECT-IDENTITY
    STATUS      current
    DESCRIPTION
        "Xerox Phaser 7100 Printer model identifier
                 (not a complete product identifier)."
    ::= { xcmPidPhaser7yyyFamily 7 }
            -- => SAP PID string = "C57"
--
--     -mf "Xerox" -mo "Phaser 7100N"
xcmPidPhaser7100NC1 OBJECT-IDENTITY
    STATUS      current
    DESCRIPTION
        "Xerox Phaser 7100N Printer 
           model and configuration identifier
           (not a complete product identifier)."
    ::= { xcmPidPhaser7100 1 }
xcmPidPhaser7100NC1V1 OBJECT-IDENTITY
    STATUS      current
    DESCRIPTION
        "Xerox Phaser 70xxN Printer 
            launch model, configuration, version 1. 
            A complete product identifier."
    ::= { xcmPidPhaser7100NC1 1 }
xcmPidPhaser7100DNC1 OBJECT-IDENTITY
    STATUS      current
    DESCRIPTION
        "Xerox Phaser 70xxDN Printer 
           model and configuration identifier
           (not a complete product identifier)."
    ::= { xcmPidPhaser7100 2 }
--
--     -mf "Xerox" -mo "Phaser 7100DN"
xcmPidPhaser7100DNC1V1 OBJECT-IDENTITY
    STATUS      current
    DESCRIPTION
        "Xerox Phaser 7100DN Printer 
            launch model, configuration, version 1. 
            A complete product identifier."
    ::= { xcmPidPhaser7100DNC1 1 }
xcmPidPhaser8yyyFamily OBJECT-IDENTITY
    STATUS      current
    DESCRIPTION
        "Xerox Phaser 8yyy Family product line identifier
                 (not a complete product identifier)."
    ::= { xcmPidXeroxPhaserPrinters 6 }
xcmPidPhaser8400 OBJECT-IDENTITY
    STATUS      current
    DESCRIPTION
        "Xerox Phaser 8400 Laser Printer model identifier
                 (not a complete product identifier)."
    ::= { xcmPidPhaser8yyyFamily 1 }
            -- => SAP PID string = "C61"
xcmPidPhaser8400B OBJECT-IDENTITY
    STATUS      current
    DESCRIPTION
        "Xerox Phaser 8400B Laser Printer launch configuration model,
                  and complete product identifier. The 8400B is not
                  network connected so this SNMP id is not used."
    ::= { xcmPidPhaser8400 1 }
xcmPidPhaser8400N OBJECT-IDENTITY
    STATUS      current
    DESCRIPTION
        "Xerox Phaser 8400N Laser Printer launch configuration model,
                  and complete product identifier."
    ::= { xcmPidPhaser8400 2 }
xcmPidPhaser8400DP OBJECT-IDENTITY
    STATUS      current
    DESCRIPTION
        "Xerox Phaser 8400DP Laser Printer launch configuration model,
                  and complete product identifier."
    ::= { xcmPidPhaser8400 3 }
xcmPidPhaser8400DX OBJECT-IDENTITY
    STATUS      current
    DESCRIPTION
        "Xerox Phaser 8400DX Laser Printer launch configuration model,
                  and complete product identifier."
    ::= { xcmPidPhaser8400 4 }
xcmPidPhaser8400BD OBJECT-IDENTITY
    STATUS      current
    DESCRIPTION
        "Xerox Phaser 8400BD Laser Printer launch configuration model,
                  This is not network connected so the SNMP id is not 
                  used."
    ::= { xcmPidPhaser8400 5 }
--
--
xcmPidPhaser8560 OBJECT-IDENTITY
    STATUS      current
    DESCRIPTION
        "Xerox Phaser 8560 launch configuration
                 model identifier (not a complete product identifier)."
    ::= { xcmPidPhaser8yyyFamily 7 }
            -- => SAP PID string = "C67"
xcmPidPhaser8560v1 OBJECT-IDENTITY
    STATUS      current
    DESCRIPTION
        "Xerox Phaser 8560 Copy/Print/Scan/Fax, 30/30ppm 
         complete product identifier."
    ::= { xcmPidPhaser8560 1 }
--
--
xcmPidPhaser8560p OBJECT-IDENTITY
    STATUS      current
    DESCRIPTION
        "Xerox Phaser 8560 Color Printer model identifier
                 (not a complete product identifier)."
    ::= { xcmPidPhaser8yyyFamily 9 }
            -- => SAP PID string = "C69"
xcmPidPhaser8560N OBJECT-IDENTITY
    STATUS      current
    DESCRIPTION
        "Xerox Phaser 8560N Color Printer launch configuration
              model, and complete product identifier."
    ::= { xcmPidPhaser8560p 1 }
xcmPidPhaser8560DN OBJECT-IDENTITY
    STATUS      current
    DESCRIPTION
        "Xerox Phaser 8560DN Color Printer launch configuration
              model, and complete product identifier."
    ::= { xcmPidPhaser8560p 2 }
xcmPidPhaser8560DT OBJECT-IDENTITY
    STATUS      current
    DESCRIPTION
        "Xerox Phaser 8560DT Color Printer launch configuration
              model, and complete product identifier."
    ::= { xcmPidPhaser8560p 3 }
xcmPidPhaser8560DX OBJECT-IDENTITY
    STATUS      current
    DESCRIPTION
        "Xerox Phaser 8560DX Color Printer launch configuration
              model, and complete product identifier."
    ::= { xcmPidPhaser8560p 4 }
xcmPidPhaser8560PP OBJECT-IDENTITY
    STATUS      current
    DESCRIPTION
        "Xerox Phaser 8560PP Printer launch configuration 
              model, and complete product identifier."
    ::= { xcmPidPhaser8560p 6 }
xcmPidPhaser8860 OBJECT-IDENTITY
    STATUS      current
    DESCRIPTION
        "Xerox Phaser 8860 Color Printer model identifier
                 (not a complete product identifier)."
    ::= { xcmPidPhaser8yyyFamily 17 }
            -- => SAP PID string = "C6A"
xcmPidPhaser8860v1 OBJECT-IDENTITY
    STATUS      current
    DESCRIPTION
        "Xerox Phaser 8860N Color Printer launch configuration
              model, and complete product identifier."
    ::= { xcmPidPhaser8860 1 }
xcmPidPhaser8860MFP OBJECT-IDENTITY
    STATUS      current
    DESCRIPTION
        "Xerox Phaser 8860MFP model identifier
                 (not a complete product identifier)."
    ::= { xcmPidPhaser8yyyFamily 18 }
            -- => SAP PID string = "C6B"
xcmPidPhaser8860MFPv1 OBJECT-IDENTITY
    STATUS      current
    DESCRIPTION
        "Xerox Phaser 8860MFP MFD launch configuration
              model, and complete product identifier."
    ::= { xcmPidPhaser8860MFP 1 }
--
--
xcmPidP3200MFP OBJECT-IDENTITY
    STATUS      current
    DESCRIPTION
        "Xerox Phaser 3200 MFP system identifier
                 (not a complete product identifier)."
    ::= { xcmPidPhaser8yyyFamily 19 }
            -- => SAP PID string = "C6C"
xcmPidP3200MFPv1 OBJECT-IDENTITY
    STATUS      current
    DESCRIPTION
        "Xerox Phaser 3200 MFP system identifier
         launch configuration version #1, and
         complete product identifier."
    ::= { xcmPidP3200MFP 1 }
------------------------------------------------------------------
------------------------------------------------------------------
xcmPidPhaser9yyyFamily OBJECT-IDENTITY
    STATUS      current
    DESCRIPTION
        "Xerox Phaser 9yyy Family product line identifier
                 (not a complete product identifier)."
    ::= { xcmPidXeroxPhaserPrinters 9 }
--
--
----------------------------------------------------------------
----------------------------------------------------------------
xcmPidMidRangeColorPrinters OBJECT-IDENTITY
    STATUS      current
    DESCRIPTION
        "MidRange Color Printers product line identifier
                 (not a complete product identifier)."
    ::= { xcmPidProductIdentifiers 4 }
--
--
xcmPidDCColorSeries50 OBJECT-IDENTITY
    STATUS      current
    DESCRIPTION
        "Document Centre ColorSeries 50 mid-range color printer product
                 type identifier (not a complete product identifier)."
    ::= { xcmPidMidRangeColorPrinters 2 }
xcmPidDCColorSeries50M1 OBJECT-IDENTITY
    STATUS      current
    DESCRIPTION
        "Document Centre ColorSeries 50 mid-range color printer
                 launch configuration model identifier
                 (not a complete product identifier)."
    ::= { xcmPidDCColorSeries50 1 }
            -- => SAP PID string = "421"
xcmPidDCColorSeries50M1V1 OBJECT-IDENTITY
    STATUS      current
    DESCRIPTION
        "Document Centre ColorSeries 50 mid-range color printer
                 launch configuration version,
                 and complete product identifier."
    ::= { xcmPidDCColorSeries50M1 1 }
--
--
----------------------------------------------------------------
----------------------------------------------------------------
xcmPidDocuColor2000Series OBJECT-IDENTITY
    STATUS      current
    DESCRIPTION
        "DocuColor 2000 Family product line identifier
                 (not a complete product identifier)."
    ::= { xcmPidProductIdentifiers 17 }
--
--
--
--
--
--
--
--
----------------------------------------------------------------
----------------------------------------------------------------
xcmPidDocuColor3000series OBJECT-IDENTITY
    STATUS      current
    DESCRIPTION
        "Xerox DocuColor 3000 Digital Press product type 
 identifier (not a complete product identifier)."
    ::= { xcmPidDocuColor2000Series 7 }
--
--
--
--
xcmPidDocuColor240SPLASH OBJECT-IDENTITY
    STATUS      current
    DESCRIPTION
        "Xerox DocuColor 240 with the Fiery Controller 
         and DFE launch configuration model identifier 
         (not a complete product identifier)."
    ::= { xcmPidDocuColor3000series 8 }
            -- => SAP PID string = "A78"
xcmPidDocuColor240SPLASHv1 OBJECT-IDENTITY
    STATUS      current
    DESCRIPTION
        "Xerox DocuColor 240 with the Fiery Controller 
         and DFE configuration model and version, and complete 
         product identifier."
    ::= { xcmPidDocuColor240SPLASH 1 }
--
--
xcmPidDocuColor250SPLASH OBJECT-IDENTITY
    STATUS      current
    DESCRIPTION
        "Xerox DocuColor 250 with the Fiery Controller 
         and DFE launch configuration model identifier 
         (not a complete product identifier)."
    ::= { xcmPidDocuColor3000series 9 }
            -- => SAP PID string = "A79"
xcmPidDocuColor250SPLASHv1 OBJECT-IDENTITY
    STATUS      current
    DESCRIPTION
        "Xerox DocuColor 250 with the Fiery Controller 
         and DFE configuration model and version, and complete 
         product identifier."
    ::= { xcmPidDocuColor250SPLASH 1 }
--
--
xcmPidDocuColor242EFI OBJECT-IDENTITY
    STATUS      current
    DESCRIPTION
        "Xerox DocuColor 242 with the EFI Fiery Controller 
         launch configuration model identifier 
         (not a complete product identifier)."
    ::= { xcmPidDocuColor3000series 17 }
            -- => SAP PID string = "A7A"
xcmPidDocuColor242EFIv1 OBJECT-IDENTITY
    STATUS      current
    DESCRIPTION
        "Xerox DocuColor 242 with the EFI Fiery Controller 
         configuration model and version, and complete 
         product identifier."
    ::= { xcmPidDocuColor242EFI 1 }
--
--
xcmPidDocuColor242 OBJECT-IDENTITY
    STATUS      current
    DESCRIPTION
        "Xerox DocuColor 242 with the Fiery Color Server 
         launch configuration model identifier 
         (not a complete product identifier)."
    ::= { xcmPidDocuColor3000series 18 }
            -- => SAP PID string = "A7B"
xcmPidDocuColor242v1 OBJECT-IDENTITY
    STATUS      current
    DESCRIPTION
        "Xerox DocuColor 242 with the Fiery Color Server 
         configuration model and version, and complete 
         product identifier."
    ::= { xcmPidDocuColor242 1 }
--
--
xcmPidDocuColor252EFI OBJECT-IDENTITY
    STATUS      current
    DESCRIPTION
        "Xerox DocuColor 252 with the EFI Fiery Controller 
         launch configuration model identifier 
         (not a complete product identifier)."
    ::= { xcmPidDocuColor3000series 19 }
            -- => SAP PID string = "A7C"
xcmPidDocuColor252EFIv1 OBJECT-IDENTITY
    STATUS      current
    DESCRIPTION
        "Xerox DocuColor 252 with the EFI Fiery Controller 
         configuration model and version, and complete 
         product identifier."
    ::= { xcmPidDocuColor252EFI 1 }
--
--
xcmPidDocuColor252 OBJECT-IDENTITY
    STATUS      current
    DESCRIPTION
        "Xerox DocuColor 252 with the Fiery Color Server 
         launch configuration model identifier 
         (not a complete product identifier)."
    ::= { xcmPidDocuColor3000series 20 }
            -- => SAP PID string = "A7D"
xcmPidDocuColor252v1 OBJECT-IDENTITY
    STATUS      current
    DESCRIPTION
        "Xerox DocuColor 252 with the Fiery Color Server 
         configuration model and version, and complete 
         product identifier."
    ::= { xcmPidDocuColor252 1 }
--
--
xcmPidDocuColor260EFI OBJECT-IDENTITY
    STATUS      current
    DESCRIPTION
        "Xerox DocuColor 260 with the EFI Fiery Controller 
         launch configuration model identifier 
         (not a complete product identifier)."
    ::= { xcmPidDocuColor3000series 21 }
            -- => SAP PID string = "A7E"
xcmPidDocuColor260EFIv1 OBJECT-IDENTITY
    STATUS      current
    DESCRIPTION
        "Xerox DocuColor 260 with the EFI Fiery Controller 
         configuration model and version, and complete 
         product identifier."
    ::= { xcmPidDocuColor260EFI 1 }
--
--
xcmPidDocuColor260 OBJECT-IDENTITY
    STATUS      current
    DESCRIPTION
        "Xerox DocuColor 260 with the Fiery Color Server 
         launch configuration model identifier 
         (not a complete product identifier)."
    ::= { xcmPidDocuColor3000series 22 }
            -- => SAP PID string = "A7F"
xcmPidDocuColor260v1 OBJECT-IDENTITY
    STATUS      current
    DESCRIPTION
        "Xerox DocuColor 260 with the Fiery Color Server 
         configuration model and version, and complete 
         product identifier."
    ::= { xcmPidDocuColor260 1 }
--
xcmPidDocuColor242C OBJECT-IDENTITY
    STATUS      current
    DESCRIPTION
        "Xerox DocuColor 242 with the Creo Spire Color Server 
         launch configuration model identifier 
         (not a complete product identifier)."
    ::= { xcmPidDocuColor3000series 23 }
            -- => SAP PID string = "A7G"
xcmPidDocuColor242Cv1 OBJECT-IDENTITY
    STATUS      current
    DESCRIPTION
        "Xerox DocuColor 242 with the Creo Spire Color Server 
         configuration model and version, and complete 
         product identifier."
    ::= { xcmPidDocuColor242C 1 }
--
xcmPidDocuColor242S OBJECT-IDENTITY
    STATUS      current
    DESCRIPTION
        "Xerox DocuColor 242 Splash 
         launch configuration model identifier 
         (not a complete product identifier)."
    ::= { xcmPidDocuColor3000series 24 }
            -- => SAP PID string = "A7H"
xcmPidDocuColor242Sv1 OBJECT-IDENTITY
    STATUS      current
    DESCRIPTION
        "Xerox DocuColor 242 Splash  
         configuration model and version, and complete 
         product identifier."
    ::= { xcmPidDocuColor242S 1 }
--
xcmPidDocuColor252C OBJECT-IDENTITY
    STATUS      current
    DESCRIPTION
        "Xerox DocuColor 252 with the Creo Spire Color Server 
         launch configuration model identifier 
         (not a complete product identifier)."
    ::= { xcmPidDocuColor3000series 25 }
            -- => SAP PID string = "A7I"
xcmPidDocuColor252Cv1 OBJECT-IDENTITY
    STATUS      current
    DESCRIPTION
        "Xerox DocuColor 252 with the Creo Spire Color Server 
         configuration model and version, and complete 
         product identifier."
    ::= { xcmPidDocuColor252C 1 }
--
xcmPidDocuColor252S OBJECT-IDENTITY
    STATUS      current
    DESCRIPTION
        "Xerox DocuColor 252 Splash 
         launch configuration model identifier 
         (not a complete product identifier)."
    ::= { xcmPidDocuColor3000series 26 }
            -- => SAP PID string = "A7J"
xcmPidDocuColor252Sv1 OBJECT-IDENTITY
    STATUS      current
    DESCRIPTION
        "Xerox DocuColor 252 Splash  
         configuration model and version, and complete 
         product identifier."
    ::= { xcmPidDocuColor252S 1 }
--
xcmPidDocuColor260C OBJECT-IDENTITY
    STATUS      current
    DESCRIPTION
        "Xerox DocuColor 260 with the Creo Spire Color Server 
         launch configuration model identifier 
         (not a complete product identifier)."
    ::= { xcmPidDocuColor3000series 27 }
            -- => SAP PID string = "A7K"
xcmPidDocuColor260Cv1 OBJECT-IDENTITY
    STATUS      current
    DESCRIPTION
        "Xerox DocuColor 260 with the Creo Spire Color Server 
         configuration model and version, and complete 
         product identifier."
    ::= { xcmPidDocuColor260C 1 }
--
xcmPidDocuColor260S OBJECT-IDENTITY
    STATUS      current
    DESCRIPTION
        "Xerox DocuColor 260 Splash 
         launch configuration model identifier 
         (not a complete product identifier)."
    ::= { xcmPidDocuColor3000series 28 }
            -- => SAP PID string = "A7L"
xcmPidDocuColor260Sv1 OBJECT-IDENTITY
    STATUS      current
    DESCRIPTION
        "Xerox DocuColor 260 Splash  
         configuration model and version, and complete 
         product identifier."
    ::= { xcmPidDocuColor260S 1 }
--
--
----------------------------------------------------------------
----------------------------------------------------------------
xcmPidDocuPrintNPS OBJECT-IDENTITY
    STATUS      current
    DESCRIPTION
        "DocuPrint NPS (Network Printing Systems) product line
                 identifier (not a complete product identifier)."
    ::= { xcmPidProductIdentifiers 9 }
xcmPidDP4050NPS OBJECT-IDENTITY
    STATUS      current
    DESCRIPTION
        "DocuPrint NPS DP4050 product type identifier
                 (not a complete product identifier)."
    ::= { xcmPidDocuPrintNPS 1 }
xcmPidDP4050NPSM1 OBJECT-IDENTITY
    STATUS      current
    DESCRIPTION
        "DocuPrint NPS DP4050 launch configuration model identifier
                 (not a complete product identifier)."
    ::= { xcmPidDP4050NPS 1 }
            -- => SAP PID string = "911"
xcmPidDP4050NPSM1V1 OBJECT-IDENTITY
    STATUS      current
    DESCRIPTION
        "DocuPrint NPS DP4050 launch configuration version,
                 and complete product identifier."
    ::= { xcmPidDP4050NPSM1 1 }
xcmPidDP4090NPS OBJECT-IDENTITY
    STATUS      current
    DESCRIPTION
        "DocuPrint NPS DP4090 product type identifier
                 (not a complete product identifier)."
    ::= { xcmPidDocuPrintNPS 2 }
xcmPidDP4090NPSM1 OBJECT-IDENTITY
    STATUS      current
    DESCRIPTION
        "DocuPrint NPS DP4090 launch configuration model identifier
                 (not a complete product identifier)."
    ::= { xcmPidDP4090NPS 1 }
            -- => SAP PID string = "921"
xcmPidDP4090NPSM1V1 OBJECT-IDENTITY
    STATUS      current
    DESCRIPTION
        "DocuPrint NPS DP4090 launch configuration version,
                 and complete product identifier."
    ::= { xcmPidDP4090NPSM1 1 }
xcmPidDP4850NPS OBJECT-IDENTITY
    STATUS      current
    DESCRIPTION
        "DocuPrint NPS DP4850 product type identifier
                 (not a complete product identifier)."
    ::= { xcmPidDocuPrintNPS 3 }
xcmPidDP4850NPSM1 OBJECT-IDENTITY
    STATUS      current
    DESCRIPTION
        "DocuPrint NPS DP4850 launch configuration model identifier
                 (not a complete product identifier)."
    ::= { xcmPidDP4850NPS 1 }
            -- => SAP PID string = "931"
xcmPidDP4850NPSM1V1 OBJECT-IDENTITY
    STATUS      current
    DESCRIPTION
        "DocuPrint NPS DP4850 launch configuration version,
                 and complete product identifier."
    ::= { xcmPidDP4850NPSM1 1 }
xcmPidDP4890NPS OBJECT-IDENTITY
    STATUS      current
    DESCRIPTION
        "DocuPrint NPS DP4890 product type identifier
                 (not a complete product identifier)."
    ::= { xcmPidDocuPrintNPS 4 }
xcmPidDP4890NPSM1 OBJECT-IDENTITY
    STATUS      current
    DESCRIPTION
        "DocuPrint NPS DP4890 launch configuration model identifier
                 (not a complete product identifier)."
    ::= { xcmPidDP4890NPS 1 }
            -- => SAP PID string = "941"
xcmPidDP4890NPSM1V1 OBJECT-IDENTITY
    STATUS      current
    DESCRIPTION
        "DocuPrint NPS DP4890 launch configuration version,
                 and complete product identifier."
    ::= { xcmPidDP4890NPSM1 1 }
xcmPidDP4635NPS OBJECT-IDENTITY
    STATUS      current
    DESCRIPTION
        "DocuPrint NPS DP4635 product type identifier
                 (not a complete product identifier)."
    ::= { xcmPidDocuPrintNPS 5 }
xcmPidDP4635NPSM1 OBJECT-IDENTITY
    STATUS      current
    DESCRIPTION
        "DocuPrint NPS DP4635 launch configuration model identifier
                 (not a complete product identifier)."
    ::= { xcmPidDP4635NPS 1 }
            -- => SAP PID string = "951"
xcmPidDP4635NPSM1V1 OBJECT-IDENTITY
    STATUS      current
    DESCRIPTION
        "DocuPrint NPS DP4635 launch configuration version,
                 and complete product identifier."
    ::= { xcmPidDP4635NPSM1 1 }
xcmPidDP4635NPSMicr OBJECT-IDENTITY
    STATUS      current
    DESCRIPTION
        "DocuPrint NPS DP4635 Micr launch configuration model identifier
                 (not a complete product identifier)."
    ::= { xcmPidDP4635NPS 2 }
            -- => SAP PID string = "952"
xcmPidDP4635NPSMicrV1 OBJECT-IDENTITY
    STATUS      current
    DESCRIPTION
        "DocuPrint NPS DP4635 Micr launch configuration version,
                 and complete product identifier."
    ::= { xcmPidDP4635NPSMicr 1 }
xcmPidDP180NPS OBJECT-IDENTITY
    STATUS      current
    DESCRIPTION
        "DocuPrint NPS DP180 product type identifier
                 (not a complete product identifier)."
    ::= { xcmPidDocuPrintNPS 6 }
xcmPidDP180NPSM1 OBJECT-IDENTITY
    STATUS      current
    DESCRIPTION
        "DocuPrint NPS DP180 launch configuration model identifier
                 (not a complete product identifier)."
    ::= { xcmPidDP180NPS 1 }
            -- => SAP PID string = "961"
xcmPidDP180NPSM1V1 OBJECT-IDENTITY
    STATUS      current
    DESCRIPTION
        "DocuPrint NPS DP180 launch configuration version,
                 and complete product identifier."
    ::= { xcmPidDP180NPSM1 1 }
xcmPidDP180NPSMicr OBJECT-IDENTITY
    STATUS      current
    DESCRIPTION
        "DocuPrint NPS DP180 Micr launch configuration model identifier
                 (not a complete product identifier)."
    ::= { xcmPidDP180NPS 2 }
            -- => SAP PID string = "962"
xcmPidDP180NPSMicrV1 OBJECT-IDENTITY
    STATUS      current
    DESCRIPTION
        "DocuPrint NPS DP180 Micr launch configuration version,
                 and complete product identifier."
    ::= { xcmPidDP180NPSMicr 1 }
xcmPidDP96NPS OBJECT-IDENTITY
    STATUS      current
    DESCRIPTION
        "DocuPrint NPS DP96 product type identifier
                 (not a complete product identifier)."
    ::= { xcmPidDocuPrintNPS 7 }
xcmPidDP96NPSM1 OBJECT-IDENTITY
    STATUS      current
    DESCRIPTION
        "DocuPrint NPS DP96 launch configuration model identifier
                 (not a complete product identifier)."
    ::= { xcmPidDP96NPS 1 }
            -- => SAP PID string = "971"
xcmPidDP96NPSM1V1 OBJECT-IDENTITY
    STATUS      current
    DESCRIPTION
        "DocuPrint NPS DP96 launch configuration version,
                 and complete product identifier."
    ::= { xcmPidDP96NPSM1 1 }
xcmPidDP96NPSMicr OBJECT-IDENTITY
    STATUS      current
    DESCRIPTION
        "DocuPrint NPS DP96 Micr launch configuration model identifier
                 (not a complete product identifier)."
    ::= { xcmPidDP96NPS 2 }
            -- => SAP PID string = "972"
xcmPidDP96NPSMicrV1 OBJECT-IDENTITY
    STATUS      current
    DESCRIPTION
        "DocuPrint NPS DP96 Micr launch configuration version,
                 and complete product identifier."
    ::= { xcmPidDP96NPSMicr 1 }
xcmPidDP92cNPS OBJECT-IDENTITY
    STATUS      current
    DESCRIPTION
        "DocuPrint NPS DP92c product type identifier
                 (not a complete product identifier)."
    ::= { xcmPidDocuPrintNPS 8 }
xcmPidDP92cNPSM1 OBJECT-IDENTITY
    STATUS      current
    DESCRIPTION
        "DocuPrint NPS DP92c launch configuration model identifier
                 (not a complete product identifier)."
    ::= { xcmPidDP92cNPS 1 }
            -- => SAP PID string = "981"
xcmPidDP92cNPSM1V1 OBJECT-IDENTITY
    STATUS      current
    DESCRIPTION
        "DocuPrint NPS DP92c launch configuration version,
                 and complete product identifier."
    ::= { xcmPidDP92cNPSM1 1 }
xcmPidDP155NPS OBJECT-IDENTITY
    STATUS      current
    DESCRIPTION
        "DocuPrint NPS DP155 product type identifier
                 (not a complete product identifier)."
    ::= { xcmPidDocuPrintNPS 9 }
xcmPidDP155NPSM1 OBJECT-IDENTITY
    STATUS      current
    DESCRIPTION
        "DocuPrint NPS DP155 launch configuration model identifier
                 (not a complete product identifier)."
    ::= { xcmPidDP155NPS 1 }
            -- => SAP PID string = "991"
xcmPidDP155NPSM1V1 OBJECT-IDENTITY
    STATUS      current
    DESCRIPTION
        "DocuPrint NPS DP155 launch configuration version,
                 and complete product identifier."
    ::= { xcmPidDP155NPSM1 1 }
xcmPidDP155NPSMicr OBJECT-IDENTITY
    STATUS      current
    DESCRIPTION
        "DocuPrint NPS DP155 Micr launch configuration model identifier
                 (not a complete product identifier)."
    ::= { xcmPidDP155NPS 2 }
            -- => SAP PID string = "992"
xcmPidDP155NPSMicrV1 OBJECT-IDENTITY
    STATUS      current
    DESCRIPTION
        "DocuPrint NPS DP155 Micr launch configuration version,
                 and complete product identifier."
    ::= { xcmPidDP155NPSMicr 1 }
xcmPidDP115NPS OBJECT-IDENTITY
    STATUS      current
    DESCRIPTION
        "DocuPrint NPS DP115 product type identifier
                 (not a complete product identifier)."
    ::= { xcmPidDocuPrintNPS 17 }
xcmPidDP115NPSM1 OBJECT-IDENTITY
    STATUS      current
    DESCRIPTION
        "DocuPrint NPS DP115 launch configuration model identifier
                 (not a complete product identifier)."
    ::= { xcmPidDP115NPS 1 }
            -- => SAP PID string = "9A1"
xcmPidDP115NPSM1V1 OBJECT-IDENTITY
    STATUS      current
    DESCRIPTION
        "DocuPrint NPS DP115 launch configuration version,
                 and complete product identifier."
    ::= { xcmPidDP115NPSM1 1 }
xcmPidDP115NPSMicr OBJECT-IDENTITY
    STATUS      current
    DESCRIPTION
        "DocuPrint NPS DP115 Micr launch configuration model identifier
                 (not a complete product identifier)."
    ::= { xcmPidDP115NPS 2 }
            -- => SAP PID string = "9A2"
xcmPidDP115NPSMicrV1 OBJECT-IDENTITY
    STATUS      current
    DESCRIPTION
        "DocuPrint NPS DP115 Micr launch configuration version,
                 and complete product identifier."
    ::= { xcmPidDP115NPSMicr 1 }
xcmPidDP100NPS OBJECT-IDENTITY
    STATUS      current
    DESCRIPTION
        "DocuPrint NPS DP100 product type identifier
                 (not a complete product identifier)."
    ::= { xcmPidDocuPrintNPS 18 }
xcmPidDP100NPSM1 OBJECT-IDENTITY
    STATUS      current
    DESCRIPTION
        "DocuPrint NPS DP100 launch configuration model identifier
                 (not a complete product identifier)."
    ::= { xcmPidDP100NPS 1 }
            -- => SAP PID string = "9B1"
xcmPidDP100NPSM1V1 OBJECT-IDENTITY
    STATUS      current
    DESCRIPTION
        "DocuPrint NPS DP100 launch configuration version,
                 and complete product identifier."
    ::= { xcmPidDP100NPSM1 1 }
xcmPidDP100NPSMicr OBJECT-IDENTITY
    STATUS      current
    DESCRIPTION
        "DocuPrint NPS DP100 Micr launch configuration model identifier
                 (not a complete product identifier)."
    ::= { xcmPidDP100NPS 2 }
            -- => SAP PID string = "9B2"
xcmPidDP100NPSMicrV1 OBJECT-IDENTITY
    STATUS      current
    DESCRIPTION
        "DocuPrint NPS DP100 Micr launch configuration version,
                 and complete product identifier."
    ::= { xcmPidDP100NPSMicr 1 }
xcmPidDC2000FamilyNPS OBJECT-IDENTITY
    STATUS      current
    DESCRIPTION
        "DocuColor 2000 NPS Family product line identifier
                 (not a complete product identifier)."
    ::= { xcmPidDocuPrintNPS 19 }
xcmPidDocuColor2045NPS OBJECT-IDENTITY
    STATUS      current
    DESCRIPTION
     "Xerox DocuColor 2045 NPS/IPS product identifier
       (not a complete product identifier)."
    ::= { xcmPidDC2000FamilyNPS 1 }
            -- => SAP PID string = "9C1"
xcmPidDocuColor2045NPSV1 OBJECT-IDENTITY
    STATUS      current
    DESCRIPTION
        "Xerox DocuColor 2045 NPS/IPS launch configuration
                 version, and complete product identifier."
    ::= { xcmPidDocuColor2045NPS 1 }
xcmPidDocuColor2060NPS OBJECT-IDENTITY
    STATUS      current
    DESCRIPTION
        "Xerox DocuColor 2060 NPS/IPS product type identifier
                 (not a complete product identifier)."
    ::= { xcmPidDC2000FamilyNPS 2 }
            -- => SAP PID string = "9C2"
xcmPidDocuColor2060NPSV1 OBJECT-IDENTITY
    STATUS      current
    DESCRIPTION
        "Xerox DocuColor 2060 NPS/IPS launch configuration
                 version, and complete product identifier."
    ::= { xcmPidDocuColor2060NPS 1 }
xcmPidDocuColor5252NPS OBJECT-IDENTITY
    STATUS      current
    DESCRIPTION
        "Xerox DocuColor 5252 NPS/IPS product type identifier
                 (not a complete product identifier)."
    ::= { xcmPidDC2000FamilyNPS 3 }
            -- => SAP PID string = "9C3"
xcmPidDocuColor5252NPSV1 OBJECT-IDENTITY
    STATUS      current
    DESCRIPTION
        "Xerox DocuColor 5252 NPS/IPS launch configuration
                 version, and complete product identifier."
    ::= { xcmPidDocuColor5252NPS 1 }
------------------------------------------------------
------------------------------------------------------
xcmPidDC6000FamilyNPS OBJECT-IDENTITY
    STATUS      current
    DESCRIPTION
        "DocuColor 6000 NPS Family product line identifier
                 (not a complete product identifier)."
    ::= { xcmPidDocuPrintNPS 20 }
xcmPidDocuColor6060NPS OBJECT-IDENTITY
    STATUS      current
    DESCRIPTION
        "Xerox DocuColor 6060 NPS/IPS product type identifier
                 (not a complete product identifier)."
    ::= { xcmPidDC6000FamilyNPS 1 }
            -- => SAP PID string = "9D1"
xcmPidDocuColor6060NPSV1 OBJECT-IDENTITY
    STATUS      current
    DESCRIPTION
        "Xerox DocuColor 6060 NPS/IPS launch configuration
                 version, and complete product identifier."
    ::= { xcmPidDocuColor6060NPS 1 }
--
--
----------------------------------------------------------------
----------------------------------------------------------------
xcmPidDocuPrintEPS OBJECT-IDENTITY
    STATUS      current
    DESCRIPTION
        "DocuPrint EPS product line                          
                 identifier (not a complete product identifier)."
    ::= { xcmPidProductIdentifiers 18 }
xcmPidDP180EPS OBJECT-IDENTITY
    STATUS      current           
    DESCRIPTION
        "DocuPrint DP180 EPS product type identifier
                 (not a complete product identifier)."
    ::= { xcmPidDocuPrintEPS 1 }
xcmPidDP180EPSM1 OBJECT-IDENTITY
    STATUS      current           
    DESCRIPTION
        "DocuPrint DP180 EPS launch configuration model identifier
                 (not a complete product identifier)."
    ::= { xcmPidDP180EPS 1 }
            -- => SAP PID string = "B11"
xcmPidDP180EPSM1V1 OBJECT-IDENTITY
    STATUS      current           
    DESCRIPTION
        "DocuPrint DP180 EPS launch configuration version,
                 and complete product identifier."
    ::= { xcmPidDP180EPSM1 1 }
xcmPidDP2000EPS OBJECT-IDENTITY
    STATUS      current
    DESCRIPTION
        "DocuPrint 2000 Series EPS product type identifier
                 (not a complete product identifier)."
    ::= { xcmPidDocuPrintEPS 2 }
xcmPidDP2000S100EPS OBJECT-IDENTITY
    STATUS      current
    DESCRIPTION
     "DocuPrint 2000 Series 100 EPS launch configuration
      model identifier (not a complete product identifier)."
    ::= { xcmPidDP2000EPS 1 }
            -- => SAP PID string = "B21"
xcmPidDP2000S100EPSV1 OBJECT-IDENTITY
    STATUS      current
    DESCRIPTION
        "DocuPrint 2000 Series 100 EPS launch configuration
                 version and complete product identifier."
    ::= { xcmPidDP2000S100EPS 1 }
xcmPidDP2000S115EPS OBJECT-IDENTITY
    STATUS      current
    DESCRIPTION
        "DocuPrint 2000 Series 115 EPS launch configuration
                 model identifier
                 (not a complete product identifier)."
    ::= { xcmPidDP2000EPS 2 }
            -- => SAP PID string = "B22"
xcmPidDP2000S115EPSV1 OBJECT-IDENTITY
    STATUS      current
    DESCRIPTION
        "DocuPrint 2000 Series 115 EPS launch configuration
                 version and complete product identifier."
    ::= { xcmPidDP2000S115EPS 1 }
xcmPidDP2000S135EPS OBJECT-IDENTITY
    STATUS      current
    DESCRIPTION
        "DocuPrint 2000 Series 135 EPS launch configuration
                 model identifier
                 (not a complete product identifier)."
    ::= { xcmPidDP2000EPS 3 }
            -- => SAP PID string = "B23"
xcmPidDP2000S135EPSV1 OBJECT-IDENTITY
    STATUS      current
    DESCRIPTION
        "DocuPrint 2000 Series 135 EPS launch configuration
                 version and complete product identifier."
    ::= { xcmPidDP2000S135EPS 1 }
xcmPidDP2000S155EPS OBJECT-IDENTITY
    STATUS      current
    DESCRIPTION
     "DocuPrint 2000 Series 155 EPS launch configuration
       model identifier (not a complete product identifier)."
    ::= { xcmPidDP2000EPS 4 }
            -- => SAP PID string = "B24"
xcmPidDP2000S155EPSV1 OBJECT-IDENTITY
    STATUS      current
    DESCRIPTION
        "DocuPrint 2000 Series 155 EPS launch configuration
                 version and complete product identifier."
    ::= { xcmPidDP2000S155EPS 1 }
xcmPidDP2000S180EPS OBJECT-IDENTITY
    STATUS      current
    DESCRIPTION
        "DocuPrint 2000 Series 180 EPS launch configuration
                 model identifier
                 (not a complete product identifier)."
    ::= { xcmPidDP2000EPS 5 }
            -- => SAP PID string = "B25"
xcmPidDP2000S180EPSV1 OBJECT-IDENTITY
    STATUS      current
    DESCRIPTION
        "DocuPrint 2000 Series 180 EPS launch configuration
                 version and complete product identifier."
    ::= { xcmPidDP2000S180EPS 1 }
xcmPidDP2000S100EPSMX OBJECT-IDENTITY
    STATUS      current
    DESCRIPTION
        "DocuPrint 2000 Series 100 EPS MX launch configuration
                 model identifier
                 (not a complete product identifier)."
    ::= { xcmPidDP2000EPS 8 }
            -- => SAP PID string = "B28"
xcmPidDP2000S100EPSMXV1 OBJECT-IDENTITY
    STATUS      current
    DESCRIPTION
        "DocuPrint 2000 Series 100 EPS MX launch configuration
                 version and complete product identifier."
    ::= { xcmPidDP2000S100EPSMX 1 }
xcmPidDP2000S115EPSMX OBJECT-IDENTITY
    STATUS      current
    DESCRIPTION
        "DocuPrint 2000 Series 115 EPS MX launch configuration
                 model identifier
                 (not a complete product identifier)."
    ::= { xcmPidDP2000EPS 9 }
            -- => SAP PID string = "B29"
xcmPidDP2000S115EPSMXV1 OBJECT-IDENTITY
    STATUS      current
    DESCRIPTION
        "DocuPrint 2000 Series 115 EPS MX launch configuration
                 version and complete product identifier."
    ::= { xcmPidDP2000S115EPSMX 1 }
xcmPidDP2000S135EPSMX OBJECT-IDENTITY
    STATUS      current
    DESCRIPTION
        "DocuPrint 2000 Series 135 EPS MX launch configuration
                 model identifier
                 (not a complete product identifier)."
    ::= { xcmPidDP2000EPS 17 }
            -- => SAP PID string = "B2A"
xcmPidDP2000S135EPSMXV1 OBJECT-IDENTITY
    STATUS      current
    DESCRIPTION
        "DocuPrint 2000 Series 135 EPS MX launch configuration
                 version and complete product identifier."
    ::= { xcmPidDP2000S135EPSMX 1 }
xcmPidDP2000S155EPSMX OBJECT-IDENTITY
    STATUS      current
    DESCRIPTION
        "DocuPrint 2000 Series 155 EPS MX launch configuration
                 model identifier
                 (not a complete product identifier)."
    ::= { xcmPidDP2000EPS 18 }
            -- => SAP PID string = "B2B"
xcmPidDP2000S155EPSMXV1 OBJECT-IDENTITY
    STATUS      current
    DESCRIPTION
        "DocuPrint 2000 Series 155 EPS MX launch configuration
                 version and complete product identifier."
    ::= { xcmPidDP2000S155EPSMX 1 }
xcmPidDP2000S180EPSMX OBJECT-IDENTITY
    STATUS      current
    DESCRIPTION
        "DocuPrint 2000 Series 180 EPS MX launch configuration
                 model identifier
                 (not a complete product identifier)."
    ::= { xcmPidDP2000EPS 19 }
            -- => SAP PID string = "B2C"
xcmPidDP2000S180EPSMXV1 OBJECT-IDENTITY
    STATUS      current
    DESCRIPTION
        "DocuPrint 2000 Series 180 EPS MX launch configuration
                 version and complete product identifier."
    ::= { xcmPidDP2000S180EPSMX 1 }
xcmPidDP2000S6075 OBJECT-IDENTITY
    STATUS      current
    DESCRIPTION
        "DocuPrint 6075 launch configuration model identifier
                 (not a complete product identifier)."
    ::= { xcmPidDP2000EPS 6 }
            -- => SAP PID string = "B26"
xcmPidDP2000S6075V1 OBJECT-IDENTITY
    STATUS      current
    DESCRIPTION
        "DocuPrint 6075 launch configuration
                 version and complete product identifier."
    ::= { xcmPidDP2000S6075 1 }
xcmPidDP2000S6090 OBJECT-IDENTITY
    STATUS      current
    DESCRIPTION
        "DocuPrint 6090 launch configuration model identifier
                 (not a complete product identifier)."
    ::= { xcmPidDP2000EPS 7 }
            -- => SAP PID string = "B27"
xcmPidDP2000S6090V1 OBJECT-IDENTITY
    STATUS      current
    DESCRIPTION
        "DocuPrint 6090 launch configuration
                 version and complete product identifier."
    ::= { xcmPidDP2000S6090 1 }
xcmPidDP180EPSMicr OBJECT-IDENTITY
    STATUS      current           
    DESCRIPTION
     "DocuPrint DP180 Micr EPS launch model identifier
                 (not a complete product identifier)."
    ::= { xcmPidDP180EPS 2 }
            -- => SAP PID string = "B12"
xcmPidDP180EPSMicrV1 OBJECT-IDENTITY
    STATUS      current           
    DESCRIPTION
        "DocuPrint DP180 Micr EPS launch configuration version,
                 and complete product identifier."
    ::= { xcmPidDP180EPSMicr 1 }
--
--
----------------------------------------------------------------
----------------------------------------------------------------
xcmPidDocuTechs OBJECT-IDENTITY
    STATUS      current
    DESCRIPTION
        "DocuTech product line identifier
                 (not a complete product identifier)."
    ::= { xcmPidProductIdentifiers 5 }
--
--
xcmPidDocuTech6100 OBJECT-IDENTITY
    STATUS      current
    DESCRIPTION
        "DocuTech 6100 product type identifier
                 (not a complete product identifier)."
    ::= { xcmPidDocuTechs 4 }
xcmPidDocuTech6100M1 OBJECT-IDENTITY
    STATUS      current
    DESCRIPTION
        "DocuTech 6100 launch configuration model identifier
                 (not a complete product identifier)."
    ::= { xcmPidDocuTech6100 1 }
            -- => SAP PID string = "541"
xcmPidDocuTech6100M1V1 OBJECT-IDENTITY
    STATUS      current
    DESCRIPTION
        "DocuTech 6100 launch configuration version,
                 and complete product identifier."
    ::= { xcmPidDocuTech6100M1 1 }
xcmPidDocuTech6100M1V2 OBJECT-IDENTITY
    STATUS      current
    DESCRIPTION
        "DocuTech 6100 launch configuration version,
                 and complete product identifier."
    ::= { xcmPidDocuTech6100M1 2 }
xcmPidDocuTech6115 OBJECT-IDENTITY
    STATUS      current
    DESCRIPTION
        "DocuTech 6115 product type identifier
                 (not a complete product identifier)."
    ::= { xcmPidDocuTechs 5 }
xcmPidDocuTech6115M1 OBJECT-IDENTITY
    STATUS      current
    DESCRIPTION
        "DocuTech 6115 launch configuration model identifier
                 (not a complete product identifier)."
    ::= { xcmPidDocuTech6115 1 }
            -- => SAP PID string = "551"
xcmPidDocuTech6115M1V1 OBJECT-IDENTITY
    STATUS      current
    DESCRIPTION
        "DocuTech 6115 launch configuration version,
                 and complete product identifier."
    ::= { xcmPidDocuTech6115M1 1 }
xcmPidDocuTech6115M1V2 OBJECT-IDENTITY
    STATUS      current
    DESCRIPTION
        "DocuTech 6115 launch configuration version,
                 and complete product identifier."
    ::= { xcmPidDocuTech6115M1 2 }
xcmPidDocuTech6135 OBJECT-IDENTITY
    STATUS      current
    DESCRIPTION
        "DocuTech 6135 product type identifier
                 (not a complete product identifier)."
    ::= { xcmPidDocuTechs 2 }
xcmPidDocuTech6135M1 OBJECT-IDENTITY
    STATUS      current
    DESCRIPTION
        "DocuTech 6135 launch configuration model identifier
                 (not a complete product identifier)."
    ::= { xcmPidDocuTech6135 1 }
            -- => SAP PID string = "521"
xcmPidDocuTech6135M1V1 OBJECT-IDENTITY
    STATUS      current
    DESCRIPTION
        "DocuTech 6135 launch configuration version,
                 and complete product identifier."
    ::= { xcmPidDocuTech6135M1 1 }
xcmPidDocuTech6135M1V2 OBJECT-IDENTITY
    STATUS      current
    DESCRIPTION
        "DocuTech 6135 launch configuration version,
                 and complete product identifier."
    ::= { xcmPidDocuTech6135M1 2 }
xcmPidDocuTech6155 OBJECT-IDENTITY
    STATUS      current
    DESCRIPTION
        "DocuTech 6155 product type identifier
                 (not a complete product identifier)."
    ::= { xcmPidDocuTechs 6 }
xcmPidDocuTech6155M1 OBJECT-IDENTITY
    STATUS      current
    DESCRIPTION
        "DocuTech 6155 launch configuration model identifier
                 (not a complete product identifier)."
    ::= { xcmPidDocuTech6155 1 }
            -- => SAP PID string = "561"
xcmPidDocuTech6155M1V1 OBJECT-IDENTITY
    STATUS      current
    DESCRIPTION
        "DocuTech 6155 launch configuration version,
                 and complete product identifier."
    ::= { xcmPidDocuTech6155M1 1 }
xcmPidDocuTech6155M1V2 OBJECT-IDENTITY
    STATUS      current
    DESCRIPTION
        "DocuTech 6155 launch configuration version,
                 and complete product identifier."
    ::= { xcmPidDocuTech6155M1 2 }
xcmPidDocuTech6180 OBJECT-IDENTITY
    STATUS      current
    DESCRIPTION
        "DocuTech 6180 product type identifier
                 (not a complete product identifier)."
    ::= { xcmPidDocuTechs 3 }
xcmPidDocuTech6180M1 OBJECT-IDENTITY
    STATUS      current
    DESCRIPTION
        "DocuTech 6180 launch configuration model identifier
                 (not a complete product identifier)."
    ::= { xcmPidDocuTech6180 1 }
            -- => SAP PID string = "531"
xcmPidDocuTech6180M1V1 OBJECT-IDENTITY
    STATUS      current
    DESCRIPTION
        "DocuTech 6180 launch configuration version,
                 and complete product identifier."
    ::= { xcmPidDocuTech6180M1 1 }
xcmPidDocuTech6180M1V2 OBJECT-IDENTITY
    STATUS      current
    DESCRIPTION
        "DocuTech 6180 launch configuration version,
                 and complete product identifier."
    ::= { xcmPidDocuTech6180M1 2 }
xcmPidDocuTech6075 OBJECT-IDENTITY
    STATUS      current
    DESCRIPTION
        "DocuTech 6075 product type identifier
                 (not a complete product identifier)."
    ::= { xcmPidDocuTechs 7 }
xcmPidDocuTech6075M1 OBJECT-IDENTITY
    STATUS      current
    DESCRIPTION
        "DocuTech 6075 launch configuration model identifier
                 (not a complete product identifier)."
    ::= { xcmPidDocuTech6075 1 }
            -- => SAP PID string = "571"
xcmPidDocuTech6075M1V1 OBJECT-IDENTITY
    STATUS      current
    DESCRIPTION
        "DocuTech 6075 launch configuration version,
                 and complete product identifier."
    ::= { xcmPidDocuTech6075M1 1 }
xcmPidDocuTech6090 OBJECT-IDENTITY
    STATUS      current
    DESCRIPTION
        "DocuTech 6090 product type identifier
                 (not a complete product identifier)."
    ::= { xcmPidDocuTechs 8 }
xcmPidDocuTech6090M1 OBJECT-IDENTITY
    STATUS      current
    DESCRIPTION
        "DocuTech 6090 launch configuration model identifier
                 (not a complete product identifier)."
    ::= { xcmPidDocuTech6090 1 }
            -- => SAP PID string = "581"
xcmPidDocuTech6090M1V1 OBJECT-IDENTITY
    STATUS      current
    DESCRIPTION
        "DocuTech 6090 launch configuration version,
                 and complete product identifier."
    ::= { xcmPidDocuTech6090M1 1 }
--
--
----------------------------------------------------------------
--
----------------------------------------------------------------
xcmPidNuveraProductLine OBJECT-IDENTITY
    STATUS      current
    DESCRIPTION
        "Nuvera product line identifier
                 (not a complete product identifier)."
    ::= { xcmPidProductIdentifiers 23 }
--
--
--
--
xcmPidNuveraEAProductionSystemFamily OBJECT-IDENTITY
    STATUS      current
    DESCRIPTION
        "Xerox Nuvera EA Production System family
         identifier (not a complete product identifier)."
    ::= { xcmPidNuveraProductLine 17 }
xcmPidNuvera100x120x144x157EAPS OBJECT-IDENTITY
    STATUS      current
    DESCRIPTION
        "Xerox Nuvera 100x120x144x157 EAPS system model
         identifier (not a complete product identifier)."
    ::= { xcmPidNuveraEAProductionSystemFamily 1 }
--
--
xcmPidNuvera100x120x144x157EAPSEmbeddedFFPS OBJECT-IDENTITY
    STATUS      current
    DESCRIPTION
         "Xerox Nuvera 100x120x144x157 EAPS with an 
         embedded FreeFlow Print Server (FFPS) DFE
         system configuration model identifier 
         (not a complete product identifier)."
    ::= { xcmPidNuvera100x120x144x157EAPS 1 }
xcmPidNuvera100x120x144x157EAPSEmbeddedFFPSV1 OBJECT-IDENTITY
    STATUS      current
    DESCRIPTION
         "Xerox Nuvera 100x120x144x157 EAPS with an 
         embedded FreeFlow Print Server (FFPS) DFE
         device launch configuration version and  
         complete product identifier."
    ::= { xcmPidNuvera100x120x144x157EAPSEmbeddedFFPS 1 }
xcmPidNuveraEAPerfectingProductionSystemFamily OBJECT-IDENTITY
    STATUS      current
    DESCRIPTION
        "Xerox Nuvera EA Perfecting Production System
         family identifier (not a complete product identifier)."
    ::= { xcmPidNuveraProductLine 18 }
xcmPidNuvera200x288x314EAPPS OBJECT-IDENTITY
    STATUS      current
    DESCRIPTION
        "Xerox Nuvera 200x288x314 EAPPS system model
         identifier (not a complete product identifier)."
    ::= { xcmPidNuveraEAPerfectingProductionSystemFamily 1 }
--
--
xcmPidNuvera200x288x314EAPPSEmbeddedFFPS OBJECT-IDENTITY
    STATUS      current
    DESCRIPTION
         "Xerox Nuvera 200x288x314 EAPPS with an 
         embedded FreeFlow Print Server (FFPS) DFE
         system configuration model identifier 
         (not a complete product identifier)."
    ::= { xcmPidNuvera200x288x314EAPPS 1 }
xcmPidNuvera200x288x314EAPPSEmbeddedFFPSv1 OBJECT-IDENTITY
    STATUS      current
    DESCRIPTION
         "Xerox Nuvera 200x288x314 EAPPS with an 
         embedded FreeFlow Print Server (FFPS) DFE
         device launch configuration version and  
         complete product identifier."
    ::= { xcmPidNuvera200x288x314EAPPSEmbeddedFFPS 1 }
xcmPidNuveraMXProductionSystemFamily OBJECT-IDENTITY
    STATUS      current
    DESCRIPTION
        "Xerox Nuvera MX Production System family identifier
         (not a complete product identifier)."
    ::= { xcmPidNuveraProductLine 19 }
xcmPidNuvera100x120x144MXPS OBJECT-IDENTITY
    STATUS      current
    DESCRIPTION
        "Xerox Nuvera 100x120x144 MXPS system model
         identifier (not a complete product identifier)."
    ::= { xcmPidNuveraMXProductionSystemFamily 1 }
--
--
xcmPidNuvera100x120x144MXPSEmbeddedFFPS OBJECT-IDENTITY
    STATUS      current
    DESCRIPTION
         "Xerox Nuvera 100x120x144 MXPS with an 
         embedded FreeFlow Print Server (FFPS) DFE
         system configuration model identifier 
         (not a complete product identifier)."
    ::= { xcmPidNuvera100x120x144MXPS 1 }
xcmPidNuvera100x120x144MXPSEmbeddedFFPSV1 OBJECT-IDENTITY
    STATUS      current
    DESCRIPTION
         "Xerox Nuvera 100x120x144 MXPS with an 
         embedded FreeFlow Print Server (FFPS) DFE
         device launch configuration version and  
         complete product identifier."
    ::= { xcmPidNuvera100x120x144MXPSEmbeddedFFPS 1 }
xcmPidNuveraMXPerfectingProductionSystemFamily OBJECT-IDENTITY
    STATUS      current
    DESCRIPTION
        "Xerox Nuvera MX Perfecting Production System
         family identifier (not a complete product identifier)."
    ::= { xcmPidNuveraProductLine 20 }
xcmPidNuvera200x288MXPPS OBJECT-IDENTITY
    STATUS      current
    DESCRIPTION
        "Xerox Nuvera 200x288 MXPPS system model
         identifier (not a complete product identifier)."
    ::= { xcmPidNuveraMXPerfectingProductionSystemFamily 1 }
--
--
xcmPidNuvera200x288MXPPSEmbeddedFFPS OBJECT-IDENTITY
    STATUS      current
    DESCRIPTION
         "Xerox Nuvera 200x288 MXPPS with an 
         embedded FreeFlow Print Server (FFPS) DFE
         system configuration model identifier 
         (not a complete product identifier)."
    ::= { xcmPidNuvera200x288MXPPS 1 }
xcmPidNuvera200x288MXPPSEmbeddedFFPSV1 OBJECT-IDENTITY
    STATUS      current
    DESCRIPTION
         "Xerox Nuvera 200x288 MXPPS with an 
         embedded FreeFlow Print Server (FFPS) DFE
         device launch configuration version and  
         complete product identifier."
    ::= { xcmPidNuvera200x288MXPPSEmbeddedFFPS 1 }
-------------------------------------------------------
-------------------------------------------------------
xcmPidDocuTechHiColorEPS OBJECT-IDENTITY
    STATUS      current
    DESCRIPTION
        "DocuTech Highlight Color EPS product type identifier
                 (not a complete product identifier)."
 ::= { xcmPidDocuTechs 19 }
--
--
-------------------------------------------------------
-------------------------------------------------------
xcmPidDocuSPDFE OBJECT-IDENTITY
    STATUS      current
    DESCRIPTION
        "DocuSP-DFE B/W Copier / Printer product type identifier
                 (not a complete product identifier)."
 ::= { xcmPidDocuTechs 20 }
--
--
-------------------------------------------------------
-------------------------------------------------------
xcmPidDocuSPDFEColor OBJECT-IDENTITY
    STATUS      current
    DESCRIPTION
        "DocuSP-DFE Color Copier / Printer product type identifier
                 (not a complete product identifier)."
 ::= { xcmPidDocuTechs 21 }
--
--
-------------------------------------------------------
-------------------------------------------------------
xcmPidDocuSPTEAK OBJECT-IDENTITY
    STATUS      current
    DESCRIPTION
        "Xerox 41xx Copier / Printer with Free Flow
          Print Server product type identifier
                 (not a complete product identifier)."
 ::= { xcmPidDocuTechs 22 }
--
--
--
--
xcmPidXeroxWideFormat OBJECT-IDENTITY
    STATUS      current
    DESCRIPTION
        "Xerox Wide Format Printers product line identifier
                 (not a complete product identifier)."
    ::= { xcmPidProductIdentifiers 22 }
--
--
xcmPidColorQube OBJECT-IDENTITY
    STATUS      current
    DESCRIPTION
        "ColorQube product line identifier
                 (not a complete product identifier)."
    ::= { xcmPidProductIdentifiers 24 }
xcmPidColorQube9200 OBJECT-IDENTITY
    STATUS      current
    DESCRIPTION
        "Xerox ColorQube 9200 family identifier
           (not a complete product identifier)."
    ::= { xcmPidColorQube 1 }
xcmPidColorQube9201 OBJECT-IDENTITY
    STATUS      current
    DESCRIPTION
        "Xerox ColorQube 9201 model identifier
           (not a complete product identifier)."
    ::= { xcmPidColorQube9200 1 }
            -- => SAP PID string = "H11"
--
-- The MODEL NAME used for the PNP ID   "ColorQube 9201"
--
xcmPidColorQube9201C1 OBJECT-IDENTITY
    STATUS      current
    DESCRIPTION
        "Xerox ColorQube 9201
           model and configuration 1 identifier
           (not a complete product identifier)."
    ::= { xcmPidColorQube9201 1 }
xcmPidColorQube9201C1V1 OBJECT-IDENTITY
    STATUS      current
    DESCRIPTION
        "Xerox ColorQube 9201
            launch model, configuration 1, version 1.
            A complete product identifier."
    ::= { xcmPidColorQube9201C1 1 }
xcmPidColorQube9201C1V2 OBJECT-IDENTITY
    STATUS      current
    DESCRIPTION
        "Xerox ColorQube 9201
            launch model, configuration 1, version 2.
            A complete product identifier."
    ::= { xcmPidColorQube9201C1 2 }
xcmPidColorQube9201C1V3 OBJECT-IDENTITY
    STATUS      current
    DESCRIPTION
        "Xerox ColorQube 9201
            launch model, configuration 1, version 3.
            A complete product identifier."
    ::= { xcmPidColorQube9201C1 3 }
xcmPidColorQube9201C2 OBJECT-IDENTITY
    STATUS      current
    DESCRIPTION
        "Xerox ColorQube 9201
           model and configuration 2 identifier
           (not a complete product identifier)."
    ::= { xcmPidColorQube9201 2 }
xcmPidColorQube9201C2V1 OBJECT-IDENTITY
    STATUS      current
    DESCRIPTION
        "Xerox ColorQube 9201
            launch model, configuration 2, version 1.
            A complete product identifier."
    ::= { xcmPidColorQube9201C2 1 }
xcmPidColorQube9201C2V2 OBJECT-IDENTITY
    STATUS      current
    DESCRIPTION
        "Xerox ColorQube 9201
            launch model, configuration 2, version 2.
            A complete product identifier."
    ::= { xcmPidColorQube9201C2 2 }
xcmPidColorQube9202 OBJECT-IDENTITY
    STATUS      current
    DESCRIPTION
        "Xerox ColorQube 9202 model identifier
           (not a complete product identifier)."
    ::= { xcmPidColorQube9200 2 }
            -- => SAP PID string = "H12"
--
-- The MODEL NAME used for the PNP ID   "ColorQube 9202"
--
xcmPidColorQube9202C1 OBJECT-IDENTITY
    STATUS      current
    DESCRIPTION
        "Xerox ColorQube 9202
           model and configuration 1 identifier
           (not a complete product identifier)."
    ::= { xcmPidColorQube9202 1 }
xcmPidColorQube9202C1V1 OBJECT-IDENTITY
    STATUS      current
    DESCRIPTION
        "Xerox ColorQube 9202
            launch model, configuration 1, version 1.
            A complete product identifier."
    ::= { xcmPidColorQube9202C1 1 }
xcmPidColorQube9202C1V2 OBJECT-IDENTITY
    STATUS      current
    DESCRIPTION
        "Xerox ColorQube 9202
            launch model, configuration 1, version 2.
            A complete product identifier."
    ::= { xcmPidColorQube9202C1 2 }
xcmPidColorQube9202C1V3 OBJECT-IDENTITY
    STATUS      current
    DESCRIPTION
        "Xerox ColorQube 9202
            launch model, configuration 1, version 3.
            A complete product identifier."
    ::= { xcmPidColorQube9202C1 3 }
xcmPidColorQube9202C2 OBJECT-IDENTITY
    STATUS      current
    DESCRIPTION
        "Xerox ColorQube 9202
           model and configuration 2 identifier
           (not a complete product identifier)."
    ::= { xcmPidColorQube9202 2 }
xcmPidColorQube9202C2V1 OBJECT-IDENTITY
    STATUS      current
    DESCRIPTION
        "Xerox ColorQube 9202
            launch model, configuration 2, version 1.
            A complete product identifier."
    ::= { xcmPidColorQube9202C2 1 }
xcmPidColorQube9202C2V2 OBJECT-IDENTITY
    STATUS      current
    DESCRIPTION
        "Xerox ColorQube 9202
            launch model, configuration 2, version 2.
            A complete product identifier."
    ::= { xcmPidColorQube9202C2 2 }
xcmPidColorQube9203 OBJECT-IDENTITY
    STATUS      current
    DESCRIPTION
        "Xerox ColorQube 9203 model identifier
           (not a complete product identifier)."
    ::= { xcmPidColorQube9200 3 }
            -- => SAP PID string = "H13"
--
-- The MODEL NAME used for the PNP ID   "ColorQube 9203"
--
xcmPidColorQube9203C1 OBJECT-IDENTITY
    STATUS      current
    DESCRIPTION
        "Xerox ColorQube 9203
           model and configuration 1 identifier
           (not a complete product identifier)."
    ::= { xcmPidColorQube9203 1 }
xcmPidColorQube9203C1V1 OBJECT-IDENTITY
    STATUS      current
    DESCRIPTION
        "Xerox ColorQube 9203
            launch model, configuration 1, version 1.
            A complete product identifier."
    ::= { xcmPidColorQube9203C1 1 }
xcmPidColorQube9203C1V2 OBJECT-IDENTITY
    STATUS      current
    DESCRIPTION
        "Xerox ColorQube 9203
            launch model, configuration 1, version 2.
            A complete product identifier."
    ::= { xcmPidColorQube9203C1 2 }
xcmPidColorQube9203C1V3 OBJECT-IDENTITY
    STATUS      current
    DESCRIPTION
        "Xerox ColorQube 9203
            launch model, configuration 1, version 3.
            A complete product identifier."
    ::= { xcmPidColorQube9203C1 3 }
xcmPidColorQube9203C2 OBJECT-IDENTITY
    STATUS      current
    DESCRIPTION
        "Xerox ColorQube 9203
           model and configuration 2 identifier
           (not a complete product identifier)."
    ::= { xcmPidColorQube9203 2 }
xcmPidColorQube9203C2V1 OBJECT-IDENTITY
    STATUS      current
    DESCRIPTION
        "Xerox ColorQube 9203
            launch model, configuration 2, version 1.
            A complete product identifier."
    ::= { xcmPidColorQube9203C2 1 }
xcmPidColorQube9203C2V2 OBJECT-IDENTITY
    STATUS      current
    DESCRIPTION
        "Xerox ColorQube 9203
            launch model, configuration 2, version 2.
            A complete product identifier."
    ::= { xcmPidColorQube9203C2 2 }
--
--
xcmPidColorQube8x00 OBJECT-IDENTITY
    STATUS      current
    DESCRIPTION
        "Xerox ColorQube 8x00 family identifier
           (not a complete product identifier)."
    ::= { xcmPidColorQube 3 }
xcmPidColorQube8700 OBJECT-IDENTITY
    STATUS      current
    DESCRIPTION
        "Xerox ColorQube 8700 model identifier
           (not a complete product identifier)."
    ::= { xcmPidColorQube8x00 1 }
            -- => SAP PID string = "H31"
xcmPidColorQube8700S OBJECT-IDENTITY
    STATUS      current
    DESCRIPTION
        "Xerox ColorQube 8700
           model and S configuration identifier
           (not a complete product identifier)."
    ::= { xcmPidColorQube8700 1 }
--
-- The MODEL NAME used for the PNP ID   "ColorQube 8700S"
--
xcmPidColorQube8700Sv1 OBJECT-IDENTITY
    STATUS      current
    DESCRIPTION
        "Xerox ColorQube 8700
            launch model, S configuration, version 1.
            A complete product identifier."
    ::= { xcmPidColorQube8700S 1 }
xcmPidColorQube8700X OBJECT-IDENTITY
    STATUS      current
    DESCRIPTION
        "Xerox ColorQube 8700
           model and X configuration identifier
           (not a complete product identifier)."
    ::= { xcmPidColorQube8700 2 }
--
-- The MODEL NAME used for the PNP ID   "ColorQube 8700X"
--
xcmPidColorQube8700Xv1 OBJECT-IDENTITY
    STATUS      current
    DESCRIPTION
        "Xerox ColorQube 8700
            launch model, X configuration, version 1.
            A complete product identifier."
    ::= { xcmPidColorQube8700X 1 }
xcmPidColorQube8700XF OBJECT-IDENTITY
    STATUS      current
    DESCRIPTION
        "Xerox ColorQube 8700
           model and XF configuration identifier
           (not a complete product identifier)."
    ::= { xcmPidColorQube8700 3 }
--
-- The MODEL NAME used for the PNP ID   "ColorQube 8700XF"
--
xcmPidColorQube8700XFv1 OBJECT-IDENTITY
    STATUS      current
    DESCRIPTION
        "Xerox ColorQube 8700
            launch model, XF configuration, version 1.
            A complete product identifier."
    ::= { xcmPidColorQube8700XF 1 }
xcmPidColorQube8900 OBJECT-IDENTITY
    STATUS      current
    DESCRIPTION
        "Xerox ColorQube 8900 model identifier
           (not a complete product identifier)."
    ::= { xcmPidColorQube8x00 2 }
            -- => SAP PID string = "H32"
xcmPidColorQube8900X OBJECT-IDENTITY
    STATUS      current
    DESCRIPTION
        "Xerox ColorQube 8900
           model and X configuration identifier
           (not a complete product identifier)."
    ::= { xcmPidColorQube8900 2 }
--
-- The MODEL NAME used for the PNP ID   "ColorQube 8900X"
--
xcmPidColorQube8900Xv1 OBJECT-IDENTITY
    STATUS      current
    DESCRIPTION
        "Xerox ColorQube 8900
            launch model, X configuration, version 1.
            A complete product identifier."
    ::= { xcmPidColorQube8900X 1 }
--
xcmPidColorQube8900S OBJECT-IDENTITY
    STATUS      current
    DESCRIPTION
        "Xerox ColorQube 8900
           model and S configuration identifier
           (not a complete product identifier)."
    ::= { xcmPidColorQube8900 3 }
-- The MODEL NAME used for the PNP ID   "ColorQube 8900S"
--
xcmPidColorQube8900Sv1 OBJECT-IDENTITY
    STATUS      current
    DESCRIPTION
        "Xerox ColorQube 8900
            launch model, S configuration, version 1.
            A complete product identifier."
    ::= { xcmPidColorQube8900S 1 }
xcmPidColorQube9300 OBJECT-IDENTITY
    STATUS      current
    DESCRIPTION
        "Xerox ColorQube 9300 family identifier
           (not a complete product identifier)."
    ::= { xcmPidColorQube 4 }
xcmPidColorQube9301 OBJECT-IDENTITY
    STATUS      current
    DESCRIPTION
        "Xerox ColorQube 9301 model identifier
           (not a complete product identifier)."
    ::= { xcmPidColorQube9300 1 }
            -- => SAP PID string = "H41"
--
-- The MODEL NAME used for the PNP ID   "ColorQube 9301"
--
xcmPidColorQube9301C1 OBJECT-IDENTITY
    STATUS      current
    DESCRIPTION
        "Xerox ColorQube 9301
           model and configuration 1 identifier
           (not a complete product identifier)."
    ::= { xcmPidColorQube9301 1 }
xcmPidColorQube9301C1V1 OBJECT-IDENTITY
    STATUS      current
    DESCRIPTION
        "Xerox ColorQube 9301
            launch model, configuration 1, version 1.
            A complete product identifier."
    ::= { xcmPidColorQube9301C1 1 }
xcmPidColorQube9301C1V2 OBJECT-IDENTITY
    STATUS      current
    DESCRIPTION
        "Xerox ColorQube 9301
            launch model, configuration 1, version 2.
            A complete product identifier."
    ::= { xcmPidColorQube9301C1 2 }
xcmPidColorQube9302 OBJECT-IDENTITY
    STATUS      current
    DESCRIPTION
        "Xerox ColorQube 9302 model identifier
           (not a complete product identifier)."
    ::= { xcmPidColorQube9300 2 }
            -- => SAP PID string = "H42"
--
-- The MODEL NAME used for the PNP ID   "ColorQube 9302"
--
xcmPidColorQube9302C1 OBJECT-IDENTITY
    STATUS      current
    DESCRIPTION
        "Xerox ColorQube 9302
           model and configuration 1 identifier
           (not a complete product identifier)."
    ::= { xcmPidColorQube9302 1 }
xcmPidColorQube9302C1V1 OBJECT-IDENTITY
    STATUS      current
    DESCRIPTION
        "Xerox ColorQube 9302
            launch model, configuration 1, version 1.
            A complete product identifier."
    ::= { xcmPidColorQube9302C1 1 }
xcmPidColorQube9302C1V2 OBJECT-IDENTITY
    STATUS      current
    DESCRIPTION
        "Xerox ColorQube 9302
            launch model, configuration 1, version 2.
            A complete product identifier."
    ::= { xcmPidColorQube9302C1 2 }
xcmPidColorQube9303 OBJECT-IDENTITY
    STATUS      current
    DESCRIPTION
        "Xerox ColorQube 9303 model identifier
           (not a complete product identifier)."
    ::= { xcmPidColorQube9300 3 }
            -- => SAP PID string = "H43"
--
-- The MODEL NAME used for the PNP ID   "ColorQube 9303"
--
xcmPidColorQube9303C1 OBJECT-IDENTITY
    STATUS      current
    DESCRIPTION
        "Xerox ColorQube 9303
           model and configuration 1 identifier
           (not a complete product identifier)."
    ::= { xcmPidColorQube9303 1 }
xcmPidColorQube9303C1V1 OBJECT-IDENTITY
    STATUS      current
    DESCRIPTION
        "Xerox ColorQube 9303
            launch model, configuration 1, version 1.
            A complete product identifier."
    ::= { xcmPidColorQube9303C1 1 }
xcmPidColorQube9303C1V2 OBJECT-IDENTITY
    STATUS      current
    DESCRIPTION
        "Xerox ColorQube 9303
            launch model, configuration 1, version 2.
            A complete product identifier."
    ::= { xcmPidColorQube9303C1 2 }
--
--
----------------------------------------------------------------
----------------------------------------------------------------
xcmPidFXSystems OBJECT-IDENTITY
    STATUS      current
    DESCRIPTION
        "Fuji Xerox Systems product line identifier
                 (not a complete product identifier)."
    ::= { xcmPidProductIdentifiers 30 }
--
--
----------------------------------------------------------------
----------------------------------------------------------------
--
--
----------------------------------------------------------------
----------------------------------------------------------------
xcmPidEPCProductLine OBJECT-IDENTITY
    STATUS      current
    DESCRIPTION
        "Xerox Entry-level Production Color product line
         identifier (not a complete product identifier)."
    ::= { xcmPidProductIdentifiers 31 }
--
--
----------------------------------------------------------------
----------------------------------------------------------------
xcmPidLPMProductLine OBJECT-IDENTITY
    STATUS      current
    DESCRIPTION
        "Xerox Light Production Monochrome product line
         identifier (not a complete product identifier)."
    ::= { xcmPidProductIdentifiers 32 }
--
--
----------------------------------------------------------------
----------------------------------------------------------------
xcmPidDigitalPrintingPressProductLine OBJECT-IDENTITY
    STATUS      current
    DESCRIPTION
        "Xerox Digital Printing Press product line
         identifier (not a complete product identifier)."
    ::= { xcmPidProductIdentifiers 33 }
--
--
----------------------------------------------------------------
----------------------------------------------------------------
xcmPidDedPrintServers OBJECT-IDENTITY
    STATUS      current
    DESCRIPTION
        "Dedicated print servers product line identifier
                 (not a complete product identifier)."
    ::= { xcmPidProductIdentifiers 8 }
--
--
xcmPidPhaserPrintServer OBJECT-IDENTITY
    STATUS      current
    DESCRIPTION
        "Xerox Fast Port dedicated print server product type identifier
                 (not a complete product identifier)."
    ::= { xcmPidDedPrintServers 2 }
xcmPidPhaserEX7750 OBJECT-IDENTITY
    STATUS      current
    DESCRIPTION
        "Xerox Phaser Fiery model identifier
                 (not a complete product identifier)."
    ::= { xcmPidPhaserPrintServer 1 }
            -- => SAP PID string = "821"
xcmPidPhaserEX7750GX OBJECT-IDENTITY
    STATUS      current
    DESCRIPTION
        "Xerox Phaser EX7750 Controller with Phaser 7750GX 
         Printer configuration."
    ::= { xcmPidPhaserEX7750 1 }
xcmPidPhaserEX7750DXF OBJECT-IDENTITY
    STATUS      current
    DESCRIPTION
        "Xerox Phaser EX7750 Controller with Phaser 7750DXF 
         Printer configuration."
    ::= { xcmPidPhaserEX7750 2 }
          mib-2      OBJECT IDENTIFIER ::= { mgmt 1 }
          DisplayString ::=
              OCTET STRING
          --
          PhysAddress ::=
              OCTET STRING
          system       OBJECT IDENTIFIER ::= { mib-2 1 }
          interfaces   OBJECT IDENTIFIER ::= { mib-2 2 }
          at           OBJECT IDENTIFIER ::= { mib-2 3 }
          ip           OBJECT IDENTIFIER ::= { mib-2 4 }
          icmp         OBJECT IDENTIFIER ::= { mib-2 5 }
          tcp          OBJECT IDENTIFIER ::= { mib-2 6 }
          udp          OBJECT IDENTIFIER ::= { mib-2 7 }
          egp          OBJECT IDENTIFIER ::= { mib-2 8 }
          transmission OBJECT IDENTIFIER ::= { mib-2 10 }
          snmp         OBJECT IDENTIFIER ::= { mib-2 11 }
          ifNumber OBJECT-TYPE
              SYNTAX  INTEGER
              ACCESS  read-only
              STATUS  mandatory
              DESCRIPTION
                      "The number of network interfaces (regardless of
                      their current state) present on this system."
              ::= { interfaces 1 }
          ifTable OBJECT-TYPE
              SYNTAX  SEQUENCE OF IfEntry
              ACCESS  not-accessible
              STATUS  mandatory
              DESCRIPTION
                      "A list of interface entries.  The number of
                      entries is given by the value of ifNumber."
              ::= { interfaces 2 }
          ifEntry OBJECT-TYPE
              SYNTAX  IfEntry
              ACCESS  not-accessible
              STATUS  mandatory
              DESCRIPTION
                      "An interface entry containing objects at the
                      subnetwork layer and below for a particular
                      interface."
              INDEX   { ifIndex }
              ::= { ifTable 1 }
          IfEntry ::=
              SEQUENCE {
                  ifIndex
                      INTEGER,
                  ifDescr
                      DisplayString,
                  ifType
                      INTEGER,
                  ifMtu
                      INTEGER,
                  ifSpeed
                      Gauge,
                  ifPhysAddress
                      PhysAddress,
                  ifAdminStatus
                      INTEGER,
                  ifOperStatus
                      INTEGER,
                  ifLastChange
                      TimeTicks,
                  ifInOctets
                      Counter,
                  ifInUcastPkts
                      Counter,
                  ifInNUcastPkts
                      Counter,
                  ifInDiscards
                      Counter,
                  ifInErrors
                      Counter,
                  ifInUnknownProtos
                      Counter,
                  ifOutOctets
                      Counter,
                  ifOutUcastPkts
                      Counter,
                  ifOutNUcastPkts
                      Counter,
                  ifOutDiscards
                      Counter,
                  ifOutErrors
                      Counter,
                  ifOutQLen
                      Gauge,
                  ifSpecific
                      OBJECT IDENTIFIER
              }
          ifIndex OBJECT-TYPE
              SYNTAX  INTEGER
              ACCESS  read-only
              STATUS  mandatory
              DESCRIPTION
                      "A unique value for each interface.  Its value
                      ranges between 1 and the value of ifNumber.  The
                      value for each interface must remain constant at
                      least from one re-initialization of the entity's
                      network management system to the next re-
                      initialization."
              ::= { ifEntry 1 }
          ifDescr OBJECT-TYPE
              SYNTAX  DisplayString (SIZE (0..255))
              ACCESS  read-only
              STATUS  mandatory
              DESCRIPTION
                      "A textual string containing information about the
                      interface.  This string should include the name of
                      the manufacturer, the product name and the version
                      of the hardware interface."
              ::= { ifEntry 2 }
          ifType OBJECT-TYPE
              SYNTAX  INTEGER {
                          other(1),          
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           
                          e1(19),            
                          basicISDN(20),
                          primaryISDN(21),   
                          propPointToPointSerial(22),
                          ppp(23),
                          softwareLoopback(24),
                          eon(25),            
                          ethernet-3Mbit(26),
                          nsip(27),           
                          slip(28),           
                          ultra(29),          
                          ds3(30),            
                          sip(31),            
                          frame-relay(32)
                      }
              ACCESS  read-only
              STATUS  mandatory
              DESCRIPTION
                      "The type of interface, distinguished according to
                      the physical/link protocol(s) immediately `below'
                      the network layer in the protocol stack."
              ::= { ifEntry 3 }
          ifMtu OBJECT-TYPE
              SYNTAX  INTEGER
              ACCESS  read-only
              STATUS  mandatory
              DESCRIPTION
                      "The size of the largest datagram which can be
                      sent/received on the interface, specified in
                      octets.  For interfaces that are used for
                      transmitting network datagrams, this is the size
                      of the largest network datagram that can be sent
                      on the interface."
              ::= { ifEntry 4 }
          ifSpeed OBJECT-TYPE
              SYNTAX  Gauge
              ACCESS  read-only
              STATUS  mandatory
              DESCRIPTION
                      "An estimate of the interface's current bandwidth
                      in bits per second.  For interfaces which do not
                      vary in bandwidth or for those where no accurate
                      estimation can be made, this object should contain
                      the nominal bandwidth."
              ::= { ifEntry 5 }
          ifPhysAddress OBJECT-TYPE
              SYNTAX  PhysAddress
              ACCESS  read-only
              STATUS  mandatory
              DESCRIPTION
                      "The interface's address at the protocol layer
                      immediately `below' the network layer in the
                      protocol stack.  For interfaces which do not have
                      such an address (e.g., a serial line), this object
                      should contain an octet string of zero length."
              ::= { ifEntry 6 }
          ifAdminStatus OBJECT-TYPE
              SYNTAX  INTEGER {
                          up(1),       
                          down(2),
                          testing(3)   
                      }
              ACCESS  read-write
              STATUS  mandatory
              DESCRIPTION
                      "The desired state of the interface.  The
                      testing(3) state indicates that no operational
                      packets can be passed."
              ::= { ifEntry 7 }
          ifOperStatus OBJECT-TYPE
              SYNTAX  INTEGER {
                          up(1),       
                          down(2),
                          testing(3)   
                      }
              ACCESS  read-only
              STATUS  mandatory
              DESCRIPTION
                      "The current operational state of the interface.
                      The testing(3) state indicates that no operational
                      packets can be passed."
              ::= { ifEntry 8 }
          ifLastChange OBJECT-TYPE
              SYNTAX  TimeTicks
              ACCESS  read-only
              STATUS  mandatory
              DESCRIPTION
                      "The value of sysUpTime at the time the interface
                      entered its current operational state.  If the
                      current state was entered prior to the last re-
                      initialization of the local network management
                      subsystem, then this object contains a zero
                      value."
              ::= { ifEntry 9 }
          ifInOctets OBJECT-TYPE
              SYNTAX  Counter
              ACCESS  read-only
              STATUS  mandatory
              DESCRIPTION
                      "The total number of octets received on the
                      interface, including framing characters."
              ::= { ifEntry 10 }
          ifInUcastPkts OBJECT-TYPE
              SYNTAX  Counter
              ACCESS  read-only
              STATUS  mandatory
              DESCRIPTION
                      "The number of subnetwork-unicast packets
                      delivered to a higher-layer protocol."
              ::= { ifEntry 11 }
          ifInNUcastPkts OBJECT-TYPE
              SYNTAX  Counter
              ACCESS  read-only
              STATUS  mandatory
              DESCRIPTION
                      "The number of non-unicast (i.e., subnetwork-
                      broadcast or subnetwork-multicast) packets
                      delivered to a higher-layer protocol."
              ::= { ifEntry 12 }
          ifInDiscards OBJECT-TYPE
              SYNTAX  Counter
              ACCESS  read-only
              STATUS  mandatory
              DESCRIPTION
                      "The number of inbound packets which were chosen
                      to be discarded even though no errors had been
                      detected to prevent their being deliverable to a
                      higher-layer protocol.  One possible reason for
                      discarding such a packet could be to free up
                      buffer space."
              ::= { ifEntry 13 }
          ifInErrors OBJECT-TYPE
              SYNTAX  Counter
              ACCESS  read-only
              STATUS  mandatory
              DESCRIPTION
                      "The number of inbound packets that contained
                      errors preventing them from being deliverable to a
                      higher-layer protocol."
              ::= { ifEntry 14 }
          ifInUnknownProtos OBJECT-TYPE
              SYNTAX  Counter
              ACCESS  read-only
              STATUS  mandatory
              DESCRIPTION
                      "The number of packets received via the interface
                      which were discarded because of an unknown or
                      unsupported protocol."
              ::= { ifEntry 15 }
          ifOutOctets OBJECT-TYPE
              SYNTAX  Counter
              ACCESS  read-only
              STATUS  mandatory
              DESCRIPTION
                      "The total number of octets transmitted out of the
                      interface, including framing characters."
              ::= { ifEntry 16 }
          ifOutUcastPkts OBJECT-TYPE
              SYNTAX  Counter
              ACCESS  read-only
              STATUS  mandatory
              DESCRIPTION
                      "The total number of packets that higher-level
                      protocols requested be transmitted to a
                      subnetwork-unicast address, including those that
                      were discarded or not sent."
              ::= { ifEntry 17 }
          ifOutNUcastPkts OBJECT-TYPE
              SYNTAX  Counter
              ACCESS  read-only
              STATUS  mandatory
              DESCRIPTION
                      "The total number of packets that higher-level
                      protocols requested be transmitted to a non-
                      unicast (i.e., a subnetwork-broadcast or
                      subnetwork-multicast) address, including those
                      that were discarded or not sent."
              ::= { ifEntry 18 }
          ifOutDiscards OBJECT-TYPE
              SYNTAX  Counter
              ACCESS  read-only
              STATUS  mandatory
              DESCRIPTION
                      "The number of outbound packets which were chosen
                      to be discarded even though no errors had been
                      detected to prevent their being transmitted.  One
                      possible reason for discarding such a packet could
                      be to free up buffer space."
              ::= { ifEntry 19 }
          ifOutErrors OBJECT-TYPE
              SYNTAX  Counter
              ACCESS  read-only
              STATUS  mandatory
              DESCRIPTION
                      "The number of outbound packets that could not be
                      transmitted because of errors."
              ::= { ifEntry 20 }
          ifOutQLen OBJECT-TYPE
              SYNTAX  Gauge
              ACCESS  read-only
              STATUS  mandatory
              DESCRIPTION
                      "The length of the output packet queue (in
                      packets)."
              ::= { ifEntry 21 }
          ifSpecific OBJECT-TYPE
              SYNTAX  OBJECT IDENTIFIER
              ACCESS  read-only
              STATUS  mandatory
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { ifEntry 22 }
          atTable OBJECT-TYPE
              SYNTAX  SEQUENCE OF AtEntry
              ACCESS  not-accessible
              STATUS  deprecated
              DESCRIPTION
                      "The Address Translation tables contain the
                      NetworkAddress to `physical' address equivalences.
                      Some interfaces do not use translation tables for
                      determining address equivalences (e.g., DDN-X.25
                      has an algorithmic method); if all interfaces are
                      of this type, then the Address Translation table
                      is empty, i.e., has zero entries."
              ::= { at 1 }
          atEntry OBJECT-TYPE
              SYNTAX  AtEntry
              ACCESS  not-accessible
              STATUS  deprecated
              DESCRIPTION
                      "Each entry contains one NetworkAddress to
                      `physical' address equivalence."
              INDEX   { atIfIndex,
                        atNetAddress }
              ::= { atTable 1 }
          AtEntry ::=
              SEQUENCE {
                  atIfIndex
                      INTEGER,
                  atPhysAddress
                      PhysAddress,
                  atNetAddress
                      NetworkAddress
              }
          atIfIndex OBJECT-TYPE
              SYNTAX  INTEGER
              ACCESS  read-write
              STATUS  deprecated
              DESCRIPTION
                      "The interface on which this entry's equivalence
                      is effective.  The interface identified by a
                      particular value of this index is the same
                      interface as identified by the same value of
                      ifIndex."
              ::= { atEntry 1 }
          atPhysAddress OBJECT-TYPE
              SYNTAX  PhysAddress
              ACCESS  read-write
              STATUS  deprecated
              DESCRIPTION
                      "The media-dependent `physical' address.
                      Setting this object to a null string (one of zero
                      length) has the effect of invaliding the
                      corresponding entry in the atTable object.  That
                      is, it effectively dissasociates the interface
                      identified with said entry from the mapping
                      identified with said entry.  It is an
                      implementation-specific matter as to whether the
                      agent removes an invalidated entry from the table.
                      Accordingly, management stations must be prepared
                      to receive tabular information from agents that
                      corresponds to entries not currently in use.
                      Proper interpretation of such entries requires
                      examination of the relevant atPhysAddress object."
              ::= { atEntry 2 }
          atNetAddress OBJECT-TYPE
              SYNTAX  NetworkAddress
              ACCESS  read-write
              STATUS  deprecated
              DESCRIPTION
                      "The NetworkAddress (e.g., the IP address)
                      corresponding to the media-dependent `physical'
                      address."
              ::= { atEntry 3 }
          ipForwarding OBJECT-TYPE
              SYNTAX  INTEGER {
                          forwarding(1),    
                          not-forwarding(2) 
                      }
              ACCESS  read-write
              STATUS  mandatory
              DESCRIPTION
                      "The indication of whether this entity is acting
                      as an IP gateway in respect to the forwarding of
                      datagrams received by, but not addressed to, this
                      entity.  IP gateways forward datagrams.  IP hosts
                      do not (except those source-routed via the host).
                      Note that for some managed nodes, this object may
                      take on only a subset of the values possible.
                      Accordingly, it is appropriate for an agent to
                      return a `badValue' response if a management
                      station attempts to change this object to an
                      inappropriate value."
              ::= { ip 1 }
          ipDefaultTTL OBJECT-TYPE
              SYNTAX  INTEGER
              ACCESS  read-write
              STATUS  mandatory
              DESCRIPTION
                      "The default value inserted into the Time-To-Live
                      field of the IP header of datagrams originated at
                      this entity, whenever a TTL value is not supplied
                      by the transport layer protocol."
              ::= { ip 2 }
          ipInReceives OBJECT-TYPE
              SYNTAX  Counter
              ACCESS  read-only
              STATUS  mandatory
              DESCRIPTION
                      "The total number of input datagrams received from
                      interfaces, including those received in error."
              ::= { ip 3 }
          ipInHdrErrors OBJECT-TYPE
              SYNTAX  Counter
              ACCESS  read-only
              STATUS  mandatory
              DESCRIPTION
                      "The number of input datagrams discarded due to
                      errors in their IP headers, including bad
                      checksums, version number mismatch, other format
                      errors, time-to-live exceeded, errors discovered
                      in processing their IP options, etc."
              ::= { ip 4 }
          ipInAddrErrors OBJECT-TYPE
              SYNTAX  Counter
              ACCESS  read-only
              STATUS  mandatory
              DESCRIPTION
                      "The number of input datagrams discarded because
                      the IP address in their IP header's destination
                      field was not a valid address to be received at
                      this entity.  This count includes invalid
                      addresses (e.g., 0.0.0.0) and addresses of
                      unsupported Classes (e.g., Class E).  For entities
                      which are not IP Gateways and therefore do not
                      forward datagrams, this counter includes datagrams
                      discarded because the destination address was not
                      a local address."
              ::= { ip 5 }
          ipForwDatagrams OBJECT-TYPE
              SYNTAX  Counter
              ACCESS  read-only
              STATUS  mandatory
              DESCRIPTION
                      "The number of input datagrams for which this
                      entity was not their final IP destination, as a
                      result of which an attempt was made to find a
                      route to forward them to that final destination.
                      In entities which do not act as IP Gateways, this
                      counter will include only those packets which were
                      Source-Routed via this entity, and the Source-
                      Route option processing was successful."
              ::= { ip 6 }
          ipInUnknownProtos OBJECT-TYPE
              SYNTAX  Counter
              ACCESS  read-only
              STATUS  mandatory
              DESCRIPTION
                      "The number of locally-addressed datagrams
                      received successfully but discarded because of an
                      unknown or unsupported protocol."
              ::= { ip 7 }
          ipInDiscards OBJECT-TYPE
              SYNTAX  Counter
              ACCESS  read-only
              STATUS  mandatory
              DESCRIPTION
                      "The number of input IP datagrams for which no
                      problems were encountered to prevent their
                      continued processing, but which were discarded
                      (e.g., for lack of buffer space).  Note that this
                      counter does not include any datagrams discarded
                      while awaiting re-assembly."
              ::= { ip 8 }
          ipInDelivers OBJECT-TYPE
              SYNTAX  Counter
              ACCESS  read-only
              STATUS  mandatory
              DESCRIPTION
                      "The total number of input datagrams successfully
                      delivered to IP user-protocols (including ICMP)."
              ::= { ip 9 }
          ipOutRequests OBJECT-TYPE
              SYNTAX  Counter
              ACCESS  read-only
              STATUS  mandatory
              DESCRIPTION
                      "The total number of IP datagrams which local IP
                      user-protocols (including ICMP) supplied to IP in
                      requests for transmission.  Note that this counter
                      does not include any datagrams counted in
                      ipForwDatagrams."
              ::= { ip 10 }
          ipOutDiscards OBJECT-TYPE
              SYNTAX  Counter
              ACCESS  read-only
              STATUS  mandatory
              DESCRIPTION
                      "The number of output IP datagrams for which no
                      problem was encountered to prevent their
                      transmission to their destination, but which were
                      discarded (e.g., for lack of buffer space).  Note
                      that this counter would include datagrams counted
                      in ipForwDatagrams if any such packets met this
                      (discretionary) discard criterion."
              ::= { ip 11 }
          ipOutNoRoutes OBJECT-TYPE
              SYNTAX  Counter
              ACCESS  read-only
              STATUS  mandatory
              DESCRIPTION
                      "The number of IP datagrams discarded because no
                      route could be found to transmit them to their
                      destination.  Note that this counter includes any
                      packets counted in ipForwDatagrams which meet this
                      `no-route' criterion.  Note that this includes any
                      datagarms which a host cannot route because all of
                      its default gateways are down."
              ::= { ip 12 }
          ipReasmTimeout OBJECT-TYPE
              SYNTAX  INTEGER
              ACCESS  read-only
              STATUS  mandatory
              DESCRIPTION
                      "The maximum number of seconds which received
                      fragments are held while they are awaiting
                      reassembly at this entity."
              ::= { ip 13 }
          ipReasmReqds OBJECT-TYPE
              SYNTAX  Counter
              ACCESS  read-only
              STATUS  mandatory
              DESCRIPTION
                      "The number of IP fragments received which needed
                      to be reassembled at this entity."
              ::= { ip 14 }
          ipReasmOKs OBJECT-TYPE
              SYNTAX  Counter
              ACCESS  read-only
              STATUS  mandatory
              DESCRIPTION
                      "The number of IP datagrams successfully re-
                      assembled."
              ::= { ip 15 }
          ipReasmFails OBJECT-TYPE
              SYNTAX  Counter
              ACCESS  read-only
              STATUS  mandatory
              DESCRIPTION
                      "The number of failures detected by the IP re-
                      assembly algorithm (for whatever reason: timed
                      out, errors, etc).  Note that this is not
                      necessarily a count of discarded IP fragments
                      since some algorithms (notably the algorithm in
                      RFC 815) can lose track of the number of fragments
                      by combining them as they are received."
              ::= { ip 16 }
          ipFragOKs OBJECT-TYPE
              SYNTAX  Counter
              ACCESS  read-only
              STATUS  mandatory
              DESCRIPTION
                      "The number of IP datagrams that have been
                      successfully fragmented at this entity."
              ::= { ip 17 }
          ipFragFails OBJECT-TYPE
              SYNTAX  Counter
              ACCESS  read-only
              STATUS  mandatory
              DESCRIPTION
                      "The number of IP datagrams that have been
                      discarded because they needed to be fragmented at
                      this entity but could not be, e.g., because their
                      Don't Fragment flag was set."
              ::= { ip 18 }
          ipFragCreates OBJECT-TYPE
              SYNTAX  Counter
              ACCESS  read-only
              STATUS  mandatory
              DESCRIPTION
                      "The number of IP datagram fragments that have
                      been generated as a result of fragmentation at
                      this entity."
              ::= { ip 19 }
          ipAddrTable OBJECT-TYPE
              SYNTAX  SEQUENCE OF IpAddrEntry
              ACCESS  not-accessible
              STATUS  mandatory
              DESCRIPTION
                      "The table of addressing information relevant to
                      this entity's IP addresses."
              ::= { ip 20 }
          ipAddrEntry OBJECT-TYPE
              SYNTAX  IpAddrEntry
              ACCESS  not-accessible
              STATUS  mandatory
              DESCRIPTION
                      "The addressing information for one of this
                      entity's IP addresses."
              INDEX   { ipAdEntAddr }
              ::= { ipAddrTable 1 }
          IpAddrEntry ::=
              SEQUENCE {
                  ipAdEntAddr
                      IpAddress,
                  ipAdEntIfIndex
                      INTEGER,
                  ipAdEntNetMask
                      IpAddress,
                  ipAdEntBcastAddr
                      INTEGER,
                  ipAdEntReasmMaxSize
                      INTEGER (0..65535)
              }
          ipAdEntAddr OBJECT-TYPE
              SYNTAX  IpAddress
              ACCESS  read-only
              STATUS  mandatory
              DESCRIPTION
                      "The IP address to which this entry's addressing
                      information pertains."
              ::= { ipAddrEntry 1 }
          ipAdEntIfIndex OBJECT-TYPE
              SYNTAX  INTEGER
              ACCESS  read-only
              STATUS  mandatory
              DESCRIPTION
                      "The index value which uniquely identifies the
                      interface to which this entry is applicable.  The
                      interface identified by a particular value of this
                      index is the same interface as identified by the
                      same value of ifIndex."
              ::= { ipAddrEntry 2 }
          ipAdEntNetMask OBJECT-TYPE
              SYNTAX  IpAddress
              ACCESS  read-only
              STATUS  mandatory
              DESCRIPTION
                      "The subnet mask associated with the IP address of
                      this entry.  The value of the mask is an IP
                      address with all the network bits set to 1 and all
                      the hosts bits set to 0."
              ::= { ipAddrEntry 3 }
          ipAdEntBcastAddr OBJECT-TYPE
              SYNTAX  INTEGER
              ACCESS  read-only
              STATUS  mandatory
              DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
              ::= { ipAddrEntry 4 }
          ipAdEntReasmMaxSize OBJECT-TYPE
              SYNTAX  INTEGER (0..65535)
              ACCESS  read-only
              STATUS  mandatory
              DESCRIPTION
                      "The size of the largest IP datagram which this
                      entity can re-assemble from incoming IP fragmented
                      datagrams received on this interface."
              ::= { ipAddrEntry 5 }
          ipRouteTable OBJECT-TYPE
              SYNTAX  SEQUENCE OF IpRouteEntry
              ACCESS  not-accessible
              STATUS  mandatory
              DESCRIPTION
                      "This entity's IP Routing table."
              ::= { ip 21 }
          ipRouteEntry OBJECT-TYPE
              SYNTAX  IpRouteEntry
              ACCESS  not-accessible
              STATUS  mandatory
              DESCRIPTION
                      "A route to a particular destination."
              INDEX   { ipRouteDest }
              ::= { ipRouteTable 1 }
          IpRouteEntry ::=
              SEQUENCE {
                  ipRouteDest
                      IpAddress,
                  ipRouteIfIndex
                      INTEGER,
                  ipRouteMetric1
                      INTEGER,
                  ipRouteMetric2
                      INTEGER,
                  ipRouteMetric3
                      INTEGER,
                  ipRouteMetric4
                      INTEGER,
                  ipRouteNextHop
                      IpAddress,
                  ipRouteType
                      INTEGER,
                  ipRouteProto
                      INTEGER,
                  ipRouteAge
                      INTEGER,
                  ipRouteMask
                      IpAddress,
                  ipRouteMetric5
                      INTEGER,
                  ipRouteInfo
                      OBJECT IDENTIFIER
              }
          ipRouteDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
              ::= { ipRouteEntry 1 }
          ipRouteIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { ipRouteEntry 2 }
          ipRouteMetric1 OBJECT-TYPE
              SYNTAX  INTEGER
              ACCESS  read-write
              STATUS  mandatory
              DESCRIPTION
                      "The primary routing metric for this route.  The
                      semantics of this metric are determined by the
                      routing-protocol specified in the route's
                      ipRouteProto value.  If this metric is not used,
                      its value should be set to -1."
              ::= { ipRouteEntry 3 }
          ipRouteMetric2 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 4 }
          ipRouteMetric3 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 5 }
          ipRouteMetric4 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 6 }
          ipRouteNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
              ::= { ipRouteEntry 7 }
          ipRouteType OBJECT-TYPE
              SYNTAX  INTEGER {
                          other(1),        
                          invalid(2),      
                          direct(3),       
                          indirect(4)      
                      }
              ACCESS  read-write
              STATUS  mandatory
              DESCRIPTION
                      "The type of route.  Note that the values
                      direct(3) and indirect(4) refer to the notion of
                      direct and indirect routing in the IP
                      architecture.
                      Setting this object to the value invalid(2) has
                      the effect of invalidating the corresponding entry
                      in the ipRouteTable object.  That is, it
                      effectively dissasociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { ipRouteEntry 8 }
          ipRouteProto OBJECT-TYPE
              SYNTAX  INTEGER {
                          other(1),       
                          local(2),       
                          netmgmt(3),     
                          icmp(4),        
                          egp(5),
                          ggp(6),
                          hello(7),
                          rip(8),
                          is-is(9),
                          es-is(10),
                          ciscoIgrp(11),
                          bbnSpfIgp(12),
                          ospf(13),
                          bgp(14)
                      }
              ACCESS  read-only
              STATUS  mandatory
              DESCRIPTION
                      "The routing mechanism via which this route was
                      learned.  Inclusion of values for gateway routing
                      protocols is not intended to imply that hosts
                      should support those protocols."
              ::= { ipRouteEntry 9 }
          ipRouteAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { ipRouteEntry 10 }
          ipRouteMask OBJECT-TYPE
              SYNTAX  IpAddress
              ACCESS  read-write
              STATUS  mandatory
              DESCRIPTION
                      "Indicate the mask to be logical-ANDed with the
                      destination address before being compared to the
                      value in the ipRouteDest field.  For those systems
                      that do not support arbitrary subnet masks, an
                      agent constructs the value of the ipRouteMask by
                      determining whether the value of the correspondent
                      ipRouteDest field belong to a class-A, B, or C
                      network, and then using one of:
                           mask           network
                           255.0.0.0      class-A
                           255.255.0.0    class-B
                           255.255.255.0  class-C
                      If the value of the ipRouteDest is 0.0.0.0 (a
                      default route), then the mask value is also
                      0.0.0.0.  It should be noted that all IP routing
                      subsystems implicitly use this mechanism."
              ::= { ipRouteEntry 11 }
          ipRouteMetric5 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 12 }
          ipRouteInfo OBJECT-TYPE
              SYNTAX  OBJECT IDENTIFIER
              ACCESS  read-only
              STATUS  mandatory
              DESCRIPTION
                      "A reference to MIB definitions specific to the
                      particular routing protocol which is responsible
                      for this route, as determined by the value
                      specified in the route's ipRouteProto value.  If
                      this information is not present, its value should
                      be set to the OBJECT IDENTIFIER { 0 0 }, which is
                      a syntatically valid object identifier, and any
                      conformant implementation of ASN.1 and BER must be
                      able to generate and recognize this value."
              ::= { ipRouteEntry 13 }
          ipNetToMediaTable OBJECT-TYPE
              SYNTAX  SEQUENCE OF IpNetToMediaEntry
              ACCESS  not-accessible
              STATUS  mandatory
              DESCRIPTION
                      "The IP Address Translation table used for mapping
                      from IP addresses to physical addresses."
              ::= { ip 22 }
          ipNetToMediaEntry OBJECT-TYPE
              SYNTAX  IpNetToMediaEntry
              ACCESS  not-accessible
              STATUS  mandatory
              DESCRIPTION
                      "Each entry contains one IpAddress to `physical'
                      address equivalence."
              INDEX   { ipNetToMediaIfIndex,
                        ipNetToMediaNetAddress }
              ::= { ipNetToMediaTable 1 }
          IpNetToMediaEntry ::=
              SEQUENCE {
                  ipNetToMediaIfIndex
                      INTEGER,
                  ipNetToMediaPhysAddress
                      PhysAddress,
                  ipNetToMediaNetAddress
                      IpAddress,
                  ipNetToMediaType
                      INTEGER
              }
          ipNetToMediaIfIndex OBJECT-TYPE
              SYNTAX  INTEGER
              ACCESS  read-write
              STATUS  mandatory
              DESCRIPTION
                      "The interface on which this entry's equivalence
                      is effective.  The interface identified by a
                      particular value of this index is the same
                      interface as identified by the same value of
                      ifIndex."
              ::= { ipNetToMediaEntry 1 }
          ipNetToMediaPhysAddress OBJECT-TYPE
              SYNTAX  PhysAddress
              ACCESS  read-write
              STATUS  mandatory
              DESCRIPTION
                      "The media-dependent `physical' address."
              ::= { ipNetToMediaEntry 2 }
          ipNetToMediaNetAddress OBJECT-TYPE
              SYNTAX  IpAddress
              ACCESS  read-write
              STATUS  mandatory
              DESCRIPTION
                      "The IpAddress corresponding to the media-
                      dependent `physical' address."
              ::= { ipNetToMediaEntry 3 }
          ipNetToMediaType OBJECT-TYPE
              SYNTAX  INTEGER {
                          other(1),        
                          invalid(2),      
                          dynamic(3),
                          static(4)
                      }
              ACCESS  read-write
              STATUS  mandatory
              DESCRIPTION
                      "The type of mapping.
                      Setting this object to the value invalid(2) has
                      the effect of invalidating the corresponding entry
                      in the ipNetToMediaTable.  That is, it effectively
                      dissasociates the interface identified with said
                      entry from the mapping identified with said entry.
                      It is an implementation-specific matter as to
                      whether the agent removes an invalidated entry
                      from the table.  Accordingly, management stations
                      must be prepared to receive tabular information
                      from agents that corresponds to entries not
                      currently in use.  Proper interpretation of such
                      entries requires examination of the relevant
                      ipNetToMediaType object."
              ::= { ipNetToMediaEntry 4 }
          ipRoutingDiscards OBJECT-TYPE
              SYNTAX  Counter
              ACCESS  read-only
              STATUS  mandatory
              DESCRIPTION
                      "The number of routing entries which were chosen
                      to be discarded even though they are valid.  One
                      possible reason for discarding such an entry could
                      be to free-up buffer space for other routing
                      entries."
              ::= { ip 23 }
          icmpInMsgs OBJECT-TYPE
              SYNTAX  Counter
              ACCESS  read-only
              STATUS  mandatory
              DESCRIPTION
                      "The total number of ICMP messages which the
                      entity received.  Note that this counter includes
                      all those counted by icmpInErrors."
              ::= { icmp 1 }
          icmpInErrors OBJECT-TYPE
              SYNTAX  Counter
              ACCESS  read-only
              STATUS  mandatory
              DESCRIPTION
                      "The number of ICMP messages which the entity
                      received but determined as having ICMP-specific
                      errors (bad ICMP checksums, bad length, etc.)."
              ::= { icmp 2 }
          icmpInDestUnreachs OBJECT-TYPE
              SYNTAX  Counter
              ACCESS  read-only
              STATUS  mandatory
              DESCRIPTION
                      "The number of ICMP Destination Unreachable
                      messages received."
              ::= { icmp 3 }
          icmpInTimeExcds OBJECT-TYPE
              SYNTAX  Counter
              ACCESS  read-only
              STATUS  mandatory
              DESCRIPTION
                      "The number of ICMP Time Exceeded messages
                      received."
              ::= { icmp 4 }
          icmpInParmProbs OBJECT-TYPE
              SYNTAX  Counter
              ACCESS  read-only
              STATUS  mandatory
              DESCRIPTION
                      "The number of ICMP Parameter Problem messages
                      received."
              ::= { icmp 5 }
          icmpInSrcQuenchs OBJECT-TYPE
              SYNTAX  Counter
              ACCESS  read-only
              STATUS  mandatory
              DESCRIPTION
                      "The number of ICMP Source Quench messages
                      received."
              ::= { icmp 6 }
          icmpInRedirects OBJECT-TYPE
              SYNTAX  Counter
              ACCESS  read-only
              STATUS  mandatory
              DESCRIPTION
                      "The number of ICMP Redirect messages received."
              ::= { icmp 7 }
          icmpInEchos OBJECT-TYPE
              SYNTAX  Counter
              ACCESS  read-only
              STATUS  mandatory
              DESCRIPTION
                      "The number of ICMP Echo (request) messages
                      received."
              ::= { icmp 8 }
          icmpInEchoReps OBJECT-TYPE
              SYNTAX  Counter
              ACCESS  read-only
              STATUS  mandatory
              DESCRIPTION
                      "The number of ICMP Echo Reply messages received."
              ::= { icmp 9 }
          icmpInTimestamps OBJECT-TYPE
              SYNTAX  Counter
              ACCESS  read-only
              STATUS  mandatory
              DESCRIPTION
                      "The number of ICMP Timestamp (request) messages
                      received."
              ::= { icmp 10 }
          icmpInTimestampReps OBJECT-TYPE
              SYNTAX  Counter
              ACCESS  read-only
              STATUS  mandatory
              DESCRIPTION
                      "The number of ICMP Timestamp Reply messages
                      received."
              ::= { icmp 11 }
          icmpInAddrMasks OBJECT-TYPE
              SYNTAX  Counter
              ACCESS  read-only
              STATUS  mandatory
              DESCRIPTION
                      "The number of ICMP Address Mask Request messages
                      received."
              ::= { icmp 12 }
          icmpInAddrMaskReps OBJECT-TYPE
              SYNTAX  Counter
              ACCESS  read-only
              STATUS  mandatory
              DESCRIPTION
                      "The number of ICMP Address Mask Reply messages
                      received."
              ::= { icmp 13 }
          icmpOutMsgs OBJECT-TYPE
              SYNTAX  Counter
              ACCESS  read-only
              STATUS  mandatory
              DESCRIPTION
                      "The total number of ICMP messages which this
                      entity attempted to send.  Note that this counter
                      includes all those counted by icmpOutErrors."
              ::= { icmp 14 }
          icmpOutErrors OBJECT-TYPE
              SYNTAX  Counter
              ACCESS  read-only
              STATUS  mandatory
              DESCRIPTION
                      "The number of ICMP messages which this entity did
                      not send due to problems discovered within ICMP
                      such as a lack of buffers.  This value should not
                      include errors discovered outside the ICMP layer
                      such as the inability of IP to route the resultant
                      datagram.  In some implementations there may be no
                      types of error which contribute to this counter's
                      value."
              ::= { icmp 15 }
          icmpOutDestUnreachs OBJECT-TYPE
              SYNTAX  Counter
              ACCESS  read-only
              STATUS  mandatory
              DESCRIPTION
                      "The number of ICMP Destination Unreachable
                      messages sent."
              ::= { icmp 16 }
          icmpOutTimeExcds OBJECT-TYPE
              SYNTAX  Counter
              ACCESS  read-only
              STATUS  mandatory
              DESCRIPTION
                      "The number of ICMP Time Exceeded messages sent."
              ::= { icmp 17 }
          icmpOutParmProbs OBJECT-TYPE
              SYNTAX  Counter
              ACCESS  read-only
              STATUS  mandatory
              DESCRIPTION
                      "The number of ICMP Parameter Problem messages
                      sent."
              ::= { icmp 18 }
          icmpOutSrcQuenchs OBJECT-TYPE
              SYNTAX  Counter
              ACCESS  read-only
              STATUS  mandatory
              DESCRIPTION
                      "The number of ICMP Source Quench messages sent."
              ::= { icmp 19 }
          icmpOutRedirects OBJECT-TYPE
              SYNTAX  Counter
              ACCESS  read-only
              STATUS  mandatory
              DESCRIPTION
                      "The number of ICMP Redirect messages sent.  For a
                      host, this object will always be zero, since hosts
                      do not send redirects."
              ::= { icmp 20 }
          icmpOutEchos OBJECT-TYPE
              SYNTAX  Counter
              ACCESS  read-only
              STATUS  mandatory
              DESCRIPTION
                      "The number of ICMP Echo (request) messages sent."
              ::= { icmp 21 }
          icmpOutEchoReps OBJECT-TYPE
              SYNTAX  Counter
              ACCESS  read-only
              STATUS  mandatory
              DESCRIPTION
                      "The number of ICMP Echo Reply messages sent."
              ::= { icmp 22 }
          icmpOutTimestamps OBJECT-TYPE
              SYNTAX  Counter
              ACCESS  read-only
              STATUS  mandatory
              DESCRIPTION
                      "The number of ICMP Timestamp (request) messages
                      sent."
              ::= { icmp 23 }
          icmpOutTimestampReps OBJECT-TYPE
              SYNTAX  Counter
              ACCESS  read-only
              STATUS  mandatory
              DESCRIPTION
                      "The number of ICMP Timestamp Reply messages
                      sent."
              ::= { icmp 24 }
          icmpOutAddrMasks OBJECT-TYPE
              SYNTAX  Counter
              ACCESS  read-only
              STATUS  mandatory
              DESCRIPTION
                      "The number of ICMP Address Mask Request messages
                      sent."
              ::= { icmp 25 }
          icmpOutAddrMaskReps OBJECT-TYPE
              SYNTAX  Counter
              ACCESS  read-only
              STATUS  mandatory
              DESCRIPTION
                      "The number of ICMP Address Mask Reply messages
                      sent."
              ::= { icmp 26 }
          tcpRtoAlgorithm OBJECT-TYPE
              SYNTAX  INTEGER {
                          other(1),    
                          constant(2), 
                          rsre(3),     
                          vanj(4)      
                      }
              ACCESS  read-only
              STATUS  mandatory
              DESCRIPTION
                      "The algorithm used to determine the timeout value
                      used for retransmitting unacknowledged octets."
              ::= { tcp 1 }
          tcpRtoMin OBJECT-TYPE
              SYNTAX  INTEGER
              ACCESS  read-only
              STATUS  mandatory
              DESCRIPTION
                      "The minimum value permitted by a TCP
                      implementation for the retransmission timeout,
                      measured in milliseconds.  More refined semantics
                      for objects of this type depend upon the algorithm
                      used to determine the retransmission timeout.  In
                      particular, when the timeout algorithm is rsre(3),
                      an object of this type has the semantics of the
                      LBOUND quantity described in RFC 793."
              ::= { tcp 2 }
          tcpRtoMax OBJECT-TYPE
              SYNTAX  INTEGER
              ACCESS  read-only
              STATUS  mandatory
              DESCRIPTION
                      "The maximum value permitted by a TCP
                      implementation for the retransmission timeout,
                      measured in milliseconds.  More refined semantics
                      for objects of this type depend upon the algorithm
                      used to determine the retransmission timeout.  In
                      particular, when the timeout algorithm is rsre(3),
                      an object of this type has the semantics of the
                      UBOUND quantity described in RFC 793."
              ::= { tcp 3 }
          tcpMaxConn OBJECT-TYPE
              SYNTAX  INTEGER
              ACCESS  read-only
              STATUS  mandatory
              DESCRIPTION
                      "The limit on the total number of TCP connections
                      the entity can support.  In entities where the
                      maximum number of connections is dynamic, this
                      object should contain the value -1."
              ::= { tcp 4 }
          tcpActiveOpens OBJECT-TYPE
              SYNTAX  Counter
              ACCESS  read-only
              STATUS  mandatory
              DESCRIPTION
                      "The number of times TCP connections have made a
                      direct transition to the SYN-SENT state from the
                      CLOSED state."
              ::= { tcp 5 }
          tcpPassiveOpens OBJECT-TYPE
              SYNTAX  Counter
              ACCESS  read-only
              STATUS  mandatory
              DESCRIPTION
                      "The number of times TCP connections have made a
                      direct transition to the SYN-RCVD state from the
                      LISTEN state."
              ::= { tcp 6 }
          tcpAttemptFails OBJECT-TYPE
              SYNTAX  Counter
              ACCESS  read-only
              STATUS  mandatory
              DESCRIPTION
                      "The number of times TCP connections have made a
                      direct transition to the CLOSED state from either
                      the SYN-SENT state or the SYN-RCVD state, plus the
                      number of times TCP connections have made a direct
                      transition to the LISTEN state from the SYN-RCVD
                      state."
              ::= { tcp 7 }
          tcpEstabResets OBJECT-TYPE
              SYNTAX  Counter
              ACCESS  read-only
              STATUS  mandatory
              DESCRIPTION
                      "The number of times TCP connections have made a
                      direct transition to the CLOSED state from either
                      the ESTABLISHED state or the CLOSE-WAIT state."
              ::= { tcp 8 }
          tcpCurrEstab OBJECT-TYPE
              SYNTAX  Gauge
              ACCESS  read-only
              STATUS  mandatory
              DESCRIPTION
                      "The number of TCP connections for which the
                      current state is either ESTABLISHED or CLOSE-
                      WAIT."
              ::= { tcp 9 }
          tcpInSegs OBJECT-TYPE
              SYNTAX  Counter
              ACCESS  read-only
              STATUS  mandatory
              DESCRIPTION
                      "The total number of segments received, including
                      those received in error.  This count includes
                      segments received on currently established
                      connections."
              ::= { tcp 10 }
          tcpOutSegs OBJECT-TYPE
              SYNTAX  Counter
              ACCESS  read-only
              STATUS  mandatory
              DESCRIPTION
                      "The total number of segments sent, including
                      those on current connections but excluding those
                      containing only retransmitted octets."
              ::= { tcp 11 }
          tcpRetransSegs OBJECT-TYPE
              SYNTAX  Counter
              ACCESS  read-only
              STATUS  mandatory
              DESCRIPTION
                      "The total number of segments retransmitted - that
                      is, the number of TCP segments transmitted
                      containing one or more previously transmitted
                      octets."
              ::= { tcp 12 }
          tcpConnTable OBJECT-TYPE
              SYNTAX  SEQUENCE OF TcpConnEntry
              ACCESS  not-accessible
              STATUS  mandatory
              DESCRIPTION
                      "A table containing TCP connection-specific
                      information."
              ::= { tcp 13 }
          tcpConnEntry OBJECT-TYPE
              SYNTAX  TcpConnEntry
              ACCESS  not-accessible
              STATUS  mandatory
              DESCRIPTION
                      "Information about a particular current TCP
                      connection.  An object of this type is transient,
                      in that it ceases to exist when (or soon after)
                      the connection makes the transition to the CLOSED
                      state."
              INDEX   { tcpConnLocalAddress,
                        tcpConnLocalPort,
                        tcpConnRemAddress,
                        tcpConnRemPort }
              ::= { tcpConnTable 1 }
          TcpConnEntry ::=
              SEQUENCE {
                  tcpConnState
                      INTEGER,
                  tcpConnLocalAddress
                      IpAddress,
                  tcpConnLocalPort
                      INTEGER (0..65535),
                  tcpConnRemAddress
                      IpAddress,
                  tcpConnRemPort
                      INTEGER (0..65535)
              }
          tcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              ACCESS  read-write
              STATUS  mandatory
              DESCRIPTION
                      "The state of this TCP connection.
                      The only value which may be set by a management
                      station is deleteTCB(12).  Accordingly, it is
                      appropriate for an agent to return a `badValue'
                      response if a management station attempts to set
                      this object to any other value.
                      If a management station sets this object to the
                      value deleteTCB(12), then this has the effect of
                      deleting the TCB (as defined in RFC 793) of the
                      corresponding connection on the managed node,
                      resulting in immediate termination of the
                      connection.
                      As an implementation-specific option, a RST
                      segment may be sent from the managed node to the
                      other TCP endpoint (note however that RST segments
                      are not sent reliably)."
              ::= { tcpConnEntry 1 }
          tcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { tcpConnEntry 2 }
          tcpConnLocalPort OBJECT-TYPE
              SYNTAX  INTEGER (0..65535)
              ACCESS  read-only
              STATUS  mandatory
              DESCRIPTION
                      "The local port number for this TCP connection."
              ::= { tcpConnEntry 3 }
          tcpConnRemAddress OBJECT-TYPE
              SYNTAX  IpAddress
              ACCESS  read-only
              STATUS  mandatory
              DESCRIPTION
                      "The remote IP address for this TCP connection."
              ::= { tcpConnEntry 4 }
          tcpConnRemPort OBJECT-TYPE
              SYNTAX  INTEGER (0..65535)
              ACCESS  read-only
              STATUS  mandatory
              DESCRIPTION
                      "The remote port number for this TCP connection."
              ::= { tcpConnEntry 5 }
          tcpInErrs OBJECT-TYPE
              SYNTAX  Counter
              ACCESS  read-only
              STATUS  mandatory
              DESCRIPTION
                      "The total number of segments received in error
                      (e.g., bad TCP checksums)."
              ::= { tcp 14 }
          tcpOutRsts OBJECT-TYPE
              SYNTAX  Counter
              ACCESS  read-only
              STATUS  mandatory
              DESCRIPTION
                      "The number of TCP segments sent containing the
                      RST flag."
              ::= { tcp 15 }
          udpInDatagrams OBJECT-TYPE
              SYNTAX  Counter
              ACCESS  read-only
              STATUS  mandatory
              DESCRIPTION
                      "The total number of UDP datagrams delivered to
                      UDP users."
              ::= { udp 1 }
          udpNoPorts OBJECT-TYPE
              SYNTAX  Counter
              ACCESS  read-only
              STATUS  mandatory
              DESCRIPTION
                      "The total number of received UDP datagrams for
                      which there was no application at the destination
                      port."
              ::= { udp 2 }
          udpInErrors OBJECT-TYPE
              SYNTAX  Counter
              ACCESS  read-only
              STATUS  mandatory
              DESCRIPTION
                      "The number of received UDP datagrams that could
                      not be delivered for reasons other than the lack
                      of an application at the destination port."
              ::= { udp 3 }
          udpOutDatagrams OBJECT-TYPE
              SYNTAX  Counter
              ACCESS  read-only
              STATUS  mandatory
              DESCRIPTION
                      "The total number of UDP datagrams sent from this
                      entity."
              ::= { udp 4 }
          udpTable OBJECT-TYPE
              SYNTAX  SEQUENCE OF UdpEntry
              ACCESS  not-accessible
              STATUS  mandatory
              DESCRIPTION
                      "A table containing UDP listener information."
              ::= { udp 5 }
          udpEntry OBJECT-TYPE
              SYNTAX  UdpEntry
              ACCESS  not-accessible
              STATUS  mandatory
              DESCRIPTION
                      "Information about a particular current UDP
                      listener."
              INDEX   { udpLocalAddress, udpLocalPort }
              ::= { udpTable 1 }
          UdpEntry ::=
              SEQUENCE {
                  udpLocalAddress
                      IpAddress,
                  udpLocalPort
                      INTEGER (0..65535)
              }
          udpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { udpEntry 1 }
          udpLocalPort OBJECT-TYPE
              SYNTAX  INTEGER (0..65535)
              ACCESS  read-only
              STATUS  mandatory
              DESCRIPTION
                      "The local port number for this UDP listener."
              ::= { udpEntry 2 }
          egpInMsgs OBJECT-TYPE
              SYNTAX  Counter
              ACCESS  read-only
              STATUS  mandatory
              DESCRIPTION
                      "The number of EGP messages received without
                      error."
              ::= { egp 1 }
          egpInErrors OBJECT-TYPE
              SYNTAX  Counter
              ACCESS  read-only
              STATUS  mandatory
              DESCRIPTION
                      "The number of EGP messages received that proved
                      to be in error."
              ::= { egp 2 }
          egpOutMsgs OBJECT-TYPE
              SYNTAX  Counter
              ACCESS  read-only
              STATUS  mandatory
              DESCRIPTION
                      "The total number of locally generated EGP
                      messages."
              ::= { egp 3 }
          egpOutErrors OBJECT-TYPE
              SYNTAX  Counter
              ACCESS  read-only
              STATUS  mandatory
              DESCRIPTION
                      "The number of locally generated EGP messages not
                      sent due to resource limitations within an EGP
                      entity."
              ::= { egp 4 }
          egpNeighTable OBJECT-TYPE
              SYNTAX  SEQUENCE OF EgpNeighEntry
              ACCESS  not-accessible
              STATUS  mandatory
              DESCRIPTION
                      "The EGP neighbor table."
              ::= { egp 5 }
          egpNeighEntry OBJECT-TYPE
              SYNTAX  EgpNeighEntry
              ACCESS  not-accessible
              STATUS  mandatory
              DESCRIPTION
                      "Information about this entity's relationship with
                      a particular EGP neighbor."
              INDEX   { egpNeighAddr }
              ::= { egpNeighTable 1 }
          EgpNeighEntry ::=
              SEQUENCE {
                  egpNeighState
                      INTEGER,
                  egpNeighAddr
                      IpAddress,
                  egpNeighAs
                      INTEGER,
                  egpNeighInMsgs
                      Counter,
                  egpNeighInErrs
                      Counter,
                  egpNeighOutMsgs
                      Counter,
                  egpNeighOutErrs
                      Counter,
                  egpNeighInErrMsgs
                      Counter,
                  egpNeighOutErrMsgs
                      Counter,
                  egpNeighStateUps
                      Counter,
                  egpNeighStateDowns
                      Counter,
                  egpNeighIntervalHello
                      INTEGER,
                  egpNeighIntervalPoll
                      INTEGER,
                  egpNeighMode
                      INTEGER,
                  egpNeighEventTrigger
                      INTEGER
              }
          egpNeighState OBJECT-TYPE
              SYNTAX  INTEGER {
                          idle(1),
                          acquisition(2),
                          down(3),
                          up(4),
                          cease(5)
                      }
              ACCESS  read-only
              STATUS  mandatory
              DESCRIPTION
                      "The EGP state of the local system with respect to
                      this entry's EGP neighbor.  Each EGP state is
                      represented by a value that is one greater than
                      the numerical value associated with said state in
                      RFC 904."
              ::= { egpNeighEntry 1 }
          egpNeighAddr OBJECT-TYPE
              SYNTAX  IpAddress
              ACCESS  read-only
              STATUS  mandatory
              DESCRIPTION
                      "The IP address of this entry's EGP neighbor."
              ::= { egpNeighEntry 2 }
          egpNeighAs OBJECT-TYPE
              SYNTAX  INTEGER
              ACCESS  read-only
              STATUS  mandatory
              DESCRIPTION
                      "The autonomous system of this EGP peer.  Zero
                      should be specified if the autonomous system
                      number of the neighbor is not yet known."
              ::= { egpNeighEntry 3 }
          egpNeighInMsgs OBJECT-TYPE
              SYNTAX  Counter
              ACCESS  read-only
              STATUS  mandatory
              DESCRIPTION
                      "The number of EGP messages received without error
                      from this EGP peer."
              ::= { egpNeighEntry 4 }
          egpNeighInErrs OBJECT-TYPE
              SYNTAX  Counter
              ACCESS  read-only
              STATUS  mandatory
              DESCRIPTION
                      "The number of EGP messages received from this EGP
                      peer that proved to be in error (e.g., bad EGP
                      checksum)."
              ::= { egpNeighEntry 5 }
          egpNeighOutMsgs OBJECT-TYPE
              SYNTAX  Counter
              ACCESS  read-only
              STATUS  mandatory
              DESCRIPTION
                      "The number of locally generated EGP messages to
                      this EGP peer."
              ::= { egpNeighEntry 6 }
          egpNeighOutErrs OBJECT-TYPE
              SYNTAX  Counter
              ACCESS  read-only
              STATUS  mandatory
              DESCRIPTION
                      "The number of locally generated EGP messages not
                      sent to this EGP peer due to resource limitations
                      within an EGP entity."
              ::= { egpNeighEntry 7 }
          egpNeighInErrMsgs OBJECT-TYPE
              SYNTAX  Counter
              ACCESS  read-only
              STATUS  mandatory
              DESCRIPTION
                      "The number of EGP-defined error messages received
                      from this EGP peer."
              ::= { egpNeighEntry 8 }
          egpNeighOutErrMsgs OBJECT-TYPE
              SYNTAX  Counter
              ACCESS  read-only
              STATUS  mandatory
              DESCRIPTION
                      "The number of EGP-defined error messages sent to
                      this EGP peer."
              ::= { egpNeighEntry 9 }
          egpNeighStateUps OBJECT-TYPE
              SYNTAX  Counter
              ACCESS  read-only
              STATUS  mandatory
              DESCRIPTION
                      "The number of EGP state transitions to the UP
                      state with this EGP peer."
              ::= { egpNeighEntry 10 }
          egpNeighStateDowns OBJECT-TYPE
              SYNTAX  Counter
              ACCESS  read-only
              STATUS  mandatory
              DESCRIPTION
                      "The number of EGP state transitions from the UP
                      state to any other state with this EGP peer."
              ::= { egpNeighEntry 11 }
          egpNeighIntervalHello OBJECT-TYPE
              SYNTAX  INTEGER
              ACCESS  read-only
              STATUS  mandatory
              DESCRIPTION
                      "The interval between EGP Hello command
                      retransmissions (in hundredths of a second).  This
                      represents the t1 timer as defined in RFC 904."
              ::= { egpNeighEntry 12 }
          egpNeighIntervalPoll OBJECT-TYPE
              SYNTAX  INTEGER
              ACCESS  read-only
              STATUS  mandatory
              DESCRIPTION
                      "The interval between EGP poll command
                      retransmissions (in hundredths of a second).  This
                      represents the t3 timer as defined in RFC 904."
              ::= { egpNeighEntry 13 }
          egpNeighMode OBJECT-TYPE
              SYNTAX  INTEGER { active(1), passive(2) }
              ACCESS  read-only
              STATUS  mandatory
              DESCRIPTION
                      "The polling mode of this EGP entity, either
                      passive or active."
              ::= { egpNeighEntry 14 }
          egpNeighEventTrigger OBJECT-TYPE
              SYNTAX  INTEGER { start(1), stop(2) }
              ACCESS  read-write
              STATUS  mandatory
              DESCRIPTION
                      "A control variable used to trigger operator-
                      initiated Start and Stop events.  When read, this
                      variable always returns the most recent value that
                      egpNeighEventTrigger was set to.  If it has not
                      been set since the last initialization of the
                      network management subsystem on the node, it
                      returns a value of `stop'.
                      When set, this variable causes a Start or Stop
                      event on the specified neighbor, as specified on
                      pages 8-10 of RFC 904.  Briefly, a Start event
                      causes an Idle peer to begin neighbor acquisition
                      and a non-Idle peer to reinitiate neighbor
                      acquisition.  A stop event causes a non-Idle peer
                      to return to the Idle state until a Start event
                      occurs, either via egpNeighEventTrigger or
                      otherwise."
              ::= { egpNeighEntry 15 }
          egpAs OBJECT-TYPE
              SYNTAX  INTEGER
              ACCESS  read-only
              STATUS  mandatory
              DESCRIPTION
                      "The autonomous system number of this EGP entity."
              ::= { egp 6 }
          -- portion of the MIB until they are "proven", then as a
          --
          --
          -- where "type" is the symbolic value used for the media in
          -- the ifType column of the ifTable object, and "number" is
END
