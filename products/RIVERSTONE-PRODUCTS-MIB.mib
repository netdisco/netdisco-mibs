RIVERSTONE-PRODUCTS-MIB DEFINITIONS ::= BEGIN

IMPORTS
        MODULE-IDENTITY,
        OBJECT-IDENTITY
           FROM SNMPv2-SMI
        riverstoneProducts
          FROM RSTONE-SMI-MIB;

rsFamilyMIB MODULE-IDENTITY   
    LAST-UPDATED "200011300000Z"
    ORGANIZATION "Riverstone Networks, Inc"
    CONTACT-INFO
    "Riverstone Networks, Inc
     5200 Great America Parkway
     Santa Clara CA USA 95054
     PHONE:+1 408.878.6500
     EMAIL: nms-eng@riverstonenet.com
     WEB: http://www.riverstonenet.com"
     DESCRIPTION
            "This mib module defines system Object Identifier values for sysObjectID.0 for 
	     network elements manufactured and sold by Riverstone Networks, Inc
             http://www.riverstonenet.com/products. 

             Contains sysObjectIDs for RS Procut Line of Multi Layer Switch Routers.

             Copyright (C) Riverstone Networks, Inc 2000"

    REVISION     "200004160000Z"
    DESCRIPTION
      "Riverstone RS Family of products object IDs added."
    REVISION     "200011280000Z"
    DESCRIPTION
      "Riverstone RS1000 object ID added. Changed IA1000->IA1100, IA1100->IA1200(typo)"
    REVISION     "200011290000Z"
    DESCRIPTION
      "Riverstone IA1500 object ID added."
    REVISION     "200011300000Z"
    DESCRIPTION
      "Riverstone RS38000 object ID added."
	 ::= { riverstoneProducts 1 }  


-- ****************  RS Product Line ***************


 
rs8000  OBJECT-IDENTITY
            STATUS  current
            DESCRIPTION
            "RS 8000 8-slot switch router. 
             http://www.riverstonenet.com/products/RS8x00/rs8x00.html"
        ::= { rsFamilyMIB 1 }

rs8600  OBJECT-IDENTITY
            STATUS  current
            DESCRIPTION
            "RS 8000 16-slot switch router. 
             http://www.riverstonenet.com/products/RS8x00/rs8x00.html"
        ::= { rsFamilyMIB 2 }

rs2000  OBJECT-IDENTITY
            STATUS  current
            DESCRIPTION
            "RS 2000 2-slot switch router with fixed 16 port 10/100 Ethernet TX
             http://www.riverstonenet.com/products/RS2x00"
        ::= { rsFamilyMIB 3 }

rs2100  OBJECT-IDENTITY
            STATUS  current
            DESCRIPTION
            "RS 2100 Fixed 8 Port Gigabit Ethernet SX
             http://www.riverstonenet.com/products/RS2x00"
        ::= { rsFamilyMIB 4 }

rs3000  OBJECT-IDENTITY
            STATUS  current
            DESCRIPTION
            "RS 3000 2-slot switch router with fixed 16 port 10/100 Ethernet TX. 
             http://www.riverstonenet.com/products/RS3000"
        ::= { rsFamilyMIB 5 }

rs32000  OBJECT-IDENTITY
            STATUS  current
            DESCRIPTION
            "RS 32000 16-slot 500 10/100 or 120 GigEthernet switch router.
             http://www.riverstonenet.com/products/RS32000"
        ::= { rsFamilyMIB 6 }

rs1000  OBJECT-IDENTITY
            STATUS  current
            DESCRIPTION
            "RS 1000 2-slot switch router
             http://www.riverstonenet.com/products/RS1000"
        ::= { rsFamilyMIB 8 }

rs38000  OBJECT-IDENTITY
            STATUS  current
            DESCRIPTION
            "RS 38000 16-slot 500 10/100 or 120 GigEthernet wire-speed switch router.
             http://www.riverstonenet.com/products/RS38000"
        ::= { rsFamilyMIB 9 }



-- ****************  IA Product Line ***************



rsIA1100  OBJECT-IDENTITY
            STATUS  current
            DESCRIPTION
            "IA 1100 2-slot load balancer with fixed 16 port 10/100 Ethernet TX
             http://www.riverstonenet.com/products/internet-appliance"
        ::= { rsFamilyMIB 22 }

rsIA1200  OBJECT-IDENTITY
            STATUS  current
            DESCRIPTION
            "IA 1200 Fixed 8 port Gigabit Ethernet load balancer
             http://www.riverstonenet.com/products/internet-appliance"
        ::= { rsFamilyMIB 23 }

rsIA1500  OBJECT-IDENTITY
            STATUS  current
            DESCRIPTION
            "IA 1500 2-slot load balancer 
             http://www.riverstonenet.com/products/internet-appliance"
        ::= { rsFamilyMIB 27 }

END
