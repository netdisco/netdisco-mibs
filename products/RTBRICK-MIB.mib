RTBRICK-MIB DEFINITIONS ::= BEGIN

--
-- Top-level infrastructure of the RtBrick enterprise MIB tree
--

IMPORTS
    MODULE-IDENTITY, OBJECT-TYPE,
    Integer32, enterprises FROM SNMPv2-SMI
    TEXTUAL-CONVENTION, DisplayString,
    PhysAddress, TruthValue, RowStatus,
    TimeStamp, AutonomousType, TestAndIncr   FROM SNMPv2-TC;


rtbrick MODULE-IDENTITY
    LAST-UPDATED "201804140000Z"
    ORGANIZATION "RtBrick"
    CONTACT-INFO "E-mail: Stefan Lieberth <stefan@rtbrick.com>"
    DESCRIPTION
	"RtBrick top-level MIB tree infrastructure"
    REVISION     "201903010000Z"
    DESCRIPTION  "Initial revision"
    ::= { enterprises 50058 }


--
--  rtbrick enterprise-specific management objects
--

rtbrickTables                  OBJECT IDENTIFIER ::= { rtbrick 101 }
rtbrickProducts                OBJECT IDENTIFIER ::= { rtbrick 102 }
rtbrickTraps                   OBJECT IDENTIFIER ::= { rtbrick 103 }
rtbrickSyslogNotifications     OBJECT IDENTIFIER ::= { rtbrickTraps 1 }
rtbrickModules                 OBJECT IDENTIFIER ::= { rtbrick 104 }

END
