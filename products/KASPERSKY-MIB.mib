KASPERSKY-MIB DEFINITIONS ::= BEGIN

--
-- Top-level infrastructure of the Kaspersky Lab enterprise MIB tree
--

IMPORTS
   MODULE-IDENTITY, enterprises, OBJECT-TYPE, Integer32
           FROM SNMPv2-SMI
   MODULE-COMPLIANCE, OBJECT-GROUP
           FROM SNMPv2-CONF;

kaspersky MODULE-IDENTITY
   LAST-UPDATED "200608071800Z"
   ORGANIZATION "www.kaspersky.com"
   CONTACT-INFO "Kaspersky Lab"
   DESCRIPTION "Defined the MIB tree for Kaspersky products."
   -- revisions
   REVISION     "200608071800Z"
   DESCRIPTION  
           "Latest updated version of the kaspersky MIB module."
   REVISION     "200604250000Z"
   DESCRIPTION  
           "Initial tree."
   ::= { enterprises 23668 }

END
