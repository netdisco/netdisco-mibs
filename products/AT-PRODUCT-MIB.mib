-- ============================================================================
-- AT-PRODUCT.MIB, Allied Telesis enterprise MIB: products
--
-- Copyright (c) 2006 by Allied Telesis, Inc.
-- All rights reserved.
--
-- ============================================================================

    AT-PRODUCT-MIB DEFINITIONS ::= BEGIN

        IMPORTS
            alliedTelesis
                FROM AT-SMI-MIB
            MODULE-IDENTITY, OBJECT-IDENTITY
                FROM SNMPv2-SMI;


        products MODULE-IDENTITY
            LAST-UPDATED "201308010000Z"
            ORGANIZATION
                "Allied Telesis, Inc."
            CONTACT-INFO
                "  http://www.alliedtelesis.com"
            DESCRIPTION
                "This file defines the identities of Allied Telesis products.
                OID products is the root OBJECT IDENTIFIER. Beneath it there are subtrees
                bridgeRouter, routerSwitch and swhub, which are defined in AT-SMI-MIB."
            REVISION "201308010000Z"
            DESCRIPTION
                "Changed x950 to x930, added x230 and x310 products"
            REVISION "201307090000Z"
            DESCRIPTION
                "Added x510DP and IX5 products."
            REVISION "201304020000Z"
            DESCRIPTION
                "Added x950 products."
            REVISION "201203220000Z"
            DESCRIPTION
                "Added x510 product."
            REVISION "201112180500Z"
            DESCRIPTION
                "Added at-SBx81CFC400 and at-SBx81CFC960 products."
            REVISION "201109150000Z"
            DESCRIPTION
                "Added AT-SBx8106 product."
            REVISION "201109140000Z"
            DESCRIPTION
                "Added AT-SBx8112 product."
            REVISION "201109050000Z"
            DESCRIPTION
                "Added systemOID 196, 197 and 198"
            REVISION "201104040000Z"
            DESCRIPTION
                "Added Rapier 48x product"
            REVISION "201010120000Z"
            DESCRIPTION
                "Add swhub tree and systemOID 181 and 182"
            REVISION "201009200000Z"
            DESCRIPTION
                "Add Rapier24ib product"
            REVISION "201009070000Z"
            DESCRIPTION
                "Generic syntax tidy up"
            REVISION "201008190000Z"
            DESCRIPTION
                "Added bridgeRouter 81 at_AR560SRouter."
            REVISION "201007220000Z"
            DESCRIPTION
                "Renamed at_x600_24TsPoE_220W_PSU to at_x600_24TsPoEPlus to reflect usage."
            REVISION "201006150015Z"
            DESCRIPTION
                "MIB revision history dates in descriptions updated."
            REVISION "200905190000Z"
            DESCRIPTION
                "Added systemOID 93, 94, 95, 96, 97, 98, 99, 100 and 101"
            REVISION "200905150000Z"
            DESCRIPTION
                " Added systemOID 91,92. "
            REVISION "200803061300Z"
            DESCRIPTION
                " Added systemOID 69,70,75,76,77. "
            REVISION "200711150000Z"
            DESCRIPTION
                "Changed systemOID 67 from AT-8824R to 8724SL-V2."
            REVISION "200703210000Z"
            DESCRIPTION
                "Added systemOID for x900-48FS."
            REVISION "200702070000Z"
            DESCRIPTION
                "Added systemOID for AT-8824R."
            REVISION "200606140000Z"
            DESCRIPTION
                "Initial version of this MIB module."
            ::= { alliedTelesis 1 }



--
-- Node definitions
--

        bridgeRouter OBJECT-IDENTITY
            STATUS current
            DESCRIPTION
                "subtree beneath which brige product MIB object ids are assigned."
            ::= { products 1 }


        centreCOM-AR300Router OBJECT IDENTIFIER ::= { bridgeRouter 8 }


        centreCOM-AR720Router OBJECT IDENTIFIER ::= { bridgeRouter 11 }


        centreCOM-AR300LRouter OBJECT IDENTIFIER ::= { bridgeRouter 12 }


        centreCOM-AR310Router OBJECT IDENTIFIER ::= { bridgeRouter 13 }


        centreCOM-AR300LURouter OBJECT IDENTIFIER ::= { bridgeRouter 14 }


        centreCOM-AR300URouter OBJECT IDENTIFIER ::= { bridgeRouter 15 }


        centreCOM-AR310URouter OBJECT IDENTIFIER ::= { bridgeRouter 16 }


        centreCOM-AR350Router OBJECT IDENTIFIER ::= { bridgeRouter 17 }


        centreCOM-AR370Router OBJECT IDENTIFIER ::= { bridgeRouter 18 }


        centreCOM-AR330Router OBJECT IDENTIFIER ::= { bridgeRouter 19 }


        centreCOM-AR395Router OBJECT IDENTIFIER ::= { bridgeRouter 20 }


        centreCOM-AR390Router OBJECT IDENTIFIER ::= { bridgeRouter 21 }


        centreCOM-AR370URouter OBJECT IDENTIFIER ::= { bridgeRouter 22 }


        centreCOM-AR740Router OBJECT IDENTIFIER ::= { bridgeRouter 23 }


        centreCOM-AR140SRouter OBJECT IDENTIFIER ::= { bridgeRouter 24 }


        centreCOM-AR140URouter OBJECT IDENTIFIER ::= { bridgeRouter 25 }


        centreCOM-AR320Router OBJECT IDENTIFIER ::= { bridgeRouter 26 }


        centreCOM-AR130SRouter OBJECT IDENTIFIER ::= { bridgeRouter 27 }


        centreCOM-AR130URouter OBJECT IDENTIFIER ::= { bridgeRouter 28 }


        centreCOM-AR160Router OBJECT IDENTIFIER ::= { bridgeRouter 29 }


        at-AR740RouterDC OBJECT IDENTIFIER ::= { bridgeRouter 43 }


        centreCOM-AR120Router OBJECT IDENTIFIER ::= { bridgeRouter 44 }


        at-AR410Router OBJECT IDENTIFIER ::= { bridgeRouter 47 }


        at-AR725Router OBJECT IDENTIFIER ::= { bridgeRouter 48 }


        at-AR745Router OBJECT IDENTIFIER ::= { bridgeRouter 49 }


        at-AR410v2Router OBJECT IDENTIFIER ::= { bridgeRouter 50 }


        at-AR410v3Router OBJECT IDENTIFIER ::= { bridgeRouter 51 }


        at-AR725RouterDC OBJECT IDENTIFIER ::= { bridgeRouter 52 }


        at-AR745RouterDC OBJECT IDENTIFIER ::= { bridgeRouter 53 }


        at-AR450Router OBJECT IDENTIFIER ::= { bridgeRouter 54 }


        at-AR450DualRouter OBJECT IDENTIFIER ::= { bridgeRouter 55 }


        at-AR440Router OBJECT IDENTIFIER ::= { bridgeRouter 59 }


        at-AR441Router OBJECT IDENTIFIER ::= { bridgeRouter 60 }


        at-AR442Router OBJECT IDENTIFIER ::= { bridgeRouter 61 }


        at-AR443Router OBJECT IDENTIFIER ::= { bridgeRouter 62 }


        at-AR444Router OBJECT IDENTIFIER ::= { bridgeRouter 63 }


        at-AR420Router OBJECT IDENTIFIER ::= { bridgeRouter 64 }


        at-AR415SRouter OBJECT IDENTIFIER ::= { bridgeRouter 71 }


        at-AR415SRouterDC OBJECT IDENTIFIER ::= { bridgeRouter 72 }


        at-AR550Router OBJECT IDENTIFIER ::= { bridgeRouter 73 }


        at-AR551Router OBJECT IDENTIFIER ::= { bridgeRouter 74 }


        at-AR552Router OBJECT IDENTIFIER ::= { bridgeRouter 75 }


        at-AR550SRouterDP OBJECT IDENTIFIER ::= { bridgeRouter 76 }


        at-AR570Router OBJECT IDENTIFIER ::= { bridgeRouter 78 }


        at-AR770Router OBJECT IDENTIFIER ::= { bridgeRouter 79 }


        at-AR750SRouterDP OBJECT IDENTIFIER ::= { bridgeRouter 80 }


        at-AR560SRouter OBJECT IDENTIFIER ::= { bridgeRouter 81 }


        routerSwitch OBJECT-IDENTITY
            STATUS current
            DESCRIPTION
                "subtree beneath which router and switch product MIB object ids are assigned."
            ::= { products 14 }


        at-Rapier24 OBJECT IDENTIFIER ::= { routerSwitch 1 }


        at-Rapier16fSC OBJECT IDENTIFIER ::= { routerSwitch 2 }


        at-Rapier16fVF OBJECT IDENTIFIER ::= { routerSwitch 3 }


        at-Rapier16fMT OBJECT IDENTIFIER ::= { routerSwitch 4 }


        at-Rapier48 OBJECT IDENTIFIER ::= { routerSwitch 5 }


        at-Rapier8t8fSC OBJECT IDENTIFIER ::= { routerSwitch 6 }


        at-Rapier8t8fSCi OBJECT IDENTIFIER ::= { routerSwitch 7 }


        at-Rapier8t8fMT OBJECT IDENTIFIER ::= { routerSwitch 8 }


        at-Rapier8t8fMTi OBJECT IDENTIFIER ::= { routerSwitch 9 }


        at-Rapier8fSC OBJECT IDENTIFIER ::= { routerSwitch 10 }


        at-Rapier8fSCi OBJECT IDENTIFIER ::= { routerSwitch 11 }


        at-Rapier8fMT OBJECT IDENTIFIER ::= { routerSwitch 12 }


        at-Rapier8fMTi OBJECT IDENTIFIER ::= { routerSwitch 13 }


        at-Rapier16fMTi OBJECT IDENTIFIER ::= { routerSwitch 14 }


        at-RapierG6 OBJECT IDENTIFIER ::= { routerSwitch 15 }


        at-RapierG6SX OBJECT IDENTIFIER ::= { routerSwitch 16 }


        at-RapierG6LX OBJECT IDENTIFIER ::= { routerSwitch 17 }


        at-RapierG6MT OBJECT IDENTIFIER ::= { routerSwitch 18 }


        at-Rapier16fSCi OBJECT IDENTIFIER ::= { routerSwitch 19 }


        at-Rapier24i OBJECT IDENTIFIER ::= { routerSwitch 20 }


        at-Rapier48i OBJECT IDENTIFIER ::= { routerSwitch 21 }


        at-Switchblade4AC OBJECT IDENTIFIER ::= { routerSwitch 22 }


        at-Switchblade4DC OBJECT IDENTIFIER ::= { routerSwitch 23 }


        at-Switchblade8AC OBJECT IDENTIFIER ::= { routerSwitch 24 }


        at-Switchblade8DC OBJECT IDENTIFIER ::= { routerSwitch 25 }


        at-9816GF OBJECT IDENTIFIER ::= { routerSwitch 26 }


        at-9812TF OBJECT IDENTIFIER ::= { routerSwitch 27 }


        at-9816GB OBJECT IDENTIFIER ::= { routerSwitch 28 }


        at-9812T OBJECT IDENTIFIER ::= { routerSwitch 29 }


        at-8724XL OBJECT IDENTIFIER ::= { routerSwitch 30 }


        at-8748XL OBJECT IDENTIFIER ::= { routerSwitch 31 }


        at-8724XLDC OBJECT IDENTIFIER ::= { routerSwitch 32 }


        at-8748XLDC OBJECT IDENTIFIER ::= { routerSwitch 33 }


        at-9816GB-DC OBJECT IDENTIFIER ::= { routerSwitch 34 }


        at-9812T-DC OBJECT IDENTIFIER ::= { routerSwitch 35 }


        at-8824 OBJECT IDENTIFIER ::= { routerSwitch 36 }


        at-8848 OBJECT IDENTIFIER ::= { routerSwitch 37 }


        at-8824-DC OBJECT IDENTIFIER ::= { routerSwitch 38 }


        at-8848-DC OBJECT IDENTIFIER ::= { routerSwitch 39 }


        at-8624XL-80 OBJECT IDENTIFIER ::= { routerSwitch 41 }


        at-8724XL-80 OBJECT IDENTIFIER ::= { routerSwitch 42 }


        at-8748XL-80 OBJECT IDENTIFIER ::= { routerSwitch 43 }


        at-8948EX OBJECT IDENTIFIER ::= { routerSwitch 44 }


        at-8948i OBJECT IDENTIFIER ::= { routerSwitch 45 }


        at-8624T2M OBJECT IDENTIFIER ::= { routerSwitch 46 }


        at-Rapier24i-DC-NEBS OBJECT IDENTIFIER ::= { routerSwitch 47 }


        at-8724XL-DC-NEBS OBJECT IDENTIFIER ::= { routerSwitch 48 }


        at-9924T OBJECT IDENTIFIER ::= { routerSwitch 49 }


        at-9924SP OBJECT IDENTIFIER ::= { routerSwitch 50 }


        at-9924T-4SP OBJECT IDENTIFIER ::= { routerSwitch 51 }


        at-9924TEMC OBJECT IDENTIFIER ::= { routerSwitch 53 }


        at-8724MLB OBJECT IDENTIFIER ::= { routerSwitch 55 }


        at-8624POE OBJECT IDENTIFIER ::= { routerSwitch 56 }


        at-9924Ts OBJECT IDENTIFIER ::= { routerSwitch 57 }


        at-86482SP OBJECT IDENTIFIER ::= { routerSwitch 58 }


        at-9924Ti OBJECT IDENTIFIER ::= { routerSwitch 59 }


        at-9924SPi OBJECT IDENTIFIER ::= { routerSwitch 60 }


        at-9924Tsi OBJECT IDENTIFIER ::= { routerSwitch 61 }


        at-9924SPsi OBJECT IDENTIFIER ::= { routerSwitch 62 }


        at-8948i-N OBJECT IDENTIFIER ::= { routerSwitch 63 }


        at-9924Tsi-N OBJECT IDENTIFIER ::= { routerSwitch 64 }


        at-Rapier48w OBJECT IDENTIFIER ::= { routerSwitch 65 }


        at-8724SL-V2 OBJECT IDENTIFIER ::= { routerSwitch 67 }


        x900-48FS OBJECT IDENTIFIER ::= { routerSwitch 68 }


        at-SwitchBladex908 OBJECT IDENTIFIER ::= { routerSwitch 69 }


        at-x900-12XTS OBJECT IDENTIFIER ::= { routerSwitch 70 }


        at-Rapier48wb OBJECT IDENTIFIER ::= { routerSwitch 71 }


        at-Rapier48w-AC OBJECT IDENTIFIER ::= { routerSwitch 72 }


        at-Rapier48wb-AC OBJECT IDENTIFIER ::= { routerSwitch 73 }


        at-x900-24XT OBJECT IDENTIFIER ::= { routerSwitch 75 }


        at-x900-24XS OBJECT IDENTIFIER ::= { routerSwitch 76 }


        at-x900-24XT-N OBJECT IDENTIFIER ::= { routerSwitch 77 }


        at-x600-24Ts OBJECT IDENTIFIER ::= { routerSwitch 80 }


        at-x600-24TsXP OBJECT IDENTIFIER ::= { routerSwitch 81 }


        at-x600-48Ts OBJECT IDENTIFIER ::= { routerSwitch 82 }


        at-x600-48TsXP OBJECT IDENTIFIER ::= { routerSwitch 83 }


	at-rapier24ib-NEBS OBJECT IDENTIFIER ::= { routerSwitch 84 }


	at-rapier24ib-DC-NEBS OBJECT IDENTIFIER ::= { routerSwitch 85 }


        at-SBx8112 OBJECT IDENTIFIER ::= { routerSwitch 86 }

        at-SBx81CFC400  OBJECT IDENTIFIER ::= { routerSwitch 87 }

        at-SBx81CFC960  OBJECT IDENTIFIER ::= { routerSwitch 88 }

        at-x600-24TsPoE OBJECT IDENTIFIER ::= { routerSwitch 91 }


        at-x600-24TsPoEPlus OBJECT IDENTIFIER ::= { routerSwitch 92 }


        x610-48Ts-X-POEPlus OBJECT IDENTIFIER ::= { routerSwitch 93 }


        x610-48Ts-POEPlus OBJECT IDENTIFIER ::= { routerSwitch 94 }


        x610-24Ts-X-POEPlus OBJECT IDENTIFIER ::= { routerSwitch 95 }


        x610-24Ts-POEPlus OBJECT IDENTIFIER ::= { routerSwitch 96 }


        x610-48Ts-X OBJECT IDENTIFIER ::= { routerSwitch 97 }


        x610-48Ts OBJECT IDENTIFIER ::= { routerSwitch 98 }


        x610-24Ts-X OBJECT IDENTIFIER ::= { routerSwitch 99 }


        x610-24Ts OBJECT IDENTIFIER ::= { routerSwitch 100 }


        x610-24SP-X OBJECT IDENTIFIER ::= { routerSwitch 101 }


        at-RP48xDC OBJECT IDENTIFIER ::= { routerSwitch 105 }


        at-x510-28GTX OBJECT IDENTIFIER ::= { routerSwitch 109 }


        at-x510-28GPX OBJECT IDENTIFIER ::= { routerSwitch 110 }


        at-x510-28GSX OBJECT IDENTIFIER ::= { routerSwitch 111 }


        at-x510-52GTX OBJECT IDENTIFIER ::= { routerSwitch 112 }


        at-x510-52GPX OBJECT IDENTIFIER ::= { routerSwitch 113 }


        at-SBx8106 OBJECT IDENTIFIER ::= { routerSwitch 114 }

        at-x510DP-52GTX OBJECT IDENTIFIER ::= { routerSwitch 116 }


        at-IX5-28GPX OBJECT IDENTIFIER ::= { routerSwitch 117 }


        at-x930-28GTX OBJECT IDENTIFIER ::= { routerSwitch 118 }


        at-x930-28GPX OBJECT IDENTIFIER ::= { routerSwitch 119 }


        at-x930-28GSX OBJECT IDENTIFIER ::= { routerSwitch 120 }


        at-x930-52GTX OBJECT IDENTIFIER ::= { routerSwitch 121 }


        at-x930-52GPX OBJECT IDENTIFIER ::= { routerSwitch 122 }


        swhub OBJECT-IDENTITY
            STATUS current
            DESCRIPTION
                "subtree beneath which Layer2 switch product MIB object ids are assigned."
            ::= { products 4 }


        at-x200-GE52T OBJECT IDENTIFIER ::= { swhub 181 }


        at-x200-GE28T OBJECT IDENTIFIER ::= { swhub 182 }


        at-x210-9GT OBJECT IDENTIFIER ::= { swhub 196 }


        at-x210-16GT OBJECT IDENTIFIER ::= { swhub 197 }


        at-x210-24GT OBJECT IDENTIFIER ::= { swhub 198 }


        at-x310-26FT OBJECT IDENTIFIER ::= { swhub 216 }


        at-x310-50FT OBJECT IDENTIFIER ::= { swhub 217 }


        at-x310-26FP OBJECT IDENTIFIER ::= { swhub 218 }


        at-x310-50FP OBJECT IDENTIFIER ::= { swhub 219 }


        at-x310-26GT OBJECT IDENTIFIER ::= { swhub 220 }


        at-x310-50GT OBJECT IDENTIFIER ::= { swhub 221 }


        at-x310-26GP OBJECT IDENTIFIER ::= { swhub 222 }


        at-x310-50GP OBJECT IDENTIFIER ::= { swhub 223 }
        
        
        at-x230-10GT OBJECT IDENTIFIER ::= { swhub 224 }


        at-x230-18GT OBJECT IDENTIFIER ::= { swhub 225 }


        at-x230-28GT OBJECT IDENTIFIER ::= { swhub 226 }


        at-x230-52GT OBJECT IDENTIFIER ::= { swhub 227 }


        at-x230-10GP OBJECT IDENTIFIER ::= { swhub 228 }


        at-x230-18GP OBJECT IDENTIFIER ::= { swhub 229 }


        at-x230-28GP OBJECT IDENTIFIER ::= { swhub 230 }


        at-x230-52GP OBJECT IDENTIFIER ::= { swhub 231 }


        at-x230-10GPT OBJECT IDENTIFIER ::= { swhub 232 }


    END

--
-- AT-PRODUCT-MIB.my
--
