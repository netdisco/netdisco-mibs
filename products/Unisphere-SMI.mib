-- *****************************************************************************
-- Unisphere Networks Enterprise Structure of Management Information
--
-- Copyright (c) 1999, 2001 Unisphere Networks, Inc.  All rights reserved.
-- *****************************************************************************

Unisphere-SMI DEFINITIONS ::= BEGIN

IMPORTS
    MODULE-IDENTITY, enterprises
        FROM SNMPv2-SMI;

unisphere MODULE-IDENTITY
    LAST-UPDATED "200106012146Z"  -- 01-Jun-01 05:46 PM EDT
    ORGANIZATION "Unisphere Networks, Inc."
    CONTACT-INFO
        "       Unisphere Networks, Inc.
                Customer Service
        Postal: 10 Technology Park Drive
                Westford, MA  01886
                USA
        Tel:    +1 978 589 5800
        E-mail: info@UnisphereNetworks.com"
    DESCRIPTION
        "The Structure of Management Information for the Unisphere Networks,
        Inc. enterprise.  This is the top-level registry for managed objects
        under the Unisphere Networks SNMP management enterprise object
        identifier."
    -- Revision History
    REVISION    "200106012146Z"  -- 01-Jun-01 05:46 PM EDT
    DESCRIPTION
        "Replaced OBJECT-IDENTITYs with OBJECT IDENTIFIERs."
    REVISION    "200006011430Z"  -- 01-Jun-00 10:30 AM EDT
    DESCRIPTION
        "Added usVoiceAdmin and usDataAdmin branchs."
    REVISION    "200005240400Z"  -- 24-May-00 12:00 AM EDT
    DESCRIPTION
        "Added node for UMC MIB"   
    REVISION      "9912131936Z"  -- 13-Dec-99 02:36 PM EST
    DESCRIPTION
        "Added REFERENCE clauses to OBJECT-IDENTITY definitions."
    REVISION      "9911080000Z"  -- 08-Nov-99
    DESCRIPTION
        "The initial release of this management informaiton module."
    ::= { enterprises 4874 }    -- assigned by IANA


-- *********************************************************************
-- Top-level Unisphere Networks management module object identifier
-- assignments.
-- *********************************************************************

usProducts OBJECT IDENTIFIER
--  STATUS      current
--  DESCRIPTION
--      "usProducts is the root object identifier under which
--      sysObjectID values are assigned."
--  REFERENCE
--      "Actual values are defined in the Unisphere-Products-MIB module
--      (in the usProducts.mi2 file)."
    ::= { unisphere 1 }

usMibs OBJECT IDENTIFIER
--  STATUS      current
--  DESCRIPTION
--      "usMibs is the root object identifier under which all Unisphere
--      Networks SNMP managed object (MIB) modules are defined.  Common
--      (company-wide) MIB modules are defined directly under this
--      node."
    ::= { unisphere 2 }

usVoiceMibs OBJECT IDENTIFIER
--  STATUS      current
--  DESCRIPTION
--      "usVoiceMibs is the root object identifier under which SNMP
--      managed object (MIB) modules specific to Unisphere Networks
--      voice communications products are defined."
--  REFERENCE
--      "Actual values are defined in the Unisphere-Voice-MIBs module
--      (in the usVoiceMibs.mi2 file)."
    ::= { usMibs 1 }

usDataMibs OBJECT IDENTIFIER
--  STATUS      current
--  DESCRIPTION
--      "usDataMibs is the root object identifier under which SNMP
--      managed object (MIB) modules specific to Unisphere Networks
--      data communications products are defined."
--  REFERENCE
--      "Actual values are defined in the Unisphere-Data-MIBs module (in
--      the usDataMibs.mi2 file)."
    ::= { usMibs 2 }

usExperiment OBJECT IDENTIFIER
--  STATUS      current
--  DESCRIPTION
--      "The usExperiment object identifier roots experimental MIBs,
--      which are defined as:
--
--      1) IETF work-in-process MIBs which have not been assigned a
--         permanent object identifier by the IANA.
--
--      2) Unisphere work-in-process MIBs that have not achieved final
--         production quality or field experience.
--
--      NOTE: Support for MIBs under the usExperiment subtree is
--            temporary and changes to objects may occur without
--            notice."
    ::= { unisphere 3 }

usVoiceExperiment OBJECT IDENTIFIER
--  STATUS      current
--  DESCRIPTION
--      "usVoiceExperiment is the root object identifier under which
--      experimental SNMP managed object (MIB) modules specific to
--      Unisphere Networks voice communications products are defined."
--  REFERENCE
--      "Actual values are defined in the Unisphere-Voice-Experiment
--      module (currently not defined)."
    ::= { usExperiment 1 }

usDataExperiment OBJECT IDENTIFIER
--  STATUS      current
--  DESCRIPTION
--      "usDataExperiment is the root object identifier under which
--      experimental SNMP managed object (MIB) modules specific to
--      Unisphere Networks data communications products are defined."
--  REFERENCE
--      "Actual values are defined in the Unisphere-Data-Experiment
--      module (in the usDataExperiment.mi2 file)."
    ::= { usExperiment 2 }

usAdmin OBJECT IDENTIFIER
--  STATUS      current
--  DESCRIPTION
--      "usAdmin is reserved for administratively assigned object
--      identifiers, i.e. those not associated with MIB objects.
--      Examples include items such as chipset or ASIC identifiers."
    ::= { unisphere 4 }

usVoiceAdmin OBJECT IDENTIFIER
--  STATUS      current
--  DESCRIPTION
--      "usVoiceAdmin is the root for administratively assigned object
--      identifiers for Unisphere Networks voice communications products."
    ::= { usAdmin 1 }

usDataAdmin OBJECT IDENTIFIER
--  STATUS      current
--  DESCRIPTION
--      "usDataAdmin is the root for administratively assigned object
--      identifiers for Unisphere Networks data communications products."
--  REFERENCE
--      "Actual values are defined in the Unisphere-Data-Registry
--      module (in the usDataRegistry.mi2 file)."
    ::= { usAdmin 2 }

usAgentCapability OBJECT IDENTIFIER
--  STATUS      current
--  DESCRIPTION
--      "usAgentCapability provides a root object identifier under which
--      AGENT-CAPABILITIES modules are assigned.  Each product's agent's
--      capabilities definition appears in a separate module."
    ::= { unisphere 5 }

usVoiceAgents OBJECT IDENTIFIER
--  STATUS      current
--  DESCRIPTION
--      "usVoiceAgents is the root object identifier under which agent
--      capabilities modules for Unisphere Networks voice
--      communications products are defined."
--  REFERENCE
--      "Actual values are defined in the Unisphere-Voice-Agents module
--      (currently not defined)."
    ::= { usAgentCapability 1 }

usDataAgents OBJECT IDENTIFIER
--  STATUS      current
--  DESCRIPTION
--      "usDataAgents is the root object identifier under which agent
--      capabilities modules for Unisphere Networks' data communications
--      products are defined."
--  REFERENCE
--      "Actual values are defined in the Unisphere-Data-Agents module
--      (in the usDataAgents.mi2 file)."
    ::= { usAgentCapability 2 }

usNetMgmtProducts OBJECT IDENTIFIER
--  STATUS      current
--  DESCRIPTION
--      "usNetMgmtProducts provides a root object identifier for the
--      definition of nodes pertaining to Unisphere Networks' network
--      management products.  Examples include:
--
--              SMC-Service Management Center
--              SSC-Service Selection Server
--              NMC-Network Management Center
--              NMC-RX(routing switch element manager)
--              NMC-SMX(service mediation switch element manager)
--              UMC-Unisphere Management Center"
--  REFERENCE
--      "Actual values are defined in the Unisphere-Net-Mgmt-Products
--      module (currently not defined)."
    ::= { unisphere 6 }

usUmcMib OBJECT IDENTIFIER
--  STATUS      current
--  DESCRIPTION
--      "usUmcMib is the root object identifier for definitions of nodes
--       pertaining to the Unisphere Management Center products."
--  REFERENCE
--      "Actual values are defined in Unisphere-UMC-MIB."
    ::= { usNetMgmtProducts 1 }

END
