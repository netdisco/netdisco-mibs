F5OS-APPLIANCE-ALERT-NOTIF-MIB DEFINITIONS ::= BEGIN

IMPORTS
    MODULE-IDENTITY, NOTIFICATION-TYPE
        FROM SNMPv2-SMI
    NOTIFICATION-GROUP
        FROM SNMPv2-CONF
    f5Alerts, alertSource, alertEffect, alertSeverity,
    alertTimeStamp, alertDescription, f5AlertNotificationGroup
        FROM F5-ALERT-DEF-MIB
    ;

f5AlertNotification MODULE-IDENTITY
    LAST-UPDATED "201908040941Z"
    ORGANIZATION "F5 Networks, Inc."
    CONTACT-INFO
         "postal: F5 Networks, Inc.
                  801 5th Ave
                  Seattle,  WA 98104
          phone:  (206) 272-5555
          email:  support@f5.com"

    DESCRIPTION
        "Top-level infrastructure of the F5 Networks enterprise Alert MIB tree."

    REVISION       "201908040941Z"
    DESCRIPTION
        "F5 Alert Notification Types."

    ::= { f5Alerts 1 }

--=====================================================================--
-- F5 Alert Trap
--=====================================================================--

hardware-device-fault  NOTIFICATION-TYPE 
    OBJECTS {
              alertSource,
              alertEffect,
              alertSeverity,
              alertTimeStamp,
              alertDescription
    }
    STATUS    current
    DESCRIPTION
        "Hardware device fault detected"
    ::= { f5AlertNotification 65536 }

firmware-fault  NOTIFICATION-TYPE 
    OBJECTS {
              alertSource,
              alertEffect,
              alertSeverity,
              alertTimeStamp,
              alertDescription
    }
    STATUS    current
    DESCRIPTION
        "Firmware diagnostic state fault detected"
    ::= { f5AlertNotification 65537 }

unknown-alarm  NOTIFICATION-TYPE 
    OBJECTS {
              alertSource,
              alertEffect,
              alertSeverity,
              alertTimeStamp,
              alertDescription
    }
    STATUS    current
    DESCRIPTION
        "Unregistered alarm detected"
    ::= { f5AlertNotification 65538 }

drive-fault  NOTIFICATION-TYPE 
    OBJECTS {
              alertSource,
              alertEffect,
              alertSeverity,
              alertTimeStamp,
              alertDescription
    }
    STATUS    current
    DESCRIPTION
        "Fault in drive detected"
    ::= { f5AlertNotification 65540 }

aom-fault  NOTIFICATION-TYPE 
    OBJECTS {
              alertSource,
              alertEffect,
              alertSeverity,
              alertTimeStamp,
              alertDescription
    }
    STATUS    current
    DESCRIPTION
        "Fault detected in the AOM"
    ::= { f5AlertNotification 65543 }

drive-capacity-fault  NOTIFICATION-TYPE 
    OBJECTS {
              alertSource,
              alertEffect,
              alertSeverity,
              alertTimeStamp,
              alertDescription
    }
    STATUS    current
    DESCRIPTION
        "Running out of drive capacity"
    ::= { f5AlertNotification 65544 }

power-fault  NOTIFICATION-TYPE 
    OBJECTS {
              alertSource,
              alertEffect,
              alertSeverity,
              alertTimeStamp,
              alertDescription
    }
    STATUS    current
    DESCRIPTION
        "Power fault detected in hardware"
    ::= { f5AlertNotification 65545 }

thermal-fault  NOTIFICATION-TYPE 
    OBJECTS {
              alertSource,
              alertEffect,
              alertSeverity,
              alertTimeStamp,
              alertDescription
    }
    STATUS    current
    DESCRIPTION
        "Thermal fault detected in hardware"
    ::= { f5AlertNotification 65546 }

firmware-update-status  NOTIFICATION-TYPE 
    OBJECTS {
              alertSource,
              alertEffect,
              alertSeverity,
              alertTimeStamp,
              alertDescription
    }
    STATUS    current
    DESCRIPTION
        "Firmware update status"
    ::= { f5AlertNotification 65550 }

drive-utilization  NOTIFICATION-TYPE 
    OBJECTS {
              alertSource,
              alertEffect,
              alertSeverity,
              alertTimeStamp,
              alertDescription
    }
    STATUS    current
    DESCRIPTION
        "Drive utilization growth rate is high"
    ::= { f5AlertNotification 65551 }

datapath-fault  NOTIFICATION-TYPE 
    OBJECTS {
              alertSource,
              alertEffect,
              alertSeverity,
              alertTimeStamp,
              alertDescription
    }
    STATUS    current
    DESCRIPTION
        "Hardware datapath fault"
    ::= { f5AlertNotification 65578 }

dimm-fault  NOTIFICATION-TYPE 
    OBJECTS {
              alertSource,
              alertEffect,
              alertSeverity,
              alertTimeStamp,
              alertDescription
    }
    STATUS    current
    DESCRIPTION
        "DIMM fault detected"
    ::= { f5AlertNotification 65652 }

module-present  NOTIFICATION-TYPE 
    OBJECTS {
              alertSource,
              alertEffect,
              alertSeverity,
              alertTimeStamp,
              alertDescription
    }
    STATUS    current
    DESCRIPTION
        "Change detected in appliance module presence"
    ::= { f5AlertNotification 66304 }

psu-fault  NOTIFICATION-TYPE 
    OBJECTS {
              alertSource,
              alertEffect,
              alertSeverity,
              alertTimeStamp,
              alertDescription
    }
    STATUS    current
    DESCRIPTION
        "PSU fault detected"
    ::= { f5AlertNotification 66305 }

lcd-fault  NOTIFICATION-TYPE 
    OBJECTS {
              alertSource,
              alertEffect,
              alertSeverity,
              alertTimeStamp,
              alertDescription
    }
    STATUS    current
    DESCRIPTION
        "Fault detected in LCD module"
    ::= { f5AlertNotification 66306 }

module-communication-error  NOTIFICATION-TYPE 
    OBJECTS {
              alertSource,
              alertEffect,
              alertSeverity,
              alertTimeStamp,
              alertDescription
    }
    STATUS    current
    DESCRIPTION
        "Module communication error detected"
    ::= { f5AlertNotification 66307 }

fips-fault  NOTIFICATION-TYPE 
    OBJECTS {
              alertSource,
              alertEffect,
              alertSeverity,
              alertTimeStamp,
              alertDescription
    }
    STATUS    current
    DESCRIPTION
        "Fault detected in FIPS module"
    ::= { f5AlertNotification 66308 }

kmip-server-fault  NOTIFICATION-TYPE 
    OBJECTS {
              alertSource,
              alertEffect,
              alertSeverity,
              alertTimeStamp,
              alertDescription
    }
    STATUS    current
    DESCRIPTION
        "KMIP server communication error detected"
    ::= { f5AlertNotification 66309 }

kmip-managed-object-error  NOTIFICATION-TYPE 
    OBJECTS {
              alertSource,
              alertEffect,
              alertSeverity,
              alertTimeStamp,
              alertDescription
    }
    STATUS    current
    DESCRIPTION
        "KMIP managed object error detected"
    ::= { f5AlertNotification 66310 }

drive-sed-error  NOTIFICATION-TYPE 
    OBJECTS {
              alertSource,
              alertEffect,
              alertSeverity,
              alertTimeStamp,
              alertDescription
    }
    STATUS    current
    DESCRIPTION
        "Drive SED error detected"
    ::= { f5AlertNotification 66311 }

uefi-communication-error  NOTIFICATION-TYPE 
    OBJECTS {
              alertSource,
              alertEffect,
              alertSeverity,
              alertTimeStamp,
              alertDescription
    }
    STATUS    current
    DESCRIPTION
        "UEFI communication error detected"
    ::= { f5AlertNotification 66312 }

fipsError  NOTIFICATION-TYPE 
    OBJECTS {
              alertSource,
              alertEffect,
              alertSeverity,
              alertTimeStamp,
              alertDescription
    }
    STATUS    current
    DESCRIPTION
        "FIPS error identified in one or more services"
    ::= { f5AlertNotification 196608 }

core-dump  NOTIFICATION-TYPE 
    OBJECTS {
              alertSource,
              alertEffect,
              alertSeverity,
              alertTimeStamp,
              alertDescription
    }
    STATUS    current
    DESCRIPTION
        "Detected process crash on the system"
    ::= { f5AlertNotification 327680 }

reboot  NOTIFICATION-TYPE 
    OBJECTS {
              alertSource,
              alertEffect,
              alertSeverity,
              alertTimeStamp,
              alertDescription
    }
    STATUS    current
    DESCRIPTION
        "Trap notification when the system or node reboot is triggered."
    ::= { f5AlertNotification 327681 }

incompatible-image  NOTIFICATION-TYPE 
    OBJECTS {
              alertSource,
              alertEffect,
              alertSeverity,
              alertTimeStamp,
              alertDescription
    }
    STATUS    current
    DESCRIPTION
        "Trap notification when the platform incompatible image is imported."
    ::= { f5AlertNotification 327682 }

login-failed  NOTIFICATION-TYPE 
    OBJECTS {
              alertSource,
              alertEffect,
              alertSeverity,
              alertTimeStamp,
              alertDescription
    }
    STATUS    current
    DESCRIPTION
        "Trap notification when a bad F5OS login is happened"
    ::= { f5AlertNotification 327683 }

raidEvent  NOTIFICATION-TYPE 
    OBJECTS {
              alertSource,
              alertEffect,
              alertSeverity,
              alertTimeStamp,
              alertDescription
    }
    STATUS    current
    DESCRIPTION
        "Notification of raid event"
    ::= { f5AlertNotification 393216 }

txPwrHiAlarm  NOTIFICATION-TYPE 
    OBJECTS {
              alertSource,
              alertEffect,
              alertSeverity,
              alertTimeStamp,
              alertDescription
    }
    STATUS    current
    DESCRIPTION
        "Transmitter power high alarm"
    ::= { f5AlertNotification 262400 }

txPwrHiWarn  NOTIFICATION-TYPE 
    OBJECTS {
              alertSource,
              alertEffect,
              alertSeverity,
              alertTimeStamp,
              alertDescription
    }
    STATUS    current
    DESCRIPTION
        "Transmitter power high warning"
    ::= { f5AlertNotification 262401 }

txPwrLoAlarm  NOTIFICATION-TYPE 
    OBJECTS {
              alertSource,
              alertEffect,
              alertSeverity,
              alertTimeStamp,
              alertDescription
    }
    STATUS    current
    DESCRIPTION
        "Transmitter power low alarm"
    ::= { f5AlertNotification 262402 }

txPwrLoWarn  NOTIFICATION-TYPE 
    OBJECTS {
              alertSource,
              alertEffect,
              alertSeverity,
              alertTimeStamp,
              alertDescription
    }
    STATUS    current
    DESCRIPTION
        "Transmitter power low warning"
    ::= { f5AlertNotification 262403 }

rxPwrHiAlarm  NOTIFICATION-TYPE 
    OBJECTS {
              alertSource,
              alertEffect,
              alertSeverity,
              alertTimeStamp,
              alertDescription
    }
    STATUS    current
    DESCRIPTION
        "Receiver power high alarm"
    ::= { f5AlertNotification 262404 }

rxPwrHiWarn  NOTIFICATION-TYPE 
    OBJECTS {
              alertSource,
              alertEffect,
              alertSeverity,
              alertTimeStamp,
              alertDescription
    }
    STATUS    current
    DESCRIPTION
        "Receiver power high warning"
    ::= { f5AlertNotification 262405 }

rxPwrLoAlarm  NOTIFICATION-TYPE 
    OBJECTS {
              alertSource,
              alertEffect,
              alertSeverity,
              alertTimeStamp,
              alertDescription
    }
    STATUS    current
    DESCRIPTION
        "Receiver power low alarm"
    ::= { f5AlertNotification 262406 }

rxPwrLoWarn  NOTIFICATION-TYPE 
    OBJECTS {
              alertSource,
              alertEffect,
              alertSeverity,
              alertTimeStamp,
              alertDescription
    }
    STATUS    current
    DESCRIPTION
        "Receiver power low warning"
    ::= { f5AlertNotification 262407 }

txBiasHiAlarm  NOTIFICATION-TYPE 
    OBJECTS {
              alertSource,
              alertEffect,
              alertSeverity,
              alertTimeStamp,
              alertDescription
    }
    STATUS    current
    DESCRIPTION
        "Transmitter bias high alarm"
    ::= { f5AlertNotification 262408 }

txBiasHiWarn  NOTIFICATION-TYPE 
    OBJECTS {
              alertSource,
              alertEffect,
              alertSeverity,
              alertTimeStamp,
              alertDescription
    }
    STATUS    current
    DESCRIPTION
        "Transmitter bias high warning"
    ::= { f5AlertNotification 262409 }

txBiasLoAlarm  NOTIFICATION-TYPE 
    OBJECTS {
              alertSource,
              alertEffect,
              alertSeverity,
              alertTimeStamp,
              alertDescription
    }
    STATUS    current
    DESCRIPTION
        "Transmitter bias low alarm"
    ::= { f5AlertNotification 262410 }

txBiasLoWarn  NOTIFICATION-TYPE 
    OBJECTS {
              alertSource,
              alertEffect,
              alertSeverity,
              alertTimeStamp,
              alertDescription
    }
    STATUS    current
    DESCRIPTION
        "Transmitter bias low warning"
    ::= { f5AlertNotification 262411 }

ddmTempHiAlarm  NOTIFICATION-TYPE 
    OBJECTS {
              alertSource,
              alertEffect,
              alertSeverity,
              alertTimeStamp,
              alertDescription
    }
    STATUS    current
    DESCRIPTION
        "Optic temperature high alarm"
    ::= { f5AlertNotification 262412 }

ddmTempHiWarn  NOTIFICATION-TYPE 
    OBJECTS {
              alertSource,
              alertEffect,
              alertSeverity,
              alertTimeStamp,
              alertDescription
    }
    STATUS    current
    DESCRIPTION
        "Optic temperature high warning"
    ::= { f5AlertNotification 262413 }

ddmTempLoAlarm  NOTIFICATION-TYPE 
    OBJECTS {
              alertSource,
              alertEffect,
              alertSeverity,
              alertTimeStamp,
              alertDescription
    }
    STATUS    current
    DESCRIPTION
        "Optic temperature low alarm"
    ::= { f5AlertNotification 262414 }

ddmTempLoWarn  NOTIFICATION-TYPE 
    OBJECTS {
              alertSource,
              alertEffect,
              alertSeverity,
              alertTimeStamp,
              alertDescription
    }
    STATUS    current
    DESCRIPTION
        "Optic temperature low warning"
    ::= { f5AlertNotification 262415 }

ddmVccHiAlarm  NOTIFICATION-TYPE 
    OBJECTS {
              alertSource,
              alertEffect,
              alertSeverity,
              alertTimeStamp,
              alertDescription
    }
    STATUS    current
    DESCRIPTION
        "Optic voltage high alarm"
    ::= { f5AlertNotification 262416 }

ddmVccHiWarn  NOTIFICATION-TYPE 
    OBJECTS {
              alertSource,
              alertEffect,
              alertSeverity,
              alertTimeStamp,
              alertDescription
    }
    STATUS    current
    DESCRIPTION
        "Optic voltage high warning"
    ::= { f5AlertNotification 262417 }

ddmVccLoAlarm  NOTIFICATION-TYPE 
    OBJECTS {
              alertSource,
              alertEffect,
              alertSeverity,
              alertTimeStamp,
              alertDescription
    }
    STATUS    current
    DESCRIPTION
        "Optic voltage low alarm"
    ::= { f5AlertNotification 262418 }

ddmVccLoWarn  NOTIFICATION-TYPE 
    OBJECTS {
              alertSource,
              alertEffect,
              alertSeverity,
              alertTimeStamp,
              alertDescription
    }
    STATUS    current
    DESCRIPTION
        "Optic voltage low warning"
    ::= { f5AlertNotification 262419 }

initialization  NOTIFICATION-TYPE 
    OBJECTS {
              alertSource,
              alertEffect,
              alertSeverity,
              alertTimeStamp,
              alertDescription
    }
    STATUS    current
    DESCRIPTION
        "Critical issue in fpga and datapath initialization process"
    ::= { f5AlertNotification 262656 }

ePVA  NOTIFICATION-TYPE 
    OBJECTS {
              alertSource,
              alertEffect,
              alertSeverity,
              alertTimeStamp,
              alertDescription
    }
    STATUS    current
    DESCRIPTION
        "Could not initialize ePVA"
    ::= { f5AlertNotification 262912 }

be2Training  NOTIFICATION-TYPE 
    OBJECTS {
              alertSource,
              alertEffect,
              alertSeverity,
              alertTimeStamp,
              alertDescription
    }
    STATUS    current
    DESCRIPTION
        "Critical Bandwidth Engine link training failure"
    ::= { f5AlertNotification 262913 }

up  NOTIFICATION-TYPE 
    OBJECTS {
              alertSource,
              alertEffect,
              alertSeverity,
              alertTimeStamp,
              alertDescription
    }
    STATUS    current
    DESCRIPTION
        "Interface up"
    ::= { f5AlertNotification 263168 }

down  NOTIFICATION-TYPE 
    OBJECTS {
              alertSource,
              alertEffect,
              alertSeverity,
              alertTimeStamp,
              alertDescription
    }
    STATUS    current
    DESCRIPTION
        "Interface down"
    ::= { f5AlertNotification 263169 }

speed  NOTIFICATION-TYPE 
    OBJECTS {
              alertSource,
              alertEffect,
              alertSeverity,
              alertTimeStamp,
              alertDescription
    }
    STATUS    current
    DESCRIPTION
        "Port speed change event"
    ::= { f5AlertNotification 263170 }

disabled  NOTIFICATION-TYPE 
    OBJECTS {
              alertSource,
              alertEffect,
              alertSeverity,
              alertTimeStamp,
              alertDescription
    }
    STATUS    current
    DESCRIPTION
        "Interface disabled"
    ::= { f5AlertNotification 263171 }

inaccessibleMemory  NOTIFICATION-TYPE 
    OBJECTS {
              alertSource,
              alertEffect,
              alertSeverity,
              alertTimeStamp,
              alertDescription
    }
    STATUS    current
    DESCRIPTION
        "Notification indicating unusable hugepage memory"
    ::= { f5AlertNotification 458752 }

self-signed-key-decryption-failure  NOTIFICATION-TYPE 
    OBJECTS {
              alertSource,
              alertEffect,
              alertSeverity,
              alertTimeStamp,
              alertDescription
    }
    STATUS    current
    DESCRIPTION
        "The self-signed-key failed to be decrypted when the platform key is corrupted. This will cause the tenants to be inoperable."
    ::= { f5AlertNotification 721153 }

f5AlertsNotifyGroup  NOTIFICATION-GROUP 
    NOTIFICATIONS { 
        hardware-device-fault,
        firmware-fault,
        unknown-alarm,
        drive-fault,
        aom-fault,
        drive-capacity-fault,
        power-fault,
        thermal-fault,
        firmware-update-status,
        drive-utilization,
        datapath-fault,
        dimm-fault,
        module-present,
        psu-fault,
        lcd-fault,
        module-communication-error,
        fips-fault,
        kmip-server-fault,
        kmip-managed-object-error,
        drive-sed-error,
        uefi-communication-error,
        fipsError,
        core-dump,
        reboot,
        incompatible-image,
        login-failed,
        raidEvent,
        txPwrHiAlarm,
        txPwrHiWarn,
        txPwrLoAlarm,
        txPwrLoWarn,
        rxPwrHiAlarm,
        rxPwrHiWarn,
        rxPwrLoAlarm,
        rxPwrLoWarn,
        txBiasHiAlarm,
        txBiasHiWarn,
        txBiasLoAlarm,
        txBiasLoWarn,
        ddmTempHiAlarm,
        ddmTempHiWarn,
        ddmTempLoAlarm,
        ddmTempLoWarn,
        ddmVccHiAlarm,
        ddmVccHiWarn,
        ddmVccLoAlarm,
        ddmVccLoWarn,
        initialization,
        ePVA,
        be2Training,
        up,
        down,
        speed,
        disabled,
        inaccessibleMemory,
        self-signed-key-decryption-failure
    } 
    STATUS    current 
    DESCRIPTION
       "The notifications related to the operation of the F5 System."
    ::= { f5AlertNotificationGroup 1 }

END
