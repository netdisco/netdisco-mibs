LANCOM-L310-MIB DEFINITIONS ::= BEGIN

IMPORTS
    sysDescr, sysName
        FROM RFC1213-MIB
    DisplayString
        FROM SNMPv2-TC
    MacAddress
        FROM SNMPv2-TC
    CounterBasedGauge64
        FROM HCNUM-TC
    enterprises, OBJECT-TYPE,
    MODULE-IDENTITY, IpAddress, Counter32, Gauge32, TimeTicks, Counter64, NOTIFICATION-TYPE
        FROM SNMPv2-SMI;

lancom-l310 MODULE-IDENTITY
    LAST-UPDATED "201710201330Z"
    ORGANIZATION "LANCOM Systems GmbH"
    CONTACT-INFO "www.lancom.de"
    DESCRIPTION "Management information base definitions"
    REVISION "201710201330Z"
    DESCRIPTION "Auto-Generated on Dec 31, 2019"
    ::= { enterprises lancom-systems(2356) wlan-systems(600) lan-router(6)  310 }


-- {OID} 310.1
lcsStatus OBJECT IDENTIFIER ::= { lancom-l310 1 }

-- {SCALAR} 310.1.2
lcsStatusOperatingTime OBJECT-TYPE
    SYNTAX     DisplayString
    MAX-ACCESS read-only
    STATUS     current
    DESCRIPTION
        "-- empty --"
    ::= { lcsStatus 2 }

-- {OID} 310.1.3
lcsStatusWlan OBJECT IDENTIFIER ::= { lcsStatus 3 }

-- {TABLE} 310.1.3.51
lcsStatusWlanIfcsTable OBJECT-TYPE
    SYNTAX     SEQUENCE OF LcsStatusWlanIfcsEntry
    MAX-ACCESS not-accessible
    STATUS     current
    DESCRIPTION
        ""
    ::= { lcsStatusWlan 51 }

-- {ENTRY} 310.1.3.51.1
lcsStatusWlanIfcsEntry OBJECT-TYPE
    SYNTAX     LcsStatusWlanIfcsEntry
    MAX-ACCESS not-accessible
    STATUS     current
    DESCRIPTION
        ""
    INDEX {
        lcsStatusWlanIfcsEntryIfc
    }
    ::= { lcsStatusWlanIfcsTable 1 }

-- {SEQUENCE}
LcsStatusWlanIfcsEntry ::= SEQUENCE {
    lcsStatusWlanIfcsEntryIfc DisplayString,
    lcsStatusWlanIfcsEntryOperating INTEGER,
    lcsStatusWlanIfcsEntryOperationMode INTEGER,
    lcsStatusWlanIfcsEntryCardId DisplayString,
    lcsStatusWlanIfcsEntrySerialNumber DisplayString,
    lcsStatusWlanIfcsEntryFirmwareVersion DisplayString,
    lcsStatusWlanIfcsEntryMacAddress MacAddress,
    lcsStatusWlanIfcsEntryNumStations INTEGER,
    lcsStatusWlanIfcsEntryQueuePackets INTEGER
}

-- {COLUMN} 310.1.3.51.1.1
lcsStatusWlanIfcsEntryIfc OBJECT-TYPE
    SYNTAX     DisplayString (SIZE(0..255))
    MAX-ACCESS read-only
    STATUS     current
    DESCRIPTION
        "-- empty --"
    ::= { lcsStatusWlanIfcsEntry 1 }

-- {COLUMN} 310.1.3.51.1.3
lcsStatusWlanIfcsEntryOperating OBJECT-TYPE
    SYNTAX     INTEGER
      {
        eNo (0),
        eYes (1)
      }
    MAX-ACCESS read-only
    STATUS     current
    DESCRIPTION
        "-- empty --"
    ::= { lcsStatusWlanIfcsEntry 3 }

-- {COLUMN} 310.1.3.51.1.9
lcsStatusWlanIfcsEntryOperationMode OBJECT-TYPE
    SYNTAX     INTEGER
      {
        eAccessPoint (1),
        eManagedAp (4),
        eStation (0),
        eMonitor (2)
      }
    MAX-ACCESS read-only
    STATUS     current
    DESCRIPTION
        "lancom's description of operation mode"
    ::= { lcsStatusWlanIfcsEntry 9 }

-- {COLUMN} 310.1.3.51.1.5
lcsStatusWlanIfcsEntryCardId OBJECT-TYPE
    SYNTAX     DisplayString (SIZE(0..255))
    MAX-ACCESS read-only
    STATUS     current
    DESCRIPTION
        "-- empty --"
    ::= { lcsStatusWlanIfcsEntry 5 }

-- {COLUMN} 310.1.3.51.1.7
lcsStatusWlanIfcsEntrySerialNumber OBJECT-TYPE
    SYNTAX     DisplayString (SIZE(0..255))
    MAX-ACCESS read-only
    STATUS     current
    DESCRIPTION
        "-- empty --"
    ::= { lcsStatusWlanIfcsEntry 7 }

-- {COLUMN} 310.1.3.51.1.6
lcsStatusWlanIfcsEntryFirmwareVersion OBJECT-TYPE
    SYNTAX     DisplayString (SIZE(0..255))
    MAX-ACCESS read-only
    STATUS     current
    DESCRIPTION
        "-- empty --"
    ::= { lcsStatusWlanIfcsEntry 6 }

-- {COLUMN} 310.1.3.51.1.2
lcsStatusWlanIfcsEntryMacAddress OBJECT-TYPE
    SYNTAX     MacAddress
    MAX-ACCESS read-only
    STATUS     current
    DESCRIPTION
        "-- empty --"
    ::= { lcsStatusWlanIfcsEntry 2 }

-- {COLUMN} 310.1.3.51.1.8
lcsStatusWlanIfcsEntryNumStations OBJECT-TYPE
    SYNTAX     INTEGER (0..65535)
    MAX-ACCESS read-only
    STATUS     current
    DESCRIPTION
        "-- empty --"
    ::= { lcsStatusWlanIfcsEntry 8 }

-- {COLUMN} 310.1.3.51.1.4
lcsStatusWlanIfcsEntryQueuePackets OBJECT-TYPE
    SYNTAX     INTEGER (0..2147483647)
    MAX-ACCESS read-only
    STATUS     current
    DESCRIPTION
        "-- empty --"
    ::= { lcsStatusWlanIfcsEntry 4 }

-- {TABLE} 310.1.3.56
lcsStatusWlanNetworksTable OBJECT-TYPE
    SYNTAX     SEQUENCE OF LcsStatusWlanNetworksEntry
    MAX-ACCESS not-accessible
    STATUS     current
    DESCRIPTION
        "-- empty --"
    ::= { lcsStatusWlan 56 }

-- {ENTRY} 310.1.3.56.1
lcsStatusWlanNetworksEntry OBJECT-TYPE
    SYNTAX     LcsStatusWlanNetworksEntry
    MAX-ACCESS not-accessible
    STATUS     current
    DESCRIPTION
        ""
    INDEX {
        lcsStatusWlanNetworksEntryIfc
    }
    ::= { lcsStatusWlanNetworksTable 1 }

-- {SEQUENCE}
LcsStatusWlanNetworksEntry ::= SEQUENCE {
    lcsStatusWlanNetworksEntryIfc DisplayString,
    lcsStatusWlanNetworksEntryOperating INTEGER,
    lcsStatusWlanNetworksEntryNetworkName DisplayString,
    lcsStatusWlanNetworksEntryBssid MacAddress,
    lcsStatusWlanNetworksEntryRadioMode INTEGER,
    lcsStatusWlanNetworksEntryVlanId INTEGER,
    lcsStatusWlanNetworksEntryNumStations INTEGER,
    lcsStatusWlanNetworksEntryMcastPwrSave INTEGER,
    lcsStatusWlanNetworksEntryApsd INTEGER,
    lcsStatusWlanNetworksEntryAlarmState INTEGER,
    lcsStatusWlanNetworksEntryBasicRate INTEGER,
    lcsStatusWlanNetworksEntryMacFilter INTEGER,
    lcsStatusWlanNetworksEntryAccessMode INTEGER
}

-- {COLUMN} 310.1.3.56.1.1
lcsStatusWlanNetworksEntryIfc OBJECT-TYPE
    SYNTAX     DisplayString (SIZE(0..255))
    MAX-ACCESS read-only
    STATUS     current
    DESCRIPTION
        "-- empty --"
    ::= { lcsStatusWlanNetworksEntry 1 }

-- {COLUMN} 310.1.3.56.1.2
lcsStatusWlanNetworksEntryOperating OBJECT-TYPE
    SYNTAX     INTEGER
      {
        eNo (0),
        eYes (1)
      }
    MAX-ACCESS read-only
    STATUS     current
    DESCRIPTION
        "-- empty --"
    ::= { lcsStatusWlanNetworksEntry 2 }

-- {COLUMN} 310.1.3.56.1.3
lcsStatusWlanNetworksEntryNetworkName OBJECT-TYPE
    SYNTAX     DisplayString (SIZE(0..255))
    MAX-ACCESS read-only
    STATUS     current
    DESCRIPTION
        "-- empty --"
    ::= { lcsStatusWlanNetworksEntry 3 }

-- {COLUMN} 310.1.3.56.1.6
lcsStatusWlanNetworksEntryBssid OBJECT-TYPE
    SYNTAX     MacAddress
    MAX-ACCESS read-only
    STATUS     current
    DESCRIPTION
        "-- empty --"
    ::= { lcsStatusWlanNetworksEntry 6 }

-- {COLUMN} 310.1.3.56.1.9
lcsStatusWlanNetworksEntryRadioMode OBJECT-TYPE
    SYNTAX     INTEGER
      {
        e11bgMixed (0),
        e11gOnly (1),
        e11bOnly (2),
        e2mMixed (3),
        eTurboG (4),
        e11bgnMixed (5),
        e2m11bgnMixed (6),
        e11gnMixed (7),
        eGreenfieldGn (8),
        e11a (256),
        eTurboA (257),
        e11anMixed (259),
        eGreenfieldAn (260),
        eHalf11a (261),
        eQuarter11a (262),
        eNone (65535)
      }
    MAX-ACCESS read-only
    STATUS     current
    DESCRIPTION
        "-- empty --"
    ::= { lcsStatusWlanNetworksEntry 9 }

-- {COLUMN} 310.1.3.56.1.7
lcsStatusWlanNetworksEntryVlanId OBJECT-TYPE
    SYNTAX     INTEGER (0..65535)
    MAX-ACCESS read-only
    STATUS     current
    DESCRIPTION
        "-- empty --"
    ::= { lcsStatusWlanNetworksEntry 7 }

-- {COLUMN} 310.1.3.56.1.4
lcsStatusWlanNetworksEntryNumStations OBJECT-TYPE
    SYNTAX     INTEGER (0..65535)
    MAX-ACCESS read-only
    STATUS     current
    DESCRIPTION
        "-- empty --"
    ::= { lcsStatusWlanNetworksEntry 4 }

-- {COLUMN} 310.1.3.56.1.5
lcsStatusWlanNetworksEntryMcastPwrSave OBJECT-TYPE
    SYNTAX     INTEGER
      {
        eNo (0),
        eYes (1)
      }
    MAX-ACCESS read-only
    STATUS     current
    DESCRIPTION
        "-- empty --"
    ::= { lcsStatusWlanNetworksEntry 5 }

-- {COLUMN} 310.1.3.56.1.8
lcsStatusWlanNetworksEntryApsd OBJECT-TYPE
    SYNTAX     INTEGER
      {
        eNo (0),
        eYes (1)
      }
    MAX-ACCESS read-only
    STATUS     current
    DESCRIPTION
        "-- empty --"
    ::= { lcsStatusWlanNetworksEntry 8 }

-- {COLUMN} 310.1.3.56.1.10
lcsStatusWlanNetworksEntryAlarmState OBJECT-TYPE
    SYNTAX     INTEGER
      {
        ePhySignal (1),
        eTotalRetries (2),
        eTxErrors (4),
        eNo (0)
      }
    MAX-ACCESS read-only
    STATUS     current
    DESCRIPTION
        "-- empty --"
    ::= { lcsStatusWlanNetworksEntry 10 }

-- {COLUMN} 310.1.3.56.1.11
lcsStatusWlanNetworksEntryBasicRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanNetworksEntry 11 }

-- {COLUMN} 310.1.3.56.1.12
lcsStatusWlanNetworksEntryMacFilter OBJECT-TYPE
    SYNTAX     INTEGER
      {
        eYes (0),
        eNo (1),
        eLocalOnly (2),
        eRadiusOnly (3)
      }
    MAX-ACCESS read-only
    STATUS     current
    DESCRIPTION
        "-- empty --"
    ::= { lcsStatusWlanNetworksEntry 12 }

-- {COLUMN} 310.1.3.56.1.13
lcsStatusWlanNetworksEntryAccessMode OBJECT-TYPE
    SYNTAX     INTEGER
      {
        eNegative (0),
        ePositive (1)
      }
    MAX-ACCESS read-only
    STATUS     current
    DESCRIPTION
        "-- empty --"
    ::= { lcsStatusWlanNetworksEntry 13 }

-- {TABLE} 310.1.3.52
lcsStatusWlanByteTransportTable OBJECT-TYPE
    SYNTAX     SEQUENCE OF LcsStatusWlanByteTransportEntry
    MAX-ACCESS not-accessible
    STATUS     current
    DESCRIPTION
        "-- empty --"
    ::= { lcsStatusWlan 52 }

-- {ENTRY} 310.1.3.52.1
lcsStatusWlanByteTransportEntry OBJECT-TYPE
    SYNTAX     LcsStatusWlanByteTransportEntry
    MAX-ACCESS not-accessible
    STATUS     current
    DESCRIPTION
        ""
    INDEX {
        lcsStatusWlanByteTransportEntryIfc
    }
    ::= { lcsStatusWlanByteTransportTable 1 }

-- {SEQUENCE}
LcsStatusWlanByteTransportEntry ::= SEQUENCE {
    lcsStatusWlanByteTransportEntryIfc DisplayString,
    lcsStatusWlanByteTransportEntryTxBytes Counter64,
    lcsStatusWlanByteTransportEntryRxBytes Counter64,
    lcsStatusWlanByteTransportEntryThroughput DisplayString,
    lcsStatusWlanByteTransportEntryMaxThroughput DisplayString,
    lcsStatusWlanByteTransportEntryBytesThroughput INTEGER,
    lcsStatusWlanByteTransportEntryBytesMaxThroughput INTEGER
}

-- {COLUMN} 310.1.3.52.1.1
lcsStatusWlanByteTransportEntryIfc OBJECT-TYPE
    SYNTAX     DisplayString (SIZE(0..255))
    MAX-ACCESS read-only
    STATUS     current
    DESCRIPTION
        "-- empty --"
    ::= { lcsStatusWlanByteTransportEntry 1 }

-- {COLUMN} 310.1.3.52.1.2
lcsStatusWlanByteTransportEntryTxBytes OBJECT-TYPE
    SYNTAX     Counter64
    MAX-ACCESS read-only
    STATUS     current
    DESCRIPTION
        "-- empty --"
    ::= { lcsStatusWlanByteTransportEntry 2 }

-- {COLUMN} 310.1.3.52.1.3
lcsStatusWlanByteTransportEntryRxBytes OBJECT-TYPE
    SYNTAX     Counter64
    MAX-ACCESS read-only
    STATUS     current
    DESCRIPTION
        "-- empty --"
    ::= { lcsStatusWlanByteTransportEntry 3 }

-- {COLUMN} 310.1.3.52.1.4
lcsStatusWlanByteTransportEntryThroughput OBJECT-TYPE
    SYNTAX     DisplayString (SIZE(0..255))
    MAX-ACCESS read-only
    STATUS     current
    DESCRIPTION
        "-- empty --"
    ::= { lcsStatusWlanByteTransportEntry 4 }

-- {COLUMN} 310.1.3.52.1.5
lcsStatusWlanByteTransportEntryMaxThroughput OBJECT-TYPE
    SYNTAX     DisplayString (SIZE(0..255))
    MAX-ACCESS read-only
    STATUS     current
    DESCRIPTION
        "-- empty --"
    ::= { lcsStatusWlanByteTransportEntry 5 }

-- {COLUMN} 310.1.3.52.1.6
lcsStatusWlanByteTransportEntryBytesThroughput OBJECT-TYPE
    SYNTAX     INTEGER (0..2147483647)
    MAX-ACCESS read-only
    STATUS     current
    DESCRIPTION
        "-- empty --"
    ::= { lcsStatusWlanByteTransportEntry 6 }

-- {COLUMN} 310.1.3.52.1.7
lcsStatusWlanByteTransportEntryBytesMaxThroughput OBJECT-TYPE
    SYNTAX     INTEGER (0..2147483647)
    MAX-ACCESS read-only
    STATUS     current
    DESCRIPTION
        "-- empty --"
    ::= { lcsStatusWlanByteTransportEntry 7 }

-- {TABLE} 310.1.3.53
lcsStatusWlanPacketTransportTable OBJECT-TYPE
    SYNTAX     SEQUENCE OF LcsStatusWlanPacketTransportEntry
    MAX-ACCESS not-accessible
    STATUS     current
    DESCRIPTION
        "-- empty --"
    ::= { lcsStatusWlan 53 }

-- {ENTRY} 310.1.3.53.1
lcsStatusWlanPacketTransportEntry OBJECT-TYPE
    SYNTAX     LcsStatusWlanPacketTransportEntry
    MAX-ACCESS not-accessible
    STATUS     current
    DESCRIPTION
        ""
    INDEX {
        lcsStatusWlanPacketTransportEntryIfc
    }
    ::= { lcsStatusWlanPacketTransportTable 1 }

-- {SEQUENCE}
LcsStatusWlanPacketTransportEntry ::= SEQUENCE {
    lcsStatusWlanPacketTransportEntryIfc DisplayString,
    lcsStatusWlanPacketTransportEntryRxPackets Counter32,
    lcsStatusWlanPacketTransportEntryTxPackets Counter32,
    lcsStatusWlanPacketTransportEntryRxBroadcasts Counter32,
    lcsStatusWlanPacketTransportEntryRxMulticasts Counter32,
    lcsStatusWlanPacketTransportEntryRxUnicasts Counter32,
    lcsStatusWlanPacketTransportEntryRxAggregates Counter32,
    lcsStatusWlanPacketTransportEntryRxAggrFrames Counter32,
    lcsStatusWlanPacketTransportEntryRxAMsdu Counter32,
    lcsStatusWlanPacketTransportEntryTxBroadcasts Counter32,
    lcsStatusWlanPacketTransportEntryTxMulticasts Counter32,
    lcsStatusWlanPacketTransportEntryTxUnicasts Counter32,
    lcsStatusWlanPacketTransportEntryTxAggregates Counter32,
    lcsStatusWlanPacketTransportEntryTxAggrFrames Counter32
}

-- {COLUMN} 310.1.3.53.1.1
lcsStatusWlanPacketTransportEntryIfc OBJECT-TYPE
    SYNTAX     DisplayString (SIZE(0..255))
    MAX-ACCESS read-only
    STATUS     current
    DESCRIPTION
        "-- empty --"
    ::= { lcsStatusWlanPacketTransportEntry 1 }

-- {COLUMN} 310.1.3.53.1.2
lcsStatusWlanPacketTransportEntryRxPackets OBJECT-TYPE
    SYNTAX     Counter32
    MAX-ACCESS read-only
    STATUS     current
    DESCRIPTION
        "-- empty --"
    ::= { lcsStatusWlanPacketTransportEntry 2 }

-- {COLUMN} 310.1.3.53.1.3
lcsStatusWlanPacketTransportEntryTxPackets OBJECT-TYPE
    SYNTAX     Counter32
    MAX-ACCESS read-only
    STATUS     current
    DESCRIPTION
        "-- empty --"
    ::= { lcsStatusWlanPacketTransportEntry 3 }

-- {COLUMN} 310.1.3.53.1.4
lcsStatusWlanPacketTransportEntryRxBroadcasts OBJECT-TYPE
    SYNTAX     Counter32
    MAX-ACCESS read-only
    STATUS     current
    DESCRIPTION
        "-- empty --"
    ::= { lcsStatusWlanPacketTransportEntry 4 }

-- {COLUMN} 310.1.3.53.1.5
lcsStatusWlanPacketTransportEntryRxMulticasts OBJECT-TYPE
    SYNTAX     Counter32
    MAX-ACCESS read-only
    STATUS     current
    DESCRIPTION
        "-- empty --"
    ::= { lcsStatusWlanPacketTransportEntry 5 }

-- {COLUMN} 310.1.3.53.1.6
lcsStatusWlanPacketTransportEntryRxUnicasts OBJECT-TYPE
    SYNTAX     Counter32
    MAX-ACCESS read-only
    STATUS     current
    DESCRIPTION
        "-- empty --"
    ::= { lcsStatusWlanPacketTransportEntry 6 }

-- {COLUMN} 310.1.3.53.1.14
lcsStatusWlanPacketTransportEntryRxAggregates OBJECT-TYPE
    SYNTAX     Counter32
    MAX-ACCESS read-only
    STATUS     current
    DESCRIPTION
        "-- empty --"
    ::= { lcsStatusWlanPacketTransportEntry 14 }

-- {COLUMN} 310.1.3.53.1.15
lcsStatusWlanPacketTransportEntryRxAggrFrames OBJECT-TYPE
    SYNTAX     Counter32
    MAX-ACCESS read-only
    STATUS     current
    DESCRIPTION
        "-- empty --"
    ::= { lcsStatusWlanPacketTransportEntry 15 }

-- {COLUMN} 310.1.3.53.1.16
lcsStatusWlanPacketTransportEntryRxAMsdu OBJECT-TYPE
    SYNTAX     Counter32
    MAX-ACCESS read-only
    STATUS     current
    DESCRIPTION
        "-- empty --"
    ::= { lcsStatusWlanPacketTransportEntry 16 }

-- {COLUMN} 310.1.3.53.1.7
lcsStatusWlanPacketTransportEntryTxBroadcasts OBJECT-TYPE
    SYNTAX     Counter32
    MAX-ACCESS read-only
    STATUS     current
    DESCRIPTION
        "-- empty --"
    ::= { lcsStatusWlanPacketTransportEntry 7 }

-- {COLUMN} 310.1.3.53.1.8
lcsStatusWlanPacketTransportEntryTxMulticasts OBJECT-TYPE
    SYNTAX     Counter32
    MAX-ACCESS read-only
    STATUS     current
    DESCRIPTION
        "-- empty --"
    ::= { lcsStatusWlanPacketTransportEntry 8 }

-- {COLUMN} 310.1.3.53.1.9
lcsStatusWlanPacketTransportEntryTxUnicasts OBJECT-TYPE
    SYNTAX     Counter32
    MAX-ACCESS read-only
    STATUS     current
    DESCRIPTION
        "-- empty --"
    ::= { lcsStatusWlanPacketTransportEntry 9 }

-- {COLUMN} 310.1.3.53.1.12
lcsStatusWlanPacketTransportEntryTxAggregates OBJECT-TYPE
    SYNTAX     Counter32
    MAX-ACCESS read-only
    STATUS     current
    DESCRIPTION
        "-- empty --"
    ::= { lcsStatusWlanPacketTransportEntry 12 }

-- {COLUMN} 310.1.3.53.1.13
lcsStatusWlanPacketTransportEntryTxAggrFrames OBJECT-TYPE
    SYNTAX     Counter32
    MAX-ACCESS read-only
    STATUS     current
    DESCRIPTION
        "-- empty --"
    ::= { lcsStatusWlanPacketTransportEntry 13 }

-- {TABLE} 310.1.3.54
lcsStatusWlanErrorsTable OBJECT-TYPE
    SYNTAX     SEQUENCE OF LcsStatusWlanErrorsEntry
    MAX-ACCESS not-accessible
    STATUS     current
    DESCRIPTION
        "-- empty --"
    ::= { lcsStatusWlan 54 }

-- {ENTRY} 310.1.3.54.1
lcsStatusWlanErrorsEntry OBJECT-TYPE
    SYNTAX     LcsStatusWlanErrorsEntry
    MAX-ACCESS not-accessible
    STATUS     current
    DESCRIPTION
        ""
    INDEX {
        lcsStatusWlanErrorsEntryIfc
    }
    ::= { lcsStatusWlanErrorsTable 1 }

-- {SEQUENCE}
LcsStatusWlanErrorsEntry ::= SEQUENCE {
    lcsStatusWlanErrorsEntryIfc DisplayString,
    lcsStatusWlanErrorsEntryRxErrors Counter32,
    lcsStatusWlanErrorsEntryTxErrors Counter32,
    lcsStatusWlanErrorsEntryStackErrors Counter32,
    lcsStatusWlanErrorsEntryNicErrors Counter32,
    lcsStatusWlanErrorsEntryBusErrors Counter32,
    lcsStatusWlanErrorsEntryQueueErrors Counter32,
    lcsStatusWlanErrorsEntryTxDiscarded Counter32,
    lcsStatusWlanErrorsEntryRetries Counter32,
    lcsStatusWlanErrorsEntryMultipleRetries Counter32,
    lcsStatusWlanErrorsEntrySoftRetries Counter32,
    lcsStatusWlanErrorsEntryDupeDiscarded Counter32,
    lcsStatusWlanErrorsEntryUndecryptables Counter32,
    lcsStatusWlanErrorsEntryAged Counter32,
    lcsStatusWlanErrorsEntryMichaelErrors Counter32,
    lcsStatusWlanErrorsEntryIvSequenceErrors Counter32,
    lcsStatusWlanErrorsEntryRxCrcErrors Counter32,
    lcsStatusWlanErrorsEntryRxAggrDiscarded Counter32,
    lcsStatusWlanErrorsEntryRxPhyErrors Counter32,
    lcsStatusWlanErrorsEntryRxRestarts Counter32,
    lcsStatusWlanErrorsEntryRxDscrUnderflow Counter32,
    lcsStatusWlanErrorsEntryRxFifoOverflow Counter32,
    lcsStatusWlanErrorsEntryTxFifoUnderflow Counter32,
    lcsStatusWlanErrorsEntryAgcCalibrateFailures Counter32
}

-- {COLUMN} 310.1.3.54.1.1
lcsStatusWlanErrorsEntryIfc OBJECT-TYPE
    SYNTAX     DisplayString (SIZE(0..255))
    MAX-ACCESS read-only
    STATUS     current
    DESCRIPTION
        "-- empty --"
    ::= { lcsStatusWlanErrorsEntry 1 }

-- {COLUMN} 310.1.3.54.1.2
lcsStatusWlanErrorsEntryRxErrors OBJECT-TYPE
    SYNTAX     Counter32
    MAX-ACCESS read-only
    STATUS     current
    DESCRIPTION
        "-- empty --"
    ::= { lcsStatusWlanErrorsEntry 2 }

-- {COLUMN} 310.1.3.54.1.3
lcsStatusWlanErrorsEntryTxErrors OBJECT-TYPE
    SYNTAX     Counter32
    MAX-ACCESS read-only
    STATUS     current
    DESCRIPTION
        "-- empty --"
    ::= { lcsStatusWlanErrorsEntry 3 }

-- {COLUMN} 310.1.3.54.1.4
lcsStatusWlanErrorsEntryStackErrors OBJECT-TYPE
    SYNTAX     Counter32
    MAX-ACCESS read-only
    STATUS     current
    DESCRIPTION
        "-- empty --"
    ::= { lcsStatusWlanErrorsEntry 4 }

-- {COLUMN} 310.1.3.54.1.5
lcsStatusWlanErrorsEntryNicErrors OBJECT-TYPE
    SYNTAX     Counter32
    MAX-ACCESS read-only
    STATUS     current
    DESCRIPTION
        "-- empty --"
    ::= { lcsStatusWlanErrorsEntry 5 }

-- {COLUMN} 310.1.3.54.1.22
lcsStatusWlanErrorsEntryBusErrors OBJECT-TYPE
    SYNTAX     Counter32
    MAX-ACCESS read-only
    STATUS     current
    DESCRIPTION
        "-- empty --"
    ::= { lcsStatusWlanErrorsEntry 22 }

-- {COLUMN} 310.1.3.54.1.6
lcsStatusWlanErrorsEntryQueueErrors OBJECT-TYPE
    SYNTAX     Counter32
    MAX-ACCESS read-only
    STATUS     current
    DESCRIPTION
        "-- empty --"
    ::= { lcsStatusWlanErrorsEntry 6 }

-- {COLUMN} 310.1.3.54.1.7
lcsStatusWlanErrorsEntryTxDiscarded OBJECT-TYPE
    SYNTAX     Counter32
    MAX-ACCESS read-only
    STATUS     current
    DESCRIPTION
        "-- empty --"
    ::= { lcsStatusWlanErrorsEntry 7 }

-- {COLUMN} 310.1.3.54.1.8
lcsStatusWlanErrorsEntryRetries OBJECT-TYPE
    SYNTAX     Counter32
    MAX-ACCESS read-only
    STATUS     current
    DESCRIPTION
        "-- empty --"
    ::= { lcsStatusWlanErrorsEntry 8 }

-- {COLUMN} 310.1.3.54.1.9
lcsStatusWlanErrorsEntryMultipleRetries OBJECT-TYPE
    SYNTAX     Counter32
    MAX-ACCESS read-only
    STATUS     current
    DESCRIPTION
        "-- empty --"
    ::= { lcsStatusWlanErrorsEntry 9 }

-- {COLUMN} 310.1.3.54.1.17
lcsStatusWlanErrorsEntrySoftRetries OBJECT-TYPE
    SYNTAX     Counter32
    MAX-ACCESS read-only
    STATUS     current
    DESCRIPTION
        "-- empty --"
    ::= { lcsStatusWlanErrorsEntry 17 }

-- {COLUMN} 310.1.3.54.1.11
lcsStatusWlanErrorsEntryDupeDiscarded OBJECT-TYPE
    SYNTAX     Counter32
    MAX-ACCESS read-only
    STATUS     current
    DESCRIPTION
        "-- empty --"
    ::= { lcsStatusWlanErrorsEntry 11 }

-- {COLUMN} 310.1.3.54.1.10
lcsStatusWlanErrorsEntryUndecryptables OBJECT-TYPE
    SYNTAX     Counter32
    MAX-ACCESS read-only
    STATUS     current
    DESCRIPTION
        "-- empty --"
    ::= { lcsStatusWlanErrorsEntry 10 }

-- {COLUMN} 310.1.3.54.1.13
lcsStatusWlanErrorsEntryAged OBJECT-TYPE
    SYNTAX     Counter32
    MAX-ACCESS read-only
    STATUS     current
    DESCRIPTION
        "-- empty --"
    ::= { lcsStatusWlanErrorsEntry 13 }

-- {COLUMN} 310.1.3.54.1.14
lcsStatusWlanErrorsEntryMichaelErrors OBJECT-TYPE
    SYNTAX     Counter32
    MAX-ACCESS read-only
    STATUS     current
    DESCRIPTION
        "-- empty --"
    ::= { lcsStatusWlanErrorsEntry 14 }

-- {COLUMN} 310.1.3.54.1.15
lcsStatusWlanErrorsEntryIvSequenceErrors OBJECT-TYPE
    SYNTAX     Counter32
    MAX-ACCESS read-only
    STATUS     current
    DESCRIPTION
        "-- empty --"
    ::= { lcsStatusWlanErrorsEntry 15 }

-- {COLUMN} 310.1.3.54.1.16
lcsStatusWlanErrorsEntryRxCrcErrors OBJECT-TYPE
    SYNTAX     Counter32
    MAX-ACCESS read-only
    STATUS     current
    DESCRIPTION
        "-- empty --"
    ::= { lcsStatusWlanErrorsEntry 16 }

-- {COLUMN} 310.1.3.54.1.18
lcsStatusWlanErrorsEntryRxAggrDiscarded OBJECT-TYPE
    SYNTAX     Counter32
    MAX-ACCESS read-only
    STATUS     current
    DESCRIPTION
        "-- empty --"
    ::= { lcsStatusWlanErrorsEntry 18 }

-- {COLUMN} 310.1.3.54.1.19
lcsStatusWlanErrorsEntryRxPhyErrors OBJECT-TYPE
    SYNTAX     Counter32
    MAX-ACCESS read-only
    STATUS     current
    DESCRIPTION
        "-- empty --"
    ::= { lcsStatusWlanErrorsEntry 19 }

-- {COLUMN} 310.1.3.54.1.23
lcsStatusWlanErrorsEntryRxRestarts OBJECT-TYPE
    SYNTAX     Counter32
    MAX-ACCESS read-only
    STATUS     current
    DESCRIPTION
        "-- empty --"
    ::= { lcsStatusWlanErrorsEntry 23 }

-- {COLUMN} 310.1.3.54.1.24
lcsStatusWlanErrorsEntryRxDscrUnderflow OBJECT-TYPE
    SYNTAX     Counter32
    MAX-ACCESS read-only
    STATUS     current
    DESCRIPTION
        "-- empty --"
    ::= { lcsStatusWlanErrorsEntry 24 }

-- {COLUMN} 310.1.3.54.1.20
lcsStatusWlanErrorsEntryRxFifoOverflow OBJECT-TYPE
    SYNTAX     Counter32
    MAX-ACCESS read-only
    STATUS     current
    DESCRIPTION
        "-- empty --"
    ::= { lcsStatusWlanErrorsEntry 20 }

-- {COLUMN} 310.1.3.54.1.21
lcsStatusWlanErrorsEntryTxFifoUnderflow OBJECT-TYPE
    SYNTAX     Counter32
    MAX-ACCESS read-only
    STATUS     current
    DESCRIPTION
        "-- empty --"
    ::= { lcsStatusWlanErrorsEntry 21 }

-- {COLUMN} 310.1.3.54.1.25
lcsStatusWlanErrorsEntryAgcCalibrateFailures OBJECT-TYPE
    SYNTAX     Counter32
    MAX-ACCESS read-only
    STATUS     current
    DESCRIPTION
        "-- empty --"
    ::= { lcsStatusWlanErrorsEntry 25 }

-- {TABLE} 310.1.3.55
lcsStatusWlanWlanParameterTable OBJECT-TYPE
    SYNTAX     SEQUENCE OF LcsStatusWlanWlanParameterEntry
    MAX-ACCESS not-accessible
    STATUS     current
    DESCRIPTION
        "-- empty --"
    ::= { lcsStatusWlan 55 }

-- {ENTRY} 310.1.3.55.1
lcsStatusWlanWlanParameterEntry OBJECT-TYPE
    SYNTAX     LcsStatusWlanWlanParameterEntry
    MAX-ACCESS not-accessible
    STATUS     current
    DESCRIPTION
        ""
    INDEX {
        lcsStatusWlanWlanParameterEntryIfc
    }
    ::= { lcsStatusWlanWlanParameterTable 1 }

-- {SEQUENCE}
LcsStatusWlanWlanParameterEntry ::= SEQUENCE {
    lcsStatusWlanWlanParameterEntryIfc DisplayString,
    lcsStatusWlanWlanParameterEntryRadioBand INTEGER,
    lcsStatusWlanWlanParameterEntryRadioChannel INTEGER,
    lcsStatusWlanWlanParameterEntry108mbpsMode INTEGER,
    lcsStatusWlanWlanParameterEntryNoiseLevel INTEGER,
    lcsStatusWlanWlanParameterEntryModemLoad INTEGER,
    lcsStatusWlanWlanParameterEntryTransmitPower DisplayString,
    lcsStatusWlanWlanParameterEntryEirp DisplayString,
    lcsStatusWlanWlanParameterEntryExcEirp INTEGER,
    lcsStatusWlanWlanParameterEntryBeaconPeriod INTEGER,
    lcsStatusWlanWlanParameterEntryCountry INTEGER,
    lcsStatusWlanWlanParameterEntryRegulatoryDomain INTEGER,
    lcsStatusWlanWlanParameterEntryPhyType INTEGER,
    lcsStatusWlanWlanParameterEntrySupportedAntennas INTEGER,
    lcsStatusWlanWlanParameterEntryTxChains INTEGER,
    lcsStatusWlanWlanParameterEntryRxChains INTEGER,
    lcsStatusWlanWlanParameterEntryWepSupport INTEGER,
    lcsStatusWlanWlanParameterEntryTkipSupport INTEGER,
    lcsStatusWlanWlanParameterEntryAesSupport INTEGER,
    lcsStatusWlanWlanParameterEntryMinimumRate INTEGER,
    lcsStatusWlanWlanParameterEntryMaximumRate INTEGER,
    lcsStatusWlanWlanParameterEntryTemperatureRange INTEGER,
    lcsStatusWlanWlanParameterEntryPhyVariant DisplayString,
    lcsStatusWlanWlanParameterEntrySupportedBands INTEGER,
    lcsStatusWlanWlanParameterEntrySupports40mhz INTEGER,
    lcsStatusWlanWlanParameterEntrySupportsShortPreamble INTEGER,
    lcsStatusWlanWlanParameterEntrySupportsShortSlotTime INTEGER,
    lcsStatusWlanWlanParameterEntrySupportsShortGuardInterval INTEGER,
    lcsStatusWlanWlanParameterEntrySupportsCompression INTEGER,
    lcsStatusWlanWlanParameterEntrySupportedDfsSchemes BITS
}

-- {COLUMN} 310.1.3.55.1.1
lcsStatusWlanWlanParameterEntryIfc OBJECT-TYPE
    SYNTAX     DisplayString (SIZE(0..255))
    MAX-ACCESS read-only
    STATUS     current
    DESCRIPTION
        "-- empty --"
    ::= { lcsStatusWlanWlanParameterEntry 1 }

-- {COLUMN} 310.1.3.55.1.11
lcsStatusWlanWlanParameterEntryRadioBand OBJECT-TYPE
    SYNTAX     INTEGER
      {
        eUnknown (0),
        e24ghz (1),
        e5ghz (2)
      }
    MAX-ACCESS read-only
    STATUS     current
    DESCRIPTION
        "-- empty --"
    ::= { lcsStatusWlanWlanParameterEntry 11 }

-- {COLUMN} 310.1.3.55.1.3
lcsStatusWlanWlanParameterEntryRadioChannel OBJECT-TYPE
    SYNTAX     INTEGER (0..255)
    MAX-ACCESS read-only
    STATUS     current
    DESCRIPTION
        "-- empty --"
    ::= { lcsStatusWlanWlanParameterEntry 3 }

-- {COLUMN} 310.1.3.55.1.16
lcsStatusWlanWlanParameterEntry108mbpsMode OBJECT-TYPE
    SYNTAX     INTEGER
      {
        eNo (0),
        eYes (1)
      }
    MAX-ACCESS read-only
    STATUS     current
    DESCRIPTION
        "-- empty --"
    ::= { lcsStatusWlanWlanParameterEntry 16 }

-- {COLUMN} 310.1.3.55.1.13
lcsStatusWlanWlanParameterEntryNoiseLevel OBJECT-TYPE
    SYNTAX     INTEGER (-32768..32767)
    MAX-ACCESS read-only
    STATUS     current
    DESCRIPTION
        "-- empty --"
    ::= { lcsStatusWlanWlanParameterEntry 13 }

-- {COLUMN} 310.1.3.55.1.24
lcsStatusWlanWlanParameterEntryModemLoad OBJECT-TYPE
    SYNTAX     INTEGER (0..255)
    MAX-ACCESS read-only
    STATUS     current
    DESCRIPTION
        "-- empty --"
    ::= { lcsStatusWlanWlanParameterEntry 24 }

-- {COLUMN} 310.1.3.55.1.15
lcsStatusWlanWlanParameterEntryTransmitPower OBJECT-TYPE
    SYNTAX     DisplayString (SIZE(0..255))
    MAX-ACCESS read-only
    STATUS     current
    DESCRIPTION
        "-- empty --"
    ::= { lcsStatusWlanWlanParameterEntry 15 }

-- {COLUMN} 310.1.3.55.1.22
lcsStatusWlanWlanParameterEntryEirp OBJECT-TYPE
    SYNTAX     DisplayString (SIZE(0..255))
    MAX-ACCESS read-only
    STATUS     current
    DESCRIPTION
        "-- empty --"
    ::= { lcsStatusWlanWlanParameterEntry 22 }

-- {COLUMN} 310.1.3.55.1.23
lcsStatusWlanWlanParameterEntryExcEirp OBJECT-TYPE
    SYNTAX     INTEGER
      {
        eNo (0),
        eYes (1)
      }
    MAX-ACCESS read-only
    STATUS     current
    DESCRIPTION
        "-- empty --"
    ::= { lcsStatusWlanWlanParameterEntry 23 }

-- {COLUMN} 310.1.3.55.1.25
lcsStatusWlanWlanParameterEntryBeaconPeriod OBJECT-TYPE
    SYNTAX     INTEGER (0..65535)
    MAX-ACCESS read-only
    STATUS     current
    DESCRIPTION
        "-- empty --"
    ::= { lcsStatusWlanWlanParameterEntry 25 }

-- {COLUMN} 310.1.3.55.1.36
lcsStatusWlanWlanParameterEntryCountry OBJECT-TYPE
    SYNTAX     INTEGER
      {
        eUnknown (0),
        eAlbania (8),
        eAlgeria (12),
        eArgentina (32),
        eAustralia (36),
        eAustria (40),
        eBahrain (48),
        eBangladesh (50),
        eBelarus (112),
        eBelgium (56),
        eBosniaHerzegovina (70),
        eBrazil (76),
        eBruneiDarussalam (96),
        eBulgaria (100),
        eCanada (124),
        eChile (152),
        eChina (156),
        eColombia (170),
        eCostaRica (188),
        eCroatia (191),
        eCyprus (196),
        eCzech (203),
        eDenmark (208),
        eEcuador (218),
        eEgalistan (999),
        eEgypt (818),
        eEstonia (233),
        eEurope (998),
        eFinland (246),
        eFrance (250),
        eGermany (276),
        eGhana (288),
        eGreece (300),
        eGuatemala (320),
        eHonduras (340),
        eHongKong (344),
        eHungary (348),
        eIceland (352),
        eIndia (356),
        eIndonesia (360),
        eIreland (372),
        eIsrael (376),
        eItaly (380),
        eJapan (392),
        eJordan (400),
        eSouthKorea (410),
        eKuwait (414),
        eLatvia (428),
        eLebanon (422),
        eLiechtenstein (438),
        eLithuania (440),
        eLuxembourg (442),
        eMacau (446),
        eMacedonia (807),
        eMalaysia (458),
        eMalta (470),
        eMexico (484),
        eMoldavia (498),
        eMorocco (504),
        eNetherlands (528),
        eNewZealand (554),
        eNicaragua (558),
        eNorway (578),
        eOman (512),
        ePakistan (586),
        ePanama (591),
        eParaguay (600),
        ePeru (604),
        ePhilippines (608),
        ePoland (616),
        ePortugal (620),
        ePuertoRico (630),
        eQatar (634),
        eRomania (642),
        eRussia (643),
        eSaudiArabia (682),
        eSingapore (702),
        eSlovak (703),
        eSlovenia (705),
        eSouthAfrica (710),
        eSpain (724),
        eSweden (752),
        eSwitzerland (756),
        eTaiwan (158),
        eTanzania (834),
        eThailand (764),
        eTunisia (788),
        eTurkey (792),
        eUganda (800),
        eUkraine (804),
        eUnitedArabEmirates (784),
        eUnitedKingdom (826),
        eUnitedStatesFcc (840),
        eUruguay (858),
        eVenezuela (862)
      }
    MAX-ACCESS read-only
    STATUS     current
    DESCRIPTION
        "-- empty --"
    ::= { lcsStatusWlanWlanParameterEntry 36 }

-- {COLUMN} 310.1.3.55.1.4
lcsStatusWlanWlanParameterEntryRegulatoryDomain OBJECT-TYPE
    SYNTAX     INTEGER
      {
        eUndefined (0),
        eFcc (16),
        eCanada (32),
        eEuEtsi (48),
        eSpain (49),
        eFrance (50),
        eMkkJapan (64),
        eMkk2Japan (65),
        eIsrael (80),
        eWorld (96)
      }
    MAX-ACCESS read-only
    STATUS     current
    DESCRIPTION
        "-- empty --"
    ::= { lcsStatusWlanWlanParameterEntry 4 }

-- {COLUMN} 310.1.3.55.1.5
lcsStatusWlanWlanParameterEntryPhyType OBJECT-TYPE
    SYNTAX     INTEGER
      {
        eProprietary (0),
        eFhss (1),
        eDsss (2),
        eInfrared (3),
        eOfdm (4),
        eHrDsss (5),
        eErp (6),
        eHt (7),
        ePbcc (254)
      }
    MAX-ACCESS read-only
    STATUS     current
    DESCRIPTION
        "-- empty --"
    ::= { lcsStatusWlanWlanParameterEntry 5 }

-- {COLUMN} 310.1.3.55.1.33
lcsStatusWlanWlanParameterEntrySupportedAntennas OBJECT-TYPE
    SYNTAX     INTEGER
      {
        eNA (0),
        eAntenna1 (1),
        eAntenna1Plus2 (3),
        eAntenna1Plus3 (5),
        eAntenna1Plus2Plus3 (7)
      }
    MAX-ACCESS read-only
    STATUS     current
    DESCRIPTION
        "-- empty --"
    ::= { lcsStatusWlanWlanParameterEntry 33 }

-- {COLUMN} 310.1.3.55.1.29
lcsStatusWlanWlanParameterEntryTxChains OBJECT-TYPE
    SYNTAX     INTEGER (0..255)
    MAX-ACCESS read-only
    STATUS     current
    DESCRIPTION
        "-- empty --"
    ::= { lcsStatusWlanWlanParameterEntry 29 }

-- {COLUMN} 310.1.3.55.1.30
lcsStatusWlanWlanParameterEntryRxChains OBJECT-TYPE
    SYNTAX     INTEGER (0..255)
    MAX-ACCESS read-only
    STATUS     current
    DESCRIPTION
        "-- empty --"
    ::= { lcsStatusWlanWlanParameterEntry 30 }

-- {COLUMN} 310.1.3.55.1.7
lcsStatusWlanWlanParameterEntryWepSupport OBJECT-TYPE
    SYNTAX     INTEGER
      {
        eNo (0),
        eYes40Bits (1),
        eYes104Bits (2),
        eYes128Bits (3)
      }
    MAX-ACCESS read-only
    STATUS     current
    DESCRIPTION
        "-- empty --"
    ::= { lcsStatusWlanWlanParameterEntry 7 }

-- {COLUMN} 310.1.3.55.1.18
lcsStatusWlanWlanParameterEntryTkipSupport OBJECT-TYPE
    SYNTAX     INTEGER
      {
        eNo (0),
        eYes (1)
      }
    MAX-ACCESS read-only
    STATUS     current
    DESCRIPTION
        "-- empty --"
    ::= { lcsStatusWlanWlanParameterEntry 18 }

-- {COLUMN} 310.1.3.55.1.19
lcsStatusWlanWlanParameterEntryAesSupport OBJECT-TYPE
    SYNTAX     INTEGER
      {
        eNo (0),
        eOcb (1),
        eCcm (2),
        eOcbPlusCcm (3)
      }
    MAX-ACCESS read-only
    STATUS     current
    DESCRIPTION
        "-- empty --"
    ::= { lcsStatusWlanWlanParameterEntry 19 }

-- {COLUMN} 310.1.3.55.1.21
lcsStatusWlanWlanParameterEntryMinimumRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (12), -- 6Mbit/s
        e9M (13), -- 9Mbit/s
        e12M (14), -- 12Mbit/s
        e18M (15), -- 18Mbit/s
        e24M (16), -- 24Mbit/s
        e36M (17), -- 36Mbit/s
        e48M (18), -- 48Mbit/s
        e54M (19), -- 54Mbit/s
        eT12M (20), -- Turbo 12Mbit/s
        eT18M (21), -- Turbo 18Mbit/s
        eT24M (22), -- Turbo 24Mbit/s
        eT36M (23), -- Turbo 36Mbit/s
        eT48M (24), -- Turbo 48Mbit/s
        eT72M (25), -- Turbo 72Mbit/s
        eT96M (26), -- Turbo 96Mbit/s
        eT108M (27), -- Turbo 108Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51), -- High throughput 3 streams 195Mbit/s
        eHTDUP6M (60) -- High throughput duplicate 6Mbit/s
      }
    MAX-ACCESS read-only
    STATUS     current
    DESCRIPTION
        "-- empty --"
    ::= { lcsStatusWlanWlanParameterEntry 21 }

-- {COLUMN} 310.1.3.55.1.8
lcsStatusWlanWlanParameterEntryMaximumRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (12), -- 6Mbit/s
        e9M (13), -- 9Mbit/s
        e12M (14), -- 12Mbit/s
        e18M (15), -- 18Mbit/s
        e24M (16), -- 24Mbit/s
        e36M (17), -- 36Mbit/s
        e48M (18), -- 48Mbit/s
        e54M (19), -- 54Mbit/s
        eT12M (20), -- Turbo 12Mbit/s
        eT18M (21), -- Turbo 18Mbit/s
        eT24M (22), -- Turbo 24Mbit/s
        eT36M (23), -- Turbo 36Mbit/s
        eT48M (24), -- Turbo 48Mbit/s
        eT72M (25), -- Turbo 72Mbit/s
        eT96M (26), -- Turbo 96Mbit/s
        eT108M (27), -- Turbo 108Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51), -- High throughput 3 streams 195Mbit/s
        eHTDUP6M (60) -- High throughput duplicate 6Mbit/s
      }
    MAX-ACCESS read-only
    STATUS     current
    DESCRIPTION
        "-- empty --"
    ::= { lcsStatusWlanWlanParameterEntry 8 }

-- {COLUMN} 310.1.3.55.1.9
lcsStatusWlanWlanParameterEntryTemperatureRange OBJECT-TYPE
    SYNTAX     INTEGER
      {
        eUnknown (0),
        eCommercial0Plus40DegreeC (1),
        eIndustrial30Plus70DegreeC (2)
      }
    MAX-ACCESS read-only
    STATUS     current
    DESCRIPTION
        "-- empty --"
    ::= { lcsStatusWlanWlanParameterEntry 9 }

-- {COLUMN} 310.1.3.55.1.10
lcsStatusWlanWlanParameterEntryPhyVariant OBJECT-TYPE
    SYNTAX     DisplayString (SIZE(0..15))
    MAX-ACCESS read-only
    STATUS     current
    DESCRIPTION
        "-- empty --"
    ::= { lcsStatusWlanWlanParameterEntry 10 }

-- {COLUMN} 310.1.3.55.1.12
lcsStatusWlanWlanParameterEntrySupportedBands OBJECT-TYPE
    SYNTAX     INTEGER
      {
        eUnknown (0),
        e24ghz (1),
        e5ghz (2),
        e24ghz5ghz (3)
      }
    MAX-ACCESS read-only
    STATUS     current
    DESCRIPTION
        "-- empty --"
    ::= { lcsStatusWlanWlanParameterEntry 12 }

-- {COLUMN} 310.1.3.55.1.28
lcsStatusWlanWlanParameterEntrySupports40mhz OBJECT-TYPE
    SYNTAX     INTEGER
      {
        eNo (0),
        eYes (1)
      }
    MAX-ACCESS read-only
    STATUS     current
    DESCRIPTION
        "-- empty --"
    ::= { lcsStatusWlanWlanParameterEntry 28 }

-- {COLUMN} 310.1.3.55.1.14
lcsStatusWlanWlanParameterEntrySupportsShortPreamble OBJECT-TYPE
    SYNTAX     INTEGER
      {
        eNo (0),
        eYes (1)
      }
    MAX-ACCESS read-only
    STATUS     current
    DESCRIPTION
        "-- empty --"
    ::= { lcsStatusWlanWlanParameterEntry 14 }

-- {COLUMN} 310.1.3.55.1.17
lcsStatusWlanWlanParameterEntrySupportsShortSlotTime OBJECT-TYPE
    SYNTAX     INTEGER
      {
        eNo (0),
        eYes (1)
      }
    MAX-ACCESS read-only
    STATUS     current
    DESCRIPTION
        "-- empty --"
    ::= { lcsStatusWlanWlanParameterEntry 17 }

-- {COLUMN} 310.1.3.55.1.26
lcsStatusWlanWlanParameterEntrySupportsShortGuardInterval OBJECT-TYPE
    SYNTAX     INTEGER
      {
        eNo (0),
        e20mhz (1),
        e40mhz (2),
        e2040mhz (3)
      }
    MAX-ACCESS read-only
    STATUS     current
    DESCRIPTION
        "-- empty --"
    ::= { lcsStatusWlanWlanParameterEntry 26 }

-- {COLUMN} 310.1.3.55.1.20
lcsStatusWlanWlanParameterEntrySupportsCompression OBJECT-TYPE
    SYNTAX     INTEGER
      {
        eNo (0),
        eYes (1)
      }
    MAX-ACCESS read-only
    STATUS     current
    DESCRIPTION
        "-- empty --"
    ::= { lcsStatusWlanWlanParameterEntry 20 }

-- {COLUMN} 310.1.3.55.1.32
lcsStatusWlanWlanParameterEntrySupportedDfsSchemes OBJECT-TYPE
    SYNTAX     BITS
      {
        eJapan (3),
        eFcc (4),
        eEn302502 (5),
        eEn301893V13 (6),
        eEn301893V12 (7),
        eEn301893V15 (2),
        eEn301893V16 (1),
        eNone (0)
      }
    MAX-ACCESS read-only
    STATUS     current
    DESCRIPTION
        "-- empty --"
    ::= { lcsStatusWlanWlanParameterEntry 32 }

-- {TABLE} 310.1.3.57
lcsStatusWlanRadiosTable OBJECT-TYPE
    SYNTAX     SEQUENCE OF LcsStatusWlanRadiosEntry
    MAX-ACCESS not-accessible
    STATUS     current
    DESCRIPTION
        "-- empty --"
    ::= { lcsStatusWlan 57 }

-- {ENTRY} 310.1.3.57.1
lcsStatusWlanRadiosEntry OBJECT-TYPE
    SYNTAX     LcsStatusWlanRadiosEntry
    MAX-ACCESS not-accessible
    STATUS     current
    DESCRIPTION
        ""
    INDEX {
        lcsStatusWlanRadiosEntryIfc
    }
    ::= { lcsStatusWlanRadiosTable 1 }

-- {SEQUENCE}
LcsStatusWlanRadiosEntry ::= SEQUENCE {
    lcsStatusWlanRadiosEntryIfc DisplayString,
    lcsStatusWlanRadiosEntryRadioBand INTEGER,
    lcsStatusWlanRadiosEntryRadioChannel INTEGER,
    lcsStatusWlanRadiosEntryRadioMode INTEGER,
    lcsStatusWlanRadiosEntryExtChannel INTEGER,
    lcsStatusWlanRadiosEntry40mhzPermitted INTEGER,
    lcsStatusWlanRadiosEntryNoiseLevel INTEGER,
    lcsStatusWlanRadiosEntryModemLoad INTEGER,
    lcsStatusWlanRadiosEntryTransmitPower DisplayString,
    lcsStatusWlanRadiosEntryEirp DisplayString,
    lcsStatusWlanRadiosEntryExcEirp INTEGER,
    lcsStatusWlanRadiosEntryBackgroundScan INTEGER,
    lcsStatusWlanRadiosEntryBackgroundScanUnit INTEGER,
    lcsStatusWlanRadiosEntryDfsScheme INTEGER,
    lcsStatusWlanRadiosEntryRadarLoadThreshold INTEGER,
    lcsStatusWlanRadiosEntryShortSlotTime INTEGER,
    lcsStatusWlanRadiosEntryAggregateTimeLimitUs INTEGER
}

-- {COLUMN} 310.1.3.57.1.1
lcsStatusWlanRadiosEntryIfc OBJECT-TYPE
    SYNTAX     DisplayString (SIZE(0..255))
    MAX-ACCESS read-only
    STATUS     current
    DESCRIPTION
        "-- empty --"
    ::= { lcsStatusWlanRadiosEntry 1 }

-- {COLUMN} 310.1.3.57.1.2
lcsStatusWlanRadiosEntryRadioBand OBJECT-TYPE
    SYNTAX     INTEGER
      {
        eUnknown (0),
        e24ghz (1),
        e5ghz (2)
      }
    MAX-ACCESS read-only
    STATUS     current
    DESCRIPTION
        "-- empty --"
    ::= { lcsStatusWlanRadiosEntry 2 }

-- {COLUMN} 310.1.3.57.1.3
lcsStatusWlanRadiosEntryRadioChannel OBJECT-TYPE
    SYNTAX     INTEGER (0..255)
    MAX-ACCESS read-only
    STATUS     current
    DESCRIPTION
        "-- empty --"
    ::= { lcsStatusWlanRadiosEntry 3 }

-- {COLUMN} 310.1.3.57.1.14
lcsStatusWlanRadiosEntryRadioMode OBJECT-TYPE
    SYNTAX     INTEGER
      {
        e11bgMixed (0),
        e11gOnly (1),
        e11bOnly (2),
        e2mMixed (3),
        eTurboG (4),
        e11bgnMixed (5),
        e2m11bgnMixed (6),
        e11gnMixed (7),
        eGreenfieldGn (8),
        e11a (256),
        eTurboA (257),
        e11anMixed (259),
        eGreenfieldAn (260),
        eHalf11a (261),
        eQuarter11a (262),
        eNone (65535)
      }
    MAX-ACCESS read-only
    STATUS     current
    DESCRIPTION
        "-- empty --"
    ::= { lcsStatusWlanRadiosEntry 14 }

-- {COLUMN} 310.1.3.57.1.11
lcsStatusWlanRadiosEntryExtChannel OBJECT-TYPE
    SYNTAX     INTEGER
      {
        eNone (0),
        eAbove (1),
        eBelow (3)
      }
    MAX-ACCESS read-only
    STATUS     current
    DESCRIPTION
        "-- empty --"
    ::= { lcsStatusWlanRadiosEntry 11 }

-- {COLUMN} 310.1.3.57.1.15
lcsStatusWlanRadiosEntry40mhzPermitted OBJECT-TYPE
    SYNTAX     INTEGER
      {
        eNo (0),
        eYes (1)
      }
    MAX-ACCESS read-only
    STATUS     current
    DESCRIPTION
        "-- empty --"
    ::= { lcsStatusWlanRadiosEntry 15 }

-- {COLUMN} 310.1.3.57.1.5
lcsStatusWlanRadiosEntryNoiseLevel OBJECT-TYPE
    SYNTAX     INTEGER (-32768..32767)
    MAX-ACCESS read-only
    STATUS     current
    DESCRIPTION
        "-- empty --"
    ::= { lcsStatusWlanRadiosEntry 5 }

-- {COLUMN} 310.1.3.57.1.6
lcsStatusWlanRadiosEntryModemLoad OBJECT-TYPE
    SYNTAX     INTEGER (0..255)
    MAX-ACCESS read-only
    STATUS     current
    DESCRIPTION
        "-- empty --"
    ::= { lcsStatusWlanRadiosEntry 6 }

-- {COLUMN} 310.1.3.57.1.7
lcsStatusWlanRadiosEntryTransmitPower OBJECT-TYPE
    SYNTAX     DisplayString (SIZE(0..255))
    MAX-ACCESS read-only
    STATUS     current
    DESCRIPTION
        "-- empty --"
    ::= { lcsStatusWlanRadiosEntry 7 }

-- {COLUMN} 310.1.3.57.1.8
lcsStatusWlanRadiosEntryEirp OBJECT-TYPE
    SYNTAX     DisplayString (SIZE(0..255))
    MAX-ACCESS read-only
    STATUS     current
    DESCRIPTION
        "-- empty --"
    ::= { lcsStatusWlanRadiosEntry 8 }

-- {COLUMN} 310.1.3.57.1.9
lcsStatusWlanRadiosEntryExcEirp OBJECT-TYPE
    SYNTAX     INTEGER
      {
        eNo (0),
        eYes (1)
      }
    MAX-ACCESS read-only
    STATUS     current
    DESCRIPTION
        "-- empty --"
    ::= { lcsStatusWlanRadiosEntry 9 }

-- {COLUMN} 310.1.3.57.1.10
lcsStatusWlanRadiosEntryBackgroundScan OBJECT-TYPE
    SYNTAX     INTEGER (0..2147483647)
    MAX-ACCESS read-only
    STATUS     current
    DESCRIPTION
        "-- empty --"
    ::= { lcsStatusWlanRadiosEntry 10 }

-- {COLUMN} 310.1.3.57.1.12
lcsStatusWlanRadiosEntryBackgroundScanUnit OBJECT-TYPE
    SYNTAX     INTEGER
      {
        eSeconds (0),
        eMilliseconds (1),
        eMicroseconds (2),
        eMinutes (3),
        eHours (4),
        eDays (5),
        eWeeks (6),
        eFortnights (7)
      }
    MAX-ACCESS read-only
    STATUS     current
    DESCRIPTION
        "-- empty --"
    ::= { lcsStatusWlanRadiosEntry 12 }

-- {COLUMN} 310.1.3.57.1.13
lcsStatusWlanRadiosEntryDfsScheme OBJECT-TYPE
    SYNTAX     INTEGER
      {
        eJapan (16),
        eFcc (8),
        eEn302502 (4),
        eEn301893V13 (2),
        eEn301893V12 (1),
        eEn301893V15 (32),
        eEn301893V16 (64),
        eNone (0)
      }
    MAX-ACCESS read-only
    STATUS     current
    DESCRIPTION
        "-- empty --"
    ::= { lcsStatusWlanRadiosEntry 13 }

-- {COLUMN} 310.1.3.57.1.16
lcsStatusWlanRadiosEntryRadarLoadThreshold OBJECT-TYPE
    SYNTAX     INTEGER (0..255)
    MAX-ACCESS read-only
    STATUS     current
    DESCRIPTION
        "-- empty --"
    ::= { lcsStatusWlanRadiosEntry 16 }

-- {COLUMN} 310.1.3.57.1.17
lcsStatusWlanRadiosEntryShortSlotTime OBJECT-TYPE
    SYNTAX     INTEGER
      {
        eNo (0),
        eYes (1)
      }
    MAX-ACCESS read-only
    STATUS     current
    DESCRIPTION
        "-- empty --"
    ::= { lcsStatusWlanRadiosEntry 17 }

-- {COLUMN} 310.1.3.57.1.18
lcsStatusWlanRadiosEntryAggregateTimeLimitUs OBJECT-TYPE
    SYNTAX     INTEGER (0..2147483647)
    MAX-ACCESS read-only
    STATUS     current
    DESCRIPTION
        "-- empty --"
    ::= { lcsStatusWlanRadiosEntry 18 }

-- {TABLE} 310.1.3.58
lcsStatusWlanQosParametersTable OBJECT-TYPE
    SYNTAX     SEQUENCE OF LcsStatusWlanQosParametersEntry
    MAX-ACCESS not-accessible
    STATUS     current
    DESCRIPTION
        "-- empty --"
    ::= { lcsStatusWlan 58 }

-- {ENTRY} 310.1.3.58.1
lcsStatusWlanQosParametersEntry OBJECT-TYPE
    SYNTAX     LcsStatusWlanQosParametersEntry
    MAX-ACCESS not-accessible
    STATUS     current
    DESCRIPTION
        ""
    INDEX {
        lcsStatusWlanQosParametersEntryIfc,
        lcsStatusWlanQosParametersEntryAccessCategory
    }
    ::= { lcsStatusWlanQosParametersTable 1 }

-- {SEQUENCE}
LcsStatusWlanQosParametersEntry ::= SEQUENCE {
    lcsStatusWlanQosParametersEntryIfc DisplayString,
    lcsStatusWlanQosParametersEntryAccessCategory INTEGER,
    lcsStatusWlanQosParametersEntryTxop INTEGER,
    lcsStatusWlanQosParametersEntryCwmin INTEGER,
    lcsStatusWlanQosParametersEntryCwmax INTEGER,
    lcsStatusWlanQosParametersEntryAifs INTEGER
}

-- {COLUMN} 310.1.3.58.1.1
lcsStatusWlanQosParametersEntryIfc OBJECT-TYPE
    SYNTAX     DisplayString (SIZE(0..255))
    MAX-ACCESS read-only
    STATUS     current
    DESCRIPTION
        "-- empty --"
    ::= { lcsStatusWlanQosParametersEntry 1 }

-- {COLUMN} 310.1.3.58.1.2
lcsStatusWlanQosParametersEntryAccessCategory OBJECT-TYPE
    SYNTAX     INTEGER
      {
        eBestEffort (0),
        eBackground (1),
        eVideo (2),
        eVoice (3)
      }
    MAX-ACCESS read-only
    STATUS     current
    DESCRIPTION
        "-- empty --"
    ::= { lcsStatusWlanQosParametersEntry 2 }

-- {COLUMN} 310.1.3.58.1.3
lcsStatusWlanQosParametersEntryTxop OBJECT-TYPE
    SYNTAX     INTEGER (0..2147483647)
    MAX-ACCESS read-only
    STATUS     current
    DESCRIPTION
        "-- empty --"
    ::= { lcsStatusWlanQosParametersEntry 3 }

-- {COLUMN} 310.1.3.58.1.4
lcsStatusWlanQosParametersEntryCwmin OBJECT-TYPE
    SYNTAX     INTEGER (0..65535)
    MAX-ACCESS read-only
    STATUS     current
    DESCRIPTION
        "-- empty --"
    ::= { lcsStatusWlanQosParametersEntry 4 }

-- {COLUMN} 310.1.3.58.1.5
lcsStatusWlanQosParametersEntryCwmax OBJECT-TYPE
    SYNTAX     INTEGER (0..65535)
    MAX-ACCESS read-only
    STATUS     current
    DESCRIPTION
        "-- empty --"
    ::= { lcsStatusWlanQosParametersEntry 5 }

-- {COLUMN} 310.1.3.58.1.6
lcsStatusWlanQosParametersEntryAifs OBJECT-TYPE
    SYNTAX     INTEGER (0..255)
    MAX-ACCESS read-only
    STATUS     current
    DESCRIPTION
        "-- empty --"
    ::= { lcsStatusWlanQosParametersEntry 6 }

-- {TABLE} 310.1.3.59
lcsStatusWlanQosPacketStatisticsTable OBJECT-TYPE
    SYNTAX     SEQUENCE OF LcsStatusWlanQosPacketStatisticsEntry
    MAX-ACCESS not-accessible
    STATUS     current
    DESCRIPTION
        "-- empty --"
    ::= { lcsStatusWlan 59 }

-- {ENTRY} 310.1.3.59.1
lcsStatusWlanQosPacketStatisticsEntry OBJECT-TYPE
    SYNTAX     LcsStatusWlanQosPacketStatisticsEntry
    MAX-ACCESS not-accessible
    STATUS     current
    DESCRIPTION
        ""
    INDEX {
        lcsStatusWlanQosPacketStatisticsEntryIfc,
        lcsStatusWlanQosPacketStatisticsEntryAccessCategory
    }
    ::= { lcsStatusWlanQosPacketStatisticsTable 1 }

-- {SEQUENCE}
LcsStatusWlanQosPacketStatisticsEntry ::= SEQUENCE {
    lcsStatusWlanQosPacketStatisticsEntryIfc DisplayString,
    lcsStatusWlanQosPacketStatisticsEntryAccessCategory INTEGER,
    lcsStatusWlanQosPacketStatisticsEntryTxPackets INTEGER,
    lcsStatusWlanQosPacketStatisticsEntryTxDiscarded INTEGER
}

-- {COLUMN} 310.1.3.59.1.1
lcsStatusWlanQosPacketStatisticsEntryIfc OBJECT-TYPE
    SYNTAX     DisplayString (SIZE(0..255))
    MAX-ACCESS read-only
    STATUS     current
    DESCRIPTION
        "-- empty --"
    ::= { lcsStatusWlanQosPacketStatisticsEntry 1 }

-- {COLUMN} 310.1.3.59.1.2
lcsStatusWlanQosPacketStatisticsEntryAccessCategory OBJECT-TYPE
    SYNTAX     INTEGER
      {
        eBestEffort (0),
        eBackground (1),
        eVideo (2),
        eVoice (3)
      }
    MAX-ACCESS read-only
    STATUS     current
    DESCRIPTION
        "-- empty --"
    ::= { lcsStatusWlanQosPacketStatisticsEntry 2 }

-- {COLUMN} 310.1.3.59.1.3
lcsStatusWlanQosPacketStatisticsEntryTxPackets OBJECT-TYPE
    SYNTAX     INTEGER (0..2147483647)
    MAX-ACCESS read-only
    STATUS     current
    DESCRIPTION
        "-- empty --"
    ::= { lcsStatusWlanQosPacketStatisticsEntry 3 }

-- {COLUMN} 310.1.3.59.1.4
lcsStatusWlanQosPacketStatisticsEntryTxDiscarded OBJECT-TYPE
    SYNTAX     INTEGER (0..2147483647)
    MAX-ACCESS read-only
    STATUS     current
    DESCRIPTION
        "-- empty --"
    ::= { lcsStatusWlanQosPacketStatisticsEntry 4 }

-- {TABLE} 310.1.3.34
lcsStatusWlanScanResultsTable OBJECT-TYPE
    SYNTAX     SEQUENCE OF LcsStatusWlanScanResultsEntry
    MAX-ACCESS not-accessible
    STATUS     current
    DESCRIPTION
        "-- empty --"
    ::= { lcsStatusWlan 34 }

-- {ENTRY} 310.1.3.34.1
lcsStatusWlanScanResultsEntry OBJECT-TYPE
    SYNTAX     LcsStatusWlanScanResultsEntry
    MAX-ACCESS not-accessible
    STATUS     current
    DESCRIPTION
        ""
    INDEX {
        lcsStatusWlanScanResultsEntryBssid,
        lcsStatusWlanScanResultsEntryInterface
    }
    ::= { lcsStatusWlanScanResultsTable 1 }

-- {SEQUENCE}
LcsStatusWlanScanResultsEntry ::= SEQUENCE {
    lcsStatusWlanScanResultsEntryBssid MacAddress,
    lcsStatusWlanScanResultsEntryInterface INTEGER,
    lcsStatusWlanScanResultsEntryVendor DisplayString,
    lcsStatusWlanScanResultsEntryNetworkName DisplayString,
    lcsStatusWlanScanResultsEntryOperationMode INTEGER,
    lcsStatusWlanScanResultsEntryEncryption INTEGER,
    lcsStatusWlanScanResultsEntryPreAuthentication INTEGER,
    lcsStatusWlanScanResultsEntryBeaconPeriod INTEGER,
    lcsStatusWlanScanResultsEntryDtimPeriod INTEGER,
    lcsStatusWlanScanResultsEntryPcfFunctionality INTEGER,
    lcsStatusWlanScanResultsEntryQos INTEGER,
    lcsStatusWlanScanResultsEntryMaxAMpduLen INTEGER,
    lcsStatusWlanScanResultsEntryMaxAMsduLen INTEGER,
    lcsStatusWlanScanResultsEntryRadioBand INTEGER,
    lcsStatusWlanScanResultsEntryRadioChannel INTEGER,
    lcsStatusWlanScanResultsEntry108mbpsMode INTEGER,
    lcsStatusWlanScanResultsEntryExtChannel INTEGER,
    lcsStatusWlanScanResultsEntryPhySignal INTEGER,
    lcsStatusWlanScanResultsEntrySignalLevel INTEGER,
    lcsStatusWlanScanResultsEntryNoiseLevel INTEGER,
    lcsStatusWlanScanResultsEntryLoad DisplayString,
    lcsStatusWlanScanResultsEntryShortPreamble INTEGER,
    lcsStatusWlanScanResultsEntryShortSlotTime INTEGER,
    lcsStatusWlanScanResultsEntry40mhzMode INTEGER,
    lcsStatusWlanScanResultsEntry40mhzCoexistence INTEGER,
    lcsStatusWlanScanResultsEntry40mhzIntolerant INTEGER,
    lcsStatusWlanScanResultsEntryShortGuardInterval INTEGER,
    lcsStatusWlanScanResultsEntryTxStbc INTEGER,
    lcsStatusWlanScanResultsEntryRxStbc INTEGER,
    lcsStatusWlanScanResultsEntryLdpc INTEGER,
    lcsStatusWlanScanResultsEntryCompression INTEGER,
    lcsStatusWlanScanResultsEntryAge INTEGER,
    lcsStatusWlanScanResultsEntryRate INTEGER,
    lcsStatusWlanScanResultsEntryEffRate INTEGER,
    lcsStatusWlanScanResultsEntryNonerpPresent INTEGER,
    lcsStatusWlanScanResultsEntryIdentification DisplayString,
    lcsStatusWlanScanResultsEntryInterpointPeerName DisplayString,
    lcsStatusWlanScanResultsEntryEapolPreauthFailed INTEGER
}

-- {COLUMN} 310.1.3.34.1.1
lcsStatusWlanScanResultsEntryBssid OBJECT-TYPE
    SYNTAX     MacAddress
    MAX-ACCESS read-only
    STATUS     current
    DESCRIPTION
        "-- empty --"
    ::= { lcsStatusWlanScanResultsEntry 1 }

-- {COLUMN} 310.1.3.34.1.15
lcsStatusWlanScanResultsEntryInterface OBJECT-TYPE
    SYNTAX     INTEGER
      {
        eWlan1 (0),
        eWlan2 (1),
        eWlan3 (2),
        eWlan4 (3)
      }
    MAX-ACCESS read-only
    STATUS     current
    DESCRIPTION
        "-- empty --"
    ::= { lcsStatusWlanScanResultsEntry 15 }

-- {COLUMN} 310.1.3.34.1.34
lcsStatusWlanScanResultsEntryVendor OBJECT-TYPE
    SYNTAX     DisplayString (SIZE(0..255))
    MAX-ACCESS read-only
    STATUS     current
    DESCRIPTION
        "-- empty --"
    ::= { lcsStatusWlanScanResultsEntry 34 }

-- {COLUMN} 310.1.3.34.1.2
lcsStatusWlanScanResultsEntryNetworkName OBJECT-TYPE
    SYNTAX     DisplayString (SIZE(0..255))
    MAX-ACCESS read-only
    STATUS     current
    DESCRIPTION
        "-- empty --"
    ::= { lcsStatusWlanScanResultsEntry 2 }

-- {COLUMN} 310.1.3.34.1.3
lcsStatusWlanScanResultsEntryOperationMode OBJECT-TYPE
    SYNTAX     INTEGER
      {
        eNone (0),
        eAdhoc (1),
        eInfrastructure (2) -- lancom's description of Infrastructure
      }
    MAX-ACCESS read-only
    STATUS     current
    DESCRIPTION
        "lancom's description of operation mode"
    ::= { lcsStatusWlanScanResultsEntry 3 }

-- {COLUMN} 310.1.3.34.1.13
lcsStatusWlanScanResultsEntryEncryption OBJECT-TYPE
    SYNTAX     INTEGER
      {
        eNone (0),
        eWep (1),
        eTkip (2),
        eAes (3),
        eAesPlusTkip (4)
      }
    MAX-ACCESS read-only
    STATUS     current
    DESCRIPTION
        "-- empty --"
    ::= { lcsStatusWlanScanResultsEntry 13 }

-- {COLUMN} 310.1.3.34.1.37
lcsStatusWlanScanResultsEntryPreAuthentication OBJECT-TYPE
    SYNTAX     INTEGER
      {
        eNo (0),
        eYes (1)
      }
    MAX-ACCESS read-only
    STATUS     current
    DESCRIPTION
        "-- empty --"
    ::= { lcsStatusWlanScanResultsEntry 37 }

-- {COLUMN} 310.1.3.34.1.6
lcsStatusWlanScanResultsEntryBeaconPeriod OBJECT-TYPE
    SYNTAX     INTEGER (0..65535)
    MAX-ACCESS read-only
    STATUS     current
    DESCRIPTION
        "-- empty --"
    ::= { lcsStatusWlanScanResultsEntry 6 }

-- {COLUMN} 310.1.3.34.1.7
lcsStatusWlanScanResultsEntryDtimPeriod OBJECT-TYPE
    SYNTAX     INTEGER (0..65535)
    MAX-ACCESS read-only
    STATUS     current
    DESCRIPTION
        "-- empty --"
    ::= { lcsStatusWlanScanResultsEntry 7 }

-- {COLUMN} 310.1.3.34.1.22
lcsStatusWlanScanResultsEntryPcfFunctionality OBJECT-TYPE
    SYNTAX     INTEGER
      {
        eNone (0),
        eDelivery (1),
        eDeliveryPlusPolling (2)
      }
    MAX-ACCESS read-only
    STATUS     current
    DESCRIPTION
        "-- empty --"
    ::= { lcsStatusWlanScanResultsEntry 22 }

-- {COLUMN} 310.1.3.34.1.24
lcsStatusWlanScanResultsEntryQos OBJECT-TYPE
    SYNTAX     INTEGER
      {
        eNo (0),
        eYes (1)
      }
    MAX-ACCESS read-only
    STATUS     current
    DESCRIPTION
        "-- empty --"
    ::= { lcsStatusWlanScanResultsEntry 24 }

-- {COLUMN} 310.1.3.34.1.32
lcsStatusWlanScanResultsEntryMaxAMpduLen OBJECT-TYPE
    SYNTAX     INTEGER (0..2147483647)
    MAX-ACCESS read-only
    STATUS     current
    DESCRIPTION
        "-- empty --"
    ::= { lcsStatusWlanScanResultsEntry 32 }

-- {COLUMN} 310.1.3.34.1.33
lcsStatusWlanScanResultsEntryMaxAMsduLen OBJECT-TYPE
    SYNTAX     INTEGER (0..2147483647)
    MAX-ACCESS read-only
    STATUS     current
    DESCRIPTION
        "-- empty --"
    ::= { lcsStatusWlanScanResultsEntry 33 }

-- {COLUMN} 310.1.3.34.1.16
lcsStatusWlanScanResultsEntryRadioBand OBJECT-TYPE
    SYNTAX     INTEGER
      {
        eUnknown (0),
        e24ghz (1),
        e5ghz (2)
      }
    MAX-ACCESS read-only
    STATUS     current
    DESCRIPTION
        "-- empty --"
    ::= { lcsStatusWlanScanResultsEntry 16 }

-- {COLUMN} 310.1.3.34.1.8
lcsStatusWlanScanResultsEntryRadioChannel OBJECT-TYPE
    SYNTAX     INTEGER (0..255)
    MAX-ACCESS read-only
    STATUS     current
    DESCRIPTION
        "-- empty --"
    ::= { lcsStatusWlanScanResultsEntry 8 }

-- {COLUMN} 310.1.3.34.1.17
lcsStatusWlanScanResultsEntry108mbpsMode OBJECT-TYPE
    SYNTAX     INTEGER
      {
        eNo (0),
        eYes (1)
      }
    MAX-ACCESS read-only
    STATUS     current
    DESCRIPTION
        "-- empty --"
    ::= { lcsStatusWlanScanResultsEntry 17 }

-- {COLUMN} 310.1.3.34.1.28
lcsStatusWlanScanResultsEntryExtChannel OBJECT-TYPE
    SYNTAX     INTEGER
      {
        eNone (0),
        eAbove (1),
        eBelow (3)
      }
    MAX-ACCESS read-only
    STATUS     current
    DESCRIPTION
        "-- empty --"
    ::= { lcsStatusWlanScanResultsEntry 28 }

-- {COLUMN} 310.1.3.34.1.10
lcsStatusWlanScanResultsEntryPhySignal OBJECT-TYPE
    SYNTAX     INTEGER (0..65535)
    MAX-ACCESS read-only
    STATUS     current
    DESCRIPTION
        "-- empty --"
    ::= { lcsStatusWlanScanResultsEntry 10 }

-- {COLUMN} 310.1.3.34.1.26
lcsStatusWlanScanResultsEntrySignalLevel OBJECT-TYPE
    SYNTAX     INTEGER (-32768..32767)
    MAX-ACCESS read-only
    STATUS     current
    DESCRIPTION
        "-- empty --"
    ::= { lcsStatusWlanScanResultsEntry 26 }

-- {COLUMN} 310.1.3.34.1.11
lcsStatusWlanScanResultsEntryNoiseLevel OBJECT-TYPE
    SYNTAX     INTEGER (-128..127)
    MAX-ACCESS read-only
    STATUS     current
    DESCRIPTION
        "-- empty --"
    ::= { lcsStatusWlanScanResultsEntry 11 }

-- {COLUMN} 310.1.3.34.1.12
lcsStatusWlanScanResultsEntryLoad OBJECT-TYPE
    SYNTAX     DisplayString (SIZE(0..255))
    MAX-ACCESS read-only
    STATUS     current
    DESCRIPTION
        "-- empty --"
    ::= { lcsStatusWlanScanResultsEntry 12 }

-- {COLUMN} 310.1.3.34.1.14
lcsStatusWlanScanResultsEntryShortPreamble OBJECT-TYPE
    SYNTAX     INTEGER
      {
        eNo (0),
        eYes (1)
      }
    MAX-ACCESS read-only
    STATUS     current
    DESCRIPTION
        "-- empty --"
    ::= { lcsStatusWlanScanResultsEntry 14 }

-- {COLUMN} 310.1.3.34.1.18
lcsStatusWlanScanResultsEntryShortSlotTime OBJECT-TYPE
    SYNTAX     INTEGER
      {
        eNo (0),
        eYes (1)
      }
    MAX-ACCESS read-only
    STATUS     current
    DESCRIPTION
        "-- empty --"
    ::= { lcsStatusWlanScanResultsEntry 18 }

-- {COLUMN} 310.1.3.34.1.29
lcsStatusWlanScanResultsEntry40mhzMode OBJECT-TYPE
    SYNTAX     INTEGER
      {
        eNo (0),
        eYes (1)
      }
    MAX-ACCESS read-only
    STATUS     current
    DESCRIPTION
        "-- empty --"
    ::= { lcsStatusWlanScanResultsEntry 29 }

-- {COLUMN} 310.1.3.34.1.36
lcsStatusWlanScanResultsEntry40mhzCoexistence OBJECT-TYPE
    SYNTAX     INTEGER
      {
        eNo (0),
        eYes (1)
      }
    MAX-ACCESS read-only
    STATUS     current
    DESCRIPTION
        "-- empty --"
    ::= { lcsStatusWlanScanResultsEntry 36 }

-- {COLUMN} 310.1.3.34.1.30
lcsStatusWlanScanResultsEntry40mhzIntolerant OBJECT-TYPE
    SYNTAX     INTEGER
      {
        eNo (0),
        eYes (1)
      }
    MAX-ACCESS read-only
    STATUS     current
    DESCRIPTION
        "-- empty --"
    ::= { lcsStatusWlanScanResultsEntry 30 }

-- {COLUMN} 310.1.3.34.1.27
lcsStatusWlanScanResultsEntryShortGuardInterval OBJECT-TYPE
    SYNTAX     INTEGER
      {
        eNo (0),
        e20mhz (1),
        e40mhz (2),
        e2040mhz (3)
      }
    MAX-ACCESS read-only
    STATUS     current
    DESCRIPTION
        "-- empty --"
    ::= { lcsStatusWlanScanResultsEntry 27 }

-- {COLUMN} 310.1.3.34.1.38
lcsStatusWlanScanResultsEntryTxStbc OBJECT-TYPE
    SYNTAX     INTEGER
      {
        eNo (0),
        eYes (1)
      }
    MAX-ACCESS read-only
    STATUS     current
    DESCRIPTION
        "-- empty --"
    ::= { lcsStatusWlanScanResultsEntry 38 }

-- {COLUMN} 310.1.3.34.1.39
lcsStatusWlanScanResultsEntryRxStbc OBJECT-TYPE
    SYNTAX     INTEGER
      {
        eNone (0),
        eOne (1),
        eTwo (2),
        eThree (3)
      }
    MAX-ACCESS read-only
    STATUS     current
    DESCRIPTION
        "-- empty --"
    ::= { lcsStatusWlanScanResultsEntry 39 }

-- {COLUMN} 310.1.3.34.1.41
lcsStatusWlanScanResultsEntryLdpc OBJECT-TYPE
    SYNTAX     INTEGER
      {
        eNo (0),
        eYes (1)
      }
    MAX-ACCESS read-only
    STATUS     current
    DESCRIPTION
        "-- empty --"
    ::= { lcsStatusWlanScanResultsEntry 41 }

-- {COLUMN} 310.1.3.34.1.21
lcsStatusWlanScanResultsEntryCompression OBJECT-TYPE
    SYNTAX     INTEGER
      {
        eNo (0),
        eYes (1)
      }
    MAX-ACCESS read-only
    STATUS     current
    DESCRIPTION
        "-- empty --"
    ::= { lcsStatusWlanScanResultsEntry 21 }

-- {COLUMN} 310.1.3.34.1.25
lcsStatusWlanScanResultsEntryAge OBJECT-TYPE
    SYNTAX     INTEGER (0..2147483647)
    MAX-ACCESS read-only
    STATUS     current
    DESCRIPTION
        "-- empty --"
    ::= { lcsStatusWlanScanResultsEntry 25 }

-- {COLUMN} 310.1.3.34.1.19
lcsStatusWlanScanResultsEntryRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (12), -- 6Mbit/s
        e9M (13), -- 9Mbit/s
        e12M (14), -- 12Mbit/s
        e18M (15), -- 18Mbit/s
        e24M (16), -- 24Mbit/s
        e36M (17), -- 36Mbit/s
        e48M (18), -- 48Mbit/s
        e54M (19), -- 54Mbit/s
        eT12M (20), -- Turbo 12Mbit/s
        eT18M (21), -- Turbo 18Mbit/s
        eT24M (22), -- Turbo 24Mbit/s
        eT36M (23), -- Turbo 36Mbit/s
        eT48M (24), -- Turbo 48Mbit/s
        eT72M (25), -- Turbo 72Mbit/s
        eT96M (26), -- Turbo 96Mbit/s
        eT108M (27), -- Turbo 108Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51), -- High throughput 3 streams 195Mbit/s
        eHTDUP6M (60) -- High throughput duplicate 6Mbit/s
      }
    MAX-ACCESS read-only
    STATUS     current
    DESCRIPTION
        "-- empty --"
    ::= { lcsStatusWlanScanResultsEntry 19 }

-- {COLUMN} 310.1.3.34.1.35
lcsStatusWlanScanResultsEntryEffRate OBJECT-TYPE
    SYNTAX     INTEGER (0..2147483647)
    MAX-ACCESS read-only
    STATUS     current
    DESCRIPTION
        "-- empty --"
    ::= { lcsStatusWlanScanResultsEntry 35 }

-- {COLUMN} 310.1.3.34.1.20
lcsStatusWlanScanResultsEntryNonerpPresent OBJECT-TYPE
    SYNTAX     INTEGER
      {
        eNo (0),
        eYes (1)
      }
    MAX-ACCESS read-only
    STATUS     current
    DESCRIPTION
        "-- empty --"
    ::= { lcsStatusWlanScanResultsEntry 20 }

-- {COLUMN} 310.1.3.34.1.23
lcsStatusWlanScanResultsEntryIdentification OBJECT-TYPE
    SYNTAX     DisplayString (SIZE(0..16))
    MAX-ACCESS read-only
    STATUS     current
    DESCRIPTION
        "-- empty --"
    ::= { lcsStatusWlanScanResultsEntry 23 }

-- {COLUMN} 310.1.3.34.1.31
lcsStatusWlanScanResultsEntryInterpointPeerName OBJECT-TYPE
    SYNTAX     DisplayString (SIZE(0..16))
    MAX-ACCESS read-only
    STATUS     current
    DESCRIPTION
        "-- empty --"
    ::= { lcsStatusWlanScanResultsEntry 31 }

-- {COLUMN} 310.1.3.34.1.40
lcsStatusWlanScanResultsEntryEapolPreauthFailed OBJECT-TYPE
    SYNTAX     INTEGER
      {
        eNo (0),
        eYes (1)
      }
    MAX-ACCESS read-only
    STATUS     current
    DESCRIPTION
        "-- empty --"
    ::= { lcsStatusWlanScanResultsEntry 40 }

-- {OID} 310.1.3.36
lcsStatusWlanInterpoints OBJECT IDENTIFIER ::= { lcsStatusWlan 36 }

-- {TABLE} 310.1.3.36.1
lcsStatusWlanInterpointsAccesspointListTable OBJECT-TYPE
    SYNTAX     SEQUENCE OF LcsStatusWlanInterpointsAccesspointListEntry
    MAX-ACCESS not-accessible
    STATUS     current
    DESCRIPTION
        "-- empty --"
    ::= { lcsStatusWlanInterpoints 1 }

-- {ENTRY} 310.1.3.36.1.1
lcsStatusWlanInterpointsAccesspointListEntry OBJECT-TYPE
    SYNTAX     LcsStatusWlanInterpointsAccesspointListEntry
    MAX-ACCESS not-accessible
    STATUS     current
    DESCRIPTION
        ""
    INDEX {
        lcsStatusWlanInterpointsAccesspointListEntryIndex
    }
    ::= { lcsStatusWlanInterpointsAccesspointListTable 1 }

-- {SEQUENCE}
LcsStatusWlanInterpointsAccesspointListEntry ::= SEQUENCE {
    lcsStatusWlanInterpointsAccesspointListEntryIndex INTEGER,
    lcsStatusWlanInterpointsAccesspointListEntryMacAddress MacAddress,
    lcsStatusWlanInterpointsAccesspointListEntryLinkActive INTEGER,
    lcsStatusWlanInterpointsAccesspointListEntryRxPhySignal INTEGER,
    lcsStatusWlanInterpointsAccesspointListEntryTxRate INTEGER,
    lcsStatusWlanInterpointsAccesspointListEntryRxRate INTEGER,
    lcsStatusWlanInterpointsAccesspointListEntryEffTxRate INTEGER,
    lcsStatusWlanInterpointsAccesspointListEntryEffRxRate INTEGER,
    lcsStatusWlanInterpointsAccesspointListEntryLinkPhySignal INTEGER,
    lcsStatusWlanInterpointsAccesspointListEntryIdentification DisplayString,
    lcsStatusWlanInterpointsAccesspointListEntryInterpointPeerName DisplayString,
    lcsStatusWlanInterpointsAccesspointListEntryQos INTEGER,
    lcsStatusWlanInterpointsAccesspointListEntry40mhzMode INTEGER,
    lcsStatusWlanInterpointsAccesspointListEntryMaxAMsduLen INTEGER,
    lcsStatusWlanInterpointsAccesspointListEntryMaxAMpduLen INTEGER,
    lcsStatusWlanInterpointsAccesspointListEntryShortPreamble INTEGER,
    lcsStatusWlanInterpointsAccesspointListEntryShortGuardInterval INTEGER,
    lcsStatusWlanInterpointsAccesspointListEntryKeyHandshakeRole INTEGER,
    lcsStatusWlanInterpointsAccesspointListEntryKeyingState INTEGER,
    lcsStatusWlanInterpointsAccesspointListEntryWpaVersion INTEGER,
    lcsStatusWlanInterpointsAccesspointListEntryKeyType INTEGER,
    lcsStatusWlanInterpointsAccesspointListEntryTxBytes Counter64,
    lcsStatusWlanInterpointsAccesspointListEntryRxBytes Counter64,
    lcsStatusWlanInterpointsAccesspointListEntryThroughput DisplayString,
    lcsStatusWlanInterpointsAccesspointListEntryMaxThroughput DisplayString,
    lcsStatusWlanInterpointsAccesspointListEntryBytesThroughput INTEGER,
    lcsStatusWlanInterpointsAccesspointListEntryBytesMaxThroughput INTEGER,
    lcsStatusWlanInterpointsAccesspointListEntryTxPackets INTEGER,
    lcsStatusWlanInterpointsAccesspointListEntryTxErrors INTEGER,
    lcsStatusWlanInterpointsAccesspointListEntryTotalRetries INTEGER,
    lcsStatusWlanInterpointsAccesspointListEntryRxPackets INTEGER,
    lcsStatusWlanInterpointsAccesspointListEntryTxLimit INTEGER,
    lcsStatusWlanInterpointsAccesspointListEntryRxLimit INTEGER,
    lcsStatusWlanInterpointsAccesspointListEntryAlarmState BITS
}

-- {COLUMN} 310.1.3.36.1.1.1
lcsStatusWlanInterpointsAccesspointListEntryIndex OBJECT-TYPE
    SYNTAX     INTEGER
      {
        eP2p11 (1),
        eP2p12 (2),
        eP2p13 (3),
        eP2p14 (4),
        eP2p15 (5),
        eP2p16 (6),
        eP2p17 (32),
        eP2p18 (33),
        eP2p19 (34),
        eP2p110 (35),
        eP2p111 (36),
        eP2p112 (37),
        eP2p113 (38),
        eP2p114 (39),
        eP2p115 (40),
        eP2p116 (41)
      }
    MAX-ACCESS read-only
    STATUS     current
    DESCRIPTION
        "-- empty --"
    ::= { lcsStatusWlanInterpointsAccesspointListEntry 1 }

-- {COLUMN} 310.1.3.36.1.1.2
lcsStatusWlanInterpointsAccesspointListEntryMacAddress OBJECT-TYPE
    SYNTAX     MacAddress
    MAX-ACCESS read-only
    STATUS     current
    DESCRIPTION
        "-- empty --"
    ::= { lcsStatusWlanInterpointsAccesspointListEntry 2 }

-- {COLUMN} 310.1.3.36.1.1.40
lcsStatusWlanInterpointsAccesspointListEntryLinkActive OBJECT-TYPE
    SYNTAX     INTEGER
      {
        eNo (0),
        eYes (1)
      }
    MAX-ACCESS read-only
    STATUS     current
    DESCRIPTION
        "-- empty --"
    ::= { lcsStatusWlanInterpointsAccesspointListEntry 40 }

-- {COLUMN} 310.1.3.36.1.1.13
lcsStatusWlanInterpointsAccesspointListEntryRxPhySignal OBJECT-TYPE
    SYNTAX     INTEGER (0..65535)
    MAX-ACCESS read-only
    STATUS     current
    DESCRIPTION
        "-- empty --"
    ::= { lcsStatusWlanInterpointsAccesspointListEntry 13 }

-- {COLUMN} 310.1.3.36.1.1.16
lcsStatusWlanInterpointsAccesspointListEntryTxRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanInterpointsAccesspointListEntry 16 }

-- {COLUMN} 310.1.3.36.1.1.5
lcsStatusWlanInterpointsAccesspointListEntryRxRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanInterpointsAccesspointListEntry 5 }

-- {COLUMN} 310.1.3.36.1.1.34
lcsStatusWlanInterpointsAccesspointListEntryEffTxRate OBJECT-TYPE
    SYNTAX     INTEGER (0..2147483647)
    MAX-ACCESS read-only
    STATUS     current
    DESCRIPTION
        "-- empty --"
    ::= { lcsStatusWlanInterpointsAccesspointListEntry 34 }

-- {COLUMN} 310.1.3.36.1.1.35
lcsStatusWlanInterpointsAccesspointListEntryEffRxRate OBJECT-TYPE
    SYNTAX     INTEGER (0..2147483647)
    MAX-ACCESS read-only
    STATUS     current
    DESCRIPTION
        "-- empty --"
    ::= { lcsStatusWlanInterpointsAccesspointListEntry 35 }

-- {COLUMN} 310.1.3.36.1.1.14
lcsStatusWlanInterpointsAccesspointListEntryLinkPhySignal OBJECT-TYPE
    SYNTAX     INTEGER (0..65535)
    MAX-ACCESS read-only
    STATUS     current
    DESCRIPTION
        "-- empty --"
    ::= { lcsStatusWlanInterpointsAccesspointListEntry 14 }

-- {COLUMN} 310.1.3.36.1.1.15
lcsStatusWlanInterpointsAccesspointListEntryIdentification OBJECT-TYPE
    SYNTAX     DisplayString (SIZE(0..24))
    MAX-ACCESS read-only
    STATUS     current
    DESCRIPTION
        "-- empty --"
    ::= { lcsStatusWlanInterpointsAccesspointListEntry 15 }

-- {COLUMN} 310.1.3.36.1.1.28
lcsStatusWlanInterpointsAccesspointListEntryInterpointPeerName OBJECT-TYPE
    SYNTAX     DisplayString (SIZE(0..16))
    MAX-ACCESS read-only
    STATUS     current
    DESCRIPTION
        "-- empty --"
    ::= { lcsStatusWlanInterpointsAccesspointListEntry 28 }

-- {COLUMN} 310.1.3.36.1.1.27
lcsStatusWlanInterpointsAccesspointListEntryQos OBJECT-TYPE
    SYNTAX     INTEGER
      {
        eNo (0),
        eYes (1)
      }
    MAX-ACCESS read-only
    STATUS     current
    DESCRIPTION
        "-- empty --"
    ::= { lcsStatusWlanInterpointsAccesspointListEntry 27 }

-- {COLUMN} 310.1.3.36.1.1.31
lcsStatusWlanInterpointsAccesspointListEntry40mhzMode OBJECT-TYPE
    SYNTAX     INTEGER
      {
        eNo (0),
        eYes (1)
      }
    MAX-ACCESS read-only
    STATUS     current
    DESCRIPTION
        "-- empty --"
    ::= { lcsStatusWlanInterpointsAccesspointListEntry 31 }

-- {COLUMN} 310.1.3.36.1.1.29
lcsStatusWlanInterpointsAccesspointListEntryMaxAMsduLen OBJECT-TYPE
    SYNTAX     INTEGER (0..2147483647)
    MAX-ACCESS read-only
    STATUS     current
    DESCRIPTION
        "-- empty --"
    ::= { lcsStatusWlanInterpointsAccesspointListEntry 29 }

-- {COLUMN} 310.1.3.36.1.1.30
lcsStatusWlanInterpointsAccesspointListEntryMaxAMpduLen OBJECT-TYPE
    SYNTAX     INTEGER (0..2147483647)
    MAX-ACCESS read-only
    STATUS     current
    DESCRIPTION
        "-- empty --"
    ::= { lcsStatusWlanInterpointsAccesspointListEntry 30 }

-- {COLUMN} 310.1.3.36.1.1.32
lcsStatusWlanInterpointsAccesspointListEntryShortPreamble OBJECT-TYPE
    SYNTAX     INTEGER
      {
        eNo (0),
        eYes (1)
      }
    MAX-ACCESS read-only
    STATUS     current
    DESCRIPTION
        "-- empty --"
    ::= { lcsStatusWlanInterpointsAccesspointListEntry 32 }

-- {COLUMN} 310.1.3.36.1.1.33
lcsStatusWlanInterpointsAccesspointListEntryShortGuardInterval OBJECT-TYPE
    SYNTAX     INTEGER
      {
        eNo (0),
        e20mhz (1),
        e40mhz (2),
        e2040mhz (3)
      }
    MAX-ACCESS read-only
    STATUS     current
    DESCRIPTION
        "-- empty --"
    ::= { lcsStatusWlanInterpointsAccesspointListEntry 33 }

-- {COLUMN} 310.1.3.36.1.1.24
lcsStatusWlanInterpointsAccesspointListEntryKeyHandshakeRole OBJECT-TYPE
    SYNTAX     INTEGER
      {
        eNone (0),
        eSupplicant (1),
        eAuthenticator (2)
      }
    MAX-ACCESS read-only
    STATUS     current
    DESCRIPTION
        "-- empty --"
    ::= { lcsStatusWlanInterpointsAccesspointListEntry 24 }

-- {COLUMN} 310.1.3.36.1.1.12
lcsStatusWlanInterpointsAccesspointListEntryKeyingState OBJECT-TYPE
    SYNTAX     INTEGER
      {
        eIdle (0),
        ePending (1),
        eDone (2)
      }
    MAX-ACCESS read-only
    STATUS     current
    DESCRIPTION
        "-- empty --"
    ::= { lcsStatusWlanInterpointsAccesspointListEntry 12 }

-- {COLUMN} 310.1.3.36.1.1.21
lcsStatusWlanInterpointsAccesspointListEntryWpaVersion OBJECT-TYPE
    SYNTAX     INTEGER
      {
        eWpa1 (1),
        eWpa2 (2),
        eNone (0)
      }
    MAX-ACCESS read-only
    STATUS     current
    DESCRIPTION
        "-- empty --"
    ::= { lcsStatusWlanInterpointsAccesspointListEntry 21 }

-- {COLUMN} 310.1.3.36.1.1.36
lcsStatusWlanInterpointsAccesspointListEntryKeyType OBJECT-TYPE
    SYNTAX     INTEGER
      {
        eNone (0),
        eUnknown (1),
        eWep40Bits (5),
        eWep104Bits (13),
        eWep128Bits (16),
        eTkip (64),
        eAesOcb (65),
        eAesCcm (66)
      }
    MAX-ACCESS read-only
    STATUS     current
    DESCRIPTION
        "-- empty --"
    ::= { lcsStatusWlanInterpointsAccesspointListEntry 36 }

-- {COLUMN} 310.1.3.36.1.1.6
lcsStatusWlanInterpointsAccesspointListEntryTxBytes OBJECT-TYPE
    SYNTAX     Counter64
    MAX-ACCESS read-only
    STATUS     current
    DESCRIPTION
        "-- empty --"
    ::= { lcsStatusWlanInterpointsAccesspointListEntry 6 }

-- {COLUMN} 310.1.3.36.1.1.7
lcsStatusWlanInterpointsAccesspointListEntryRxBytes OBJECT-TYPE
    SYNTAX     Counter64
    MAX-ACCESS read-only
    STATUS     current
    DESCRIPTION
        "-- empty --"
    ::= { lcsStatusWlanInterpointsAccesspointListEntry 7 }

-- {COLUMN} 310.1.3.36.1.1.8
lcsStatusWlanInterpointsAccesspointListEntryThroughput OBJECT-TYPE
    SYNTAX     DisplayString (SIZE(0..255))
    MAX-ACCESS read-only
    STATUS     current
    DESCRIPTION
        "-- empty --"
    ::= { lcsStatusWlanInterpointsAccesspointListEntry 8 }

-- {COLUMN} 310.1.3.36.1.1.17
lcsStatusWlanInterpointsAccesspointListEntryMaxThroughput OBJECT-TYPE
    SYNTAX     DisplayString (SIZE(0..255))
    MAX-ACCESS read-only
    STATUS     current
    DESCRIPTION
        "-- empty --"
    ::= { lcsStatusWlanInterpointsAccesspointListEntry 17 }

-- {COLUMN} 310.1.3.36.1.1.19
lcsStatusWlanInterpointsAccesspointListEntryBytesThroughput OBJECT-TYPE
    SYNTAX     INTEGER (0..2147483647)
    MAX-ACCESS read-only
    STATUS     current
    DESCRIPTION
        "-- empty --"
    ::= { lcsStatusWlanInterpointsAccesspointListEntry 19 }

-- {COLUMN} 310.1.3.36.1.1.20
lcsStatusWlanInterpointsAccesspointListEntryBytesMaxThroughput OBJECT-TYPE
    SYNTAX     INTEGER (0..2147483647)
    MAX-ACCESS read-only
    STATUS     current
    DESCRIPTION
        "-- empty --"
    ::= { lcsStatusWlanInterpointsAccesspointListEntry 20 }

-- {COLUMN} 310.1.3.36.1.1.25
lcsStatusWlanInterpointsAccesspointListEntryTxPackets OBJECT-TYPE
    SYNTAX     INTEGER (0..2147483647)
    MAX-ACCESS read-only
    STATUS     current
    DESCRIPTION
        "-- empty --"
    ::= { lcsStatusWlanInterpointsAccesspointListEntry 25 }

-- {COLUMN} 310.1.3.36.1.1.37
lcsStatusWlanInterpointsAccesspointListEntryTxErrors OBJECT-TYPE
    SYNTAX     INTEGER (0..2147483647)
    MAX-ACCESS read-only
    STATUS     current
    DESCRIPTION
        "-- empty --"
    ::= { lcsStatusWlanInterpointsAccesspointListEntry 37 }

-- {COLUMN} 310.1.3.36.1.1.38
lcsStatusWlanInterpointsAccesspointListEntryTotalRetries OBJECT-TYPE
    SYNTAX     INTEGER (0..2147483647)
    MAX-ACCESS read-only
    STATUS     current
    DESCRIPTION
        "-- empty --"
    ::= { lcsStatusWlanInterpointsAccesspointListEntry 38 }

-- {COLUMN} 310.1.3.36.1.1.26
lcsStatusWlanInterpointsAccesspointListEntryRxPackets OBJECT-TYPE
    SYNTAX     INTEGER (0..2147483647)
    MAX-ACCESS read-only
    STATUS     current
    DESCRIPTION
        "-- empty --"
    ::= { lcsStatusWlanInterpointsAccesspointListEntry 26 }

-- {COLUMN} 310.1.3.36.1.1.22
lcsStatusWlanInterpointsAccesspointListEntryTxLimit OBJECT-TYPE
    SYNTAX     INTEGER (0..2147483647)
    MAX-ACCESS read-only
    STATUS     current
    DESCRIPTION
        "-- empty --"
    ::= { lcsStatusWlanInterpointsAccesspointListEntry 22 }

-- {COLUMN} 310.1.3.36.1.1.23
lcsStatusWlanInterpointsAccesspointListEntryRxLimit OBJECT-TYPE
    SYNTAX     INTEGER (0..2147483647)
    MAX-ACCESS read-only
    STATUS     current
    DESCRIPTION
        "-- empty --"
    ::= { lcsStatusWlanInterpointsAccesspointListEntry 23 }

-- {COLUMN} 310.1.3.36.1.1.39
lcsStatusWlanInterpointsAccesspointListEntryAlarmState OBJECT-TYPE
    SYNTAX     BITS
      {
        ePhySignal (31),
        eTotalRetries (30),
        eTxErrors (29),
        eNo (0)
      }
    MAX-ACCESS read-only
    STATUS     current
    DESCRIPTION
        "-- empty --"
    ::= { lcsStatusWlanInterpointsAccesspointListEntry 39 }

-- {TABLE} 310.1.3.36.3
lcsStatusWlanInterpointsKeyListTable OBJECT-TYPE
    SYNTAX     SEQUENCE OF LcsStatusWlanInterpointsKeyListEntry
    MAX-ACCESS not-accessible
    STATUS     current
    DESCRIPTION
        "-- empty --"
    ::= { lcsStatusWlanInterpoints 3 }

-- {ENTRY} 310.1.3.36.3.1
lcsStatusWlanInterpointsKeyListEntry OBJECT-TYPE
    SYNTAX     LcsStatusWlanInterpointsKeyListEntry
    MAX-ACCESS not-accessible
    STATUS     current
    DESCRIPTION
        ""
    INDEX {
        lcsStatusWlanInterpointsKeyListEntryIndex
    }
    ::= { lcsStatusWlanInterpointsKeyListTable 1 }

-- {SEQUENCE}
LcsStatusWlanInterpointsKeyListEntry ::= SEQUENCE {
    lcsStatusWlanInterpointsKeyListEntryIndex INTEGER,
    lcsStatusWlanInterpointsKeyListEntrySource INTEGER,
    lcsStatusWlanInterpointsKeyListEntryAge INTEGER,
    lcsStatusWlanInterpointsKeyListEntryKeyType INTEGER,
    lcsStatusWlanInterpointsKeyListEntryKeyValue DisplayString,
    lcsStatusWlanInterpointsKeyListEntryTsc DisplayString,
    lcsStatusWlanInterpointsKeyListEntryRscBe DisplayString,
    lcsStatusWlanInterpointsKeyListEntryRscBk DisplayString,
    lcsStatusWlanInterpointsKeyListEntryRscEe DisplayString,
    lcsStatusWlanInterpointsKeyListEntryRscCl DisplayString,
    lcsStatusWlanInterpointsKeyListEntryRscVi DisplayString,
    lcsStatusWlanInterpointsKeyListEntryRscVo DisplayString,
    lcsStatusWlanInterpointsKeyListEntryRscNc DisplayString,
    lcsStatusWlanInterpointsKeyListEntryIvSequenceErrors INTEGER
}

-- {COLUMN} 310.1.3.36.3.1.1
lcsStatusWlanInterpointsKeyListEntryIndex OBJECT-TYPE
    SYNTAX     INTEGER
      {
        eP2p11 (1),
        eP2p12 (2),
        eP2p13 (3),
        eP2p14 (4),
        eP2p15 (5),
        eP2p16 (6),
        eP2p17 (32),
        eP2p18 (33),
        eP2p19 (34),
        eP2p110 (35),
        eP2p111 (36),
        eP2p112 (37),
        eP2p113 (38),
        eP2p114 (39),
        eP2p115 (40),
        eP2p116 (41)
      }
    MAX-ACCESS read-only
    STATUS     current
    DESCRIPTION
        "-- empty --"
    ::= { lcsStatusWlanInterpointsKeyListEntry 1 }

-- {COLUMN} 310.1.3.36.3.1.2
lcsStatusWlanInterpointsKeyListEntrySource OBJECT-TYPE
    SYNTAX     INTEGER
      {
        eNone (0),
        eStatic (1),
        eDynamic (2)
      }
    MAX-ACCESS read-only
    STATUS     current
    DESCRIPTION
        "-- empty --"
    ::= { lcsStatusWlanInterpointsKeyListEntry 2 }

-- {COLUMN} 310.1.3.36.3.1.7
lcsStatusWlanInterpointsKeyListEntryAge OBJECT-TYPE
    SYNTAX     INTEGER (0..2147483647)
    MAX-ACCESS read-only
    STATUS     current
    DESCRIPTION
        "-- empty --"
    ::= { lcsStatusWlanInterpointsKeyListEntry 7 }

-- {COLUMN} 310.1.3.36.3.1.3
lcsStatusWlanInterpointsKeyListEntryKeyType OBJECT-TYPE
    SYNTAX     INTEGER
      {
        eNone (0),
        eUnknown (1),
        eWep40Bits (5),
        eWep104Bits (13),
        eWep128Bits (16),
        eTkip (64),
        eAesOcb (65),
        eAesCcm (66)
      }
    MAX-ACCESS read-only
    STATUS     current
    DESCRIPTION
        "-- empty --"
    ::= { lcsStatusWlanInterpointsKeyListEntry 3 }

-- {COLUMN} 310.1.3.36.3.1.4
lcsStatusWlanInterpointsKeyListEntryKeyValue OBJECT-TYPE
    SYNTAX     DisplayString (SIZE(0..255))
    MAX-ACCESS read-only
    STATUS     current
    DESCRIPTION
        "-- empty --"
    ::= { lcsStatusWlanInterpointsKeyListEntry 4 }

-- {COLUMN} 310.1.3.36.3.1.5
lcsStatusWlanInterpointsKeyListEntryTsc OBJECT-TYPE
    SYNTAX     DisplayString (SIZE(0..255))
    MAX-ACCESS read-only
    STATUS     current
    DESCRIPTION
        "-- empty --"
    ::= { lcsStatusWlanInterpointsKeyListEntry 5 }

-- {COLUMN} 310.1.3.36.3.1.16
lcsStatusWlanInterpointsKeyListEntryRscBe OBJECT-TYPE
    SYNTAX     DisplayString (SIZE(0..255))
    MAX-ACCESS read-only
    STATUS     current
    DESCRIPTION
        "-- empty --"
    ::= { lcsStatusWlanInterpointsKeyListEntry 16 }

-- {COLUMN} 310.1.3.36.3.1.17
lcsStatusWlanInterpointsKeyListEntryRscBk OBJECT-TYPE
    SYNTAX     DisplayString (SIZE(0..255))
    MAX-ACCESS read-only
    STATUS     current
    DESCRIPTION
        "-- empty --"
    ::= { lcsStatusWlanInterpointsKeyListEntry 17 }

-- {COLUMN} 310.1.3.36.3.1.19
lcsStatusWlanInterpointsKeyListEntryRscEe OBJECT-TYPE
    SYNTAX     DisplayString (SIZE(0..255))
    MAX-ACCESS read-only
    STATUS     current
    DESCRIPTION
        "-- empty --"
    ::= { lcsStatusWlanInterpointsKeyListEntry 19 }

-- {COLUMN} 310.1.3.36.3.1.20
lcsStatusWlanInterpointsKeyListEntryRscCl OBJECT-TYPE
    SYNTAX     DisplayString (SIZE(0..255))
    MAX-ACCESS read-only
    STATUS     current
    DESCRIPTION
        "-- empty --"
    ::= { lcsStatusWlanInterpointsKeyListEntry 20 }

-- {COLUMN} 310.1.3.36.3.1.21
lcsStatusWlanInterpointsKeyListEntryRscVi OBJECT-TYPE
    SYNTAX     DisplayString (SIZE(0..255))
    MAX-ACCESS read-only
    STATUS     current
    DESCRIPTION
        "-- empty --"
    ::= { lcsStatusWlanInterpointsKeyListEntry 21 }

-- {COLUMN} 310.1.3.36.3.1.22
lcsStatusWlanInterpointsKeyListEntryRscVo OBJECT-TYPE
    SYNTAX     DisplayString (SIZE(0..255))
    MAX-ACCESS read-only
    STATUS     current
    DESCRIPTION
        "-- empty --"
    ::= { lcsStatusWlanInterpointsKeyListEntry 22 }

-- {COLUMN} 310.1.3.36.3.1.23
lcsStatusWlanInterpointsKeyListEntryRscNc OBJECT-TYPE
    SYNTAX     DisplayString (SIZE(0..255))
    MAX-ACCESS read-only
    STATUS     current
    DESCRIPTION
        "-- empty --"
    ::= { lcsStatusWlanInterpointsKeyListEntry 23 }

-- {COLUMN} 310.1.3.36.3.1.8
lcsStatusWlanInterpointsKeyListEntryIvSequenceErrors OBJECT-TYPE
    SYNTAX     INTEGER (0..2147483647)
    MAX-ACCESS read-only
    STATUS     current
    DESCRIPTION
        "-- empty --"
    ::= { lcsStatusWlanInterpointsKeyListEntry 8 }

-- {TABLE} 310.1.3.41
lcsStatusWlanGroupEncryptionKeysTable OBJECT-TYPE
    SYNTAX     SEQUENCE OF LcsStatusWlanGroupEncryptionKeysEntry
    MAX-ACCESS not-accessible
    STATUS     current
    DESCRIPTION
        "-- empty --"
    ::= { lcsStatusWlan 41 }

-- {ENTRY} 310.1.3.41.1
lcsStatusWlanGroupEncryptionKeysEntry OBJECT-TYPE
    SYNTAX     LcsStatusWlanGroupEncryptionKeysEntry
    MAX-ACCESS not-accessible
    STATUS     current
    DESCRIPTION
        ""
    INDEX {
        lcsStatusWlanGroupEncryptionKeysEntryIndex
    }
    ::= { lcsStatusWlanGroupEncryptionKeysTable 1 }

-- {SEQUENCE}
LcsStatusWlanGroupEncryptionKeysEntry ::= SEQUENCE {
    lcsStatusWlanGroupEncryptionKeysEntryIndex DisplayString,
    lcsStatusWlanGroupEncryptionKeysEntrySource INTEGER,
    lcsStatusWlanGroupEncryptionKeysEntryAge INTEGER,
    lcsStatusWlanGroupEncryptionKeysEntryKeyType INTEGER,
    lcsStatusWlanGroupEncryptionKeysEntryKeyValue DisplayString,
    lcsStatusWlanGroupEncryptionKeysEntryTsc DisplayString,
    lcsStatusWlanGroupEncryptionKeysEntryRscBe DisplayString,
    lcsStatusWlanGroupEncryptionKeysEntryRscBk DisplayString,
    lcsStatusWlanGroupEncryptionKeysEntryRscEe DisplayString,
    lcsStatusWlanGroupEncryptionKeysEntryRscCl DisplayString,
    lcsStatusWlanGroupEncryptionKeysEntryRscVi DisplayString,
    lcsStatusWlanGroupEncryptionKeysEntryRscVo DisplayString,
    lcsStatusWlanGroupEncryptionKeysEntryRscNc DisplayString,
    lcsStatusWlanGroupEncryptionKeysEntryIvSequenceErrors INTEGER
}

-- {COLUMN} 310.1.3.41.1.1
lcsStatusWlanGroupEncryptionKeysEntryIndex OBJECT-TYPE
    SYNTAX     DisplayString (SIZE(0..255))
    MAX-ACCESS read-only
    STATUS     current
    DESCRIPTION
        "-- empty --"
    ::= { lcsStatusWlanGroupEncryptionKeysEntry 1 }

-- {COLUMN} 310.1.3.41.1.2
lcsStatusWlanGroupEncryptionKeysEntrySource OBJECT-TYPE
    SYNTAX     INTEGER
      {
        eNone (0),
        eStatic (1),
        eDynamic (2)
      }
    MAX-ACCESS read-only
    STATUS     current
    DESCRIPTION
        "-- empty --"
    ::= { lcsStatusWlanGroupEncryptionKeysEntry 2 }

-- {COLUMN} 310.1.3.41.1.7
lcsStatusWlanGroupEncryptionKeysEntryAge OBJECT-TYPE
    SYNTAX     INTEGER (0..2147483647)
    MAX-ACCESS read-only
    STATUS     current
    DESCRIPTION
        "-- empty --"
    ::= { lcsStatusWlanGroupEncryptionKeysEntry 7 }

-- {COLUMN} 310.1.3.41.1.3
lcsStatusWlanGroupEncryptionKeysEntryKeyType OBJECT-TYPE
    SYNTAX     INTEGER
      {
        eNone (0),
        eUnknown (1),
        eWep40Bits (5),
        eWep104Bits (13),
        eWep128Bits (16),
        eTkip (64),
        eAesOcb (65),
        eAesCcm (66)
      }
    MAX-ACCESS read-only
    STATUS     current
    DESCRIPTION
        "-- empty --"
    ::= { lcsStatusWlanGroupEncryptionKeysEntry 3 }

-- {COLUMN} 310.1.3.41.1.4
lcsStatusWlanGroupEncryptionKeysEntryKeyValue OBJECT-TYPE
    SYNTAX     DisplayString (SIZE(0..255))
    MAX-ACCESS read-only
    STATUS     current
    DESCRIPTION
        "-- empty --"
    ::= { lcsStatusWlanGroupEncryptionKeysEntry 4 }

-- {COLUMN} 310.1.3.41.1.5
lcsStatusWlanGroupEncryptionKeysEntryTsc OBJECT-TYPE
    SYNTAX     DisplayString (SIZE(0..255))
    MAX-ACCESS read-only
    STATUS     current
    DESCRIPTION
        "-- empty --"
    ::= { lcsStatusWlanGroupEncryptionKeysEntry 5 }

-- {COLUMN} 310.1.3.41.1.16
lcsStatusWlanGroupEncryptionKeysEntryRscBe OBJECT-TYPE
    SYNTAX     DisplayString (SIZE(0..255))
    MAX-ACCESS read-only
    STATUS     current
    DESCRIPTION
        "-- empty --"
    ::= { lcsStatusWlanGroupEncryptionKeysEntry 16 }

-- {COLUMN} 310.1.3.41.1.17
lcsStatusWlanGroupEncryptionKeysEntryRscBk OBJECT-TYPE
    SYNTAX     DisplayString (SIZE(0..255))
    MAX-ACCESS read-only
    STATUS     current
    DESCRIPTION
        "-- empty --"
    ::= { lcsStatusWlanGroupEncryptionKeysEntry 17 }

-- {COLUMN} 310.1.3.41.1.19
lcsStatusWlanGroupEncryptionKeysEntryRscEe OBJECT-TYPE
    SYNTAX     DisplayString (SIZE(0..255))
    MAX-ACCESS read-only
    STATUS     current
    DESCRIPTION
        "-- empty --"
    ::= { lcsStatusWlanGroupEncryptionKeysEntry 19 }

-- {COLUMN} 310.1.3.41.1.20
lcsStatusWlanGroupEncryptionKeysEntryRscCl OBJECT-TYPE
    SYNTAX     DisplayString (SIZE(0..255))
    MAX-ACCESS read-only
    STATUS     current
    DESCRIPTION
        "-- empty --"
    ::= { lcsStatusWlanGroupEncryptionKeysEntry 20 }

-- {COLUMN} 310.1.3.41.1.21
lcsStatusWlanGroupEncryptionKeysEntryRscVi OBJECT-TYPE
    SYNTAX     DisplayString (SIZE(0..255))
    MAX-ACCESS read-only
    STATUS     current
    DESCRIPTION
        "-- empty --"
    ::= { lcsStatusWlanGroupEncryptionKeysEntry 21 }

-- {COLUMN} 310.1.3.41.1.22
lcsStatusWlanGroupEncryptionKeysEntryRscVo OBJECT-TYPE
    SYNTAX     DisplayString (SIZE(0..255))
    MAX-ACCESS read-only
    STATUS     current
    DESCRIPTION
        "-- empty --"
    ::= { lcsStatusWlanGroupEncryptionKeysEntry 22 }

-- {COLUMN} 310.1.3.41.1.23
lcsStatusWlanGroupEncryptionKeysEntryRscNc OBJECT-TYPE
    SYNTAX     DisplayString (SIZE(0..255))
    MAX-ACCESS read-only
    STATUS     current
    DESCRIPTION
        "-- empty --"
    ::= { lcsStatusWlanGroupEncryptionKeysEntry 23 }

-- {COLUMN} 310.1.3.41.1.8
lcsStatusWlanGroupEncryptionKeysEntryIvSequenceErrors OBJECT-TYPE
    SYNTAX     INTEGER (0..2147483647)
    MAX-ACCESS read-only
    STATUS     current
    DESCRIPTION
        "-- empty --"
    ::= { lcsStatusWlanGroupEncryptionKeysEntry 8 }

-- {TABLE} 310.1.3.42
lcsStatusWlanChannelScanResultsTable OBJECT-TYPE
    SYNTAX     SEQUENCE OF LcsStatusWlanChannelScanResultsEntry
    MAX-ACCESS not-accessible
    STATUS     current
    DESCRIPTION
        "-- empty --"
    ::= { lcsStatusWlan 42 }

-- {ENTRY} 310.1.3.42.1
lcsStatusWlanChannelScanResultsEntry OBJECT-TYPE
    SYNTAX     LcsStatusWlanChannelScanResultsEntry
    MAX-ACCESS not-accessible
    STATUS     current
    DESCRIPTION
        ""
    INDEX {
        lcsStatusWlanChannelScanResultsEntryRadioBand,
        lcsStatusWlanChannelScanResultsEntryRadioChannel,
        lcsStatusWlanChannelScanResultsEntryInterface
    }
    ::= { lcsStatusWlanChannelScanResultsTable 1 }

-- {SEQUENCE}
LcsStatusWlanChannelScanResultsEntry ::= SEQUENCE {
    lcsStatusWlanChannelScanResultsEntryRadioBand INTEGER,
    lcsStatusWlanChannelScanResultsEntryRadioChannel INTEGER,
    lcsStatusWlanChannelScanResultsEntry108mbpsMode INTEGER,
    lcsStatusWlanChannelScanResultsEntryInterface INTEGER,
    lcsStatusWlanChannelScanResultsEntryDfsScheme INTEGER,
    lcsStatusWlanChannelScanResultsEntryDfsState INTEGER,
    lcsStatusWlanChannelScanResultsEntryRemTime INTEGER,
    lcsStatusWlanChannelScanResultsEntryScanned INTEGER,
    lcsStatusWlanChannelScanResultsEntryScanAge INTEGER,
    lcsStatusWlanChannelScanResultsEntryUsage BITS,
    lcsStatusWlanChannelScanResultsEntryNoiseLevel INTEGER,
    lcsStatusWlanChannelScanResultsEntryNumBss INTEGER,
    lcsStatusWlanChannelScanResultsEntryPulseCount INTEGER,
    lcsStatusWlanChannelScanResultsEntryRadarDetected INTEGER,
    lcsStatusWlanChannelScanResultsEntryRadarPattern DisplayString,
    lcsStatusWlanChannelScanResultsEntryNonHtBss INTEGER,
    lcsStatusWlanChannelScanResultsEntryNonHtBssAge INTEGER,
    lcsStatusWlanChannelScanResultsEntry40mIntolerantBss INTEGER,
    lcsStatusWlanChannelScanResultsEntry40mIntolerantBssAge INTEGER,
    lcsStatusWlanChannelScanResultsEntry40mIntolerantBssReported INTEGER,
    lcsStatusWlanChannelScanResultsEntry40mIntolerantBssReportedAge INTEGER
}

-- {COLUMN} 310.1.3.42.1.9
lcsStatusWlanChannelScanResultsEntryRadioBand OBJECT-TYPE
    SYNTAX     INTEGER
      {
        eUnknown (0),
        e24ghz (1),
        e5ghz (2)
      }
    MAX-ACCESS read-only
    STATUS     current
    DESCRIPTION
        "-- empty --"
    ::= { lcsStatusWlanChannelScanResultsEntry 9 }

-- {COLUMN} 310.1.3.42.1.1
lcsStatusWlanChannelScanResultsEntryRadioChannel OBJECT-TYPE
    SYNTAX     INTEGER (0..255)
    MAX-ACCESS read-only
    STATUS     current
    DESCRIPTION
        "-- empty --"
    ::= { lcsStatusWlanChannelScanResultsEntry 1 }

-- {COLUMN} 310.1.3.42.1.8
lcsStatusWlanChannelScanResultsEntry108mbpsMode OBJECT-TYPE
    SYNTAX     INTEGER
      {
        eNo (0),
        eYes (1)
      }
    MAX-ACCESS read-only
    STATUS     current
    DESCRIPTION
        "-- empty --"
    ::= { lcsStatusWlanChannelScanResultsEntry 8 }

-- {COLUMN} 310.1.3.42.1.2
lcsStatusWlanChannelScanResultsEntryInterface OBJECT-TYPE
    SYNTAX     INTEGER
      {
        eWlan1 (0),
        eWlan2 (1),
        eWlan3 (2),
        eWlan4 (3)
      }
    MAX-ACCESS read-only
    STATUS     current
    DESCRIPTION
        "-- empty --"
    ::= { lcsStatusWlanChannelScanResultsEntry 2 }

-- {COLUMN} 310.1.3.42.1.14
lcsStatusWlanChannelScanResultsEntryDfsScheme OBJECT-TYPE
    SYNTAX     INTEGER
      {
        eJapan (16),
        eFcc (8),
        eEn302502 (4),
        eEn301893V13 (2),
        eEn301893V12 (1),
        eEn301893V15 (32),
        eEn301893V16 (64),
        eNone (0)
      }
    MAX-ACCESS read-only
    STATUS     current
    DESCRIPTION
        "-- empty --"
    ::= { lcsStatusWlanChannelScanResultsEntry 14 }

-- {COLUMN} 310.1.3.42.1.12
lcsStatusWlanChannelScanResultsEntryDfsState OBJECT-TYPE
    SYNTAX     INTEGER
      {
        eUnknown (2),
        eClear (0),
        eBlocked (1)
      }
    MAX-ACCESS read-only
    STATUS     current
    DESCRIPTION
        "-- empty --"
    ::= { lcsStatusWlanChannelScanResultsEntry 12 }

-- {COLUMN} 310.1.3.42.1.11
lcsStatusWlanChannelScanResultsEntryRemTime OBJECT-TYPE
    SYNTAX     INTEGER (0..2147483647)
    MAX-ACCESS read-only
    STATUS     current
    DESCRIPTION
        "-- empty --"
    ::= { lcsStatusWlanChannelScanResultsEntry 11 }

-- {COLUMN} 310.1.3.42.1.3
lcsStatusWlanChannelScanResultsEntryScanned OBJECT-TYPE
    SYNTAX     INTEGER
      {
        eNo (0),
        eYes (1)
      }
    MAX-ACCESS read-only
    STATUS     current
    DESCRIPTION
        "-- empty --"
    ::= { lcsStatusWlanChannelScanResultsEntry 3 }

-- {COLUMN} 310.1.3.42.1.16
lcsStatusWlanChannelScanResultsEntryScanAge OBJECT-TYPE
    SYNTAX     INTEGER (0..2147483647)
    MAX-ACCESS read-only
    STATUS     current
    DESCRIPTION
        "-- empty --"
    ::= { lcsStatusWlanChannelScanResultsEntry 16 }

-- {COLUMN} 310.1.3.42.1.15
lcsStatusWlanChannelScanResultsEntryUsage OBJECT-TYPE
    SYNTAX     BITS
      {
        eOperation (31),
        eBackgroundScan (30),
        eOverlapScan (29),
        eNone (0)
      }
    MAX-ACCESS read-only
    STATUS     current
    DESCRIPTION
        "-- empty --"
    ::= { lcsStatusWlanChannelScanResultsEntry 15 }

-- {COLUMN} 310.1.3.42.1.4
lcsStatusWlanChannelScanResultsEntryNoiseLevel OBJECT-TYPE
    SYNTAX     INTEGER (-128..127)
    MAX-ACCESS read-only
    STATUS     current
    DESCRIPTION
        "-- empty --"
    ::= { lcsStatusWlanChannelScanResultsEntry 4 }

-- {COLUMN} 310.1.3.42.1.6
lcsStatusWlanChannelScanResultsEntryNumBss OBJECT-TYPE
    SYNTAX     INTEGER (0..65535)
    MAX-ACCESS read-only
    STATUS     current
    DESCRIPTION
        "-- empty --"
    ::= { lcsStatusWlanChannelScanResultsEntry 6 }

-- {COLUMN} 310.1.3.42.1.10
lcsStatusWlanChannelScanResultsEntryPulseCount OBJECT-TYPE
    SYNTAX     INTEGER (0..2147483647)
    MAX-ACCESS read-only
    STATUS     current
    DESCRIPTION
        "-- empty --"
    ::= { lcsStatusWlanChannelScanResultsEntry 10 }

-- {COLUMN} 310.1.3.42.1.7
lcsStatusWlanChannelScanResultsEntryRadarDetected OBJECT-TYPE
    SYNTAX     INTEGER
      {
        eNo (0),
        eYes (1)
      }
    MAX-ACCESS read-only
    STATUS     current
    DESCRIPTION
        "-- empty --"
    ::= { lcsStatusWlanChannelScanResultsEntry 7 }

-- {COLUMN} 310.1.3.42.1.13
lcsStatusWlanChannelScanResultsEntryRadarPattern OBJECT-TYPE
    SYNTAX     DisplayString (SIZE(0..40))
    MAX-ACCESS read-only
    STATUS     current
    DESCRIPTION
        "-- empty --"
    ::= { lcsStatusWlanChannelScanResultsEntry 13 }

-- {COLUMN} 310.1.3.42.1.17
lcsStatusWlanChannelScanResultsEntryNonHtBss OBJECT-TYPE
    SYNTAX     INTEGER
      {
        eNo (0),
        eYes (1)
      }
    MAX-ACCESS read-only
    STATUS     current
    DESCRIPTION
        "-- empty --"
    ::= { lcsStatusWlanChannelScanResultsEntry 17 }

-- {COLUMN} 310.1.3.42.1.18
lcsStatusWlanChannelScanResultsEntryNonHtBssAge OBJECT-TYPE
    SYNTAX     INTEGER (0..2147483647)
    MAX-ACCESS read-only
    STATUS     current
    DESCRIPTION
        "-- empty --"
    ::= { lcsStatusWlanChannelScanResultsEntry 18 }

-- {COLUMN} 310.1.3.42.1.19
lcsStatusWlanChannelScanResultsEntry40mIntolerantBss OBJECT-TYPE
    SYNTAX     INTEGER
      {
        eNo (0),
        eYes (1)
      }
    MAX-ACCESS read-only
    STATUS     current
    DESCRIPTION
        "-- empty --"
    ::= { lcsStatusWlanChannelScanResultsEntry 19 }

-- {COLUMN} 310.1.3.42.1.20
lcsStatusWlanChannelScanResultsEntry40mIntolerantBssAge OBJECT-TYPE
    SYNTAX     INTEGER (0..2147483647)
    MAX-ACCESS read-only
    STATUS     current
    DESCRIPTION
        "-- empty --"
    ::= { lcsStatusWlanChannelScanResultsEntry 20 }

-- {COLUMN} 310.1.3.42.1.21
lcsStatusWlanChannelScanResultsEntry40mIntolerantBssReported OBJECT-TYPE
    SYNTAX     INTEGER
      {
        eNo (0),
        eYes (1)
      }
    MAX-ACCESS read-only
    STATUS     current
    DESCRIPTION
        "-- empty --"
    ::= { lcsStatusWlanChannelScanResultsEntry 21 }

-- {COLUMN} 310.1.3.42.1.22
lcsStatusWlanChannelScanResultsEntry40mIntolerantBssReportedAge OBJECT-TYPE
    SYNTAX     INTEGER (0..2147483647)
    MAX-ACCESS read-only
    STATUS     current
    DESCRIPTION
        "-- empty --"
    ::= { lcsStatusWlanChannelScanResultsEntry 22 }

-- {OID} 310.1.3.43
lcsStatusWlanClient OBJECT IDENTIFIER ::= { lcsStatusWlan 43 }

-- {TABLE} 310.1.3.43.52
lcsStatusWlanClientConnectionRejectsTable OBJECT-TYPE
    SYNTAX     SEQUENCE OF LcsStatusWlanClientConnectionRejectsEntry
    MAX-ACCESS not-accessible
    STATUS     current
    DESCRIPTION
        "-- empty --"
    ::= { lcsStatusWlanClient 52 }

-- {ENTRY} 310.1.3.43.52.1
lcsStatusWlanClientConnectionRejectsEntry OBJECT-TYPE
    SYNTAX     LcsStatusWlanClientConnectionRejectsEntry
    MAX-ACCESS not-accessible
    STATUS     current
    DESCRIPTION
        ""
    INDEX {
        lcsStatusWlanClientConnectionRejectsEntryBssid,
        lcsStatusWlanClientConnectionRejectsEntryInterface
    }
    ::= { lcsStatusWlanClientConnectionRejectsTable 1 }

-- {SEQUENCE}
LcsStatusWlanClientConnectionRejectsEntry ::= SEQUENCE {
    lcsStatusWlanClientConnectionRejectsEntryBssid MacAddress,
    lcsStatusWlanClientConnectionRejectsEntryInterface INTEGER,
    lcsStatusWlanClientConnectionRejectsEntryAge INTEGER,
    lcsStatusWlanClientConnectionRejectsEntryEvent INTEGER,
    lcsStatusWlanClientConnectionRejectsEntryStatusOrReason INTEGER
}

-- {COLUMN} 310.1.3.43.52.1.1
lcsStatusWlanClientConnectionRejectsEntryBssid OBJECT-TYPE
    SYNTAX     MacAddress
    MAX-ACCESS read-only
    STATUS     current
    DESCRIPTION
        "-- empty --"
    ::= { lcsStatusWlanClientConnectionRejectsEntry 1 }

-- {COLUMN} 310.1.3.43.52.1.2
lcsStatusWlanClientConnectionRejectsEntryInterface OBJECT-TYPE
    SYNTAX     INTEGER
      {
        eWlan1 (1)
      }
    MAX-ACCESS read-only
    STATUS     current
    DESCRIPTION
        "-- empty --"
    ::= { lcsStatusWlanClientConnectionRejectsEntry 2 }

-- {COLUMN} 310.1.3.43.52.1.3
lcsStatusWlanClientConnectionRejectsEntryAge OBJECT-TYPE
    SYNTAX     INTEGER (0..2147483647)
    MAX-ACCESS read-only
    STATUS     current
    DESCRIPTION
        "-- empty --"
    ::= { lcsStatusWlanClientConnectionRejectsEntry 3 }

-- {COLUMN} 310.1.3.43.52.1.4
lcsStatusWlanClientConnectionRejectsEntryEvent OBJECT-TYPE
    SYNTAX     INTEGER
      {
        eAuthenticateReject (3),
        eAssociateReject (4),
        eDeauthenticate (1),
        eDisassociate (2)
      }
    MAX-ACCESS read-only
    STATUS     current
    DESCRIPTION
        "-- empty --"
    ::= { lcsStatusWlanClientConnectionRejectsEntry 4 }

-- {COLUMN} 310.1.3.43.52.1.5
lcsStatusWlanClientConnectionRejectsEntryStatusOrReason OBJECT-TYPE
    SYNTAX     INTEGER (0..65535)
    MAX-ACCESS read-only
    STATUS     current
    DESCRIPTION
        "-- empty --"
    ::= { lcsStatusWlanClientConnectionRejectsEntry 5 }

-- {TABLE} 310.1.3.43.51
lcsStatusWlanClientIfcsTable OBJECT-TYPE
    SYNTAX     SEQUENCE OF LcsStatusWlanClientIfcsEntry
    MAX-ACCESS not-accessible
    STATUS     current
    DESCRIPTION
        ""
    ::= { lcsStatusWlanClient 51 }

-- {ENTRY} 310.1.3.43.51.1
lcsStatusWlanClientIfcsEntry OBJECT-TYPE
    SYNTAX     LcsStatusWlanClientIfcsEntry
    MAX-ACCESS not-accessible
    STATUS     current
    DESCRIPTION
        ""
    INDEX {
        lcsStatusWlanClientIfcsEntryIfc
    }
    ::= { lcsStatusWlanClientIfcsTable 1 }

-- {SEQUENCE}
LcsStatusWlanClientIfcsEntry ::= SEQUENCE {
    lcsStatusWlanClientIfcsEntryIfc DisplayString,
    lcsStatusWlanClientIfcsEntryState INTEGER,
    lcsStatusWlanClientIfcsEntryStationMode INTEGER,
    lcsStatusWlanClientIfcsEntryConnectTime INTEGER,
    lcsStatusWlanClientIfcsEntryAid INTEGER,
    lcsStatusWlanClientIfcsEntryPhySignal INTEGER,
    lcsStatusWlanClientIfcsEntryLinkPhySignal INTEGER,
    lcsStatusWlanClientIfcsEntryLinkSignalLevel INTEGER,
    lcsStatusWlanClientIfcsEntryIdentification DisplayString,
    lcsStatusWlanClientIfcsEntryTxRate INTEGER,
    lcsStatusWlanClientIfcsEntryRxRate INTEGER,
    lcsStatusWlanClientIfcsEntryEffTxRate INTEGER,
    lcsStatusWlanClientIfcsEntryEffRxRate INTEGER,
    lcsStatusWlanClientIfcsEntryTxBytes Counter64,
    lcsStatusWlanClientIfcsEntryRxBytes Counter64,
    lcsStatusWlanClientIfcsEntryThroughput DisplayString,
    lcsStatusWlanClientIfcsEntryMaxThroughput DisplayString,
    lcsStatusWlanClientIfcsEntryBytesThroughput INTEGER,
    lcsStatusWlanClientIfcsEntryBytesMaxThroughput INTEGER,
    lcsStatusWlanClientIfcsEntryTxPackets Counter32,
    lcsStatusWlanClientIfcsEntryRxPackets Counter32,
    lcsStatusWlanClientIfcsEntryTxErrors INTEGER,
    lcsStatusWlanClientIfcsEntryTotalRetries INTEGER,
    lcsStatusWlanClientIfcsEntryTxLimit INTEGER,
    lcsStatusWlanClientIfcsEntryRxLimit INTEGER,
    lcsStatusWlanClientIfcsEntryClBrgSupport INTEGER,
    lcsStatusWlanClientIfcsEntryWpaVersion INTEGER,
    lcsStatusWlanClientIfcsEntryKeyType INTEGER,
    lcsStatusWlanClientIfcsEntryQos INTEGER,
    lcsStatusWlanClientIfcsEntryAlarmState INTEGER,
    lcsStatusWlanClientIfcsEntryMaxAMpduLen INTEGER,
    lcsStatusWlanClientIfcsEntryMaxAMsduLen INTEGER,
    lcsStatusWlanClientIfcsEntryAllow40mhz INTEGER,
    lcsStatusWlanClientIfcsEntryExtChannel INTEGER,
    lcsStatusWlanClientIfcsEntry40mhzCoexistence INTEGER
}

-- {COLUMN} 310.1.3.43.51.1.1
lcsStatusWlanClientIfcsEntryIfc OBJECT-TYPE
    SYNTAX     DisplayString (SIZE(0..255))
    MAX-ACCESS read-only
    STATUS     current
    DESCRIPTION
        "-- empty --"
    ::= { lcsStatusWlanClientIfcsEntry 1 }

-- {COLUMN} 310.1.3.43.51.1.2
lcsStatusWlanClientIfcsEntryState OBJECT-TYPE
    SYNTAX     INTEGER
      {
        eNone (0),
        eScanning (6),
        eJoined (5),
        eChallenge (7),
        eAuthenticated (2),
        eAssociated (9),
        eWaitPmkCache (11),
        e1xNegotiation (10),
        eKeyHandshake (8),
        eConnected (3)
      }
    MAX-ACCESS read-only
    STATUS     current
    DESCRIPTION
        "-- empty --"
    ::= { lcsStatusWlanClientIfcsEntry 2 }

-- {COLUMN} 310.1.3.43.51.1.3
lcsStatusWlanClientIfcsEntryStationMode OBJECT-TYPE
    SYNTAX     INTEGER
      {
        eNone (0),
        eAdhoc (1),
        eInfrastructure (2) -- lancom's description of Infrastructure
      }
    MAX-ACCESS read-only
    STATUS     current
    DESCRIPTION
        "-- empty --"
    ::= { lcsStatusWlanClientIfcsEntry 3 }

-- {COLUMN} 310.1.3.43.51.1.25
lcsStatusWlanClientIfcsEntryConnectTime OBJECT-TYPE
    SYNTAX     INTEGER (0..2147483647)
    MAX-ACCESS read-only
    STATUS     current
    DESCRIPTION
        "-- empty --"
    ::= { lcsStatusWlanClientIfcsEntry 25 }

-- {COLUMN} 310.1.3.43.51.1.23
lcsStatusWlanClientIfcsEntryAid OBJECT-TYPE
    SYNTAX     INTEGER (0..65535)
    MAX-ACCESS read-only
    STATUS     current
    DESCRIPTION
        "-- empty --"
    ::= { lcsStatusWlanClientIfcsEntry 23 }

-- {COLUMN} 310.1.3.43.51.1.7
lcsStatusWlanClientIfcsEntryPhySignal OBJECT-TYPE
    SYNTAX     INTEGER (0..65535)
    MAX-ACCESS read-only
    STATUS     current
    DESCRIPTION
        "-- empty --"
    ::= { lcsStatusWlanClientIfcsEntry 7 }

-- {COLUMN} 310.1.3.43.51.1.22
lcsStatusWlanClientIfcsEntryLinkPhySignal OBJECT-TYPE
    SYNTAX     INTEGER (0..65535)
    MAX-ACCESS read-only
    STATUS     current
    DESCRIPTION
        "-- empty --"
    ::= { lcsStatusWlanClientIfcsEntry 22 }

-- {COLUMN} 310.1.3.43.51.1.26
lcsStatusWlanClientIfcsEntryLinkSignalLevel OBJECT-TYPE
    SYNTAX     INTEGER (-32768..32767)
    MAX-ACCESS read-only
    STATUS     current
    DESCRIPTION
        "-- empty --"
    ::= { lcsStatusWlanClientIfcsEntry 26 }

-- {COLUMN} 310.1.3.43.51.1.24
lcsStatusWlanClientIfcsEntryIdentification OBJECT-TYPE
    SYNTAX     DisplayString (SIZE(0..24))
    MAX-ACCESS read-only
    STATUS     current
    DESCRIPTION
        "-- empty --"
    ::= { lcsStatusWlanClientIfcsEntry 24 }

-- {COLUMN} 310.1.3.43.51.1.9
lcsStatusWlanClientIfcsEntryTxRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanClientIfcsEntry 9 }

-- {COLUMN} 310.1.3.43.51.1.5
lcsStatusWlanClientIfcsEntryRxRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanClientIfcsEntry 5 }

-- {COLUMN} 310.1.3.43.51.1.29
lcsStatusWlanClientIfcsEntryEffTxRate OBJECT-TYPE
    SYNTAX     INTEGER (0..2147483647)
    MAX-ACCESS read-only
    STATUS     current
    DESCRIPTION
        "-- empty --"
    ::= { lcsStatusWlanClientIfcsEntry 29 }

-- {COLUMN} 310.1.3.43.51.1.30
lcsStatusWlanClientIfcsEntryEffRxRate OBJECT-TYPE
    SYNTAX     INTEGER (0..2147483647)
    MAX-ACCESS read-only
    STATUS     current
    DESCRIPTION
        "-- empty --"
    ::= { lcsStatusWlanClientIfcsEntry 30 }

-- {COLUMN} 310.1.3.43.51.1.11
lcsStatusWlanClientIfcsEntryTxBytes OBJECT-TYPE
    SYNTAX     Counter64
    MAX-ACCESS read-only
    STATUS     current
    DESCRIPTION
        "-- empty --"
    ::= { lcsStatusWlanClientIfcsEntry 11 }

-- {COLUMN} 310.1.3.43.51.1.12
lcsStatusWlanClientIfcsEntryRxBytes OBJECT-TYPE
    SYNTAX     Counter64
    MAX-ACCESS read-only
    STATUS     current
    DESCRIPTION
        "-- empty --"
    ::= { lcsStatusWlanClientIfcsEntry 12 }

-- {COLUMN} 310.1.3.43.51.1.6
lcsStatusWlanClientIfcsEntryThroughput OBJECT-TYPE
    SYNTAX     DisplayString (SIZE(0..14))
    MAX-ACCESS read-only
    STATUS     current
    DESCRIPTION
        "-- empty --"
    ::= { lcsStatusWlanClientIfcsEntry 6 }

-- {COLUMN} 310.1.3.43.51.1.10
lcsStatusWlanClientIfcsEntryMaxThroughput OBJECT-TYPE
    SYNTAX     DisplayString (SIZE(0..14))
    MAX-ACCESS read-only
    STATUS     current
    DESCRIPTION
        "-- empty --"
    ::= { lcsStatusWlanClientIfcsEntry 10 }

-- {COLUMN} 310.1.3.43.51.1.13
lcsStatusWlanClientIfcsEntryBytesThroughput OBJECT-TYPE
    SYNTAX     INTEGER (0..2147483647)
    MAX-ACCESS read-only
    STATUS     current
    DESCRIPTION
        "-- empty --"
    ::= { lcsStatusWlanClientIfcsEntry 13 }

-- {COLUMN} 310.1.3.43.51.1.14
lcsStatusWlanClientIfcsEntryBytesMaxThroughput OBJECT-TYPE
    SYNTAX     INTEGER (0..2147483647)
    MAX-ACCESS read-only
    STATUS     current
    DESCRIPTION
        "-- empty --"
    ::= { lcsStatusWlanClientIfcsEntry 14 }

-- {COLUMN} 310.1.3.43.51.1.20
lcsStatusWlanClientIfcsEntryTxPackets OBJECT-TYPE
    SYNTAX     Counter32
    MAX-ACCESS read-only
    STATUS     current
    DESCRIPTION
        "-- empty --"
    ::= { lcsStatusWlanClientIfcsEntry 20 }

-- {COLUMN} 310.1.3.43.51.1.21
lcsStatusWlanClientIfcsEntryRxPackets OBJECT-TYPE
    SYNTAX     Counter32
    MAX-ACCESS read-only
    STATUS     current
    DESCRIPTION
        "-- empty --"
    ::= { lcsStatusWlanClientIfcsEntry 21 }

-- {COLUMN} 310.1.3.43.51.1.32
lcsStatusWlanClientIfcsEntryTxErrors OBJECT-TYPE
    SYNTAX     INTEGER (0..2147483647)
    MAX-ACCESS read-only
    STATUS     current
    DESCRIPTION
        "-- empty --"
    ::= { lcsStatusWlanClientIfcsEntry 32 }

-- {COLUMN} 310.1.3.43.51.1.33
lcsStatusWlanClientIfcsEntryTotalRetries OBJECT-TYPE
    SYNTAX     INTEGER (0..2147483647)
    MAX-ACCESS read-only
    STATUS     current
    DESCRIPTION
        "-- empty --"
    ::= { lcsStatusWlanClientIfcsEntry 33 }

-- {COLUMN} 310.1.3.43.51.1.17
lcsStatusWlanClientIfcsEntryTxLimit OBJECT-TYPE
    SYNTAX     INTEGER (0..2147483647)
    MAX-ACCESS read-only
    STATUS     current
    DESCRIPTION
        "-- empty --"
    ::= { lcsStatusWlanClientIfcsEntry 17 }

-- {COLUMN} 310.1.3.43.51.1.18
lcsStatusWlanClientIfcsEntryRxLimit OBJECT-TYPE
    SYNTAX     INTEGER (0..2147483647)
    MAX-ACCESS read-only
    STATUS     current
    DESCRIPTION
        "-- empty --"
    ::= { lcsStatusWlanClientIfcsEntry 18 }

-- {COLUMN} 310.1.3.43.51.1.15
lcsStatusWlanClientIfcsEntryClBrgSupport OBJECT-TYPE
    SYNTAX     INTEGER
      {
        eNo (0),
        eYes (1)
      }
    MAX-ACCESS read-only
    STATUS     current
    DESCRIPTION
        "-- empty --"
    ::= { lcsStatusWlanClientIfcsEntry 15 }

-- {COLUMN} 310.1.3.43.51.1.16
lcsStatusWlanClientIfcsEntryWpaVersion OBJECT-TYPE
    SYNTAX     INTEGER
      {
        eWpa1 (1),
        eWpa2 (2),
        eNone (0)
      }
    MAX-ACCESS read-only
    STATUS     current
    DESCRIPTION
        "-- empty --"
    ::= { lcsStatusWlanClientIfcsEntry 16 }

-- {COLUMN} 310.1.3.43.51.1.31
lcsStatusWlanClientIfcsEntryKeyType OBJECT-TYPE
    SYNTAX     INTEGER
      {
        eNone (0),
        eUnknown (1),
        eWep40Bits (5),
        eWep104Bits (13),
        eWep128Bits (16),
        eTkip (64),
        eAesOcb (65),
        eAesCcm (66)
      }
    MAX-ACCESS read-only
    STATUS     current
    DESCRIPTION
        "-- empty --"
    ::= { lcsStatusWlanClientIfcsEntry 31 }

-- {COLUMN} 310.1.3.43.51.1.19
lcsStatusWlanClientIfcsEntryQos OBJECT-TYPE
    SYNTAX     INTEGER
      {
        eNo (0),
        eYes (1)
      }
    MAX-ACCESS read-only
    STATUS     current
    DESCRIPTION
        "-- empty --"
    ::= { lcsStatusWlanClientIfcsEntry 19 }

-- {COLUMN} 310.1.3.43.51.1.34
lcsStatusWlanClientIfcsEntryAlarmState OBJECT-TYPE
    SYNTAX     INTEGER
      {
        ePhySignal (1),
        eTotalRetries (2),
        eTxErrors (4),
        eNo (0)
      }
    MAX-ACCESS read-only
    STATUS     current
    DESCRIPTION
        "-- empty --"
    ::= { lcsStatusWlanClientIfcsEntry 34 }

-- {COLUMN} 310.1.3.43.51.1.27
lcsStatusWlanClientIfcsEntryMaxAMpduLen OBJECT-TYPE
    SYNTAX     INTEGER (0..2147483647)
    MAX-ACCESS read-only
    STATUS     current
    DESCRIPTION
        "-- empty --"
    ::= { lcsStatusWlanClientIfcsEntry 27 }

-- {COLUMN} 310.1.3.43.51.1.28
lcsStatusWlanClientIfcsEntryMaxAMsduLen OBJECT-TYPE
    SYNTAX     INTEGER (0..2147483647)
    MAX-ACCESS read-only
    STATUS     current
    DESCRIPTION
        "-- empty --"
    ::= { lcsStatusWlanClientIfcsEntry 28 }

-- {COLUMN} 310.1.3.43.51.1.35
lcsStatusWlanClientIfcsEntryAllow40mhz OBJECT-TYPE
    SYNTAX     INTEGER
      {
        eNo (0),
        eYes (1)
      }
    MAX-ACCESS read-only
    STATUS     current
    DESCRIPTION
        "-- empty --"
    ::= { lcsStatusWlanClientIfcsEntry 35 }

-- {COLUMN} 310.1.3.43.51.1.36
lcsStatusWlanClientIfcsEntryExtChannel OBJECT-TYPE
    SYNTAX     INTEGER
      {
        eNone (0),
        eAbove (1),
        eBelow (3)
      }
    MAX-ACCESS read-only
    STATUS     current
    DESCRIPTION
        "-- empty --"
    ::= { lcsStatusWlanClientIfcsEntry 36 }

-- {COLUMN} 310.1.3.43.51.1.37
lcsStatusWlanClientIfcsEntry40mhzCoexistence OBJECT-TYPE
    SYNTAX     INTEGER
      {
        eNo (0),
        eYes (1)
      }
    MAX-ACCESS read-only
    STATUS     current
    DESCRIPTION
        "-- empty --"
    ::= { lcsStatusWlanClientIfcsEntry 37 }

-- {TABLE} 310.1.3.43.1
lcsStatusWlanClientIpv4TranslationTableTable OBJECT-TYPE
    SYNTAX     SEQUENCE OF LcsStatusWlanClientIpv4TranslationTableEntry
    MAX-ACCESS not-accessible
    STATUS     current
    DESCRIPTION
        "-- empty --"
    ::= { lcsStatusWlanClient 1 }

-- {ENTRY} 310.1.3.43.1.1
lcsStatusWlanClientIpv4TranslationTableEntry OBJECT-TYPE
    SYNTAX     LcsStatusWlanClientIpv4TranslationTableEntry
    MAX-ACCESS not-accessible
    STATUS     current
    DESCRIPTION
        ""
    INDEX {
        lcsStatusWlanClientIpv4TranslationTableEntryIpAddress
    }
    ::= { lcsStatusWlanClientIpv4TranslationTableTable 1 }

-- {SEQUENCE}
LcsStatusWlanClientIpv4TranslationTableEntry ::= SEQUENCE {
    lcsStatusWlanClientIpv4TranslationTableEntryIpAddress IpAddress,
    lcsStatusWlanClientIpv4TranslationTableEntryMacAddress MacAddress,
    lcsStatusWlanClientIpv4TranslationTableEntryAge INTEGER
}

-- {COLUMN} 310.1.3.43.1.1.1
lcsStatusWlanClientIpv4TranslationTableEntryIpAddress OBJECT-TYPE
    SYNTAX     IpAddress
    MAX-ACCESS read-only
    STATUS     current
    DESCRIPTION
        "-- empty --"
    ::= { lcsStatusWlanClientIpv4TranslationTableEntry 1 }

-- {COLUMN} 310.1.3.43.1.1.2
lcsStatusWlanClientIpv4TranslationTableEntryMacAddress OBJECT-TYPE
    SYNTAX     MacAddress
    MAX-ACCESS read-only
    STATUS     current
    DESCRIPTION
        "-- empty --"
    ::= { lcsStatusWlanClientIpv4TranslationTableEntry 2 }

-- {COLUMN} 310.1.3.43.1.1.3
lcsStatusWlanClientIpv4TranslationTableEntryAge OBJECT-TYPE
    SYNTAX     INTEGER (0..2147483647)
    MAX-ACCESS read-only
    STATUS     current
    DESCRIPTION
        "-- empty --"
    ::= { lcsStatusWlanClientIpv4TranslationTableEntry 3 }

-- {TABLE} 310.1.3.43.10
lcsStatusWlanClientPppoeIdTranslationTableTable OBJECT-TYPE
    SYNTAX     SEQUENCE OF LcsStatusWlanClientPppoeIdTranslationTableEntry
    MAX-ACCESS not-accessible
    STATUS     current
    DESCRIPTION
        "-- empty --"
    ::= { lcsStatusWlanClient 10 }

-- {ENTRY} 310.1.3.43.10.1
lcsStatusWlanClientPppoeIdTranslationTableEntry OBJECT-TYPE
    SYNTAX     LcsStatusWlanClientPppoeIdTranslationTableEntry
    MAX-ACCESS not-accessible
    STATUS     current
    DESCRIPTION
        ""
    INDEX {
        lcsStatusWlanClientPppoeIdTranslationTableEntrySessionId
    }
    ::= { lcsStatusWlanClientPppoeIdTranslationTableTable 1 }

-- {SEQUENCE}
LcsStatusWlanClientPppoeIdTranslationTableEntry ::= SEQUENCE {
    lcsStatusWlanClientPppoeIdTranslationTableEntrySessionId INTEGER,
    lcsStatusWlanClientPppoeIdTranslationTableEntryMacAddress MacAddress,
    lcsStatusWlanClientPppoeIdTranslationTableEntryAge INTEGER
}

-- {COLUMN} 310.1.3.43.10.1.1
lcsStatusWlanClientPppoeIdTranslationTableEntrySessionId OBJECT-TYPE
    SYNTAX     INTEGER (0..65535)
    MAX-ACCESS read-only
    STATUS     current
    DESCRIPTION
        "-- empty --"
    ::= { lcsStatusWlanClientPppoeIdTranslationTableEntry 1 }

-- {COLUMN} 310.1.3.43.10.1.2
lcsStatusWlanClientPppoeIdTranslationTableEntryMacAddress OBJECT-TYPE
    SYNTAX     MacAddress
    MAX-ACCESS read-only
    STATUS     current
    DESCRIPTION
        "-- empty --"
    ::= { lcsStatusWlanClientPppoeIdTranslationTableEntry 2 }

-- {COLUMN} 310.1.3.43.10.1.3
lcsStatusWlanClientPppoeIdTranslationTableEntryAge OBJECT-TYPE
    SYNTAX     INTEGER (0..2147483647)
    MAX-ACCESS read-only
    STATUS     current
    DESCRIPTION
        "-- empty --"
    ::= { lcsStatusWlanClientPppoeIdTranslationTableEntry 3 }

-- {TABLE} 310.1.3.43.11
lcsStatusWlanClientPppoeUniqTranslationTableTable OBJECT-TYPE
    SYNTAX     SEQUENCE OF LcsStatusWlanClientPppoeUniqTranslationTableEntry
    MAX-ACCESS not-accessible
    STATUS     current
    DESCRIPTION
        "-- empty --"
    ::= { lcsStatusWlanClient 11 }

-- {ENTRY} 310.1.3.43.11.1
lcsStatusWlanClientPppoeUniqTranslationTableEntry OBJECT-TYPE
    SYNTAX     LcsStatusWlanClientPppoeUniqTranslationTableEntry
    MAX-ACCESS not-accessible
    STATUS     current
    DESCRIPTION
        ""
    INDEX {
        lcsStatusWlanClientPppoeUniqTranslationTableEntryHostUniqLen,
        lcsStatusWlanClientPppoeUniqTranslationTableEntryHostUniq
    }
    ::= { lcsStatusWlanClientPppoeUniqTranslationTableTable 1 }

-- {SEQUENCE}
LcsStatusWlanClientPppoeUniqTranslationTableEntry ::= SEQUENCE {
    lcsStatusWlanClientPppoeUniqTranslationTableEntryHostUniqLen INTEGER,
    lcsStatusWlanClientPppoeUniqTranslationTableEntryHostUniq DisplayString,
    lcsStatusWlanClientPppoeUniqTranslationTableEntryMacAddress MacAddress,
    lcsStatusWlanClientPppoeUniqTranslationTableEntryAge INTEGER
}

-- {COLUMN} 310.1.3.43.11.1.1
lcsStatusWlanClientPppoeUniqTranslationTableEntryHostUniqLen OBJECT-TYPE
    SYNTAX     INTEGER (0..65535)
    MAX-ACCESS read-only
    STATUS     current
    DESCRIPTION
        "-- empty --"
    ::= { lcsStatusWlanClientPppoeUniqTranslationTableEntry 1 }

-- {COLUMN} 310.1.3.43.11.1.2
lcsStatusWlanClientPppoeUniqTranslationTableEntryHostUniq OBJECT-TYPE
    SYNTAX     DisplayString (SIZE(0..255))
    MAX-ACCESS read-only
    STATUS     current
    DESCRIPTION
        "-- empty --"
    ::= { lcsStatusWlanClientPppoeUniqTranslationTableEntry 2 }

-- {COLUMN} 310.1.3.43.11.1.3
lcsStatusWlanClientPppoeUniqTranslationTableEntryMacAddress OBJECT-TYPE
    SYNTAX     MacAddress
    MAX-ACCESS read-only
    STATUS     current
    DESCRIPTION
        "-- empty --"
    ::= { lcsStatusWlanClientPppoeUniqTranslationTableEntry 3 }

-- {COLUMN} 310.1.3.43.11.1.4
lcsStatusWlanClientPppoeUniqTranslationTableEntryAge OBJECT-TYPE
    SYNTAX     INTEGER (0..2147483647)
    MAX-ACCESS read-only
    STATUS     current
    DESCRIPTION
        "-- empty --"
    ::= { lcsStatusWlanClientPppoeUniqTranslationTableEntry 4 }

-- {TABLE} 310.1.3.43.12
lcsStatusWlanClientIpv6TranslationTableTable OBJECT-TYPE
    SYNTAX     SEQUENCE OF LcsStatusWlanClientIpv6TranslationTableEntry
    MAX-ACCESS not-accessible
    STATUS     current
    DESCRIPTION
        "-- empty --"
    ::= { lcsStatusWlanClient 12 }

-- {ENTRY} 310.1.3.43.12.1
lcsStatusWlanClientIpv6TranslationTableEntry OBJECT-TYPE
    SYNTAX     LcsStatusWlanClientIpv6TranslationTableEntry
    MAX-ACCESS not-accessible
    STATUS     current
    DESCRIPTION
        ""
    INDEX {
        lcsStatusWlanClientIpv6TranslationTableEntryIpAddress
    }
    ::= { lcsStatusWlanClientIpv6TranslationTableTable 1 }

-- {SEQUENCE}
LcsStatusWlanClientIpv6TranslationTableEntry ::= SEQUENCE {
    lcsStatusWlanClientIpv6TranslationTableEntryIpAddress IpAddress,
    lcsStatusWlanClientIpv6TranslationTableEntryMacAddress MacAddress,
    lcsStatusWlanClientIpv6TranslationTableEntryAge INTEGER,
    lcsStatusWlanClientIpv6TranslationTableEntryInternal INTEGER
}

-- {COLUMN} 310.1.3.43.12.1.1
lcsStatusWlanClientIpv6TranslationTableEntryIpAddress OBJECT-TYPE
    SYNTAX     IpAddress
    MAX-ACCESS read-only
    STATUS     current
    DESCRIPTION
        "-- empty --"
    ::= { lcsStatusWlanClientIpv6TranslationTableEntry 1 }

-- {COLUMN} 310.1.3.43.12.1.2
lcsStatusWlanClientIpv6TranslationTableEntryMacAddress OBJECT-TYPE
    SYNTAX     MacAddress
    MAX-ACCESS read-only
    STATUS     current
    DESCRIPTION
        "-- empty --"
    ::= { lcsStatusWlanClientIpv6TranslationTableEntry 2 }

-- {COLUMN} 310.1.3.43.12.1.3
lcsStatusWlanClientIpv6TranslationTableEntryAge OBJECT-TYPE
    SYNTAX     INTEGER (0..2147483647)
    MAX-ACCESS read-only
    STATUS     current
    DESCRIPTION
        "-- empty --"
    ::= { lcsStatusWlanClientIpv6TranslationTableEntry 3 }

-- {COLUMN} 310.1.3.43.12.1.4
lcsStatusWlanClientIpv6TranslationTableEntryInternal OBJECT-TYPE
    SYNTAX     INTEGER
      {
        eNo (0),
        eYes (1)
      }
    MAX-ACCESS read-only
    STATUS     current
    DESCRIPTION
        "-- empty --"
    ::= { lcsStatusWlanClientIpv6TranslationTableEntry 4 }

-- {TABLE} 310.1.3.45
lcsStatusWlanSeenClientsTable OBJECT-TYPE
    SYNTAX     SEQUENCE OF LcsStatusWlanSeenClientsEntry
    MAX-ACCESS not-accessible
    STATUS     current
    DESCRIPTION
        "-- empty --"
    ::= { lcsStatusWlan 45 }

-- {ENTRY} 310.1.3.45.1
lcsStatusWlanSeenClientsEntry OBJECT-TYPE
    SYNTAX     LcsStatusWlanSeenClientsEntry
    MAX-ACCESS not-accessible
    STATUS     current
    DESCRIPTION
        ""
    INDEX {
        lcsStatusWlanSeenClientsEntryMacAddress,
        lcsStatusWlanSeenClientsEntryInterface
    }
    ::= { lcsStatusWlanSeenClientsTable 1 }

-- {SEQUENCE}
LcsStatusWlanSeenClientsEntry ::= SEQUENCE {
    lcsStatusWlanSeenClientsEntryMacAddress MacAddress,
    lcsStatusWlanSeenClientsEntryInterface INTEGER,
    lcsStatusWlanSeenClientsEntryVendor DisplayString,
    lcsStatusWlanSeenClientsEntryRadioBand INTEGER,
    lcsStatusWlanSeenClientsEntrySignalLevel INTEGER,
    lcsStatusWlanSeenClientsEntryRxPhySignal INTEGER,
    lcsStatusWlanSeenClientsEntryAge INTEGER,
    lcsStatusWlanSeenClientsEntryNumProbes Counter32,
    lcsStatusWlanSeenClientsEntryNumProberspOk Counter32,
    lcsStatusWlanSeenClientsEntryNumProberspBad Counter32,
    lcsStatusWlanSeenClientsEntryNumProberspSuppressed Counter32,
    lcsStatusWlanSeenClientsEntryNetworkName DisplayString
}

-- {COLUMN} 310.1.3.45.1.1
lcsStatusWlanSeenClientsEntryMacAddress OBJECT-TYPE
    SYNTAX     MacAddress
    MAX-ACCESS read-only
    STATUS     current
    DESCRIPTION
        "-- empty --"
    ::= { lcsStatusWlanSeenClientsEntry 1 }

-- {COLUMN} 310.1.3.45.1.2
lcsStatusWlanSeenClientsEntryInterface OBJECT-TYPE
    SYNTAX     INTEGER
      {
        eWlan1 (0),
        eWlan2 (1),
        eWlan3 (2),
        eWlan4 (3)
      }
    MAX-ACCESS read-only
    STATUS     current
    DESCRIPTION
        "-- empty --"
    ::= { lcsStatusWlanSeenClientsEntry 2 }

-- {COLUMN} 310.1.3.45.1.8
lcsStatusWlanSeenClientsEntryVendor OBJECT-TYPE
    SYNTAX     DisplayString (SIZE(0..255))
    MAX-ACCESS read-only
    STATUS     current
    DESCRIPTION
        "-- empty --"
    ::= { lcsStatusWlanSeenClientsEntry 8 }

-- {COLUMN} 310.1.3.45.1.11
lcsStatusWlanSeenClientsEntryRadioBand OBJECT-TYPE
    SYNTAX     INTEGER
      {
        eUnknown (0),
        e24ghz (1),
        e5ghz (2)
      }
    MAX-ACCESS read-only
    STATUS     current
    DESCRIPTION
        "-- empty --"
    ::= { lcsStatusWlanSeenClientsEntry 11 }

-- {COLUMN} 310.1.3.45.1.3
lcsStatusWlanSeenClientsEntrySignalLevel OBJECT-TYPE
    SYNTAX     INTEGER (-128..127)
    MAX-ACCESS read-only
    STATUS     current
    DESCRIPTION
        "-- empty --"
    ::= { lcsStatusWlanSeenClientsEntry 3 }

-- {COLUMN} 310.1.3.45.1.6
lcsStatusWlanSeenClientsEntryRxPhySignal OBJECT-TYPE
    SYNTAX     INTEGER (0..65535)
    MAX-ACCESS read-only
    STATUS     current
    DESCRIPTION
        "-- empty --"
    ::= { lcsStatusWlanSeenClientsEntry 6 }

-- {COLUMN} 310.1.3.45.1.4
lcsStatusWlanSeenClientsEntryAge OBJECT-TYPE
    SYNTAX     INTEGER (0..2147483647)
    MAX-ACCESS read-only
    STATUS     current
    DESCRIPTION
        "-- empty --"
    ::= { lcsStatusWlanSeenClientsEntry 4 }

-- {COLUMN} 310.1.3.45.1.7
lcsStatusWlanSeenClientsEntryNumProbes OBJECT-TYPE
    SYNTAX     Counter32
    MAX-ACCESS read-only
    STATUS     current
    DESCRIPTION
        "-- empty --"
    ::= { lcsStatusWlanSeenClientsEntry 7 }

-- {COLUMN} 310.1.3.45.1.9
lcsStatusWlanSeenClientsEntryNumProberspOk OBJECT-TYPE
    SYNTAX     Counter32
    MAX-ACCESS read-only
    STATUS     current
    DESCRIPTION
        "-- empty --"
    ::= { lcsStatusWlanSeenClientsEntry 9 }

-- {COLUMN} 310.1.3.45.1.10
lcsStatusWlanSeenClientsEntryNumProberspBad OBJECT-TYPE
    SYNTAX     Counter32
    MAX-ACCESS read-only
    STATUS     current
    DESCRIPTION
        "-- empty --"
    ::= { lcsStatusWlanSeenClientsEntry 10 }

-- {COLUMN} 310.1.3.45.1.12
lcsStatusWlanSeenClientsEntryNumProberspSuppressed OBJECT-TYPE
    SYNTAX     Counter32
    MAX-ACCESS read-only
    STATUS     current
    DESCRIPTION
        "-- empty --"
    ::= { lcsStatusWlanSeenClientsEntry 12 }

-- {COLUMN} 310.1.3.45.1.5
lcsStatusWlanSeenClientsEntryNetworkName OBJECT-TYPE
    SYNTAX     DisplayString (SIZE(0..32))
    MAX-ACCESS read-only
    STATUS     current
    DESCRIPTION
        "-- empty --"
    ::= { lcsStatusWlanSeenClientsEntry 5 }

-- {TABLE} 310.1.3.46
lcsStatusWlanLogTableTable OBJECT-TYPE
    SYNTAX     SEQUENCE OF LcsStatusWlanLogTableEntry
    MAX-ACCESS not-accessible
    STATUS     current
    DESCRIPTION
        "-- empty --"
    ::= { lcsStatusWlan 46 }

-- {ENTRY} 310.1.3.46.1
lcsStatusWlanLogTableEntry OBJECT-TYPE
    SYNTAX     LcsStatusWlanLogTableEntry
    MAX-ACCESS not-accessible
    STATUS     current
    DESCRIPTION
        ""
    INDEX {
        lcsStatusWlanLogTableEntryIndex
    }
    ::= { lcsStatusWlanLogTableTable 1 }

-- {SEQUENCE}
LcsStatusWlanLogTableEntry ::= SEQUENCE {
    lcsStatusWlanLogTableEntryIndex INTEGER,
    lcsStatusWlanLogTableEntryTime DisplayString,
    lcsStatusWlanLogTableEntryInterface INTEGER,
    lcsStatusWlanLogTableEntryEvent DisplayString,
    lcsStatusWlanLogTableEntryAddress MacAddress,
    lcsStatusWlanLogTableEntryReason DisplayString
}

-- {COLUMN} 310.1.3.46.1.1
lcsStatusWlanLogTableEntryIndex OBJECT-TYPE
    SYNTAX     INTEGER (0..2147483647)
    MAX-ACCESS read-only
    STATUS     current
    DESCRIPTION
        "-- empty --"
    ::= { lcsStatusWlanLogTableEntry 1 }

-- {COLUMN} 310.1.3.46.1.2
lcsStatusWlanLogTableEntryTime OBJECT-TYPE
    SYNTAX     DisplayString (SIZE(0..19))
    MAX-ACCESS read-only
    STATUS     current
    DESCRIPTION
        "-- empty --"
    ::= { lcsStatusWlanLogTableEntry 2 }

-- {COLUMN} 310.1.3.46.1.3
lcsStatusWlanLogTableEntryInterface OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-only
    STATUS     current
    DESCRIPTION
        "-- empty --"
    ::= { lcsStatusWlanLogTableEntry 3 }

-- {COLUMN} 310.1.3.46.1.4
lcsStatusWlanLogTableEntryEvent OBJECT-TYPE
    SYNTAX     DisplayString (SIZE(0..90))
    MAX-ACCESS read-only
    STATUS     current
    DESCRIPTION
        "-- empty --"
    ::= { lcsStatusWlanLogTableEntry 4 }

-- {COLUMN} 310.1.3.46.1.5
lcsStatusWlanLogTableEntryAddress OBJECT-TYPE
    SYNTAX     MacAddress
    MAX-ACCESS read-only
    STATUS     current
    DESCRIPTION
        "-- empty --"
    ::= { lcsStatusWlanLogTableEntry 5 }

-- {COLUMN} 310.1.3.46.1.6
lcsStatusWlanLogTableEntryReason OBJECT-TYPE
    SYNTAX     DisplayString (SIZE(0..127))
    MAX-ACCESS read-only
    STATUS     current
    DESCRIPTION
        "-- empty --"
    ::= { lcsStatusWlanLogTableEntry 6 }

-- {SCALAR} 310.1.3.11
lcsStatusWlanDeleteValues OBJECT-TYPE
    SYNTAX     DisplayString
    MAX-ACCESS read-write
    STATUS     current
    DESCRIPTION
        "-- empty --"
    ::= { lcsStatusWlan 11 }

-- {TABLE} 310.1.3.47
lcsStatusWlanPairwiseKeysTable OBJECT-TYPE
    SYNTAX     SEQUENCE OF LcsStatusWlanPairwiseKeysEntry
    MAX-ACCESS not-accessible
    STATUS     current
    DESCRIPTION
        "-- empty --"
    ::= { lcsStatusWlan 47 }

-- {ENTRY} 310.1.3.47.1
lcsStatusWlanPairwiseKeysEntry OBJECT-TYPE
    SYNTAX     LcsStatusWlanPairwiseKeysEntry
    MAX-ACCESS not-accessible
    STATUS     current
    DESCRIPTION
        ""
    INDEX {
        lcsStatusWlanPairwiseKeysEntryIndex
    }
    ::= { lcsStatusWlanPairwiseKeysTable 1 }

-- {SEQUENCE}
LcsStatusWlanPairwiseKeysEntry ::= SEQUENCE {
    lcsStatusWlanPairwiseKeysEntryIndex INTEGER,
    lcsStatusWlanPairwiseKeysEntryAge INTEGER,
    lcsStatusWlanPairwiseKeysEntryKeyType INTEGER,
    lcsStatusWlanPairwiseKeysEntryKeyValue DisplayString,
    lcsStatusWlanPairwiseKeysEntryTsc DisplayString,
    lcsStatusWlanPairwiseKeysEntryRscBe DisplayString,
    lcsStatusWlanPairwiseKeysEntryRscBk DisplayString,
    lcsStatusWlanPairwiseKeysEntryRscEe DisplayString,
    lcsStatusWlanPairwiseKeysEntryRscCl DisplayString,
    lcsStatusWlanPairwiseKeysEntryRscVi DisplayString,
    lcsStatusWlanPairwiseKeysEntryRscVo DisplayString,
    lcsStatusWlanPairwiseKeysEntryRscNc DisplayString,
    lcsStatusWlanPairwiseKeysEntryIvSequenceErrors INTEGER
}

-- {COLUMN} 310.1.3.47.1.1
lcsStatusWlanPairwiseKeysEntryIndex OBJECT-TYPE
    SYNTAX     INTEGER (0..65535)
    MAX-ACCESS read-only
    STATUS     current
    DESCRIPTION
        "-- empty --"
    ::= { lcsStatusWlanPairwiseKeysEntry 1 }

-- {COLUMN} 310.1.3.47.1.7
lcsStatusWlanPairwiseKeysEntryAge OBJECT-TYPE
    SYNTAX     INTEGER (0..2147483647)
    MAX-ACCESS read-only
    STATUS     current
    DESCRIPTION
        "-- empty --"
    ::= { lcsStatusWlanPairwiseKeysEntry 7 }

-- {COLUMN} 310.1.3.47.1.3
lcsStatusWlanPairwiseKeysEntryKeyType OBJECT-TYPE
    SYNTAX     INTEGER
      {
        eNone (0),
        eUnknown (1),
        eWep40Bits (5),
        eWep104Bits (13),
        eWep128Bits (16),
        eTkip (64),
        eAesOcb (65),
        eAesCcm (66)
      }
    MAX-ACCESS read-only
    STATUS     current
    DESCRIPTION
        "-- empty --"
    ::= { lcsStatusWlanPairwiseKeysEntry 3 }

-- {COLUMN} 310.1.3.47.1.4
lcsStatusWlanPairwiseKeysEntryKeyValue OBJECT-TYPE
    SYNTAX     DisplayString (SIZE(0..255))
    MAX-ACCESS read-only
    STATUS     current
    DESCRIPTION
        "-- empty --"
    ::= { lcsStatusWlanPairwiseKeysEntry 4 }

-- {COLUMN} 310.1.3.47.1.5
lcsStatusWlanPairwiseKeysEntryTsc OBJECT-TYPE
    SYNTAX     DisplayString (SIZE(0..255))
    MAX-ACCESS read-only
    STATUS     current
    DESCRIPTION
        "-- empty --"
    ::= { lcsStatusWlanPairwiseKeysEntry 5 }

-- {COLUMN} 310.1.3.47.1.16
lcsStatusWlanPairwiseKeysEntryRscBe OBJECT-TYPE
    SYNTAX     DisplayString (SIZE(0..255))
    MAX-ACCESS read-only
    STATUS     current
    DESCRIPTION
        "-- empty --"
    ::= { lcsStatusWlanPairwiseKeysEntry 16 }

-- {COLUMN} 310.1.3.47.1.17
lcsStatusWlanPairwiseKeysEntryRscBk OBJECT-TYPE
    SYNTAX     DisplayString (SIZE(0..255))
    MAX-ACCESS read-only
    STATUS     current
    DESCRIPTION
        "-- empty --"
    ::= { lcsStatusWlanPairwiseKeysEntry 17 }

-- {COLUMN} 310.1.3.47.1.19
lcsStatusWlanPairwiseKeysEntryRscEe OBJECT-TYPE
    SYNTAX     DisplayString (SIZE(0..255))
    MAX-ACCESS read-only
    STATUS     current
    DESCRIPTION
        "-- empty --"
    ::= { lcsStatusWlanPairwiseKeysEntry 19 }

-- {COLUMN} 310.1.3.47.1.20
lcsStatusWlanPairwiseKeysEntryRscCl OBJECT-TYPE
    SYNTAX     DisplayString (SIZE(0..255))
    MAX-ACCESS read-only
    STATUS     current
    DESCRIPTION
        "-- empty --"
    ::= { lcsStatusWlanPairwiseKeysEntry 20 }

-- {COLUMN} 310.1.3.47.1.21
lcsStatusWlanPairwiseKeysEntryRscVi OBJECT-TYPE
    SYNTAX     DisplayString (SIZE(0..255))
    MAX-ACCESS read-only
    STATUS     current
    DESCRIPTION
        "-- empty --"
    ::= { lcsStatusWlanPairwiseKeysEntry 21 }

-- {COLUMN} 310.1.3.47.1.22
lcsStatusWlanPairwiseKeysEntryRscVo OBJECT-TYPE
    SYNTAX     DisplayString (SIZE(0..255))
    MAX-ACCESS read-only
    STATUS     current
    DESCRIPTION
        "-- empty --"
    ::= { lcsStatusWlanPairwiseKeysEntry 22 }

-- {COLUMN} 310.1.3.47.1.23
lcsStatusWlanPairwiseKeysEntryRscNc OBJECT-TYPE
    SYNTAX     DisplayString (SIZE(0..255))
    MAX-ACCESS read-only
    STATUS     current
    DESCRIPTION
        "-- empty --"
    ::= { lcsStatusWlanPairwiseKeysEntry 23 }

-- {COLUMN} 310.1.3.47.1.8
lcsStatusWlanPairwiseKeysEntryIvSequenceErrors OBJECT-TYPE
    SYNTAX     INTEGER (0..2147483647)
    MAX-ACCESS read-only
    STATUS     current
    DESCRIPTION
        "-- empty --"
    ::= { lcsStatusWlanPairwiseKeysEntry 8 }

-- {OID} 310.1.3.60
lcsStatusWlanPmkCaching OBJECT IDENTIFIER ::= { lcsStatusWlan 60 }

-- {TABLE} 310.1.3.60.1
lcsStatusWlanPmkCachingContentsTable OBJECT-TYPE
    SYNTAX     SEQUENCE OF LcsStatusWlanPmkCachingContentsEntry
    MAX-ACCESS not-accessible
    STATUS     current
    DESCRIPTION
        "-- empty --"
    ::= { lcsStatusWlanPmkCaching 1 }

-- {ENTRY} 310.1.3.60.1.1
lcsStatusWlanPmkCachingContentsEntry OBJECT-TYPE
    SYNTAX     LcsStatusWlanPmkCachingContentsEntry
    MAX-ACCESS not-accessible
    STATUS     current
    DESCRIPTION
        ""
    INDEX {
        lcsStatusWlanPmkCachingContentsEntryAuthenticator,
        lcsStatusWlanPmkCachingContentsEntrySupplicant
    }
    ::= { lcsStatusWlanPmkCachingContentsTable 1 }

-- {SEQUENCE}
LcsStatusWlanPmkCachingContentsEntry ::= SEQUENCE {
    lcsStatusWlanPmkCachingContentsEntryAuthenticator MacAddress,
    lcsStatusWlanPmkCachingContentsEntrySupplicant MacAddress,
    lcsStatusWlanPmkCachingContentsEntrySource INTEGER,
    lcsStatusWlanPmkCachingContentsEntryUserName DisplayString,
    lcsStatusWlanPmkCachingContentsEntryVlanId INTEGER,
    lcsStatusWlanPmkCachingContentsEntryLifetime INTEGER,
    lcsStatusWlanPmkCachingContentsEntryExpired INTEGER
}

-- {COLUMN} 310.1.3.60.1.1.1
lcsStatusWlanPmkCachingContentsEntryAuthenticator OBJECT-TYPE
    SYNTAX     MacAddress
    MAX-ACCESS read-only
    STATUS     current
    DESCRIPTION
        "-- empty --"
    ::= { lcsStatusWlanPmkCachingContentsEntry 1 }

-- {COLUMN} 310.1.3.60.1.1.2
lcsStatusWlanPmkCachingContentsEntrySupplicant OBJECT-TYPE
    SYNTAX     MacAddress
    MAX-ACCESS read-only
    STATUS     current
    DESCRIPTION
        "-- empty --"
    ::= { lcsStatusWlanPmkCachingContentsEntry 2 }

-- {COLUMN} 310.1.3.60.1.1.7
lcsStatusWlanPmkCachingContentsEntrySource OBJECT-TYPE
    SYNTAX     INTEGER
      {
        eUnknown (0),
        eAuthentication (1),
        ePreAuthentication (2),
        eController (3)
      }
    MAX-ACCESS read-only
    STATUS     current
    DESCRIPTION
        "-- empty --"
    ::= { lcsStatusWlanPmkCachingContentsEntry 7 }

-- {COLUMN} 310.1.3.60.1.1.3
lcsStatusWlanPmkCachingContentsEntryUserName OBJECT-TYPE
    SYNTAX     DisplayString (SIZE(0..255))
    MAX-ACCESS read-only
    STATUS     current
    DESCRIPTION
        "-- empty --"
    ::= { lcsStatusWlanPmkCachingContentsEntry 3 }

-- {COLUMN} 310.1.3.60.1.1.4
lcsStatusWlanPmkCachingContentsEntryVlanId OBJECT-TYPE
    SYNTAX     INTEGER (0..65535)
    MAX-ACCESS read-only
    STATUS     current
    DESCRIPTION
        "-- empty --"
    ::= { lcsStatusWlanPmkCachingContentsEntry 4 }

-- {COLUMN} 310.1.3.60.1.1.5
lcsStatusWlanPmkCachingContentsEntryLifetime OBJECT-TYPE
    SYNTAX     INTEGER (0..2147483647)
    MAX-ACCESS read-only
    STATUS     current
    DESCRIPTION
        "-- empty --"
    ::= { lcsStatusWlanPmkCachingContentsEntry 5 }

-- {COLUMN} 310.1.3.60.1.1.6
lcsStatusWlanPmkCachingContentsEntryExpired OBJECT-TYPE
    SYNTAX     INTEGER
      {
        eNo (0),
        eYes (1)
      }
    MAX-ACCESS read-only
    STATUS     current
    DESCRIPTION
        "-- empty --"
    ::= { lcsStatusWlanPmkCachingContentsEntry 6 }

-- {TABLE} 310.1.3.70
lcsStatusWlanVlanGroupkeyMappingTable OBJECT-TYPE
    SYNTAX     SEQUENCE OF LcsStatusWlanVlanGroupkeyMappingEntry
    MAX-ACCESS not-accessible
    STATUS     current
    DESCRIPTION
        "-- empty --"
    ::= { lcsStatusWlan 70 }

-- {ENTRY} 310.1.3.70.1
lcsStatusWlanVlanGroupkeyMappingEntry OBJECT-TYPE
    SYNTAX     LcsStatusWlanVlanGroupkeyMappingEntry
    MAX-ACCESS not-accessible
    STATUS     current
    DESCRIPTION
        ""
    INDEX {
        lcsStatusWlanVlanGroupkeyMappingEntryNetwork,
        lcsStatusWlanVlanGroupkeyMappingEntryVlanId
    }
    ::= { lcsStatusWlanVlanGroupkeyMappingTable 1 }

-- {SEQUENCE}
LcsStatusWlanVlanGroupkeyMappingEntry ::= SEQUENCE {
    lcsStatusWlanVlanGroupkeyMappingEntryNetwork INTEGER,
    lcsStatusWlanVlanGroupkeyMappingEntryVlanId INTEGER,
    lcsStatusWlanVlanGroupkeyMappingEntryGroupkeyIndex INTEGER,
    lcsStatusWlanVlanGroupkeyMappingEntrySource INTEGER
}

-- {COLUMN} 310.1.3.70.1.1
lcsStatusWlanVlanGroupkeyMappingEntryNetwork OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-only
    STATUS     current
    DESCRIPTION
        "-- empty --"
    ::= { lcsStatusWlanVlanGroupkeyMappingEntry 1 }

-- {COLUMN} 310.1.3.70.1.2
lcsStatusWlanVlanGroupkeyMappingEntryVlanId OBJECT-TYPE
    SYNTAX     INTEGER (0..65535)
    MAX-ACCESS read-only
    STATUS     current
    DESCRIPTION
        "-- empty --"
    ::= { lcsStatusWlanVlanGroupkeyMappingEntry 2 }

-- {COLUMN} 310.1.3.70.1.3
lcsStatusWlanVlanGroupkeyMappingEntryGroupkeyIndex OBJECT-TYPE
    SYNTAX     INTEGER (0..255)
    MAX-ACCESS read-only
    STATUS     current
    DESCRIPTION
        "-- empty --"
    ::= { lcsStatusWlanVlanGroupkeyMappingEntry 3 }

-- {COLUMN} 310.1.3.70.1.4
lcsStatusWlanVlanGroupkeyMappingEntrySource OBJECT-TYPE
    SYNTAX     INTEGER
      {
        eManual (1),
        eAutomatic (2)
      }
    MAX-ACCESS read-only
    STATUS     current
    DESCRIPTION
        "-- empty --"
    ::= { lcsStatusWlanVlanGroupkeyMappingEntry 4 }

-- {TABLE} 310.1.3.32
lcsStatusWlanStationTableTable OBJECT-TYPE
    SYNTAX     SEQUENCE OF LcsStatusWlanStationTableEntry
    MAX-ACCESS not-accessible
    STATUS     current
    DESCRIPTION
        "-- empty --"
    ::= { lcsStatusWlan 32 }

-- {ENTRY} 310.1.3.32.1
lcsStatusWlanStationTableEntry OBJECT-TYPE
    SYNTAX     LcsStatusWlanStationTableEntry
    MAX-ACCESS not-accessible
    STATUS     current
    DESCRIPTION
        ""
    INDEX {
        lcsStatusWlanStationTableEntryIndex
    }
    ::= { lcsStatusWlanStationTableTable 1 }

-- {SEQUENCE}
LcsStatusWlanStationTableEntry ::= SEQUENCE {
    lcsStatusWlanStationTableEntryIndex INTEGER,
    lcsStatusWlanStationTableEntryAid INTEGER,
    lcsStatusWlanStationTableEntryInterface INTEGER,
    lcsStatusWlanStationTableEntryNetwork INTEGER,
    lcsStatusWlanStationTableEntryVlanId INTEGER,
    lcsStatusWlanStationTableEntryIdleTimeout INTEGER,
    lcsStatusWlanStationTableEntryPhySignal INTEGER,
    lcsStatusWlanStationTableEntryMacAddress MacAddress,
    lcsStatusWlanStationTableEntryUserName DisplayString,
    lcsStatusWlanStationTableEntryIdentification DisplayString,
    lcsStatusWlanStationTableEntryTxBytes Counter64,
    lcsStatusWlanStationTableEntryRxBytes Counter64,
    lcsStatusWlanStationTableEntryThroughput DisplayString,
    lcsStatusWlanStationTableEntryMaxThroughput DisplayString,
    lcsStatusWlanStationTableEntryBytesThroughput INTEGER,
    lcsStatusWlanStationTableEntryBytesMaxThroughput INTEGER,
    lcsStatusWlanStationTableEntryTxPackets Counter32,
    lcsStatusWlanStationTableEntryRxPackets Counter32,
    lcsStatusWlanStationTableEntryTxErrors INTEGER,
    lcsStatusWlanStationTableEntryTotalRetries INTEGER,
    lcsStatusWlanStationTableEntryTxLimit INTEGER,
    lcsStatusWlanStationTableEntryRxLimit INTEGER,
    lcsStatusWlanStationTableEntryState INTEGER,
    lcsStatusWlanStationTableEntryMacCheck INTEGER,
    lcsStatusWlanStationTableEntryLastEvent INTEGER,
    lcsStatusWlanStationTableEntryLastError INTEGER,
    lcsStatusWlanStationTableEntryTxRate INTEGER,
    lcsStatusWlanStationTableEntryRxRate INTEGER,
    lcsStatusWlanStationTableEntryEffTxRate INTEGER,
    lcsStatusWlanStationTableEntryEffRxRate INTEGER,
    lcsStatusWlanStationTableEntryWpaVersion INTEGER,
    lcsStatusWlanStationTableEntryQos INTEGER,
    lcsStatusWlanStationTableEntryKeyType INTEGER,
    lcsStatusWlanStationTableEntryPowerSaving INTEGER,
    lcsStatusWlanStationTableEntrySmPwrsave INTEGER,
    lcsStatusWlanStationTableEntryApsd BITS,
    lcsStatusWlanStationTableEntryListenInterval INTEGER,
    lcsStatusWlanStationTableEntryConnectTime INTEGER,
    lcsStatusWlanStationTableEntry40mhzMode INTEGER,
    lcsStatusWlanStationTableEntry40mhzCoexistence INTEGER,
    lcsStatusWlanStationTableEntryMaxAMsduLen INTEGER,
    lcsStatusWlanStationTableEntryMaxAMpduLen INTEGER,
    lcsStatusWlanStationTableEntry40mhzIntolerant INTEGER,
    lcsStatusWlanStationTableEntry20mhzRequested INTEGER,
    lcsStatusWlanStationTableEntryShortPreamble INTEGER,
    lcsStatusWlanStationTableEntryShortSlotTime INTEGER,
    lcsStatusWlanStationTableEntryShortGuardInterval INTEGER,
    lcsStatusWlanStationTableEntryClBrgSupport INTEGER,
    lcsStatusWlanStationTableEntryIpv4Address IpAddress,
    lcsStatusWlanStationTableEntryIpv6Address IpAddress,
    lcsStatusWlanStationTableEntryAlarmState INTEGER
}

-- {COLUMN} 310.1.3.32.1.1
lcsStatusWlanStationTableEntryIndex OBJECT-TYPE
    SYNTAX     INTEGER (0..65535)
    MAX-ACCESS read-only
    STATUS     current
    DESCRIPTION
        "-- empty --"
    ::= { lcsStatusWlanStationTableEntry 1 }

-- {COLUMN} 310.1.3.32.1.19
lcsStatusWlanStationTableEntryAid OBJECT-TYPE
    SYNTAX     INTEGER (0..65535)
    MAX-ACCESS read-only
    STATUS     current
    DESCRIPTION
        "-- empty --"
    ::= { lcsStatusWlanStationTableEntry 19 }

-- {COLUMN} 310.1.3.32.1.15
lcsStatusWlanStationTableEntryInterface OBJECT-TYPE
    SYNTAX     INTEGER
      {
        eWlan1 (0),
        eWlan2 (1),
        eWlan3 (2),
        eWlan4 (3)
      }
    MAX-ACCESS read-only
    STATUS     current
    DESCRIPTION
        "-- empty --"
    ::= { lcsStatusWlanStationTableEntry 15 }

-- {COLUMN} 310.1.3.32.1.25
lcsStatusWlanStationTableEntryNetwork OBJECT-TYPE
    SYNTAX     INTEGER
      {
        e1 (0),
        e2 (1),
        e3 (2),
        e4 (3),
        e5 (4),
        e6 (5),
        e7 (6),
        e8 (7),
        e9 (8),
        e10 (9),
        e11 (10),
        e12 (11),
        e13 (12),
        e14 (13),
        e15 (14),
        e16 (15)
      }
    MAX-ACCESS read-only
    STATUS     current
    DESCRIPTION
        "-- empty --"
    ::= { lcsStatusWlanStationTableEntry 25 }

-- {COLUMN} 310.1.3.32.1.38
lcsStatusWlanStationTableEntryVlanId OBJECT-TYPE
    SYNTAX     INTEGER (0..65535)
    MAX-ACCESS read-only
    STATUS     current
    DESCRIPTION
        "-- empty --"
    ::= { lcsStatusWlanStationTableEntry 38 }

-- {COLUMN} 310.1.3.32.1.43
lcsStatusWlanStationTableEntryIdleTimeout OBJECT-TYPE
    SYNTAX     INTEGER (0..2147483647)
    MAX-ACCESS read-only
    STATUS     current
    DESCRIPTION
        "-- empty --"
    ::= { lcsStatusWlanStationTableEntry 43 }

-- {COLUMN} 310.1.3.32.1.26
lcsStatusWlanStationTableEntryPhySignal OBJECT-TYPE
    SYNTAX     INTEGER (0..65535)
    MAX-ACCESS read-only
    STATUS     current
    DESCRIPTION
        "-- empty --"
    ::= { lcsStatusWlanStationTableEntry 26 }

-- {COLUMN} 310.1.3.32.1.4
lcsStatusWlanStationTableEntryMacAddress OBJECT-TYPE
    SYNTAX     MacAddress
    MAX-ACCESS read-only
    STATUS     current
    DESCRIPTION
        "-- empty --"
    ::= { lcsStatusWlanStationTableEntry 4 }

-- {COLUMN} 310.1.3.32.1.39
lcsStatusWlanStationTableEntryUserName OBJECT-TYPE
    SYNTAX     DisplayString (SIZE(0..255))
    MAX-ACCESS read-only
    STATUS     current
    DESCRIPTION
        "-- empty --"
    ::= { lcsStatusWlanStationTableEntry 39 }

-- {COLUMN} 310.1.3.32.1.9
lcsStatusWlanStationTableEntryIdentification OBJECT-TYPE
    SYNTAX     DisplayString (SIZE(0..24))
    MAX-ACCESS read-only
    STATUS     current
    DESCRIPTION
        "-- empty --"
    ::= { lcsStatusWlanStationTableEntry 9 }

-- {COLUMN} 310.1.3.32.1.6
lcsStatusWlanStationTableEntryTxBytes OBJECT-TYPE
    SYNTAX     Counter64
    MAX-ACCESS read-only
    STATUS     current
    DESCRIPTION
        "-- empty --"
    ::= { lcsStatusWlanStationTableEntry 6 }

-- {COLUMN} 310.1.3.32.1.7
lcsStatusWlanStationTableEntryRxBytes OBJECT-TYPE
    SYNTAX     Counter64
    MAX-ACCESS read-only
    STATUS     current
    DESCRIPTION
        "-- empty --"
    ::= { lcsStatusWlanStationTableEntry 7 }

-- {COLUMN} 310.1.3.32.1.20
lcsStatusWlanStationTableEntryThroughput OBJECT-TYPE
    SYNTAX     DisplayString (SIZE(0..14))
    MAX-ACCESS read-only
    STATUS     current
    DESCRIPTION
        "-- empty --"
    ::= { lcsStatusWlanStationTableEntry 20 }

-- {COLUMN} 310.1.3.32.1.29
lcsStatusWlanStationTableEntryMaxThroughput OBJECT-TYPE
    SYNTAX     DisplayString (SIZE(0..14))
    MAX-ACCESS read-only
    STATUS     current
    DESCRIPTION
        "-- empty --"
    ::= { lcsStatusWlanStationTableEntry 29 }

-- {COLUMN} 310.1.3.32.1.30
lcsStatusWlanStationTableEntryBytesThroughput OBJECT-TYPE
    SYNTAX     INTEGER (0..2147483647)
    MAX-ACCESS read-only
    STATUS     current
    DESCRIPTION
        "-- empty --"
    ::= { lcsStatusWlanStationTableEntry 30 }

-- {COLUMN} 310.1.3.32.1.31
lcsStatusWlanStationTableEntryBytesMaxThroughput OBJECT-TYPE
    SYNTAX     INTEGER (0..2147483647)
    MAX-ACCESS read-only
    STATUS     current
    DESCRIPTION
        "-- empty --"
    ::= { lcsStatusWlanStationTableEntry 31 }

-- {COLUMN} 310.1.3.32.1.41
lcsStatusWlanStationTableEntryTxPackets OBJECT-TYPE
    SYNTAX     Counter32
    MAX-ACCESS read-only
    STATUS     current
    DESCRIPTION
        "-- empty --"
    ::= { lcsStatusWlanStationTableEntry 41 }

-- {COLUMN} 310.1.3.32.1.42
lcsStatusWlanStationTableEntryRxPackets OBJECT-TYPE
    SYNTAX     Counter32
    MAX-ACCESS read-only
    STATUS     current
    DESCRIPTION
        "-- empty --"
    ::= { lcsStatusWlanStationTableEntry 42 }

-- {COLUMN} 310.1.3.32.1.55
lcsStatusWlanStationTableEntryTxErrors OBJECT-TYPE
    SYNTAX     INTEGER (0..2147483647)
    MAX-ACCESS read-only
    STATUS     current
    DESCRIPTION
        "-- empty --"
    ::= { lcsStatusWlanStationTableEntry 55 }

-- {COLUMN} 310.1.3.32.1.56
lcsStatusWlanStationTableEntryTotalRetries OBJECT-TYPE
    SYNTAX     INTEGER (0..2147483647)
    MAX-ACCESS read-only
    STATUS     current
    DESCRIPTION
        "-- empty --"
    ::= { lcsStatusWlanStationTableEntry 56 }

-- {COLUMN} 310.1.3.32.1.35
lcsStatusWlanStationTableEntryTxLimit OBJECT-TYPE
    SYNTAX     INTEGER (0..2147483647)
    MAX-ACCESS read-only
    STATUS     current
    DESCRIPTION
        "-- empty --"
    ::= { lcsStatusWlanStationTableEntry 35 }

-- {COLUMN} 310.1.3.32.1.36
lcsStatusWlanStationTableEntryRxLimit OBJECT-TYPE
    SYNTAX     INTEGER (0..2147483647)
    MAX-ACCESS read-only
    STATUS     current
    DESCRIPTION
        "-- empty --"
    ::= { lcsStatusWlanStationTableEntry 36 }

-- {COLUMN} 310.1.3.32.1.10
lcsStatusWlanStationTableEntryState OBJECT-TYPE
    SYNTAX     INTEGER
      {
        eNone (0),
        eAdhoc (1),
        eAuthenticated (2),
        eConnected (3),
        eAssociated (9),
        eMacCheck (4),
        e1xNegotiation (10),
        eKeyHandshake (8)
      }
    MAX-ACCESS read-only
    STATUS     current
    DESCRIPTION
        "-- empty --"
    ::= { lcsStatusWlanStationTableEntry 10 }

-- {COLUMN} 310.1.3.32.1.40
lcsStatusWlanStationTableEntryMacCheck OBJECT-TYPE
    SYNTAX     INTEGER
      {
        eNone (0),
        eLocal (1),
        eRadius (2)
      }
    MAX-ACCESS read-only
    STATUS     current
    DESCRIPTION
        "-- empty --"
    ::= { lcsStatusWlanStationTableEntry 40 }

-- {COLUMN} 310.1.3.32.1.34
lcsStatusWlanStationTableEntryLastEvent OBJECT-TYPE
    SYNTAX     INTEGER
      {
        eNone (0),
        eAuthSuccess (1),
        eDeauth (2),
        eAssocSuccess (3),
        eReassocSuccess (4),
        eDisassoc (5),
        eRadiusSuccess (6),
        eAuthReject (7),
        eAssocReject (8),
        eKeyhandshakeSuccess (9),
        eKeyhandshakeTimeout (10),
        eKeyhandshakeFailure (11),
        eRadiusReject (12),
        eSupervision (13),
        e8021xSuccess (14),
        e8021xFailure (15),
        eIdleTimeout (16),
        eAdminDeassoc (17),
        eRoamed (18)
      }
    MAX-ACCESS read-only
    STATUS     current
    DESCRIPTION
        "-- empty --"
    ::= { lcsStatusWlanStationTableEntry 34 }

-- {COLUMN} 310.1.3.32.1.44
lcsStatusWlanStationTableEntryLastError OBJECT-TYPE
    SYNTAX     INTEGER
      {
        eNone (0),
        eAuthSuccess (1),
        eDeauth (2),
        eAssocSuccess (3),
        eReassocSuccess (4),
        eDisassoc (5),
        eRadiusSuccess (6),
        eAuthReject (7),
        eAssocReject (8),
        eKeyhandshakeSuccess (9),
        eKeyhandshakeTimeout (10),
        eKeyhandshakeFailure (11),
        eRadiusReject (12),
        eSupervision (13),
        e8021xSuccess (14),
        e8021xFailure (15),
        eIdleTimeout (16),
        eAdminDeassoc (17),
        eRoamed (18)
      }
    MAX-ACCESS read-only
    STATUS     current
    DESCRIPTION
        "-- empty --"
    ::= { lcsStatusWlanStationTableEntry 44 }

-- {COLUMN} 310.1.3.32.1.28
lcsStatusWlanStationTableEntryTxRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanStationTableEntry 28 }

-- {COLUMN} 310.1.3.32.1.13
lcsStatusWlanStationTableEntryRxRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51) -- High throughput 3 streams 195Mbit/s
      }
    MAX-ACCESS read-only
    STATUS     current
    DESCRIPTION
        "-- empty --"
    ::= { lcsStatusWlanStationTableEntry 13 }

-- {COLUMN} 310.1.3.32.1.50
lcsStatusWlanStationTableEntryEffTxRate OBJECT-TYPE
    SYNTAX     INTEGER (0..2147483647)
    MAX-ACCESS read-only
    STATUS     current
    DESCRIPTION
        "-- empty --"
    ::= { lcsStatusWlanStationTableEntry 50 }

-- {COLUMN} 310.1.3.32.1.51
lcsStatusWlanStationTableEntryEffRxRate OBJECT-TYPE
    SYNTAX     INTEGER (0..2147483647)
    MAX-ACCESS read-only
    STATUS     current
    DESCRIPTION
        "-- empty --"
    ::= { lcsStatusWlanStationTableEntry 51 }

-- {COLUMN} 310.1.3.32.1.33
lcsStatusWlanStationTableEntryWpaVersion OBJECT-TYPE
    SYNTAX     INTEGER
      {
        eWpa1 (1),
        eWpa2 (2),
        eNone (0)
      }
    MAX-ACCESS read-only
    STATUS     current
    DESCRIPTION
        "-- empty --"
    ::= { lcsStatusWlanStationTableEntry 33 }

-- {COLUMN} 310.1.3.32.1.37
lcsStatusWlanStationTableEntryQos OBJECT-TYPE
    SYNTAX     INTEGER
      {
        eNo (0),
        eYes (1)
      }
    MAX-ACCESS read-only
    STATUS     current
    DESCRIPTION
        "-- empty --"
    ::= { lcsStatusWlanStationTableEntry 37 }

-- {COLUMN} 310.1.3.32.1.14
lcsStatusWlanStationTableEntryKeyType OBJECT-TYPE
    SYNTAX     INTEGER
      {
        eNone (0),
        eUnknown (1),
        eWep40Bits (5),
        eWep104Bits (13),
        eWep128Bits (16),
        eTkip (64),
        eAesOcb (65),
        eAesCcm (66)
      }
    MAX-ACCESS read-only
    STATUS     current
    DESCRIPTION
        "-- empty --"
    ::= { lcsStatusWlanStationTableEntry 14 }

-- {COLUMN} 310.1.3.32.1.16
lcsStatusWlanStationTableEntryPowerSaving OBJECT-TYPE
    SYNTAX     INTEGER
      {
        eUnknown (0),
        eInactive (1),
        eActive (2)
      }
    MAX-ACCESS read-only
    STATUS     current
    DESCRIPTION
        "-- empty --"
    ::= { lcsStatusWlanStationTableEntry 16 }

-- {COLUMN} 310.1.3.32.1.54
lcsStatusWlanStationTableEntrySmPwrsave OBJECT-TYPE
    SYNTAX     INTEGER
      {
        eInactive (0),
        eDynamic (2),
        eStatic (1)
      }
    MAX-ACCESS read-only
    STATUS     current
    DESCRIPTION
        "-- empty --"
    ::= { lcsStatusWlanStationTableEntry 54 }

-- {COLUMN} 310.1.3.32.1.52
lcsStatusWlanStationTableEntryApsd OBJECT-TYPE
    SYNTAX     BITS
      {
        eBe (7),
        eBk (6),
        eVi (5),
        eVo (4),
        eNo (0)
      }
    MAX-ACCESS read-only
    STATUS     current
    DESCRIPTION
        "-- empty --"
    ::= { lcsStatusWlanStationTableEntry 52 }

-- {COLUMN} 310.1.3.32.1.17
lcsStatusWlanStationTableEntryListenInterval OBJECT-TYPE
    SYNTAX     INTEGER (0..65535)
    MAX-ACCESS read-only
    STATUS     current
    DESCRIPTION
        "-- empty --"
    ::= { lcsStatusWlanStationTableEntry 17 }

-- {COLUMN} 310.1.3.32.1.18
lcsStatusWlanStationTableEntryConnectTime OBJECT-TYPE
    SYNTAX     INTEGER (0..2147483647)
    MAX-ACCESS read-only
    STATUS     current
    DESCRIPTION
        "-- empty --"
    ::= { lcsStatusWlanStationTableEntry 18 }

-- {COLUMN} 310.1.3.32.1.46
lcsStatusWlanStationTableEntry40mhzMode OBJECT-TYPE
    SYNTAX     INTEGER
      {
        eNo (0),
        eYes (1)
      }
    MAX-ACCESS read-only
    STATUS     current
    DESCRIPTION
        "-- empty --"
    ::= { lcsStatusWlanStationTableEntry 46 }

-- {COLUMN} 310.1.3.32.1.58
lcsStatusWlanStationTableEntry40mhzCoexistence OBJECT-TYPE
    SYNTAX     INTEGER
      {
        eNo (0),
        eYes (1)
      }
    MAX-ACCESS read-only
    STATUS     current
    DESCRIPTION
        "-- empty --"
    ::= { lcsStatusWlanStationTableEntry 58 }

-- {COLUMN} 310.1.3.32.1.48
lcsStatusWlanStationTableEntryMaxAMsduLen OBJECT-TYPE
    SYNTAX     INTEGER (0..2147483647)
    MAX-ACCESS read-only
    STATUS     current
    DESCRIPTION
        "-- empty --"
    ::= { lcsStatusWlanStationTableEntry 48 }

-- {COLUMN} 310.1.3.32.1.49
lcsStatusWlanStationTableEntryMaxAMpduLen OBJECT-TYPE
    SYNTAX     INTEGER (0..2147483647)
    MAX-ACCESS read-only
    STATUS     current
    DESCRIPTION
        "-- empty --"
    ::= { lcsStatusWlanStationTableEntry 49 }

-- {COLUMN} 310.1.3.32.1.47
lcsStatusWlanStationTableEntry40mhzIntolerant OBJECT-TYPE
    SYNTAX     INTEGER
      {
        eNo (0),
        eYes (1)
      }
    MAX-ACCESS read-only
    STATUS     current
    DESCRIPTION
        "-- empty --"
    ::= { lcsStatusWlanStationTableEntry 47 }

-- {COLUMN} 310.1.3.32.1.59
lcsStatusWlanStationTableEntry20mhzRequested OBJECT-TYPE
    SYNTAX     INTEGER
      {
        eNo (0),
        eYes (1)
      }
    MAX-ACCESS read-only
    STATUS     current
    DESCRIPTION
        "-- empty --"
    ::= { lcsStatusWlanStationTableEntry 59 }

-- {COLUMN} 310.1.3.32.1.23
lcsStatusWlanStationTableEntryShortPreamble OBJECT-TYPE
    SYNTAX     INTEGER
      {
        eNo (0),
        eYes (1)
      }
    MAX-ACCESS read-only
    STATUS     current
    DESCRIPTION
        "-- empty --"
    ::= { lcsStatusWlanStationTableEntry 23 }

-- {COLUMN} 310.1.3.32.1.21
lcsStatusWlanStationTableEntryShortSlotTime OBJECT-TYPE
    SYNTAX     INTEGER
      {
        eNo (0),
        eYes (1)
      }
    MAX-ACCESS read-only
    STATUS     current
    DESCRIPTION
        "-- empty --"
    ::= { lcsStatusWlanStationTableEntry 21 }

-- {COLUMN} 310.1.3.32.1.45
lcsStatusWlanStationTableEntryShortGuardInterval OBJECT-TYPE
    SYNTAX     INTEGER
      {
        eNo (0),
        e20mhz (1),
        e40mhz (2),
        e2040mhz (3)
      }
    MAX-ACCESS read-only
    STATUS     current
    DESCRIPTION
        "-- empty --"
    ::= { lcsStatusWlanStationTableEntry 45 }

-- {COLUMN} 310.1.3.32.1.32
lcsStatusWlanStationTableEntryClBrgSupport OBJECT-TYPE
    SYNTAX     INTEGER
      {
        eNo (0),
        eYes (1)
      }
    MAX-ACCESS read-only
    STATUS     current
    DESCRIPTION
        "-- empty --"
    ::= { lcsStatusWlanStationTableEntry 32 }

-- {COLUMN} 310.1.3.32.1.27
lcsStatusWlanStationTableEntryIpv4Address OBJECT-TYPE
    SYNTAX     IpAddress
    MAX-ACCESS read-only
    STATUS     current
    DESCRIPTION
        "-- empty --"
    ::= { lcsStatusWlanStationTableEntry 27 }

-- {COLUMN} 310.1.3.32.1.53
lcsStatusWlanStationTableEntryIpv6Address OBJECT-TYPE
    SYNTAX     IpAddress
    MAX-ACCESS read-only
    STATUS     current
    DESCRIPTION
        "-- empty --"
    ::= { lcsStatusWlanStationTableEntry 53 }

-- {COLUMN} 310.1.3.32.1.57
lcsStatusWlanStationTableEntryAlarmState OBJECT-TYPE
    SYNTAX     INTEGER
      {
        ePhySignal (1),
        eTotalRetries (2),
        eTxErrors (4),
        eNo (0)
      }
    MAX-ACCESS read-only
    STATUS     current
    DESCRIPTION
        "-- empty --"
    ::= { lcsStatusWlanStationTableEntry 57 }

-- {SCALAR} 310.1.3.37
lcsStatusWlanDeassocStation OBJECT-TYPE
    SYNTAX     DisplayString
    MAX-ACCESS read-write
    STATUS     current
    DESCRIPTION
        "-- empty --"
    ::= { lcsStatusWlan 37 }

-- {TABLE} 310.1.3.38
lcsStatusWlanIappTableTable OBJECT-TYPE
    SYNTAX     SEQUENCE OF LcsStatusWlanIappTableEntry
    MAX-ACCESS not-accessible
    STATUS     current
    DESCRIPTION
        "-- empty --"
    ::= { lcsStatusWlan 38 }

-- {ENTRY} 310.1.3.38.1
lcsStatusWlanIappTableEntry OBJECT-TYPE
    SYNTAX     LcsStatusWlanIappTableEntry
    MAX-ACCESS not-accessible
    STATUS     current
    DESCRIPTION
        ""
    INDEX {
        lcsStatusWlanIappTableEntryBssid,
        lcsStatusWlanIappTableEntryIpAddress,
        lcsStatusWlanIappTableEntryNetworkName
    }
    ::= { lcsStatusWlanIappTableTable 1 }

-- {SEQUENCE}
LcsStatusWlanIappTableEntry ::= SEQUENCE {
    lcsStatusWlanIappTableEntryBssid MacAddress,
    lcsStatusWlanIappTableEntryIpAddress IpAddress,
    lcsStatusWlanIappTableEntryNetworkName DisplayString,
    lcsStatusWlanIappTableEntryTimer INTEGER,
    lcsStatusWlanIappTableEntryTimeout INTEGER,
    lcsStatusWlanIappTableEntryCapabilities BITS
}

-- {COLUMN} 310.1.3.38.1.2
lcsStatusWlanIappTableEntryBssid OBJECT-TYPE
    SYNTAX     MacAddress
    MAX-ACCESS read-only
    STATUS     current
    DESCRIPTION
        "-- empty --"
    ::= { lcsStatusWlanIappTableEntry 2 }

-- {COLUMN} 310.1.3.38.1.1
lcsStatusWlanIappTableEntryIpAddress OBJECT-TYPE
    SYNTAX     IpAddress
    MAX-ACCESS read-only
    STATUS     current
    DESCRIPTION
        "-- empty --"
    ::= { lcsStatusWlanIappTableEntry 1 }

-- {COLUMN} 310.1.3.38.1.6
lcsStatusWlanIappTableEntryNetworkName OBJECT-TYPE
    SYNTAX     DisplayString (SIZE(0..16))
    MAX-ACCESS read-only
    STATUS     current
    DESCRIPTION
        "-- empty --"
    ::= { lcsStatusWlanIappTableEntry 6 }

-- {COLUMN} 310.1.3.38.1.3
lcsStatusWlanIappTableEntryTimer OBJECT-TYPE
    SYNTAX     INTEGER (0..65535)
    MAX-ACCESS read-only
    STATUS     current
    DESCRIPTION
        "-- empty --"
    ::= { lcsStatusWlanIappTableEntry 3 }

-- {COLUMN} 310.1.3.38.1.4
lcsStatusWlanIappTableEntryTimeout OBJECT-TYPE
    SYNTAX     INTEGER (0..65535)
    MAX-ACCESS read-only
    STATUS     current
    DESCRIPTION
        "-- empty --"
    ::= { lcsStatusWlanIappTableEntry 4 }

-- {COLUMN} 310.1.3.38.1.5
lcsStatusWlanIappTableEntryCapabilities OBJECT-TYPE
    SYNTAX     BITS
      {
        ePrivacy (2),
        eForward (1)
      }
    MAX-ACCESS read-only
    STATUS     current
    DESCRIPTION
        "-- empty --"
    ::= { lcsStatusWlanIappTableEntry 5 }

-- {TABLE} 310.1.3.40
lcsStatusWlanForeignStationsTable OBJECT-TYPE
    SYNTAX     SEQUENCE OF LcsStatusWlanForeignStationsEntry
    MAX-ACCESS not-accessible
    STATUS     current
    DESCRIPTION
        "-- empty --"
    ::= { lcsStatusWlan 40 }

-- {ENTRY} 310.1.3.40.1
lcsStatusWlanForeignStationsEntry OBJECT-TYPE
    SYNTAX     LcsStatusWlanForeignStationsEntry
    MAX-ACCESS not-accessible
    STATUS     current
    DESCRIPTION
        ""
    INDEX {
        lcsStatusWlanForeignStationsEntryMacAddress
    }
    ::= { lcsStatusWlanForeignStationsTable 1 }

-- {SEQUENCE}
LcsStatusWlanForeignStationsEntry ::= SEQUENCE {
    lcsStatusWlanForeignStationsEntryMacAddress MacAddress,
    lcsStatusWlanForeignStationsEntryBssid MacAddress,
    lcsStatusWlanForeignStationsEntryNetworkName DisplayString
}

-- {COLUMN} 310.1.3.40.1.1
lcsStatusWlanForeignStationsEntryMacAddress OBJECT-TYPE
    SYNTAX     MacAddress
    MAX-ACCESS read-only
    STATUS     current
    DESCRIPTION
        "-- empty --"
    ::= { lcsStatusWlanForeignStationsEntry 1 }

-- {COLUMN} 310.1.3.40.1.2
lcsStatusWlanForeignStationsEntryBssid OBJECT-TYPE
    SYNTAX     MacAddress
    MAX-ACCESS read-only
    STATUS     current
    DESCRIPTION
        "-- empty --"
    ::= { lcsStatusWlanForeignStationsEntry 2 }

-- {COLUMN} 310.1.3.40.1.3
lcsStatusWlanForeignStationsEntryNetworkName OBJECT-TYPE
    SYNTAX     DisplayString (SIZE(0..255))
    MAX-ACCESS read-only
    STATUS     current
    DESCRIPTION
        "-- empty --"
    ::= { lcsStatusWlanForeignStationsEntry 3 }

-- {TABLE} 310.1.3.44
lcsStatusWlanCompetingNetworksTable OBJECT-TYPE
    SYNTAX     SEQUENCE OF LcsStatusWlanCompetingNetworksEntry
    MAX-ACCESS not-accessible
    STATUS     current
    DESCRIPTION
        "-- empty --"
    ::= { lcsStatusWlan 44 }

-- {ENTRY} 310.1.3.44.1
lcsStatusWlanCompetingNetworksEntry OBJECT-TYPE
    SYNTAX     LcsStatusWlanCompetingNetworksEntry
    MAX-ACCESS not-accessible
    STATUS     current
    DESCRIPTION
        ""
    INDEX {
        lcsStatusWlanCompetingNetworksEntryBssid,
        lcsStatusWlanCompetingNetworksEntryInterface
    }
    ::= { lcsStatusWlanCompetingNetworksTable 1 }

-- {SEQUENCE}
LcsStatusWlanCompetingNetworksEntry ::= SEQUENCE {
    lcsStatusWlanCompetingNetworksEntryBssid MacAddress,
    lcsStatusWlanCompetingNetworksEntryInterface INTEGER,
    lcsStatusWlanCompetingNetworksEntryVendor DisplayString,
    lcsStatusWlanCompetingNetworksEntryNetworkName DisplayString,
    lcsStatusWlanCompetingNetworksEntryOperationMode INTEGER,
    lcsStatusWlanCompetingNetworksEntryEncryption INTEGER,
    lcsStatusWlanCompetingNetworksEntryPreAuthentication INTEGER,
    lcsStatusWlanCompetingNetworksEntryBeaconPeriod INTEGER,
    lcsStatusWlanCompetingNetworksEntryDtimPeriod INTEGER,
    lcsStatusWlanCompetingNetworksEntryPcfFunctionality INTEGER,
    lcsStatusWlanCompetingNetworksEntryQos INTEGER,
    lcsStatusWlanCompetingNetworksEntryMaxAMpduLen INTEGER,
    lcsStatusWlanCompetingNetworksEntryMaxAMsduLen INTEGER,
    lcsStatusWlanCompetingNetworksEntryRadioBand INTEGER,
    lcsStatusWlanCompetingNetworksEntryRadioChannel INTEGER,
    lcsStatusWlanCompetingNetworksEntry108mbpsMode INTEGER,
    lcsStatusWlanCompetingNetworksEntryExtChannel INTEGER,
    lcsStatusWlanCompetingNetworksEntryPhySignal INTEGER,
    lcsStatusWlanCompetingNetworksEntrySignalLevel INTEGER,
    lcsStatusWlanCompetingNetworksEntryNoiseLevel INTEGER,
    lcsStatusWlanCompetingNetworksEntryLoad DisplayString,
    lcsStatusWlanCompetingNetworksEntryShortPreamble INTEGER,
    lcsStatusWlanCompetingNetworksEntryShortSlotTime INTEGER,
    lcsStatusWlanCompetingNetworksEntry40mhzMode INTEGER,
    lcsStatusWlanCompetingNetworksEntry40mhzCoexistence INTEGER,
    lcsStatusWlanCompetingNetworksEntry40mhzIntolerant INTEGER,
    lcsStatusWlanCompetingNetworksEntryShortGuardInterval INTEGER,
    lcsStatusWlanCompetingNetworksEntryTxStbc INTEGER,
    lcsStatusWlanCompetingNetworksEntryRxStbc INTEGER,
    lcsStatusWlanCompetingNetworksEntryLdpc INTEGER,
    lcsStatusWlanCompetingNetworksEntryCompression INTEGER,
    lcsStatusWlanCompetingNetworksEntryAge INTEGER,
    lcsStatusWlanCompetingNetworksEntryRate INTEGER,
    lcsStatusWlanCompetingNetworksEntryEffRate INTEGER,
    lcsStatusWlanCompetingNetworksEntryNonerpPresent INTEGER,
    lcsStatusWlanCompetingNetworksEntryIdentification DisplayString,
    lcsStatusWlanCompetingNetworksEntryInterpointPeerName DisplayString,
    lcsStatusWlanCompetingNetworksEntryEapolPreauthFailed INTEGER
}

-- {COLUMN} 310.1.3.44.1.1
lcsStatusWlanCompetingNetworksEntryBssid OBJECT-TYPE
    SYNTAX     MacAddress
    MAX-ACCESS read-only
    STATUS     current
    DESCRIPTION
        "-- empty --"
    ::= { lcsStatusWlanCompetingNetworksEntry 1 }

-- {COLUMN} 310.1.3.44.1.15
lcsStatusWlanCompetingNetworksEntryInterface OBJECT-TYPE
    SYNTAX     INTEGER
      {
        eWlan1 (0),
        eWlan2 (1),
        eWlan3 (2),
        eWlan4 (3)
      }
    MAX-ACCESS read-only
    STATUS     current
    DESCRIPTION
        "-- empty --"
    ::= { lcsStatusWlanCompetingNetworksEntry 15 }

-- {COLUMN} 310.1.3.44.1.34
lcsStatusWlanCompetingNetworksEntryVendor OBJECT-TYPE
    SYNTAX     DisplayString (SIZE(0..255))
    MAX-ACCESS read-only
    STATUS     current
    DESCRIPTION
        "-- empty --"
    ::= { lcsStatusWlanCompetingNetworksEntry 34 }

-- {COLUMN} 310.1.3.44.1.2
lcsStatusWlanCompetingNetworksEntryNetworkName OBJECT-TYPE
    SYNTAX     DisplayString (SIZE(0..255))
    MAX-ACCESS read-only
    STATUS     current
    DESCRIPTION
        "-- empty --"
    ::= { lcsStatusWlanCompetingNetworksEntry 2 }

-- {COLUMN} 310.1.3.44.1.3
lcsStatusWlanCompetingNetworksEntryOperationMode OBJECT-TYPE
    SYNTAX     INTEGER
      {
        eNone (0),
        eAdhoc (1),
        eInfrastructure (2) -- lancom's description of Infrastructure
      }
    MAX-ACCESS read-only
    STATUS     current
    DESCRIPTION
        "lancom's description of operation mode"
    ::= { lcsStatusWlanCompetingNetworksEntry 3 }

-- {COLUMN} 310.1.3.44.1.13
lcsStatusWlanCompetingNetworksEntryEncryption OBJECT-TYPE
    SYNTAX     INTEGER
      {
        eNone (0),
        eWep (1),
        eTkip (2),
        eAes (3),
        eAesPlusTkip (4)
      }
    MAX-ACCESS read-only
    STATUS     current
    DESCRIPTION
        "-- empty --"
    ::= { lcsStatusWlanCompetingNetworksEntry 13 }

-- {COLUMN} 310.1.3.44.1.37
lcsStatusWlanCompetingNetworksEntryPreAuthentication OBJECT-TYPE
    SYNTAX     INTEGER
      {
        eNo (0),
        eYes (1)
      }
    MAX-ACCESS read-only
    STATUS     current
    DESCRIPTION
        "-- empty --"
    ::= { lcsStatusWlanCompetingNetworksEntry 37 }

-- {COLUMN} 310.1.3.44.1.6
lcsStatusWlanCompetingNetworksEntryBeaconPeriod OBJECT-TYPE
    SYNTAX     INTEGER (0..65535)
    MAX-ACCESS read-only
    STATUS     current
    DESCRIPTION
        "-- empty --"
    ::= { lcsStatusWlanCompetingNetworksEntry 6 }

-- {COLUMN} 310.1.3.44.1.7
lcsStatusWlanCompetingNetworksEntryDtimPeriod OBJECT-TYPE
    SYNTAX     INTEGER (0..65535)
    MAX-ACCESS read-only
    STATUS     current
    DESCRIPTION
        "-- empty --"
    ::= { lcsStatusWlanCompetingNetworksEntry 7 }

-- {COLUMN} 310.1.3.44.1.22
lcsStatusWlanCompetingNetworksEntryPcfFunctionality OBJECT-TYPE
    SYNTAX     INTEGER
      {
        eNone (0),
        eDelivery (1),
        eDeliveryPlusPolling (2)
      }
    MAX-ACCESS read-only
    STATUS     current
    DESCRIPTION
        "-- empty --"
    ::= { lcsStatusWlanCompetingNetworksEntry 22 }

-- {COLUMN} 310.1.3.44.1.24
lcsStatusWlanCompetingNetworksEntryQos OBJECT-TYPE
    SYNTAX     INTEGER
      {
        eNo (0),
        eYes (1)
      }
    MAX-ACCESS read-only
    STATUS     current
    DESCRIPTION
        "-- empty --"
    ::= { lcsStatusWlanCompetingNetworksEntry 24 }

-- {COLUMN} 310.1.3.44.1.32
lcsStatusWlanCompetingNetworksEntryMaxAMpduLen OBJECT-TYPE
    SYNTAX     INTEGER (0..2147483647)
    MAX-ACCESS read-only
    STATUS     current
    DESCRIPTION
        "-- empty --"
    ::= { lcsStatusWlanCompetingNetworksEntry 32 }

-- {COLUMN} 310.1.3.44.1.33
lcsStatusWlanCompetingNetworksEntryMaxAMsduLen OBJECT-TYPE
    SYNTAX     INTEGER (0..2147483647)
    MAX-ACCESS read-only
    STATUS     current
    DESCRIPTION
        "-- empty --"
    ::= { lcsStatusWlanCompetingNetworksEntry 33 }

-- {COLUMN} 310.1.3.44.1.16
lcsStatusWlanCompetingNetworksEntryRadioBand OBJECT-TYPE
    SYNTAX     INTEGER
      {
        eUnknown (0),
        e24ghz (1),
        e5ghz (2)
      }
    MAX-ACCESS read-only
    STATUS     current
    DESCRIPTION
        "-- empty --"
    ::= { lcsStatusWlanCompetingNetworksEntry 16 }

-- {COLUMN} 310.1.3.44.1.8
lcsStatusWlanCompetingNetworksEntryRadioChannel OBJECT-TYPE
    SYNTAX     INTEGER (0..255)
    MAX-ACCESS read-only
    STATUS     current
    DESCRIPTION
        "-- empty --"
    ::= { lcsStatusWlanCompetingNetworksEntry 8 }

-- {COLUMN} 310.1.3.44.1.17
lcsStatusWlanCompetingNetworksEntry108mbpsMode OBJECT-TYPE
    SYNTAX     INTEGER
      {
        eNo (0),
        eYes (1)
      }
    MAX-ACCESS read-only
    STATUS     current
    DESCRIPTION
        "-- empty --"
    ::= { lcsStatusWlanCompetingNetworksEntry 17 }

-- {COLUMN} 310.1.3.44.1.28
lcsStatusWlanCompetingNetworksEntryExtChannel OBJECT-TYPE
    SYNTAX     INTEGER
      {
        eNone (0),
        eAbove (1),
        eBelow (3)
      }
    MAX-ACCESS read-only
    STATUS     current
    DESCRIPTION
        "-- empty --"
    ::= { lcsStatusWlanCompetingNetworksEntry 28 }

-- {COLUMN} 310.1.3.44.1.10
lcsStatusWlanCompetingNetworksEntryPhySignal OBJECT-TYPE
    SYNTAX     INTEGER (0..65535)
    MAX-ACCESS read-only
    STATUS     current
    DESCRIPTION
        "-- empty --"
    ::= { lcsStatusWlanCompetingNetworksEntry 10 }

-- {COLUMN} 310.1.3.44.1.26
lcsStatusWlanCompetingNetworksEntrySignalLevel OBJECT-TYPE
    SYNTAX     INTEGER (-32768..32767)
    MAX-ACCESS read-only
    STATUS     current
    DESCRIPTION
        "-- empty --"
    ::= { lcsStatusWlanCompetingNetworksEntry 26 }

-- {COLUMN} 310.1.3.44.1.11
lcsStatusWlanCompetingNetworksEntryNoiseLevel OBJECT-TYPE
    SYNTAX     INTEGER (-128..127)
    MAX-ACCESS read-only
    STATUS     current
    DESCRIPTION
        "-- empty --"
    ::= { lcsStatusWlanCompetingNetworksEntry 11 }

-- {COLUMN} 310.1.3.44.1.12
lcsStatusWlanCompetingNetworksEntryLoad OBJECT-TYPE
    SYNTAX     DisplayString (SIZE(0..255))
    MAX-ACCESS read-only
    STATUS     current
    DESCRIPTION
        "-- empty --"
    ::= { lcsStatusWlanCompetingNetworksEntry 12 }

-- {COLUMN} 310.1.3.44.1.14
lcsStatusWlanCompetingNetworksEntryShortPreamble OBJECT-TYPE
    SYNTAX     INTEGER
      {
        eNo (0),
        eYes (1)
      }
    MAX-ACCESS read-only
    STATUS     current
    DESCRIPTION
        "-- empty --"
    ::= { lcsStatusWlanCompetingNetworksEntry 14 }

-- {COLUMN} 310.1.3.44.1.18
lcsStatusWlanCompetingNetworksEntryShortSlotTime OBJECT-TYPE
    SYNTAX     INTEGER
      {
        eNo (0),
        eYes (1)
      }
    MAX-ACCESS read-only
    STATUS     current
    DESCRIPTION
        "-- empty --"
    ::= { lcsStatusWlanCompetingNetworksEntry 18 }

-- {COLUMN} 310.1.3.44.1.29
lcsStatusWlanCompetingNetworksEntry40mhzMode OBJECT-TYPE
    SYNTAX     INTEGER
      {
        eNo (0),
        eYes (1)
      }
    MAX-ACCESS read-only
    STATUS     current
    DESCRIPTION
        "-- empty --"
    ::= { lcsStatusWlanCompetingNetworksEntry 29 }

-- {COLUMN} 310.1.3.44.1.36
lcsStatusWlanCompetingNetworksEntry40mhzCoexistence OBJECT-TYPE
    SYNTAX     INTEGER
      {
        eNo (0),
        eYes (1)
      }
    MAX-ACCESS read-only
    STATUS     current
    DESCRIPTION
        "-- empty --"
    ::= { lcsStatusWlanCompetingNetworksEntry 36 }

-- {COLUMN} 310.1.3.44.1.30
lcsStatusWlanCompetingNetworksEntry40mhzIntolerant OBJECT-TYPE
    SYNTAX     INTEGER
      {
        eNo (0),
        eYes (1)
      }
    MAX-ACCESS read-only
    STATUS     current
    DESCRIPTION
        "-- empty --"
    ::= { lcsStatusWlanCompetingNetworksEntry 30 }

-- {COLUMN} 310.1.3.44.1.27
lcsStatusWlanCompetingNetworksEntryShortGuardInterval OBJECT-TYPE
    SYNTAX     INTEGER
      {
        eNo (0),
        e20mhz (1),
        e40mhz (2),
        e2040mhz (3)
      }
    MAX-ACCESS read-only
    STATUS     current
    DESCRIPTION
        "-- empty --"
    ::= { lcsStatusWlanCompetingNetworksEntry 27 }

-- {COLUMN} 310.1.3.44.1.38
lcsStatusWlanCompetingNetworksEntryTxStbc OBJECT-TYPE
    SYNTAX     INTEGER
      {
        eNo (0),
        eYes (1)
      }
    MAX-ACCESS read-only
    STATUS     current
    DESCRIPTION
        "-- empty --"
    ::= { lcsStatusWlanCompetingNetworksEntry 38 }

-- {COLUMN} 310.1.3.44.1.39
lcsStatusWlanCompetingNetworksEntryRxStbc OBJECT-TYPE
    SYNTAX     INTEGER
      {
        eNone (0),
        eOne (1),
        eTwo (2),
        eThree (3)
      }
    MAX-ACCESS read-only
    STATUS     current
    DESCRIPTION
        "-- empty --"
    ::= { lcsStatusWlanCompetingNetworksEntry 39 }

-- {COLUMN} 310.1.3.44.1.41
lcsStatusWlanCompetingNetworksEntryLdpc OBJECT-TYPE
    SYNTAX     INTEGER
      {
        eNo (0),
        eYes (1)
      }
    MAX-ACCESS read-only
    STATUS     current
    DESCRIPTION
        "-- empty --"
    ::= { lcsStatusWlanCompetingNetworksEntry 41 }

-- {COLUMN} 310.1.3.44.1.21
lcsStatusWlanCompetingNetworksEntryCompression OBJECT-TYPE
    SYNTAX     INTEGER
      {
        eNo (0),
        eYes (1)
      }
    MAX-ACCESS read-only
    STATUS     current
    DESCRIPTION
        "-- empty --"
    ::= { lcsStatusWlanCompetingNetworksEntry 21 }

-- {COLUMN} 310.1.3.44.1.25
lcsStatusWlanCompetingNetworksEntryAge OBJECT-TYPE
    SYNTAX     INTEGER (0..2147483647)
    MAX-ACCESS read-only
    STATUS     current
    DESCRIPTION
        "-- empty --"
    ::= { lcsStatusWlanCompetingNetworksEntry 25 }

-- {COLUMN} 310.1.3.44.1.19
lcsStatusWlanCompetingNetworksEntryRate OBJECT-TYPE
    SYNTAX     INTEGER
      {
        eUnknown (0),
        e1M (1), -- 1Mbit/s
        e2M (2), -- 2Mbit/s
        e5M (3), -- 5Mbit/s
        e5M5 (4), -- 5.5Mbit/s
        e8M (5), -- 8Mbit/s
        e11M (6), -- 11Mbit/s
        e6M (12), -- 6Mbit/s
        e9M (13), -- 9Mbit/s
        e12M (14), -- 12Mbit/s
        e18M (15), -- 18Mbit/s
        e24M (16), -- 24Mbit/s
        e36M (17), -- 36Mbit/s
        e48M (18), -- 48Mbit/s
        e54M (19), -- 54Mbit/s
        eT12M (20), -- Turbo 12Mbit/s
        eT18M (21), -- Turbo 18Mbit/s
        eT24M (22), -- Turbo 24Mbit/s
        eT36M (23), -- Turbo 36Mbit/s
        eT48M (24), -- Turbo 48Mbit/s
        eT72M (25), -- Turbo 72Mbit/s
        eT96M (26), -- Turbo 96Mbit/s
        eT108M (27), -- Turbo 108Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43), -- High throughput 2 streams 130Mbit/s
        eHT3S19M5 (44), -- High throughput 3 streams 19.5Mbit/s
        eHT3S39M (45), -- High throughput 3 streams 39Mbit/s
        eHT3S58M5 (46), -- High throughput 3 streams 58.5Mbit/s
        eHT3S78M (47), -- High throughput 3 streams 78Mbit/s
        eHT3S117M (48), -- High throughput 3 streams 117Mbit/s
        eHT3S156M (49), -- High throughput 3 streams 156Mbit/s
        eHT3S175M5 (50), -- High throughput 3 streams 175.5Mbit/s
        eHT3S195M (51), -- High throughput 3 streams 195Mbit/s
        eHTDUP6M (60) -- High throughput duplicate 6Mbit/s
      }
    MAX-ACCESS read-only
    STATUS     current
    DESCRIPTION
        "-- empty --"
    ::= { lcsStatusWlanCompetingNetworksEntry 19 }

-- {COLUMN} 310.1.3.44.1.35
lcsStatusWlanCompetingNetworksEntryEffRate OBJECT-TYPE
    SYNTAX     INTEGER (0..2147483647)
    MAX-ACCESS read-only
    STATUS     current
    DESCRIPTION
        "-- empty --"
    ::= { lcsStatusWlanCompetingNetworksEntry 35 }

-- {COLUMN} 310.1.3.44.1.20
lcsStatusWlanCompetingNetworksEntryNonerpPresent OBJECT-TYPE
    SYNTAX     INTEGER
      {
        eNo (0),
        eYes (1)
      }
    MAX-ACCESS read-only
    STATUS     current
    DESCRIPTION
        "-- empty --"
    ::= { lcsStatusWlanCompetingNetworksEntry 20 }

-- {COLUMN} 310.1.3.44.1.23
lcsStatusWlanCompetingNetworksEntryIdentification OBJECT-TYPE
    SYNTAX     DisplayString (SIZE(0..16))
    MAX-ACCESS read-only
    STATUS     current
    DESCRIPTION
        "-- empty --"
    ::= { lcsStatusWlanCompetingNetworksEntry 23 }

-- {COLUMN} 310.1.3.44.1.31
lcsStatusWlanCompetingNetworksEntryInterpointPeerName OBJECT-TYPE
    SYNTAX     DisplayString (SIZE(0..16))
    MAX-ACCESS read-only
    STATUS     current
    DESCRIPTION
        "-- empty --"
    ::= { lcsStatusWlanCompetingNetworksEntry 31 }

-- {COLUMN} 310.1.3.44.1.40
lcsStatusWlanCompetingNetworksEntryEapolPreauthFailed OBJECT-TYPE
    SYNTAX     INTEGER
      {
        eNo (0),
        eYes (1)
      }
    MAX-ACCESS read-only
    STATUS     current
    DESCRIPTION
        "-- empty --"
    ::= { lcsStatusWlanCompetingNetworksEntry 40 }

-- {TABLE} 310.1.3.48
lcsStatusWlanRadiusCacheTable OBJECT-TYPE
    SYNTAX     SEQUENCE OF LcsStatusWlanRadiusCacheEntry
    MAX-ACCESS not-accessible
    STATUS     current
    DESCRIPTION
        "-- empty --"
    ::= { lcsStatusWlan 48 }

-- {ENTRY} 310.1.3.48.1
lcsStatusWlanRadiusCacheEntry OBJECT-TYPE
    SYNTAX     LcsStatusWlanRadiusCacheEntry
    MAX-ACCESS not-accessible
    STATUS     current
    DESCRIPTION
        ""
    INDEX {
        lcsStatusWlanRadiusCacheEntryMacAddress
    }
    ::= { lcsStatusWlanRadiusCacheTable 1 }

-- {SEQUENCE}
LcsStatusWlanRadiusCacheEntry ::= SEQUENCE {
    lcsStatusWlanRadiusCacheEntryMacAddress MacAddress,
    lcsStatusWlanRadiusCacheEntryAllowed INTEGER,
    lcsStatusWlanRadiusCacheEntryAge INTEGER
}

-- {COLUMN} 310.1.3.48.1.1
lcsStatusWlanRadiusCacheEntryMacAddress OBJECT-TYPE
    SYNTAX     MacAddress
    MAX-ACCESS read-only
    STATUS     current
    DESCRIPTION
        "-- empty --"
    ::= { lcsStatusWlanRadiusCacheEntry 1 }

-- {COLUMN} 310.1.3.48.1.2
lcsStatusWlanRadiusCacheEntryAllowed OBJECT-TYPE
    SYNTAX     INTEGER
      {
        eNo (0),
        eYes (1)
      }
    MAX-ACCESS read-only
    STATUS     current
    DESCRIPTION
        "-- empty --"
    ::= { lcsStatusWlanRadiusCacheEntry 2 }

-- {COLUMN} 310.1.3.48.1.3
lcsStatusWlanRadiusCacheEntryAge OBJECT-TYPE
    SYNTAX     INTEGER (0..2147483647)
    MAX-ACCESS read-only
    STATUS     current
    DESCRIPTION
        "-- empty --"
    ::= { lcsStatusWlanRadiusCacheEntry 3 }

-- {SCALAR} 310.1.3.100
lcsStatusWlanDfsForceRescan OBJECT-TYPE
    SYNTAX     DisplayString
    MAX-ACCESS read-write
    STATUS     current
    DESCRIPTION
        "-- empty --"
    ::= { lcsStatusWlan 100 }

-- {OID} 310.1.4
lcsStatusWan OBJECT IDENTIFIER ::= { lcsStatus 4 }

-- {TABLE} 310.1.4.1
lcsStatusWanByteTransportTable OBJECT-TYPE
    SYNTAX     SEQUENCE OF LcsStatusWanByteTransportEntry
    MAX-ACCESS not-accessible
    STATUS     current
    DESCRIPTION
        "-- empty --"
    ::= { lcsStatusWan 1 }

-- {ENTRY} 310.1.4.1.1
lcsStatusWanByteTransportEntry OBJECT-TYPE
    SYNTAX     LcsStatusWanByteTransportEntry
    MAX-ACCESS not-accessible
    STATUS     current
    DESCRIPTION
        ""
    INDEX {
        lcsStatusWanByteTransportEntryIfc
    }
    ::= { lcsStatusWanByteTransportTable 1 }

-- {SEQUENCE}
LcsStatusWanByteTransportEntry ::= SEQUENCE {
    lcsStatusWanByteTransportEntryIfc INTEGER,
    lcsStatusWanByteTransportEntryCrxBytes Counter32,
    lcsStatusWanByteTransportEntryRxBytes Counter32,
    lcsStatusWanByteTransportEntryTxBytes Counter32,
    lcsStatusWanByteTransportEntryCtxBytes Counter32
}

-- {COLUMN} 310.1.4.1.1.1
lcsStatusWanByteTransportEntryIfc OBJECT-TYPE
    SYNTAX     INTEGER
      {
        eDslCh1 (1),
        eModem (2)
      }
    MAX-ACCESS read-only
    STATUS     current
    DESCRIPTION
        "-- empty --"
    ::= { lcsStatusWanByteTransportEntry 1 }

-- {COLUMN} 310.1.4.1.1.2
lcsStatusWanByteTransportEntryCrxBytes OBJECT-TYPE
    SYNTAX     Counter32
    MAX-ACCESS read-only
    STATUS     current
    DESCRIPTION
        "-- empty --"
    ::= { lcsStatusWanByteTransportEntry 2 }

-- {COLUMN} 310.1.4.1.1.3
lcsStatusWanByteTransportEntryRxBytes OBJECT-TYPE
    SYNTAX     Counter32
    MAX-ACCESS read-only
    STATUS     current
    DESCRIPTION
        "-- empty --"
    ::= { lcsStatusWanByteTransportEntry 3 }

-- {COLUMN} 310.1.4.1.1.4
lcsStatusWanByteTransportEntryTxBytes OBJECT-TYPE
    SYNTAX     Counter32
    MAX-ACCESS read-only
    STATUS     current
    DESCRIPTION
        "-- empty --"
    ::= { lcsStatusWanByteTransportEntry 4 }

-- {COLUMN} 310.1.4.1.1.5
lcsStatusWanByteTransportEntryCtxBytes OBJECT-TYPE
    SYNTAX     Counter32
    MAX-ACCESS read-only
    STATUS     current
    DESCRIPTION
        "-- empty --"
    ::= { lcsStatusWanByteTransportEntry 5 }

-- {TABLE} 310.1.4.2
lcsStatusWanPacketTransportTable OBJECT-TYPE
    SYNTAX     SEQUENCE OF LcsStatusWanPacketTransportEntry
    MAX-ACCESS not-accessible
    STATUS     current
    DESCRIPTION
        "-- empty --"
    ::= { lcsStatusWan 2 }

-- {ENTRY} 310.1.4.2.1
lcsStatusWanPacketTransportEntry OBJECT-TYPE
    SYNTAX     LcsStatusWanPacketTransportEntry
    MAX-ACCESS not-accessible
    STATUS     current
    DESCRIPTION
        ""
    INDEX {
        lcsStatusWanPacketTransportEntryIfc
    }
    ::= { lcsStatusWanPacketTransportTable 1 }

-- {SEQUENCE}
LcsStatusWanPacketTransportEntry ::= SEQUENCE {
    lcsStatusWanPacketTransportEntryIfc INTEGER,
    lcsStatusWanPacketTransportEntryRx Counter32,
    lcsStatusWanPacketTransportEntryTxTotal Counter32,
    lcsStatusWanPacketTransportEntryTxNormal Counter32,
    lcsStatusWanPacketTransportEntryTxReliable Counter32,
    lcsStatusWanPacketTransportEntryTxUrgent Counter32
}

-- {COLUMN} 310.1.4.2.1.1
lcsStatusWanPacketTransportEntryIfc OBJECT-TYPE
    SYNTAX     INTEGER
      {
        eDslCh1 (1),
        eModem (2)
      }
    MAX-ACCESS read-only
    STATUS     current
    DESCRIPTION
        "-- empty --"
    ::= { lcsStatusWanPacketTransportEntry 1 }

-- {COLUMN} 310.1.4.2.1.2
lcsStatusWanPacketTransportEntryRx OBJECT-TYPE
    SYNTAX     Counter32
    MAX-ACCESS read-only
    STATUS     current
    DESCRIPTION
        "-- empty --"
    ::= { lcsStatusWanPacketTransportEntry 2 }

-- {COLUMN} 310.1.4.2.1.3
lcsStatusWanPacketTransportEntryTxTotal OBJECT-TYPE
    SYNTAX     Counter32
    MAX-ACCESS read-only
    STATUS     current
    DESCRIPTION
        "-- empty --"
    ::= { lcsStatusWanPacketTransportEntry 3 }

-- {COLUMN} 310.1.4.2.1.4
lcsStatusWanPacketTransportEntryTxNormal OBJECT-TYPE
    SYNTAX     Counter32
    MAX-ACCESS read-only
    STATUS     current
    DESCRIPTION
        "-- empty --"
    ::= { lcsStatusWanPacketTransportEntry 4 }

-- {COLUMN} 310.1.4.2.1.5
lcsStatusWanPacketTransportEntryTxReliable OBJECT-TYPE
    SYNTAX     Counter32
    MAX-ACCESS read-only
    STATUS     current
    DESCRIPTION
        "-- empty --"
    ::= { lcsStatusWanPacketTransportEntry 5 }

-- {COLUMN} 310.1.4.2.1.6
lcsStatusWanPacketTransportEntryTxUrgent OBJECT-TYPE
    SYNTAX     Counter32
    MAX-ACCESS read-only
    STATUS     current
    DESCRIPTION
        "-- empty --"
    ::= { lcsStatusWanPacketTransportEntry 6 }

-- {TABLE} 310.1.4.3
lcsStatusWanErrorsTable OBJECT-TYPE
    SYNTAX     SEQUENCE OF LcsStatusWanErrorsEntry
    MAX-ACCESS not-accessible
    STATUS     current
    DESCRIPTION
        "-- empty --"
    ::= { lcsStatusWan 3 }

-- {ENTRY} 310.1.4.3.1
lcsStatusWanErrorsEntry OBJECT-TYPE
    SYNTAX     LcsStatusWanErrorsEntry
    MAX-ACCESS not-accessible
    STATUS     current
    DESCRIPTION
        ""
    INDEX {
        lcsStatusWanErrorsEntryIfc
    }
    ::= { lcsStatusWanErrorsTable 1 }

-- {SEQUENCE}
LcsStatusWanErrorsEntry ::= SEQUENCE {
    lcsStatusWanErrorsEntryIfc INTEGER,
    lcsStatusWanErrorsEntryRxL1Error Counter32,
    lcsStatusWanErrorsEntryRxL2Error Counter32,
    lcsStatusWanErrorsEntryRxL3Error Counter32,
    lcsStatusWanErrorsEntryStackError Counter32,
    lcsStatusWanErrorsEntryTxError Counter32,
    lcsStatusWanErrorsEntryQueueErrors Counter32
}

-- {COLUMN} 310.1.4.3.1.1
lcsStatusWanErrorsEntryIfc OBJECT-TYPE
    SYNTAX     INTEGER
      {
        eDslCh1 (1),
        eModem (2)
      }
    MAX-ACCESS read-only
    STATUS     current
    DESCRIPTION
        "-- empty --"
    ::= { lcsStatusWanErrorsEntry 1 }

-- {COLUMN} 310.1.4.3.1.2
lcsStatusWanErrorsEntryRxL1Error OBJECT-TYPE
    SYNTAX     Counter32
    MAX-ACCESS read-only
    STATUS     current
    DESCRIPTION
        "-- empty --"
    ::= { lcsStatusWanErrorsEntry 2 }

-- {COLUMN} 310.1.4.3.1.3
lcsStatusWanErrorsEntryRxL2Error OBJECT-TYPE
    SYNTAX     Counter32
    MAX-ACCESS read-only
    STATUS     current
    DESCRIPTION
        "-- empty --"
    ::= { lcsStatusWanErrorsEntry 3 }

-- {COLUMN} 310.1.4.3.1.4
lcsStatusWanErrorsEntryRxL3Error OBJECT-TYPE
    SYNTAX     Counter32
    MAX-ACCESS read-only
    STATUS     current
    DESCRIPTION
        "-- empty --"
    ::= { lcsStatusWanErrorsEntry 4 }

-- {COLUMN} 310.1.4.3.1.5
lcsStatusWanErrorsEntryStackError OBJECT-TYPE
    SYNTAX     Counter32
    MAX-ACCESS read-only
    STATUS     current
    DESCRIPTION
        "-- empty --"
    ::= { lcsStatusWanErrorsEntry 5 }

-- {COLUMN} 310.1.4.3.1.6
lcsStatusWanErrorsEntryTxError OBJECT-TYPE
    SYNTAX     Counter32
    MAX-ACCESS read-only
    STATUS     current
    DESCRIPTION
        "-- empty --"
    ::= { lcsStatusWanErrorsEntry 6 }

-- {COLUMN} 310.1.4.3.1.7
lcsStatusWanErrorsEntryQueueErrors OBJECT-TYPE
    SYNTAX     Counter32
    MAX-ACCESS read-only
    STATUS     current
    DESCRIPTION
        "-- empty --"
    ::= { lcsStatusWanErrorsEntry 7 }

-- {SCALAR} 310.1.4.4
lcsStatusWanWanTxDiscarded OBJECT-TYPE
    SYNTAX     Counter32
    MAX-ACCESS read-only
    STATUS     current
    DESCRIPTION
        "-- empty --"
    ::= { lcsStatusWan 4 }

-- {SCALAR} 310.1.4.5
lcsStatusWanWanHeapPackets OBJECT-TYPE
    SYNTAX     INTEGER (0..2147483647)
    MAX-ACCESS read-only
    STATUS     current
    DESCRIPTION
        "-- empty --"
    ::= { lcsStatusWan 5 }

-- {SCALAR} 310.1.4.6
lcsStatusWanWanQueuePackets OBJECT-TYPE
    SYNTAX     INTEGER (0..2147483647)
    MAX-ACCESS read-only
    STATUS     current
    DESCRIPTION
        "-- empty --"
    ::= { lcsStatusWan 6 }

-- {SCALAR} 310.1.4.7
lcsStatusWanWanQueueErrors OBJECT-TYPE
    SYNTAX     Counter32
    MAX-ACCESS read-only
    STATUS     current
    DESCRIPTION
        "-- empty --"
    ::= { lcsStatusWan 7 }

-- {SCALAR} 310.1.4.21
lcsStatusWanWanQueueMgtDrop OBJECT-TYPE
    SYNTAX     Counter32
    MAX-ACCESS read-only
    STATUS     current
    DESCRIPTION
        "-- empty --"
    ::= { lcsStatusWan 21 }

-- {TABLE} 310.1.4.8
lcsStatusWanThroughputTable OBJECT-TYPE
    SYNTAX     SEQUENCE OF LcsStatusWanThroughputEntry
    MAX-ACCESS not-accessible
    STATUS     current
    DESCRIPTION
        "-- empty --"
    ::= { lcsStatusWan 8 }

-- {ENTRY} 310.1.4.8.1
lcsStatusWanThroughputEntry OBJECT-TYPE
    SYNTAX     LcsStatusWanThroughputEntry
    MAX-ACCESS not-accessible
    STATUS     current
    DESCRIPTION
        ""
    INDEX {
        lcsStatusWanThroughputEntryIfc
    }
    ::= { lcsStatusWanThroughputTable 1 }

-- {SEQUENCE}
LcsStatusWanThroughputEntry ::= SEQUENCE {
    lcsStatusWanThroughputEntryIfc INTEGER,
    lcsStatusWanThroughputEntryRxSCurrent INTEGER,
    lcsStatusWanThroughputEntryTxSCurrent INTEGER,
    lcsStatusWanThroughputEntryRxSAverage INTEGER,
    lcsStatusWanThroughputEntryTxSAverage INTEGER
}

-- {COLUMN} 310.1.4.8.1.1
lcsStatusWanThroughputEntryIfc OBJECT-TYPE
    SYNTAX     INTEGER
      {
        eDslCh1 (1),
        eModem (2)
      }
    MAX-ACCESS read-only
    STATUS     current
    DESCRIPTION
        "-- empty --"
    ::= { lcsStatusWanThroughputEntry 1 }

-- {COLUMN} 310.1.4.8.1.2
lcsStatusWanThroughputEntryRxSCurrent OBJECT-TYPE
    SYNTAX     INTEGER (0..2147483647)
    MAX-ACCESS read-only
    STATUS     current
    DESCRIPTION
        "-- empty --"
    ::= { lcsStatusWanThroughputEntry 2 }

-- {COLUMN} 310.1.4.8.1.3
lcsStatusWanThroughputEntryTxSCurrent OBJECT-TYPE
    SYNTAX     INTEGER (0..2147483647)
    MAX-ACCESS read-only
    STATUS     current
    DESCRIPTION
        "-- empty --"
    ::= { lcsStatusWanThroughputEntry 3 }

-- {COLUMN} 310.1.4.8.1.4
lcsStatusWanThroughputEntryRxSAverage OBJECT-TYPE
    SYNTAX     INTEGER (0..2147483647)
    MAX-ACCESS read-only
    STATUS     current
    DESCRIPTION
        "-- empty --"
    ::= { lcsStatusWanThroughputEntry 4 }

-- {COLUMN} 310.1.4.8.1.5
lcsStatusWanThroughputEntryTxSAverage OBJECT-TYPE
    SYNTAX     INTEGER (0..2147483647)
    MAX-ACCESS read-only
    STATUS     current
    DESCRIPTION
        "-- empty --"
    ::= { lcsStatusWanThroughputEntry 5 }

-- {SCALAR} 310.1.4.9
lcsStatusWanDeleteValues OBJECT-TYPE
    SYNTAX     DisplayString
    MAX-ACCESS read-write
    STATUS     current
    DESCRIPTION
        "-- empty --"
    ::= { lcsStatusWan 9 }

-- {SCALAR} 310.1.4.10
lcsStatusWanConnections OBJECT-TYPE
    SYNTAX     INTEGER (0..2147483647)
    MAX-ACCESS read-only
    STATUS     current
    DESCRIPTION
        "-- empty --"
    ::= { lcsStatusWan 10 }

-- {TABLE} 310.1.4.11
lcsStatusWanMtuTable OBJECT-TYPE
    SYNTAX     SEQUENCE OF LcsStatusWanMtuEntry
    MAX-ACCESS not-accessible
    STATUS     current
    DESCRIPTION
        "-- empty --"
    ::= { lcsStatusWan 11 }

-- {ENTRY} 310.1.4.11.1
lcsStatusWanMtuEntry OBJECT-TYPE
    SYNTAX     LcsStatusWanMtuEntry
    MAX-ACCESS not-accessible
    STATUS     current
    DESCRIPTION
        ""
    INDEX {
        lcsStatusWanMtuEntryPeer
    }
    ::= { lcsStatusWanMtuTable 1 }

-- {SEQUENCE}
LcsStatusWanMtuEntry ::= SEQUENCE {
    lcsStatusWanMtuEntryPeer DisplayString,
    lcsStatusWanMtuEntryMtu INTEGER
}

-- {COLUMN} 310.1.4.11.1.1
lcsStatusWanMtuEntryPeer OBJECT-TYPE
    SYNTAX     DisplayString (SIZE(0..16))
    MAX-ACCESS read-only
    STATUS     current
    DESCRIPTION
        "-- empty --"
    ::= { lcsStatusWanMtuEntry 1 }

-- {COLUMN} 310.1.4.11.1.2
lcsStatusWanMtuEntryMtu OBJECT-TYPE
    SYNTAX     INTEGER (0..65535)
    MAX-ACCESS read-only
    STATUS     current
    DESCRIPTION
        "-- empty --"
    ::= { lcsStatusWanMtuEntry 2 }

-- {OID} 310.1.4.20
lcsStatusWanActions OBJECT IDENTIFIER ::= { lcsStatusWan 20 }

-- {TABLE} 310.1.4.20.1
lcsStatusWanActionsActionTableTable OBJECT-TYPE
    SYNTAX     SEQUENCE OF LcsStatusWanActionsActionTableEntry
    MAX-ACCESS not-accessible
    STATUS     current
    DESCRIPTION
        "-- empty --"
    ::= { lcsStatusWanActions 1 }

-- {ENTRY} 310.1.4.20.1.1
lcsStatusWanActionsActionTableEntry OBJECT-TYPE
    SYNTAX     LcsStatusWanActionsActionTableEntry
    MAX-ACCESS not-accessible
    STATUS     current
    DESCRIPTION
        ""
    INDEX {
        lcsStatusWanActionsActionTableEntryTime
    }
    ::= { lcsStatusWanActionsActionTableTable 1 }

-- {SEQUENCE}
LcsStatusWanActionsActionTableEntry ::= SEQUENCE {
    lcsStatusWanActionsActionTableEntryTime DisplayString,
    lcsStatusWanActionsActionTableEntryAction DisplayString,
    lcsStatusWanActionsActionTableEntryResult DisplayString
}

-- {COLUMN} 310.1.4.20.1.1.1
lcsStatusWanActionsActionTableEntryTime OBJECT-TYPE
    SYNTAX     DisplayString (SIZE(0..19))
    MAX-ACCESS read-only
    STATUS     current
    DESCRIPTION
        "-- empty --"
    ::= { lcsStatusWanActionsActionTableEntry 1 }

-- {COLUMN} 310.1.4.20.1.1.2
lcsStatusWanActionsActionTableEntryAction OBJECT-TYPE
    SYNTAX     DisplayString (SIZE(0..255))
    MAX-ACCESS read-only
    STATUS     current
    DESCRIPTION
        "-- empty --"
    ::= { lcsStatusWanActionsActionTableEntry 2 }

-- {COLUMN} 310.1.4.20.1.1.3
lcsStatusWanActionsActionTableEntryResult OBJECT-TYPE
    SYNTAX     DisplayString (SIZE(0..100))
    MAX-ACCESS read-only
    STATUS     current
    DESCRIPTION
        "-- empty --"
    ::= { lcsStatusWanActionsActionTableEntry 3 }

-- {TABLE} 310.1.4.20.2
lcsStatusWanActionsLockTableTable OBJECT-TYPE
    SYNTAX     SEQUENCE OF LcsStatusWanActionsLockTableEntry
    MAX-ACCESS not-accessible
    STATUS     current
    DESCRIPTION
        "-- empty --"
    ::= { lcsStatusWanActions 2 }

-- {ENTRY} 310.1.4.20.2.1
lcsStatusWanActionsLockTableEntry OBJECT-TYPE
    SYNTAX     LcsStatusWanActionsLockTableEntry
    MAX-ACCESS not-accessible
    STATUS     current
    DESCRIPTION
        ""
    INDEX {
        lcsStatusWanActionsLockTableEntryIndex
    }
    ::= { lcsStatusWanActionsLockTableTable 1 }

-- {SEQUENCE}
LcsStatusWanActionsLockTableEntry ::= SEQUENCE {
    lcsStatusWanActionsLockTableEntryIndex INTEGER,
    lcsStatusWanActionsLockTableEntryRemainingLocktime INTEGER
}

-- {COLUMN} 310.1.4.20.2.1.1
lcsStatusWanActionsLockTableEntryIndex OBJECT-TYPE
    SYNTAX     INTEGER (0..65535)
    MAX-ACCESS read-only
    STATUS     current
    DESCRIPTION
        "-- empty --"
    ::= { lcsStatusWanActionsLockTableEntry 1 }

-- {COLUMN} 310.1.4.20.2.1.2
lcsStatusWanActionsLockTableEntryRemainingLocktime OBJECT-TYPE
    SYNTAX     INTEGER (0..2147483647)
    MAX-ACCESS read-only
    STATUS     current
    DESCRIPTION
        "-- empty --"
    ::= { lcsStatusWanActionsLockTableEntry 2 }

-- {OID} 310.1.5
lcsStatusLan OBJECT IDENTIFIER ::= { lcsStatus 5 }

-- {SCALAR} 310.1.5.7
lcsStatusLanLanHeapPackets OBJECT-TYPE
    SYNTAX     INTEGER (0..2147483647)
    MAX-ACCESS read-only
    STATUS     current
    DESCRIPTION
        "-- empty --"
    ::= { lcsStatusLan 7 }

-- {SCALAR} 310.1.5.11
lcsStatusLanDeleteValues OBJECT-TYPE
    SYNTAX     DisplayString
    MAX-ACCESS read-write
    STATUS     current
    DESCRIPTION
        "-- empty --"
    ::= { lcsStatusLan 11 }

-- {SCALAR} 310.1.5.60
lcsStatusLanLanQueueMgtDrop OBJECT-TYPE
    SYNTAX     Counter32
    MAX-ACCESS read-only
    STATUS     current
    DESCRIPTION
        "-- empty --"
    ::= { lcsStatusLan 60 }

-- {OID} 310.1.5.80
lcsStatusLanIeee8021x OBJECT IDENTIFIER ::= { lcsStatusLan 80 }

-- {TABLE} 310.1.5.80.1
lcsStatusLanIeee8021xSupplicantIfcStateTable OBJECT-TYPE
    SYNTAX     SEQUENCE OF LcsStatusLanIeee8021xSupplicantIfcStateEntry
    MAX-ACCESS not-accessible
    STATUS     current
    DESCRIPTION
        "-- empty --"
    ::= { lcsStatusLanIeee8021x 1 }

-- {ENTRY} 310.1.5.80.1.1
lcsStatusLanIeee8021xSupplicantIfcStateEntry OBJECT-TYPE
    SYNTAX     LcsStatusLanIeee8021xSupplicantIfcStateEntry
    MAX-ACCESS not-accessible
    STATUS     current
    DESCRIPTION
        ""
    INDEX {
        lcsStatusLanIeee8021xSupplicantIfcStateEntryIfc
    }
    ::= { lcsStatusLanIeee8021xSupplicantIfcStateTable 1 }

-- {SEQUENCE}
LcsStatusLanIeee8021xSupplicantIfcStateEntry ::= SEQUENCE {
    lcsStatusLanIeee8021xSupplicantIfcStateEntryIfc INTEGER,
    lcsStatusLanIeee8021xSupplicantIfcStateEntryMethod INTEGER,
    lcsStatusLanIeee8021xSupplicantIfcStateEntryState INTEGER,
    lcsStatusLanIeee8021xSupplicantIfcStateEntryAuthenticatorAddress MacAddress
}

-- {COLUMN} 310.1.5.80.1.1.1
lcsStatusLanIeee8021xSupplicantIfcStateEntryIfc OBJECT-TYPE
    SYNTAX     INTEGER
      {
        eLan1 (1)
      }
    MAX-ACCESS read-only
    STATUS     current
    DESCRIPTION
        "-- empty --"
    ::= { lcsStatusLanIeee8021xSupplicantIfcStateEntry 1 }

-- {COLUMN} 310.1.5.80.1.1.2
lcsStatusLanIeee8021xSupplicantIfcStateEntryMethod OBJECT-TYPE
    SYNTAX     INTEGER
      {
        eNone (0),
        eMd5 (1024),
        eTls (3328),
        eTtlsPap (5383),
        eTtlsChap (5384),
        eTtlsMschap (5567),
        eTtlsMschapv2 (5402),
        eTtlsMd5 (5380),
        ePeapMschapv2 (6426),
        ePeapGtc (6406)
      }
    MAX-ACCESS read-only
    STATUS     current
    DESCRIPTION
        "-- empty --"
    ::= { lcsStatusLanIeee8021xSupplicantIfcStateEntry 2 }

-- {COLUMN} 310.1.5.80.1.1.3
lcsStatusLanIeee8021xSupplicantIfcStateEntryState OBJECT-TYPE
    SYNTAX     INTEGER
      {
        eIdle (0),
        eUnauthorized (1),
        eAuthorized (2)
      }
    MAX-ACCESS read-only
    STATUS     current
    DESCRIPTION
        "-- empty --"
    ::= { lcsStatusLanIeee8021xSupplicantIfcStateEntry 3 }

-- {COLUMN} 310.1.5.80.1.1.4
lcsStatusLanIeee8021xSupplicantIfcStateEntryAuthenticatorAddress OBJECT-TYPE
    SYNTAX     MacAddress
    MAX-ACCESS read-only
    STATUS     current
    DESCRIPTION
        "-- empty --"
    ::= { lcsStatusLanIeee8021xSupplicantIfcStateEntry 4 }

-- {TABLE} 310.1.5.51
lcsStatusLanInterfacesTable OBJECT-TYPE
    SYNTAX     SEQUENCE OF LcsStatusLanInterfacesEntry
    MAX-ACCESS not-accessible
    STATUS     current
    DESCRIPTION
        "-- empty --"
    ::= { lcsStatusLan 51 }

-- {ENTRY} 310.1.5.51.1
lcsStatusLanInterfacesEntry OBJECT-TYPE
    SYNTAX     LcsStatusLanInterfacesEntry
    MAX-ACCESS not-accessible
    STATUS     current
    DESCRIPTION
        ""
    INDEX {
        lcsStatusLanInterfacesEntryIfc
    }
    ::= { lcsStatusLanInterfacesTable 1 }

-- {SEQUENCE}
LcsStatusLanInterfacesEntry ::= SEQUENCE {
    lcsStatusLanInterfacesEntryIfc DisplayString,
    lcsStatusLanInterfacesEntryQueuePackets INTEGER,
    lcsStatusLanInterfacesEntryLinkActive INTEGER,
    lcsStatusLanInterfacesEntryConnector INTEGER,
    lcsStatusLanInterfacesEntryAutoNegotiation INTEGER,
    lcsStatusLanInterfacesEntryFlowControl INTEGER,
    lcsStatusLanInterfacesEntryMdiMode INTEGER,
    lcsStatusLanInterfacesEntryRemoteFault INTEGER,
    lcsStatusLanInterfacesEntryClockRole INTEGER
}

-- {COLUMN} 310.1.5.51.1.1
lcsStatusLanInterfacesEntryIfc OBJECT-TYPE
    SYNTAX     DisplayString (SIZE(0..255))
    MAX-ACCESS read-only
    STATUS     current
    DESCRIPTION
        "-- empty --"
    ::= { lcsStatusLanInterfacesEntry 1 }

-- {COLUMN} 310.1.5.51.1.2
lcsStatusLanInterfacesEntryQueuePackets OBJECT-TYPE
    SYNTAX     INTEGER (0..2147483647)
    MAX-ACCESS read-only
    STATUS     current
    DESCRIPTION
        "-- empty --"
    ::= { lcsStatusLanInterfacesEntry 2 }

-- {COLUMN} 310.1.5.51.1.3
lcsStatusLanInterfacesEntryLinkActive OBJECT-TYPE
    SYNTAX     INTEGER
      {
        eNo (0),
        eYes (1)
      }
    MAX-ACCESS read-only
    STATUS     current
    DESCRIPTION
        "-- empty --"
    ::= { lcsStatusLanInterfacesEntry 3 }

-- {COLUMN} 310.1.5.51.1.4
lcsStatusLanInterfacesEntryConnector OBJECT-TYPE
    SYNTAX     INTEGER
      {
        eNone (0),
        e10b2 (33),
        e10b5 (34),
        e10bT (1),
        eFd10bTx (2),
        e100bTx (3),
        eFd100bTx (4),
        eFd1000bTx (6),
        eFd1000bF (70),
        ePowerDown (255)
      }
    MAX-ACCESS read-only
    STATUS     current
    DESCRIPTION
        "-- empty --"
    ::= { lcsStatusLanInterfacesEntry 4 }

-- {COLUMN} 310.1.5.51.1.8
lcsStatusLanInterfacesEntryAutoNegotiation OBJECT-TYPE
    SYNTAX     INTEGER
      {
        ePending (0),
        eCompleted (1),
        eDisabled (2),
        eNotAvailable (3)
      }
    MAX-ACCESS read-only
    STATUS     current
    DESCRIPTION
        "-- empty --"
    ::= { lcsStatusLanInterfacesEntry 8 }

-- {COLUMN} 310.1.5.51.1.6
lcsStatusLanInterfacesEntryFlowControl OBJECT-TYPE
    SYNTAX     INTEGER
      {
        eNo (0),
        eYes (1)
      }
    MAX-ACCESS read-only
    STATUS     current
    DESCRIPTION
        "-- empty --"
    ::= { lcsStatusLanInterfacesEntry 6 }

-- {COLUMN} 310.1.5.51.1.7
lcsStatusLanInterfacesEntryMdiMode OBJECT-TYPE
    SYNTAX     INTEGER
      {
        eUnknown (0),
        eMdi (1),
        eMdix (2),
        eNotApplicable (3)
      }
    MAX-ACCESS read-only
    STATUS     current
    DESCRIPTION
        "-- empty --"
    ::= { lcsStatusLanInterfacesEntry 7 }

-- {COLUMN} 310.1.5.51.1.11
lcsStatusLanInterfacesEntryRemoteFault OBJECT-TYPE
    SYNTAX     INTEGER
      {
        eNo (0),
        eYes (1)
      }
    MAX-ACCESS read-only
    STATUS     current
    DESCRIPTION
        "-- empty --"
    ::= { lcsStatusLanInterfacesEntry 11 }

-- {COLUMN} 310.1.5.51.1.10
lcsStatusLanInterfacesEntryClockRole OBJECT-TYPE
    SYNTAX     INTEGER
      {
        eNone (0),
        eMaster (1),
        eSlave (2),
        eFault (3)
      }
    MAX-ACCESS read-only
    STATUS     current
    DESCRIPTION
        "-- empty --"
    ::= { lcsStatusLanInterfacesEntry 10 }

-- {TABLE} 310.1.5.52
lcsStatusLanByteTransportTable OBJECT-TYPE
    SYNTAX     SEQUENCE OF LcsStatusLanByteTransportEntry
    MAX-ACCESS not-accessible
    STATUS     current
    DESCRIPTION
        "-- empty --"
    ::= { lcsStatusLan 52 }

-- {ENTRY} 310.1.5.52.1
lcsStatusLanByteTransportEntry OBJECT-TYPE
    SYNTAX     LcsStatusLanByteTransportEntry
    MAX-ACCESS not-accessible
    STATUS     current
    DESCRIPTION
        ""
    INDEX {
        lcsStatusLanByteTransportEntryIfc
    }
    ::= { lcsStatusLanByteTransportTable 1 }

-- {SEQUENCE}
LcsStatusLanByteTransportEntry ::= SEQUENCE {
    lcsStatusLanByteTransportEntryIfc DisplayString,
    lcsStatusLanByteTransportEntryTxBytes Counter64,
    lcsStatusLanByteTransportEntryRxBytes Counter64,
    lcsStatusLanByteTransportEntryThroughput DisplayString,
    lcsStatusLanByteTransportEntryMaxThroughput DisplayString,
    lcsStatusLanByteTransportEntryBytesThroughput INTEGER,
    lcsStatusLanByteTransportEntryBytesMaxThroughput INTEGER
}

-- {COLUMN} 310.1.5.52.1.1
lcsStatusLanByteTransportEntryIfc OBJECT-TYPE
    SYNTAX     DisplayString (SIZE(0..255))
    MAX-ACCESS read-only
    STATUS     current
    DESCRIPTION
        "-- empty --"
    ::= { lcsStatusLanByteTransportEntry 1 }

-- {COLUMN} 310.1.5.52.1.2
lcsStatusLanByteTransportEntryTxBytes OBJECT-TYPE
    SYNTAX     Counter64
    MAX-ACCESS read-only
    STATUS     current
    DESCRIPTION
        "-- empty --"
    ::= { lcsStatusLanByteTransportEntry 2 }

-- {COLUMN} 310.1.5.52.1.3
lcsStatusLanByteTransportEntryRxBytes OBJECT-TYPE
    SYNTAX     Counter64
    MAX-ACCESS read-only
    STATUS     current
    DESCRIPTION
        "-- empty --"
    ::= { lcsStatusLanByteTransportEntry 3 }

-- {COLUMN} 310.1.5.52.1.4
lcsStatusLanByteTransportEntryThroughput OBJECT-TYPE
    SYNTAX     DisplayString (SIZE(0..255))
    MAX-ACCESS read-only
    STATUS     current
    DESCRIPTION
        "-- empty --"
    ::= { lcsStatusLanByteTransportEntry 4 }

-- {COLUMN} 310.1.5.52.1.5
lcsStatusLanByteTransportEntryMaxThroughput OBJECT-TYPE
    SYNTAX     DisplayString (SIZE(0..255))
    MAX-ACCESS read-only
    STATUS     current
    DESCRIPTION
        "-- empty --"
    ::= { lcsStatusLanByteTransportEntry 5 }

-- {COLUMN} 310.1.5.52.1.6
lcsStatusLanByteTransportEntryBytesThroughput OBJECT-TYPE
    SYNTAX     INTEGER (0..2147483647)
    MAX-ACCESS read-only
    STATUS     current
    DESCRIPTION
        "-- empty --"
    ::= { lcsStatusLanByteTransportEntry 6 }

-- {COLUMN} 310.1.5.52.1.7
lcsStatusLanByteTransportEntryBytesMaxThroughput OBJECT-TYPE
    SYNTAX     INTEGER (0..2147483647)
    MAX-ACCESS read-only
    STATUS     current
    DESCRIPTION
        "-- empty --"
    ::= { lcsStatusLanByteTransportEntry 7 }

-- {TABLE} 310.1.5.53
lcsStatusLanPacketTransportTable OBJECT-TYPE
    SYNTAX     SEQUENCE OF LcsStatusLanPacketTransportEntry
    MAX-ACCESS not-accessible
    STATUS     current
    DESCRIPTION
        "-- empty --"
    ::= { lcsStatusLan 53 }

-- {ENTRY} 310.1.5.53.1
lcsStatusLanPacketTransportEntry OBJECT-TYPE
    SYNTAX     LcsStatusLanPacketTransportEntry
    MAX-ACCESS not-accessible
    STATUS     current
    DESCRIPTION
        ""
    INDEX {
        lcsStatusLanPacketTransportEntryIfc
    }
    ::= { lcsStatusLanPacketTransportTable 1 }

-- {SEQUENCE}
LcsStatusLanPacketTransportEntry ::= SEQUENCE {
    lcsStatusLanPacketTransportEntryIfc DisplayString,
    lcsStatusLanPacketTransportEntryRxPackets Counter32,
    lcsStatusLanPacketTransportEntryTxPackets Counter32,
    lcsStatusLanPacketTransportEntryRxBroadcasts Counter32,
    lcsStatusLanPacketTransportEntryRxMulticasts Counter32,
    lcsStatusLanPacketTransportEntryRxUnicasts Counter32,
    lcsStatusLanPacketTransportEntryTxBroadcasts Counter32,
    lcsStatusLanPacketTransportEntryTxMulticasts Counter32,
    lcsStatusLanPacketTransportEntryTxUnicasts Counter32
}

-- {COLUMN} 310.1.5.53.1.1
lcsStatusLanPacketTransportEntryIfc OBJECT-TYPE
    SYNTAX     DisplayString (SIZE(0..255))
    MAX-ACCESS read-only
    STATUS     current
    DESCRIPTION
        "-- empty --"
    ::= { lcsStatusLanPacketTransportEntry 1 }

-- {COLUMN} 310.1.5.53.1.2
lcsStatusLanPacketTransportEntryRxPackets OBJECT-TYPE
    SYNTAX     Counter32
    MAX-ACCESS read-only
    STATUS     current
    DESCRIPTION
        "-- empty --"
    ::= { lcsStatusLanPacketTransportEntry 2 }

-- {COLUMN} 310.1.5.53.1.3
lcsStatusLanPacketTransportEntryTxPackets OBJECT-TYPE
    SYNTAX     Counter32
    MAX-ACCESS read-only
    STATUS     current
    DESCRIPTION
        "-- empty --"
    ::= { lcsStatusLanPacketTransportEntry 3 }

-- {COLUMN} 310.1.5.53.1.4
lcsStatusLanPacketTransportEntryRxBroadcasts OBJECT-TYPE
    SYNTAX     Counter32
    MAX-ACCESS read-only
    STATUS     current
    DESCRIPTION
        "-- empty --"
    ::= { lcsStatusLanPacketTransportEntry 4 }

-- {COLUMN} 310.1.5.53.1.5
lcsStatusLanPacketTransportEntryRxMulticasts OBJECT-TYPE
    SYNTAX     Counter32
    MAX-ACCESS read-only
    STATUS     current
    DESCRIPTION
        "-- empty --"
    ::= { lcsStatusLanPacketTransportEntry 5 }

-- {COLUMN} 310.1.5.53.1.6
lcsStatusLanPacketTransportEntryRxUnicasts OBJECT-TYPE
    SYNTAX     Counter32
    MAX-ACCESS read-only
    STATUS     current
    DESCRIPTION
        "-- empty --"
    ::= { lcsStatusLanPacketTransportEntry 6 }

-- {COLUMN} 310.1.5.53.1.7
lcsStatusLanPacketTransportEntryTxBroadcasts OBJECT-TYPE
    SYNTAX     Counter32
    MAX-ACCESS read-only
    STATUS     current
    DESCRIPTION
        "-- empty --"
    ::= { lcsStatusLanPacketTransportEntry 7 }

-- {COLUMN} 310.1.5.53.1.8
lcsStatusLanPacketTransportEntryTxMulticasts OBJECT-TYPE
    SYNTAX     Counter32
    MAX-ACCESS read-only
    STATUS     current
    DESCRIPTION
        "-- empty --"
    ::= { lcsStatusLanPacketTransportEntry 8 }

-- {COLUMN} 310.1.5.53.1.9
lcsStatusLanPacketTransportEntryTxUnicasts OBJECT-TYPE
    SYNTAX     Counter32
    MAX-ACCESS read-only
    STATUS     current
    DESCRIPTION
        "-- empty --"
    ::= { lcsStatusLanPacketTransportEntry 9 }

-- {TABLE} 310.1.5.54
lcsStatusLanErrorsTable OBJECT-TYPE
    SYNTAX     SEQUENCE OF LcsStatusLanErrorsEntry
    MAX-ACCESS not-accessible
    STATUS     current
    DESCRIPTION
        "-- empty --"
    ::= { lcsStatusLan 54 }

-- {ENTRY} 310.1.5.54.1
lcsStatusLanErrorsEntry OBJECT-TYPE
    SYNTAX     LcsStatusLanErrorsEntry
    MAX-ACCESS not-accessible
    STATUS     current
    DESCRIPTION
        ""
    INDEX {
        lcsStatusLanErrorsEntryIfc
    }
    ::= { lcsStatusLanErrorsTable 1 }

-- {SEQUENCE}
LcsStatusLanErrorsEntry ::= SEQUENCE {
    lcsStatusLanErrorsEntryIfc DisplayString,
    lcsStatusLanErrorsEntryRxErrors Counter32,
    lcsStatusLanErrorsEntryTxErrors Counter32,
    lcsStatusLanErrorsEntryStackErrors Counter32,
    lcsStatusLanErrorsEntryNicErrors Counter32,
    lcsStatusLanErrorsEntryQueueErrors Counter32,
    lcsStatusLanErrorsEntryRxCrcErrors Counter32,
    lcsStatusLanErrorsEntryCollisions Counter32,
    lcsStatusLanErrorsEntrySingleCollisions Counter32,
    lcsStatusLanErrorsEntryMultipleCollisions Counter32,
    lcsStatusLanErrorsEntryLateCollisions Counter32,
    lcsStatusLanErrorsEntryExcessiveCollisions Counter32,
    lcsStatusLanErrorsEntryRxAlignErrors Counter32,
    lcsStatusLanErrorsEntryRxTooShort Counter32,
    lcsStatusLanErrorsEntryRxTooLong Counter32,
    lcsStatusLanErrorsEntryTxCarrier Counter32,
    lcsStatusLanErrorsEntryTxDeferred Counter32,
    lcsStatusLanErrorsEntryRxPhyErrors Counter32,
    lcsStatusLanErrorsEntryRxDscrUnderflow Counter32,
    lcsStatusLanErrorsEntryRxFifoOverflow Counter32,
    lcsStatusLanErrorsEntryTxDiscarded Counter32
}

-- {COLUMN} 310.1.5.54.1.1
lcsStatusLanErrorsEntryIfc OBJECT-TYPE
    SYNTAX     DisplayString (SIZE(0..255))
    MAX-ACCESS read-only
    STATUS     current
    DESCRIPTION
        "-- empty --"
    ::= { lcsStatusLanErrorsEntry 1 }

-- {COLUMN} 310.1.5.54.1.2
lcsStatusLanErrorsEntryRxErrors OBJECT-TYPE
    SYNTAX     Counter32
    MAX-ACCESS read-only
    STATUS     current
    DESCRIPTION
        "-- empty --"
    ::= { lcsStatusLanErrorsEntry 2 }

-- {COLUMN} 310.1.5.54.1.3
lcsStatusLanErrorsEntryTxErrors OBJECT-TYPE
    SYNTAX     Counter32
    MAX-ACCESS read-only
    STATUS     current
    DESCRIPTION
        "-- empty --"
    ::= { lcsStatusLanErrorsEntry 3 }

-- {COLUMN} 310.1.5.54.1.4
lcsStatusLanErrorsEntryStackErrors OBJECT-TYPE
    SYNTAX     Counter32
    MAX-ACCESS read-only
    STATUS     current
    DESCRIPTION
        "-- empty --"
    ::= { lcsStatusLanErrorsEntry 4 }

-- {COLUMN} 310.1.5.54.1.5
lcsStatusLanErrorsEntryNicErrors OBJECT-TYPE
    SYNTAX     Counter32
    MAX-ACCESS read-only
    STATUS     current
    DESCRIPTION
        "-- empty --"
    ::= { lcsStatusLanErrorsEntry 5 }

-- {COLUMN} 310.1.5.54.1.6
lcsStatusLanErrorsEntryQueueErrors OBJECT-TYPE
    SYNTAX     Counter32
    MAX-ACCESS read-only
    STATUS     current
    DESCRIPTION
        "-- empty --"
    ::= { lcsStatusLanErrorsEntry 6 }

-- {COLUMN} 310.1.5.54.1.7
lcsStatusLanErrorsEntryRxCrcErrors OBJECT-TYPE
    SYNTAX     Counter32
    MAX-ACCESS read-only
    STATUS     current
    DESCRIPTION
        "-- empty --"
    ::= { lcsStatusLanErrorsEntry 7 }

-- {COLUMN} 310.1.5.54.1.8
lcsStatusLanErrorsEntryCollisions OBJECT-TYPE
    SYNTAX     Counter32
    MAX-ACCESS read-only
    STATUS     current
    DESCRIPTION
        "-- empty --"
    ::= { lcsStatusLanErrorsEntry 8 }

-- {COLUMN} 310.1.5.54.1.9
lcsStatusLanErrorsEntrySingleCollisions OBJECT-TYPE
    SYNTAX     Counter32
    MAX-ACCESS read-only
    STATUS     current
    DESCRIPTION
        "-- empty --"
    ::= { lcsStatusLanErrorsEntry 9 }

-- {COLUMN} 310.1.5.54.1.10
lcsStatusLanErrorsEntryMultipleCollisions OBJECT-TYPE
    SYNTAX     Counter32
    MAX-ACCESS read-only
    STATUS     current
    DESCRIPTION
        "-- empty --"
    ::= { lcsStatusLanErrorsEntry 10 }

-- {COLUMN} 310.1.5.54.1.11
lcsStatusLanErrorsEntryLateCollisions OBJECT-TYPE
    SYNTAX     Counter32
    MAX-ACCESS read-only
    STATUS     current
    DESCRIPTION
        "-- empty --"
    ::= { lcsStatusLanErrorsEntry 11 }

-- {COLUMN} 310.1.5.54.1.12
lcsStatusLanErrorsEntryExcessiveCollisions OBJECT-TYPE
    SYNTAX     Counter32
    MAX-ACCESS read-only
    STATUS     current
    DESCRIPTION
        "-- empty --"
    ::= { lcsStatusLanErrorsEntry 12 }

-- {COLUMN} 310.1.5.54.1.13
lcsStatusLanErrorsEntryRxAlignErrors OBJECT-TYPE
    SYNTAX     Counter32
    MAX-ACCESS read-only
    STATUS     current
    DESCRIPTION
        "-- empty --"
    ::= { lcsStatusLanErrorsEntry 13 }

-- {COLUMN} 310.1.5.54.1.14
lcsStatusLanErrorsEntryRxTooShort OBJECT-TYPE
    SYNTAX     Counter32
    MAX-ACCESS read-only
    STATUS     current
    DESCRIPTION
        "-- empty --"
    ::= { lcsStatusLanErrorsEntry 14 }

-- {COLUMN} 310.1.5.54.1.15
lcsStatusLanErrorsEntryRxTooLong OBJECT-TYPE
    SYNTAX     Counter32
    MAX-ACCESS read-only
    STATUS     current
    DESCRIPTION
        "-- empty --"
    ::= { lcsStatusLanErrorsEntry 15 }

-- {COLUMN} 310.1.5.54.1.16
lcsStatusLanErrorsEntryTxCarrier OBJECT-TYPE
    SYNTAX     Counter32
    MAX-ACCESS read-only
    STATUS     current
    DESCRIPTION
        "-- empty --"
    ::= { lcsStatusLanErrorsEntry 16 }

-- {COLUMN} 310.1.5.54.1.17
lcsStatusLanErrorsEntryTxDeferred OBJECT-TYPE
    SYNTAX     Counter32
    MAX-ACCESS read-only
    STATUS     current
    DESCRIPTION
        "-- empty --"
    ::= { lcsStatusLanErrorsEntry 17 }

-- {COLUMN} 310.1.5.54.1.18
lcsStatusLanErrorsEntryRxPhyErrors OBJECT-TYPE
    SYNTAX     Counter32
    MAX-ACCESS read-only
    STATUS     current
    DESCRIPTION
        "-- empty --"
    ::= { lcsStatusLanErrorsEntry 18 }

-- {COLUMN} 310.1.5.54.1.21
lcsStatusLanErrorsEntryRxDscrUnderflow OBJECT-TYPE
    SYNTAX     Counter32
    MAX-ACCESS read-only
    STATUS     current
    DESCRIPTION
        "-- empty --"
    ::= { lcsStatusLanErrorsEntry 21 }

-- {COLUMN} 310.1.5.54.1.19
lcsStatusLanErrorsEntryRxFifoOverflow OBJECT-TYPE
    SYNTAX     Counter32
    MAX-ACCESS read-only
    STATUS     current
    DESCRIPTION
        "-- empty --"
    ::= { lcsStatusLanErrorsEntry 19 }

-- {COLUMN} 310.1.5.54.1.20
lcsStatusLanErrorsEntryTxDiscarded OBJECT-TYPE
    SYNTAX     Counter32
    MAX-ACCESS read-only
    STATUS     current
    DESCRIPTION
        "-- empty --"
    ::= { lcsStatusLanErrorsEntry 20 }

-- {OID} 310.1.6
lcsStatusPpp OBJECT IDENTIFIER ::= { lcsStatus 6 }

-- {TABLE} 310.1.6.1
lcsStatusPppPppPhasesTable OBJECT-TYPE
    SYNTAX     SEQUENCE OF LcsStatusPppPppPhasesEntry
    MAX-ACCESS not-accessible
    STATUS     current
    DESCRIPTION
        "-- empty --"
    ::= { lcsStatusPpp 1 }

-- {ENTRY} 310.1.6.1.1
lcsStatusPppPppPhasesEntry OBJECT-TYPE
    SYNTAX     LcsStatusPppPppPhasesEntry
    MAX-ACCESS not-accessible
    STATUS     current
    DESCRIPTION
        ""
    INDEX {
        lcsStatusPppPppPhasesEntryIfc
    }
    ::= { lcsStatusPppPppPhasesTable 1 }

-- {SEQUENCE}
LcsStatusPppPppPhasesEntry ::= SEQUENCE {
    lcsStatusPppPppPhasesEntryIfc INTEGER,
    lcsStatusPppPppPhasesEntryPhaseTo INTEGER,
    lcsStatusPppPppPhasesEntryLcp INTEGER,
    lcsStatusPppPppPhasesEntryIpcp INTEGER,
    lcsStatusPppPppPhasesEntryCcp INTEGER
}

-- {COLUMN} 310.1.6.1.1.1
lcsStatusPppPppPhasesEntryIfc OBJECT-TYPE
    SYNTAX     INTEGER
      {
        eDslCh1 (1),
        eModem (2)
      }
    MAX-ACCESS read-only
    STATUS     current
    DESCRIPTION
        "-- empty --"
    ::= { lcsStatusPppPppPhasesEntry 1 }

-- {COLUMN} 310.1.6.1.1.2
lcsStatusPppPppPhasesEntryPhaseTo OBJECT-TYPE
    SYNTAX     INTEGER
      {
        eDead (1),
        eEstablish (2),
        eTerminate (3),
        eAuthenticate (4),
        eCallback (5),
        eNetwork (6)
      }
    MAX-ACCESS read-only
    STATUS     current
    DESCRIPTION
        "-- empty --"
    ::= { lcsStatusPppPppPhasesEntry 2 }

-- {COLUMN} 310.1.6.1.1.3
lcsStatusPppPppPhasesEntryLcp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 3 }

-- {COLUMN} 310.1.6.1.1.4
lcsStatusPppPppPhasesEntryIpcp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 4 }

-- {COLUMN} 310.1.6.1.1.6
lcsStatusPppPppPhasesEntryCcp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 6 }

-- {OID} 310.1.6.2
lcsStatusPppLcp OBJECT IDENTIFIER ::= { lcsStatusPpp 2 }

-- {SCALAR} 310.1.6.2.1
lcsStatusPppLcpRxErrors OBJECT-TYPE
    SYNTAX     Counter32
    MAX-ACCESS read-only
    STATUS     current
    DESCRIPTION
        "-- empty --"
    ::= { lcsStatusPppLcp 1 }

-- {SCALAR} 310.1.6.2.2
lcsStatusPppLcpRxDiscarded OBJECT-TYPE
    SYNTAX     Counter32
    MAX-ACCESS read-only
    STATUS     current
    DESCRIPTION
        "-- empty --"
    ::= { lcsStatusPppLcp 2 }

-- {SCALAR} 310.1.6.2.3
lcsStatusPppLcpRxConfigRequest OBJECT-TYPE
    SYNTAX     Counter32
    MAX-ACCESS read-only
    STATUS     current
    DESCRIPTION
        "-- empty --"
    ::= { lcsStatusPppLcp 3 }

-- {SCALAR} 310.1.6.2.4
lcsStatusPppLcpRxConfigAck OBJECT-TYPE
    SYNTAX     Counter32
    MAX-ACCESS read-only
    STATUS     current
    DESCRIPTION
        "-- empty --"
    ::= { lcsStatusPppLcp 4 }

-- {SCALAR} 310.1.6.2.5
lcsStatusPppLcpRxConfigNak OBJECT-TYPE
    SYNTAX     Counter32
    MAX-ACCESS read-only
    STATUS     current
    DESCRIPTION
        "-- empty --"
    ::= { lcsStatusPppLcp 5 }

-- {SCALAR} 310.1.6.2.6
lcsStatusPppLcpRxConfigReject OBJECT-TYPE
    SYNTAX     Counter32
    MAX-ACCESS read-only
    STATUS     current
    DESCRIPTION
        "-- empty --"
    ::= { lcsStatusPppLcp 6 }

-- {SCALAR} 310.1.6.2.7
lcsStatusPppLcpRxTerminateRequest OBJECT-TYPE
    SYNTAX     Counter32
    MAX-ACCESS read-only
    STATUS     current
    DESCRIPTION
        "-- empty --"
    ::= { lcsStatusPppLcp 7 }

-- {SCALAR} 310.1.6.2.8
lcsStatusPppLcpRxTerminateAck OBJECT-TYPE
    SYNTAX     Counter32
    MAX-ACCESS read-only
    STATUS     current
    DESCRIPTION
        "-- empty --"
    ::= { lcsStatusPppLcp 8 }

-- {SCALAR} 310.1.6.2.9
lcsStatusPppLcpRxCodeReject OBJECT-TYPE
    SYNTAX     Counter32
    MAX-ACCESS read-only
    STATUS     current
    DESCRIPTION
        "-- empty --"
    ::= { lcsStatusPppLcp 9 }

-- {SCALAR} 310.1.6.2.10
lcsStatusPppLcpRxProtocolReject OBJECT-TYPE
    SYNTAX     Counter32
    MAX-ACCESS read-only
    STATUS     current
    DESCRIPTION
        "-- empty --"
    ::= { lcsStatusPppLcp 10 }

-- {SCALAR} 310.1.6.2.11
lcsStatusPppLcpRxEchoRequest OBJECT-TYPE
    SYNTAX     Counter32
    MAX-ACCESS read-only
    STATUS     current
    DESCRIPTION
        "-- empty --"
    ::= { lcsStatusPppLcp 11 }

-- {SCALAR} 310.1.6.2.12
lcsStatusPppLcpRxEchoReply OBJECT-TYPE
    SYNTAX     Counter32
    MAX-ACCESS read-only
    STATUS     current
    DESCRIPTION
        "-- empty --"
    ::= { lcsStatusPppLcp 12 }

-- {SCALAR} 310.1.6.2.13
lcsStatusPppLcpRxDiscardRequest OBJECT-TYPE
    SYNTAX     Counter32
    MAX-ACCESS read-only
    STATUS     current
    DESCRIPTION
        "-- empty --"
    ::= { lcsStatusPppLcp 13 }

-- {SCALAR} 310.1.6.2.14
lcsStatusPppLcpTxConfigRequest OBJECT-TYPE
    SYNTAX     Counter32
    MAX-ACCESS read-only
    STATUS     current
    DESCRIPTION
        "-- empty --"
    ::= { lcsStatusPppLcp 14 }

-- {SCALAR} 310.1.6.2.15
lcsStatusPppLcpTxConfigAck OBJECT-TYPE
    SYNTAX     Counter32
    MAX-ACCESS read-only
    STATUS     current
    DESCRIPTION
        "-- empty --"
    ::= { lcsStatusPppLcp 15 }

-- {SCALAR} 310.1.6.2.16
lcsStatusPppLcpTxConfigNak OBJECT-TYPE
    SYNTAX     Counter32
    MAX-ACCESS read-only
    STATUS     current
    DESCRIPTION
        "-- empty --"
    ::= { lcsStatusPppLcp 16 }

-- {SCALAR} 310.1.6.2.17
lcsStatusPppLcpTxConfigReject OBJECT-TYPE
    SYNTAX     Counter32
    MAX-ACCESS read-only
    STATUS     current
    DESCRIPTION
        "-- empty --"
    ::= { lcsStatusPppLcp 17 }

-- {SCALAR} 310.1.6.2.18
lcsStatusPppLcpTxTerminateRequest OBJECT-TYPE
    SYNTAX     Counter32
    MAX-ACCESS read-only
    STATUS     current
    DESCRIPTION
        "-- empty --"
    ::= { lcsStatusPppLcp 18 }

-- {SCALAR} 310.1.6.2.19
lcsStatusPppLcpTxTerminateAck OBJECT-TYPE
    SYNTAX     Counter32
    MAX-ACCESS read-only
    STATUS     current
    DESCRIPTION
        "-- empty --"
    ::= { lcsStatusPppLcp 19 }

-- {SCALAR} 310.1.6.2.20
lcsStatusPppLcpTxCodeReject OBJECT-TYPE
    SYNTAX     Counter32
    MAX-ACCESS read-only
    STATUS     current
    DESCRIPTION
        "-- empty --"
    ::= { lcsStatusPppLcp 20 }

-- {SCALAR} 310.1.6.2.21
lcsStatusPppLcpTxProtocolReject OBJECT-TYPE
    SYNTAX     Counter32
    MAX-ACCESS read-only
    STATUS     current
    DESCRIPTION
        "-- empty --"
    ::= { lcsStatusPppLcp 21 }

-- {SCALAR} 310.1.6.2.22
lcsStatusPppLcpTxEchoRequest OBJECT-TYPE
    SYNTAX     Counter32
    MAX-ACCESS read-only
    STATUS     current
    DESCRIPTION
        "-- empty --"
    ::= { lcsStatusPppLcp 22 }

-- {SCALAR} 310.1.6.2.23
lcsStatusPppLcpTxEchoReply OBJECT-TYPE
    SYNTAX     Counter32
    MAX-ACCESS read-only
    STATUS     current
    DESCRIPTION
        "-- empty --"
    ::= { lcsStatusPppLcp 23 }

-- {SCALAR} 310.1.6.2.24
lcsStatusPppLcpTxDiscardRequest OBJECT-TYPE
    SYNTAX     Counter32
    MAX-ACCESS read-only
    STATUS     current
    DESCRIPTION
        "-- empty --"
    ::= { lcsStatusPppLcp 24 }

-- {SCALAR} 310.1.6.2.25
lcsStatusPppLcpDeleteValues OBJECT-TYPE
    SYNTAX     DisplayString
    MAX-ACCESS read-write
    STATUS     current
    DESCRIPTION
        "-- empty --"
    ::= { lcsStatusPppLcp 25 }

-- {OID} 310.1.6.3
lcsStatusPppPap OBJECT IDENTIFIER ::= { lcsStatusPpp 3 }

-- {SCALAR} 310.1.6.3.1
lcsStatusPppPapRxDiscarded OBJECT-TYPE
    SYNTAX     Counter32
    MAX-ACCESS read-only
    STATUS     current
    DESCRIPTION
        "-- empty --"
    ::= { lcsStatusPppPap 1 }

-- {SCALAR} 310.1.6.3.2
lcsStatusPppPapRxRequest OBJECT-TYPE
    SYNTAX     Counter32
    MAX-ACCESS read-only
    STATUS     current
    DESCRIPTION
        "-- empty --"
    ::= { lcsStatusPppPap 2 }

-- {SCALAR} 310.1.6.3.3
lcsStatusPppPapRxSuccess OBJECT-TYPE
    SYNTAX     Counter32
    MAX-ACCESS read-only
    STATUS     current
    DESCRIPTION
        "-- empty --"
    ::= { lcsStatusPppPap 3 }

-- {SCALAR} 310.1.6.3.4
lcsStatusPppPapRxFailure OBJECT-TYPE
    SYNTAX     Counter32
    MAX-ACCESS read-only
    STATUS     current
    DESCRIPTION
        "-- empty --"
    ::= { lcsStatusPppPap 4 }

-- {SCALAR} 310.1.6.3.5
lcsStatusPppPapTxRetry OBJECT-TYPE
    SYNTAX     Counter32
    MAX-ACCESS read-only
    STATUS     current
    DESCRIPTION
        "-- empty --"
    ::= { lcsStatusPppPap 5 }

-- {SCALAR} 310.1.6.3.6
lcsStatusPppPapTxRequest OBJECT-TYPE
    SYNTAX     Counter32
    MAX-ACCESS read-only
    STATUS     current
    DESCRIPTION
        "-- empty --"
    ::= { lcsStatusPppPap 6 }

-- {SCALAR} 310.1.6.3.7
lcsStatusPppPapTxSuccess OBJECT-TYPE
    SYNTAX     Counter32
    MAX-ACCESS read-only
    STATUS     current
    DESCRIPTION
        "-- empty --"
    ::= { lcsStatusPppPap 7 }

-- {SCALAR} 310.1.6.3.8
lcsStatusPppPapTxFailure OBJECT-TYPE
    SYNTAX     Counter32
    MAX-ACCESS read-only
    STATUS     current
    DESCRIPTION
        "-- empty --"
    ::= { lcsStatusPppPap 8 }

-- {SCALAR} 310.1.6.3.9
lcsStatusPppPapDeleteValues OBJECT-TYPE
    SYNTAX     DisplayString
    MAX-ACCESS read-write
    STATUS     current
    DESCRIPTION
        "-- empty --"
    ::= { lcsStatusPppPap 9 }

-- {OID} 310.1.6.4
lcsStatusPppChap OBJECT IDENTIFIER ::= { lcsStatusPpp 4 }

-- {SCALAR} 310.1.6.4.1
lcsStatusPppChapRxDiscarded OBJECT-TYPE
    SYNTAX     Counter32
    MAX-ACCESS read-only
    STATUS     current
    DESCRIPTION
        "-- empty --"
    ::= { lcsStatusPppChap 1 }

-- {SCALAR} 310.1.6.4.2
lcsStatusPppChapRxChallenge OBJECT-TYPE
    SYNTAX     Counter32
    MAX-ACCESS read-only
    STATUS     current
    DESCRIPTION
        "-- empty --"
    ::= { lcsStatusPppChap 2 }

-- {SCALAR} 310.1.6.4.3
lcsStatusPppChapRxResponse OBJECT-TYPE
    SYNTAX     Counter32
    MAX-ACCESS read-only
    STATUS     current
    DESCRIPTION
        "-- empty --"
    ::= { lcsStatusPppChap 3 }

-- {SCALAR} 310.1.6.4.4
lcsStatusPppChapRxSuccess OBJECT-TYPE
    SYNTAX     Counter32
    MAX-ACCESS read-only
    STATUS     current
    DESCRIPTION
        "-- empty --"
    ::= { lcsStatusPppChap 4 }

-- {SCALAR} 310.1.6.4.5
lcsStatusPppChapRxFailure OBJECT-TYPE
    SYNTAX     Counter32
    MAX-ACCESS read-only
    STATUS     current
    DESCRIPTION
        "-- empty --"
    ::= { lcsStatusPppChap 5 }

-- {SCALAR} 310.1.6.4.6
lcsStatusPppChapTxRetry OBJECT-TYPE
    SYNTAX     Counter32
    MAX-ACCESS read-only
    STATUS     current
    DESCRIPTION
        "-- empty --"
    ::= { lcsStatusPppChap 6 }

-- {SCALAR} 310.1.6.4.7
lcsStatusPppChapTxChallenge OBJECT-TYPE
    SYNTAX     Counter32
    MAX-ACCESS read-only
    STATUS     current
    DESCRIPTION
        "-- empty --"
    ::= { lcsStatusPppChap 7 }

-- {SCALAR} 310.1.6.4.8
lcsStatusPppChapTxResponse OBJECT-TYPE
    SYNTAX     Counter32
    MAX-ACCESS read-only
    STATUS     current
    DESCRIPTION
        "-- empty --"
    ::= { lcsStatusPppChap 8 }

-- {SCALAR} 310.1.6.4.9
lcsStatusPppChapTxSuccess OBJECT-TYPE
    SYNTAX     Counter32
    MAX-ACCESS read-only
    STATUS     current
    DESCRIPTION
        "-- empty --"
    ::= { lcsStatusPppChap 9 }

-- {SCALAR} 310.1.6.4.10
lcsStatusPppChapTxFailure OBJECT-TYPE
    SYNTAX     Counter32
    MAX-ACCESS read-only
    STATUS     current
    DESCRIPTION
        "-- empty --"
    ::= { lcsStatusPppChap 10 }

-- {SCALAR} 310.1.6.4.11
lcsStatusPppChapDeleteValues OBJECT-TYPE
    SYNTAX     DisplayString
    MAX-ACCESS read-write
    STATUS     current
    DESCRIPTION
        "-- empty --"
    ::= { lcsStatusPppChap 11 }

-- {OID} 310.1.6.6
lcsStatusPppIpcp OBJECT IDENTIFIER ::= { lcsStatusPpp 6 }

-- {SCALAR} 310.1.6.6.1
lcsStatusPppIpcpRxDiscarded OBJECT-TYPE
    SYNTAX     Counter32
    MAX-ACCESS read-only
    STATUS     current
    DESCRIPTION
        "-- empty --"
    ::= { lcsStatusPppIpcp 1 }

-- {SCALAR} 310.1.6.6.2
lcsStatusPppIpcpRxConfigRequest OBJECT-TYPE
    SYNTAX     Counter32
    MAX-ACCESS read-only
    STATUS     current
    DESCRIPTION
        "-- empty --"
    ::= { lcsStatusPppIpcp 2 }

-- {SCALAR} 310.1.6.6.3
lcsStatusPppIpcpRxConfigAck OBJECT-TYPE
    SYNTAX     Counter32
    MAX-ACCESS read-only
    STATUS     current
    DESCRIPTION
        "-- empty --"
    ::= { lcsStatusPppIpcp 3 }

-- {SCALAR} 310.1.6.6.4
lcsStatusPppIpcpRxConfigNak OBJECT-TYPE
    SYNTAX     Counter32
    MAX-ACCESS read-only
    STATUS     current
    DESCRIPTION
        "-- empty --"
    ::= { lcsStatusPppIpcp 4 }

-- {SCALAR} 310.1.6.6.5
lcsStatusPppIpcpRxConfigReject OBJECT-TYPE
    SYNTAX     Counter32
    MAX-ACCESS read-only
    STATUS     current
    DESCRIPTION
        "-- empty --"
    ::= { lcsStatusPppIpcp 5 }

-- {SCALAR} 310.1.6.6.6
lcsStatusPppIpcpRxTerminateRequest OBJECT-TYPE
    SYNTAX     Counter32
    MAX-ACCESS read-only
    STATUS     current
    DESCRIPTION
        "-- empty --"
    ::= { lcsStatusPppIpcp 6 }

-- {SCALAR} 310.1.6.6.7
lcsStatusPppIpcpRxTerminateAck OBJECT-TYPE
    SYNTAX     Counter32
    MAX-ACCESS read-only
    STATUS     current
    DESCRIPTION
        "-- empty --"
    ::= { lcsStatusPppIpcp 7 }

-- {SCALAR} 310.1.6.6.8
lcsStatusPppIpcpRxCodeReject OBJECT-TYPE
    SYNTAX     Counter32
    MAX-ACCESS read-only
    STATUS     current
    DESCRIPTION
        "-- empty --"
    ::= { lcsStatusPppIpcp 8 }

-- {SCALAR} 310.1.6.6.9
lcsStatusPppIpcpTxConfigRequest OBJECT-TYPE
    SYNTAX     Counter32
    MAX-ACCESS read-only
    STATUS     current
    DESCRIPTION
        "-- empty --"
    ::= { lcsStatusPppIpcp 9 }

-- {SCALAR} 310.1.6.6.10
lcsStatusPppIpcpTxConfigAck OBJECT-TYPE
    SYNTAX     Counter32
    MAX-ACCESS read-only
    STATUS     current
    DESCRIPTION
        "-- empty --"
    ::= { lcsStatusPppIpcp 10 }

-- {SCALAR} 310.1.6.6.11
lcsStatusPppIpcpTxConfigNak OBJECT-TYPE
    SYNTAX     Counter32
    MAX-ACCESS read-only
    STATUS     current
    DESCRIPTION
        "-- empty --"
    ::= { lcsStatusPppIpcp 11 }

-- {SCALAR} 310.1.6.6.12
lcsStatusPppIpcpTxConfigReject OBJECT-TYPE
    SYNTAX     Counter32
    MAX-ACCESS read-only
    STATUS     current
    DESCRIPTION
        "-- empty --"
    ::= { lcsStatusPppIpcp 12 }

-- {SCALAR} 310.1.6.6.13
lcsStatusPppIpcpTxTerminateRequest OBJECT-TYPE
    SYNTAX     Counter32
    MAX-ACCESS read-only
    STATUS     current
    DESCRIPTION
        "-- empty --"
    ::= { lcsStatusPppIpcp 13 }

-- {SCALAR} 310.1.6.6.14
lcsStatusPppIpcpTxTerminateAck OBJECT-TYPE
    SYNTAX     Counter32
    MAX-ACCESS read-only
    STATUS     current
    DESCRIPTION
        "-- empty --"
    ::= { lcsStatusPppIpcp 14 }

-- {SCALAR} 310.1.6.6.15
lcsStatusPppIpcpTxCodeReject OBJECT-TYPE
    SYNTAX     Counter32
    MAX-ACCESS read-only
    STATUS     current
    DESCRIPTION
        "-- empty --"
    ::= { lcsStatusPppIpcp 15 }

-- {SCALAR} 310.1.6.6.16
lcsStatusPppIpcpDeleteValues OBJECT-TYPE
    SYNTAX     DisplayString
    MAX-ACCESS read-write
    STATUS     current
    DESCRIPTION
        "-- empty --"
    ::= { lcsStatusPppIpcp 16 }

-- {OID} 310.1.6.10
lcsStatusPppCcp OBJECT IDENTIFIER ::= { lcsStatusPpp 10 }

-- {SCALAR} 310.1.6.10.1
lcsStatusPppCcpRxDiscarded OBJECT-TYPE
    SYNTAX     Counter32
    MAX-ACCESS read-only
    STATUS     current
    DESCRIPTION
        "-- empty --"
    ::= { lcsStatusPppCcp 1 }

-- {SCALAR} 310.1.6.10.2
lcsStatusPppCcpRxConfigRequest OBJECT-TYPE
    SYNTAX     Counter32
    MAX-ACCESS read-only
    STATUS     current
    DESCRIPTION
        "-- empty --"
    ::= { lcsStatusPppCcp 2 }

-- {SCALAR} 310.1.6.10.3
lcsStatusPppCcpRxConfigAck OBJECT-TYPE
    SYNTAX     Counter32
    MAX-ACCESS read-only
    STATUS     current
    DESCRIPTION
        "-- empty --"
    ::= { lcsStatusPppCcp 3 }

-- {SCALAR} 310.1.6.10.4
lcsStatusPppCcpRxConfigNak OBJECT-TYPE
    SYNTAX     Counter32
    MAX-ACCESS read-only
    STATUS     current
    DESCRIPTION
        "-- empty --"
    ::= { lcsStatusPppCcp 4 }

-- {SCALAR} 310.1.6.10.5
lcsStatusPppCcpRxConfigReject OBJECT-TYPE
    SYNTAX     Counter32
    MAX-ACCESS read-only
    STATUS     current
    DESCRIPTION
        "-- empty --"
    ::= { lcsStatusPppCcp 5 }

-- {SCALAR} 310.1.6.10.6
lcsStatusPppCcpRxTerminateRequest OBJECT-TYPE
    SYNTAX     Counter32
    MAX-ACCESS read-only
    STATUS     current
    DESCRIPTION
        "-- empty --"
    ::= { lcsStatusPppCcp 6 }

-- {SCALAR} 310.1.6.10.7
lcsStatusPppCcpRxTerminateAck OBJECT-TYPE
    SYNTAX     Counter32
    MAX-ACCESS read-only
    STATUS     current
    DESCRIPTION
        "-- empty --"
    ::= { lcsStatusPppCcp 7 }

-- {SCALAR} 310.1.6.10.8
lcsStatusPppCcpRxCodeReject OBJECT-TYPE
    SYNTAX     Counter32
    MAX-ACCESS read-only
    STATUS     current
    DESCRIPTION
        "-- empty --"
    ::= { lcsStatusPppCcp 8 }

-- {SCALAR} 310.1.6.10.9
lcsStatusPppCcpRxResetRequest OBJECT-TYPE
    SYNTAX     Counter32
    MAX-ACCESS read-only
    STATUS     current
    DESCRIPTION
        "-- empty --"
    ::= { lcsStatusPppCcp 9 }

-- {SCALAR} 310.1.6.10.10
lcsStatusPppCcpRxResetAck OBJECT-TYPE
    SYNTAX     Counter32
    MAX-ACCESS read-only
    STATUS     current
    DESCRIPTION
        "-- empty --"
    ::= { lcsStatusPppCcp 10 }

-- {SCALAR} 310.1.6.10.11
lcsStatusPppCcpTxConfigRequest OBJECT-TYPE
    SYNTAX     Counter32
    MAX-ACCESS read-only
    STATUS     current
    DESCRIPTION
        "-- empty --"
    ::= { lcsStatusPppCcp 11 }

-- {SCALAR} 310.1.6.10.12
lcsStatusPppCcpTxConfigAck OBJECT-TYPE
    SYNTAX     Counter32
    MAX-ACCESS read-only
    STATUS     current
    DESCRIPTION
        "-- empty --"
    ::= { lcsStatusPppCcp 12 }

-- {SCALAR} 310.1.6.10.13
lcsStatusPppCcpTxConfigNak OBJECT-TYPE
    SYNTAX     Counter32
    MAX-ACCESS read-only
    STATUS     current
    DESCRIPTION
        "-- empty --"
    ::= { lcsStatusPppCcp 13 }

-- {SCALAR} 310.1.6.10.14
lcsStatusPppCcpTxConfigReject OBJECT-TYPE
    SYNTAX     Counter32
    MAX-ACCESS read-only
    STATUS     current
    DESCRIPTION
        "-- empty --"
    ::= { lcsStatusPppCcp 14 }

-- {SCALAR} 310.1.6.10.15
lcsStatusPppCcpTxTerminateRequest OBJECT-TYPE
    SYNTAX     Counter32
    MAX-ACCESS read-only
    STATUS     current
    DESCRIPTION
        "-- empty --"
    ::= { lcsStatusPppCcp 15 }

-- {SCALAR} 310.1.6.10.16
lcsStatusPppCcpTxTerminateAck OBJECT-TYPE
    SYNTAX     Counter32
    MAX-ACCESS read-only
    STATUS     current
    DESCRIPTION
        "-- empty --"
    ::= { lcsStatusPppCcp 16 }

-- {SCALAR} 310.1.6.10.17
lcsStatusPppCcpTxCodeReject OBJECT-TYPE
    SYNTAX     Counter32
    MAX-ACCESS read-only
    STATUS     current
    DESCRIPTION
        "-- empty --"
    ::= { lcsStatusPppCcp 17 }

-- {SCALAR} 310.1.6.10.19
lcsStatusPppCcpTxResetRequest OBJECT-TYPE
    SYNTAX     Counter32
    MAX-ACCESS read-only
    STATUS     current
    DESCRIPTION
        "-- empty --"
    ::= { lcsStatusPppCcp 19 }

-- {SCALAR} 310.1.6.10.20
lcsStatusPppCcpTxResetAck OBJECT-TYPE
    SYNTAX     Counter32
    MAX-ACCESS read-only
    STATUS     current
    DESCRIPTION
        "-- empty --"
    ::= { lcsStatusPppCcp 20 }

-- {SCALAR} 310.1.6.10.22
lcsStatusPppCcpCompressionErrors OBJECT-TYPE
    SYNTAX     Counter32
    MAX-ACCESS read-only
    STATUS     current
    DESCRIPTION
        "-- empty --"
    ::= { lcsStatusPppCcp 22 }

-- {SCALAR} 310.1.6.10.21
lcsStatusPppCcpDeleteValues OBJECT-TYPE
    SYNTAX     DisplayString
    MAX-ACCESS read-write
    STATUS     current
    DESCRIPTION
        "-- empty --"
    ::= { lcsStatusPppCcp 21 }

-- {OID} 310.1.6.8
lcsStatusPppRxOptions OBJECT IDENTIFIER ::= { lcsStatusPpp 8 }

-- {TABLE} 310.1.6.8.1
lcsStatusPppRxOptionsLcpTable OBJECT-TYPE
    SYNTAX     SEQUENCE OF LcsStatusPppRxOptionsLcpEntry
    MAX-ACCESS not-accessible
    STATUS     current
    DESCRIPTION
        "-- empty --"
    ::= { lcsStatusPppRxOptions 1 }

-- {ENTRY} 310.1.6.8.1.1
lcsStatusPppRxOptionsLcpEntry OBJECT-TYPE
    SYNTAX     LcsStatusPppRxOptionsLcpEntry
    MAX-ACCESS not-accessible
    STATUS     current
    DESCRIPTION
        ""
    INDEX {
        lcsStatusPppRxOptionsLcpEntryIfc
    }
    ::= { lcsStatusPppRxOptionsLcpTable 1 }

-- {SEQUENCE}
LcsStatusPppRxOptionsLcpEntry ::= SEQUENCE {
    lcsStatusPppRxOptionsLcpEntryIfc INTEGER,
    lcsStatusPppRxOptionsLcpEntryMru INTEGER,
    lcsStatusPppRxOptionsLcpEntryAuthentRequest INTEGER,
    lcsStatusPppRxOptionsLcpEntryMagicNum DisplayString
}

-- {COLUMN} 310.1.6.8.1.1.1
lcsStatusPppRxOptionsLcpEntryIfc OBJECT-TYPE
    SYNTAX     INTEGER
      {
        eDslCh1 (1),
        eModem (2)
      }
    MAX-ACCESS read-only
    STATUS     current
    DESCRIPTION
        "-- empty --"
    ::= { lcsStatusPppRxOptionsLcpEntry 1 }

-- {COLUMN} 310.1.6.8.1.1.2
lcsStatusPppRxOptionsLcpEntryMru OBJECT-TYPE
    SYNTAX     INTEGER (0..65535)
    MAX-ACCESS read-only
    STATUS     current
    DESCRIPTION
        "-- empty --"
    ::= { lcsStatusPppRxOptionsLcpEntry 2 }

-- {COLUMN} 310.1.6.8.1.1.4
lcsStatusPppRxOptionsLcpEntryAuthentRequest OBJECT-TYPE
    SYNTAX     INTEGER
      {
        eNone (0),
        eMsChapv2 (32),
        eMsChap (16),
        eChap (8),
        ePap (4)
      }
    MAX-ACCESS read-only
    STATUS     current
    DESCRIPTION
        "-- empty --"
    ::= { lcsStatusPppRxOptionsLcpEntry 4 }

-- {COLUMN} 310.1.6.8.1.1.6
lcsStatusPppRxOptionsLcpEntryMagicNum OBJECT-TYPE
    SYNTAX     DisplayString (SIZE(0..8))
    MAX-ACCESS read-only
    STATUS     current
    DESCRIPTION
        "-- empty --"
    ::= { lcsStatusPppRxOptionsLcpEntry 6 }

-- {TABLE} 310.1.6.8.3
lcsStatusPppRxOptionsIpcpTable OBJECT-TYPE
    SYNTAX     SEQUENCE OF LcsStatusPppRxOptionsIpcpEntry
    MAX-ACCESS not-accessible
    STATUS     current
    DESCRIPTION
        "-- empty --"
    ::= { lcsStatusPppRxOptions 3 }

-- {ENTRY} 310.1.6.8.3.1
lcsStatusPppRxOptionsIpcpEntry OBJECT-TYPE
    SYNTAX     LcsStatusPppRxOptionsIpcpEntry
    MAX-ACCESS not-accessible
    STATUS     current
    DESCRIPTION
        ""
    INDEX {
        lcsStatusPppRxOptionsIpcpEntryIfc
    }
    ::= { lcsStatusPppRxOptionsIpcpTable 1 }

-- {SEQUENCE}
LcsStatusPppRxOptionsIpcpEntry ::= SEQUENCE {
    lcsStatusPppRxOptionsIpcpEntryIfc INTEGER,
    lcsStatusPppRxOptionsIpcpEntryIpAddress IpAddress,
    lcsStatusPppRxOptionsIpcpEntryDnsDefault IpAddress,
    lcsStatusPppRxOptionsIpcpEntryDnsBackup IpAddress,
    lcsStatusPppRxOptionsIpcpEntryNbnsDefault IpAddress,
    lcsStatusPppRxOptionsIpcpEntryNbnsBackup IpAddress
}

-- {COLUMN} 310.1.6.8.3.1.1
lcsStatusPppRxOptionsIpcpEntryIfc OBJECT-TYPE
    SYNTAX     INTEGER
      {
        eDslCh1 (1),
        eModem (2)
      }
    MAX-ACCESS read-only
    STATUS     current
    DESCRIPTION
        "-- empty --"
    ::= { lcsStatusPppRxOptionsIpcpEntry 1 }

-- {COLUMN} 310.1.6.8.3.1.2
lcsStatusPppRxOptionsIpcpEntryIpAddress OBJECT-TYPE
    SYNTAX     IpAddress
    MAX-ACCESS read-only
    STATUS     current
    DESCRIPTION
        "-- empty --"
    ::= { lcsStatusPppRxOptionsIpcpEntry 2 }

-- {COLUMN} 310.1.6.8.3.1.3
lcsStatusPppRxOptionsIpcpEntryDnsDefault OBJECT-TYPE
    SYNTAX     IpAddress
    MAX-ACCESS read-only
    STATUS     current
    DESCRIPTION
        "-- empty --"
    ::= { lcsStatusPppRxOptionsIpcpEntry 3 }

-- {COLUMN} 310.1.6.8.3.1.5
lcsStatusPppRxOptionsIpcpEntryDnsBackup OBJECT-TYPE
    SYNTAX     IpAddress
    MAX-ACCESS read-only
    STATUS     current
    DESCRIPTION
        "-- empty --"
    ::= { lcsStatusPppRxOptionsIpcpEntry 5 }

-- {COLUMN} 310.1.6.8.3.1.4
lcsStatusPppRxOptionsIpcpEntryNbnsDefault OBJECT-TYPE
    SYNTAX     IpAddress
    MAX-ACCESS read-only
    STATUS     current
    DESCRIPTION
        "-- empty --"
    ::= { lcsStatusPppRxOptionsIpcpEntry 4 }

-- {COLUMN} 310.1.6.8.3.1.6
lcsStatusPppRxOptionsIpcpEntryNbnsBackup OBJECT-TYPE
    SYNTAX     IpAddress
    MAX-ACCESS read-only
    STATUS     current
    DESCRIPTION
        "-- empty --"
    ::= { lcsStatusPppRxOptionsIpcpEntry 6 }

-- {OID} 310.1.6.9
lcsStatusPppTxOptions OBJECT IDENTIFIER ::= { lcsStatusPpp 9 }

-- {TABLE} 310.1.6.9.1
lcsStatusPppTxOptionsLcpTable OBJECT-TYPE
    SYNTAX     SEQUENCE OF LcsStatusPppTxOptionsLcpEntry
    MAX-ACCESS not-accessible
    STATUS     current
    DESCRIPTION
        "-- empty --"
    ::= { lcsStatusPppTxOptions 1 }

-- {ENTRY} 310.1.6.9.1.1
lcsStatusPppTxOptionsLcpEntry OBJECT-TYPE
    SYNTAX     LcsStatusPppTxOptionsLcpEntry
    MAX-ACCESS not-accessible
    STATUS     current
    DESCRIPTION
        ""
    INDEX {
        lcsStatusPppTxOptionsLcpEntryIfc
    }
    ::= { lcsStatusPppTxOptionsLcpTable 1 }

-- {SEQUENCE}
LcsStatusPppTxOptionsLcpEntry ::= SEQUENCE {
    lcsStatusPppTxOptionsLcpEntryIfc INTEGER,
    lcsStatusPppTxOptionsLcpEntryMru INTEGER,
    lcsStatusPppTxOptionsLcpEntryAuthentRequest INTEGER,
    lcsStatusPppTxOptionsLcpEntryMagicNum DisplayString
}

-- {COLUMN} 310.1.6.9.1.1.1
lcsStatusPppTxOptionsLcpEntryIfc OBJECT-TYPE
    SYNTAX     INTEGER
      {
        eDslCh1 (1),
        eModem (2)
      }
    MAX-ACCESS read-only
    STATUS     current
    DESCRIPTION
        "-- empty --"
    ::= { lcsStatusPppTxOptionsLcpEntry 1 }

-- {COLUMN} 310.1.6.9.1.1.2
lcsStatusPppTxOptionsLcpEntryMru OBJECT-TYPE
    SYNTAX     INTEGER (0..65535)
    MAX-ACCESS read-only
    STATUS     current
    DESCRIPTION
        "-- empty --"
    ::= { lcsStatusPppTxOptionsLcpEntry 2 }

-- {COLUMN} 310.1.6.9.1.1.4
lcsStatusPppTxOptionsLcpEntryAuthentRequest OBJECT-TYPE
    SYNTAX     INTEGER
      {
        eNone (0),
        eMsChapv2 (32),
        eMsChap (16),
        eChap (8),
        ePap (4)
      }
    MAX-ACCESS read-only
    STATUS     current
    DESCRIPTION
        "-- empty --"
    ::= { lcsStatusPppTxOptionsLcpEntry 4 }

-- {COLUMN} 310.1.6.9.1.1.6
lcsStatusPppTxOptionsLcpEntryMagicNum OBJECT-TYPE
    SYNTAX     DisplayString (SIZE(0..8))
    MAX-ACCESS read-only
    STATUS     current
    DESCRIPTION
        "-- empty --"
    ::= { lcsStatusPppTxOptionsLcpEntry 6 }

-- {TABLE} 310.1.6.9.3
lcsStatusPppTxOptionsIpcpTable OBJECT-TYPE
    SYNTAX     SEQUENCE OF LcsStatusPppTxOptionsIpcpEntry
    MAX-ACCESS not-accessible
    STATUS     current
    DESCRIPTION
        "-- empty --"
    ::= { lcsStatusPppTxOptions 3 }

-- {ENTRY} 310.1.6.9.3.1
lcsStatusPppTxOptionsIpcpEntry OBJECT-TYPE
    SYNTAX     LcsStatusPppTxOptionsIpcpEntry
    MAX-ACCESS not-accessible
    STATUS     current
    DESCRIPTION
        ""
    INDEX {
        lcsStatusPppTxOptionsIpcpEntryIfc
    }
    ::= { lcsStatusPppTxOptionsIpcpTable 1 }

-- {SEQUENCE}
LcsStatusPppTxOptionsIpcpEntry ::= SEQUENCE {
    lcsStatusPppTxOptionsIpcpEntryIfc INTEGER,
    lcsStatusPppTxOptionsIpcpEntryIpAddress IpAddress,
    lcsStatusPppTxOptionsIpcpEntryDnsDefault IpAddress,
    lcsStatusPppTxOptionsIpcpEntryDnsBackup IpAddress,
    lcsStatusPppTxOptionsIpcpEntryNbnsDefault IpAddress,
    lcsStatusPppTxOptionsIpcpEntryNbnsBackup IpAddress
}

-- {COLUMN} 310.1.6.9.3.1.1
lcsStatusPppTxOptionsIpcpEntryIfc OBJECT-TYPE
    SYNTAX     INTEGER
      {
        eDslCh1 (1),
        eModem (2)
      }
    MAX-ACCESS read-only
    STATUS     current
    DESCRIPTION
        "-- empty --"
    ::= { lcsStatusPppTxOptionsIpcpEntry 1 }

-- {COLUMN} 310.1.6.9.3.1.2
lcsStatusPppTxOptionsIpcpEntryIpAddress OBJECT-TYPE
    SYNTAX     IpAddress
    MAX-ACCESS read-only
    STATUS     current
    DESCRIPTION
        "-- empty --"
    ::= { lcsStatusPppTxOptionsIpcpEntry 2 }

-- {COLUMN} 310.1.6.9.3.1.3
lcsStatusPppTxOptionsIpcpEntryDnsDefault OBJECT-TYPE
    SYNTAX     IpAddress
    MAX-ACCESS read-only
    STATUS     current
    DESCRIPTION
        "-- empty --"
    ::= { lcsStatusPppTxOptionsIpcpEntry 3 }

-- {COLUMN} 310.1.6.9.3.1.5
lcsStatusPppTxOptionsIpcpEntryDnsBackup OBJECT-TYPE
    SYNTAX     IpAddress
    MAX-ACCESS read-only
    STATUS     current
    DESCRIPTION
        "-- empty --"
    ::= { lcsStatusPppTxOptionsIpcpEntry 5 }

-- {COLUMN} 310.1.6.9.3.1.4
lcsStatusPppTxOptionsIpcpEntryNbnsDefault OBJECT-TYPE
    SYNTAX     IpAddress
    MAX-ACCESS read-only
    STATUS     current
    DESCRIPTION
        "-- empty --"
    ::= { lcsStatusPppTxOptionsIpcpEntry 4 }

-- {COLUMN} 310.1.6.9.3.1.6
lcsStatusPppTxOptionsIpcpEntryNbnsBackup OBJECT-TYPE
    SYNTAX     IpAddress
    MAX-ACCESS read-only
    STATUS     current
    DESCRIPTION
        "-- empty --"
    ::= { lcsStatusPppTxOptionsIpcpEntry 6 }

-- {SCALAR} 310.1.6.13
lcsStatusPppDeleteValues OBJECT-TYPE
    SYNTAX     DisplayString
    MAX-ACCESS read-write
    STATUS     current
    DESCRIPTION
        "-- empty --"
    ::= { lcsStatusPpp 13 }

-- {OID} 310.1.9
lcsStatusTcpIp OBJECT IDENTIFIER ::= { lcsStatus 9 }

-- {OID} 310.1.9.1
lcsStatusTcpIpArp OBJECT IDENTIFIER ::= { lcsStatusTcpIp 1 }

-- {SCALAR} 310.1.9.1.1
lcsStatusTcpIpArpLanRx OBJECT-TYPE
    SYNTAX     Counter32
    MAX-ACCESS read-only
    STATUS     current
    DESCRIPTION
        "-- empty --"
    ::= { lcsStatusTcpIpArp 1 }

-- {SCALAR} 310.1.9.1.2
lcsStatusTcpIpArpLanTx OBJECT-TYPE
    SYNTAX     Counter32
    MAX-ACCESS read-only
    STATUS     current
    DESCRIPTION
        "-- empty --"
    ::= { lcsStatusTcpIpArp 2 }

-- {SCALAR} 310.1.9.1.3
lcsStatusTcpIpArpLanErrors OBJECT-TYPE
    SYNTAX     Counter32
    MAX-ACCESS read-only
    STATUS     current
    DESCRIPTION
        "-- empty --"
    ::= { lcsStatusTcpIpArp 3 }

-- {SCALAR} 310.1.9.1.4
lcsStatusTcpIpArpWanRx OBJECT-TYPE
    SYNTAX     Counter32
    MAX-ACCESS read-only
    STATUS     current
    DESCRIPTION
        "-- empty --"
    ::= { lcsStatusTcpIpArp 4 }

-- {SCALAR} 310.1.9.1.5
lcsStatusTcpIpArpWanTx OBJECT-TYPE
    SYNTAX     Counter32
    MAX-ACCESS read-only
    STATUS     current
    DESCRIPTION
        "-- empty --"
    ::= { lcsStatusTcpIpArp 5 }

-- {SCALAR} 310.1.9.1.6
lcsStatusTcpIpArpWanErrors OBJECT-TYPE
    SYNTAX     Counter32
    MAX-ACCESS read-only
    STATUS     current
    DESCRIPTION
        "-- empty --"
    ::= { lcsStatusTcpIpArp 6 }

-- {TABLE} 310.1.9.1.7
lcsStatusTcpIpArpTableArpTable OBJECT-TYPE
    SYNTAX     SEQUENCE OF LcsStatusTcpIpArpTableArpEntry
    MAX-ACCESS not-accessible
    STATUS     current
    DESCRIPTION
        "-- empty --"
    ::= { lcsStatusTcpIpArp 7 }

-- {ENTRY} 310.1.9.1.7.1
lcsStatusTcpIpArpTableArpEntry OBJECT-TYPE
    SYNTAX     LcsStatusTcpIpArpTableArpEntry
    MAX-ACCESS not-accessible
    STATUS     current
    DESCRIPTION
        ""
    INDEX {
        lcsStatusTcpIpArpTableArpEntryIpAddress
    }
    ::= { lcsStatusTcpIpArpTableArpTable 1 }

-- {SEQUENCE}
LcsStatusTcpIpArpTableArpEntry ::= SEQUENCE {
    lcsStatusTcpIpArpTableArpEntryIpAddress IpAddress,
    lcsStatusTcpIpArpTableArpEntryMacAddress MacAddress,
    lcsStatusTcpIpArpTableArpEntryLastAccess INTEGER,
    lcsStatusTcpIpArpTableArpEntryConnect INTEGER,
    lcsStatusTcpIpArpTableArpEntryVlanId INTEGER,
    lcsStatusTcpIpArpTableArpEntryPeer DisplayString
}

-- {COLUMN} 310.1.9.1.7.1.1
lcsStatusTcpIpArpTableArpEntryIpAddress OBJECT-TYPE
    SYNTAX     IpAddress
    MAX-ACCESS read-only
    STATUS     current
    DESCRIPTION
        "-- empty --"
    ::= { lcsStatusTcpIpArpTableArpEntry 1 }

-- {COLUMN} 310.1.9.1.7.1.2
lcsStatusTcpIpArpTableArpEntryMacAddress OBJECT-TYPE
    SYNTAX     MacAddress
    MAX-ACCESS read-only
    STATUS     current
    DESCRIPTION
        "-- empty --"
    ::= { lcsStatusTcpIpArpTableArpEntry 2 }

-- {COLUMN} 310.1.9.1.7.1.3
lcsStatusTcpIpArpTableArpEntryLastAccess OBJECT-TYPE
    SYNTAX     INTEGER (0..2147483647)
    MAX-ACCESS read-only
    STATUS     current
    DESCRIPTION
        "-- empty --"
    ::= { lcsStatusTcpIpArpTableArpEntry 3 }

-- {COLUMN} 310.1.9.1.7.1.8
lcsStatusTcpIpArpTableArpEntryConnect OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eWan (32768)
      }
    MAX-ACCESS read-only
    STATUS     current
    DESCRIPTION
        "-- empty --"
    ::= { lcsStatusTcpIpArpTableArpEntry 8 }

-- {COLUMN} 310.1.9.1.7.1.7
lcsStatusTcpIpArpTableArpEntryVlanId OBJECT-TYPE
    SYNTAX     INTEGER (0..65535)
    MAX-ACCESS read-only
    STATUS     current
    DESCRIPTION
        "-- empty --"
    ::= { lcsStatusTcpIpArpTableArpEntry 7 }

-- {COLUMN} 310.1.9.1.7.1.6
lcsStatusTcpIpArpTableArpEntryPeer OBJECT-TYPE
    SYNTAX     DisplayString (SIZE(0..255))
    MAX-ACCESS read-only
    STATUS     current
    DESCRIPTION
        "-- empty --"
    ::= { lcsStatusTcpIpArpTableArpEntry 6 }

-- {SCALAR} 310.1.9.1.8
lcsStatusTcpIpArpDeleteValues OBJECT-TYPE
    SYNTAX     DisplayString
    MAX-ACCESS read-write
    STATUS     current
    DESCRIPTION
        "-- empty --"
    ::= { lcsStatusTcpIpArp 8 }

-- {OID} 310.1.9.2
lcsStatusTcpIpIp OBJECT IDENTIFIER ::= { lcsStatusTcpIp 2 }

-- {SCALAR} 310.1.9.2.1
lcsStatusTcpIpIpLanRx OBJECT-TYPE
    SYNTAX     Counter32
    MAX-ACCESS read-only
    STATUS     current
    DESCRIPTION
        "-- empty --"
    ::= { lcsStatusTcpIpIp 1 }

-- {SCALAR} 310.1.9.2.2
lcsStatusTcpIpIpLanTx OBJECT-TYPE
    SYNTAX     Counter32
    MAX-ACCESS read-only
    STATUS     current
    DESCRIPTION
        "-- empty --"
    ::= { lcsStatusTcpIpIp 2 }

-- {SCALAR} 310.1.9.2.3
lcsStatusTcpIpIpLanChecksumErrors OBJECT-TYPE
    SYNTAX     Counter32
    MAX-ACCESS read-only
    STATUS     current
    DESCRIPTION
        "-- empty --"
    ::= { lcsStatusTcpIpIp 3 }

-- {SCALAR} 310.1.9.2.4
lcsStatusTcpIpIpLanServiceErrors OBJECT-TYPE
    SYNTAX     Counter32
    MAX-ACCESS read-only
    STATUS     current
    DESCRIPTION
        "-- empty --"
    ::= { lcsStatusTcpIpIp 4 }

-- {SCALAR} 310.1.9.2.10
lcsStatusTcpIpIpLanFragmentationErrors OBJECT-TYPE
    SYNTAX     Counter32
    MAX-ACCESS read-only
    STATUS     current
    DESCRIPTION
        "-- empty --"
    ::= { lcsStatusTcpIpIp 10 }

-- {SCALAR} 310.1.9.2.13
lcsStatusTcpIpIpLanFragmentations OBJECT-TYPE
    SYNTAX     Counter32
    MAX-ACCESS read-only
    STATUS     current
    DESCRIPTION
        "-- empty --"
    ::= { lcsStatusTcpIpIp 13 }

-- {SCALAR} 310.1.9.2.14
lcsStatusTcpIpIpLanFragmentationsForced OBJECT-TYPE
    SYNTAX     Counter32
    MAX-ACCESS read-only
    STATUS     current
    DESCRIPTION
        "-- empty --"
    ::= { lcsStatusTcpIpIp 14 }

-- {SCALAR} 310.1.9.2.5
lcsStatusTcpIpIpWanRx OBJECT-TYPE
    SYNTAX     Counter32
    MAX-ACCESS read-only
    STATUS     current
    DESCRIPTION
        "-- empty --"
    ::= { lcsStatusTcpIpIp 5 }

-- {SCALAR} 310.1.9.2.6
lcsStatusTcpIpIpWanTx OBJECT-TYPE
    SYNTAX     Counter32
    MAX-ACCESS read-only
    STATUS     current
    DESCRIPTION
        "-- empty --"
    ::= { lcsStatusTcpIpIp 6 }

-- {SCALAR} 310.1.9.2.7
lcsStatusTcpIpIpWanChecksumErrors OBJECT-TYPE
    SYNTAX     Counter32
    MAX-ACCESS read-only
    STATUS     current
    DESCRIPTION
        "-- empty --"
    ::= { lcsStatusTcpIpIp 7 }

-- {SCALAR} 310.1.9.2.8
lcsStatusTcpIpIpWanServiceErrors OBJECT-TYPE
    SYNTAX     Counter32
    MAX-ACCESS read-only
    STATUS     current
    DESCRIPTION
        "-- empty --"
    ::= { lcsStatusTcpIpIp 8 }

-- {SCALAR} 310.1.9.2.11
lcsStatusTcpIpIpWanFragmentationErrors OBJECT-TYPE
    SYNTAX     Counter32
    MAX-ACCESS read-only
    STATUS     current
    DESCRIPTION
        "-- empty --"
    ::= { lcsStatusTcpIpIp 11 }

-- {SCALAR} 310.1.9.2.15
lcsStatusTcpIpIpWanFragmentations OBJECT-TYPE
    SYNTAX     Counter32
    MAX-ACCESS read-only
    STATUS     current
    DESCRIPTION
        "-- empty --"
    ::= { lcsStatusTcpIpIp 15 }

-- {SCALAR} 310.1.9.2.16
lcsStatusTcpIpIpWanFragmentationsForced OBJECT-TYPE
    SYNTAX     Counter32
    MAX-ACCESS read-only
    STATUS     current
    DESCRIPTION
        "-- empty --"
    ::= { lcsStatusTcpIpIp 16 }

-- {SCALAR} 310.1.9.2.9
lcsStatusTcpIpIpWanRxDisconnect OBJECT-TYPE
    SYNTAX     Counter32
    MAX-ACCESS read-only
    STATUS     current
    DESCRIPTION
        "-- empty --"
    ::= { lcsStatusTcpIpIp 9 }

-- {SCALAR} 310.1.9.2.17
lcsStatusTcpIpIpLoopError OBJECT-TYPE
    SYNTAX     Counter32
    MAX-ACCESS read-only
    STATUS     current
    DESCRIPTION
        "-- empty --"
    ::= { lcsStatusTcpIpIp 17 }

-- {SCALAR} 310.1.9.2.12
lcsStatusTcpIpIpDeleteValues OBJECT-TYPE
    SYNTAX     DisplayString
    MAX-ACCESS read-write
    STATUS     current
    DESCRIPTION
        "-- empty --"
    ::= { lcsStatusTcpIpIp 12 }

-- {OID} 310.1.9.3
lcsStatusTcpIpIcmp OBJECT IDENTIFIER ::= { lcsStatusTcpIp 3 }

-- {SCALAR} 310.1.9.3.1
lcsStatusTcpIpIcmpLanRx OBJECT-TYPE
    SYNTAX     Counter32
    MAX-ACCESS read-only
    STATUS     current
    DESCRIPTION
        "-- empty --"
    ::= { lcsStatusTcpIpIcmp 1 }

-- {SCALAR} 310.1.9.3.2
lcsStatusTcpIpIcmpLanTx OBJECT-TYPE
    SYNTAX     Counter32
    MAX-ACCESS read-only
    STATUS     current
    DESCRIPTION
        "-- empty --"
    ::= { lcsStatusTcpIpIcmp 2 }

-- {SCALAR} 310.1.9.3.3
lcsStatusTcpIpIcmpLanChecksumErrors OBJECT-TYPE
    SYNTAX     Counter32
    MAX-ACCESS read-only
    STATUS     current
    DESCRIPTION
        "-- empty --"
    ::= { lcsStatusTcpIpIcmp 3 }

-- {SCALAR} 310.1.9.3.4
lcsStatusTcpIpIcmpLanServiceErrors OBJECT-TYPE
    SYNTAX     Counter32
    MAX-ACCESS read-only
    STATUS     current
    DESCRIPTION
        "-- empty --"
    ::= { lcsStatusTcpIpIcmp 4 }

-- {SCALAR} 310.1.9.3.5
lcsStatusTcpIpIcmpWanRx OBJECT-TYPE
    SYNTAX     Counter32
    MAX-ACCESS read-only
    STATUS     current
    DESCRIPTION
        "-- empty --"
    ::= { lcsStatusTcpIpIcmp 5 }

-- {SCALAR} 310.1.9.3.6
lcsStatusTcpIpIcmpWanTx OBJECT-TYPE
    SYNTAX     Counter32
    MAX-ACCESS read-only
    STATUS     current
    DESCRIPTION
        "-- empty --"
    ::= { lcsStatusTcpIpIcmp 6 }

-- {SCALAR} 310.1.9.3.7
lcsStatusTcpIpIcmpWanChecksumErrors OBJECT-TYPE
    SYNTAX     Counter32
    MAX-ACCESS read-only
    STATUS     current
    DESCRIPTION
        "-- empty --"
    ::= { lcsStatusTcpIpIcmp 7 }

-- {SCALAR} 310.1.9.3.8
lcsStatusTcpIpIcmpWanServiceErrors OBJECT-TYPE
    SYNTAX     Counter32
    MAX-ACCESS read-only
    STATUS     current
    DESCRIPTION
        "-- empty --"
    ::= { lcsStatusTcpIpIcmp 8 }

-- {SCALAR} 310.1.9.3.9
lcsStatusTcpIpIcmpDeleteValues OBJECT-TYPE
    SYNTAX     DisplayString
    MAX-ACCESS read-write
    STATUS     current
    DESCRIPTION
        "-- empty --"
    ::= { lcsStatusTcpIpIcmp 9 }

-- {OID} 310.1.9.4
lcsStatusTcpIpTftp OBJECT IDENTIFIER ::= { lcsStatusTcpIp 4 }

-- {SCALAR} 310.1.9.4.1
lcsStatusTcpIpTftpLanRx OBJECT-TYPE
    SYNTAX     Counter32
    MAX-ACCESS read-only
    STATUS     current
    DESCRIPTION
        "-- empty --"
    ::= { lcsStatusTcpIpTftp 1 }

-- {SCALAR} 310.1.9.4.2
lcsStatusTcpIpTftpLanRxReadRequest OBJECT-TYPE
    SYNTAX     Counter32
    MAX-ACCESS read-only
    STATUS     current
    DESCRIPTION
        "-- empty --"
    ::= { lcsStatusTcpIpTftp 2 }

-- {SCALAR} 310.1.9.4.3
lcsStatusTcpIpTftpLanRxWriteRequest OBJECT-TYPE
    SYNTAX     Counter32
    MAX-ACCESS read-only
    STATUS     current
    DESCRIPTION
        "-- empty --"
    ::= { lcsStatusTcpIpTftp 3 }

-- {SCALAR} 310.1.9.4.4
lcsStatusTcpIpTftpLanRxData OBJECT-TYPE
    SYNTAX     Counter32
    MAX-ACCESS read-only
    STATUS     current
    DESCRIPTION
        "-- empty --"
    ::= { lcsStatusTcpIpTftp 4 }

-- {SCALAR} 310.1.9.4.5
lcsStatusTcpIpTftpLanRxAck OBJECT-TYPE
    SYNTAX     Counter32
    MAX-ACCESS read-only
    STATUS     current
    DESCRIPTION
        "-- empty --"
    ::= { lcsStatusTcpIpTftp 5 }

-- {SCALAR} 310.1.9.4.6
lcsStatusTcpIpTftpLanRxOptionAck OBJECT-TYPE
    SYNTAX     Counter32
    MAX-ACCESS read-only
    STATUS     current
    DESCRIPTION
        "-- empty --"
    ::= { lcsStatusTcpIpTftp 6 }

-- {SCALAR} 310.1.9.4.7
lcsStatusTcpIpTftpLanRxErrors OBJECT-TYPE
    SYNTAX     Counter32
    MAX-ACCESS read-only
    STATUS     current
    DESCRIPTION
        "-- empty --"
    ::= { lcsStatusTcpIpTftp 7 }

-- {SCALAR} 310.1.9.4.8
lcsStatusTcpIpTftpLanRxBadPackets OBJECT-TYPE
    SYNTAX     Counter32
    MAX-ACCESS read-only
    STATUS     current
    DESCRIPTION
        "-- empty --"
    ::= { lcsStatusTcpIpTftp 8 }

-- {SCALAR} 310.1.9.4.9
lcsStatusTcpIpTftpLanTx OBJECT-TYPE
    SYNTAX     Counter32
    MAX-ACCESS read-only
    STATUS     current
    DESCRIPTION
        "-- empty --"
    ::= { lcsStatusTcpIpTftp 9 }

-- {SCALAR} 310.1.9.4.10
lcsStatusTcpIpTftpLanTxData OBJECT-TYPE
    SYNTAX     Counter32
    MAX-ACCESS read-only
    STATUS     current
    DESCRIPTION
        "-- empty --"
    ::= { lcsStatusTcpIpTftp 10 }

-- {SCALAR} 310.1.9.4.11
lcsStatusTcpIpTftpLanTxAck OBJECT-TYPE
    SYNTAX     Counter32
    MAX-ACCESS read-only
    STATUS     current
    DESCRIPTION
        "-- empty --"
    ::= { lcsStatusTcpIpTftp 11 }

-- {SCALAR} 310.1.9.4.12
lcsStatusTcpIpTftpLanTxOptionAck OBJECT-TYPE
    SYNTAX     Counter32
    MAX-ACCESS read-only
    STATUS     current
    DESCRIPTION
        "-- empty --"
    ::= { lcsStatusTcpIpTftp 12 }

-- {SCALAR} 310.1.9.4.13
lcsStatusTcpIpTftpLanTxErrors OBJECT-TYPE
    SYNTAX     Counter32
    MAX-ACCESS read-only
    STATUS     current
    DESCRIPTION
        "-- empty --"
    ::= { lcsStatusTcpIpTftp 13 }

-- {SCALAR} 310.1.9.4.14
lcsStatusTcpIpTftpLanTxRepeats OBJECT-TYPE
    SYNTAX     Counter32
    MAX-ACCESS read-only
    STATUS     current
    DESCRIPTION
        "-- empty --"
    ::= { lcsStatusTcpIpTftp 14 }

-- {SCALAR} 310.1.9.4.15
lcsStatusTcpIpTftpLanConnections OBJECT-TYPE
    SYNTAX     Counter32
    MAX-ACCESS read-only
    STATUS     current
    DESCRIPTION
        "-- empty --"
    ::= { lcsStatusTcpIpTftp 15 }

-- {SCALAR} 310.1.9.4.16
lcsStatusTcpIpTftpWanRx OBJECT-TYPE
    SYNTAX     Counter32
    MAX-ACCESS read-only
    STATUS     current
    DESCRIPTION
        "-- empty --"
    ::= { lcsStatusTcpIpTftp 16 }

-- {SCALAR} 310.1.9.4.17
lcsStatusTcpIpTftpWanRxReadRequest OBJECT-TYPE
    SYNTAX     Counter32
    MAX-ACCESS read-only
    STATUS     current
    DESCRIPTION
        "-- empty --"
    ::= { lcsStatusTcpIpTftp 17 }

-- {SCALAR} 310.1.9.4.18
lcsStatusTcpIpTftpWanRxWriteRequest OBJECT-TYPE
    SYNTAX     Counter32
    MAX-ACCESS read-only
    STATUS     current
    DESCRIPTION
        "-- empty --"
    ::= { lcsStatusTcpIpTftp 18 }

-- {SCALAR} 310.1.9.4.19
lcsStatusTcpIpTftpWanRxData OBJECT-TYPE
    SYNTAX     Counter32
    MAX-ACCESS read-only
    STATUS     current
    DESCRIPTION
        "-- empty --"
    ::= { lcsStatusTcpIpTftp 19 }

-- {SCALAR} 310.1.9.4.20
lcsStatusTcpIpTftpWanRxAck OBJECT-TYPE
    SYNTAX     Counter32
    MAX-ACCESS read-only
    STATUS     current
    DESCRIPTION
        "-- empty --"
    ::= { lcsStatusTcpIpTftp 20 }

-- {SCALAR} 310.1.9.4.21
lcsStatusTcpIpTftpWanRxOptionAck OBJECT-TYPE
    SYNTAX     Counter32
    MAX-ACCESS read-only
    STATUS     current
    DESCRIPTION
        "-- empty --"
    ::= { lcsStatusTcpIpTftp 21 }

-- {SCALAR} 310.1.9.4.22
lcsStatusTcpIpTftpWanRxErrors OBJECT-TYPE
    SYNTAX     Counter32
    MAX-ACCESS read-only
    STATUS     current
    DESCRIPTION
        "-- empty --"
    ::= { lcsStatusTcpIpTftp 22 }

-- {SCALAR} 310.1.9.4.23
lcsStatusTcpIpTftpWanRxBadPackets OBJECT-TYPE
    SYNTAX     Counter32
    MAX-ACCESS read-only
    STATUS     current
    DESCRIPTION
        "-- empty --"
    ::= { lcsStatusTcpIpTftp 23 }

-- {SCALAR} 310.1.9.4.24
lcsStatusTcpIpTftpWanTx OBJECT-TYPE
    SYNTAX     Counter32
    MAX-ACCESS read-only
    STATUS     current
    DESCRIPTION
        "-- empty --"
    ::= { lcsStatusTcpIpTftp 24 }

-- {SCALAR} 310.1.9.4.25
lcsStatusTcpIpTftpWanTxData OBJECT-TYPE
    SYNTAX     Counter32
    MAX-ACCESS read-only
    STATUS     current
    DESCRIPTION
        "-- empty --"
    ::= { lcsStatusTcpIpTftp 25 }

-- {SCALAR} 310.1.9.4.26
lcsStatusTcpIpTftpWanTxAck OBJECT-TYPE
    SYNTAX     Counter32
    MAX-ACCESS read-only
    STATUS     current
    DESCRIPTION
        "-- empty --"
    ::= { lcsStatusTcpIpTftp 26 }

-- {SCALAR} 310.1.9.4.27
lcsStatusTcpIpTftpWanTxOptionAck OBJECT-TYPE
    SYNTAX     Counter32
    MAX-ACCESS read-only
    STATUS     current
    DESCRIPTION
        "-- empty --"
    ::= { lcsStatusTcpIpTftp 27 }

-- {SCALAR} 310.1.9.4.28
lcsStatusTcpIpTftpWanTxErrors OBJECT-TYPE
    SYNTAX     Counter32
    MAX-ACCESS read-only
    STATUS     current
    DESCRIPTION
        "-- empty --"
    ::= { lcsStatusTcpIpTftp 28 }

-- {SCALAR} 310.1.9.4.29
lcsStatusTcpIpTftpWanTxRepeats OBJECT-TYPE
    SYNTAX     Counter32
    MAX-ACCESS read-only
    STATUS     current
    DESCRIPTION
        "-- empty --"
    ::= { lcsStatusTcpIpTftp 29 }

-- {SCALAR} 310.1.9.4.30
lcsStatusTcpIpTftpWanConnections OBJECT-TYPE
    SYNTAX     Counter32
    MAX-ACCESS read-only
    STATUS     current
    DESCRIPTION
        "-- empty --"
    ::= { lcsStatusTcpIpTftp 30 }

-- {SCALAR} 310.1.9.4.31
lcsStatusTcpIpTftpDeleteValues OBJECT-TYPE
    SYNTAX     DisplayString
    MAX-ACCESS read-write
    STATUS     current
    DESCRIPTION
        "-- empty --"
    ::= { lcsStatusTcpIpTftp 31 }

-- {OID} 310.1.9.5
lcsStatusTcpIpTcp OBJECT IDENTIFIER ::= { lcsStatusTcpIp 5 }

-- {SCALAR} 310.1.9.5.1
lcsStatusTcpIpTcpLanRx OBJECT-TYPE
    SYNTAX     Counter32
    MAX-ACCESS read-only
    STATUS     current
    DESCRIPTION
        "-- empty --"
    ::= { lcsStatusTcpIpTcp 1 }

-- {SCALAR} 310.1.9.5.2
lcsStatusTcpIpTcpLanTx OBJECT-TYPE
    SYNTAX     Counter32
    MAX-ACCESS read-only
    STATUS     current
    DESCRIPTION
        "-- empty --"
    ::= { lcsStatusTcpIpTcp 2 }

-- {SCALAR} 310.1.9.5.3
lcsStatusTcpIpTcpLanTxRepeats OBJECT-TYPE
    SYNTAX     Counter32
    MAX-ACCESS read-only
    STATUS     current
    DESCRIPTION
        "-- empty --"
    ::= { lcsStatusTcpIpTcp 3 }

-- {SCALAR} 310.1.9.5.4
lcsStatusTcpIpTcpLanChecksumErrors OBJECT-TYPE
    SYNTAX     Counter32
    MAX-ACCESS read-only
    STATUS     current
    DESCRIPTION
        "-- empty --"
    ::= { lcsStatusTcpIpTcp 4 }

-- {SCALAR} 310.1.9.5.5
lcsStatusTcpIpTcpLanServiceErrors OBJECT-TYPE
    SYNTAX     Counter32
    MAX-ACCESS read-only
    STATUS     current
    DESCRIPTION
        "-- empty --"
    ::= { lcsStatusTcpIpTcp 5 }

-- {SCALAR} 310.1.9.5.6
lcsStatusTcpIpTcpLanConnections OBJECT-TYPE
    SYNTAX     Counter32
    MAX-ACCESS read-only
    STATUS     current
    DESCRIPTION
        "-- empty --"
    ::= { lcsStatusTcpIpTcp 6 }

-- {SCALAR} 310.1.9.5.7
lcsStatusTcpIpTcpWanRx OBJECT-TYPE
    SYNTAX     Counter32
    MAX-ACCESS read-only
    STATUS     current
    DESCRIPTION
        "-- empty --"
    ::= { lcsStatusTcpIpTcp 7 }

-- {SCALAR} 310.1.9.5.8
lcsStatusTcpIpTcpWanTx OBJECT-TYPE
    SYNTAX     Counter32
    MAX-ACCESS read-only
    STATUS     current
    DESCRIPTION
        "-- empty --"
    ::= { lcsStatusTcpIpTcp 8 }

-- {SCALAR} 310.1.9.5.9
lcsStatusTcpIpTcpWanTxRepeats OBJECT-TYPE
    SYNTAX     Counter32
    MAX-ACCESS read-only
    STATUS     current
    DESCRIPTION
        "-- empty --"
    ::= { lcsStatusTcpIpTcp 9 }

-- {SCALAR} 310.1.9.5.10
lcsStatusTcpIpTcpWanChecksumErrors OBJECT-TYPE
    SYNTAX     Counter32
    MAX-ACCESS read-only
    STATUS     current
    DESCRIPTION
        "-- empty --"
    ::= { lcsStatusTcpIpTcp 10 }

-- {SCALAR} 310.1.9.5.11
lcsStatusTcpIpTcpWanServiceErrors OBJECT-TYPE
    SYNTAX     Counter32
    MAX-ACCESS read-only
    STATUS     current
    DESCRIPTION
        "-- empty --"
    ::= { lcsStatusTcpIpTcp 11 }

-- {SCALAR} 310.1.9.5.12
lcsStatusTcpIpTcpWanConnections OBJECT-TYPE
    SYNTAX     Counter32
    MAX-ACCESS read-only
    STATUS     current
    DESCRIPTION
        "-- empty --"
    ::= { lcsStatusTcpIpTcp 12 }

-- {SCALAR} 310.1.9.5.13
lcsStatusTcpIpTcpDeleteValues OBJECT-TYPE
    SYNTAX     DisplayString
    MAX-ACCESS read-write
    STATUS     current
    DESCRIPTION
        "-- empty --"
    ::= { lcsStatusTcpIpTcp 13 }

-- {OID} 310.1.9.6
lcsStatusTcpIpDhcp OBJECT IDENTIFIER ::= { lcsStatusTcpIp 6 }

-- {SCALAR} 310.1.9.6.1
lcsStatusTcpIpDhcpLanRx OBJECT-TYPE
    SYNTAX     Counter32
    MAX-ACCESS read-only
    STATUS     current
    DESCRIPTION
        "-- empty --"
    ::= { lcsStatusTcpIpDhcp 1 }

-- {SCALAR} 310.1.9.6.2
lcsStatusTcpIpDhcpLanTx OBJECT-TYPE
    SYNTAX     Counter32
    MAX-ACCESS read-only
    STATUS     current
    DESCRIPTION
        "-- empty --"
    ::= { lcsStatusTcpIpDhcp 2 }

-- {SCALAR} 310.1.9.6.3
lcsStatusTcpIpDhcpWanRx OBJECT-TYPE
    SYNTAX     Counter32
    MAX-ACCESS read-only
    STATUS     current
    DESCRIPTION
        "-- empty --"
    ::= { lcsStatusTcpIpDhcp 3 }

-- {SCALAR} 310.1.9.6.19
lcsStatusTcpIpDhcpWanTx OBJECT-TYPE
    SYNTAX     Counter32
    MAX-ACCESS read-only
    STATUS     current
    DESCRIPTION
        "-- empty --"
    ::= { lcsStatusTcpIpDhcp 19 }

-- {SCALAR} 310.1.9.6.4
lcsStatusTcpIpDhcpDiscard OBJECT-TYPE
    SYNTAX     Counter32
    MAX-ACCESS read-only
    STATUS     current
    DESCRIPTION
        "-- empty --"
    ::= { lcsStatusTcpIpDhcp 4 }

-- {SCALAR} 310.1.9.6.5
lcsStatusTcpIpDhcpRxDiscover OBJECT-TYPE
    SYNTAX     Counter32
    MAX-ACCESS read-only
    STATUS     current
    DESCRIPTION
        "-- empty --"
    ::= { lcsStatusTcpIpDhcp 5 }

-- {SCALAR} 310.1.9.6.6
lcsStatusTcpIpDhcpRxRequest OBJECT-TYPE
    SYNTAX     Counter32
    MAX-ACCESS read-only
    STATUS     current
    DESCRIPTION
        "-- empty --"
    ::= { lcsStatusTcpIpDhcp 6 }

-- {SCALAR} 310.1.9.6.7
lcsStatusTcpIpDhcpRxDecline OBJECT-TYPE
    SYNTAX     Counter32
    MAX-ACCESS read-only
    STATUS     current
    DESCRIPTION
        "-- empty --"
    ::= { lcsStatusTcpIpDhcp 7 }

-- {SCALAR} 310.1.9.6.8
lcsStatusTcpIpDhcpRxInform OBJECT-TYPE
    SYNTAX     Counter32
    MAX-ACCESS read-only
    STATUS     current
    DESCRIPTION
        "-- empty --"
    ::= { lcsStatusTcpIpDhcp 8 }

-- {SCALAR} 310.1.9.6.9
lcsStatusTcpIpDhcpRxRelease OBJECT-TYPE
    SYNTAX     Counter32
    MAX-ACCESS read-only
    STATUS     current
    DESCRIPTION
        "-- empty --"
    ::= { lcsStatusTcpIpDhcp 9 }

-- {SCALAR} 310.1.9.6.10
lcsStatusTcpIpDhcpTxOffer OBJECT-TYPE
    SYNTAX     Counter32
    MAX-ACCESS read-only
    STATUS     current
    DESCRIPTION
        "-- empty --"
    ::= { lcsStatusTcpIpDhcp 10 }

-- {SCALAR} 310.1.9.6.11
lcsStatusTcpIpDhcpTxAck OBJECT-TYPE
    SYNTAX     Counter32
    MAX-ACCESS read-only
    STATUS     current
    DESCRIPTION
        "-- empty --"
    ::= { lcsStatusTcpIpDhcp 11 }

-- {SCALAR} 310.1.9.6.12
lcsStatusTcpIpDhcpTxNak OBJECT-TYPE
    SYNTAX     Counter32
    MAX-ACCESS read-only
    STATUS     current
    DESCRIPTION
        "-- empty --"
    ::= { lcsStatusTcpIpDhcp 12 }

-- {SCALAR} 310.1.9.6.13
lcsStatusTcpIpDhcpServerError OBJECT-TYPE
    SYNTAX     Counter32
    MAX-ACCESS read-only
    STATUS     current
    DESCRIPTION
        "-- empty --"
    ::= { lcsStatusTcpIpDhcp 13 }

-- {SCALAR} 310.1.9.6.14
lcsStatusTcpIpDhcpAssigned OBJECT-TYPE
    SYNTAX     INTEGER (0..2147483647)
    MAX-ACCESS read-only
    STATUS     current
    DESCRIPTION
        "-- empty --"
    ::= { lcsStatusTcpIpDhcp 14 }

-- {SCALAR} 310.1.9.6.15
lcsStatusTcpIpDhcpMacConflicts OBJECT-TYPE
    SYNTAX     Counter32
    MAX-ACCESS read-only
    STATUS     current
    DESCRIPTION
        "-- empty --"
    ::= { lcsStatusTcpIpDhcp 15 }

-- {TABLE} 310.1.9.6.20
lcsStatusTcpIpDhcpNetworkListTable OBJECT-TYPE
    SYNTAX     SEQUENCE OF LcsStatusTcpIpDhcpNetworkListEntry
    MAX-ACCESS not-accessible
    STATUS     current
    DESCRIPTION
        "-- empty --"
    ::= { lcsStatusTcpIpDhcp 20 }

-- {ENTRY} 310.1.9.6.20.1
lcsStatusTcpIpDhcpNetworkListEntry OBJECT-TYPE
    SYNTAX     LcsStatusTcpIpDhcpNetworkListEntry
    MAX-ACCESS not-accessible
    STATUS     current
    DESCRIPTION
        ""
    INDEX {
        lcsStatusTcpIpDhcpNetworkListEntryNetworkName
    }
    ::= { lcsStatusTcpIpDhcpNetworkListTable 1 }

-- {SEQUENCE}
LcsStatusTcpIpDhcpNetworkListEntry ::= SEQUENCE {
    lcsStatusTcpIpDhcpNetworkListEntryNetworkName DisplayString,
    lcsStatusTcpIpDhcpNetworkListEntryStartAddressPool IpAddress,
    lcsStatusTcpIpDhcpNetworkListEntryEndAddressPool IpAddress,
    lcsStatusTcpIpDhcpNetworkListEntryNetmask IpAddress,
    lcsStatusTcpIpDhcpNetworkListEntryBroadcastAddress IpAddress,
    lcsStatusTcpIpDhcpNetworkListEntryGatewayAddress IpAddress,
    lcsStatusTcpIpDhcpNetworkListEntryDnsDefault IpAddress,
    lcsStatusTcpIpDhcpNetworkListEntryDnsBackup IpAddress,
    lcsStatusTcpIpDhcpNetworkListEntryNbnsDefault IpAddress,
    lcsStatusTcpIpDhcpNetworkListEntryNbnsBackup IpAddress,
    lcsStatusTcpIpDhcpNetworkListEntryServerFlags DisplayString,
    lcsStatusTcpIpDhcpNetworkListEntryBroadcastBit INTEGER,
    lcsStatusTcpIpDhcpNetworkListEntryServerId IpAddress,
    lcsStatusTcpIpDhcpNetworkListEntryLanIfc INTEGER,
    lcsStatusTcpIpDhcpNetworkListEntryVlanId INTEGER,
    lcsStatusTcpIpDhcpNetworkListEntryMasterServer IpAddress,
    lcsStatusTcpIpDhcpNetworkListEntry2ndMasterServer IpAddress,
    lcsStatusTcpIpDhcpNetworkListEntry3rdMasterServer IpAddress,
    lcsStatusTcpIpDhcpNetworkListEntry4thMasterServer IpAddress,
    lcsStatusTcpIpDhcpNetworkListEntryCache INTEGER,
    lcsStatusTcpIpDhcpNetworkListEntryAdaption INTEGER,
    lcsStatusTcpIpDhcpNetworkListEntryCluster INTEGER
}

-- {COLUMN} 310.1.9.6.20.1.1
lcsStatusTcpIpDhcpNetworkListEntryNetworkName OBJECT-TYPE
    SYNTAX     DisplayString (SIZE(0..16))
    MAX-ACCESS read-only
    STATUS     current
    DESCRIPTION
        "-- empty --"
    ::= { lcsStatusTcpIpDhcpNetworkListEntry 1 }

-- {COLUMN} 310.1.9.6.20.1.2
lcsStatusTcpIpDhcpNetworkListEntryStartAddressPool OBJECT-TYPE
    SYNTAX     IpAddress
    MAX-ACCESS read-only
    STATUS     current
    DESCRIPTION
        "-- empty --"
    ::= { lcsStatusTcpIpDhcpNetworkListEntry 2 }

-- {COLUMN} 310.1.9.6.20.1.3
lcsStatusTcpIpDhcpNetworkListEntryEndAddressPool OBJECT-TYPE
    SYNTAX     IpAddress
    MAX-ACCESS read-only
    STATUS     current
    DESCRIPTION
        "-- empty --"
    ::= { lcsStatusTcpIpDhcpNetworkListEntry 3 }

-- {COLUMN} 310.1.9.6.20.1.4
lcsStatusTcpIpDhcpNetworkListEntryNetmask OBJECT-TYPE
    SYNTAX     IpAddress
    MAX-ACCESS read-only
    STATUS     current
    DESCRIPTION
        "-- empty --"
    ::= { lcsStatusTcpIpDhcpNetworkListEntry 4 }

-- {COLUMN} 310.1.9.6.20.1.5
lcsStatusTcpIpDhcpNetworkListEntryBroadcastAddress OBJECT-TYPE
    SYNTAX     IpAddress
    MAX-ACCESS read-only
    STATUS     current
    DESCRIPTION
        "-- empty --"
    ::= { lcsStatusTcpIpDhcpNetworkListEntry 5 }

-- {COLUMN} 310.1.9.6.20.1.6
lcsStatusTcpIpDhcpNetworkListEntryGatewayAddress OBJECT-TYPE
    SYNTAX     IpAddress
    MAX-ACCESS read-only
    STATUS     current
    DESCRIPTION
        "-- empty --"
    ::= { lcsStatusTcpIpDhcpNetworkListEntry 6 }

-- {COLUMN} 310.1.9.6.20.1.7
lcsStatusTcpIpDhcpNetworkListEntryDnsDefault OBJECT-TYPE
    SYNTAX     IpAddress
    MAX-ACCESS read-only
    STATUS     current
    DESCRIPTION
        "-- empty --"
    ::= { lcsStatusTcpIpDhcpNetworkListEntry 7 }

-- {COLUMN} 310.1.9.6.20.1.8
lcsStatusTcpIpDhcpNetworkListEntryDnsBackup OBJECT-TYPE
    SYNTAX     IpAddress
    MAX-ACCESS read-only
    STATUS     current
    DESCRIPTION
        "-- empty --"
    ::= { lcsStatusTcpIpDhcpNetworkListEntry 8 }

-- {COLUMN} 310.1.9.6.20.1.9
lcsStatusTcpIpDhcpNetworkListEntryNbnsDefault OBJECT-TYPE
    SYNTAX     IpAddress
    MAX-ACCESS read-only
    STATUS     current
    DESCRIPTION
        "-- empty --"
    ::= { lcsStatusTcpIpDhcpNetworkListEntry 9 }

-- {COLUMN} 310.1.9.6.20.1.10
lcsStatusTcpIpDhcpNetworkListEntryNbnsBackup OBJECT-TYPE
    SYNTAX     IpAddress
    MAX-ACCESS read-only
    STATUS     current
    DESCRIPTION
        "-- empty --"
    ::= { lcsStatusTcpIpDhcpNetworkListEntry 10 }

-- {COLUMN} 310.1.9.6.20.1.11
lcsStatusTcpIpDhcpNetworkListEntryServerFlags OBJECT-TYPE
    SYNTAX     DisplayString (SIZE(0..255))
    MAX-ACCESS read-only
    STATUS     current
    DESCRIPTION
        "-- empty --"
    ::= { lcsStatusTcpIpDhcpNetworkListEntry 11 }

-- {COLUMN} 310.1.9.6.20.1.13
lcsStatusTcpIpDhcpNetworkListEntryBroadcastBit OBJECT-TYPE
    SYNTAX     INTEGER
      {
        eNo (0),
        eYes (1)
      }
    MAX-ACCESS read-only
    STATUS     current
    DESCRIPTION
        "-- empty --"
    ::= { lcsStatusTcpIpDhcpNetworkListEntry 13 }

-- {COLUMN} 310.1.9.6.20.1.14
lcsStatusTcpIpDhcpNetworkListEntryServerId OBJECT-TYPE
    SYNTAX     IpAddress
    MAX-ACCESS read-only
    STATUS     current
    DESCRIPTION
        "-- empty --"
    ::= { lcsStatusTcpIpDhcpNetworkListEntry 14 }

-- {COLUMN} 310.1.9.6.20.1.24
lcsStatusTcpIpDhcpNetworkListEntryLanIfc OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusTcpIpDhcpNetworkListEntry 24 }

-- {COLUMN} 310.1.9.6.20.1.16
lcsStatusTcpIpDhcpNetworkListEntryVlanId OBJECT-TYPE
    SYNTAX     INTEGER (0..65535)
    MAX-ACCESS read-only
    STATUS     current
    DESCRIPTION
        "-- empty --"
    ::= { lcsStatusTcpIpDhcpNetworkListEntry 16 }

-- {COLUMN} 310.1.9.6.20.1.17
lcsStatusTcpIpDhcpNetworkListEntryMasterServer OBJECT-TYPE
    SYNTAX     IpAddress
    MAX-ACCESS read-only
    STATUS     current
    DESCRIPTION
        "-- empty --"
    ::= { lcsStatusTcpIpDhcpNetworkListEntry 17 }

-- {COLUMN} 310.1.9.6.20.1.21
lcsStatusTcpIpDhcpNetworkListEntry2ndMasterServer OBJECT-TYPE
    SYNTAX     IpAddress
    MAX-ACCESS read-only
    STATUS     current
    DESCRIPTION
        "-- empty --"
    ::= { lcsStatusTcpIpDhcpNetworkListEntry 21 }

-- {COLUMN} 310.1.9.6.20.1.22
lcsStatusTcpIpDhcpNetworkListEntry3rdMasterServer OBJECT-TYPE
    SYNTAX     IpAddress
    MAX-ACCESS read-only
    STATUS     current
    DESCRIPTION
        "-- empty --"
    ::= { lcsStatusTcpIpDhcpNetworkListEntry 22 }

-- {COLUMN} 310.1.9.6.20.1.23
lcsStatusTcpIpDhcpNetworkListEntry4thMasterServer OBJECT-TYPE
    SYNTAX     IpAddress
    MAX-ACCESS read-only
    STATUS     current
    DESCRIPTION
        "-- empty --"
    ::= { lcsStatusTcpIpDhcpNetworkListEntry 23 }

-- {COLUMN} 310.1.9.6.20.1.18
lcsStatusTcpIpDhcpNetworkListEntryCache OBJECT-TYPE
    SYNTAX     INTEGER
      {
        eNo (0),
        eYes (1)
      }
    MAX-ACCESS read-only
    STATUS     current
    DESCRIPTION
        "-- empty --"
    ::= { lcsStatusTcpIpDhcpNetworkListEntry 18 }

-- {COLUMN} 310.1.9.6.20.1.19
lcsStatusTcpIpDhcpNetworkListEntryAdaption OBJECT-TYPE
    SYNTAX     INTEGER
      {
        eNo (0),
        eYes (1)
      }
    MAX-ACCESS read-only
    STATUS     current
    DESCRIPTION
        "-- empty --"
    ::= { lcsStatusTcpIpDhcpNetworkListEntry 19 }

-- {COLUMN} 310.1.9.6.20.1.20
lcsStatusTcpIpDhcpNetworkListEntryCluster OBJECT-TYPE
    SYNTAX     INTEGER
      {
        eNo (0),
        eYes (1)
      }
    MAX-ACCESS read-only
    STATUS     current
    DESCRIPTION
        "-- empty --"
    ::= { lcsStatusTcpIpDhcpNetworkListEntry 20 }

-- {TABLE} 310.1.9.6.16
lcsStatusTcpIpDhcpDhcpTableTable OBJECT-TYPE
    SYNTAX     SEQUENCE OF LcsStatusTcpIpDhcpDhcpTableEntry
    MAX-ACCESS not-accessible
    STATUS     current
    DESCRIPTION
        "-- empty --"
    ::= { lcsStatusTcpIpDhcp 16 }

-- {ENTRY} 310.1.9.6.16.1
lcsStatusTcpIpDhcpDhcpTableEntry OBJECT-TYPE
    SYNTAX     LcsStatusTcpIpDhcpDhcpTableEntry
    MAX-ACCESS not-accessible
    STATUS     current
    DESCRIPTION
        ""
    INDEX {
        lcsStatusTcpIpDhcpDhcpTableEntryIpAddress,
        lcsStatusTcpIpDhcpDhcpTableEntryNetworkName
    }
    ::= { lcsStatusTcpIpDhcpDhcpTableTable 1 }

-- {SEQUENCE}
LcsStatusTcpIpDhcpDhcpTableEntry ::= SEQUENCE {
    lcsStatusTcpIpDhcpDhcpTableEntryIpAddress IpAddress,
    lcsStatusTcpIpDhcpDhcpTableEntryMacAddress DisplayString,
    lcsStatusTcpIpDhcpDhcpTableEntryTimeout INTEGER,
    lcsStatusTcpIpDhcpDhcpTableEntryHostname DisplayString,
    lcsStatusTcpIpDhcpDhcpTableEntryType BITS,
    lcsStatusTcpIpDhcpDhcpTableEntryLanIfc INTEGER,
    lcsStatusTcpIpDhcpDhcpTableEntryVlanId INTEGER,
    lcsStatusTcpIpDhcpDhcpTableEntryNetworkName DisplayString,
    lcsStatusTcpIpDhcpDhcpTableEntryAssignment DisplayString,
    lcsStatusTcpIpDhcpDhcpTableEntryAssignmentNumeric Gauge32
}

-- {COLUMN} 310.1.9.6.16.1.1
lcsStatusTcpIpDhcpDhcpTableEntryIpAddress OBJECT-TYPE
    SYNTAX     IpAddress
    MAX-ACCESS read-only
    STATUS     current
    DESCRIPTION
        "-- empty --"
    ::= { lcsStatusTcpIpDhcpDhcpTableEntry 1 }

-- {COLUMN} 310.1.9.6.16.1.2
lcsStatusTcpIpDhcpDhcpTableEntryMacAddress OBJECT-TYPE
    SYNTAX     DisplayString (SIZE(0..12))
    MAX-ACCESS read-only
    STATUS     current
    DESCRIPTION
        "-- empty --"
    ::= { lcsStatusTcpIpDhcpDhcpTableEntry 2 }

-- {COLUMN} 310.1.9.6.16.1.3
lcsStatusTcpIpDhcpDhcpTableEntryTimeout OBJECT-TYPE
    SYNTAX     INTEGER (0..2147483647)
    MAX-ACCESS read-only
    STATUS     current
    DESCRIPTION
        "-- empty --"
    ::= { lcsStatusTcpIpDhcpDhcpTableEntry 3 }

-- {COLUMN} 310.1.9.6.16.1.4
lcsStatusTcpIpDhcpDhcpTableEntryHostname OBJECT-TYPE
    SYNTAX     DisplayString (SIZE(0..65))
    MAX-ACCESS read-only
    STATUS     current
    DESCRIPTION
        "-- empty --"
    ::= { lcsStatusTcpIpDhcpDhcpTableEntry 4 }

-- {COLUMN} 310.1.9.6.16.1.5
lcsStatusTcpIpDhcpDhcpTableEntryType OBJECT-TYPE
    SYNTAX     BITS
      {
        enew (15),
        enewreq (14),
        eDyn (11),
        eUnkn (13),
        eStat (12),
        eBootp (10),
        eRelay (4),
        eCache (8)
      }
    MAX-ACCESS read-only
    STATUS     current
    DESCRIPTION
        "-- empty --"
    ::= { lcsStatusTcpIpDhcpDhcpTableEntry 5 }

-- {COLUMN} 310.1.9.6.16.1.10
lcsStatusTcpIpDhcpDhcpTableEntryLanIfc OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusTcpIpDhcpDhcpTableEntry 10 }

-- {COLUMN} 310.1.9.6.16.1.8
lcsStatusTcpIpDhcpDhcpTableEntryVlanId OBJECT-TYPE
    SYNTAX     INTEGER (0..65535)
    MAX-ACCESS read-only
    STATUS     current
    DESCRIPTION
        "-- empty --"
    ::= { lcsStatusTcpIpDhcpDhcpTableEntry 8 }

-- {COLUMN} 310.1.9.6.16.1.9
lcsStatusTcpIpDhcpDhcpTableEntryNetworkName OBJECT-TYPE
    SYNTAX     DisplayString (SIZE(0..17))
    MAX-ACCESS read-only
    STATUS     current
    DESCRIPTION
        "-- empty --"
    ::= { lcsStatusTcpIpDhcpDhcpTableEntry 9 }

-- {COLUMN} 310.1.9.6.16.1.11
lcsStatusTcpIpDhcpDhcpTableEntryAssignment OBJECT-TYPE
    SYNTAX     DisplayString (SIZE(0..21))
    MAX-ACCESS read-only
    STATUS     current
    DESCRIPTION
        "-- empty --"
    ::= { lcsStatusTcpIpDhcpDhcpTableEntry 11 }

-- {COLUMN} 310.1.9.6.16.1.12
lcsStatusTcpIpDhcpDhcpTableEntryAssignmentNumeric OBJECT-TYPE
    SYNTAX     Gauge32
    MAX-ACCESS read-only
    STATUS     current
    DESCRIPTION
        "-- empty --"
    ::= { lcsStatusTcpIpDhcpDhcpTableEntry 12 }

-- {SCALAR} 310.1.9.6.18
lcsStatusTcpIpDhcpDeleteValues OBJECT-TYPE
    SYNTAX     DisplayString
    MAX-ACCESS read-write
    STATUS     current
    DESCRIPTION
        "-- empty --"
    ::= { lcsStatusTcpIpDhcp 18 }

-- {SCALAR} 310.1.9.7
lcsStatusTcpIpDeleteValues OBJECT-TYPE
    SYNTAX     DisplayString
    MAX-ACCESS read-write
    STATUS     current
    DESCRIPTION
        "-- empty --"
    ::= { lcsStatusTcpIp 7 }

-- {OID} 310.1.9.8
lcsStatusTcpIpNetbios OBJECT IDENTIFIER ::= { lcsStatusTcpIp 8 }

-- {SCALAR} 310.1.9.8.1
lcsStatusTcpIpNetbiosLanRx OBJECT-TYPE
    SYNTAX     Counter32
    MAX-ACCESS read-only
    STATUS     current
    DESCRIPTION
        "-- empty --"
    ::= { lcsStatusTcpIpNetbios 1 }

-- {SCALAR} 310.1.9.8.2
lcsStatusTcpIpNetbiosLanTx OBJECT-TYPE
    SYNTAX     Counter32
    MAX-ACCESS read-only
    STATUS     current
    DESCRIPTION
        "-- empty --"
    ::= { lcsStatusTcpIpNetbios 2 }

-- {SCALAR} 310.1.9.8.3
lcsStatusTcpIpNetbiosWanRx OBJECT-TYPE
    SYNTAX     Counter32
    MAX-ACCESS read-only
    STATUS     current
    DESCRIPTION
        "-- empty --"
    ::= { lcsStatusTcpIpNetbios 3 }

-- {SCALAR} 310.1.9.8.4
lcsStatusTcpIpNetbiosWanTx OBJECT-TYPE
    SYNTAX     Counter32
    MAX-ACCESS read-only
    STATUS     current
    DESCRIPTION
        "-- empty --"
    ::= { lcsStatusTcpIpNetbios 4 }

-- {SCALAR} 310.1.9.8.5
lcsStatusTcpIpNetbiosRegisters OBJECT-TYPE
    SYNTAX     Counter32
    MAX-ACCESS read-only
    STATUS     current
    DESCRIPTION
        "-- empty --"
    ::= { lcsStatusTcpIpNetbios 5 }

-- {SCALAR} 310.1.9.8.6
lcsStatusTcpIpNetbiosConflicts OBJECT-TYPE
    SYNTAX     Counter32
    MAX-ACCESS read-only
    STATUS     current
    DESCRIPTION
        "-- empty --"
    ::= { lcsStatusTcpIpNetbios 6 }

-- {SCALAR} 310.1.9.8.7
lcsStatusTcpIpNetbiosReleases OBJECT-TYPE
    SYNTAX     Counter32
    MAX-ACCESS read-only
    STATUS     current
    DESCRIPTION
        "-- empty --"
    ::= { lcsStatusTcpIpNetbios 7 }

-- {SCALAR} 310.1.9.8.8
lcsStatusTcpIpNetbiosRefreshs OBJECT-TYPE
    SYNTAX     Counter32
    MAX-ACCESS read-only
    STATUS     current
    DESCRIPTION
        "-- empty --"
    ::= { lcsStatusTcpIpNetbios 8 }

-- {SCALAR} 310.1.9.8.9
lcsStatusTcpIpNetbiosTimeouts OBJECT-TYPE
    SYNTAX     Counter32
    MAX-ACCESS read-only
    STATUS     current
    DESCRIPTION
        "-- empty --"
    ::= { lcsStatusTcpIpNetbios 9 }

-- {SCALAR} 310.1.9.8.10
lcsStatusTcpIpNetbiosHosts OBJECT-TYPE
    SYNTAX     INTEGER (0..2147483647)
    MAX-ACCESS read-only
    STATUS     current
    DESCRIPTION
        "-- empty --"
    ::= { lcsStatusTcpIpNetbios 10 }

-- {SCALAR} 310.1.9.8.11
lcsStatusTcpIpNetbiosGroups OBJECT-TYPE
    SYNTAX     INTEGER (0..2147483647)
    MAX-ACCESS read-only
    STATUS     current
    DESCRIPTION
        "-- empty --"
    ::= { lcsStatusTcpIpNetbios 11 }

-- {SCALAR} 310.1.9.8.12
lcsStatusTcpIpNetbiosBNodes OBJECT-TYPE
    SYNTAX     INTEGER (0..2147483647)
    MAX-ACCESS read-only
    STATUS     current
    DESCRIPTION
        "-- empty --"
    ::= { lcsStatusTcpIpNetbios 12 }

-- {SCALAR} 310.1.9.8.13
lcsStatusTcpIpNetbiosPNodes OBJECT-TYPE
    SYNTAX     INTEGER (0..2147483647)
    MAX-ACCESS read-only
    STATUS     current
    DESCRIPTION
        "-- empty --"
    ::= { lcsStatusTcpIpNetbios 13 }

-- {SCALAR} 310.1.9.8.14
lcsStatusTcpIpNetbiosMNodes OBJECT-TYPE
    SYNTAX     INTEGER (0..2147483647)
    MAX-ACCESS read-only
    STATUS     current
    DESCRIPTION
        "-- empty --"
    ::= { lcsStatusTcpIpNetbios 14 }

-- {SCALAR} 310.1.9.8.15
lcsStatusTcpIpNetbiosWNodes OBJECT-TYPE
    SYNTAX     INTEGER (0..2147483647)
    MAX-ACCESS read-only
    STATUS     current
    DESCRIPTION
        "-- empty --"
    ::= { lcsStatusTcpIpNetbios 15 }

-- {TABLE} 310.1.9.8.16
lcsStatusTcpIpNetbiosPeersTable OBJECT-TYPE
    SYNTAX     SEQUENCE OF LcsStatusTcpIpNetbiosPeersEntry
    MAX-ACCESS not-accessible
    STATUS     current
    DESCRIPTION
        "-- empty --"
    ::= { lcsStatusTcpIpNetbios 16 }

-- {ENTRY} 310.1.9.8.16.1
lcsStatusTcpIpNetbiosPeersEntry OBJECT-TYPE
    SYNTAX     LcsStatusTcpIpNetbiosPeersEntry
    MAX-ACCESS not-accessible
    STATUS     current
    DESCRIPTION
        ""
    INDEX {
        lcsStatusTcpIpNetbiosPeersEntryName
    }
    ::= { lcsStatusTcpIpNetbiosPeersTable 1 }

-- {SEQUENCE}
LcsStatusTcpIpNetbiosPeersEntry ::= SEQUENCE {
    lcsStatusTcpIpNetbiosPeersEntryName DisplayString,
    lcsStatusTcpIpNetbiosPeersEntryType INTEGER,
    lcsStatusTcpIpNetbiosPeersEntryBackoff INTEGER,
    lcsStatusTcpIpNetbiosPeersEntryTime INTEGER
}

-- {COLUMN} 310.1.9.8.16.1.1
lcsStatusTcpIpNetbiosPeersEntryName OBJECT-TYPE
    SYNTAX     DisplayString (SIZE(0..16))
    MAX-ACCESS read-only
    STATUS     current
    DESCRIPTION
        "-- empty --"
    ::= { lcsStatusTcpIpNetbiosPeersEntry 1 }

-- {COLUMN} 310.1.9.8.16.1.2
lcsStatusTcpIpNetbiosPeersEntryType OBJECT-TYPE
    SYNTAX     INTEGER
      {
        eWorkstation (1),
        eRouter (0)
      }
    MAX-ACCESS read-only
    STATUS     current
    DESCRIPTION
        "-- empty --"
    ::= { lcsStatusTcpIpNetbiosPeersEntry 2 }

-- {COLUMN} 310.1.9.8.16.1.3
lcsStatusTcpIpNetbiosPeersEntryBackoff OBJECT-TYPE
    SYNTAX     INTEGER (0..255)
    MAX-ACCESS read-only
    STATUS     current
    DESCRIPTION
        "-- empty --"
    ::= { lcsStatusTcpIpNetbiosPeersEntry 3 }

-- {COLUMN} 310.1.9.8.16.1.4
lcsStatusTcpIpNetbiosPeersEntryTime OBJECT-TYPE
    SYNTAX     INTEGER (0..65535)
    MAX-ACCESS read-only
    STATUS     current
    DESCRIPTION
        "-- empty --"
    ::= { lcsStatusTcpIpNetbiosPeersEntry 4 }

-- {TABLE} 310.1.9.8.18
lcsStatusTcpIpNetbiosNetworksTable OBJECT-TYPE
    SYNTAX     SEQUENCE OF LcsStatusTcpIpNetbiosNetworksEntry
    MAX-ACCESS not-accessible
    STATUS     current
    DESCRIPTION
        "-- empty --"
    ::= { lcsStatusTcpIpNetbios 18 }

-- {ENTRY} 310.1.9.8.18.1
lcsStatusTcpIpNetbiosNetworksEntry OBJECT-TYPE
    SYNTAX     LcsStatusTcpIpNetbiosNetworksEntry
    MAX-ACCESS not-accessible
    STATUS     current
    DESCRIPTION
        ""
    INDEX {
        lcsStatusTcpIpNetbiosNetworksEntryNetworkName
    }
    ::= { lcsStatusTcpIpNetbiosNetworksTable 1 }

-- {SEQUENCE}
LcsStatusTcpIpNetbiosNetworksEntry ::= SEQUENCE {
    lcsStatusTcpIpNetbiosNetworksEntryNetworkName DisplayString,
    lcsStatusTcpIpNetbiosNetworksEntryNtDomain DisplayString,
    lcsStatusTcpIpNetbiosNetworksEntryRtgTag INTEGER,
    lcsStatusTcpIpNetbiosNetworksEntryInterface INTEGER,
    lcsStatusTcpIpNetbiosNetworksEntryVlanId INTEGER
}

-- {COLUMN} 310.1.9.8.18.1.1
lcsStatusTcpIpNetbiosNetworksEntryNetworkName OBJECT-TYPE
    SYNTAX     DisplayString (SIZE(0..16))
    MAX-ACCESS read-only
    STATUS     current
    DESCRIPTION
        "-- empty --"
    ::= { lcsStatusTcpIpNetbiosNetworksEntry 1 }

-- {COLUMN} 310.1.9.8.18.1.2
lcsStatusTcpIpNetbiosNetworksEntryNtDomain OBJECT-TYPE
    SYNTAX     DisplayString (SIZE(0..15))
    MAX-ACCESS read-only
    STATUS     current
    DESCRIPTION
        "-- empty --"
    ::= { lcsStatusTcpIpNetbiosNetworksEntry 2 }

-- {COLUMN} 310.1.9.8.18.1.3
lcsStatusTcpIpNetbiosNetworksEntryRtgTag OBJECT-TYPE
    SYNTAX     INTEGER (0..65535)
    MAX-ACCESS read-only
    STATUS     current
    DESCRIPTION
        "-- empty --"
    ::= { lcsStatusTcpIpNetbiosNetworksEntry 3 }

-- {COLUMN} 310.1.9.8.18.1.7
lcsStatusTcpIpNetbiosNetworksEntryInterface OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusTcpIpNetbiosNetworksEntry 7 }

-- {COLUMN} 310.1.9.8.18.1.5
lcsStatusTcpIpNetbiosNetworksEntryVlanId OBJECT-TYPE
    SYNTAX     INTEGER (0..65535)
    MAX-ACCESS read-only
    STATUS     current
    DESCRIPTION
        "-- empty --"
    ::= { lcsStatusTcpIpNetbiosNetworksEntry 5 }

-- {TABLE} 310.1.9.8.19
lcsStatusTcpIpNetbiosGroupListTable OBJECT-TYPE
    SYNTAX     SEQUENCE OF LcsStatusTcpIpNetbiosGroupListEntry
    MAX-ACCESS not-accessible
    STATUS     current
    DESCRIPTION
        "-- empty --"
    ::= { lcsStatusTcpIpNetbios 19 }

-- {ENTRY} 310.1.9.8.19.1
lcsStatusTcpIpNetbiosGroupListEntry OBJECT-TYPE
    SYNTAX     LcsStatusTcpIpNetbiosGroupListEntry
    MAX-ACCESS not-accessible
    STATUS     current
    DESCRIPTION
        ""
    INDEX {
        lcsStatusTcpIpNetbiosGroupListEntryGroupDomain,
        lcsStatusTcpIpNetbiosGroupListEntryType,
        lcsStatusTcpIpNetbiosGroupListEntryIpAddress,
        lcsStatusTcpIpNetbiosGroupListEntryRtgTag
    }
    ::= { lcsStatusTcpIpNetbiosGroupListTable 1 }

-- {SEQUENCE}
LcsStatusTcpIpNetbiosGroupListEntry ::= SEQUENCE {
    lcsStatusTcpIpNetbiosGroupListEntryGroupDomain DisplayString,
    lcsStatusTcpIpNetbiosGroupListEntryType DisplayString,
    lcsStatusTcpIpNetbiosGroupListEntryIpAddress IpAddress,
    lcsStatusTcpIpNetbiosGroupListEntryRtgTag INTEGER,
    lcsStatusTcpIpNetbiosGroupListEntryPeer DisplayString,
    lcsStatusTcpIpNetbiosGroupListEntryNetworkName DisplayString,
    lcsStatusTcpIpNetbiosGroupListEntryTimeout INTEGER,
    lcsStatusTcpIpNetbiosGroupListEntryFlags DisplayString
}

-- {COLUMN} 310.1.9.8.19.1.1
lcsStatusTcpIpNetbiosGroupListEntryGroupDomain OBJECT-TYPE
    SYNTAX     DisplayString (SIZE(0..15))
    MAX-ACCESS read-only
    STATUS     current
    DESCRIPTION
        "-- empty --"
    ::= { lcsStatusTcpIpNetbiosGroupListEntry 1 }

-- {COLUMN} 310.1.9.8.19.1.2
lcsStatusTcpIpNetbiosGroupListEntryType OBJECT-TYPE
    SYNTAX     DisplayString (SIZE(0..1))
    MAX-ACCESS read-only
    STATUS     current
    DESCRIPTION
        "-- empty --"
    ::= { lcsStatusTcpIpNetbiosGroupListEntry 2 }

-- {COLUMN} 310.1.9.8.19.1.3
lcsStatusTcpIpNetbiosGroupListEntryIpAddress OBJECT-TYPE
    SYNTAX     IpAddress
    MAX-ACCESS read-only
    STATUS     current
    DESCRIPTION
        "-- empty --"
    ::= { lcsStatusTcpIpNetbiosGroupListEntry 3 }

-- {COLUMN} 310.1.9.8.19.1.8
lcsStatusTcpIpNetbiosGroupListEntryRtgTag OBJECT-TYPE
    SYNTAX     INTEGER (0..65535)
    MAX-ACCESS read-only
    STATUS     current
    DESCRIPTION
        "-- empty --"
    ::= { lcsStatusTcpIpNetbiosGroupListEntry 8 }

-- {COLUMN} 310.1.9.8.19.1.4
lcsStatusTcpIpNetbiosGroupListEntryPeer OBJECT-TYPE
    SYNTAX     DisplayString (SIZE(0..16))
    MAX-ACCESS read-only
    STATUS     current
    DESCRIPTION
        "-- empty --"
    ::= { lcsStatusTcpIpNetbiosGroupListEntry 4 }

-- {COLUMN} 310.1.9.8.19.1.7
lcsStatusTcpIpNetbiosGroupListEntryNetworkName OBJECT-TYPE
    SYNTAX     DisplayString (SIZE(0..16))
    MAX-ACCESS read-only
    STATUS     current
    DESCRIPTION
        "-- empty --"
    ::= { lcsStatusTcpIpNetbiosGroupListEntry 7 }

-- {COLUMN} 310.1.9.8.19.1.5
lcsStatusTcpIpNetbiosGroupListEntryTimeout OBJECT-TYPE
    SYNTAX     INTEGER (0..2147483647)
    MAX-ACCESS read-only
    STATUS     current
    DESCRIPTION
        "-- empty --"
    ::= { lcsStatusTcpIpNetbiosGroupListEntry 5 }

-- {COLUMN} 310.1.9.8.19.1.6
lcsStatusTcpIpNetbiosGroupListEntryFlags OBJECT-TYPE
    SYNTAX     DisplayString (SIZE(0..2))
    MAX-ACCESS read-only
    STATUS     current
    DESCRIPTION
        "-- empty --"
    ::= { lcsStatusTcpIpNetbiosGroupListEntry 6 }

-- {TABLE} 310.1.9.8.20
lcsStatusTcpIpNetbiosHostListTable OBJECT-TYPE
    SYNTAX     SEQUENCE OF LcsStatusTcpIpNetbiosHostListEntry
    MAX-ACCESS not-accessible
    STATUS     current
    DESCRIPTION
        "-- empty --"
    ::= { lcsStatusTcpIpNetbios 20 }

-- {ENTRY} 310.1.9.8.20.1
lcsStatusTcpIpNetbiosHostListEntry OBJECT-TYPE
    SYNTAX     LcsStatusTcpIpNetbiosHostListEntry
    MAX-ACCESS not-accessible
    STATUS     current
    DESCRIPTION
        ""
    INDEX {
        lcsStatusTcpIpNetbiosHostListEntryName,
        lcsStatusTcpIpNetbiosHostListEntryType,
        lcsStatusTcpIpNetbiosHostListEntryIpAddress,
        lcsStatusTcpIpNetbiosHostListEntryRtgTag
    }
    ::= { lcsStatusTcpIpNetbiosHostListTable 1 }

-- {SEQUENCE}
LcsStatusTcpIpNetbiosHostListEntry ::= SEQUENCE {
    lcsStatusTcpIpNetbiosHostListEntryName DisplayString,
    lcsStatusTcpIpNetbiosHostListEntryType DisplayString,
    lcsStatusTcpIpNetbiosHostListEntryIpAddress IpAddress,
    lcsStatusTcpIpNetbiosHostListEntryRtgTag INTEGER,
    lcsStatusTcpIpNetbiosHostListEntryPeer DisplayString,
    lcsStatusTcpIpNetbiosHostListEntryNetworkName DisplayString,
    lcsStatusTcpIpNetbiosHostListEntryTimeout INTEGER,
    lcsStatusTcpIpNetbiosHostListEntryFlags DisplayString
}

-- {COLUMN} 310.1.9.8.20.1.1
lcsStatusTcpIpNetbiosHostListEntryName OBJECT-TYPE
    SYNTAX     DisplayString (SIZE(0..15))
    MAX-ACCESS read-only
    STATUS     current
    DESCRIPTION
        "-- empty --"
    ::= { lcsStatusTcpIpNetbiosHostListEntry 1 }

-- {COLUMN} 310.1.9.8.20.1.2
lcsStatusTcpIpNetbiosHostListEntryType OBJECT-TYPE
    SYNTAX     DisplayString (SIZE(0..1))
    MAX-ACCESS read-only
    STATUS     current
    DESCRIPTION
        "-- empty --"
    ::= { lcsStatusTcpIpNetbiosHostListEntry 2 }

-- {COLUMN} 310.1.9.8.20.1.3
lcsStatusTcpIpNetbiosHostListEntryIpAddress OBJECT-TYPE
    SYNTAX     IpAddress
    MAX-ACCESS read-only
    STATUS     current
    DESCRIPTION
        "-- empty --"
    ::= { lcsStatusTcpIpNetbiosHostListEntry 3 }

-- {COLUMN} 310.1.9.8.20.1.8
lcsStatusTcpIpNetbiosHostListEntryRtgTag OBJECT-TYPE
    SYNTAX     INTEGER (0..65535)
    MAX-ACCESS read-only
    STATUS     current
    DESCRIPTION
        "-- empty --"
    ::= { lcsStatusTcpIpNetbiosHostListEntry 8 }

-- {COLUMN} 310.1.9.8.20.1.4
lcsStatusTcpIpNetbiosHostListEntryPeer OBJECT-TYPE
    SYNTAX     DisplayString (SIZE(0..16))
    MAX-ACCESS read-only
    STATUS     current
    DESCRIPTION
        "-- empty --"
    ::= { lcsStatusTcpIpNetbiosHostListEntry 4 }

-- {COLUMN} 310.1.9.8.20.1.7
lcsStatusTcpIpNetbiosHostListEntryNetworkName OBJECT-TYPE
    SYNTAX     DisplayString (SIZE(0..16))
    MAX-ACCESS read-only
    STATUS     current
    DESCRIPTION
        "-- empty --"
    ::= { lcsStatusTcpIpNetbiosHostListEntry 7 }

-- {COLUMN} 310.1.9.8.20.1.5
lcsStatusTcpIpNetbiosHostListEntryTimeout OBJECT-TYPE
    SYNTAX     INTEGER (0..2147483647)
    MAX-ACCESS read-only
    STATUS     current
    DESCRIPTION
        "-- empty --"
    ::= { lcsStatusTcpIpNetbiosHostListEntry 5 }

-- {COLUMN} 310.1.9.8.20.1.6
lcsStatusTcpIpNetbiosHostListEntryFlags OBJECT-TYPE
    SYNTAX     DisplayString (SIZE(0..2))
    MAX-ACCESS read-only
    STATUS     current
    DESCRIPTION
        "-- empty --"
    ::= { lcsStatusTcpIpNetbiosHostListEntry 6 }

-- {TABLE} 310.1.9.8.21
lcsStatusTcpIpNetbiosServerListTable OBJECT-TYPE
    SYNTAX     SEQUENCE OF LcsStatusTcpIpNetbiosServerListEntry
    MAX-ACCESS not-accessible
    STATUS     current
    DESCRIPTION
        "-- empty --"
    ::= { lcsStatusTcpIpNetbios 21 }

-- {ENTRY} 310.1.9.8.21.1
lcsStatusTcpIpNetbiosServerListEntry OBJECT-TYPE
    SYNTAX     LcsStatusTcpIpNetbiosServerListEntry
    MAX-ACCESS not-accessible
    STATUS     current
    DESCRIPTION
        ""
    INDEX {
        lcsStatusTcpIpNetbiosServerListEntryHost,
        lcsStatusTcpIpNetbiosServerListEntryGroupDomain,
        lcsStatusTcpIpNetbiosServerListEntryIpAddress,
        lcsStatusTcpIpNetbiosServerListEntryRtgTag
    }
    ::= { lcsStatusTcpIpNetbiosServerListTable 1 }

-- {SEQUENCE}
LcsStatusTcpIpNetbiosServerListEntry ::= SEQUENCE {
    lcsStatusTcpIpNetbiosServerListEntryHost DisplayString,
    lcsStatusTcpIpNetbiosServerListEntryGroupDomain DisplayString,
    lcsStatusTcpIpNetbiosServerListEntryIpAddress DisplayString,
    lcsStatusTcpIpNetbiosServerListEntryRtgTag INTEGER,
    lcsStatusTcpIpNetbiosServerListEntryOsVer DisplayString,
    lcsStatusTcpIpNetbiosServerListEntrySmbVer DisplayString,
    lcsStatusTcpIpNetbiosServerListEntryServerTyp DisplayString,
    lcsStatusTcpIpNetbiosServerListEntryPeer DisplayString,
    lcsStatusTcpIpNetbiosServerListEntryNetworkName DisplayString,
    lcsStatusTcpIpNetbiosServerListEntryTimeout INTEGER,
    lcsStatusTcpIpNetbiosServerListEntryFlags DisplayString
}

-- {COLUMN} 310.1.9.8.21.1.1
lcsStatusTcpIpNetbiosServerListEntryHost OBJECT-TYPE
    SYNTAX     DisplayString (SIZE(0..15))
    MAX-ACCESS read-only
    STATUS     current
    DESCRIPTION
        "-- empty --"
    ::= { lcsStatusTcpIpNetbiosServerListEntry 1 }

-- {COLUMN} 310.1.9.8.21.1.2
lcsStatusTcpIpNetbiosServerListEntryGroupDomain OBJECT-TYPE
    SYNTAX     DisplayString (SIZE(0..16))
    MAX-ACCESS read-only
    STATUS     current
    DESCRIPTION
        "-- empty --"
    ::= { lcsStatusTcpIpNetbiosServerListEntry 2 }

-- {COLUMN} 310.1.9.8.21.1.4
lcsStatusTcpIpNetbiosServerListEntryIpAddress OBJECT-TYPE
    SYNTAX     DisplayString (SIZE(0..15))
    MAX-ACCESS read-only
    STATUS     current
    DESCRIPTION
        "-- empty --"
    ::= { lcsStatusTcpIpNetbiosServerListEntry 4 }

-- {COLUMN} 310.1.9.8.21.1.12
lcsStatusTcpIpNetbiosServerListEntryRtgTag OBJECT-TYPE
    SYNTAX     INTEGER (0..65535)
    MAX-ACCESS read-only
    STATUS     current
    DESCRIPTION
        "-- empty --"
    ::= { lcsStatusTcpIpNetbiosServerListEntry 12 }

-- {COLUMN} 310.1.9.8.21.1.5
lcsStatusTcpIpNetbiosServerListEntryOsVer OBJECT-TYPE
    SYNTAX     DisplayString (SIZE(0..2))
    MAX-ACCESS read-only
    STATUS     current
    DESCRIPTION
        "-- empty --"
    ::= { lcsStatusTcpIpNetbiosServerListEntry 5 }

-- {COLUMN} 310.1.9.8.21.1.6
lcsStatusTcpIpNetbiosServerListEntrySmbVer OBJECT-TYPE
    SYNTAX     DisplayString (SIZE(0..2))
    MAX-ACCESS read-only
    STATUS     current
    DESCRIPTION
        "-- empty --"
    ::= { lcsStatusTcpIpNetbiosServerListEntry 6 }

-- {COLUMN} 310.1.9.8.21.1.7
lcsStatusTcpIpNetbiosServerListEntryServerTyp OBJECT-TYPE
    SYNTAX     DisplayString (SIZE(0..4))
    MAX-ACCESS read-only
    STATUS     current
    DESCRIPTION
        "-- empty --"
    ::= { lcsStatusTcpIpNetbiosServerListEntry 7 }

-- {COLUMN} 310.1.9.8.21.1.8
lcsStatusTcpIpNetbiosServerListEntryPeer OBJECT-TYPE
    SYNTAX     DisplayString (SIZE(0..16))
    MAX-ACCESS read-only
    STATUS     current
    DESCRIPTION
        "-- empty --"
    ::= { lcsStatusTcpIpNetbiosServerListEntry 8 }

-- {COLUMN} 310.1.9.8.21.1.11
lcsStatusTcpIpNetbiosServerListEntryNetworkName OBJECT-TYPE
    SYNTAX     DisplayString (SIZE(0..16))
    MAX-ACCESS read-only
    STATUS     current
    DESCRIPTION
        "-- empty --"
    ::= { lcsStatusTcpIpNetbiosServerListEntry 11 }

-- {COLUMN} 310.1.9.8.21.1.9
lcsStatusTcpIpNetbiosServerListEntryTimeout OBJECT-TYPE
    SYNTAX     INTEGER (0..2147483647)
    MAX-ACCESS read-only
    STATUS     current
    DESCRIPTION
        "-- empty --"
    ::= { lcsStatusTcpIpNetbiosServerListEntry 9 }

-- {COLUMN} 310.1.9.8.21.1.10
lcsStatusTcpIpNetbiosServerListEntryFlags OBJECT-TYPE
    SYNTAX     DisplayString (SIZE(0..2))
    MAX-ACCESS read-only
    STATUS     current
    DESCRIPTION
        "-- empty --"
    ::= { lcsStatusTcpIpNetbiosServerListEntry 10 }

-- {TABLE} 310.1.9.8.22
lcsStatusTcpIpNetbiosBrowserListTable OBJECT-TYPE
    SYNTAX     SEQUENCE OF LcsStatusTcpIpNetbiosBrowserListEntry
    MAX-ACCESS not-accessible
    STATUS     current
    DESCRIPTION
        "-- empty --"
    ::= { lcsStatusTcpIpNetbios 22 }

-- {ENTRY} 310.1.9.8.22.1
lcsStatusTcpIpNetbiosBrowserListEntry OBJECT-TYPE
    SYNTAX     LcsStatusTcpIpNetbiosBrowserListEntry
    MAX-ACCESS not-accessible
    STATUS     current
    DESCRIPTION
        ""
    INDEX {
        lcsStatusTcpIpNetbiosBrowserListEntryBrowser,
        lcsStatusTcpIpNetbiosBrowserListEntryGroupDomain,
        lcsStatusTcpIpNetbiosBrowserListEntryIpAddress,
        lcsStatusTcpIpNetbiosBrowserListEntryRtgTag
    }
    ::= { lcsStatusTcpIpNetbiosBrowserListTable 1 }

-- {SEQUENCE}
LcsStatusTcpIpNetbiosBrowserListEntry ::= SEQUENCE {
    lcsStatusTcpIpNetbiosBrowserListEntryBrowser DisplayString,
    lcsStatusTcpIpNetbiosBrowserListEntryGroupDomain DisplayString,
    lcsStatusTcpIpNetbiosBrowserListEntryIpAddress DisplayString,
    lcsStatusTcpIpNetbiosBrowserListEntryRtgTag INTEGER,
    lcsStatusTcpIpNetbiosBrowserListEntryOsVer DisplayString,
    lcsStatusTcpIpNetbiosBrowserListEntryServerTyp DisplayString,
    lcsStatusTcpIpNetbiosBrowserListEntryPeer DisplayString,
    lcsStatusTcpIpNetbiosBrowserListEntryNetworkName DisplayString,
    lcsStatusTcpIpNetbiosBrowserListEntryTimeout INTEGER,
    lcsStatusTcpIpNetbiosBrowserListEntryFlags DisplayString
}

-- {COLUMN} 310.1.9.8.22.1.1
lcsStatusTcpIpNetbiosBrowserListEntryBrowser OBJECT-TYPE
    SYNTAX     DisplayString (SIZE(0..15))
    MAX-ACCESS read-only
    STATUS     current
    DESCRIPTION
        "-- empty --"
    ::= { lcsStatusTcpIpNetbiosBrowserListEntry 1 }

-- {COLUMN} 310.1.9.8.22.1.2
lcsStatusTcpIpNetbiosBrowserListEntryGroupDomain OBJECT-TYPE
    SYNTAX     DisplayString (SIZE(0..16))
    MAX-ACCESS read-only
    STATUS     current
    DESCRIPTION
        "-- empty --"
    ::= { lcsStatusTcpIpNetbiosBrowserListEntry 2 }

-- {COLUMN} 310.1.9.8.22.1.4
lcsStatusTcpIpNetbiosBrowserListEntryIpAddress OBJECT-TYPE
    SYNTAX     DisplayString (SIZE(0..15))
    MAX-ACCESS read-only
    STATUS     current
    DESCRIPTION
        "-- empty --"
    ::= { lcsStatusTcpIpNetbiosBrowserListEntry 4 }

-- {COLUMN} 310.1.9.8.22.1.12
lcsStatusTcpIpNetbiosBrowserListEntryRtgTag OBJECT-TYPE
    SYNTAX     INTEGER (0..65535)
    MAX-ACCESS read-only
    STATUS     current
    DESCRIPTION
        "-- empty --"
    ::= { lcsStatusTcpIpNetbiosBrowserListEntry 12 }

-- {COLUMN} 310.1.9.8.22.1.5
lcsStatusTcpIpNetbiosBrowserListEntryOsVer OBJECT-TYPE
    SYNTAX     DisplayString (SIZE(0..2))
    MAX-ACCESS read-only
    STATUS     current
    DESCRIPTION
        "-- empty --"
    ::= { lcsStatusTcpIpNetbiosBrowserListEntry 5 }

-- {COLUMN} 310.1.9.8.22.1.7
lcsStatusTcpIpNetbiosBrowserListEntryServerTyp OBJECT-TYPE
    SYNTAX     DisplayString (SIZE(0..4))
    MAX-ACCESS read-only
    STATUS     current
    DESCRIPTION
        "-- empty --"
    ::= { lcsStatusTcpIpNetbiosBrowserListEntry 7 }

-- {COLUMN} 310.1.9.8.22.1.8
lcsStatusTcpIpNetbiosBrowserListEntryPeer OBJECT-TYPE
    SYNTAX     DisplayString (SIZE(0..16))
    MAX-ACCESS read-only
    STATUS     current
    DESCRIPTION
        "-- empty --"
    ::= { lcsStatusTcpIpNetbiosBrowserListEntry 8 }

-- {COLUMN} 310.1.9.8.22.1.11
lcsStatusTcpIpNetbiosBrowserListEntryNetworkName OBJECT-TYPE
    SYNTAX     DisplayString (SIZE(0..16))
    MAX-ACCESS read-only
    STATUS     current
    DESCRIPTION
        "-- empty --"
    ::= { lcsStatusTcpIpNetbiosBrowserListEntry 11 }

-- {COLUMN} 310.1.9.8.22.1.9
lcsStatusTcpIpNetbiosBrowserListEntryTimeout OBJECT-TYPE
    SYNTAX     INTEGER (0..2147483647)
    MAX-ACCESS read-only
    STATUS     current
    DESCRIPTION
        "-- empty --"
    ::= { lcsStatusTcpIpNetbiosBrowserListEntry 9 }

-- {COLUMN} 310.1.9.8.22.1.10
lcsStatusTcpIpNetbiosBrowserListEntryFlags OBJECT-TYPE
    SYNTAX     DisplayString (SIZE(0..2))
    MAX-ACCESS read-only
    STATUS     current
    DESCRIPTION
        "-- empty --"
    ::= { lcsStatusTcpIpNetbiosBrowserListEntry 10 }

-- {SCALAR} 310.1.9.8.17
lcsStatusTcpIpNetbiosDeleteValues OBJECT-TYPE
    SYNTAX     DisplayString
    MAX-ACCESS read-write
    STATUS     current
    DESCRIPTION
        "-- empty --"
    ::= { lcsStatusTcpIpNetbios 17 }

-- {OID} 310.1.9.9
lcsStatusTcpIpDns OBJECT IDENTIFIER ::= { lcsStatusTcpIp 9 }

-- {SCALAR} 310.1.9.9.1
lcsStatusTcpIpDnsLanRx OBJECT-TYPE
    SYNTAX     Counter32
    MAX-ACCESS read-only
    STATUS     current
    DESCRIPTION
        "-- empty --"
    ::= { lcsStatusTcpIpDns 1 }

-- {SCALAR} 310.1.9.9.2
lcsStatusTcpIpDnsLanTx OBJECT-TYPE
    SYNTAX     Counter32
    MAX-ACCESS read-only
    STATUS     current
    DESCRIPTION
        "-- empty --"
    ::= { lcsStatusTcpIpDns 2 }

-- {SCALAR} 310.1.9.9.3
lcsStatusTcpIpDnsWanRx OBJECT-TYPE
    SYNTAX     Counter32
    MAX-ACCESS read-only
    STATUS     current
    DESCRIPTION
        "-- empty --"
    ::= { lcsStatusTcpIpDns 3 }

-- {SCALAR} 310.1.9.9.4
lcsStatusTcpIpDnsWanTx OBJECT-TYPE
    SYNTAX     Counter32
    MAX-ACCESS read-only
    STATUS     current
    DESCRIPTION
        "-- empty --"
    ::= { lcsStatusTcpIpDns 4 }

-- {SCALAR} 310.1.9.9.5
lcsStatusTcpIpDnsForwarded OBJECT-TYPE
    SYNTAX     Counter32
    MAX-ACCESS read-only
    STATUS     current
    DESCRIPTION
        "-- empty --"
    ::= { lcsStatusTcpIpDns 5 }

-- {SCALAR} 310.1.9.9.6
lcsStatusTcpIpDnsErrors OBJECT-TYPE
    SYNTAX     Counter32
    MAX-ACCESS read-only
    STATUS     current
    DESCRIPTION
        "-- empty --"
    ::= { lcsStatusTcpIpDns 6 }

-- {SCALAR} 310.1.9.9.7
lcsStatusTcpIpDnsDnsAccess OBJECT-TYPE
    SYNTAX     Counter32
    MAX-ACCESS read-only
    STATUS     current
    DESCRIPTION
        "-- empty --"
    ::= { lcsStatusTcpIpDns 7 }

-- {SCALAR} 310.1.9.9.8
lcsStatusTcpIpDnsDhcpAccess OBJECT-TYPE
    SYNTAX     Counter32
    MAX-ACCESS read-only
    STATUS     current
    DESCRIPTION
        "-- empty --"
    ::= { lcsStatusTcpIpDns 8 }

-- {SCALAR} 310.1.9.9.9
lcsStatusTcpIpDnsNetbiosAccess OBJECT-TYPE
    SYNTAX     Counter32
    MAX-ACCESS read-only
    STATUS     current
    DESCRIPTION
        "-- empty --"
    ::= { lcsStatusTcpIpDns 9 }

-- {SCALAR} 310.1.9.9.10
lcsStatusTcpIpDnsFilter OBJECT-TYPE
    SYNTAX     Counter32
    MAX-ACCESS read-only
    STATUS     current
    DESCRIPTION
        "-- empty --"
    ::= { lcsStatusTcpIpDns 10 }

-- {TABLE} 310.1.9.9.11
lcsStatusTcpIpDnsHitListTable OBJECT-TYPE
    SYNTAX     SEQUENCE OF LcsStatusTcpIpDnsHitListEntry
    MAX-ACCESS not-accessible
    STATUS     current
    DESCRIPTION
        "-- empty --"
    ::= { lcsStatusTcpIpDns 11 }

-- {ENTRY} 310.1.9.9.11.1
lcsStatusTcpIpDnsHitListEntry OBJECT-TYPE
    SYNTAX     LcsStatusTcpIpDnsHitListEntry
    MAX-ACCESS not-accessible
    STATUS     current
    DESCRIPTION
        ""
    INDEX {
        lcsStatusTcpIpDnsHitListEntryDomain
    }
    ::= { lcsStatusTcpIpDnsHitListTable 1 }

-- {SEQUENCE}
LcsStatusTcpIpDnsHitListEntry ::= SEQUENCE {
    lcsStatusTcpIpDnsHitListEntryDomain DisplayString,
    lcsStatusTcpIpDnsHitListEntryRequests INTEGER,
    lcsStatusTcpIpDnsHitListEntryTime DisplayString,
    lcsStatusTcpIpDnsHitListEntryIpAddress IpAddress
}

-- {COLUMN} 310.1.9.9.11.1.1
lcsStatusTcpIpDnsHitListEntryDomain OBJECT-TYPE
    SYNTAX     DisplayString (SIZE(0..64))
    MAX-ACCESS read-only
    STATUS     current
    DESCRIPTION
        "-- empty --"
    ::= { lcsStatusTcpIpDnsHitListEntry 1 }

-- {COLUMN} 310.1.9.9.11.1.2
lcsStatusTcpIpDnsHitListEntryRequests OBJECT-TYPE
    SYNTAX     INTEGER (0..2147483647)
    MAX-ACCESS read-only
    STATUS     current
    DESCRIPTION
        "-- empty --"
    ::= { lcsStatusTcpIpDnsHitListEntry 2 }

-- {COLUMN} 310.1.9.9.11.1.3
lcsStatusTcpIpDnsHitListEntryTime OBJECT-TYPE
    SYNTAX     DisplayString (SIZE(0..20))
    MAX-ACCESS read-only
    STATUS     current
    DESCRIPTION
        "-- empty --"
    ::= { lcsStatusTcpIpDnsHitListEntry 3 }

-- {COLUMN} 310.1.9.9.11.1.4
lcsStatusTcpIpDnsHitListEntryIpAddress OBJECT-TYPE
    SYNTAX     IpAddress
    MAX-ACCESS read-only
    STATUS     current
    DESCRIPTION
        "-- empty --"
    ::= { lcsStatusTcpIpDnsHitListEntry 4 }

-- {SCALAR} 310.1.9.9.12
lcsStatusTcpIpDnsDeleteValues OBJECT-TYPE
    SYNTAX     DisplayString
    MAX-ACCESS read-write
    STATUS     current
    DESCRIPTION
        "-- empty --"
    ::= { lcsStatusTcpIpDns 12 }

-- {OID} 310.1.9.10
lcsStatusTcpIpHttp OBJECT IDENTIFIER ::= { lcsStatusTcpIp 10 }

-- {SCALAR} 310.1.9.10.1
lcsStatusTcpIpHttpHttpAccesses OBJECT-TYPE
    SYNTAX     Counter32
    MAX-ACCESS read-only
    STATUS     current
    DESCRIPTION
        "-- empty --"
    ::= { lcsStatusTcpIpHttp 1 }

-- {SCALAR} 310.1.9.10.6
lcsStatusTcpIpHttpHttpsAccesses OBJECT-TYPE
    SYNTAX     Counter32
    MAX-ACCESS read-only
    STATUS     current
    DESCRIPTION
        "-- empty --"
    ::= { lcsStatusTcpIpHttp 6 }

-- {SCALAR} 310.1.9.10.2
lcsStatusTcpIpHttpHttpNotfoundErrors OBJECT-TYPE
    SYNTAX     Counter32
    MAX-ACCESS read-only
    STATUS     current
    DESCRIPTION
        "-- empty --"
    ::= { lcsStatusTcpIpHttp 2 }

-- {SCALAR} 310.1.9.10.3
lcsStatusTcpIpHttpHttpAuthenticationErrors OBJECT-TYPE
    SYNTAX     Counter32
    MAX-ACCESS read-only
    STATUS     current
    DESCRIPTION
        "-- empty --"
    ::= { lcsStatusTcpIpHttp 3 }

-- {SCALAR} 310.1.9.10.4
lcsStatusTcpIpHttpHttpProtocolErrors OBJECT-TYPE
    SYNTAX     Counter32
    MAX-ACCESS read-only
    STATUS     current
    DESCRIPTION
        "-- empty --"
    ::= { lcsStatusTcpIpHttp 4 }

-- {TABLE} 310.1.9.10.7
lcsStatusTcpIpHttpAgentListTable OBJECT-TYPE
    SYNTAX     SEQUENCE OF LcsStatusTcpIpHttpAgentListEntry
    MAX-ACCESS not-accessible
    STATUS     current
    DESCRIPTION
        "-- empty --"
    ::= { lcsStatusTcpIpHttp 7 }

-- {ENTRY} 310.1.9.10.7.1
lcsStatusTcpIpHttpAgentListEntry OBJECT-TYPE
    SYNTAX     LcsStatusTcpIpHttpAgentListEntry
    MAX-ACCESS not-accessible
    STATUS     current
    DESCRIPTION
        ""
    INDEX {
        lcsStatusTcpIpHttpAgentListEntryAgentName
    }
    ::= { lcsStatusTcpIpHttpAgentListTable 1 }

-- {SEQUENCE}
LcsStatusTcpIpHttpAgentListEntry ::= SEQUENCE {
    lcsStatusTcpIpHttpAgentListEntryAgentName DisplayString,
    lcsStatusTcpIpHttpAgentListEntryAccesses INTEGER
}

-- {COLUMN} 310.1.9.10.7.1.1
lcsStatusTcpIpHttpAgentListEntryAgentName OBJECT-TYPE
    SYNTAX     DisplayString (SIZE(0..67))
    MAX-ACCESS read-only
    STATUS     current
    DESCRIPTION
        "-- empty --"
    ::= { lcsStatusTcpIpHttpAgentListEntry 1 }

-- {COLUMN} 310.1.9.10.7.1.2
lcsStatusTcpIpHttpAgentListEntryAccesses OBJECT-TYPE
    SYNTAX     INTEGER (0..2147483647)
    MAX-ACCESS read-only
    STATUS     current
    DESCRIPTION
        "-- empty --"
    ::= { lcsStatusTcpIpHttpAgentListEntry 2 }

-- {SCALAR} 310.1.9.10.5
lcsStatusTcpIpHttpDeleteValues OBJECT-TYPE
    SYNTAX     DisplayString
    MAX-ACCESS read-write
    STATUS     current
    DESCRIPTION
        "-- empty --"
    ::= { lcsStatusTcpIpHttp 5 }

-- {SCALAR} 310.1.9.10.15
lcsStatusTcpIpHttpMaxHttpJobCount OBJECT-TYPE
    SYNTAX     INTEGER (0..2147483647)
    MAX-ACCESS read-only
    STATUS     current
    DESCRIPTION
        "-- empty --"
    ::= { lcsStatusTcpIpHttp 15 }

-- {SCALAR} 310.1.9.10.16
lcsStatusTcpIpHttpJobCount OBJECT-TYPE
    SYNTAX     INTEGER (0..2147483647)
    MAX-ACCESS read-only
    STATUS     current
    DESCRIPTION
        "-- empty --"
    ::= { lcsStatusTcpIpHttp 16 }

-- {SCALAR} 310.1.9.10.17
lcsStatusTcpIpHttpIdleJobs OBJECT-TYPE
    SYNTAX     INTEGER (0..2147483647)
    MAX-ACCESS read-only
    STATUS     current
    DESCRIPTION
        "-- empty --"
    ::= { lcsStatusTcpIpHttp 17 }

-- {TABLE} 310.1.9.10.8
lcsStatusTcpIpHttpActiveTunnelsTable OBJECT-TYPE
    SYNTAX     SEQUENCE OF LcsStatusTcpIpHttpActiveTunnelsEntry
    MAX-ACCESS not-accessible
    STATUS     current
    DESCRIPTION
        "-- empty --"
    ::= { lcsStatusTcpIpHttp 8 }

-- {ENTRY} 310.1.9.10.8.1
lcsStatusTcpIpHttpActiveTunnelsEntry OBJECT-TYPE
    SYNTAX     LcsStatusTcpIpHttpActiveTunnelsEntry
    MAX-ACCESS not-accessible
    STATUS     current
    DESCRIPTION
        ""
    INDEX {
        lcsStatusTcpIpHttpActiveTunnelsEntryIndex
    }
    ::= { lcsStatusTcpIpHttpActiveTunnelsTable 1 }

-- {SEQUENCE}
LcsStatusTcpIpHttpActiveTunnelsEntry ::= SEQUENCE {
    lcsStatusTcpIpHttpActiveTunnelsEntryIndex INTEGER,
    lcsStatusTcpIpHttpActiveTunnelsEntryRemoteAddress IpAddress,
    lcsStatusTcpIpHttpActiveTunnelsEntryRemotePort INTEGER,
    lcsStatusTcpIpHttpActiveTunnelsEntryLocalHost DisplayString,
    lcsStatusTcpIpHttpActiveTunnelsEntryLocalPort INTEGER,
    lcsStatusTcpIpHttpActiveTunnelsEntryLocalRtgTag INTEGER,
    lcsStatusTcpIpHttpActiveTunnelsEntryIdleTime INTEGER,
    lcsStatusTcpIpHttpActiveTunnelsEntryState INTEGER,
    lcsStatusTcpIpHttpActiveTunnelsEntryNumConnections INTEGER
}

-- {COLUMN} 310.1.9.10.8.1.1
lcsStatusTcpIpHttpActiveTunnelsEntryIndex OBJECT-TYPE
    SYNTAX     INTEGER (0..2147483647)
    MAX-ACCESS read-only
    STATUS     current
    DESCRIPTION
        "-- empty --"
    ::= { lcsStatusTcpIpHttpActiveTunnelsEntry 1 }

-- {COLUMN} 310.1.9.10.8.1.2
lcsStatusTcpIpHttpActiveTunnelsEntryRemoteAddress OBJECT-TYPE
    SYNTAX     IpAddress
    MAX-ACCESS read-only
    STATUS     current
    DESCRIPTION
        "-- empty --"
    ::= { lcsStatusTcpIpHttpActiveTunnelsEntry 2 }

-- {COLUMN} 310.1.9.10.8.1.3
lcsStatusTcpIpHttpActiveTunnelsEntryRemotePort OBJECT-TYPE
    SYNTAX     INTEGER (0..65535)
    MAX-ACCESS read-only
    STATUS     current
    DESCRIPTION
        "-- empty --"
    ::= { lcsStatusTcpIpHttpActiveTunnelsEntry 3 }

-- {COLUMN} 310.1.9.10.8.1.4
lcsStatusTcpIpHttpActiveTunnelsEntryLocalHost OBJECT-TYPE
    SYNTAX     DisplayString (SIZE(0..48))
    MAX-ACCESS read-only
    STATUS     current
    DESCRIPTION
        "-- empty --"
    ::= { lcsStatusTcpIpHttpActiveTunnelsEntry 4 }

-- {COLUMN} 310.1.9.10.8.1.5
lcsStatusTcpIpHttpActiveTunnelsEntryLocalPort OBJECT-TYPE
    SYNTAX     INTEGER (0..65535)
    MAX-ACCESS read-only
    STATUS     current
    DESCRIPTION
        "-- empty --"
    ::= { lcsStatusTcpIpHttpActiveTunnelsEntry 5 }

-- {COLUMN} 310.1.9.10.8.1.7
lcsStatusTcpIpHttpActiveTunnelsEntryLocalRtgTag OBJECT-TYPE
    SYNTAX     INTEGER (0..65535)
    MAX-ACCESS read-only
    STATUS     current
    DESCRIPTION
        "-- empty --"
    ::= { lcsStatusTcpIpHttpActiveTunnelsEntry 7 }

-- {COLUMN} 310.1.9.10.8.1.6
lcsStatusTcpIpHttpActiveTunnelsEntryIdleTime OBJECT-TYPE
    SYNTAX     INTEGER (0..2147483647)
    MAX-ACCESS read-only
    STATUS     current
    DESCRIPTION
        "-- empty --"
    ::= { lcsStatusTcpIpHttpActiveTunnelsEntry 6 }

-- {COLUMN} 310.1.9.10.8.1.9
lcsStatusTcpIpHttpActiveTunnelsEntryState OBJECT-TYPE
    SYNTAX     INTEGER
      {
        eActive (0),
        eClosing (1)
      }
    MAX-ACCESS read-only
    STATUS     current
    DESCRIPTION
        "-- empty --"
    ::= { lcsStatusTcpIpHttpActiveTunnelsEntry 9 }

-- {COLUMN} 310.1.9.10.8.1.8
lcsStatusTcpIpHttpActiveTunnelsEntryNumConnections OBJECT-TYPE
    SYNTAX     INTEGER (0..2147483647)
    MAX-ACCESS read-only
    STATUS     current
    DESCRIPTION
        "-- empty --"
    ::= { lcsStatusTcpIpHttpActiveTunnelsEntry 8 }

-- {TABLE} 310.1.9.20
lcsStatusTcpIpNetworkListTable OBJECT-TYPE
    SYNTAX     SEQUENCE OF LcsStatusTcpIpNetworkListEntry
    MAX-ACCESS not-accessible
    STATUS     current
    DESCRIPTION
        "-- empty --"
    ::= { lcsStatusTcpIp 20 }

-- {ENTRY} 310.1.9.20.1
lcsStatusTcpIpNetworkListEntry OBJECT-TYPE
    SYNTAX     LcsStatusTcpIpNetworkListEntry
    MAX-ACCESS not-accessible
    STATUS     current
    DESCRIPTION
        ""
    INDEX {
        lcsStatusTcpIpNetworkListEntryNetworkName
    }
    ::= { lcsStatusTcpIpNetworkListTable 1 }

-- {SEQUENCE}
LcsStatusTcpIpNetworkListEntry ::= SEQUENCE {
    lcsStatusTcpIpNetworkListEntryNetworkName DisplayString,
    lcsStatusTcpIpNetworkListEntryIpAddress IpAddress,
    lcsStatusTcpIpNetworkListEntryIpNetmask IpAddress,
    lcsStatusTcpIpNetworkListEntryVlanId INTEGER,
    lcsStatusTcpIpNetworkListEntryInterface INTEGER,
    lcsStatusTcpIpNetworkListEntrySrcCheck INTEGER,
    lcsStatusTcpIpNetworkListEntryType INTEGER,
    lcsStatusTcpIpNetworkListEntryRtgTag INTEGER
}

-- {COLUMN} 310.1.9.20.1.1
lcsStatusTcpIpNetworkListEntryNetworkName OBJECT-TYPE
    SYNTAX     DisplayString (SIZE(0..17))
    MAX-ACCESS read-only
    STATUS     current
    DESCRIPTION
        "-- empty --"
    ::= { lcsStatusTcpIpNetworkListEntry 1 }

-- {COLUMN} 310.1.9.20.1.2
lcsStatusTcpIpNetworkListEntryIpAddress OBJECT-TYPE
    SYNTAX     IpAddress
    MAX-ACCESS read-only
    STATUS     current
    DESCRIPTION
        "-- empty --"
    ::= { lcsStatusTcpIpNetworkListEntry 2 }

-- {COLUMN} 310.1.9.20.1.3
lcsStatusTcpIpNetworkListEntryIpNetmask OBJECT-TYPE
    SYNTAX     IpAddress
    MAX-ACCESS read-only
    STATUS     current
    DESCRIPTION
        "-- empty --"
    ::= { lcsStatusTcpIpNetworkListEntry 3 }

-- {COLUMN} 310.1.9.20.1.4
lcsStatusTcpIpNetworkListEntryVlanId OBJECT-TYPE
    SYNTAX     INTEGER (0..65535)
    MAX-ACCESS read-only
    STATUS     current
    DESCRIPTION
        "-- empty --"
    ::= { lcsStatusTcpIpNetworkListEntry 4 }

-- {COLUMN} 310.1.9.20.1.5
lcsStatusTcpIpNetworkListEntryInterface OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusTcpIpNetworkListEntry 5 }

-- {COLUMN} 310.1.9.20.1.6
lcsStatusTcpIpNetworkListEntrySrcCheck OBJECT-TYPE
    SYNTAX     INTEGER
      {
        eStrict (1),
        eLoose (0)
      }
    MAX-ACCESS read-only
    STATUS     current
    DESCRIPTION
        "-- empty --"
    ::= { lcsStatusTcpIpNetworkListEntry 6 }

-- {COLUMN} 310.1.9.20.1.7
lcsStatusTcpIpNetworkListEntryType OBJECT-TYPE
    SYNTAX     INTEGER
      {
        eDisabled (0),
        eIntranet (1),
        eDmz (2)
      }
    MAX-ACCESS read-only
    STATUS     current
    DESCRIPTION
        "-- empty --"
    ::= { lcsStatusTcpIpNetworkListEntry 7 }

-- {COLUMN} 310.1.9.20.1.8
lcsStatusTcpIpNetworkListEntryRtgTag OBJECT-TYPE
    SYNTAX     INTEGER (0..65535)
    MAX-ACCESS read-only
    STATUS     current
    DESCRIPTION
        "-- empty --"
    ::= { lcsStatusTcpIpNetworkListEntry 8 }

-- {OID} 310.1.9.11
lcsStatusTcpIpSyslog OBJECT IDENTIFIER ::= { lcsStatusTcpIp 11 }

-- {TABLE} 310.1.9.11.11
lcsStatusTcpIpSyslogLastMessagesTable OBJECT-TYPE
    SYNTAX     SEQUENCE OF LcsStatusTcpIpSyslogLastMessagesEntry
    MAX-ACCESS not-accessible
    STATUS     current
    DESCRIPTION
        "-- empty --"
    ::= { lcsStatusTcpIpSyslog 11 }

-- {ENTRY} 310.1.9.11.11.1
lcsStatusTcpIpSyslogLastMessagesEntry OBJECT-TYPE
    SYNTAX     LcsStatusTcpIpSyslogLastMessagesEntry
    MAX-ACCESS not-accessible
    STATUS     current
    DESCRIPTION
        ""
    INDEX {
        lcsStatusTcpIpSyslogLastMessagesEntryIdx
    }
    ::= { lcsStatusTcpIpSyslogLastMessagesTable 1 }

-- {SEQUENCE}
LcsStatusTcpIpSyslogLastMessagesEntry ::= SEQUENCE {
    lcsStatusTcpIpSyslogLastMessagesEntryIdx INTEGER,
    lcsStatusTcpIpSyslogLastMessagesEntryTime DisplayString,
    lcsStatusTcpIpSyslogLastMessagesEntrySource INTEGER,
    lcsStatusTcpIpSyslogLastMessagesEntryLevel INTEGER,
    lcsStatusTcpIpSyslogLastMessagesEntryMessage DisplayString
}

-- {COLUMN} 310.1.9.11.11.1.1
lcsStatusTcpIpSyslogLastMessagesEntryIdx OBJECT-TYPE
    SYNTAX     INTEGER (0..2147483647)
    MAX-ACCESS read-only
    STATUS     current
    DESCRIPTION
        "-- empty --"
    ::= { lcsStatusTcpIpSyslogLastMessagesEntry 1 }

-- {COLUMN} 310.1.9.11.11.1.2
lcsStatusTcpIpSyslogLastMessagesEntryTime OBJECT-TYPE
    SYNTAX     DisplayString (SIZE(0..21))
    MAX-ACCESS read-only
    STATUS     current
    DESCRIPTION
        "-- empty --"
    ::= { lcsStatusTcpIpSyslogLastMessagesEntry 2 }

-- {COLUMN} 310.1.9.11.11.1.3
lcsStatusTcpIpSyslogLastMessagesEntrySource OBJECT-TYPE
    SYNTAX     INTEGER
      {
        eKern (0),
        eUser (1),
        eMail (2),
        eDaemon (3),
        eAuth (4),
        eSyslog (5),
        eLpr (6),
        eNews (7),
        eUucp (8),
        eCron (9),
        eAuthpriv (10),
        eLocal0 (16),
        eLocal1 (17),
        eLocal2 (18),
        eLocal3 (19),
        eLocal4 (20),
        eLocal5 (21),
        eLocal6 (22),
        eLocal7 (23)
      }
    MAX-ACCESS read-only
    STATUS     current
    DESCRIPTION
        "-- empty --"
    ::= { lcsStatusTcpIpSyslogLastMessagesEntry 3 }

-- {COLUMN} 310.1.9.11.11.1.4
lcsStatusTcpIpSyslogLastMessagesEntryLevel OBJECT-TYPE
    SYNTAX     INTEGER
      {
        eEmergency (0),
        eAlarm (1),
        eCritical (2),
        eError (3),
        eWarning (4),
        eNotice (5),
        eInfo (6),
        eDebug (7)
      }
    MAX-ACCESS read-only
    STATUS     current
    DESCRIPTION
        "-- empty --"
    ::= { lcsStatusTcpIpSyslogLastMessagesEntry 4 }

-- {COLUMN} 310.1.9.11.11.1.5
lcsStatusTcpIpSyslogLastMessagesEntryMessage OBJECT-TYPE
    SYNTAX     DisplayString (SIZE(0..144))
    MAX-ACCESS read-only
    STATUS     current
    DESCRIPTION
        "-- empty --"
    ::= { lcsStatusTcpIpSyslogLastMessagesEntry 5 }

-- {SCALAR} 310.1.9.11.99
lcsStatusTcpIpSyslogDeleteValues OBJECT-TYPE
    SYNTAX     DisplayString
    MAX-ACCESS read-write
    STATUS     current
    DESCRIPTION
        "-- empty --"
    ::= { lcsStatusTcpIpSyslog 99 }

-- {OID} 310.1.9.13
lcsStatusTcpIpRadiusc OBJECT IDENTIFIER ::= { lcsStatusTcpIp 13 }

-- {SCALAR} 310.1.9.13.1
lcsStatusTcpIpRadiuscInvalAuthAddrResp OBJECT-TYPE
    SYNTAX     Counter32
    MAX-ACCESS read-only
    STATUS     current
    DESCRIPTION
        ""
    ::= { lcsStatusTcpIpRadiusc 1 }

-- {TABLE} 310.1.9.13.2
lcsStatusTcpIpRadiuscAuthServTable OBJECT-TYPE
    SYNTAX     SEQUENCE OF LcsStatusTcpIpRadiuscAuthServEntry
    MAX-ACCESS not-accessible
    STATUS     current
    DESCRIPTION
        ""
    ::= { lcsStatusTcpIpRadiusc 2 }

-- {ENTRY} 310.1.9.13.2.1
lcsStatusTcpIpRadiuscAuthServEntry OBJECT-TYPE
    SYNTAX     LcsStatusTcpIpRadiuscAuthServEntry
    MAX-ACCESS not-accessible
    STATUS     current
    DESCRIPTION
        ""
    INDEX {
        lcsStatusTcpIpRadiuscAuthServEntryIpAddr,
        lcsStatusTcpIpRadiuscAuthServEntryPort
    }
    ::= { lcsStatusTcpIpRadiuscAuthServTable 1 }

-- {SEQUENCE}
LcsStatusTcpIpRadiuscAuthServEntry ::= SEQUENCE {
    lcsStatusTcpIpRadiuscAuthServEntryIpAddr IpAddress,
    lcsStatusTcpIpRadiuscAuthServEntryPort INTEGER,
    lcsStatusTcpIpRadiuscAuthServEntryLastRequest INTEGER,
    lcsStatusTcpIpRadiuscAuthServEntryRoundTripTime Counter32,
    lcsStatusTcpIpRadiuscAuthServEntryAccReq Counter32,
    lcsStatusTcpIpRadiuscAuthServEntryAccRetrs Counter32,
    lcsStatusTcpIpRadiuscAuthServEntryAccAccepts Counter32,
    lcsStatusTcpIpRadiuscAuthServEntryAccRej Counter32,
    lcsStatusTcpIpRadiuscAuthServEntryAccChallenges Counter32,
    lcsStatusTcpIpRadiuscAuthServEntryMalfAccResp Counter32,
    lcsStatusTcpIpRadiuscAuthServEntryBadAuth Counter32,
    lcsStatusTcpIpRadiuscAuthServEntryPendReq Counter32,
    lcsStatusTcpIpRadiuscAuthServEntryTimeouts Counter32,
    lcsStatusTcpIpRadiuscAuthServEntryUnknownTypes Counter32,
    lcsStatusTcpIpRadiuscAuthServEntryDropped Counter32
}

-- {COLUMN} 310.1.9.13.2.1.1
lcsStatusTcpIpRadiuscAuthServEntryIpAddr OBJECT-TYPE
    SYNTAX     IpAddress
    MAX-ACCESS read-only
    STATUS     current
    DESCRIPTION
        ""
    ::= { lcsStatusTcpIpRadiuscAuthServEntry 1 }

-- {COLUMN} 310.1.9.13.2.1.2
lcsStatusTcpIpRadiuscAuthServEntryPort OBJECT-TYPE
    SYNTAX     INTEGER (0..65535)
    MAX-ACCESS read-only
    STATUS     current
    DESCRIPTION
        ""
    ::= { lcsStatusTcpIpRadiuscAuthServEntry 2 }

-- {COLUMN} 310.1.9.13.2.1.3
lcsStatusTcpIpRadiuscAuthServEntryLastRequest OBJECT-TYPE
    SYNTAX     INTEGER (0..2147483647)
    MAX-ACCESS read-only
    STATUS     current
    DESCRIPTION
        ""
    ::= { lcsStatusTcpIpRadiuscAuthServEntry 3 }

-- {COLUMN} 310.1.9.13.2.1.4
lcsStatusTcpIpRadiuscAuthServEntryRoundTripTime OBJECT-TYPE
    SYNTAX     Counter32
    MAX-ACCESS read-only
    STATUS     current
    DESCRIPTION
        ""
    ::= { lcsStatusTcpIpRadiuscAuthServEntry 4 }

-- {COLUMN} 310.1.9.13.2.1.5
lcsStatusTcpIpRadiuscAuthServEntryAccReq OBJECT-TYPE
    SYNTAX     Counter32
    MAX-ACCESS read-only
    STATUS     current
    DESCRIPTION
        ""
    ::= { lcsStatusTcpIpRadiuscAuthServEntry 5 }

-- {COLUMN} 310.1.9.13.2.1.6
lcsStatusTcpIpRadiuscAuthServEntryAccRetrs OBJECT-TYPE
    SYNTAX     Counter32
    MAX-ACCESS read-only
    STATUS     current
    DESCRIPTION
        ""
    ::= { lcsStatusTcpIpRadiuscAuthServEntry 6 }

-- {COLUMN} 310.1.9.13.2.1.7
lcsStatusTcpIpRadiuscAuthServEntryAccAccepts OBJECT-TYPE
    SYNTAX     Counter32
    MAX-ACCESS read-only
    STATUS     current
    DESCRIPTION
        ""
    ::= { lcsStatusTcpIpRadiuscAuthServEntry 7 }

-- {COLUMN} 310.1.9.13.2.1.8
lcsStatusTcpIpRadiuscAuthServEntryAccRej OBJECT-TYPE
    SYNTAX     Counter32
    MAX-ACCESS read-only
    STATUS     current
    DESCRIPTION
        ""
    ::= { lcsStatusTcpIpRadiuscAuthServEntry 8 }

-- {COLUMN} 310.1.9.13.2.1.9
lcsStatusTcpIpRadiuscAuthServEntryAccChallenges OBJECT-TYPE
    SYNTAX     Counter32
    MAX-ACCESS read-only
    STATUS     current
    DESCRIPTION
        ""
    ::= { lcsStatusTcpIpRadiuscAuthServEntry 9 }

-- {COLUMN} 310.1.9.13.2.1.10
lcsStatusTcpIpRadiuscAuthServEntryMalfAccResp OBJECT-TYPE
    SYNTAX     Counter32
    MAX-ACCESS read-only
    STATUS     current
    DESCRIPTION
        ""
    ::= { lcsStatusTcpIpRadiuscAuthServEntry 10 }

-- {COLUMN} 310.1.9.13.2.1.11
lcsStatusTcpIpRadiuscAuthServEntryBadAuth OBJECT-TYPE
    SYNTAX     Counter32
    MAX-ACCESS read-only
    STATUS     current
    DESCRIPTION
        ""
    ::= { lcsStatusTcpIpRadiuscAuthServEntry 11 }

-- {COLUMN} 310.1.9.13.2.1.12
lcsStatusTcpIpRadiuscAuthServEntryPendReq OBJECT-TYPE
    SYNTAX     Counter32
    MAX-ACCESS read-only
    STATUS     current
    DESCRIPTION
        ""
    ::= { lcsStatusTcpIpRadiuscAuthServEntry 12 }

-- {COLUMN} 310.1.9.13.2.1.13
lcsStatusTcpIpRadiuscAuthServEntryTimeouts OBJECT-TYPE
    SYNTAX     Counter32
    MAX-ACCESS read-only
    STATUS     current
    DESCRIPTION
        ""
    ::= { lcsStatusTcpIpRadiuscAuthServEntry 13 }

-- {COLUMN} 310.1.9.13.2.1.14
lcsStatusTcpIpRadiuscAuthServEntryUnknownTypes OBJECT-TYPE
    SYNTAX     Counter32
    MAX-ACCESS read-only
    STATUS     current
    DESCRIPTION
        ""
    ::= { lcsStatusTcpIpRadiuscAuthServEntry 14 }

-- {COLUMN} 310.1.9.13.2.1.15
lcsStatusTcpIpRadiuscAuthServEntryDropped OBJECT-TYPE
    SYNTAX     Counter32
    MAX-ACCESS read-only
    STATUS     current
    DESCRIPTION
        ""
    ::= { lcsStatusTcpIpRadiuscAuthServEntry 15 }

-- {SCALAR} 310.1.9.13.11
lcsStatusTcpIpRadiuscInvalAccntAddrResp OBJECT-TYPE
    SYNTAX     Counter32
    MAX-ACCESS read-only
    STATUS     current
    DESCRIPTION
        ""
    ::= { lcsStatusTcpIpRadiusc 11 }

-- {TABLE} 310.1.9.13.12
lcsStatusTcpIpRadiuscAccntServTable OBJECT-TYPE
    SYNTAX     SEQUENCE OF LcsStatusTcpIpRadiuscAccntServEntry
    MAX-ACCESS not-accessible
    STATUS     current
    DESCRIPTION
        ""
    ::= { lcsStatusTcpIpRadiusc 12 }

-- {ENTRY} 310.1.9.13.12.1
lcsStatusTcpIpRadiuscAccntServEntry OBJECT-TYPE
    SYNTAX     LcsStatusTcpIpRadiuscAccntServEntry
    MAX-ACCESS not-accessible
    STATUS     current
    DESCRIPTION
        ""
    INDEX {
        lcsStatusTcpIpRadiuscAccntServEntryIpAddr,
        lcsStatusTcpIpRadiuscAccntServEntryPort
    }
    ::= { lcsStatusTcpIpRadiuscAccntServTable 1 }

-- {SEQUENCE}
LcsStatusTcpIpRadiuscAccntServEntry ::= SEQUENCE {
    lcsStatusTcpIpRadiuscAccntServEntryIpAddr IpAddress,
    lcsStatusTcpIpRadiuscAccntServEntryPort INTEGER,
    lcsStatusTcpIpRadiuscAccntServEntryLastRequest INTEGER,
    lcsStatusTcpIpRadiuscAccntServEntryRoundTripTime Counter32,
    lcsStatusTcpIpRadiuscAccntServEntryAccntReq Counter32,
    lcsStatusTcpIpRadiuscAccntServEntryAccntRetrans Counter32,
    lcsStatusTcpIpRadiuscAccntServEntryAccntResp Counter32,
    lcsStatusTcpIpRadiuscAccntServEntryMalfAccntResp Counter32,
    lcsStatusTcpIpRadiuscAccntServEntryBadAuth Counter32,
    lcsStatusTcpIpRadiuscAccntServEntryPendReq Counter32,
    lcsStatusTcpIpRadiuscAccntServEntryTimeouts Counter32,
    lcsStatusTcpIpRadiuscAccntServEntryUnknownTypes Counter32,
    lcsStatusTcpIpRadiuscAccntServEntryDropped Counter32
}

-- {COLUMN} 310.1.9.13.12.1.1
lcsStatusTcpIpRadiuscAccntServEntryIpAddr OBJECT-TYPE
    SYNTAX     IpAddress
    MAX-ACCESS read-only
    STATUS     current
    DESCRIPTION
        ""
    ::= { lcsStatusTcpIpRadiuscAccntServEntry 1 }

-- {COLUMN} 310.1.9.13.12.1.2
lcsStatusTcpIpRadiuscAccntServEntryPort OBJECT-TYPE
    SYNTAX     INTEGER (0..65535)
    MAX-ACCESS read-only
    STATUS     current
    DESCRIPTION
        ""
    ::= { lcsStatusTcpIpRadiuscAccntServEntry 2 }

-- {COLUMN} 310.1.9.13.12.1.3
lcsStatusTcpIpRadiuscAccntServEntryLastRequest OBJECT-TYPE
    SYNTAX     INTEGER (0..2147483647)
    MAX-ACCESS read-only
    STATUS     current
    DESCRIPTION
        ""
    ::= { lcsStatusTcpIpRadiuscAccntServEntry 3 }

-- {COLUMN} 310.1.9.13.12.1.4
lcsStatusTcpIpRadiuscAccntServEntryRoundTripTime OBJECT-TYPE
    SYNTAX     Counter32
    MAX-ACCESS read-only
    STATUS     current
    DESCRIPTION
        ""
    ::= { lcsStatusTcpIpRadiuscAccntServEntry 4 }

-- {COLUMN} 310.1.9.13.12.1.5
lcsStatusTcpIpRadiuscAccntServEntryAccntReq OBJECT-TYPE
    SYNTAX     Counter32
    MAX-ACCESS read-only
    STATUS     current
    DESCRIPTION
        ""
    ::= { lcsStatusTcpIpRadiuscAccntServEntry 5 }

-- {COLUMN} 310.1.9.13.12.1.6
lcsStatusTcpIpRadiuscAccntServEntryAccntRetrans OBJECT-TYPE
    SYNTAX     Counter32
    MAX-ACCESS read-only
    STATUS     current
    DESCRIPTION
        ""
    ::= { lcsStatusTcpIpRadiuscAccntServEntry 6 }

-- {COLUMN} 310.1.9.13.12.1.7
lcsStatusTcpIpRadiuscAccntServEntryAccntResp OBJECT-TYPE
    SYNTAX     Counter32
    MAX-ACCESS read-only
    STATUS     current
    DESCRIPTION
        ""
    ::= { lcsStatusTcpIpRadiuscAccntServEntry 7 }

-- {COLUMN} 310.1.9.13.12.1.8
lcsStatusTcpIpRadiuscAccntServEntryMalfAccntResp OBJECT-TYPE
    SYNTAX     Counter32
    MAX-ACCESS read-only
    STATUS     current
    DESCRIPTION
        ""
    ::= { lcsStatusTcpIpRadiuscAccntServEntry 8 }

-- {COLUMN} 310.1.9.13.12.1.9
lcsStatusTcpIpRadiuscAccntServEntryBadAuth OBJECT-TYPE
    SYNTAX     Counter32
    MAX-ACCESS read-only
    STATUS     current
    DESCRIPTION
        ""
    ::= { lcsStatusTcpIpRadiuscAccntServEntry 9 }

-- {COLUMN} 310.1.9.13.12.1.10
lcsStatusTcpIpRadiuscAccntServEntryPendReq OBJECT-TYPE
    SYNTAX     Counter32
    MAX-ACCESS read-only
    STATUS     current
    DESCRIPTION
        ""
    ::= { lcsStatusTcpIpRadiuscAccntServEntry 10 }

-- {COLUMN} 310.1.9.13.12.1.11
lcsStatusTcpIpRadiuscAccntServEntryTimeouts OBJECT-TYPE
    SYNTAX     Counter32
    MAX-ACCESS read-only
    STATUS     current
    DESCRIPTION
        ""
    ::= { lcsStatusTcpIpRadiuscAccntServEntry 11 }

-- {COLUMN} 310.1.9.13.12.1.12
lcsStatusTcpIpRadiuscAccntServEntryUnknownTypes OBJECT-TYPE
    SYNTAX     Counter32
    MAX-ACCESS read-only
    STATUS     current
    DESCRIPTION
        ""
    ::= { lcsStatusTcpIpRadiuscAccntServEntry 12 }

-- {COLUMN} 310.1.9.13.12.1.13
lcsStatusTcpIpRadiuscAccntServEntryDropped OBJECT-TYPE
    SYNTAX     Counter32
    MAX-ACCESS read-only
    STATUS     current
    DESCRIPTION
        ""
    ::= { lcsStatusTcpIpRadiuscAccntServEntry 13 }

-- {OID} 310.1.9.12
lcsStatusTcpIpRadiuss OBJECT IDENTIFIER ::= { lcsStatusTcpIp 12 }

-- {OID} 310.1.9.12.1
lcsStatusTcpIpRadiussAccess OBJECT IDENTIFIER ::= { lcsStatusTcpIpRadiuss 1 }

-- {SCALAR} 310.1.9.12.1.100
lcsStatusTcpIpRadiussAccessDeleteValues OBJECT-TYPE
    SYNTAX     DisplayString
    MAX-ACCESS read-write
    STATUS     current
    DESCRIPTION
        "-- empty --"
    ::= { lcsStatusTcpIpRadiussAccess 100 }

-- {TABLE} 310.1.9.12.1.15
lcsStatusTcpIpRadiussAccessClientsTable OBJECT-TYPE
    SYNTAX     SEQUENCE OF LcsStatusTcpIpRadiussAccessClientsEntry
    MAX-ACCESS not-accessible
    STATUS     current
    DESCRIPTION
        "-- empty --"
    ::= { lcsStatusTcpIpRadiussAccess 15 }

-- {ENTRY} 310.1.9.12.1.15.1
lcsStatusTcpIpRadiussAccessClientsEntry OBJECT-TYPE
    SYNTAX     LcsStatusTcpIpRadiussAccessClientsEntry
    MAX-ACCESS not-accessible
    STATUS     current
    DESCRIPTION
        ""
    INDEX {
        lcsStatusTcpIpRadiussAccessClientsEntryIpAddress
    }
    ::= { lcsStatusTcpIpRadiussAccessClientsTable 1 }

-- {SEQUENCE}
LcsStatusTcpIpRadiussAccessClientsEntry ::= SEQUENCE {
    lcsStatusTcpIpRadiussAccessClientsEntryIpAddress IpAddress,
    lcsStatusTcpIpRadiussAccessClientsEntryLastRequest INTEGER,
    lcsStatusTcpIpRadiussAccessClientsEntryLastStatusRequest INTEGER,
    lcsStatusTcpIpRadiussAccessClientsEntryNasIdent DisplayString,
    lcsStatusTcpIpRadiussAccessClientsEntryAccessRequests Counter32,
    lcsStatusTcpIpRadiussAccessClientsEntryStatusRequests Counter32,
    lcsStatusTcpIpRadiussAccessClientsEntryDuplicateRequests Counter32,
    lcsStatusTcpIpRadiussAccessClientsEntryAccessAccepts Counter32,
    lcsStatusTcpIpRadiussAccessClientsEntryAccessRejects Counter32,
    lcsStatusTcpIpRadiussAccessClientsEntryAccessChallenges Counter32,
    lcsStatusTcpIpRadiussAccessClientsEntryStatusResponses Counter32,
    lcsStatusTcpIpRadiussAccessClientsEntryMalfAccReq Counter32,
    lcsStatusTcpIpRadiussAccessClientsEntryBadAuthenticator Counter32,
    lcsStatusTcpIpRadiussAccessClientsEntryDropped Counter32,
    lcsStatusTcpIpRadiussAccessClientsEntryUnknownType Counter32
}

-- {COLUMN} 310.1.9.12.1.15.1.1
lcsStatusTcpIpRadiussAccessClientsEntryIpAddress OBJECT-TYPE
    SYNTAX     IpAddress
    MAX-ACCESS read-only
    STATUS     current
    DESCRIPTION
        "-- empty --"
    ::= { lcsStatusTcpIpRadiussAccessClientsEntry 1 }

-- {COLUMN} 310.1.9.12.1.15.1.13
lcsStatusTcpIpRadiussAccessClientsEntryLastRequest OBJECT-TYPE
    SYNTAX     INTEGER (0..2147483647)
    MAX-ACCESS read-only
    STATUS     current
    DESCRIPTION
        "-- empty --"
    ::= { lcsStatusTcpIpRadiussAccessClientsEntry 13 }

-- {COLUMN} 310.1.9.12.1.15.1.32
lcsStatusTcpIpRadiussAccessClientsEntryLastStatusRequest OBJECT-TYPE
    SYNTAX     INTEGER (0..2147483647)
    MAX-ACCESS read-only
    STATUS     current
    DESCRIPTION
        "-- empty --"
    ::= { lcsStatusTcpIpRadiussAccessClientsEntry 32 }

-- {COLUMN} 310.1.9.12.1.15.1.14
lcsStatusTcpIpRadiussAccessClientsEntryNasIdent OBJECT-TYPE
    SYNTAX     DisplayString (SIZE(0..64))
    MAX-ACCESS read-only
    STATUS     current
    DESCRIPTION
        "-- empty --"
    ::= { lcsStatusTcpIpRadiussAccessClientsEntry 14 }

-- {COLUMN} 310.1.9.12.1.15.1.4
lcsStatusTcpIpRadiussAccessClientsEntryAccessRequests OBJECT-TYPE
    SYNTAX     Counter32
    MAX-ACCESS read-only
    STATUS     current
    DESCRIPTION
        "-- empty --"
    ::= { lcsStatusTcpIpRadiussAccessClientsEntry 4 }

-- {COLUMN} 310.1.9.12.1.15.1.30
lcsStatusTcpIpRadiussAccessClientsEntryStatusRequests OBJECT-TYPE
    SYNTAX     Counter32
    MAX-ACCESS read-only
    STATUS     current
    DESCRIPTION
        "-- empty --"
    ::= { lcsStatusTcpIpRadiussAccessClientsEntry 30 }

-- {COLUMN} 310.1.9.12.1.15.1.5
lcsStatusTcpIpRadiussAccessClientsEntryDuplicateRequests OBJECT-TYPE
    SYNTAX     Counter32
    MAX-ACCESS read-only
    STATUS     current
    DESCRIPTION
        "-- empty --"
    ::= { lcsStatusTcpIpRadiussAccessClientsEntry 5 }

-- {COLUMN} 310.1.9.12.1.15.1.6
lcsStatusTcpIpRadiussAccessClientsEntryAccessAccepts OBJECT-TYPE
    SYNTAX     Counter32
    MAX-ACCESS read-only
    STATUS     current
    DESCRIPTION
        "-- empty --"
    ::= { lcsStatusTcpIpRadiussAccessClientsEntry 6 }

-- {COLUMN} 310.1.9.12.1.15.1.7
lcsStatusTcpIpRadiussAccessClientsEntryAccessRejects OBJECT-TYPE
    SYNTAX     Counter32
    MAX-ACCESS read-only
    STATUS     current
    DESCRIPTION
        "-- empty --"
    ::= { lcsStatusTcpIpRadiussAccessClientsEntry 7 }

-- {COLUMN} 310.1.9.12.1.15.1.8
lcsStatusTcpIpRadiussAccessClientsEntryAccessChallenges OBJECT-TYPE
    SYNTAX     Counter32
    MAX-ACCESS read-only
    STATUS     current
    DESCRIPTION
        "-- empty --"
    ::= { lcsStatusTcpIpRadiussAccessClientsEntry 8 }

-- {COLUMN} 310.1.9.12.1.15.1.31
lcsStatusTcpIpRadiussAccessClientsEntryStatusResponses OBJECT-TYPE
    SYNTAX     Counter32
    MAX-ACCESS read-only
    STATUS     current
    DESCRIPTION
        "-- empty --"
    ::= { lcsStatusTcpIpRadiussAccessClientsEntry 31 }

-- {COLUMN} 310.1.9.12.1.15.1.9
lcsStatusTcpIpRadiussAccessClientsEntryMalfAccReq OBJECT-TYPE
    SYNTAX     Counter32
    MAX-ACCESS read-only
    STATUS     current
    DESCRIPTION
        ""
    ::= { lcsStatusTcpIpRadiussAccessClientsEntry 9 }

-- {COLUMN} 310.1.9.12.1.15.1.10
lcsStatusTcpIpRadiussAccessClientsEntryBadAuthenticator OBJECT-TYPE
    SYNTAX     Counter32
    MAX-ACCESS read-only
    STATUS     current
    DESCRIPTION
        "-- empty --"
    ::= { lcsStatusTcpIpRadiussAccessClientsEntry 10 }

-- {COLUMN} 310.1.9.12.1.15.1.11
lcsStatusTcpIpRadiussAccessClientsEntryDropped OBJECT-TYPE
    SYNTAX     Counter32
    MAX-ACCESS read-only
    STATUS     current
    DESCRIPTION
        "-- empty --"
    ::= { lcsStatusTcpIpRadiussAccessClientsEntry 11 }

-- {COLUMN} 310.1.9.12.1.15.1.12
lcsStatusTcpIpRadiussAccessClientsEntryUnknownType OBJECT-TYPE
    SYNTAX     Counter32
    MAX-ACCESS read-only
    STATUS     current
    DESCRIPTION
        "-- empty --"
    ::= { lcsStatusTcpIpRadiussAccessClientsEntry 12 }

-- {SCALAR} 310.1.9.12.1.30
lcsStatusTcpIpRadiussAccessTotalStatusRequests OBJECT-TYPE
    SYNTAX     Counter32
    MAX-ACCESS read-only
    STATUS     current
    DESCRIPTION
        "-- empty --"
    ::= { lcsStatusTcpIpRadiussAccess 30 }

-- {SCALAR} 310.1.9.12.1.31
lcsStatusTcpIpRadiussAccessTotalStatusResponses OBJECT-TYPE
    SYNTAX     Counter32
    MAX-ACCESS read-only
    STATUS     current
    DESCRIPTION
        "-- empty --"
    ::= { lcsStatusTcpIpRadiussAccess 31 }

-- {SCALAR} 310.1.9.12.1.5
lcsStatusTcpIpRadiussAccessTotalAccessRequests OBJECT-TYPE
    SYNTAX     Counter32
    MAX-ACCESS read-only
    STATUS     current
    DESCRIPTION
        "-- empty --"
    ::= { lcsStatusTcpIpRadiussAccess 5 }

-- {SCALAR} 310.1.9.12.1.6
lcsStatusTcpIpRadiussAccessTotalInvalidAccessRequests OBJECT-TYPE
    SYNTAX     Counter32
    MAX-ACCESS read-only
    STATUS     current
    DESCRIPTION
        "-- empty --"
    ::= { lcsStatusTcpIpRadiussAccess 6 }

-- {SCALAR} 310.1.9.12.1.7
lcsStatusTcpIpRadiussAccessTotalDuplicateAccessRequests OBJECT-TYPE
    SYNTAX     Counter32
    MAX-ACCESS read-only
    STATUS     current
    DESCRIPTION
        "-- empty --"
    ::= { lcsStatusTcpIpRadiussAccess 7 }

-- {SCALAR} 310.1.9.12.1.8
lcsStatusTcpIpRadiussAccessTotalAccessAccepts OBJECT-TYPE
    SYNTAX     Counter32
    MAX-ACCESS read-only
    STATUS     current
    DESCRIPTION
        "-- empty --"
    ::= { lcsStatusTcpIpRadiussAccess 8 }

-- {SCALAR} 310.1.9.12.1.9
lcsStatusTcpIpRadiussAccessTotalAccessRejects OBJECT-TYPE
    SYNTAX     Counter32
    MAX-ACCESS read-only
    STATUS     current
    DESCRIPTION
        "-- empty --"
    ::= { lcsStatusTcpIpRadiussAccess 9 }

-- {SCALAR} 310.1.9.12.1.10
lcsStatusTcpIpRadiussAccessTotalAccessChallenges OBJECT-TYPE
    SYNTAX     Counter32
    MAX-ACCESS read-only
    STATUS     current
    DESCRIPTION
        "-- empty --"
    ::= { lcsStatusTcpIpRadiussAccess 10 }

-- {SCALAR} 310.1.9.12.1.11
lcsStatusTcpIpRadiussAccessTotalMalformedAccessRequests OBJECT-TYPE
    SYNTAX     Counter32
    MAX-ACCESS read-only
    STATUS     current
    DESCRIPTION
        "-- empty --"
    ::= { lcsStatusTcpIpRadiussAccess 11 }

-- {SCALAR} 310.1.9.12.1.12
lcsStatusTcpIpRadiussAccessTotalAccessBadAuthenticator OBJECT-TYPE
    SYNTAX     Counter32
    MAX-ACCESS read-only
    STATUS     current
    DESCRIPTION
        "-- empty --"
    ::= { lcsStatusTcpIpRadiussAccess 12 }

-- {SCALAR} 310.1.9.12.1.13
lcsStatusTcpIpRadiussAccessTotalAccessDropped OBJECT-TYPE
    SYNTAX     Counter32
    MAX-ACCESS read-only
    STATUS     current
    DESCRIPTION
        "-- empty --"
    ::= { lcsStatusTcpIpRadiussAccess 13 }

-- {SCALAR} 310.1.9.12.1.14
lcsStatusTcpIpRadiussAccessTotalAccessUnknownType OBJECT-TYPE
    SYNTAX     Counter32
    MAX-ACCESS read-only
    STATUS     current
    DESCRIPTION
        "-- empty --"
    ::= { lcsStatusTcpIpRadiussAccess 14 }

-- {OID} 310.1.9.12.2
lcsStatusTcpIpRadiussAccnt OBJECT IDENTIFIER ::= { lcsStatusTcpIpRadiuss 2 }

-- {SCALAR} 310.1.9.12.2.100
lcsStatusTcpIpRadiussAccntDeleteValues OBJECT-TYPE
    SYNTAX     DisplayString
    MAX-ACCESS read-write
    STATUS     current
    DESCRIPTION
        "-- empty --"
    ::= { lcsStatusTcpIpRadiussAccnt 100 }

-- {TABLE} 310.1.9.12.2.15
lcsStatusTcpIpRadiussAccntClientsTable OBJECT-TYPE
    SYNTAX     SEQUENCE OF LcsStatusTcpIpRadiussAccntClientsEntry
    MAX-ACCESS not-accessible
    STATUS     current
    DESCRIPTION
        "-- empty --"
    ::= { lcsStatusTcpIpRadiussAccnt 15 }

-- {ENTRY} 310.1.9.12.2.15.1
lcsStatusTcpIpRadiussAccntClientsEntry OBJECT-TYPE
    SYNTAX     LcsStatusTcpIpRadiussAccntClientsEntry
    MAX-ACCESS not-accessible
    STATUS     current
    DESCRIPTION
        ""
    INDEX {
        lcsStatusTcpIpRadiussAccntClientsEntryIpAddress
    }
    ::= { lcsStatusTcpIpRadiussAccntClientsTable 1 }

-- {SEQUENCE}
LcsStatusTcpIpRadiussAccntClientsEntry ::= SEQUENCE {
    lcsStatusTcpIpRadiussAccntClientsEntryIpAddress IpAddress,
    lcsStatusTcpIpRadiussAccntClientsEntryLastRequest INTEGER,
    lcsStatusTcpIpRadiussAccntClientsEntryLastStatusRequest INTEGER,
    lcsStatusTcpIpRadiussAccntClientsEntryNasIdent DisplayString,
    lcsStatusTcpIpRadiussAccntClientsEntryAccountRequests Counter32,
    lcsStatusTcpIpRadiussAccntClientsEntryStatusRequests Counter32,
    lcsStatusTcpIpRadiussAccntClientsEntryDuplicateRequests Counter32,
    lcsStatusTcpIpRadiussAccntClientsEntryAccountResponses Counter32,
    lcsStatusTcpIpRadiussAccntClientsEntryAccountNorecords Counter32,
    lcsStatusTcpIpRadiussAccntClientsEntryStatusResponses Counter32,
    lcsStatusTcpIpRadiussAccntClientsEntryMalfAccReq Counter32,
    lcsStatusTcpIpRadiussAccntClientsEntryBadAuthenticator Counter32,
    lcsStatusTcpIpRadiussAccntClientsEntryDropped Counter32,
    lcsStatusTcpIpRadiussAccntClientsEntryUnknownType Counter32
}

-- {COLUMN} 310.1.9.12.2.15.1.1
lcsStatusTcpIpRadiussAccntClientsEntryIpAddress OBJECT-TYPE
    SYNTAX     IpAddress
    MAX-ACCESS read-only
    STATUS     current
    DESCRIPTION
        "-- empty --"
    ::= { lcsStatusTcpIpRadiussAccntClientsEntry 1 }

-- {COLUMN} 310.1.9.12.2.15.1.13
lcsStatusTcpIpRadiussAccntClientsEntryLastRequest OBJECT-TYPE
    SYNTAX     INTEGER (0..2147483647)
    MAX-ACCESS read-only
    STATUS     current
    DESCRIPTION
        "-- empty --"
    ::= { lcsStatusTcpIpRadiussAccntClientsEntry 13 }

-- {COLUMN} 310.1.9.12.2.15.1.32
lcsStatusTcpIpRadiussAccntClientsEntryLastStatusRequest OBJECT-TYPE
    SYNTAX     INTEGER (0..2147483647)
    MAX-ACCESS read-only
    STATUS     current
    DESCRIPTION
        "-- empty --"
    ::= { lcsStatusTcpIpRadiussAccntClientsEntry 32 }

-- {COLUMN} 310.1.9.12.2.15.1.14
lcsStatusTcpIpRadiussAccntClientsEntryNasIdent OBJECT-TYPE
    SYNTAX     DisplayString (SIZE(0..64))
    MAX-ACCESS read-only
    STATUS     current
    DESCRIPTION
        "-- empty --"
    ::= { lcsStatusTcpIpRadiussAccntClientsEntry 14 }

-- {COLUMN} 310.1.9.12.2.15.1.4
lcsStatusTcpIpRadiussAccntClientsEntryAccountRequests OBJECT-TYPE
    SYNTAX     Counter32
    MAX-ACCESS read-only
    STATUS     current
    DESCRIPTION
        "-- empty --"
    ::= { lcsStatusTcpIpRadiussAccntClientsEntry 4 }

-- {COLUMN} 310.1.9.12.2.15.1.30
lcsStatusTcpIpRadiussAccntClientsEntryStatusRequests OBJECT-TYPE
    SYNTAX     Counter32
    MAX-ACCESS read-only
    STATUS     current
    DESCRIPTION
        "-- empty --"
    ::= { lcsStatusTcpIpRadiussAccntClientsEntry 30 }

-- {COLUMN} 310.1.9.12.2.15.1.5
lcsStatusTcpIpRadiussAccntClientsEntryDuplicateRequests OBJECT-TYPE
    SYNTAX     Counter32
    MAX-ACCESS read-only
    STATUS     current
    DESCRIPTION
        "-- empty --"
    ::= { lcsStatusTcpIpRadiussAccntClientsEntry 5 }

-- {COLUMN} 310.1.9.12.2.15.1.6
lcsStatusTcpIpRadiussAccntClientsEntryAccountResponses OBJECT-TYPE
    SYNTAX     Counter32
    MAX-ACCESS read-only
    STATUS     current
    DESCRIPTION
        "-- empty --"
    ::= { lcsStatusTcpIpRadiussAccntClientsEntry 6 }

-- {COLUMN} 310.1.9.12.2.15.1.7
lcsStatusTcpIpRadiussAccntClientsEntryAccountNorecords OBJECT-TYPE
    SYNTAX     Counter32
    MAX-ACCESS read-only
    STATUS     current
    DESCRIPTION
        "-- empty --"
    ::= { lcsStatusTcpIpRadiussAccntClientsEntry 7 }

-- {COLUMN} 310.1.9.12.2.15.1.31
lcsStatusTcpIpRadiussAccntClientsEntryStatusResponses OBJECT-TYPE
    SYNTAX     Counter32
    MAX-ACCESS read-only
    STATUS     current
    DESCRIPTION
        "-- empty --"
    ::= { lcsStatusTcpIpRadiussAccntClientsEntry 31 }

-- {COLUMN} 310.1.9.12.2.15.1.9
lcsStatusTcpIpRadiussAccntClientsEntryMalfAccReq OBJECT-TYPE
    SYNTAX     Counter32
    MAX-ACCESS read-only
    STATUS     current
    DESCRIPTION
        ""
    ::= { lcsStatusTcpIpRadiussAccntClientsEntry 9 }

-- {COLUMN} 310.1.9.12.2.15.1.10
lcsStatusTcpIpRadiussAccntClientsEntryBadAuthenticator OBJECT-TYPE
    SYNTAX     Counter32
    MAX-ACCESS read-only
    STATUS     current
    DESCRIPTION
        "-- empty --"
    ::= { lcsStatusTcpIpRadiussAccntClientsEntry 10 }

-- {COLUMN} 310.1.9.12.2.15.1.11
lcsStatusTcpIpRadiussAccntClientsEntryDropped OBJECT-TYPE
    SYNTAX     Counter32
    MAX-ACCESS read-only
    STATUS     current
    DESCRIPTION
        "-- empty --"
    ::= { lcsStatusTcpIpRadiussAccntClientsEntry 11 }

-- {COLUMN} 310.1.9.12.2.15.1.12
lcsStatusTcpIpRadiussAccntClientsEntryUnknownType OBJECT-TYPE
    SYNTAX     Counter32
    MAX-ACCESS read-only
    STATUS     current
    DESCRIPTION
        "-- empty --"
    ::= { lcsStatusTcpIpRadiussAccntClientsEntry 12 }

-- {TABLE} 310.1.9.12.2.16
lcsStatusTcpIpRadiussAccntActAccntSessTable OBJECT-TYPE
    SYNTAX     SEQUENCE OF LcsStatusTcpIpRadiussAccntActAccntSessEntry
    MAX-ACCESS not-accessible
    STATUS     current
    DESCRIPTION
        ""
    ::= { lcsStatusTcpIpRadiussAccnt 16 }

-- {ENTRY} 310.1.9.12.2.16.1
lcsStatusTcpIpRadiussAccntActAccntSessEntry OBJECT-TYPE
    SYNTAX     LcsStatusTcpIpRadiussAccntActAccntSessEntry
    MAX-ACCESS not-accessible
    STATUS     current
    DESCRIPTION
        ""
    INDEX {
        lcsStatusTcpIpRadiussAccntActAccntSessEntryIndex
    }
    ::= { lcsStatusTcpIpRadiussAccntActAccntSessTable 1 }

-- {SEQUENCE}
LcsStatusTcpIpRadiussAccntActAccntSessEntry ::= SEQUENCE {
    lcsStatusTcpIpRadiussAccntActAccntSessEntryIndex INTEGER,
    lcsStatusTcpIpRadiussAccntActAccntSessEntryStartTime DisplayString,
    lcsStatusTcpIpRadiussAccntActAccntSessEntryLastUpdate INTEGER,
    lcsStatusTcpIpRadiussAccntActAccntSessEntryUpdateDelta INTEGER,
    lcsStatusTcpIpRadiussAccntActAccntSessEntryNasIpAddress IpAddress,
    lcsStatusTcpIpRadiussAccntActAccntSessEntryNasIdent DisplayString,
    lcsStatusTcpIpRadiussAccntActAccntSessEntryNasPortType INTEGER,
    lcsStatusTcpIpRadiussAccntActAccntSessEntryNasPortId INTEGER,
    lcsStatusTcpIpRadiussAccntActAccntSessEntrySessionId DisplayString,
    lcsStatusTcpIpRadiussAccntActAccntSessEntryCalledStationId DisplayString,
    lcsStatusTcpIpRadiussAccntActAccntSessEntryCallingStationId DisplayString,
    lcsStatusTcpIpRadiussAccntActAccntSessEntryUserName DisplayString,
    lcsStatusTcpIpRadiussAccntActAccntSessEntrySessionTime INTEGER,
    lcsStatusTcpIpRadiussAccntActAccntSessEntryInputPackets Counter32,
    lcsStatusTcpIpRadiussAccntActAccntSessEntryOutputPackets Counter32,
    lcsStatusTcpIpRadiussAccntActAccntSessEntryInputOctets Counter64,
    lcsStatusTcpIpRadiussAccntActAccntSessEntryOutputOctets Counter64,
    lcsStatusTcpIpRadiussAccntActAccntSessEntryIpAddress IpAddress
}

-- {COLUMN} 310.1.9.12.2.16.1.1
lcsStatusTcpIpRadiussAccntActAccntSessEntryIndex OBJECT-TYPE
    SYNTAX     INTEGER (0..2147483647)
    MAX-ACCESS read-only
    STATUS     current
    DESCRIPTION
        "-- empty --"
    ::= { lcsStatusTcpIpRadiussAccntActAccntSessEntry 1 }

-- {COLUMN} 310.1.9.12.2.16.1.12
lcsStatusTcpIpRadiussAccntActAccntSessEntryStartTime OBJECT-TYPE
    SYNTAX     DisplayString (SIZE(0..19))
    MAX-ACCESS read-only
    STATUS     current
    DESCRIPTION
        "-- empty --"
    ::= { lcsStatusTcpIpRadiussAccntActAccntSessEntry 12 }

-- {COLUMN} 310.1.9.12.2.16.1.15
lcsStatusTcpIpRadiussAccntActAccntSessEntryLastUpdate OBJECT-TYPE
    SYNTAX     INTEGER (0..2147483647)
    MAX-ACCESS read-only
    STATUS     current
    DESCRIPTION
        "-- empty --"
    ::= { lcsStatusTcpIpRadiussAccntActAccntSessEntry 15 }

-- {COLUMN} 310.1.9.12.2.16.1.16
lcsStatusTcpIpRadiussAccntActAccntSessEntryUpdateDelta OBJECT-TYPE
    SYNTAX     INTEGER (0..2147483647)
    MAX-ACCESS read-only
    STATUS     current
    DESCRIPTION
        "-- empty --"
    ::= { lcsStatusTcpIpRadiussAccntActAccntSessEntry 16 }

-- {COLUMN} 310.1.9.12.2.16.1.2
lcsStatusTcpIpRadiussAccntActAccntSessEntryNasIpAddress OBJECT-TYPE
    SYNTAX     IpAddress
    MAX-ACCESS read-only
    STATUS     current
    DESCRIPTION
        "-- empty --"
    ::= { lcsStatusTcpIpRadiussAccntActAccntSessEntry 2 }

-- {COLUMN} 310.1.9.12.2.16.1.3
lcsStatusTcpIpRadiussAccntActAccntSessEntryNasIdent OBJECT-TYPE
    SYNTAX     DisplayString (SIZE(0..64))
    MAX-ACCESS read-only
    STATUS     current
    DESCRIPTION
        "-- empty --"
    ::= { lcsStatusTcpIpRadiussAccntActAccntSessEntry 3 }

-- {COLUMN} 310.1.9.12.2.16.1.17
lcsStatusTcpIpRadiussAccntActAccntSessEntryNasPortType OBJECT-TYPE
    SYNTAX     INTEGER
      {
        eAsync (0),
        eSync (1),
        eIsdnSync (2),
        eV120 (3),
        eV110 (4),
        eVirtual (5),
        ePiafs (6),
        eHdlcClearChannel (7),
        eX25 (8),
        eX75 (9),
        eG3Fax (10),
        eSdsl (11),
        eAdslCap (12),
        eAdslDmt (13),
        eIdsl (14),
        eEthernet (15),
        eXdsl (16),
        eCable (17),
        eWirelessOther (18),
        eWireless80211 (19),
        eTokenRing (20),
        eFddi (21),
        eWirelessCdma2000 (22),
        eWirelessUmts (23),
        eWireless1xEv (24),
        eIapp (25),
        eFttp (26),
        eWireless80216 (27),
        eWireless80220 (28),
        eWireless80222 (29),
        ePppoa (30),
        ePppoeoa (31),
        ePppoeoe (32),
        ePppoeovlan (33),
        ePppoeoqinq (34),
        eXpon (35),
        eUnknown (-1)
      }
    MAX-ACCESS read-only
    STATUS     current
    DESCRIPTION
        "-- empty --"
    ::= { lcsStatusTcpIpRadiussAccntActAccntSessEntry 17 }

-- {COLUMN} 310.1.9.12.2.16.1.18
lcsStatusTcpIpRadiussAccntActAccntSessEntryNasPortId OBJECT-TYPE
    SYNTAX     INTEGER (0..2147483647)
    MAX-ACCESS read-only
    STATUS     current
    DESCRIPTION
        "-- empty --"
    ::= { lcsStatusTcpIpRadiussAccntActAccntSessEntry 18 }

-- {COLUMN} 310.1.9.12.2.16.1.4
lcsStatusTcpIpRadiussAccntActAccntSessEntrySessionId OBJECT-TYPE
    SYNTAX     DisplayString (SIZE(0..128))
    MAX-ACCESS read-only
    STATUS     current
    DESCRIPTION
        "-- empty --"
    ::= { lcsStatusTcpIpRadiussAccntActAccntSessEntry 4 }

-- {COLUMN} 310.1.9.12.2.16.1.19
lcsStatusTcpIpRadiussAccntActAccntSessEntryCalledStationId OBJECT-TYPE
    SYNTAX     DisplayString (SIZE(0..48))
    MAX-ACCESS read-only
    STATUS     current
    DESCRIPTION
        "-- empty --"
    ::= { lcsStatusTcpIpRadiussAccntActAccntSessEntry 19 }

-- {COLUMN} 310.1.9.12.2.16.1.20
lcsStatusTcpIpRadiussAccntActAccntSessEntryCallingStationId OBJECT-TYPE
    SYNTAX     DisplayString (SIZE(0..48))
    MAX-ACCESS read-only
    STATUS     current
    DESCRIPTION
        "-- empty --"
    ::= { lcsStatusTcpIpRadiussAccntActAccntSessEntry 20 }

-- {COLUMN} 310.1.9.12.2.16.1.5
lcsStatusTcpIpRadiussAccntActAccntSessEntryUserName OBJECT-TYPE
    SYNTAX     DisplayString (SIZE(0..48))
    MAX-ACCESS read-only
    STATUS     current
    DESCRIPTION
        "-- empty --"
    ::= { lcsStatusTcpIpRadiussAccntActAccntSessEntry 5 }

-- {COLUMN} 310.1.9.12.2.16.1.6
lcsStatusTcpIpRadiussAccntActAccntSessEntrySessionTime OBJECT-TYPE
    SYNTAX     INTEGER (0..2147483647)
    MAX-ACCESS read-only
    STATUS     current
    DESCRIPTION
        "-- empty --"
    ::= { lcsStatusTcpIpRadiussAccntActAccntSessEntry 6 }

-- {COLUMN} 310.1.9.12.2.16.1.7
lcsStatusTcpIpRadiussAccntActAccntSessEntryInputPackets OBJECT-TYPE
    SYNTAX     Counter32
    MAX-ACCESS read-only
    STATUS     current
    DESCRIPTION
        "-- empty --"
    ::= { lcsStatusTcpIpRadiussAccntActAccntSessEntry 7 }

-- {COLUMN} 310.1.9.12.2.16.1.8
lcsStatusTcpIpRadiussAccntActAccntSessEntryOutputPackets OBJECT-TYPE
    SYNTAX     Counter32
    MAX-ACCESS read-only
    STATUS     current
    DESCRIPTION
        "-- empty --"
    ::= { lcsStatusTcpIpRadiussAccntActAccntSessEntry 8 }

-- {COLUMN} 310.1.9.12.2.16.1.9
lcsStatusTcpIpRadiussAccntActAccntSessEntryInputOctets OBJECT-TYPE
    SYNTAX     Counter64
    MAX-ACCESS read-only
    STATUS     current
    DESCRIPTION
        "-- empty --"
    ::= { lcsStatusTcpIpRadiussAccntActAccntSessEntry 9 }

-- {COLUMN} 310.1.9.12.2.16.1.10
lcsStatusTcpIpRadiussAccntActAccntSessEntryOutputOctets OBJECT-TYPE
    SYNTAX     Counter64
    MAX-ACCESS read-only
    STATUS     current
    DESCRIPTION
        "-- empty --"
    ::= { lcsStatusTcpIpRadiussAccntActAccntSessEntry 10 }

-- {COLUMN} 310.1.9.12.2.16.1.11
lcsStatusTcpIpRadiussAccntActAccntSessEntryIpAddress OBJECT-TYPE
    SYNTAX     IpAddress
    MAX-ACCESS read-only
    STATUS     current
    DESCRIPTION
        "-- empty --"
    ::= { lcsStatusTcpIpRadiussAccntActAccntSessEntry 11 }

-- {TABLE} 310.1.9.12.2.17
lcsStatusTcpIpRadiussAccntComplAccntSessTable OBJECT-TYPE
    SYNTAX     SEQUENCE OF LcsStatusTcpIpRadiussAccntComplAccntSessEntry
    MAX-ACCESS not-accessible
    STATUS     current
    DESCRIPTION
        ""
    ::= { lcsStatusTcpIpRadiussAccnt 17 }

-- {ENTRY} 310.1.9.12.2.17.1
lcsStatusTcpIpRadiussAccntComplAccntSessEntry OBJECT-TYPE
    SYNTAX     LcsStatusTcpIpRadiussAccntComplAccntSessEntry
    MAX-ACCESS not-accessible
    STATUS     current
    DESCRIPTION
        ""
    INDEX {
        lcsStatusTcpIpRadiussAccntComplAccntSessEntryIndex
    }
    ::= { lcsStatusTcpIpRadiussAccntComplAccntSessTable 1 }

-- {SEQUENCE}
LcsStatusTcpIpRadiussAccntComplAccntSessEntry ::= SEQUENCE {
    lcsStatusTcpIpRadiussAccntComplAccntSessEntryIndex INTEGER,
    lcsStatusTcpIpRadiussAccntComplAccntSessEntryStartTime DisplayString,
    lcsStatusTcpIpRadiussAccntComplAccntSessEntryStopTime DisplayString,
    lcsStatusTcpIpRadiussAccntComplAccntSessEntryTerminateCause INTEGER,
    lcsStatusTcpIpRadiussAccntComplAccntSessEntryNasIpAddress IpAddress,
    lcsStatusTcpIpRadiussAccntComplAccntSessEntryNasIdent DisplayString,
    lcsStatusTcpIpRadiussAccntComplAccntSessEntryNasPortType INTEGER,
    lcsStatusTcpIpRadiussAccntComplAccntSessEntryNasPortId INTEGER,
    lcsStatusTcpIpRadiussAccntComplAccntSessEntrySessionId DisplayString,
    lcsStatusTcpIpRadiussAccntComplAccntSessEntryCalledStationId DisplayString,
    lcsStatusTcpIpRadiussAccntComplAccntSessEntryCallingStationId DisplayString,
    lcsStatusTcpIpRadiussAccntComplAccntSessEntryUserName DisplayString,
    lcsStatusTcpIpRadiussAccntComplAccntSessEntrySessionTime INTEGER,
    lcsStatusTcpIpRadiussAccntComplAccntSessEntryInputPackets Counter32,
    lcsStatusTcpIpRadiussAccntComplAccntSessEntryOutputPackets Counter32,
    lcsStatusTcpIpRadiussAccntComplAccntSessEntryInputOctets Counter64,
    lcsStatusTcpIpRadiussAccntComplAccntSessEntryOutputOctets Counter64,
    lcsStatusTcpIpRadiussAccntComplAccntSessEntryIpAddress IpAddress
}

-- {COLUMN} 310.1.9.12.2.17.1.1
lcsStatusTcpIpRadiussAccntComplAccntSessEntryIndex OBJECT-TYPE
    SYNTAX     INTEGER (0..2147483647)
    MAX-ACCESS read-only
    STATUS     current
    DESCRIPTION
        "-- empty --"
    ::= { lcsStatusTcpIpRadiussAccntComplAccntSessEntry 1 }

-- {COLUMN} 310.1.9.12.2.17.1.12
lcsStatusTcpIpRadiussAccntComplAccntSessEntryStartTime OBJECT-TYPE
    SYNTAX     DisplayString (SIZE(0..19))
    MAX-ACCESS read-only
    STATUS     current
    DESCRIPTION
        "-- empty --"
    ::= { lcsStatusTcpIpRadiussAccntComplAccntSessEntry 12 }

-- {COLUMN} 310.1.9.12.2.17.1.13
lcsStatusTcpIpRadiussAccntComplAccntSessEntryStopTime OBJECT-TYPE
    SYNTAX     DisplayString (SIZE(0..19))
    MAX-ACCESS read-only
    STATUS     current
    DESCRIPTION
        "-- empty --"
    ::= { lcsStatusTcpIpRadiussAccntComplAccntSessEntry 13 }

-- {COLUMN} 310.1.9.12.2.17.1.14
lcsStatusTcpIpRadiussAccntComplAccntSessEntryTerminateCause OBJECT-TYPE
    SYNTAX     INTEGER
      {
        eUserRequest (1),
        eLostCarrier (2),
        eLostService (3),
        eIdleTimeout (4),
        eSessionTimeout (5),
        eAdminReset (6),
        eAdminReboot (7),
        ePortError (8),
        eNasError (9),
        eNasRequest (10),
        eNasReboot (11),
        ePortUnneeded (12),
        ePortPreempted (13),
        ePortSuspended (14),
        eServiceUnavailable (15),
        eCallback (16),
        eUserError (17),
        eHostRequest (18),
        eSupplicantRestart (19),
        eReauthenticationFailure (20),
        ePortReinit (21),
        ePortAdminDisabled (22)
      }
    MAX-ACCESS read-only
    STATUS     current
    DESCRIPTION
        "-- empty --"
    ::= { lcsStatusTcpIpRadiussAccntComplAccntSessEntry 14 }

-- {COLUMN} 310.1.9.12.2.17.1.2
lcsStatusTcpIpRadiussAccntComplAccntSessEntryNasIpAddress OBJECT-TYPE
    SYNTAX     IpAddress
    MAX-ACCESS read-only
    STATUS     current
    DESCRIPTION
        "-- empty --"
    ::= { lcsStatusTcpIpRadiussAccntComplAccntSessEntry 2 }

-- {COLUMN} 310.1.9.12.2.17.1.3
lcsStatusTcpIpRadiussAccntComplAccntSessEntryNasIdent OBJECT-TYPE
    SYNTAX     DisplayString (SIZE(0..64))
    MAX-ACCESS read-only
    STATUS     current
    DESCRIPTION
        "-- empty --"
    ::= { lcsStatusTcpIpRadiussAccntComplAccntSessEntry 3 }

-- {COLUMN} 310.1.9.12.2.17.1.17
lcsStatusTcpIpRadiussAccntComplAccntSessEntryNasPortType OBJECT-TYPE
    SYNTAX     INTEGER
      {
        eAsync (0),
        eSync (1),
        eIsdnSync (2),
        eV120 (3),
        eV110 (4),
        eVirtual (5),
        ePiafs (6),
        eHdlcClearChannel (7),
        eX25 (8),
        eX75 (9),
        eG3Fax (10),
        eSdsl (11),
        eAdslCap (12),
        eAdslDmt (13),
        eIdsl (14),
        eEthernet (15),
        eXdsl (16),
        eCable (17),
        eWirelessOther (18),
        eWireless80211 (19),
        eTokenRing (20),
        eFddi (21),
        eWirelessCdma2000 (22),
        eWirelessUmts (23),
        eWireless1xEv (24),
        eIapp (25),
        eFttp (26),
        eWireless80216 (27),
        eWireless80220 (28),
        eWireless80222 (29),
        ePppoa (30),
        ePppoeoa (31),
        ePppoeoe (32),
        ePppoeovlan (33),
        ePppoeoqinq (34),
        eXpon (35),
        eUnknown (-1)
      }
    MAX-ACCESS read-only
    STATUS     current
    DESCRIPTION
        "-- empty --"
    ::= { lcsStatusTcpIpRadiussAccntComplAccntSessEntry 17 }

-- {COLUMN} 310.1.9.12.2.17.1.18
lcsStatusTcpIpRadiussAccntComplAccntSessEntryNasPortId OBJECT-TYPE
    SYNTAX     INTEGER (0..2147483647)
    MAX-ACCESS read-only
    STATUS     current
    DESCRIPTION
        "-- empty --"
    ::= { lcsStatusTcpIpRadiussAccntComplAccntSessEntry 18 }

-- {COLUMN} 310.1.9.12.2.17.1.4
lcsStatusTcpIpRadiussAccntComplAccntSessEntrySessionId OBJECT-TYPE
    SYNTAX     DisplayString (SIZE(0..128))
    MAX-ACCESS read-only
    STATUS     current
    DESCRIPTION
        "-- empty --"
    ::= { lcsStatusTcpIpRadiussAccntComplAccntSessEntry 4 }

-- {COLUMN} 310.1.9.12.2.17.1.19
lcsStatusTcpIpRadiussAccntComplAccntSessEntryCalledStationId OBJECT-TYPE
    SYNTAX     DisplayString (SIZE(0..48))
    MAX-ACCESS read-only
    STATUS     current
    DESCRIPTION
        "-- empty --"
    ::= { lcsStatusTcpIpRadiussAccntComplAccntSessEntry 19 }

-- {COLUMN} 310.1.9.12.2.17.1.20
lcsStatusTcpIpRadiussAccntComplAccntSessEntryCallingStationId OBJECT-TYPE
    SYNTAX     DisplayString (SIZE(0..48))
    MAX-ACCESS read-only
    STATUS     current
    DESCRIPTION
        "-- empty --"
    ::= { lcsStatusTcpIpRadiussAccntComplAccntSessEntry 20 }

-- {COLUMN} 310.1.9.12.2.17.1.5
lcsStatusTcpIpRadiussAccntComplAccntSessEntryUserName OBJECT-TYPE
    SYNTAX     DisplayString (SIZE(0..48))
    MAX-ACCESS read-only
    STATUS     current
    DESCRIPTION
        "-- empty --"
    ::= { lcsStatusTcpIpRadiussAccntComplAccntSessEntry 5 }

-- {COLUMN} 310.1.9.12.2.17.1.6
lcsStatusTcpIpRadiussAccntComplAccntSessEntrySessionTime OBJECT-TYPE
    SYNTAX     INTEGER (0..2147483647)
    MAX-ACCESS read-only
    STATUS     current
    DESCRIPTION
        "-- empty --"
    ::= { lcsStatusTcpIpRadiussAccntComplAccntSessEntry 6 }

-- {COLUMN} 310.1.9.12.2.17.1.7
lcsStatusTcpIpRadiussAccntComplAccntSessEntryInputPackets OBJECT-TYPE
    SYNTAX     Counter32
    MAX-ACCESS read-only
    STATUS     current
    DESCRIPTION
        "-- empty --"
    ::= { lcsStatusTcpIpRadiussAccntComplAccntSessEntry 7 }

-- {COLUMN} 310.1.9.12.2.17.1.8
lcsStatusTcpIpRadiussAccntComplAccntSessEntryOutputPackets OBJECT-TYPE
    SYNTAX     Counter32
    MAX-ACCESS read-only
    STATUS     current
    DESCRIPTION
        "-- empty --"
    ::= { lcsStatusTcpIpRadiussAccntComplAccntSessEntry 8 }

-- {COLUMN} 310.1.9.12.2.17.1.9
lcsStatusTcpIpRadiussAccntComplAccntSessEntryInputOctets OBJECT-TYPE
    SYNTAX     Counter64
    MAX-ACCESS read-only
    STATUS     current
    DESCRIPTION
        "-- empty --"
    ::= { lcsStatusTcpIpRadiussAccntComplAccntSessEntry 9 }

-- {COLUMN} 310.1.9.12.2.17.1.10
lcsStatusTcpIpRadiussAccntComplAccntSessEntryOutputOctets OBJECT-TYPE
    SYNTAX     Counter64
    MAX-ACCESS read-only
    STATUS     current
    DESCRIPTION
        "-- empty --"
    ::= { lcsStatusTcpIpRadiussAccntComplAccntSessEntry 10 }

-- {COLUMN} 310.1.9.12.2.17.1.11
lcsStatusTcpIpRadiussAccntComplAccntSessEntryIpAddress OBJECT-TYPE
    SYNTAX     IpAddress
    MAX-ACCESS read-only
    STATUS     current
    DESCRIPTION
        "-- empty --"
    ::= { lcsStatusTcpIpRadiussAccntComplAccntSessEntry 11 }

-- {TABLE} 310.1.9.12.2.18
lcsStatusTcpIpRadiussAccntAccountingTotalTable OBJECT-TYPE
    SYNTAX     SEQUENCE OF LcsStatusTcpIpRadiussAccntAccountingTotalEntry
    MAX-ACCESS not-accessible
    STATUS     current
    DESCRIPTION
        "-- empty --"
    ::= { lcsStatusTcpIpRadiussAccnt 18 }

-- {ENTRY} 310.1.9.12.2.18.1
lcsStatusTcpIpRadiussAccntAccountingTotalEntry OBJECT-TYPE
    SYNTAX     LcsStatusTcpIpRadiussAccntAccountingTotalEntry
    MAX-ACCESS not-accessible
    STATUS     current
    DESCRIPTION
        ""
    INDEX {
        lcsStatusTcpIpRadiussAccntAccountingTotalEntryUserName
    }
    ::= { lcsStatusTcpIpRadiussAccntAccountingTotalTable 1 }

-- {SEQUENCE}
LcsStatusTcpIpRadiussAccntAccountingTotalEntry ::= SEQUENCE {
    lcsStatusTcpIpRadiussAccntAccountingTotalEntryUserName DisplayString,
    lcsStatusTcpIpRadiussAccntAccountingTotalEntryTime INTEGER,
    lcsStatusTcpIpRadiussAccntAccountingTotalEntryInputPackets INTEGER,
    lcsStatusTcpIpRadiussAccntAccountingTotalEntryOutputPackets INTEGER,
    lcsStatusTcpIpRadiussAccntAccountingTotalEntryInputOctets INTEGER,
    lcsStatusTcpIpRadiussAccntAccountingTotalEntryOutputOctets INTEGER,
    lcsStatusTcpIpRadiussAccntAccountingTotalEntryFirstLogin DisplayString
}

-- {COLUMN} 310.1.9.12.2.18.1.1
lcsStatusTcpIpRadiussAccntAccountingTotalEntryUserName OBJECT-TYPE
    SYNTAX     DisplayString (SIZE(0..48))
    MAX-ACCESS read-only
    STATUS     current
    DESCRIPTION
        "-- empty --"
    ::= { lcsStatusTcpIpRadiussAccntAccountingTotalEntry 1 }

-- {COLUMN} 310.1.9.12.2.18.1.2
lcsStatusTcpIpRadiussAccntAccountingTotalEntryTime OBJECT-TYPE
    SYNTAX     INTEGER (0..2147483647)
    MAX-ACCESS read-only
    STATUS     current
    DESCRIPTION
        "-- empty --"
    ::= { lcsStatusTcpIpRadiussAccntAccountingTotalEntry 2 }

-- {COLUMN} 310.1.9.12.2.18.1.3
lcsStatusTcpIpRadiussAccntAccountingTotalEntryInputPackets OBJECT-TYPE
    SYNTAX     INTEGER (0..2147483647)
    MAX-ACCESS read-only
    STATUS     current
    DESCRIPTION
        "-- empty --"
    ::= { lcsStatusTcpIpRadiussAccntAccountingTotalEntry 3 }

-- {COLUMN} 310.1.9.12.2.18.1.4
lcsStatusTcpIpRadiussAccntAccountingTotalEntryOutputPackets OBJECT-TYPE
    SYNTAX     INTEGER (0..2147483647)
    MAX-ACCESS read-only
    STATUS     current
    DESCRIPTION
        "-- empty --"
    ::= { lcsStatusTcpIpRadiussAccntAccountingTotalEntry 4 }

-- {COLUMN} 310.1.9.12.2.18.1.5
lcsStatusTcpIpRadiussAccntAccountingTotalEntryInputOctets OBJECT-TYPE
    SYNTAX     INTEGER (0..2147483647)
    MAX-ACCESS read-only
    STATUS     current
    DESCRIPTION
        "-- empty --"
    ::= { lcsStatusTcpIpRadiussAccntAccountingTotalEntry 5 }

-- {COLUMN} 310.1.9.12.2.18.1.6
lcsStatusTcpIpRadiussAccntAccountingTotalEntryOutputOctets OBJECT-TYPE
    SYNTAX     INTEGER (0..2147483647)
    MAX-ACCESS read-only
    STATUS     current
    DESCRIPTION
        "-- empty --"
    ::= { lcsStatusTcpIpRadiussAccntAccountingTotalEntry 6 }

-- {COLUMN} 310.1.9.12.2.18.1.7
lcsStatusTcpIpRadiussAccntAccountingTotalEntryFirstLogin OBJECT-TYPE
    SYNTAX     DisplayString (SIZE(0..21))
    MAX-ACCESS read-only
    STATUS     current
    DESCRIPTION
        "-- empty --"
    ::= { lcsStatusTcpIpRadiussAccntAccountingTotalEntry 7 }

-- {SCALAR} 310.1.9.12.2.19
lcsStatusTcpIpRadiussAccntDeleteAccountingTotal OBJECT-TYPE
    SYNTAX     DisplayString
    MAX-ACCESS read-write
    STATUS     current
    DESCRIPTION
        "-- empty --"
    ::= { lcsStatusTcpIpRadiussAccnt 19 }

-- {SCALAR} 310.1.9.12.2.30
lcsStatusTcpIpRadiussAccntTotalStatusRequests OBJECT-TYPE
    SYNTAX     Counter32
    MAX-ACCESS read-only
    STATUS     current
    DESCRIPTION
        "-- empty --"
    ::= { lcsStatusTcpIpRadiussAccnt 30 }

-- {SCALAR} 310.1.9.12.2.31
lcsStatusTcpIpRadiussAccntTotalStatusResponses OBJECT-TYPE
    SYNTAX     Counter32
    MAX-ACCESS read-only
    STATUS     current
    DESCRIPTION
        "-- empty --"
    ::= { lcsStatusTcpIpRadiussAccnt 31 }

-- {SCALAR} 310.1.9.12.2.5
lcsStatusTcpIpRadiussAccntTotalAccountRequests OBJECT-TYPE
    SYNTAX     Counter32
    MAX-ACCESS read-only
    STATUS     current
    DESCRIPTION
        "-- empty --"
    ::= { lcsStatusTcpIpRadiussAccnt 5 }

-- {SCALAR} 310.1.9.12.2.6
lcsStatusTcpIpRadiussAccntTotalInvalidAccountRequests OBJECT-TYPE
    SYNTAX     Counter32
    MAX-ACCESS read-only
    STATUS     current
    DESCRIPTION
        "-- empty --"
    ::= { lcsStatusTcpIpRadiussAccnt 6 }

-- {SCALAR} 310.1.9.12.2.7
lcsStatusTcpIpRadiussAccntTotalDuplicateAccountRequests OBJECT-TYPE
    SYNTAX     Counter32
    MAX-ACCESS read-only
    STATUS     current
    DESCRIPTION
        "-- empty --"
    ::= { lcsStatusTcpIpRadiussAccnt 7 }

-- {SCALAR} 310.1.9.12.2.8
lcsStatusTcpIpRadiussAccntTotalAccountResponses OBJECT-TYPE
    SYNTAX     Counter32
    MAX-ACCESS read-only
    STATUS     current
    DESCRIPTION
        "-- empty --"
    ::= { lcsStatusTcpIpRadiussAccnt 8 }

-- {SCALAR} 310.1.9.12.2.9
lcsStatusTcpIpRadiussAccntTotalMalformedAccountRequests OBJECT-TYPE
    SYNTAX     Counter32
    MAX-ACCESS read-only
    STATUS     current
    DESCRIPTION
        "-- empty --"
    ::= { lcsStatusTcpIpRadiussAccnt 9 }

-- {SCALAR} 310.1.9.12.2.10
lcsStatusTcpIpRadiussAccntTotalAccountBadAuthenticator OBJECT-TYPE
    SYNTAX     Counter32
    MAX-ACCESS read-only
    STATUS     current
    DESCRIPTION
        "-- empty --"
    ::= { lcsStatusTcpIpRadiussAccnt 10 }

-- {SCALAR} 310.1.9.12.2.11
lcsStatusTcpIpRadiussAccntTotalAccountDropped OBJECT-TYPE
    SYNTAX     Counter32
    MAX-ACCESS read-only
    STATUS     current
    DESCRIPTION
        "-- empty --"
    ::= { lcsStatusTcpIpRadiussAccnt 11 }

-- {SCALAR} 310.1.9.12.2.12
lcsStatusTcpIpRadiussAccntTotalAccountNorecord OBJECT-TYPE
    SYNTAX     Counter32
    MAX-ACCESS read-only
    STATUS     current
    DESCRIPTION
        "-- empty --"
    ::= { lcsStatusTcpIpRadiussAccnt 12 }

-- {SCALAR} 310.1.9.12.2.13
lcsStatusTcpIpRadiussAccntTotalAccountUnknownType OBJECT-TYPE
    SYNTAX     Counter32
    MAX-ACCESS read-only
    STATUS     current
    DESCRIPTION
        "-- empty --"
    ::= { lcsStatusTcpIpRadiussAccnt 13 }

-- {TABLE} 310.1.9.12.10
lcsStatusTcpIpRadiussLogTableTable OBJECT-TYPE
    SYNTAX     SEQUENCE OF LcsStatusTcpIpRadiussLogTableEntry
    MAX-ACCESS not-accessible
    STATUS     current
    DESCRIPTION
        "-- empty --"
    ::= { lcsStatusTcpIpRadiuss 10 }

-- {ENTRY} 310.1.9.12.10.1
lcsStatusTcpIpRadiussLogTableEntry OBJECT-TYPE
    SYNTAX     LcsStatusTcpIpRadiussLogTableEntry
    MAX-ACCESS not-accessible
    STATUS     current
    DESCRIPTION
        ""
    INDEX {
        lcsStatusTcpIpRadiussLogTableEntryIndex
    }
    ::= { lcsStatusTcpIpRadiussLogTableTable 1 }

-- {SEQUENCE}
LcsStatusTcpIpRadiussLogTableEntry ::= SEQUENCE {
    lcsStatusTcpIpRadiussLogTableEntryIndex INTEGER,
    lcsStatusTcpIpRadiussLogTableEntryTime DisplayString,
    lcsStatusTcpIpRadiussLogTableEntryEvent DisplayString
}

-- {COLUMN} 310.1.9.12.10.1.1
lcsStatusTcpIpRadiussLogTableEntryIndex OBJECT-TYPE
    SYNTAX     INTEGER (0..2147483647)
    MAX-ACCESS read-only
    STATUS     current
    DESCRIPTION
        "-- empty --"
    ::= { lcsStatusTcpIpRadiussLogTableEntry 1 }

-- {COLUMN} 310.1.9.12.10.1.2
lcsStatusTcpIpRadiussLogTableEntryTime OBJECT-TYPE
    SYNTAX     DisplayString (SIZE(0..21))
    MAX-ACCESS read-only
    STATUS     current
    DESCRIPTION
        "-- empty --"
    ::= { lcsStatusTcpIpRadiussLogTableEntry 2 }

-- {COLUMN} 310.1.9.12.10.1.3
lcsStatusTcpIpRadiussLogTableEntryEvent OBJECT-TYPE
    SYNTAX     DisplayString (SIZE(0..128))
    MAX-ACCESS read-only
    STATUS     current
    DESCRIPTION
        "-- empty --"
    ::= { lcsStatusTcpIpRadiussLogTableEntry 3 }

-- {SCALAR} 310.1.9.12.100
lcsStatusTcpIpRadiussDeleteValues OBJECT-TYPE
    SYNTAX     DisplayString
    MAX-ACCESS read-write
    STATUS     current
    DESCRIPTION
        "-- empty --"
    ::= { lcsStatusTcpIpRadiuss 100 }

-- {OID} 310.1.10
lcsStatusIpRouter OBJECT IDENTIFIER ::= { lcsStatus 10 }

-- {SCALAR} 310.1.10.1
lcsStatusIpRouterLanRx OBJECT-TYPE
    SYNTAX     Counter32
    MAX-ACCESS read-only
    STATUS     current
    DESCRIPTION
        "-- empty --"
    ::= { lcsStatusIpRouter 1 }

-- {SCALAR} 310.1.10.2
lcsStatusIpRouterLanTx OBJECT-TYPE
    SYNTAX     Counter32
    MAX-ACCESS read-only
    STATUS     current
    DESCRIPTION
        "-- empty --"
    ::= { lcsStatusIpRouter 2 }

-- {SCALAR} 310.1.10.3
lcsStatusIpRouterLanLocalRoutings OBJECT-TYPE
    SYNTAX     Counter32
    MAX-ACCESS read-only
    STATUS     current
    DESCRIPTION
        "-- empty --"
    ::= { lcsStatusIpRouter 3 }

-- {SCALAR} 310.1.10.4
lcsStatusIpRouterLanNetworkErrors OBJECT-TYPE
    SYNTAX     Counter32
    MAX-ACCESS read-only
    STATUS     current
    DESCRIPTION
        "-- empty --"
    ::= { lcsStatusIpRouter 4 }

-- {SCALAR} 310.1.10.5
lcsStatusIpRouterLanRoutingErrors OBJECT-TYPE
    SYNTAX     Counter32
    MAX-ACCESS read-only
    STATUS     current
    DESCRIPTION
        "-- empty --"
    ::= { lcsStatusIpRouter 5 }

-- {SCALAR} 310.1.10.6
lcsStatusIpRouterLanTtlErrors OBJECT-TYPE
    SYNTAX     Counter32
    MAX-ACCESS read-only
    STATUS     current
    DESCRIPTION
        "-- empty --"
    ::= { lcsStatusIpRouter 6 }

-- {SCALAR} 310.1.10.7
lcsStatusIpRouterLanFilters OBJECT-TYPE
    SYNTAX     Counter32
    MAX-ACCESS read-only
    STATUS     current
    DESCRIPTION
        "-- empty --"
    ::= { lcsStatusIpRouter 7 }

-- {SCALAR} 310.1.10.8
lcsStatusIpRouterLanDiscards OBJECT-TYPE
    SYNTAX     Counter32
    MAX-ACCESS read-only
    STATUS     current
    DESCRIPTION
        "-- empty --"
    ::= { lcsStatusIpRouter 8 }

-- {SCALAR} 310.1.10.9
lcsStatusIpRouterWanRx OBJECT-TYPE
    SYNTAX     Counter32
    MAX-ACCESS read-only
    STATUS     current
    DESCRIPTION
        "-- empty --"
    ::= { lcsStatusIpRouter 9 }

-- {SCALAR} 310.1.10.10
lcsStatusIpRouterWanTx OBJECT-TYPE
    SYNTAX     Counter32
    MAX-ACCESS read-only
    STATUS     current
    DESCRIPTION
        "-- empty --"
    ::= { lcsStatusIpRouter 10 }

-- {SCALAR} 310.1.10.11
lcsStatusIpRouterWanNetworkErrors OBJECT-TYPE
    SYNTAX     Counter32
    MAX-ACCESS read-only
    STATUS     current
    DESCRIPTION
        "-- empty --"
    ::= { lcsStatusIpRouter 11 }

-- {SCALAR} 310.1.10.12
lcsStatusIpRouterWanTtlErrors OBJECT-TYPE
    SYNTAX     Counter32
    MAX-ACCESS read-only
    STATUS     current
    DESCRIPTION
        "-- empty --"
    ::= { lcsStatusIpRouter 12 }

-- {SCALAR} 310.1.10.13
lcsStatusIpRouterWanFilters OBJECT-TYPE
    SYNTAX     Counter32
    MAX-ACCESS read-only
    STATUS     current
    DESCRIPTION
        "-- empty --"
    ::= { lcsStatusIpRouter 13 }

-- {SCALAR} 310.1.10.14
lcsStatusIpRouterWanDiscards OBJECT-TYPE
    SYNTAX     Counter32
    MAX-ACCESS read-only
    STATUS     current
    DESCRIPTION
        "-- empty --"
    ::= { lcsStatusIpRouter 14 }

-- {SCALAR} 310.1.10.15
lcsStatusIpRouterWanTypeErrors OBJECT-TYPE
    SYNTAX     Counter32
    MAX-ACCESS read-only
    STATUS     current
    DESCRIPTION
        "-- empty --"
    ::= { lcsStatusIpRouter 15 }

-- {SCALAR} 310.1.10.16
lcsStatusIpRouterArpErrors OBJECT-TYPE
    SYNTAX     Counter32
    MAX-ACCESS read-only
    STATUS     current
    DESCRIPTION
        "-- empty --"
    ::= { lcsStatusIpRouter 16 }

-- {TABLE} 310.1.10.17
lcsStatusIpRouterEstablishTableTable OBJECT-TYPE
    SYNTAX     SEQUENCE OF LcsStatusIpRouterEstablishTableEntry
    MAX-ACCESS not-accessible
    STATUS     current
    DESCRIPTION
        "-- empty --"
    ::= { lcsStatusIpRouter 17 }

-- {ENTRY} 310.1.10.17.1
lcsStatusIpRouterEstablishTableEntry OBJECT-TYPE
    SYNTAX     LcsStatusIpRouterEstablishTableEntry
    MAX-ACCESS not-accessible
    STATUS     current
    DESCRIPTION
        ""
    INDEX {
        lcsStatusIpRouterEstablishTableEntryTime,
        lcsStatusIpRouterEstablishTableEntryCounter
    }
    ::= { lcsStatusIpRouterEstablishTableTable 1 }

-- {SEQUENCE}
LcsStatusIpRouterEstablishTableEntry ::= SEQUENCE {
    lcsStatusIpRouterEstablishTableEntryTime DisplayString,
    lcsStatusIpRouterEstablishTableEntryDestAddress IpAddress,
    lcsStatusIpRouterEstablishTableEntrySrcAddress IpAddress,
    lcsStatusIpRouterEstablishTableEntryProt INTEGER,
    lcsStatusIpRouterEstablishTableEntryDPortFrom INTEGER,
    lcsStatusIpRouterEstablishTableEntrySourcePort INTEGER,
    lcsStatusIpRouterEstablishTableEntryCounter INTEGER
}

-- {COLUMN} 310.1.10.17.1.1
lcsStatusIpRouterEstablishTableEntryTime OBJECT-TYPE
    SYNTAX     DisplayString (SIZE(0..19))
    MAX-ACCESS read-only
    STATUS     current
    DESCRIPTION
        "-- empty --"
    ::= { lcsStatusIpRouterEstablishTableEntry 1 }

-- {COLUMN} 310.1.10.17.1.2
lcsStatusIpRouterEstablishTableEntryDestAddress OBJECT-TYPE
    SYNTAX     IpAddress
    MAX-ACCESS read-only
    STATUS     current
    DESCRIPTION
        "-- empty --"
    ::= { lcsStatusIpRouterEstablishTableEntry 2 }

-- {COLUMN} 310.1.10.17.1.3
lcsStatusIpRouterEstablishTableEntrySrcAddress OBJECT-TYPE
    SYNTAX     IpAddress
    MAX-ACCESS read-only
    STATUS     current
    DESCRIPTION
        "-- empty --"
    ::= { lcsStatusIpRouterEstablishTableEntry 3 }

-- {COLUMN} 310.1.10.17.1.4
lcsStatusIpRouterEstablishTableEntryProt OBJECT-TYPE
    SYNTAX     INTEGER
      {
        eIcmp (1),
        eIgmp (2),
        eGgt (3),
        eIpip (4),
        eTcp (6),
        eEgp (8),
        eUdp (17),
        eGre (47),
        eEsp (50),
        eAh (51),
        eCftp (62),
        eIpcomp (108),
        eVrrp (112),
        eSrp (119)
      }
    MAX-ACCESS read-only
    STATUS     current
    DESCRIPTION
        "-- empty --"
    ::= { lcsStatusIpRouterEstablishTableEntry 4 }

-- {COLUMN} 310.1.10.17.1.5
lcsStatusIpRouterEstablishTableEntryDPortFrom OBJECT-TYPE
    SYNTAX     INTEGER (0..65535)
    MAX-ACCESS read-only
    STATUS     current
    DESCRIPTION
        "-- empty --"
    ::= { lcsStatusIpRouterEstablishTableEntry 5 }

-- {COLUMN} 310.1.10.17.1.6
lcsStatusIpRouterEstablishTableEntrySourcePort OBJECT-TYPE
    SYNTAX     INTEGER (0..65535)
    MAX-ACCESS read-only
    STATUS     current
    DESCRIPTION
        "-- empty --"
    ::= { lcsStatusIpRouterEstablishTableEntry 6 }

-- {COLUMN} 310.1.10.17.1.7
lcsStatusIpRouterEstablishTableEntryCounter OBJECT-TYPE
    SYNTAX     INTEGER (0..2147483647)
    MAX-ACCESS read-only
    STATUS     current
    DESCRIPTION
        "-- empty --"
    ::= { lcsStatusIpRouterEstablishTableEntry 7 }

-- {TABLE} 310.1.10.18
lcsStatusIpRouterProtocolTableTable OBJECT-TYPE
    SYNTAX     SEQUENCE OF LcsStatusIpRouterProtocolTableEntry
    MAX-ACCESS not-accessible
    STATUS     current
    DESCRIPTION
        "-- empty --"
    ::= { lcsStatusIpRouter 18 }

-- {ENTRY} 310.1.10.18.1
lcsStatusIpRouterProtocolTableEntry OBJECT-TYPE
    SYNTAX     LcsStatusIpRouterProtocolTableEntry
    MAX-ACCESS not-accessible
    STATUS     current
    DESCRIPTION
        ""
    INDEX {
        lcsStatusIpRouterProtocolTableEntryProt
    }
    ::= { lcsStatusIpRouterProtocolTableTable 1 }

-- {SEQUENCE}
LcsStatusIpRouterProtocolTableEntry ::= SEQUENCE {
    lcsStatusIpRouterProtocolTableEntryProt INTEGER,
    lcsStatusIpRouterProtocolTableEntryLanTx Counter32,
    lcsStatusIpRouterProtocolTableEntryWanTx Counter32
}

-- {COLUMN} 310.1.10.18.1.1
lcsStatusIpRouterProtocolTableEntryProt OBJECT-TYPE
    SYNTAX     INTEGER
      {
        eIcmp (1),
        eIgmp (2),
        eGgt (3),
        eIpip (4),
        eTcp (6),
        eEgp (8),
        eUdp (17),
        eGre (47),
        eEsp (50),
        eAh (51),
        eCftp (62),
        eIpcomp (108),
        eVrrp (112),
        eSrp (119)
      }
    MAX-ACCESS read-only
    STATUS     current
    DESCRIPTION
        "-- empty --"
    ::= { lcsStatusIpRouterProtocolTableEntry 1 }

-- {COLUMN} 310.1.10.18.1.2
lcsStatusIpRouterProtocolTableEntryLanTx OBJECT-TYPE
    SYNTAX     Counter32
    MAX-ACCESS read-only
    STATUS     current
    DESCRIPTION
        "-- empty --"
    ::= { lcsStatusIpRouterProtocolTableEntry 2 }

-- {COLUMN} 310.1.10.18.1.3
lcsStatusIpRouterProtocolTableEntryWanTx OBJECT-TYPE
    SYNTAX     Counter32
    MAX-ACCESS read-only
    STATUS     current
    DESCRIPTION
        "-- empty --"
    ::= { lcsStatusIpRouterProtocolTableEntry 3 }

-- {OID} 310.1.10.19
lcsStatusIpRouterRip OBJECT IDENTIFIER ::= { lcsStatusIpRouter 19 }

-- {SCALAR} 310.1.10.19.1
lcsStatusIpRouterRipRx OBJECT-TYPE
    SYNTAX     Counter32
    MAX-ACCESS read-only
    STATUS     current
    DESCRIPTION
        "-- empty --"
    ::= { lcsStatusIpRouterRip 1 }

-- {SCALAR} 310.1.10.19.2
lcsStatusIpRouterRipRequests OBJECT-TYPE
    SYNTAX     Counter32
    MAX-ACCESS read-only
    STATUS     current
    DESCRIPTION
        "-- empty --"
    ::= { lcsStatusIpRouterRip 2 }

-- {SCALAR} 310.1.10.19.3
lcsStatusIpRouterRipResponse OBJECT-TYPE
    SYNTAX     Counter32
    MAX-ACCESS read-only
    STATUS     current
    DESCRIPTION
        "-- empty --"
    ::= { lcsStatusIpRouterRip 3 }

-- {SCALAR} 310.1.10.19.4
lcsStatusIpRouterRipDiscards OBJECT-TYPE
    SYNTAX     Counter32
    MAX-ACCESS read-only
    STATUS     current
    DESCRIPTION
        "-- empty --"
    ::= { lcsStatusIpRouterRip 4 }

-- {SCALAR} 310.1.10.19.5
lcsStatusIpRouterRipErrors OBJECT-TYPE
    SYNTAX     Counter32
    MAX-ACCESS read-only
    STATUS     current
    DESCRIPTION
        "-- empty --"
    ::= { lcsStatusIpRouterRip 5 }

-- {SCALAR} 310.1.10.19.6
lcsStatusIpRouterRipEntryErrors OBJECT-TYPE
    SYNTAX     Counter32
    MAX-ACCESS read-only
    STATUS     current
    DESCRIPTION
        "-- empty --"
    ::= { lcsStatusIpRouterRip 6 }

-- {SCALAR} 310.1.10.19.7
lcsStatusIpRouterRipTx OBJECT-TYPE
    SYNTAX     Counter32
    MAX-ACCESS read-only
    STATUS     current
    DESCRIPTION
        "-- empty --"
    ::= { lcsStatusIpRouterRip 7 }

-- {TABLE} 310.1.10.19.8
lcsStatusIpRouterRipBestRoutesTable OBJECT-TYPE
    SYNTAX     SEQUENCE OF LcsStatusIpRouterRipBestRoutesEntry
    MAX-ACCESS not-accessible
    STATUS     current
    DESCRIPTION
        "-- empty --"
    ::= { lcsStatusIpRouterRip 8 }

-- {ENTRY} 310.1.10.19.8.1
lcsStatusIpRouterRipBestRoutesEntry OBJECT-TYPE
    SYNTAX     LcsStatusIpRouterRipBestRoutesEntry
    MAX-ACCESS not-accessible
    STATUS     current
    DESCRIPTION
        ""
    INDEX {
        lcsStatusIpRouterRipBestRoutesEntryIpAddress,
        lcsStatusIpRouterRipBestRoutesEntryIpNetmask,
        lcsStatusIpRouterRipBestRoutesEntryRtgTag,
        lcsStatusIpRouterRipBestRoutesEntryGateway
    }
    ::= { lcsStatusIpRouterRipBestRoutesTable 1 }

-- {SEQUENCE}
LcsStatusIpRouterRipBestRoutesEntry ::= SEQUENCE {
    lcsStatusIpRouterRipBestRoutesEntryIpAddress IpAddress,
    lcsStatusIpRouterRipBestRoutesEntryIpNetmask IpAddress,
    lcsStatusIpRouterRipBestRoutesEntryRtgTag INTEGER,
    lcsStatusIpRouterRipBestRoutesEntryGateway IpAddress,
    lcsStatusIpRouterRipBestRoutesEntryDistance INTEGER,
    lcsStatusIpRouterRipBestRoutesEntryTime INTEGER,
    lcsStatusIpRouterRipBestRoutesEntryPeer DisplayString,
    lcsStatusIpRouterRipBestRoutesEntryPort INTEGER,
    lcsStatusIpRouterRipBestRoutesEntryVlanId INTEGER,
    lcsStatusIpRouterRipBestRoutesEntryNetworkName DisplayString
}

-- {COLUMN} 310.1.10.19.8.1.1
lcsStatusIpRouterRipBestRoutesEntryIpAddress OBJECT-TYPE
    SYNTAX     IpAddress
    MAX-ACCESS read-only
    STATUS     current
    DESCRIPTION
        "-- empty --"
    ::= { lcsStatusIpRouterRipBestRoutesEntry 1 }

-- {COLUMN} 310.1.10.19.8.1.2
lcsStatusIpRouterRipBestRoutesEntryIpNetmask OBJECT-TYPE
    SYNTAX     IpAddress
    MAX-ACCESS read-only
    STATUS     current
    DESCRIPTION
        "-- empty --"
    ::= { lcsStatusIpRouterRipBestRoutesEntry 2 }

-- {COLUMN} 310.1.10.19.8.1.6
lcsStatusIpRouterRipBestRoutesEntryRtgTag OBJECT-TYPE
    SYNTAX     INTEGER (0..65535)
    MAX-ACCESS read-only
    STATUS     current
    DESCRIPTION
        "-- empty --"
    ::= { lcsStatusIpRouterRipBestRoutesEntry 6 }

-- {COLUMN} 310.1.10.19.8.1.5
lcsStatusIpRouterRipBestRoutesEntryGateway OBJECT-TYPE
    SYNTAX     IpAddress
    MAX-ACCESS read-only
    STATUS     current
    DESCRIPTION
        "-- empty --"
    ::= { lcsStatusIpRouterRipBestRoutesEntry 5 }

-- {COLUMN} 310.1.10.19.8.1.4
lcsStatusIpRouterRipBestRoutesEntryDistance OBJECT-TYPE
    SYNTAX     INTEGER (0..65535)
    MAX-ACCESS read-only
    STATUS     current
    DESCRIPTION
        "-- empty --"
    ::= { lcsStatusIpRouterRipBestRoutesEntry 4 }

-- {COLUMN} 310.1.10.19.8.1.3
lcsStatusIpRouterRipBestRoutesEntryTime OBJECT-TYPE
    SYNTAX     INTEGER (0..65535)
    MAX-ACCESS read-only
    STATUS     current
    DESCRIPTION
        "-- empty --"
    ::= { lcsStatusIpRouterRipBestRoutesEntry 3 }

-- {COLUMN} 310.1.10.19.8.1.8
lcsStatusIpRouterRipBestRoutesEntryPeer OBJECT-TYPE
    SYNTAX     DisplayString (SIZE(0..255))
    MAX-ACCESS read-only
    STATUS     current
    DESCRIPTION
        "-- empty --"
    ::= { lcsStatusIpRouterRipBestRoutesEntry 8 }

-- {COLUMN} 310.1.10.19.8.1.12
lcsStatusIpRouterRipBestRoutesEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusIpRouterRipBestRoutesEntry 12 }

-- {COLUMN} 310.1.10.19.8.1.10
lcsStatusIpRouterRipBestRoutesEntryVlanId OBJECT-TYPE
    SYNTAX     INTEGER (0..65535)
    MAX-ACCESS read-only
    STATUS     current
    DESCRIPTION
        "-- empty --"
    ::= { lcsStatusIpRouterRipBestRoutesEntry 10 }

-- {COLUMN} 310.1.10.19.8.1.11
lcsStatusIpRouterRipBestRoutesEntryNetworkName OBJECT-TYPE
    SYNTAX     DisplayString (SIZE(0..255))
    MAX-ACCESS read-only
    STATUS     current
    DESCRIPTION
        "-- empty --"
    ::= { lcsStatusIpRouterRipBestRoutesEntry 11 }

-- {TABLE} 310.1.10.19.20
lcsStatusIpRouterRipAllRoutesTable OBJECT-TYPE
    SYNTAX     SEQUENCE OF LcsStatusIpRouterRipAllRoutesEntry
    MAX-ACCESS not-accessible
    STATUS     current
    DESCRIPTION
        "-- empty --"
    ::= { lcsStatusIpRouterRip 20 }

-- {ENTRY} 310.1.10.19.20.1
lcsStatusIpRouterRipAllRoutesEntry OBJECT-TYPE
    SYNTAX     LcsStatusIpRouterRipAllRoutesEntry
    MAX-ACCESS not-accessible
    STATUS     current
    DESCRIPTION
        ""
    INDEX {
        lcsStatusIpRouterRipAllRoutesEntryIpAddress,
        lcsStatusIpRouterRipAllRoutesEntryIpNetmask,
        lcsStatusIpRouterRipAllRoutesEntryRtgTag,
        lcsStatusIpRouterRipAllRoutesEntryGateway
    }
    ::= { lcsStatusIpRouterRipAllRoutesTable 1 }

-- {SEQUENCE}
LcsStatusIpRouterRipAllRoutesEntry ::= SEQUENCE {
    lcsStatusIpRouterRipAllRoutesEntryIpAddress IpAddress,
    lcsStatusIpRouterRipAllRoutesEntryIpNetmask IpAddress,
    lcsStatusIpRouterRipAllRoutesEntryRtgTag INTEGER,
    lcsStatusIpRouterRipAllRoutesEntryGateway IpAddress,
    lcsStatusIpRouterRipAllRoutesEntryDistance INTEGER,
    lcsStatusIpRouterRipAllRoutesEntryTime INTEGER,
    lcsStatusIpRouterRipAllRoutesEntryPeer DisplayString,
    lcsStatusIpRouterRipAllRoutesEntryPort INTEGER,
    lcsStatusIpRouterRipAllRoutesEntryVlanId INTEGER,
    lcsStatusIpRouterRipAllRoutesEntryNetworkName DisplayString
}

-- {COLUMN} 310.1.10.19.20.1.1
lcsStatusIpRouterRipAllRoutesEntryIpAddress OBJECT-TYPE
    SYNTAX     IpAddress
    MAX-ACCESS read-only
    STATUS     current
    DESCRIPTION
        "-- empty --"
    ::= { lcsStatusIpRouterRipAllRoutesEntry 1 }

-- {COLUMN} 310.1.10.19.20.1.2
lcsStatusIpRouterRipAllRoutesEntryIpNetmask OBJECT-TYPE
    SYNTAX     IpAddress
    MAX-ACCESS read-only
    STATUS     current
    DESCRIPTION
        "-- empty --"
    ::= { lcsStatusIpRouterRipAllRoutesEntry 2 }

-- {COLUMN} 310.1.10.19.20.1.6
lcsStatusIpRouterRipAllRoutesEntryRtgTag OBJECT-TYPE
    SYNTAX     INTEGER (0..65535)
    MAX-ACCESS read-only
    STATUS     current
    DESCRIPTION
        "-- empty --"
    ::= { lcsStatusIpRouterRipAllRoutesEntry 6 }

-- {COLUMN} 310.1.10.19.20.1.5
lcsStatusIpRouterRipAllRoutesEntryGateway OBJECT-TYPE
    SYNTAX     IpAddress
    MAX-ACCESS read-only
    STATUS     current
    DESCRIPTION
        "-- empty --"
    ::= { lcsStatusIpRouterRipAllRoutesEntry 5 }

-- {COLUMN} 310.1.10.19.20.1.4
lcsStatusIpRouterRipAllRoutesEntryDistance OBJECT-TYPE
    SYNTAX     INTEGER (0..65535)
    MAX-ACCESS read-only
    STATUS     current
    DESCRIPTION
        "-- empty --"
    ::= { lcsStatusIpRouterRipAllRoutesEntry 4 }

-- {COLUMN} 310.1.10.19.20.1.3
lcsStatusIpRouterRipAllRoutesEntryTime OBJECT-TYPE
    SYNTAX     INTEGER (0..65535)
    MAX-ACCESS read-only
    STATUS     current
    DESCRIPTION
        "-- empty --"
    ::= { lcsStatusIpRouterRipAllRoutesEntry 3 }

-- {COLUMN} 310.1.10.19.20.1.8
lcsStatusIpRouterRipAllRoutesEntryPeer OBJECT-TYPE
    SYNTAX     DisplayString (SIZE(0..255))
    MAX-ACCESS read-only
    STATUS     current
    DESCRIPTION
        "-- empty --"
    ::= { lcsStatusIpRouterRipAllRoutesEntry 8 }

-- {COLUMN} 310.1.10.19.20.1.12
lcsStatusIpRouterRipAllRoutesEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusIpRouterRipAllRoutesEntry 12 }

-- {COLUMN} 310.1.10.19.20.1.10
lcsStatusIpRouterRipAllRoutesEntryVlanId OBJECT-TYPE
    SYNTAX     INTEGER (0..65535)
    MAX-ACCESS read-only
    STATUS     current
    DESCRIPTION
        "-- empty --"
    ::= { lcsStatusIpRouterRipAllRoutesEntry 10 }

-- {COLUMN} 310.1.10.19.20.1.11
lcsStatusIpRouterRipAllRoutesEntryNetworkName OBJECT-TYPE
    SYNTAX     DisplayString (SIZE(0..255))
    MAX-ACCESS read-only
    STATUS     current
    DESCRIPTION
        "-- empty --"
    ::= { lcsStatusIpRouterRipAllRoutesEntry 11 }

-- {SCALAR} 310.1.10.19.9
lcsStatusIpRouterRipDeleteValues OBJECT-TYPE
    SYNTAX     DisplayString
    MAX-ACCESS read-write
    STATUS     current
    DESCRIPTION
        "-- empty --"
    ::= { lcsStatusIpRouterRip 9 }

-- {TABLE} 310.1.10.19.10
lcsStatusIpRouterRipLanSitesTable OBJECT-TYPE
    SYNTAX     SEQUENCE OF LcsStatusIpRouterRipLanSitesEntry
    MAX-ACCESS not-accessible
    STATUS     current
    DESCRIPTION
        "-- empty --"
    ::= { lcsStatusIpRouterRip 10 }

-- {ENTRY} 310.1.10.19.10.1
lcsStatusIpRouterRipLanSitesEntry OBJECT-TYPE
    SYNTAX     LcsStatusIpRouterRipLanSitesEntry
    MAX-ACCESS not-accessible
    STATUS     current
    DESCRIPTION
        ""
    INDEX {
        lcsStatusIpRouterRipLanSitesEntryNetworkName
    }
    ::= { lcsStatusIpRouterRipLanSitesTable 1 }

-- {SEQUENCE}
LcsStatusIpRouterRipLanSitesEntry ::= SEQUENCE {
    lcsStatusIpRouterRipLanSitesEntryNetworkName DisplayString,
    lcsStatusIpRouterRipLanSitesEntryRipType INTEGER,
    lcsStatusIpRouterRipLanSitesEntryRipSend INTEGER,
    lcsStatusIpRouterRipLanSitesEntryRipAccept INTEGER,
    lcsStatusIpRouterRipLanSitesEntryPropagate INTEGER,
    lcsStatusIpRouterRipLanSitesEntryPoisonedReverse INTEGER,
    lcsStatusIpRouterRipLanSitesEntryDftRtgTag INTEGER,
    lcsStatusIpRouterRipLanSitesEntryRtgTagList DisplayString,
    lcsStatusIpRouterRipLanSitesEntryRxFilter DisplayString,
    lcsStatusIpRouterRipLanSitesEntryTxFilter DisplayString,
    lcsStatusIpRouterRipLanSitesEntryPort INTEGER,
    lcsStatusIpRouterRipLanSitesEntryVlanId INTEGER
}

-- {COLUMN} 310.1.10.19.10.1.1
lcsStatusIpRouterRipLanSitesEntryNetworkName OBJECT-TYPE
    SYNTAX     DisplayString (SIZE(0..16))
    MAX-ACCESS read-only
    STATUS     current
    DESCRIPTION
        "-- empty --"
    ::= { lcsStatusIpRouterRipLanSitesEntry 1 }

-- {COLUMN} 310.1.10.19.10.1.2
lcsStatusIpRouterRipLanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipLanSitesEntry 2 }

-- {COLUMN} 310.1.10.19.10.1.12
lcsStatusIpRouterRipLanSitesEntryRipSend OBJECT-TYPE
    SYNTAX     INTEGER
      {
        eNo (0),
        eYes (1)
      }
    MAX-ACCESS read-only
    STATUS     current
    DESCRIPTION
        "-- empty --"
    ::= { lcsStatusIpRouterRipLanSitesEntry 12 }

-- {COLUMN} 310.1.10.19.10.1.3
lcsStatusIpRouterRipLanSitesEntryRipAccept OBJECT-TYPE
    SYNTAX     INTEGER
      {
        eNo (0),
        eYes (1)
      }
    MAX-ACCESS read-only
    STATUS     current
    DESCRIPTION
        "-- empty --"
    ::= { lcsStatusIpRouterRipLanSitesEntry 3 }

-- {COLUMN} 310.1.10.19.10.1.4
lcsStatusIpRouterRipLanSitesEntryPropagate OBJECT-TYPE
    SYNTAX     INTEGER
      {
        eNo (0),
        eYes (1)
      }
    MAX-ACCESS read-only
    STATUS     current
    DESCRIPTION
        "-- empty --"
    ::= { lcsStatusIpRouterRipLanSitesEntry 4 }

-- {COLUMN} 310.1.10.19.10.1.9
lcsStatusIpRouterRipLanSitesEntryPoisonedReverse OBJECT-TYPE
    SYNTAX     INTEGER
      {
        eNo (0),
        eYes (1)
      }
    MAX-ACCESS read-only
    STATUS     current
    DESCRIPTION
        "-- empty --"
    ::= { lcsStatusIpRouterRipLanSitesEntry 9 }

-- {COLUMN} 310.1.10.19.10.1.5
lcsStatusIpRouterRipLanSitesEntryDftRtgTag OBJECT-TYPE
    SYNTAX     INTEGER (0..65535)
    MAX-ACCESS read-only
    STATUS     current
    DESCRIPTION
        "-- empty --"
    ::= { lcsStatusIpRouterRipLanSitesEntry 5 }

-- {COLUMN} 310.1.10.19.10.1.6
lcsStatusIpRouterRipLanSitesEntryRtgTagList OBJECT-TYPE
    SYNTAX     DisplayString (SIZE(0..33))
    MAX-ACCESS read-only
    STATUS     current
    DESCRIPTION
        "-- empty --"
    ::= { lcsStatusIpRouterRipLanSitesEntry 6 }

-- {COLUMN} 310.1.10.19.10.1.10
lcsStatusIpRouterRipLanSitesEntryRxFilter OBJECT-TYPE
    SYNTAX     DisplayString (SIZE(0..16))
    MAX-ACCESS read-only
    STATUS     current
    DESCRIPTION
        "-- empty --"
    ::= { lcsStatusIpRouterRipLanSitesEntry 10 }

-- {COLUMN} 310.1.10.19.10.1.11
lcsStatusIpRouterRipLanSitesEntryTxFilter OBJECT-TYPE
    SYNTAX     DisplayString (SIZE(0..16))
    MAX-ACCESS read-only
    STATUS     current
    DESCRIPTION
        "-- empty --"
    ::= { lcsStatusIpRouterRipLanSitesEntry 11 }

-- {COLUMN} 310.1.10.19.10.1.31
lcsStatusIpRouterRipLanSitesEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusIpRouterRipLanSitesEntry 31 }

-- {COLUMN} 310.1.10.19.10.1.8
lcsStatusIpRouterRipLanSitesEntryVlanId OBJECT-TYPE
    SYNTAX     INTEGER (0..65535)
    MAX-ACCESS read-only
    STATUS     current
    DESCRIPTION
        "-- empty --"
    ::= { lcsStatusIpRouterRipLanSitesEntry 8 }

-- {TABLE} 310.1.10.19.12
lcsStatusIpRouterRipVrrpSitesTable OBJECT-TYPE
    SYNTAX     SEQUENCE OF LcsStatusIpRouterRipVrrpSitesEntry
    MAX-ACCESS not-accessible
    STATUS     current
    DESCRIPTION
        "-- empty --"
    ::= { lcsStatusIpRouterRip 12 }

-- {ENTRY} 310.1.10.19.12.1
lcsStatusIpRouterRipVrrpSitesEntry OBJECT-TYPE
    SYNTAX     LcsStatusIpRouterRipVrrpSitesEntry
    MAX-ACCESS not-accessible
    STATUS     current
    DESCRIPTION
        ""
    INDEX {
        lcsStatusIpRouterRipVrrpSitesEntryNetworkName,
        lcsStatusIpRouterRipVrrpSitesEntryRouterId
    }
    ::= { lcsStatusIpRouterRipVrrpSitesTable 1 }

-- {SEQUENCE}
LcsStatusIpRouterRipVrrpSitesEntry ::= SEQUENCE {
    lcsStatusIpRouterRipVrrpSitesEntryNetworkName DisplayString,
    lcsStatusIpRouterRipVrrpSitesEntryRipType INTEGER,
    lcsStatusIpRouterRipVrrpSitesEntryRouterId INTEGER
}

-- {COLUMN} 310.1.10.19.12.1.1
lcsStatusIpRouterRipVrrpSitesEntryNetworkName OBJECT-TYPE
    SYNTAX     DisplayString (SIZE(0..16))
    MAX-ACCESS read-only
    STATUS     current
    DESCRIPTION
        "-- empty --"
    ::= { lcsStatusIpRouterRipVrrpSitesEntry 1 }

-- {COLUMN} 310.1.10.19.12.1.2
lcsStatusIpRouterRipVrrpSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipVrrpSitesEntry 2 }

-- {COLUMN} 310.1.10.19.12.1.3
lcsStatusIpRouterRipVrrpSitesEntryRouterId OBJECT-TYPE
    SYNTAX     INTEGER (0..255)
    MAX-ACCESS read-only
    STATUS     current
    DESCRIPTION
        "-- empty --"
    ::= { lcsStatusIpRouterRipVrrpSitesEntry 3 }

-- {TABLE} 310.1.10.19.11
lcsStatusIpRouterRipWanSitesTable OBJECT-TYPE
    SYNTAX     SEQUENCE OF LcsStatusIpRouterRipWanSitesEntry
    MAX-ACCESS not-accessible
    STATUS     current
    DESCRIPTION
        "-- empty --"
    ::= { lcsStatusIpRouterRip 11 }

-- {ENTRY} 310.1.10.19.11.1
lcsStatusIpRouterRipWanSitesEntry OBJECT-TYPE
    SYNTAX     LcsStatusIpRouterRipWanSitesEntry
    MAX-ACCESS not-accessible
    STATUS     current
    DESCRIPTION
        ""
    INDEX {
        lcsStatusIpRouterRipWanSitesEntryPeer
    }
    ::= { lcsStatusIpRouterRipWanSitesTable 1 }

-- {SEQUENCE}
LcsStatusIpRouterRipWanSitesEntry ::= SEQUENCE {
    lcsStatusIpRouterRipWanSitesEntryPeer DisplayString,
    lcsStatusIpRouterRipWanSitesEntryRipType INTEGER,
    lcsStatusIpRouterRipWanSitesEntryRipSend INTEGER,
    lcsStatusIpRouterRipWanSitesEntryRipAccept INTEGER,
    lcsStatusIpRouterRipWanSitesEntryMasquerade INTEGER,
    lcsStatusIpRouterRipWanSitesEntryPoisonedReverse INTEGER,
    lcsStatusIpRouterRipWanSitesEntryRfc2091 INTEGER,
    lcsStatusIpRouterRipWanSitesEntryGateway IpAddress,
    lcsStatusIpRouterRipWanSitesEntryDftRtgTag INTEGER,
    lcsStatusIpRouterRipWanSitesEntryRtgTagList DisplayString,
    lcsStatusIpRouterRipWanSitesEntryRxFilter DisplayString,
    lcsStatusIpRouterRipWanSitesEntryTxFilter DisplayString
}

-- {COLUMN} 310.1.10.19.11.1.1
lcsStatusIpRouterRipWanSitesEntryPeer OBJECT-TYPE
    SYNTAX     DisplayString (SIZE(0..16))
    MAX-ACCESS read-only
    STATUS     current
    DESCRIPTION
        "-- empty --"
    ::= { lcsStatusIpRouterRipWanSitesEntry 1 }

-- {COLUMN} 310.1.10.19.11.1.2
lcsStatusIpRouterRipWanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipWanSitesEntry 2 }

-- {COLUMN} 310.1.10.19.11.1.12
lcsStatusIpRouterRipWanSitesEntryRipSend OBJECT-TYPE
    SYNTAX     INTEGER
      {
        eNo (0),
        eYes (1)
      }
    MAX-ACCESS read-only
    STATUS     current
    DESCRIPTION
        "-- empty --"
    ::= { lcsStatusIpRouterRipWanSitesEntry 12 }

-- {COLUMN} 310.1.10.19.11.1.3
lcsStatusIpRouterRipWanSitesEntryRipAccept OBJECT-TYPE
    SYNTAX     INTEGER
      {
        eNo (0),
        eYes (1)
      }
    MAX-ACCESS read-only
    STATUS     current
    DESCRIPTION
        "-- empty --"
    ::= { lcsStatusIpRouterRipWanSitesEntry 3 }

-- {COLUMN} 310.1.10.19.11.1.4
lcsStatusIpRouterRipWanSitesEntryMasquerade OBJECT-TYPE
    SYNTAX     INTEGER
      {
        eAuto (0),
        eOn (1),
        eIntranet (2)
      }
    MAX-ACCESS read-only
    STATUS     current
    DESCRIPTION
        "-- empty --"
    ::= { lcsStatusIpRouterRipWanSitesEntry 4 }

-- {COLUMN} 310.1.10.19.11.1.7
lcsStatusIpRouterRipWanSitesEntryPoisonedReverse OBJECT-TYPE
    SYNTAX     INTEGER
      {
        eNo (0),
        eYes (1)
      }
    MAX-ACCESS read-only
    STATUS     current
    DESCRIPTION
        "-- empty --"
    ::= { lcsStatusIpRouterRipWanSitesEntry 7 }

-- {COLUMN} 310.1.10.19.11.1.8
lcsStatusIpRouterRipWanSitesEntryRfc2091 OBJECT-TYPE
    SYNTAX     INTEGER
      {
        eNo (0),
        eYes (1)
      }
    MAX-ACCESS read-only
    STATUS     current
    DESCRIPTION
        "-- empty --"
    ::= { lcsStatusIpRouterRipWanSitesEntry 8 }

-- {COLUMN} 310.1.10.19.11.1.9
lcsStatusIpRouterRipWanSitesEntryGateway OBJECT-TYPE
    SYNTAX     IpAddress
    MAX-ACCESS read-only
    STATUS     current
    DESCRIPTION
        "-- empty --"
    ::= { lcsStatusIpRouterRipWanSitesEntry 9 }

-- {COLUMN} 310.1.10.19.11.1.5
lcsStatusIpRouterRipWanSitesEntryDftRtgTag OBJECT-TYPE
    SYNTAX     INTEGER (0..65535)
    MAX-ACCESS read-only
    STATUS     current
    DESCRIPTION
        "-- empty --"
    ::= { lcsStatusIpRouterRipWanSitesEntry 5 }

-- {COLUMN} 310.1.10.19.11.1.6
lcsStatusIpRouterRipWanSitesEntryRtgTagList OBJECT-TYPE
    SYNTAX     DisplayString (SIZE(0..33))
    MAX-ACCESS read-only
    STATUS     current
    DESCRIPTION
        "-- empty --"
    ::= { lcsStatusIpRouterRipWanSitesEntry 6 }

-- {COLUMN} 310.1.10.19.11.1.10
lcsStatusIpRouterRipWanSitesEntryRxFilter OBJECT-TYPE
    SYNTAX     DisplayString (SIZE(0..16))
    MAX-ACCESS read-only
    STATUS     current
    DESCRIPTION
        "-- empty --"
    ::= { lcsStatusIpRouterRipWanSitesEntry 10 }

-- {COLUMN} 310.1.10.19.11.1.11
lcsStatusIpRouterRipWanSitesEntryTxFilter OBJECT-TYPE
    SYNTAX     DisplayString (SIZE(0..16))
    MAX-ACCESS read-only
    STATUS     current
    DESCRIPTION
        "-- empty --"
    ::= { lcsStatusIpRouterRipWanSitesEntry 11 }

-- {TABLE} 310.1.10.19.13
lcsStatusIpRouterRipDynLanSitesTable OBJECT-TYPE
    SYNTAX     SEQUENCE OF LcsStatusIpRouterRipDynLanSitesEntry
    MAX-ACCESS not-accessible
    STATUS     current
    DESCRIPTION
        "-- empty --"
    ::= { lcsStatusIpRouterRip 13 }

-- {ENTRY} 310.1.10.19.13.1
lcsStatusIpRouterRipDynLanSitesEntry OBJECT-TYPE
    SYNTAX     LcsStatusIpRouterRipDynLanSitesEntry
    MAX-ACCESS not-accessible
    STATUS     current
    DESCRIPTION
        ""
    INDEX {
        lcsStatusIpRouterRipDynLanSitesEntryGateway
    }
    ::= { lcsStatusIpRouterRipDynLanSitesTable 1 }

-- {SEQUENCE}
LcsStatusIpRouterRipDynLanSitesEntry ::= SEQUENCE {
    lcsStatusIpRouterRipDynLanSitesEntryGateway DisplayString,
    lcsStatusIpRouterRipDynLanSitesEntryRipType INTEGER,
    lcsStatusIpRouterRipDynLanSitesEntryRipSend INTEGER,
    lcsStatusIpRouterRipDynLanSitesEntryRipAccept INTEGER,
    lcsStatusIpRouterRipDynLanSitesEntryPoisonedReverse INTEGER,
    lcsStatusIpRouterRipDynLanSitesEntryDftRtgTag INTEGER,
    lcsStatusIpRouterRipDynLanSitesEntryRtgTagList DisplayString,
    lcsStatusIpRouterRipDynLanSitesEntryRxFilter DisplayString,
    lcsStatusIpRouterRipDynLanSitesEntryTxFilter DisplayString,
    lcsStatusIpRouterRipDynLanSitesEntryPort INTEGER,
    lcsStatusIpRouterRipDynLanSitesEntryVlanId INTEGER
}

-- {COLUMN} 310.1.10.19.13.1.1
lcsStatusIpRouterRipDynLanSitesEntryGateway OBJECT-TYPE
    SYNTAX     DisplayString (SIZE(0..16))
    MAX-ACCESS read-only
    STATUS     current
    DESCRIPTION
        "-- empty --"
    ::= { lcsStatusIpRouterRipDynLanSitesEntry 1 }

-- {COLUMN} 310.1.10.19.13.1.2
lcsStatusIpRouterRipDynLanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipDynLanSitesEntry 2 }

-- {COLUMN} 310.1.10.19.13.1.12
lcsStatusIpRouterRipDynLanSitesEntryRipSend OBJECT-TYPE
    SYNTAX     INTEGER
      {
        eNo (0),
        eYes (1)
      }
    MAX-ACCESS read-only
    STATUS     current
    DESCRIPTION
        "-- empty --"
    ::= { lcsStatusIpRouterRipDynLanSitesEntry 12 }

-- {COLUMN} 310.1.10.19.13.1.3
lcsStatusIpRouterRipDynLanSitesEntryRipAccept OBJECT-TYPE
    SYNTAX     INTEGER
      {
        eNo (0),
        eYes (1)
      }
    MAX-ACCESS read-only
    STATUS     current
    DESCRIPTION
        "-- empty --"
    ::= { lcsStatusIpRouterRipDynLanSitesEntry 3 }

-- {COLUMN} 310.1.10.19.13.1.4
lcsStatusIpRouterRipDynLanSitesEntryPoisonedReverse OBJECT-TYPE
    SYNTAX     INTEGER
      {
        eNo (0),
        eYes (1)
      }
    MAX-ACCESS read-only
    STATUS     current
    DESCRIPTION
        "-- empty --"
    ::= { lcsStatusIpRouterRipDynLanSitesEntry 4 }

-- {COLUMN} 310.1.10.19.13.1.5
lcsStatusIpRouterRipDynLanSitesEntryDftRtgTag OBJECT-TYPE
    SYNTAX     INTEGER (0..65535)
    MAX-ACCESS read-only
    STATUS     current
    DESCRIPTION
        "-- empty --"
    ::= { lcsStatusIpRouterRipDynLanSitesEntry 5 }

-- {COLUMN} 310.1.10.19.13.1.6
lcsStatusIpRouterRipDynLanSitesEntryRtgTagList OBJECT-TYPE
    SYNTAX     DisplayString (SIZE(0..33))
    MAX-ACCESS read-only
    STATUS     current
    DESCRIPTION
        "-- empty --"
    ::= { lcsStatusIpRouterRipDynLanSitesEntry 6 }

-- {COLUMN} 310.1.10.19.13.1.10
lcsStatusIpRouterRipDynLanSitesEntryRxFilter OBJECT-TYPE
    SYNTAX     DisplayString (SIZE(0..16))
    MAX-ACCESS read-only
    STATUS     current
    DESCRIPTION
        "-- empty --"
    ::= { lcsStatusIpRouterRipDynLanSitesEntry 10 }

-- {COLUMN} 310.1.10.19.13.1.11
lcsStatusIpRouterRipDynLanSitesEntryTxFilter OBJECT-TYPE
    SYNTAX     DisplayString (SIZE(0..16))
    MAX-ACCESS read-only
    STATUS     current
    DESCRIPTION
        "-- empty --"
    ::= { lcsStatusIpRouterRipDynLanSitesEntry 11 }

-- {COLUMN} 310.1.10.19.13.1.31
lcsStatusIpRouterRipDynLanSitesEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusIpRouterRipDynLanSitesEntry 31 }

-- {COLUMN} 310.1.10.19.13.1.8
lcsStatusIpRouterRipDynLanSitesEntryVlanId OBJECT-TYPE
    SYNTAX     INTEGER (0..65535)
    MAX-ACCESS read-only
    STATUS     current
    DESCRIPTION
        "-- empty --"
    ::= { lcsStatusIpRouterRipDynLanSitesEntry 8 }

-- {TABLE} 310.1.10.19.14
lcsStatusIpRouterRipDynWanSitesTable OBJECT-TYPE
    SYNTAX     SEQUENCE OF LcsStatusIpRouterRipDynWanSitesEntry
    MAX-ACCESS not-accessible
    STATUS     current
    DESCRIPTION
        "-- empty --"
    ::= { lcsStatusIpRouterRip 14 }

-- {ENTRY} 310.1.10.19.14.1
lcsStatusIpRouterRipDynWanSitesEntry OBJECT-TYPE
    SYNTAX     LcsStatusIpRouterRipDynWanSitesEntry
    MAX-ACCESS not-accessible
    STATUS     current
    DESCRIPTION
        ""
    INDEX {
        lcsStatusIpRouterRipDynWanSitesEntryPeer
    }
    ::= { lcsStatusIpRouterRipDynWanSitesTable 1 }

-- {SEQUENCE}
LcsStatusIpRouterRipDynWanSitesEntry ::= SEQUENCE {
    lcsStatusIpRouterRipDynWanSitesEntryPeer DisplayString,
    lcsStatusIpRouterRipDynWanSitesEntryRipType INTEGER,
    lcsStatusIpRouterRipDynWanSitesEntryRipSend INTEGER,
    lcsStatusIpRouterRipDynWanSitesEntryRipAccept INTEGER,
    lcsStatusIpRouterRipDynWanSitesEntryMasquerade INTEGER,
    lcsStatusIpRouterRipDynWanSitesEntryPoisonedReverse INTEGER,
    lcsStatusIpRouterRipDynWanSitesEntryRfc2091 INTEGER,
    lcsStatusIpRouterRipDynWanSitesEntryGateway IpAddress,
    lcsStatusIpRouterRipDynWanSitesEntryDftRtgTag INTEGER,
    lcsStatusIpRouterRipDynWanSitesEntryRtgTagList DisplayString,
    lcsStatusIpRouterRipDynWanSitesEntryRxFilter DisplayString,
    lcsStatusIpRouterRipDynWanSitesEntryTxFilter DisplayString
}

-- {COLUMN} 310.1.10.19.14.1.1
lcsStatusIpRouterRipDynWanSitesEntryPeer OBJECT-TYPE
    SYNTAX     DisplayString (SIZE(0..16))
    MAX-ACCESS read-only
    STATUS     current
    DESCRIPTION
        "-- empty --"
    ::= { lcsStatusIpRouterRipDynWanSitesEntry 1 }

-- {COLUMN} 310.1.10.19.14.1.2
lcsStatusIpRouterRipDynWanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipDynWanSitesEntry 2 }

-- {COLUMN} 310.1.10.19.14.1.12
lcsStatusIpRouterRipDynWanSitesEntryRipSend OBJECT-TYPE
    SYNTAX     INTEGER
      {
        eNo (0),
        eYes (1)
      }
    MAX-ACCESS read-only
    STATUS     current
    DESCRIPTION
        "-- empty --"
    ::= { lcsStatusIpRouterRipDynWanSitesEntry 12 }

-- {COLUMN} 310.1.10.19.14.1.3
lcsStatusIpRouterRipDynWanSitesEntryRipAccept OBJECT-TYPE
    SYNTAX     INTEGER
      {
        eNo (0),
        eYes (1)
      }
    MAX-ACCESS read-only
    STATUS     current
    DESCRIPTION
        "-- empty --"
    ::= { lcsStatusIpRouterRipDynWanSitesEntry 3 }

-- {COLUMN} 310.1.10.19.14.1.4
lcsStatusIpRouterRipDynWanSitesEntryMasquerade OBJECT-TYPE
    SYNTAX     INTEGER
      {
        eAuto (0),
        eOn (1),
        eIntranet (2)
      }
    MAX-ACCESS read-only
    STATUS     current
    DESCRIPTION
        "-- empty --"
    ::= { lcsStatusIpRouterRipDynWanSitesEntry 4 }

-- {COLUMN} 310.1.10.19.14.1.7
lcsStatusIpRouterRipDynWanSitesEntryPoisonedReverse OBJECT-TYPE
    SYNTAX     INTEGER
      {
        eNo (0),
        eYes (1)
      }
    MAX-ACCESS read-only
    STATUS     current
    DESCRIPTION
        "-- empty --"
    ::= { lcsStatusIpRouterRipDynWanSitesEntry 7 }

-- {COLUMN} 310.1.10.19.14.1.8
lcsStatusIpRouterRipDynWanSitesEntryRfc2091 OBJECT-TYPE
    SYNTAX     INTEGER
      {
        eNo (0),
        eYes (1)
      }
    MAX-ACCESS read-only
    STATUS     current
    DESCRIPTION
        "-- empty --"
    ::= { lcsStatusIpRouterRipDynWanSitesEntry 8 }

-- {COLUMN} 310.1.10.19.14.1.9
lcsStatusIpRouterRipDynWanSitesEntryGateway OBJECT-TYPE
    SYNTAX     IpAddress
    MAX-ACCESS read-only
    STATUS     current
    DESCRIPTION
        "-- empty --"
    ::= { lcsStatusIpRouterRipDynWanSitesEntry 9 }

-- {COLUMN} 310.1.10.19.14.1.5
lcsStatusIpRouterRipDynWanSitesEntryDftRtgTag OBJECT-TYPE
    SYNTAX     INTEGER (0..65535)
    MAX-ACCESS read-only
    STATUS     current
    DESCRIPTION
        "-- empty --"
    ::= { lcsStatusIpRouterRipDynWanSitesEntry 5 }

-- {COLUMN} 310.1.10.19.14.1.6
lcsStatusIpRouterRipDynWanSitesEntryRtgTagList OBJECT-TYPE
    SYNTAX     DisplayString (SIZE(0..33))
    MAX-ACCESS read-only
    STATUS     current
    DESCRIPTION
        "-- empty --"
    ::= { lcsStatusIpRouterRipDynWanSitesEntry 6 }

-- {COLUMN} 310.1.10.19.14.1.10
lcsStatusIpRouterRipDynWanSitesEntryRxFilter OBJECT-TYPE
    SYNTAX     DisplayString (SIZE(0..16))
    MAX-ACCESS read-only
    STATUS     current
    DESCRIPTION
        "-- empty --"
    ::= { lcsStatusIpRouterRipDynWanSitesEntry 10 }

-- {COLUMN} 310.1.10.19.14.1.11
lcsStatusIpRouterRipDynWanSitesEntryTxFilter OBJECT-TYPE
    SYNTAX     DisplayString (SIZE(0..16))
    MAX-ACCESS read-only
    STATUS     current
    DESCRIPTION
        "-- empty --"
    ::= { lcsStatusIpRouterRipDynWanSitesEntry 11 }

-- {TABLE} 310.1.10.19.16
lcsStatusIpRouterRipWildcardSitesTable OBJECT-TYPE
    SYNTAX     SEQUENCE OF LcsStatusIpRouterRipWildcardSitesEntry
    MAX-ACCESS not-accessible
    STATUS     current
    DESCRIPTION
        "-- empty --"
    ::= { lcsStatusIpRouterRip 16 }

-- {ENTRY} 310.1.10.19.16.1
lcsStatusIpRouterRipWildcardSitesEntry OBJECT-TYPE
    SYNTAX     LcsStatusIpRouterRipWildcardSitesEntry
    MAX-ACCESS not-accessible
    STATUS     current
    DESCRIPTION
        ""
    INDEX {
        lcsStatusIpRouterRipWildcardSitesEntryPeer
    }
    ::= { lcsStatusIpRouterRipWildcardSitesTable 1 }

-- {SEQUENCE}
LcsStatusIpRouterRipWildcardSitesEntry ::= SEQUENCE {
    lcsStatusIpRouterRipWildcardSitesEntryPeer DisplayString,
    lcsStatusIpRouterRipWildcardSitesEntryRipType INTEGER,
    lcsStatusIpRouterRipWildcardSitesEntryRipSend INTEGER,
    lcsStatusIpRouterRipWildcardSitesEntryRipAccept INTEGER,
    lcsStatusIpRouterRipWildcardSitesEntryMasquerade INTEGER,
    lcsStatusIpRouterRipWildcardSitesEntryPoisonedReverse INTEGER,
    lcsStatusIpRouterRipWildcardSitesEntryRfc2091 INTEGER,
    lcsStatusIpRouterRipWildcardSitesEntryGateway IpAddress,
    lcsStatusIpRouterRipWildcardSitesEntryDftRtgTag INTEGER,
    lcsStatusIpRouterRipWildcardSitesEntryRtgTagList DisplayString,
    lcsStatusIpRouterRipWildcardSitesEntryRxFilter DisplayString,
    lcsStatusIpRouterRipWildcardSitesEntryTxFilter DisplayString
}

-- {COLUMN} 310.1.10.19.16.1.1
lcsStatusIpRouterRipWildcardSitesEntryPeer OBJECT-TYPE
    SYNTAX     DisplayString (SIZE(0..16))
    MAX-ACCESS read-only
    STATUS     current
    DESCRIPTION
        "-- empty --"
    ::= { lcsStatusIpRouterRipWildcardSitesEntry 1 }

-- {COLUMN} 310.1.10.19.16.1.2
lcsStatusIpRouterRipWildcardSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipWildcardSitesEntry 2 }

-- {COLUMN} 310.1.10.19.16.1.12
lcsStatusIpRouterRipWildcardSitesEntryRipSend OBJECT-TYPE
    SYNTAX     INTEGER
      {
        eNo (0),
        eYes (1)
      }
    MAX-ACCESS read-only
    STATUS     current
    DESCRIPTION
        "-- empty --"
    ::= { lcsStatusIpRouterRipWildcardSitesEntry 12 }

-- {COLUMN} 310.1.10.19.16.1.3
lcsStatusIpRouterRipWildcardSitesEntryRipAccept OBJECT-TYPE
    SYNTAX     INTEGER
      {
        eNo (0),
        eYes (1)
      }
    MAX-ACCESS read-only
    STATUS     current
    DESCRIPTION
        "-- empty --"
    ::= { lcsStatusIpRouterRipWildcardSitesEntry 3 }

-- {COLUMN} 310.1.10.19.16.1.4
lcsStatusIpRouterRipWildcardSitesEntryMasquerade OBJECT-TYPE
    SYNTAX     INTEGER
      {
        eAuto (0),
        eOn (1),
        eIntranet (2)
      }
    MAX-ACCESS read-only
    STATUS     current
    DESCRIPTION
        "-- empty --"
    ::= { lcsStatusIpRouterRipWildcardSitesEntry 4 }

-- {COLUMN} 310.1.10.19.16.1.7
lcsStatusIpRouterRipWildcardSitesEntryPoisonedReverse OBJECT-TYPE
    SYNTAX     INTEGER
      {
        eNo (0),
        eYes (1)
      }
    MAX-ACCESS read-only
    STATUS     current
    DESCRIPTION
        "-- empty --"
    ::= { lcsStatusIpRouterRipWildcardSitesEntry 7 }

-- {COLUMN} 310.1.10.19.16.1.8
lcsStatusIpRouterRipWildcardSitesEntryRfc2091 OBJECT-TYPE
    SYNTAX     INTEGER
      {
        eNo (0),
        eYes (1)
      }
    MAX-ACCESS read-only
    STATUS     current
    DESCRIPTION
        "-- empty --"
    ::= { lcsStatusIpRouterRipWildcardSitesEntry 8 }

-- {COLUMN} 310.1.10.19.16.1.9
lcsStatusIpRouterRipWildcardSitesEntryGateway OBJECT-TYPE
    SYNTAX     IpAddress
    MAX-ACCESS read-only
    STATUS     current
    DESCRIPTION
        "-- empty --"
    ::= { lcsStatusIpRouterRipWildcardSitesEntry 9 }

-- {COLUMN} 310.1.10.19.16.1.5
lcsStatusIpRouterRipWildcardSitesEntryDftRtgTag OBJECT-TYPE
    SYNTAX     INTEGER (0..65535)
    MAX-ACCESS read-only
    STATUS     current
    DESCRIPTION
        "-- empty --"
    ::= { lcsStatusIpRouterRipWildcardSitesEntry 5 }

-- {COLUMN} 310.1.10.19.16.1.6
lcsStatusIpRouterRipWildcardSitesEntryRtgTagList OBJECT-TYPE
    SYNTAX     DisplayString (SIZE(0..33))
    MAX-ACCESS read-only
    STATUS     current
    DESCRIPTION
        "-- empty --"
    ::= { lcsStatusIpRouterRipWildcardSitesEntry 6 }

-- {COLUMN} 310.1.10.19.16.1.10
lcsStatusIpRouterRipWildcardSitesEntryRxFilter OBJECT-TYPE
    SYNTAX     DisplayString (SIZE(0..16))
    MAX-ACCESS read-only
    STATUS     current
    DESCRIPTION
        "-- empty --"
    ::= { lcsStatusIpRouterRipWildcardSitesEntry 10 }

-- {COLUMN} 310.1.10.19.16.1.11
lcsStatusIpRouterRipWildcardSitesEntryTxFilter OBJECT-TYPE
    SYNTAX     DisplayString (SIZE(0..16))
    MAX-ACCESS read-only
    STATUS     current
    DESCRIPTION
        "-- empty --"
    ::= { lcsStatusIpRouterRipWildcardSitesEntry 11 }

-- {TABLE} 310.1.10.19.15
lcsStatusIpRouterRipFilterTable OBJECT-TYPE
    SYNTAX     SEQUENCE OF LcsStatusIpRouterRipFilterEntry
    MAX-ACCESS not-accessible
    STATUS     current
    DESCRIPTION
        "-- empty --"
    ::= { lcsStatusIpRouterRip 15 }

-- {ENTRY} 310.1.10.19.15.1
lcsStatusIpRouterRipFilterEntry OBJECT-TYPE
    SYNTAX     LcsStatusIpRouterRipFilterEntry
    MAX-ACCESS not-accessible
    STATUS     current
    DESCRIPTION
        ""
    INDEX {
        lcsStatusIpRouterRipFilterEntryIdx
    }
    ::= { lcsStatusIpRouterRipFilterTable 1 }

-- {SEQUENCE}
LcsStatusIpRouterRipFilterEntry ::= SEQUENCE {
    lcsStatusIpRouterRipFilterEntryIdx INTEGER,
    lcsStatusIpRouterRipFilterEntryName DisplayString,
    lcsStatusIpRouterRipFilterEntryIpAddress IpAddress,
    lcsStatusIpRouterRipFilterEntryIpNetmask IpAddress,
    lcsStatusIpRouterRipFilterEntryType INTEGER
}

-- {COLUMN} 310.1.10.19.15.1.1
lcsStatusIpRouterRipFilterEntryIdx OBJECT-TYPE
    SYNTAX     INTEGER (0..65535)
    MAX-ACCESS read-only
    STATUS     current
    DESCRIPTION
        "-- empty --"
    ::= { lcsStatusIpRouterRipFilterEntry 1 }

-- {COLUMN} 310.1.10.19.15.1.3
lcsStatusIpRouterRipFilterEntryName OBJECT-TYPE
    SYNTAX     DisplayString (SIZE(0..255))
    MAX-ACCESS read-only
    STATUS     current
    DESCRIPTION
        "-- empty --"
    ::= { lcsStatusIpRouterRipFilterEntry 3 }

-- {COLUMN} 310.1.10.19.15.1.4
lcsStatusIpRouterRipFilterEntryIpAddress OBJECT-TYPE
    SYNTAX     IpAddress
    MAX-ACCESS read-only
    STATUS     current
    DESCRIPTION
        "-- empty --"
    ::= { lcsStatusIpRouterRipFilterEntry 4 }

-- {COLUMN} 310.1.10.19.15.1.5
lcsStatusIpRouterRipFilterEntryIpNetmask OBJECT-TYPE
    SYNTAX     IpAddress
    MAX-ACCESS read-only
    STATUS     current
    DESCRIPTION
        "-- empty --"
    ::= { lcsStatusIpRouterRipFilterEntry 5 }

-- {COLUMN} 310.1.10.19.15.1.2
lcsStatusIpRouterRipFilterEntryType OBJECT-TYPE
    SYNTAX     INTEGER
      {
        eUnknown (0),
        ePositive (1),
        eNegative (2)
      }
    MAX-ACCESS read-only
    STATUS     current
    DESCRIPTION
        "-- empty --"
    ::= { lcsStatusIpRouterRipFilterEntry 2 }

-- {SCALAR} 310.1.10.20
lcsStatusIpRouterDeleteValues OBJECT-TYPE
    SYNTAX     DisplayString
    MAX-ACCESS read-write
    STATUS     current
    DESCRIPTION
        "-- empty --"
    ::= { lcsStatusIpRouter 20 }

-- {TABLE} 310.1.10.21
lcsStatusIpRouterServiceTableTable OBJECT-TYPE
    SYNTAX     SEQUENCE OF LcsStatusIpRouterServiceTableEntry
    MAX-ACCESS not-accessible
    STATUS     current
    DESCRIPTION
        "-- empty --"
    ::= { lcsStatusIpRouter 21 }

-- {ENTRY} 310.1.10.21.1
lcsStatusIpRouterServiceTableEntry OBJECT-TYPE
    SYNTAX     LcsStatusIpRouterServiceTableEntry
    MAX-ACCESS not-accessible
    STATUS     current
    DESCRIPTION
        ""
    INDEX {
        lcsStatusIpRouterServiceTableEntryService
    }
    ::= { lcsStatusIpRouterServiceTableTable 1 }

-- {SEQUENCE}
LcsStatusIpRouterServiceTableEntry ::= SEQUENCE {
    lcsStatusIpRouterServiceTableEntryService INTEGER,
    lcsStatusIpRouterServiceTableEntryPacketRx Counter32,
    lcsStatusIpRouterServiceTableEntryPacketTx Counter32,
    lcsStatusIpRouterServiceTableEntryPacketRel DisplayString,
    lcsStatusIpRouterServiceTableEntryKbytesRx Counter32,
    lcsStatusIpRouterServiceTableEntryKbytesTx Counter32,
    lcsStatusIpRouterServiceTableEntryKbytesRel DisplayString
}

-- {COLUMN} 310.1.10.21.1.1
lcsStatusIpRouterServiceTableEntryService OBJECT-TYPE
    SYNTAX     INTEGER
      {
        eIcmp (1),
        eFtp (2),
        eHttp (3),
        eSmtp (4),
        eDns (5),
        eTelnet (6),
        eTftp (7),
        eDhcp (8),
        ePop3 (9),
        eNetbios (10),
        eImap2 (11),
        eNews (12),
        eIrc (13),
        eSnmp (14),
        eOther (15),
        eTotal (16)
      }
    MAX-ACCESS read-only
    STATUS     current
    DESCRIPTION
        "-- empty --"
    ::= { lcsStatusIpRouterServiceTableEntry 1 }

-- {COLUMN} 310.1.10.21.1.2
lcsStatusIpRouterServiceTableEntryPacketRx OBJECT-TYPE
    SYNTAX     Counter32
    MAX-ACCESS read-only
    STATUS     current
    DESCRIPTION
        "-- empty --"
    ::= { lcsStatusIpRouterServiceTableEntry 2 }

-- {COLUMN} 310.1.10.21.1.3
lcsStatusIpRouterServiceTableEntryPacketTx OBJECT-TYPE
    SYNTAX     Counter32
    MAX-ACCESS read-only
    STATUS     current
    DESCRIPTION
        "-- empty --"
    ::= { lcsStatusIpRouterServiceTableEntry 3 }

-- {COLUMN} 310.1.10.21.1.4
lcsStatusIpRouterServiceTableEntryPacketRel OBJECT-TYPE
    SYNTAX     DisplayString (SIZE(0..255))
    MAX-ACCESS read-only
    STATUS     current
    DESCRIPTION
        "-- empty --"
    ::= { lcsStatusIpRouterServiceTableEntry 4 }

-- {COLUMN} 310.1.10.21.1.5
lcsStatusIpRouterServiceTableEntryKbytesRx OBJECT-TYPE
    SYNTAX     Counter32
    MAX-ACCESS read-only
    STATUS     current
    DESCRIPTION
        "-- empty --"
    ::= { lcsStatusIpRouterServiceTableEntry 5 }

-- {COLUMN} 310.1.10.21.1.6
lcsStatusIpRouterServiceTableEntryKbytesTx OBJECT-TYPE
    SYNTAX     Counter32
    MAX-ACCESS read-only
    STATUS     current
    DESCRIPTION
        "-- empty --"
    ::= { lcsStatusIpRouterServiceTableEntry 6 }

-- {COLUMN} 310.1.10.21.1.7
lcsStatusIpRouterServiceTableEntryKbytesRel OBJECT-TYPE
    SYNTAX     DisplayString (SIZE(0..255))
    MAX-ACCESS read-only
    STATUS     current
    DESCRIPTION
        "-- empty --"
    ::= { lcsStatusIpRouterServiceTableEntry 7 }

-- {TABLE} 310.1.10.22
lcsStatusIpRouterFilterListTable OBJECT-TYPE
    SYNTAX     SEQUENCE OF LcsStatusIpRouterFilterListEntry
    MAX-ACCESS not-accessible
    STATUS     current
    DESCRIPTION
        "-- empty --"
    ::= { lcsStatusIpRouter 22 }

-- {ENTRY} 310.1.10.22.1
lcsStatusIpRouterFilterListEntry OBJECT-TYPE
    SYNTAX     LcsStatusIpRouterFilterListEntry
    MAX-ACCESS not-accessible
    STATUS     current
    DESCRIPTION
        ""
    INDEX {
        lcsStatusIpRouterFilterListEntryIdx
    }
    ::= { lcsStatusIpRouterFilterListTable 1 }

-- {SEQUENCE}
LcsStatusIpRouterFilterListEntry ::= SEQUENCE {
    lcsStatusIpRouterFilterListEntryIdx INTEGER,
    lcsStatusIpRouterFilterListEntryProt INTEGER,
    lcsStatusIpRouterFilterListEntrySrcMac DisplayString,
    lcsStatusIpRouterFilterListEntrySrcAddress IpAddress,
    lcsStatusIpRouterFilterListEntrySrcNetmask IpAddress,
    lcsStatusIpRouterFilterListEntrySSt INTEGER,
    lcsStatusIpRouterFilterListEntrySEnd INTEGER,
    lcsStatusIpRouterFilterListEntryDstMac DisplayString,
    lcsStatusIpRouterFilterListEntryDstAddress IpAddress,
    lcsStatusIpRouterFilterListEntryDstNetmask IpAddress,
    lcsStatusIpRouterFilterListEntryDSt INTEGER,
    lcsStatusIpRouterFilterListEntryDEnd INTEGER,
    lcsStatusIpRouterFilterListEntryAction DisplayString,
    lcsStatusIpRouterFilterListEntryLinked INTEGER,
    lcsStatusIpRouterFilterListEntryPrio INTEGER,
    lcsStatusIpRouterFilterListEntryRtgTag INTEGER
}

-- {COLUMN} 310.1.10.22.1.1
lcsStatusIpRouterFilterListEntryIdx OBJECT-TYPE
    SYNTAX     INTEGER (0..2147483647)
    MAX-ACCESS read-only
    STATUS     current
    DESCRIPTION
        "-- empty --"
    ::= { lcsStatusIpRouterFilterListEntry 1 }

-- {COLUMN} 310.1.10.22.1.2
lcsStatusIpRouterFilterListEntryProt OBJECT-TYPE
    SYNTAX     INTEGER (0..255)
    MAX-ACCESS read-only
    STATUS     current
    DESCRIPTION
        "-- empty --"
    ::= { lcsStatusIpRouterFilterListEntry 2 }

-- {COLUMN} 310.1.10.22.1.13
lcsStatusIpRouterFilterListEntrySrcMac OBJECT-TYPE
    SYNTAX     DisplayString (SIZE(0..255))
    MAX-ACCESS read-only
    STATUS     current
    DESCRIPTION
        "-- empty --"
    ::= { lcsStatusIpRouterFilterListEntry 13 }

-- {COLUMN} 310.1.10.22.1.3
lcsStatusIpRouterFilterListEntrySrcAddress OBJECT-TYPE
    SYNTAX     IpAddress
    MAX-ACCESS read-only
    STATUS     current
    DESCRIPTION
        "-- empty --"
    ::= { lcsStatusIpRouterFilterListEntry 3 }

-- {COLUMN} 310.1.10.22.1.4
lcsStatusIpRouterFilterListEntrySrcNetmask OBJECT-TYPE
    SYNTAX     IpAddress
    MAX-ACCESS read-only
    STATUS     current
    DESCRIPTION
        "-- empty --"
    ::= { lcsStatusIpRouterFilterListEntry 4 }

-- {COLUMN} 310.1.10.22.1.5
lcsStatusIpRouterFilterListEntrySSt OBJECT-TYPE
    SYNTAX     INTEGER (0..65535)
    MAX-ACCESS read-only
    STATUS     current
    DESCRIPTION
        "-- empty --"
    ::= { lcsStatusIpRouterFilterListEntry 5 }

-- {COLUMN} 310.1.10.22.1.6
lcsStatusIpRouterFilterListEntrySEnd OBJECT-TYPE
    SYNTAX     INTEGER (0..65535)
    MAX-ACCESS read-only
    STATUS     current
    DESCRIPTION
        "-- empty --"
    ::= { lcsStatusIpRouterFilterListEntry 6 }

-- {COLUMN} 310.1.10.22.1.14
lcsStatusIpRouterFilterListEntryDstMac OBJECT-TYPE
    SYNTAX     DisplayString (SIZE(0..255))
    MAX-ACCESS read-only
    STATUS     current
    DESCRIPTION
        "-- empty --"
    ::= { lcsStatusIpRouterFilterListEntry 14 }

-- {COLUMN} 310.1.10.22.1.7
lcsStatusIpRouterFilterListEntryDstAddress OBJECT-TYPE
    SYNTAX     IpAddress
    MAX-ACCESS read-only
    STATUS     current
    DESCRIPTION
        "-- empty --"
    ::= { lcsStatusIpRouterFilterListEntry 7 }

-- {COLUMN} 310.1.10.22.1.8
lcsStatusIpRouterFilterListEntryDstNetmask OBJECT-TYPE
    SYNTAX     IpAddress
    MAX-ACCESS read-only
    STATUS     current
    DESCRIPTION
        "-- empty --"
    ::= { lcsStatusIpRouterFilterListEntry 8 }

-- {COLUMN} 310.1.10.22.1.9
lcsStatusIpRouterFilterListEntryDSt OBJECT-TYPE
    SYNTAX     INTEGER (0..65535)
    MAX-ACCESS read-only
    STATUS     current
    DESCRIPTION
        "-- empty --"
    ::= { lcsStatusIpRouterFilterListEntry 9 }

-- {COLUMN} 310.1.10.22.1.10
lcsStatusIpRouterFilterListEntryDEnd OBJECT-TYPE
    SYNTAX     INTEGER (0..65535)
    MAX-ACCESS read-only
    STATUS     current
    DESCRIPTION
        "-- empty --"
    ::= { lcsStatusIpRouterFilterListEntry 10 }

-- {COLUMN} 310.1.10.22.1.11
lcsStatusIpRouterFilterListEntryAction OBJECT-TYPE
    SYNTAX     DisplayString (SIZE(0..255))
    MAX-ACCESS read-only
    STATUS     current
    DESCRIPTION
        "-- empty --"
    ::= { lcsStatusIpRouterFilterListEntry 11 }

-- {COLUMN} 310.1.10.22.1.15
lcsStatusIpRouterFilterListEntryLinked OBJECT-TYPE
    SYNTAX     INTEGER
      {
        eNo (0),
        eYes (1)
      }
    MAX-ACCESS read-only
    STATUS     current
    DESCRIPTION
        "-- empty --"
    ::= { lcsStatusIpRouterFilterListEntry 15 }

-- {COLUMN} 310.1.10.22.1.16
lcsStatusIpRouterFilterListEntryPrio OBJECT-TYPE
    SYNTAX     INTEGER (0..65535)
    MAX-ACCESS read-only
    STATUS     current
    DESCRIPTION
        "-- empty --"
    ::= { lcsStatusIpRouterFilterListEntry 16 }

-- {COLUMN} 310.1.10.22.1.17
lcsStatusIpRouterFilterListEntryRtgTag OBJECT-TYPE
    SYNTAX     INTEGER (0..65535)
    MAX-ACCESS read-only
    STATUS     current
    DESCRIPTION
        "-- empty --"
    ::= { lcsStatusIpRouterFilterListEntry 17 }

-- {TABLE} 310.1.10.23
lcsStatusIpRouterConnectionListTable OBJECT-TYPE
    SYNTAX     SEQUENCE OF LcsStatusIpRouterConnectionListEntry
    MAX-ACCESS not-accessible
    STATUS     current
    DESCRIPTION
        "-- empty --"
    ::= { lcsStatusIpRouter 23 }

-- {ENTRY} 310.1.10.23.1
lcsStatusIpRouterConnectionListEntry OBJECT-TYPE
    SYNTAX     LcsStatusIpRouterConnectionListEntry
    MAX-ACCESS not-accessible
    STATUS     current
    DESCRIPTION
        ""
    INDEX {
        lcsStatusIpRouterConnectionListEntrySrcAddress,
        lcsStatusIpRouterConnectionListEntryDstAddress,
        lcsStatusIpRouterConnectionListEntryProt,
        lcsStatusIpRouterConnectionListEntrySrcPort,
        lcsStatusIpRouterConnectionListEntryDstPort
    }
    ::= { lcsStatusIpRouterConnectionListTable 1 }

-- {SEQUENCE}
LcsStatusIpRouterConnectionListEntry ::= SEQUENCE {
    lcsStatusIpRouterConnectionListEntrySrcAddress IpAddress,
    lcsStatusIpRouterConnectionListEntryDstAddress IpAddress,
    lcsStatusIpRouterConnectionListEntryProt INTEGER,
    lcsStatusIpRouterConnectionListEntrySrcPort INTEGER,
    lcsStatusIpRouterConnectionListEntryDstPort INTEGER,
    lcsStatusIpRouterConnectionListEntryRtgTag INTEGER,
    lcsStatusIpRouterConnectionListEntryTimeout INTEGER,
    lcsStatusIpRouterConnectionListEntryFlags INTEGER,
    lcsStatusIpRouterConnectionListEntryFilterRule DisplayString,
    lcsStatusIpRouterConnectionListEntrySrcRoute DisplayString,
    lcsStatusIpRouterConnectionListEntryDestRoute DisplayString
}

-- {COLUMN} 310.1.10.23.1.1
lcsStatusIpRouterConnectionListEntrySrcAddress OBJECT-TYPE
    SYNTAX     IpAddress
    MAX-ACCESS read-only
    STATUS     current
    DESCRIPTION
        "-- empty --"
    ::= { lcsStatusIpRouterConnectionListEntry 1 }

-- {COLUMN} 310.1.10.23.1.2
lcsStatusIpRouterConnectionListEntryDstAddress OBJECT-TYPE
    SYNTAX     IpAddress
    MAX-ACCESS read-only
    STATUS     current
    DESCRIPTION
        "-- empty --"
    ::= { lcsStatusIpRouterConnectionListEntry 2 }

-- {COLUMN} 310.1.10.23.1.3
lcsStatusIpRouterConnectionListEntryProt OBJECT-TYPE
    SYNTAX     INTEGER (0..255)
    MAX-ACCESS read-only
    STATUS     current
    DESCRIPTION
        "-- empty --"
    ::= { lcsStatusIpRouterConnectionListEntry 3 }

-- {COLUMN} 310.1.10.23.1.4
lcsStatusIpRouterConnectionListEntrySrcPort OBJECT-TYPE
    SYNTAX     INTEGER (0..65535)
    MAX-ACCESS read-only
    STATUS     current
    DESCRIPTION
        "-- empty --"
    ::= { lcsStatusIpRouterConnectionListEntry 4 }

-- {COLUMN} 310.1.10.23.1.5
lcsStatusIpRouterConnectionListEntryDstPort OBJECT-TYPE
    SYNTAX     INTEGER (0..65535)
    MAX-ACCESS read-only
    STATUS     current
    DESCRIPTION
        "-- empty --"
    ::= { lcsStatusIpRouterConnectionListEntry 5 }

-- {COLUMN} 310.1.10.23.1.11
lcsStatusIpRouterConnectionListEntryRtgTag OBJECT-TYPE
    SYNTAX     INTEGER (0..65535)
    MAX-ACCESS read-only
    STATUS     current
    DESCRIPTION
        "-- empty --"
    ::= { lcsStatusIpRouterConnectionListEntry 11 }

-- {COLUMN} 310.1.10.23.1.6
lcsStatusIpRouterConnectionListEntryTimeout OBJECT-TYPE
    SYNTAX     INTEGER (0..65535)
    MAX-ACCESS read-only
    STATUS     current
    DESCRIPTION
        "-- empty --"
    ::= { lcsStatusIpRouterConnectionListEntry 6 }

-- {COLUMN} 310.1.10.23.1.7
lcsStatusIpRouterConnectionListEntryFlags OBJECT-TYPE
    SYNTAX     INTEGER (0..2147483647)
    MAX-ACCESS read-only
    STATUS     current
    DESCRIPTION
        "-- empty --"
    ::= { lcsStatusIpRouterConnectionListEntry 7 }

-- {COLUMN} 310.1.10.23.1.8
lcsStatusIpRouterConnectionListEntryFilterRule OBJECT-TYPE
    SYNTAX     DisplayString (SIZE(0..255))
    MAX-ACCESS read-only
    STATUS     current
    DESCRIPTION
        "-- empty --"
    ::= { lcsStatusIpRouterConnectionListEntry 8 }

-- {COLUMN} 310.1.10.23.1.9
lcsStatusIpRouterConnectionListEntrySrcRoute OBJECT-TYPE
    SYNTAX     DisplayString (SIZE(0..255))
    MAX-ACCESS read-only
    STATUS     current
    DESCRIPTION
        "-- empty --"
    ::= { lcsStatusIpRouterConnectionListEntry 9 }

-- {COLUMN} 310.1.10.23.1.10
lcsStatusIpRouterConnectionListEntryDestRoute OBJECT-TYPE
    SYNTAX     DisplayString (SIZE(0..255))
    MAX-ACCESS read-only
    STATUS     current
    DESCRIPTION
        "-- empty --"
    ::= { lcsStatusIpRouterConnectionListEntry 10 }

-- {TABLE} 310.1.10.29
lcsStatusIpRouterOpenPortListTable OBJECT-TYPE
    SYNTAX     SEQUENCE OF LcsStatusIpRouterOpenPortListEntry
    MAX-ACCESS not-accessible
    STATUS     current
    DESCRIPTION
        "-- empty --"
    ::= { lcsStatusIpRouter 29 }

-- {ENTRY} 310.1.10.29.1
lcsStatusIpRouterOpenPortListEntry OBJECT-TYPE
    SYNTAX     LcsStatusIpRouterOpenPortListEntry
    MAX-ACCESS not-accessible
    STATUS     current
    DESCRIPTION
        ""
    INDEX {
        lcsStatusIpRouterOpenPortListEntrySrcAddress,
        lcsStatusIpRouterOpenPortListEntryDstAddress,
        lcsStatusIpRouterOpenPortListEntryProt,
        lcsStatusIpRouterOpenPortListEntryDstPort
    }
    ::= { lcsStatusIpRouterOpenPortListTable 1 }

-- {SEQUENCE}
LcsStatusIpRouterOpenPortListEntry ::= SEQUENCE {
    lcsStatusIpRouterOpenPortListEntrySrcAddress IpAddress,
    lcsStatusIpRouterOpenPortListEntryDstAddress IpAddress,
    lcsStatusIpRouterOpenPortListEntryProt INTEGER,
    lcsStatusIpRouterOpenPortListEntryDstPort INTEGER,
    lcsStatusIpRouterOpenPortListEntryTimeout INTEGER,
    lcsStatusIpRouterOpenPortListEntryFilterRule DisplayString,
    lcsStatusIpRouterOpenPortListEntrySrcRoute DisplayString
}

-- {COLUMN} 310.1.10.29.1.1
lcsStatusIpRouterOpenPortListEntrySrcAddress OBJECT-TYPE
    SYNTAX     IpAddress
    MAX-ACCESS read-only
    STATUS     current
    DESCRIPTION
        "-- empty --"
    ::= { lcsStatusIpRouterOpenPortListEntry 1 }

-- {COLUMN} 310.1.10.29.1.2
lcsStatusIpRouterOpenPortListEntryDstAddress OBJECT-TYPE
    SYNTAX     IpAddress
    MAX-ACCESS read-only
    STATUS     current
    DESCRIPTION
        "-- empty --"
    ::= { lcsStatusIpRouterOpenPortListEntry 2 }

-- {COLUMN} 310.1.10.29.1.3
lcsStatusIpRouterOpenPortListEntryProt OBJECT-TYPE
    SYNTAX     INTEGER (0..255)
    MAX-ACCESS read-only
    STATUS     current
    DESCRIPTION
        "-- empty --"
    ::= { lcsStatusIpRouterOpenPortListEntry 3 }

-- {COLUMN} 310.1.10.29.1.5
lcsStatusIpRouterOpenPortListEntryDstPort OBJECT-TYPE
    SYNTAX     INTEGER (0..65535)
    MAX-ACCESS read-only
    STATUS     current
    DESCRIPTION
        "-- empty --"
    ::= { lcsStatusIpRouterOpenPortListEntry 5 }

-- {COLUMN} 310.1.10.29.1.6
lcsStatusIpRouterOpenPortListEntryTimeout OBJECT-TYPE
    SYNTAX     INTEGER (0..65535)
    MAX-ACCESS read-only
    STATUS     current
    DESCRIPTION
        "-- empty --"
    ::= { lcsStatusIpRouterOpenPortListEntry 6 }

-- {COLUMN} 310.1.10.29.1.8
lcsStatusIpRouterOpenPortListEntryFilterRule OBJECT-TYPE
    SYNTAX     DisplayString (SIZE(0..255))
    MAX-ACCESS read-only
    STATUS     current
    DESCRIPTION
        "-- empty --"
    ::= { lcsStatusIpRouterOpenPortListEntry 8 }

-- {COLUMN} 310.1.10.29.1.9
lcsStatusIpRouterOpenPortListEntrySrcRoute OBJECT-TYPE
    SYNTAX     DisplayString (SIZE(0..255))
    MAX-ACCESS read-only
    STATUS     current
    DESCRIPTION
        "-- empty --"
    ::= { lcsStatusIpRouterOpenPortListEntry 9 }

-- {TABLE} 310.1.10.24
lcsStatusIpRouterHostBlockListTable OBJECT-TYPE
    SYNTAX     SEQUENCE OF LcsStatusIpRouterHostBlockListEntry
    MAX-ACCESS not-accessible
    STATUS     current
    DESCRIPTION
        "-- empty --"
    ::= { lcsStatusIpRouter 24 }

-- {ENTRY} 310.1.10.24.1
lcsStatusIpRouterHostBlockListEntry OBJECT-TYPE
    SYNTAX     LcsStatusIpRouterHostBlockListEntry
    MAX-ACCESS not-accessible
    STATUS     current
    DESCRIPTION
        ""
    INDEX {
        lcsStatusIpRouterHostBlockListEntrySrcAddress
    }
    ::= { lcsStatusIpRouterHostBlockListTable 1 }

-- {SEQUENCE}
LcsStatusIpRouterHostBlockListEntry ::= SEQUENCE {
    lcsStatusIpRouterHostBlockListEntrySrcAddress IpAddress,
    lcsStatusIpRouterHostBlockListEntryTimeout INTEGER,
    lcsStatusIpRouterHostBlockListEntryFilterRule DisplayString
}

-- {COLUMN} 310.1.10.24.1.1
lcsStatusIpRouterHostBlockListEntrySrcAddress OBJECT-TYPE
    SYNTAX     IpAddress
    MAX-ACCESS read-only
    STATUS     current
    DESCRIPTION
        "-- empty --"
    ::= { lcsStatusIpRouterHostBlockListEntry 1 }

-- {COLUMN} 310.1.10.24.1.2
lcsStatusIpRouterHostBlockListEntryTimeout OBJECT-TYPE
    SYNTAX     INTEGER (0..2147483647)
    MAX-ACCESS read-only
    STATUS     current
    DESCRIPTION
        "-- empty --"
    ::= { lcsStatusIpRouterHostBlockListEntry 2 }

-- {COLUMN} 310.1.10.24.1.3
lcsStatusIpRouterHostBlockListEntryFilterRule OBJECT-TYPE
    SYNTAX     DisplayString (SIZE(0..255))
    MAX-ACCESS read-only
    STATUS     current
    DESCRIPTION
        "-- empty --"
    ::= { lcsStatusIpRouterHostBlockListEntry 3 }

-- {TABLE} 310.1.10.25
lcsStatusIpRouterPortBlockListTable OBJECT-TYPE
    SYNTAX     SEQUENCE OF LcsStatusIpRouterPortBlockListEntry
    MAX-ACCESS not-accessible
    STATUS     current
    DESCRIPTION
        "-- empty --"
    ::= { lcsStatusIpRouter 25 }

-- {ENTRY} 310.1.10.25.1
lcsStatusIpRouterPortBlockListEntry OBJECT-TYPE
    SYNTAX     LcsStatusIpRouterPortBlockListEntry
    MAX-ACCESS not-accessible
    STATUS     current
    DESCRIPTION
        ""
    INDEX {
        lcsStatusIpRouterPortBlockListEntryDstAddress
    }
    ::= { lcsStatusIpRouterPortBlockListTable 1 }

-- {SEQUENCE}
LcsStatusIpRouterPortBlockListEntry ::= SEQUENCE {
    lcsStatusIpRouterPortBlockListEntryDstAddress IpAddress,
    lcsStatusIpRouterPortBlockListEntryProt INTEGER,
    lcsStatusIpRouterPortBlockListEntryDstPort INTEGER,
    lcsStatusIpRouterPortBlockListEntryTimeout INTEGER,
    lcsStatusIpRouterPortBlockListEntryFilterRule DisplayString
}

-- {COLUMN} 310.1.10.25.1.1
lcsStatusIpRouterPortBlockListEntryDstAddress OBJECT-TYPE
    SYNTAX     IpAddress
    MAX-ACCESS read-only
    STATUS     current
    DESCRIPTION
        "-- empty --"
    ::= { lcsStatusIpRouterPortBlockListEntry 1 }

-- {COLUMN} 310.1.10.25.1.2
lcsStatusIpRouterPortBlockListEntryProt OBJECT-TYPE
    SYNTAX     INTEGER (0..65535)
    MAX-ACCESS read-only
    STATUS     current
    DESCRIPTION
        "-- empty --"
    ::= { lcsStatusIpRouterPortBlockListEntry 2 }

-- {COLUMN} 310.1.10.25.1.3
lcsStatusIpRouterPortBlockListEntryDstPort OBJECT-TYPE
    SYNTAX     INTEGER (0..65535)
    MAX-ACCESS read-only
    STATUS     current
    DESCRIPTION
        "-- empty --"
    ::= { lcsStatusIpRouterPortBlockListEntry 3 }

-- {COLUMN} 310.1.10.25.1.4
lcsStatusIpRouterPortBlockListEntryTimeout OBJECT-TYPE
    SYNTAX     INTEGER (0..2147483647)
    MAX-ACCESS read-only
    STATUS     current
    DESCRIPTION
        "-- empty --"
    ::= { lcsStatusIpRouterPortBlockListEntry 4 }

-- {COLUMN} 310.1.10.25.1.5
lcsStatusIpRouterPortBlockListEntryFilterRule OBJECT-TYPE
    SYNTAX     DisplayString (SIZE(0..255))
    MAX-ACCESS read-only
    STATUS     current
    DESCRIPTION
        "-- empty --"
    ::= { lcsStatusIpRouterPortBlockListEntry 5 }

-- {TABLE} 310.1.10.26
lcsStatusIpRouterLogTableTable OBJECT-TYPE
    SYNTAX     SEQUENCE OF LcsStatusIpRouterLogTableEntry
    MAX-ACCESS not-accessible
    STATUS     current
    DESCRIPTION
        "-- empty --"
    ::= { lcsStatusIpRouter 26 }

-- {ENTRY} 310.1.10.26.1
lcsStatusIpRouterLogTableEntry OBJECT-TYPE
    SYNTAX     LcsStatusIpRouterLogTableEntry
    MAX-ACCESS not-accessible
    STATUS     current
    DESCRIPTION
        ""
    INDEX {
        lcsStatusIpRouterLogTableEntryIdx
    }
    ::= { lcsStatusIpRouterLogTableTable 1 }

-- {SEQUENCE}
LcsStatusIpRouterLogTableEntry ::= SEQUENCE {
    lcsStatusIpRouterLogTableEntryIdx INTEGER,
    lcsStatusIpRouterLogTableEntrySystemTime DisplayString,
    lcsStatusIpRouterLogTableEntrySrcAddress IpAddress,
    lcsStatusIpRouterLogTableEntryDstAddress IpAddress,
    lcsStatusIpRouterLogTableEntryProt INTEGER,
    lcsStatusIpRouterLogTableEntrySrcPort INTEGER,
    lcsStatusIpRouterLogTableEntryDstPort INTEGER,
    lcsStatusIpRouterLogTableEntryFilterRule DisplayString,
    lcsStatusIpRouterLogTableEntryLimit INTEGER,
    lcsStatusIpRouterLogTableEntryThreshold INTEGER,
    lcsStatusIpRouterLogTableEntryAction INTEGER
}

-- {COLUMN} 310.1.10.26.1.1
lcsStatusIpRouterLogTableEntryIdx OBJECT-TYPE
    SYNTAX     INTEGER (0..65535)
    MAX-ACCESS read-only
    STATUS     current
    DESCRIPTION
        "-- empty --"
    ::= { lcsStatusIpRouterLogTableEntry 1 }

-- {COLUMN} 310.1.10.26.1.2
lcsStatusIpRouterLogTableEntrySystemTime OBJECT-TYPE
    SYNTAX     DisplayString (SIZE(0..19))
    MAX-ACCESS read-only
    STATUS     current
    DESCRIPTION
        "-- empty --"
    ::= { lcsStatusIpRouterLogTableEntry 2 }

-- {COLUMN} 310.1.10.26.1.3
lcsStatusIpRouterLogTableEntrySrcAddress OBJECT-TYPE
    SYNTAX     IpAddress
    MAX-ACCESS read-only
    STATUS     current
    DESCRIPTION
        "-- empty --"
    ::= { lcsStatusIpRouterLogTableEntry 3 }

-- {COLUMN} 310.1.10.26.1.4
lcsStatusIpRouterLogTableEntryDstAddress OBJECT-TYPE
    SYNTAX     IpAddress
    MAX-ACCESS read-only
    STATUS     current
    DESCRIPTION
        "-- empty --"
    ::= { lcsStatusIpRouterLogTableEntry 4 }

-- {COLUMN} 310.1.10.26.1.5
lcsStatusIpRouterLogTableEntryProt OBJECT-TYPE
    SYNTAX     INTEGER (0..255)
    MAX-ACCESS read-only
    STATUS     current
    DESCRIPTION
        "-- empty --"
    ::= { lcsStatusIpRouterLogTableEntry 5 }

-- {COLUMN} 310.1.10.26.1.6
lcsStatusIpRouterLogTableEntrySrcPort OBJECT-TYPE
    SYNTAX     INTEGER (0..65535)
    MAX-ACCESS read-only
    STATUS     current
    DESCRIPTION
        "-- empty --"
    ::= { lcsStatusIpRouterLogTableEntry 6 }

-- {COLUMN} 310.1.10.26.1.7
lcsStatusIpRouterLogTableEntryDstPort OBJECT-TYPE
    SYNTAX     INTEGER (0..65535)
    MAX-ACCESS read-only
    STATUS     current
    DESCRIPTION
        "-- empty --"
    ::= { lcsStatusIpRouterLogTableEntry 7 }

-- {COLUMN} 310.1.10.26.1.8
lcsStatusIpRouterLogTableEntryFilterRule OBJECT-TYPE
    SYNTAX     DisplayString (SIZE(0..32))
    MAX-ACCESS read-only
    STATUS     current
    DESCRIPTION
        "-- empty --"
    ::= { lcsStatusIpRouterLogTableEntry 8 }

-- {COLUMN} 310.1.10.26.1.9
lcsStatusIpRouterLogTableEntryLimit OBJECT-TYPE
    SYNTAX     INTEGER (0..2147483647)
    MAX-ACCESS read-only
    STATUS     current
    DESCRIPTION
        "-- empty --"
    ::= { lcsStatusIpRouterLogTableEntry 9 }

-- {COLUMN} 310.1.10.26.1.10
lcsStatusIpRouterLogTableEntryThreshold OBJECT-TYPE
    SYNTAX     INTEGER (0..2147483647)
    MAX-ACCESS read-only
    STATUS     current
    DESCRIPTION
        "-- empty --"
    ::= { lcsStatusIpRouterLogTableEntry 10 }

-- {COLUMN} 310.1.10.26.1.11
lcsStatusIpRouterLogTableEntryAction OBJECT-TYPE
    SYNTAX     INTEGER (0..2147483647)
    MAX-ACCESS read-only
    STATUS     current
    DESCRIPTION
        "-- empty --"
    ::= { lcsStatusIpRouterLogTableEntry 11 }

-- {TABLE} 310.1.10.27
lcsStatusIpRouterHoConnListTable OBJECT-TYPE
    SYNTAX     SEQUENCE OF LcsStatusIpRouterHoConnListEntry
    MAX-ACCESS not-accessible
    STATUS     current
    DESCRIPTION
        "-- empty --"
    ::= { lcsStatusIpRouter 27 }

-- {ENTRY} 310.1.10.27.1
lcsStatusIpRouterHoConnListEntry OBJECT-TYPE
    SYNTAX     LcsStatusIpRouterHoConnListEntry
    MAX-ACCESS not-accessible
    STATUS     current
    DESCRIPTION
        ""
    INDEX {
        lcsStatusIpRouterHoConnListEntryDstAddress
    }
    ::= { lcsStatusIpRouterHoConnListTable 1 }

-- {SEQUENCE}
LcsStatusIpRouterHoConnListEntry ::= SEQUENCE {
    lcsStatusIpRouterHoConnListEntryDstAddress IpAddress,
    lcsStatusIpRouterHoConnListEntryNumHoConn INTEGER,
    lcsStatusIpRouterHoConnListEntryTimeout INTEGER
}

-- {COLUMN} 310.1.10.27.1.1
lcsStatusIpRouterHoConnListEntryDstAddress OBJECT-TYPE
    SYNTAX     IpAddress
    MAX-ACCESS read-only
    STATUS     current
    DESCRIPTION
        "-- empty --"
    ::= { lcsStatusIpRouterHoConnListEntry 1 }

-- {COLUMN} 310.1.10.27.1.2
lcsStatusIpRouterHoConnListEntryNumHoConn OBJECT-TYPE
    SYNTAX     INTEGER (0..2147483647)
    MAX-ACCESS read-only
    STATUS     current
    DESCRIPTION
        "-- empty --"
    ::= { lcsStatusIpRouterHoConnListEntry 2 }

-- {COLUMN} 310.1.10.27.1.3
lcsStatusIpRouterHoConnListEntryTimeout OBJECT-TYPE
    SYNTAX     INTEGER (0..65535)
    MAX-ACCESS read-only
    STATUS     current
    DESCRIPTION
        "-- empty --"
    ::= { lcsStatusIpRouterHoConnListEntry 3 }

-- {TABLE} 310.1.10.28
lcsStatusIpRouterQosTable OBJECT-TYPE
    SYNTAX     SEQUENCE OF LcsStatusIpRouterQosEntry
    MAX-ACCESS not-accessible
    STATUS     current
    DESCRIPTION
        "-- empty --"
    ::= { lcsStatusIpRouter 28 }

-- {ENTRY} 310.1.10.28.1
lcsStatusIpRouterQosEntry OBJECT-TYPE
    SYNTAX     LcsStatusIpRouterQosEntry
    MAX-ACCESS not-accessible
    STATUS     current
    DESCRIPTION
        ""
    INDEX {
        lcsStatusIpRouterQosEntryIfc
    }
    ::= { lcsStatusIpRouterQosTable 1 }

-- {SEQUENCE}
LcsStatusIpRouterQosEntry ::= SEQUENCE {
    lcsStatusIpRouterQosEntryIfc INTEGER,
    lcsStatusIpRouterQosEntryPeer DisplayString,
    lcsStatusIpRouterQosEntryUpstreamRate INTEGER,
    lcsStatusIpRouterQosEntryDownstreamRate INTEGER,
    lcsStatusIpRouterQosEntryRxReserved INTEGER,
    lcsStatusIpRouterQosEntryRxRequested INTEGER,
    lcsStatusIpRouterQosEntryRxBlocksPending INTEGER,
    lcsStatusIpRouterQosEntryTxReserved INTEGER,
    lcsStatusIpRouterQosEntryTxRequested INTEGER,
    lcsStatusIpRouterQosEntryTxFavoured INTEGER,
    lcsStatusIpRouterQosEntryTxBlocksPending INTEGER,
    lcsStatusIpRouterQosEntryFragmentSize INTEGER,
    lcsStatusIpRouterQosEntryPmtuSize INTEGER
}

-- {COLUMN} 310.1.10.28.1.1
lcsStatusIpRouterQosEntryIfc OBJECT-TYPE
    SYNTAX     INTEGER
      {
        eDslCh1 (1),
        eModem (2)
      }
    MAX-ACCESS read-only
    STATUS     current
    DESCRIPTION
        "-- empty --"
    ::= { lcsStatusIpRouterQosEntry 1 }

-- {COLUMN} 310.1.10.28.1.2
lcsStatusIpRouterQosEntryPeer OBJECT-TYPE
    SYNTAX     DisplayString (SIZE(0..16))
    MAX-ACCESS read-only
    STATUS     current
    DESCRIPTION
        "-- empty --"
    ::= { lcsStatusIpRouterQosEntry 2 }

-- {COLUMN} 310.1.10.28.1.8
lcsStatusIpRouterQosEntryUpstreamRate OBJECT-TYPE
    SYNTAX     INTEGER (0..2147483647)
    MAX-ACCESS read-only
    STATUS     current
    DESCRIPTION
        "-- empty --"
    ::= { lcsStatusIpRouterQosEntry 8 }

-- {COLUMN} 310.1.10.28.1.3
lcsStatusIpRouterQosEntryDownstreamRate OBJECT-TYPE
    SYNTAX     INTEGER (0..2147483647)
    MAX-ACCESS read-only
    STATUS     current
    DESCRIPTION
        "-- empty --"
    ::= { lcsStatusIpRouterQosEntry 3 }

-- {COLUMN} 310.1.10.28.1.4
lcsStatusIpRouterQosEntryRxReserved OBJECT-TYPE
    SYNTAX     INTEGER (0..2147483647)
    MAX-ACCESS read-only
    STATUS     current
    DESCRIPTION
        "-- empty --"
    ::= { lcsStatusIpRouterQosEntry 4 }

-- {COLUMN} 310.1.10.28.1.11
lcsStatusIpRouterQosEntryRxRequested OBJECT-TYPE
    SYNTAX     INTEGER (0..2147483647)
    MAX-ACCESS read-only
    STATUS     current
    DESCRIPTION
        "-- empty --"
    ::= { lcsStatusIpRouterQosEntry 11 }

-- {COLUMN} 310.1.10.28.1.5
lcsStatusIpRouterQosEntryRxBlocksPending OBJECT-TYPE
    SYNTAX     INTEGER (0..65535)
    MAX-ACCESS read-only
    STATUS     current
    DESCRIPTION
        "-- empty --"
    ::= { lcsStatusIpRouterQosEntry 5 }

-- {COLUMN} 310.1.10.28.1.9
lcsStatusIpRouterQosEntryTxReserved OBJECT-TYPE
    SYNTAX     INTEGER (0..2147483647)
    MAX-ACCESS read-only
    STATUS     current
    DESCRIPTION
        "-- empty --"
    ::= { lcsStatusIpRouterQosEntry 9 }

-- {COLUMN} 310.1.10.28.1.12
lcsStatusIpRouterQosEntryTxRequested OBJECT-TYPE
    SYNTAX     INTEGER (0..2147483647)
    MAX-ACCESS read-only
    STATUS     current
    DESCRIPTION
        "-- empty --"
    ::= { lcsStatusIpRouterQosEntry 12 }

-- {COLUMN} 310.1.10.28.1.13
lcsStatusIpRouterQosEntryTxFavoured OBJECT-TYPE
    SYNTAX     INTEGER (0..2147483647)
    MAX-ACCESS read-only
    STATUS     current
    DESCRIPTION
        "-- empty --"
    ::= { lcsStatusIpRouterQosEntry 13 }

-- {COLUMN} 310.1.10.28.1.10
lcsStatusIpRouterQosEntryTxBlocksPending OBJECT-TYPE
    SYNTAX     INTEGER (0..65535)
    MAX-ACCESS read-only
    STATUS     current
    DESCRIPTION
        "-- empty --"
    ::= { lcsStatusIpRouterQosEntry 10 }

-- {COLUMN} 310.1.10.28.1.6
lcsStatusIpRouterQosEntryFragmentSize OBJECT-TYPE
    SYNTAX     INTEGER (0..65535)
    MAX-ACCESS read-only
    STATUS     current
    DESCRIPTION
        "-- empty --"
    ::= { lcsStatusIpRouterQosEntry 6 }

-- {COLUMN} 310.1.10.28.1.7
lcsStatusIpRouterQosEntryPmtuSize OBJECT-TYPE
    SYNTAX     INTEGER (0..65535)
    MAX-ACCESS read-only
    STATUS     current
    DESCRIPTION
        "-- empty --"
    ::= { lcsStatusIpRouterQosEntry 7 }

-- {SCALAR} 310.1.10.34
lcsStatusIpRouterRules OBJECT-TYPE
    SYNTAX     INTEGER (0..2147483647)
    MAX-ACCESS read-only
    STATUS     current
    DESCRIPTION
        "-- empty --"
    ::= { lcsStatusIpRouter 34 }

-- {SCALAR} 310.1.10.35
lcsStatusIpRouterFilter OBJECT-TYPE
    SYNTAX     INTEGER (0..2147483647)
    MAX-ACCESS read-only
    STATUS     current
    DESCRIPTION
        "-- empty --"
    ::= { lcsStatusIpRouter 35 }

-- {SCALAR} 310.1.10.31
lcsStatusIpRouterL4Errors OBJECT-TYPE
    SYNTAX     Counter32
    MAX-ACCESS read-only
    STATUS     current
    DESCRIPTION
        "-- empty --"
    ::= { lcsStatusIpRouter 31 }

-- {OID} 310.1.10.33
lcsStatusIpRouterVrrp OBJECT IDENTIFIER ::= { lcsStatusIpRouter 33 }

-- {SCALAR} 310.1.10.33.5
lcsStatusIpRouterVrrpOperating OBJECT-TYPE
    SYNTAX     INTEGER
      {
        eNo (0),
        eYes (1)
      }
    MAX-ACCESS read-only
    STATUS     current
    DESCRIPTION
        "-- empty --"
    ::= { lcsStatusIpRouterVrrp 5 }

-- {SCALAR} 310.1.10.33.1
lcsStatusIpRouterVrrpRx OBJECT-TYPE
    SYNTAX     Counter32
    MAX-ACCESS read-only
    STATUS     current
    DESCRIPTION
        "-- empty --"
    ::= { lcsStatusIpRouterVrrp 1 }

-- {SCALAR} 310.1.10.33.2
lcsStatusIpRouterVrrpTx OBJECT-TYPE
    SYNTAX     Counter32
    MAX-ACCESS read-only
    STATUS     current
    DESCRIPTION
        "-- empty --"
    ::= { lcsStatusIpRouterVrrp 2 }

-- {SCALAR} 310.1.10.33.3
lcsStatusIpRouterVrrpError OBJECT-TYPE
    SYNTAX     Counter32
    MAX-ACCESS read-only
    STATUS     current
    DESCRIPTION
        "-- empty --"
    ::= { lcsStatusIpRouterVrrp 3 }

-- {SCALAR} 310.1.10.33.4
lcsStatusIpRouterVrrpDrop OBJECT-TYPE
    SYNTAX     Counter32
    MAX-ACCESS read-only
    STATUS     current
    DESCRIPTION
        "-- empty --"
    ::= { lcsStatusIpRouterVrrp 4 }

-- {SCALAR} 310.1.10.33.7
lcsStatusIpRouterVrrpQueueErrors OBJECT-TYPE
    SYNTAX     Counter32
    MAX-ACCESS read-only
    STATUS     current
    DESCRIPTION
        "-- empty --"
    ::= { lcsStatusIpRouterVrrp 7 }

-- {SCALAR} 310.1.10.33.6
lcsStatusIpRouterVrrpInternalServices OBJECT-TYPE
    SYNTAX     INTEGER
      {
        eNo (0),
        eYes (1)
      }
    MAX-ACCESS read-only
    STATUS     current
    DESCRIPTION
        "-- empty --"
    ::= { lcsStatusIpRouterVrrp 6 }

-- {TABLE} 310.1.10.33.10
lcsStatusIpRouterVrrpVirtualRouterTable OBJECT-TYPE
    SYNTAX     SEQUENCE OF LcsStatusIpRouterVrrpVirtualRouterEntry
    MAX-ACCESS not-accessible
    STATUS     current
    DESCRIPTION
        "-- empty --"
    ::= { lcsStatusIpRouterVrrp 10 }

-- {ENTRY} 310.1.10.33.10.1
lcsStatusIpRouterVrrpVirtualRouterEntry OBJECT-TYPE
    SYNTAX     LcsStatusIpRouterVrrpVirtualRouterEntry
    MAX-ACCESS not-accessible
    STATUS     current
    DESCRIPTION
        ""
    INDEX {
        lcsStatusIpRouterVrrpVirtualRouterEntryRouterId
    }
    ::= { lcsStatusIpRouterVrrpVirtualRouterTable 1 }

-- {SEQUENCE}
LcsStatusIpRouterVrrpVirtualRouterEntry ::= SEQUENCE {
    lcsStatusIpRouterVrrpVirtualRouterEntryRouterId INTEGER,
    lcsStatusIpRouterVrrpVirtualRouterEntryVirtAddress IpAddress,
    lcsStatusIpRouterVrrpVirtualRouterEntryPrio INTEGER,
    lcsStatusIpRouterVrrpVirtualRouterEntryBPrio INTEGER,
    lcsStatusIpRouterVrrpVirtualRouterEntryPeer DisplayString,
    lcsStatusIpRouterVrrpVirtualRouterEntryState INTEGER,
    lcsStatusIpRouterVrrpVirtualRouterEntryBackup INTEGER,
    lcsStatusIpRouterVrrpVirtualRouterEntryMaster IpAddress,
    lcsStatusIpRouterVrrpVirtualRouterEntryPort INTEGER,
    lcsStatusIpRouterVrrpVirtualRouterEntryVlanId INTEGER,
    lcsStatusIpRouterVrrpVirtualRouterEntryNetworkName DisplayString
}

-- {COLUMN} 310.1.10.33.10.1.1
lcsStatusIpRouterVrrpVirtualRouterEntryRouterId OBJECT-TYPE
    SYNTAX     INTEGER (0..255)
    MAX-ACCESS read-only
    STATUS     current
    DESCRIPTION
        "-- empty --"
    ::= { lcsStatusIpRouterVrrpVirtualRouterEntry 1 }

-- {COLUMN} 310.1.10.33.10.1.2
lcsStatusIpRouterVrrpVirtualRouterEntryVirtAddress OBJECT-TYPE
    SYNTAX     IpAddress
    MAX-ACCESS read-only
    STATUS     current
    DESCRIPTION
        "-- empty --"
    ::= { lcsStatusIpRouterVrrpVirtualRouterEntry 2 }

-- {COLUMN} 310.1.10.33.10.1.3
lcsStatusIpRouterVrrpVirtualRouterEntryPrio OBJECT-TYPE
    SYNTAX     INTEGER (0..255)
    MAX-ACCESS read-only
    STATUS     current
    DESCRIPTION
        "-- empty --"
    ::= { lcsStatusIpRouterVrrpVirtualRouterEntry 3 }

-- {COLUMN} 310.1.10.33.10.1.4
lcsStatusIpRouterVrrpVirtualRouterEntryBPrio OBJECT-TYPE
    SYNTAX     INTEGER (0..255)
    MAX-ACCESS read-only
    STATUS     current
    DESCRIPTION
        "-- empty --"
    ::= { lcsStatusIpRouterVrrpVirtualRouterEntry 4 }

-- {COLUMN} 310.1.10.33.10.1.5
lcsStatusIpRouterVrrpVirtualRouterEntryPeer OBJECT-TYPE
    SYNTAX     DisplayString (SIZE(0..16))
    MAX-ACCESS read-only
    STATUS     current
    DESCRIPTION
        "-- empty --"
    ::= { lcsStatusIpRouterVrrpVirtualRouterEntry 5 }

-- {COLUMN} 310.1.10.33.10.1.6
lcsStatusIpRouterVrrpVirtualRouterEntryState OBJECT-TYPE
    SYNTAX     INTEGER
      {
        eInit (0),
        eListen (1),
        eStandby (2),
        eMaster (3),
        eDown (4),
        eReconnect (5)
      }
    MAX-ACCESS read-only
    STATUS     current
    DESCRIPTION
        "-- empty --"
    ::= { lcsStatusIpRouterVrrpVirtualRouterEntry 6 }

-- {COLUMN} 310.1.10.33.10.1.7
lcsStatusIpRouterVrrpVirtualRouterEntryBackup OBJECT-TYPE
    SYNTAX     INTEGER
      {
        eNo (0),
        eYes (1)
      }
    MAX-ACCESS read-only
    STATUS     current
    DESCRIPTION
        "-- empty --"
    ::= { lcsStatusIpRouterVrrpVirtualRouterEntry 7 }

-- {COLUMN} 310.1.10.33.10.1.8
lcsStatusIpRouterVrrpVirtualRouterEntryMaster OBJECT-TYPE
    SYNTAX     IpAddress
    MAX-ACCESS read-only
    STATUS     current
    DESCRIPTION
        "-- empty --"
    ::= { lcsStatusIpRouterVrrpVirtualRouterEntry 8 }

-- {COLUMN} 310.1.10.33.10.1.12
lcsStatusIpRouterVrrpVirtualRouterEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusIpRouterVrrpVirtualRouterEntry 12 }

-- {COLUMN} 310.1.10.33.10.1.10
lcsStatusIpRouterVrrpVirtualRouterEntryVlanId OBJECT-TYPE
    SYNTAX     INTEGER (0..65535)
    MAX-ACCESS read-only
    STATUS     current
    DESCRIPTION
        "-- empty --"
    ::= { lcsStatusIpRouterVrrpVirtualRouterEntry 10 }

-- {COLUMN} 310.1.10.33.10.1.11
lcsStatusIpRouterVrrpVirtualRouterEntryNetworkName OBJECT-TYPE
    SYNTAX     DisplayString (SIZE(0..16))
    MAX-ACCESS read-only
    STATUS     current
    DESCRIPTION
        "-- empty --"
    ::= { lcsStatusIpRouterVrrpVirtualRouterEntry 11 }

-- {TABLE} 310.1.10.33.11
lcsStatusIpRouterVrrpMacListTable OBJECT-TYPE
    SYNTAX     SEQUENCE OF LcsStatusIpRouterVrrpMacListEntry
    MAX-ACCESS not-accessible
    STATUS     current
    DESCRIPTION
        "-- empty --"
    ::= { lcsStatusIpRouterVrrp 11 }

-- {ENTRY} 310.1.10.33.11.1
lcsStatusIpRouterVrrpMacListEntry OBJECT-TYPE
    SYNTAX     LcsStatusIpRouterVrrpMacListEntry
    MAX-ACCESS not-accessible
    STATUS     current
    DESCRIPTION
        ""
    INDEX {
        lcsStatusIpRouterVrrpMacListEntryVirtAddress
    }
    ::= { lcsStatusIpRouterVrrpMacListTable 1 }

-- {SEQUENCE}
LcsStatusIpRouterVrrpMacListEntry ::= SEQUENCE {
    lcsStatusIpRouterVrrpMacListEntryVirtAddress IpAddress,
    lcsStatusIpRouterVrrpMacListEntryMacAddress MacAddress,
    lcsStatusIpRouterVrrpMacListEntryRouterId INTEGER
}

-- {COLUMN} 310.1.10.33.11.1.1
lcsStatusIpRouterVrrpMacListEntryVirtAddress OBJECT-TYPE
    SYNTAX     IpAddress
    MAX-ACCESS read-only
    STATUS     current
    DESCRIPTION
        "-- empty --"
    ::= { lcsStatusIpRouterVrrpMacListEntry 1 }

-- {COLUMN} 310.1.10.33.11.1.2
lcsStatusIpRouterVrrpMacListEntryMacAddress OBJECT-TYPE
    SYNTAX     MacAddress
    MAX-ACCESS read-only
    STATUS     current
    DESCRIPTION
        "-- empty --"
    ::= { lcsStatusIpRouterVrrpMacListEntry 2 }

-- {COLUMN} 310.1.10.33.11.1.3
lcsStatusIpRouterVrrpMacListEntryRouterId OBJECT-TYPE
    SYNTAX     INTEGER (0..255)
    MAX-ACCESS read-only
    STATUS     current
    DESCRIPTION
        "-- empty --"
    ::= { lcsStatusIpRouterVrrpMacListEntry 3 }

-- {TABLE} 310.1.10.33.12
lcsStatusIpRouterVrrpEventLogTable OBJECT-TYPE
    SYNTAX     SEQUENCE OF LcsStatusIpRouterVrrpEventLogEntry
    MAX-ACCESS not-accessible
    STATUS     current
    DESCRIPTION
        "-- empty --"
    ::= { lcsStatusIpRouterVrrp 12 }

-- {ENTRY} 310.1.10.33.12.1
lcsStatusIpRouterVrrpEventLogEntry OBJECT-TYPE
    SYNTAX     LcsStatusIpRouterVrrpEventLogEntry
    MAX-ACCESS not-accessible
    STATUS     current
    DESCRIPTION
        ""
    INDEX {
        lcsStatusIpRouterVrrpEventLogEntryIdx
    }
    ::= { lcsStatusIpRouterVrrpEventLogTable 1 }

-- {SEQUENCE}
LcsStatusIpRouterVrrpEventLogEntry ::= SEQUENCE {
    lcsStatusIpRouterVrrpEventLogEntryIdx INTEGER,
    lcsStatusIpRouterVrrpEventLogEntrySystemTime DisplayString,
    lcsStatusIpRouterVrrpEventLogEntrySrcAddress IpAddress,
    lcsStatusIpRouterVrrpEventLogEntryVrid INTEGER,
    lcsStatusIpRouterVrrpEventLogEntryEvent INTEGER,
    lcsStatusIpRouterVrrpEventLogEntryInfo DisplayString
}

-- {COLUMN} 310.1.10.33.12.1.1
lcsStatusIpRouterVrrpEventLogEntryIdx OBJECT-TYPE
    SYNTAX     INTEGER (0..65535)
    MAX-ACCESS read-only
    STATUS     current
    DESCRIPTION
        "-- empty --"
    ::= { lcsStatusIpRouterVrrpEventLogEntry 1 }

-- {COLUMN} 310.1.10.33.12.1.2
lcsStatusIpRouterVrrpEventLogEntrySystemTime OBJECT-TYPE
    SYNTAX     DisplayString (SIZE(0..19))
    MAX-ACCESS read-only
    STATUS     current
    DESCRIPTION
        "-- empty --"
    ::= { lcsStatusIpRouterVrrpEventLogEntry 2 }

-- {COLUMN} 310.1.10.33.12.1.3
lcsStatusIpRouterVrrpEventLogEntrySrcAddress OBJECT-TYPE
    SYNTAX     IpAddress
    MAX-ACCESS read-only
    STATUS     current
    DESCRIPTION
        "-- empty --"
    ::= { lcsStatusIpRouterVrrpEventLogEntry 3 }

-- {COLUMN} 310.1.10.33.12.1.4
lcsStatusIpRouterVrrpEventLogEntryVrid OBJECT-TYPE
    SYNTAX     INTEGER (0..255)
    MAX-ACCESS read-only
    STATUS     current
    DESCRIPTION
        "-- empty --"
    ::= { lcsStatusIpRouterVrrpEventLogEntry 4 }

-- {COLUMN} 310.1.10.33.12.1.5
lcsStatusIpRouterVrrpEventLogEntryEvent OBJECT-TYPE
    SYNTAX     INTEGER
      {
        eInvalidTtl (1),
        eInvalidVersion (2),
        eBadNumberOfVirtualAddresses (3),
        eBadAuthenticationType (4),
        eBadAdvertisementInterval (5),
        eInvalidVrid (6),
        eInvalidRouterAddress (7),
        eInvalidPriority (8),
        eVirtualRouterStopped (9),
        eVirtualRouterStarted (10),
        eLinkUp (11),
        eLinkDown (12),
        eNewMaster (13),
        eBackupStarted (14),
        eBackupEnded (15)
      }
    MAX-ACCESS read-only
    STATUS     current
    DESCRIPTION
        "-- empty --"
    ::= { lcsStatusIpRouterVrrpEventLogEntry 5 }

-- {COLUMN} 310.1.10.33.12.1.6
lcsStatusIpRouterVrrpEventLogEntryInfo OBJECT-TYPE
    SYNTAX     DisplayString (SIZE(0..255))
    MAX-ACCESS read-only
    STATUS     current
    DESCRIPTION
        "-- empty --"
    ::= { lcsStatusIpRouterVrrpEventLogEntry 6 }

-- {SCALAR} 310.1.10.33.20
lcsStatusIpRouterVrrpDeleteValues OBJECT-TYPE
    SYNTAX     DisplayString
    MAX-ACCESS read-write
    STATUS     current
    DESCRIPTION
        "-- empty --"
    ::= { lcsStatusIpRouterVrrp 20 }

-- {TABLE} 310.1.10.30
lcsStatusIpRouterActIpRoutingTabTable OBJECT-TYPE
    SYNTAX     SEQUENCE OF LcsStatusIpRouterActIpRoutingTabEntry
    MAX-ACCESS not-accessible
    STATUS     current
    DESCRIPTION
        "-- empty --"
    ::= { lcsStatusIpRouter 30 }

-- {ENTRY} 310.1.10.30.1
lcsStatusIpRouterActIpRoutingTabEntry OBJECT-TYPE
    SYNTAX     LcsStatusIpRouterActIpRoutingTabEntry
    MAX-ACCESS not-accessible
    STATUS     current
    DESCRIPTION
        ""
    INDEX {
        lcsStatusIpRouterActIpRoutingTabEntryIpAddress,
        lcsStatusIpRouterActIpRoutingTabEntryIpNetmask,
        lcsStatusIpRouterActIpRoutingTabEntryRtgTag
    }
    ::= { lcsStatusIpRouterActIpRoutingTabTable 1 }

-- {SEQUENCE}
LcsStatusIpRouterActIpRoutingTabEntry ::= SEQUENCE {
    lcsStatusIpRouterActIpRoutingTabEntryIpAddress IpAddress,
    lcsStatusIpRouterActIpRoutingTabEntryIpNetmask IpAddress,
    lcsStatusIpRouterActIpRoutingTabEntryRtgTag INTEGER,
    lcsStatusIpRouterActIpRoutingTabEntryGateway IpAddress,
    lcsStatusIpRouterActIpRoutingTabEntryPeer DisplayString,
    lcsStatusIpRouterActIpRoutingTabEntryDistance INTEGER,
    lcsStatusIpRouterActIpRoutingTabEntryMasquerade INTEGER,
    lcsStatusIpRouterActIpRoutingTabEntryType INTEGER
}

-- {COLUMN} 310.1.10.30.1.1
lcsStatusIpRouterActIpRoutingTabEntryIpAddress OBJECT-TYPE
    SYNTAX     IpAddress
    MAX-ACCESS read-only
    STATUS     current
    DESCRIPTION
        "-- empty --"
    ::= { lcsStatusIpRouterActIpRoutingTabEntry 1 }

-- {COLUMN} 310.1.10.30.1.2
lcsStatusIpRouterActIpRoutingTabEntryIpNetmask OBJECT-TYPE
    SYNTAX     IpAddress
    MAX-ACCESS read-only
    STATUS     current
    DESCRIPTION
        "-- empty --"
    ::= { lcsStatusIpRouterActIpRoutingTabEntry 2 }

-- {COLUMN} 310.1.10.30.1.3
lcsStatusIpRouterActIpRoutingTabEntryRtgTag OBJECT-TYPE
    SYNTAX     INTEGER (0..65535)
    MAX-ACCESS read-only
    STATUS     current
    DESCRIPTION
        "-- empty --"
    ::= { lcsStatusIpRouterActIpRoutingTabEntry 3 }

-- {COLUMN} 310.1.10.30.1.4
lcsStatusIpRouterActIpRoutingTabEntryGateway OBJECT-TYPE
    SYNTAX     IpAddress
    MAX-ACCESS read-only
    STATUS     current
    DESCRIPTION
        "-- empty --"
    ::= { lcsStatusIpRouterActIpRoutingTabEntry 4 }

-- {COLUMN} 310.1.10.30.1.5
lcsStatusIpRouterActIpRoutingTabEntryPeer OBJECT-TYPE
    SYNTAX     DisplayString (SIZE(0..255))
    MAX-ACCESS read-only
    STATUS     current
    DESCRIPTION
        "-- empty --"
    ::= { lcsStatusIpRouterActIpRoutingTabEntry 5 }

-- {COLUMN} 310.1.10.30.1.6
lcsStatusIpRouterActIpRoutingTabEntryDistance OBJECT-TYPE
    SYNTAX     INTEGER (0..255)
    MAX-ACCESS read-only
    STATUS     current
    DESCRIPTION
        "-- empty --"
    ::= { lcsStatusIpRouterActIpRoutingTabEntry 6 }

-- {COLUMN} 310.1.10.30.1.7
lcsStatusIpRouterActIpRoutingTabEntryMasquerade OBJECT-TYPE
    SYNTAX     INTEGER
      {
        eNo (0),
        eOn (1),
        eIntranet (2),
        eUnknown (255)
      }
    MAX-ACCESS read-only
    STATUS     current
    DESCRIPTION
        "-- empty --"
    ::= { lcsStatusIpRouterActIpRoutingTabEntry 7 }

-- {COLUMN} 310.1.10.30.1.8
lcsStatusIpRouterActIpRoutingTabEntryType OBJECT-TYPE
    SYNTAX     INTEGER
      {
        eUnknown (0),
        eStatic (1),
        eRip (2),
        eVpn (3),
        eCapwap (4),
        eRas (5),
        eIntranet (6),
        eDmz (7),
        eDisabled (8)
      }
    MAX-ACCESS read-only
    STATUS     current
    DESCRIPTION
        "-- empty --"
    ::= { lcsStatusIpRouterActIpRoutingTabEntry 8 }

-- {OID} 310.1.11
lcsStatusConfig OBJECT IDENTIFIER ::= { lcsStatus 11 }

-- {SCALAR} 310.1.11.1
lcsStatusConfigLanActiveConnections OBJECT-TYPE
    SYNTAX     INTEGER (0..65535)
    MAX-ACCESS read-only
    STATUS     current
    DESCRIPTION
        "-- empty --"
    ::= { lcsStatusConfig 1 }

-- {SCALAR} 310.1.11.2
lcsStatusConfigLanTotalConnections OBJECT-TYPE
    SYNTAX     Counter32
    MAX-ACCESS read-only
    STATUS     current
    DESCRIPTION
        "-- empty --"
    ::= { lcsStatusConfig 2 }

-- {SCALAR} 310.1.11.3
lcsStatusConfigWanActiveConnections OBJECT-TYPE
    SYNTAX     INTEGER (0..65535)
    MAX-ACCESS read-only
    STATUS     current
    DESCRIPTION
        "-- empty --"
    ::= { lcsStatusConfig 3 }

-- {SCALAR} 310.1.11.4
lcsStatusConfigWanTotalConnections OBJECT-TYPE
    SYNTAX     Counter32
    MAX-ACCESS read-only
    STATUS     current
    DESCRIPTION
        "-- empty --"
    ::= { lcsStatusConfig 4 }

-- {SCALAR} 310.1.11.5
lcsStatusConfigOutbandActiveConnections OBJECT-TYPE
    SYNTAX     INTEGER (0..65535)
    MAX-ACCESS read-only
    STATUS     current
    DESCRIPTION
        "-- empty --"
    ::= { lcsStatusConfig 5 }

-- {SCALAR} 310.1.11.6
lcsStatusConfigOutbandTotalConnections OBJECT-TYPE
    SYNTAX     Counter32
    MAX-ACCESS read-only
    STATUS     current
    DESCRIPTION
        "-- empty --"
    ::= { lcsStatusConfig 6 }

-- {SCALAR} 310.1.11.7
lcsStatusConfigOutbandBitrate OBJECT-TYPE
    SYNTAX     INTEGER (0..2147483647)
    MAX-ACCESS read-only
    STATUS     current
    DESCRIPTION
        "-- empty --"
    ::= { lcsStatusConfig 7 }

-- {SCALAR} 310.1.11.8
lcsStatusConfigLoginErrors OBJECT-TYPE
    SYNTAX     Counter32
    MAX-ACCESS read-only
    STATUS     current
    DESCRIPTION
        "-- empty --"
    ::= { lcsStatusConfig 8 }

-- {SCALAR} 310.1.11.9
lcsStatusConfigLoginLocks OBJECT-TYPE
    SYNTAX     Counter32
    MAX-ACCESS read-only
    STATUS     current
    DESCRIPTION
        "-- empty --"
    ::= { lcsStatusConfig 9 }

-- {SCALAR} 310.1.11.10
lcsStatusConfigLoginRejects OBJECT-TYPE
    SYNTAX     Counter32
    MAX-ACCESS read-only
    STATUS     current
    DESCRIPTION
        "-- empty --"
    ::= { lcsStatusConfig 10 }

-- {SCALAR} 310.1.11.13
lcsStatusConfigStartScan OBJECT-TYPE
    SYNTAX     DisplayString
    MAX-ACCESS read-write
    STATUS     current
    DESCRIPTION
        "-- empty --"
    ::= { lcsStatusConfig 13 }

-- {TABLE} 310.1.11.14
lcsStatusConfigScanResultsTable OBJECT-TYPE
    SYNTAX     SEQUENCE OF LcsStatusConfigScanResultsEntry
    MAX-ACCESS not-accessible
    STATUS     current
    DESCRIPTION
        "-- empty --"
    ::= { lcsStatusConfig 14 }

-- {ENTRY} 310.1.11.14.1
lcsStatusConfigScanResultsEntry OBJECT-TYPE
    SYNTAX     LcsStatusConfigScanResultsEntry
    MAX-ACCESS not-accessible
    STATUS     current
    DESCRIPTION
        ""
    INDEX {
        lcsStatusConfigScanResultsEntryIpAddress,
        lcsStatusConfigScanResultsEntryRtgTag
    }
    ::= { lcsStatusConfigScanResultsTable 1 }

-- {SEQUENCE}
LcsStatusConfigScanResultsEntry ::= SEQUENCE {
    lcsStatusConfigScanResultsEntryIpAddress IpAddress,
    lcsStatusConfigScanResultsEntryRtgTag INTEGER,
    lcsStatusConfigScanResultsEntryName DisplayString,
    lcsStatusConfigScanResultsEntryDeviceType DisplayString,
    lcsStatusConfigScanResultsEntryVersion DisplayString,
    lcsStatusConfigScanResultsEntryCapiPort INTEGER,
    lcsStatusConfigScanResultsEntryHttpPort INTEGER,
    lcsStatusConfigScanResultsEntryHttpsPort INTEGER,
    lcsStatusConfigScanResultsEntryState INTEGER
}

-- {COLUMN} 310.1.11.14.1.1
lcsStatusConfigScanResultsEntryIpAddress OBJECT-TYPE
    SYNTAX     IpAddress
    MAX-ACCESS read-only
    STATUS     current
    DESCRIPTION
        "-- empty --"
    ::= { lcsStatusConfigScanResultsEntry 1 }

-- {COLUMN} 310.1.11.14.1.9
lcsStatusConfigScanResultsEntryRtgTag OBJECT-TYPE
    SYNTAX     INTEGER (0..65535)
    MAX-ACCESS read-only
    STATUS     current
    DESCRIPTION
        "-- empty --"
    ::= { lcsStatusConfigScanResultsEntry 9 }

-- {COLUMN} 310.1.11.14.1.2
lcsStatusConfigScanResultsEntryName OBJECT-TYPE
    SYNTAX     DisplayString (SIZE(0..17))
    MAX-ACCESS read-only
    STATUS     current
    DESCRIPTION
        "-- empty --"
    ::= { lcsStatusConfigScanResultsEntry 2 }

-- {COLUMN} 310.1.11.14.1.3
lcsStatusConfigScanResultsEntryDeviceType OBJECT-TYPE
    SYNTAX     DisplayString (SIZE(0..64))
    MAX-ACCESS read-only
    STATUS     current
    DESCRIPTION
        "-- empty --"
    ::= { lcsStatusConfigScanResultsEntry 3 }

-- {COLUMN} 310.1.11.14.1.4
lcsStatusConfigScanResultsEntryVersion OBJECT-TYPE
    SYNTAX     DisplayString (SIZE(0..30))
    MAX-ACCESS read-only
    STATUS     current
    DESCRIPTION
        "-- empty --"
    ::= { lcsStatusConfigScanResultsEntry 4 }

-- {COLUMN} 310.1.11.14.1.6
lcsStatusConfigScanResultsEntryCapiPort OBJECT-TYPE
    SYNTAX     INTEGER (0..65535)
    MAX-ACCESS read-only
    STATUS     current
    DESCRIPTION
        "-- empty --"
    ::= { lcsStatusConfigScanResultsEntry 6 }

-- {COLUMN} 310.1.11.14.1.7
lcsStatusConfigScanResultsEntryHttpPort OBJECT-TYPE
    SYNTAX     INTEGER (0..65535)
    MAX-ACCESS read-only
    STATUS     current
    DESCRIPTION
        "-- empty --"
    ::= { lcsStatusConfigScanResultsEntry 7 }

-- {COLUMN} 310.1.11.14.1.8
lcsStatusConfigScanResultsEntryHttpsPort OBJECT-TYPE
    SYNTAX     INTEGER (0..65535)
    MAX-ACCESS read-only
    STATUS     current
    DESCRIPTION
        "-- empty --"
    ::= { lcsStatusConfigScanResultsEntry 8 }

-- {COLUMN} 310.1.11.14.1.5
lcsStatusConfigScanResultsEntryState OBJECT-TYPE
    SYNTAX     INTEGER
      {
        eScanning (0),
        eReady (1),
        eError (2)
      }
    MAX-ACCESS read-only
    STATUS     current
    DESCRIPTION
        "-- empty --"
    ::= { lcsStatusConfigScanResultsEntry 5 }

-- {TABLE} 310.1.11.16
lcsStatusConfigFeaturesTable OBJECT-TYPE
    SYNTAX     SEQUENCE OF LcsStatusConfigFeaturesEntry
    MAX-ACCESS not-accessible
    STATUS     current
    DESCRIPTION
        "-- empty --"
    ::= { lcsStatusConfig 16 }

-- {ENTRY} 310.1.11.16.1
lcsStatusConfigFeaturesEntry OBJECT-TYPE
    SYNTAX     LcsStatusConfigFeaturesEntry
    MAX-ACCESS not-accessible
    STATUS     current
    DESCRIPTION
        ""
    INDEX {
        lcsStatusConfigFeaturesEntryFeature,
        lcsStatusConfigFeaturesEntryIndex
    }
    ::= { lcsStatusConfigFeaturesTable 1 }

-- {SEQUENCE}
LcsStatusConfigFeaturesEntry ::= SEQUENCE {
    lcsStatusConfigFeaturesEntryFeature INTEGER,
    lcsStatusConfigFeaturesEntryExpires DisplayString,
    lcsStatusConfigFeaturesEntryExpire Gauge32,
    lcsStatusConfigFeaturesEntryState INTEGER,
    lcsStatusConfigFeaturesEntryIndex INTEGER,
    lcsStatusConfigFeaturesEntryCount INTEGER
}

-- {COLUMN} 310.1.11.16.1.1
lcsStatusConfigFeaturesEntryFeature OBJECT-TYPE
    SYNTAX     INTEGER
      {
        eIpx (1),
        eLanBridge (2),
        eLancapi (3),
        eLeasedLine (4),
        eSwitchedLine (5),
        eDslInterface (6),
        eFax (7),
        eModem (8),
        eVpn5 (9),
        eVpn25 (10),
        eCommonCriteria (11),
        eProductionOk (12),
        eVpn100 (13),
        eWlc4025100 (14),
        eWlanPointToPoint (15),
        ePublicSpot (16),
        eVpn200 (17),
        eVpn500 (18),
        eVpn1000 (19),
        eHermes1Wpa (20),
        eVpn3 (21),
        eUmts (22),
        eDynamicVpn (23),
        eWlan5ghz (24),
        eWlanNoEncryption (25),
        eVoipAdvanced32 (26),
        eVoipBasic (27),
        eWlanFccRestrictions (28),
        eWlc402550 (29),
        eWlc400612 (30),
        eVoipAdvanced8 (31),
        eContentfilterAdditive (36),
        eWlcPublicSpot (37),
        eWlanMonitorMode (38),
        eWlanNo5ghz (39),
        eWlcApUpgrade (40),
        eWlanDfs3 (41),
        eInProduction (42),
        eNetioServer (43),
        eLanWlanBridge (44),
        eEthernetIp (45),
        eProfinet (46),
        eWlanFilteredAveraging (47),
        eVpn50 (48),
        eWlcApBasic (49),
        ePms (50)
      }
    MAX-ACCESS read-only
    STATUS     current
    DESCRIPTION
        "-- empty --"
    ::= { lcsStatusConfigFeaturesEntry 1 }

-- {COLUMN} 310.1.11.16.1.2
lcsStatusConfigFeaturesEntryExpires OBJECT-TYPE
    SYNTAX     DisplayString (SIZE(0..255))
    MAX-ACCESS read-only
    STATUS     current
    DESCRIPTION
        "-- empty --"
    ::= { lcsStatusConfigFeaturesEntry 2 }

-- {COLUMN} 310.1.11.16.1.3
lcsStatusConfigFeaturesEntryExpire OBJECT-TYPE
    SYNTAX     Gauge32
    MAX-ACCESS read-only
    STATUS     current
    DESCRIPTION
        "-- empty --"
    ::= { lcsStatusConfigFeaturesEntry 3 }

-- {COLUMN} 310.1.11.16.1.4
lcsStatusConfigFeaturesEntryState OBJECT-TYPE
    SYNTAX     INTEGER
      {
        eLocked (0),
        eActive (1),
        eHidden (2),
        eExpired (3)
      }
    MAX-ACCESS read-only
    STATUS     current
    DESCRIPTION
        "-- empty --"
    ::= { lcsStatusConfigFeaturesEntry 4 }

-- {COLUMN} 310.1.11.16.1.5
lcsStatusConfigFeaturesEntryIndex OBJECT-TYPE
    SYNTAX     INTEGER (0..2147483647)
    MAX-ACCESS read-only
    STATUS     current
    DESCRIPTION
        "-- empty --"
    ::= { lcsStatusConfigFeaturesEntry 5 }

-- {COLUMN} 310.1.11.16.1.6
lcsStatusConfigFeaturesEntryCount OBJECT-TYPE
    SYNTAX     INTEGER (0..2147483647)
    MAX-ACCESS read-only
    STATUS     current
    DESCRIPTION
        "-- empty --"
    ::= { lcsStatusConfigFeaturesEntry 6 }

-- {OID} 310.1.11.65
lcsStatusConfigLl2m OBJECT IDENTIFIER ::= { lcsStatusConfig 65 }

-- {SCALAR} 310.1.11.65.1
lcsStatusConfigLl2mRxPackets OBJECT-TYPE
    SYNTAX     INTEGER (0..2147483647)
    MAX-ACCESS read-only
    STATUS     current
    DESCRIPTION
        "-- empty --"
    ::= { lcsStatusConfigLl2m 1 }

-- {SCALAR} 310.1.11.65.2
lcsStatusConfigLl2mRxBroadcastPackets OBJECT-TYPE
    SYNTAX     INTEGER (0..2147483647)
    MAX-ACCESS read-only
    STATUS     current
    DESCRIPTION
        "-- empty --"
    ::= { lcsStatusConfigLl2m 2 }

-- {SCALAR} 310.1.11.65.3
lcsStatusConfigLl2mRxMulticastPackets OBJECT-TYPE
    SYNTAX     INTEGER (0..2147483647)
    MAX-ACCESS read-only
    STATUS     current
    DESCRIPTION
        "-- empty --"
    ::= { lcsStatusConfigLl2m 3 }

-- {SCALAR} 310.1.11.65.4
lcsStatusConfigLl2mRxUnicastPackets OBJECT-TYPE
    SYNTAX     INTEGER (0..2147483647)
    MAX-ACCESS read-only
    STATUS     current
    DESCRIPTION
        "-- empty --"
    ::= { lcsStatusConfigLl2m 4 }

-- {SCALAR} 310.1.11.65.5
lcsStatusConfigLl2mRxDiscard OBJECT-TYPE
    SYNTAX     INTEGER (0..2147483647)
    MAX-ACCESS read-only
    STATUS     current
    DESCRIPTION
        "-- empty --"
    ::= { lcsStatusConfigLl2m 5 }

-- {SCALAR} 310.1.11.65.6
lcsStatusConfigLl2mRxMalformed OBJECT-TYPE
    SYNTAX     INTEGER (0..2147483647)
    MAX-ACCESS read-only
    STATUS     current
    DESCRIPTION
        "-- empty --"
    ::= { lcsStatusConfigLl2m 6 }

-- {OID} 310.1.11.65.20
lcsStatusConfigLl2mServer OBJECT IDENTIFIER ::= { lcsStatusConfigLl2m 20 }

-- {SCALAR} 310.1.11.65.20.1
lcsStatusConfigLl2mServerRxPackets OBJECT-TYPE
    SYNTAX     INTEGER (0..2147483647)
    MAX-ACCESS read-only
    STATUS     current
    DESCRIPTION
        "-- empty --"
    ::= { lcsStatusConfigLl2mServer 1 }

-- {SCALAR} 310.1.11.65.20.2
lcsStatusConfigLl2mServerRxBroadcastPackets OBJECT-TYPE
    SYNTAX     INTEGER (0..2147483647)
    MAX-ACCESS read-only
    STATUS     current
    DESCRIPTION
        "-- empty --"
    ::= { lcsStatusConfigLl2mServer 2 }

-- {SCALAR} 310.1.11.65.20.3
lcsStatusConfigLl2mServerRxMulticastPackets OBJECT-TYPE
    SYNTAX     INTEGER (0..2147483647)
    MAX-ACCESS read-only
    STATUS     current
    DESCRIPTION
        "-- empty --"
    ::= { lcsStatusConfigLl2mServer 3 }

-- {SCALAR} 310.1.11.65.20.4
lcsStatusConfigLl2mServerRxUnicastPackets OBJECT-TYPE
    SYNTAX     INTEGER (0..2147483647)
    MAX-ACCESS read-only
    STATUS     current
    DESCRIPTION
        "-- empty --"
    ::= { lcsStatusConfigLl2mServer 4 }

-- {SCALAR} 310.1.11.65.20.5
lcsStatusConfigLl2mServerRxDiscard OBJECT-TYPE
    SYNTAX     INTEGER (0..2147483647)
    MAX-ACCESS read-only
    STATUS     current
    DESCRIPTION
        "-- empty --"
    ::= { lcsStatusConfigLl2mServer 5 }

-- {SCALAR} 310.1.11.65.20.99
lcsStatusConfigLl2mServerDeleteValues OBJECT-TYPE
    SYNTAX     DisplayString
    MAX-ACCESS read-write
    STATUS     current
    DESCRIPTION
        "-- empty --"
    ::= { lcsStatusConfigLl2mServer 99 }

-- {OID} 310.1.11.65.30
lcsStatusConfigLl2mClient OBJECT IDENTIFIER ::= { lcsStatusConfigLl2m 30 }

-- {SCALAR} 310.1.11.65.30.1
lcsStatusConfigLl2mClientRxPackets OBJECT-TYPE
    SYNTAX     INTEGER (0..2147483647)
    MAX-ACCESS read-only
    STATUS     current
    DESCRIPTION
        "-- empty --"
    ::= { lcsStatusConfigLl2mClient 1 }

-- {SCALAR} 310.1.11.65.30.2
lcsStatusConfigLl2mClientRxBroadcastPackets OBJECT-TYPE
    SYNTAX     INTEGER (0..2147483647)
    MAX-ACCESS read-only
    STATUS     current
    DESCRIPTION
        "-- empty --"
    ::= { lcsStatusConfigLl2mClient 2 }

-- {SCALAR} 310.1.11.65.30.3
lcsStatusConfigLl2mClientRxMulticastPackets OBJECT-TYPE
    SYNTAX     INTEGER (0..2147483647)
    MAX-ACCESS read-only
    STATUS     current
    DESCRIPTION
        "-- empty --"
    ::= { lcsStatusConfigLl2mClient 3 }

-- {SCALAR} 310.1.11.65.30.4
lcsStatusConfigLl2mClientRxUnicastPackets OBJECT-TYPE
    SYNTAX     INTEGER (0..2147483647)
    MAX-ACCESS read-only
    STATUS     current
    DESCRIPTION
        "-- empty --"
    ::= { lcsStatusConfigLl2mClient 4 }

-- {SCALAR} 310.1.11.65.30.5
lcsStatusConfigLl2mClientRxDiscard OBJECT-TYPE
    SYNTAX     INTEGER (0..2147483647)
    MAX-ACCESS read-only
    STATUS     current
    DESCRIPTION
        "-- empty --"
    ::= { lcsStatusConfigLl2mClient 5 }

-- {SCALAR} 310.1.11.65.30.99
lcsStatusConfigLl2mClientDeleteValues OBJECT-TYPE
    SYNTAX     DisplayString
    MAX-ACCESS read-write
    STATUS     current
    DESCRIPTION
        "-- empty --"
    ::= { lcsStatusConfigLl2mClient 99 }

-- {SCALAR} 310.1.11.65.99
lcsStatusConfigLl2mDeleteValues OBJECT-TYPE
    SYNTAX     DisplayString
    MAX-ACCESS read-write
    STATUS     current
    DESCRIPTION
        "-- empty --"
    ::= { lcsStatusConfigLl2m 99 }

-- {SCALAR} 310.1.11.11
lcsStatusConfigDeleteValues OBJECT-TYPE
    SYNTAX     DisplayString
    MAX-ACCESS read-write
    STATUS     current
    DESCRIPTION
        "-- empty --"
    ::= { lcsStatusConfig 11 }

-- {TABLE} 310.1.11.12
lcsStatusConfigEventLogTable OBJECT-TYPE
    SYNTAX     SEQUENCE OF LcsStatusConfigEventLogEntry
    MAX-ACCESS not-accessible
    STATUS     current
    DESCRIPTION
        "-- empty --"
    ::= { lcsStatusConfig 12 }

-- {ENTRY} 310.1.11.12.1
lcsStatusConfigEventLogEntry OBJECT-TYPE
    SYNTAX     LcsStatusConfigEventLogEntry
    MAX-ACCESS not-accessible
    STATUS     current
    DESCRIPTION
        ""
    INDEX {
        lcsStatusConfigEventLogEntryIdx
    }
    ::= { lcsStatusConfigEventLogTable 1 }

-- {SEQUENCE}
LcsStatusConfigEventLogEntry ::= SEQUENCE {
    lcsStatusConfigEventLogEntryIdx INTEGER,
    lcsStatusConfigEventLogEntrySystemTime DisplayString,
    lcsStatusConfigEventLogEntryEvent INTEGER,
    lcsStatusConfigEventLogEntryAccess INTEGER,
    lcsStatusConfigEventLogEntryIpAddressNew DisplayString,
    lcsStatusConfigEventLogEntryInfo1 DisplayString,
    lcsStatusConfigEventLogEntryInfo2 DisplayString
}

-- {COLUMN} 310.1.11.12.1.1
lcsStatusConfigEventLogEntryIdx OBJECT-TYPE
    SYNTAX     INTEGER (0..255)
    MAX-ACCESS read-only
    STATUS     current
    DESCRIPTION
        "-- empty --"
    ::= { lcsStatusConfigEventLogEntry 1 }

-- {COLUMN} 310.1.11.12.1.7
lcsStatusConfigEventLogEntrySystemTime OBJECT-TYPE
    SYNTAX     DisplayString (SIZE(0..19))
    MAX-ACCESS read-only
    STATUS     current
    DESCRIPTION
        "-- empty --"
    ::= { lcsStatusConfigEventLogEntry 7 }

-- {COLUMN} 310.1.11.12.1.2
lcsStatusConfigEventLogEntryEvent OBJECT-TYPE
    SYNTAX     INTEGER
      {
        eFwUplStart (4), -- Firmware upload was started
        eUplsucc (5), -- Firmware or configuration upload successful
        eUplfailto (6), -- The upload the firmware or configuration failed: maximum time was exceeded
        eUplfailincl (7), -- The upload the firmware or configuration failed: incomplete configuration
        eUplfailbaddev (8), -- The upload the firmware or configuration failed: wrong device
        eUplinvversion (7000),
        eUplfileexists (7001),
        eLogin (9), -- Login to configuration successful
        eLogout (10), -- Logout from configuration was successful
        eCnfuplstart (11), -- Configuration upload was started
        eCnfdnlstart (12), -- Configuration download was started
        eScrptuplstart (79),
        eScrptdnlstart (80),
        eCnfdnlsucc (13), -- Configuration download successful
        eErrlogin (29) -- Error during login to configuration
      }
    MAX-ACCESS read-only
    STATUS     current
    DESCRIPTION
        "-- empty --"
    ::= { lcsStatusConfigEventLogEntry 2 }

-- {COLUMN} 310.1.11.12.1.3
lcsStatusConfigEventLogEntryAccess OBJECT-TYPE
    SYNTAX     INTEGER
      {
        eOutband (0),
        eTelnet (1),
        eTftp (2),
        eHttp (3),
        eSnmp (4),
        eHttps (5),
        eTelnetSsl (6),
        eSsh (7),
        eLl2m (8),
        ePpp (254),
        eUnknown (255)
      }
    MAX-ACCESS read-only
    STATUS     current
    DESCRIPTION
        "-- empty --"
    ::= { lcsStatusConfigEventLogEntry 3 }

-- {COLUMN} 310.1.11.12.1.8
lcsStatusConfigEventLogEntryIpAddressNew OBJECT-TYPE
    SYNTAX     DisplayString (SIZE(0..255))
    MAX-ACCESS read-only
    STATUS     current
    DESCRIPTION
        ""
    ::= { lcsStatusConfigEventLogEntry 8 }

-- {COLUMN} 310.1.11.12.1.5
lcsStatusConfigEventLogEntryInfo1 OBJECT-TYPE
    SYNTAX     DisplayString (SIZE(0..32))
    MAX-ACCESS read-only
    STATUS     current
    DESCRIPTION
        "-- empty --"
    ::= { lcsStatusConfigEventLogEntry 5 }

-- {COLUMN} 310.1.11.12.1.6
lcsStatusConfigEventLogEntryInfo2 OBJECT-TYPE
    SYNTAX     DisplayString (SIZE(0..64))
    MAX-ACCESS read-only
    STATUS     current
    DESCRIPTION
        "-- empty --"
    ::= { lcsStatusConfigEventLogEntry 6 }

-- {OID} 310.1.11.70
lcsStatusConfigDownloadStatus OBJECT IDENTIFIER ::= { lcsStatusConfig 70 }

-- {SCALAR} 310.1.11.70.1
lcsStatusConfigDownloadStatusFirmwareSuccesses OBJECT-TYPE
    SYNTAX     INTEGER (0..2147483647)
    MAX-ACCESS read-only
    STATUS     current
    DESCRIPTION
        "-- empty --"
    ::= { lcsStatusConfigDownloadStatus 1 }

-- {SCALAR} 310.1.11.70.2
lcsStatusConfigDownloadStatusFirmwareFailures OBJECT-TYPE
    SYNTAX     INTEGER (0..2147483647)
    MAX-ACCESS read-only
    STATUS     current
    DESCRIPTION
        "-- empty --"
    ::= { lcsStatusConfigDownloadStatus 2 }

-- {SCALAR} 310.1.11.70.3
lcsStatusConfigDownloadStatusConfigurationSuccesses OBJECT-TYPE
    SYNTAX     INTEGER (0..2147483647)
    MAX-ACCESS read-only
    STATUS     current
    DESCRIPTION
        "-- empty --"
    ::= { lcsStatusConfigDownloadStatus 3 }

-- {SCALAR} 310.1.11.70.4
lcsStatusConfigDownloadStatusConfigurationFailures OBJECT-TYPE
    SYNTAX     INTEGER (0..2147483647)
    MAX-ACCESS read-only
    STATUS     current
    DESCRIPTION
        "-- empty --"
    ::= { lcsStatusConfigDownloadStatus 4 }

-- {SCALAR} 310.1.11.70.5
lcsStatusConfigDownloadStatusScriptSuccesses OBJECT-TYPE
    SYNTAX     INTEGER (0..2147483647)
    MAX-ACCESS read-only
    STATUS     current
    DESCRIPTION
        "-- empty --"
    ::= { lcsStatusConfigDownloadStatus 5 }

-- {SCALAR} 310.1.11.70.6
lcsStatusConfigDownloadStatusScriptFailures OBJECT-TYPE
    SYNTAX     INTEGER (0..2147483647)
    MAX-ACCESS read-only
    STATUS     current
    DESCRIPTION
        "-- empty --"
    ::= { lcsStatusConfigDownloadStatus 6 }

-- {SCALAR} 310.1.11.70.7
lcsStatusConfigDownloadStatusFileSuccesses OBJECT-TYPE
    SYNTAX     INTEGER (0..2147483647)
    MAX-ACCESS read-only
    STATUS     current
    DESCRIPTION
        "-- empty --"
    ::= { lcsStatusConfigDownloadStatus 7 }

-- {SCALAR} 310.1.11.70.8
lcsStatusConfigDownloadStatusFileFailures OBJECT-TYPE
    SYNTAX     INTEGER (0..2147483647)
    MAX-ACCESS read-only
    STATUS     current
    DESCRIPTION
        "-- empty --"
    ::= { lcsStatusConfigDownloadStatus 8 }

-- {TABLE} 310.1.11.70.20
lcsStatusConfigDownloadStatusLastOperationsTable OBJECT-TYPE
    SYNTAX     SEQUENCE OF LcsStatusConfigDownloadStatusLastOperationsEntry
    MAX-ACCESS not-accessible
    STATUS     current
    DESCRIPTION
        "-- empty --"
    ::= { lcsStatusConfigDownloadStatus 20 }

-- {ENTRY} 310.1.11.70.20.1
lcsStatusConfigDownloadStatusLastOperationsEntry OBJECT-TYPE
    SYNTAX     LcsStatusConfigDownloadStatusLastOperationsEntry
    MAX-ACCESS not-accessible
    STATUS     current
    DESCRIPTION
        ""
    INDEX {
        lcsStatusConfigDownloadStatusLastOperationsEntryIndex
    }
    ::= { lcsStatusConfigDownloadStatusLastOperationsTable 1 }

-- {SEQUENCE}
LcsStatusConfigDownloadStatusLastOperationsEntry ::= SEQUENCE {
    lcsStatusConfigDownloadStatusLastOperationsEntryIndex INTEGER,
    lcsStatusConfigDownloadStatusLastOperationsEntryIdentifier INTEGER,
    lcsStatusConfigDownloadStatusLastOperationsEntryType INTEGER,
    lcsStatusConfigDownloadStatusLastOperationsEntryUrl DisplayString,
    lcsStatusConfigDownloadStatusLastOperationsEntryStatus INTEGER,
    lcsStatusConfigDownloadStatusLastOperationsEntryFailureReason DisplayString
}

-- {COLUMN} 310.1.11.70.20.1.1
lcsStatusConfigDownloadStatusLastOperationsEntryIndex OBJECT-TYPE
    SYNTAX     INTEGER (0..2147483647)
    MAX-ACCESS read-only
    STATUS     current
    DESCRIPTION
        "-- empty --"
    ::= { lcsStatusConfigDownloadStatusLastOperationsEntry 1 }

-- {COLUMN} 310.1.11.70.20.1.2
lcsStatusConfigDownloadStatusLastOperationsEntryIdentifier OBJECT-TYPE
    SYNTAX     INTEGER (0..2147483647)
    MAX-ACCESS read-only
    STATUS     current
    DESCRIPTION
        "-- empty --"
    ::= { lcsStatusConfigDownloadStatusLastOperationsEntry 2 }

-- {COLUMN} 310.1.11.70.20.1.3
lcsStatusConfigDownloadStatusLastOperationsEntryType OBJECT-TYPE
    SYNTAX     INTEGER
      {
        eFirmware (1),
        eConfiguration (0),
        eScript (2),
        eFile (3)
      }
    MAX-ACCESS read-only
    STATUS     current
    DESCRIPTION
        "-- empty --"
    ::= { lcsStatusConfigDownloadStatusLastOperationsEntry 3 }

-- {COLUMN} 310.1.11.70.20.1.4
lcsStatusConfigDownloadStatusLastOperationsEntryUrl OBJECT-TYPE
    SYNTAX     DisplayString (SIZE(0..252))
    MAX-ACCESS read-only
    STATUS     current
    DESCRIPTION
        "-- empty --"
    ::= { lcsStatusConfigDownloadStatusLastOperationsEntry 4 }

-- {COLUMN} 310.1.11.70.20.1.5
lcsStatusConfigDownloadStatusLastOperationsEntryStatus OBJECT-TYPE
    SYNTAX     INTEGER
      {
        eIdle (0),
        ePending (1),
        eSuccess (2),
        eFailure (3),
        eUnknown (4)
      }
    MAX-ACCESS read-only
    STATUS     current
    DESCRIPTION
        "-- empty --"
    ::= { lcsStatusConfigDownloadStatusLastOperationsEntry 5 }

-- {COLUMN} 310.1.11.70.20.1.6
lcsStatusConfigDownloadStatusLastOperationsEntryFailureReason OBJECT-TYPE
    SYNTAX     DisplayString (SIZE(0..100))
    MAX-ACCESS read-only
    STATUS     current
    DESCRIPTION
        "-- empty --"
    ::= { lcsStatusConfigDownloadStatusLastOperationsEntry 6 }

-- {SCALAR} 310.1.11.70.99
lcsStatusConfigDownloadStatusDeleteValues OBJECT-TYPE
    SYNTAX     DisplayString
    MAX-ACCESS read-write
    STATUS     current
    DESCRIPTION
        "-- empty --"
    ::= { lcsStatusConfigDownloadStatus 99 }

-- {OID} 310.1.12
lcsStatusQueue OBJECT IDENTIFIER ::= { lcsStatus 12 }

-- {SCALAR} 310.1.12.1
lcsStatusQueueLanHeapPackets OBJECT-TYPE
    SYNTAX     INTEGER (0..2147483647)
    MAX-ACCESS read-only
    STATUS     current
    DESCRIPTION
        "-- empty --"
    ::= { lcsStatusQueue 1 }

-- {SCALAR} 310.1.12.2
lcsStatusQueueQueuePackets OBJECT-TYPE
    SYNTAX     INTEGER (0..2147483647)
    MAX-ACCESS read-only
    STATUS     current
    DESCRIPTION
        "LAN Queue Packets"
    ::= { lcsStatusQueue 2 }

-- {SCALAR} 310.1.12.3
lcsStatusQueueWanHeapPackets OBJECT-TYPE
    SYNTAX     INTEGER (0..2147483647)
    MAX-ACCESS read-only
    STATUS     current
    DESCRIPTION
        "-- empty --"
    ::= { lcsStatusQueue 3 }

-- {SCALAR} 310.1.12.4
lcsStatusQueueWanQueuePackets OBJECT-TYPE
    SYNTAX     INTEGER (0..2147483647)
    MAX-ACCESS read-only
    STATUS     current
    DESCRIPTION
        "-- empty --"
    ::= { lcsStatusQueue 4 }

-- {SCALAR} 310.1.12.7
lcsStatusQueueArpQueryQueuePackets OBJECT-TYPE
    SYNTAX     INTEGER (0..2147483647)
    MAX-ACCESS read-only
    STATUS     current
    DESCRIPTION
        "-- empty --"
    ::= { lcsStatusQueue 7 }

-- {SCALAR} 310.1.12.8
lcsStatusQueueArpQueuePackets OBJECT-TYPE
    SYNTAX     INTEGER (0..2147483647)
    MAX-ACCESS read-only
    STATUS     current
    DESCRIPTION
        "-- empty --"
    ::= { lcsStatusQueue 8 }

-- {SCALAR} 310.1.12.9
lcsStatusQueueIpQueuePackets OBJECT-TYPE
    SYNTAX     INTEGER (0..2147483647)
    MAX-ACCESS read-only
    STATUS     current
    DESCRIPTION
        "-- empty --"
    ::= { lcsStatusQueue 9 }

-- {SCALAR} 310.1.12.10
lcsStatusQueueIpUrgentQueuePackets OBJECT-TYPE
    SYNTAX     INTEGER (0..2147483647)
    MAX-ACCESS read-only
    STATUS     current
    DESCRIPTION
        "-- empty --"
    ::= { lcsStatusQueue 10 }

-- {SCALAR} 310.1.12.11
lcsStatusQueueIcmpQueuePackets OBJECT-TYPE
    SYNTAX     INTEGER (0..2147483647)
    MAX-ACCESS read-only
    STATUS     current
    DESCRIPTION
        "-- empty --"
    ::= { lcsStatusQueue 11 }

-- {SCALAR} 310.1.12.12
lcsStatusQueueTcpQueuePackets OBJECT-TYPE
    SYNTAX     INTEGER (0..2147483647)
    MAX-ACCESS read-only
    STATUS     current
    DESCRIPTION
        "-- empty --"
    ::= { lcsStatusQueue 12 }

-- {SCALAR} 310.1.12.13
lcsStatusQueueTftpServerQueuePackets OBJECT-TYPE
    SYNTAX     INTEGER (0..2147483647)
    MAX-ACCESS read-only
    STATUS     current
    DESCRIPTION
        "-- empty --"
    ::= { lcsStatusQueue 13 }

-- {SCALAR} 310.1.12.14
lcsStatusQueueSnmpQueuePackets OBJECT-TYPE
    SYNTAX     INTEGER (0..2147483647)
    MAX-ACCESS read-only
    STATUS     current
    DESCRIPTION
        "-- empty --"
    ::= { lcsStatusQueue 14 }

-- {SCALAR} 310.1.12.22
lcsStatusQueueProtHeapPackets OBJECT-TYPE
    SYNTAX     INTEGER (0..2147483647)
    MAX-ACCESS read-only
    STATUS     current
    DESCRIPTION
        "-- empty --"
    ::= { lcsStatusQueue 22 }

-- {SCALAR} 310.1.12.27
lcsStatusQueueDhcpServerQueuePackets OBJECT-TYPE
    SYNTAX     INTEGER (0..2147483647)
    MAX-ACCESS read-only
    STATUS     current
    DESCRIPTION
        "-- empty --"
    ::= { lcsStatusQueue 27 }

-- {SCALAR} 310.1.12.28
lcsStatusQueueDhcpClientQueuePackets OBJECT-TYPE
    SYNTAX     INTEGER (0..2147483647)
    MAX-ACCESS read-only
    STATUS     current
    DESCRIPTION
        "-- empty --"
    ::= { lcsStatusQueue 28 }

-- {SCALAR} 310.1.12.29
lcsStatusQueueIprRipQueuePackets OBJECT-TYPE
    SYNTAX     INTEGER (0..2147483647)
    MAX-ACCESS read-only
    STATUS     current
    DESCRIPTION
        "-- empty --"
    ::= { lcsStatusQueue 29 }

-- {SCALAR} 310.1.12.40
lcsStatusQueueWlanManagementHeapPackets OBJECT-TYPE
    SYNTAX     INTEGER (0..2147483647)
    MAX-ACCESS read-only
    STATUS     current
    DESCRIPTION
        "-- empty --"
    ::= { lcsStatusQueue 40 }

-- {TABLE} 310.1.13
lcsStatusConnectionTable OBJECT-TYPE
    SYNTAX     SEQUENCE OF LcsStatusConnectionEntry
    MAX-ACCESS not-accessible
    STATUS     current
    DESCRIPTION
        "-- empty --"
    ::= { lcsStatus 13 }

-- {ENTRY} 310.1.13.1
lcsStatusConnectionEntry OBJECT-TYPE
    SYNTAX     LcsStatusConnectionEntry
    MAX-ACCESS not-accessible
    STATUS     current
    DESCRIPTION
        ""
    INDEX {
        lcsStatusConnectionEntryIfc
    }
    ::= { lcsStatusConnectionTable 1 }

-- {SEQUENCE}
LcsStatusConnectionEntry ::= SEQUENCE {
    lcsStatusConnectionEntryIfc INTEGER,
    lcsStatusConnectionEntryConnections INTEGER,
    lcsStatusConnectionEntryActive INTEGER,
    lcsStatusConnectionEntryPassive INTEGER,
    lcsStatusConnectionEntryErrors INTEGER,
    lcsStatusConnectionEntryConTime DisplayString,
    lcsStatusConnectionEntryCharge INTEGER
}

-- {COLUMN} 310.1.13.1.1
lcsStatusConnectionEntryIfc OBJECT-TYPE
    SYNTAX     INTEGER
      {
        eDslCh1 (1),
        eModem (2)
      }
    MAX-ACCESS read-only
    STATUS     current
    DESCRIPTION
        "-- empty --"
    ::= { lcsStatusConnectionEntry 1 }

-- {COLUMN} 310.1.13.1.2
lcsStatusConnectionEntryConnections OBJECT-TYPE
    SYNTAX     INTEGER (0..2147483647)
    MAX-ACCESS read-only
    STATUS     current
    DESCRIPTION
        "-- empty --"
    ::= { lcsStatusConnectionEntry 2 }

-- {COLUMN} 310.1.13.1.3
lcsStatusConnectionEntryActive OBJECT-TYPE
    SYNTAX     INTEGER (0..2147483647)
    MAX-ACCESS read-only
    STATUS     current
    DESCRIPTION
        "-- empty --"
    ::= { lcsStatusConnectionEntry 3 }

-- {COLUMN} 310.1.13.1.4
lcsStatusConnectionEntryPassive OBJECT-TYPE
    SYNTAX     INTEGER (0..2147483647)
    MAX-ACCESS read-only
    STATUS     current
    DESCRIPTION
        "-- empty --"
    ::= { lcsStatusConnectionEntry 4 }

-- {COLUMN} 310.1.13.1.5
lcsStatusConnectionEntryErrors OBJECT-TYPE
    SYNTAX     INTEGER (0..2147483647)
    MAX-ACCESS read-only
    STATUS     current
    DESCRIPTION
        "-- empty --"
    ::= { lcsStatusConnectionEntry 5 }

-- {COLUMN} 310.1.13.1.6
lcsStatusConnectionEntryConTime OBJECT-TYPE
    SYNTAX     DisplayString (SIZE(0..255))
    MAX-ACCESS read-only
    STATUS     current
    DESCRIPTION
        "-- empty --"
    ::= { lcsStatusConnectionEntry 6 }

-- {COLUMN} 310.1.13.1.7
lcsStatusConnectionEntryCharge OBJECT-TYPE
    SYNTAX     INTEGER (0..2147483647)
    MAX-ACCESS read-only
    STATUS     current
    DESCRIPTION
        "-- empty --"
    ::= { lcsStatusConnectionEntry 7 }

-- {TABLE} 310.1.14
lcsStatusInfoConnectionTable OBJECT-TYPE
    SYNTAX     SEQUENCE OF LcsStatusInfoConnectionEntry
    MAX-ACCESS not-accessible
    STATUS     current
    DESCRIPTION
        "-- empty --"
    ::= { lcsStatus 14 }

-- {ENTRY} 310.1.14.1
lcsStatusInfoConnectionEntry OBJECT-TYPE
    SYNTAX     LcsStatusInfoConnectionEntry
    MAX-ACCESS not-accessible
    STATUS     current
    DESCRIPTION
        ""
    INDEX {
        lcsStatusInfoConnectionEntryIfc
    }
    ::= { lcsStatusInfoConnectionTable 1 }

-- {SEQUENCE}
LcsStatusInfoConnectionEntry ::= SEQUENCE {
    lcsStatusInfoConnectionEntryIfc INTEGER,
    lcsStatusInfoConnectionEntryStatus DisplayString,
    lcsStatusInfoConnectionEntryMode INTEGER,
    lcsStatusInfoConnectionEntryDialupRemote DisplayString,
    lcsStatusInfoConnectionEntryPeer DisplayString,
    lcsStatusInfoConnectionEntryB1Dt INTEGER,
    lcsStatusInfoConnectionEntryB2Dt INTEGER
}

-- {COLUMN} 310.1.14.1.1
lcsStatusInfoConnectionEntryIfc OBJECT-TYPE
    SYNTAX     INTEGER
      {
        eDslCh1 (1),
        eModem (2)
      }
    MAX-ACCESS read-only
    STATUS     current
    DESCRIPTION
        "-- empty --"
    ::= { lcsStatusInfoConnectionEntry 1 }

-- {COLUMN} 310.1.14.1.2
lcsStatusInfoConnectionEntryStatus OBJECT-TYPE
    SYNTAX     DisplayString (SIZE(0..16))
    MAX-ACCESS read-only
    STATUS     current
    DESCRIPTION
        "-- empty --"
    ::= { lcsStatusInfoConnectionEntry 2 }

-- {COLUMN} 310.1.14.1.3
lcsStatusInfoConnectionEntryMode OBJECT-TYPE
    SYNTAX     INTEGER
      {
        eUnknown (0),
        eActive (4),
        ePassive (5),
        eCallback (9)
      }
    MAX-ACCESS read-only
    STATUS     current
    DESCRIPTION
        "-- empty --"
    ::= { lcsStatusInfoConnectionEntry 3 }

-- {COLUMN} 310.1.14.1.4
lcsStatusInfoConnectionEntryDialupRemote OBJECT-TYPE
    SYNTAX     DisplayString (SIZE(0..20))
    MAX-ACCESS read-only
    STATUS     current
    DESCRIPTION
        "-- empty --"
    ::= { lcsStatusInfoConnectionEntry 4 }

-- {COLUMN} 310.1.14.1.5
lcsStatusInfoConnectionEntryPeer OBJECT-TYPE
    SYNTAX     DisplayString (SIZE(0..16))
    MAX-ACCESS read-only
    STATUS     current
    DESCRIPTION
        "-- empty --"
    ::= { lcsStatusInfoConnectionEntry 5 }

-- {COLUMN} 310.1.14.1.6
lcsStatusInfoConnectionEntryB1Dt OBJECT-TYPE
    SYNTAX     INTEGER (0..65535)
    MAX-ACCESS read-only
    STATUS     current
    DESCRIPTION
        "-- empty --"
    ::= { lcsStatusInfoConnectionEntry 6 }

-- {COLUMN} 310.1.14.1.7
lcsStatusInfoConnectionEntryB2Dt OBJECT-TYPE
    SYNTAX     INTEGER (0..65535)
    MAX-ACCESS read-only
    STATUS     current
    DESCRIPTION
        "-- empty --"
    ::= { lcsStatusInfoConnectionEntry 7 }

-- {TABLE} 310.1.15
lcsStatusLayerConnectionTable OBJECT-TYPE
    SYNTAX     SEQUENCE OF LcsStatusLayerConnectionEntry
    MAX-ACCESS not-accessible
    STATUS     current
    DESCRIPTION
        "-- empty --"
    ::= { lcsStatus 15 }

-- {ENTRY} 310.1.15.1
lcsStatusLayerConnectionEntry OBJECT-TYPE
    SYNTAX     LcsStatusLayerConnectionEntry
    MAX-ACCESS not-accessible
    STATUS     current
    DESCRIPTION
        ""
    INDEX {
        lcsStatusLayerConnectionEntryIfc
    }
    ::= { lcsStatusLayerConnectionTable 1 }

-- {SEQUENCE}
LcsStatusLayerConnectionEntry ::= SEQUENCE {
    lcsStatusLayerConnectionEntryIfc INTEGER,
    lcsStatusLayerConnectionEntryWanLayer DisplayString,
    lcsStatusLayerConnectionEntryEncaps INTEGER,
    lcsStatusLayerConnectionEntryLay3 INTEGER,
    lcsStatusLayerConnectionEntryLay2 INTEGER,
    lcsStatusLayerConnectionEntryL2Opt INTEGER,
    lcsStatusLayerConnectionEntryLay1 INTEGER,
    lcsStatusLayerConnectionEntryL1Parameter INTEGER
}

-- {COLUMN} 310.1.15.1.1
lcsStatusLayerConnectionEntryIfc OBJECT-TYPE
    SYNTAX     INTEGER
      {
        eDslCh1 (1),
        eModem (2)
      }
    MAX-ACCESS read-only
    STATUS     current
    DESCRIPTION
        "-- empty --"
    ::= { lcsStatusLayerConnectionEntry 1 }

-- {COLUMN} 310.1.15.1.2
lcsStatusLayerConnectionEntryWanLayer OBJECT-TYPE
    SYNTAX     DisplayString (SIZE(0..9))
    MAX-ACCESS read-only
    STATUS     current
    DESCRIPTION
        "-- empty --"
    ::= { lcsStatusLayerConnectionEntry 2 }

-- {COLUMN} 310.1.15.1.3
lcsStatusLayerConnectionEntryEncaps OBJECT-TYPE
    SYNTAX     INTEGER
      {
        eEther (0),
        eTrans (255)
      }
    MAX-ACCESS read-only
    STATUS     current
    DESCRIPTION
        "-- empty --"
    ::= { lcsStatusLayerConnectionEntry 3 }

-- {COLUMN} 310.1.15.1.4
lcsStatusLayerConnectionEntryLay3 OBJECT-TYPE
    SYNTAX     INTEGER
      {
        ePpp (4),
        eAppp (5),
        eScppp (6),
        eScappp (7),
        eSctrans (8),
        eDhcp (9),
        eTRANS (255)
      }
    MAX-ACCESS read-only
    STATUS     current
    DESCRIPTION
        "-- empty --"
    ::= { lcsStatusLayerConnectionEntry 4 }

-- {COLUMN} 310.1.15.1.5
lcsStatusLayerConnectionEntryLay2 OBJECT-TYPE
    SYNTAX     INTEGER
      {
        eSscop (6),
        ePppoe (5),
        eX75lapb (0),
        eTrans (1)
      }
    MAX-ACCESS read-only
    STATUS     current
    DESCRIPTION
        "-- empty --"
    ::= { lcsStatusLayerConnectionEntry 5 }

-- {COLUMN} 310.1.15.1.6
lcsStatusLayerConnectionEntryL2Opt OBJECT-TYPE
    SYNTAX     INTEGER
      {
        eNone (255),
        eCompr (0),
        eBundle (1),
        eBndPlusCmpr (2)
      }
    MAX-ACCESS read-only
    STATUS     current
    DESCRIPTION
        "-- empty --"
    ::= { lcsStatusLayerConnectionEntry 6 }

-- {COLUMN} 310.1.15.1.7
lcsStatusLayerConnectionEntryLay1 OBJECT-TYPE
    SYNTAX     INTEGER
      {
        eAdsl (2),
        eEth (4),
        eHdlc64k (0),
        eHdlc56k (1),
        eSerial (6),
        eModem (5)
      }
    MAX-ACCESS read-only
    STATUS     current
    DESCRIPTION
        "-- empty --"
    ::= { lcsStatusLayerConnectionEntry 7 }

-- {COLUMN} 310.1.15.1.8
lcsStatusLayerConnectionEntryL1Parameter OBJECT-TYPE
    SYNTAX     INTEGER
      {
        eNone (0),
        eV21300 (1),
        eV23600 (2),
        eV231200 (3),
        eV221200 (4),
        eV22bis2400 (5),
        eV32qam4800 (6),
        eV32qam9600 (7),
        eV32bis7200 (8),
        eV32tcm9600 (9),
        eV32bis12000 (10),
        eV32bis14400 (11),
        eV342400 (12),
        eV344800 (13),
        eV347200 (14),
        eV349600 (15),
        eV3412000 (16),
        eV3414400 (17),
        eV3416800 (18),
        eV3419200 (19),
        eV3421600 (20),
        eV3424000 (21),
        eV3426400 (22),
        eV3428800 (23),
        eV3431200 (24),
        eV3433600 (25),
        eV9028000 (26),
        eV9029333 (27),
        eV9030667 (28),
        eV9032000 (29),
        eV9033333 (30),
        eV9034667 (31),
        eV9036000 (32),
        eV9037333 (33),
        eV9038667 (34),
        eV9040000 (35),
        eV9041333 (36),
        eV9042667 (37),
        eV9044000 (38),
        eV9045333 (39),
        eV9046667 (40),
        eV9048000 (41),
        eV9049333 (42),
        eV9050667 (43),
        eV9052000 (44),
        eV9053333 (45),
        eV9054667 (46),
        eV9056000 (47)
      }
    MAX-ACCESS read-only
    STATUS     current
    DESCRIPTION
        "-- empty --"
    ::= { lcsStatusLayerConnectionEntry 8 }

-- {TABLE} 310.1.16
lcsStatusCallInformationTable OBJECT-TYPE
    SYNTAX     SEQUENCE OF LcsStatusCallInformationEntry
    MAX-ACCESS not-accessible
    STATUS     current
    DESCRIPTION
        "-- empty --"
    ::= { lcsStatus 16 }

-- {ENTRY} 310.1.16.1
lcsStatusCallInformationEntry OBJECT-TYPE
    SYNTAX     LcsStatusCallInformationEntry
    MAX-ACCESS not-accessible
    STATUS     current
    DESCRIPTION
        ""
    INDEX {
        lcsStatusCallInformationEntrySystemTime,
        lcsStatusCallInformationEntryCounter
    }
    ::= { lcsStatusCallInformationTable 1 }

-- {SEQUENCE}
LcsStatusCallInformationEntry ::= SEQUENCE {
    lcsStatusCallInformationEntrySystemTime Gauge32,
    lcsStatusCallInformationEntryIfc INTEGER,
    lcsStatusCallInformationEntryClipCaller DisplayString,
    lcsStatusCallInformationEntryDialCaller DisplayString,
    lcsStatusCallInformationEntryCapab INTEGER,
    lcsStatusCallInformationEntryBChan INTEGER,
    lcsStatusCallInformationEntryCounter INTEGER
}

-- {COLUMN} 310.1.16.1.1
lcsStatusCallInformationEntrySystemTime OBJECT-TYPE
    SYNTAX     Gauge32
    MAX-ACCESS read-only
    STATUS     current
    DESCRIPTION
        "-- empty --"
    ::= { lcsStatusCallInformationEntry 1 }

-- {COLUMN} 310.1.16.1.2
lcsStatusCallInformationEntryIfc OBJECT-TYPE
    SYNTAX     INTEGER
      {
        eDsl1 (1),
        eModem (2)
      }
    MAX-ACCESS read-only
    STATUS     current
    DESCRIPTION
        "-- empty --"
    ::= { lcsStatusCallInformationEntry 2 }

-- {COLUMN} 310.1.16.1.3
lcsStatusCallInformationEntryClipCaller OBJECT-TYPE
    SYNTAX     DisplayString (SIZE(0..20))
    MAX-ACCESS read-only
    STATUS     current
    DESCRIPTION
        "-- empty --"
    ::= { lcsStatusCallInformationEntry 3 }

-- {COLUMN} 310.1.16.1.4
lcsStatusCallInformationEntryDialCaller OBJECT-TYPE
    SYNTAX     DisplayString (SIZE(0..20))
    MAX-ACCESS read-only
    STATUS     current
    DESCRIPTION
        "-- empty --"
    ::= { lcsStatusCallInformationEntry 4 }

-- {COLUMN} 310.1.16.1.5
lcsStatusCallInformationEntryCapab OBJECT-TYPE
    SYNTAX     INTEGER
      {
        eUnknown (255),
        eHdlc64k (0),
        eHdlc56k (1),
        eV1109k6 (3),
        eV11019k2 (67),
        eV11038k4 (131),
        eModem (5),
        eA31khz (13),
        eSpeech (14),
        eFaxG23 (15)
      }
    MAX-ACCESS read-only
    STATUS     current
    DESCRIPTION
        "-- empty --"
    ::= { lcsStatusCallInformationEntry 5 }

-- {COLUMN} 310.1.16.1.6
lcsStatusCallInformationEntryBChan OBJECT-TYPE
    SYNTAX     INTEGER (0..65535)
    MAX-ACCESS read-only
    STATUS     current
    DESCRIPTION
        "-- empty --"
    ::= { lcsStatusCallInformationEntry 6 }

-- {COLUMN} 310.1.16.1.7
lcsStatusCallInformationEntryCounter OBJECT-TYPE
    SYNTAX     INTEGER (0..2147483647)
    MAX-ACCESS read-only
    STATUS     current
    DESCRIPTION
        "-- empty --"
    ::= { lcsStatusCallInformationEntry 7 }

-- {TABLE} 310.1.17
lcsStatusRemoteConnectionsTable OBJECT-TYPE
    SYNTAX     SEQUENCE OF LcsStatusRemoteConnectionsEntry
    MAX-ACCESS not-accessible
    STATUS     current
    DESCRIPTION
        "-- empty --"
    ::= { lcsStatus 17 }

-- {ENTRY} 310.1.17.1
lcsStatusRemoteConnectionsEntry OBJECT-TYPE
    SYNTAX     LcsStatusRemoteConnectionsEntry
    MAX-ACCESS not-accessible
    STATUS     current
    DESCRIPTION
        ""
    INDEX {
        lcsStatusRemoteConnectionsEntryConnStart,
        lcsStatusRemoteConnectionsEntryCounter
    }
    ::= { lcsStatusRemoteConnectionsTable 1 }

-- {SEQUENCE}
LcsStatusRemoteConnectionsEntry ::= SEQUENCE {
    lcsStatusRemoteConnectionsEntryConnStart DisplayString,
    lcsStatusRemoteConnectionsEntryRemoteId DisplayString,
    lcsStatusRemoteConnectionsEntryMode INTEGER,
    lcsStatusRemoteConnectionsEntryIfc INTEGER,
    lcsStatusRemoteConnectionsEntryConnTime DisplayString,
    lcsStatusRemoteConnectionsEntryCharge INTEGER,
    lcsStatusRemoteConnectionsEntryCounter INTEGER
}

-- {COLUMN} 310.1.17.1.1
lcsStatusRemoteConnectionsEntryConnStart OBJECT-TYPE
    SYNTAX     DisplayString (SIZE(0..19))
    MAX-ACCESS read-only
    STATUS     current
    DESCRIPTION
        "-- empty --"
    ::= { lcsStatusRemoteConnectionsEntry 1 }

-- {COLUMN} 310.1.17.1.2
lcsStatusRemoteConnectionsEntryRemoteId OBJECT-TYPE
    SYNTAX     DisplayString (SIZE(0..16))
    MAX-ACCESS read-only
    STATUS     current
    DESCRIPTION
        "-- empty --"
    ::= { lcsStatusRemoteConnectionsEntry 2 }

-- {COLUMN} 310.1.17.1.3
lcsStatusRemoteConnectionsEntryMode OBJECT-TYPE
    SYNTAX     INTEGER
      {
        eUnknown (0),
        eActive (4),
        ePassive (5),
        eCallback (9)
      }
    MAX-ACCESS read-only
    STATUS     current
    DESCRIPTION
        "-- empty --"
    ::= { lcsStatusRemoteConnectionsEntry 3 }

-- {COLUMN} 310.1.17.1.4
lcsStatusRemoteConnectionsEntryIfc OBJECT-TYPE
    SYNTAX     INTEGER
      {
        eDslCh1 (1),
        eModem (2)
      }
    MAX-ACCESS read-only
    STATUS     current
    DESCRIPTION
        "-- empty --"
    ::= { lcsStatusRemoteConnectionsEntry 4 }

-- {COLUMN} 310.1.17.1.5
lcsStatusRemoteConnectionsEntryConnTime OBJECT-TYPE
    SYNTAX     DisplayString (SIZE(0..255))
    MAX-ACCESS read-only
    STATUS     current
    DESCRIPTION
        "-- empty --"
    ::= { lcsStatusRemoteConnectionsEntry 5 }

-- {COLUMN} 310.1.17.1.6
lcsStatusRemoteConnectionsEntryCharge OBJECT-TYPE
    SYNTAX     INTEGER (0..2147483647)
    MAX-ACCESS read-only
    STATUS     current
    DESCRIPTION
        "-- empty --"
    ::= { lcsStatusRemoteConnectionsEntry 6 }

-- {COLUMN} 310.1.17.1.8
lcsStatusRemoteConnectionsEntryCounter OBJECT-TYPE
    SYNTAX     INTEGER (0..2147483647)
    MAX-ACCESS read-only
    STATUS     current
    DESCRIPTION
        "-- empty --"
    ::= { lcsStatusRemoteConnectionsEntry 8 }

-- {SCALAR} 310.1.18
lcsStatusCurrentTime OBJECT-TYPE
    SYNTAX     DisplayString
    MAX-ACCESS read-only
    STATUS     current
    DESCRIPTION
        "-- empty --"
    ::= { lcsStatus 18 }

-- {OID} 310.1.21
lcsStatusTime OBJECT IDENTIFIER ::= { lcsStatus 21 }

-- {SCALAR} 310.1.21.1
lcsStatusTimeCurrentTime OBJECT-TYPE
    SYNTAX     DisplayString
    MAX-ACCESS read-only
    STATUS     current
    DESCRIPTION
        "-- empty --"
    ::= { lcsStatusTime 1 }

-- {SCALAR} 310.1.21.2
lcsStatusTimeSource OBJECT-TYPE
    SYNTAX     INTEGER
      {
        eManual (1),
        eLan (3),
        eRam (4),
        eNtp (9),
        eCapwap (10),
        eRtc (11),
        eLanconfig (8),
        eNo (0)
      }
    MAX-ACCESS read-only
    STATUS     current
    DESCRIPTION
        "-- empty --"
    ::= { lcsStatusTime 2 }

-- {SCALAR} 310.1.21.3
lcsStatusTimeSetCount OBJECT-TYPE
    SYNTAX     Counter32
    MAX-ACCESS read-only
    STATUS     current
    DESCRIPTION
        "-- empty --"
    ::= { lcsStatusTime 3 }

-- {SCALAR} 310.1.21.10
lcsStatusTimeTimezone OBJECT-TYPE
    SYNTAX     INTEGER
      {
        e0 (0),
        eplus1 (1), -- plus 1 hour
        eplus2 (2), -- plus 2 hours
        eplus3 (3), -- plus 3 hours
        eplus4 (4), -- plus 4 hours
        eplus5 (5), -- plus 5 hours
        eplus6 (6), -- plus 6 hours
        eplus7 (7), -- plus 7 hours
        eplus8 (8), -- plus 8 hours
        eplus9 (9), -- plus 9 hours
        eplus10 (10), -- plus 10 hours
        eplus11 (11), -- plus 11 hours
        eplus12 (12), -- plus 12 hours
        eplus13 (13), -- plus 13 hours
        eplus14 (14), -- plus 14 hours
        eminus1 (255), -- minus 1 hour
        eminus2 (254), -- minus 2 hours
        eminus3 (253), -- minus 3 hours
        eminus4 (252), -- minus 4 hours
        eminus5 (251), -- minus 5 hours
        eminus6 (250), -- minus 6 hours
        eminus7 (249), -- minus 7 hours
        eminus8 (248), -- minus 8 hours
        eminus9 (247), -- minus 9 hours
        eminus10 (246), -- minus 10 hours
        eminus11 (245), -- minus 11 hours
        eminus12 (244) -- minus 12 hours
      }
    MAX-ACCESS read-only
    STATUS     current
    DESCRIPTION
        "-- empty --"
    ::= { lcsStatusTime 10 }

-- {SCALAR} 310.1.21.11
lcsStatusTimeDaylightSavingTime OBJECT-TYPE
    SYNTAX     INTEGER
      {
        eNo (0),
        eYes (1),
        eEuropeEu (2),
        eUsa (4),
        eUserDefined (255)
      }
    MAX-ACCESS read-only
    STATUS     current
    DESCRIPTION
        "-- empty --"
    ::= { lcsStatusTime 11 }

-- {TABLE} 310.1.21.12
lcsStatusTimeDstClockChangesTable OBJECT-TYPE
    SYNTAX     SEQUENCE OF LcsStatusTimeDstClockChangesEntry
    MAX-ACCESS not-accessible
    STATUS     current
    DESCRIPTION
        "-- empty --"
    ::= { lcsStatusTime 12 }

-- {ENTRY} 310.1.21.12.1
lcsStatusTimeDstClockChangesEntry OBJECT-TYPE
    SYNTAX     LcsStatusTimeDstClockChangesEntry
    MAX-ACCESS not-accessible
    STATUS     current
    DESCRIPTION
        ""
    INDEX {
        lcsStatusTimeDstClockChangesEntryEvent
    }
    ::= { lcsStatusTimeDstClockChangesTable 1 }

-- {SEQUENCE}
LcsStatusTimeDstClockChangesEntry ::= SEQUENCE {
    lcsStatusTimeDstClockChangesEntryEvent INTEGER,
    lcsStatusTimeDstClockChangesEntryIndex INTEGER,
    lcsStatusTimeDstClockChangesEntryDay INTEGER,
    lcsStatusTimeDstClockChangesEntryMonth INTEGER,
    lcsStatusTimeDstClockChangesEntryHour INTEGER,
    lcsStatusTimeDstClockChangesEntryMinute INTEGER,
    lcsStatusTimeDstClockChangesEntryTimeType INTEGER
}

-- {COLUMN} 310.1.21.12.1.1
lcsStatusTimeDstClockChangesEntryEvent OBJECT-TYPE
    SYNTAX     INTEGER
      {
        eStart (1),
        eEnd (2)
      }
    MAX-ACCESS read-only
    STATUS     current
    DESCRIPTION
        "-- empty --"
    ::= { lcsStatusTimeDstClockChangesEntry 1 }

-- {COLUMN} 310.1.21.12.1.2
lcsStatusTimeDstClockChangesEntryIndex OBJECT-TYPE
    SYNTAX     INTEGER
      {
        e4Last (252),
        e3Last (253),
        e2Last (254),
        eLast (255),
        eFirst (1),
        eSecond (2),
        eThird (3),
        eFourth (4)
      }
    MAX-ACCESS read-only
    STATUS     current
    DESCRIPTION
        "-- empty --"
    ::= { lcsStatusTimeDstClockChangesEntry 2 }

-- {COLUMN} 310.1.21.12.1.3
lcsStatusTimeDstClockChangesEntryDay OBJECT-TYPE
    SYNTAX     INTEGER
      {
        eSunday (0),
        eMonday (1),
        eTuesday (2),
        eWednesday (3),
        eThursday (4),
        eFriday (5),
        eSaturday (6)
      }
    MAX-ACCESS read-only
    STATUS     current
    DESCRIPTION
        "-- empty --"
    ::= { lcsStatusTimeDstClockChangesEntry 3 }

-- {COLUMN} 310.1.21.12.1.4
lcsStatusTimeDstClockChangesEntryMonth OBJECT-TYPE
    SYNTAX     INTEGER
      {
        eJanuary (1),
        eFebruary (2),
        eMarch (3),
        eApril (4),
        eMay (5),
        eJune (6),
        eJuly (7),
        eAugust (8),
        eSeptember (9),
        eOctober (10),
        eNovember (11),
        eDecember (12)
      }
    MAX-ACCESS read-only
    STATUS     current
    DESCRIPTION
        "-- empty --"
    ::= { lcsStatusTimeDstClockChangesEntry 4 }

-- {COLUMN} 310.1.21.12.1.5
lcsStatusTimeDstClockChangesEntryHour OBJECT-TYPE
    SYNTAX     INTEGER (0..255)
    MAX-ACCESS read-only
    STATUS     current
    DESCRIPTION
        "-- empty --"
    ::= { lcsStatusTimeDstClockChangesEntry 5 }

-- {COLUMN} 310.1.21.12.1.6
lcsStatusTimeDstClockChangesEntryMinute OBJECT-TYPE
    SYNTAX     INTEGER (0..255)
    MAX-ACCESS read-only
    STATUS     current
    DESCRIPTION
        "-- empty --"
    ::= { lcsStatusTimeDstClockChangesEntry 6 }

-- {COLUMN} 310.1.21.12.1.7
lcsStatusTimeDstClockChangesEntryTimeType OBJECT-TYPE
    SYNTAX     INTEGER
      {
        eUtc (1),
        eLst (0)
      }
    MAX-ACCESS read-only
    STATUS     current
    DESCRIPTION
        "-- empty --"
    ::= { lcsStatusTimeDstClockChangesEntry 7 }

-- {OID} 310.1.22
lcsStatusLcr OBJECT IDENTIFIER ::= { lcsStatus 22 }

-- {SCALAR} 310.1.22.1
lcsStatusLcrTotalCalls OBJECT-TYPE
    SYNTAX     Counter32
    MAX-ACCESS read-only
    STATUS     current
    DESCRIPTION
        "-- empty --"
    ::= { lcsStatusLcr 1 }

-- {SCALAR} 310.1.22.2
lcsStatusLcrFoundEvents OBJECT-TYPE
    SYNTAX     Counter32
    MAX-ACCESS read-only
    STATUS     current
    DESCRIPTION
        "-- empty --"
    ::= { lcsStatusLcr 2 }

-- {SCALAR} 310.1.22.3
lcsStatusLcrNotfoundErrors OBJECT-TYPE
    SYNTAX     Counter32
    MAX-ACCESS read-only
    STATUS     current
    DESCRIPTION
        "-- empty --"
    ::= { lcsStatusLcr 3 }

-- {SCALAR} 310.1.22.4
lcsStatusLcrMissingtimeErrors OBJECT-TYPE
    SYNTAX     Counter32
    MAX-ACCESS read-only
    STATUS     current
    DESCRIPTION
        "-- empty --"
    ::= { lcsStatusLcr 4 }

-- {TABLE} 310.1.22.6
lcsStatusLcrProviderTable OBJECT-TYPE
    SYNTAX     SEQUENCE OF LcsStatusLcrProviderEntry
    MAX-ACCESS not-accessible
    STATUS     current
    DESCRIPTION
        "-- empty --"
    ::= { lcsStatusLcr 6 }

-- {ENTRY} 310.1.22.6.1
lcsStatusLcrProviderEntry OBJECT-TYPE
    SYNTAX     LcsStatusLcrProviderEntry
    MAX-ACCESS not-accessible
    STATUS     current
    DESCRIPTION
        ""
    INDEX {
        lcsStatusLcrProviderEntryProvider
    }
    ::= { lcsStatusLcrProviderTable 1 }

-- {SEQUENCE}
LcsStatusLcrProviderEntry ::= SEQUENCE {
    lcsStatusLcrProviderEntryProvider DisplayString,
    lcsStatusLcrProviderEntryFailures INTEGER,
    lcsStatusLcrProviderEntrySuccesses INTEGER
}

-- {COLUMN} 310.1.22.6.1.1
lcsStatusLcrProviderEntryProvider OBJECT-TYPE
    SYNTAX     DisplayString (SIZE(0..10))
    MAX-ACCESS read-only
    STATUS     current
    DESCRIPTION
        "-- empty --"
    ::= { lcsStatusLcrProviderEntry 1 }

-- {COLUMN} 310.1.22.6.1.2
lcsStatusLcrProviderEntryFailures OBJECT-TYPE
    SYNTAX     INTEGER (0..2147483647)
    MAX-ACCESS read-only
    STATUS     current
    DESCRIPTION
        "-- empty --"
    ::= { lcsStatusLcrProviderEntry 2 }

-- {COLUMN} 310.1.22.6.1.3
lcsStatusLcrProviderEntrySuccesses OBJECT-TYPE
    SYNTAX     INTEGER (0..2147483647)
    MAX-ACCESS read-only
    STATUS     current
    DESCRIPTION
        "-- empty --"
    ::= { lcsStatusLcrProviderEntry 3 }

-- {SCALAR} 310.1.22.7
lcsStatusLcrDeleteValues OBJECT-TYPE
    SYNTAX     DisplayString
    MAX-ACCESS read-write
    STATUS     current
    DESCRIPTION
        "-- empty --"
    ::= { lcsStatusLcr 7 }

-- {OID} 310.1.24
lcsStatusCharging OBJECT IDENTIFIER ::= { lcsStatus 24 }

-- {SCALAR} 310.1.24.6
lcsStatusChargingSpareDaysPerPeriod OBJECT-TYPE
    SYNTAX     INTEGER (0..65535)
    MAX-ACCESS read-only
    STATUS     current
    DESCRIPTION
        "-- empty --"
    ::= { lcsStatusCharging 6 }

-- {SCALAR} 310.1.24.10
lcsStatusChargingSpareDialupMinutes OBJECT-TYPE
    SYNTAX     INTEGER (0..2147483647)
    MAX-ACCESS read-only
    STATUS     current
    DESCRIPTION
        "-- empty --"
    ::= { lcsStatusCharging 10 }

-- {SCALAR} 310.1.24.11
lcsStatusChargingDialupMinutesActive OBJECT-TYPE
    SYNTAX     INTEGER (0..2147483647)
    MAX-ACCESS read-only
    STATUS     current
    DESCRIPTION
        "-- empty --"
    ::= { lcsStatusCharging 11 }

-- {SCALAR} 310.1.24.1
lcsStatusChargingSpareDslBroadbandMinutes OBJECT-TYPE
    SYNTAX     INTEGER (0..2147483647)
    MAX-ACCESS read-only
    STATUS     current
    DESCRIPTION
        "-- empty --"
    ::= { lcsStatusCharging 1 }

-- {SCALAR} 310.1.24.9
lcsStatusChargingRouterDslBroadbandMinutesActive OBJECT-TYPE
    SYNTAX     INTEGER (0..2147483647)
    MAX-ACCESS read-only
    STATUS     current
    DESCRIPTION
        "-- empty --"
    ::= { lcsStatusCharging 9 }

-- {TABLE} 310.1.24.2
lcsStatusChargingTimeTableTable OBJECT-TYPE
    SYNTAX     SEQUENCE OF LcsStatusChargingTimeTableEntry
    MAX-ACCESS not-accessible
    STATUS     current
    DESCRIPTION
        "-- empty --"
    ::= { lcsStatusCharging 2 }

-- {ENTRY} 310.1.24.2.1
lcsStatusChargingTimeTableEntry OBJECT-TYPE
    SYNTAX     LcsStatusChargingTimeTableEntry
    MAX-ACCESS not-accessible
    STATUS     current
    DESCRIPTION
        ""
    INDEX {
        lcsStatusChargingTimeTableEntryIfc
    }
    ::= { lcsStatusChargingTimeTableTable 1 }

-- {SEQUENCE}
LcsStatusChargingTimeTableEntry ::= SEQUENCE {
    lcsStatusChargingTimeTableEntryIfc INTEGER,
    lcsStatusChargingTimeTableEntryBudgetMinutes INTEGER,
    lcsStatusChargingTimeTableEntrySpareMinutes INTEGER,
    lcsStatusChargingTimeTableEntryMinutesActive INTEGER,
    lcsStatusChargingTimeTableEntryMinutesPassive INTEGER
}

-- {COLUMN} 310.1.24.2.1.1
lcsStatusChargingTimeTableEntryIfc OBJECT-TYPE
    SYNTAX     INTEGER
      {
        eRouterDslBroadband (1),
        eRouterSerial (2),
        eLancapi (3),
        eAb1 (4),
        eAb2 (5),
        eAb3 (6),
        eAb4 (7),
        eTimeModul (255)
      }
    MAX-ACCESS read-only
    STATUS     current
    DESCRIPTION
        "-- empty --"
    ::= { lcsStatusChargingTimeTableEntry 1 }

-- {COLUMN} 310.1.24.2.1.2
lcsStatusChargingTimeTableEntryBudgetMinutes OBJECT-TYPE
    SYNTAX     INTEGER (0..2147483647)
    MAX-ACCESS read-only
    STATUS     current
    DESCRIPTION
        "-- empty --"
    ::= { lcsStatusChargingTimeTableEntry 2 }

-- {COLUMN} 310.1.24.2.1.3
lcsStatusChargingTimeTableEntrySpareMinutes OBJECT-TYPE
    SYNTAX     INTEGER (0..2147483647)
    MAX-ACCESS read-only
    STATUS     current
    DESCRIPTION
        "-- empty --"
    ::= { lcsStatusChargingTimeTableEntry 3 }

-- {COLUMN} 310.1.24.2.1.4
lcsStatusChargingTimeTableEntryMinutesActive OBJECT-TYPE
    SYNTAX     INTEGER (0..2147483647)
    MAX-ACCESS read-only
    STATUS     current
    DESCRIPTION
        "-- empty --"
    ::= { lcsStatusChargingTimeTableEntry 4 }

-- {COLUMN} 310.1.24.2.1.5
lcsStatusChargingTimeTableEntryMinutesPassive OBJECT-TYPE
    SYNTAX     INTEGER (0..2147483647)
    MAX-ACCESS read-only
    STATUS     current
    DESCRIPTION
        "-- empty --"
    ::= { lcsStatusChargingTimeTableEntry 5 }

-- {SCALAR} 310.1.24.3
lcsStatusChargingDeleteValues OBJECT-TYPE
    SYNTAX     DisplayString
    MAX-ACCESS read-write
    STATUS     current
    DESCRIPTION
        "-- empty --"
    ::= { lcsStatusCharging 3 }

-- {OID} 310.1.25
lcsStatusDslol OBJECT IDENTIFIER ::= { lcsStatus 25 }

-- {SCALAR} 310.1.25.1
lcsStatusDslolRxPackets OBJECT-TYPE
    SYNTAX     Counter32
    MAX-ACCESS read-only
    STATUS     current
    DESCRIPTION
        "-- empty --"
    ::= { lcsStatusDslol 1 }

-- {SCALAR} 310.1.25.2
lcsStatusDslolTxPackets OBJECT-TYPE
    SYNTAX     Counter32
    MAX-ACCESS read-only
    STATUS     current
    DESCRIPTION
        "-- empty --"
    ::= { lcsStatusDslol 2 }

-- {SCALAR} 310.1.25.3
lcsStatusDslolRxErrors OBJECT-TYPE
    SYNTAX     Counter32
    MAX-ACCESS read-only
    STATUS     current
    DESCRIPTION
        "-- empty --"
    ::= { lcsStatusDslol 3 }

-- {SCALAR} 310.1.25.4
lcsStatusDslolTxErrors OBJECT-TYPE
    SYNTAX     Counter32
    MAX-ACCESS read-only
    STATUS     current
    DESCRIPTION
        "-- empty --"
    ::= { lcsStatusDslol 4 }

-- {SCALAR} 310.1.25.5
lcsStatusDslolRxNoConnection OBJECT-TYPE
    SYNTAX     Counter32
    MAX-ACCESS read-only
    STATUS     current
    DESCRIPTION
        "-- empty --"
    ::= { lcsStatusDslol 5 }

-- {SCALAR} 310.1.25.6
lcsStatusDslolNicErrors OBJECT-TYPE
    SYNTAX     Counter32
    MAX-ACCESS read-only
    STATUS     current
    DESCRIPTION
        "-- empty --"
    ::= { lcsStatusDslol 6 }

-- {SCALAR} 310.1.25.7
lcsStatusDslolQueuePackets OBJECT-TYPE
    SYNTAX     INTEGER (0..2147483647)
    MAX-ACCESS read-only
    STATUS     current
    DESCRIPTION
        "-- empty --"
    ::= { lcsStatusDslol 7 }

-- {SCALAR} 310.1.25.8
lcsStatusDslolQueueErrors OBJECT-TYPE
    SYNTAX     Counter32
    MAX-ACCESS read-only
    STATUS     current
    DESCRIPTION
        "-- empty --"
    ::= { lcsStatusDslol 8 }

-- {SCALAR} 310.1.25.9
lcsStatusDslolRxBytes OBJECT-TYPE
    SYNTAX     Counter64
    MAX-ACCESS read-only
    STATUS     current
    DESCRIPTION
        "-- empty --"
    ::= { lcsStatusDslol 9 }

-- {SCALAR} 310.1.25.10
lcsStatusDslolTxBytes OBJECT-TYPE
    SYNTAX     Counter64
    MAX-ACCESS read-only
    STATUS     current
    DESCRIPTION
        "-- empty --"
    ::= { lcsStatusDslol 10 }

-- {SCALAR} 310.1.25.11
lcsStatusDslolRxUnicasts OBJECT-TYPE
    SYNTAX     Counter32
    MAX-ACCESS read-only
    STATUS     current
    DESCRIPTION
        "-- empty --"
    ::= { lcsStatusDslol 11 }

-- {SCALAR} 310.1.25.12
lcsStatusDslolTxBroadcasts OBJECT-TYPE
    SYNTAX     Counter32
    MAX-ACCESS read-only
    STATUS     current
    DESCRIPTION
        "-- empty --"
    ::= { lcsStatusDslol 12 }

-- {SCALAR} 310.1.25.13
lcsStatusDslolTxUnicasts OBJECT-TYPE
    SYNTAX     Counter32
    MAX-ACCESS read-only
    STATUS     current
    DESCRIPTION
        "-- empty --"
    ::= { lcsStatusDslol 13 }

-- {SCALAR} 310.1.25.14
lcsStatusDslolLinkActive OBJECT-TYPE
    SYNTAX     INTEGER
      {
        eNo (0),
        eYes (1)
      }
    MAX-ACCESS read-only
    STATUS     current
    DESCRIPTION
        "-- empty --"
    ::= { lcsStatusDslol 14 }

-- {OID} 310.1.25.24
lcsStatusDslolDslol OBJECT IDENTIFIER ::= { lcsStatusDslol 24 }

-- {SCALAR} 310.1.25.24.1
lcsStatusDslolDslolIpConfiguration OBJECT-TYPE
    SYNTAX     INTEGER
      {
        eValid (1),
        eInvalid (0)
      }
    MAX-ACCESS read-only
    STATUS     current
    DESCRIPTION
        "-- empty --"
    ::= { lcsStatusDslolDslol 1 }

-- {SCALAR} 310.1.25.24.2
lcsStatusDslolDslolIpNetwork OBJECT-TYPE
    SYNTAX     IpAddress
    MAX-ACCESS read-only
    STATUS     current
    DESCRIPTION
        "-- empty --"
    ::= { lcsStatusDslolDslol 2 }

-- {SCALAR} 310.1.25.24.3
lcsStatusDslolDslolIpNetmask OBJECT-TYPE
    SYNTAX     IpAddress
    MAX-ACCESS read-only
    STATUS     current
    DESCRIPTION
        "-- empty --"
    ::= { lcsStatusDslolDslol 3 }

-- {SCALAR} 310.1.25.24.4
lcsStatusDslolDslolGatewayIp OBJECT-TYPE
    SYNTAX     IpAddress
    MAX-ACCESS read-only
    STATUS     current
    DESCRIPTION
        "-- empty --"
    ::= { lcsStatusDslolDslol 4 }

-- {SCALAR} 310.1.25.24.5
lcsStatusDslolDslolGatewayMac OBJECT-TYPE
    SYNTAX     DisplayString (SIZE(0..12))
    MAX-ACCESS read-only
    STATUS     current
    DESCRIPTION
        "-- empty --"
    ::= { lcsStatusDslolDslol 5 }

-- {SCALAR} 310.1.25.24.6
lcsStatusDslolDslolCatchDhcp OBJECT-TYPE
    SYNTAX     INTEGER
      {
        eYes (1),
        eNo (0)
      }
    MAX-ACCESS read-only
    STATUS     current
    DESCRIPTION
        "-- empty --"
    ::= { lcsStatusDslolDslol 6 }

-- {SCALAR} 310.1.25.24.7
lcsStatusDslolDslolExclusiveMode OBJECT-TYPE
    SYNTAX     INTEGER
      {
        eYes (1),
        eNo (0)
      }
    MAX-ACCESS read-only
    STATUS     current
    DESCRIPTION
        "-- empty --"
    ::= { lcsStatusDslolDslol 7 }

-- {SCALAR} 310.1.25.17
lcsStatusDslolRxCrcErrors OBJECT-TYPE
    SYNTAX     Counter32
    MAX-ACCESS read-only
    STATUS     current
    DESCRIPTION
        "-- empty --"
    ::= { lcsStatusDslol 17 }

-- {SCALAR} 310.1.25.18
lcsStatusDslolRxAlignErrors OBJECT-TYPE
    SYNTAX     Counter32
    MAX-ACCESS read-only
    STATUS     current
    DESCRIPTION
        "-- empty --"
    ::= { lcsStatusDslol 18 }

-- {SCALAR} 310.1.25.19
lcsStatusDslolCollisions OBJECT-TYPE
    SYNTAX     Counter32
    MAX-ACCESS read-only
    STATUS     current
    DESCRIPTION
        "-- empty --"
    ::= { lcsStatusDslol 19 }

-- {SCALAR} 310.1.25.20
lcsStatusDslolSingleCollisions OBJECT-TYPE
    SYNTAX     Counter32
    MAX-ACCESS read-only
    STATUS     current
    DESCRIPTION
        "-- empty --"
    ::= { lcsStatusDslol 20 }

-- {SCALAR} 310.1.25.21
lcsStatusDslolMultipleCollisions OBJECT-TYPE
    SYNTAX     Counter32
    MAX-ACCESS read-only
    STATUS     current
    DESCRIPTION
        "-- empty --"
    ::= { lcsStatusDslol 21 }

-- {SCALAR} 310.1.25.22
lcsStatusDslolLateCollisions OBJECT-TYPE
    SYNTAX     Counter32
    MAX-ACCESS read-only
    STATUS     current
    DESCRIPTION
        "-- empty --"
    ::= { lcsStatusDslol 22 }

-- {SCALAR} 310.1.25.23
lcsStatusDslolExcessiveCollisions OBJECT-TYPE
    SYNTAX     Counter32
    MAX-ACCESS read-only
    STATUS     current
    DESCRIPTION
        "-- empty --"
    ::= { lcsStatusDslol 23 }

-- {SCALAR} 310.1.25.25
lcsStatusDslolRxTooShort OBJECT-TYPE
    SYNTAX     Counter32
    MAX-ACCESS read-only
    STATUS     current
    DESCRIPTION
        "-- empty --"
    ::= { lcsStatusDslol 25 }

-- {SCALAR} 310.1.25.26
lcsStatusDslolRxTooLong OBJECT-TYPE
    SYNTAX     Counter32
    MAX-ACCESS read-only
    STATUS     current
    DESCRIPTION
        "-- empty --"
    ::= { lcsStatusDslol 26 }

-- {SCALAR} 310.1.25.27
lcsStatusDslolTxCarrier OBJECT-TYPE
    SYNTAX     Counter32
    MAX-ACCESS read-only
    STATUS     current
    DESCRIPTION
        "-- empty --"
    ::= { lcsStatusDslol 27 }

-- {SCALAR} 310.1.25.28
lcsStatusDslolTxDeferred OBJECT-TYPE
    SYNTAX     Counter32
    MAX-ACCESS read-only
    STATUS     current
    DESCRIPTION
        "-- empty --"
    ::= { lcsStatusDslol 28 }

-- {OID} 310.1.25.31
lcsStatusDslolPppoe OBJECT IDENTIFIER ::= { lcsStatusDslol 31 }

-- {SCALAR} 310.1.25.31.1
lcsStatusDslolPppoeTxPadi OBJECT-TYPE
    SYNTAX     INTEGER (0..2147483647)
    MAX-ACCESS read-only
    STATUS     current
    DESCRIPTION
        "-- empty --"
    ::= { lcsStatusDslolPppoe 1 }

-- {SCALAR} 310.1.25.31.2
lcsStatusDslolPppoeRxPado OBJECT-TYPE
    SYNTAX     INTEGER (0..2147483647)
    MAX-ACCESS read-only
    STATUS     current
    DESCRIPTION
        "-- empty --"
    ::= { lcsStatusDslolPppoe 2 }

-- {SCALAR} 310.1.25.31.3
lcsStatusDslolPppoeTxPadr OBJECT-TYPE
    SYNTAX     INTEGER (0..2147483647)
    MAX-ACCESS read-only
    STATUS     current
    DESCRIPTION
        "-- empty --"
    ::= { lcsStatusDslolPppoe 3 }

-- {SCALAR} 310.1.25.31.4
lcsStatusDslolPppoeRxPads OBJECT-TYPE
    SYNTAX     INTEGER (0..2147483647)
    MAX-ACCESS read-only
    STATUS     current
    DESCRIPTION
        "-- empty --"
    ::= { lcsStatusDslolPppoe 4 }

-- {SCALAR} 310.1.25.31.5
lcsStatusDslolPppoeTxPadt OBJECT-TYPE
    SYNTAX     INTEGER (0..2147483647)
    MAX-ACCESS read-only
    STATUS     current
    DESCRIPTION
        "-- empty --"
    ::= { lcsStatusDslolPppoe 5 }

-- {SCALAR} 310.1.25.31.6
lcsStatusDslolPppoeRxPadt OBJECT-TYPE
    SYNTAX     INTEGER (0..2147483647)
    MAX-ACCESS read-only
    STATUS     current
    DESCRIPTION
        "-- empty --"
    ::= { lcsStatusDslolPppoe 6 }

-- {SCALAR} 310.1.25.31.7
lcsStatusDslolPppoeTxProtocol OBJECT-TYPE
    SYNTAX     INTEGER (0..2147483647)
    MAX-ACCESS read-only
    STATUS     current
    DESCRIPTION
        "-- empty --"
    ::= { lcsStatusDslolPppoe 7 }

-- {SCALAR} 310.1.25.31.8
lcsStatusDslolPppoeRxProtocol OBJECT-TYPE
    SYNTAX     INTEGER (0..2147483647)
    MAX-ACCESS read-only
    STATUS     current
    DESCRIPTION
        "-- empty --"
    ::= { lcsStatusDslolPppoe 8 }

-- {SCALAR} 310.1.25.31.9
lcsStatusDslolPppoeTxData OBJECT-TYPE
    SYNTAX     INTEGER (0..2147483647)
    MAX-ACCESS read-only
    STATUS     current
    DESCRIPTION
        "-- empty --"
    ::= { lcsStatusDslolPppoe 9 }

-- {SCALAR} 310.1.25.31.10
lcsStatusDslolPppoeRxData OBJECT-TYPE
    SYNTAX     INTEGER (0..2147483647)
    MAX-ACCESS read-only
    STATUS     current
    DESCRIPTION
        "-- empty --"
    ::= { lcsStatusDslolPppoe 10 }

-- {SCALAR} 310.1.25.31.11
lcsStatusDslolPppoeRxBad OBJECT-TYPE
    SYNTAX     INTEGER (0..2147483647)
    MAX-ACCESS read-only
    STATUS     current
    DESCRIPTION
        "-- empty --"
    ::= { lcsStatusDslolPppoe 11 }

-- {SCALAR} 310.1.25.31.12
lcsStatusDslolPppoeAcName OBJECT-TYPE
    SYNTAX     DisplayString (SIZE(0..63))
    MAX-ACCESS read-only
    STATUS     current
    DESCRIPTION
        "-- empty --"
    ::= { lcsStatusDslolPppoe 12 }

-- {SCALAR} 310.1.25.31.13
lcsStatusDslolPppoeService OBJECT-TYPE
    SYNTAX     DisplayString (SIZE(0..63))
    MAX-ACCESS read-only
    STATUS     current
    DESCRIPTION
        "-- empty --"
    ::= { lcsStatusDslolPppoe 13 }

-- {SCALAR} 310.1.25.31.30
lcsStatusDslolPppoeDeleteValues OBJECT-TYPE
    SYNTAX     DisplayString
    MAX-ACCESS read-write
    STATUS     current
    DESCRIPTION
        "-- empty --"
    ::= { lcsStatusDslolPppoe 30 }

-- {SCALAR} 310.1.25.30
lcsStatusDslolDeleteValues OBJECT-TYPE
    SYNTAX     DisplayString
    MAX-ACCESS read-write
    STATUS     current
    DESCRIPTION
        "-- empty --"
    ::= { lcsStatusDslol 30 }

-- {OID} 310.1.27
lcsStatusPptp OBJECT IDENTIFIER ::= { lcsStatus 27 }

-- {SCALAR} 310.1.27.1
lcsStatusPptpRxPackets OBJECT-TYPE
    SYNTAX     Counter32
    MAX-ACCESS read-only
    STATUS     current
    DESCRIPTION
        "-- empty --"
    ::= { lcsStatusPptp 1 }

-- {SCALAR} 310.1.27.2
lcsStatusPptpTxPackets OBJECT-TYPE
    SYNTAX     Counter32
    MAX-ACCESS read-only
    STATUS     current
    DESCRIPTION
        "-- empty --"
    ::= { lcsStatusPptp 2 }

-- {SCALAR} 310.1.27.3
lcsStatusPptpEchoRetries OBJECT-TYPE
    SYNTAX     Counter32
    MAX-ACCESS read-only
    STATUS     current
    DESCRIPTION
        "-- empty --"
    ::= { lcsStatusPptp 3 }

-- {SCALAR} 310.1.27.4
lcsStatusPptpAckTimeouts OBJECT-TYPE
    SYNTAX     Counter32
    MAX-ACCESS read-only
    STATUS     current
    DESCRIPTION
        "-- empty --"
    ::= { lcsStatusPptp 4 }

-- {SCALAR} 310.1.27.5
lcsStatusPptpDroppedPackets OBJECT-TYPE
    SYNTAX     Counter32
    MAX-ACCESS read-only
    STATUS     current
    DESCRIPTION
        "-- empty --"
    ::= { lcsStatusPptp 5 }

-- {SCALAR} 310.1.27.6
lcsStatusPptpRxErrors OBJECT-TYPE
    SYNTAX     Counter32
    MAX-ACCESS read-only
    STATUS     current
    DESCRIPTION
        "-- empty --"
    ::= { lcsStatusPptp 6 }

-- {SCALAR} 310.1.27.7
lcsStatusPptpTcpErrors OBJECT-TYPE
    SYNTAX     Counter32
    MAX-ACCESS read-only
    STATUS     current
    DESCRIPTION
        "-- empty --"
    ::= { lcsStatusPptp 7 }

-- {SCALAR} 310.1.27.8
lcsStatusPptpCallErrors OBJECT-TYPE
    SYNTAX     Counter32
    MAX-ACCESS read-only
    STATUS     current
    DESCRIPTION
        "-- empty --"
    ::= { lcsStatusPptp 8 }

-- {TABLE} 310.1.27.9
lcsStatusPptpConnectionsTable OBJECT-TYPE
    SYNTAX     SEQUENCE OF LcsStatusPptpConnectionsEntry
    MAX-ACCESS not-accessible
    STATUS     current
    DESCRIPTION
        "-- empty --"
    ::= { lcsStatusPptp 9 }

-- {ENTRY} 310.1.27.9.1
lcsStatusPptpConnectionsEntry OBJECT-TYPE
    SYNTAX     LcsStatusPptpConnectionsEntry
    MAX-ACCESS not-accessible
    STATUS     current
    DESCRIPTION
        ""
    INDEX {
        lcsStatusPptpConnectionsEntryChannel
    }
    ::= { lcsStatusPptpConnectionsTable 1 }

-- {SEQUENCE}
LcsStatusPptpConnectionsEntry ::= SEQUENCE {
    lcsStatusPptpConnectionsEntryChannel DisplayString,
    lcsStatusPptpConnectionsEntryState INTEGER,
    lcsStatusPptpConnectionsEntryLastError INTEGER,
    lcsStatusPptpConnectionsEntryMode INTEGER,
    lcsStatusPptpConnectionsEntryShTime INTEGER,
    lcsStatusPptpConnectionsEntryPhysConnection DisplayString,
    lcsStatusPptpConnectionsEntryPeerAddress IpAddress,
    lcsStatusPptpConnectionsEntryIpAddress IpAddress,
    lcsStatusPptpConnectionsEntryDnsDefault IpAddress,
    lcsStatusPptpConnectionsEntryDnsBackup IpAddress,
    lcsStatusPptpConnectionsEntryNbnsDefault IpAddress,
    lcsStatusPptpConnectionsEntryNbnsBackup IpAddress,
    lcsStatusPptpConnectionsEntryConnTime Gauge32,
    lcsStatusPptpConnectionsEntryGateway IpAddress,
    lcsStatusPptpConnectionsEntryEncryption INTEGER
}

-- {COLUMN} 310.1.27.9.1.1
lcsStatusPptpConnectionsEntryChannel OBJECT-TYPE
    SYNTAX     DisplayString (SIZE(0..16))
    MAX-ACCESS read-only
    STATUS     current
    DESCRIPTION
        "-- empty --"
    ::= { lcsStatusPptpConnectionsEntry 1 }

-- {COLUMN} 310.1.27.9.1.3
lcsStatusPptpConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusPptpConnectionsEntry 3 }

-- {COLUMN} 310.1.27.9.1.11
lcsStatusPptpConnectionsEntryLastError OBJECT-TYPE
    SYNTAX     INTEGER
      {
        eNone (0),
        eRemoteDisconnected (17153),
        eManualDisconnect (17154),
        eShortholdExpired (17155),
        ePhysicalDisconnected (17156),
        eInvalidPhysicalChannel (17157),
        eDynamicVpnReconnect (17158),
        eConfigurationChanged (17159),
        eRemovedFromConfig (17160),
        eRemoteDoubled (267),
        eIcmpConnError (275),
        eDhcpTimeout (277),
        ePptpNoResponse (278),
        eVpnNoResponse (279),
        eArpNoResponse (280),
        ePptpNoChannel (513),
        ePptpBadFormat (514),
        ePptpBadValue (515),
        ePptpNoRessource (516),
        ePptpBadCallId (517),
        ePptpGenError (518),
        ePptpNoAddress (519),
        ePptpDnsResolvError (520),
        ePptpTcpConnError (521),
        eLcpRejected (32768),
        eAuthError (32769),
        eAuthRejected (32770),
        eLcpConnError (32771),
        ePapRejected (32784),
        ePapRxTimeout (32785),
        ePapTxTimeout (32786),
        eWrongPapReq (32787),
        ePapNakReceived (32788),
        eUnknPapPeer (32789),
        eChapRejected (32800),
        eChapRxTimeout (32801),
        eChapTxTimeout (32802),
        eWrongChapResp (32803),
        eChapFailRecvd (32804),
        eUnknChapPeer (32805),
        eIpxcpRejected (32816),
        eWrongIpxcpNet (32817),
        eIpxcpNetReject (32818),
        eIpxcpRouteUnkn (32819),
        eIpcpRejected (32832),
        eCcpRejected (32848),
        eNoNcpAvailable (33008)
      }
    MAX-ACCESS read-write
    STATUS     current
    DESCRIPTION
        "-- empty --"
    ::= { lcsStatusPptpConnectionsEntry 11 }

-- {COLUMN} 310.1.27.9.1.4
lcsStatusPptpConnectionsEntryMode OBJECT-TYPE
    SYNTAX     INTEGER
      {
        eActive (128),
        ePassive (0)
      }
    MAX-ACCESS read-only
    STATUS     current
    DESCRIPTION
        "-- empty --"
    ::= { lcsStatusPptpConnectionsEntry 4 }

-- {COLUMN} 310.1.27.9.1.5
lcsStatusPptpConnectionsEntryShTime OBJECT-TYPE
    SYNTAX     INTEGER (0..65535)
    MAX-ACCESS read-only
    STATUS     current
    DESCRIPTION
        "-- empty --"
    ::= { lcsStatusPptpConnectionsEntry 5 }

-- {COLUMN} 310.1.27.9.1.6
lcsStatusPptpConnectionsEntryPhysConnection OBJECT-TYPE
    SYNTAX     DisplayString (SIZE(0..16))
    MAX-ACCESS read-only
    STATUS     current
    DESCRIPTION
        "-- empty --"
    ::= { lcsStatusPptpConnectionsEntry 6 }

-- {COLUMN} 310.1.27.9.1.7
lcsStatusPptpConnectionsEntryPeerAddress OBJECT-TYPE
    SYNTAX     IpAddress
    MAX-ACCESS read-only
    STATUS     current
    DESCRIPTION
        "-- empty --"
    ::= { lcsStatusPptpConnectionsEntry 7 }

-- {COLUMN} 310.1.27.9.1.8
lcsStatusPptpConnectionsEntryIpAddress OBJECT-TYPE
    SYNTAX     IpAddress
    MAX-ACCESS read-only
    STATUS     current
    DESCRIPTION
        "-- empty --"
    ::= { lcsStatusPptpConnectionsEntry 8 }

-- {COLUMN} 310.1.27.9.1.9
lcsStatusPptpConnectionsEntryDnsDefault OBJECT-TYPE
    SYNTAX     IpAddress
    MAX-ACCESS read-only
    STATUS     current
    DESCRIPTION
        "-- empty --"
    ::= { lcsStatusPptpConnectionsEntry 9 }

-- {COLUMN} 310.1.27.9.1.12
lcsStatusPptpConnectionsEntryDnsBackup OBJECT-TYPE
    SYNTAX     IpAddress
    MAX-ACCESS read-only
    STATUS     current
    DESCRIPTION
        "-- empty --"
    ::= { lcsStatusPptpConnectionsEntry 12 }

-- {COLUMN} 310.1.27.9.1.10
lcsStatusPptpConnectionsEntryNbnsDefault OBJECT-TYPE
    SYNTAX     IpAddress
    MAX-ACCESS read-only
    STATUS     current
    DESCRIPTION
        "-- empty --"
    ::= { lcsStatusPptpConnectionsEntry 10 }

-- {COLUMN} 310.1.27.9.1.13
lcsStatusPptpConnectionsEntryNbnsBackup OBJECT-TYPE
    SYNTAX     IpAddress
    MAX-ACCESS read-only
    STATUS     current
    DESCRIPTION
        "-- empty --"
    ::= { lcsStatusPptpConnectionsEntry 13 }

-- {COLUMN} 310.1.27.9.1.14
lcsStatusPptpConnectionsEntryConnTime OBJECT-TYPE
    SYNTAX     Gauge32
    MAX-ACCESS read-only
    STATUS     current
    DESCRIPTION
        "-- empty --"
    ::= { lcsStatusPptpConnectionsEntry 14 }

-- {COLUMN} 310.1.27.9.1.15
lcsStatusPptpConnectionsEntryGateway OBJECT-TYPE
    SYNTAX     IpAddress
    MAX-ACCESS read-only
    STATUS     current
    DESCRIPTION
        "-- empty --"
    ::= { lcsStatusPptpConnectionsEntry 15 }

-- {COLUMN} 310.1.27.9.1.16
lcsStatusPptpConnectionsEntryEncryption OBJECT-TYPE
    SYNTAX     INTEGER
      {
        eOff (0),
        e40Bits (224),
        e56Bits (192),
        e128Bits (64)
      }
    MAX-ACCESS read-only
    STATUS     current
    DESCRIPTION
        "-- empty --"
    ::= { lcsStatusPptpConnectionsEntry 16 }

-- {SCALAR} 310.1.27.10
lcsStatusPptpTunnel OBJECT-TYPE
    SYNTAX     INTEGER (0..2147483647)
    MAX-ACCESS read-only
    STATUS     current
    DESCRIPTION
        "-- empty --"
    ::= { lcsStatusPptp 10 }

-- {SCALAR} 310.1.27.11
lcsStatusPptpDeleteValues OBJECT-TYPE
    SYNTAX     DisplayString
    MAX-ACCESS read-write
    STATUS     current
    DESCRIPTION
        "-- empty --"
    ::= { lcsStatusPptp 11 }

-- {SCALAR} 310.1.27.12
lcsStatusPptpFlowControlQueue OBJECT-TYPE
    SYNTAX     INTEGER (0..2147483647)
    MAX-ACCESS read-only
    STATUS     current
    DESCRIPTION
        "-- empty --"
    ::= { lcsStatusPptp 12 }

-- {OID} 310.1.31
lcsStatusLanBridge OBJECT IDENTIFIER ::= { lcsStatus 31 }

-- {SCALAR} 310.1.31.8
lcsStatusLanBridgeIsolatedMode OBJECT-TYPE
    SYNTAX     INTEGER
      {
        eNo (0),
        eYes (1)
      }
    MAX-ACCESS read-only
    STATUS     current
    DESCRIPTION
        "-- empty --"
    ::= { lcsStatusLanBridge 8 }

-- {TABLE} 310.1.31.1
lcsStatusLanBridgeAddressTableTable OBJECT-TYPE
    SYNTAX     SEQUENCE OF LcsStatusLanBridgeAddressTableEntry
    MAX-ACCESS not-accessible
    STATUS     current
    DESCRIPTION
        "-- empty --"
    ::= { lcsStatusLanBridge 1 }

-- {ENTRY} 310.1.31.1.1
lcsStatusLanBridgeAddressTableEntry OBJECT-TYPE
    SYNTAX     LcsStatusLanBridgeAddressTableEntry
    MAX-ACCESS not-accessible
    STATUS     current
    DESCRIPTION
        ""
    INDEX {
        lcsStatusLanBridgeAddressTableEntryIndex
    }
    ::= { lcsStatusLanBridgeAddressTableTable 1 }

-- {SEQUENCE}
LcsStatusLanBridgeAddressTableEntry ::= SEQUENCE {
    lcsStatusLanBridgeAddressTableEntryIndex INTEGER,
    lcsStatusLanBridgeAddressTableEntryAge INTEGER,
    lcsStatusLanBridgeAddressTableEntryMacAddress MacAddress,
    lcsStatusLanBridgeAddressTableEntryVlanId INTEGER,
    lcsStatusLanBridgeAddressTableEntryBridgeGroup INTEGER,
    lcsStatusLanBridgeAddressTableEntryPort DisplayString,
    lcsStatusLanBridgeAddressTableEntryBrgAddr MacAddress
}

-- {COLUMN} 310.1.31.1.1.1
lcsStatusLanBridgeAddressTableEntryIndex OBJECT-TYPE
    SYNTAX     INTEGER (0..2147483647)
    MAX-ACCESS read-only
    STATUS     current
    DESCRIPTION
        "-- empty --"
    ::= { lcsStatusLanBridgeAddressTableEntry 1 }

-- {COLUMN} 310.1.31.1.1.2
lcsStatusLanBridgeAddressTableEntryAge OBJECT-TYPE
    SYNTAX     INTEGER (0..65535)
    MAX-ACCESS read-only
    STATUS     current
    DESCRIPTION
        "-- empty --"
    ::= { lcsStatusLanBridgeAddressTableEntry 2 }

-- {COLUMN} 310.1.31.1.1.3
lcsStatusLanBridgeAddressTableEntryMacAddress OBJECT-TYPE
    SYNTAX     MacAddress
    MAX-ACCESS read-only
    STATUS     current
    DESCRIPTION
        "-- empty --"
    ::= { lcsStatusLanBridgeAddressTableEntry 3 }

-- {COLUMN} 310.1.31.1.1.7
lcsStatusLanBridgeAddressTableEntryVlanId OBJECT-TYPE
    SYNTAX     INTEGER (0..65535)
    MAX-ACCESS read-only
    STATUS     current
    DESCRIPTION
        "-- empty --"
    ::= { lcsStatusLanBridgeAddressTableEntry 7 }

-- {COLUMN} 310.1.31.1.1.8
lcsStatusLanBridgeAddressTableEntryBridgeGroup OBJECT-TYPE
    SYNTAX     INTEGER
      {
        eBrg1 (0),
        eBrg2 (1),
        eBrg3 (2),
        eBrg4 (3),
        eBrg5 (4),
        eBrg6 (5),
        eBrg7 (6),
        eBrg8 (7),
        eNone (255)
      }
    MAX-ACCESS read-only
    STATUS     current
    DESCRIPTION
        "-- empty --"
    ::= { lcsStatusLanBridgeAddressTableEntry 8 }

-- {COLUMN} 310.1.31.1.1.9
lcsStatusLanBridgeAddressTableEntryPort OBJECT-TYPE
    SYNTAX     DisplayString (SIZE(0..255))
    MAX-ACCESS read-only
    STATUS     current
    DESCRIPTION
        "-- empty --"
    ::= { lcsStatusLanBridgeAddressTableEntry 9 }

-- {COLUMN} 310.1.31.1.1.6
lcsStatusLanBridgeAddressTableEntryBrgAddr OBJECT-TYPE
    SYNTAX     MacAddress
    MAX-ACCESS read-only
    STATUS     current
    DESCRIPTION
        "-- empty --"
    ::= { lcsStatusLanBridgeAddressTableEntry 6 }

-- {TABLE} 310.1.31.11
lcsStatusLanBridgePortDataTable OBJECT-TYPE
    SYNTAX     SEQUENCE OF LcsStatusLanBridgePortDataEntry
    MAX-ACCESS not-accessible
    STATUS     current
    DESCRIPTION
        "-- empty --"
    ::= { lcsStatusLanBridge 11 }

-- {ENTRY} 310.1.31.11.1
lcsStatusLanBridgePortDataEntry OBJECT-TYPE
    SYNTAX     LcsStatusLanBridgePortDataEntry
    MAX-ACCESS not-accessible
    STATUS     current
    DESCRIPTION
        ""
    INDEX {
        lcsStatusLanBridgePortDataEntryPort
    }
    ::= { lcsStatusLanBridgePortDataTable 1 }

-- {SEQUENCE}
LcsStatusLanBridgePortDataEntry ::= SEQUENCE {
    lcsStatusLanBridgePortDataEntryPort DisplayString,
    lcsStatusLanBridgePortDataEntryOperatingState INTEGER,
    lcsStatusLanBridgePortDataEntryPointToPointPort INTEGER,
    lcsStatusLanBridgePortDataEntryBridgeGroup INTEGER,
    lcsStatusLanBridgePortDataEntryInPackets INTEGER,
    lcsStatusLanBridgePortDataEntryOutPackets INTEGER,
    lcsStatusLanBridgePortDataEntryInDiscards INTEGER
}

-- {COLUMN} 310.1.31.11.1.1
lcsStatusLanBridgePortDataEntryPort OBJECT-TYPE
    SYNTAX     DisplayString (SIZE(0..255))
    MAX-ACCESS read-only
    STATUS     current
    DESCRIPTION
        "-- empty --"
    ::= { lcsStatusLanBridgePortDataEntry 1 }

-- {COLUMN} 310.1.31.11.1.3
lcsStatusLanBridgePortDataEntryOperatingState OBJECT-TYPE
    SYNTAX     INTEGER
      {
        eUp (1),
        eDown (2),
        eTesting (3),
        eUnknown (4),
        eDormant (5),
        eNotPresent (6),
        eLowerLayerDown (7)
      }
    MAX-ACCESS read-only
    STATUS     current
    DESCRIPTION
        "-- empty --"
    ::= { lcsStatusLanBridgePortDataEntry 3 }

-- {COLUMN} 310.1.31.11.1.2
lcsStatusLanBridgePortDataEntryPointToPointPort OBJECT-TYPE
    SYNTAX     INTEGER
      {
        eNo (0),
        eYes (1)
      }
    MAX-ACCESS read-only
    STATUS     current
    DESCRIPTION
        "-- empty --"
    ::= { lcsStatusLanBridgePortDataEntry 2 }

-- {COLUMN} 310.1.31.11.1.5
lcsStatusLanBridgePortDataEntryBridgeGroup OBJECT-TYPE
    SYNTAX     INTEGER
      {
        eBrg1 (0),
        eBrg2 (1),
        eBrg3 (2),
        eBrg4 (3),
        eBrg5 (4),
        eBrg6 (5),
        eBrg7 (6),
        eBrg8 (7),
        eNone (255)
      }
    MAX-ACCESS read-only
    STATUS     current
    DESCRIPTION
        "-- empty --"
    ::= { lcsStatusLanBridgePortDataEntry 5 }

-- {COLUMN} 310.1.31.11.1.6
lcsStatusLanBridgePortDataEntryInPackets OBJECT-TYPE
    SYNTAX     INTEGER (0..2147483647)
    MAX-ACCESS read-only
    STATUS     current
    DESCRIPTION
        "-- empty --"
    ::= { lcsStatusLanBridgePortDataEntry 6 }

-- {COLUMN} 310.1.31.11.1.7
lcsStatusLanBridgePortDataEntryOutPackets OBJECT-TYPE
    SYNTAX     INTEGER (0..2147483647)
    MAX-ACCESS read-only
    STATUS     current
    DESCRIPTION
        "-- empty --"
    ::= { lcsStatusLanBridgePortDataEntry 7 }

-- {COLUMN} 310.1.31.11.1.8
lcsStatusLanBridgePortDataEntryInDiscards OBJECT-TYPE
    SYNTAX     INTEGER (0..2147483647)
    MAX-ACCESS read-only
    STATUS     current
    DESCRIPTION
        "-- empty --"
    ::= { lcsStatusLanBridgePortDataEntry 8 }

-- {SCALAR} 310.1.31.99
lcsStatusLanBridgeDeleteValues OBJECT-TYPE
    SYNTAX     DisplayString
    MAX-ACCESS read-write
    STATUS     current
    DESCRIPTION
        "-- empty --"
    ::= { lcsStatusLanBridge 99 }

-- {TABLE} 310.1.31.9
lcsStatusLanBridgeConnectionTableTable OBJECT-TYPE
    SYNTAX     SEQUENCE OF LcsStatusLanBridgeConnectionTableEntry
    MAX-ACCESS not-accessible
    STATUS     current
    DESCRIPTION
        "-- empty --"
    ::= { lcsStatusLanBridge 9 }

-- {ENTRY} 310.1.31.9.1
lcsStatusLanBridgeConnectionTableEntry OBJECT-TYPE
    SYNTAX     LcsStatusLanBridgeConnectionTableEntry
    MAX-ACCESS not-accessible
    STATUS     current
    DESCRIPTION
        ""
    INDEX {
        lcsStatusLanBridgeConnectionTableEntryIndex
    }
    ::= { lcsStatusLanBridgeConnectionTableTable 1 }

-- {SEQUENCE}
LcsStatusLanBridgeConnectionTableEntry ::= SEQUENCE {
    lcsStatusLanBridgeConnectionTableEntryIndex INTEGER,
    lcsStatusLanBridgeConnectionTableEntryInterface INTEGER,
    lcsStatusLanBridgeConnectionTableEntryName DisplayString,
    lcsStatusLanBridgeConnectionTableEntryProtocol DisplayString,
    lcsStatusLanBridgeConnectionTableEntrySubProtocol INTEGER,
    lcsStatusLanBridgeConnectionTableEntrySourceAddress IpAddress,
    lcsStatusLanBridgeConnectionTableEntrySourcePort INTEGER,
    lcsStatusLanBridgeConnectionTableEntryDestPort INTEGER,
    lcsStatusLanBridgeConnectionTableEntryDestAddress IpAddress,
    lcsStatusLanBridgeConnectionTableEntryDestMac DisplayString,
    lcsStatusLanBridgeConnectionTableEntryAge INTEGER
}

-- {COLUMN} 310.1.31.9.1.1
lcsStatusLanBridgeConnectionTableEntryIndex OBJECT-TYPE
    SYNTAX     INTEGER (0..2147483647)
    MAX-ACCESS read-only
    STATUS     current
    DESCRIPTION
        "-- empty --"
    ::= { lcsStatusLanBridgeConnectionTableEntry 1 }

-- {COLUMN} 310.1.31.9.1.11
lcsStatusLanBridgeConnectionTableEntryInterface OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsStatusLanBridgeConnectionTableEntry 11 }

-- {COLUMN} 310.1.31.9.1.12
lcsStatusLanBridgeConnectionTableEntryName OBJECT-TYPE
    SYNTAX     DisplayString (SIZE(0..15))
    MAX-ACCESS read-only
    STATUS     current
    DESCRIPTION
        "-- empty --"
    ::= { lcsStatusLanBridgeConnectionTableEntry 12 }

-- {COLUMN} 310.1.31.9.1.3
lcsStatusLanBridgeConnectionTableEntryProtocol OBJECT-TYPE
    SYNTAX     DisplayString (SIZE(0..4))
    MAX-ACCESS read-only
    STATUS     current
    DESCRIPTION
        "-- empty --"
    ::= { lcsStatusLanBridgeConnectionTableEntry 3 }

-- {COLUMN} 310.1.31.9.1.4
lcsStatusLanBridgeConnectionTableEntrySubProtocol OBJECT-TYPE
    SYNTAX     INTEGER (0..65535)
    MAX-ACCESS read-only
    STATUS     current
    DESCRIPTION
        "-- empty --"
    ::= { lcsStatusLanBridgeConnectionTableEntry 4 }

-- {COLUMN} 310.1.31.9.1.5
lcsStatusLanBridgeConnectionTableEntrySourceAddress OBJECT-TYPE
    SYNTAX     IpAddress
    MAX-ACCESS read-only
    STATUS     current
    DESCRIPTION
        "-- empty --"
    ::= { lcsStatusLanBridgeConnectionTableEntry 5 }

-- {COLUMN} 310.1.31.9.1.6
lcsStatusLanBridgeConnectionTableEntrySourcePort OBJECT-TYPE
    SYNTAX     INTEGER (0..65535)
    MAX-ACCESS read-only
    STATUS     current
    DESCRIPTION
        "-- empty --"
    ::= { lcsStatusLanBridgeConnectionTableEntry 6 }

-- {COLUMN} 310.1.31.9.1.7
lcsStatusLanBridgeConnectionTableEntryDestPort OBJECT-TYPE
    SYNTAX     INTEGER (0..65535)
    MAX-ACCESS read-only
    STATUS     current
    DESCRIPTION
        "-- empty --"
    ::= { lcsStatusLanBridgeConnectionTableEntry 7 }

-- {COLUMN} 310.1.31.9.1.8
lcsStatusLanBridgeConnectionTableEntryDestAddress OBJECT-TYPE
    SYNTAX     IpAddress
    MAX-ACCESS read-only
    STATUS     current
    DESCRIPTION
        "-- empty --"
    ::= { lcsStatusLanBridgeConnectionTableEntry 8 }

-- {COLUMN} 310.1.31.9.1.9
lcsStatusLanBridgeConnectionTableEntryDestMac OBJECT-TYPE
    SYNTAX     DisplayString (SIZE(0..12))
    MAX-ACCESS read-only
    STATUS     current
    DESCRIPTION
        "-- empty --"
    ::= { lcsStatusLanBridgeConnectionTableEntry 9 }

-- {COLUMN} 310.1.31.9.1.10
lcsStatusLanBridgeConnectionTableEntryAge OBJECT-TYPE
    SYNTAX     INTEGER (0..2147483647)
    MAX-ACCESS read-only
    STATUS     current
    DESCRIPTION
        "-- empty --"
    ::= { lcsStatusLanBridgeConnectionTableEntry 10 }

-- {TABLE} 310.1.31.10
lcsStatusLanBridgeDhcpTableTable OBJECT-TYPE
    SYNTAX     SEQUENCE OF LcsStatusLanBridgeDhcpTableEntry
    MAX-ACCESS not-accessible
    STATUS     current
    DESCRIPTION
        "-- empty --"
    ::= { lcsStatusLanBridge 10 }

-- {ENTRY} 310.1.31.10.1
lcsStatusLanBridgeDhcpTableEntry OBJECT-TYPE
    SYNTAX     LcsStatusLanBridgeDhcpTableEntry
    MAX-ACCESS not-accessible
    STATUS     current
    DESCRIPTION
        ""
    INDEX {
        lcsStatusLanBridgeDhcpTableEntryMacAddress
    }
    ::= { lcsStatusLanBridgeDhcpTableTable 1 }

-- {SEQUENCE}
LcsStatusLanBridgeDhcpTableEntry ::= SEQUENCE {
    lcsStatusLanBridgeDhcpTableEntryMacAddress MacAddress,
    lcsStatusLanBridgeDhcpTableEntryPort DisplayString,
    lcsStatusLanBridgeDhcpTableEntrySrcPort DisplayString,
    lcsStatusLanBridgeDhcpTableEntryIpAddress IpAddress,
    lcsStatusLanBridgeDhcpTableEntryLastUpdate INTEGER
}

-- {COLUMN} 310.1.31.10.1.1
lcsStatusLanBridgeDhcpTableEntryMacAddress OBJECT-TYPE
    SYNTAX     MacAddress
    MAX-ACCESS read-only
    STATUS     current
    DESCRIPTION
        "-- empty --"
    ::= { lcsStatusLanBridgeDhcpTableEntry 1 }

-- {COLUMN} 310.1.31.10.1.6
lcsStatusLanBridgeDhcpTableEntryPort OBJECT-TYPE
    SYNTAX     DisplayString (SIZE(0..255))
    MAX-ACCESS read-only
    STATUS     current
    DESCRIPTION
        "-- empty --"
    ::= { lcsStatusLanBridgeDhcpTableEntry 6 }

-- {COLUMN} 310.1.31.10.1.7
lcsStatusLanBridgeDhcpTableEntrySrcPort OBJECT-TYPE
    SYNTAX     DisplayString (SIZE(0..255))
    MAX-ACCESS read-only
    STATUS     current
    DESCRIPTION
        "-- empty --"
    ::= { lcsStatusLanBridgeDhcpTableEntry 7 }

-- {COLUMN} 310.1.31.10.1.4
lcsStatusLanBridgeDhcpTableEntryIpAddress OBJECT-TYPE
    SYNTAX     IpAddress
    MAX-ACCESS read-only
    STATUS     current
    DESCRIPTION
        "-- empty --"
    ::= { lcsStatusLanBridgeDhcpTableEntry 4 }

-- {COLUMN} 310.1.31.10.1.5
lcsStatusLanBridgeDhcpTableEntryLastUpdate OBJECT-TYPE
    SYNTAX     INTEGER (0..2147483647)
    MAX-ACCESS read-only
    STATUS     current
    DESCRIPTION
        "-- empty --"
    ::= { lcsStatusLanBridgeDhcpTableEntry 5 }

-- {OID} 310.1.31.20
lcsStatusLanBridgeSpanningTree OBJECT IDENTIFIER ::= { lcsStatusLanBridge 20 }

-- {SCALAR} 310.1.31.20.1
lcsStatusLanBridgeSpanningTreeOperating OBJECT-TYPE
    SYNTAX     INTEGER
      {
        eNo (0),
        eYes (1)
      }
    MAX-ACCESS read-only
    STATUS     current
    DESCRIPTION
        "-- empty --"
    ::= { lcsStatusLanBridgeSpanningTree 1 }

-- {SCALAR} 310.1.31.20.2
lcsStatusLanBridgeSpanningTreeBridgeId OBJECT-TYPE
    SYNTAX     DisplayString (SIZE(0..20))
    MAX-ACCESS read-only
    STATUS     current
    DESCRIPTION
        "-- empty --"
    ::= { lcsStatusLanBridgeSpanningTree 2 }

-- {SCALAR} 310.1.31.20.3
lcsStatusLanBridgeSpanningTreeRootBridge OBJECT-TYPE
    SYNTAX     DisplayString (SIZE(0..20))
    MAX-ACCESS read-only
    STATUS     current
    DESCRIPTION
        "-- empty --"
    ::= { lcsStatusLanBridgeSpanningTree 3 }

-- {SCALAR} 310.1.31.20.11
lcsStatusLanBridgeSpanningTreeRootPort OBJECT-TYPE
    SYNTAX     DisplayString
    MAX-ACCESS read-only
    STATUS     current
    DESCRIPTION
        "-- empty --"
    ::= { lcsStatusLanBridgeSpanningTree 11 }

-- {SCALAR} 310.1.31.20.5
lcsStatusLanBridgeSpanningTreeRootPathCost OBJECT-TYPE
    SYNTAX     INTEGER (0..2147483647)
    MAX-ACCESS read-only
    STATUS     current
    DESCRIPTION
        "-- empty --"
    ::= { lcsStatusLanBridgeSpanningTree 5 }

-- {TABLE} 310.1.31.20.6
lcsStatusLanBridgeSpanningTreePortTableTable OBJECT-TYPE
    SYNTAX     SEQUENCE OF LcsStatusLanBridgeSpanningTreePortTableEntry
    MAX-ACCESS not-accessible
    STATUS     current
    DESCRIPTION
        "-- empty --"
    ::= { lcsStatusLanBridgeSpanningTree 6 }

-- {ENTRY} 310.1.31.20.6.1
lcsStatusLanBridgeSpanningTreePortTableEntry OBJECT-TYPE
    SYNTAX     LcsStatusLanBridgeSpanningTreePortTableEntry
    MAX-ACCESS not-accessible
    STATUS     current
    DESCRIPTION
        ""
    INDEX {
        lcsStatusLanBridgeSpanningTreePortTableEntryDescription
    }
    ::= { lcsStatusLanBridgeSpanningTreePortTableTable 1 }

-- {SEQUENCE}
LcsStatusLanBridgeSpanningTreePortTableEntry ::= SEQUENCE {
    lcsStatusLanBridgeSpanningTreePortTableEntryDescription DisplayString,
    lcsStatusLanBridgeSpanningTreePortTableEntryPriority INTEGER,
    lcsStatusLanBridgeSpanningTreePortTableEntryState INTEGER,
    lcsStatusLanBridgeSpanningTreePortTableEntryRoot DisplayString,
    lcsStatusLanBridgeSpanningTreePortTableEntryBridge DisplayString,
    lcsStatusLanBridgeSpanningTreePortTableEntryPathCost INTEGER
}

-- {COLUMN} 310.1.31.20.6.1.1
lcsStatusLanBridgeSpanningTreePortTableEntryDescription OBJECT-TYPE
    SYNTAX     DisplayString (SIZE(0..13))
    MAX-ACCESS read-only
    STATUS     current
    DESCRIPTION
        "-- empty --"
    ::= { lcsStatusLanBridgeSpanningTreePortTableEntry 1 }

-- {COLUMN} 310.1.31.20.6.1.2
lcsStatusLanBridgeSpanningTreePortTableEntryPriority OBJECT-TYPE
    SYNTAX     INTEGER (0..255)
    MAX-ACCESS read-only
    STATUS     current
    DESCRIPTION
        "-- empty --"
    ::= { lcsStatusLanBridgeSpanningTreePortTableEntry 2 }

-- {COLUMN} 310.1.31.20.6.1.3
lcsStatusLanBridgeSpanningTreePortTableEntryState OBJECT-TYPE
    SYNTAX     INTEGER
      {
        eDisabled (0),
        eListening (1),
        eLearning (2),
        eForwarding (3),
        eBlocking (4)
      }
    MAX-ACCESS read-only
    STATUS     current
    DESCRIPTION
        "-- empty --"
    ::= { lcsStatusLanBridgeSpanningTreePortTableEntry 3 }

-- {COLUMN} 310.1.31.20.6.1.4
lcsStatusLanBridgeSpanningTreePortTableEntryRoot OBJECT-TYPE
    SYNTAX     DisplayString (SIZE(0..16))
    MAX-ACCESS read-only
    STATUS     current
    DESCRIPTION
        "-- empty --"
    ::= { lcsStatusLanBridgeSpanningTreePortTableEntry 4 }

-- {COLUMN} 310.1.31.20.6.1.5
lcsStatusLanBridgeSpanningTreePortTableEntryBridge OBJECT-TYPE
    SYNTAX     DisplayString (SIZE(0..16))
    MAX-ACCESS read-only
    STATUS     current
    DESCRIPTION
        "-- empty --"
    ::= { lcsStatusLanBridgeSpanningTreePortTableEntry 5 }

-- {COLUMN} 310.1.31.20.6.1.6
lcsStatusLanBridgeSpanningTreePortTableEntryPathCost OBJECT-TYPE
    SYNTAX     INTEGER (0..2147483647)
    MAX-ACCESS read-only
    STATUS     current
    DESCRIPTION
        "-- empty --"
    ::= { lcsStatusLanBridgeSpanningTreePortTableEntry 6 }

-- {SCALAR} 310.1.31.20.7
lcsStatusLanBridgeSpanningTreeProtocolVersion OBJECT-TYPE
    SYNTAX     INTEGER
      {
        eClassic (0),
        eRapid (1)
      }
    MAX-ACCESS read-only
    STATUS     current
    DESCRIPTION
        "-- empty --"
    ::= { lcsStatusLanBridgeSpanningTree 7 }

-- {SCALAR} 310.1.31.20.8
lcsStatusLanBridgeSpanningTreePathCostComputation OBJECT-TYPE
    SYNTAX     INTEGER
      {
        eClassic (0),
        eRapid (1)
      }
    MAX-ACCESS read-only
    STATUS     current
    DESCRIPTION
        "-- empty --"
    ::= { lcsStatusLanBridgeSpanningTree 8 }

-- {SCALAR} 310.1.31.20.9
lcsStatusLanBridgeSpanningTreeBridgePriority OBJECT-TYPE
    SYNTAX     INTEGER (0..65535)
    MAX-ACCESS read-only
    STATUS     current
    DESCRIPTION
        "-- empty --"
    ::= { lcsStatusLanBridgeSpanningTree 9 }

-- {TABLE} 310.1.31.20.12
lcsStatusLanBridgeSpanningTreeLogTableTable OBJECT-TYPE
    SYNTAX     SEQUENCE OF LcsStatusLanBridgeSpanningTreeLogTableEntry
    MAX-ACCESS not-accessible
    STATUS     current
    DESCRIPTION
        "-- empty --"
    ::= { lcsStatusLanBridgeSpanningTree 12 }

-- {ENTRY} 310.1.31.20.12.1
lcsStatusLanBridgeSpanningTreeLogTableEntry OBJECT-TYPE
    SYNTAX     LcsStatusLanBridgeSpanningTreeLogTableEntry
    MAX-ACCESS not-accessible
    STATUS     current
    DESCRIPTION
        ""
    INDEX {
        lcsStatusLanBridgeSpanningTreeLogTableEntryIndex
    }
    ::= { lcsStatusLanBridgeSpanningTreeLogTableTable 1 }

-- {SEQUENCE}
LcsStatusLanBridgeSpanningTreeLogTableEntry ::= SEQUENCE {
    lcsStatusLanBridgeSpanningTreeLogTableEntryIndex INTEGER,
    lcsStatusLanBridgeSpanningTreeLogTableEntryTime DisplayString,
    lcsStatusLanBridgeSpanningTreeLogTableEntryEvent DisplayString
}

-- {COLUMN} 310.1.31.20.12.1.1
lcsStatusLanBridgeSpanningTreeLogTableEntryIndex OBJECT-TYPE
    SYNTAX     INTEGER (0..2147483647)
    MAX-ACCESS read-only
    STATUS     current
    DESCRIPTION
        "-- empty --"
    ::= { lcsStatusLanBridgeSpanningTreeLogTableEntry 1 }

-- {COLUMN} 310.1.31.20.12.1.2
lcsStatusLanBridgeSpanningTreeLogTableEntryTime OBJECT-TYPE
    SYNTAX     DisplayString (SIZE(0..19))
    MAX-ACCESS read-only
    STATUS     current
    DESCRIPTION
        "-- empty --"
    ::= { lcsStatusLanBridgeSpanningTreeLogTableEntry 2 }

-- {COLUMN} 310.1.31.20.12.1.3
lcsStatusLanBridgeSpanningTreeLogTableEntryEvent OBJECT-TYPE
    SYNTAX     DisplayString (SIZE(0..69))
    MAX-ACCESS read-only
    STATUS     current
    DESCRIPTION
        "-- empty --"
    ::= { lcsStatusLanBridgeSpanningTreeLogTableEntry 3 }

-- {TABLE} 310.1.31.20.10
lcsStatusLanBridgeSpanningTreeRstpPortTableTable OBJECT-TYPE
    SYNTAX     SEQUENCE OF LcsStatusLanBridgeSpanningTreeRstpPortTableEntry
    MAX-ACCESS not-accessible
    STATUS     current
    DESCRIPTION
        "-- empty --"
    ::= { lcsStatusLanBridgeSpanningTree 10 }

-- {ENTRY} 310.1.31.20.10.1
lcsStatusLanBridgeSpanningTreeRstpPortTableEntry OBJECT-TYPE
    SYNTAX     LcsStatusLanBridgeSpanningTreeRstpPortTableEntry
    MAX-ACCESS not-accessible
    STATUS     current
    DESCRIPTION
        ""
    INDEX {
        lcsStatusLanBridgeSpanningTreeRstpPortTableEntryDescription
    }
    ::= { lcsStatusLanBridgeSpanningTreeRstpPortTableTable 1 }

-- {SEQUENCE}
LcsStatusLanBridgeSpanningTreeRstpPortTableEntry ::= SEQUENCE {
    lcsStatusLanBridgeSpanningTreeRstpPortTableEntryDescription DisplayString,
    lcsStatusLanBridgeSpanningTreeRstpPortTableEntryRole INTEGER,
    lcsStatusLanBridgeSpanningTreeRstpPortTableEntryLearning INTEGER,
    lcsStatusLanBridgeSpanningTreeRstpPortTableEntryForwarding INTEGER,
    lcsStatusLanBridgeSpanningTreeRstpPortTableEntryEdgePort INTEGER,
    lcsStatusLanBridgeSpanningTreeRstpPortTableEntryProtocolVersion INTEGER,
    lcsStatusLanBridgeSpanningTreeRstpPortTableEntryPathCost INTEGER
}

-- {COLUMN} 310.1.31.20.10.1.1
lcsStatusLanBridgeSpanningTreeRstpPortTableEntryDescription OBJECT-TYPE
    SYNTAX     DisplayString (SIZE(0..255))
    MAX-ACCESS read-only
    STATUS     current
    DESCRIPTION
        "-- empty --"
    ::= { lcsStatusLanBridgeSpanningTreeRstpPortTableEntry 1 }

-- {COLUMN} 310.1.31.20.10.1.2
lcsStatusLanBridgeSpanningTreeRstpPortTableEntryRole OBJECT-TYPE
    SYNTAX     INTEGER
      {
        eRoot (0),
        eDesignated (1),
        eAlternate (2),
        eBackup (3),
        eDisabled (4)
      }
    MAX-ACCESS read-only
    STATUS     current
    DESCRIPTION
        "-- empty --"
    ::= { lcsStatusLanBridgeSpanningTreeRstpPortTableEntry 2 }

-- {COLUMN} 310.1.31.20.10.1.3
lcsStatusLanBridgeSpanningTreeRstpPortTableEntryLearning OBJECT-TYPE
    SYNTAX     INTEGER
      {
        eNo (0),
        eYes (1)
      }
    MAX-ACCESS read-only
    STATUS     current
    DESCRIPTION
        "-- empty --"
    ::= { lcsStatusLanBridgeSpanningTreeRstpPortTableEntry 3 }

-- {COLUMN} 310.1.31.20.10.1.4
lcsStatusLanBridgeSpanningTreeRstpPortTableEntryForwarding OBJECT-TYPE
    SYNTAX     INTEGER
      {
        eNo (0),
        eYes (1)
      }
    MAX-ACCESS read-only
    STATUS     current
    DESCRIPTION
        "-- empty --"
    ::= { lcsStatusLanBridgeSpanningTreeRstpPortTableEntry 4 }

-- {COLUMN} 310.1.31.20.10.1.5
lcsStatusLanBridgeSpanningTreeRstpPortTableEntryEdgePort OBJECT-TYPE
    SYNTAX     INTEGER
      {
        eNo (0),
        eYes (1)
      }
    MAX-ACCESS read-only
    STATUS     current
    DESCRIPTION
        "-- empty --"
    ::= { lcsStatusLanBridgeSpanningTreeRstpPortTableEntry 5 }

-- {COLUMN} 310.1.31.20.10.1.6
lcsStatusLanBridgeSpanningTreeRstpPortTableEntryProtocolVersion OBJECT-TYPE
    SYNTAX     INTEGER
      {
        eClassic (0),
        eRapid (1)
      }
    MAX-ACCESS read-only
    STATUS     current
    DESCRIPTION
        "-- empty --"
    ::= { lcsStatusLanBridgeSpanningTreeRstpPortTableEntry 6 }

-- {COLUMN} 310.1.31.20.10.1.7
lcsStatusLanBridgeSpanningTreeRstpPortTableEntryPathCost OBJECT-TYPE
    SYNTAX     INTEGER (0..2147483647)
    MAX-ACCESS read-only
    STATUS     current
    DESCRIPTION
        "-- empty --"
    ::= { lcsStatusLanBridgeSpanningTreeRstpPortTableEntry 7 }

-- {OID} 310.1.31.30
lcsStatusLanBridgeIgmpSnooping OBJECT IDENTIFIER ::= { lcsStatusLanBridge 30 }

-- {SCALAR} 310.1.31.30.1
lcsStatusLanBridgeIgmpSnoopingOperating OBJECT-TYPE
    SYNTAX     INTEGER
      {
        eNo (0),
        eYes (1)
      }
    MAX-ACCESS read-only
    STATUS     current
    DESCRIPTION
        "-- empty --"
    ::= { lcsStatusLanBridgeIgmpSnooping 1 }

-- {TABLE} 310.1.31.30.2
lcsStatusLanBridgeIgmpSnoopingPortStatusTable OBJECT-TYPE
    SYNTAX     SEQUENCE OF LcsStatusLanBridgeIgmpSnoopingPortStatusEntry
    MAX-ACCESS not-accessible
    STATUS     current
    DESCRIPTION
        "-- empty --"
    ::= { lcsStatusLanBridgeIgmpSnooping 2 }

-- {ENTRY} 310.1.31.30.2.1
lcsStatusLanBridgeIgmpSnoopingPortStatusEntry OBJECT-TYPE
    SYNTAX     LcsStatusLanBridgeIgmpSnoopingPortStatusEntry
    MAX-ACCESS not-accessible
    STATUS     current
    DESCRIPTION
        ""
    INDEX {
        lcsStatusLanBridgeIgmpSnoopingPortStatusEntryPort
    }
    ::= { lcsStatusLanBridgeIgmpSnoopingPortStatusTable 1 }

-- {SEQUENCE}
LcsStatusLanBridgeIgmpSnoopingPortStatusEntry ::= SEQUENCE {
    lcsStatusLanBridgeIgmpSnoopingPortStatusEntryPort DisplayString,
    lcsStatusLanBridgeIgmpSnoopingPortStatusEntryRouterPort INTEGER,
    lcsStatusLanBridgeIgmpSnoopingPortStatusEntryIpv4Packets Counter32,
    lcsStatusLanBridgeIgmpSnoopingPortStatusEntryDataPackets Counter32,
    lcsStatusLanBridgeIgmpSnoopingPortStatusEntryControlPackets Counter32,
    lcsStatusLanBridgeIgmpSnoopingPortStatusEntryBadPackets Counter32
}

-- {COLUMN} 310.1.31.30.2.1.1
lcsStatusLanBridgeIgmpSnoopingPortStatusEntryPort OBJECT-TYPE
    SYNTAX     DisplayString (SIZE(0..13))
    MAX-ACCESS read-only
    STATUS     current
    DESCRIPTION
        "-- empty --"
    ::= { lcsStatusLanBridgeIgmpSnoopingPortStatusEntry 1 }

-- {COLUMN} 310.1.31.30.2.1.2
lcsStatusLanBridgeIgmpSnoopingPortStatusEntryRouterPort OBJECT-TYPE
    SYNTAX     INTEGER
      {
        eNo (0),
        eAuto (1),
        eYes (2)
      }
    MAX-ACCESS read-only
    STATUS     current
    DESCRIPTION
        "-- empty --"
    ::= { lcsStatusLanBridgeIgmpSnoopingPortStatusEntry 2 }

-- {COLUMN} 310.1.31.30.2.1.10
lcsStatusLanBridgeIgmpSnoopingPortStatusEntryIpv4Packets OBJECT-TYPE
    SYNTAX     Counter32
    MAX-ACCESS read-only
    STATUS     current
    DESCRIPTION
        "-- empty --"
    ::= { lcsStatusLanBridgeIgmpSnoopingPortStatusEntry 10 }

-- {COLUMN} 310.1.31.30.2.1.12
lcsStatusLanBridgeIgmpSnoopingPortStatusEntryDataPackets OBJECT-TYPE
    SYNTAX     Counter32
    MAX-ACCESS read-only
    STATUS     current
    DESCRIPTION
        "-- empty --"
    ::= { lcsStatusLanBridgeIgmpSnoopingPortStatusEntry 12 }

-- {COLUMN} 310.1.31.30.2.1.13
lcsStatusLanBridgeIgmpSnoopingPortStatusEntryControlPackets OBJECT-TYPE
    SYNTAX     Counter32
    MAX-ACCESS read-only
    STATUS     current
    DESCRIPTION
        "-- empty --"
    ::= { lcsStatusLanBridgeIgmpSnoopingPortStatusEntry 13 }

-- {COLUMN} 310.1.31.30.2.1.14
lcsStatusLanBridgeIgmpSnoopingPortStatusEntryBadPackets OBJECT-TYPE
    SYNTAX     Counter32
    MAX-ACCESS read-only
    STATUS     current
    DESCRIPTION
        "-- empty --"
    ::= { lcsStatusLanBridgeIgmpSnoopingPortStatusEntry 14 }

-- {TABLE} 310.1.31.30.3
lcsStatusLanBridgeIgmpSnoopingGroupsTable OBJECT-TYPE
    SYNTAX     SEQUENCE OF LcsStatusLanBridgeIgmpSnoopingGroupsEntry
    MAX-ACCESS not-accessible
    STATUS     current
    DESCRIPTION
        "-- empty --"
    ::= { lcsStatusLanBridgeIgmpSnooping 3 }

-- {ENTRY} 310.1.31.30.3.1
lcsStatusLanBridgeIgmpSnoopingGroupsEntry OBJECT-TYPE
    SYNTAX     LcsStatusLanBridgeIgmpSnoopingGroupsEntry
    MAX-ACCESS not-accessible
    STATUS     current
    DESCRIPTION
        ""
    INDEX {
        lcsStatusLanBridgeIgmpSnoopingGroupsEntryAddress,
        lcsStatusLanBridgeIgmpSnoopingGroupsEntryVlanId
    }
    ::= { lcsStatusLanBridgeIgmpSnoopingGroupsTable 1 }

-- {SEQUENCE}
LcsStatusLanBridgeIgmpSnoopingGroupsEntry ::= SEQUENCE {
    lcsStatusLanBridgeIgmpSnoopingGroupsEntryAddress IpAddress,
    lcsStatusLanBridgeIgmpSnoopingGroupsEntryVlanId INTEGER,
    lcsStatusLanBridgeIgmpSnoopingGroupsEntryAllowLearning INTEGER,
    lcsStatusLanBridgeIgmpSnoopingGroupsEntryStaticMembers DisplayString,
    lcsStatusLanBridgeIgmpSnoopingGroupsEntryDynamicMembers DisplayString
}

-- {COLUMN} 310.1.31.30.3.1.1
lcsStatusLanBridgeIgmpSnoopingGroupsEntryAddress OBJECT-TYPE
    SYNTAX     IpAddress
    MAX-ACCESS read-only
    STATUS     current
    DESCRIPTION
        "-- empty --"
    ::= { lcsStatusLanBridgeIgmpSnoopingGroupsEntry 1 }

-- {COLUMN} 310.1.31.30.3.1.4
lcsStatusLanBridgeIgmpSnoopingGroupsEntryVlanId OBJECT-TYPE
    SYNTAX     INTEGER (0..65535)
    MAX-ACCESS read-only
    STATUS     current
    DESCRIPTION
        "-- empty --"
    ::= { lcsStatusLanBridgeIgmpSnoopingGroupsEntry 4 }

-- {COLUMN} 310.1.31.30.3.1.5
lcsStatusLanBridgeIgmpSnoopingGroupsEntryAllowLearning OBJECT-TYPE
    SYNTAX     INTEGER
      {
        eYes (0),
        eNo (1)
      }
    MAX-ACCESS read-only
    STATUS     current
    DESCRIPTION
        "-- empty --"
    ::= { lcsStatusLanBridgeIgmpSnoopingGroupsEntry 5 }

-- {COLUMN} 310.1.31.30.3.1.3
lcsStatusLanBridgeIgmpSnoopingGroupsEntryStaticMembers OBJECT-TYPE
    SYNTAX     DisplayString (SIZE(0..255))
    MAX-ACCESS read-only
    STATUS     current
    DESCRIPTION
        "-- empty --"
    ::= { lcsStatusLanBridgeIgmpSnoopingGroupsEntry 3 }

-- {COLUMN} 310.1.31.30.3.1.2
lcsStatusLanBridgeIgmpSnoopingGroupsEntryDynamicMembers OBJECT-TYPE
    SYNTAX     DisplayString (SIZE(0..255))
    MAX-ACCESS read-only
    STATUS     current
    DESCRIPTION
        "-- empty --"
    ::= { lcsStatusLanBridgeIgmpSnoopingGroupsEntry 2 }

-- {TABLE} 310.1.31.30.4
lcsStatusLanBridgeIgmpSnoopingSimulatedQueriersTable OBJECT-TYPE
    SYNTAX     SEQUENCE OF LcsStatusLanBridgeIgmpSnoopingSimulatedQueriersEntry
    MAX-ACCESS not-accessible
    STATUS     current
    DESCRIPTION
        "-- empty --"
    ::= { lcsStatusLanBridgeIgmpSnooping 4 }

-- {ENTRY} 310.1.31.30.4.1
lcsStatusLanBridgeIgmpSnoopingSimulatedQueriersEntry OBJECT-TYPE
    SYNTAX     LcsStatusLanBridgeIgmpSnoopingSimulatedQueriersEntry
    MAX-ACCESS not-accessible
    STATUS     current
    DESCRIPTION
        ""
    INDEX {
        lcsStatusLanBridgeIgmpSnoopingSimulatedQueriersEntryName
    }
    ::= { lcsStatusLanBridgeIgmpSnoopingSimulatedQueriersTable 1 }

-- {SEQUENCE}
LcsStatusLanBridgeIgmpSnoopingSimulatedQueriersEntry ::= SEQUENCE {
    lcsStatusLanBridgeIgmpSnoopingSimulatedQueriersEntryName DisplayString,
    lcsStatusLanBridgeIgmpSnoopingSimulatedQueriersEntryBridgeGroup INTEGER,
    lcsStatusLanBridgeIgmpSnoopingSimulatedQueriersEntryVlanId INTEGER,
    lcsStatusLanBridgeIgmpSnoopingSimulatedQueriersEntryStatus INTEGER
}

-- {COLUMN} 310.1.31.30.4.1.1
lcsStatusLanBridgeIgmpSnoopingSimulatedQueriersEntryName OBJECT-TYPE
    SYNTAX     DisplayString (SIZE(0..255))
    MAX-ACCESS read-only
    STATUS     current
    DESCRIPTION
        "-- empty --"
    ::= { lcsStatusLanBridgeIgmpSnoopingSimulatedQueriersEntry 1 }

-- {COLUMN} 310.1.31.30.4.1.3
lcsStatusLanBridgeIgmpSnoopingSimulatedQueriersEntryBridgeGroup OBJECT-TYPE
    SYNTAX     INTEGER
      {
        eBrg1 (0),
        eBrg2 (1),
        eBrg3 (2),
        eBrg4 (3),
        eBrg5 (4),
        eBrg6 (5),
        eBrg7 (6),
        eBrg8 (7),
        eNone (255)
      }
    MAX-ACCESS read-only
    STATUS     current
    DESCRIPTION
        "-- empty --"
    ::= { lcsStatusLanBridgeIgmpSnoopingSimulatedQueriersEntry 3 }

-- {COLUMN} 310.1.31.30.4.1.4
lcsStatusLanBridgeIgmpSnoopingSimulatedQueriersEntryVlanId OBJECT-TYPE
    SYNTAX     INTEGER (0..65535)
    MAX-ACCESS read-only
    STATUS     current
    DESCRIPTION
        "-- empty --"
    ::= { lcsStatusLanBridgeIgmpSnoopingSimulatedQueriersEntry 4 }

-- {COLUMN} 310.1.31.30.4.1.5
lcsStatusLanBridgeIgmpSnoopingSimulatedQueriersEntryStatus OBJECT-TYPE
    SYNTAX     INTEGER
      {
        eInitial (0),
        eQuerier (1),
        eNonQuerier (2)
      }
    MAX-ACCESS read-only
    STATUS     current
    DESCRIPTION
        "-- empty --"
    ::= { lcsStatusLanBridgeIgmpSnoopingSimulatedQueriersEntry 5 }

-- {SCALAR} 310.1.31.30.10
lcsStatusLanBridgeIgmpSnoopingIpv4Packets OBJECT-TYPE
    SYNTAX     Counter32
    MAX-ACCESS read-only
    STATUS     current
    DESCRIPTION
        "-- empty --"
    ::= { lcsStatusLanBridgeIgmpSnooping 10 }

-- {SCALAR} 310.1.31.30.12
lcsStatusLanBridgeIgmpSnoopingDataPackets OBJECT-TYPE
    SYNTAX     Counter32
    MAX-ACCESS read-only
    STATUS     current
    DESCRIPTION
        "-- empty --"
    ::= { lcsStatusLanBridgeIgmpSnooping 12 }

-- {SCALAR} 310.1.31.30.13
lcsStatusLanBridgeIgmpSnoopingControlPackets OBJECT-TYPE
    SYNTAX     Counter32
    MAX-ACCESS read-only
    STATUS     current
    DESCRIPTION
        "-- empty --"
    ::= { lcsStatusLanBridgeIgmpSnooping 13 }

-- {SCALAR} 310.1.31.30.14
lcsStatusLanBridgeIgmpSnoopingBadPackets OBJECT-TYPE
    SYNTAX     Counter32
    MAX-ACCESS read-only
    STATUS     current
    DESCRIPTION
        "-- empty --"
    ::= { lcsStatusLanBridgeIgmpSnooping 14 }

-- {SCALAR} 310.1.31.30.99
lcsStatusLanBridgeIgmpSnoopingDeleteValues OBJECT-TYPE
    SYNTAX     DisplayString
    MAX-ACCESS read-write
    STATUS     current
    DESCRIPTION
        "-- empty --"
    ::= { lcsStatusLanBridgeIgmpSnooping 99 }

-- {OID} 310.1.32
lcsStatusDhcpClient OBJECT IDENTIFIER ::= { lcsStatus 32 }

-- {TABLE} 310.1.32.20
lcsStatusDhcpClientWanIpListTable OBJECT-TYPE
    SYNTAX     SEQUENCE OF LcsStatusDhcpClientWanIpListEntry
    MAX-ACCESS not-accessible
    STATUS     current
    DESCRIPTION
        "-- empty --"
    ::= { lcsStatusDhcpClient 20 }

-- {ENTRY} 310.1.32.20.1
lcsStatusDhcpClientWanIpListEntry OBJECT-TYPE
    SYNTAX     LcsStatusDhcpClientWanIpListEntry
    MAX-ACCESS not-accessible
    STATUS     current
    DESCRIPTION
        ""
    INDEX {
        lcsStatusDhcpClientWanIpListEntryIfc
    }
    ::= { lcsStatusDhcpClientWanIpListTable 1 }

-- {SEQUENCE}
LcsStatusDhcpClientWanIpListEntry ::= SEQUENCE {
    lcsStatusDhcpClientWanIpListEntryIfc INTEGER,
    lcsStatusDhcpClientWanIpListEntryIpAddress IpAddress,
    lcsStatusDhcpClientWanIpListEntryIpNetmask IpAddress,
    lcsStatusDhcpClientWanIpListEntryGateway IpAddress,
    lcsStatusDhcpClientWanIpListEntryDnsDefault IpAddress,
    lcsStatusDhcpClientWanIpListEntryDnsBackup IpAddress,
    lcsStatusDhcpClientWanIpListEntryNbnsDefault IpAddress,
    lcsStatusDhcpClientWanIpListEntryNbnsBackup IpAddress,
    lcsStatusDhcpClientWanIpListEntryDomain DisplayString,
    lcsStatusDhcpClientWanIpListEntryDhcpServer IpAddress
}

-- {COLUMN} 310.1.32.20.1.1
lcsStatusDhcpClientWanIpListEntryIfc OBJECT-TYPE
    SYNTAX     INTEGER
      {
        eDslCh1 (1),
        eModem (2)
      }
    MAX-ACCESS read-only
    STATUS     current
    DESCRIPTION
        "-- empty --"
    ::= { lcsStatusDhcpClientWanIpListEntry 1 }

-- {COLUMN} 310.1.32.20.1.2
lcsStatusDhcpClientWanIpListEntryIpAddress OBJECT-TYPE
    SYNTAX     IpAddress
    MAX-ACCESS read-only
    STATUS     current
    DESCRIPTION
        "-- empty --"
    ::= { lcsStatusDhcpClientWanIpListEntry 2 }

-- {COLUMN} 310.1.32.20.1.3
lcsStatusDhcpClientWanIpListEntryIpNetmask OBJECT-TYPE
    SYNTAX     IpAddress
    MAX-ACCESS read-only
    STATUS     current
    DESCRIPTION
        "-- empty --"
    ::= { lcsStatusDhcpClientWanIpListEntry 3 }

-- {COLUMN} 310.1.32.20.1.4
lcsStatusDhcpClientWanIpListEntryGateway OBJECT-TYPE
    SYNTAX     IpAddress
    MAX-ACCESS read-only
    STATUS     current
    DESCRIPTION
        "-- empty --"
    ::= { lcsStatusDhcpClientWanIpListEntry 4 }

-- {COLUMN} 310.1.32.20.1.5
lcsStatusDhcpClientWanIpListEntryDnsDefault OBJECT-TYPE
    SYNTAX     IpAddress
    MAX-ACCESS read-only
    STATUS     current
    DESCRIPTION
        "-- empty --"
    ::= { lcsStatusDhcpClientWanIpListEntry 5 }

-- {COLUMN} 310.1.32.20.1.6
lcsStatusDhcpClientWanIpListEntryDnsBackup OBJECT-TYPE
    SYNTAX     IpAddress
    MAX-ACCESS read-only
    STATUS     current
    DESCRIPTION
        "-- empty --"
    ::= { lcsStatusDhcpClientWanIpListEntry 6 }

-- {COLUMN} 310.1.32.20.1.7
lcsStatusDhcpClientWanIpListEntryNbnsDefault OBJECT-TYPE
    SYNTAX     IpAddress
    MAX-ACCESS read-only
    STATUS     current
    DESCRIPTION
        "-- empty --"
    ::= { lcsStatusDhcpClientWanIpListEntry 7 }

-- {COLUMN} 310.1.32.20.1.8
lcsStatusDhcpClientWanIpListEntryNbnsBackup OBJECT-TYPE
    SYNTAX     IpAddress
    MAX-ACCESS read-only
    STATUS     current
    DESCRIPTION
        "-- empty --"
    ::= { lcsStatusDhcpClientWanIpListEntry 8 }

-- {COLUMN} 310.1.32.20.1.10
lcsStatusDhcpClientWanIpListEntryDomain OBJECT-TYPE
    SYNTAX     DisplayString (SIZE(0..255))
    MAX-ACCESS read-only
    STATUS     current
    DESCRIPTION
        "-- empty --"
    ::= { lcsStatusDhcpClientWanIpListEntry 10 }

-- {COLUMN} 310.1.32.20.1.9
lcsStatusDhcpClientWanIpListEntryDhcpServer OBJECT-TYPE
    SYNTAX     IpAddress
    MAX-ACCESS read-only
    STATUS     current
    DESCRIPTION
        "-- empty --"
    ::= { lcsStatusDhcpClientWanIpListEntry 9 }

-- {TABLE} 310.1.32.21
lcsStatusDhcpClientLanIpListTable OBJECT-TYPE
    SYNTAX     SEQUENCE OF LcsStatusDhcpClientLanIpListEntry
    MAX-ACCESS not-accessible
    STATUS     current
    DESCRIPTION
        "-- empty --"
    ::= { lcsStatusDhcpClient 21 }

-- {ENTRY} 310.1.32.21.1
lcsStatusDhcpClientLanIpListEntry OBJECT-TYPE
    SYNTAX     LcsStatusDhcpClientLanIpListEntry
    MAX-ACCESS not-accessible
    STATUS     current
    DESCRIPTION
        ""
    INDEX {
        lcsStatusDhcpClientLanIpListEntryIfc
    }
    ::= { lcsStatusDhcpClientLanIpListTable 1 }

-- {SEQUENCE}
LcsStatusDhcpClientLanIpListEntry ::= SEQUENCE {
    lcsStatusDhcpClientLanIpListEntryIfc DisplayString,
    lcsStatusDhcpClientLanIpListEntryIpAddress IpAddress,
    lcsStatusDhcpClientLanIpListEntryIpNetmask IpAddress,
    lcsStatusDhcpClientLanIpListEntryGateway IpAddress,
    lcsStatusDhcpClientLanIpListEntryDnsDefault IpAddress,
    lcsStatusDhcpClientLanIpListEntryDnsBackup IpAddress,
    lcsStatusDhcpClientLanIpListEntryNbnsDefault IpAddress,
    lcsStatusDhcpClientLanIpListEntryNbnsBackup IpAddress,
    lcsStatusDhcpClientLanIpListEntryDomain DisplayString,
    lcsStatusDhcpClientLanIpListEntryDhcpServer IpAddress
}

-- {COLUMN} 310.1.32.21.1.1
lcsStatusDhcpClientLanIpListEntryIfc OBJECT-TYPE
    SYNTAX     DisplayString (SIZE(0..16))
    MAX-ACCESS read-only
    STATUS     current
    DESCRIPTION
        "-- empty --"
    ::= { lcsStatusDhcpClientLanIpListEntry 1 }

-- {COLUMN} 310.1.32.21.1.2
lcsStatusDhcpClientLanIpListEntryIpAddress OBJECT-TYPE
    SYNTAX     IpAddress
    MAX-ACCESS read-only
    STATUS     current
    DESCRIPTION
        "-- empty --"
    ::= { lcsStatusDhcpClientLanIpListEntry 2 }

-- {COLUMN} 310.1.32.21.1.3
lcsStatusDhcpClientLanIpListEntryIpNetmask OBJECT-TYPE
    SYNTAX     IpAddress
    MAX-ACCESS read-only
    STATUS     current
    DESCRIPTION
        "-- empty --"
    ::= { lcsStatusDhcpClientLanIpListEntry 3 }

-- {COLUMN} 310.1.32.21.1.4
lcsStatusDhcpClientLanIpListEntryGateway OBJECT-TYPE
    SYNTAX     IpAddress
    MAX-ACCESS read-only
    STATUS     current
    DESCRIPTION
        "-- empty --"
    ::= { lcsStatusDhcpClientLanIpListEntry 4 }

-- {COLUMN} 310.1.32.21.1.5
lcsStatusDhcpClientLanIpListEntryDnsDefault OBJECT-TYPE
    SYNTAX     IpAddress
    MAX-ACCESS read-only
    STATUS     current
    DESCRIPTION
        "-- empty --"
    ::= { lcsStatusDhcpClientLanIpListEntry 5 }

-- {COLUMN} 310.1.32.21.1.6
lcsStatusDhcpClientLanIpListEntryDnsBackup OBJECT-TYPE
    SYNTAX     IpAddress
    MAX-ACCESS read-only
    STATUS     current
    DESCRIPTION
        "-- empty --"
    ::= { lcsStatusDhcpClientLanIpListEntry 6 }

-- {COLUMN} 310.1.32.21.1.7
lcsStatusDhcpClientLanIpListEntryNbnsDefault OBJECT-TYPE
    SYNTAX     IpAddress
    MAX-ACCESS read-only
    STATUS     current
    DESCRIPTION
        "-- empty --"
    ::= { lcsStatusDhcpClientLanIpListEntry 7 }

-- {COLUMN} 310.1.32.21.1.8
lcsStatusDhcpClientLanIpListEntryNbnsBackup OBJECT-TYPE
    SYNTAX     IpAddress
    MAX-ACCESS read-only
    STATUS     current
    DESCRIPTION
        "-- empty --"
    ::= { lcsStatusDhcpClientLanIpListEntry 8 }

-- {COLUMN} 310.1.32.21.1.10
lcsStatusDhcpClientLanIpListEntryDomain OBJECT-TYPE
    SYNTAX     DisplayString (SIZE(0..255))
    MAX-ACCESS read-only
    STATUS     current
    DESCRIPTION
        "-- empty --"
    ::= { lcsStatusDhcpClientLanIpListEntry 10 }

-- {COLUMN} 310.1.32.21.1.9
lcsStatusDhcpClientLanIpListEntryDhcpServer OBJECT-TYPE
    SYNTAX     IpAddress
    MAX-ACCESS read-only
    STATUS     current
    DESCRIPTION
        "-- empty --"
    ::= { lcsStatusDhcpClientLanIpListEntry 9 }

-- {OID} 310.1.35
lcsStatusSnmp OBJECT IDENTIFIER ::= { lcsStatus 35 }

-- {TABLE} 310.1.35.1
lcsStatusSnmpEventTable OBJECT-TYPE
    SYNTAX     SEQUENCE OF LcsStatusSnmpEventEntry
    MAX-ACCESS not-accessible
    STATUS     current
    DESCRIPTION
        "-- empty --"
    ::= { lcsStatusSnmp 1 }

-- {ENTRY} 310.1.35.1.1
lcsStatusSnmpEventEntry OBJECT-TYPE
    SYNTAX     LcsStatusSnmpEventEntry
    MAX-ACCESS not-accessible
    STATUS     current
    DESCRIPTION
        ""
    INDEX {
        lcsStatusSnmpEventEntryTrapName,
        lcsStatusSnmpEventEntryVendorName
    }
    ::= { lcsStatusSnmpEventTable 1 }

-- {SEQUENCE}
LcsStatusSnmpEventEntry ::= SEQUENCE {
    lcsStatusSnmpEventEntryTrapName INTEGER,
    lcsStatusSnmpEventEntryVendorName INTEGER,
    lcsStatusSnmpEventEntryCount INTEGER
}

-- {COLUMN} 310.1.35.1.1.1
lcsStatusSnmpEventEntryTrapName OBJECT-TYPE
    SYNTAX     INTEGER
      {
        eColdstart (255),
        eWarmstart (1),
        eLinkdown (2),
        eLinkup (3),
        eAuthfail (4),
        eEpgnloss (5),
        eEnterprise (6)
      }
    MAX-ACCESS read-only
    STATUS     current
    DESCRIPTION
        "-- empty --"
    ::= { lcsStatusSnmpEventEntry 1 }

-- {COLUMN} 310.1.35.1.1.2
lcsStatusSnmpEventEntryVendorName OBJECT-TYPE
    SYNTAX     INTEGER
      {
        eFwUplStart (4), -- Firmware upload was started
        eUplsucc (5), -- Firmware or configuration upload successful
        eUplfailto (6), -- The upload the firmware or configuration failed: maximum time was exceeded
        eUplfailincl (7), -- The upload the firmware or configuration failed: incomplete configuration
        eUplfailbaddev (8), -- The upload the firmware or configuration failed: wrong device
        eLogin (9), -- Login to configuration successful
        eLogout (10), -- Logout from configuration was successful
        eCnfuplstart (11), -- Configuration upload was started
        eCnfdnlstart (12), -- Configuration download was started
        eScrptuplstart (79),
        eScrptdnlstart (80),
        eCnfdnlsucc (13), -- Configuration download successful
        eErrlogin (29), -- Error during login to configuration
        eUplinvversion (7000),
        eUplfileexists (7001),
        eNone (0),
        ePptpconn (28), -- Status of PPTP connection
        ePppoesconn (39),
        eIpfwflt (26), -- Information about a firewall event
        eVrrp (41),
        eTempmonovertemp (4000), -- Device temperature exceeds the upper tempreature limit
        eTempmonnoovertemp (4001), -- Device temperature falls below the upper temperature limit and is in the normal operating range again
        eTempmonundertemp (4002), -- Device temperature under-runs the lower temperature limit
        eTempmonnoundertemp (4003), -- Device temperature rises above the lower temperature limit and is in the normal operating range again
        eLanOvertempThrottle (5002), -- Throttling of LAN Speed due to temperature exceedance active
        eLanOvertempThrottleEnd (5003), -- Throttling of LAN Speed due to temperature exceedance stopped
        eLanOvertempThrottleRecommend (5004), -- Throttling of LAN Speed due to temperature exceedance recommended
        eAssrej (22),
        eKeyhandshakeTimeout (33),
        eWlanovertemp (48),
        eWlanovertempend (49),
        eWlanundertemp (50),
        eWlanundertempend (51),
        eBssscan (14),
        eBssstart (15),
        eBssjoin (16),
        eCardhung (25),
        eExceirp (42),
        eWlanConfadaptRadiochannel (6100),
        eWlanConfadaptRadiomode (6101),
        eWlanConfadaptBasicRate (6102),
        eWlanConfadaptEapolRate (6103),
        eWlanConfadaptEncryption (6104),
        eWlanAlarmNetwSignal (6203),
        eWlanAlarmNetwTxtotretries (6204),
        eWlanAlarmNetwTxerrors (6205),
        eAuthstation (17),
        eDeauthstation (18),
        eAssstation (19),
        eReassstation (20),
        eDisassstation (21),
        eMacchkfail (52),
        eConnected (54),
        eRoamed (53),
        eIdleTimeout (46),
        eSupervision (35),
        eAdminDeassoc (47),
        eWlanAlarmP2pSignal (6200),
        eWlanAlarmP2pTxtotretries (6201),
        eWlanAlarmP2pTxerrors (6202),
        eClLostconn (55),
        eClAuthfail (56),
        eClAssocfail (57),
        eCl8021xFail (59),
        eClConnected (58),
        eWlanAlarmClientSignal (6206),
        eWlanAlarmClientTxtotretries (6207),
        eWlanAlarmClientTxerrors (6208),
        eWlanDfsAllblocked (6300),
        eSpgtreePortstatchg (1000),
        eSpgtreeRootportchg (1002),
        eSpgtreeRstpstatchg (1001),
        eLanauthuseradd (3000),
        eLanauthuserdel (3001),
        eLanauthsessionstart (3002),
        eLanauthsessionend (3003),
        eStatChan (1), -- WAN connection status
        eHttpTunnelOpen (2000), -- HTTP tunnel opened successful
        eHttpTunnelClose (2001), -- HTTP tunnel closed successful
        eLicensemgtexpire (77)
      }
    MAX-ACCESS read-only
    STATUS     current
    DESCRIPTION
        "-- empty --"
    ::= { lcsStatusSnmpEventEntry 2 }

-- {COLUMN} 310.1.35.1.1.3
lcsStatusSnmpEventEntryCount OBJECT-TYPE
    SYNTAX     INTEGER (0..2147483647)
    MAX-ACCESS read-only
    STATUS     current
    DESCRIPTION
        "-- empty --"
    ::= { lcsStatusSnmpEventEntry 3 }

-- {SCALAR} 310.1.35.2
lcsStatusSnmpRejectedRequests OBJECT-TYPE
    SYNTAX     INTEGER (0..2147483647)
    MAX-ACCESS read-only
    STATUS     current
    DESCRIPTION
        "-- empty --"
    ::= { lcsStatusSnmp 2 }

-- {SCALAR} 310.1.35.3
lcsStatusSnmpQueueBlockErrors OBJECT-TYPE
    SYNTAX     INTEGER (0..2147483647)
    MAX-ACCESS read-only
    STATUS     current
    DESCRIPTION
        "-- empty --"
    ::= { lcsStatusSnmp 3 }

-- {SCALAR} 310.1.35.4
lcsStatusSnmpDroppedPackets OBJECT-TYPE
    SYNTAX     INTEGER (0..2147483647)
    MAX-ACCESS read-only
    STATUS     current
    DESCRIPTION
        "-- empty --"
    ::= { lcsStatusSnmp 4 }

-- {OID} 310.1.43
lcsStatusMail OBJECT IDENTIFIER ::= { lcsStatus 43 }

-- {SCALAR} 310.1.43.1
lcsStatusMailBufferedMails OBJECT-TYPE
    SYNTAX     INTEGER (0..65535)
    MAX-ACCESS read-only
    STATUS     current
    DESCRIPTION
        "-- empty --"
    ::= { lcsStatusMail 1 }

-- {SCALAR} 310.1.43.2
lcsStatusMailSentMails OBJECT-TYPE
    SYNTAX     Counter32
    MAX-ACCESS read-only
    STATUS     current
    DESCRIPTION
        "-- empty --"
    ::= { lcsStatusMail 2 }

-- {SCALAR} 310.1.43.3
lcsStatusMailDiscardedMails OBJECT-TYPE
    SYNTAX     Counter32
    MAX-ACCESS read-only
    STATUS     current
    DESCRIPTION
        "-- empty --"
    ::= { lcsStatusMail 3 }

-- {SCALAR} 310.1.43.4
lcsStatusMailClearBuffer OBJECT-TYPE
    SYNTAX     DisplayString
    MAX-ACCESS read-write
    STATUS     current
    DESCRIPTION
        "-- empty --"
    ::= { lcsStatusMail 4 }

-- {SCALAR} 310.1.43.5
lcsStatusMailDeleteStatistics OBJECT-TYPE
    SYNTAX     DisplayString
    MAX-ACCESS read-write
    STATUS     current
    DESCRIPTION
        "-- empty --"
    ::= { lcsStatusMail 5 }

-- {OID} 310.1.44
lcsStatusPublicSpot OBJECT IDENTIFIER ::= { lcsStatus 44 }

-- {TABLE} 310.1.44.1
lcsStatusPublicSpotStationTableTable OBJECT-TYPE
    SYNTAX     SEQUENCE OF LcsStatusPublicSpotStationTableEntry
    MAX-ACCESS not-accessible
    STATUS     current
    DESCRIPTION
        "-- empty --"
    ::= { lcsStatusPublicSpot 1 }

-- {ENTRY} 310.1.44.1.1
lcsStatusPublicSpotStationTableEntry OBJECT-TYPE
    SYNTAX     LcsStatusPublicSpotStationTableEntry
    MAX-ACCESS not-accessible
    STATUS     current
    DESCRIPTION
        ""
    INDEX {
        lcsStatusPublicSpotStationTableEntryMacAddress
    }
    ::= { lcsStatusPublicSpotStationTableTable 1 }

-- {SEQUENCE}
LcsStatusPublicSpotStationTableEntry ::= SEQUENCE {
    lcsStatusPublicSpotStationTableEntryMacAddress DisplayString,
    lcsStatusPublicSpotStationTableEntryPort DisplayString,
    lcsStatusPublicSpotStationTableEntryIpAddress DisplayString,
    lcsStatusPublicSpotStationTableEntryName DisplayString,
    lcsStatusPublicSpotStationTableEntryProvider DisplayString,
    lcsStatusPublicSpotStationTableEntryTxBytes INTEGER,
    lcsStatusPublicSpotStationTableEntryRxBytes INTEGER,
    lcsStatusPublicSpotStationTableEntryTxPackets INTEGER,
    lcsStatusPublicSpotStationTableEntryRxPackets INTEGER,
    lcsStatusPublicSpotStationTableEntryLoginTime INTEGER,
    lcsStatusPublicSpotStationTableEntryState INTEGER,
    lcsStatusPublicSpotStationTableEntrySessionId INTEGER,
    lcsStatusPublicSpotStationTableEntrySecExpire INTEGER,
    lcsStatusPublicSpotStationTableEntryVolExpire INTEGER,
    lcsStatusPublicSpotStationTableEntryAccCycle INTEGER,
    lcsStatusPublicSpotStationTableEntryIdleTimeout INTEGER,
    lcsStatusPublicSpotStationTableEntryTxLimit INTEGER,
    lcsStatusPublicSpotStationTableEntryRxLimit INTEGER,
    lcsStatusPublicSpotStationTableEntryOrigHost DisplayString
}

-- {COLUMN} 310.1.44.1.1.1
lcsStatusPublicSpotStationTableEntryMacAddress OBJECT-TYPE
    SYNTAX     DisplayString (SIZE(0..12))
    MAX-ACCESS read-only
    STATUS     current
    DESCRIPTION
        "-- empty --"
    ::= { lcsStatusPublicSpotStationTableEntry 1 }

-- {COLUMN} 310.1.44.1.1.19
lcsStatusPublicSpotStationTableEntryPort OBJECT-TYPE
    SYNTAX     DisplayString (SIZE(0..13))
    MAX-ACCESS read-only
    STATUS     current
    DESCRIPTION
        "-- empty --"
    ::= { lcsStatusPublicSpotStationTableEntry 19 }

-- {COLUMN} 310.1.44.1.1.2
lcsStatusPublicSpotStationTableEntryIpAddress OBJECT-TYPE
    SYNTAX     DisplayString (SIZE(0..15))
    MAX-ACCESS read-only
    STATUS     current
    DESCRIPTION
        "-- empty --"
    ::= { lcsStatusPublicSpotStationTableEntry 2 }

-- {COLUMN} 310.1.44.1.1.3
lcsStatusPublicSpotStationTableEntryName OBJECT-TYPE
    SYNTAX     DisplayString (SIZE(0..64))
    MAX-ACCESS read-only
    STATUS     current
    DESCRIPTION
        "-- empty --"
    ::= { lcsStatusPublicSpotStationTableEntry 3 }

-- {COLUMN} 310.1.44.1.1.4
lcsStatusPublicSpotStationTableEntryProvider OBJECT-TYPE
    SYNTAX     DisplayString (SIZE(0..16))
    MAX-ACCESS read-only
    STATUS     current
    DESCRIPTION
        "-- empty --"
    ::= { lcsStatusPublicSpotStationTableEntry 4 }

-- {COLUMN} 310.1.44.1.1.5
lcsStatusPublicSpotStationTableEntryTxBytes OBJECT-TYPE
    SYNTAX     INTEGER (0..2147483647)
    MAX-ACCESS read-only
    STATUS     current
    DESCRIPTION
        "-- empty --"
    ::= { lcsStatusPublicSpotStationTableEntry 5 }

-- {COLUMN} 310.1.44.1.1.6
lcsStatusPublicSpotStationTableEntryRxBytes OBJECT-TYPE
    SYNTAX     INTEGER (0..2147483647)
    MAX-ACCESS read-only
    STATUS     current
    DESCRIPTION
        "-- empty --"
    ::= { lcsStatusPublicSpotStationTableEntry 6 }

-- {COLUMN} 310.1.44.1.1.7
lcsStatusPublicSpotStationTableEntryTxPackets OBJECT-TYPE
    SYNTAX     INTEGER (0..2147483647)
    MAX-ACCESS read-only
    STATUS     current
    DESCRIPTION
        "-- empty --"
    ::= { lcsStatusPublicSpotStationTableEntry 7 }

-- {COLUMN} 310.1.44.1.1.8
lcsStatusPublicSpotStationTableEntryRxPackets OBJECT-TYPE
    SYNTAX     INTEGER (0..2147483647)
    MAX-ACCESS read-only
    STATUS     current
    DESCRIPTION
        "-- empty --"
    ::= { lcsStatusPublicSpotStationTableEntry 8 }

-- {COLUMN} 310.1.44.1.1.9
lcsStatusPublicSpotStationTableEntryLoginTime OBJECT-TYPE
    SYNTAX     INTEGER (0..2147483647)
    MAX-ACCESS read-only
    STATUS     current
    DESCRIPTION
        "-- empty --"
    ::= { lcsStatusPublicSpotStationTableEntry 9 }

-- {COLUMN} 310.1.44.1.1.10
lcsStatusPublicSpotStationTableEntryState OBJECT-TYPE
    SYNTAX     INTEGER
      {
        eUnauthenticated (0),
        eAuthenticated (1),
        eDeceased (2)
      }
    MAX-ACCESS read-only
    STATUS     current
    DESCRIPTION
        "-- empty --"
    ::= { lcsStatusPublicSpotStationTableEntry 10 }

-- {COLUMN} 310.1.44.1.1.11
lcsStatusPublicSpotStationTableEntrySessionId OBJECT-TYPE
    SYNTAX     INTEGER (0..2147483647)
    MAX-ACCESS read-only
    STATUS     current
    DESCRIPTION
        "-- empty --"
    ::= { lcsStatusPublicSpotStationTableEntry 11 }

-- {COLUMN} 310.1.44.1.1.12
lcsStatusPublicSpotStationTableEntrySecExpire OBJECT-TYPE
    SYNTAX     INTEGER (0..2147483647)
    MAX-ACCESS read-only
    STATUS     current
    DESCRIPTION
        "-- empty --"
    ::= { lcsStatusPublicSpotStationTableEntry 12 }

-- {COLUMN} 310.1.44.1.1.13
lcsStatusPublicSpotStationTableEntryVolExpire OBJECT-TYPE
    SYNTAX     INTEGER (0..2147483647)
    MAX-ACCESS read-only
    STATUS     current
    DESCRIPTION
        "-- empty --"
    ::= { lcsStatusPublicSpotStationTableEntry 13 }

-- {COLUMN} 310.1.44.1.1.14
lcsStatusPublicSpotStationTableEntryAccCycle OBJECT-TYPE
    SYNTAX     INTEGER (0..2147483647)
    MAX-ACCESS read-only
    STATUS     current
    DESCRIPTION
        "-- empty --"
    ::= { lcsStatusPublicSpotStationTableEntry 14 }

-- {COLUMN} 310.1.44.1.1.16
lcsStatusPublicSpotStationTableEntryIdleTimeout OBJECT-TYPE
    SYNTAX     INTEGER (0..2147483647)
    MAX-ACCESS read-only
    STATUS     current
    DESCRIPTION
        "-- empty --"
    ::= { lcsStatusPublicSpotStationTableEntry 16 }

-- {COLUMN} 310.1.44.1.1.17
lcsStatusPublicSpotStationTableEntryTxLimit OBJECT-TYPE
    SYNTAX     INTEGER (0..2147483647)
    MAX-ACCESS read-only
    STATUS     current
    DESCRIPTION
        "-- empty --"
    ::= { lcsStatusPublicSpotStationTableEntry 17 }

-- {COLUMN} 310.1.44.1.1.18
lcsStatusPublicSpotStationTableEntryRxLimit OBJECT-TYPE
    SYNTAX     INTEGER (0..2147483647)
    MAX-ACCESS read-only
    STATUS     current
    DESCRIPTION
        "-- empty --"
    ::= { lcsStatusPublicSpotStationTableEntry 18 }

-- {COLUMN} 310.1.44.1.1.20
lcsStatusPublicSpotStationTableEntryOrigHost OBJECT-TYPE
    SYNTAX     DisplayString (SIZE(0..255))
    MAX-ACCESS read-only
    STATUS     current
    DESCRIPTION
        "-- empty --"
    ::= { lcsStatusPublicSpotStationTableEntry 20 }

-- {SCALAR} 310.1.44.2
lcsStatusPublicSpotDeleteStation OBJECT-TYPE
    SYNTAX     DisplayString
    MAX-ACCESS read-write
    STATUS     current
    DESCRIPTION
        "-- empty --"
    ::= { lcsStatusPublicSpot 2 }

-- {SCALAR} 310.1.44.5
lcsStatusPublicSpotDisconnectUser OBJECT-TYPE
    SYNTAX     DisplayString
    MAX-ACCESS read-write
    STATUS     current
    DESCRIPTION
        "-- empty --"
    ::= { lcsStatusPublicSpot 5 }

-- {SCALAR} 310.1.44.3
lcsStatusPublicSpotCleanupTable OBJECT-TYPE
    SYNTAX     DisplayString
    MAX-ACCESS read-write
    STATUS     current
    DESCRIPTION
        "-- empty --"
    ::= { lcsStatusPublicSpot 3 }

-- {SCALAR} 310.1.44.4
lcsStatusPublicSpotDeleteValues OBJECT-TYPE
    SYNTAX     DisplayString
    MAX-ACCESS read-write
    STATUS     current
    DESCRIPTION
        "-- empty --"
    ::= { lcsStatusPublicSpot 4 }

-- {TABLE} 310.1.44.7
lcsStatusPublicSpotRadiusMacCheckCacheTable OBJECT-TYPE
    SYNTAX     SEQUENCE OF LcsStatusPublicSpotRadiusMacCheckCacheEntry
    MAX-ACCESS not-accessible
    STATUS     current
    DESCRIPTION
        "-- empty --"
    ::= { lcsStatusPublicSpot 7 }

-- {ENTRY} 310.1.44.7.1
lcsStatusPublicSpotRadiusMacCheckCacheEntry OBJECT-TYPE
    SYNTAX     LcsStatusPublicSpotRadiusMacCheckCacheEntry
    MAX-ACCESS not-accessible
    STATUS     current
    DESCRIPTION
        ""
    INDEX {
        lcsStatusPublicSpotRadiusMacCheckCacheEntryMacAddress
    }
    ::= { lcsStatusPublicSpotRadiusMacCheckCacheTable 1 }

-- {SEQUENCE}
LcsStatusPublicSpotRadiusMacCheckCacheEntry ::= SEQUENCE {
    lcsStatusPublicSpotRadiusMacCheckCacheEntryMacAddress MacAddress,
    lcsStatusPublicSpotRadiusMacCheckCacheEntryState INTEGER,
    lcsStatusPublicSpotRadiusMacCheckCacheEntryAge INTEGER,
    lcsStatusPublicSpotRadiusMacCheckCacheEntryResponseAge INTEGER
}

-- {COLUMN} 310.1.44.7.1.1
lcsStatusPublicSpotRadiusMacCheckCacheEntryMacAddress OBJECT-TYPE
    SYNTAX     MacAddress
    MAX-ACCESS read-only
    STATUS     current
    DESCRIPTION
        "-- empty --"
    ::= { lcsStatusPublicSpotRadiusMacCheckCacheEntry 1 }

-- {COLUMN} 310.1.44.7.1.2
lcsStatusPublicSpotRadiusMacCheckCacheEntryState OBJECT-TYPE
    SYNTAX     INTEGER
      {
        ePending (1),
        eReject (2),
        eAccept (3)
      }
    MAX-ACCESS read-only
    STATUS     current
    DESCRIPTION
        "-- empty --"
    ::= { lcsStatusPublicSpotRadiusMacCheckCacheEntry 2 }

-- {COLUMN} 310.1.44.7.1.3
lcsStatusPublicSpotRadiusMacCheckCacheEntryAge OBJECT-TYPE
    SYNTAX     INTEGER (0..2147483647)
    MAX-ACCESS read-only
    STATUS     current
    DESCRIPTION
        "-- empty --"
    ::= { lcsStatusPublicSpotRadiusMacCheckCacheEntry 3 }

-- {COLUMN} 310.1.44.7.1.4
lcsStatusPublicSpotRadiusMacCheckCacheEntryResponseAge OBJECT-TYPE
    SYNTAX     INTEGER (0..2147483647)
    MAX-ACCESS read-only
    STATUS     current
    DESCRIPTION
        "-- empty --"
    ::= { lcsStatusPublicSpotRadiusMacCheckCacheEntry 4 }

-- {TABLE} 310.1.44.31
lcsStatusPublicSpotFreeNetsTable OBJECT-TYPE
    SYNTAX     SEQUENCE OF LcsStatusPublicSpotFreeNetsEntry
    MAX-ACCESS not-accessible
    STATUS     current
    DESCRIPTION
        ""
    ::= { lcsStatusPublicSpot 31 }

-- {ENTRY} 310.1.44.31.1
lcsStatusPublicSpotFreeNetsEntry OBJECT-TYPE
    SYNTAX     LcsStatusPublicSpotFreeNetsEntry
    MAX-ACCESS not-accessible
    STATUS     current
    DESCRIPTION
        ""
    INDEX {
        lcsStatusPublicSpotFreeNetsEntryAddress
    }
    ::= { lcsStatusPublicSpotFreeNetsTable 1 }

-- {SEQUENCE}
LcsStatusPublicSpotFreeNetsEntry ::= SEQUENCE {
    lcsStatusPublicSpotFreeNetsEntryAddress IpAddress,
    lcsStatusPublicSpotFreeNetsEntryMask IpAddress
}

-- {COLUMN} 310.1.44.31.1.1
lcsStatusPublicSpotFreeNetsEntryAddress OBJECT-TYPE
    SYNTAX     IpAddress
    MAX-ACCESS read-only
    STATUS     current
    DESCRIPTION
        "-- empty --"
    ::= { lcsStatusPublicSpotFreeNetsEntry 1 }

-- {COLUMN} 310.1.44.31.1.2
lcsStatusPublicSpotFreeNetsEntryMask OBJECT-TYPE
    SYNTAX     IpAddress
    MAX-ACCESS read-only
    STATUS     current
    DESCRIPTION
        "-- empty --"
    ::= { lcsStatusPublicSpotFreeNetsEntry 2 }

-- {TABLE} 310.1.44.32
lcsStatusPublicSpotFreeHostsTable OBJECT-TYPE
    SYNTAX     SEQUENCE OF LcsStatusPublicSpotFreeHostsEntry
    MAX-ACCESS not-accessible
    STATUS     current
    DESCRIPTION
        "-- empty --"
    ::= { lcsStatusPublicSpot 32 }

-- {ENTRY} 310.1.44.32.1
lcsStatusPublicSpotFreeHostsEntry OBJECT-TYPE
    SYNTAX     LcsStatusPublicSpotFreeHostsEntry
    MAX-ACCESS not-accessible
    STATUS     current
    DESCRIPTION
        ""
    INDEX {
        lcsStatusPublicSpotFreeHostsEntryAddress,
        lcsStatusPublicSpotFreeHostsEntryHostName,
        lcsStatusPublicSpotFreeHostsEntrySource
    }
    ::= { lcsStatusPublicSpotFreeHostsTable 1 }

-- {SEQUENCE}
LcsStatusPublicSpotFreeHostsEntry ::= SEQUENCE {
    lcsStatusPublicSpotFreeHostsEntryAddress IpAddress,
    lcsStatusPublicSpotFreeHostsEntryHostName DisplayString,
    lcsStatusPublicSpotFreeHostsEntrySource INTEGER,
    lcsStatusPublicSpotFreeHostsEntryTtl INTEGER,
    lcsStatusPublicSpotFreeHostsEntryAge INTEGER
}

-- {COLUMN} 310.1.44.32.1.1
lcsStatusPublicSpotFreeHostsEntryAddress OBJECT-TYPE
    SYNTAX     IpAddress
    MAX-ACCESS read-only
    STATUS     current
    DESCRIPTION
        "-- empty --"
    ::= { lcsStatusPublicSpotFreeHostsEntry 1 }

-- {COLUMN} 310.1.44.32.1.2
lcsStatusPublicSpotFreeHostsEntryHostName OBJECT-TYPE
    SYNTAX     DisplayString (SIZE(0..64))
    MAX-ACCESS read-only
    STATUS     current
    DESCRIPTION
        "-- empty --"
    ::= { lcsStatusPublicSpotFreeHostsEntry 2 }

-- {COLUMN} 310.1.44.32.1.3
lcsStatusPublicSpotFreeHostsEntrySource OBJECT-TYPE
    SYNTAX     INTEGER
      {
        eDynamic (1),
        eStatic (2),
        eNone (0)
      }
    MAX-ACCESS read-only
    STATUS     current
    DESCRIPTION
        "-- empty --"
    ::= { lcsStatusPublicSpotFreeHostsEntry 3 }

-- {COLUMN} 310.1.44.32.1.4
lcsStatusPublicSpotFreeHostsEntryTtl OBJECT-TYPE
    SYNTAX     INTEGER (0..2147483647)
    MAX-ACCESS read-only
    STATUS     current
    DESCRIPTION
        "-- empty --"
    ::= { lcsStatusPublicSpotFreeHostsEntry 4 }

-- {COLUMN} 310.1.44.32.1.5
lcsStatusPublicSpotFreeHostsEntryAge OBJECT-TYPE
    SYNTAX     INTEGER (0..2147483647)
    MAX-ACCESS read-only
    STATUS     current
    DESCRIPTION
        "-- empty --"
    ::= { lcsStatusPublicSpotFreeHostsEntry 5 }

-- {TABLE} 310.1.44.6
lcsStatusPublicSpotLogTableTable OBJECT-TYPE
    SYNTAX     SEQUENCE OF LcsStatusPublicSpotLogTableEntry
    MAX-ACCESS not-accessible
    STATUS     current
    DESCRIPTION
        "-- empty --"
    ::= { lcsStatusPublicSpot 6 }

-- {ENTRY} 310.1.44.6.1
lcsStatusPublicSpotLogTableEntry OBJECT-TYPE
    SYNTAX     LcsStatusPublicSpotLogTableEntry
    MAX-ACCESS not-accessible
    STATUS     current
    DESCRIPTION
        ""
    INDEX {
        lcsStatusPublicSpotLogTableEntryIndex
    }
    ::= { lcsStatusPublicSpotLogTableTable 1 }

-- {SEQUENCE}
LcsStatusPublicSpotLogTableEntry ::= SEQUENCE {
    lcsStatusPublicSpotLogTableEntryIndex INTEGER,
    lcsStatusPublicSpotLogTableEntryTime DisplayString,
    lcsStatusPublicSpotLogTableEntryEvent DisplayString
}

-- {COLUMN} 310.1.44.6.1.1
lcsStatusPublicSpotLogTableEntryIndex OBJECT-TYPE
    SYNTAX     INTEGER (0..2147483647)
    MAX-ACCESS read-only
    STATUS     current
    DESCRIPTION
        "-- empty --"
    ::= { lcsStatusPublicSpotLogTableEntry 1 }

-- {COLUMN} 310.1.44.6.1.2
lcsStatusPublicSpotLogTableEntryTime OBJECT-TYPE
    SYNTAX     DisplayString (SIZE(0..21))
    MAX-ACCESS read-only
    STATUS     current
    DESCRIPTION
        "-- empty --"
    ::= { lcsStatusPublicSpotLogTableEntry 2 }

-- {COLUMN} 310.1.44.6.1.3
lcsStatusPublicSpotLogTableEntryEvent OBJECT-TYPE
    SYNTAX     DisplayString (SIZE(0..252))
    MAX-ACCESS read-only
    STATUS     current
    DESCRIPTION
        "-- empty --"
    ::= { lcsStatusPublicSpotLogTableEntry 3 }

-- {OID} 310.1.46
lcsStatusIeee8021x OBJECT IDENTIFIER ::= { lcsStatus 46 }

-- {TABLE} 310.1.46.1
lcsStatusIeee8021xStationTableTable OBJECT-TYPE
    SYNTAX     SEQUENCE OF LcsStatusIeee8021xStationTableEntry
    MAX-ACCESS not-accessible
    STATUS     current
    DESCRIPTION
        "-- empty --"
    ::= { lcsStatusIeee8021x 1 }

-- {ENTRY} 310.1.46.1.1
lcsStatusIeee8021xStationTableEntry OBJECT-TYPE
    SYNTAX     LcsStatusIeee8021xStationTableEntry
    MAX-ACCESS not-accessible
    STATUS     current
    DESCRIPTION
        ""
    INDEX {
        lcsStatusIeee8021xStationTableEntryMacAddress
    }
    ::= { lcsStatusIeee8021xStationTableTable 1 }

-- {SEQUENCE}
LcsStatusIeee8021xStationTableEntry ::= SEQUENCE {
    lcsStatusIeee8021xStationTableEntryMacAddress DisplayString,
    lcsStatusIeee8021xStationTableEntryAuthIfc DisplayString,
    lcsStatusIeee8021xStationTableEntryCommIfc DisplayString,
    lcsStatusIeee8021xStationTableEntrySessionId DisplayString,
    lcsStatusIeee8021xStationTableEntryPortMode INTEGER,
    lcsStatusIeee8021xStationTableEntryPortStatus INTEGER,
    lcsStatusIeee8021xStationTableEntryUserName DisplayString,
    lcsStatusIeee8021xStationTableEntryReplyMsg DisplayString
}

-- {COLUMN} 310.1.46.1.1.1
lcsStatusIeee8021xStationTableEntryMacAddress OBJECT-TYPE
    SYNTAX     DisplayString (SIZE(0..12))
    MAX-ACCESS read-only
    STATUS     current
    DESCRIPTION
        "-- empty --"
    ::= { lcsStatusIeee8021xStationTableEntry 1 }

-- {COLUMN} 310.1.46.1.1.2
lcsStatusIeee8021xStationTableEntryAuthIfc OBJECT-TYPE
    SYNTAX     DisplayString (SIZE(0..255))
    MAX-ACCESS read-only
    STATUS     current
    DESCRIPTION
        "-- empty --"
    ::= { lcsStatusIeee8021xStationTableEntry 2 }

-- {COLUMN} 310.1.46.1.1.8
lcsStatusIeee8021xStationTableEntryCommIfc OBJECT-TYPE
    SYNTAX     DisplayString (SIZE(0..255))
    MAX-ACCESS read-only
    STATUS     current
    DESCRIPTION
        "-- empty --"
    ::= { lcsStatusIeee8021xStationTableEntry 8 }

-- {COLUMN} 310.1.46.1.1.3
lcsStatusIeee8021xStationTableEntrySessionId OBJECT-TYPE
    SYNTAX     DisplayString (SIZE(0..8))
    MAX-ACCESS read-only
    STATUS     current
    DESCRIPTION
        "-- empty --"
    ::= { lcsStatusIeee8021xStationTableEntry 3 }

-- {COLUMN} 310.1.46.1.1.4
lcsStatusIeee8021xStationTableEntryPortMode OBJECT-TYPE
    SYNTAX     INTEGER
      {
        eForceUnauth (0),
        eForceAuth (1),
        eAuto (2)
      }
    MAX-ACCESS read-only
    STATUS     current
    DESCRIPTION
        "-- empty --"
    ::= { lcsStatusIeee8021xStationTableEntry 4 }

-- {COLUMN} 310.1.46.1.1.5
lcsStatusIeee8021xStationTableEntryPortStatus OBJECT-TYPE
    SYNTAX     INTEGER
      {
        eUnauthorized (0),
        eAuthorized (1)
      }
    MAX-ACCESS read-only
    STATUS     current
    DESCRIPTION
        "-- empty --"
    ::= { lcsStatusIeee8021xStationTableEntry 5 }

-- {COLUMN} 310.1.46.1.1.6
lcsStatusIeee8021xStationTableEntryUserName OBJECT-TYPE
    SYNTAX     DisplayString (SIZE(0..255))
    MAX-ACCESS read-only
    STATUS     current
    DESCRIPTION
        "-- empty --"
    ::= { lcsStatusIeee8021xStationTableEntry 6 }

-- {COLUMN} 310.1.46.1.1.7
lcsStatusIeee8021xStationTableEntryReplyMsg OBJECT-TYPE
    SYNTAX     DisplayString (SIZE(0..255))
    MAX-ACCESS read-only
    STATUS     current
    DESCRIPTION
        "-- empty --"
    ::= { lcsStatusIeee8021xStationTableEntry 7 }

-- {SCALAR} 310.1.46.2
lcsStatusIeee8021xForceReauth OBJECT-TYPE
    SYNTAX     DisplayString
    MAX-ACCESS read-write
    STATUS     current
    DESCRIPTION
        "-- empty --"
    ::= { lcsStatusIeee8021x 2 }

-- {OID} 310.1.47
lcsStatusHardwareInfo OBJECT IDENTIFIER ::= { lcsStatus 47 }

-- {SCALAR} 310.1.47.6
lcsStatusHardwareInfoModelNumber OBJECT-TYPE
    SYNTAX     DisplayString (SIZE(0..64))
    MAX-ACCESS read-only
    STATUS     current
    DESCRIPTION
        "-- empty --"
    ::= { lcsStatusHardwareInfo 6 }

-- {SCALAR} 310.1.47.39
lcsStatusHardwareInfoExtendedName OBJECT-TYPE
    SYNTAX     DisplayString (SIZE(0..127))
    MAX-ACCESS read-only
    STATUS     current
    DESCRIPTION
        "-- empty --"
    ::= { lcsStatusHardwareInfo 39 }

-- {SCALAR} 310.1.47.7
lcsStatusHardwareInfoSerialNumber OBJECT-TYPE
    SYNTAX     DisplayString (SIZE(0..18))
    MAX-ACCESS read-only
    STATUS     current
    DESCRIPTION
        "-- empty --"
    ::= { lcsStatusHardwareInfo 7 }

-- {SCALAR} 310.1.47.40
lcsStatusHardwareInfoModLevel OBJECT-TYPE
    SYNTAX     DisplayString (SIZE(0..32))
    MAX-ACCESS read-only
    STATUS     current
    DESCRIPTION
        "-- empty --"
    ::= { lcsStatusHardwareInfo 40 }

-- {SCALAR} 310.1.47.41
lcsStatusHardwareInfoProductionDate OBJECT-TYPE
    SYNTAX     DisplayString (SIZE(0..10))
    MAX-ACCESS read-only
    STATUS     current
    DESCRIPTION
        "-- empty --"
    ::= { lcsStatusHardwareInfo 41 }

-- {SCALAR} 310.1.47.44
lcsStatusHardwareInfoPldVersion OBJECT-TYPE
    SYNTAX     DisplayString (SIZE(0..7))
    MAX-ACCESS read-only
    STATUS     current
    DESCRIPTION
        "-- empty --"
    ::= { lcsStatusHardwareInfo 44 }

-- {SCALAR} 310.1.47.8
lcsStatusHardwareInfoBoardRevision OBJECT-TYPE
    SYNTAX     DisplayString (SIZE(0..1))
    MAX-ACCESS read-only
    STATUS     current
    DESCRIPTION
        "-- empty --"
    ::= { lcsStatusHardwareInfo 8 }

-- {SCALAR} 310.1.47.1
lcsStatusHardwareInfoCpuType OBJECT-TYPE
    SYNTAX     DisplayString (SIZE(0..39))
    MAX-ACCESS read-only
    STATUS     current
    DESCRIPTION
        "-- empty --"
    ::= { lcsStatusHardwareInfo 1 }

-- {SCALAR} 310.1.47.2
lcsStatusHardwareInfoCpuClockMhz OBJECT-TYPE
    SYNTAX     INTEGER (0..2147483647)
    MAX-ACCESS read-only
    STATUS     current
    DESCRIPTION
        "-- empty --"
    ::= { lcsStatusHardwareInfo 2 }

-- {SCALAR} 310.1.47.3
lcsStatusHardwareInfoCpuLoadPercent OBJECT-TYPE
    SYNTAX     INTEGER (0..255)
    MAX-ACCESS read-only
    STATUS     current
    DESCRIPTION
        "-- empty --"
    ::= { lcsStatusHardwareInfo 3 }

-- {SCALAR} 310.1.47.12
lcsStatusHardwareInfoCpuLoad1sPercent OBJECT-TYPE
    SYNTAX     INTEGER (0..255)
    MAX-ACCESS read-only
    STATUS     current
    DESCRIPTION
        "-- empty --"
    ::= { lcsStatusHardwareInfo 12 }

-- {SCALAR} 310.1.47.13
lcsStatusHardwareInfoCpuLoad5sPercent OBJECT-TYPE
    SYNTAX     INTEGER (0..255)
    MAX-ACCESS read-only
    STATUS     current
    DESCRIPTION
        "-- empty --"
    ::= { lcsStatusHardwareInfo 13 }

-- {SCALAR} 310.1.47.14
lcsStatusHardwareInfoCpuLoad60sPercent OBJECT-TYPE
    SYNTAX     INTEGER (0..255)
    MAX-ACCESS read-only
    STATUS     current
    DESCRIPTION
        "-- empty --"
    ::= { lcsStatusHardwareInfo 14 }

-- {SCALAR} 310.1.47.15
lcsStatusHardwareInfoCpuLoad300sPercent OBJECT-TYPE
    SYNTAX     INTEGER (0..255)
    MAX-ACCESS read-only
    STATUS     current
    DESCRIPTION
        "-- empty --"
    ::= { lcsStatusHardwareInfo 15 }

-- {TABLE} 310.1.47.30
lcsStatusHardwareInfoPciDeviceListTable OBJECT-TYPE
    SYNTAX     SEQUENCE OF LcsStatusHardwareInfoPciDeviceListEntry
    MAX-ACCESS not-accessible
    STATUS     current
    DESCRIPTION
        "-- empty --"
    ::= { lcsStatusHardwareInfo 30 }

-- {ENTRY} 310.1.47.30.1
lcsStatusHardwareInfoPciDeviceListEntry OBJECT-TYPE
    SYNTAX     LcsStatusHardwareInfoPciDeviceListEntry
    MAX-ACCESS not-accessible
    STATUS     current
    DESCRIPTION
        ""
    INDEX {
        lcsStatusHardwareInfoPciDeviceListEntryHostBridge,
        lcsStatusHardwareInfoPciDeviceListEntryBus,
        lcsStatusHardwareInfoPciDeviceListEntryDevice,
        lcsStatusHardwareInfoPciDeviceListEntryFunction
    }
    ::= { lcsStatusHardwareInfoPciDeviceListTable 1 }

-- {SEQUENCE}
LcsStatusHardwareInfoPciDeviceListEntry ::= SEQUENCE {
    lcsStatusHardwareInfoPciDeviceListEntryHostBridge INTEGER,
    lcsStatusHardwareInfoPciDeviceListEntryBus INTEGER,
    lcsStatusHardwareInfoPciDeviceListEntryDevice INTEGER,
    lcsStatusHardwareInfoPciDeviceListEntryFunction INTEGER,
    lcsStatusHardwareInfoPciDeviceListEntryType INTEGER,
    lcsStatusHardwareInfoPciDeviceListEntryDeviceId DisplayString,
    lcsStatusHardwareInfoPciDeviceListEntrySubsystemId DisplayString,
    lcsStatusHardwareInfoPciDeviceListEntryClass INTEGER,
    lcsStatusHardwareInfoPciDeviceListEntryInterruptCount Counter64
}

-- {COLUMN} 310.1.47.30.1.1
lcsStatusHardwareInfoPciDeviceListEntryHostBridge OBJECT-TYPE
    SYNTAX     INTEGER (0..2147483647)
    MAX-ACCESS read-only
    STATUS     current
    DESCRIPTION
        "-- empty --"
    ::= { lcsStatusHardwareInfoPciDeviceListEntry 1 }

-- {COLUMN} 310.1.47.30.1.2
lcsStatusHardwareInfoPciDeviceListEntryBus OBJECT-TYPE
    SYNTAX     INTEGER (0..2147483647)
    MAX-ACCESS read-only
    STATUS     current
    DESCRIPTION
        "-- empty --"
    ::= { lcsStatusHardwareInfoPciDeviceListEntry 2 }

-- {COLUMN} 310.1.47.30.1.3
lcsStatusHardwareInfoPciDeviceListEntryDevice OBJECT-TYPE
    SYNTAX     INTEGER (0..2147483647)
    MAX-ACCESS read-only
    STATUS     current
    DESCRIPTION
        "-- empty --"
    ::= { lcsStatusHardwareInfoPciDeviceListEntry 3 }

-- {COLUMN} 310.1.47.30.1.4
lcsStatusHardwareInfoPciDeviceListEntryFunction OBJECT-TYPE
    SYNTAX     INTEGER (0..2147483647)
    MAX-ACCESS read-only
    STATUS     current
    DESCRIPTION
        "-- empty --"
    ::= { lcsStatusHardwareInfoPciDeviceListEntry 4 }

-- {COLUMN} 310.1.47.30.1.8
lcsStatusHardwareInfoPciDeviceListEntryType OBJECT-TYPE
    SYNTAX     INTEGER
      {
        ePci (0),
        ePcie (1)
      }
    MAX-ACCESS read-only
    STATUS     current
    DESCRIPTION
        "-- empty --"
    ::= { lcsStatusHardwareInfoPciDeviceListEntry 8 }

-- {COLUMN} 310.1.47.30.1.5
lcsStatusHardwareInfoPciDeviceListEntryDeviceId OBJECT-TYPE
    SYNTAX     DisplayString (SIZE(0..255))
    MAX-ACCESS read-only
    STATUS     current
    DESCRIPTION
        "-- empty --"
    ::= { lcsStatusHardwareInfoPciDeviceListEntry 5 }

-- {COLUMN} 310.1.47.30.1.6
lcsStatusHardwareInfoPciDeviceListEntrySubsystemId OBJECT-TYPE
    SYNTAX     DisplayString (SIZE(0..255))
    MAX-ACCESS read-only
    STATUS     current
    DESCRIPTION
        "-- empty --"
    ::= { lcsStatusHardwareInfoPciDeviceListEntry 6 }

-- {COLUMN} 310.1.47.30.1.7
lcsStatusHardwareInfoPciDeviceListEntryClass OBJECT-TYPE
    SYNTAX     INTEGER
      {
        eEthernet (131072),
        eTokenRing (131328),
        eNetwork (163840),
        eAudio (262400),
        ePciBridge (394240),
        ePciBridgeSubtractive (394241),
        eCardbusBridge (395008),
        eIsaBridge (393472),
        eCommunication (491520),
        eUart16550 (458754),
        eUart16950 (458758),
        ePowerpc (729088),
        eUsbUhci (787200),
        eUsbOhci (787216),
        eUsbEhci (787232),
        eOhci1394 (786448)
      }
    MAX-ACCESS read-only
    STATUS     current
    DESCRIPTION
        "-- empty --"
    ::= { lcsStatusHardwareInfoPciDeviceListEntry 7 }

-- {COLUMN} 310.1.47.30.1.9
lcsStatusHardwareInfoPciDeviceListEntryInterruptCount OBJECT-TYPE
    SYNTAX     Counter64
    MAX-ACCESS read-only
    STATUS     current
    DESCRIPTION
        "-- empty --"
    ::= { lcsStatusHardwareInfoPciDeviceListEntry 9 }

-- {SCALAR} 310.1.47.4
lcsStatusHardwareInfoTotalMemoryKbytes OBJECT-TYPE
    SYNTAX     INTEGER (0..2147483647)
    MAX-ACCESS read-only
    STATUS     current
    DESCRIPTION
        "-- empty --"
    ::= { lcsStatusHardwareInfo 4 }

-- {SCALAR} 310.1.47.5
lcsStatusHardwareInfoFreeMemoryKbytes OBJECT-TYPE
    SYNTAX     INTEGER (0..2147483647)
    MAX-ACCESS read-only
    STATUS     current
    DESCRIPTION
        "-- empty --"
    ::= { lcsStatusHardwareInfo 5 }

-- {SCALAR} 310.1.47.9
lcsStatusHardwareInfoSwVersion OBJECT-TYPE
    SYNTAX     DisplayString (SIZE(0..39))
    MAX-ACCESS read-only
    STATUS     current
    DESCRIPTION
        "-- empty --"
    ::= { lcsStatusHardwareInfo 9 }

-- {SCALAR} 310.1.47.20
lcsStatusHardwareInfoTemperatureDegrees OBJECT-TYPE
    SYNTAX     INTEGER (-32768..32767)
    MAX-ACCESS read-only
    STATUS     current
    DESCRIPTION
        "-- empty --"
    ::= { lcsStatusHardwareInfo 20 }

-- {TABLE} 310.1.48
lcsStatusChannelTable OBJECT-TYPE
    SYNTAX     SEQUENCE OF LcsStatusChannelEntry
    MAX-ACCESS not-accessible
    STATUS     current
    DESCRIPTION
        "-- empty --"
    ::= { lcsStatus 48 }

-- {ENTRY} 310.1.48.1
lcsStatusChannelEntry OBJECT-TYPE
    SYNTAX     LcsStatusChannelEntry
    MAX-ACCESS not-accessible
    STATUS     current
    DESCRIPTION
        ""
    INDEX {
        lcsStatusChannelEntryChan
    }
    ::= { lcsStatusChannelTable 1 }

-- {SEQUENCE}
LcsStatusChannelEntry ::= SEQUENCE {
    lcsStatusChannelEntryChan INTEGER,
    lcsStatusChannelEntryPhChan INTEGER,
    lcsStatusChannelEntryPlci INTEGER,
    lcsStatusChannelEntryBus INTEGER,
    lcsStatusChannelEntryState INTEGER,
    lcsStatusChannelEntryApp INTEGER,
    lcsStatusChannelEntryConnector INTEGER,
    lcsStatusChannelEntryCause INTEGER,
    lcsStatusChannelEntryNumber DisplayString,
    lcsStatusChannelEntrySubaddress INTEGER,
    lcsStatusChannelEntryCharge INTEGER,
    lcsStatusChannelEntryConnStart INTEGER,
    lcsStatusChannelEntryConnTime INTEGER,
    lcsStatusChannelEntryExtra DisplayString,
    lcsStatusChannelEntryIsdnDisplay DisplayString,
    lcsStatusChannelEntryPptpConns INTEGER,
    lcsStatusChannelEntryVpnConns INTEGER
}

-- {COLUMN} 310.1.48.1.1
lcsStatusChannelEntryChan OBJECT-TYPE
    SYNTAX     INTEGER
      {
        eDslErr (1),
        eDslLine (2),
        eExtErr (3),
        eExt (4)
      }
    MAX-ACCESS read-only
    STATUS     current
    DESCRIPTION
        "-- empty --"
    ::= { lcsStatusChannelEntry 1 }

-- {COLUMN} 310.1.48.1.15
lcsStatusChannelEntryPhChan OBJECT-TYPE
    SYNTAX     INTEGER (0..2147483647)
    MAX-ACCESS read-only
    STATUS     current
    DESCRIPTION
        "-- empty --"
    ::= { lcsStatusChannelEntry 15 }

-- {COLUMN} 310.1.48.1.2
lcsStatusChannelEntryPlci OBJECT-TYPE
    SYNTAX     INTEGER (0..2147483647)
    MAX-ACCESS read-only
    STATUS     current
    DESCRIPTION
        "-- empty --"
    ::= { lcsStatusChannelEntry 2 }

-- {COLUMN} 310.1.48.1.3
lcsStatusChannelEntryBus OBJECT-TYPE
    SYNTAX     INTEGER (0..2147483647)
    MAX-ACCESS read-only
    STATUS     current
    DESCRIPTION
        "-- empty --"
    ::= { lcsStatusChannelEntry 3 }

-- {COLUMN} 310.1.48.1.4
lcsStatusChannelEntryState OBJECT-TYPE
    SYNTAX     INTEGER (0..2147483647)
    MAX-ACCESS read-only
    STATUS     current
    DESCRIPTION
        "-- empty --"
    ::= { lcsStatusChannelEntry 4 }

-- {COLUMN} 310.1.48.1.5
lcsStatusChannelEntryApp OBJECT-TYPE
    SYNTAX     INTEGER
      {
        eNone (0),
        eRouter (1),
        eCapi (2),
        eAB (3),
        eTimeModule (255)
      }
    MAX-ACCESS read-only
    STATUS     current
    DESCRIPTION
        "-- empty --"
    ::= { lcsStatusChannelEntry 5 }

-- {COLUMN} 310.1.48.1.6
lcsStatusChannelEntryConnector OBJECT-TYPE
    SYNTAX     INTEGER
      {
        eUnk (0),
        eAct (1),
        ePas (2),
        ePerm (3)
      }
    MAX-ACCESS read-only
    STATUS     current
    DESCRIPTION
        ""
    ::= { lcsStatusChannelEntry 6 }

-- {COLUMN} 310.1.48.1.7
lcsStatusChannelEntryCause OBJECT-TYPE
    SYNTAX     INTEGER (0..65535)
    MAX-ACCESS read-write
    STATUS     current
    DESCRIPTION
        "-- empty --"
    ::= { lcsStatusChannelEntry 7 }

-- {COLUMN} 310.1.48.1.8
lcsStatusChannelEntryNumber OBJECT-TYPE
    SYNTAX     DisplayString (SIZE(0..40))
    MAX-ACCESS read-only
    STATUS     current
    DESCRIPTION
        "-- empty --"
    ::= { lcsStatusChannelEntry 8 }

-- {COLUMN} 310.1.48.1.9
lcsStatusChannelEntrySubaddress OBJECT-TYPE
    SYNTAX     INTEGER (0..2147483647)
    MAX-ACCESS read-only
    STATUS     current
    DESCRIPTION
        "-- empty --"
    ::= { lcsStatusChannelEntry 9 }

-- {COLUMN} 310.1.48.1.10
lcsStatusChannelEntryCharge OBJECT-TYPE
    SYNTAX     INTEGER (0..2147483647)
    MAX-ACCESS read-only
    STATUS     current
    DESCRIPTION
        "-- empty --"
    ::= { lcsStatusChannelEntry 10 }

-- {COLUMN} 310.1.48.1.13
lcsStatusChannelEntryConnStart OBJECT-TYPE
    SYNTAX     INTEGER (0..2147483647)
    MAX-ACCESS read-only
    STATUS     current
    DESCRIPTION
        "-- empty --"
    ::= { lcsStatusChannelEntry 13 }

-- {COLUMN} 310.1.48.1.12
lcsStatusChannelEntryConnTime OBJECT-TYPE
    SYNTAX     INTEGER (0..2147483647)
    MAX-ACCESS read-only
    STATUS     current
    DESCRIPTION
        "-- empty --"
    ::= { lcsStatusChannelEntry 12 }

-- {COLUMN} 310.1.48.1.11
lcsStatusChannelEntryExtra OBJECT-TYPE
    SYNTAX     DisplayString (SIZE(0..16))
    MAX-ACCESS read-only
    STATUS     current
    DESCRIPTION
        "-- empty --"
    ::= { lcsStatusChannelEntry 11 }

-- {COLUMN} 310.1.48.1.14
lcsStatusChannelEntryIsdnDisplay OBJECT-TYPE
    SYNTAX     DisplayString (SIZE(0..34))
    MAX-ACCESS read-only
    STATUS     current
    DESCRIPTION
        "-- empty --"
    ::= { lcsStatusChannelEntry 14 }

-- {COLUMN} 310.1.48.1.16
lcsStatusChannelEntryPptpConns OBJECT-TYPE
    SYNTAX     INTEGER (0..2147483647)
    MAX-ACCESS read-only
    STATUS     current
    DESCRIPTION
        "-- empty --"
    ::= { lcsStatusChannelEntry 16 }

-- {COLUMN} 310.1.48.1.17
lcsStatusChannelEntryVpnConns OBJECT-TYPE
    SYNTAX     INTEGER (0..2147483647)
    MAX-ACCESS read-only
    STATUS     current
    DESCRIPTION
        "-- empty --"
    ::= { lcsStatusChannelEntry 17 }

-- {OID} 310.1.49
lcsStatusModemMobile OBJECT IDENTIFIER ::= { lcsStatus 49 }

-- {SCALAR} 310.1.49.4
lcsStatusModemMobileOperating OBJECT-TYPE
    SYNTAX     INTEGER
      {
        eNo (0),
        eModem (1)
      }
    MAX-ACCESS read-only
    STATUS     current
    DESCRIPTION
        "-- empty --"
    ::= { lcsStatusModemMobile 4 }

-- {SCALAR} 310.1.49.1
lcsStatusModemMobileModemInfo OBJECT-TYPE
    SYNTAX     DisplayString (SIZE(0..255))
    MAX-ACCESS read-only
    STATUS     current
    DESCRIPTION
        "-- empty --"
    ::= { lcsStatusModemMobile 1 }

-- {SCALAR} 310.1.49.2
lcsStatusModemMobileConnectInfo OBJECT-TYPE
    SYNTAX     DisplayString (SIZE(0..63))
    MAX-ACCESS read-only
    STATUS     current
    DESCRIPTION
        "-- empty --"
    ::= { lcsStatusModemMobile 2 }

-- {SCALAR} 310.1.49.3
lcsStatusModemMobileState OBJECT-TYPE
    SYNTAX     INTEGER
      {
        eWaitForDevice (15),
        eDeactivated (0),
        eDeviceDetection (1),
        eReset (2),
        eInitializing (3),
        eModemId (4),
        eReady (5),
        eConnecting (6),
        ePassConnecting (7),
        eDataMode (8)
      }
    MAX-ACCESS read-only
    STATUS     current
    DESCRIPTION
        "-- empty --"
    ::= { lcsStatusModemMobile 3 }

-- {SCALAR} 310.1.49.5
lcsStatusModemMobileDataRate OBJECT-TYPE
    SYNTAX     INTEGER (0..2147483647)
    MAX-ACCESS read-only
    STATUS     current
    DESCRIPTION
        "-- empty --"
    ::= { lcsStatusModemMobile 5 }

-- {SCALAR} 310.1.49.14
lcsStatusModemMobileDroppedTxPackets OBJECT-TYPE
    SYNTAX     INTEGER (0..2147483647)
    MAX-ACCESS read-only
    STATUS     current
    DESCRIPTION
        "-- empty --"
    ::= { lcsStatusModemMobile 14 }

-- {SCALAR} 310.1.49.22
lcsStatusModemMobileRxTimeouts OBJECT-TYPE
    SYNTAX     INTEGER (0..2147483647)
    MAX-ACCESS read-only
    STATUS     current
    DESCRIPTION
        "-- empty --"
    ::= { lcsStatusModemMobile 22 }

-- {OID} 310.1.50
lcsStatusFileSystem OBJECT IDENTIFIER ::= { lcsStatus 50 }

-- {TABLE} 310.1.50.1
lcsStatusFileSystemContentsTable OBJECT-TYPE
    SYNTAX     SEQUENCE OF LcsStatusFileSystemContentsEntry
    MAX-ACCESS not-accessible
    STATUS     current
    DESCRIPTION
        "-- empty --"
    ::= { lcsStatusFileSystem 1 }

-- {ENTRY} 310.1.50.1.1
lcsStatusFileSystemContentsEntry OBJECT-TYPE
    SYNTAX     LcsStatusFileSystemContentsEntry
    MAX-ACCESS not-accessible
    STATUS     current
    DESCRIPTION
        ""
    INDEX {
        lcsStatusFileSystemContentsEntryName
    }
    ::= { lcsStatusFileSystemContentsTable 1 }

-- {SEQUENCE}
LcsStatusFileSystemContentsEntry ::= SEQUENCE {
    lcsStatusFileSystemContentsEntryName DisplayString,
    lcsStatusFileSystemContentsEntrySize INTEGER
}

-- {COLUMN} 310.1.50.1.1.1
lcsStatusFileSystemContentsEntryName OBJECT-TYPE
    SYNTAX     DisplayString (SIZE(0..255))
    MAX-ACCESS read-only
    STATUS     current
    DESCRIPTION
        "-- empty --"
    ::= { lcsStatusFileSystemContentsEntry 1 }

-- {COLUMN} 310.1.50.1.1.2
lcsStatusFileSystemContentsEntrySize OBJECT-TYPE
    SYNTAX     INTEGER (0..2147483647)
    MAX-ACCESS read-only
    STATUS     current
    DESCRIPTION
        "-- empty --"
    ::= { lcsStatusFileSystemContentsEntry 2 }

-- {TABLE} 310.1.50.2
lcsStatusFileSystemVolumesTable OBJECT-TYPE
    SYNTAX     SEQUENCE OF LcsStatusFileSystemVolumesEntry
    MAX-ACCESS not-accessible
    STATUS     current
    DESCRIPTION
        "-- empty --"
    ::= { lcsStatusFileSystem 2 }

-- {ENTRY} 310.1.50.2.1
lcsStatusFileSystemVolumesEntry OBJECT-TYPE
    SYNTAX     LcsStatusFileSystemVolumesEntry
    MAX-ACCESS not-accessible
    STATUS     current
    DESCRIPTION
        ""
    INDEX {
        lcsStatusFileSystemVolumesEntryId
    }
    ::= { lcsStatusFileSystemVolumesTable 1 }

-- {SEQUENCE}
LcsStatusFileSystemVolumesEntry ::= SEQUENCE {
    lcsStatusFileSystemVolumesEntryId DisplayString,
    lcsStatusFileSystemVolumesEntryMountpoints DisplayString,
    lcsStatusFileSystemVolumesEntryFilesystem DisplayString,
    lcsStatusFileSystemVolumesEntryUnmountable INTEGER,
    lcsStatusFileSystemVolumesEntryFree DisplayString,
    lcsStatusFileSystemVolumesEntrySize DisplayString,
    lcsStatusFileSystemVolumesEntryFb INTEGER,
    lcsStatusFileSystemVolumesEntrySb INTEGER
}

-- {COLUMN} 310.1.50.2.1.1
lcsStatusFileSystemVolumesEntryId OBJECT-TYPE
    SYNTAX     DisplayString (SIZE(0..255))
    MAX-ACCESS read-only
    STATUS     current
    DESCRIPTION
        "-- empty --"
    ::= { lcsStatusFileSystemVolumesEntry 1 }

-- {COLUMN} 310.1.50.2.1.2
lcsStatusFileSystemVolumesEntryMountpoints OBJECT-TYPE
    SYNTAX     DisplayString (SIZE(0..255))
    MAX-ACCESS read-only
    STATUS     current
    DESCRIPTION
        "-- empty --"
    ::= { lcsStatusFileSystemVolumesEntry 2 }

-- {COLUMN} 310.1.50.2.1.3
lcsStatusFileSystemVolumesEntryFilesystem OBJECT-TYPE
    SYNTAX     DisplayString (SIZE(0..255))
    MAX-ACCESS read-only
    STATUS     current
    DESCRIPTION
        "-- empty --"
    ::= { lcsStatusFileSystemVolumesEntry 3 }

-- {COLUMN} 310.1.50.2.1.4
lcsStatusFileSystemVolumesEntryUnmountable OBJECT-TYPE
    SYNTAX     INTEGER (0..255)
    MAX-ACCESS read-only
    STATUS     current
    DESCRIPTION
        "-- empty --"
    ::= { lcsStatusFileSystemVolumesEntry 4 }

-- {COLUMN} 310.1.50.2.1.5
lcsStatusFileSystemVolumesEntryFree OBJECT-TYPE
    SYNTAX     DisplayString (SIZE(0..255))
    MAX-ACCESS read-only
    STATUS     current
    DESCRIPTION
        "-- empty --"
    ::= { lcsStatusFileSystemVolumesEntry 5 }

-- {COLUMN} 310.1.50.2.1.6
lcsStatusFileSystemVolumesEntrySize OBJECT-TYPE
    SYNTAX     DisplayString (SIZE(0..255))
    MAX-ACCESS read-only
    STATUS     current
    DESCRIPTION
        "-- empty --"
    ::= { lcsStatusFileSystemVolumesEntry 6 }

-- {COLUMN} 310.1.50.2.1.7
lcsStatusFileSystemVolumesEntryFb OBJECT-TYPE
    SYNTAX     INTEGER (0..2147483647)
    MAX-ACCESS read-only
    STATUS     current
    DESCRIPTION
        "-- empty --"
    ::= { lcsStatusFileSystemVolumesEntry 7 }

-- {COLUMN} 310.1.50.2.1.8
lcsStatusFileSystemVolumesEntrySb OBJECT-TYPE
    SYNTAX     INTEGER (0..2147483647)
    MAX-ACCESS read-only
    STATUS     current
    DESCRIPTION
        "-- empty --"
    ::= { lcsStatusFileSystemVolumesEntry 8 }

-- {SCALAR} 310.1.50.3
lcsStatusFileSystemUnmount OBJECT-TYPE
    SYNTAX     DisplayString
    MAX-ACCESS read-write
    STATUS     current
    DESCRIPTION
        "-- empty --"
    ::= { lcsStatusFileSystem 3 }

-- {SCALAR} 310.1.50.4
lcsStatusFileSystemSecureErase OBJECT-TYPE
    SYNTAX     DisplayString
    MAX-ACCESS read-write
    STATUS     current
    DESCRIPTION
        "-- empty --"
    ::= { lcsStatusFileSystem 4 }

-- {OID} 310.1.52
lcsStatusPppoeServer OBJECT IDENTIFIER ::= { lcsStatus 52 }

-- {SCALAR} 310.1.52.1
lcsStatusPppoeServerRxPackets OBJECT-TYPE
    SYNTAX     Counter32
    MAX-ACCESS read-only
    STATUS     current
    DESCRIPTION
        "-- empty --"
    ::= { lcsStatusPppoeServer 1 }

-- {SCALAR} 310.1.52.2
lcsStatusPppoeServerTxPackets OBJECT-TYPE
    SYNTAX     Counter32
    MAX-ACCESS read-only
    STATUS     current
    DESCRIPTION
        "-- empty --"
    ::= { lcsStatusPppoeServer 2 }

-- {SCALAR} 310.1.52.5
lcsStatusPppoeServerDroppedPackets OBJECT-TYPE
    SYNTAX     Counter32
    MAX-ACCESS read-only
    STATUS     current
    DESCRIPTION
        "-- empty --"
    ::= { lcsStatusPppoeServer 5 }

-- {SCALAR} 310.1.52.6
lcsStatusPppoeServerRxErrors OBJECT-TYPE
    SYNTAX     Counter32
    MAX-ACCESS read-only
    STATUS     current
    DESCRIPTION
        "-- empty --"
    ::= { lcsStatusPppoeServer 6 }

-- {SCALAR} 310.1.52.8
lcsStatusPppoeServerSessionErrors OBJECT-TYPE
    SYNTAX     Counter32
    MAX-ACCESS read-only
    STATUS     current
    DESCRIPTION
        "-- empty --"
    ::= { lcsStatusPppoeServer 8 }

-- {TABLE} 310.1.52.9
lcsStatusPppoeServerConnectionsTable OBJECT-TYPE
    SYNTAX     SEQUENCE OF LcsStatusPppoeServerConnectionsEntry
    MAX-ACCESS not-accessible
    STATUS     current
    DESCRIPTION
        "-- empty --"
    ::= { lcsStatusPppoeServer 9 }

-- {ENTRY} 310.1.52.9.1
lcsStatusPppoeServerConnectionsEntry OBJECT-TYPE
    SYNTAX     LcsStatusPppoeServerConnectionsEntry
    MAX-ACCESS not-accessible
    STATUS     current
    DESCRIPTION
        ""
    INDEX {
        lcsStatusPppoeServerConnectionsEntryChannel,
        lcsStatusPppoeServerConnectionsEntryMacAddress
    }
    ::= { lcsStatusPppoeServerConnectionsTable 1 }

-- {SEQUENCE}
LcsStatusPppoeServerConnectionsEntry ::= SEQUENCE {
    lcsStatusPppoeServerConnectionsEntryChannel DisplayString,
    lcsStatusPppoeServerConnectionsEntryMacAddress DisplayString,
    lcsStatusPppoeServerConnectionsEntryState INTEGER,
    lcsStatusPppoeServerConnectionsEntryLastError INTEGER,
    lcsStatusPppoeServerConnectionsEntryShTime INTEGER,
    lcsStatusPppoeServerConnectionsEntryPeerAddress IpAddress,
    lcsStatusPppoeServerConnectionsEntryConnTime Gauge32
}

-- {COLUMN} 310.1.52.9.1.1
lcsStatusPppoeServerConnectionsEntryChannel OBJECT-TYPE
    SYNTAX     DisplayString (SIZE(0..16))
    MAX-ACCESS read-only
    STATUS     current
    DESCRIPTION
        "-- empty --"
    ::= { lcsStatusPppoeServerConnectionsEntry 1 }

-- {COLUMN} 310.1.52.9.1.2
lcsStatusPppoeServerConnectionsEntryMacAddress OBJECT-TYPE
    SYNTAX     DisplayString (SIZE(0..12))
    MAX-ACCESS read-only
    STATUS     current
    DESCRIPTION
        "-- empty --"
    ::= { lcsStatusPppoeServerConnectionsEntry 2 }

-- {COLUMN} 310.1.52.9.1.3
lcsStatusPppoeServerConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusPppoeServerConnectionsEntry 3 }

-- {COLUMN} 310.1.52.9.1.4
lcsStatusPppoeServerConnectionsEntryLastError OBJECT-TYPE
    SYNTAX     INTEGER
      {
        eNone (0),
        eRemoteDisconnected (17153),
        eManualDisconnect (17154),
        eShortholdExpired (17155),
        ePhysicalDisconnected (17156),
        eInvalidPhysicalChannel (17157),
        eDynamicVpnReconnect (17158),
        eConfigurationChanged (17159),
        eRemovedFromConfig (17160),
        eRemoteDoubled (267),
        eIcmpConnError (275),
        eDhcpTimeout (277),
        ePptpNoResponse (278),
        eVpnNoResponse (279),
        eArpNoResponse (280),
        ePptpNoChannel (513),
        ePptpBadFormat (514),
        ePptpBadValue (515),
        ePptpNoRessource (516),
        ePptpBadCallId (517),
        ePptpGenError (518),
        eLcpRejected (32768),
        eAuthError (32769),
        eAuthRejected (32770),
        eLcpConnError (32771),
        ePapRejected (32784),
        ePapRxTimeout (32785),
        ePapTxTimeout (32786),
        eWrongPapReq (32787),
        ePapNakReceived (32788),
        eUnknPapPeer (32789),
        eChapRejected (32800),
        eChapRxTimeout (32801),
        eChapTxTimeout (32802),
        eWrongChapResp (32803),
        eChapFailRecvd (32804),
        eUnknChapPeer (32805),
        eIpxcpRejected (32816),
        eWrongIpxcpNet (32817),
        eIpxcpNetReject (32818),
        eIpxcpRouteUnkn (32819),
        eIpcpRejected (32832),
        eCcpRejected (32848),
        eNoNcpAvailable (33008)
      }
    MAX-ACCESS read-write
    STATUS     current
    DESCRIPTION
        "-- empty --"
    ::= { lcsStatusPppoeServerConnectionsEntry 4 }

-- {COLUMN} 310.1.52.9.1.5
lcsStatusPppoeServerConnectionsEntryShTime OBJECT-TYPE
    SYNTAX     INTEGER (0..65535)
    MAX-ACCESS read-only
    STATUS     current
    DESCRIPTION
        "-- empty --"
    ::= { lcsStatusPppoeServerConnectionsEntry 5 }

-- {COLUMN} 310.1.52.9.1.6
lcsStatusPppoeServerConnectionsEntryPeerAddress OBJECT-TYPE
    SYNTAX     IpAddress
    MAX-ACCESS read-only
    STATUS     current
    DESCRIPTION
        "-- empty --"
    ::= { lcsStatusPppoeServerConnectionsEntry 6 }

-- {COLUMN} 310.1.52.9.1.7
lcsStatusPppoeServerConnectionsEntryConnTime OBJECT-TYPE
    SYNTAX     Gauge32
    MAX-ACCESS read-only
    STATUS     current
    DESCRIPTION
        "-- empty --"
    ::= { lcsStatusPppoeServerConnectionsEntry 7 }

-- {SCALAR} 310.1.52.10
lcsStatusPppoeServerNumConnections OBJECT-TYPE
    SYNTAX     INTEGER (0..2147483647)
    MAX-ACCESS read-only
    STATUS     current
    DESCRIPTION
        "-- empty --"
    ::= { lcsStatusPppoeServer 10 }

-- {SCALAR} 310.1.52.11
lcsStatusPppoeServerDeleteValues OBJECT-TYPE
    SYNTAX     DisplayString
    MAX-ACCESS read-write
    STATUS     current
    DESCRIPTION
        "-- empty --"
    ::= { lcsStatusPppoeServer 11 }

-- {OID} 310.1.56
lcsStatusAccounting OBJECT IDENTIFIER ::= { lcsStatus 56 }

-- {TABLE} 310.1.56.1
lcsStatusAccountingCurrentUserTable OBJECT-TYPE
    SYNTAX     SEQUENCE OF LcsStatusAccountingCurrentUserEntry
    MAX-ACCESS not-accessible
    STATUS     current
    DESCRIPTION
        "-- empty --"
    ::= { lcsStatusAccounting 1 }

-- {ENTRY} 310.1.56.1.1
lcsStatusAccountingCurrentUserEntry OBJECT-TYPE
    SYNTAX     LcsStatusAccountingCurrentUserEntry
    MAX-ACCESS not-accessible
    STATUS     current
    DESCRIPTION
        ""
    INDEX {
        lcsStatusAccountingCurrentUserEntryUsername,
        lcsStatusAccountingCurrentUserEntryMacAddress,
        lcsStatusAccountingCurrentUserEntryPeer,
        lcsStatusAccountingCurrentUserEntryConnType
    }
    ::= { lcsStatusAccountingCurrentUserTable 1 }

-- {SEQUENCE}
LcsStatusAccountingCurrentUserEntry ::= SEQUENCE {
    lcsStatusAccountingCurrentUserEntryUsername DisplayString,
    lcsStatusAccountingCurrentUserEntryMacAddress DisplayString,
    lcsStatusAccountingCurrentUserEntryPeer DisplayString,
    lcsStatusAccountingCurrentUserEntryConnType INTEGER,
    lcsStatusAccountingCurrentUserEntryRxKbytes INTEGER,
    lcsStatusAccountingCurrentUserEntryTxKbytes INTEGER,
    lcsStatusAccountingCurrentUserEntryTotalTime Gauge32,
    lcsStatusAccountingCurrentUserEntryConnections INTEGER
}

-- {COLUMN} 310.1.56.1.1.1
lcsStatusAccountingCurrentUserEntryUsername OBJECT-TYPE
    SYNTAX     DisplayString (SIZE(0..28))
    MAX-ACCESS read-only
    STATUS     current
    DESCRIPTION
        "-- empty --"
    ::= { lcsStatusAccountingCurrentUserEntry 1 }

-- {COLUMN} 310.1.56.1.1.2
lcsStatusAccountingCurrentUserEntryMacAddress OBJECT-TYPE
    SYNTAX     DisplayString (SIZE(0..255))
    MAX-ACCESS read-only
    STATUS     current
    DESCRIPTION
        "-- empty --"
    ::= { lcsStatusAccountingCurrentUserEntry 2 }

-- {COLUMN} 310.1.56.1.1.3
lcsStatusAccountingCurrentUserEntryPeer OBJECT-TYPE
    SYNTAX     DisplayString (SIZE(0..16))
    MAX-ACCESS read-only
    STATUS     current
    DESCRIPTION
        "-- empty --"
    ::= { lcsStatusAccountingCurrentUserEntry 3 }

-- {COLUMN} 310.1.56.1.1.4
lcsStatusAccountingCurrentUserEntryConnType OBJECT-TYPE
    SYNTAX     INTEGER
      {
        eUnknown (0),
        eDialUp (1),
        eLeasedLine (2),
        eDslLine (4),
        eVpnConn (7),
        ePptpConn (8)
      }
    MAX-ACCESS read-only
    STATUS     current
    DESCRIPTION
        "-- empty --"
    ::= { lcsStatusAccountingCurrentUserEntry 4 }

-- {COLUMN} 310.1.56.1.1.5
lcsStatusAccountingCurrentUserEntryRxKbytes OBJECT-TYPE
    SYNTAX     INTEGER (0..2147483647)
    MAX-ACCESS read-only
    STATUS     current
    DESCRIPTION
        "-- empty --"
    ::= { lcsStatusAccountingCurrentUserEntry 5 }

-- {COLUMN} 310.1.56.1.1.6
lcsStatusAccountingCurrentUserEntryTxKbytes OBJECT-TYPE
    SYNTAX     INTEGER (0..2147483647)
    MAX-ACCESS read-only
    STATUS     current
    DESCRIPTION
        "-- empty --"
    ::= { lcsStatusAccountingCurrentUserEntry 6 }

-- {COLUMN} 310.1.56.1.1.8
lcsStatusAccountingCurrentUserEntryTotalTime OBJECT-TYPE
    SYNTAX     Gauge32
    MAX-ACCESS read-only
    STATUS     current
    DESCRIPTION
        "-- empty --"
    ::= { lcsStatusAccountingCurrentUserEntry 8 }

-- {COLUMN} 310.1.56.1.1.9
lcsStatusAccountingCurrentUserEntryConnections OBJECT-TYPE
    SYNTAX     INTEGER (0..2147483647)
    MAX-ACCESS read-only
    STATUS     current
    DESCRIPTION
        "-- empty --"
    ::= { lcsStatusAccountingCurrentUserEntry 9 }

-- {TABLE} 310.1.56.2
lcsStatusAccountingAccountingListTable OBJECT-TYPE
    SYNTAX     SEQUENCE OF LcsStatusAccountingAccountingListEntry
    MAX-ACCESS not-accessible
    STATUS     current
    DESCRIPTION
        "-- empty --"
    ::= { lcsStatusAccounting 2 }

-- {ENTRY} 310.1.56.2.1
lcsStatusAccountingAccountingListEntry OBJECT-TYPE
    SYNTAX     LcsStatusAccountingAccountingListEntry
    MAX-ACCESS not-accessible
    STATUS     current
    DESCRIPTION
        ""
    INDEX {
        lcsStatusAccountingAccountingListEntryUsername,
        lcsStatusAccountingAccountingListEntryMacAddress,
        lcsStatusAccountingAccountingListEntryPeer,
        lcsStatusAccountingAccountingListEntryConnType
    }
    ::= { lcsStatusAccountingAccountingListTable 1 }

-- {SEQUENCE}
LcsStatusAccountingAccountingListEntry ::= SEQUENCE {
    lcsStatusAccountingAccountingListEntryUsername DisplayString,
    lcsStatusAccountingAccountingListEntryMacAddress DisplayString,
    lcsStatusAccountingAccountingListEntryPeer DisplayString,
    lcsStatusAccountingAccountingListEntryConnType INTEGER,
    lcsStatusAccountingAccountingListEntryRxKbytes INTEGER,
    lcsStatusAccountingAccountingListEntryTxKbytes INTEGER,
    lcsStatusAccountingAccountingListEntryTotalTime Gauge32,
    lcsStatusAccountingAccountingListEntryConnections INTEGER
}

-- {COLUMN} 310.1.56.2.1.1
lcsStatusAccountingAccountingListEntryUsername OBJECT-TYPE
    SYNTAX     DisplayString (SIZE(0..28))
    MAX-ACCESS read-only
    STATUS     current
    DESCRIPTION
        "-- empty --"
    ::= { lcsStatusAccountingAccountingListEntry 1 }

-- {COLUMN} 310.1.56.2.1.2
lcsStatusAccountingAccountingListEntryMacAddress OBJECT-TYPE
    SYNTAX     DisplayString (SIZE(0..255))
    MAX-ACCESS read-only
    STATUS     current
    DESCRIPTION
        "-- empty --"
    ::= { lcsStatusAccountingAccountingListEntry 2 }

-- {COLUMN} 310.1.56.2.1.3
lcsStatusAccountingAccountingListEntryPeer OBJECT-TYPE
    SYNTAX     DisplayString (SIZE(0..16))
    MAX-ACCESS read-only
    STATUS     current
    DESCRIPTION
        "-- empty --"
    ::= { lcsStatusAccountingAccountingListEntry 3 }

-- {COLUMN} 310.1.56.2.1.4
lcsStatusAccountingAccountingListEntryConnType OBJECT-TYPE
    SYNTAX     INTEGER
      {
        eUnknown (0),
        eDialUp (1),
        eLeasedLine (2),
        eDslLine (4),
        eVpnConn (7),
        ePptpConn (8)
      }
    MAX-ACCESS read-only
    STATUS     current
    DESCRIPTION
        "-- empty --"
    ::= { lcsStatusAccountingAccountingListEntry 4 }

-- {COLUMN} 310.1.56.2.1.5
lcsStatusAccountingAccountingListEntryRxKbytes OBJECT-TYPE
    SYNTAX     INTEGER (0..2147483647)
    MAX-ACCESS read-only
    STATUS     current
    DESCRIPTION
        "-- empty --"
    ::= { lcsStatusAccountingAccountingListEntry 5 }

-- {COLUMN} 310.1.56.2.1.6
lcsStatusAccountingAccountingListEntryTxKbytes OBJECT-TYPE
    SYNTAX     INTEGER (0..2147483647)
    MAX-ACCESS read-only
    STATUS     current
    DESCRIPTION
        "-- empty --"
    ::= { lcsStatusAccountingAccountingListEntry 6 }

-- {COLUMN} 310.1.56.2.1.8
lcsStatusAccountingAccountingListEntryTotalTime OBJECT-TYPE
    SYNTAX     Gauge32
    MAX-ACCESS read-only
    STATUS     current
    DESCRIPTION
        "-- empty --"
    ::= { lcsStatusAccountingAccountingListEntry 8 }

-- {COLUMN} 310.1.56.2.1.9
lcsStatusAccountingAccountingListEntryConnections OBJECT-TYPE
    SYNTAX     INTEGER (0..2147483647)
    MAX-ACCESS read-only
    STATUS     current
    DESCRIPTION
        "-- empty --"
    ::= { lcsStatusAccountingAccountingListEntry 9 }

-- {TABLE} 310.1.56.3
lcsStatusAccountingLastSnapshotTable OBJECT-TYPE
    SYNTAX     SEQUENCE OF LcsStatusAccountingLastSnapshotEntry
    MAX-ACCESS not-accessible
    STATUS     current
    DESCRIPTION
        "-- empty --"
    ::= { lcsStatusAccounting 3 }

-- {ENTRY} 310.1.56.3.1
lcsStatusAccountingLastSnapshotEntry OBJECT-TYPE
    SYNTAX     LcsStatusAccountingLastSnapshotEntry
    MAX-ACCESS not-accessible
    STATUS     current
    DESCRIPTION
        ""
    INDEX {
        lcsStatusAccountingLastSnapshotEntryUsername,
        lcsStatusAccountingLastSnapshotEntryMacAddress,
        lcsStatusAccountingLastSnapshotEntryPeer,
        lcsStatusAccountingLastSnapshotEntryConnType
    }
    ::= { lcsStatusAccountingLastSnapshotTable 1 }

-- {SEQUENCE}
LcsStatusAccountingLastSnapshotEntry ::= SEQUENCE {
    lcsStatusAccountingLastSnapshotEntryUsername DisplayString,
    lcsStatusAccountingLastSnapshotEntryMacAddress DisplayString,
    lcsStatusAccountingLastSnapshotEntryPeer DisplayString,
    lcsStatusAccountingLastSnapshotEntryConnType INTEGER,
    lcsStatusAccountingLastSnapshotEntryRxKbytes INTEGER,
    lcsStatusAccountingLastSnapshotEntryTxKbytes INTEGER,
    lcsStatusAccountingLastSnapshotEntryTotalTime Gauge32,
    lcsStatusAccountingLastSnapshotEntryConnections INTEGER
}

-- {COLUMN} 310.1.56.3.1.1
lcsStatusAccountingLastSnapshotEntryUsername OBJECT-TYPE
    SYNTAX     DisplayString (SIZE(0..28))
    MAX-ACCESS read-only
    STATUS     current
    DESCRIPTION
        "-- empty --"
    ::= { lcsStatusAccountingLastSnapshotEntry 1 }

-- {COLUMN} 310.1.56.3.1.2
lcsStatusAccountingLastSnapshotEntryMacAddress OBJECT-TYPE
    SYNTAX     DisplayString (SIZE(0..255))
    MAX-ACCESS read-only
    STATUS     current
    DESCRIPTION
        "-- empty --"
    ::= { lcsStatusAccountingLastSnapshotEntry 2 }

-- {COLUMN} 310.1.56.3.1.3
lcsStatusAccountingLastSnapshotEntryPeer OBJECT-TYPE
    SYNTAX     DisplayString (SIZE(0..16))
    MAX-ACCESS read-only
    STATUS     current
    DESCRIPTION
        "-- empty --"
    ::= { lcsStatusAccountingLastSnapshotEntry 3 }

-- {COLUMN} 310.1.56.3.1.4
lcsStatusAccountingLastSnapshotEntryConnType OBJECT-TYPE
    SYNTAX     INTEGER
      {
        eUnknown (0),
        eDialUp (1),
        eLeasedLine (2),
        eDslLine (4),
        eVpnConn (7),
        ePptpConn (8)
      }
    MAX-ACCESS read-only
    STATUS     current
    DESCRIPTION
        "-- empty --"
    ::= { lcsStatusAccountingLastSnapshotEntry 4 }

-- {COLUMN} 310.1.56.3.1.5
lcsStatusAccountingLastSnapshotEntryRxKbytes OBJECT-TYPE
    SYNTAX     INTEGER (0..2147483647)
    MAX-ACCESS read-only
    STATUS     current
    DESCRIPTION
        "-- empty --"
    ::= { lcsStatusAccountingLastSnapshotEntry 5 }

-- {COLUMN} 310.1.56.3.1.6
lcsStatusAccountingLastSnapshotEntryTxKbytes OBJECT-TYPE
    SYNTAX     INTEGER (0..2147483647)
    MAX-ACCESS read-only
    STATUS     current
    DESCRIPTION
        "-- empty --"
    ::= { lcsStatusAccountingLastSnapshotEntry 6 }

-- {COLUMN} 310.1.56.3.1.8
lcsStatusAccountingLastSnapshotEntryTotalTime OBJECT-TYPE
    SYNTAX     Gauge32
    MAX-ACCESS read-only
    STATUS     current
    DESCRIPTION
        "-- empty --"
    ::= { lcsStatusAccountingLastSnapshotEntry 8 }

-- {COLUMN} 310.1.56.3.1.9
lcsStatusAccountingLastSnapshotEntryConnections OBJECT-TYPE
    SYNTAX     INTEGER (0..2147483647)
    MAX-ACCESS read-only
    STATUS     current
    DESCRIPTION
        "-- empty --"
    ::= { lcsStatusAccountingLastSnapshotEntry 9 }

-- {TABLE} 310.1.56.5
lcsStatusAccountingTimeLastSnapshotTable OBJECT-TYPE
    SYNTAX     SEQUENCE OF LcsStatusAccountingTimeLastSnapshotEntry
    MAX-ACCESS not-accessible
    STATUS     current
    DESCRIPTION
        "-- empty --"
    ::= { lcsStatusAccounting 5 }

-- {ENTRY} 310.1.56.5.1
lcsStatusAccountingTimeLastSnapshotEntry OBJECT-TYPE
    SYNTAX     LcsStatusAccountingTimeLastSnapshotEntry
    MAX-ACCESS not-accessible
    STATUS     current
    DESCRIPTION
        ""
    INDEX {
        lcsStatusAccountingTimeLastSnapshotEntrySystemTime
    }
    ::= { lcsStatusAccountingTimeLastSnapshotTable 1 }

-- {SEQUENCE}
LcsStatusAccountingTimeLastSnapshotEntry ::= SEQUENCE {
    lcsStatusAccountingTimeLastSnapshotEntrySystemTime Counter32
}

-- {COLUMN} 310.1.56.5.1.1
lcsStatusAccountingTimeLastSnapshotEntrySystemTime OBJECT-TYPE
    SYNTAX     Counter32
    MAX-ACCESS read-only
    STATUS     current
    DESCRIPTION
        "-- empty --"
    ::= { lcsStatusAccountingTimeLastSnapshotEntry 1 }

-- {SCALAR} 310.1.56.4
lcsStatusAccountingDeleteValues OBJECT-TYPE
    SYNTAX     DisplayString
    MAX-ACCESS read-write
    STATUS     current
    DESCRIPTION
        "-- empty --"
    ::= { lcsStatusAccounting 4 }

-- {OID} 310.1.59
lcsStatusWtpMngmt OBJECT IDENTIFIER ::= { lcsStatus 59 }

-- {TABLE} 310.1.59.1
lcsStatusWtpMngmtApConnectionsTable OBJECT-TYPE
    SYNTAX     SEQUENCE OF LcsStatusWtpMngmtApConnectionsEntry
    MAX-ACCESS not-accessible
    STATUS     current
    DESCRIPTION
        "-- empty --"
    ::= { lcsStatusWtpMngmt 1 }

-- {ENTRY} 310.1.59.1.1
lcsStatusWtpMngmtApConnectionsEntry OBJECT-TYPE
    SYNTAX     LcsStatusWtpMngmtApConnectionsEntry
    MAX-ACCESS not-accessible
    STATUS     current
    DESCRIPTION
        ""
    INDEX {
        lcsStatusWtpMngmtApConnectionsEntryConnId
    }
    ::= { lcsStatusWtpMngmtApConnectionsTable 1 }

-- {SEQUENCE}
LcsStatusWtpMngmtApConnectionsEntry ::= SEQUENCE {
    lcsStatusWtpMngmtApConnectionsEntryConnId INTEGER,
    lcsStatusWtpMngmtApConnectionsEntryIpAddress IpAddress,
    lcsStatusWtpMngmtApConnectionsEntryPort INTEGER,
    lcsStatusWtpMngmtApConnectionsEntryPriority INTEGER,
    lcsStatusWtpMngmtApConnectionsEntryResult INTEGER,
    lcsStatusWtpMngmtApConnectionsEntryResptime INTEGER,
    lcsStatusWtpMngmtApConnectionsEntryUtilisation DisplayString,
    lcsStatusWtpMngmtApConnectionsEntryName DisplayString,
    lcsStatusWtpMngmtApConnectionsEntryState INTEGER,
    lcsStatusWtpMngmtApConnectionsEntryFirmwareVersion DisplayString,
    lcsStatusWtpMngmtApConnectionsEntryPmtu INTEGER,
    lcsStatusWtpMngmtApConnectionsEntryDscpForControlPackets INTEGER,
    lcsStatusWtpMngmtApConnectionsEntryDscpForDataPackets INTEGER
}

-- {COLUMN} 310.1.59.1.1.1
lcsStatusWtpMngmtApConnectionsEntryConnId OBJECT-TYPE
    SYNTAX     INTEGER (0..2147483647)
    MAX-ACCESS read-only
    STATUS     current
    DESCRIPTION
        "-- empty --"
    ::= { lcsStatusWtpMngmtApConnectionsEntry 1 }

-- {COLUMN} 310.1.59.1.1.2
lcsStatusWtpMngmtApConnectionsEntryIpAddress OBJECT-TYPE
    SYNTAX     IpAddress
    MAX-ACCESS read-only
    STATUS     current
    DESCRIPTION
        "-- empty --"
    ::= { lcsStatusWtpMngmtApConnectionsEntry 2 }

-- {COLUMN} 310.1.59.1.1.3
lcsStatusWtpMngmtApConnectionsEntryPort OBJECT-TYPE
    SYNTAX     INTEGER (0..65535)
    MAX-ACCESS read-only
    STATUS     current
    DESCRIPTION
        "-- empty --"
    ::= { lcsStatusWtpMngmtApConnectionsEntry 3 }

-- {COLUMN} 310.1.59.1.1.8
lcsStatusWtpMngmtApConnectionsEntryPriority OBJECT-TYPE
    SYNTAX     INTEGER
      {
        eUnspec (0),
        ePrimary (1),
        eSecondary (2)
      }
    MAX-ACCESS read-only
    STATUS     current
    DESCRIPTION
        "-- empty --"
    ::= { lcsStatusWtpMngmtApConnectionsEntry 8 }

-- {COLUMN} 310.1.59.1.1.7
lcsStatusWtpMngmtApConnectionsEntryResult OBJECT-TYPE
    SYNTAX     INTEGER
      {
        eSuccess (0),
        eFailure (1),
        eSuccessNat (2),
        eJoinFailUnspecified (3),
        eJoinFailResourceDepletion (4),
        eJoinFailUnknwnSrc (5),
        eJoinFailIncorrectData (6),
        eJoinFailSessionIdInUse (7),
        eJoinFailWtpNotSupported (8),
        eJoinFailBindingNotSupp (9),
        eResetFailUnableToReset (10),
        eResetFailFirmwWriteErr (11),
        eConfigurationErrorServProvAnyhow (12),
        eConfigurationErrorServNotProv (13),
        eImageDataErrorChecksum (14),
        eImageDataErrorLength (15),
        eImageDataErrorOther (16),
        eImageDataErrorAlrPresent (17),
        eMessageUnexpectedInvalid (18),
        eMessageUnexpectedUnrecognized (19),
        eFailMissingMandMsgElem (20),
        eFailUnrecognizedMsgElem (21),
        eUnsupportedLoaderVersion (300),
        eUnsupportedFirmwareVersion (301),
        eUnknown (302),
        eJoinFailAlreadyConnected (303)
      }
    MAX-ACCESS read-only
    STATUS     current
    DESCRIPTION
        "-- empty --"
    ::= { lcsStatusWtpMngmtApConnectionsEntry 7 }

-- {COLUMN} 310.1.59.1.1.4
lcsStatusWtpMngmtApConnectionsEntryResptime OBJECT-TYPE
    SYNTAX     INTEGER (0..2147483647)
    MAX-ACCESS read-only
    STATUS     current
    DESCRIPTION
        "-- empty --"
    ::= { lcsStatusWtpMngmtApConnectionsEntry 4 }

-- {COLUMN} 310.1.59.1.1.9
lcsStatusWtpMngmtApConnectionsEntryUtilisation OBJECT-TYPE
    SYNTAX     DisplayString (SIZE(0..6))
    MAX-ACCESS read-only
    STATUS     current
    DESCRIPTION
        "-- empty --"
    ::= { lcsStatusWtpMngmtApConnectionsEntry 9 }

-- {COLUMN} 310.1.59.1.1.5
lcsStatusWtpMngmtApConnectionsEntryName OBJECT-TYPE
    SYNTAX     DisplayString (SIZE(0..31))
    MAX-ACCESS read-only
    STATUS     current
    DESCRIPTION
        "-- empty --"
    ::= { lcsStatusWtpMngmtApConnectionsEntry 5 }

-- {COLUMN} 310.1.59.1.1.6
lcsStatusWtpMngmtApConnectionsEntryState OBJECT-TYPE
    SYNTAX     INTEGER
      {
        eUnknown (0),
        eIdle (5),
        eDiscovery (10),
        eDtlsSetup (15),
        eJoin (20),
        eConfigure (25),
        eImageData (30),
        eReset (35),
        eDtlsTeardown (40),
        eSulking (45),
        eRun (100)
      }
    MAX-ACCESS read-only
    STATUS     current
    DESCRIPTION
        "-- empty --"
    ::= { lcsStatusWtpMngmtApConnectionsEntry 6 }

-- {COLUMN} 310.1.59.1.1.10
lcsStatusWtpMngmtApConnectionsEntryFirmwareVersion OBJECT-TYPE
    SYNTAX     DisplayString (SIZE(0..31))
    MAX-ACCESS read-only
    STATUS     current
    DESCRIPTION
        "-- empty --"
    ::= { lcsStatusWtpMngmtApConnectionsEntry 10 }

-- {COLUMN} 310.1.59.1.1.11
lcsStatusWtpMngmtApConnectionsEntryPmtu OBJECT-TYPE
    SYNTAX     INTEGER (0..2147483647)
    MAX-ACCESS read-only
    STATUS     current
    DESCRIPTION
        "-- empty --"
    ::= { lcsStatusWtpMngmtApConnectionsEntry 11 }

-- {COLUMN} 310.1.59.1.1.12
lcsStatusWtpMngmtApConnectionsEntryDscpForControlPackets OBJECT-TYPE
    SYNTAX     INTEGER
      {
        eBestEffort (0),
        eAssuredForwarding11 (40),
        eAssuredForwarding12 (48),
        eAssuredForwarding13 (56),
        eAssuredForwarding21 (72),
        eAssuredForwarding22 (80),
        eAssuredForwarding23 (88),
        eAssuredForwarding31 (104),
        eAssuredForwarding32 (112),
        eAssuredForwarding33 (120),
        eAssuredForwarding41 (136),
        eAssuredForwarding42 (144),
        eAssuredForwarding43 (152),
        eExpeditedForwarding (184)
      }
    MAX-ACCESS read-only
    STATUS     current
    DESCRIPTION
        "-- empty --"
    ::= { lcsStatusWtpMngmtApConnectionsEntry 12 }

-- {COLUMN} 310.1.59.1.1.13
lcsStatusWtpMngmtApConnectionsEntryDscpForDataPackets OBJECT-TYPE
    SYNTAX     INTEGER
      {
        eBestEffort (0),
        eAssuredForwarding11 (40),
        eAssuredForwarding12 (48),
        eAssuredForwarding13 (56),
        eAssuredForwarding21 (72),
        eAssuredForwarding22 (80),
        eAssuredForwarding23 (88),
        eAssuredForwarding31 (104),
        eAssuredForwarding32 (112),
        eAssuredForwarding33 (120),
        eAssuredForwarding41 (136),
        eAssuredForwarding42 (144),
        eAssuredForwarding43 (152),
        eExpeditedForwarding (184)
      }
    MAX-ACCESS read-only
    STATUS     current
    DESCRIPTION
        "-- empty --"
    ::= { lcsStatusWtpMngmtApConnectionsEntry 13 }

-- {TABLE} 310.1.59.99
lcsStatusWtpMngmtGlobalconfigTable OBJECT-TYPE
    SYNTAX     SEQUENCE OF LcsStatusWtpMngmtGlobalconfigEntry
    MAX-ACCESS not-accessible
    STATUS     current
    DESCRIPTION
        "-- empty --"
    ::= { lcsStatusWtpMngmt 99 }

-- {ENTRY} 310.1.59.99.1
lcsStatusWtpMngmtGlobalconfigEntry OBJECT-TYPE
    SYNTAX     LcsStatusWtpMngmtGlobalconfigEntry
    MAX-ACCESS not-accessible
    STATUS     current
    DESCRIPTION
        ""
    INDEX {
        lcsStatusWtpMngmtGlobalconfigEntryVersion
    }
    ::= { lcsStatusWtpMngmtGlobalconfigTable 1 }

-- {SEQUENCE}
LcsStatusWtpMngmtGlobalconfigEntry ::= SEQUENCE {
    lcsStatusWtpMngmtGlobalconfigEntryVersion INTEGER,
    lcsStatusWtpMngmtGlobalconfigEntryIpAddress IpAddress,
    lcsStatusWtpMngmtGlobalconfigEntryNetMask IpAddress,
    lcsStatusWtpMngmtGlobalconfigEntryGateway IpAddress,
    lcsStatusWtpMngmtGlobalconfigEntryDns1 IpAddress,
    lcsStatusWtpMngmtGlobalconfigEntryDns2 IpAddress,
    lcsStatusWtpMngmtGlobalconfigEntryMgmtVlanid INTEGER,
    lcsStatusWtpMngmtGlobalconfigEntryMgmtVlantrunk INTEGER,
    lcsStatusWtpMngmtGlobalconfigEntryDnsSuffix DisplayString
}

-- {COLUMN} 310.1.59.99.1.1
lcsStatusWtpMngmtGlobalconfigEntryVersion OBJECT-TYPE
    SYNTAX     INTEGER (0..2147483647)
    MAX-ACCESS read-only
    STATUS     current
    DESCRIPTION
        "-- empty --"
    ::= { lcsStatusWtpMngmtGlobalconfigEntry 1 }

-- {COLUMN} 310.1.59.99.1.2
lcsStatusWtpMngmtGlobalconfigEntryIpAddress OBJECT-TYPE
    SYNTAX     IpAddress
    MAX-ACCESS read-only
    STATUS     current
    DESCRIPTION
        "-- empty --"
    ::= { lcsStatusWtpMngmtGlobalconfigEntry 2 }

-- {COLUMN} 310.1.59.99.1.3
lcsStatusWtpMngmtGlobalconfigEntryNetMask OBJECT-TYPE
    SYNTAX     IpAddress
    MAX-ACCESS read-only
    STATUS     current
    DESCRIPTION
        "-- empty --"
    ::= { lcsStatusWtpMngmtGlobalconfigEntry 3 }

-- {COLUMN} 310.1.59.99.1.4
lcsStatusWtpMngmtGlobalconfigEntryGateway OBJECT-TYPE
    SYNTAX     IpAddress
    MAX-ACCESS read-only
    STATUS     current
    DESCRIPTION
        "-- empty --"
    ::= { lcsStatusWtpMngmtGlobalconfigEntry 4 }

-- {COLUMN} 310.1.59.99.1.5
lcsStatusWtpMngmtGlobalconfigEntryDns1 OBJECT-TYPE
    SYNTAX     IpAddress
    MAX-ACCESS read-only
    STATUS     current
    DESCRIPTION
        "-- empty --"
    ::= { lcsStatusWtpMngmtGlobalconfigEntry 5 }

-- {COLUMN} 310.1.59.99.1.6
lcsStatusWtpMngmtGlobalconfigEntryDns2 OBJECT-TYPE
    SYNTAX     IpAddress
    MAX-ACCESS read-only
    STATUS     current
    DESCRIPTION
        "-- empty --"
    ::= { lcsStatusWtpMngmtGlobalconfigEntry 6 }

-- {COLUMN} 310.1.59.99.1.8
lcsStatusWtpMngmtGlobalconfigEntryMgmtVlanid OBJECT-TYPE
    SYNTAX     INTEGER (0..65535)
    MAX-ACCESS read-only
    STATUS     current
    DESCRIPTION
        "-- empty --"
    ::= { lcsStatusWtpMngmtGlobalconfigEntry 8 }

-- {COLUMN} 310.1.59.99.1.9
lcsStatusWtpMngmtGlobalconfigEntryMgmtVlantrunk OBJECT-TYPE
    SYNTAX     INTEGER (0..65535)
    MAX-ACCESS read-only
    STATUS     current
    DESCRIPTION
        "-- empty --"
    ::= { lcsStatusWtpMngmtGlobalconfigEntry 9 }

-- {COLUMN} 310.1.59.99.1.14
lcsStatusWtpMngmtGlobalconfigEntryDnsSuffix OBJECT-TYPE
    SYNTAX     DisplayString (SIZE(0..63))
    MAX-ACCESS read-only
    STATUS     current
    DESCRIPTION
        "-- empty --"
    ::= { lcsStatusWtpMngmtGlobalconfigEntry 14 }

-- {TABLE} 310.1.59.100
lcsStatusWtpMngmtLastWlcTable OBJECT-TYPE
    SYNTAX     SEQUENCE OF LcsStatusWtpMngmtLastWlcEntry
    MAX-ACCESS not-accessible
    STATUS     current
    DESCRIPTION
        "-- empty --"
    ::= { lcsStatusWtpMngmt 100 }

-- {ENTRY} 310.1.59.100.1
lcsStatusWtpMngmtLastWlcEntry OBJECT-TYPE
    SYNTAX     LcsStatusWtpMngmtLastWlcEntry
    MAX-ACCESS not-accessible
    STATUS     current
    DESCRIPTION
        ""
    INDEX {
        lcsStatusWtpMngmtLastWlcEntryIpAddress
    }
    ::= { lcsStatusWtpMngmtLastWlcTable 1 }

-- {SEQUENCE}
LcsStatusWtpMngmtLastWlcEntry ::= SEQUENCE {
    lcsStatusWtpMngmtLastWlcEntryIpAddress IpAddress,
    lcsStatusWtpMngmtLastWlcEntryPort INTEGER,
    lcsStatusWtpMngmtLastWlcEntryName DisplayString,
    lcsStatusWtpMngmtLastWlcEntryMgmtVlanId INTEGER,
    lcsStatusWtpMngmtLastWlcEntryRoutetag INTEGER,
    lcsStatusWtpMngmtLastWlcEntryType INTEGER
}

-- {COLUMN} 310.1.59.100.1.1
lcsStatusWtpMngmtLastWlcEntryIpAddress OBJECT-TYPE
    SYNTAX     IpAddress
    MAX-ACCESS read-only
    STATUS     current
    DESCRIPTION
        "-- empty --"
    ::= { lcsStatusWtpMngmtLastWlcEntry 1 }

-- {COLUMN} 310.1.59.100.1.2
lcsStatusWtpMngmtLastWlcEntryPort OBJECT-TYPE
    SYNTAX     INTEGER (0..65535)
    MAX-ACCESS read-only
    STATUS     current
    DESCRIPTION
        "-- empty --"
    ::= { lcsStatusWtpMngmtLastWlcEntry 2 }

-- {COLUMN} 310.1.59.100.1.3
lcsStatusWtpMngmtLastWlcEntryName OBJECT-TYPE
    SYNTAX     DisplayString (SIZE(0..31))
    MAX-ACCESS read-only
    STATUS     current
    DESCRIPTION
        "-- empty --"
    ::= { lcsStatusWtpMngmtLastWlcEntry 3 }

-- {COLUMN} 310.1.59.100.1.6
lcsStatusWtpMngmtLastWlcEntryMgmtVlanId OBJECT-TYPE
    SYNTAX     INTEGER (0..65535)
    MAX-ACCESS read-only
    STATUS     current
    DESCRIPTION
        "-- empty --"
    ::= { lcsStatusWtpMngmtLastWlcEntry 6 }

-- {COLUMN} 310.1.59.100.1.4
lcsStatusWtpMngmtLastWlcEntryRoutetag OBJECT-TYPE
    SYNTAX     INTEGER (0..65535)
    MAX-ACCESS read-only
    STATUS     current
    DESCRIPTION
        "-- empty --"
    ::= { lcsStatusWtpMngmtLastWlcEntry 4 }

-- {COLUMN} 310.1.59.100.1.5
lcsStatusWtpMngmtLastWlcEntryType OBJECT-TYPE
    SYNTAX     INTEGER (0..255)
    MAX-ACCESS read-only
    STATUS     current
    DESCRIPTION
        "-- empty --"
    ::= { lcsStatusWtpMngmtLastWlcEntry 5 }

-- {TABLE} 310.1.59.101
lcsStatusWtpMngmtRadioprofilsTable OBJECT-TYPE
    SYNTAX     SEQUENCE OF LcsStatusWtpMngmtRadioprofilsEntry
    MAX-ACCESS not-accessible
    STATUS     current
    DESCRIPTION
        ""
    ::= { lcsStatusWtpMngmt 101 }

-- {ENTRY} 310.1.59.101.1
lcsStatusWtpMngmtRadioprofilsEntry OBJECT-TYPE
    SYNTAX     LcsStatusWtpMngmtRadioprofilsEntry
    MAX-ACCESS not-accessible
    STATUS     current
    DESCRIPTION
        ""
    INDEX {
        lcsStatusWtpMngmtRadioprofilsEntryName
    }
    ::= { lcsStatusWtpMngmtRadioprofilsTable 1 }

-- {SEQUENCE}
LcsStatusWtpMngmtRadioprofilsEntry ::= SEQUENCE {
    lcsStatusWtpMngmtRadioprofilsEntryName DisplayString,
    lcsStatusWtpMngmtRadioprofilsEntryCountry INTEGER,
    lcsStatusWtpMngmtRadioprofilsEntry24ghzMode INTEGER,
    lcsStatusWtpMngmtRadioprofilsEntry5ghzMode INTEGER,
    lcsStatusWtpMngmtRadioprofilsEntrySubbands INTEGER,
    lcsStatusWtpMngmtRadioprofilsEntryQos INTEGER,
    lcsStatusWtpMngmtRadioprofilsEntryDtimPeriod INTEGER,
    lcsStatusWtpMngmtRadioprofilsEntryBackgroundScan INTEGER,
    lcsStatusWtpMngmtRadioprofilsEntryAntennaGain INTEGER,
    lcsStatusWtpMngmtRadioprofilsEntryTxPowerReduction INTEGER,
    lcsStatusWtpMngmtRadioprofilsEntryMgmtVLANIdnew INTEGER,
    lcsStatusWtpMngmtRadioprofilsEntryMgmtVLANId INTEGER,
    lcsStatusWtpMngmtRadioprofilsEntryMgmtVlanTrunk INTEGER,
    lcsStatusWtpMngmtRadioprofilsEntryIndoorOnlyOperation INTEGER,
    lcsStatusWtpMngmtRadioprofilsEntryReportSeenClients INTEGER
}

-- {COLUMN} 310.1.59.101.1.1
lcsStatusWtpMngmtRadioprofilsEntryName OBJECT-TYPE
    SYNTAX     DisplayString (SIZE(0..31))
    MAX-ACCESS read-only
    STATUS     current
    DESCRIPTION
        "-- empty --"
    ::= { lcsStatusWtpMngmtRadioprofilsEntry 1 }

-- {COLUMN} 310.1.59.101.1.4
lcsStatusWtpMngmtRadioprofilsEntryCountry OBJECT-TYPE
    SYNTAX     INTEGER
      {
        eDefault (0),
        eAlbania (8),
        eAlgeria (12),
        eArgentina (32),
        eAustralia (36),
        eAustria (40),
        eBahrain (48),
        eBangladesh (50),
        eBelarus (112),
        eBelgium (56),
        eBosniaHerzegovina (70),
        eBrazil (76),
        eBruneiDarussalam (96),
        eBulgaria (100),
        eCanada (124),
        eChile (152),
        eChina (156),
        eColombia (170),
        eCostaRica (188),
        eCroatia (191),
        eCyprus (196),
        eCzech (203),
        eDenmark (208),
        eEcuador (218),
        eEgalistan (999),
        eEgypt (818),
        eEstonia (233),
        eEurope (998),
        eFinland (246),
        eFrance (250),
        eGermany (276),
        eGhana (288),
        eGreece (300),
        eGuatemala (320),
        eHonduras (340),
        eHongKong (344),
        eHungary (348),
        eIceland (352),
        eIndia (356),
        eIndonesia (360),
        eIreland (372),
        eIsrael (376),
        eItaly (380),
        eJapan (392),
        eJordan (400),
        eSouthKorea (410),
        eKuwait (414),
        eLatvia (428),
        eLebanon (422),
        eLiechtenstein (438),
        eLithuania (440),
        eLuxembourg (442),
        eMacau (446),
        eMacedonia (807),
        eMalaysia (458),
        eMalta (470),
        eMexico (484),
        eMoldavia (498),
        eMorocco (504),
        eNetherlands (528),
        eNewZealand (554),
        eNicaragua (558),
        eNorway (578),
        eOman (512),
        ePakistan (586),
        ePanama (591),
        eParaguay (600),
        ePeru (604),
        ePhilippines (608),
        ePoland (616),
        ePortugal (620),
        ePuertoRico (630),
        eQatar (634),
        eRomania (642),
        eRussia (643),
        eSaudiArabia (682),
        eSingapore (702),
        eSlovak (703),
        eSlovenia (705),
        eSouthAfrica (710),
        eSpain (724),
        eSweden (752),
        eSwitzerland (756),
        eTaiwan (158),
        eTanzania (834),
        eThailand (764),
        eTunisia (788),
        eTurkey (792),
        eUganda (800),
        eUkraine (804),
        eUnitedArabEmirates (784),
        eUnitedKingdom (826),
        eUnitedStatesFcc (840),
        eUruguay (858),
        eVenezuela (862)
      }
    MAX-ACCESS read-only
    STATUS     current
    DESCRIPTION
        "-- empty --"
    ::= { lcsStatusWtpMngmtRadioprofilsEntry 4 }

-- {COLUMN} 310.1.59.101.1.6
lcsStatusWtpMngmtRadioprofilsEntry24ghzMode OBJECT-TYPE
    SYNTAX     INTEGER
      {
        e11bgMixed (0),
        e11bOnly (2),
        e11gOnly (1),
        e11bgnMixed (4),
        e11gnMixed (5),
        eGreenfield (6)
      }
    MAX-ACCESS read-only
    STATUS     current
    DESCRIPTION
        "-- empty --"
    ::= { lcsStatusWtpMngmtRadioprofilsEntry 6 }

-- {COLUMN} 310.1.59.101.1.7
lcsStatusWtpMngmtRadioprofilsEntry5ghzMode OBJECT-TYPE
    SYNTAX     INTEGER
      {
        eNormal (0),
        e11anMixed (4),
        eGreenfield (5)
      }
    MAX-ACCESS read-only
    STATUS     current
    DESCRIPTION
        "-- empty --"
    ::= { lcsStatusWtpMngmtRadioprofilsEntry 7 }

-- {COLUMN} 310.1.59.101.1.8
lcsStatusWtpMngmtRadioprofilsEntrySubbands OBJECT-TYPE
    SYNTAX     INTEGER
      {
        eBand1 (1),
        eBand2 (2),
        eBand3 (3),
        eBand1Plus2 (4),
        eBand1Plus3 (5),
        eBand2Plus3 (6),
        eBand1Plus2Plus3 (0)
      }
    MAX-ACCESS read-only
    STATUS     current
    DESCRIPTION
        "-- empty --"
    ::= { lcsStatusWtpMngmtRadioprofilsEntry 8 }

-- {COLUMN} 310.1.59.101.1.9
lcsStatusWtpMngmtRadioprofilsEntryQos OBJECT-TYPE
    SYNTAX     INTEGER
      {
        eNo (0),
        eYes (1)
      }
    MAX-ACCESS read-only
    STATUS     current
    DESCRIPTION
        "-- empty --"
    ::= { lcsStatusWtpMngmtRadioprofilsEntry 9 }

-- {COLUMN} 310.1.59.101.1.10
lcsStatusWtpMngmtRadioprofilsEntryDtimPeriod OBJECT-TYPE
    SYNTAX     INTEGER (0..255)
    MAX-ACCESS read-only
    STATUS     current
    DESCRIPTION
        "-- empty --"
    ::= { lcsStatusWtpMngmtRadioprofilsEntry 10 }

-- {COLUMN} 310.1.59.101.1.11
lcsStatusWtpMngmtRadioprofilsEntryBackgroundScan OBJECT-TYPE
    SYNTAX     INTEGER (0..2147483647)
    MAX-ACCESS read-only
    STATUS     current
    DESCRIPTION
        "-- empty --"
    ::= { lcsStatusWtpMngmtRadioprofilsEntry 11 }

-- {COLUMN} 310.1.59.101.1.12
lcsStatusWtpMngmtRadioprofilsEntryAntennaGain OBJECT-TYPE
    SYNTAX     INTEGER (-128..127)
    MAX-ACCESS read-only
    STATUS     current
    DESCRIPTION
        "-- empty --"
    ::= { lcsStatusWtpMngmtRadioprofilsEntry 12 }

-- {COLUMN} 310.1.59.101.1.13
lcsStatusWtpMngmtRadioprofilsEntryTxPowerReduction OBJECT-TYPE
    SYNTAX     INTEGER (0..255)
    MAX-ACCESS read-only
    STATUS     current
    DESCRIPTION
        "-- empty --"
    ::= { lcsStatusWtpMngmtRadioprofilsEntry 13 }

-- {COLUMN} 310.1.59.101.1.19
lcsStatusWtpMngmtRadioprofilsEntryMgmtVLANIdnew OBJECT-TYPE
    SYNTAX     INTEGER (0..65535)
    MAX-ACCESS read-only
    STATUS     current
    DESCRIPTION
        ""
    ::= { lcsStatusWtpMngmtRadioprofilsEntry 19 }

-- {COLUMN} 310.1.59.101.1.14
lcsStatusWtpMngmtRadioprofilsEntryMgmtVLANId OBJECT-TYPE
    SYNTAX     INTEGER (0..65535)
    MAX-ACCESS read-only
    STATUS     obsolete
    DESCRIPTION
        ""
    ::= { lcsStatusWtpMngmtRadioprofilsEntry 14 }

-- {COLUMN} 310.1.59.101.1.15
lcsStatusWtpMngmtRadioprofilsEntryMgmtVlanTrunk OBJECT-TYPE
    SYNTAX     INTEGER (0..65535)
    MAX-ACCESS read-only
    STATUS     current
    DESCRIPTION
        "-- empty --"
    ::= { lcsStatusWtpMngmtRadioprofilsEntry 15 }

-- {COLUMN} 310.1.59.101.1.16
lcsStatusWtpMngmtRadioprofilsEntryIndoorOnlyOperation OBJECT-TYPE
    SYNTAX     INTEGER
      {
        eNo (0),
        eYes (1)
      }
    MAX-ACCESS read-only
    STATUS     current
    DESCRIPTION
        "-- empty --"
    ::= { lcsStatusWtpMngmtRadioprofilsEntry 16 }

-- {COLUMN} 310.1.59.101.1.20
lcsStatusWtpMngmtRadioprofilsEntryReportSeenClients OBJECT-TYPE
    SYNTAX     INTEGER
      {
        eYes (1),
        eNo (0)
      }
    MAX-ACCESS read-only
    STATUS     current
    DESCRIPTION
        "-- empty --"
    ::= { lcsStatusWtpMngmtRadioprofilsEntry 20 }

-- {TABLE} 310.1.59.102
lcsStatusWtpMngmtRadioModeTable OBJECT-TYPE
    SYNTAX     SEQUENCE OF LcsStatusWtpMngmtRadioModeEntry
    MAX-ACCESS not-accessible
    STATUS     current
    DESCRIPTION
        "-- empty --"
    ::= { lcsStatusWtpMngmt 102 }

-- {ENTRY} 310.1.59.102.1
lcsStatusWtpMngmtRadioModeEntry OBJECT-TYPE
    SYNTAX     LcsStatusWtpMngmtRadioModeEntry
    MAX-ACCESS not-accessible
    STATUS     current
    DESCRIPTION
        ""
    INDEX {
        lcsStatusWtpMngmtRadioModeEntryIndex
    }
    ::= { lcsStatusWtpMngmtRadioModeTable 1 }

-- {SEQUENCE}
LcsStatusWtpMngmtRadioModeEntry ::= SEQUENCE {
    lcsStatusWtpMngmtRadioModeEntryIndex INTEGER,
    lcsStatusWtpMngmtRadioModeEntryRadioMode INTEGER,
    lcsStatusWtpMngmtRadioModeEntryOperating INTEGER,
    lcsStatusWtpMngmtRadioModeEntryRadioChannel INTEGER,
    lcsStatusWtpMngmtRadioModeEntryChannelList DisplayString,
    lcsStatusWtpMngmtRadioModeEntryAllow40mhz INTEGER,
    lcsStatusWtpMngmtRadioModeEntryAntennaMask INTEGER,
    lcsStatusWtpMngmtRadioModeEntryAntennaGain INTEGER,
    lcsStatusWtpMngmtRadioModeEntryTxPowerReduction INTEGER
}

-- {COLUMN} 310.1.59.102.1.1
lcsStatusWtpMngmtRadioModeEntryIndex OBJECT-TYPE
    SYNTAX     INTEGER (0..255)
    MAX-ACCESS read-only
    STATUS     current
    DESCRIPTION
        "-- empty --"
    ::= { lcsStatusWtpMngmtRadioModeEntry 1 }

-- {COLUMN} 310.1.59.102.1.2
lcsStatusWtpMngmtRadioModeEntryRadioMode OBJECT-TYPE
    SYNTAX     INTEGER
      {
        eDefault (0),
        e24ghz (1),
        e5ghz (2),
        eOff (3)
      }
    MAX-ACCESS read-only
    STATUS     current
    DESCRIPTION
        "-- empty --"
    ::= { lcsStatusWtpMngmtRadioModeEntry 2 }

-- {COLUMN} 310.1.59.102.1.3
lcsStatusWtpMngmtRadioModeEntryOperating OBJECT-TYPE
    SYNTAX     INTEGER
      {
        eYes (0),
        eNo (1)
      }
    MAX-ACCESS read-only
    STATUS     current
    DESCRIPTION
        "-- empty --"
    ::= { lcsStatusWtpMngmtRadioModeEntry 3 }

-- {COLUMN} 310.1.59.102.1.5
lcsStatusWtpMngmtRadioModeEntryRadioChannel OBJECT-TYPE
    SYNTAX     INTEGER
      {
        eAuto (0)
      }
    MAX-ACCESS read-only
    STATUS     current
    DESCRIPTION
        "-- empty --"
    ::= { lcsStatusWtpMngmtRadioModeEntry 5 }

-- {COLUMN} 310.1.59.102.1.4
lcsStatusWtpMngmtRadioModeEntryChannelList OBJECT-TYPE
    SYNTAX     DisplayString (SIZE(0..48))
    MAX-ACCESS read-only
    STATUS     current
    DESCRIPTION
        "-- empty --"
    ::= { lcsStatusWtpMngmtRadioModeEntry 4 }

-- {COLUMN} 310.1.59.102.1.6
lcsStatusWtpMngmtRadioModeEntryAllow40mhz OBJECT-TYPE
    SYNTAX     INTEGER
      {
        eAuto (0),
        eNo (1)
      }
    MAX-ACCESS read-only
    STATUS     current
    DESCRIPTION
        "-- empty --"
    ::= { lcsStatusWtpMngmtRadioModeEntry 6 }

-- {COLUMN} 310.1.59.102.1.7
lcsStatusWtpMngmtRadioModeEntryAntennaMask OBJECT-TYPE
    SYNTAX     INTEGER
      {
        eAuto (0),
        eAntenna1 (1),
        eAntenna1Plus2 (3),
        eAntenna1Plus3 (5),
        eAntenna1Plus2Plus3 (7)
      }
    MAX-ACCESS read-only
    STATUS     current
    DESCRIPTION
        "-- empty --"
    ::= { lcsStatusWtpMngmtRadioModeEntry 7 }

-- {COLUMN} 310.1.59.102.1.8
lcsStatusWtpMngmtRadioModeEntryAntennaGain OBJECT-TYPE
    SYNTAX     INTEGER (-128..127)
    MAX-ACCESS read-only
    STATUS     current
    DESCRIPTION
        "-- empty --"
    ::= { lcsStatusWtpMngmtRadioModeEntry 8 }

-- {COLUMN} 310.1.59.102.1.9
lcsStatusWtpMngmtRadioModeEntryTxPowerReduction OBJECT-TYPE
    SYNTAX     INTEGER (0..255)
    MAX-ACCESS read-only
    STATUS     current
    DESCRIPTION
        "-- empty --"
    ::= { lcsStatusWtpMngmtRadioModeEntry 9 }

-- {TABLE} 310.1.59.103
lcsStatusWtpMngmtNetwprofilsTable OBJECT-TYPE
    SYNTAX     SEQUENCE OF LcsStatusWtpMngmtNetwprofilsEntry
    MAX-ACCESS not-accessible
    STATUS     current
    DESCRIPTION
        "network profiles"
    ::= { lcsStatusWtpMngmt 103 }

-- {ENTRY} 310.1.59.103.1
lcsStatusWtpMngmtNetwprofilsEntry OBJECT-TYPE
    SYNTAX     LcsStatusWtpMngmtNetwprofilsEntry
    MAX-ACCESS not-accessible
    STATUS     current
    DESCRIPTION
        ""
    INDEX {
        lcsStatusWtpMngmtNetwprofilsEntryName
    }
    ::= { lcsStatusWtpMngmtNetwprofilsTable 1 }

-- {SEQUENCE}
LcsStatusWtpMngmtNetwprofilsEntry ::= SEQUENCE {
    lcsStatusWtpMngmtNetwprofilsEntryName DisplayString,
    lcsStatusWtpMngmtNetwprofilsEntrySsid DisplayString,
    lcsStatusWtpMngmtNetwprofilsEntryOperating INTEGER,
    lcsStatusWtpMngmtNetwprofilsEntryVlanMode INTEGER,
    lcsStatusWtpMngmtNetwprofilsEntryVlanIdnew INTEGER,
    lcsStatusWtpMngmtNetwprofilsEntryVlanId INTEGER,
    lcsStatusWtpMngmtNetwprofilsEntryEncryption INTEGER,
    lcsStatusWtpMngmtNetwprofilsEntryWpa1SessionKeytypes INTEGER,
    lcsStatusWtpMngmtNetwprofilsEntryWpa2SessionKeytypes INTEGER,
    lcsStatusWtpMngmtNetwprofilsEntryWpaVersion INTEGER,
    lcsStatusWtpMngmtNetwprofilsEntryKey DisplayString,
    lcsStatusWtpMngmtNetwprofilsEntryRadioBand INTEGER,
    lcsStatusWtpMngmtNetwprofilsEntryContinuation INTEGER,
    lcsStatusWtpMngmtNetwprofilsEntryMinTxRate INTEGER,
    lcsStatusWtpMngmtNetwprofilsEntryMaxTxRate INTEGER,
    lcsStatusWtpMngmtNetwprofilsEntryBasicRate INTEGER,
    lcsStatusWtpMngmtNetwprofilsEntry11bPreamble INTEGER,
    lcsStatusWtpMngmtNetwprofilsEntryMacFilter INTEGER,
    lcsStatusWtpMngmtNetwprofilsEntryClBrgSupport INTEGER,
    lcsStatusWtpMngmtNetwprofilsEntryMaxStations INTEGER,
    lcsStatusWtpMngmtNetwprofilsEntrySsidBroadcast INTEGER,
    lcsStatusWtpMngmtNetwprofilsEntryVlanTrunk INTEGER,
    lcsStatusWtpMngmtNetwprofilsEntryMinHtMcs INTEGER,
    lcsStatusWtpMngmtNetwprofilsEntryMaxHtMcs INTEGER,
    lcsStatusWtpMngmtNetwprofilsEntryShortGuardInterval INTEGER,
    lcsStatusWtpMngmtNetwprofilsEntryMaxSpatialStreams INTEGER,
    lcsStatusWtpMngmtNetwprofilsEntrySendAggregates INTEGER,
    lcsStatusWtpMngmtNetwprofilsEntryRadiusAccounting INTEGER,
    lcsStatusWtpMngmtNetwprofilsEntryConnectSsidTo INTEGER,
    lcsStatusWtpMngmtNetwprofilsEntryInterStationTraffic INTEGER,
    lcsStatusWtpMngmtNetwprofilsEntryRadiusProfile DisplayString
}

-- {COLUMN} 310.1.59.103.1.1
lcsStatusWtpMngmtNetwprofilsEntryName OBJECT-TYPE
    SYNTAX     DisplayString (SIZE(0..31))
    MAX-ACCESS read-only
    STATUS     current
    DESCRIPTION
        "-- empty --"
    ::= { lcsStatusWtpMngmtNetwprofilsEntry 1 }

-- {COLUMN} 310.1.59.103.1.21
lcsStatusWtpMngmtNetwprofilsEntrySsid OBJECT-TYPE
    SYNTAX     DisplayString (SIZE(0..32))
    MAX-ACCESS read-only
    STATUS     current
    DESCRIPTION
        "-- empty --"
    ::= { lcsStatusWtpMngmtNetwprofilsEntry 21 }

-- {COLUMN} 310.1.59.103.1.4
lcsStatusWtpMngmtNetwprofilsEntryOperating OBJECT-TYPE
    SYNTAX     INTEGER
      {
        eYes (0),
        eNo (1)
      }
    MAX-ACCESS read-only
    STATUS     current
    DESCRIPTION
        "-- empty --"
    ::= { lcsStatusWtpMngmtNetwprofilsEntry 4 }

-- {COLUMN} 310.1.59.103.1.30
lcsStatusWtpMngmtNetwprofilsEntryVlanMode OBJECT-TYPE
    SYNTAX     INTEGER
      {
        eUntagged (0),
        eTagged (1)
      }
    MAX-ACCESS read-only
    STATUS     current
    DESCRIPTION
        "-- empty --"
    ::= { lcsStatusWtpMngmtNetwprofilsEntry 30 }

-- {COLUMN} 310.1.59.103.1.34
lcsStatusWtpMngmtNetwprofilsEntryVlanIdnew OBJECT-TYPE
    SYNTAX     INTEGER (0..65535)
    MAX-ACCESS read-only
    STATUS     current
    DESCRIPTION
        ""
    ::= { lcsStatusWtpMngmtNetwprofilsEntry 34 }

-- {COLUMN} 310.1.59.103.1.5
lcsStatusWtpMngmtNetwprofilsEntryVlanId OBJECT-TYPE
    SYNTAX     INTEGER (0..65535)
    MAX-ACCESS read-only
    STATUS     obsolete
    DESCRIPTION
        ""
    ::= { lcsStatusWtpMngmtNetwprofilsEntry 5 }

-- {COLUMN} 310.1.59.103.1.6
lcsStatusWtpMngmtNetwprofilsEntryEncryption OBJECT-TYPE
    SYNTAX     INTEGER
      {
        e80211iWpaPsk (0),
        e80211iWpa8021x (1),
        eWep104Bits (2),
        eWep40Bits (3),
        eWep104Bits8021x (4),
        eWep40Bits8021x (5),
        eNone (6)
      }
    MAX-ACCESS read-only
    STATUS     current
    DESCRIPTION
        "-- empty --"
    ::= { lcsStatusWtpMngmtNetwprofilsEntry 6 }

-- {COLUMN} 310.1.59.103.1.7
lcsStatusWtpMngmtNetwprofilsEntryWpa1SessionKeytypes OBJECT-TYPE
    SYNTAX     INTEGER
      {
        eTkipAes (0),
        eAes (1),
        eTkip (2)
      }
    MAX-ACCESS read-only
    STATUS     current
    DESCRIPTION
        "-- empty --"
    ::= { lcsStatusWtpMngmtNetwprofilsEntry 7 }

-- {COLUMN} 310.1.59.103.1.27
lcsStatusWtpMngmtNetwprofilsEntryWpa2SessionKeytypes OBJECT-TYPE
    SYNTAX     INTEGER
      {
        eTkipAes (0),
        eAes (1),
        eTkip (2)
      }
    MAX-ACCESS read-only
    STATUS     current
    DESCRIPTION
        "-- empty --"
    ::= { lcsStatusWtpMngmtNetwprofilsEntry 27 }

-- {COLUMN} 310.1.59.103.1.8
lcsStatusWtpMngmtNetwprofilsEntryWpaVersion OBJECT-TYPE
    SYNTAX     INTEGER
      {
        eWpa12 (0),
        eWpa1 (1),
        eWpa2 (2)
      }
    MAX-ACCESS read-only
    STATUS     current
    DESCRIPTION
        "-- empty --"
    ::= { lcsStatusWtpMngmtNetwprofilsEntry 8 }

-- {COLUMN} 310.1.59.103.1.9
lcsStatusWtpMngmtNetwprofilsEntryKey OBJECT-TYPE
    SYNTAX     DisplayString (SIZE(0..63))
    MAX-ACCESS read-only
    STATUS     current
    DESCRIPTION
        "-- empty --"
    ::= { lcsStatusWtpMngmtNetwprofilsEntry 9 }

-- {COLUMN} 310.1.59.103.1.10
lcsStatusWtpMngmtNetwprofilsEntryRadioBand OBJECT-TYPE
    SYNTAX     INTEGER
      {
        e24ghz5ghz (0),
        e24ghz (1),
        e5ghz (2)
      }
    MAX-ACCESS read-only
    STATUS     current
    DESCRIPTION
        "-- empty --"
    ::= { lcsStatusWtpMngmtNetwprofilsEntry 10 }

-- {COLUMN} 310.1.59.103.1.11
lcsStatusWtpMngmtNetwprofilsEntryContinuation OBJECT-TYPE
    SYNTAX     INTEGER (0..65535)
    MAX-ACCESS read-only
    STATUS     current
    DESCRIPTION
        ""
    ::= { lcsStatusWtpMngmtNetwprofilsEntry 11 }

-- {COLUMN} 310.1.59.103.1.12
lcsStatusWtpMngmtNetwprofilsEntryMinTxRate OBJECT-TYPE
    SYNTAX     INTEGER
      {
        eAuto (0),
        e1M (1), -- 1Mbit/s
        e2M (2), -- 2Mbit/s
        e5M5 (3), -- 5.5Mbit/s
        e11M (4), -- 11Mbit/s
        e6M (5), -- 6Mbit/s
        e9M (6), -- 9Mbit/s
        e12M (7), -- 12Mbit/s
        e18M (8), -- 18Mbit/s
        e24M (9), -- 24Mbit/s
        e36M (10), -- 36Mbit/s
        e48M (11), -- 48Mbit/s
        e54M (12), -- 54Mbit/s
        eT72M (13), -- Turbo 72Mbit/s
        eT96M (14), -- Turbo 96Mbit/s
        eT108M (15) -- Turbo 108Mbit/s
      }
    MAX-ACCESS read-only
    STATUS     current
    DESCRIPTION
        "-- empty --"
    ::= { lcsStatusWtpMngmtNetwprofilsEntry 12 }

-- {COLUMN} 310.1.59.103.1.13
lcsStatusWtpMngmtNetwprofilsEntryMaxTxRate OBJECT-TYPE
    SYNTAX     INTEGER
      {
        eAuto (0),
        e1M (1), -- 1Mbit/s
        e2M (2), -- 2Mbit/s
        e5M5 (3), -- 5.5Mbit/s
        e11M (4), -- 11Mbit/s
        e6M (5), -- 6Mbit/s
        e9M (6), -- 9Mbit/s
        e12M (7), -- 12Mbit/s
        e18M (8), -- 18Mbit/s
        e24M (9), -- 24Mbit/s
        e36M (10), -- 36Mbit/s
        e48M (11), -- 48Mbit/s
        e54M (12), -- 54Mbit/s
        eT72M (13), -- Turbo 72Mbit/s
        eT96M (14), -- Turbo 96Mbit/s
        eT108M (15) -- Turbo 108Mbit/s
      }
    MAX-ACCESS read-only
    STATUS     current
    DESCRIPTION
        "-- empty --"
    ::= { lcsStatusWtpMngmtNetwprofilsEntry 13 }

-- {COLUMN} 310.1.59.103.1.14
lcsStatusWtpMngmtNetwprofilsEntryBasicRate OBJECT-TYPE
    SYNTAX     INTEGER
      {
        e1M (1), -- 1Mbit/s
        e2M (0), -- 2Mbit/s
        e5M5 (3), -- 5.5Mbit/s
        e11M (4), -- 11Mbit/s
        e6M (5), -- 6Mbit/s
        e9M (6), -- 9Mbit/s
        e12M (7), -- 12Mbit/s
        e18M (8), -- 18Mbit/s
        e24M (9), -- 24Mbit/s
        e36M (10), -- 36Mbit/s
        e48M (11), -- 48Mbit/s
        e54M (12), -- 54Mbit/s
        eT72M (13), -- Turbo 72Mbit/s
        eT96M (14), -- Turbo 96Mbit/s
        eT108M (15) -- Turbo 108Mbit/s
      }
    MAX-ACCESS read-only
    STATUS     current
    DESCRIPTION
        "-- empty --"
    ::= { lcsStatusWtpMngmtNetwprofilsEntry 14 }

-- {COLUMN} 310.1.59.103.1.15
lcsStatusWtpMngmtNetwprofilsEntry11bPreamble OBJECT-TYPE
    SYNTAX     INTEGER
      {
        eAuto (0),
        eLong (1)
      }
    MAX-ACCESS read-only
    STATUS     current
    DESCRIPTION
        "-- empty --"
    ::= { lcsStatusWtpMngmtNetwprofilsEntry 15 }

-- {COLUMN} 310.1.59.103.1.16
lcsStatusWtpMngmtNetwprofilsEntryMacFilter OBJECT-TYPE
    SYNTAX     INTEGER
      {
        eYes (1),
        eNo (0)
      }
    MAX-ACCESS read-only
    STATUS     current
    DESCRIPTION
        "-- empty --"
    ::= { lcsStatusWtpMngmtNetwprofilsEntry 16 }

-- {COLUMN} 310.1.59.103.1.17
lcsStatusWtpMngmtNetwprofilsEntryClBrgSupport OBJECT-TYPE
    SYNTAX     INTEGER
      {
        eNo (0),
        eYes (1),
        eExclusive (2)
      }
    MAX-ACCESS read-only
    STATUS     current
    DESCRIPTION
        "-- empty --"
    ::= { lcsStatusWtpMngmtNetwprofilsEntry 17 }

-- {COLUMN} 310.1.59.103.1.18
lcsStatusWtpMngmtNetwprofilsEntryMaxStations OBJECT-TYPE
    SYNTAX     INTEGER (0..65535)
    MAX-ACCESS read-only
    STATUS     current
    DESCRIPTION
        "-- empty --"
    ::= { lcsStatusWtpMngmtNetwprofilsEntry 18 }

-- {COLUMN} 310.1.59.103.1.19
lcsStatusWtpMngmtNetwprofilsEntrySsidBroadcast OBJECT-TYPE
    SYNTAX     INTEGER
      {
        eYes (0),
        eNo (1),
        eTightened (2)
      }
    MAX-ACCESS read-only
    STATUS     current
    DESCRIPTION
        "-- empty --"
    ::= { lcsStatusWtpMngmtNetwprofilsEntry 19 }

-- {COLUMN} 310.1.59.103.1.20
lcsStatusWtpMngmtNetwprofilsEntryVlanTrunk OBJECT-TYPE
    SYNTAX     INTEGER (0..65535)
    MAX-ACCESS read-only
    STATUS     current
    DESCRIPTION
        "-- empty --"
    ::= { lcsStatusWtpMngmtNetwprofilsEntry 20 }

-- {COLUMN} 310.1.59.103.1.22
lcsStatusWtpMngmtNetwprofilsEntryMinHtMcs OBJECT-TYPE
    SYNTAX     INTEGER
      {
        eAuto (0),
        eMcs08 (1),
        eMcs19 (2),
        eMcs210 (3),
        eMcs311 (4),
        eMcs412 (5),
        eMcs513 (6),
        eMcs614 (7),
        eMcs715 (8)
      }
    MAX-ACCESS read-only
    STATUS     current
    DESCRIPTION
        "-- empty --"
    ::= { lcsStatusWtpMngmtNetwprofilsEntry 22 }

-- {COLUMN} 310.1.59.103.1.23
lcsStatusWtpMngmtNetwprofilsEntryMaxHtMcs OBJECT-TYPE
    SYNTAX     INTEGER
      {
        eAuto (0),
        eMcs08 (1),
        eMcs19 (2),
        eMcs210 (3),
        eMcs311 (4),
        eMcs412 (5),
        eMcs513 (6),
        eMcs614 (7),
        eMcs715 (8)
      }
    MAX-ACCESS read-only
    STATUS     current
    DESCRIPTION
        "-- empty --"
    ::= { lcsStatusWtpMngmtNetwprofilsEntry 23 }

-- {COLUMN} 310.1.59.103.1.24
lcsStatusWtpMngmtNetwprofilsEntryShortGuardInterval OBJECT-TYPE
    SYNTAX     INTEGER
      {
        eAuto (0),
        eNo (1)
      }
    MAX-ACCESS read-only
    STATUS     current
    DESCRIPTION
        "-- empty --"
    ::= { lcsStatusWtpMngmtNetwprofilsEntry 24 }

-- {COLUMN} 310.1.59.103.1.25
lcsStatusWtpMngmtNetwprofilsEntryMaxSpatialStreams OBJECT-TYPE
    SYNTAX     INTEGER
      {
        eAuto (0),
        eOne (1),
        eTwo (2)
      }
    MAX-ACCESS read-only
    STATUS     current
    DESCRIPTION
        "-- empty --"
    ::= { lcsStatusWtpMngmtNetwprofilsEntry 25 }

-- {COLUMN} 310.1.59.103.1.26
lcsStatusWtpMngmtNetwprofilsEntrySendAggregates OBJECT-TYPE
    SYNTAX     INTEGER
      {
        eYes (1),
        eNo (0)
      }
    MAX-ACCESS read-only
    STATUS     current
    DESCRIPTION
        "-- empty --"
    ::= { lcsStatusWtpMngmtNetwprofilsEntry 26 }

-- {COLUMN} 310.1.59.103.1.28
lcsStatusWtpMngmtNetwprofilsEntryRadiusAccounting OBJECT-TYPE
    SYNTAX     INTEGER
      {
        eYes (1),
        eNo (0)
      }
    MAX-ACCESS read-only
    STATUS     current
    DESCRIPTION
        "-- empty --"
    ::= { lcsStatusWtpMngmtNetwprofilsEntry 28 }

-- {COLUMN} 310.1.59.103.1.32
lcsStatusWtpMngmtNetwprofilsEntryConnectSsidTo OBJECT-TYPE
    SYNTAX     INTEGER
      {
        eLan (0),
        eWlcTunnel1 (1),
        eWlcTunnel2 (2),
        eWlcTunnel3 (3),
        eWlcTunnel4 (4),
        eWlcTunnel5 (5),
        eWlcTunnel6 (6),
        eWlcTunnel7 (7),
        eWlcTunnel8 (8),
        eWlcTunnel9 (9),
        eWlcTunnel10 (10),
        eWlcTunnel11 (11),
        eWlcTunnel12 (12),
        eWlcTunnel13 (13),
        eWlcTunnel14 (14),
        eWlcTunnel15 (15),
        eWlcTunnel16 (16),
        eWlcTunnel17 (17),
        eWlcTunnel18 (18),
        eWlcTunnel19 (19),
        eWlcTunnel20 (20),
        eWlcTunnel21 (21),
        eWlcTunnel22 (22),
        eWlcTunnel23 (23),
        eWlcTunnel24 (24),
        eWlcTunnel25 (25),
        eWlcTunnel26 (26),
        eWlcTunnel27 (27),
        eWlcTunnel28 (28),
        eWlcTunnel29 (29),
        eWlcTunnel30 (30),
        eWlcTunnel31 (31),
        eWlcTunnel32 (32)
      }
    MAX-ACCESS read-only
    STATUS     current
    DESCRIPTION
        "-- empty --"
    ::= { lcsStatusWtpMngmtNetwprofilsEntry 32 }

-- {COLUMN} 310.1.59.103.1.33
lcsStatusWtpMngmtNetwprofilsEntryInterStationTraffic OBJECT-TYPE
    SYNTAX     INTEGER
      {
        eYes (1),
        eNo (0)
      }
    MAX-ACCESS read-only
    STATUS     current
    DESCRIPTION
        "-- empty --"
    ::= { lcsStatusWtpMngmtNetwprofilsEntry 33 }

-- {COLUMN} 310.1.59.103.1.35
lcsStatusWtpMngmtNetwprofilsEntryRadiusProfile OBJECT-TYPE
    SYNTAX     DisplayString (SIZE(0..16))
    MAX-ACCESS read-only
    STATUS     current
    DESCRIPTION
        "-- empty --"
    ::= { lcsStatusWtpMngmtNetwprofilsEntry 35 }

-- {TABLE} 310.1.59.104
lcsStatusWtpMngmtApBridgeInterfacesTable OBJECT-TYPE
    SYNTAX     SEQUENCE OF LcsStatusWtpMngmtApBridgeInterfacesEntry
    MAX-ACCESS not-accessible
    STATUS     current
    DESCRIPTION
        "-- empty --"
    ::= { lcsStatusWtpMngmt 104 }

-- {ENTRY} 310.1.59.104.1
lcsStatusWtpMngmtApBridgeInterfacesEntry OBJECT-TYPE
    SYNTAX     LcsStatusWtpMngmtApBridgeInterfacesEntry
    MAX-ACCESS not-accessible
    STATUS     current
    DESCRIPTION
        ""
    INDEX {
        lcsStatusWtpMngmtApBridgeInterfacesEntryBridgeInterface
    }
    ::= { lcsStatusWtpMngmtApBridgeInterfacesTable 1 }

-- {SEQUENCE}
LcsStatusWtpMngmtApBridgeInterfacesEntry ::= SEQUENCE {
    lcsStatusWtpMngmtApBridgeInterfacesEntryBridgeInterface INTEGER,
    lcsStatusWtpMngmtApBridgeInterfacesEntryRegisteredConnections INTEGER,
    lcsStatusWtpMngmtApBridgeInterfacesEntryRecvUnicasts INTEGER,
    lcsStatusWtpMngmtApBridgeInterfacesEntryRecvMulticasts INTEGER,
    lcsStatusWtpMngmtApBridgeInterfacesEntryRecvBroadcasts INTEGER,
    lcsStatusWtpMngmtApBridgeInterfacesEntryTransUnicastPackets INTEGER,
    lcsStatusWtpMngmtApBridgeInterfacesEntryTransMultiBroadPckts INTEGER,
    lcsStatusWtpMngmtApBridgeInterfacesEntryDroppedPackets INTEGER
}

-- {COLUMN} 310.1.59.104.1.1
lcsStatusWtpMngmtApBridgeInterfacesEntryBridgeInterface OBJECT-TYPE
    SYNTAX     INTEGER
      {
        eLan (0),
        eWlcTunnel1 (1),
        eWlcTunnel2 (2),
        eWlcTunnel3 (3),
        eWlcTunnel4 (4),
        eWlcTunnel5 (5),
        eWlcTunnel6 (6),
        eWlcTunnel7 (7),
        eWlcTunnel8 (8),
        eWlcTunnel9 (9),
        eWlcTunnel10 (10),
        eWlcTunnel11 (11),
        eWlcTunnel12 (12),
        eWlcTunnel13 (13),
        eWlcTunnel14 (14),
        eWlcTunnel15 (15),
        eWlcTunnel16 (16),
        eWlcTunnel17 (17),
        eWlcTunnel18 (18),
        eWlcTunnel19 (19),
        eWlcTunnel20 (20),
        eWlcTunnel21 (21),
        eWlcTunnel22 (22),
        eWlcTunnel23 (23),
        eWlcTunnel24 (24),
        eWlcTunnel25 (25),
        eWlcTunnel26 (26),
        eWlcTunnel27 (27),
        eWlcTunnel28 (28),
        eWlcTunnel29 (29),
        eWlcTunnel30 (30),
        eWlcTunnel31 (31),
        eWlcTunnel32 (32)
      }
    MAX-ACCESS read-only
    STATUS     current
    DESCRIPTION
        "-- empty --"
    ::= { lcsStatusWtpMngmtApBridgeInterfacesEntry 1 }

-- {COLUMN} 310.1.59.104.1.2
lcsStatusWtpMngmtApBridgeInterfacesEntryRegisteredConnections OBJECT-TYPE
    SYNTAX     INTEGER (0..2147483647)
    MAX-ACCESS read-only
    STATUS     current
    DESCRIPTION
        "-- empty --"
    ::= { lcsStatusWtpMngmtApBridgeInterfacesEntry 2 }

-- {COLUMN} 310.1.59.104.1.3
lcsStatusWtpMngmtApBridgeInterfacesEntryRecvUnicasts OBJECT-TYPE
    SYNTAX     INTEGER (0..2147483647)
    MAX-ACCESS read-only
    STATUS     current
    DESCRIPTION
        "-- empty --"
    ::= { lcsStatusWtpMngmtApBridgeInterfacesEntry 3 }

-- {COLUMN} 310.1.59.104.1.4
lcsStatusWtpMngmtApBridgeInterfacesEntryRecvMulticasts OBJECT-TYPE
    SYNTAX     INTEGER (0..2147483647)
    MAX-ACCESS read-only
    STATUS     current
    DESCRIPTION
        "-- empty --"
    ::= { lcsStatusWtpMngmtApBridgeInterfacesEntry 4 }

-- {COLUMN} 310.1.59.104.1.5
lcsStatusWtpMngmtApBridgeInterfacesEntryRecvBroadcasts OBJECT-TYPE
    SYNTAX     INTEGER (0..2147483647)
    MAX-ACCESS read-only
    STATUS     current
    DESCRIPTION
        "-- empty --"
    ::= { lcsStatusWtpMngmtApBridgeInterfacesEntry 5 }

-- {COLUMN} 310.1.59.104.1.6
lcsStatusWtpMngmtApBridgeInterfacesEntryTransUnicastPackets OBJECT-TYPE
    SYNTAX     INTEGER (0..2147483647)
    MAX-ACCESS read-only
    STATUS     current
    DESCRIPTION
        "-- empty --"
    ::= { lcsStatusWtpMngmtApBridgeInterfacesEntry 6 }

-- {COLUMN} 310.1.59.104.1.7
lcsStatusWtpMngmtApBridgeInterfacesEntryTransMultiBroadPckts OBJECT-TYPE
    SYNTAX     INTEGER (0..2147483647)
    MAX-ACCESS read-only
    STATUS     current
    DESCRIPTION
        ""
    ::= { lcsStatusWtpMngmtApBridgeInterfacesEntry 7 }

-- {COLUMN} 310.1.59.104.1.8
lcsStatusWtpMngmtApBridgeInterfacesEntryDroppedPackets OBJECT-TYPE
    SYNTAX     INTEGER (0..2147483647)
    MAX-ACCESS read-only
    STATUS     current
    DESCRIPTION
        "-- empty --"
    ::= { lcsStatusWtpMngmtApBridgeInterfacesEntry 8 }

-- {TABLE} 310.1.59.105
lcsStatusWtpMngmtRadiusServerProfilesTable OBJECT-TYPE
    SYNTAX     SEQUENCE OF LcsStatusWtpMngmtRadiusServerProfilesEntry
    MAX-ACCESS not-accessible
    STATUS     current
    DESCRIPTION
        "-- empty --"
    ::= { lcsStatusWtpMngmt 105 }

-- {ENTRY} 310.1.59.105.1
lcsStatusWtpMngmtRadiusServerProfilesEntry OBJECT-TYPE
    SYNTAX     LcsStatusWtpMngmtRadiusServerProfilesEntry
    MAX-ACCESS not-accessible
    STATUS     current
    DESCRIPTION
        ""
    INDEX {
        lcsStatusWtpMngmtRadiusServerProfilesEntryName
    }
    ::= { lcsStatusWtpMngmtRadiusServerProfilesTable 1 }

-- {SEQUENCE}
LcsStatusWtpMngmtRadiusServerProfilesEntry ::= SEQUENCE {
    lcsStatusWtpMngmtRadiusServerProfilesEntryName DisplayString,
    lcsStatusWtpMngmtRadiusServerProfilesEntryAccessIp IpAddress,
    lcsStatusWtpMngmtRadiusServerProfilesEntryAccessPort INTEGER,
    lcsStatusWtpMngmtRadiusServerProfilesEntryAccessSecret DisplayString,
    lcsStatusWtpMngmtRadiusServerProfilesEntryAccessLoopback DisplayString,
    lcsStatusWtpMngmtRadiusServerProfilesEntryAccessProtocol INTEGER,
    lcsStatusWtpMngmtRadiusServerProfilesEntryAccountIp IpAddress,
    lcsStatusWtpMngmtRadiusServerProfilesEntryAccountPort INTEGER,
    lcsStatusWtpMngmtRadiusServerProfilesEntryAccountSecret DisplayString,
    lcsStatusWtpMngmtRadiusServerProfilesEntryAccountLoopback DisplayString,
    lcsStatusWtpMngmtRadiusServerProfilesEntryAccountProtocol INTEGER,
    lcsStatusWtpMngmtRadiusServerProfilesEntryBackup DisplayString
}

-- {COLUMN} 310.1.59.105.1.1
lcsStatusWtpMngmtRadiusServerProfilesEntryName OBJECT-TYPE
    SYNTAX     DisplayString (SIZE(0..16))
    MAX-ACCESS read-only
    STATUS     current
    DESCRIPTION
        "-- empty --"
    ::= { lcsStatusWtpMngmtRadiusServerProfilesEntry 1 }

-- {COLUMN} 310.1.59.105.1.7
lcsStatusWtpMngmtRadiusServerProfilesEntryAccessIp OBJECT-TYPE
    SYNTAX     IpAddress
    MAX-ACCESS read-only
    STATUS     current
    DESCRIPTION
        "-- empty --"
    ::= { lcsStatusWtpMngmtRadiusServerProfilesEntry 7 }

-- {COLUMN} 310.1.59.105.1.8
lcsStatusWtpMngmtRadiusServerProfilesEntryAccessPort OBJECT-TYPE
    SYNTAX     INTEGER (0..65535)
    MAX-ACCESS read-only
    STATUS     current
    DESCRIPTION
        "-- empty --"
    ::= { lcsStatusWtpMngmtRadiusServerProfilesEntry 8 }

-- {COLUMN} 310.1.59.105.1.9
lcsStatusWtpMngmtRadiusServerProfilesEntryAccessSecret OBJECT-TYPE
    SYNTAX     DisplayString (SIZE(0..64))
    MAX-ACCESS read-only
    STATUS     current
    DESCRIPTION
        "-- empty --"
    ::= { lcsStatusWtpMngmtRadiusServerProfilesEntry 9 }

-- {COLUMN} 310.1.59.105.1.10
lcsStatusWtpMngmtRadiusServerProfilesEntryAccessLoopback OBJECT-TYPE
    SYNTAX     DisplayString (SIZE(0..16))
    MAX-ACCESS read-only
    STATUS     current
    DESCRIPTION
        "-- empty --"
    ::= { lcsStatusWtpMngmtRadiusServerProfilesEntry 10 }

-- {COLUMN} 310.1.59.105.1.11
lcsStatusWtpMngmtRadiusServerProfilesEntryAccessProtocol OBJECT-TYPE
    SYNTAX     INTEGER
      {
        eRadius (0),
        eRadsec (1)
      }
    MAX-ACCESS read-only
    STATUS     current
    DESCRIPTION
        "-- empty --"
    ::= { lcsStatusWtpMngmtRadiusServerProfilesEntry 11 }

-- {COLUMN} 310.1.59.105.1.2
lcsStatusWtpMngmtRadiusServerProfilesEntryAccountIp OBJECT-TYPE
    SYNTAX     IpAddress
    MAX-ACCESS read-only
    STATUS     current
    DESCRIPTION
        "-- empty --"
    ::= { lcsStatusWtpMngmtRadiusServerProfilesEntry 2 }

-- {COLUMN} 310.1.59.105.1.3
lcsStatusWtpMngmtRadiusServerProfilesEntryAccountPort OBJECT-TYPE
    SYNTAX     INTEGER (0..65535)
    MAX-ACCESS read-only
    STATUS     current
    DESCRIPTION
        "-- empty --"
    ::= { lcsStatusWtpMngmtRadiusServerProfilesEntry 3 }

-- {COLUMN} 310.1.59.105.1.4
lcsStatusWtpMngmtRadiusServerProfilesEntryAccountSecret OBJECT-TYPE
    SYNTAX     DisplayString (SIZE(0..64))
    MAX-ACCESS read-only
    STATUS     current
    DESCRIPTION
        "-- empty --"
    ::= { lcsStatusWtpMngmtRadiusServerProfilesEntry 4 }

-- {COLUMN} 310.1.59.105.1.5
lcsStatusWtpMngmtRadiusServerProfilesEntryAccountLoopback OBJECT-TYPE
    SYNTAX     DisplayString (SIZE(0..16))
    MAX-ACCESS read-only
    STATUS     current
    DESCRIPTION
        "-- empty --"
    ::= { lcsStatusWtpMngmtRadiusServerProfilesEntry 5 }

-- {COLUMN} 310.1.59.105.1.6
lcsStatusWtpMngmtRadiusServerProfilesEntryAccountProtocol OBJECT-TYPE
    SYNTAX     INTEGER
      {
        eRadius (0),
        eRadsec (1)
      }
    MAX-ACCESS read-only
    STATUS     current
    DESCRIPTION
        "-- empty --"
    ::= { lcsStatusWtpMngmtRadiusServerProfilesEntry 6 }

-- {COLUMN} 310.1.59.105.1.12
lcsStatusWtpMngmtRadiusServerProfilesEntryBackup OBJECT-TYPE
    SYNTAX     DisplayString (SIZE(0..16))
    MAX-ACCESS read-only
    STATUS     current
    DESCRIPTION
        "-- empty --"
    ::= { lcsStatusWtpMngmtRadiusServerProfilesEntry 12 }

-- {TABLE} 310.1.59.120
lcsStatusWtpMngmtLogTableTable OBJECT-TYPE
    SYNTAX     SEQUENCE OF LcsStatusWtpMngmtLogTableEntry
    MAX-ACCESS not-accessible
    STATUS     current
    DESCRIPTION
        "-- empty --"
    ::= { lcsStatusWtpMngmt 120 }

-- {ENTRY} 310.1.59.120.1
lcsStatusWtpMngmtLogTableEntry OBJECT-TYPE
    SYNTAX     LcsStatusWtpMngmtLogTableEntry
    MAX-ACCESS not-accessible
    STATUS     current
    DESCRIPTION
        ""
    INDEX {
        lcsStatusWtpMngmtLogTableEntryIndex
    }
    ::= { lcsStatusWtpMngmtLogTableTable 1 }

-- {SEQUENCE}
LcsStatusWtpMngmtLogTableEntry ::= SEQUENCE {
    lcsStatusWtpMngmtLogTableEntryIndex INTEGER,
    lcsStatusWtpMngmtLogTableEntryTime DisplayString,
    lcsStatusWtpMngmtLogTableEntryEvent DisplayString
}

-- {COLUMN} 310.1.59.120.1.1
lcsStatusWtpMngmtLogTableEntryIndex OBJECT-TYPE
    SYNTAX     INTEGER (0..2147483647)
    MAX-ACCESS read-only
    STATUS     current
    DESCRIPTION
        "-- empty --"
    ::= { lcsStatusWtpMngmtLogTableEntry 1 }

-- {COLUMN} 310.1.59.120.1.2
lcsStatusWtpMngmtLogTableEntryTime OBJECT-TYPE
    SYNTAX     DisplayString (SIZE(0..19))
    MAX-ACCESS read-only
    STATUS     current
    DESCRIPTION
        "-- empty --"
    ::= { lcsStatusWtpMngmtLogTableEntry 2 }

-- {COLUMN} 310.1.59.120.1.6
lcsStatusWtpMngmtLogTableEntryEvent OBJECT-TYPE
    SYNTAX     DisplayString (SIZE(0..80))
    MAX-ACCESS read-only
    STATUS     current
    DESCRIPTION
        "-- empty --"
    ::= { lcsStatusWtpMngmtLogTableEntry 6 }

-- {OID} 310.1.61
lcsStatusCerts OBJECT IDENTIFIER ::= { lcsStatus 61 }

-- {OID} 310.1.61.1
lcsStatusCertsScepClnt OBJECT IDENTIFIER ::= { lcsStatusCerts 1 }

-- {TABLE} 310.1.61.1.4
lcsStatusCertsScepClntCasTable OBJECT-TYPE
    SYNTAX     SEQUENCE OF LcsStatusCertsScepClntCasEntry
    MAX-ACCESS not-accessible
    STATUS     current
    DESCRIPTION
        "-- empty --"
    ::= { lcsStatusCertsScepClnt 4 }

-- {ENTRY} 310.1.61.1.4.1
lcsStatusCertsScepClntCasEntry OBJECT-TYPE
    SYNTAX     LcsStatusCertsScepClntCasEntry
    MAX-ACCESS not-accessible
    STATUS     current
    DESCRIPTION
        ""
    INDEX {
        lcsStatusCertsScepClntCasEntryIdx
    }
    ::= { lcsStatusCertsScepClntCasTable 1 }

-- {SEQUENCE}
LcsStatusCertsScepClntCasEntry ::= SEQUENCE {
    lcsStatusCertsScepClntCasEntryIdx INTEGER,
    lcsStatusCertsScepClntCasEntryName DisplayString,
    lcsStatusCertsScepClntCasEntryExpires DisplayString,
    lcsStatusCertsScepClntCasEntryIssued DisplayString,
    lcsStatusCertsScepClntCasEntryKeyUsage DisplayString,
    lcsStatusCertsScepClntCasEntryIssuer DisplayString,
    lcsStatusCertsScepClntCasEntrySubject DisplayString,
    lcsStatusCertsScepClntCasEntryStatus DisplayString,
    lcsStatusCertsScepClntCasEntryMd5Fingerprint DisplayString,
    lcsStatusCertsScepClntCasEntrySha1Fingerprint DisplayString,
    lcsStatusCertsScepClntCasEntryExpSnmp Counter32,
    lcsStatusCertsScepClntCasEntryIssSnmp Counter32
}

-- {COLUMN} 310.1.61.1.4.1.1
lcsStatusCertsScepClntCasEntryIdx OBJECT-TYPE
    SYNTAX     INTEGER (0..2147483647)
    MAX-ACCESS read-only
    STATUS     current
    DESCRIPTION
        "-- empty --"
    ::= { lcsStatusCertsScepClntCasEntry 1 }

-- {COLUMN} 310.1.61.1.4.1.2
lcsStatusCertsScepClntCasEntryName OBJECT-TYPE
    SYNTAX     DisplayString (SIZE(0..255))
    MAX-ACCESS read-only
    STATUS     current
    DESCRIPTION
        "-- empty --"
    ::= { lcsStatusCertsScepClntCasEntry 2 }

-- {COLUMN} 310.1.61.1.4.1.3
lcsStatusCertsScepClntCasEntryExpires OBJECT-TYPE
    SYNTAX     DisplayString (SIZE(0..255))
    MAX-ACCESS read-only
    STATUS     current
    DESCRIPTION
        "-- empty --"
    ::= { lcsStatusCertsScepClntCasEntry 3 }

-- {COLUMN} 310.1.61.1.4.1.4
lcsStatusCertsScepClntCasEntryIssued OBJECT-TYPE
    SYNTAX     DisplayString (SIZE(0..255))
    MAX-ACCESS read-only
    STATUS     current
    DESCRIPTION
        "-- empty --"
    ::= { lcsStatusCertsScepClntCasEntry 4 }

-- {COLUMN} 310.1.61.1.4.1.5
lcsStatusCertsScepClntCasEntryKeyUsage OBJECT-TYPE
    SYNTAX     DisplayString (SIZE(0..255))
    MAX-ACCESS read-only
    STATUS     current
    DESCRIPTION
        "-- empty --"
    ::= { lcsStatusCertsScepClntCasEntry 5 }

-- {COLUMN} 310.1.61.1.4.1.6
lcsStatusCertsScepClntCasEntryIssuer OBJECT-TYPE
    SYNTAX     DisplayString (SIZE(0..255))
    MAX-ACCESS read-only
    STATUS     current
    DESCRIPTION
        "-- empty --"
    ::= { lcsStatusCertsScepClntCasEntry 6 }

-- {COLUMN} 310.1.61.1.4.1.7
lcsStatusCertsScepClntCasEntrySubject OBJECT-TYPE
    SYNTAX     DisplayString (SIZE(0..255))
    MAX-ACCESS read-only
    STATUS     current
    DESCRIPTION
        "-- empty --"
    ::= { lcsStatusCertsScepClntCasEntry 7 }

-- {COLUMN} 310.1.61.1.4.1.8
lcsStatusCertsScepClntCasEntryStatus OBJECT-TYPE
    SYNTAX     DisplayString (SIZE(0..255))
    MAX-ACCESS read-only
    STATUS     current
    DESCRIPTION
        "-- empty --"
    ::= { lcsStatusCertsScepClntCasEntry 8 }

-- {COLUMN} 310.1.61.1.4.1.10
lcsStatusCertsScepClntCasEntryMd5Fingerprint OBJECT-TYPE
    SYNTAX     DisplayString (SIZE(0..255))
    MAX-ACCESS read-only
    STATUS     current
    DESCRIPTION
        "-- empty --"
    ::= { lcsStatusCertsScepClntCasEntry 10 }

-- {COLUMN} 310.1.61.1.4.1.11
lcsStatusCertsScepClntCasEntrySha1Fingerprint OBJECT-TYPE
    SYNTAX     DisplayString (SIZE(0..255))
    MAX-ACCESS read-only
    STATUS     current
    DESCRIPTION
        "-- empty --"
    ::= { lcsStatusCertsScepClntCasEntry 11 }

-- {COLUMN} 310.1.61.1.4.1.12
lcsStatusCertsScepClntCasEntryExpSnmp OBJECT-TYPE
    SYNTAX     Counter32
    MAX-ACCESS read-only
    STATUS     current
    DESCRIPTION
        "-- empty --"
    ::= { lcsStatusCertsScepClntCasEntry 12 }

-- {COLUMN} 310.1.61.1.4.1.13
lcsStatusCertsScepClntCasEntryIssSnmp OBJECT-TYPE
    SYNTAX     Counter32
    MAX-ACCESS read-only
    STATUS     current
    DESCRIPTION
        "-- empty --"
    ::= { lcsStatusCertsScepClntCasEntry 13 }

-- {TABLE} 310.1.61.1.5
lcsStatusCertsScepClntRasTable OBJECT-TYPE
    SYNTAX     SEQUENCE OF LcsStatusCertsScepClntRasEntry
    MAX-ACCESS not-accessible
    STATUS     current
    DESCRIPTION
        "-- empty --"
    ::= { lcsStatusCertsScepClnt 5 }

-- {ENTRY} 310.1.61.1.5.1
lcsStatusCertsScepClntRasEntry OBJECT-TYPE
    SYNTAX     LcsStatusCertsScepClntRasEntry
    MAX-ACCESS not-accessible
    STATUS     current
    DESCRIPTION
        ""
    INDEX {
        lcsStatusCertsScepClntRasEntryIdx
    }
    ::= { lcsStatusCertsScepClntRasTable 1 }

-- {SEQUENCE}
LcsStatusCertsScepClntRasEntry ::= SEQUENCE {
    lcsStatusCertsScepClntRasEntryIdx INTEGER,
    lcsStatusCertsScepClntRasEntryName DisplayString,
    lcsStatusCertsScepClntRasEntryExpires DisplayString,
    lcsStatusCertsScepClntRasEntryIssued DisplayString,
    lcsStatusCertsScepClntRasEntryKeyUsage DisplayString,
    lcsStatusCertsScepClntRasEntryIssuer DisplayString,
    lcsStatusCertsScepClntRasEntrySubject DisplayString,
    lcsStatusCertsScepClntRasEntryStatus DisplayString,
    lcsStatusCertsScepClntRasEntryExpSnmp Counter32,
    lcsStatusCertsScepClntRasEntryIssSnmp Counter32
}

-- {COLUMN} 310.1.61.1.5.1.1
lcsStatusCertsScepClntRasEntryIdx OBJECT-TYPE
    SYNTAX     INTEGER (0..2147483647)
    MAX-ACCESS read-only
    STATUS     current
    DESCRIPTION
        "-- empty --"
    ::= { lcsStatusCertsScepClntRasEntry 1 }

-- {COLUMN} 310.1.61.1.5.1.2
lcsStatusCertsScepClntRasEntryName OBJECT-TYPE
    SYNTAX     DisplayString (SIZE(0..255))
    MAX-ACCESS read-only
    STATUS     current
    DESCRIPTION
        "-- empty --"
    ::= { lcsStatusCertsScepClntRasEntry 2 }

-- {COLUMN} 310.1.61.1.5.1.3
lcsStatusCertsScepClntRasEntryExpires OBJECT-TYPE
    SYNTAX     DisplayString (SIZE(0..255))
    MAX-ACCESS read-only
    STATUS     current
    DESCRIPTION
        "-- empty --"
    ::= { lcsStatusCertsScepClntRasEntry 3 }

-- {COLUMN} 310.1.61.1.5.1.4
lcsStatusCertsScepClntRasEntryIssued OBJECT-TYPE
    SYNTAX     DisplayString (SIZE(0..255))
    MAX-ACCESS read-only
    STATUS     current
    DESCRIPTION
        "-- empty --"
    ::= { lcsStatusCertsScepClntRasEntry 4 }

-- {COLUMN} 310.1.61.1.5.1.5
lcsStatusCertsScepClntRasEntryKeyUsage OBJECT-TYPE
    SYNTAX     DisplayString (SIZE(0..255))
    MAX-ACCESS read-only
    STATUS     current
    DESCRIPTION
        "-- empty --"
    ::= { lcsStatusCertsScepClntRasEntry 5 }

-- {COLUMN} 310.1.61.1.5.1.6
lcsStatusCertsScepClntRasEntryIssuer OBJECT-TYPE
    SYNTAX     DisplayString (SIZE(0..255))
    MAX-ACCESS read-only
    STATUS     current
    DESCRIPTION
        "-- empty --"
    ::= { lcsStatusCertsScepClntRasEntry 6 }

-- {COLUMN} 310.1.61.1.5.1.7
lcsStatusCertsScepClntRasEntrySubject OBJECT-TYPE
    SYNTAX     DisplayString (SIZE(0..255))
    MAX-ACCESS read-only
    STATUS     current
    DESCRIPTION
        "-- empty --"
    ::= { lcsStatusCertsScepClntRasEntry 7 }

-- {COLUMN} 310.1.61.1.5.1.8
lcsStatusCertsScepClntRasEntryStatus OBJECT-TYPE
    SYNTAX     DisplayString (SIZE(0..255))
    MAX-ACCESS read-only
    STATUS     current
    DESCRIPTION
        "-- empty --"
    ::= { lcsStatusCertsScepClntRasEntry 8 }

-- {COLUMN} 310.1.61.1.5.1.9
lcsStatusCertsScepClntRasEntryExpSnmp OBJECT-TYPE
    SYNTAX     Counter32
    MAX-ACCESS read-only
    STATUS     current
    DESCRIPTION
        "-- empty --"
    ::= { lcsStatusCertsScepClntRasEntry 9 }

-- {COLUMN} 310.1.61.1.5.1.10
lcsStatusCertsScepClntRasEntryIssSnmp OBJECT-TYPE
    SYNTAX     Counter32
    MAX-ACCESS read-only
    STATUS     current
    DESCRIPTION
        "-- empty --"
    ::= { lcsStatusCertsScepClntRasEntry 10 }

-- {TABLE} 310.1.61.1.6
lcsStatusCertsScepClntCertsTable OBJECT-TYPE
    SYNTAX     SEQUENCE OF LcsStatusCertsScepClntCertsEntry
    MAX-ACCESS not-accessible
    STATUS     current
    DESCRIPTION
        "-- empty --"
    ::= { lcsStatusCertsScepClnt 6 }

-- {ENTRY} 310.1.61.1.6.1
lcsStatusCertsScepClntCertsEntry OBJECT-TYPE
    SYNTAX     LcsStatusCertsScepClntCertsEntry
    MAX-ACCESS not-accessible
    STATUS     current
    DESCRIPTION
        ""
    INDEX {
        lcsStatusCertsScepClntCertsEntryIdx
    }
    ::= { lcsStatusCertsScepClntCertsTable 1 }

-- {SEQUENCE}
LcsStatusCertsScepClntCertsEntry ::= SEQUENCE {
    lcsStatusCertsScepClntCertsEntryIdx INTEGER,
    lcsStatusCertsScepClntCertsEntryName DisplayString,
    lcsStatusCertsScepClntCertsEntryExpires DisplayString,
    lcsStatusCertsScepClntCertsEntryIssued DisplayString,
    lcsStatusCertsScepClntCertsEntryKeyUsage DisplayString,
    lcsStatusCertsScepClntCertsEntryExtendedKeyusage DisplayString,
    lcsStatusCertsScepClntCertsEntrySubjectaltname DisplayString,
    lcsStatusCertsScepClntCertsEntryIssuer DisplayString,
    lcsStatusCertsScepClntCertsEntrySubject DisplayString,
    lcsStatusCertsScepClntCertsEntryStatus DisplayString,
    lcsStatusCertsScepClntCertsEntryExpSnmp Counter32,
    lcsStatusCertsScepClntCertsEntryIssSnmp Counter32,
    lcsStatusCertsScepClntCertsEntryFilename DisplayString
}

-- {COLUMN} 310.1.61.1.6.1.1
lcsStatusCertsScepClntCertsEntryIdx OBJECT-TYPE
    SYNTAX     INTEGER (0..2147483647)
    MAX-ACCESS read-only
    STATUS     current
    DESCRIPTION
        "-- empty --"
    ::= { lcsStatusCertsScepClntCertsEntry 1 }

-- {COLUMN} 310.1.61.1.6.1.2
lcsStatusCertsScepClntCertsEntryName OBJECT-TYPE
    SYNTAX     DisplayString (SIZE(0..255))
    MAX-ACCESS read-only
    STATUS     current
    DESCRIPTION
        "-- empty --"
    ::= { lcsStatusCertsScepClntCertsEntry 2 }

-- {COLUMN} 310.1.61.1.6.1.3
lcsStatusCertsScepClntCertsEntryExpires OBJECT-TYPE
    SYNTAX     DisplayString (SIZE(0..255))
    MAX-ACCESS read-only
    STATUS     current
    DESCRIPTION
        "-- empty --"
    ::= { lcsStatusCertsScepClntCertsEntry 3 }

-- {COLUMN} 310.1.61.1.6.1.4
lcsStatusCertsScepClntCertsEntryIssued OBJECT-TYPE
    SYNTAX     DisplayString (SIZE(0..255))
    MAX-ACCESS read-only
    STATUS     current
    DESCRIPTION
        "-- empty --"
    ::= { lcsStatusCertsScepClntCertsEntry 4 }

-- {COLUMN} 310.1.61.1.6.1.5
lcsStatusCertsScepClntCertsEntryKeyUsage OBJECT-TYPE
    SYNTAX     DisplayString (SIZE(0..255))
    MAX-ACCESS read-only
    STATUS     current
    DESCRIPTION
        "-- empty --"
    ::= { lcsStatusCertsScepClntCertsEntry 5 }

-- {COLUMN} 310.1.61.1.6.1.12
lcsStatusCertsScepClntCertsEntryExtendedKeyusage OBJECT-TYPE
    SYNTAX     DisplayString (SIZE(0..255))
    MAX-ACCESS read-only
    STATUS     current
    DESCRIPTION
        "-- empty --"
    ::= { lcsStatusCertsScepClntCertsEntry 12 }

-- {COLUMN} 310.1.61.1.6.1.6
lcsStatusCertsScepClntCertsEntrySubjectaltname OBJECT-TYPE
    SYNTAX     DisplayString (SIZE(0..255))
    MAX-ACCESS read-only
    STATUS     current
    DESCRIPTION
        "-- empty --"
    ::= { lcsStatusCertsScepClntCertsEntry 6 }

-- {COLUMN} 310.1.61.1.6.1.7
lcsStatusCertsScepClntCertsEntryIssuer OBJECT-TYPE
    SYNTAX     DisplayString (SIZE(0..255))
    MAX-ACCESS read-only
    STATUS     current
    DESCRIPTION
        "-- empty --"
    ::= { lcsStatusCertsScepClntCertsEntry 7 }

-- {COLUMN} 310.1.61.1.6.1.8
lcsStatusCertsScepClntCertsEntrySubject OBJECT-TYPE
    SYNTAX     DisplayString (SIZE(0..255))
    MAX-ACCESS read-only
    STATUS     current
    DESCRIPTION
        "-- empty --"
    ::= { lcsStatusCertsScepClntCertsEntry 8 }

-- {COLUMN} 310.1.61.1.6.1.9
lcsStatusCertsScepClntCertsEntryStatus OBJECT-TYPE
    SYNTAX     DisplayString (SIZE(0..255))
    MAX-ACCESS read-only
    STATUS     current
    DESCRIPTION
        "-- empty --"
    ::= { lcsStatusCertsScepClntCertsEntry 9 }

-- {COLUMN} 310.1.61.1.6.1.10
lcsStatusCertsScepClntCertsEntryExpSnmp OBJECT-TYPE
    SYNTAX     Counter32
    MAX-ACCESS read-only
    STATUS     current
    DESCRIPTION
        "-- empty --"
    ::= { lcsStatusCertsScepClntCertsEntry 10 }

-- {COLUMN} 310.1.61.1.6.1.11
lcsStatusCertsScepClntCertsEntryIssSnmp OBJECT-TYPE
    SYNTAX     Counter32
    MAX-ACCESS read-only
    STATUS     current
    DESCRIPTION
        "-- empty --"
    ::= { lcsStatusCertsScepClntCertsEntry 11 }

-- {COLUMN} 310.1.61.1.6.1.13
lcsStatusCertsScepClntCertsEntryFilename OBJECT-TYPE
    SYNTAX     DisplayString (SIZE(0..255))
    MAX-ACCESS read-only
    STATUS     current
    DESCRIPTION
        "-- empty --"
    ::= { lcsStatusCertsScepClntCertsEntry 13 }

-- {SCALAR} 310.1.61.1.8
lcsStatusCertsScepClntScepClientState OBJECT-TYPE
    SYNTAX     DisplayString
    MAX-ACCESS read-only
    STATUS     current
    DESCRIPTION
        "-- empty --"
    ::= { lcsStatusCertsScepClnt 8 }

-- {TABLE} 310.1.61.4
lcsStatusCertsDeviceCertificatesTable OBJECT-TYPE
    SYNTAX     SEQUENCE OF LcsStatusCertsDeviceCertificatesEntry
    MAX-ACCESS not-accessible
    STATUS     current
    DESCRIPTION
        "-- empty --"
    ::= { lcsStatusCerts 4 }

-- {ENTRY} 310.1.61.4.1
lcsStatusCertsDeviceCertificatesEntry OBJECT-TYPE
    SYNTAX     LcsStatusCertsDeviceCertificatesEntry
    MAX-ACCESS not-accessible
    STATUS     current
    DESCRIPTION
        ""
    INDEX {
        lcsStatusCertsDeviceCertificatesEntryFilename
    }
    ::= { lcsStatusCertsDeviceCertificatesTable 1 }

-- {SEQUENCE}
LcsStatusCertsDeviceCertificatesEntry ::= SEQUENCE {
    lcsStatusCertsDeviceCertificatesEntryFilename DisplayString,
    lcsStatusCertsDeviceCertificatesEntryApplication DisplayString,
    lcsStatusCertsDeviceCertificatesEntryAvailable INTEGER,
    lcsStatusCertsDeviceCertificatesEntryExpires DisplayString,
    lcsStatusCertsDeviceCertificatesEntryIssued DisplayString,
    lcsStatusCertsDeviceCertificatesEntryKeyUsage DisplayString,
    lcsStatusCertsDeviceCertificatesEntryExtendedKeyusage DisplayString,
    lcsStatusCertsDeviceCertificatesEntrySubjectaltname DisplayString,
    lcsStatusCertsDeviceCertificatesEntryIssuer DisplayString,
    lcsStatusCertsDeviceCertificatesEntrySubject DisplayString
}

-- {COLUMN} 310.1.61.4.1.1
lcsStatusCertsDeviceCertificatesEntryFilename OBJECT-TYPE
    SYNTAX     DisplayString (SIZE(0..255))
    MAX-ACCESS read-only
    STATUS     current
    DESCRIPTION
        "-- empty --"
    ::= { lcsStatusCertsDeviceCertificatesEntry 1 }

-- {COLUMN} 310.1.61.4.1.9
lcsStatusCertsDeviceCertificatesEntryApplication OBJECT-TYPE
    SYNTAX     DisplayString (SIZE(0..15))
    MAX-ACCESS read-only
    STATUS     current
    DESCRIPTION
        "-- empty --"
    ::= { lcsStatusCertsDeviceCertificatesEntry 9 }

-- {COLUMN} 310.1.61.4.1.2
lcsStatusCertsDeviceCertificatesEntryAvailable OBJECT-TYPE
    SYNTAX     INTEGER
      {
        eNo (0),
        eYes (1)
      }
    MAX-ACCESS read-only
    STATUS     current
    DESCRIPTION
        "-- empty --"
    ::= { lcsStatusCertsDeviceCertificatesEntry 2 }

-- {COLUMN} 310.1.61.4.1.3
lcsStatusCertsDeviceCertificatesEntryExpires OBJECT-TYPE
    SYNTAX     DisplayString (SIZE(0..20))
    MAX-ACCESS read-only
    STATUS     current
    DESCRIPTION
        "-- empty --"
    ::= { lcsStatusCertsDeviceCertificatesEntry 3 }

-- {COLUMN} 310.1.61.4.1.4
lcsStatusCertsDeviceCertificatesEntryIssued OBJECT-TYPE
    SYNTAX     DisplayString (SIZE(0..20))
    MAX-ACCESS read-only
    STATUS     current
    DESCRIPTION
        "-- empty --"
    ::= { lcsStatusCertsDeviceCertificatesEntry 4 }

-- {COLUMN} 310.1.61.4.1.5
lcsStatusCertsDeviceCertificatesEntryKeyUsage OBJECT-TYPE
    SYNTAX     DisplayString (SIZE(0..251))
    MAX-ACCESS read-only
    STATUS     current
    DESCRIPTION
        "-- empty --"
    ::= { lcsStatusCertsDeviceCertificatesEntry 5 }

-- {COLUMN} 310.1.61.4.1.12
lcsStatusCertsDeviceCertificatesEntryExtendedKeyusage OBJECT-TYPE
    SYNTAX     DisplayString (SIZE(0..251))
    MAX-ACCESS read-only
    STATUS     current
    DESCRIPTION
        "-- empty --"
    ::= { lcsStatusCertsDeviceCertificatesEntry 12 }

-- {COLUMN} 310.1.61.4.1.6
lcsStatusCertsDeviceCertificatesEntrySubjectaltname OBJECT-TYPE
    SYNTAX     DisplayString (SIZE(0..251))
    MAX-ACCESS read-only
    STATUS     current
    DESCRIPTION
        "-- empty --"
    ::= { lcsStatusCertsDeviceCertificatesEntry 6 }

-- {COLUMN} 310.1.61.4.1.7
lcsStatusCertsDeviceCertificatesEntryIssuer OBJECT-TYPE
    SYNTAX     DisplayString (SIZE(0..251))
    MAX-ACCESS read-only
    STATUS     current
    DESCRIPTION
        "-- empty --"
    ::= { lcsStatusCertsDeviceCertificatesEntry 7 }

-- {COLUMN} 310.1.61.4.1.8
lcsStatusCertsDeviceCertificatesEntrySubject OBJECT-TYPE
    SYNTAX     DisplayString (SIZE(0..251))
    MAX-ACCESS read-only
    STATUS     current
    DESCRIPTION
        "-- empty --"
    ::= { lcsStatusCertsDeviceCertificatesEntry 8 }

-- {OID} 310.1.62
lcsStatusVlan OBJECT IDENTIFIER ::= { lcsStatus 62 }

-- {SCALAR} 310.1.62.4
lcsStatusVlanOperating OBJECT-TYPE
    SYNTAX     INTEGER
      {
        eNo (0),
        eYes (1)
      }
    MAX-ACCESS read-only
    STATUS     current
    DESCRIPTION
        "-- empty --"
    ::= { lcsStatusVlan 4 }

-- {TABLE} 310.1.62.1
lcsStatusVlanNetworksTable OBJECT-TYPE
    SYNTAX     SEQUENCE OF LcsStatusVlanNetworksEntry
    MAX-ACCESS not-accessible
    STATUS     current
    DESCRIPTION
        "-- empty --"
    ::= { lcsStatusVlan 1 }

-- {ENTRY} 310.1.62.1.1
lcsStatusVlanNetworksEntry OBJECT-TYPE
    SYNTAX     LcsStatusVlanNetworksEntry
    MAX-ACCESS not-accessible
    STATUS     current
    DESCRIPTION
        ""
    INDEX {
        lcsStatusVlanNetworksEntryVlanId
    }
    ::= { lcsStatusVlanNetworksTable 1 }

-- {SEQUENCE}
LcsStatusVlanNetworksEntry ::= SEQUENCE {
    lcsStatusVlanNetworksEntryVlanId INTEGER,
    lcsStatusVlanNetworksEntryPorts DisplayString
}

-- {COLUMN} 310.1.62.1.1.1
lcsStatusVlanNetworksEntryVlanId OBJECT-TYPE
    SYNTAX     INTEGER (0..65535)
    MAX-ACCESS read-only
    STATUS     current
    DESCRIPTION
        "-- empty --"
    ::= { lcsStatusVlanNetworksEntry 1 }

-- {COLUMN} 310.1.62.1.1.4
lcsStatusVlanNetworksEntryPorts OBJECT-TYPE
    SYNTAX     DisplayString (SIZE(0..255))
    MAX-ACCESS read-only
    STATUS     current
    DESCRIPTION
        "-- empty --"
    ::= { lcsStatusVlanNetworksEntry 4 }

-- {TABLE} 310.1.62.2
lcsStatusVlanPortTableTable OBJECT-TYPE
    SYNTAX     SEQUENCE OF LcsStatusVlanPortTableEntry
    MAX-ACCESS not-accessible
    STATUS     current
    DESCRIPTION
        "-- empty --"
    ::= { lcsStatusVlan 2 }

-- {ENTRY} 310.1.62.2.1
lcsStatusVlanPortTableEntry OBJECT-TYPE
    SYNTAX     LcsStatusVlanPortTableEntry
    MAX-ACCESS not-accessible
    STATUS     current
    DESCRIPTION
        ""
    INDEX {
        lcsStatusVlanPortTableEntryPort
    }
    ::= { lcsStatusVlanPortTableTable 1 }

-- {SEQUENCE}
LcsStatusVlanPortTableEntry ::= SEQUENCE {
    lcsStatusVlanPortTableEntryPort DisplayString,
    lcsStatusVlanPortTableEntryTaggingMode INTEGER,
    lcsStatusVlanPortTableEntryAllowAllVlans INTEGER,
    lcsStatusVlanPortTableEntryPortVlanId INTEGER
}

-- {COLUMN} 310.1.62.2.1.1
lcsStatusVlanPortTableEntryPort OBJECT-TYPE
    SYNTAX     DisplayString (SIZE(0..255))
    MAX-ACCESS read-only
    STATUS     current
    DESCRIPTION
        "-- empty --"
    ::= { lcsStatusVlanPortTableEntry 1 }

-- {COLUMN} 310.1.62.2.1.6
lcsStatusVlanPortTableEntryTaggingMode OBJECT-TYPE
    SYNTAX     INTEGER
      {
        eIngressMixed (0),
        eNever (1),
        eMixed (2),
        eAlways (3)
      }
    MAX-ACCESS read-only
    STATUS     current
    DESCRIPTION
        "-- empty --"
    ::= { lcsStatusVlanPortTableEntry 6 }

-- {COLUMN} 310.1.62.2.1.4
lcsStatusVlanPortTableEntryAllowAllVlans OBJECT-TYPE
    SYNTAX     INTEGER
      {
        eNo (0),
        eYes (1)
      }
    MAX-ACCESS read-only
    STATUS     current
    DESCRIPTION
        "-- empty --"
    ::= { lcsStatusVlanPortTableEntry 4 }

-- {COLUMN} 310.1.62.2.1.5
lcsStatusVlanPortTableEntryPortVlanId OBJECT-TYPE
    SYNTAX     INTEGER (0..65535)
    MAX-ACCESS read-only
    STATUS     current
    DESCRIPTION
        "-- empty --"
    ::= { lcsStatusVlanPortTableEntry 5 }

-- {OID} 310.1.67
lcsStatusComPorts OBJECT IDENTIFIER ::= { lcsStatus 67 }

-- {TABLE} 310.1.67.1
lcsStatusComPortsDevTable OBJECT-TYPE
    SYNTAX     SEQUENCE OF LcsStatusComPortsDevEntry
    MAX-ACCESS not-accessible
    STATUS     current
    DESCRIPTION
        ""
    ::= { lcsStatusComPorts 1 }

-- {ENTRY} 310.1.67.1.1
lcsStatusComPortsDevEntry OBJECT-TYPE
    SYNTAX     LcsStatusComPortsDevEntry
    MAX-ACCESS not-accessible
    STATUS     current
    DESCRIPTION
        ""
    INDEX {
        lcsStatusComPortsDevEntryIndex
    }
    ::= { lcsStatusComPortsDevTable 1 }

-- {SEQUENCE}
LcsStatusComPortsDevEntry ::= SEQUENCE {
    lcsStatusComPortsDevEntryIndex INTEGER,
    lcsStatusComPortsDevEntryDeviceType INTEGER,
    lcsStatusComPortsDevEntryBus INTEGER,
    lcsStatusComPortsDevEntryDevice INTEGER,
    lcsStatusComPortsDevEntryVendor INTEGER,
    lcsStatusComPortsDevEntryUsbDriver INTEGER,
    lcsStatusComPortsDevEntryState INTEGER,
    lcsStatusComPortsDevEntryFirmwareVersion DisplayString,
    lcsStatusComPortsDevEntryServ INTEGER,
    lcsStatusComPortsDevEntryFullName DisplayString
}

-- {COLUMN} 310.1.67.1.1.1
lcsStatusComPortsDevEntryIndex OBJECT-TYPE
    SYNTAX     INTEGER (0..2147483647)
    MAX-ACCESS read-only
    STATUS     current
    DESCRIPTION
        "-- empty --"
    ::= { lcsStatusComPortsDevEntry 1 }

-- {COLUMN} 310.1.67.1.1.2
lcsStatusComPortsDevEntryDeviceType OBJECT-TYPE
    SYNTAX     INTEGER
      {
        eOutbandModem (2),
        eOutband (1)
      }
    MAX-ACCESS read-only
    STATUS     current
    DESCRIPTION
        "-- empty --"
    ::= { lcsStatusComPortsDevEntry 2 }

-- {COLUMN} 310.1.67.1.1.3
lcsStatusComPortsDevEntryBus OBJECT-TYPE
    SYNTAX     INTEGER
      {
        eOutband (1),
        eCardbus (2),
        eUsb (3),
        eVirtual (4)
      }
    MAX-ACCESS read-only
    STATUS     current
    DESCRIPTION
        "-- empty --"
    ::= { lcsStatusComPortsDevEntry 3 }

-- {COLUMN} 310.1.67.1.1.4
lcsStatusComPortsDevEntryDevice OBJECT-TYPE
    SYNTAX     INTEGER (0..65535)
    MAX-ACCESS read-only
    STATUS     current
    DESCRIPTION
        "-- empty --"
    ::= { lcsStatusComPortsDevEntry 4 }

-- {COLUMN} 310.1.67.1.1.5
lcsStatusComPortsDevEntryVendor OBJECT-TYPE
    SYNTAX     INTEGER (0..65535)
    MAX-ACCESS read-only
    STATUS     current
    DESCRIPTION
        "-- empty --"
    ::= { lcsStatusComPortsDevEntry 5 }

-- {COLUMN} 310.1.67.1.1.11
lcsStatusComPortsDevEntryUsbDriver OBJECT-TYPE
    SYNTAX     INTEGER
      {
        eNone (0),
        eUbsa (1),
        eUchcom (2),
        eUftdi (3),
        eUgensa (4),
        eUhmodem (5),
        eUkyopon (6),
        eUplcom (7),
        eUslsa (8),
        eUcdcacm (10)
      }
    MAX-ACCESS read-only
    STATUS     current
    DESCRIPTION
        "-- empty --"
    ::= { lcsStatusComPortsDevEntry 11 }

-- {COLUMN} 310.1.67.1.1.13
lcsStatusComPortsDevEntryState OBJECT-TYPE
    SYNTAX     INTEGER
      {
        eUnknown (0),
        eInitialize (1),
        eWaitForFirmware (2),
        eReady (3),
        eInUse (4),
        eExclusive (5),
        eInitialize2 (6),
        eResetting (7)
      }
    MAX-ACCESS read-only
    STATUS     current
    DESCRIPTION
        "-- empty --"
    ::= { lcsStatusComPortsDevEntry 13 }

-- {COLUMN} 310.1.67.1.1.14
lcsStatusComPortsDevEntryFirmwareVersion OBJECT-TYPE
    SYNTAX     DisplayString (SIZE(0..63))
    MAX-ACCESS read-only
    STATUS     current
    DESCRIPTION
        "-- empty --"
    ::= { lcsStatusComPortsDevEntry 14 }

-- {COLUMN} 310.1.67.1.1.15
lcsStatusComPortsDevEntryServ OBJECT-TYPE
    SYNTAX     INTEGER
      {
        eWan (1),
        eCOMPortServ (2)
      }
    MAX-ACCESS read-only
    STATUS     current
    DESCRIPTION
        ""
    ::= { lcsStatusComPortsDevEntry 15 }

-- {COLUMN} 310.1.67.1.1.99
lcsStatusComPortsDevEntryFullName OBJECT-TYPE
    SYNTAX     DisplayString (SIZE(0..31))
    MAX-ACCESS read-only
    STATUS     current
    DESCRIPTION
        "-- empty --"
    ::= { lcsStatusComPortsDevEntry 99 }

-- {OID} 310.1.67.2
lcsStatusComPortsComPortServer OBJECT IDENTIFIER ::= { lcsStatusComPorts 2 }

-- {TABLE} 310.1.67.2.1
lcsStatusComPortsComPortServerNetworkStatusTable OBJECT-TYPE
    SYNTAX     SEQUENCE OF LcsStatusComPortsComPortServerNetworkStatusEntry
    MAX-ACCESS not-accessible
    STATUS     current
    DESCRIPTION
        "-- empty --"
    ::= { lcsStatusComPortsComPortServer 1 }

-- {ENTRY} 310.1.67.2.1.1
lcsStatusComPortsComPortServerNetworkStatusEntry OBJECT-TYPE
    SYNTAX     LcsStatusComPortsComPortServerNetworkStatusEntry
    MAX-ACCESS not-accessible
    STATUS     current
    DESCRIPTION
        ""
    INDEX {
        lcsStatusComPortsComPortServerNetworkStatusEntryDeviceType,
        lcsStatusComPortsComPortServerNetworkStatusEntryPortNumber
    }
    ::= { lcsStatusComPortsComPortServerNetworkStatusTable 1 }

-- {SEQUENCE}
LcsStatusComPortsComPortServerNetworkStatusEntry ::= SEQUENCE {
    lcsStatusComPortsComPortServerNetworkStatusEntryDeviceType INTEGER,
    lcsStatusComPortsComPortServerNetworkStatusEntryPortNumber INTEGER,
    lcsStatusComPortsComPortServerNetworkStatusEntryFullName DisplayString,
    lcsStatusComPortsComPortServerNetworkStatusEntryConnectionStatus INTEGER,
    lcsStatusComPortsComPortServerNetworkStatusEntryLastError INTEGER,
    lcsStatusComPortsComPortServerNetworkStatusEntryRemoteAddress IpAddress,
    lcsStatusComPortsComPortServerNetworkStatusEntryLocalPort INTEGER,
    lcsStatusComPortsComPortServerNetworkStatusEntryRemotePort INTEGER
}

-- {COLUMN} 310.1.67.2.1.1.1
lcsStatusComPortsComPortServerNetworkStatusEntryDeviceType OBJECT-TYPE
    SYNTAX     INTEGER
      {
        eOutband (1)
      }
    MAX-ACCESS read-only
    STATUS     current
    DESCRIPTION
        "-- empty --"
    ::= { lcsStatusComPortsComPortServerNetworkStatusEntry 1 }

-- {COLUMN} 310.1.67.2.1.1.2
lcsStatusComPortsComPortServerNetworkStatusEntryPortNumber OBJECT-TYPE
    SYNTAX     INTEGER (0..255)
    MAX-ACCESS read-only
    STATUS     current
    DESCRIPTION
        "-- empty --"
    ::= { lcsStatusComPortsComPortServerNetworkStatusEntry 2 }

-- {COLUMN} 310.1.67.2.1.1.99
lcsStatusComPortsComPortServerNetworkStatusEntryFullName OBJECT-TYPE
    SYNTAX     DisplayString (SIZE(0..255))
    MAX-ACCESS read-only
    STATUS     current
    DESCRIPTION
        "-- empty --"
    ::= { lcsStatusComPortsComPortServerNetworkStatusEntry 99 }

-- {COLUMN} 310.1.67.2.1.1.4
lcsStatusComPortsComPortServerNetworkStatusEntryConnectionStatus OBJECT-TYPE
    SYNTAX     INTEGER
      {
        eIdle (0),
        eListening (1),
        eConnecting (2),
        eConnected (3),
        eNotListening (4),
        eConErrBackoff (5)
      }
    MAX-ACCESS read-only
    STATUS     current
    DESCRIPTION
        "-- empty --"
    ::= { lcsStatusComPortsComPortServerNetworkStatusEntry 4 }

-- {COLUMN} 310.1.67.2.1.1.5
lcsStatusComPortsComPortServerNetworkStatusEntryLastError OBJECT-TYPE
    SYNTAX     INTEGER
      {
        eNone (0),
        eDnsError (1),
        eTCPConnErr (2),
        eRemDisc (3)
      }
    MAX-ACCESS read-only
    STATUS     current
    DESCRIPTION
        "-- empty --"
    ::= { lcsStatusComPortsComPortServerNetworkStatusEntry 5 }

-- {COLUMN} 310.1.67.2.1.1.6
lcsStatusComPortsComPortServerNetworkStatusEntryRemoteAddress OBJECT-TYPE
    SYNTAX     IpAddress
    MAX-ACCESS read-only
    STATUS     current
    DESCRIPTION
        "-- empty --"
    ::= { lcsStatusComPortsComPortServerNetworkStatusEntry 6 }

-- {COLUMN} 310.1.67.2.1.1.7
lcsStatusComPortsComPortServerNetworkStatusEntryLocalPort OBJECT-TYPE
    SYNTAX     INTEGER (0..65535)
    MAX-ACCESS read-only
    STATUS     current
    DESCRIPTION
        "-- empty --"
    ::= { lcsStatusComPortsComPortServerNetworkStatusEntry 7 }

-- {COLUMN} 310.1.67.2.1.1.8
lcsStatusComPortsComPortServerNetworkStatusEntryRemotePort OBJECT-TYPE
    SYNTAX     INTEGER (0..65535)
    MAX-ACCESS read-only
    STATUS     current
    DESCRIPTION
        "-- empty --"
    ::= { lcsStatusComPortsComPortServerNetworkStatusEntry 8 }

-- {TABLE} 310.1.67.2.2
lcsStatusComPortsComPortServerComPortStatusTable OBJECT-TYPE
    SYNTAX     SEQUENCE OF LcsStatusComPortsComPortServerComPortStatusEntry
    MAX-ACCESS not-accessible
    STATUS     current
    DESCRIPTION
        "-- empty --"
    ::= { lcsStatusComPortsComPortServer 2 }

-- {ENTRY} 310.1.67.2.2.1
lcsStatusComPortsComPortServerComPortStatusEntry OBJECT-TYPE
    SYNTAX     LcsStatusComPortsComPortServerComPortStatusEntry
    MAX-ACCESS not-accessible
    STATUS     current
    DESCRIPTION
        ""
    INDEX {
        lcsStatusComPortsComPortServerComPortStatusEntryDeviceType,
        lcsStatusComPortsComPortServerComPortStatusEntryPortNumber
    }
    ::= { lcsStatusComPortsComPortServerComPortStatusTable 1 }

-- {SEQUENCE}
LcsStatusComPortsComPortServerComPortStatusEntry ::= SEQUENCE {
    lcsStatusComPortsComPortServerComPortStatusEntryDeviceType INTEGER,
    lcsStatusComPortsComPortServerComPortStatusEntryPortNumber INTEGER,
    lcsStatusComPortsComPortServerComPortStatusEntryFullName DisplayString,
    lcsStatusComPortsComPortServerComPortStatusEntryInterfaceStatus INTEGER,
    lcsStatusComPortsComPortServerComPortStatusEntryBitRate INTEGER,
    lcsStatusComPortsComPortServerComPortStatusEntryDataBits INTEGER,
    lcsStatusComPortsComPortServerComPortStatusEntryParity INTEGER,
    lcsStatusComPortsComPortServerComPortStatusEntryStopBits INTEGER,
    lcsStatusComPortsComPortServerComPortStatusEntryHandshake INTEGER
}

-- {COLUMN} 310.1.67.2.2.1.1
lcsStatusComPortsComPortServerComPortStatusEntryDeviceType OBJECT-TYPE
    SYNTAX     INTEGER
      {
        eOutband (1)
      }
    MAX-ACCESS read-only
    STATUS     current
    DESCRIPTION
        "-- empty --"
    ::= { lcsStatusComPortsComPortServerComPortStatusEntry 1 }

-- {COLUMN} 310.1.67.2.2.1.2
lcsStatusComPortsComPortServerComPortStatusEntryPortNumber OBJECT-TYPE
    SYNTAX     INTEGER (0..255)
    MAX-ACCESS read-only
    STATUS     current
    DESCRIPTION
        "-- empty --"
    ::= { lcsStatusComPortsComPortServerComPortStatusEntry 2 }

-- {COLUMN} 310.1.67.2.2.1.99
lcsStatusComPortsComPortServerComPortStatusEntryFullName OBJECT-TYPE
    SYNTAX     DisplayString (SIZE(0..255))
    MAX-ACCESS read-only
    STATUS     current
    DESCRIPTION
        "-- empty --"
    ::= { lcsStatusComPortsComPortServerComPortStatusEntry 99 }

-- {COLUMN} 310.1.67.2.2.1.4
lcsStatusComPortsComPortServerComPortStatusEntryInterfaceStatus OBJECT-TYPE
    SYNTAX     INTEGER
      {
        eNotPresent (0),
        eNotReady (1),
        eReady (2)
      }
    MAX-ACCESS read-only
    STATUS     current
    DESCRIPTION
        "-- empty --"
    ::= { lcsStatusComPortsComPortServerComPortStatusEntry 4 }

-- {COLUMN} 310.1.67.2.2.1.5
lcsStatusComPortsComPortServerComPortStatusEntryBitRate OBJECT-TYPE
    SYNTAX     INTEGER
      {
        e110 (110),
        e300 (300),
        e600 (600),
        e1200 (1200),
        e2400 (2400),
        e4800 (4800),
        e9600 (9600),
        e19200 (19200),
        e38400 (38400),
        e57600 (57600),
        e115200 (115200),
        e125000 (125000),
        e230400 (230400)
      }
    MAX-ACCESS read-only
    STATUS     current
    DESCRIPTION
        "-- empty --"
    ::= { lcsStatusComPortsComPortServerComPortStatusEntry 5 }

-- {COLUMN} 310.1.67.2.2.1.6
lcsStatusComPortsComPortServerComPortStatusEntryDataBits OBJECT-TYPE
    SYNTAX     INTEGER
      {
        e7 (7),
        e8 (8)
      }
    MAX-ACCESS read-only
    STATUS     current
    DESCRIPTION
        "-- empty --"
    ::= { lcsStatusComPortsComPortServerComPortStatusEntry 6 }

-- {COLUMN} 310.1.67.2.2.1.7
lcsStatusComPortsComPortServerComPortStatusEntryParity OBJECT-TYPE
    SYNTAX     INTEGER
      {
        eNone (1),
        eOdd (2),
        eEven (3)
      }
    MAX-ACCESS read-only
    STATUS     current
    DESCRIPTION
        "-- empty --"
    ::= { lcsStatusComPortsComPortServerComPortStatusEntry 7 }

-- {COLUMN} 310.1.67.2.2.1.8
lcsStatusComPortsComPortServerComPortStatusEntryStopBits OBJECT-TYPE
    SYNTAX     INTEGER
      {
        e1 (1),
        e2 (2)
      }
    MAX-ACCESS read-only
    STATUS     current
    DESCRIPTION
        "-- empty --"
    ::= { lcsStatusComPortsComPortServerComPortStatusEntry 8 }

-- {COLUMN} 310.1.67.2.2.1.9
lcsStatusComPortsComPortServerComPortStatusEntryHandshake OBJECT-TYPE
    SYNTAX     INTEGER
      {
        eNone (0),
        eRtsCts (1)
      }
    MAX-ACCESS read-only
    STATUS     current
    DESCRIPTION
        "-- empty --"
    ::= { lcsStatusComPortsComPortServerComPortStatusEntry 9 }

-- {TABLE} 310.1.67.2.3
lcsStatusComPortsComPortServerByteCountersTable OBJECT-TYPE
    SYNTAX     SEQUENCE OF LcsStatusComPortsComPortServerByteCountersEntry
    MAX-ACCESS not-accessible
    STATUS     current
    DESCRIPTION
        "-- empty --"
    ::= { lcsStatusComPortsComPortServer 3 }

-- {ENTRY} 310.1.67.2.3.1
lcsStatusComPortsComPortServerByteCountersEntry OBJECT-TYPE
    SYNTAX     LcsStatusComPortsComPortServerByteCountersEntry
    MAX-ACCESS not-accessible
    STATUS     current
    DESCRIPTION
        ""
    INDEX {
        lcsStatusComPortsComPortServerByteCountersEntryDeviceType,
        lcsStatusComPortsComPortServerByteCountersEntryPortNumber
    }
    ::= { lcsStatusComPortsComPortServerByteCountersTable 1 }

-- {SEQUENCE}
LcsStatusComPortsComPortServerByteCountersEntry ::= SEQUENCE {
    lcsStatusComPortsComPortServerByteCountersEntryDeviceType INTEGER,
    lcsStatusComPortsComPortServerByteCountersEntryPortNumber INTEGER,
    lcsStatusComPortsComPortServerByteCountersEntryFullName DisplayString,
    lcsStatusComPortsComPortServerByteCountersEntrySerialTx INTEGER,
    lcsStatusComPortsComPortServerByteCountersEntrySerialRx INTEGER,
    lcsStatusComPortsComPortServerByteCountersEntryNetworkTx INTEGER,
    lcsStatusComPortsComPortServerByteCountersEntryNetworkRx INTEGER
}

-- {COLUMN} 310.1.67.2.3.1.1
lcsStatusComPortsComPortServerByteCountersEntryDeviceType OBJECT-TYPE
    SYNTAX     INTEGER
      {
        eOutband (1)
      }
    MAX-ACCESS read-only
    STATUS     current
    DESCRIPTION
        "-- empty --"
    ::= { lcsStatusComPortsComPortServerByteCountersEntry 1 }

-- {COLUMN} 310.1.67.2.3.1.2
lcsStatusComPortsComPortServerByteCountersEntryPortNumber OBJECT-TYPE
    SYNTAX     INTEGER (0..255)
    MAX-ACCESS read-only
    STATUS     current
    DESCRIPTION
        "-- empty --"
    ::= { lcsStatusComPortsComPortServerByteCountersEntry 2 }

-- {COLUMN} 310.1.67.2.3.1.99
lcsStatusComPortsComPortServerByteCountersEntryFullName OBJECT-TYPE
    SYNTAX     DisplayString (SIZE(0..255))
    MAX-ACCESS read-only
    STATUS     current
    DESCRIPTION
        "-- empty --"
    ::= { lcsStatusComPortsComPortServerByteCountersEntry 99 }

-- {COLUMN} 310.1.67.2.3.1.4
lcsStatusComPortsComPortServerByteCountersEntrySerialTx OBJECT-TYPE
    SYNTAX     INTEGER (0..2147483647)
    MAX-ACCESS read-only
    STATUS     current
    DESCRIPTION
        "-- empty --"
    ::= { lcsStatusComPortsComPortServerByteCountersEntry 4 }

-- {COLUMN} 310.1.67.2.3.1.5
lcsStatusComPortsComPortServerByteCountersEntrySerialRx OBJECT-TYPE
    SYNTAX     INTEGER (0..2147483647)
    MAX-ACCESS read-only
    STATUS     current
    DESCRIPTION
        "-- empty --"
    ::= { lcsStatusComPortsComPortServerByteCountersEntry 5 }

-- {COLUMN} 310.1.67.2.3.1.6
lcsStatusComPortsComPortServerByteCountersEntryNetworkTx OBJECT-TYPE
    SYNTAX     INTEGER (0..2147483647)
    MAX-ACCESS read-only
    STATUS     current
    DESCRIPTION
        "-- empty --"
    ::= { lcsStatusComPortsComPortServerByteCountersEntry 6 }

-- {COLUMN} 310.1.67.2.3.1.7
lcsStatusComPortsComPortServerByteCountersEntryNetworkRx OBJECT-TYPE
    SYNTAX     INTEGER (0..2147483647)
    MAX-ACCESS read-only
    STATUS     current
    DESCRIPTION
        "-- empty --"
    ::= { lcsStatusComPortsComPortServerByteCountersEntry 7 }

-- {TABLE} 310.1.67.2.4
lcsStatusComPortsComPortServerComPortErrorsTable OBJECT-TYPE
    SYNTAX     SEQUENCE OF LcsStatusComPortsComPortServerComPortErrorsEntry
    MAX-ACCESS not-accessible
    STATUS     current
    DESCRIPTION
        "-- empty --"
    ::= { lcsStatusComPortsComPortServer 4 }

-- {ENTRY} 310.1.67.2.4.1
lcsStatusComPortsComPortServerComPortErrorsEntry OBJECT-TYPE
    SYNTAX     LcsStatusComPortsComPortServerComPortErrorsEntry
    MAX-ACCESS not-accessible
    STATUS     current
    DESCRIPTION
        ""
    INDEX {
        lcsStatusComPortsComPortServerComPortErrorsEntryDeviceType,
        lcsStatusComPortsComPortServerComPortErrorsEntryPortNumber
    }
    ::= { lcsStatusComPortsComPortServerComPortErrorsTable 1 }

-- {SEQUENCE}
LcsStatusComPortsComPortServerComPortErrorsEntry ::= SEQUENCE {
    lcsStatusComPortsComPortServerComPortErrorsEntryDeviceType INTEGER,
    lcsStatusComPortsComPortServerComPortErrorsEntryPortNumber INTEGER,
    lcsStatusComPortsComPortServerComPortErrorsEntryFullName DisplayString,
    lcsStatusComPortsComPortServerComPortErrorsEntryParityErrors INTEGER,
    lcsStatusComPortsComPortServerComPortErrorsEntryFramingErrors INTEGER,
    lcsStatusComPortsComPortServerComPortErrorsEntryRxLostErrors INTEGER
}

-- {COLUMN} 310.1.67.2.4.1.1
lcsStatusComPortsComPortServerComPortErrorsEntryDeviceType OBJECT-TYPE
    SYNTAX     INTEGER
      {
        eOutband (1)
      }
    MAX-ACCESS read-only
    STATUS     current
    DESCRIPTION
        "-- empty --"
    ::= { lcsStatusComPortsComPortServerComPortErrorsEntry 1 }

-- {COLUMN} 310.1.67.2.4.1.2
lcsStatusComPortsComPortServerComPortErrorsEntryPortNumber OBJECT-TYPE
    SYNTAX     INTEGER (0..255)
    MAX-ACCESS read-only
    STATUS     current
    DESCRIPTION
        "-- empty --"
    ::= { lcsStatusComPortsComPortServerComPortErrorsEntry 2 }

-- {COLUMN} 310.1.67.2.4.1.99
lcsStatusComPortsComPortServerComPortErrorsEntryFullName OBJECT-TYPE
    SYNTAX     DisplayString (SIZE(0..255))
    MAX-ACCESS read-only
    STATUS     current
    DESCRIPTION
        "-- empty --"
    ::= { lcsStatusComPortsComPortServerComPortErrorsEntry 99 }

-- {COLUMN} 310.1.67.2.4.1.4
lcsStatusComPortsComPortServerComPortErrorsEntryParityErrors OBJECT-TYPE
    SYNTAX     INTEGER (0..2147483647)
    MAX-ACCESS read-only
    STATUS     current
    DESCRIPTION
        "-- empty --"
    ::= { lcsStatusComPortsComPortServerComPortErrorsEntry 4 }

-- {COLUMN} 310.1.67.2.4.1.5
lcsStatusComPortsComPortServerComPortErrorsEntryFramingErrors OBJECT-TYPE
    SYNTAX     INTEGER (0..2147483647)
    MAX-ACCESS read-only
    STATUS     current
    DESCRIPTION
        "-- empty --"
    ::= { lcsStatusComPortsComPortServerComPortErrorsEntry 5 }

-- {COLUMN} 310.1.67.2.4.1.6
lcsStatusComPortsComPortServerComPortErrorsEntryRxLostErrors OBJECT-TYPE
    SYNTAX     INTEGER (0..2147483647)
    MAX-ACCESS read-only
    STATUS     current
    DESCRIPTION
        "-- empty --"
    ::= { lcsStatusComPortsComPortServerComPortErrorsEntry 6 }

-- {TABLE} 310.1.67.2.5
lcsStatusComPortsComPortServerConnTable OBJECT-TYPE
    SYNTAX     SEQUENCE OF LcsStatusComPortsComPortServerConnEntry
    MAX-ACCESS not-accessible
    STATUS     current
    DESCRIPTION
        ""
    ::= { lcsStatusComPortsComPortServer 5 }

-- {ENTRY} 310.1.67.2.5.1
lcsStatusComPortsComPortServerConnEntry OBJECT-TYPE
    SYNTAX     LcsStatusComPortsComPortServerConnEntry
    MAX-ACCESS not-accessible
    STATUS     current
    DESCRIPTION
        ""
    INDEX {
        lcsStatusComPortsComPortServerConnEntryDeviceType,
        lcsStatusComPortsComPortServerConnEntryPortNumber
    }
    ::= { lcsStatusComPortsComPortServerConnTable 1 }

-- {SEQUENCE}
LcsStatusComPortsComPortServerConnEntry ::= SEQUENCE {
    lcsStatusComPortsComPortServerConnEntryDeviceType INTEGER,
    lcsStatusComPortsComPortServerConnEntryPortNumber INTEGER,
    lcsStatusComPortsComPortServerConnEntryFullName DisplayString,
    lcsStatusComPortsComPortServerConnEntryServGrant INTEGER,
    lcsStatusComPortsComPortServerConnEntryServRej INTEGER,
    lcsStatusComPortsComPortServerConnEntryClntSucc INTEGER,
    lcsStatusComPortsComPortServerConnEntryClntDnsErr INTEGER,
    lcsStatusComPortsComPortServerConnEntryClntTcpErr INTEGER,
    lcsStatusComPortsComPortServerConnEntryClntRemDisc INTEGER
}

-- {COLUMN} 310.1.67.2.5.1.1
lcsStatusComPortsComPortServerConnEntryDeviceType OBJECT-TYPE
    SYNTAX     INTEGER
      {
        eOutband (1)
      }
    MAX-ACCESS read-only
    STATUS     current
    DESCRIPTION
        "-- empty --"
    ::= { lcsStatusComPortsComPortServerConnEntry 1 }

-- {COLUMN} 310.1.67.2.5.1.2
lcsStatusComPortsComPortServerConnEntryPortNumber OBJECT-TYPE
    SYNTAX     INTEGER (0..255)
    MAX-ACCESS read-only
    STATUS     current
    DESCRIPTION
        "-- empty --"
    ::= { lcsStatusComPortsComPortServerConnEntry 2 }

-- {COLUMN} 310.1.67.2.5.1.99
lcsStatusComPortsComPortServerConnEntryFullName OBJECT-TYPE
    SYNTAX     DisplayString (SIZE(0..255))
    MAX-ACCESS read-only
    STATUS     current
    DESCRIPTION
        "-- empty --"
    ::= { lcsStatusComPortsComPortServerConnEntry 99 }

-- {COLUMN} 310.1.67.2.5.1.4
lcsStatusComPortsComPortServerConnEntryServGrant OBJECT-TYPE
    SYNTAX     INTEGER (0..2147483647)
    MAX-ACCESS read-only
    STATUS     current
    DESCRIPTION
        ""
    ::= { lcsStatusComPortsComPortServerConnEntry 4 }

-- {COLUMN} 310.1.67.2.5.1.5
lcsStatusComPortsComPortServerConnEntryServRej OBJECT-TYPE
    SYNTAX     INTEGER (0..2147483647)
    MAX-ACCESS read-only
    STATUS     current
    DESCRIPTION
        ""
    ::= { lcsStatusComPortsComPortServerConnEntry 5 }

-- {COLUMN} 310.1.67.2.5.1.6
lcsStatusComPortsComPortServerConnEntryClntSucc OBJECT-TYPE
    SYNTAX     INTEGER (0..2147483647)
    MAX-ACCESS read-only
    STATUS     current
    DESCRIPTION
        ""
    ::= { lcsStatusComPortsComPortServerConnEntry 6 }

-- {COLUMN} 310.1.67.2.5.1.7
lcsStatusComPortsComPortServerConnEntryClntDnsErr OBJECT-TYPE
    SYNTAX     INTEGER (0..2147483647)
    MAX-ACCESS read-only
    STATUS     current
    DESCRIPTION
        ""
    ::= { lcsStatusComPortsComPortServerConnEntry 7 }

-- {COLUMN} 310.1.67.2.5.1.8
lcsStatusComPortsComPortServerConnEntryClntTcpErr OBJECT-TYPE
    SYNTAX     INTEGER (0..2147483647)
    MAX-ACCESS read-only
    STATUS     current
    DESCRIPTION
        ""
    ::= { lcsStatusComPortsComPortServerConnEntry 8 }

-- {COLUMN} 310.1.67.2.5.1.9
lcsStatusComPortsComPortServerConnEntryClntRemDisc OBJECT-TYPE
    SYNTAX     INTEGER (0..2147483647)
    MAX-ACCESS read-only
    STATUS     current
    DESCRIPTION
        ""
    ::= { lcsStatusComPortsComPortServerConnEntry 9 }

-- {SCALAR} 310.1.67.2.99
lcsStatusComPortsComPortServerDeleteValues OBJECT-TYPE
    SYNTAX     DisplayString
    MAX-ACCESS read-write
    STATUS     current
    DESCRIPTION
        "-- empty --"
    ::= { lcsStatusComPortsComPortServer 99 }

-- {OID} 310.1.69
lcsStatusTacacsPlus OBJECT IDENTIFIER ::= { lcsStatus 69 }

-- {SCALAR} 310.1.69.1
lcsStatusTacacsPlusAuthenticationErrors OBJECT-TYPE
    SYNTAX     Counter32
    MAX-ACCESS read-only
    STATUS     current
    DESCRIPTION
        "-- empty --"
    ::= { lcsStatusTacacsPlus 1 }

-- {SCALAR} 310.1.69.2
lcsStatusTacacsPlusAuthorisationErrors OBJECT-TYPE
    SYNTAX     Counter32
    MAX-ACCESS read-only
    STATUS     current
    DESCRIPTION
        "-- empty --"
    ::= { lcsStatusTacacsPlus 2 }

-- {SCALAR} 310.1.69.3
lcsStatusTacacsPlusDeleteValues OBJECT-TYPE
    SYNTAX     DisplayString
    MAX-ACCESS read-write
    STATUS     current
    DESCRIPTION
        "-- empty --"
    ::= { lcsStatusTacacsPlus 3 }

-- {OID} 310.1.70
lcsStatusTemperatureMonitor OBJECT IDENTIFIER ::= { lcsStatus 70 }

-- {TABLE} 310.1.70.1
lcsStatusTemperatureMonitorExtremesTable OBJECT-TYPE
    SYNTAX     SEQUENCE OF LcsStatusTemperatureMonitorExtremesEntry
    MAX-ACCESS not-accessible
    STATUS     current
    DESCRIPTION
        "-- empty --"
    ::= { lcsStatusTemperatureMonitor 1 }

-- {ENTRY} 310.1.70.1.1
lcsStatusTemperatureMonitorExtremesEntry OBJECT-TYPE
    SYNTAX     LcsStatusTemperatureMonitorExtremesEntry
    MAX-ACCESS not-accessible
    STATUS     current
    DESCRIPTION
        ""
    INDEX {
        lcsStatusTemperatureMonitorExtremesEntryType
    }
    ::= { lcsStatusTemperatureMonitorExtremesTable 1 }

-- {SEQUENCE}
LcsStatusTemperatureMonitorExtremesEntry ::= SEQUENCE {
    lcsStatusTemperatureMonitorExtremesEntryType INTEGER,
    lcsStatusTemperatureMonitorExtremesEntryValue INTEGER,
    lcsStatusTemperatureMonitorExtremesEntryTime DisplayString
}

-- {COLUMN} 310.1.70.1.1.1
lcsStatusTemperatureMonitorExtremesEntryType OBJECT-TYPE
    SYNTAX     INTEGER
      {
        eMinimum1 (1),
        eMaximum1 (2),
        eMinimum2 (257),
        eMaximum2 (258),
        eMinimum3 (513),
        eMaximum3 (514),
        eMinimum4 (769),
        eMaximum4 (770),
        eMinimum5 (1025),
        eMaximum5 (1026),
        eMinimum6 (1281),
        eMaximum6 (1282),
        eMinimum7 (1537),
        eMaximum7 (1538),
        eMinimum8 (1793),
        eMaximum8 (1794)
      }
    MAX-ACCESS read-only
    STATUS     current
    DESCRIPTION
        "-- empty --"
    ::= { lcsStatusTemperatureMonitorExtremesEntry 1 }

-- {COLUMN} 310.1.70.1.1.2
lcsStatusTemperatureMonitorExtremesEntryValue OBJECT-TYPE
    SYNTAX     INTEGER (-32768..32767)
    MAX-ACCESS read-only
    STATUS     current
    DESCRIPTION
        "-- empty --"
    ::= { lcsStatusTemperatureMonitorExtremesEntry 2 }

-- {COLUMN} 310.1.70.1.1.3
lcsStatusTemperatureMonitorExtremesEntryTime OBJECT-TYPE
    SYNTAX     DisplayString (SIZE(0..255))
    MAX-ACCESS read-only
    STATUS     current
    DESCRIPTION
        "-- empty --"
    ::= { lcsStatusTemperatureMonitorExtremesEntry 3 }

-- {SCALAR} 310.1.100
lcsStatusDeleteValues OBJECT-TYPE
    SYNTAX     DisplayString
    MAX-ACCESS read-write
    STATUS     current
    DESCRIPTION
        "-- empty --"
    ::= { lcsStatus 100 }

-- {OID} 310.2
lcsSetup OBJECT IDENTIFIER ::= { lancom-l310 2 }

-- {SCALAR} 310.2.1
lcsSetupName OBJECT-TYPE
    SYNTAX     DisplayString (SIZE(0..16))
    MAX-ACCESS read-only
    STATUS     current
    DESCRIPTION
        "-- empty --"
    ::= { lcsSetup 1 }

-- {OID} 310.2.2
lcsSetupWan OBJECT IDENTIFIER ::= { lcsSetup 2 }

-- {TABLE} 310.2.2.2
lcsSetupWanDialupPeersTable OBJECT-TYPE
    SYNTAX     SEQUENCE OF LcsSetupWanDialupPeersEntry
    MAX-ACCESS not-accessible
    STATUS     current
    DESCRIPTION
        "-- empty --"
    ::= { lcsSetupWan 2 }

-- {ENTRY} 310.2.2.2.1
lcsSetupWanDialupPeersEntry OBJECT-TYPE
    SYNTAX     LcsSetupWanDialupPeersEntry
    MAX-ACCESS not-accessible
    STATUS     current
    DESCRIPTION
        ""
    INDEX {
        lcsSetupWanDialupPeersEntryPeer
    }
    ::= { lcsSetupWanDialupPeersTable 1 }

-- {SEQUENCE}
LcsSetupWanDialupPeersEntry ::= SEQUENCE {
    lcsSetupWanDialupPeersEntryPeer DisplayString,
    lcsSetupWanDialupPeersEntryDialupRemote DisplayString,
    lcsSetupWanDialupPeersEntryB1Dt INTEGER,
    lcsSetupWanDialupPeersEntryB2Dt INTEGER,
    lcsSetupWanDialupPeersEntryWanLayer DisplayString,
    lcsSetupWanDialupPeersEntryCallback INTEGER
}

-- {COLUMN} 310.2.2.2.1.1
lcsSetupWanDialupPeersEntryPeer OBJECT-TYPE
    SYNTAX     DisplayString (SIZE(0..16))
    MAX-ACCESS read-write
    STATUS     current
    DESCRIPTION
        "-- empty --"
    ::= { lcsSetupWanDialupPeersEntry 1 }

-- {COLUMN} 310.2.2.2.1.2
lcsSetupWanDialupPeersEntryDialupRemote OBJECT-TYPE
    SYNTAX     DisplayString (SIZE(0..31))
    MAX-ACCESS read-write
    STATUS     current
    DESCRIPTION
        "-- empty --"
    ::= { lcsSetupWanDialupPeersEntry 2 }

-- {COLUMN} 310.2.2.2.1.3
lcsSetupWanDialupPeersEntryB1Dt OBJECT-TYPE
    SYNTAX     INTEGER (0..65535)
    MAX-ACCESS read-write
    STATUS     current
    DESCRIPTION
        "-- empty --"
    ::= { lcsSetupWanDialupPeersEntry 3 }

-- {COLUMN} 310.2.2.2.1.4
lcsSetupWanDialupPeersEntryB2Dt OBJECT-TYPE
    SYNTAX     INTEGER (0..65535)
    MAX-ACCESS read-write
    STATUS     current
    DESCRIPTION
        "-- empty --"
    ::= { lcsSetupWanDialupPeersEntry 4 }

-- {COLUMN} 310.2.2.2.1.5
lcsSetupWanDialupPeersEntryWanLayer OBJECT-TYPE
    SYNTAX     DisplayString (SIZE(0..9))
    MAX-ACCESS read-write
    STATUS     current
    DESCRIPTION
        "-- empty --"
    ::= { lcsSetupWanDialupPeersEntry 5 }

-- {COLUMN} 310.2.2.2.1.6
lcsSetupWanDialupPeersEntryCallback OBJECT-TYPE
    SYNTAX     INTEGER
      {
        eNo (0),
        eAuto (1),
        eName (5),
        eFast (9),
        eLooser (2)
      }
    MAX-ACCESS read-write
    STATUS     current
    DESCRIPTION
        "-- empty --"
    ::= { lcsSetupWanDialupPeersEntry 6 }

-- {TABLE} 310.2.2.3
lcsSetupWanRoundrobinTable OBJECT-TYPE
    SYNTAX     SEQUENCE OF LcsSetupWanRoundrobinEntry
    MAX-ACCESS not-accessible
    STATUS     current
    DESCRIPTION
        "-- empty --"
    ::= { lcsSetupWan 3 }

-- {ENTRY} 310.2.2.3.1
lcsSetupWanRoundrobinEntry OBJECT-TYPE
    SYNTAX     LcsSetupWanRoundrobinEntry
    MAX-ACCESS not-accessible
    STATUS     current
    DESCRIPTION
        ""
    INDEX {
        lcsSetupWanRoundrobinEntryPeer
    }
    ::= { lcsSetupWanRoundrobinTable 1 }

-- {SEQUENCE}
LcsSetupWanRoundrobinEntry ::= SEQUENCE {
    lcsSetupWanRoundrobinEntryPeer DisplayString,
    lcsSetupWanRoundrobinEntryRoundRobin DisplayString,
    lcsSetupWanRoundrobinEntryHead INTEGER
}

-- {COLUMN} 310.2.2.3.1.1
lcsSetupWanRoundrobinEntryPeer OBJECT-TYPE
    SYNTAX     DisplayString (SIZE(0..18))
    MAX-ACCESS read-write
    STATUS     current
    DESCRIPTION
        "-- empty --"
    ::= { lcsSetupWanRoundrobinEntry 1 }

-- {COLUMN} 310.2.2.3.1.2
lcsSetupWanRoundrobinEntryRoundRobin OBJECT-TYPE
    SYNTAX     DisplayString (SIZE(0..53))
    MAX-ACCESS read-write
    STATUS     current
    DESCRIPTION
        "-- empty --"
    ::= { lcsSetupWanRoundrobinEntry 2 }

-- {COLUMN} 310.2.2.3.1.3
lcsSetupWanRoundrobinEntryHead OBJECT-TYPE
    SYNTAX     INTEGER
      {
        eLast (0),
        eFirst (1)
      }
    MAX-ACCESS read-write
    STATUS     current
    DESCRIPTION
        "-- empty --"
    ::= { lcsSetupWanRoundrobinEntry 3 }

-- {TABLE} 310.2.2.4
lcsSetupWanLayerTable OBJECT-TYPE
    SYNTAX     SEQUENCE OF LcsSetupWanLayerEntry
    MAX-ACCESS not-accessible
    STATUS     current
    DESCRIPTION
        "-- empty --"
    ::= { lcsSetupWan 4 }

-- {ENTRY} 310.2.2.4.1
lcsSetupWanLayerEntry OBJECT-TYPE
    SYNTAX     LcsSetupWanLayerEntry
    MAX-ACCESS not-accessible
    STATUS     current
    DESCRIPTION
        ""
    INDEX {
        lcsSetupWanLayerEntryWanLayer
    }
    ::= { lcsSetupWanLayerTable 1 }

-- {SEQUENCE}
LcsSetupWanLayerEntry ::= SEQUENCE {
    lcsSetupWanLayerEntryWanLayer DisplayString,
    lcsSetupWanLayerEntryEncaps INTEGER,
    lcsSetupWanLayerEntryLay3 INTEGER,
    lcsSetupWanLayerEntryLay2 INTEGER,
    lcsSetupWanLayerEntryL2Opt INTEGER,
    lcsSetupWanLayerEntryLay1 INTEGER
}

-- {COLUMN} 310.2.2.4.1.1
lcsSetupWanLayerEntryWanLayer OBJECT-TYPE
    SYNTAX     DisplayString (SIZE(0..9))
    MAX-ACCESS read-write
    STATUS     current
    DESCRIPTION
        "-- empty --"
    ::= { lcsSetupWanLayerEntry 1 }

-- {COLUMN} 310.2.2.4.1.2
lcsSetupWanLayerEntryEncaps OBJECT-TYPE
    SYNTAX     INTEGER
      {
        eEther (0),
        eTrans (255)
      }
    MAX-ACCESS read-write
    STATUS     current
    DESCRIPTION
        "-- empty --"
    ::= { lcsSetupWanLayerEntry 2 }

-- {COLUMN} 310.2.2.4.1.3
lcsSetupWanLayerEntryLay3 OBJECT-TYPE
    SYNTAX     INTEGER
      {
        ePpp (4),
        eAppp (5),
        eScppp (6),
        eScappp (7),
        eSctrans (8),
        eDhcp (9),
        eTRANS (255)
      }
    MAX-ACCESS read-write
    STATUS     current
    DESCRIPTION
        "-- empty --"
    ::= { lcsSetupWanLayerEntry 3 }

-- {COLUMN} 310.2.2.4.1.4
lcsSetupWanLayerEntryLay2 OBJECT-TYPE
    SYNTAX     INTEGER
      {
        ePppoe (5),
        eTrans (1)
      }
    MAX-ACCESS read-write
    STATUS     current
    DESCRIPTION
        "-- empty --"
    ::= { lcsSetupWanLayerEntry 4 }

-- {COLUMN} 310.2.2.4.1.5
lcsSetupWanLayerEntryL2Opt OBJECT-TYPE
    SYNTAX     INTEGER
      {
        eNone (255),
        eCompr (0)
      }
    MAX-ACCESS read-write
    STATUS     current
    DESCRIPTION
        "-- empty --"
    ::= { lcsSetupWanLayerEntry 5 }

-- {COLUMN} 310.2.2.4.1.6
lcsSetupWanLayerEntryLay1 OBJECT-TYPE
    SYNTAX     INTEGER
      {
        eEth (4),
        eSerial (6)
      }
    MAX-ACCESS read-write
    STATUS     current
    DESCRIPTION
        "-- empty --"
    ::= { lcsSetupWanLayerEntry 6 }

-- {TABLE} 310.2.2.5
lcsSetupWanPppTable OBJECT-TYPE
    SYNTAX     SEQUENCE OF LcsSetupWanPppEntry
    MAX-ACCESS not-accessible
    STATUS     current
    DESCRIPTION
        "-- empty --"
    ::= { lcsSetupWan 5 }

-- {ENTRY} 310.2.2.5.1
lcsSetupWanPppEntry OBJECT-TYPE
    SYNTAX     LcsSetupWanPppEntry
    MAX-ACCESS not-accessible
    STATUS     current
    DESCRIPTION
        ""
    INDEX {
        lcsSetupWanPppEntryPeer
    }
    ::= { lcsSetupWanPppTable 1 }

-- {SEQUENCE}
LcsSetupWanPppEntry ::= SEQUENCE {
    lcsSetupWanPppEntryPeer DisplayString,
    lcsSetupWanPppEntryAuthentRequest BITS,
    lcsSetupWanPppEntryAuthentResponse BITS,
    lcsSetupWanPppEntryKey DisplayString,
    lcsSetupWanPppEntryTime INTEGER,
    lcsSetupWanPppEntryTry INTEGER,
    lcsSetupWanPppEntryConf INTEGER,
    lcsSetupWanPppEntryFail INTEGER,
    lcsSetupWanPppEntryTerm INTEGER,
    lcsSetupWanPppEntryUsername DisplayString,
    lcsSetupWanPppEntryRights BITS
}

-- {COLUMN} 310.2.2.5.1.1
lcsSetupWanPppEntryPeer OBJECT-TYPE
    SYNTAX     DisplayString (SIZE(0..16))
    MAX-ACCESS read-write
    STATUS     current
    DESCRIPTION
        "-- empty --"
    ::= { lcsSetupWanPppEntry 1 }

-- {COLUMN} 310.2.2.5.1.2
lcsSetupWanPppEntryAuthentRequest OBJECT-TYPE
    SYNTAX     BITS
      {
        eNone (0),
        eMsChapv2 (2),
        eMsChap (3),
        eChap (4),
        ePap (5)
      }
    MAX-ACCESS read-write
    STATUS     current
    DESCRIPTION
        "-- empty --"
    ::= { lcsSetupWanPppEntry 2 }

-- {COLUMN} 310.2.2.5.1.11
lcsSetupWanPppEntryAuthentResponse OBJECT-TYPE
    SYNTAX     BITS
      {
        eNone (0),
        eMsChapv2 (2),
        eMsChap (3),
        eChap (4),
        ePap (5)
      }
    MAX-ACCESS read-write
    STATUS     current
    DESCRIPTION
        "-- empty --"
    ::= { lcsSetupWanPppEntry 11 }

-- {COLUMN} 310.2.2.5.1.3
lcsSetupWanPppEntryKey OBJECT-TYPE
    SYNTAX     DisplayString (SIZE(0..32))
    MAX-ACCESS read-write
    STATUS     current
    DESCRIPTION
        "-- empty --"
    ::= { lcsSetupWanPppEntry 3 }

-- {COLUMN} 310.2.2.5.1.4
lcsSetupWanPppEntryTime OBJECT-TYPE
    SYNTAX     INTEGER (0..255)
    MAX-ACCESS read-write
    STATUS     current
    DESCRIPTION
        "-- empty --"
    ::= { lcsSetupWanPppEntry 4 }

-- {COLUMN} 310.2.2.5.1.5
lcsSetupWanPppEntryTry OBJECT-TYPE
    SYNTAX     INTEGER (0..255)
    MAX-ACCESS read-write
    STATUS     current
    DESCRIPTION
        "-- empty --"
    ::= { lcsSetupWanPppEntry 5 }

-- {COLUMN} 310.2.2.5.1.7
lcsSetupWanPppEntryConf OBJECT-TYPE
    SYNTAX     INTEGER (0..255)
    MAX-ACCESS read-write
    STATUS     current
    DESCRIPTION
        "-- empty --"
    ::= { lcsSetupWanPppEntry 7 }

-- {COLUMN} 310.2.2.5.1.8
lcsSetupWanPppEntryFail OBJECT-TYPE
    SYNTAX     INTEGER (0..255)
    MAX-ACCESS read-write
    STATUS     current
    DESCRIPTION
        "-- empty --"
    ::= { lcsSetupWanPppEntry 8 }

-- {COLUMN} 310.2.2.5.1.9
lcsSetupWanPppEntryTerm OBJECT-TYPE
    SYNTAX     INTEGER (0..255)
    MAX-ACCESS read-write
    STATUS     current
    DESCRIPTION
        "-- empty --"
    ::= { lcsSetupWanPppEntry 9 }

-- {COLUMN} 310.2.2.5.1.6
lcsSetupWanPppEntryUsername OBJECT-TYPE
    SYNTAX     DisplayString (SIZE(0..64))
    MAX-ACCESS read-write
    STATUS     current
    DESCRIPTION
        "-- empty --"
    ::= { lcsSetupWanPppEntry 6 }

-- {COLUMN} 310.2.2.5.1.10
lcsSetupWanPppEntryRights OBJECT-TYPE
    SYNTAX     BITS
      {
        eNone (0),
        eIp (7),
        eNbt (6)
      }
    MAX-ACCESS read-write
    STATUS     current
    DESCRIPTION
        "-- empty --"
    ::= { lcsSetupWanPppEntry 10 }

-- {TABLE} 310.2.2.19
lcsSetupWanDslBroadbandPeersTable OBJECT-TYPE
    SYNTAX     SEQUENCE OF LcsSetupWanDslBroadbandPeersEntry
    MAX-ACCESS not-accessible
    STATUS     current
    DESCRIPTION
        "-- empty --"
    ::= { lcsSetupWan 19 }

-- {ENTRY} 310.2.2.19.1
lcsSetupWanDslBroadbandPeersEntry OBJECT-TYPE
    SYNTAX     LcsSetupWanDslBroadbandPeersEntry
    MAX-ACCESS not-accessible
    STATUS     current
    DESCRIPTION
        ""
    INDEX {
        lcsSetupWanDslBroadbandPeersEntryPeer
    }
    ::= { lcsSetupWanDslBroadbandPeersTable 1 }

-- {SEQUENCE}
LcsSetupWanDslBroadbandPeersEntry ::= SEQUENCE {
    lcsSetupWanDslBroadbandPeersEntryPeer DisplayString,
    lcsSetupWanDslBroadbandPeersEntryShTime INTEGER,
    lcsSetupWanDslBroadbandPeersEntryAcName DisplayString,
    lcsSetupWanDslBroadbandPeersEntryServicename DisplayString,
    lcsSetupWanDslBroadbandPeersEntryWanLayer DisplayString,
    lcsSetupWanDslBroadbandPeersEntryMacType INTEGER,
    lcsSetupWanDslBroadbandPeersEntryUserDefMac MacAddress,
    lcsSetupWanDslBroadbandPeersEntryVlanId INTEGER
}

-- {COLUMN} 310.2.2.19.1.1
lcsSetupWanDslBroadbandPeersEntryPeer OBJECT-TYPE
    SYNTAX     DisplayString (SIZE(0..16))
    MAX-ACCESS read-write
    STATUS     current
    DESCRIPTION
        "-- empty --"
    ::= { lcsSetupWanDslBroadbandPeersEntry 1 }

-- {COLUMN} 310.2.2.19.1.3
lcsSetupWanDslBroadbandPeersEntryShTime OBJECT-TYPE
    SYNTAX     INTEGER (0..65535)
    MAX-ACCESS read-write
    STATUS     current
    DESCRIPTION
        "-- empty --"
    ::= { lcsSetupWanDslBroadbandPeersEntry 3 }

-- {COLUMN} 310.2.2.19.1.9
lcsSetupWanDslBroadbandPeersEntryAcName OBJECT-TYPE
    SYNTAX     DisplayString (SIZE(0..64))
    MAX-ACCESS read-write
    STATUS     current
    DESCRIPTION
        "-- empty --"
    ::= { lcsSetupWanDslBroadbandPeersEntry 9 }

-- {COLUMN} 310.2.2.19.1.10
lcsSetupWanDslBroadbandPeersEntryServicename OBJECT-TYPE
    SYNTAX     DisplayString (SIZE(0..32))
    MAX-ACCESS read-write
    STATUS     current
    DESCRIPTION
        "-- empty --"
    ::= { lcsSetupWanDslBroadbandPeersEntry 10 }

-- {COLUMN} 310.2.2.19.1.5
lcsSetupWanDslBroadbandPeersEntryWanLayer OBJECT-TYPE
    SYNTAX     DisplayString (SIZE(0..9))
    MAX-ACCESS read-write
    STATUS     current
    DESCRIPTION
        "-- empty --"
    ::= { lcsSetupWanDslBroadbandPeersEntry 5 }

-- {COLUMN} 310.2.2.19.1.15
lcsSetupWanDslBroadbandPeersEntryMacType OBJECT-TYPE
    SYNTAX     INTEGER
      {
        eGlobal (1),
        eLocal (0),
        eUserDef (2)
      }
    MAX-ACCESS read-write
    STATUS     current
    DESCRIPTION
        "-- empty --"
    ::= { lcsSetupWanDslBroadbandPeersEntry 15 }

-- {COLUMN} 310.2.2.19.1.13
lcsSetupWanDslBroadbandPeersEntryUserDefMac OBJECT-TYPE
    SYNTAX     MacAddress
    MAX-ACCESS read-write
    STATUS     current
    DESCRIPTION
        "-- empty --"
    ::= { lcsSetupWanDslBroadbandPeersEntry 13 }

-- {COLUMN} 310.2.2.19.1.16
lcsSetupWanDslBroadbandPeersEntryVlanId OBJECT-TYPE
    SYNTAX     INTEGER (0..65535)
    MAX-ACCESS read-write
    STATUS     current
    DESCRIPTION
        "-- empty --"
    ::= { lcsSetupWanDslBroadbandPeersEntry 16 }

-- {TABLE} 310.2.2.26
lcsSetupWanMtuListTable OBJECT-TYPE
    SYNTAX     SEQUENCE OF LcsSetupWanMtuListEntry
    MAX-ACCESS not-accessible
    STATUS     current
    DESCRIPTION
        "-- empty --"
    ::= { lcsSetupWan 26 }

-- {ENTRY} 310.2.2.26.1
lcsSetupWanMtuListEntry OBJECT-TYPE
    SYNTAX     LcsSetupWanMtuListEntry
    MAX-ACCESS not-accessible
    STATUS     current
    DESCRIPTION
        ""
    INDEX {
        lcsSetupWanMtuListEntryPeer
    }
    ::= { lcsSetupWanMtuListTable 1 }

-- {SEQUENCE}
LcsSetupWanMtuListEntry ::= SEQUENCE {
    lcsSetupWanMtuListEntryPeer DisplayString,
    lcsSetupWanMtuListEntryMtu INTEGER
}

-- {COLUMN} 310.2.2.26.1.1
lcsSetupWanMtuListEntryPeer OBJECT-TYPE
    SYNTAX     DisplayString (SIZE(0..16))
    MAX-ACCESS read-write
    STATUS     current
    DESCRIPTION
        "-- empty --"
    ::= { lcsSetupWanMtuListEntry 1 }

-- {COLUMN} 310.2.2.26.1.2
lcsSetupWanMtuListEntryMtu OBJECT-TYPE
    SYNTAX     INTEGER (0..65535)
    MAX-ACCESS read-write
    STATUS     current
    DESCRIPTION
        "-- empty --"
    ::= { lcsSetupWanMtuListEntry 2 }

-- {TABLE} 310.2.2.20
lcsSetupWanIpListTable OBJECT-TYPE
    SYNTAX     SEQUENCE OF LcsSetupWanIpListEntry
    MAX-ACCESS not-accessible
    STATUS     current
    DESCRIPTION
        "-- empty --"
    ::= { lcsSetupWan 20 }

-- {ENTRY} 310.2.2.20.1
lcsSetupWanIpListEntry OBJECT-TYPE
    SYNTAX     LcsSetupWanIpListEntry
    MAX-ACCESS not-accessible
    STATUS     current
    DESCRIPTION
        ""
    INDEX {
        lcsSetupWanIpListEntryPeer
    }
    ::= { lcsSetupWanIpListTable 1 }

-- {SEQUENCE}
LcsSetupWanIpListEntry ::= SEQUENCE {
    lcsSetupWanIpListEntryPeer DisplayString,
    lcsSetupWanIpListEntryIpAddress IpAddress,
    lcsSetupWanIpListEntryIpNetmask IpAddress,
    lcsSetupWanIpListEntryMasqIpAddr IpAddress,
    lcsSetupWanIpListEntryGateway IpAddress,
    lcsSetupWanIpListEntryDnsDefault IpAddress,
    lcsSetupWanIpListEntryDnsBackup IpAddress,
    lcsSetupWanIpListEntryNbnsDefault IpAddress,
    lcsSetupWanIpListEntryNbnsBackup IpAddress
}

-- {COLUMN} 310.2.2.20.1.1
lcsSetupWanIpListEntryPeer OBJECT-TYPE
    SYNTAX     DisplayString (SIZE(0..16))
    MAX-ACCESS read-write
    STATUS     current
    DESCRIPTION
        "-- empty --"
    ::= { lcsSetupWanIpListEntry 1 }

-- {COLUMN} 310.2.2.20.1.2
lcsSetupWanIpListEntryIpAddress OBJECT-TYPE
    SYNTAX     IpAddress
    MAX-ACCESS read-write
    STATUS     current
    DESCRIPTION
        "-- empty --"
    ::= { lcsSetupWanIpListEntry 2 }

-- {COLUMN} 310.2.2.20.1.3
lcsSetupWanIpListEntryIpNetmask OBJECT-TYPE
    SYNTAX     IpAddress
    MAX-ACCESS read-write
    STATUS     current
    DESCRIPTION
        "-- empty --"
    ::= { lcsSetupWanIpListEntry 3 }

-- {COLUMN} 310.2.2.20.1.9
lcsSetupWanIpListEntryMasqIpAddr OBJECT-TYPE
    SYNTAX     IpAddress
    MAX-ACCESS read-write
    STATUS     current
    DESCRIPTION
        "-- empty --"
    ::= { lcsSetupWanIpListEntry 9 }

-- {COLUMN} 310.2.2.20.1.4
lcsSetupWanIpListEntryGateway OBJECT-TYPE
    SYNTAX     IpAddress
    MAX-ACCESS read-write
    STATUS     current
    DESCRIPTION
        "-- empty --"
    ::= { lcsSetupWanIpListEntry 4 }

-- {COLUMN} 310.2.2.20.1.5
lcsSetupWanIpListEntryDnsDefault OBJECT-TYPE
    SYNTAX     IpAddress
    MAX-ACCESS read-write
    STATUS     current
    DESCRIPTION
        "-- empty --"
    ::= { lcsSetupWanIpListEntry 5 }

-- {COLUMN} 310.2.2.20.1.6
lcsSetupWanIpListEntryDnsBackup OBJECT-TYPE
    SYNTAX     IpAddress
    MAX-ACCESS read-write
    STATUS     current
    DESCRIPTION
        "-- empty --"
    ::= { lcsSetupWanIpListEntry 6 }

-- {COLUMN} 310.2.2.20.1.7
lcsSetupWanIpListEntryNbnsDefault OBJECT-TYPE
    SYNTAX     IpAddress
    MAX-ACCESS read-write
    STATUS     current
    DESCRIPTION
        "-- empty --"
    ::= { lcsSetupWanIpListEntry 7 }

-- {COLUMN} 310.2.2.20.1.8
lcsSetupWanIpListEntryNbnsBackup OBJECT-TYPE
    SYNTAX     IpAddress
    MAX-ACCESS read-write
    STATUS     current
    DESCRIPTION
        "-- empty --"
    ::= { lcsSetupWanIpListEntry 8 }

-- {TABLE} 310.2.2.21
lcsSetupWanPptpPeersTable OBJECT-TYPE
    SYNTAX     SEQUENCE OF LcsSetupWanPptpPeersEntry
    MAX-ACCESS not-accessible
    STATUS     current
    DESCRIPTION
        "-- empty --"
    ::= { lcsSetupWan 21 }

-- {ENTRY} 310.2.2.21.1
lcsSetupWanPptpPeersEntry OBJECT-TYPE
    SYNTAX     LcsSetupWanPptpPeersEntry
    MAX-ACCESS not-accessible
    STATUS     current
    DESCRIPTION
        ""
    INDEX {
        lcsSetupWanPptpPeersEntryPeer
    }
    ::= { lcsSetupWanPptpPeersTable 1 }

-- {SEQUENCE}
LcsSetupWanPptpPeersEntry ::= SEQUENCE {
    lcsSetupWanPptpPeersEntryPeer DisplayString,
    lcsSetupWanPptpPeersEntryIpAddress DisplayString,
    lcsSetupWanPptpPeersEntryRtgTag INTEGER,
    lcsSetupWanPptpPeersEntryPort INTEGER,
    lcsSetupWanPptpPeersEntryShTime INTEGER
}

-- {COLUMN} 310.2.2.21.1.1
lcsSetupWanPptpPeersEntryPeer OBJECT-TYPE
    SYNTAX     DisplayString (SIZE(0..16))
    MAX-ACCESS read-write
    STATUS     current
    DESCRIPTION
        "-- empty --"
    ::= { lcsSetupWanPptpPeersEntry 1 }

-- {COLUMN} 310.2.2.21.1.6
lcsSetupWanPptpPeersEntryIpAddress OBJECT-TYPE
    SYNTAX     DisplayString (SIZE(0..63))
    MAX-ACCESS read-write
    STATUS     current
    DESCRIPTION
        "-- empty --"
    ::= { lcsSetupWanPptpPeersEntry 6 }

-- {COLUMN} 310.2.2.21.1.5
lcsSetupWanPptpPeersEntryRtgTag OBJECT-TYPE
    SYNTAX     INTEGER (0..65535)
    MAX-ACCESS read-write
    STATUS     current
    DESCRIPTION
        "-- empty --"
    ::= { lcsSetupWanPptpPeersEntry 5 }

-- {COLUMN} 310.2.2.21.1.3
lcsSetupWanPptpPeersEntryPort OBJECT-TYPE
    SYNTAX     INTEGER (0..65535)
    MAX-ACCESS read-write
    STATUS     current
    DESCRIPTION
        "-- empty --"
    ::= { lcsSetupWanPptpPeersEntry 3 }

-- {COLUMN} 310.2.2.21.1.4
lcsSetupWanPptpPeersEntryShTime OBJECT-TYPE
    SYNTAX     INTEGER (0..65535)
    MAX-ACCESS read-write
    STATUS     current
    DESCRIPTION
        "-- empty --"
    ::= { lcsSetupWanPptpPeersEntry 4 }

-- {TABLE} 310.2.2.30
lcsSetupWanAdditionalPptpGatewaysTable OBJECT-TYPE
    SYNTAX     SEQUENCE OF LcsSetupWanAdditionalPptpGatewaysEntry
    MAX-ACCESS not-accessible
    STATUS     current
    DESCRIPTION
        "-- empty --"
    ::= { lcsSetupWan 30 }

-- {ENTRY} 310.2.2.30.1
lcsSetupWanAdditionalPptpGatewaysEntry OBJECT-TYPE
    SYNTAX     LcsSetupWanAdditionalPptpGatewaysEntry
    MAX-ACCESS not-accessible
    STATUS     current
    DESCRIPTION
        ""
    INDEX {
        lcsSetupWanAdditionalPptpGatewaysEntryPeer
    }
    ::= { lcsSetupWanAdditionalPptpGatewaysTable 1 }

-- {SEQUENCE}
LcsSetupWanAdditionalPptpGatewaysEntry ::= SEQUENCE {
    lcsSetupWanAdditionalPptpGatewaysEntryPeer DisplayString,
    lcsSetupWanAdditionalPptpGatewaysEntryGateway1 DisplayString,
    lcsSetupWanAdditionalPptpGatewaysEntryRtgTag1 INTEGER,
    lcsSetupWanAdditionalPptpGatewaysEntryGateway2 DisplayString,
    lcsSetupWanAdditionalPptpGatewaysEntryRtgTag2 INTEGER,
    lcsSetupWanAdditionalPptpGatewaysEntryGateway3 DisplayString,
    lcsSetupWanAdditionalPptpGatewaysEntryRtgTag3 INTEGER,
    lcsSetupWanAdditionalPptpGatewaysEntryGateway4 DisplayString,
    lcsSetupWanAdditionalPptpGatewaysEntryRtgTag4 INTEGER,
    lcsSetupWanAdditionalPptpGatewaysEntryGateway5 DisplayString,
    lcsSetupWanAdditionalPptpGatewaysEntryRtgTag5 INTEGER,
    lcsSetupWanAdditionalPptpGatewaysEntryGateway6 DisplayString,
    lcsSetupWanAdditionalPptpGatewaysEntryRtgTag6 INTEGER,
    lcsSetupWanAdditionalPptpGatewaysEntryGateway7 DisplayString,
    lcsSetupWanAdditionalPptpGatewaysEntryRtgTag7 INTEGER,
    lcsSetupWanAdditionalPptpGatewaysEntryGateway8 DisplayString,
    lcsSetupWanAdditionalPptpGatewaysEntryRtgTag8 INTEGER,
    lcsSetupWanAdditionalPptpGatewaysEntryGateway9 DisplayString,
    lcsSetupWanAdditionalPptpGatewaysEntryRtgTag9 INTEGER,
    lcsSetupWanAdditionalPptpGatewaysEntryGateway10 DisplayString,
    lcsSetupWanAdditionalPptpGatewaysEntryRtgTag10 INTEGER,
    lcsSetupWanAdditionalPptpGatewaysEntryGateway11 DisplayString,
    lcsSetupWanAdditionalPptpGatewaysEntryRtgTag11 INTEGER,
    lcsSetupWanAdditionalPptpGatewaysEntryGateway12 DisplayString,
    lcsSetupWanAdditionalPptpGatewaysEntryRtgTag12 INTEGER,
    lcsSetupWanAdditionalPptpGatewaysEntryGateway13 DisplayString,
    lcsSetupWanAdditionalPptpGatewaysEntryRtgTag13 INTEGER,
    lcsSetupWanAdditionalPptpGatewaysEntryGateway14 DisplayString,
    lcsSetupWanAdditionalPptpGatewaysEntryRtgTag14 INTEGER,
    lcsSetupWanAdditionalPptpGatewaysEntryGateway15 DisplayString,
    lcsSetupWanAdditionalPptpGatewaysEntryRtgTag15 INTEGER,
    lcsSetupWanAdditionalPptpGatewaysEntryGateway16 DisplayString,
    lcsSetupWanAdditionalPptpGatewaysEntryRtgTag16 INTEGER,
    lcsSetupWanAdditionalPptpGatewaysEntryGateway17 DisplayString,
    lcsSetupWanAdditionalPptpGatewaysEntryRtgTag17 INTEGER,
    lcsSetupWanAdditionalPptpGatewaysEntryGateway18 DisplayString,
    lcsSetupWanAdditionalPptpGatewaysEntryRtgTag18 INTEGER,
    lcsSetupWanAdditionalPptpGatewaysEntryGateway19 DisplayString,
    lcsSetupWanAdditionalPptpGatewaysEntryRtgTag19 INTEGER,
    lcsSetupWanAdditionalPptpGatewaysEntryGateway20 DisplayString,
    lcsSetupWanAdditionalPptpGatewaysEntryRtgTag20 INTEGER,
    lcsSetupWanAdditionalPptpGatewaysEntryGateway21 DisplayString,
    lcsSetupWanAdditionalPptpGatewaysEntryRtgTag21 INTEGER,
    lcsSetupWanAdditionalPptpGatewaysEntryGateway22 DisplayString,
    lcsSetupWanAdditionalPptpGatewaysEntryRtgTag22 INTEGER,
    lcsSetupWanAdditionalPptpGatewaysEntryGateway23 DisplayString,
    lcsSetupWanAdditionalPptpGatewaysEntryRtgTag23 INTEGER,
    lcsSetupWanAdditionalPptpGatewaysEntryGateway24 DisplayString,
    lcsSetupWanAdditionalPptpGatewaysEntryRtgTag24 INTEGER,
    lcsSetupWanAdditionalPptpGatewaysEntryGateway25 DisplayString,
    lcsSetupWanAdditionalPptpGatewaysEntryRtgTag25 INTEGER,
    lcsSetupWanAdditionalPptpGatewaysEntryGateway26 DisplayString,
    lcsSetupWanAdditionalPptpGatewaysEntryRtgTag26 INTEGER,
    lcsSetupWanAdditionalPptpGatewaysEntryGateway27 DisplayString,
    lcsSetupWanAdditionalPptpGatewaysEntryRtgTag27 INTEGER,
    lcsSetupWanAdditionalPptpGatewaysEntryGateway28 DisplayString,
    lcsSetupWanAdditionalPptpGatewaysEntryRtgTag28 INTEGER,
    lcsSetupWanAdditionalPptpGatewaysEntryGateway29 DisplayString,
    lcsSetupWanAdditionalPptpGatewaysEntryRtgTag29 INTEGER,
    lcsSetupWanAdditionalPptpGatewaysEntryGateway30 DisplayString,
    lcsSetupWanAdditionalPptpGatewaysEntryRtgTag30 INTEGER,
    lcsSetupWanAdditionalPptpGatewaysEntryGateway31 DisplayString,
    lcsSetupWanAdditionalPptpGatewaysEntryRtgTag31 INTEGER,
    lcsSetupWanAdditionalPptpGatewaysEntryGateway32 DisplayString,
    lcsSetupWanAdditionalPptpGatewaysEntryRtgTag32 INTEGER,
    lcsSetupWanAdditionalPptpGatewaysEntryBeginWith INTEGER
}

-- {COLUMN} 310.2.2.30.1.1
lcsSetupWanAdditionalPptpGatewaysEntryPeer OBJECT-TYPE
    SYNTAX     DisplayString (SIZE(0..16))
    MAX-ACCESS read-write
    STATUS     current
    DESCRIPTION
        "-- empty --"
    ::= { lcsSetupWanAdditionalPptpGatewaysEntry 1 }

-- {COLUMN} 310.2.2.30.1.3
lcsSetupWanAdditionalPptpGatewaysEntryGateway1 OBJECT-TYPE
    SYNTAX     DisplayString (SIZE(0..63))
    MAX-ACCESS read-write
    STATUS     current
    DESCRIPTION
        "-- empty --"
    ::= { lcsSetupWanAdditionalPptpGatewaysEntry 3 }

-- {COLUMN} 310.2.2.30.1.4
lcsSetupWanAdditionalPptpGatewaysEntryRtgTag1 OBJECT-TYPE
    SYNTAX     INTEGER (0..65535)
    MAX-ACCESS read-write
    STATUS     current
    DESCRIPTION
        "-- empty --"
    ::= { lcsSetupWanAdditionalPptpGatewaysEntry 4 }

-- {COLUMN} 310.2.2.30.1.5
lcsSetupWanAdditionalPptpGatewaysEntryGateway2 OBJECT-TYPE
    SYNTAX     DisplayString (SIZE(0..63))
    MAX-ACCESS read-write
    STATUS     current
    DESCRIPTION
        "-- empty --"
    ::= { lcsSetupWanAdditionalPptpGatewaysEntry 5 }

-- {COLUMN} 310.2.2.30.1.6
lcsSetupWanAdditionalPptpGatewaysEntryRtgTag2 OBJECT-TYPE
    SYNTAX     INTEGER (0..65535)
    MAX-ACCESS read-write
    STATUS     current
    DESCRIPTION
        "-- empty --"
    ::= { lcsSetupWanAdditionalPptpGatewaysEntry 6 }

-- {COLUMN} 310.2.2.30.1.7
lcsSetupWanAdditionalPptpGatewaysEntryGateway3 OBJECT-TYPE
    SYNTAX     DisplayString (SIZE(0..63))
    MAX-ACCESS read-write
    STATUS     current
    DESCRIPTION
        "-- empty --"
    ::= { lcsSetupWanAdditionalPptpGatewaysEntry 7 }

-- {COLUMN} 310.2.2.30.1.8
lcsSetupWanAdditionalPptpGatewaysEntryRtgTag3 OBJECT-TYPE
    SYNTAX     INTEGER (0..65535)
    MAX-ACCESS read-write
    STATUS     current
    DESCRIPTION
        "-- empty --"
    ::= { lcsSetupWanAdditionalPptpGatewaysEntry 8 }

-- {COLUMN} 310.2.2.30.1.9
lcsSetupWanAdditionalPptpGatewaysEntryGateway4 OBJECT-TYPE
    SYNTAX     DisplayString (SIZE(0..63))
    MAX-ACCESS read-write
    STATUS     current
    DESCRIPTION
        "-- empty --"
    ::= { lcsSetupWanAdditionalPptpGatewaysEntry 9 }

-- {COLUMN} 310.2.2.30.1.10
lcsSetupWanAdditionalPptpGatewaysEntryRtgTag4 OBJECT-TYPE
    SYNTAX     INTEGER (0..65535)
    MAX-ACCESS read-write
    STATUS     current
    DESCRIPTION
        "-- empty --"
    ::= { lcsSetupWanAdditionalPptpGatewaysEntry 10 }

-- {COLUMN} 310.2.2.30.1.11
lcsSetupWanAdditionalPptpGatewaysEntryGateway5 OBJECT-TYPE
    SYNTAX     DisplayString (SIZE(0..63))
    MAX-ACCESS read-write
    STATUS     current
    DESCRIPTION
        "-- empty --"
    ::= { lcsSetupWanAdditionalPptpGatewaysEntry 11 }

-- {COLUMN} 310.2.2.30.1.12
lcsSetupWanAdditionalPptpGatewaysEntryRtgTag5 OBJECT-TYPE
    SYNTAX     INTEGER (0..65535)
    MAX-ACCESS read-write
    STATUS     current
    DESCRIPTION
        "-- empty --"
    ::= { lcsSetupWanAdditionalPptpGatewaysEntry 12 }

-- {COLUMN} 310.2.2.30.1.13
lcsSetupWanAdditionalPptpGatewaysEntryGateway6 OBJECT-TYPE
    SYNTAX     DisplayString (SIZE(0..63))
    MAX-ACCESS read-write
    STATUS     current
    DESCRIPTION
        "-- empty --"
    ::= { lcsSetupWanAdditionalPptpGatewaysEntry 13 }

-- {COLUMN} 310.2.2.30.1.14
lcsSetupWanAdditionalPptpGatewaysEntryRtgTag6 OBJECT-TYPE
    SYNTAX     INTEGER (0..65535)
    MAX-ACCESS read-write
    STATUS     current
    DESCRIPTION
        "-- empty --"
    ::= { lcsSetupWanAdditionalPptpGatewaysEntry 14 }

-- {COLUMN} 310.2.2.30.1.15
lcsSetupWanAdditionalPptpGatewaysEntryGateway7 OBJECT-TYPE
    SYNTAX     DisplayString (SIZE(0..63))
    MAX-ACCESS read-write
    STATUS     current
    DESCRIPTION
        "-- empty --"
    ::= { lcsSetupWanAdditionalPptpGatewaysEntry 15 }

-- {COLUMN} 310.2.2.30.1.16
lcsSetupWanAdditionalPptpGatewaysEntryRtgTag7 OBJECT-TYPE
    SYNTAX     INTEGER (0..65535)
    MAX-ACCESS read-write
    STATUS     current
    DESCRIPTION
        "-- empty --"
    ::= { lcsSetupWanAdditionalPptpGatewaysEntry 16 }

-- {COLUMN} 310.2.2.30.1.17
lcsSetupWanAdditionalPptpGatewaysEntryGateway8 OBJECT-TYPE
    SYNTAX     DisplayString (SIZE(0..63))
    MAX-ACCESS read-write
    STATUS     current
    DESCRIPTION
        "-- empty --"
    ::= { lcsSetupWanAdditionalPptpGatewaysEntry 17 }

-- {COLUMN} 310.2.2.30.1.18
lcsSetupWanAdditionalPptpGatewaysEntryRtgTag8 OBJECT-TYPE
    SYNTAX     INTEGER (0..65535)
    MAX-ACCESS read-write
    STATUS     current
    DESCRIPTION
        "-- empty --"
    ::= { lcsSetupWanAdditionalPptpGatewaysEntry 18 }

-- {COLUMN} 310.2.2.30.1.19
lcsSetupWanAdditionalPptpGatewaysEntryGateway9 OBJECT-TYPE
    SYNTAX     DisplayString (SIZE(0..63))
    MAX-ACCESS read-write
    STATUS     current
    DESCRIPTION
        "-- empty --"
    ::= { lcsSetupWanAdditionalPptpGatewaysEntry 19 }

-- {COLUMN} 310.2.2.30.1.20
lcsSetupWanAdditionalPptpGatewaysEntryRtgTag9 OBJECT-TYPE
    SYNTAX     INTEGER (0..65535)
    MAX-ACCESS read-write
    STATUS     current
    DESCRIPTION
        "-- empty --"
    ::= { lcsSetupWanAdditionalPptpGatewaysEntry 20 }

-- {COLUMN} 310.2.2.30.1.21
lcsSetupWanAdditionalPptpGatewaysEntryGateway10 OBJECT-TYPE
    SYNTAX     DisplayString (SIZE(0..63))
    MAX-ACCESS read-write
    STATUS     current
    DESCRIPTION
        "-- empty --"
    ::= { lcsSetupWanAdditionalPptpGatewaysEntry 21 }

-- {COLUMN} 310.2.2.30.1.22
lcsSetupWanAdditionalPptpGatewaysEntryRtgTag10 OBJECT-TYPE
    SYNTAX     INTEGER (0..65535)
    MAX-ACCESS read-write
    STATUS     current
    DESCRIPTION
        "-- empty --"
    ::= { lcsSetupWanAdditionalPptpGatewaysEntry 22 }

-- {COLUMN} 310.2.2.30.1.23
lcsSetupWanAdditionalPptpGatewaysEntryGateway11 OBJECT-TYPE
    SYNTAX     DisplayString (SIZE(0..63))
    MAX-ACCESS read-write
    STATUS     current
    DESCRIPTION
        "-- empty --"
    ::= { lcsSetupWanAdditionalPptpGatewaysEntry 23 }

-- {COLUMN} 310.2.2.30.1.24
lcsSetupWanAdditionalPptpGatewaysEntryRtgTag11 OBJECT-TYPE
    SYNTAX     INTEGER (0..65535)
    MAX-ACCESS read-write
    STATUS     current
    DESCRIPTION
        "-- empty --"
    ::= { lcsSetupWanAdditionalPptpGatewaysEntry 24 }

-- {COLUMN} 310.2.2.30.1.25
lcsSetupWanAdditionalPptpGatewaysEntryGateway12 OBJECT-TYPE
    SYNTAX     DisplayString (SIZE(0..63))
    MAX-ACCESS read-write
    STATUS     current
    DESCRIPTION
        "-- empty --"
    ::= { lcsSetupWanAdditionalPptpGatewaysEntry 25 }

-- {COLUMN} 310.2.2.30.1.26
lcsSetupWanAdditionalPptpGatewaysEntryRtgTag12 OBJECT-TYPE
    SYNTAX     INTEGER (0..65535)
    MAX-ACCESS read-write
    STATUS     current
    DESCRIPTION
        "-- empty --"
    ::= { lcsSetupWanAdditionalPptpGatewaysEntry 26 }

-- {COLUMN} 310.2.2.30.1.27
lcsSetupWanAdditionalPptpGatewaysEntryGateway13 OBJECT-TYPE
    SYNTAX     DisplayString (SIZE(0..63))
    MAX-ACCESS read-write
    STATUS     current
    DESCRIPTION
        "-- empty --"
    ::= { lcsSetupWanAdditionalPptpGatewaysEntry 27 }

-- {COLUMN} 310.2.2.30.1.28
lcsSetupWanAdditionalPptpGatewaysEntryRtgTag13 OBJECT-TYPE
    SYNTAX     INTEGER (0..65535)
    MAX-ACCESS read-write
    STATUS     current
    DESCRIPTION
        "-- empty --"
    ::= { lcsSetupWanAdditionalPptpGatewaysEntry 28 }

-- {COLUMN} 310.2.2.30.1.29
lcsSetupWanAdditionalPptpGatewaysEntryGateway14 OBJECT-TYPE
    SYNTAX     DisplayString (SIZE(0..63))
    MAX-ACCESS read-write
    STATUS     current
    DESCRIPTION
        "-- empty --"
    ::= { lcsSetupWanAdditionalPptpGatewaysEntry 29 }

-- {COLUMN} 310.2.2.30.1.30
lcsSetupWanAdditionalPptpGatewaysEntryRtgTag14 OBJECT-TYPE
    SYNTAX     INTEGER (0..65535)
    MAX-ACCESS read-write
    STATUS     current
    DESCRIPTION
        "-- empty --"
    ::= { lcsSetupWanAdditionalPptpGatewaysEntry 30 }

-- {COLUMN} 310.2.2.30.1.31
lcsSetupWanAdditionalPptpGatewaysEntryGateway15 OBJECT-TYPE
    SYNTAX     DisplayString (SIZE(0..63))
    MAX-ACCESS read-write
    STATUS     current
    DESCRIPTION
        "-- empty --"
    ::= { lcsSetupWanAdditionalPptpGatewaysEntry 31 }

-- {COLUMN} 310.2.2.30.1.32
lcsSetupWanAdditionalPptpGatewaysEntryRtgTag15 OBJECT-TYPE
    SYNTAX     INTEGER (0..65535)
    MAX-ACCESS read-write
    STATUS     current
    DESCRIPTION
        "-- empty --"
    ::= { lcsSetupWanAdditionalPptpGatewaysEntry 32 }

-- {COLUMN} 310.2.2.30.1.33
lcsSetupWanAdditionalPptpGatewaysEntryGateway16 OBJECT-TYPE
    SYNTAX     DisplayString (SIZE(0..63))
    MAX-ACCESS read-write
    STATUS     current
    DESCRIPTION
        "-- empty --"
    ::= { lcsSetupWanAdditionalPptpGatewaysEntry 33 }

-- {COLUMN} 310.2.2.30.1.34
lcsSetupWanAdditionalPptpGatewaysEntryRtgTag16 OBJECT-TYPE
    SYNTAX     INTEGER (0..65535)
    MAX-ACCESS read-write
    STATUS     current
    DESCRIPTION
        "-- empty --"
    ::= { lcsSetupWanAdditionalPptpGatewaysEntry 34 }

-- {COLUMN} 310.2.2.30.1.35
lcsSetupWanAdditionalPptpGatewaysEntryGateway17 OBJECT-TYPE
    SYNTAX     DisplayString (SIZE(0..63))
    MAX-ACCESS read-write
    STATUS     current
    DESCRIPTION
        "-- empty --"
    ::= { lcsSetupWanAdditionalPptpGatewaysEntry 35 }

-- {COLUMN} 310.2.2.30.1.36
lcsSetupWanAdditionalPptpGatewaysEntryRtgTag17 OBJECT-TYPE
    SYNTAX     INTEGER (0..65535)
    MAX-ACCESS read-write
    STATUS     current
    DESCRIPTION
        "-- empty --"
    ::= { lcsSetupWanAdditionalPptpGatewaysEntry 36 }

-- {COLUMN} 310.2.2.30.1.37
lcsSetupWanAdditionalPptpGatewaysEntryGateway18 OBJECT-TYPE
    SYNTAX     DisplayString (SIZE(0..63))
    MAX-ACCESS read-write
    STATUS     current
    DESCRIPTION
        "-- empty --"
    ::= { lcsSetupWanAdditionalPptpGatewaysEntry 37 }

-- {COLUMN} 310.2.2.30.1.38
lcsSetupWanAdditionalPptpGatewaysEntryRtgTag18 OBJECT-TYPE
    SYNTAX     INTEGER (0..65535)
    MAX-ACCESS read-write
    STATUS     current
    DESCRIPTION
        "-- empty --"
    ::= { lcsSetupWanAdditionalPptpGatewaysEntry 38 }

-- {COLUMN} 310.2.2.30.1.39
lcsSetupWanAdditionalPptpGatewaysEntryGateway19 OBJECT-TYPE
    SYNTAX     DisplayString (SIZE(0..63))
    MAX-ACCESS read-write
    STATUS     current
    DESCRIPTION
        "-- empty --"
    ::= { lcsSetupWanAdditionalPptpGatewaysEntry 39 }

-- {COLUMN} 310.2.2.30.1.40
lcsSetupWanAdditionalPptpGatewaysEntryRtgTag19 OBJECT-TYPE
    SYNTAX     INTEGER (0..65535)
    MAX-ACCESS read-write
    STATUS     current
    DESCRIPTION
        "-- empty --"
    ::= { lcsSetupWanAdditionalPptpGatewaysEntry 40 }

-- {COLUMN} 310.2.2.30.1.41
lcsSetupWanAdditionalPptpGatewaysEntryGateway20 OBJECT-TYPE
    SYNTAX     DisplayString (SIZE(0..63))
    MAX-ACCESS read-write
    STATUS     current
    DESCRIPTION
        "-- empty --"
    ::= { lcsSetupWanAdditionalPptpGatewaysEntry 41 }

-- {COLUMN} 310.2.2.30.1.42
lcsSetupWanAdditionalPptpGatewaysEntryRtgTag20 OBJECT-TYPE
    SYNTAX     INTEGER (0..65535)
    MAX-ACCESS read-write
    STATUS     current
    DESCRIPTION
        "-- empty --"
    ::= { lcsSetupWanAdditionalPptpGatewaysEntry 42 }

-- {COLUMN} 310.2.2.30.1.43
lcsSetupWanAdditionalPptpGatewaysEntryGateway21 OBJECT-TYPE
    SYNTAX     DisplayString (SIZE(0..63))
    MAX-ACCESS read-write
    STATUS     current
    DESCRIPTION
        "-- empty --"
    ::= { lcsSetupWanAdditionalPptpGatewaysEntry 43 }

-- {COLUMN} 310.2.2.30.1.44
lcsSetupWanAdditionalPptpGatewaysEntryRtgTag21 OBJECT-TYPE
    SYNTAX     INTEGER (0..65535)
    MAX-ACCESS read-write
    STATUS     current
    DESCRIPTION
        "-- empty --"
    ::= { lcsSetupWanAdditionalPptpGatewaysEntry 44 }

-- {COLUMN} 310.2.2.30.1.45
lcsSetupWanAdditionalPptpGatewaysEntryGateway22 OBJECT-TYPE
    SYNTAX     DisplayString (SIZE(0..63))
    MAX-ACCESS read-write
    STATUS     current
    DESCRIPTION
        "-- empty --"
    ::= { lcsSetupWanAdditionalPptpGatewaysEntry 45 }

-- {COLUMN} 310.2.2.30.1.46
lcsSetupWanAdditionalPptpGatewaysEntryRtgTag22 OBJECT-TYPE
    SYNTAX     INTEGER (0..65535)
    MAX-ACCESS read-write
    STATUS     current
    DESCRIPTION
        "-- empty --"
    ::= { lcsSetupWanAdditionalPptpGatewaysEntry 46 }

-- {COLUMN} 310.2.2.30.1.47
lcsSetupWanAdditionalPptpGatewaysEntryGateway23 OBJECT-TYPE
    SYNTAX     DisplayString (SIZE(0..63))
    MAX-ACCESS read-write
    STATUS     current
    DESCRIPTION
        "-- empty --"
    ::= { lcsSetupWanAdditionalPptpGatewaysEntry 47 }

-- {COLUMN} 310.2.2.30.1.48
lcsSetupWanAdditionalPptpGatewaysEntryRtgTag23 OBJECT-TYPE
    SYNTAX     INTEGER (0..65535)
    MAX-ACCESS read-write
    STATUS     current
    DESCRIPTION
        "-- empty --"
    ::= { lcsSetupWanAdditionalPptpGatewaysEntry 48 }

-- {COLUMN} 310.2.2.30.1.49
lcsSetupWanAdditionalPptpGatewaysEntryGateway24 OBJECT-TYPE
    SYNTAX     DisplayString (SIZE(0..63))
    MAX-ACCESS read-write
    STATUS     current
    DESCRIPTION
        "-- empty --"
    ::= { lcsSetupWanAdditionalPptpGatewaysEntry 49 }

-- {COLUMN} 310.2.2.30.1.50
lcsSetupWanAdditionalPptpGatewaysEntryRtgTag24 OBJECT-TYPE
    SYNTAX     INTEGER (0..65535)
    MAX-ACCESS read-write
    STATUS     current
    DESCRIPTION
        "-- empty --"
    ::= { lcsSetupWanAdditionalPptpGatewaysEntry 50 }

-- {COLUMN} 310.2.2.30.1.51
lcsSetupWanAdditionalPptpGatewaysEntryGateway25 OBJECT-TYPE
    SYNTAX     DisplayString (SIZE(0..63))
    MAX-ACCESS read-write
    STATUS     current
    DESCRIPTION
        "-- empty --"
    ::= { lcsSetupWanAdditionalPptpGatewaysEntry 51 }

-- {COLUMN} 310.2.2.30.1.52
lcsSetupWanAdditionalPptpGatewaysEntryRtgTag25 OBJECT-TYPE
    SYNTAX     INTEGER (0..65535)
    MAX-ACCESS read-write
    STATUS     current
    DESCRIPTION
        "-- empty --"
    ::= { lcsSetupWanAdditionalPptpGatewaysEntry 52 }

-- {COLUMN} 310.2.2.30.1.53
lcsSetupWanAdditionalPptpGatewaysEntryGateway26 OBJECT-TYPE
    SYNTAX     DisplayString (SIZE(0..63))
    MAX-ACCESS read-write
    STATUS     current
    DESCRIPTION
        "-- empty --"
    ::= { lcsSetupWanAdditionalPptpGatewaysEntry 53 }

-- {COLUMN} 310.2.2.30.1.54
lcsSetupWanAdditionalPptpGatewaysEntryRtgTag26 OBJECT-TYPE
    SYNTAX     INTEGER (0..65535)
    MAX-ACCESS read-write
    STATUS     current
    DESCRIPTION
        "-- empty --"
    ::= { lcsSetupWanAdditionalPptpGatewaysEntry 54 }

-- {COLUMN} 310.2.2.30.1.55
lcsSetupWanAdditionalPptpGatewaysEntryGateway27 OBJECT-TYPE
    SYNTAX     DisplayString (SIZE(0..63))
    MAX-ACCESS read-write
    STATUS     current
    DESCRIPTION
        "-- empty --"
    ::= { lcsSetupWanAdditionalPptpGatewaysEntry 55 }

-- {COLUMN} 310.2.2.30.1.56
lcsSetupWanAdditionalPptpGatewaysEntryRtgTag27 OBJECT-TYPE
    SYNTAX     INTEGER (0..65535)
    MAX-ACCESS read-write
    STATUS     current
    DESCRIPTION
        "-- empty --"
    ::= { lcsSetupWanAdditionalPptpGatewaysEntry 56 }

-- {COLUMN} 310.2.2.30.1.57
lcsSetupWanAdditionalPptpGatewaysEntryGateway28 OBJECT-TYPE
    SYNTAX     DisplayString (SIZE(0..63))
    MAX-ACCESS read-write
    STATUS     current
    DESCRIPTION
        "-- empty --"
    ::= { lcsSetupWanAdditionalPptpGatewaysEntry 57 }

-- {COLUMN} 310.2.2.30.1.58
lcsSetupWanAdditionalPptpGatewaysEntryRtgTag28 OBJECT-TYPE
    SYNTAX     INTEGER (0..65535)
    MAX-ACCESS read-write
    STATUS     current
    DESCRIPTION
        "-- empty --"
    ::= { lcsSetupWanAdditionalPptpGatewaysEntry 58 }

-- {COLUMN} 310.2.2.30.1.59
lcsSetupWanAdditionalPptpGatewaysEntryGateway29 OBJECT-TYPE
    SYNTAX     DisplayString (SIZE(0..63))
    MAX-ACCESS read-write
    STATUS     current
    DESCRIPTION
        "-- empty --"
    ::= { lcsSetupWanAdditionalPptpGatewaysEntry 59 }

-- {COLUMN} 310.2.2.30.1.60
lcsSetupWanAdditionalPptpGatewaysEntryRtgTag29 OBJECT-TYPE
    SYNTAX     INTEGER (0..65535)
    MAX-ACCESS read-write
    STATUS     current
    DESCRIPTION
        "-- empty --"
    ::= { lcsSetupWanAdditionalPptpGatewaysEntry 60 }

-- {COLUMN} 310.2.2.30.1.61
lcsSetupWanAdditionalPptpGatewaysEntryGateway30 OBJECT-TYPE
    SYNTAX     DisplayString (SIZE(0..63))
    MAX-ACCESS read-write
    STATUS     current
    DESCRIPTION
        "-- empty --"
    ::= { lcsSetupWanAdditionalPptpGatewaysEntry 61 }

-- {COLUMN} 310.2.2.30.1.62
lcsSetupWanAdditionalPptpGatewaysEntryRtgTag30 OBJECT-TYPE
    SYNTAX     INTEGER (0..65535)
    MAX-ACCESS read-write
    STATUS     current
    DESCRIPTION
        "-- empty --"
    ::= { lcsSetupWanAdditionalPptpGatewaysEntry 62 }

-- {COLUMN} 310.2.2.30.1.63
lcsSetupWanAdditionalPptpGatewaysEntryGateway31 OBJECT-TYPE
    SYNTAX     DisplayString (SIZE(0..63))
    MAX-ACCESS read-write
    STATUS     current
    DESCRIPTION
        "-- empty --"
    ::= { lcsSetupWanAdditionalPptpGatewaysEntry 63 }

-- {COLUMN} 310.2.2.30.1.64
lcsSetupWanAdditionalPptpGatewaysEntryRtgTag31 OBJECT-TYPE
    SYNTAX     INTEGER (0..65535)
    MAX-ACCESS read-write
    STATUS     current
    DESCRIPTION
        "-- empty --"
    ::= { lcsSetupWanAdditionalPptpGatewaysEntry 64 }

-- {COLUMN} 310.2.2.30.1.65
lcsSetupWanAdditionalPptpGatewaysEntryGateway32 OBJECT-TYPE
    SYNTAX     DisplayString (SIZE(0..63))
    MAX-ACCESS read-write
    STATUS     current
    DESCRIPTION
        "-- empty --"
    ::= { lcsSetupWanAdditionalPptpGatewaysEntry 65 }

-- {COLUMN} 310.2.2.30.1.66
lcsSetupWanAdditionalPptpGatewaysEntryRtgTag32 OBJECT-TYPE
    SYNTAX     INTEGER (0..65535)
    MAX-ACCESS read-write
    STATUS     current
    DESCRIPTION
        "-- empty --"
    ::= { lcsSetupWanAdditionalPptpGatewaysEntry 66 }

-- {COLUMN} 310.2.2.30.1.2
lcsSetupWanAdditionalPptpGatewaysEntryBeginWith OBJECT-TYPE
    SYNTAX     INTEGER
      {
        eLastUsed (0),
        eFirst (1),
        eRandom (2)
      }
    MAX-ACCESS read-write
    STATUS     current
    DESCRIPTION
        "-- empty --"
    ::= { lcsSetupWanAdditionalPptpGatewaysEntry 2 }

-- {SCALAR} 310.2.2.31
lcsSetupWanPptpSourceCheck OBJECT-TYPE
    SYNTAX     INTEGER
      {
        eAddress (0),
        eTagPlusAddress (1)
      }
    MAX-ACCESS read-only
    STATUS     current
    DESCRIPTION
        "-- empty --"
    ::= { lcsSetupWan 31 }

-- {OID} 310.2.2.22
lcsSetupWanRadius OBJECT IDENTIFIER ::= { lcsSetupWan 22 }

-- {SCALAR} 310.2.2.22.1
lcsSetupWanRadiusOperating OBJECT-TYPE
    SYNTAX     INTEGER
      {
        eNo (0),
        eYes (1),
        eExclusive (2)
      }
    MAX-ACCESS read-only
    STATUS     current
    DESCRIPTION
        "-- empty --"
    ::= { lcsSetupWanRadius 1 }

-- {SCALAR} 310.2.2.22.2
lcsSetupWanRadiusServerAddress OBJECT-TYPE
    SYNTAX     IpAddress
    MAX-ACCESS read-only
    STATUS     current
    DESCRIPTION
        "-- empty --"
    ::= { lcsSetupWanRadius 2 }

-- {SCALAR} 310.2.2.22.3
lcsSetupWanRadiusAuthPort OBJECT-TYPE
    SYNTAX     INTEGER (0..65535)
    MAX-ACCESS read-only
    STATUS     current
    DESCRIPTION
        "-- empty --"
    ::= { lcsSetupWanRadius 3 }

-- {SCALAR} 310.2.2.22.8
lcsSetupWanRadiusLoopbackAddr OBJECT-TYPE
    SYNTAX     DisplayString (SIZE(0..16))
    MAX-ACCESS read-only
    STATUS     current
    DESCRIPTION
        "-- empty --"
    ::= { lcsSetupWanRadius 8 }

-- {SCALAR} 310.2.2.22.9
lcsSetupWanRadiusProtocol OBJECT-TYPE
    SYNTAX     INTEGER
      {
        eRadius (0),
        eRadsec (1)
      }
    MAX-ACCESS read-write
    STATUS     current
    DESCRIPTION
        "-- empty --"
    ::= { lcsSetupWanRadius 9 }

-- {SCALAR} 310.2.2.22.4
lcsSetupWanRadiusSecret OBJECT-TYPE
    SYNTAX     DisplayString (SIZE(0..64))
    MAX-ACCESS read-only
    STATUS     current
    DESCRIPTION
        "-- empty --"
    ::= { lcsSetupWanRadius 4 }

-- {SCALAR} 310.2.2.22.5
lcsSetupWanRadiusPppOperation OBJECT-TYPE
    SYNTAX     INTEGER
      {
        eNo (0),
        eYes (1),
        eExclusive (2)
      }
    MAX-ACCESS read-only
    STATUS     current
    DESCRIPTION
        "-- empty --"
    ::= { lcsSetupWanRadius 5 }

-- {SCALAR} 310.2.2.22.10
lcsSetupWanRadiusAuthProtocols OBJECT-TYPE
    SYNTAX     BITS
      {
        eNone (0),
        eMsChapv2 (2),
        eMsChap (3),
        eChap (4),
        ePap (5)
      }
    MAX-ACCESS read-only
    STATUS     current
    DESCRIPTION
        "-- empty --"
    ::= { lcsSetupWanRadius 10 }

-- {SCALAR} 310.2.2.22.6
lcsSetupWanRadiusClipOperation OBJECT-TYPE
    SYNTAX     INTEGER
      {
        eNo (0),
        eYes (1),
        eExclusive (2)
      }
    MAX-ACCESS read-only
    STATUS     current
    DESCRIPTION
        "-- empty --"
    ::= { lcsSetupWanRadius 6 }

-- {SCALAR} 310.2.2.22.7
lcsSetupWanRadiusClipPassword OBJECT-TYPE
    SYNTAX     DisplayString (SIZE(0..64))
    MAX-ACCESS read-only
    STATUS     current
    DESCRIPTION
        "-- empty --"
    ::= { lcsSetupWanRadius 7 }

-- {TABLE} 310.2.2.23
lcsSetupWanPollingTableTable OBJECT-TYPE
    SYNTAX     SEQUENCE OF LcsSetupWanPollingTableEntry
    MAX-ACCESS not-accessible
    STATUS     current
    DESCRIPTION
        "-- empty --"
    ::= { lcsSetupWan 23 }

-- {ENTRY} 310.2.2.23.1
lcsSetupWanPollingTableEntry OBJECT-TYPE
    SYNTAX     LcsSetupWanPollingTableEntry
    MAX-ACCESS not-accessible
    STATUS     current
    DESCRIPTION
        ""
    INDEX {
        lcsSetupWanPollingTableEntryPeer
    }
    ::= { lcsSetupWanPollingTableTable 1 }

-- {SEQUENCE}
LcsSetupWanPollingTableEntry ::= SEQUENCE {
    lcsSetupWanPollingTableEntryPeer DisplayString,
    lcsSetupWanPollingTableEntryIpAddress1 IpAddress,
    lcsSetupWanPollingTableEntryIpAddress2 IpAddress,
    lcsSetupWanPollingTableEntryIpAddress3 IpAddress,
    lcsSetupWanPollingTableEntryIpAddress4 IpAddress,
    lcsSetupWanPollingTableEntryTime INTEGER,
    lcsSetupWanPollingTableEntryTry INTEGER,
    lcsSetupWanPollingTableEntryLoopbackAddr DisplayString,
    lcsSetupWanPollingTableEntryType INTEGER
}

-- {COLUMN} 310.2.2.23.1.1
lcsSetupWanPollingTableEntryPeer OBJECT-TYPE
    SYNTAX     DisplayString (SIZE(0..16))
    MAX-ACCESS read-write
    STATUS     current
    DESCRIPTION
        "-- empty --"
    ::= { lcsSetupWanPollingTableEntry 1 }

-- {COLUMN} 310.2.2.23.1.2
lcsSetupWanPollingTableEntryIpAddress1 OBJECT-TYPE
    SYNTAX     IpAddress
    MAX-ACCESS read-write
    STATUS     current
    DESCRIPTION
        "-- empty --"
    ::= { lcsSetupWanPollingTableEntry 2 }

-- {COLUMN} 310.2.2.23.1.5
lcsSetupWanPollingTableEntryIpAddress2 OBJECT-TYPE
    SYNTAX     IpAddress
    MAX-ACCESS read-write
    STATUS     current
    DESCRIPTION
        "-- empty --"
    ::= { lcsSetupWanPollingTableEntry 5 }

-- {COLUMN} 310.2.2.23.1.6
lcsSetupWanPollingTableEntryIpAddress3 OBJECT-TYPE
    SYNTAX     IpAddress
    MAX-ACCESS read-write
    STATUS     current
    DESCRIPTION
        "-- empty --"
    ::= { lcsSetupWanPollingTableEntry 6 }

-- {COLUMN} 310.2.2.23.1.7
lcsSetupWanPollingTableEntryIpAddress4 OBJECT-TYPE
    SYNTAX     IpAddress
    MAX-ACCESS read-write
    STATUS     current
    DESCRIPTION
        "-- empty --"
    ::= { lcsSetupWanPollingTableEntry 7 }

-- {COLUMN} 310.2.2.23.1.3
lcsSetupWanPollingTableEntryTime OBJECT-TYPE
    SYNTAX     INTEGER (0..65535)
    MAX-ACCESS read-write
    STATUS     current
    DESCRIPTION
        "-- empty --"
    ::= { lcsSetupWanPollingTableEntry 3 }

-- {COLUMN} 310.2.2.23.1.4
lcsSetupWanPollingTableEntryTry OBJECT-TYPE
    SYNTAX     INTEGER (0..255)
    MAX-ACCESS read-write
    STATUS     current
    DESCRIPTION
        "-- empty --"
    ::= { lcsSetupWanPollingTableEntry 4 }

-- {COLUMN} 310.2.2.23.1.8
lcsSetupWanPollingTableEntryLoopbackAddr OBJECT-TYPE
    SYNTAX     DisplayString (SIZE(0..16))
    MAX-ACCESS read-write
    STATUS     current
    DESCRIPTION
        "-- empty --"
    ::= { lcsSetupWanPollingTableEntry 8 }

-- {COLUMN} 310.2.2.23.1.9
lcsSetupWanPollingTableEntryType OBJECT-TYPE
    SYNTAX     INTEGER
      {
        eAuto (1),
        eForced (0)
      }
    MAX-ACCESS read-write
    STATUS     current
    DESCRIPTION
        "-- empty --"
    ::= { lcsSetupWanPollingTableEntry 9 }

-- {TABLE} 310.2.2.24
lcsSetupWanBackupPeersTable OBJECT-TYPE
    SYNTAX     SEQUENCE OF LcsSetupWanBackupPeersEntry
    MAX-ACCESS not-accessible
    STATUS     current
    DESCRIPTION
        "-- empty --"
    ::= { lcsSetupWan 24 }

-- {ENTRY} 310.2.2.24.1
lcsSetupWanBackupPeersEntry OBJECT-TYPE
    SYNTAX     LcsSetupWanBackupPeersEntry
    MAX-ACCESS not-accessible
    STATUS     current
    DESCRIPTION
        ""
    INDEX {
        lcsSetupWanBackupPeersEntryPeer
    }
    ::= { lcsSetupWanBackupPeersTable 1 }

-- {SEQUENCE}
LcsSetupWanBackupPeersEntry ::= SEQUENCE {
    lcsSetupWanBackupPeersEntryPeer DisplayString,
    lcsSetupWanBackupPeersEntryAlternativePeers DisplayString,
    lcsSetupWanBackupPeersEntryHead INTEGER
}

-- {COLUMN} 310.2.2.24.1.1
lcsSetupWanBackupPeersEntryPeer OBJECT-TYPE
    SYNTAX     DisplayString (SIZE(0..18))
    MAX-ACCESS read-write
    STATUS     current
    DESCRIPTION
        "-- empty --"
    ::= { lcsSetupWanBackupPeersEntry 1 }

-- {COLUMN} 310.2.2.24.1.2
lcsSetupWanBackupPeersEntryAlternativePeers OBJECT-TYPE
    SYNTAX     DisplayString (SIZE(0..53))
    MAX-ACCESS read-write
    STATUS     current
    DESCRIPTION
        "-- empty --"
    ::= { lcsSetupWanBackupPeersEntry 2 }

-- {COLUMN} 310.2.2.24.1.3
lcsSetupWanBackupPeersEntryHead OBJECT-TYPE
    SYNTAX     INTEGER
      {
        eLast (0),
        eFirst (1)
      }
    MAX-ACCESS read-write
    STATUS     current
    DESCRIPTION
        "-- empty --"
    ::= { lcsSetupWanBackupPeersEntry 3 }

-- {TABLE} 310.2.2.25
lcsSetupWanActionTableTable OBJECT-TYPE
    SYNTAX     SEQUENCE OF LcsSetupWanActionTableEntry
    MAX-ACCESS not-accessible
    STATUS     current
    DESCRIPTION
        "-- empty --"
    ::= { lcsSetupWan 25 }

-- {ENTRY} 310.2.2.25.1
lcsSetupWanActionTableEntry OBJECT-TYPE
    SYNTAX     LcsSetupWanActionTableEntry
    MAX-ACCESS not-accessible
    STATUS     current
    DESCRIPTION
        ""
    INDEX {
        lcsSetupWanActionTableEntryIndex
    }
    ::= { lcsSetupWanActionTableTable 1 }

-- {SEQUENCE}
LcsSetupWanActionTableEntry ::= SEQUENCE {
    lcsSetupWanActionTableEntryIndex INTEGER,
    lcsSetupWanActionTableEntryActive INTEGER,
    lcsSetupWanActionTableEntryHostName DisplayString,
    lcsSetupWanActionTableEntryPeer DisplayString,
    lcsSetupWanActionTableEntryLockTime INTEGER,
    lcsSetupWanActionTableEntryCondition INTEGER,
    lcsSetupWanActionTableEntryAction DisplayString,
    lcsSetupWanActionTableEntryCheckFor DisplayString,
    lcsSetupWanActionTableEntryOwner DisplayString
}

-- {COLUMN} 310.2.2.25.1.1
lcsSetupWanActionTableEntryIndex OBJECT-TYPE
    SYNTAX     INTEGER (0..65535)
    MAX-ACCESS read-write
    STATUS     current
    DESCRIPTION
        "-- empty --"
    ::= { lcsSetupWanActionTableEntry 1 }

-- {COLUMN} 310.2.2.25.1.8
lcsSetupWanActionTableEntryActive OBJECT-TYPE
    SYNTAX     INTEGER
      {
        eYes (0),
        eNo (1)
      }
    MAX-ACCESS read-write
    STATUS     current
    DESCRIPTION
        "-- empty --"
    ::= { lcsSetupWanActionTableEntry 8 }

-- {COLUMN} 310.2.2.25.1.2
lcsSetupWanActionTableEntryHostName OBJECT-TYPE
    SYNTAX     DisplayString (SIZE(0..64))
    MAX-ACCESS read-write
    STATUS     current
    DESCRIPTION
        "-- empty --"
    ::= { lcsSetupWanActionTableEntry 2 }

-- {COLUMN} 310.2.2.25.1.3
lcsSetupWanActionTableEntryPeer OBJECT-TYPE
    SYNTAX     DisplayString (SIZE(0..16))
    MAX-ACCESS read-write
    STATUS     current
    DESCRIPTION
        "-- empty --"
    ::= { lcsSetupWanActionTableEntry 3 }

-- {COLUMN} 310.2.2.25.1.4
lcsSetupWanActionTableEntryLockTime OBJECT-TYPE
    SYNTAX     INTEGER (0..2147483647)
    MAX-ACCESS read-write
    STATUS     current
    DESCRIPTION
        "-- empty --"
    ::= { lcsSetupWanActionTableEntry 4 }

-- {COLUMN} 310.2.2.25.1.5
lcsSetupWanActionTableEntryCondition OBJECT-TYPE
    SYNTAX     INTEGER
      {
        eEstablish (0),
        eDisconnect (1),
        eEnd (2),
        eFailure (3),
        eEstablishFailure (4)
      }
    MAX-ACCESS read-write
    STATUS     current
    DESCRIPTION
        "-- empty --"
    ::= { lcsSetupWanActionTableEntry 5 }

-- {COLUMN} 310.2.2.25.1.6
lcsSetupWanActionTableEntryAction OBJECT-TYPE
    SYNTAX     DisplayString (SIZE(0..250))
    MAX-ACCESS read-write
    STATUS     current
    DESCRIPTION
        "-- empty --"
    ::= { lcsSetupWanActionTableEntry 6 }

-- {COLUMN} 310.2.2.25.1.7
lcsSetupWanActionTableEntryCheckFor OBJECT-TYPE
    SYNTAX     DisplayString (SIZE(0..50))
    MAX-ACCESS read-write
    STATUS     current
    DESCRIPTION
        "-- empty --"
    ::= { lcsSetupWanActionTableEntry 7 }

-- {COLUMN} 310.2.2.25.1.9
lcsSetupWanActionTableEntryOwner OBJECT-TYPE
    SYNTAX     DisplayString (SIZE(0..16))
    MAX-ACCESS read-write
    STATUS     current
    DESCRIPTION
        "-- empty --"
    ::= { lcsSetupWanActionTableEntry 9 }

-- {SCALAR} 310.2.2.18
lcsSetupWanBackupDelaySeconds OBJECT-TYPE
    SYNTAX     INTEGER (0..65535)
    MAX-ACCESS read-only
    STATUS     current
    DESCRIPTION
        "-- empty --"
    ::= { lcsSetupWan 18 }

-- {TABLE} 310.2.2.6
lcsSetupWanIncomingCallingNumbersTable OBJECT-TYPE
    SYNTAX     SEQUENCE OF LcsSetupWanIncomingCallingNumbersEntry
    MAX-ACCESS not-accessible
    STATUS     current
    DESCRIPTION
        "-- empty --"
    ::= { lcsSetupWan 6 }

-- {ENTRY} 310.2.2.6.1
lcsSetupWanIncomingCallingNumbersEntry OBJECT-TYPE
    SYNTAX     LcsSetupWanIncomingCallingNumbersEntry
    MAX-ACCESS not-accessible
    STATUS     current
    DESCRIPTION
        ""
    INDEX {
        lcsSetupWanIncomingCallingNumbersEntryDialupRemote
    }
    ::= { lcsSetupWanIncomingCallingNumbersTable 1 }

-- {SEQUENCE}
LcsSetupWanIncomingCallingNumbersEntry ::= SEQUENCE {
    lcsSetupWanIncomingCallingNumbersEntryDialupRemote DisplayString,
    lcsSetupWanIncomingCallingNumbersEntryPeer DisplayString
}

-- {COLUMN} 310.2.2.6.1.1
lcsSetupWanIncomingCallingNumbersEntryDialupRemote OBJECT-TYPE
    SYNTAX     DisplayString (SIZE(0..31))
    MAX-ACCESS read-write
    STATUS     current
    DESCRIPTION
        "-- empty --"
    ::= { lcsSetupWanIncomingCallingNumbersEntry 1 }

-- {COLUMN} 310.2.2.6.1.2
lcsSetupWanIncomingCallingNumbersEntryPeer OBJECT-TYPE
    SYNTAX     DisplayString (SIZE(0..16))
    MAX-ACCESS read-write
    STATUS     current
    DESCRIPTION
        "-- empty --"
    ::= { lcsSetupWanIncomingCallingNumbersEntry 2 }

-- {TABLE} 310.2.2.8
lcsSetupWanScriptsTable OBJECT-TYPE
    SYNTAX     SEQUENCE OF LcsSetupWanScriptsEntry
    MAX-ACCESS not-accessible
    STATUS     current
    DESCRIPTION
        "-- empty --"
    ::= { lcsSetupWan 8 }

-- {ENTRY} 310.2.2.8.1
lcsSetupWanScriptsEntry OBJECT-TYPE
    SYNTAX     LcsSetupWanScriptsEntry
    MAX-ACCESS not-accessible
    STATUS     current
    DESCRIPTION
        ""
    INDEX {
        lcsSetupWanScriptsEntryPeer
    }
    ::= { lcsSetupWanScriptsTable 1 }

-- {SEQUENCE}
LcsSetupWanScriptsEntry ::= SEQUENCE {
    lcsSetupWanScriptsEntryPeer DisplayString,
    lcsSetupWanScriptsEntryScript DisplayString
}

-- {COLUMN} 310.2.2.8.1.1
lcsSetupWanScriptsEntryPeer OBJECT-TYPE
    SYNTAX     DisplayString (SIZE(0..18))
    MAX-ACCESS read-write
    STATUS     current
    DESCRIPTION
        "-- empty --"
    ::= { lcsSetupWanScriptsEntry 1 }

-- {COLUMN} 310.2.2.8.1.2
lcsSetupWanScriptsEntryScript OBJECT-TYPE
    SYNTAX     DisplayString (SIZE(0..58))
    MAX-ACCESS read-write
    STATUS     current
    DESCRIPTION
        "-- empty --"
    ::= { lcsSetupWanScriptsEntry 2 }

-- {SCALAR} 310.2.2.9
lcsSetupWanProtect OBJECT-TYPE
    SYNTAX     INTEGER
      {
        eNone (0),
        eNumber (2),
        eScreened (4)
      }
    MAX-ACCESS read-only
    STATUS     current
    DESCRIPTION
        "-- empty --"
    ::= { lcsSetupWan 9 }

-- {SCALAR} 310.2.2.10
lcsSetupWanCallbackAttempts OBJECT-TYPE
    SYNTAX     INTEGER (0..255)
    MAX-ACCESS read-only
    STATUS     current
    DESCRIPTION
        "-- empty --"
    ::= { lcsSetupWan 10 }

-- {OID} 310.2.2.13
lcsSetupWanManualDialing OBJECT IDENTIFIER ::= { lcsSetupWan 13 }

-- {SCALAR} 310.2.2.13.1
lcsSetupWanManualDialingConnect OBJECT-TYPE
    SYNTAX     DisplayString
    MAX-ACCESS read-write
    STATUS     current
    DESCRIPTION
        "-- empty --"
    ::= { lcsSetupWanManualDialing 1 }

-- {SCALAR} 310.2.2.13.2
lcsSetupWanManualDialingDisconnect OBJECT-TYPE
    SYNTAX     DisplayString
    MAX-ACCESS read-write
    STATUS     current
    DESCRIPTION
        "-- empty --"
    ::= { lcsSetupWanManualDialing 2 }

-- {TABLE} 310.2.2.11
lcsSetupWanRouterInterfaceTable OBJECT-TYPE
    SYNTAX     SEQUENCE OF LcsSetupWanRouterInterfaceEntry
    MAX-ACCESS not-accessible
    STATUS     current
    DESCRIPTION
        "-- empty --"
    ::= { lcsSetupWan 11 }

-- {ENTRY} 310.2.2.11.1
lcsSetupWanRouterInterfaceEntry OBJECT-TYPE
    SYNTAX     LcsSetupWanRouterInterfaceEntry
    MAX-ACCESS not-accessible
    STATUS     current
    DESCRIPTION
        ""
    INDEX {
        lcsSetupWanRouterInterfaceEntryIfc
    }
    ::= { lcsSetupWanRouterInterfaceTable 1 }

-- {SEQUENCE}
LcsSetupWanRouterInterfaceEntry ::= SEQUENCE {
    lcsSetupWanRouterInterfaceEntryIfc INTEGER,
    lcsSetupWanRouterInterfaceEntryMsnEaz DisplayString,
    lcsSetupWanRouterInterfaceEntryYc INTEGER,
    lcsSetupWanRouterInterfaceEntryClip INTEGER,
    lcsSetupWanRouterInterfaceEntryAcceptCalls INTEGER,
    lcsSetupWanRouterInterfaceEntryTypeOfInterface INTEGER
}

-- {COLUMN} 310.2.2.11.1.1
lcsSetupWanRouterInterfaceEntryIfc OBJECT-TYPE
    SYNTAX     INTEGER
      {
        eDsl1 (1),
        eModem (2)
      }
    MAX-ACCESS read-only
    STATUS     current
    DESCRIPTION
        "-- empty --"
    ::= { lcsSetupWanRouterInterfaceEntry 1 }

-- {COLUMN} 310.2.2.11.1.2
lcsSetupWanRouterInterfaceEntryMsnEaz OBJECT-TYPE
    SYNTAX     DisplayString (SIZE(0..30))
    MAX-ACCESS read-write
    STATUS     current
    DESCRIPTION
        "-- empty --"
    ::= { lcsSetupWanRouterInterfaceEntry 2 }

-- {COLUMN} 310.2.2.11.1.8
lcsSetupWanRouterInterfaceEntryYc OBJECT-TYPE
    SYNTAX     INTEGER
      {
        eYes (0),
        eNo (1)
      }
    MAX-ACCESS read-write
    STATUS     current
    DESCRIPTION
        "-- empty --"
    ::= { lcsSetupWanRouterInterfaceEntry 8 }

-- {COLUMN} 310.2.2.11.1.3
lcsSetupWanRouterInterfaceEntryClip OBJECT-TYPE
    SYNTAX     INTEGER
      {
        eYes (0),
        eNo (1)
      }
    MAX-ACCESS read-write
    STATUS     current
    DESCRIPTION
        "-- empty --"
    ::= { lcsSetupWanRouterInterfaceEntry 3 }

-- {COLUMN} 310.2.2.11.1.9
lcsSetupWanRouterInterfaceEntryAcceptCalls OBJECT-TYPE
    SYNTAX     INTEGER
      {
        eAll (0),
        eNone (128)
      }
    MAX-ACCESS read-write
    STATUS     current
    DESCRIPTION
        "-- empty --"
    ::= { lcsSetupWanRouterInterfaceEntry 9 }

-- {COLUMN} 310.2.2.11.1.10
lcsSetupWanRouterInterfaceEntryTypeOfInterface OBJECT-TYPE
    SYNTAX     INTEGER (0..2147483647)
    MAX-ACCESS read-only
    STATUS     current
    DESCRIPTION
        "-- empty --"
    ::= { lcsSetupWanRouterInterfaceEntry 10 }

-- {SCALAR} 310.2.2.7
lcsSetupWanDialPrefix OBJECT-TYPE
    SYNTAX     DisplayString (SIZE(0..8))
    MAX-ACCESS read-only
    STATUS     current
    DESCRIPTION
        "-- empty --"
    ::= { lcsSetupWan 7 }

-- {OID} 310.2.18
lcsSetupAccounting OBJECT IDENTIFIER ::= { lcsSetup 18 }

-- {SCALAR} 310.2.18.1
lcsSetupAccountingOperating OBJECT-TYPE
    SYNTAX     INTEGER
      {
        eNo (0),
        eYes (1)
      }
    MAX-ACCESS read-only
    STATUS     current
    DESCRIPTION
        "-- empty --"
    ::= { lcsSetupAccounting 1 }

-- {SCALAR} 310.2.18.2
lcsSetupAccountingSaveToFlashrom OBJECT-TYPE
    SYNTAX     INTEGER
      {
        eNo (0),
        eYes (1)
      }
    MAX-ACCESS read-only
    STATUS     current
    DESCRIPTION
        "-- empty --"
    ::= { lcsSetupAccounting 2 }

-- {SCALAR} 310.2.18.10
lcsSetupAccountingDiscriminator OBJECT-TYPE
    SYNTAX     INTEGER
      {
        eMacAddress (0),
        eIpAddress (1)
      }
    MAX-ACCESS read-only
    STATUS     current
    DESCRIPTION
        "-- empty --"
    ::= { lcsSetupAccounting 10 }

-- {SCALAR} 310.2.18.3
lcsSetupAccountingSortBy OBJECT-TYPE
    SYNTAX     INTEGER
      {
        eTime (0),
        eData (1)
      }
    MAX-ACCESS read-only
    STATUS     current
    DESCRIPTION
        "-- empty --"
    ::= { lcsSetupAccounting 3 }

-- {TABLE} 310.2.18.4
lcsSetupAccountingCurrentUserTable OBJECT-TYPE
    SYNTAX     SEQUENCE OF LcsSetupAccountingCurrentUserEntry
    MAX-ACCESS not-accessible
    STATUS     current
    DESCRIPTION
        "-- empty --"
    ::= { lcsSetupAccounting 4 }

-- {ENTRY} 310.2.18.4.1
lcsSetupAccountingCurrentUserEntry OBJECT-TYPE
    SYNTAX     LcsSetupAccountingCurrentUserEntry
    MAX-ACCESS not-accessible
    STATUS     current
    DESCRIPTION
        ""
    INDEX {
        lcsSetupAccountingCurrentUserEntryUsername,
        lcsSetupAccountingCurrentUserEntryMacAddress,
        lcsSetupAccountingCurrentUserEntryPeer,
        lcsSetupAccountingCurrentUserEntryConnType
    }
    ::= { lcsSetupAccountingCurrentUserTable 1 }

-- {SEQUENCE}
LcsSetupAccountingCurrentUserEntry ::= SEQUENCE {
    lcsSetupAccountingCurrentUserEntryUsername DisplayString,
    lcsSetupAccountingCurrentUserEntryMacAddress DisplayString,
    lcsSetupAccountingCurrentUserEntryPeer DisplayString,
    lcsSetupAccountingCurrentUserEntryConnType INTEGER,
    lcsSetupAccountingCurrentUserEntryRxKbytes INTEGER,
    lcsSetupAccountingCurrentUserEntryTxKbytes INTEGER,
    lcsSetupAccountingCurrentUserEntryTotalTime Gauge32,
    lcsSetupAccountingCurrentUserEntryConnections INTEGER
}

-- {COLUMN} 310.2.18.4.1.1
lcsSetupAccountingCurrentUserEntryUsername OBJECT-TYPE
    SYNTAX     DisplayString (SIZE(0..28))
    MAX-ACCESS read-only
    STATUS     current
    DESCRIPTION
        "-- empty --"
    ::= { lcsSetupAccountingCurrentUserEntry 1 }

-- {COLUMN} 310.2.18.4.1.2
lcsSetupAccountingCurrentUserEntryMacAddress OBJECT-TYPE
    SYNTAX     DisplayString (SIZE(0..255))
    MAX-ACCESS read-only
    STATUS     current
    DESCRIPTION
        "-- empty --"
    ::= { lcsSetupAccountingCurrentUserEntry 2 }

-- {COLUMN} 310.2.18.4.1.3
lcsSetupAccountingCurrentUserEntryPeer OBJECT-TYPE
    SYNTAX     DisplayString (SIZE(0..16))
    MAX-ACCESS read-only
    STATUS     current
    DESCRIPTION
        "-- empty --"
    ::= { lcsSetupAccountingCurrentUserEntry 3 }

-- {COLUMN} 310.2.18.4.1.4
lcsSetupAccountingCurrentUserEntryConnType OBJECT-TYPE
    SYNTAX     INTEGER
      {
        eUnknown (0),
        eDialUp (1),
        eLeasedLine (2),
        eDslLine (4),
        eVpnConn (7),
        ePptpConn (8)
      }
    MAX-ACCESS read-only
    STATUS     current
    DESCRIPTION
        "-- empty --"
    ::= { lcsSetupAccountingCurrentUserEntry 4 }

-- {COLUMN} 310.2.18.4.1.5
lcsSetupAccountingCurrentUserEntryRxKbytes OBJECT-TYPE
    SYNTAX     INTEGER (0..2147483647)
    MAX-ACCESS read-only
    STATUS     current
    DESCRIPTION
        "-- empty --"
    ::= { lcsSetupAccountingCurrentUserEntry 5 }

-- {COLUMN} 310.2.18.4.1.6
lcsSetupAccountingCurrentUserEntryTxKbytes OBJECT-TYPE
    SYNTAX     INTEGER (0..2147483647)
    MAX-ACCESS read-only
    STATUS     current
    DESCRIPTION
        "-- empty --"
    ::= { lcsSetupAccountingCurrentUserEntry 6 }

-- {COLUMN} 310.2.18.4.1.8
lcsSetupAccountingCurrentUserEntryTotalTime OBJECT-TYPE
    SYNTAX     Gauge32
    MAX-ACCESS read-only
    STATUS     current
    DESCRIPTION
        "-- empty --"
    ::= { lcsSetupAccountingCurrentUserEntry 8 }

-- {COLUMN} 310.2.18.4.1.9
lcsSetupAccountingCurrentUserEntryConnections OBJECT-TYPE
    SYNTAX     INTEGER (0..2147483647)
    MAX-ACCESS read-only
    STATUS     current
    DESCRIPTION
        "-- empty --"
    ::= { lcsSetupAccountingCurrentUserEntry 9 }

-- {TABLE} 310.2.18.5
lcsSetupAccountingAccountingListTable OBJECT-TYPE
    SYNTAX     SEQUENCE OF LcsSetupAccountingAccountingListEntry
    MAX-ACCESS not-accessible
    STATUS     current
    DESCRIPTION
        "-- empty --"
    ::= { lcsSetupAccounting 5 }

-- {ENTRY} 310.2.18.5.1
lcsSetupAccountingAccountingListEntry OBJECT-TYPE
    SYNTAX     LcsSetupAccountingAccountingListEntry
    MAX-ACCESS not-accessible
    STATUS     current
    DESCRIPTION
        ""
    INDEX {
        lcsSetupAccountingAccountingListEntryUsername,
        lcsSetupAccountingAccountingListEntryMacAddress,
        lcsSetupAccountingAccountingListEntryPeer,
        lcsSetupAccountingAccountingListEntryConnType
    }
    ::= { lcsSetupAccountingAccountingListTable 1 }

-- {SEQUENCE}
LcsSetupAccountingAccountingListEntry ::= SEQUENCE {
    lcsSetupAccountingAccountingListEntryUsername DisplayString,
    lcsSetupAccountingAccountingListEntryMacAddress DisplayString,
    lcsSetupAccountingAccountingListEntryPeer DisplayString,
    lcsSetupAccountingAccountingListEntryConnType INTEGER,
    lcsSetupAccountingAccountingListEntryRxKbytes INTEGER,
    lcsSetupAccountingAccountingListEntryTxKbytes INTEGER,
    lcsSetupAccountingAccountingListEntryTotalTime Gauge32,
    lcsSetupAccountingAccountingListEntryConnections INTEGER
}

-- {COLUMN} 310.2.18.5.1.1
lcsSetupAccountingAccountingListEntryUsername OBJECT-TYPE
    SYNTAX     DisplayString (SIZE(0..28))
    MAX-ACCESS read-only
    STATUS     current
    DESCRIPTION
        "-- empty --"
    ::= { lcsSetupAccountingAccountingListEntry 1 }

-- {COLUMN} 310.2.18.5.1.2
lcsSetupAccountingAccountingListEntryMacAddress OBJECT-TYPE
    SYNTAX     DisplayString (SIZE(0..255))
    MAX-ACCESS read-only
    STATUS     current
    DESCRIPTION
        "-- empty --"
    ::= { lcsSetupAccountingAccountingListEntry 2 }

-- {COLUMN} 310.2.18.5.1.3
lcsSetupAccountingAccountingListEntryPeer OBJECT-TYPE
    SYNTAX     DisplayString (SIZE(0..16))
    MAX-ACCESS read-only
    STATUS     current
    DESCRIPTION
        "-- empty --"
    ::= { lcsSetupAccountingAccountingListEntry 3 }

-- {COLUMN} 310.2.18.5.1.4
lcsSetupAccountingAccountingListEntryConnType OBJECT-TYPE
    SYNTAX     INTEGER
      {
        eUnknown (0),
        eDialUp (1),
        eLeasedLine (2),
        eDslLine (4),
        eVpnConn (7),
        ePptpConn (8)
      }
    MAX-ACCESS read-only
    STATUS     current
    DESCRIPTION
        "-- empty --"
    ::= { lcsSetupAccountingAccountingListEntry 4 }

-- {COLUMN} 310.2.18.5.1.5
lcsSetupAccountingAccountingListEntryRxKbytes OBJECT-TYPE
    SYNTAX     INTEGER (0..2147483647)
    MAX-ACCESS read-only
    STATUS     current
    DESCRIPTION
        "-- empty --"
    ::= { lcsSetupAccountingAccountingListEntry 5 }

-- {COLUMN} 310.2.18.5.1.6
lcsSetupAccountingAccountingListEntryTxKbytes OBJECT-TYPE
    SYNTAX     INTEGER (0..2147483647)
    MAX-ACCESS read-only
    STATUS     current
    DESCRIPTION
        "-- empty --"
    ::= { lcsSetupAccountingAccountingListEntry 6 }

-- {COLUMN} 310.2.18.5.1.8
lcsSetupAccountingAccountingListEntryTotalTime OBJECT-TYPE
    SYNTAX     Gauge32
    MAX-ACCESS read-only
    STATUS     current
    DESCRIPTION
        "-- empty --"
    ::= { lcsSetupAccountingAccountingListEntry 8 }

-- {COLUMN} 310.2.18.5.1.9
lcsSetupAccountingAccountingListEntryConnections OBJECT-TYPE
    SYNTAX     INTEGER (0..2147483647)
    MAX-ACCESS read-only
    STATUS     current
    DESCRIPTION
        "-- empty --"
    ::= { lcsSetupAccountingAccountingListEntry 9 }

-- {SCALAR} 310.2.18.6
lcsSetupAccountingDeleteAccountingList OBJECT-TYPE
    SYNTAX     DisplayString
    MAX-ACCESS read-write
    STATUS     current
    DESCRIPTION
        "-- empty --"
    ::= { lcsSetupAccounting 6 }

-- {TABLE} 310.2.18.8
lcsSetupAccountingTimeSnapshotTable OBJECT-TYPE
    SYNTAX     SEQUENCE OF LcsSetupAccountingTimeSnapshotEntry
    MAX-ACCESS not-accessible
    STATUS     current
    DESCRIPTION
        "-- empty --"
    ::= { lcsSetupAccounting 8 }

-- {ENTRY} 310.2.18.8.1
lcsSetupAccountingTimeSnapshotEntry OBJECT-TYPE
    SYNTAX     LcsSetupAccountingTimeSnapshotEntry
    MAX-ACCESS not-accessible
    STATUS     current
    DESCRIPTION
        ""
    INDEX {
        lcsSetupAccountingTimeSnapshotEntryIndex
    }
    ::= { lcsSetupAccountingTimeSnapshotTable 1 }

-- {SEQUENCE}
LcsSetupAccountingTimeSnapshotEntry ::= SEQUENCE {
    lcsSetupAccountingTimeSnapshotEntryIndex INTEGER,
    lcsSetupAccountingTimeSnapshotEntryActive INTEGER,
    lcsSetupAccountingTimeSnapshotEntryType INTEGER,
    lcsSetupAccountingTimeSnapshotEntryDay INTEGER,
    lcsSetupAccountingTimeSnapshotEntryDayofweek INTEGER,
    lcsSetupAccountingTimeSnapshotEntryHour INTEGER,
    lcsSetupAccountingTimeSnapshotEntryMinute INTEGER
}

-- {COLUMN} 310.2.18.8.1.1
lcsSetupAccountingTimeSnapshotEntryIndex OBJECT-TYPE
    SYNTAX     INTEGER (0..255)
    MAX-ACCESS read-only
    STATUS     current
    DESCRIPTION
        "-- empty --"
    ::= { lcsSetupAccountingTimeSnapshotEntry 1 }

-- {COLUMN} 310.2.18.8.1.2
lcsSetupAccountingTimeSnapshotEntryActive OBJECT-TYPE
    SYNTAX     INTEGER
      {
        eYes (1),
        eNo (0)
      }
    MAX-ACCESS read-write
    STATUS     current
    DESCRIPTION
        "-- empty --"
    ::= { lcsSetupAccountingTimeSnapshotEntry 2 }

-- {COLUMN} 310.2.18.8.1.3
lcsSetupAccountingTimeSnapshotEntryType OBJECT-TYPE
    SYNTAX     INTEGER
      {
        eMonthly (0),
        eWeekly (1),
        eDaily (2)
      }
    MAX-ACCESS read-write
    STATUS     current
    DESCRIPTION
        "-- empty --"
    ::= { lcsSetupAccountingTimeSnapshotEntry 3 }

-- {COLUMN} 310.2.18.8.1.4
lcsSetupAccountingTimeSnapshotEntryDay OBJECT-TYPE
    SYNTAX     INTEGER (0..255)
    MAX-ACCESS read-write
    STATUS     current
    DESCRIPTION
        "-- empty --"
    ::= { lcsSetupAccountingTimeSnapshotEntry 4 }

-- {COLUMN} 310.2.18.8.1.5
lcsSetupAccountingTimeSnapshotEntryDayofweek OBJECT-TYPE
    SYNTAX     INTEGER
      {
        eUnknown (0),
        eSunday (1),
        eMonday (2),
        eTuesday (3),
        eWednesday (4),
        eThursday (5),
        eFriday (6),
        eSaturday (7)
      }
    MAX-ACCESS read-write
    STATUS     current
    DESCRIPTION
        "-- empty --"
    ::= { lcsSetupAccountingTimeSnapshotEntry 5 }

-- {COLUMN} 310.2.18.8.1.6
lcsSetupAccountingTimeSnapshotEntryHour OBJECT-TYPE
    SYNTAX     INTEGER (0..255)
    MAX-ACCESS read-write
    STATUS     current
    DESCRIPTION
        "-- empty --"
    ::= { lcsSetupAccountingTimeSnapshotEntry 6 }

-- {COLUMN} 310.2.18.8.1.7
lcsSetupAccountingTimeSnapshotEntryMinute OBJECT-TYPE
    SYNTAX     INTEGER (0..255)
    MAX-ACCESS read-write
    STATUS     current
    DESCRIPTION
        "-- empty --"
    ::= { lcsSetupAccountingTimeSnapshotEntry 7 }

-- {TABLE} 310.2.18.9
lcsSetupAccountingLastSnapshotTable OBJECT-TYPE
    SYNTAX     SEQUENCE OF LcsSetupAccountingLastSnapshotEntry
    MAX-ACCESS not-accessible
    STATUS     current
    DESCRIPTION
        "-- empty --"
    ::= { lcsSetupAccounting 9 }

-- {ENTRY} 310.2.18.9.1
lcsSetupAccountingLastSnapshotEntry OBJECT-TYPE
    SYNTAX     LcsSetupAccountingLastSnapshotEntry
    MAX-ACCESS not-accessible
    STATUS     current
    DESCRIPTION
        ""
    INDEX {
        lcsSetupAccountingLastSnapshotEntryUsername,
        lcsSetupAccountingLastSnapshotEntryMacAddress,
        lcsSetupAccountingLastSnapshotEntryPeer,
        lcsSetupAccountingLastSnapshotEntryConnType
    }
    ::= { lcsSetupAccountingLastSnapshotTable 1 }

-- {SEQUENCE}
LcsSetupAccountingLastSnapshotEntry ::= SEQUENCE {
    lcsSetupAccountingLastSnapshotEntryUsername DisplayString,
    lcsSetupAccountingLastSnapshotEntryMacAddress DisplayString,
    lcsSetupAccountingLastSnapshotEntryPeer DisplayString,
    lcsSetupAccountingLastSnapshotEntryConnType INTEGER,
    lcsSetupAccountingLastSnapshotEntryRxKbytes INTEGER,
    lcsSetupAccountingLastSnapshotEntryTxKbytes INTEGER,
    lcsSetupAccountingLastSnapshotEntryTotalTime Gauge32,
    lcsSetupAccountingLastSnapshotEntryConnections INTEGER
}

-- {COLUMN} 310.2.18.9.1.1
lcsSetupAccountingLastSnapshotEntryUsername OBJECT-TYPE
    SYNTAX     DisplayString (SIZE(0..28))
    MAX-ACCESS read-only
    STATUS     current
    DESCRIPTION
        "-- empty --"
    ::= { lcsSetupAccountingLastSnapshotEntry 1 }

-- {COLUMN} 310.2.18.9.1.2
lcsSetupAccountingLastSnapshotEntryMacAddress OBJECT-TYPE
    SYNTAX     DisplayString (SIZE(0..255))
    MAX-ACCESS read-only
    STATUS     current
    DESCRIPTION
        "-- empty --"
    ::= { lcsSetupAccountingLastSnapshotEntry 2 }

-- {COLUMN} 310.2.18.9.1.3
lcsSetupAccountingLastSnapshotEntryPeer OBJECT-TYPE
    SYNTAX     DisplayString (SIZE(0..16))
    MAX-ACCESS read-only
    STATUS     current
    DESCRIPTION
        "-- empty --"
    ::= { lcsSetupAccountingLastSnapshotEntry 3 }

-- {COLUMN} 310.2.18.9.1.4
lcsSetupAccountingLastSnapshotEntryConnType OBJECT-TYPE
    SYNTAX     INTEGER
      {
        eUnknown (0),
        eDialUp (1),
        eLeasedLine (2),
        eDslLine (4),
        eVpnConn (7),
        ePptpConn (8)
      }
    MAX-ACCESS read-only
    STATUS     current
    DESCRIPTION
        "-- empty --"
    ::= { lcsSetupAccountingLastSnapshotEntry 4 }

-- {COLUMN} 310.2.18.9.1.5
lcsSetupAccountingLastSnapshotEntryRxKbytes OBJECT-TYPE
    SYNTAX     INTEGER (0..2147483647)
    MAX-ACCESS read-only
    STATUS     current
    DESCRIPTION
        "-- empty --"
    ::= { lcsSetupAccountingLastSnapshotEntry 5 }

-- {COLUMN} 310.2.18.9.1.6
lcsSetupAccountingLastSnapshotEntryTxKbytes OBJECT-TYPE
    SYNTAX     INTEGER (0..2147483647)
    MAX-ACCESS read-only
    STATUS     current
    DESCRIPTION
        "-- empty --"
    ::= { lcsSetupAccountingLastSnapshotEntry 6 }

-- {COLUMN} 310.2.18.9.1.8
lcsSetupAccountingLastSnapshotEntryTotalTime OBJECT-TYPE
    SYNTAX     Gauge32
    MAX-ACCESS read-only
    STATUS     current
    DESCRIPTION
        "-- empty --"
    ::= { lcsSetupAccountingLastSnapshotEntry 8 }

-- {COLUMN} 310.2.18.9.1.9
lcsSetupAccountingLastSnapshotEntryConnections OBJECT-TYPE
    SYNTAX     INTEGER (0..2147483647)
    MAX-ACCESS read-only
    STATUS     current
    DESCRIPTION
        "-- empty --"
    ::= { lcsSetupAccountingLastSnapshotEntry 9 }

-- {OID} 310.2.3
lcsSetupCharges OBJECT IDENTIFIER ::= { lcsSetup 3 }

-- {SCALAR} 310.2.3.2
lcsSetupChargesDaysPerPeriod OBJECT-TYPE
    SYNTAX     INTEGER (0..65535)
    MAX-ACCESS read-only
    STATUS     current
    DESCRIPTION
        "-- empty --"
    ::= { lcsSetupCharges 2 }

-- {SCALAR} 310.2.3.13
lcsSetupChargesDialupMinutesBudget OBJECT-TYPE
    SYNTAX     INTEGER (0..2147483647)
    MAX-ACCESS read-only
    STATUS     current
    DESCRIPTION
        "-- empty --"
    ::= { lcsSetupCharges 13 }

-- {SCALAR} 310.2.3.14
lcsSetupChargesSpareDialupMinutes OBJECT-TYPE
    SYNTAX     INTEGER (0..2147483647)
    MAX-ACCESS read-only
    STATUS     current
    DESCRIPTION
        "-- empty --"
    ::= { lcsSetupCharges 14 }

-- {SCALAR} 310.2.3.15
lcsSetupChargesDialupMinutesActive OBJECT-TYPE
    SYNTAX     INTEGER (0..2147483647)
    MAX-ACCESS read-only
    STATUS     current
    DESCRIPTION
        "-- empty --"
    ::= { lcsSetupCharges 15 }

-- {TABLE} 310.2.3.7
lcsSetupChargesTimeTableTable OBJECT-TYPE
    SYNTAX     SEQUENCE OF LcsSetupChargesTimeTableEntry
    MAX-ACCESS not-accessible
    STATUS     current
    DESCRIPTION
        "-- empty --"
    ::= { lcsSetupCharges 7 }

-- {ENTRY} 310.2.3.7.1
lcsSetupChargesTimeTableEntry OBJECT-TYPE
    SYNTAX     LcsSetupChargesTimeTableEntry
    MAX-ACCESS not-accessible
    STATUS     current
    DESCRIPTION
        ""
    INDEX {
        lcsSetupChargesTimeTableEntryIfc
    }
    ::= { lcsSetupChargesTimeTableTable 1 }

-- {SEQUENCE}
LcsSetupChargesTimeTableEntry ::= SEQUENCE {
    lcsSetupChargesTimeTableEntryIfc INTEGER,
    lcsSetupChargesTimeTableEntryBudgetMinutes INTEGER,
    lcsSetupChargesTimeTableEntrySpareMinutes INTEGER,
    lcsSetupChargesTimeTableEntryMinutesActive INTEGER,
    lcsSetupChargesTimeTableEntryMinutesPassive INTEGER
}

-- {COLUMN} 310.2.3.7.1.1
lcsSetupChargesTimeTableEntryIfc OBJECT-TYPE
    SYNTAX     INTEGER
      {
        eRouterDslBroadband (1),
        eRouterSerial (2),
        eLancapi (3),
        eAb1 (4),
        eAb2 (5),
        eAb3 (6),
        eAb4 (7),
        eTimeModul (255)
      }
    MAX-ACCESS read-only
    STATUS     current
    DESCRIPTION
        "-- empty --"
    ::= { lcsSetupChargesTimeTableEntry 1 }

-- {COLUMN} 310.2.3.7.1.2
lcsSetupChargesTimeTableEntryBudgetMinutes OBJECT-TYPE
    SYNTAX     INTEGER (0..2147483647)
    MAX-ACCESS read-only
    STATUS     current
    DESCRIPTION
        "-- empty --"
    ::= { lcsSetupChargesTimeTableEntry 2 }

-- {COLUMN} 310.2.3.7.1.3
lcsSetupChargesTimeTableEntrySpareMinutes OBJECT-TYPE
    SYNTAX     INTEGER (0..2147483647)
    MAX-ACCESS read-only
    STATUS     current
    DESCRIPTION
        "-- empty --"
    ::= { lcsSetupChargesTimeTableEntry 3 }

-- {COLUMN} 310.2.3.7.1.4
lcsSetupChargesTimeTableEntryMinutesActive OBJECT-TYPE
    SYNTAX     INTEGER (0..2147483647)
    MAX-ACCESS read-only
    STATUS     current
    DESCRIPTION
        "-- empty --"
    ::= { lcsSetupChargesTimeTableEntry 4 }

-- {COLUMN} 310.2.3.7.1.5
lcsSetupChargesTimeTableEntryMinutesPassive OBJECT-TYPE
    SYNTAX     INTEGER (0..2147483647)
    MAX-ACCESS read-only
    STATUS     current
    DESCRIPTION
        "-- empty --"
    ::= { lcsSetupChargesTimeTableEntry 5 }

-- {SCALAR} 310.2.3.8
lcsSetupChargesDslBroadbandMinutesBudget OBJECT-TYPE
    SYNTAX     INTEGER (0..2147483647)
    MAX-ACCESS read-only
    STATUS     current
    DESCRIPTION
        "-- empty --"
    ::= { lcsSetupCharges 8 }

-- {SCALAR} 310.2.3.11
lcsSetupChargesAdditionalDslBroadbandBudget OBJECT-TYPE
    SYNTAX     INTEGER (0..2147483647)
    MAX-ACCESS read-only
    STATUS     current
    DESCRIPTION
        "-- empty --"
    ::= { lcsSetupCharges 11 }

-- {SCALAR} 310.2.3.9
lcsSetupChargesSpareDslBroadbandMinutes OBJECT-TYPE
    SYNTAX     INTEGER (0..2147483647)
    MAX-ACCESS read-only
    STATUS     current
    DESCRIPTION
        "-- empty --"
    ::= { lcsSetupCharges 9 }

-- {SCALAR} 310.2.3.10
lcsSetupChargesRouterDslBroadbandMinutesActive OBJECT-TYPE
    SYNTAX     INTEGER (0..2147483647)
    MAX-ACCESS read-only
    STATUS     current
    DESCRIPTION
        "-- empty --"
    ::= { lcsSetupCharges 10 }

-- {SCALAR} 310.2.3.12
lcsSetupChargesActivateAdditionalBudget OBJECT-TYPE
    SYNTAX     DisplayString
    MAX-ACCESS read-write
    STATUS     current
    DESCRIPTION
        "-- empty --"
    ::= { lcsSetupCharges 12 }

-- {SCALAR} 310.2.3.16
lcsSetupChargesResetBudgets OBJECT-TYPE
    SYNTAX     DisplayString
    MAX-ACCESS read-write
    STATUS     current
    DESCRIPTION
        "-- empty --"
    ::= { lcsSetupCharges 16 }

-- {OID} 310.2.4
lcsSetupLan OBJECT IDENTIFIER ::= { lcsSetup 4 }

-- {SCALAR} 310.2.4.2
lcsSetupLanMacAddress OBJECT-TYPE
    SYNTAX     MacAddress
    MAX-ACCESS read-only
    STATUS     current
    DESCRIPTION
        "-- empty --"
    ::= { lcsSetupLan 2 }

-- {SCALAR} 310.2.4.3
lcsSetupLanSpareHeap OBJECT-TYPE
    SYNTAX     INTEGER (0..65535)
    MAX-ACCESS read-only
    STATUS     current
    DESCRIPTION
        "-- empty --"
    ::= { lcsSetupLan 3 }

-- {SCALAR} 310.2.4.8
lcsSetupLanTraceMac OBJECT-TYPE
    SYNTAX     MacAddress
    MAX-ACCESS read-write
    STATUS     current
    DESCRIPTION
        "-- empty --"
    ::= { lcsSetupLan 8 }

-- {SCALAR} 310.2.4.9
lcsSetupLanTraceLevel OBJECT-TYPE
    SYNTAX     INTEGER (0..255)
    MAX-ACCESS read-write
    STATUS     current
    DESCRIPTION
        "-- empty --"
    ::= { lcsSetupLan 9 }

-- {OID} 310.2.4.10
lcsSetupLanIeee8021x OBJECT IDENTIFIER ::= { lcsSetupLan 10 }

-- {TABLE} 310.2.4.10.1
lcsSetupLanIeee8021xSupplicantIfcSetupTable OBJECT-TYPE
    SYNTAX     SEQUENCE OF LcsSetupLanIeee8021xSupplicantIfcSetupEntry
    MAX-ACCESS not-accessible
    STATUS     current
    DESCRIPTION
        "-- empty --"
    ::= { lcsSetupLanIeee8021x 1 }

-- {ENTRY} 310.2.4.10.1.1
lcsSetupLanIeee8021xSupplicantIfcSetupEntry OBJECT-TYPE
    SYNTAX     LcsSetupLanIeee8021xSupplicantIfcSetupEntry
    MAX-ACCESS not-accessible
    STATUS     current
    DESCRIPTION
        ""
    INDEX {
        lcsSetupLanIeee8021xSupplicantIfcSetupEntryIfc
    }
    ::= { lcsSetupLanIeee8021xSupplicantIfcSetupTable 1 }

-- {SEQUENCE}
LcsSetupLanIeee8021xSupplicantIfcSetupEntry ::= SEQUENCE {
    lcsSetupLanIeee8021xSupplicantIfcSetupEntryIfc INTEGER,
    lcsSetupLanIeee8021xSupplicantIfcSetupEntryMethod INTEGER,
    lcsSetupLanIeee8021xSupplicantIfcSetupEntryCredentials DisplayString
}

-- {COLUMN} 310.2.4.10.1.1.1
lcsSetupLanIeee8021xSupplicantIfcSetupEntryIfc OBJECT-TYPE
    SYNTAX     INTEGER
      {
        eLan1 (1)
      }
    MAX-ACCESS read-only
    STATUS     current
    DESCRIPTION
        "-- empty --"
    ::= { lcsSetupLanIeee8021xSupplicantIfcSetupEntry 1 }

-- {COLUMN} 310.2.4.10.1.1.2
lcsSetupLanIeee8021xSupplicantIfcSetupEntryMethod OBJECT-TYPE
    SYNTAX     INTEGER
      {
        eNone (0),
        eMd5 (1024),
        eTls (3328),
        eTtlsPap (5383),
        eTtlsChap (5384),
        eTtlsMschap (5567),
        eTtlsMschapv2 (5402),
        eTtlsMd5 (5380),
        ePeapMschapv2 (6426),
        ePeapGtc (6406)
      }
    MAX-ACCESS read-write
    STATUS     current
    DESCRIPTION
        "-- empty --"
    ::= { lcsSetupLanIeee8021xSupplicantIfcSetupEntry 2 }

-- {COLUMN} 310.2.4.10.1.1.3
lcsSetupLanIeee8021xSupplicantIfcSetupEntryCredentials OBJECT-TYPE
    SYNTAX     DisplayString (SIZE(0..64))
    MAX-ACCESS read-write
    STATUS     current
    DESCRIPTION
        "-- empty --"
    ::= { lcsSetupLanIeee8021xSupplicantIfcSetupEntry 3 }

-- {SCALAR} 310.2.4.11
lcsSetupLanLinkupReportDelayMs OBJECT-TYPE
    SYNTAX     INTEGER (0..2147483647)
    MAX-ACCESS read-write
    STATUS     current
    DESCRIPTION
        "-- empty --"
    ::= { lcsSetupLan 11 }

-- {OID} 310.2.7
lcsSetupTcpIp OBJECT IDENTIFIER ::= { lcsSetup 7 }

-- {SCALAR} 310.2.7.1
lcsSetupTcpIpOperating OBJECT-TYPE
    SYNTAX     INTEGER
      {
        eNo (0),
        eYes (1)
      }
    MAX-ACCESS read-only
    STATUS     current
    DESCRIPTION
        "-- empty --"
    ::= { lcsSetupTcpIp 1 }

-- {TABLE} 310.2.7.30
lcsSetupTcpIpNetworkListTable OBJECT-TYPE
    SYNTAX     SEQUENCE OF LcsSetupTcpIpNetworkListEntry
    MAX-ACCESS not-accessible
    STATUS     current
    DESCRIPTION
        "-- empty --"
    ::= { lcsSetupTcpIp 30 }

-- {ENTRY} 310.2.7.30.1
lcsSetupTcpIpNetworkListEntry OBJECT-TYPE
    SYNTAX     LcsSetupTcpIpNetworkListEntry
    MAX-ACCESS not-accessible
    STATUS     current
    DESCRIPTION
        ""
    INDEX {
        lcsSetupTcpIpNetworkListEntryNetworkName
    }
    ::= { lcsSetupTcpIpNetworkListTable 1 }

-- {SEQUENCE}
LcsSetupTcpIpNetworkListEntry ::= SEQUENCE {
    lcsSetupTcpIpNetworkListEntryNetworkName DisplayString,
    lcsSetupTcpIpNetworkListEntryIpAddress IpAddress,
    lcsSetupTcpIpNetworkListEntryIpNetmask IpAddress,
    lcsSetupTcpIpNetworkListEntryVlanId INTEGER,
    lcsSetupTcpIpNetworkListEntryInterface INTEGER,
    lcsSetupTcpIpNetworkListEntrySrcCheck INTEGER,
    lcsSetupTcpIpNetworkListEntryType INTEGER,
    lcsSetupTcpIpNetworkListEntryRtgTag INTEGER,
    lcsSetupTcpIpNetworkListEntryComment DisplayString
}

-- {COLUMN} 310.2.7.30.1.1
lcsSetupTcpIpNetworkListEntryNetworkName OBJECT-TYPE
    SYNTAX     DisplayString (SIZE(0..17))
    MAX-ACCESS read-write
    STATUS     current
    DESCRIPTION
        "-- empty --"
    ::= { lcsSetupTcpIpNetworkListEntry 1 }

-- {COLUMN} 310.2.7.30.1.2
lcsSetupTcpIpNetworkListEntryIpAddress OBJECT-TYPE
    SYNTAX     IpAddress
    MAX-ACCESS read-write
    STATUS     current
    DESCRIPTION
        "-- empty --"
    ::= { lcsSetupTcpIpNetworkListEntry 2 }

-- {COLUMN} 310.2.7.30.1.3
lcsSetupTcpIpNetworkListEntryIpNetmask OBJECT-TYPE
    SYNTAX     IpAddress
    MAX-ACCESS read-write
    STATUS     current
    DESCRIPTION
        "-- empty --"
    ::= { lcsSetupTcpIpNetworkListEntry 3 }

-- {COLUMN} 310.2.7.30.1.4
lcsSetupTcpIpNetworkListEntryVlanId OBJECT-TYPE
    SYNTAX     INTEGER (0..65535)
    MAX-ACCESS read-write
    STATUS     current
    DESCRIPTION
        "-- empty --"
    ::= { lcsSetupTcpIpNetworkListEntry 4 }

-- {COLUMN} 310.2.7.30.1.5
lcsSetupTcpIpNetworkListEntryInterface OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-write
    STATUS     current
    DESCRIPTION
        "-- empty --"
    ::= { lcsSetupTcpIpNetworkListEntry 5 }

-- {COLUMN} 310.2.7.30.1.6
lcsSetupTcpIpNetworkListEntrySrcCheck OBJECT-TYPE
    SYNTAX     INTEGER
      {
        eStrict (1),
        eLoose (0)
      }
    MAX-ACCESS read-write
    STATUS     current
    DESCRIPTION
        "-- empty --"
    ::= { lcsSetupTcpIpNetworkListEntry 6 }

-- {COLUMN} 310.2.7.30.1.7
lcsSetupTcpIpNetworkListEntryType OBJECT-TYPE
    SYNTAX     INTEGER
      {
        eDisabled (0),
        eIntranet (1),
        eDmz (2)
      }
    MAX-ACCESS read-write
    STATUS     current
    DESCRIPTION
        "-- empty --"
    ::= { lcsSetupTcpIpNetworkListEntry 7 }

-- {COLUMN} 310.2.7.30.1.8
lcsSetupTcpIpNetworkListEntryRtgTag OBJECT-TYPE
    SYNTAX     INTEGER (0..65535)
    MAX-ACCESS read-write
    STATUS     current
    DESCRIPTION
        "-- empty --"
    ::= { lcsSetupTcpIpNetworkListEntry 8 }

-- {COLUMN} 310.2.7.30.1.9
lcsSetupTcpIpNetworkListEntryComment OBJECT-TYPE
    SYNTAX     DisplayString (SIZE(0..64))
    MAX-ACCESS read-write
    STATUS     current
    DESCRIPTION
        "-- empty --"
    ::= { lcsSetupTcpIpNetworkListEntry 9 }

-- {TABLE} 310.2.7.17
lcsSetupTcpIpLoopbackListTable OBJECT-TYPE
    SYNTAX     SEQUENCE OF LcsSetupTcpIpLoopbackListEntry
    MAX-ACCESS not-accessible
    STATUS     current
    DESCRIPTION
        "-- empty --"
    ::= { lcsSetupTcpIp 17 }

-- {ENTRY} 310.2.7.17.1
lcsSetupTcpIpLoopbackListEntry OBJECT-TYPE
    SYNTAX     LcsSetupTcpIpLoopbackListEntry
    MAX-ACCESS not-accessible
    STATUS     current
    DESCRIPTION
        ""
    INDEX {
        lcsSetupTcpIpLoopbackListEntryName
    }
    ::= { lcsSetupTcpIpLoopbackListTable 1 }

-- {SEQUENCE}
LcsSetupTcpIpLoopbackListEntry ::= SEQUENCE {
    lcsSetupTcpIpLoopbackListEntryName DisplayString,
    lcsSetupTcpIpLoopbackListEntryLoopbackAddr IpAddress,
    lcsSetupTcpIpLoopbackListEntryRtgTag INTEGER
}

-- {COLUMN} 310.2.7.17.1.2
lcsSetupTcpIpLoopbackListEntryName OBJECT-TYPE
    SYNTAX     DisplayString (SIZE(0..16))
    MAX-ACCESS read-write
    STATUS     current
    DESCRIPTION
        "-- empty --"
    ::= { lcsSetupTcpIpLoopbackListEntry 2 }

-- {COLUMN} 310.2.7.17.1.1
lcsSetupTcpIpLoopbackListEntryLoopbackAddr OBJECT-TYPE
    SYNTAX     IpAddress
    MAX-ACCESS read-write
    STATUS     current
    DESCRIPTION
        "-- empty --"
    ::= { lcsSetupTcpIpLoopbackListEntry 1 }

-- {COLUMN} 310.2.7.17.1.3
lcsSetupTcpIpLoopbackListEntryRtgTag OBJECT-TYPE
    SYNTAX     INTEGER (0..65535)
    MAX-ACCESS read-write
    STATUS     current
    DESCRIPTION
        "-- empty --"
    ::= { lcsSetupTcpIpLoopbackListEntry 3 }

-- {TABLE} 310.2.7.6
lcsSetupTcpIpAccessListTable OBJECT-TYPE
    SYNTAX     SEQUENCE OF LcsSetupTcpIpAccessListEntry
    MAX-ACCESS not-accessible
    STATUS     current
    DESCRIPTION
        "-- empty --"
    ::= { lcsSetupTcpIp 6 }

-- {ENTRY} 310.2.7.6.1
lcsSetupTcpIpAccessListEntry OBJECT-TYPE
    SYNTAX     LcsSetupTcpIpAccessListEntry
    MAX-ACCESS not-accessible
    STATUS     current
    DESCRIPTION
        ""
    INDEX {
        lcsSetupTcpIpAccessListEntryIpAddress,
        lcsSetupTcpIpAccessListEntryIpNetmask,
        lcsSetupTcpIpAccessListEntryRtgTag
    }
    ::= { lcsSetupTcpIpAccessListTable 1 }

-- {SEQUENCE}
LcsSetupTcpIpAccessListEntry ::= SEQUENCE {
    lcsSetupTcpIpAccessListEntryIpAddress IpAddress,
    lcsSetupTcpIpAccessListEntryIpNetmask IpAddress,
    lcsSetupTcpIpAccessListEntryRtgTag INTEGER
}

-- {COLUMN} 310.2.7.6.1.1
lcsSetupTcpIpAccessListEntryIpAddress OBJECT-TYPE
    SYNTAX     IpAddress
    MAX-ACCESS read-write
    STATUS     current
    DESCRIPTION
        "-- empty --"
    ::= { lcsSetupTcpIpAccessListEntry 1 }

-- {COLUMN} 310.2.7.6.1.2
lcsSetupTcpIpAccessListEntryIpNetmask OBJECT-TYPE
    SYNTAX     IpAddress
    MAX-ACCESS read-write
    STATUS     current
    DESCRIPTION
        "-- empty --"
    ::= { lcsSetupTcpIpAccessListEntry 2 }

-- {COLUMN} 310.2.7.6.1.3
lcsSetupTcpIpAccessListEntryRtgTag OBJECT-TYPE
    SYNTAX     INTEGER (0..65535)
    MAX-ACCESS read-write
    STATUS     current
    DESCRIPTION
        "-- empty --"
    ::= { lcsSetupTcpIpAccessListEntry 3 }

-- {SCALAR} 310.2.7.7
lcsSetupTcpIpDnsDefault OBJECT-TYPE
    SYNTAX     IpAddress
    MAX-ACCESS read-only
    STATUS     current
    DESCRIPTION
        "-- empty --"
    ::= { lcsSetupTcpIp 7 }

-- {SCALAR} 310.2.7.8
lcsSetupTcpIpDnsBackup OBJECT-TYPE
    SYNTAX     IpAddress
    MAX-ACCESS read-only
    STATUS     current
    DESCRIPTION
        "-- empty --"
    ::= { lcsSetupTcpIp 8 }

-- {SCALAR} 310.2.7.9
lcsSetupTcpIpNbnsDefault OBJECT-TYPE
    SYNTAX     IpAddress
    MAX-ACCESS read-only
    STATUS     current
    DESCRIPTION
        "-- empty --"
    ::= { lcsSetupTcpIp 9 }

-- {SCALAR} 310.2.7.10
lcsSetupTcpIpNbnsBackup OBJECT-TYPE
    SYNTAX     IpAddress
    MAX-ACCESS read-only
    STATUS     current
    DESCRIPTION
        "-- empty --"
    ::= { lcsSetupTcpIp 10 }

-- {TABLE} 310.2.7.16
lcsSetupTcpIpArpTableTable OBJECT-TYPE
    SYNTAX     SEQUENCE OF LcsSetupTcpIpArpTableEntry
    MAX-ACCESS not-accessible
    STATUS     current
    DESCRIPTION
        "-- empty --"
    ::= { lcsSetupTcpIp 16 }

-- {ENTRY} 310.2.7.16.1
lcsSetupTcpIpArpTableEntry OBJECT-TYPE
    SYNTAX     LcsSetupTcpIpArpTableEntry
    MAX-ACCESS not-accessible
    STATUS     current
    DESCRIPTION
        ""
    INDEX {
        lcsSetupTcpIpArpTableEntryIpAddress
    }
    ::= { lcsSetupTcpIpArpTableTable 1 }

-- {SEQUENCE}
LcsSetupTcpIpArpTableEntry ::= SEQUENCE {
    lcsSetupTcpIpArpTableEntryIpAddress IpAddress,
    lcsSetupTcpIpArpTableEntryMacAddress MacAddress,
    lcsSetupTcpIpArpTableEntryLastAccess INTEGER,
    lcsSetupTcpIpArpTableEntryConnect INTEGER,
    lcsSetupTcpIpArpTableEntryVlanId INTEGER,
    lcsSetupTcpIpArpTableEntryPeer DisplayString
}

-- {COLUMN} 310.2.7.16.1.1
lcsSetupTcpIpArpTableEntryIpAddress OBJECT-TYPE
    SYNTAX     IpAddress
    MAX-ACCESS read-only
    STATUS     current
    DESCRIPTION
        "-- empty --"
    ::= { lcsSetupTcpIpArpTableEntry 1 }

-- {COLUMN} 310.2.7.16.1.2
lcsSetupTcpIpArpTableEntryMacAddress OBJECT-TYPE
    SYNTAX     MacAddress
    MAX-ACCESS read-only
    STATUS     current
    DESCRIPTION
        "-- empty --"
    ::= { lcsSetupTcpIpArpTableEntry 2 }

-- {COLUMN} 310.2.7.16.1.3
lcsSetupTcpIpArpTableEntryLastAccess OBJECT-TYPE
    SYNTAX     INTEGER (0..2147483647)
    MAX-ACCESS read-only
    STATUS     current
    DESCRIPTION
        "-- empty --"
    ::= { lcsSetupTcpIpArpTableEntry 3 }

-- {COLUMN} 310.2.7.16.1.8
lcsSetupTcpIpArpTableEntryConnect OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eWan (32768)
      }
    MAX-ACCESS read-only
    STATUS     current
    DESCRIPTION
        "-- empty --"
    ::= { lcsSetupTcpIpArpTableEntry 8 }

-- {COLUMN} 310.2.7.16.1.7
lcsSetupTcpIpArpTableEntryVlanId OBJECT-TYPE
    SYNTAX     INTEGER (0..65535)
    MAX-ACCESS read-only
    STATUS     current
    DESCRIPTION
        "-- empty --"
    ::= { lcsSetupTcpIpArpTableEntry 7 }

-- {COLUMN} 310.2.7.16.1.6
lcsSetupTcpIpArpTableEntryPeer OBJECT-TYPE
    SYNTAX     DisplayString (SIZE(0..255))
    MAX-ACCESS read-only
    STATUS     current
    DESCRIPTION
        "-- empty --"
    ::= { lcsSetupTcpIpArpTableEntry 6 }

-- {SCALAR} 310.2.7.20
lcsSetupTcpIpNonLocArpReplies OBJECT-TYPE
    SYNTAX     INTEGER
      {
        eNo (0),
        eYes (1)
      }
    MAX-ACCESS read-only
    STATUS     current
    DESCRIPTION
        "-- empty --"
    ::= { lcsSetupTcpIp 20 }

-- {SCALAR} 310.2.7.22
lcsSetupTcpIpIcmpOnArpTimeout OBJECT-TYPE
    SYNTAX     INTEGER
      {
        eNo (0),
        eYes (1)
      }
    MAX-ACCESS read-only
    STATUS     current
    DESCRIPTION
        "-- empty --"
    ::= { lcsSetupTcpIp 22 }

-- {SCALAR} 310.2.7.11
lcsSetupTcpIpArpAgingMinutes OBJECT-TYPE
    SYNTAX     INTEGER (0..255)
    MAX-ACCESS read-only
    STATUS     current
    DESCRIPTION
        "-- empty --"
    ::= { lcsSetupTcpIp 11 }

-- {OID} 310.2.7.21
lcsSetupTcpIpAliveTest OBJECT IDENTIFIER ::= { lcsSetupTcpIp 21 }

-- {SCALAR} 310.2.7.21.1
lcsSetupTcpIpAliveTestTargetAddress OBJECT-TYPE
    SYNTAX     IpAddress
    MAX-ACCESS read-only
    STATUS     current
    DESCRIPTION
        "-- empty --"
    ::= { lcsSetupTcpIpAliveTest 1 }

-- {SCALAR} 310.2.7.21.2
lcsSetupTcpIpAliveTestTestInterval OBJECT-TYPE
    SYNTAX     INTEGER (0..2147483647)
    MAX-ACCESS read-only
    STATUS     current
    DESCRIPTION
        "-- empty --"
    ::= { lcsSetupTcpIpAliveTest 2 }

-- {SCALAR} 310.2.7.21.3
lcsSetupTcpIpAliveTestRetryCount OBJECT-TYPE
    SYNTAX     INTEGER (0..2147483647)
    MAX-ACCESS read-only
    STATUS     current
    DESCRIPTION
        "-- empty --"
    ::= { lcsSetupTcpIpAliveTest 3 }

-- {SCALAR} 310.2.7.21.4
lcsSetupTcpIpAliveTestRetryInterval OBJECT-TYPE
    SYNTAX     INTEGER (0..2147483647)
    MAX-ACCESS read-only
    STATUS     current
    DESCRIPTION
        "-- empty --"
    ::= { lcsSetupTcpIpAliveTest 4 }

-- {SCALAR} 310.2.7.21.5
lcsSetupTcpIpAliveTestFailLimit OBJECT-TYPE
    SYNTAX     INTEGER (0..2147483647)
    MAX-ACCESS read-only
    STATUS     current
    DESCRIPTION
        "-- empty --"
    ::= { lcsSetupTcpIpAliveTest 5 }

-- {SCALAR} 310.2.7.21.6
lcsSetupTcpIpAliveTestBootType OBJECT-TYPE
    SYNTAX     INTEGER
      {
        eWarmBoot (0),
        eColdBoot (1),
        eAction (2)
      }
    MAX-ACCESS read-only
    STATUS     current
    DESCRIPTION
        "-- empty --"
    ::= { lcsSetupTcpIpAliveTest 6 }

-- {SCALAR} 310.2.7.21.7
lcsSetupTcpIpAliveTestAction OBJECT-TYPE
    SYNTAX     DisplayString (SIZE(0..251))
    MAX-ACCESS read-only
    STATUS     current
    DESCRIPTION
        "-- empty --"
    ::= { lcsSetupTcpIpAliveTest 7 }

-- {OID} 310.2.8
lcsSetupIpRouter OBJECT IDENTIFIER ::= { lcsSetup 8 }

-- {SCALAR} 310.2.8.1
lcsSetupIpRouterOperating OBJECT-TYPE
    SYNTAX     INTEGER
      {
        eNo (0),
        eYes (1)
      }
    MAX-ACCESS read-only
    STATUS     current
    DESCRIPTION
        "-- empty --"
    ::= { lcsSetupIpRouter 1 }

-- {TABLE} 310.2.8.2
lcsSetupIpRouterIpRoutingTableTable OBJECT-TYPE
    SYNTAX     SEQUENCE OF LcsSetupIpRouterIpRoutingTableEntry
    MAX-ACCESS not-accessible
    STATUS     current
    DESCRIPTION
        "-- empty --"
    ::= { lcsSetupIpRouter 2 }

-- {ENTRY} 310.2.8.2.1
lcsSetupIpRouterIpRoutingTableEntry OBJECT-TYPE
    SYNTAX     LcsSetupIpRouterIpRoutingTableEntry
    MAX-ACCESS not-accessible
    STATUS     current
    DESCRIPTION
        ""
    INDEX {
        lcsSetupIpRouterIpRoutingTableEntryIpAddress,
        lcsSetupIpRouterIpRoutingTableEntryIpNetmask,
        lcsSetupIpRouterIpRoutingTableEntryRtgTag
    }
    ::= { lcsSetupIpRouterIpRoutingTableTable 1 }

-- {SEQUENCE}
LcsSetupIpRouterIpRoutingTableEntry ::= SEQUENCE {
    lcsSetupIpRouterIpRoutingTableEntryIpAddress IpAddress,
    lcsSetupIpRouterIpRoutingTableEntryIpNetmask IpAddress,
    lcsSetupIpRouterIpRoutingTableEntryRtgTag INTEGER,
    lcsSetupIpRouterIpRoutingTableEntryPeerOrIp DisplayString,
    lcsSetupIpRouterIpRoutingTableEntryDistance INTEGER,
    lcsSetupIpRouterIpRoutingTableEntryMasquerade INTEGER,
    lcsSetupIpRouterIpRoutingTableEntryActive INTEGER,
    lcsSetupIpRouterIpRoutingTableEntryComment DisplayString
}

-- {COLUMN} 310.2.8.2.1.1
lcsSetupIpRouterIpRoutingTableEntryIpAddress OBJECT-TYPE
    SYNTAX     IpAddress
    MAX-ACCESS read-write
    STATUS     current
    DESCRIPTION
        "-- empty --"
    ::= { lcsSetupIpRouterIpRoutingTableEntry 1 }

-- {COLUMN} 310.2.8.2.1.2
lcsSetupIpRouterIpRoutingTableEntryIpNetmask OBJECT-TYPE
    SYNTAX     IpAddress
    MAX-ACCESS read-write
    STATUS     current
    DESCRIPTION
        "-- empty --"
    ::= { lcsSetupIpRouterIpRoutingTableEntry 2 }

-- {COLUMN} 310.2.8.2.1.8
lcsSetupIpRouterIpRoutingTableEntryRtgTag OBJECT-TYPE
    SYNTAX     INTEGER (0..65535)
    MAX-ACCESS read-write
    STATUS     current
    DESCRIPTION
        "-- empty --"
    ::= { lcsSetupIpRouterIpRoutingTableEntry 8 }

-- {COLUMN} 310.2.8.2.1.3
lcsSetupIpRouterIpRoutingTableEntryPeerOrIp OBJECT-TYPE
    SYNTAX     DisplayString (SIZE(0..16))
    MAX-ACCESS read-write
    STATUS     current
    DESCRIPTION
        "-- empty --"
    ::= { lcsSetupIpRouterIpRoutingTableEntry 3 }

-- {COLUMN} 310.2.8.2.1.4
lcsSetupIpRouterIpRoutingTableEntryDistance OBJECT-TYPE
    SYNTAX     INTEGER (0..255)
    MAX-ACCESS read-write
    STATUS     current
    DESCRIPTION
        "-- empty --"
    ::= { lcsSetupIpRouterIpRoutingTableEntry 4 }

-- {COLUMN} 310.2.8.2.1.5
lcsSetupIpRouterIpRoutingTableEntryMasquerade OBJECT-TYPE
    SYNTAX     INTEGER
      {
        eNo (0),
        eOn (1),
        eIntranet (2)
      }
    MAX-ACCESS read-write
    STATUS     current
    DESCRIPTION
        "-- empty --"
    ::= { lcsSetupIpRouterIpRoutingTableEntry 5 }

-- {COLUMN} 310.2.8.2.1.6
lcsSetupIpRouterIpRoutingTableEntryActive OBJECT-TYPE
    SYNTAX     INTEGER
      {
        eNo (1),
        eYes (0),
        eSemi (2)
      }
    MAX-ACCESS read-write
    STATUS     current
    DESCRIPTION
        "-- empty --"
    ::= { lcsSetupIpRouterIpRoutingTableEntry 6 }

-- {COLUMN} 310.2.8.2.1.7
lcsSetupIpRouterIpRoutingTableEntryComment OBJECT-TYPE
    SYNTAX     DisplayString (SIZE(0..64))
    MAX-ACCESS read-write
    STATUS     current
    DESCRIPTION
        "-- empty --"
    ::= { lcsSetupIpRouterIpRoutingTableEntry 7 }

-- {TABLE} 310.2.8.13
lcsSetupIpRouterDefaultTimeListTable OBJECT-TYPE
    SYNTAX     SEQUENCE OF LcsSetupIpRouterDefaultTimeListEntry
    MAX-ACCESS not-accessible
    STATUS     current
    DESCRIPTION
        "-- empty --"
    ::= { lcsSetupIpRouter 13 }

-- {ENTRY} 310.2.8.13.1
lcsSetupIpRouterDefaultTimeListEntry OBJECT-TYPE
    SYNTAX     LcsSetupIpRouterDefaultTimeListEntry
    MAX-ACCESS not-accessible
    STATUS     current
    DESCRIPTION
        ""
    INDEX {
        lcsSetupIpRouterDefaultTimeListEntryIndex
    }
    ::= { lcsSetupIpRouterDefaultTimeListTable 1 }

-- {SEQUENCE}
LcsSetupIpRouterDefaultTimeListEntry ::= SEQUENCE {
    lcsSetupIpRouterDefaultTimeListEntryIndex INTEGER,
    lcsSetupIpRouterDefaultTimeListEntryDays BITS,
    lcsSetupIpRouterDefaultTimeListEntryStart DisplayString,
    lcsSetupIpRouterDefaultTimeListEntryStop DisplayString,
    lcsSetupIpRouterDefaultTimeListEntryPeer DisplayString
}

-- {COLUMN} 310.2.8.13.1.1
lcsSetupIpRouterDefaultTimeListEntryIndex OBJECT-TYPE
    SYNTAX     INTEGER (0..65535)
    MAX-ACCESS read-write
    STATUS     current
    DESCRIPTION
        "-- empty --"
    ::= { lcsSetupIpRouterDefaultTimeListEntry 1 }

-- {COLUMN} 310.2.8.13.1.2
lcsSetupIpRouterDefaultTimeListEntryDays OBJECT-TYPE
    SYNTAX     BITS
      {
        eMonday (7),
        eTuesday (6),
        eWednesday (5),
        eThursday (4),
        eFriday (3),
        eSaturday (2),
        eSunday (1),
        eHoliday (0)
      }
    MAX-ACCESS read-write
    STATUS     current
    DESCRIPTION
        "-- empty --"
    ::= { lcsSetupIpRouterDefaultTimeListEntry 2 }

-- {COLUMN} 310.2.8.13.1.3
lcsSetupIpRouterDefaultTimeListEntryStart OBJECT-TYPE
    SYNTAX     DisplayString (SIZE(0..5))
    MAX-ACCESS read-write
    STATUS     current
    DESCRIPTION
        "-- empty --"
    ::= { lcsSetupIpRouterDefaultTimeListEntry 3 }

-- {COLUMN} 310.2.8.13.1.4
lcsSetupIpRouterDefaultTimeListEntryStop OBJECT-TYPE
    SYNTAX     DisplayString (SIZE(0..5))
    MAX-ACCESS read-write
    STATUS     current
    DESCRIPTION
        "-- empty --"
    ::= { lcsSetupIpRouterDefaultTimeListEntry 4 }

-- {COLUMN} 310.2.8.13.1.5
lcsSetupIpRouterDefaultTimeListEntryPeer OBJECT-TYPE
    SYNTAX     DisplayString (SIZE(0..16))
    MAX-ACCESS read-write
    STATUS     current
    DESCRIPTION
        "-- empty --"
    ::= { lcsSetupIpRouterDefaultTimeListEntry 5 }

-- {SCALAR} 310.2.8.14
lcsSetupIpRouterUsageDefaultTimetable OBJECT-TYPE
    SYNTAX     INTEGER
      {
        eNo (0),
        eYes (1)
      }
    MAX-ACCESS read-only
    STATUS     current
    DESCRIPTION
        "-- empty --"
    ::= { lcsSetupIpRouter 14 }

-- {SCALAR} 310.2.8.5
lcsSetupIpRouterProxyArp OBJECT-TYPE
    SYNTAX     INTEGER
      {
        eNo (0),
        eYes (1)
      }
    MAX-ACCESS read-only
    STATUS     current
    DESCRIPTION
        "-- empty --"
    ::= { lcsSetupIpRouter 5 }

-- {SCALAR} 310.2.8.6
lcsSetupIpRouterSendIcmpRedirect OBJECT-TYPE
    SYNTAX     INTEGER
      {
        eNo (1),
        eYes (0)
      }
    MAX-ACCESS read-only
    STATUS     current
    DESCRIPTION
        "-- empty --"
    ::= { lcsSetupIpRouter 6 }

-- {SCALAR} 310.2.8.11
lcsSetupIpRouterStartWanPool OBJECT-TYPE
    SYNTAX     IpAddress
    MAX-ACCESS read-only
    STATUS     current
    DESCRIPTION
        "-- empty --"
    ::= { lcsSetupIpRouter 11 }

-- {SCALAR} 310.2.8.12
lcsSetupIpRouterEndWanPool OBJECT-TYPE
    SYNTAX     IpAddress
    MAX-ACCESS read-only
    STATUS     current
    DESCRIPTION
        "-- empty --"
    ::= { lcsSetupIpRouter 12 }

-- {OID} 310.2.8.7
lcsSetupIpRouterRoutingMethod OBJECT IDENTIFIER ::= { lcsSetupIpRouter 7 }

-- {SCALAR} 310.2.8.7.1
lcsSetupIpRouterRoutingMethodRoutingMethod OBJECT-TYPE
    SYNTAX     INTEGER
      {
        eNormal (0),
        eTypeOfService (1),
        eDiffserv (2)
      }
    MAX-ACCESS read-only
    STATUS     current
    DESCRIPTION
        "-- empty --"
    ::= { lcsSetupIpRouterRoutingMethod 1 }

-- {SCALAR} 310.2.8.7.2
lcsSetupIpRouterRoutingMethodIcmpRoutingMethod OBJECT-TYPE
    SYNTAX     INTEGER
      {
        eNormal (0),
        eReliable (1)
      }
    MAX-ACCESS read-only
    STATUS     current
    DESCRIPTION
        "-- empty --"
    ::= { lcsSetupIpRouterRoutingMethod 2 }

-- {SCALAR} 310.2.8.7.3
lcsSetupIpRouterRoutingMethodSynAckSpeedup OBJECT-TYPE
    SYNTAX     INTEGER
      {
        eNo (0),
        eYes (1)
      }
    MAX-ACCESS read-only
    STATUS     current
    DESCRIPTION
        "-- empty --"
    ::= { lcsSetupIpRouterRoutingMethod 3 }

-- {SCALAR} 310.2.8.7.4
lcsSetupIpRouterRoutingMethodL2L3Tagging OBJECT-TYPE
    SYNTAX     INTEGER
      {
        eNo (0),
        eYes (1),
        eAuto (2)
      }
    MAX-ACCESS read-only
    STATUS     current
    DESCRIPTION
        "-- empty --"
    ::= { lcsSetupIpRouterRoutingMethod 4 }

-- {SCALAR} 310.2.8.7.5
lcsSetupIpRouterRoutingMethodL3L2Tagging OBJECT-TYPE
    SYNTAX     INTEGER
      {
        eNo (0),
        eYes (1)
      }
    MAX-ACCESS read-only
    STATUS     current
    DESCRIPTION
        "-- empty --"
    ::= { lcsSetupIpRouterRoutingMethod 5 }

-- {SCALAR} 310.2.8.7.6
lcsSetupIpRouterRoutingMethodRouteInternalServices OBJECT-TYPE
    SYNTAX     INTEGER
      {
        eNo (0),
        eYes (1)
      }
    MAX-ACCESS read-only
    STATUS     current
    DESCRIPTION
        "-- empty --"
    ::= { lcsSetupIpRouterRoutingMethod 6 }

-- {OID} 310.2.8.8
lcsSetupIpRouterRip OBJECT IDENTIFIER ::= { lcsSetupIpRouter 8 }

-- {TABLE} 310.2.8.8.5
lcsSetupIpRouterRipLanSitesTable OBJECT-TYPE
    SYNTAX     SEQUENCE OF LcsSetupIpRouterRipLanSitesEntry
    MAX-ACCESS not-accessible
    STATUS     current
    DESCRIPTION
        "-- empty --"
    ::= { lcsSetupIpRouterRip 5 }

-- {ENTRY} 310.2.8.8.5.1
lcsSetupIpRouterRipLanSitesEntry OBJECT-TYPE
    SYNTAX     LcsSetupIpRouterRipLanSitesEntry
    MAX-ACCESS not-accessible
    STATUS     current
    DESCRIPTION
        ""
    INDEX {
        lcsSetupIpRouterRipLanSitesEntryNetworkName
    }
    ::= { lcsSetupIpRouterRipLanSitesTable 1 }

-- {SEQUENCE}
LcsSetupIpRouterRipLanSitesEntry ::= SEQUENCE {
    lcsSetupIpRouterRipLanSitesEntryNetworkName DisplayString,
    lcsSetupIpRouterRipLanSitesEntryRipType INTEGER,
    lcsSetupIpRouterRipLanSitesEntryRipSend INTEGER,
    lcsSetupIpRouterRipLanSitesEntryRipAccept INTEGER,
    lcsSetupIpRouterRipLanSitesEntryPropagate INTEGER,
    lcsSetupIpRouterRipLanSitesEntryPoisonedReverse INTEGER,
    lcsSetupIpRouterRipLanSitesEntryDftRtgTag INTEGER,
    lcsSetupIpRouterRipLanSitesEntryRtgTagList DisplayString,
    lcsSetupIpRouterRipLanSitesEntryRxFilter DisplayString,
    lcsSetupIpRouterRipLanSitesEntryTxFilter DisplayString
}

-- {COLUMN} 310.2.8.8.5.1.1
lcsSetupIpRouterRipLanSitesEntryNetworkName OBJECT-TYPE
    SYNTAX     DisplayString (SIZE(0..16))
    MAX-ACCESS read-write
    STATUS     current
    DESCRIPTION
        "-- empty --"
    ::= { lcsSetupIpRouterRipLanSitesEntry 1 }

-- {COLUMN} 310.2.8.8.5.1.2
lcsSetupIpRouterRipLanSitesEntryRipType OBJECT-TYPE
    SYNTAX     INTEGER
      {
        eOff (0),
        eRip1 (1),
        eR1Comp (2),
        eRip2 (3)
      }
    MAX-ACCESS read-write
    STATUS     current
    DESCRIPTION
        "-- empty --"
    ::= { lcsSetupIpRouterRipLanSitesEntry 2 }

-- {COLUMN} 310.2.8.8.5.1.12
lcsSetupIpRouterRipLanSitesEntryRipSend OBJECT-TYPE
    SYNTAX     INTEGER
      {
        eNo (0),
        eYes (1)
      }
    MAX-ACCESS read-write
    STATUS     current
    DESCRIPTION
        "-- empty --"
    ::= { lcsSetupIpRouterRipLanSitesEntry 12 }

-- {COLUMN} 310.2.8.8.5.1.3
lcsSetupIpRouterRipLanSitesEntryRipAccept OBJECT-TYPE
    SYNTAX     INTEGER
      {
        eNo (0),
        eYes (1)
      }
    MAX-ACCESS read-write
    STATUS     current
    DESCRIPTION
        "-- empty --"
    ::= { lcsSetupIpRouterRipLanSitesEntry 3 }

-- {COLUMN} 310.2.8.8.5.1.4
lcsSetupIpRouterRipLanSitesEntryPropagate OBJECT-TYPE
    SYNTAX     INTEGER
      {
        eNo (0),
        eYes (1)
      }
    MAX-ACCESS read-write
    STATUS     current
    DESCRIPTION
        "-- empty --"
    ::= { lcsSetupIpRouterRipLanSitesEntry 4 }

-- {COLUMN} 310.2.8.8.5.1.7
lcsSetupIpRouterRipLanSitesEntryPoisonedReverse OBJECT-TYPE
    SYNTAX     INTEGER
      {
        eNo (0),
        eYes (1)
      }
    MAX-ACCESS read-write
    STATUS     current
    DESCRIPTION
        "-- empty --"
    ::= { lcsSetupIpRouterRipLanSitesEntry 7 }

-- {COLUMN} 310.2.8.8.5.1.5
lcsSetupIpRouterRipLanSitesEntryDftRtgTag OBJECT-TYPE
    SYNTAX     INTEGER (0..65535)
    MAX-ACCESS read-write
    STATUS     current
    DESCRIPTION
        "-- empty --"
    ::= { lcsSetupIpRouterRipLanSitesEntry 5 }

-- {COLUMN} 310.2.8.8.5.1.6
lcsSetupIpRouterRipLanSitesEntryRtgTagList OBJECT-TYPE
    SYNTAX     DisplayString (SIZE(0..33))
    MAX-ACCESS read-write
    STATUS     current
    DESCRIPTION
        "-- empty --"
    ::= { lcsSetupIpRouterRipLanSitesEntry 6 }

-- {COLUMN} 310.2.8.8.5.1.10
lcsSetupIpRouterRipLanSitesEntryRxFilter OBJECT-TYPE
    SYNTAX     DisplayString (SIZE(0..16))
    MAX-ACCESS read-write
    STATUS     current
    DESCRIPTION
        "-- empty --"
    ::= { lcsSetupIpRouterRipLanSitesEntry 10 }

-- {COLUMN} 310.2.8.8.5.1.11
lcsSetupIpRouterRipLanSitesEntryTxFilter OBJECT-TYPE
    SYNTAX     DisplayString (SIZE(0..16))
    MAX-ACCESS read-write
    STATUS     current
    DESCRIPTION
        "-- empty --"
    ::= { lcsSetupIpRouterRipLanSitesEntry 11 }

-- {TABLE} 310.2.8.8.4
lcsSetupIpRouterRipWanSitesTable OBJECT-TYPE
    SYNTAX     SEQUENCE OF LcsSetupIpRouterRipWanSitesEntry
    MAX-ACCESS not-accessible
    STATUS     current
    DESCRIPTION
        "-- empty --"
    ::= { lcsSetupIpRouterRip 4 }

-- {ENTRY} 310.2.8.8.4.1
lcsSetupIpRouterRipWanSitesEntry OBJECT-TYPE
    SYNTAX     LcsSetupIpRouterRipWanSitesEntry
    MAX-ACCESS not-accessible
    STATUS     current
    DESCRIPTION
        ""
    INDEX {
        lcsSetupIpRouterRipWanSitesEntryPeer
    }
    ::= { lcsSetupIpRouterRipWanSitesTable 1 }

-- {SEQUENCE}
LcsSetupIpRouterRipWanSitesEntry ::= SEQUENCE {
    lcsSetupIpRouterRipWanSitesEntryPeer DisplayString,
    lcsSetupIpRouterRipWanSitesEntryRipType INTEGER,
    lcsSetupIpRouterRipWanSitesEntryRipSend INTEGER,
    lcsSetupIpRouterRipWanSitesEntryRipAccept INTEGER,
    lcsSetupIpRouterRipWanSitesEntryMasquerade INTEGER,
    lcsSetupIpRouterRipWanSitesEntryPoisonedReverse INTEGER,
    lcsSetupIpRouterRipWanSitesEntryRfc2091 INTEGER,
    lcsSetupIpRouterRipWanSitesEntryGateway IpAddress,
    lcsSetupIpRouterRipWanSitesEntryDftRtgTag INTEGER,
    lcsSetupIpRouterRipWanSitesEntryRtgTagList DisplayString,
    lcsSetupIpRouterRipWanSitesEntryRxFilter DisplayString,
    lcsSetupIpRouterRipWanSitesEntryTxFilter DisplayString
}

-- {COLUMN} 310.2.8.8.4.1.1
lcsSetupIpRouterRipWanSitesEntryPeer OBJECT-TYPE
    SYNTAX     DisplayString (SIZE(0..16))
    MAX-ACCESS read-write
    STATUS     current
    DESCRIPTION
        "-- empty --"
    ::= { lcsSetupIpRouterRipWanSitesEntry 1 }

-- {COLUMN} 310.2.8.8.4.1.2
lcsSetupIpRouterRipWanSitesEntryRipType OBJECT-TYPE
    SYNTAX     INTEGER
      {
        eOff (0),
        eRip1 (1),
        eR1Comp (2),
        eRip2 (3)
      }
    MAX-ACCESS read-write
    STATUS     current
    DESCRIPTION
        "-- empty --"
    ::= { lcsSetupIpRouterRipWanSitesEntry 2 }

-- {COLUMN} 310.2.8.8.4.1.12
lcsSetupIpRouterRipWanSitesEntryRipSend OBJECT-TYPE
    SYNTAX     INTEGER
      {
        eNo (0),
        eYes (1)
      }
    MAX-ACCESS read-write
    STATUS     current
    DESCRIPTION
        "-- empty --"
    ::= { lcsSetupIpRouterRipWanSitesEntry 12 }

-- {COLUMN} 310.2.8.8.4.1.3
lcsSetupIpRouterRipWanSitesEntryRipAccept OBJECT-TYPE
    SYNTAX     INTEGER
      {
        eNo (0),
        eYes (1)
      }
    MAX-ACCESS read-write
    STATUS     current
    DESCRIPTION
        "-- empty --"
    ::= { lcsSetupIpRouterRipWanSitesEntry 3 }

-- {COLUMN} 310.2.8.8.4.1.4
lcsSetupIpRouterRipWanSitesEntryMasquerade OBJECT-TYPE
    SYNTAX     INTEGER
      {
        eAuto (0),
        eOn (1),
        eIntranet (2)
      }
    MAX-ACCESS read-write
    STATUS     current
    DESCRIPTION
        "-- empty --"
    ::= { lcsSetupIpRouterRipWanSitesEntry 4 }

-- {COLUMN} 310.2.8.8.4.1.7
lcsSetupIpRouterRipWanSitesEntryPoisonedReverse OBJECT-TYPE
    SYNTAX     INTEGER
      {
        eNo (0),
        eYes (1)
      }
    MAX-ACCESS read-write
    STATUS     current
    DESCRIPTION
        "-- empty --"
    ::= { lcsSetupIpRouterRipWanSitesEntry 7 }

-- {COLUMN} 310.2.8.8.4.1.8
lcsSetupIpRouterRipWanSitesEntryRfc2091 OBJECT-TYPE
    SYNTAX     INTEGER
      {
        eNo (0),
        eYes (1)
      }
    MAX-ACCESS read-write
    STATUS     current
    DESCRIPTION
        "-- empty --"
    ::= { lcsSetupIpRouterRipWanSitesEntry 8 }

-- {COLUMN} 310.2.8.8.4.1.9
lcsSetupIpRouterRipWanSitesEntryGateway OBJECT-TYPE
    SYNTAX     IpAddress
    MAX-ACCESS read-write
    STATUS     current
    DESCRIPTION
        "-- empty --"
    ::= { lcsSetupIpRouterRipWanSitesEntry 9 }

-- {COLUMN} 310.2.8.8.4.1.5
lcsSetupIpRouterRipWanSitesEntryDftRtgTag OBJECT-TYPE
    SYNTAX     INTEGER (0..65535)
    MAX-ACCESS read-write
    STATUS     current
    DESCRIPTION
        "-- empty --"
    ::= { lcsSetupIpRouterRipWanSitesEntry 5 }

-- {COLUMN} 310.2.8.8.4.1.6
lcsSetupIpRouterRipWanSitesEntryRtgTagList OBJECT-TYPE
    SYNTAX     DisplayString (SIZE(0..33))
    MAX-ACCESS read-write
    STATUS     current
    DESCRIPTION
        "-- empty --"
    ::= { lcsSetupIpRouterRipWanSitesEntry 6 }

-- {COLUMN} 310.2.8.8.4.1.10
lcsSetupIpRouterRipWanSitesEntryRxFilter OBJECT-TYPE
    SYNTAX     DisplayString (SIZE(0..16))
    MAX-ACCESS read-write
    STATUS     current
    DESCRIPTION
        "-- empty --"
    ::= { lcsSetupIpRouterRipWanSitesEntry 10 }

-- {COLUMN} 310.2.8.8.4.1.11
lcsSetupIpRouterRipWanSitesEntryTxFilter OBJECT-TYPE
    SYNTAX     DisplayString (SIZE(0..16))
    MAX-ACCESS read-write
    STATUS     current
    DESCRIPTION
        "-- empty --"
    ::= { lcsSetupIpRouterRipWanSitesEntry 11 }

-- {SCALAR} 310.2.8.8.2
lcsSetupIpRouterRipR1Mask OBJECT-TYPE
    SYNTAX     INTEGER
      {
        eClass (0),
        eAddress (1),
        eClPlusAddr (2)
      }
    MAX-ACCESS read-only
    STATUS     current
    DESCRIPTION
        "-- empty --"
    ::= { lcsSetupIpRouterRip 2 }

-- {TABLE} 310.2.8.8.7
lcsSetupIpRouterRipFilterTable OBJECT-TYPE
    SYNTAX     SEQUENCE OF LcsSetupIpRouterRipFilterEntry
    MAX-ACCESS not-accessible
    STATUS     current
    DESCRIPTION
        "-- empty --"
    ::= { lcsSetupIpRouterRip 7 }

-- {ENTRY} 310.2.8.8.7.1
lcsSetupIpRouterRipFilterEntry OBJECT-TYPE
    SYNTAX     LcsSetupIpRouterRipFilterEntry
    MAX-ACCESS not-accessible
    STATUS     current
    DESCRIPTION
        ""
    INDEX {
        lcsSetupIpRouterRipFilterEntryName
    }
    ::= { lcsSetupIpRouterRipFilterTable 1 }

-- {SEQUENCE}
LcsSetupIpRouterRipFilterEntry ::= SEQUENCE {
    lcsSetupIpRouterRipFilterEntryName DisplayString,
    lcsSetupIpRouterRipFilterEntryFilter DisplayString
}

-- {COLUMN} 310.2.8.8.7.1.1
lcsSetupIpRouterRipFilterEntryName OBJECT-TYPE
    SYNTAX     DisplayString (SIZE(0..18))
    MAX-ACCESS read-write
    STATUS     current
    DESCRIPTION
        "-- empty --"
    ::= { lcsSetupIpRouterRipFilterEntry 1 }

-- {COLUMN} 310.2.8.8.7.1.2
lcsSetupIpRouterRipFilterEntryFilter OBJECT-TYPE
    SYNTAX     DisplayString (SIZE(0..64))
    MAX-ACCESS read-write
    STATUS     current
    DESCRIPTION
        "-- empty --"
    ::= { lcsSetupIpRouterRipFilterEntry 2 }

-- {OID} 310.2.8.8.6
lcsSetupIpRouterRipParameter OBJECT IDENTIFIER ::= { lcsSetupIpRouterRip 6 }

-- {SCALAR} 310.2.8.8.6.1
lcsSetupIpRouterRipParameterUpdate OBJECT-TYPE
    SYNTAX     INTEGER (0..255)
    MAX-ACCESS read-write
    STATUS     current
    DESCRIPTION
        "-- empty --"
    ::= { lcsSetupIpRouterRipParameter 1 }

-- {SCALAR} 310.2.8.8.6.2
lcsSetupIpRouterRipParameterHolddown OBJECT-TYPE
    SYNTAX     INTEGER (0..255)
    MAX-ACCESS read-write
    STATUS     current
    DESCRIPTION
        "-- empty --"
    ::= { lcsSetupIpRouterRipParameter 2 }

-- {SCALAR} 310.2.8.8.6.3
lcsSetupIpRouterRipParameterInvalidate OBJECT-TYPE
    SYNTAX     INTEGER (0..255)
    MAX-ACCESS read-write
    STATUS     current
    DESCRIPTION
        "-- empty --"
    ::= { lcsSetupIpRouterRipParameter 3 }

-- {SCALAR} 310.2.8.8.6.4
lcsSetupIpRouterRipParameterFlush OBJECT-TYPE
    SYNTAX     INTEGER (0..255)
    MAX-ACCESS read-write
    STATUS     current
    DESCRIPTION
        "-- empty --"
    ::= { lcsSetupIpRouterRipParameter 4 }

-- {SCALAR} 310.2.8.8.6.5
lcsSetupIpRouterRipParameterUpdDelay OBJECT-TYPE
    SYNTAX     INTEGER (0..255)
    MAX-ACCESS read-write
    STATUS     current
    DESCRIPTION
        "-- empty --"
    ::= { lcsSetupIpRouterRipParameter 5 }

-- {SCALAR} 310.2.8.8.6.6
lcsSetupIpRouterRipParameterMaxHopcount OBJECT-TYPE
    SYNTAX     INTEGER (0..255)
    MAX-ACCESS read-write
    STATUS     current
    DESCRIPTION
        "-- empty --"
    ::= { lcsSetupIpRouterRipParameter 6 }

-- {SCALAR} 310.2.8.8.6.7
lcsSetupIpRouterRipParameterRoutesPerFrame OBJECT-TYPE
    SYNTAX     INTEGER (0..255)
    MAX-ACCESS read-write
    STATUS     current
    DESCRIPTION
        "-- empty --"
    ::= { lcsSetupIpRouterRipParameter 7 }

-- {TABLE} 310.2.8.8.8
lcsSetupIpRouterRipBestRoutesTable OBJECT-TYPE
    SYNTAX     SEQUENCE OF LcsSetupIpRouterRipBestRoutesEntry
    MAX-ACCESS not-accessible
    STATUS     current
    DESCRIPTION
        "-- empty --"
    ::= { lcsSetupIpRouterRip 8 }

-- {ENTRY} 310.2.8.8.8.1
lcsSetupIpRouterRipBestRoutesEntry OBJECT-TYPE
    SYNTAX     LcsSetupIpRouterRipBestRoutesEntry
    MAX-ACCESS not-accessible
    STATUS     current
    DESCRIPTION
        ""
    INDEX {
        lcsSetupIpRouterRipBestRoutesEntryIpAddress,
        lcsSetupIpRouterRipBestRoutesEntryIpNetmask,
        lcsSetupIpRouterRipBestRoutesEntryRtgTag,
        lcsSetupIpRouterRipBestRoutesEntryGateway
    }
    ::= { lcsSetupIpRouterRipBestRoutesTable 1 }

-- {SEQUENCE}
LcsSetupIpRouterRipBestRoutesEntry ::= SEQUENCE {
    lcsSetupIpRouterRipBestRoutesEntryIpAddress IpAddress,
    lcsSetupIpRouterRipBestRoutesEntryIpNetmask IpAddress,
    lcsSetupIpRouterRipBestRoutesEntryRtgTag INTEGER,
    lcsSetupIpRouterRipBestRoutesEntryGateway IpAddress,
    lcsSetupIpRouterRipBestRoutesEntryDistance INTEGER,
    lcsSetupIpRouterRipBestRoutesEntryTime INTEGER,
    lcsSetupIpRouterRipBestRoutesEntryPeer DisplayString,
    lcsSetupIpRouterRipBestRoutesEntryPort INTEGER,
    lcsSetupIpRouterRipBestRoutesEntryVlanId INTEGER,
    lcsSetupIpRouterRipBestRoutesEntryNetworkName DisplayString
}

-- {COLUMN} 310.2.8.8.8.1.1
lcsSetupIpRouterRipBestRoutesEntryIpAddress OBJECT-TYPE
    SYNTAX     IpAddress
    MAX-ACCESS read-only
    STATUS     current
    DESCRIPTION
        "-- empty --"
    ::= { lcsSetupIpRouterRipBestRoutesEntry 1 }

-- {COLUMN} 310.2.8.8.8.1.2
lcsSetupIpRouterRipBestRoutesEntryIpNetmask OBJECT-TYPE
    SYNTAX     IpAddress
    MAX-ACCESS read-only
    STATUS     current
    DESCRIPTION
        "-- empty --"
    ::= { lcsSetupIpRouterRipBestRoutesEntry 2 }

-- {COLUMN} 310.2.8.8.8.1.6
lcsSetupIpRouterRipBestRoutesEntryRtgTag OBJECT-TYPE
    SYNTAX     INTEGER (0..65535)
    MAX-ACCESS read-only
    STATUS     current
    DESCRIPTION
        "-- empty --"
    ::= { lcsSetupIpRouterRipBestRoutesEntry 6 }

-- {COLUMN} 310.2.8.8.8.1.5
lcsSetupIpRouterRipBestRoutesEntryGateway OBJECT-TYPE
    SYNTAX     IpAddress
    MAX-ACCESS read-only
    STATUS     current
    DESCRIPTION
        "-- empty --"
    ::= { lcsSetupIpRouterRipBestRoutesEntry 5 }

-- {COLUMN} 310.2.8.8.8.1.4
lcsSetupIpRouterRipBestRoutesEntryDistance OBJECT-TYPE
    SYNTAX     INTEGER (0..65535)
    MAX-ACCESS read-only
    STATUS     current
    DESCRIPTION
        "-- empty --"
    ::= { lcsSetupIpRouterRipBestRoutesEntry 4 }

-- {COLUMN} 310.2.8.8.8.1.3
lcsSetupIpRouterRipBestRoutesEntryTime OBJECT-TYPE
    SYNTAX     INTEGER (0..65535)
    MAX-ACCESS read-only
    STATUS     current
    DESCRIPTION
        "-- empty --"
    ::= { lcsSetupIpRouterRipBestRoutesEntry 3 }

-- {COLUMN} 310.2.8.8.8.1.8
lcsSetupIpRouterRipBestRoutesEntryPeer OBJECT-TYPE
    SYNTAX     DisplayString (SIZE(0..255))
    MAX-ACCESS read-only
    STATUS     current
    DESCRIPTION
        "-- empty --"
    ::= { lcsSetupIpRouterRipBestRoutesEntry 8 }

-- {COLUMN} 310.2.8.8.8.1.12
lcsSetupIpRouterRipBestRoutesEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsSetupIpRouterRipBestRoutesEntry 12 }

-- {COLUMN} 310.2.8.8.8.1.10
lcsSetupIpRouterRipBestRoutesEntryVlanId OBJECT-TYPE
    SYNTAX     INTEGER (0..65535)
    MAX-ACCESS read-only
    STATUS     current
    DESCRIPTION
        "-- empty --"
    ::= { lcsSetupIpRouterRipBestRoutesEntry 10 }

-- {COLUMN} 310.2.8.8.8.1.11
lcsSetupIpRouterRipBestRoutesEntryNetworkName OBJECT-TYPE
    SYNTAX     DisplayString (SIZE(0..255))
    MAX-ACCESS read-only
    STATUS     current
    DESCRIPTION
        "-- empty --"
    ::= { lcsSetupIpRouterRipBestRoutesEntry 11 }

-- {TABLE} 310.2.8.8.9
lcsSetupIpRouterRipAllRoutesTable OBJECT-TYPE
    SYNTAX     SEQUENCE OF LcsSetupIpRouterRipAllRoutesEntry
    MAX-ACCESS not-accessible
    STATUS     current
    DESCRIPTION
        "-- empty --"
    ::= { lcsSetupIpRouterRip 9 }

-- {ENTRY} 310.2.8.8.9.1
lcsSetupIpRouterRipAllRoutesEntry OBJECT-TYPE
    SYNTAX     LcsSetupIpRouterRipAllRoutesEntry
    MAX-ACCESS not-accessible
    STATUS     current
    DESCRIPTION
        ""
    INDEX {
        lcsSetupIpRouterRipAllRoutesEntryIpAddress,
        lcsSetupIpRouterRipAllRoutesEntryIpNetmask,
        lcsSetupIpRouterRipAllRoutesEntryRtgTag,
        lcsSetupIpRouterRipAllRoutesEntryGateway
    }
    ::= { lcsSetupIpRouterRipAllRoutesTable 1 }

-- {SEQUENCE}
LcsSetupIpRouterRipAllRoutesEntry ::= SEQUENCE {
    lcsSetupIpRouterRipAllRoutesEntryIpAddress IpAddress,
    lcsSetupIpRouterRipAllRoutesEntryIpNetmask IpAddress,
    lcsSetupIpRouterRipAllRoutesEntryRtgTag INTEGER,
    lcsSetupIpRouterRipAllRoutesEntryGateway IpAddress,
    lcsSetupIpRouterRipAllRoutesEntryDistance INTEGER,
    lcsSetupIpRouterRipAllRoutesEntryTime INTEGER,
    lcsSetupIpRouterRipAllRoutesEntryPeer DisplayString,
    lcsSetupIpRouterRipAllRoutesEntryPort INTEGER,
    lcsSetupIpRouterRipAllRoutesEntryVlanId INTEGER,
    lcsSetupIpRouterRipAllRoutesEntryNetworkName DisplayString
}

-- {COLUMN} 310.2.8.8.9.1.1
lcsSetupIpRouterRipAllRoutesEntryIpAddress OBJECT-TYPE
    SYNTAX     IpAddress
    MAX-ACCESS read-only
    STATUS     current
    DESCRIPTION
        "-- empty --"
    ::= { lcsSetupIpRouterRipAllRoutesEntry 1 }

-- {COLUMN} 310.2.8.8.9.1.2
lcsSetupIpRouterRipAllRoutesEntryIpNetmask OBJECT-TYPE
    SYNTAX     IpAddress
    MAX-ACCESS read-only
    STATUS     current
    DESCRIPTION
        "-- empty --"
    ::= { lcsSetupIpRouterRipAllRoutesEntry 2 }

-- {COLUMN} 310.2.8.8.9.1.6
lcsSetupIpRouterRipAllRoutesEntryRtgTag OBJECT-TYPE
    SYNTAX     INTEGER (0..65535)
    MAX-ACCESS read-only
    STATUS     current
    DESCRIPTION
        "-- empty --"
    ::= { lcsSetupIpRouterRipAllRoutesEntry 6 }

-- {COLUMN} 310.2.8.8.9.1.5
lcsSetupIpRouterRipAllRoutesEntryGateway OBJECT-TYPE
    SYNTAX     IpAddress
    MAX-ACCESS read-only
    STATUS     current
    DESCRIPTION
        "-- empty --"
    ::= { lcsSetupIpRouterRipAllRoutesEntry 5 }

-- {COLUMN} 310.2.8.8.9.1.4
lcsSetupIpRouterRipAllRoutesEntryDistance OBJECT-TYPE
    SYNTAX     INTEGER (0..65535)
    MAX-ACCESS read-only
    STATUS     current
    DESCRIPTION
        "-- empty --"
    ::= { lcsSetupIpRouterRipAllRoutesEntry 4 }

-- {COLUMN} 310.2.8.8.9.1.3
lcsSetupIpRouterRipAllRoutesEntryTime OBJECT-TYPE
    SYNTAX     INTEGER (0..65535)
    MAX-ACCESS read-only
    STATUS     current
    DESCRIPTION
        "-- empty --"
    ::= { lcsSetupIpRouterRipAllRoutesEntry 3 }

-- {COLUMN} 310.2.8.8.9.1.8
lcsSetupIpRouterRipAllRoutesEntryPeer OBJECT-TYPE
    SYNTAX     DisplayString (SIZE(0..255))
    MAX-ACCESS read-only
    STATUS     current
    DESCRIPTION
        "-- empty --"
    ::= { lcsSetupIpRouterRipAllRoutesEntry 8 }

-- {COLUMN} 310.2.8.8.9.1.12
lcsSetupIpRouterRipAllRoutesEntryPort OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsSetupIpRouterRipAllRoutesEntry 12 }

-- {COLUMN} 310.2.8.8.9.1.10
lcsSetupIpRouterRipAllRoutesEntryVlanId OBJECT-TYPE
    SYNTAX     INTEGER (0..65535)
    MAX-ACCESS read-only
    STATUS     current
    DESCRIPTION
        "-- empty --"
    ::= { lcsSetupIpRouterRipAllRoutesEntry 10 }

-- {COLUMN} 310.2.8.8.9.1.11
lcsSetupIpRouterRipAllRoutesEntryNetworkName OBJECT-TYPE
    SYNTAX     DisplayString (SIZE(0..255))
    MAX-ACCESS read-only
    STATUS     current
    DESCRIPTION
        "-- empty --"
    ::= { lcsSetupIpRouterRipAllRoutesEntry 11 }

-- {OID} 310.2.8.9
lcsSetupIpRouter1NNat OBJECT IDENTIFIER ::= { lcsSetupIpRouter 9 }

-- {SCALAR} 310.2.8.9.1
lcsSetupIpRouter1NNatTcpAgingSeconds OBJECT-TYPE
    SYNTAX     INTEGER (0..65535)
    MAX-ACCESS read-only
    STATUS     current
    DESCRIPTION
        "-- empty --"
    ::= { lcsSetupIpRouter1NNat 1 }

-- {SCALAR} 310.2.8.9.2
lcsSetupIpRouter1NNatUdpAgingSeconds OBJECT-TYPE
    SYNTAX     INTEGER (0..65535)
    MAX-ACCESS read-only
    STATUS     current
    DESCRIPTION
        "-- empty --"
    ::= { lcsSetupIpRouter1NNat 2 }

-- {SCALAR} 310.2.8.9.3
lcsSetupIpRouter1NNatIcmpAgingSeconds OBJECT-TYPE
    SYNTAX     INTEGER (0..65535)
    MAX-ACCESS read-only
    STATUS     current
    DESCRIPTION
        "-- empty --"
    ::= { lcsSetupIpRouter1NNat 3 }

-- {TABLE} 310.2.8.9.4
lcsSetupIpRouter1NNatServiceTableTable OBJECT-TYPE
    SYNTAX     SEQUENCE OF LcsSetupIpRouter1NNatServiceTableEntry
    MAX-ACCESS not-accessible
    STATUS     current
    DESCRIPTION
        "-- empty --"
    ::= { lcsSetupIpRouter1NNat 4 }

-- {ENTRY} 310.2.8.9.4.1
lcsSetupIpRouter1NNatServiceTableEntry OBJECT-TYPE
    SYNTAX     LcsSetupIpRouter1NNatServiceTableEntry
    MAX-ACCESS not-accessible
    STATUS     current
    DESCRIPTION
        ""
    INDEX {
        lcsSetupIpRouter1NNatServiceTableEntryDPortFrom,
        lcsSetupIpRouter1NNatServiceTableEntryDPortTo,
        lcsSetupIpRouter1NNatServiceTableEntryProtocol,
        lcsSetupIpRouter1NNatServiceTableEntryPeer,
        lcsSetupIpRouter1NNatServiceTableEntryWanAddress
    }
    ::= { lcsSetupIpRouter1NNatServiceTableTable 1 }

-- {SEQUENCE}
LcsSetupIpRouter1NNatServiceTableEntry ::= SEQUENCE {
    lcsSetupIpRouter1NNatServiceTableEntryDPortFrom INTEGER,
    lcsSetupIpRouter1NNatServiceTableEntryDPortTo INTEGER,
    lcsSetupIpRouter1NNatServiceTableEntryProtocol INTEGER,
    lcsSetupIpRouter1NNatServiceTableEntryPeer DisplayString,
    lcsSetupIpRouter1NNatServiceTableEntryWanAddress IpAddress,
    lcsSetupIpRouter1NNatServiceTableEntryIntranetAddress IpAddress,
    lcsSetupIpRouter1NNatServiceTableEntryMapPort INTEGER,
    lcsSetupIpRouter1NNatServiceTableEntryActive INTEGER,
    lcsSetupIpRouter1NNatServiceTableEntryComment DisplayString
}

-- {COLUMN} 310.2.8.9.4.1.1
lcsSetupIpRouter1NNatServiceTableEntryDPortFrom OBJECT-TYPE
    SYNTAX     INTEGER (0..65535)
    MAX-ACCESS read-write
    STATUS     current
    DESCRIPTION
        "-- empty --"
    ::= { lcsSetupIpRouter1NNatServiceTableEntry 1 }

-- {COLUMN} 310.2.8.9.4.1.3
lcsSetupIpRouter1NNatServiceTableEntryDPortTo OBJECT-TYPE
    SYNTAX     INTEGER (0..65535)
    MAX-ACCESS read-write
    STATUS     current
    DESCRIPTION
        "-- empty --"
    ::= { lcsSetupIpRouter1NNatServiceTableEntry 3 }

-- {COLUMN} 310.2.8.9.4.1.8
lcsSetupIpRouter1NNatServiceTableEntryProtocol OBJECT-TYPE
    SYNTAX     INTEGER
      {
        eTcp (1),
        eUdp (2),
        eTcpPlusUdp (0)
      }
    MAX-ACCESS read-write
    STATUS     current
    DESCRIPTION
        "-- empty --"
    ::= { lcsSetupIpRouter1NNatServiceTableEntry 8 }

-- {COLUMN} 310.2.8.9.4.1.7
lcsSetupIpRouter1NNatServiceTableEntryPeer OBJECT-TYPE
    SYNTAX     DisplayString (SIZE(0..16))
    MAX-ACCESS read-write
    STATUS     current
    DESCRIPTION
        "-- empty --"
    ::= { lcsSetupIpRouter1NNatServiceTableEntry 7 }

-- {COLUMN} 310.2.8.9.4.1.9
lcsSetupIpRouter1NNatServiceTableEntryWanAddress OBJECT-TYPE
    SYNTAX     IpAddress
    MAX-ACCESS read-write
    STATUS     current
    DESCRIPTION
        "-- empty --"
    ::= { lcsSetupIpRouter1NNatServiceTableEntry 9 }

-- {COLUMN} 310.2.8.9.4.1.2
lcsSetupIpRouter1NNatServiceTableEntryIntranetAddress OBJECT-TYPE
    SYNTAX     IpAddress
    MAX-ACCESS read-write
    STATUS     current
    DESCRIPTION
        "-- empty --"
    ::= { lcsSetupIpRouter1NNatServiceTableEntry 2 }

-- {COLUMN} 310.2.8.9.4.1.4
lcsSetupIpRouter1NNatServiceTableEntryMapPort OBJECT-TYPE
    SYNTAX     INTEGER (0..65535)
    MAX-ACCESS read-write
    STATUS     current
    DESCRIPTION
        "-- empty --"
    ::= { lcsSetupIpRouter1NNatServiceTableEntry 4 }

-- {COLUMN} 310.2.8.9.4.1.5
lcsSetupIpRouter1NNatServiceTableEntryActive OBJECT-TYPE
    SYNTAX     INTEGER
      {
        eNo (1),
        eYes (0)
      }
    MAX-ACCESS read-write
    STATUS     current
    DESCRIPTION
        "-- empty --"
    ::= { lcsSetupIpRouter1NNatServiceTableEntry 5 }

-- {COLUMN} 310.2.8.9.4.1.6
lcsSetupIpRouter1NNatServiceTableEntryComment OBJECT-TYPE
    SYNTAX     DisplayString (SIZE(0..64))
    MAX-ACCESS read-write
    STATUS     current
    DESCRIPTION
        "-- empty --"
    ::= { lcsSetupIpRouter1NNatServiceTableEntry 6 }

-- {TABLE} 310.2.8.9.5
lcsSetupIpRouter1NNatTable1NNatTable OBJECT-TYPE
    SYNTAX     SEQUENCE OF LcsSetupIpRouter1NNatTable1NNatEntry
    MAX-ACCESS not-accessible
    STATUS     current
    DESCRIPTION
        "-- empty --"
    ::= { lcsSetupIpRouter1NNat 5 }

-- {ENTRY} 310.2.8.9.5.1
lcsSetupIpRouter1NNatTable1NNatEntry OBJECT-TYPE
    SYNTAX     LcsSetupIpRouter1NNatTable1NNatEntry
    MAX-ACCESS not-accessible
    STATUS     current
    DESCRIPTION
        ""
    INDEX {
        lcsSetupIpRouter1NNatTable1NNatEntryIntranetAddress
    }
    ::= { lcsSetupIpRouter1NNatTable1NNatTable 1 }

-- {SEQUENCE}
LcsSetupIpRouter1NNatTable1NNatEntry ::= SEQUENCE {
    lcsSetupIpRouter1NNatTable1NNatEntryIntranetAddress IpAddress,
    lcsSetupIpRouter1NNatTable1NNatEntrySourcePort INTEGER,
    lcsSetupIpRouter1NNatTable1NNatEntryProtocol INTEGER,
    lcsSetupIpRouter1NNatTable1NNatEntryTimeout INTEGER,
    lcsSetupIpRouter1NNatTable1NNatEntryHandler DisplayString,
    lcsSetupIpRouter1NNatTable1NNatEntryRemoteAddress IpAddress
}

-- {COLUMN} 310.2.8.9.5.1.1
lcsSetupIpRouter1NNatTable1NNatEntryIntranetAddress OBJECT-TYPE
    SYNTAX     IpAddress
    MAX-ACCESS read-only
    STATUS     current
    DESCRIPTION
        "-- empty --"
    ::= { lcsSetupIpRouter1NNatTable1NNatEntry 1 }

-- {COLUMN} 310.2.8.9.5.1.2
lcsSetupIpRouter1NNatTable1NNatEntrySourcePort OBJECT-TYPE
    SYNTAX     INTEGER (0..65535)
    MAX-ACCESS read-only
    STATUS     current
    DESCRIPTION
        "-- empty --"
    ::= { lcsSetupIpRouter1NNatTable1NNatEntry 2 }

-- {COLUMN} 310.2.8.9.5.1.3
lcsSetupIpRouter1NNatTable1NNatEntryProtocol OBJECT-TYPE
    SYNTAX     INTEGER
      {
        eTcp (6),
        eUdp (17),
        eIcmp (1)
      }
    MAX-ACCESS read-only
    STATUS     current
    DESCRIPTION
        "-- empty --"
    ::= { lcsSetupIpRouter1NNatTable1NNatEntry 3 }

-- {COLUMN} 310.2.8.9.5.1.4
lcsSetupIpRouter1NNatTable1NNatEntryTimeout OBJECT-TYPE
    SYNTAX     INTEGER (0..65535)
    MAX-ACCESS read-only
    STATUS     current
    DESCRIPTION
        "-- empty --"
    ::= { lcsSetupIpRouter1NNatTable1NNatEntry 4 }

-- {COLUMN} 310.2.8.9.5.1.5
lcsSetupIpRouter1NNatTable1NNatEntryHandler OBJECT-TYPE
    SYNTAX     DisplayString (SIZE(0..255))
    MAX-ACCESS read-only
    STATUS     current
    DESCRIPTION
        "-- empty --"
    ::= { lcsSetupIpRouter1NNatTable1NNatEntry 5 }

-- {COLUMN} 310.2.8.9.5.1.6
lcsSetupIpRouter1NNatTable1NNatEntryRemoteAddress OBJECT-TYPE
    SYNTAX     IpAddress
    MAX-ACCESS read-only
    STATUS     current
    DESCRIPTION
        "-- empty --"
    ::= { lcsSetupIpRouter1NNatTable1NNatEntry 6 }

-- {SCALAR} 310.2.8.9.6
lcsSetupIpRouter1NNatFragments OBJECT-TYPE
    SYNTAX     INTEGER
      {
        eFilter (0),
        eRoute (1),
        eReassemble (2)
      }
    MAX-ACCESS read-only
    STATUS     current
    DESCRIPTION
        "-- empty --"
    ::= { lcsSetupIpRouter1NNat 6 }

-- {SCALAR} 310.2.8.9.7
lcsSetupIpRouter1NNatFragmentAgingSeconds OBJECT-TYPE
    SYNTAX     INTEGER (0..255)
    MAX-ACCESS read-only
    STATUS     current
    DESCRIPTION
        "-- empty --"
    ::= { lcsSetupIpRouter1NNat 7 }

-- {SCALAR} 310.2.8.9.8
lcsSetupIpRouter1NNatIpsecAgingSeconds OBJECT-TYPE
    SYNTAX     INTEGER (0..65535)
    MAX-ACCESS read-only
    STATUS     current
    DESCRIPTION
        "-- empty --"
    ::= { lcsSetupIpRouter1NNat 8 }

-- {TABLE} 310.2.8.9.9
lcsSetupIpRouter1NNatIpsecTableTable OBJECT-TYPE
    SYNTAX     SEQUENCE OF LcsSetupIpRouter1NNatIpsecTableEntry
    MAX-ACCESS not-accessible
    STATUS     current
    DESCRIPTION
        "-- empty --"
    ::= { lcsSetupIpRouter1NNat 9 }

-- {ENTRY} 310.2.8.9.9.1
lcsSetupIpRouter1NNatIpsecTableEntry OBJECT-TYPE
    SYNTAX     LcsSetupIpRouter1NNatIpsecTableEntry
    MAX-ACCESS not-accessible
    STATUS     current
    DESCRIPTION
        ""
    INDEX {
        lcsSetupIpRouter1NNatIpsecTableEntryRemoteAddress
    }
    ::= { lcsSetupIpRouter1NNatIpsecTableTable 1 }

-- {SEQUENCE}
LcsSetupIpRouter1NNatIpsecTableEntry ::= SEQUENCE {
    lcsSetupIpRouter1NNatIpsecTableEntryRemoteAddress IpAddress,
    lcsSetupIpRouter1NNatIpsecTableEntryLocalAddress IpAddress,
    lcsSetupIpRouter1NNatIpsecTableEntryRcHi DisplayString,
    lcsSetupIpRouter1NNatIpsecTableEntryRcLo DisplayString,
    lcsSetupIpRouter1NNatIpsecTableEntryLcHi DisplayString,
    lcsSetupIpRouter1NNatIpsecTableEntryLcLo DisplayString,
    lcsSetupIpRouter1NNatIpsecTableEntryRemoteSpi DisplayString,
    lcsSetupIpRouter1NNatIpsecTableEntryLocalSpi DisplayString,
    lcsSetupIpRouter1NNatIpsecTableEntryTimeout INTEGER,
    lcsSetupIpRouter1NNatIpsecTableEntryCo INTEGER,
    lcsSetupIpRouter1NNatIpsecTableEntryNl INTEGER,
    lcsSetupIpRouter1NNatIpsecTableEntryNr INTEGER,
    lcsSetupIpRouter1NNatIpsecTableEntryDp INTEGER,
    lcsSetupIpRouter1NNatIpsecTableEntryFlags DisplayString
}

-- {COLUMN} 310.2.8.9.9.1.1
lcsSetupIpRouter1NNatIpsecTableEntryRemoteAddress OBJECT-TYPE
    SYNTAX     IpAddress
    MAX-ACCESS read-only
    STATUS     current
    DESCRIPTION
        "-- empty --"
    ::= { lcsSetupIpRouter1NNatIpsecTableEntry 1 }

-- {COLUMN} 310.2.8.9.9.1.2
lcsSetupIpRouter1NNatIpsecTableEntryLocalAddress OBJECT-TYPE
    SYNTAX     IpAddress
    MAX-ACCESS read-only
    STATUS     current
    DESCRIPTION
        "-- empty --"
    ::= { lcsSetupIpRouter1NNatIpsecTableEntry 2 }

-- {COLUMN} 310.2.8.9.9.1.3
lcsSetupIpRouter1NNatIpsecTableEntryRcHi OBJECT-TYPE
    SYNTAX     DisplayString (SIZE(0..8))
    MAX-ACCESS read-only
    STATUS     current
    DESCRIPTION
        "-- empty --"
    ::= { lcsSetupIpRouter1NNatIpsecTableEntry 3 }

-- {COLUMN} 310.2.8.9.9.1.4
lcsSetupIpRouter1NNatIpsecTableEntryRcLo OBJECT-TYPE
    SYNTAX     DisplayString (SIZE(0..8))
    MAX-ACCESS read-only
    STATUS     current
    DESCRIPTION
        "-- empty --"
    ::= { lcsSetupIpRouter1NNatIpsecTableEntry 4 }

-- {COLUMN} 310.2.8.9.9.1.5
lcsSetupIpRouter1NNatIpsecTableEntryLcHi OBJECT-TYPE
    SYNTAX     DisplayString (SIZE(0..8))
    MAX-ACCESS read-only
    STATUS     current
    DESCRIPTION
        "-- empty --"
    ::= { lcsSetupIpRouter1NNatIpsecTableEntry 5 }

-- {COLUMN} 310.2.8.9.9.1.6
lcsSetupIpRouter1NNatIpsecTableEntryLcLo OBJECT-TYPE
    SYNTAX     DisplayString (SIZE(0..8))
    MAX-ACCESS read-only
    STATUS     current
    DESCRIPTION
        "-- empty --"
    ::= { lcsSetupIpRouter1NNatIpsecTableEntry 6 }

-- {COLUMN} 310.2.8.9.9.1.7
lcsSetupIpRouter1NNatIpsecTableEntryRemoteSpi OBJECT-TYPE
    SYNTAX     DisplayString (SIZE(0..8))
    MAX-ACCESS read-only
    STATUS     current
    DESCRIPTION
        "-- empty --"
    ::= { lcsSetupIpRouter1NNatIpsecTableEntry 7 }

-- {COLUMN} 310.2.8.9.9.1.8
lcsSetupIpRouter1NNatIpsecTableEntryLocalSpi OBJECT-TYPE
    SYNTAX     DisplayString (SIZE(0..8))
    MAX-ACCESS read-only
    STATUS     current
    DESCRIPTION
        "-- empty --"
    ::= { lcsSetupIpRouter1NNatIpsecTableEntry 8 }

-- {COLUMN} 310.2.8.9.9.1.9
lcsSetupIpRouter1NNatIpsecTableEntryTimeout OBJECT-TYPE
    SYNTAX     INTEGER (0..2147483647)
    MAX-ACCESS read-only
    STATUS     current
    DESCRIPTION
        "-- empty --"
    ::= { lcsSetupIpRouter1NNatIpsecTableEntry 9 }

-- {COLUMN} 310.2.8.9.9.1.11
lcsSetupIpRouter1NNatIpsecTableEntryCo OBJECT-TYPE
    SYNTAX     INTEGER (0..255)
    MAX-ACCESS read-only
    STATUS     current
    DESCRIPTION
        "-- empty --"
    ::= { lcsSetupIpRouter1NNatIpsecTableEntry 11 }

-- {COLUMN} 310.2.8.9.9.1.12
lcsSetupIpRouter1NNatIpsecTableEntryNl OBJECT-TYPE
    SYNTAX     INTEGER (0..255)
    MAX-ACCESS read-only
    STATUS     current
    DESCRIPTION
        "-- empty --"
    ::= { lcsSetupIpRouter1NNatIpsecTableEntry 12 }

-- {COLUMN} 310.2.8.9.9.1.13
lcsSetupIpRouter1NNatIpsecTableEntryNr OBJECT-TYPE
    SYNTAX     INTEGER (0..255)
    MAX-ACCESS read-only
    STATUS     current
    DESCRIPTION
        "-- empty --"
    ::= { lcsSetupIpRouter1NNatIpsecTableEntry 13 }

-- {COLUMN} 310.2.8.9.9.1.14
lcsSetupIpRouter1NNatIpsecTableEntryDp OBJECT-TYPE
    SYNTAX     INTEGER (0..255)
    MAX-ACCESS read-only
    STATUS     current
    DESCRIPTION
        "-- empty --"
    ::= { lcsSetupIpRouter1NNatIpsecTableEntry 14 }

-- {COLUMN} 310.2.8.9.9.1.10
lcsSetupIpRouter1NNatIpsecTableEntryFlags OBJECT-TYPE
    SYNTAX     DisplayString (SIZE(0..4))
    MAX-ACCESS read-only
    STATUS     current
    DESCRIPTION
        "-- empty --"
    ::= { lcsSetupIpRouter1NNatIpsecTableEntry 10 }

-- {SCALAR} 310.2.8.9.10
lcsSetupIpRouter1NNatIdSpoofing OBJECT-TYPE
    SYNTAX     INTEGER
      {
        eNo (0),
        eYes (1)
      }
    MAX-ACCESS read-only
    STATUS     current
    DESCRIPTION
        "-- empty --"
    ::= { lcsSetupIpRouter1NNat 10 }

-- {OID} 310.2.8.10
lcsSetupIpRouterFirewall OBJECT IDENTIFIER ::= { lcsSetupIpRouter 10 }

-- {SCALAR} 310.2.8.10.11
lcsSetupIpRouterFirewallOperating OBJECT-TYPE
    SYNTAX     INTEGER
      {
        eNo (0),
        eYes (1)
      }
    MAX-ACCESS read-only
    STATUS     current
    DESCRIPTION
        "-- empty --"
    ::= { lcsSetupIpRouterFirewall 11 }

-- {TABLE} 310.2.8.10.4
lcsSetupIpRouterFirewallActionsTable OBJECT-TYPE
    SYNTAX     SEQUENCE OF LcsSetupIpRouterFirewallActionsEntry
    MAX-ACCESS not-accessible
    STATUS     current
    DESCRIPTION
        "-- empty --"
    ::= { lcsSetupIpRouterFirewall 4 }

-- {ENTRY} 310.2.8.10.4.1
lcsSetupIpRouterFirewallActionsEntry OBJECT-TYPE
    SYNTAX     LcsSetupIpRouterFirewallActionsEntry
    MAX-ACCESS not-accessible
    STATUS     current
    DESCRIPTION
        ""
    INDEX {
        lcsSetupIpRouterFirewallActionsEntryName
    }
    ::= { lcsSetupIpRouterFirewallActionsTable 1 }

-- {SEQUENCE}
LcsSetupIpRouterFirewallActionsEntry ::= SEQUENCE {
    lcsSetupIpRouterFirewallActionsEntryName DisplayString,
    lcsSetupIpRouterFirewallActionsEntryDescription DisplayString
}

-- {COLUMN} 310.2.8.10.4.1.1
lcsSetupIpRouterFirewallActionsEntryName OBJECT-TYPE
    SYNTAX     DisplayString (SIZE(0..32))
    MAX-ACCESS read-write
    STATUS     current
    DESCRIPTION
        "-- empty --"
    ::= { lcsSetupIpRouterFirewallActionsEntry 1 }

-- {COLUMN} 310.2.8.10.4.1.2
lcsSetupIpRouterFirewallActionsEntryDescription OBJECT-TYPE
    SYNTAX     DisplayString (SIZE(0..64))
    MAX-ACCESS read-write
    STATUS     current
    DESCRIPTION
        "-- empty --"
    ::= { lcsSetupIpRouterFirewallActionsEntry 2 }

-- {TABLE} 310.2.8.10.1
lcsSetupIpRouterFirewallObjectsTable OBJECT-TYPE
    SYNTAX     SEQUENCE OF LcsSetupIpRouterFirewallObjectsEntry
    MAX-ACCESS not-accessible
    STATUS     current
    DESCRIPTION
        "-- empty --"
    ::= { lcsSetupIpRouterFirewall 1 }

-- {ENTRY} 310.2.8.10.1.1
lcsSetupIpRouterFirewallObjectsEntry OBJECT-TYPE
    SYNTAX     LcsSetupIpRouterFirewallObjectsEntry
    MAX-ACCESS not-accessible
    STATUS     current
    DESCRIPTION
        ""
    INDEX {
        lcsSetupIpRouterFirewallObjectsEntryName
    }
    ::= { lcsSetupIpRouterFirewallObjectsTable 1 }

-- {SEQUENCE}
LcsSetupIpRouterFirewallObjectsEntry ::= SEQUENCE {
    lcsSetupIpRouterFirewallObjectsEntryName DisplayString,
    lcsSetupIpRouterFirewallObjectsEntryDescription DisplayString
}

-- {COLUMN} 310.2.8.10.1.1.1
lcsSetupIpRouterFirewallObjectsEntryName OBJECT-TYPE
    SYNTAX     DisplayString (SIZE(0..32))
    MAX-ACCESS read-write
    STATUS     current
    DESCRIPTION
        "-- empty --"
    ::= { lcsSetupIpRouterFirewallObjectsEntry 1 }

-- {COLUMN} 310.2.8.10.1.1.2
lcsSetupIpRouterFirewallObjectsEntryDescription OBJECT-TYPE
    SYNTAX     DisplayString (SIZE(0..64))
    MAX-ACCESS read-write
    STATUS     current
    DESCRIPTION
        "-- empty --"
    ::= { lcsSetupIpRouterFirewallObjectsEntry 2 }

-- {TABLE} 310.2.8.10.2
lcsSetupIpRouterFirewallRulesTable OBJECT-TYPE
    SYNTAX     SEQUENCE OF LcsSetupIpRouterFirewallRulesEntry
    MAX-ACCESS not-accessible
    STATUS     current
    DESCRIPTION
        "-- empty --"
    ::= { lcsSetupIpRouterFirewall 2 }

-- {ENTRY} 310.2.8.10.2.1
lcsSetupIpRouterFirewallRulesEntry OBJECT-TYPE
    SYNTAX     LcsSetupIpRouterFirewallRulesEntry
    MAX-ACCESS not-accessible
    STATUS     current
    DESCRIPTION
        ""
    INDEX {
        lcsSetupIpRouterFirewallRulesEntryName
    }
    ::= { lcsSetupIpRouterFirewallRulesTable 1 }

-- {SEQUENCE}
LcsSetupIpRouterFirewallRulesEntry ::= SEQUENCE {
    lcsSetupIpRouterFirewallRulesEntryName DisplayString,
    lcsSetupIpRouterFirewallRulesEntryProt DisplayString,
    lcsSetupIpRouterFirewallRulesEntrySource DisplayString,
    lcsSetupIpRouterFirewallRulesEntryDestination DisplayString,
    lcsSetupIpRouterFirewallRulesEntryAction DisplayString,
    lcsSetupIpRouterFirewallRulesEntryLinked INTEGER,
    lcsSetupIpRouterFirewallRulesEntryPrio INTEGER,
    lcsSetupIpRouterFirewallRulesEntryFirewallRule INTEGER,
    lcsSetupIpRouterFirewallRulesEntryStateful INTEGER,
    lcsSetupIpRouterFirewallRulesEntryRtgTag INTEGER,
    lcsSetupIpRouterFirewallRulesEntryComment DisplayString
}

-- {COLUMN} 310.2.8.10.2.1.1
lcsSetupIpRouterFirewallRulesEntryName OBJECT-TYPE
    SYNTAX     DisplayString (SIZE(0..32))
    MAX-ACCESS read-write
    STATUS     current
    DESCRIPTION
        "-- empty --"
    ::= { lcsSetupIpRouterFirewallRulesEntry 1 }

-- {COLUMN} 310.2.8.10.2.1.2
lcsSetupIpRouterFirewallRulesEntryProt OBJECT-TYPE
    SYNTAX     DisplayString (SIZE(0..10))
    MAX-ACCESS read-write
    STATUS     current
    DESCRIPTION
        "-- empty --"
    ::= { lcsSetupIpRouterFirewallRulesEntry 2 }

-- {COLUMN} 310.2.8.10.2.1.3
lcsSetupIpRouterFirewallRulesEntrySource OBJECT-TYPE
    SYNTAX     DisplayString (SIZE(0..40))
    MAX-ACCESS read-write
    STATUS     current
    DESCRIPTION
        "-- empty --"
    ::= { lcsSetupIpRouterFirewallRulesEntry 3 }

-- {COLUMN} 310.2.8.10.2.1.4
lcsSetupIpRouterFirewallRulesEntryDestination OBJECT-TYPE
    SYNTAX     DisplayString (SIZE(0..40))
    MAX-ACCESS read-write
    STATUS     current
    DESCRIPTION
        "-- empty --"
    ::= { lcsSetupIpRouterFirewallRulesEntry 4 }

-- {COLUMN} 310.2.8.10.2.1.7
lcsSetupIpRouterFirewallRulesEntryAction OBJECT-TYPE
    SYNTAX     DisplayString (SIZE(0..40))
    MAX-ACCESS read-write
    STATUS     current
    DESCRIPTION
        "-- empty --"
    ::= { lcsSetupIpRouterFirewallRulesEntry 7 }

-- {COLUMN} 310.2.8.10.2.1.8
lcsSetupIpRouterFirewallRulesEntryLinked OBJECT-TYPE
    SYNTAX     INTEGER
      {
        eNo (0),
        eYes (1)
      }
    MAX-ACCESS read-write
    STATUS     current
    DESCRIPTION
        "-- empty --"
    ::= { lcsSetupIpRouterFirewallRulesEntry 8 }

-- {COLUMN} 310.2.8.10.2.1.9
lcsSetupIpRouterFirewallRulesEntryPrio OBJECT-TYPE
    SYNTAX     INTEGER (0..65535)
    MAX-ACCESS read-write
    STATUS     current
    DESCRIPTION
        "-- empty --"
    ::= { lcsSetupIpRouterFirewallRulesEntry 9 }

-- {COLUMN} 310.2.8.10.2.1.10
lcsSetupIpRouterFirewallRulesEntryFirewallRule OBJECT-TYPE
    SYNTAX     INTEGER
      {
        eNo (1),
        eYes (0)
      }
    MAX-ACCESS read-write
    STATUS     current
    DESCRIPTION
        "-- empty --"
    ::= { lcsSetupIpRouterFirewallRulesEntry 10 }

-- {COLUMN} 310.2.8.10.2.1.12
lcsSetupIpRouterFirewallRulesEntryStateful OBJECT-TYPE
    SYNTAX     INTEGER
      {
        eNo (1),
        eYes (0)
      }
    MAX-ACCESS read-write
    STATUS     current
    DESCRIPTION
        "-- empty --"
    ::= { lcsSetupIpRouterFirewallRulesEntry 12 }

-- {COLUMN} 310.2.8.10.2.1.14
lcsSetupIpRouterFirewallRulesEntryRtgTag OBJECT-TYPE
    SYNTAX     INTEGER (0..65535)
    MAX-ACCESS read-write
    STATUS     current
    DESCRIPTION
        "-- empty --"
    ::= { lcsSetupIpRouterFirewallRulesEntry 14 }

-- {COLUMN} 310.2.8.10.2.1.13
lcsSetupIpRouterFirewallRulesEntryComment OBJECT-TYPE
    SYNTAX     DisplayString (SIZE(0..64))
    MAX-ACCESS read-write
    STATUS     current
    DESCRIPTION
        "-- empty --"
    ::= { lcsSetupIpRouterFirewallRulesEntry 13 }

-- {TABLE} 310.2.8.10.3
lcsSetupIpRouterFirewallFilterListTable OBJECT-TYPE
    SYNTAX     SEQUENCE OF LcsSetupIpRouterFirewallFilterListEntry
    MAX-ACCESS not-accessible
    STATUS     current
    DESCRIPTION
        "-- empty --"
    ::= { lcsSetupIpRouterFirewall 3 }

-- {ENTRY} 310.2.8.10.3.1
lcsSetupIpRouterFirewallFilterListEntry OBJECT-TYPE
    SYNTAX     LcsSetupIpRouterFirewallFilterListEntry
    MAX-ACCESS not-accessible
    STATUS     current
    DESCRIPTION
        ""
    INDEX {
        lcsSetupIpRouterFirewallFilterListEntryIdx
    }
    ::= { lcsSetupIpRouterFirewallFilterListTable 1 }

-- {SEQUENCE}
LcsSetupIpRouterFirewallFilterListEntry ::= SEQUENCE {
    lcsSetupIpRouterFirewallFilterListEntryIdx INTEGER,
    lcsSetupIpRouterFirewallFilterListEntryProt INTEGER,
    lcsSetupIpRouterFirewallFilterListEntrySrcMac DisplayString,
    lcsSetupIpRouterFirewallFilterListEntrySrcAddress IpAddress,
    lcsSetupIpRouterFirewallFilterListEntrySrcNetmask IpAddress,
    lcsSetupIpRouterFirewallFilterListEntrySSt INTEGER,
    lcsSetupIpRouterFirewallFilterListEntrySEnd INTEGER,
    lcsSetupIpRouterFirewallFilterListEntryDstMac DisplayString,
    lcsSetupIpRouterFirewallFilterListEntryDstAddress IpAddress,
    lcsSetupIpRouterFirewallFilterListEntryDstNetmask IpAddress,
    lcsSetupIpRouterFirewallFilterListEntryDSt INTEGER,
    lcsSetupIpRouterFirewallFilterListEntryDEnd INTEGER,
    lcsSetupIpRouterFirewallFilterListEntryAction DisplayString,
    lcsSetupIpRouterFirewallFilterListEntryLinked INTEGER,
    lcsSetupIpRouterFirewallFilterListEntryPrio INTEGER,
    lcsSetupIpRouterFirewallFilterListEntryRtgTag INTEGER
}

-- {COLUMN} 310.2.8.10.3.1.1
lcsSetupIpRouterFirewallFilterListEntryIdx OBJECT-TYPE
    SYNTAX     INTEGER (0..2147483647)
    MAX-ACCESS read-only
    STATUS     current
    DESCRIPTION
        "-- empty --"
    ::= { lcsSetupIpRouterFirewallFilterListEntry 1 }

-- {COLUMN} 310.2.8.10.3.1.2
lcsSetupIpRouterFirewallFilterListEntryProt OBJECT-TYPE
    SYNTAX     INTEGER (0..255)
    MAX-ACCESS read-only
    STATUS     current
    DESCRIPTION
        "-- empty --"
    ::= { lcsSetupIpRouterFirewallFilterListEntry 2 }

-- {COLUMN} 310.2.8.10.3.1.13
lcsSetupIpRouterFirewallFilterListEntrySrcMac OBJECT-TYPE
    SYNTAX     DisplayString (SIZE(0..255))
    MAX-ACCESS read-only
    STATUS     current
    DESCRIPTION
        "-- empty --"
    ::= { lcsSetupIpRouterFirewallFilterListEntry 13 }

-- {COLUMN} 310.2.8.10.3.1.3
lcsSetupIpRouterFirewallFilterListEntrySrcAddress OBJECT-TYPE
    SYNTAX     IpAddress
    MAX-ACCESS read-only
    STATUS     current
    DESCRIPTION
        "-- empty --"
    ::= { lcsSetupIpRouterFirewallFilterListEntry 3 }

-- {COLUMN} 310.2.8.10.3.1.4
lcsSetupIpRouterFirewallFilterListEntrySrcNetmask OBJECT-TYPE
    SYNTAX     IpAddress
    MAX-ACCESS read-only
    STATUS     current
    DESCRIPTION
        "-- empty --"
    ::= { lcsSetupIpRouterFirewallFilterListEntry 4 }

-- {COLUMN} 310.2.8.10.3.1.5
lcsSetupIpRouterFirewallFilterListEntrySSt OBJECT-TYPE
    SYNTAX     INTEGER (0..65535)
    MAX-ACCESS read-only
    STATUS     current
    DESCRIPTION
        "-- empty --"
    ::= { lcsSetupIpRouterFirewallFilterListEntry 5 }

-- {COLUMN} 310.2.8.10.3.1.6
lcsSetupIpRouterFirewallFilterListEntrySEnd OBJECT-TYPE
    SYNTAX     INTEGER (0..65535)
    MAX-ACCESS read-only
    STATUS     current
    DESCRIPTION
        "-- empty --"
    ::= { lcsSetupIpRouterFirewallFilterListEntry 6 }

-- {COLUMN} 310.2.8.10.3.1.14
lcsSetupIpRouterFirewallFilterListEntryDstMac OBJECT-TYPE
    SYNTAX     DisplayString (SIZE(0..255))
    MAX-ACCESS read-only
    STATUS     current
    DESCRIPTION
        "-- empty --"
    ::= { lcsSetupIpRouterFirewallFilterListEntry 14 }

-- {COLUMN} 310.2.8.10.3.1.7
lcsSetupIpRouterFirewallFilterListEntryDstAddress OBJECT-TYPE
    SYNTAX     IpAddress
    MAX-ACCESS read-only
    STATUS     current
    DESCRIPTION
        "-- empty --"
    ::= { lcsSetupIpRouterFirewallFilterListEntry 7 }

-- {COLUMN} 310.2.8.10.3.1.8
lcsSetupIpRouterFirewallFilterListEntryDstNetmask OBJECT-TYPE
    SYNTAX     IpAddress
    MAX-ACCESS read-only
    STATUS     current
    DESCRIPTION
        "-- empty --"
    ::= { lcsSetupIpRouterFirewallFilterListEntry 8 }

-- {COLUMN} 310.2.8.10.3.1.9
lcsSetupIpRouterFirewallFilterListEntryDSt OBJECT-TYPE
    SYNTAX     INTEGER (0..65535)
    MAX-ACCESS read-only
    STATUS     current
    DESCRIPTION
        "-- empty --"
    ::= { lcsSetupIpRouterFirewallFilterListEntry 9 }

-- {COLUMN} 310.2.8.10.3.1.10
lcsSetupIpRouterFirewallFilterListEntryDEnd OBJECT-TYPE
    SYNTAX     INTEGER (0..65535)
    MAX-ACCESS read-only
    STATUS     current
    DESCRIPTION
        "-- empty --"
    ::= { lcsSetupIpRouterFirewallFilterListEntry 10 }

-- {COLUMN} 310.2.8.10.3.1.11
lcsSetupIpRouterFirewallFilterListEntryAction OBJECT-TYPE
    SYNTAX     DisplayString (SIZE(0..255))
    MAX-ACCESS read-only
    STATUS     current
    DESCRIPTION
        "-- empty --"
    ::= { lcsSetupIpRouterFirewallFilterListEntry 11 }

-- {COLUMN} 310.2.8.10.3.1.15
lcsSetupIpRouterFirewallFilterListEntryLinked OBJECT-TYPE
    SYNTAX     INTEGER
      {
        eNo (0),
        eYes (1)
      }
    MAX-ACCESS read-only
    STATUS     current
    DESCRIPTION
        "-- empty --"
    ::= { lcsSetupIpRouterFirewallFilterListEntry 15 }

-- {COLUMN} 310.2.8.10.3.1.16
lcsSetupIpRouterFirewallFilterListEntryPrio OBJECT-TYPE
    SYNTAX     INTEGER (0..65535)
    MAX-ACCESS read-only
    STATUS     current
    DESCRIPTION
        "-- empty --"
    ::= { lcsSetupIpRouterFirewallFilterListEntry 16 }

-- {COLUMN} 310.2.8.10.3.1.17
lcsSetupIpRouterFirewallFilterListEntryRtgTag OBJECT-TYPE
    SYNTAX     INTEGER (0..65535)
    MAX-ACCESS read-only
    STATUS     current
    DESCRIPTION
        "-- empty --"
    ::= { lcsSetupIpRouterFirewallFilterListEntry 17 }

-- {TABLE} 310.2.8.10.5
lcsSetupIpRouterFirewallConnectionListTable OBJECT-TYPE
    SYNTAX     SEQUENCE OF LcsSetupIpRouterFirewallConnectionListEntry
    MAX-ACCESS not-accessible
    STATUS     current
    DESCRIPTION
        "-- empty --"
    ::= { lcsSetupIpRouterFirewall 5 }

-- {ENTRY} 310.2.8.10.5.1
lcsSetupIpRouterFirewallConnectionListEntry OBJECT-TYPE
    SYNTAX     LcsSetupIpRouterFirewallConnectionListEntry
    MAX-ACCESS not-accessible
    STATUS     current
    DESCRIPTION
        ""
    INDEX {
        lcsSetupIpRouterFirewallConnectionListEntrySrcAddress,
        lcsSetupIpRouterFirewallConnectionListEntryDstAddress,
        lcsSetupIpRouterFirewallConnectionListEntryProt,
        lcsSetupIpRouterFirewallConnectionListEntrySrcPort,
        lcsSetupIpRouterFirewallConnectionListEntryDstPort
    }
    ::= { lcsSetupIpRouterFirewallConnectionListTable 1 }

-- {SEQUENCE}
LcsSetupIpRouterFirewallConnectionListEntry ::= SEQUENCE {
    lcsSetupIpRouterFirewallConnectionListEntrySrcAddress IpAddress,
    lcsSetupIpRouterFirewallConnectionListEntryDstAddress IpAddress,
    lcsSetupIpRouterFirewallConnectionListEntryProt INTEGER,
    lcsSetupIpRouterFirewallConnectionListEntrySrcPort INTEGER,
    lcsSetupIpRouterFirewallConnectionListEntryDstPort INTEGER,
    lcsSetupIpRouterFirewallConnectionListEntryRtgTag INTEGER,
    lcsSetupIpRouterFirewallConnectionListEntryTimeout INTEGER,
    lcsSetupIpRouterFirewallConnectionListEntryFlags INTEGER,
    lcsSetupIpRouterFirewallConnectionListEntryFilterRule DisplayString,
    lcsSetupIpRouterFirewallConnectionListEntrySrcRoute DisplayString,
    lcsSetupIpRouterFirewallConnectionListEntryDestRoute DisplayString
}

-- {COLUMN} 310.2.8.10.5.1.1
lcsSetupIpRouterFirewallConnectionListEntrySrcAddress OBJECT-TYPE
    SYNTAX     IpAddress
    MAX-ACCESS read-only
    STATUS     current
    DESCRIPTION
        "-- empty --"
    ::= { lcsSetupIpRouterFirewallConnectionListEntry 1 }

-- {COLUMN} 310.2.8.10.5.1.2
lcsSetupIpRouterFirewallConnectionListEntryDstAddress OBJECT-TYPE
    SYNTAX     IpAddress
    MAX-ACCESS read-only
    STATUS     current
    DESCRIPTION
        "-- empty --"
    ::= { lcsSetupIpRouterFirewallConnectionListEntry 2 }

-- {COLUMN} 310.2.8.10.5.1.3
lcsSetupIpRouterFirewallConnectionListEntryProt OBJECT-TYPE
    SYNTAX     INTEGER (0..255)
    MAX-ACCESS read-only
    STATUS     current
    DESCRIPTION
        "-- empty --"
    ::= { lcsSetupIpRouterFirewallConnectionListEntry 3 }

-- {COLUMN} 310.2.8.10.5.1.4
lcsSetupIpRouterFirewallConnectionListEntrySrcPort OBJECT-TYPE
    SYNTAX     INTEGER (0..65535)
    MAX-ACCESS read-only
    STATUS     current
    DESCRIPTION
        "-- empty --"
    ::= { lcsSetupIpRouterFirewallConnectionListEntry 4 }

-- {COLUMN} 310.2.8.10.5.1.5
lcsSetupIpRouterFirewallConnectionListEntryDstPort OBJECT-TYPE
    SYNTAX     INTEGER (0..65535)
    MAX-ACCESS read-only
    STATUS     current
    DESCRIPTION
        "-- empty --"
    ::= { lcsSetupIpRouterFirewallConnectionListEntry 5 }

-- {COLUMN} 310.2.8.10.5.1.11
lcsSetupIpRouterFirewallConnectionListEntryRtgTag OBJECT-TYPE
    SYNTAX     INTEGER (0..65535)
    MAX-ACCESS read-only
    STATUS     current
    DESCRIPTION
        "-- empty --"
    ::= { lcsSetupIpRouterFirewallConnectionListEntry 11 }

-- {COLUMN} 310.2.8.10.5.1.6
lcsSetupIpRouterFirewallConnectionListEntryTimeout OBJECT-TYPE
    SYNTAX     INTEGER (0..65535)
    MAX-ACCESS read-only
    STATUS     current
    DESCRIPTION
        "-- empty --"
    ::= { lcsSetupIpRouterFirewallConnectionListEntry 6 }

-- {COLUMN} 310.2.8.10.5.1.7
lcsSetupIpRouterFirewallConnectionListEntryFlags OBJECT-TYPE
    SYNTAX     INTEGER (0..2147483647)
    MAX-ACCESS read-only
    STATUS     current
    DESCRIPTION
        "-- empty --"
    ::= { lcsSetupIpRouterFirewallConnectionListEntry 7 }

-- {COLUMN} 310.2.8.10.5.1.8
lcsSetupIpRouterFirewallConnectionListEntryFilterRule OBJECT-TYPE
    SYNTAX     DisplayString (SIZE(0..255))
    MAX-ACCESS read-only
    STATUS     current
    DESCRIPTION
        "-- empty --"
    ::= { lcsSetupIpRouterFirewallConnectionListEntry 8 }

-- {COLUMN} 310.2.8.10.5.1.9
lcsSetupIpRouterFirewallConnectionListEntrySrcRoute OBJECT-TYPE
    SYNTAX     DisplayString (SIZE(0..255))
    MAX-ACCESS read-only
    STATUS     current
    DESCRIPTION
        "-- empty --"
    ::= { lcsSetupIpRouterFirewallConnectionListEntry 9 }

-- {COLUMN} 310.2.8.10.5.1.10
lcsSetupIpRouterFirewallConnectionListEntryDestRoute OBJECT-TYPE
    SYNTAX     DisplayString (SIZE(0..255))
    MAX-ACCESS read-only
    STATUS     current
    DESCRIPTION
        "-- empty --"
    ::= { lcsSetupIpRouterFirewallConnectionListEntry 10 }

-- {TABLE} 310.2.8.10.19
lcsSetupIpRouterFirewallOpenPortListTable OBJECT-TYPE
    SYNTAX     SEQUENCE OF LcsSetupIpRouterFirewallOpenPortListEntry
    MAX-ACCESS not-accessible
    STATUS     current
    DESCRIPTION
        "-- empty --"
    ::= { lcsSetupIpRouterFirewall 19 }

-- {ENTRY} 310.2.8.10.19.1
lcsSetupIpRouterFirewallOpenPortListEntry OBJECT-TYPE
    SYNTAX     LcsSetupIpRouterFirewallOpenPortListEntry
    MAX-ACCESS not-accessible
    STATUS     current
    DESCRIPTION
        ""
    INDEX {
        lcsSetupIpRouterFirewallOpenPortListEntrySrcAddress,
        lcsSetupIpRouterFirewallOpenPortListEntryDstAddress,
        lcsSetupIpRouterFirewallOpenPortListEntryProt,
        lcsSetupIpRouterFirewallOpenPortListEntryDstPort
    }
    ::= { lcsSetupIpRouterFirewallOpenPortListTable 1 }

-- {SEQUENCE}
LcsSetupIpRouterFirewallOpenPortListEntry ::= SEQUENCE {
    lcsSetupIpRouterFirewallOpenPortListEntrySrcAddress IpAddress,
    lcsSetupIpRouterFirewallOpenPortListEntryDstAddress IpAddress,
    lcsSetupIpRouterFirewallOpenPortListEntryProt INTEGER,
    lcsSetupIpRouterFirewallOpenPortListEntryDstPort INTEGER,
    lcsSetupIpRouterFirewallOpenPortListEntryTimeout INTEGER,
    lcsSetupIpRouterFirewallOpenPortListEntryFilterRule DisplayString,
    lcsSetupIpRouterFirewallOpenPortListEntrySrcRoute DisplayString
}

-- {COLUMN} 310.2.8.10.19.1.1
lcsSetupIpRouterFirewallOpenPortListEntrySrcAddress OBJECT-TYPE
    SYNTAX     IpAddress
    MAX-ACCESS read-only
    STATUS     current
    DESCRIPTION
        "-- empty --"
    ::= { lcsSetupIpRouterFirewallOpenPortListEntry 1 }

-- {COLUMN} 310.2.8.10.19.1.2
lcsSetupIpRouterFirewallOpenPortListEntryDstAddress OBJECT-TYPE
    SYNTAX     IpAddress
    MAX-ACCESS read-only
    STATUS     current
    DESCRIPTION
        "-- empty --"
    ::= { lcsSetupIpRouterFirewallOpenPortListEntry 2 }

-- {COLUMN} 310.2.8.10.19.1.3
lcsSetupIpRouterFirewallOpenPortListEntryProt OBJECT-TYPE
    SYNTAX     INTEGER (0..255)
    MAX-ACCESS read-only
    STATUS     current
    DESCRIPTION
        "-- empty --"
    ::= { lcsSetupIpRouterFirewallOpenPortListEntry 3 }

-- {COLUMN} 310.2.8.10.19.1.5
lcsSetupIpRouterFirewallOpenPortListEntryDstPort OBJECT-TYPE
    SYNTAX     INTEGER (0..65535)
    MAX-ACCESS read-only
    STATUS     current
    DESCRIPTION
        "-- empty --"
    ::= { lcsSetupIpRouterFirewallOpenPortListEntry 5 }

-- {COLUMN} 310.2.8.10.19.1.6
lcsSetupIpRouterFirewallOpenPortListEntryTimeout OBJECT-TYPE
    SYNTAX     INTEGER (0..65535)
    MAX-ACCESS read-only
    STATUS     current
    DESCRIPTION
        "-- empty --"
    ::= { lcsSetupIpRouterFirewallOpenPortListEntry 6 }

-- {COLUMN} 310.2.8.10.19.1.8
lcsSetupIpRouterFirewallOpenPortListEntryFilterRule OBJECT-TYPE
    SYNTAX     DisplayString (SIZE(0..255))
    MAX-ACCESS read-only
    STATUS     current
    DESCRIPTION
        "-- empty --"
    ::= { lcsSetupIpRouterFirewallOpenPortListEntry 8 }

-- {COLUMN} 310.2.8.10.19.1.9
lcsSetupIpRouterFirewallOpenPortListEntrySrcRoute OBJECT-TYPE
    SYNTAX     DisplayString (SIZE(0..255))
    MAX-ACCESS read-only
    STATUS     current
    DESCRIPTION
        "-- empty --"
    ::= { lcsSetupIpRouterFirewallOpenPortListEntry 9 }

-- {TABLE} 310.2.8.10.6
lcsSetupIpRouterFirewallHostBlockListTable OBJECT-TYPE
    SYNTAX     SEQUENCE OF LcsSetupIpRouterFirewallHostBlockListEntry
    MAX-ACCESS not-accessible
    STATUS     current
    DESCRIPTION
        "-- empty --"
    ::= { lcsSetupIpRouterFirewall 6 }

-- {ENTRY} 310.2.8.10.6.1
lcsSetupIpRouterFirewallHostBlockListEntry OBJECT-TYPE
    SYNTAX     LcsSetupIpRouterFirewallHostBlockListEntry
    MAX-ACCESS not-accessible
    STATUS     current
    DESCRIPTION
        ""
    INDEX {
        lcsSetupIpRouterFirewallHostBlockListEntrySrcAddress
    }
    ::= { lcsSetupIpRouterFirewallHostBlockListTable 1 }

-- {SEQUENCE}
LcsSetupIpRouterFirewallHostBlockListEntry ::= SEQUENCE {
    lcsSetupIpRouterFirewallHostBlockListEntrySrcAddress IpAddress,
    lcsSetupIpRouterFirewallHostBlockListEntryTimeout INTEGER,
    lcsSetupIpRouterFirewallHostBlockListEntryFilterRule DisplayString
}

-- {COLUMN} 310.2.8.10.6.1.1
lcsSetupIpRouterFirewallHostBlockListEntrySrcAddress OBJECT-TYPE
    SYNTAX     IpAddress
    MAX-ACCESS read-only
    STATUS     current
    DESCRIPTION
        "-- empty --"
    ::= { lcsSetupIpRouterFirewallHostBlockListEntry 1 }

-- {COLUMN} 310.2.8.10.6.1.2
lcsSetupIpRouterFirewallHostBlockListEntryTimeout OBJECT-TYPE
    SYNTAX     INTEGER (0..2147483647)
    MAX-ACCESS read-only
    STATUS     current
    DESCRIPTION
        "-- empty --"
    ::= { lcsSetupIpRouterFirewallHostBlockListEntry 2 }

-- {COLUMN} 310.2.8.10.6.1.3
lcsSetupIpRouterFirewallHostBlockListEntryFilterRule OBJECT-TYPE
    SYNTAX     DisplayString (SIZE(0..255))
    MAX-ACCESS read-only
    STATUS     current
    DESCRIPTION
        "-- empty --"
    ::= { lcsSetupIpRouterFirewallHostBlockListEntry 3 }

-- {TABLE} 310.2.8.10.7
lcsSetupIpRouterFirewallPortBlockListTable OBJECT-TYPE
    SYNTAX     SEQUENCE OF LcsSetupIpRouterFirewallPortBlockListEntry
    MAX-ACCESS not-accessible
    STATUS     current
    DESCRIPTION
        "-- empty --"
    ::= { lcsSetupIpRouterFirewall 7 }

-- {ENTRY} 310.2.8.10.7.1
lcsSetupIpRouterFirewallPortBlockListEntry OBJECT-TYPE
    SYNTAX     LcsSetupIpRouterFirewallPortBlockListEntry
    MAX-ACCESS not-accessible
    STATUS     current
    DESCRIPTION
        ""
    INDEX {
        lcsSetupIpRouterFirewallPortBlockListEntryDstAddress
    }
    ::= { lcsSetupIpRouterFirewallPortBlockListTable 1 }

-- {SEQUENCE}
LcsSetupIpRouterFirewallPortBlockListEntry ::= SEQUENCE {
    lcsSetupIpRouterFirewallPortBlockListEntryDstAddress IpAddress,
    lcsSetupIpRouterFirewallPortBlockListEntryProt INTEGER,
    lcsSetupIpRouterFirewallPortBlockListEntryDstPort INTEGER,
    lcsSetupIpRouterFirewallPortBlockListEntryTimeout INTEGER,
    lcsSetupIpRouterFirewallPortBlockListEntryFilterRule DisplayString
}

-- {COLUMN} 310.2.8.10.7.1.1
lcsSetupIpRouterFirewallPortBlockListEntryDstAddress OBJECT-TYPE
    SYNTAX     IpAddress
    MAX-ACCESS read-only
    STATUS     current
    DESCRIPTION
        "-- empty --"
    ::= { lcsSetupIpRouterFirewallPortBlockListEntry 1 }

-- {COLUMN} 310.2.8.10.7.1.2
lcsSetupIpRouterFirewallPortBlockListEntryProt OBJECT-TYPE
    SYNTAX     INTEGER (0..65535)
    MAX-ACCESS read-only
    STATUS     current
    DESCRIPTION
        "-- empty --"
    ::= { lcsSetupIpRouterFirewallPortBlockListEntry 2 }

-- {COLUMN} 310.2.8.10.7.1.3
lcsSetupIpRouterFirewallPortBlockListEntryDstPort OBJECT-TYPE
    SYNTAX     INTEGER (0..65535)
    MAX-ACCESS read-only
    STATUS     current
    DESCRIPTION
        "-- empty --"
    ::= { lcsSetupIpRouterFirewallPortBlockListEntry 3 }

-- {COLUMN} 310.2.8.10.7.1.4
lcsSetupIpRouterFirewallPortBlockListEntryTimeout OBJECT-TYPE
    SYNTAX     INTEGER (0..2147483647)
    MAX-ACCESS read-only
    STATUS     current
    DESCRIPTION
        "-- empty --"
    ::= { lcsSetupIpRouterFirewallPortBlockListEntry 4 }

-- {COLUMN} 310.2.8.10.7.1.5
lcsSetupIpRouterFirewallPortBlockListEntryFilterRule OBJECT-TYPE
    SYNTAX     DisplayString (SIZE(0..255))
    MAX-ACCESS read-only
    STATUS     current
    DESCRIPTION
        "-- empty --"
    ::= { lcsSetupIpRouterFirewallPortBlockListEntry 5 }

-- {SCALAR} 310.2.8.10.8
lcsSetupIpRouterFirewallMaxHalfOpenConns OBJECT-TYPE
    SYNTAX     INTEGER (0..2147483647)
    MAX-ACCESS read-only
    STATUS     current
    DESCRIPTION
        "-- empty --"
    ::= { lcsSetupIpRouterFirewall 8 }

-- {SCALAR} 310.2.8.10.9
lcsSetupIpRouterFirewallDosAction OBJECT-TYPE
    SYNTAX     DisplayString (SIZE(0..29))
    MAX-ACCESS read-write
    STATUS     current
    DESCRIPTION
        "-- empty --"
    ::= { lcsSetupIpRouterFirewall 9 }

-- {SCALAR} 310.2.8.10.12
lcsSetupIpRouterFirewallPortScanThreshold OBJECT-TYPE
    SYNTAX     INTEGER (0..2147483647)
    MAX-ACCESS read-only
    STATUS     current
    DESCRIPTION
        "-- empty --"
    ::= { lcsSetupIpRouterFirewall 12 }

-- {SCALAR} 310.2.8.10.13
lcsSetupIpRouterFirewallIdsAction OBJECT-TYPE
    SYNTAX     DisplayString (SIZE(0..29))
    MAX-ACCESS read-write
    STATUS     current
    DESCRIPTION
        "-- empty --"
    ::= { lcsSetupIpRouterFirewall 13 }

-- {SCALAR} 310.2.8.10.10
lcsSetupIpRouterFirewallAdminEmail OBJECT-TYPE
    SYNTAX     DisplayString (SIZE(0..255))
    MAX-ACCESS read-only
    STATUS     current
    DESCRIPTION
        "-- empty --"
    ::= { lcsSetupIpRouterFirewall 10 }

-- {SCALAR} 310.2.8.10.14
lcsSetupIpRouterFirewallPingBlock OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewall 14 }

-- {SCALAR} 310.2.8.10.15
lcsSetupIpRouterFirewallStealthMode OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewall 15 }

-- {SCALAR} 310.2.8.10.16
lcsSetupIpRouterFirewallAuthPort OBJECT-TYPE
    SYNTAX     INTEGER
      {
        eClosed (0),
        eStealth (1)
      }
    MAX-ACCESS read-only
    STATUS     current
    DESCRIPTION
        "-- empty --"
    ::= { lcsSetupIpRouterFirewall 16 }

-- {SCALAR} 310.2.8.10.17
lcsSetupIpRouterFirewallDenySessionRecover OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewall 17 }

-- {OID} 310.2.8.10.20
lcsSetupIpRouterFirewallApplications OBJECT IDENTIFIER ::= { lcsSetupIpRouterFirewall 20 }

-- {OID} 310.2.8.10.20.1
lcsSetupIpRouterFirewallApplicationsFtp OBJECT IDENTIFIER ::= { lcsSetupIpRouterFirewallApplications 1 }

-- {SCALAR} 310.2.8.10.20.1.1
lcsSetupIpRouterFirewallApplicationsFtpFtpBlock OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsFtp 1 }

-- {SCALAR} 310.2.8.10.20.1.2
lcsSetupIpRouterFirewallApplicationsFtpActiveFtpBlock OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsFtp 2 }

-- {SCALAR} 310.2.8.10.20.1.3
lcsSetupIpRouterFirewallApplicationsFtpMinPort OBJECT-TYPE
    SYNTAX     INTEGER (0..65535)
    MAX-ACCESS read-only
    STATUS     current
    DESCRIPTION
        "-- empty --"
    ::= { lcsSetupIpRouterFirewallApplicationsFtp 3 }

-- {SCALAR} 310.2.8.10.20.1.4
lcsSetupIpRouterFirewallApplicationsFtpCheckHostIp OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsFtp 4 }

-- {SCALAR} 310.2.8.10.20.1.5
lcsSetupIpRouterFirewallApplicationsFtpFxpBlock OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsFtp 5 }

-- {OID} 310.2.8.10.20.2
lcsSetupIpRouterFirewallApplicationsIrc OBJECT IDENTIFIER ::= { lcsSetupIpRouterFirewallApplications 2 }

-- {SCALAR} 310.2.8.10.20.2.1
lcsSetupIpRouterFirewallApplicationsIrcIrcBlock OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsIrc 1 }

-- {SCALAR} 310.2.8.10.20.2.2
lcsSetupIpRouterFirewallApplicationsIrcDdcBlock OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsIrc 2 }

-- {SCALAR} 310.2.8.10.20.2.3
lcsSetupIpRouterFirewallApplicationsIrcMinPort OBJECT-TYPE
    SYNTAX     INTEGER (0..65535)
    MAX-ACCESS read-only
    STATUS     current
    DESCRIPTION
        "-- empty --"
    ::= { lcsSetupIpRouterFirewallApplicationsIrc 3 }

-- {SCALAR} 310.2.8.10.20.2.4
lcsSetupIpRouterFirewallApplicationsIrcCheckHostIp OBJECT-TYPE
    SYNTAX     INTEGER
      {
        eOff (0),
        eAllways (1),
        eWan (2),
        eDefaultRoute (3)
      }
    MAX-ACCESS read-only
    STATUS     current
    DESCRIPTION
        "-- empty --"
    ::= { lcsSetupIpRouterFirewallApplicationsIrc 4 }

-- {SCALAR} 310.2.8.10.20.10
lcsSetupIpRouterFirewallApplicationsApplAction OBJECT-TYPE
    SYNTAX     DisplayString (SIZE(0..29))
    MAX-ACCESS read-write
    STATUS     current
    DESCRIPTION
        "-- empty --"
    ::= { lcsSetupIpRouterFirewallApplications 10 }

-- {TABLE} 310.2.8.19
lcsSetupIpRouterNNNatTable OBJECT-TYPE
    SYNTAX     SEQUENCE OF LcsSetupIpRouterNNNatEntry
    MAX-ACCESS not-accessible
    STATUS     current
    DESCRIPTION
        "-- empty --"
    ::= { lcsSetupIpRouter 19 }

-- {ENTRY} 310.2.8.19.1
lcsSetupIpRouterNNNatEntry OBJECT-TYPE
    SYNTAX     LcsSetupIpRouterNNNatEntry
    MAX-ACCESS not-accessible
    STATUS     current
    DESCRIPTION
        ""
    INDEX {
        lcsSetupIpRouterNNNatEntryIdx
    }
    ::= { lcsSetupIpRouterNNNatTable 1 }

-- {SEQUENCE}
LcsSetupIpRouterNNNatEntry ::= SEQUENCE {
    lcsSetupIpRouterNNNatEntryIdx DisplayString,
    lcsSetupIpRouterNNNatEntrySrcAddress IpAddress,
    lcsSetupIpRouterNNNatEntrySrcMask IpAddress,
    lcsSetupIpRouterNNNatEntryDstStation DisplayString,
    lcsSetupIpRouterNNNatEntryMappedNetwork IpAddress
}

-- {COLUMN} 310.2.8.19.1.1
lcsSetupIpRouterNNNatEntryIdx OBJECT-TYPE
    SYNTAX     DisplayString (SIZE(0..4))
    MAX-ACCESS read-write
    STATUS     current
    DESCRIPTION
        "-- empty --"
    ::= { lcsSetupIpRouterNNNatEntry 1 }

-- {COLUMN} 310.2.8.19.1.2
lcsSetupIpRouterNNNatEntrySrcAddress OBJECT-TYPE
    SYNTAX     IpAddress
    MAX-ACCESS read-write
    STATUS     current
    DESCRIPTION
        "-- empty --"
    ::= { lcsSetupIpRouterNNNatEntry 2 }

-- {COLUMN} 310.2.8.19.1.3
lcsSetupIpRouterNNNatEntrySrcMask OBJECT-TYPE
    SYNTAX     IpAddress
    MAX-ACCESS read-write
    STATUS     current
    DESCRIPTION
        "-- empty --"
    ::= { lcsSetupIpRouterNNNatEntry 3 }

-- {COLUMN} 310.2.8.19.1.4
lcsSetupIpRouterNNNatEntryDstStation OBJECT-TYPE
    SYNTAX     DisplayString (SIZE(0..16))
    MAX-ACCESS read-write
    STATUS     current
    DESCRIPTION
        "-- empty --"
    ::= { lcsSetupIpRouterNNNatEntry 4 }

-- {COLUMN} 310.2.8.19.1.5
lcsSetupIpRouterNNNatEntryMappedNetwork OBJECT-TYPE
    SYNTAX     IpAddress
    MAX-ACCESS read-write
    STATUS     current
    DESCRIPTION
        "-- empty --"
    ::= { lcsSetupIpRouterNNNatEntry 5 }

-- {OID} 310.2.8.21
lcsSetupIpRouterVrrp OBJECT IDENTIFIER ::= { lcsSetupIpRouter 21 }

-- {SCALAR} 310.2.8.21.1
lcsSetupIpRouterVrrpOperating OBJECT-TYPE
    SYNTAX     INTEGER
      {
        eNo (0),
        eYes (1)
      }
    MAX-ACCESS read-only
    STATUS     current
    DESCRIPTION
        "-- empty --"
    ::= { lcsSetupIpRouterVrrp 1 }

-- {TABLE} 310.2.8.21.2
lcsSetupIpRouterVrrpVrrpListTable OBJECT-TYPE
    SYNTAX     SEQUENCE OF LcsSetupIpRouterVrrpVrrpListEntry
    MAX-ACCESS not-accessible
    STATUS     current
    DESCRIPTION
        "-- empty --"
    ::= { lcsSetupIpRouterVrrp 2 }

-- {ENTRY} 310.2.8.21.2.1
lcsSetupIpRouterVrrpVrrpListEntry OBJECT-TYPE
    SYNTAX     LcsSetupIpRouterVrrpVrrpListEntry
    MAX-ACCESS not-accessible
    STATUS     current
    DESCRIPTION
        ""
    INDEX {
        lcsSetupIpRouterVrrpVrrpListEntryRouterId
    }
    ::= { lcsSetupIpRouterVrrpVrrpListTable 1 }

-- {SEQUENCE}
LcsSetupIpRouterVrrpVrrpListEntry ::= SEQUENCE {
    lcsSetupIpRouterVrrpVrrpListEntryRouterId INTEGER,
    lcsSetupIpRouterVrrpVrrpListEntryVirtAddress IpAddress,
    lcsSetupIpRouterVrrpVrrpListEntryPrio INTEGER,
    lcsSetupIpRouterVrrpVrrpListEntryBPrio INTEGER,
    lcsSetupIpRouterVrrpVrrpListEntryPeer DisplayString,
    lcsSetupIpRouterVrrpVrrpListEntryComment DisplayString
}

-- {COLUMN} 310.2.8.21.2.1.1
lcsSetupIpRouterVrrpVrrpListEntryRouterId OBJECT-TYPE
    SYNTAX     INTEGER (0..255)
    MAX-ACCESS read-write
    STATUS     current
    DESCRIPTION
        "-- empty --"
    ::= { lcsSetupIpRouterVrrpVrrpListEntry 1 }

-- {COLUMN} 310.2.8.21.2.1.2
lcsSetupIpRouterVrrpVrrpListEntryVirtAddress OBJECT-TYPE
    SYNTAX     IpAddress
    MAX-ACCESS read-write
    STATUS     current
    DESCRIPTION
        "-- empty --"
    ::= { lcsSetupIpRouterVrrpVrrpListEntry 2 }

-- {COLUMN} 310.2.8.21.2.1.3
lcsSetupIpRouterVrrpVrrpListEntryPrio OBJECT-TYPE
    SYNTAX     INTEGER (0..255)
    MAX-ACCESS read-write
    STATUS     current
    DESCRIPTION
        "-- empty --"
    ::= { lcsSetupIpRouterVrrpVrrpListEntry 3 }

-- {COLUMN} 310.2.8.21.2.1.4
lcsSetupIpRouterVrrpVrrpListEntryBPrio OBJECT-TYPE
    SYNTAX     INTEGER (0..255)
    MAX-ACCESS read-write
    STATUS     current
    DESCRIPTION
        "-- empty --"
    ::= { lcsSetupIpRouterVrrpVrrpListEntry 4 }

-- {COLUMN} 310.2.8.21.2.1.5
lcsSetupIpRouterVrrpVrrpListEntryPeer OBJECT-TYPE
    SYNTAX     DisplayString (SIZE(0..16))
    MAX-ACCESS read-write
    STATUS     current
    DESCRIPTION
        "-- empty --"
    ::= { lcsSetupIpRouterVrrpVrrpListEntry 5 }

-- {COLUMN} 310.2.8.21.2.1.6
lcsSetupIpRouterVrrpVrrpListEntryComment OBJECT-TYPE
    SYNTAX     DisplayString (SIZE(0..64))
    MAX-ACCESS read-write
    STATUS     current
    DESCRIPTION
        "-- empty --"
    ::= { lcsSetupIpRouterVrrpVrrpListEntry 6 }

-- {SCALAR} 310.2.8.21.3
lcsSetupIpRouterVrrpReconnectDelay OBJECT-TYPE
    SYNTAX     INTEGER (0..65535)
    MAX-ACCESS read-only
    STATUS     current
    DESCRIPTION
        "-- empty --"
    ::= { lcsSetupIpRouterVrrp 3 }

-- {SCALAR} 310.2.8.21.4
lcsSetupIpRouterVrrpAdvertIntervall OBJECT-TYPE
    SYNTAX     INTEGER (0..255)
    MAX-ACCESS read-only
    STATUS     current
    DESCRIPTION
        "-- empty --"
    ::= { lcsSetupIpRouterVrrp 4 }

-- {SCALAR} 310.2.8.21.5
lcsSetupIpRouterVrrpInternalServices OBJECT-TYPE
    SYNTAX     INTEGER
      {
        eNo (0),
        eYes (1)
      }
    MAX-ACCESS read-only
    STATUS     current
    DESCRIPTION
        "-- empty --"
    ::= { lcsSetupIpRouterVrrp 5 }

-- {SCALAR} 310.2.8.22
lcsSetupIpRouterWanTagCreation OBJECT-TYPE
    SYNTAX     INTEGER
      {
        eManual (0),
        eAuto (1)
      }
    MAX-ACCESS read-only
    STATUS     current
    DESCRIPTION
        "-- empty --"
    ::= { lcsSetupIpRouter 22 }

-- {TABLE} 310.2.8.23
lcsSetupIpRouterTagTableTable OBJECT-TYPE
    SYNTAX     SEQUENCE OF LcsSetupIpRouterTagTableEntry
    MAX-ACCESS not-accessible
    STATUS     current
    DESCRIPTION
        "-- empty --"
    ::= { lcsSetupIpRouter 23 }

-- {ENTRY} 310.2.8.23.1
lcsSetupIpRouterTagTableEntry OBJECT-TYPE
    SYNTAX     LcsSetupIpRouterTagTableEntry
    MAX-ACCESS not-accessible
    STATUS     current
    DESCRIPTION
        ""
    INDEX {
        lcsSetupIpRouterTagTableEntryPeer
    }
    ::= { lcsSetupIpRouterTagTableTable 1 }

-- {SEQUENCE}
LcsSetupIpRouterTagTableEntry ::= SEQUENCE {
    lcsSetupIpRouterTagTableEntryPeer DisplayString,
    lcsSetupIpRouterTagTableEntryRtgTag INTEGER,
    lcsSetupIpRouterTagTableEntryStartWanPool IpAddress,
    lcsSetupIpRouterTagTableEntryEndWanPool IpAddress
}

-- {COLUMN} 310.2.8.23.1.1
lcsSetupIpRouterTagTableEntryPeer OBJECT-TYPE
    SYNTAX     DisplayString (SIZE(0..16))
    MAX-ACCESS read-write
    STATUS     current
    DESCRIPTION
        "-- empty --"
    ::= { lcsSetupIpRouterTagTableEntry 1 }

-- {COLUMN} 310.2.8.23.1.2
lcsSetupIpRouterTagTableEntryRtgTag OBJECT-TYPE
    SYNTAX     INTEGER (0..65535)
    MAX-ACCESS read-write
    STATUS     current
    DESCRIPTION
        "-- empty --"
    ::= { lcsSetupIpRouterTagTableEntry 2 }

-- {COLUMN} 310.2.8.23.1.3
lcsSetupIpRouterTagTableEntryStartWanPool OBJECT-TYPE
    SYNTAX     IpAddress
    MAX-ACCESS read-write
    STATUS     current
    DESCRIPTION
        "-- empty --"
    ::= { lcsSetupIpRouterTagTableEntry 3 }

-- {COLUMN} 310.2.8.23.1.4
lcsSetupIpRouterTagTableEntryEndWanPool OBJECT-TYPE
    SYNTAX     IpAddress
    MAX-ACCESS read-write
    STATUS     current
    DESCRIPTION
        "-- empty --"
    ::= { lcsSetupIpRouterTagTableEntry 4 }

-- {OID} 310.2.9
lcsSetupSnmp OBJECT IDENTIFIER ::= { lcsSetup 9 }

-- {SCALAR} 310.2.9.1
lcsSetupSnmpSendTraps OBJECT-TYPE
    SYNTAX     INTEGER
      {
        eNo (0),
        eYes (1)
      }
    MAX-ACCESS read-only
    STATUS     current
    DESCRIPTION
        "-- empty --"
    ::= { lcsSetupSnmp 1 }

-- {TABLE} 310.2.9.2
lcsSetupSnmpIpTrapsTable OBJECT-TYPE
    SYNTAX     SEQUENCE OF LcsSetupSnmpIpTrapsEntry
    MAX-ACCESS not-accessible
    STATUS     current
    DESCRIPTION
        "-- empty --"
    ::= { lcsSetupSnmp 2 }

-- {ENTRY} 310.2.9.2.1
lcsSetupSnmpIpTrapsEntry OBJECT-TYPE
    SYNTAX     LcsSetupSnmpIpTrapsEntry
    MAX-ACCESS not-accessible
    STATUS     current
    DESCRIPTION
        ""
    INDEX {
        lcsSetupSnmpIpTrapsEntryTrapIp
    }
    ::= { lcsSetupSnmpIpTrapsTable 1 }

-- {SEQUENCE}
LcsSetupSnmpIpTrapsEntry ::= SEQUENCE {
    lcsSetupSnmpIpTrapsEntryTrapIp IpAddress,
    lcsSetupSnmpIpTrapsEntryLoopbackAddr DisplayString,
    lcsSetupSnmpIpTrapsEntryVersion INTEGER
}

-- {COLUMN} 310.2.9.2.1.1
lcsSetupSnmpIpTrapsEntryTrapIp OBJECT-TYPE
    SYNTAX     IpAddress
    MAX-ACCESS read-write
    STATUS     current
    DESCRIPTION
        "-- empty --"
    ::= { lcsSetupSnmpIpTrapsEntry 1 }

-- {COLUMN} 310.2.9.2.1.3
lcsSetupSnmpIpTrapsEntryLoopbackAddr OBJECT-TYPE
    SYNTAX     DisplayString (SIZE(0..16))
    MAX-ACCESS read-write
    STATUS     current
    DESCRIPTION
        "-- empty --"
    ::= { lcsSetupSnmpIpTrapsEntry 3 }

-- {COLUMN} 310.2.9.2.1.4
lcsSetupSnmpIpTrapsEntryVersion OBJECT-TYPE
    SYNTAX     INTEGER
      {
        eSnmpv1 (1),
        eSnmpv2 (0)
      }
    MAX-ACCESS read-write
    STATUS     current
    DESCRIPTION
        "-- empty --"
    ::= { lcsSetupSnmpIpTrapsEntry 4 }

-- {SCALAR} 310.2.9.3
lcsSetupSnmpAdministrator OBJECT-TYPE
    SYNTAX     DisplayString (SIZE(0..255))
    MAX-ACCESS read-only
    STATUS     current
    DESCRIPTION
        "-- empty --"
    ::= { lcsSetupSnmp 3 }

-- {SCALAR} 310.2.9.4
lcsSetupSnmpLocation OBJECT-TYPE
    SYNTAX     DisplayString (SIZE(0..255))
    MAX-ACCESS read-only
    STATUS     current
    DESCRIPTION
        "-- empty --"
    ::= { lcsSetupSnmp 4 }

-- {SCALAR} 310.2.9.5
lcsSetupSnmpRegisterMonitor OBJECT-TYPE
    SYNTAX     DisplayString
    MAX-ACCESS read-write
    STATUS     current
    DESCRIPTION
        "-- empty --"
    ::= { lcsSetupSnmp 5 }

-- {SCALAR} 310.2.9.6
lcsSetupSnmpDeleteMonitor OBJECT-TYPE
    SYNTAX     DisplayString
    MAX-ACCESS read-write
    STATUS     current
    DESCRIPTION
        "-- empty --"
    ::= { lcsSetupSnmp 6 }

-- {TABLE} 310.2.9.7
lcsSetupSnmpMonitorTableTable OBJECT-TYPE
    SYNTAX     SEQUENCE OF LcsSetupSnmpMonitorTableEntry
    MAX-ACCESS not-accessible
    STATUS     current
    DESCRIPTION
        "-- empty --"
    ::= { lcsSetupSnmp 7 }

-- {ENTRY} 310.2.9.7.1
lcsSetupSnmpMonitorTableEntry OBJECT-TYPE
    SYNTAX     LcsSetupSnmpMonitorTableEntry
    MAX-ACCESS not-accessible
    STATUS     current
    DESCRIPTION
        ""
    INDEX {
        lcsSetupSnmpMonitorTableEntryIpAddress,
        lcsSetupSnmpMonitorTableEntryPort
    }
    ::= { lcsSetupSnmpMonitorTableTable 1 }

-- {SEQUENCE}
LcsSetupSnmpMonitorTableEntry ::= SEQUENCE {
    lcsSetupSnmpMonitorTableEntryIpAddress IpAddress,
    lcsSetupSnmpMonitorTableEntryPort INTEGER,
    lcsSetupSnmpMonitorTableEntryMacAddress DisplayString,
    lcsSetupSnmpMonitorTableEntryVlanId INTEGER,
    lcsSetupSnmpMonitorTableEntryTimeout INTEGER,
    lcsSetupSnmpMonitorTableEntryPeer DisplayString,
    lcsSetupSnmpMonitorTableEntryLoopbackAddr IpAddress,
    lcsSetupSnmpMonitorTableEntryLanIfc DisplayString
}

-- {COLUMN} 310.2.9.7.1.1
lcsSetupSnmpMonitorTableEntryIpAddress OBJECT-TYPE
    SYNTAX     IpAddress
    MAX-ACCESS read-only
    STATUS     current
    DESCRIPTION
        "-- empty --"
    ::= { lcsSetupSnmpMonitorTableEntry 1 }

-- {COLUMN} 310.2.9.7.1.2
lcsSetupSnmpMonitorTableEntryPort OBJECT-TYPE
    SYNTAX     INTEGER (0..65535)
    MAX-ACCESS read-only
    STATUS     current
    DESCRIPTION
        "-- empty --"
    ::= { lcsSetupSnmpMonitorTableEntry 2 }

-- {COLUMN} 310.2.9.7.1.4
lcsSetupSnmpMonitorTableEntryMacAddress OBJECT-TYPE
    SYNTAX     DisplayString (SIZE(0..12))
    MAX-ACCESS read-only
    STATUS     current
    DESCRIPTION
        "-- empty --"
    ::= { lcsSetupSnmpMonitorTableEntry 4 }

-- {COLUMN} 310.2.9.7.1.7
lcsSetupSnmpMonitorTableEntryVlanId OBJECT-TYPE
    SYNTAX     INTEGER (0..65535)
    MAX-ACCESS read-only
    STATUS     current
    DESCRIPTION
        "-- empty --"
    ::= { lcsSetupSnmpMonitorTableEntry 7 }

-- {COLUMN} 310.2.9.7.1.3
lcsSetupSnmpMonitorTableEntryTimeout OBJECT-TYPE
    SYNTAX     INTEGER (0..65535)
    MAX-ACCESS read-only
    STATUS     current
    DESCRIPTION
        "-- empty --"
    ::= { lcsSetupSnmpMonitorTableEntry 3 }

-- {COLUMN} 310.2.9.7.1.5
lcsSetupSnmpMonitorTableEntryPeer OBJECT-TYPE
    SYNTAX     DisplayString (SIZE(0..16))
    MAX-ACCESS read-only
    STATUS     current
    DESCRIPTION
        "-- empty --"
    ::= { lcsSetupSnmpMonitorTableEntry 5 }

-- {COLUMN} 310.2.9.7.1.6
lcsSetupSnmpMonitorTableEntryLoopbackAddr OBJECT-TYPE
    SYNTAX     IpAddress
    MAX-ACCESS read-only
    STATUS     current
    DESCRIPTION
        "-- empty --"
    ::= { lcsSetupSnmpMonitorTableEntry 6 }

-- {COLUMN} 310.2.9.7.1.8
lcsSetupSnmpMonitorTableEntryLanIfc OBJECT-TYPE
    SYNTAX     DisplayString (SIZE(0..255))
    MAX-ACCESS read-only
    STATUS     current
    DESCRIPTION
        "-- empty --"
    ::= { lcsSetupSnmpMonitorTableEntry 8 }

-- {SCALAR} 310.2.9.10
lcsSetupSnmpPasswordRequiredForSnmpReadAccess OBJECT-TYPE
    SYNTAX     INTEGER
      {
        eNo (0),
        eYes (1)
      }
    MAX-ACCESS read-only
    STATUS     current
    DESCRIPTION
        "-- empty --"
    ::= { lcsSetupSnmp 10 }

-- {SCALAR} 310.2.9.15
lcsSetupSnmpReadOnlyCommunity OBJECT-TYPE
    SYNTAX     DisplayString (SIZE(0..31))
    MAX-ACCESS read-only
    STATUS     current
    DESCRIPTION
        "-- empty --"
    ::= { lcsSetupSnmp 15 }

-- {SCALAR} 310.2.9.20
lcsSetupSnmpFullHostMib OBJECT-TYPE
    SYNTAX     INTEGER
      {
        eNo (0),
        eYes (1)
      }
    MAX-ACCESS read-only
    STATUS     current
    DESCRIPTION
        "-- empty --"
    ::= { lcsSetupSnmp 20 }

-- {SCALAR} 310.2.9.11
lcsSetupSnmpComment1 OBJECT-TYPE
    SYNTAX     DisplayString (SIZE(0..255))
    MAX-ACCESS read-only
    STATUS     current
    DESCRIPTION
        "-- empty --"
    ::= { lcsSetupSnmp 11 }

-- {SCALAR} 310.2.9.12
lcsSetupSnmpComment2 OBJECT-TYPE
    SYNTAX     DisplayString (SIZE(0..255))
    MAX-ACCESS read-only
    STATUS     current
    DESCRIPTION
        "-- empty --"
    ::= { lcsSetupSnmp 12 }

-- {SCALAR} 310.2.9.13
lcsSetupSnmpComment3 OBJECT-TYPE
    SYNTAX     DisplayString (SIZE(0..255))
    MAX-ACCESS read-only
    STATUS     current
    DESCRIPTION
        "-- empty --"
    ::= { lcsSetupSnmp 13 }

-- {SCALAR} 310.2.9.14
lcsSetupSnmpComment4 OBJECT-TYPE
    SYNTAX     DisplayString (SIZE(0..255))
    MAX-ACCESS read-only
    STATUS     current
    DESCRIPTION
        "-- empty --"
    ::= { lcsSetupSnmp 14 }

-- {SCALAR} 310.2.9.16
lcsSetupSnmpComment5 OBJECT-TYPE
    SYNTAX     DisplayString (SIZE(0..255))
    MAX-ACCESS read-only
    STATUS     current
    DESCRIPTION
        "-- empty --"
    ::= { lcsSetupSnmp 16 }

-- {SCALAR} 310.2.9.17
lcsSetupSnmpComment6 OBJECT-TYPE
    SYNTAX     DisplayString (SIZE(0..255))
    MAX-ACCESS read-only
    STATUS     current
    DESCRIPTION
        "-- empty --"
    ::= { lcsSetupSnmp 17 }

-- {SCALAR} 310.2.9.18
lcsSetupSnmpComment7 OBJECT-TYPE
    SYNTAX     DisplayString (SIZE(0..255))
    MAX-ACCESS read-only
    STATUS     current
    DESCRIPTION
        "-- empty --"
    ::= { lcsSetupSnmp 18 }

-- {SCALAR} 310.2.9.19
lcsSetupSnmpComment8 OBJECT-TYPE
    SYNTAX     DisplayString (SIZE(0..255))
    MAX-ACCESS read-only
    STATUS     current
    DESCRIPTION
        "-- empty --"
    ::= { lcsSetupSnmp 19 }

-- {OID} 310.2.10
lcsSetupDhcp OBJECT IDENTIFIER ::= { lcsSetup 10 }

-- {TABLE} 310.2.10.20
lcsSetupDhcpNetworkListTable OBJECT-TYPE
    SYNTAX     SEQUENCE OF LcsSetupDhcpNetworkListEntry
    MAX-ACCESS not-accessible
    STATUS     current
    DESCRIPTION
        "-- empty --"
    ::= { lcsSetupDhcp 20 }

-- {ENTRY} 310.2.10.20.1
lcsSetupDhcpNetworkListEntry OBJECT-TYPE
    SYNTAX     LcsSetupDhcpNetworkListEntry
    MAX-ACCESS not-accessible
    STATUS     current
    DESCRIPTION
        ""
    INDEX {
        lcsSetupDhcpNetworkListEntryNetworkName
    }
    ::= { lcsSetupDhcpNetworkListTable 1 }

-- {SEQUENCE}
LcsSetupDhcpNetworkListEntry ::= SEQUENCE {
    lcsSetupDhcpNetworkListEntryNetworkName DisplayString,
    lcsSetupDhcpNetworkListEntryStartAddressPool IpAddress,
    lcsSetupDhcpNetworkListEntryEndAddressPool IpAddress,
    lcsSetupDhcpNetworkListEntryNetmask IpAddress,
    lcsSetupDhcpNetworkListEntryBroadcastAddress IpAddress,
    lcsSetupDhcpNetworkListEntryGatewayAddress IpAddress,
    lcsSetupDhcpNetworkListEntryDnsDefault IpAddress,
    lcsSetupDhcpNetworkListEntryDnsBackup IpAddress,
    lcsSetupDhcpNetworkListEntryNbnsDefault IpAddress,
    lcsSetupDhcpNetworkListEntryNbnsBackup IpAddress,
    lcsSetupDhcpNetworkListEntryOperating INTEGER,
    lcsSetupDhcpNetworkListEntryBroadcastBit INTEGER,
    lcsSetupDhcpNetworkListEntryMasterServer IpAddress,
    lcsSetupDhcpNetworkListEntry2ndMasterServer IpAddress,
    lcsSetupDhcpNetworkListEntry3rdMasterServer IpAddress,
    lcsSetupDhcpNetworkListEntry4thMasterServer IpAddress,
    lcsSetupDhcpNetworkListEntryCache INTEGER,
    lcsSetupDhcpNetworkListEntryAdaption INTEGER,
    lcsSetupDhcpNetworkListEntryCluster INTEGER
}

-- {COLUMN} 310.2.10.20.1.1
lcsSetupDhcpNetworkListEntryNetworkName OBJECT-TYPE
    SYNTAX     DisplayString (SIZE(0..16))
    MAX-ACCESS read-write
    STATUS     current
    DESCRIPTION
        "-- empty --"
    ::= { lcsSetupDhcpNetworkListEntry 1 }

-- {COLUMN} 310.2.10.20.1.2
lcsSetupDhcpNetworkListEntryStartAddressPool OBJECT-TYPE
    SYNTAX     IpAddress
    MAX-ACCESS read-write
    STATUS     current
    DESCRIPTION
        "-- empty --"
    ::= { lcsSetupDhcpNetworkListEntry 2 }

-- {COLUMN} 310.2.10.20.1.3
lcsSetupDhcpNetworkListEntryEndAddressPool OBJECT-TYPE
    SYNTAX     IpAddress
    MAX-ACCESS read-write
    STATUS     current
    DESCRIPTION
        "-- empty --"
    ::= { lcsSetupDhcpNetworkListEntry 3 }

-- {COLUMN} 310.2.10.20.1.4
lcsSetupDhcpNetworkListEntryNetmask OBJECT-TYPE
    SYNTAX     IpAddress
    MAX-ACCESS read-write
    STATUS     current
    DESCRIPTION
        "-- empty --"
    ::= { lcsSetupDhcpNetworkListEntry 4 }

-- {COLUMN} 310.2.10.20.1.5
lcsSetupDhcpNetworkListEntryBroadcastAddress OBJECT-TYPE
    SYNTAX     IpAddress
    MAX-ACCESS read-write
    STATUS     current
    DESCRIPTION
        "-- empty --"
    ::= { lcsSetupDhcpNetworkListEntry 5 }

-- {COLUMN} 310.2.10.20.1.6
lcsSetupDhcpNetworkListEntryGatewayAddress OBJECT-TYPE
    SYNTAX     IpAddress
    MAX-ACCESS read-write
    STATUS     current
    DESCRIPTION
        "-- empty --"
    ::= { lcsSetupDhcpNetworkListEntry 6 }

-- {COLUMN} 310.2.10.20.1.7
lcsSetupDhcpNetworkListEntryDnsDefault OBJECT-TYPE
    SYNTAX     IpAddress
    MAX-ACCESS read-write
    STATUS     current
    DESCRIPTION
        "-- empty --"
    ::= { lcsSetupDhcpNetworkListEntry 7 }

-- {COLUMN} 310.2.10.20.1.8
lcsSetupDhcpNetworkListEntryDnsBackup OBJECT-TYPE
    SYNTAX     IpAddress
    MAX-ACCESS read-write
    STATUS     current
    DESCRIPTION
        "-- empty --"
    ::= { lcsSetupDhcpNetworkListEntry 8 }

-- {COLUMN} 310.2.10.20.1.9
lcsSetupDhcpNetworkListEntryNbnsDefault OBJECT-TYPE
    SYNTAX     IpAddress
    MAX-ACCESS read-write
    STATUS     current
    DESCRIPTION
        "-- empty --"
    ::= { lcsSetupDhcpNetworkListEntry 9 }

-- {COLUMN} 310.2.10.20.1.10
lcsSetupDhcpNetworkListEntryNbnsBackup OBJECT-TYPE
    SYNTAX     IpAddress
    MAX-ACCESS read-write
    STATUS     current
    DESCRIPTION
        "-- empty --"
    ::= { lcsSetupDhcpNetworkListEntry 10 }

-- {COLUMN} 310.2.10.20.1.11
lcsSetupDhcpNetworkListEntryOperating OBJECT-TYPE
    SYNTAX     INTEGER
      {
        eNo (0),
        eYes (1),
        eAuto (2),
        eRelay (16),
        eClient (4)
      }
    MAX-ACCESS read-write
    STATUS     current
    DESCRIPTION
        "-- empty --"
    ::= { lcsSetupDhcpNetworkListEntry 11 }

-- {COLUMN} 310.2.10.20.1.12
lcsSetupDhcpNetworkListEntryBroadcastBit OBJECT-TYPE
    SYNTAX     INTEGER
      {
        eNo (0),
        eYes (1)
      }
    MAX-ACCESS read-write
    STATUS     current
    DESCRIPTION
        "-- empty --"
    ::= { lcsSetupDhcpNetworkListEntry 12 }

-- {COLUMN} 310.2.10.20.1.13
lcsSetupDhcpNetworkListEntryMasterServer OBJECT-TYPE
    SYNTAX     IpAddress
    MAX-ACCESS read-write
    STATUS     current
    DESCRIPTION
        "-- empty --"
    ::= { lcsSetupDhcpNetworkListEntry 13 }

-- {COLUMN} 310.2.10.20.1.17
lcsSetupDhcpNetworkListEntry2ndMasterServer OBJECT-TYPE
    SYNTAX     IpAddress
    MAX-ACCESS read-write
    STATUS     current
    DESCRIPTION
        "-- empty --"
    ::= { lcsSetupDhcpNetworkListEntry 17 }

-- {COLUMN} 310.2.10.20.1.18
lcsSetupDhcpNetworkListEntry3rdMasterServer OBJECT-TYPE
    SYNTAX     IpAddress
    MAX-ACCESS read-write
    STATUS     current
    DESCRIPTION
        "-- empty --"
    ::= { lcsSetupDhcpNetworkListEntry 18 }

-- {COLUMN} 310.2.10.20.1.19
lcsSetupDhcpNetworkListEntry4thMasterServer OBJECT-TYPE
    SYNTAX     IpAddress
    MAX-ACCESS read-write
    STATUS     current
    DESCRIPTION
        "-- empty --"
    ::= { lcsSetupDhcpNetworkListEntry 19 }

-- {COLUMN} 310.2.10.20.1.14
lcsSetupDhcpNetworkListEntryCache OBJECT-TYPE
    SYNTAX     INTEGER
      {
        eNo (0),
        eYes (1)
      }
    MAX-ACCESS read-write
    STATUS     current
    DESCRIPTION
        "-- empty --"
    ::= { lcsSetupDhcpNetworkListEntry 14 }

-- {COLUMN} 310.2.10.20.1.15
lcsSetupDhcpNetworkListEntryAdaption OBJECT-TYPE
    SYNTAX     INTEGER
      {
        eNo (0),
        eYes (1)
      }
    MAX-ACCESS read-write
    STATUS     current
    DESCRIPTION
        "-- empty --"
    ::= { lcsSetupDhcpNetworkListEntry 15 }

-- {COLUMN} 310.2.10.20.1.16
lcsSetupDhcpNetworkListEntryCluster OBJECT-TYPE
    SYNTAX     INTEGER
      {
        eNo (0),
        eYes (1)
      }
    MAX-ACCESS read-write
    STATUS     current
    DESCRIPTION
        "-- empty --"
    ::= { lcsSetupDhcpNetworkListEntry 16 }

-- {TABLE} 310.2.10.18
lcsSetupDhcpPortsTable OBJECT-TYPE
    SYNTAX     SEQUENCE OF LcsSetupDhcpPortsEntry
    MAX-ACCESS not-accessible
    STATUS     current
    DESCRIPTION
        "-- empty --"
    ::= { lcsSetupDhcp 18 }

-- {ENTRY} 310.2.10.18.1
lcsSetupDhcpPortsEntry OBJECT-TYPE
    SYNTAX     LcsSetupDhcpPortsEntry
    MAX-ACCESS not-accessible
    STATUS     current
    DESCRIPTION
        ""
    INDEX {
        lcsSetupDhcpPortsEntryPort
    }
    ::= { lcsSetupDhcpPortsTable 1 }

-- {SEQUENCE}
LcsSetupDhcpPortsEntry ::= SEQUENCE {
    lcsSetupDhcpPortsEntryPort DisplayString,
    lcsSetupDhcpPortsEntryEnableDhcp INTEGER
}

-- {COLUMN} 310.2.10.18.1.2
lcsSetupDhcpPortsEntryPort OBJECT-TYPE
    SYNTAX     DisplayString (SIZE(0..13))
    MAX-ACCESS read-only
    STATUS     current
    DESCRIPTION
        "-- empty --"
    ::= { lcsSetupDhcpPortsEntry 2 }

-- {COLUMN} 310.2.10.18.1.3
lcsSetupDhcpPortsEntryEnableDhcp OBJECT-TYPE
    SYNTAX     INTEGER
      {
        eNo (0),
        eYes (1)
      }
    MAX-ACCESS read-write
    STATUS     current
    DESCRIPTION
        "-- empty --"
    ::= { lcsSetupDhcpPortsEntry 3 }

-- {SCALAR} 310.2.10.6
lcsSetupDhcpMaxLeaseTimeMinutes OBJECT-TYPE
    SYNTAX     INTEGER (0..2147483647)
    MAX-ACCESS read-only
    STATUS     current
    DESCRIPTION
        "-- empty --"
    ::= { lcsSetupDhcp 6 }

-- {SCALAR} 310.2.10.7
lcsSetupDhcpDefaultLeaseTimeMinutes OBJECT-TYPE
    SYNTAX     INTEGER (0..2147483647)
    MAX-ACCESS read-only
    STATUS     current
    DESCRIPTION
        "-- empty --"
    ::= { lcsSetupDhcp 7 }

-- {TABLE} 310.2.10.8
lcsSetupDhcpDhcpTableTable OBJECT-TYPE
    SYNTAX     SEQUENCE OF LcsSetupDhcpDhcpTableEntry
    MAX-ACCESS not-accessible
    STATUS     current
    DESCRIPTION
        "-- empty --"
    ::= { lcsSetupDhcp 8 }

-- {ENTRY} 310.2.10.8.1
lcsSetupDhcpDhcpTableEntry OBJECT-TYPE
    SYNTAX     LcsSetupDhcpDhcpTableEntry
    MAX-ACCESS not-accessible
    STATUS     current
    DESCRIPTION
        ""
    INDEX {
        lcsSetupDhcpDhcpTableEntryIpAddress,
        lcsSetupDhcpDhcpTableEntryNetworkName
    }
    ::= { lcsSetupDhcpDhcpTableTable 1 }

-- {SEQUENCE}
LcsSetupDhcpDhcpTableEntry ::= SEQUENCE {
    lcsSetupDhcpDhcpTableEntryIpAddress IpAddress,
    lcsSetupDhcpDhcpTableEntryMacAddress DisplayString,
    lcsSetupDhcpDhcpTableEntryTimeout INTEGER,
    lcsSetupDhcpDhcpTableEntryHostname DisplayString,
    lcsSetupDhcpDhcpTableEntryType BITS,
    lcsSetupDhcpDhcpTableEntryLanIfc INTEGER,
    lcsSetupDhcpDhcpTableEntryVlanId INTEGER,
    lcsSetupDhcpDhcpTableEntryNetworkName DisplayString,
    lcsSetupDhcpDhcpTableEntryAssignment DisplayString,
    lcsSetupDhcpDhcpTableEntryAssignmentNumeric Gauge32
}

-- {COLUMN} 310.2.10.8.1.1
lcsSetupDhcpDhcpTableEntryIpAddress OBJECT-TYPE
    SYNTAX     IpAddress
    MAX-ACCESS read-only
    STATUS     current
    DESCRIPTION
        "-- empty --"
    ::= { lcsSetupDhcpDhcpTableEntry 1 }

-- {COLUMN} 310.2.10.8.1.2
lcsSetupDhcpDhcpTableEntryMacAddress OBJECT-TYPE
    SYNTAX     DisplayString (SIZE(0..12))
    MAX-ACCESS read-only
    STATUS     current
    DESCRIPTION
        "-- empty --"
    ::= { lcsSetupDhcpDhcpTableEntry 2 }

-- {COLUMN} 310.2.10.8.1.3
lcsSetupDhcpDhcpTableEntryTimeout OBJECT-TYPE
    SYNTAX     INTEGER (0..2147483647)
    MAX-ACCESS read-only
    STATUS     current
    DESCRIPTION
        "-- empty --"
    ::= { lcsSetupDhcpDhcpTableEntry 3 }

-- {COLUMN} 310.2.10.8.1.4
lcsSetupDhcpDhcpTableEntryHostname OBJECT-TYPE
    SYNTAX     DisplayString (SIZE(0..65))
    MAX-ACCESS read-only
    STATUS     current
    DESCRIPTION
        "-- empty --"
    ::= { lcsSetupDhcpDhcpTableEntry 4 }

-- {COLUMN} 310.2.10.8.1.5
lcsSetupDhcpDhcpTableEntryType OBJECT-TYPE
    SYNTAX     BITS
      {
        enew (15),
        enewreq (14),
        eDyn (11),
        eUnkn (13),
        eStat (12),
        eBootp (10),
        eRelay (4),
        eCache (8)
      }
    MAX-ACCESS read-only
    STATUS     current
    DESCRIPTION
        "-- empty --"
    ::= { lcsSetupDhcpDhcpTableEntry 5 }

-- {COLUMN} 310.2.10.8.1.10
lcsSetupDhcpDhcpTableEntryLanIfc OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eWlcTunnel1 (1792),
        eWlcTunnel2 (1793),
        eWlcTunnel3 (1794),
        eWlcTunnel4 (1795),
        eWlcTunnel5 (1796),
        eWlcTunnel6 (1797),
        eWlcTunnel7 (1798),
        eWlcTunnel8 (1799),
        eWlcTunnel9 (1800),
        eWlcTunnel10 (1801),
        eWlcTunnel11 (1802),
        eWlcTunnel12 (1803),
        eWlcTunnel13 (1804),
        eWlcTunnel14 (1805),
        eWlcTunnel15 (1806),
        eWlcTunnel16 (1807),
        eWlcTunnel17 (1808),
        eWlcTunnel18 (1809),
        eWlcTunnel19 (1810),
        eWlcTunnel20 (1811),
        eWlcTunnel21 (1812),
        eWlcTunnel22 (1813),
        eWlcTunnel23 (1814),
        eWlcTunnel24 (1815),
        eWlcTunnel25 (1816),
        eWlcTunnel26 (1817),
        eWlcTunnel27 (1818),
        eWlcTunnel28 (1819),
        eWlcTunnel29 (1820),
        eWlcTunnel30 (1821),
        eWlcTunnel31 (1822),
        eWlcTunnel32 (1823),
        eBrg1 (1536),
        eBrg2 (1537),
        eBrg3 (1538),
        eBrg4 (1539),
        eBrg5 (1540),
        eBrg6 (1541),
        eBrg7 (1542),
        eBrg8 (1543),
        eAny (65535)
      }
    MAX-ACCESS read-only
    STATUS     current
    DESCRIPTION
        "-- empty --"
    ::= { lcsSetupDhcpDhcpTableEntry 10 }

-- {COLUMN} 310.2.10.8.1.8
lcsSetupDhcpDhcpTableEntryVlanId OBJECT-TYPE
    SYNTAX     INTEGER (0..65535)
    MAX-ACCESS read-only
    STATUS     current
    DESCRIPTION
        "-- empty --"
    ::= { lcsSetupDhcpDhcpTableEntry 8 }

-- {COLUMN} 310.2.10.8.1.9
lcsSetupDhcpDhcpTableEntryNetworkName OBJECT-TYPE
    SYNTAX     DisplayString (SIZE(0..17))
    MAX-ACCESS read-only
    STATUS     current
    DESCRIPTION
        "-- empty --"
    ::= { lcsSetupDhcpDhcpTableEntry 9 }

-- {COLUMN} 310.2.10.8.1.11
lcsSetupDhcpDhcpTableEntryAssignment OBJECT-TYPE
    SYNTAX     DisplayString (SIZE(0..21))
    MAX-ACCESS read-only
    STATUS     current
    DESCRIPTION
        "-- empty --"
    ::= { lcsSetupDhcpDhcpTableEntry 11 }

-- {COLUMN} 310.2.10.8.1.12
lcsSetupDhcpDhcpTableEntryAssignmentNumeric OBJECT-TYPE
    SYNTAX     Gauge32
    MAX-ACCESS read-only
    STATUS     current
    DESCRIPTION
        "-- empty --"
    ::= { lcsSetupDhcpDhcpTableEntry 12 }

-- {TABLE} 310.2.10.9
lcsSetupDhcpHostsTable OBJECT-TYPE
    SYNTAX     SEQUENCE OF LcsSetupDhcpHostsEntry
    MAX-ACCESS not-accessible
    STATUS     current
    DESCRIPTION
        "-- empty --"
    ::= { lcsSetupDhcp 9 }

-- {ENTRY} 310.2.10.9.1
lcsSetupDhcpHostsEntry OBJECT-TYPE
    SYNTAX     LcsSetupDhcpHostsEntry
    MAX-ACCESS not-accessible
    STATUS     current
    DESCRIPTION
        ""
    INDEX {
        lcsSetupDhcpHostsEntryMacAddress,
        lcsSetupDhcpHostsEntryNetworkName
    }
    ::= { lcsSetupDhcpHostsTable 1 }

-- {SEQUENCE}
LcsSetupDhcpHostsEntry ::= SEQUENCE {
    lcsSetupDhcpHostsEntryMacAddress DisplayString,
    lcsSetupDhcpHostsEntryNetworkName DisplayString,
    lcsSetupDhcpHostsEntryIpAddress IpAddress,
    lcsSetupDhcpHostsEntryHostname DisplayString,
    lcsSetupDhcpHostsEntryImageAlias DisplayString
}

-- {COLUMN} 310.2.10.9.1.1
lcsSetupDhcpHostsEntryMacAddress OBJECT-TYPE
    SYNTAX     DisplayString (SIZE(0..12))
    MAX-ACCESS read-write
    STATUS     current
    DESCRIPTION
        "-- empty --"
    ::= { lcsSetupDhcpHostsEntry 1 }

-- {COLUMN} 310.2.10.9.1.5
lcsSetupDhcpHostsEntryNetworkName OBJECT-TYPE
    SYNTAX     DisplayString (SIZE(0..16))
    MAX-ACCESS read-write
    STATUS     current
    DESCRIPTION
        "-- empty --"
    ::= { lcsSetupDhcpHostsEntry 5 }

-- {COLUMN} 310.2.10.9.1.2
lcsSetupDhcpHostsEntryIpAddress OBJECT-TYPE
    SYNTAX     IpAddress
    MAX-ACCESS read-write
    STATUS     current
    DESCRIPTION
        "-- empty --"
    ::= { lcsSetupDhcpHostsEntry 2 }

-- {COLUMN} 310.2.10.9.1.3
lcsSetupDhcpHostsEntryHostname OBJECT-TYPE
    SYNTAX     DisplayString (SIZE(0..30))
    MAX-ACCESS read-write
    STATUS     current
    DESCRIPTION
        "-- empty --"
    ::= { lcsSetupDhcpHostsEntry 3 }

-- {COLUMN} 310.2.10.9.1.4
lcsSetupDhcpHostsEntryImageAlias OBJECT-TYPE
    SYNTAX     DisplayString (SIZE(0..16))
    MAX-ACCESS read-write
    STATUS     current
    DESCRIPTION
        "-- empty --"
    ::= { lcsSetupDhcpHostsEntry 4 }

-- {TABLE} 310.2.10.10
lcsSetupDhcpAliasListTable OBJECT-TYPE
    SYNTAX     SEQUENCE OF LcsSetupDhcpAliasListEntry
    MAX-ACCESS not-accessible
    STATUS     current
    DESCRIPTION
        "-- empty --"
    ::= { lcsSetupDhcp 10 }

-- {ENTRY} 310.2.10.10.1
lcsSetupDhcpAliasListEntry OBJECT-TYPE
    SYNTAX     LcsSetupDhcpAliasListEntry
    MAX-ACCESS not-accessible
    STATUS     current
    DESCRIPTION
        ""
    INDEX {
        lcsSetupDhcpAliasListEntryImageAlias
    }
    ::= { lcsSetupDhcpAliasListTable 1 }

-- {SEQUENCE}
LcsSetupDhcpAliasListEntry ::= SEQUENCE {
    lcsSetupDhcpAliasListEntryImageAlias DisplayString,
    lcsSetupDhcpAliasListEntryImageServer IpAddress,
    lcsSetupDhcpAliasListEntryImageFile DisplayString
}

-- {COLUMN} 310.2.10.10.1.1
lcsSetupDhcpAliasListEntryImageAlias OBJECT-TYPE
    SYNTAX     DisplayString (SIZE(0..16))
    MAX-ACCESS read-write
    STATUS     current
    DESCRIPTION
        "-- empty --"
    ::= { lcsSetupDhcpAliasListEntry 1 }

-- {COLUMN} 310.2.10.10.1.3
lcsSetupDhcpAliasListEntryImageServer OBJECT-TYPE
    SYNTAX     IpAddress
    MAX-ACCESS read-write
    STATUS     current
    DESCRIPTION
        "-- empty --"
    ::= { lcsSetupDhcpAliasListEntry 3 }

-- {COLUMN} 310.2.10.10.1.2
lcsSetupDhcpAliasListEntryImageFile OBJECT-TYPE
    SYNTAX     DisplayString (SIZE(0..60))
    MAX-ACCESS read-write
    STATUS     current
    DESCRIPTION
        "-- empty --"
    ::= { lcsSetupDhcpAliasListEntry 2 }

-- {TABLE} 310.2.10.21
lcsSetupDhcpAdditionalOptionsTable OBJECT-TYPE
    SYNTAX     SEQUENCE OF LcsSetupDhcpAdditionalOptionsEntry
    MAX-ACCESS not-accessible
    STATUS     current
    DESCRIPTION
        "-- empty --"
    ::= { lcsSetupDhcp 21 }

-- {ENTRY} 310.2.10.21.1
lcsSetupDhcpAdditionalOptionsEntry OBJECT-TYPE
    SYNTAX     LcsSetupDhcpAdditionalOptionsEntry
    MAX-ACCESS not-accessible
    STATUS     current
    DESCRIPTION
        ""
    INDEX {
        lcsSetupDhcpAdditionalOptionsEntryOptionNumber,
        lcsSetupDhcpAdditionalOptionsEntryNetworkName
    }
    ::= { lcsSetupDhcpAdditionalOptionsTable 1 }

-- {SEQUENCE}
LcsSetupDhcpAdditionalOptionsEntry ::= SEQUENCE {
    lcsSetupDhcpAdditionalOptionsEntryOptionNumber INTEGER,
    lcsSetupDhcpAdditionalOptionsEntryNetworkName DisplayString,
    lcsSetupDhcpAdditionalOptionsEntryOptionType INTEGER,
    lcsSetupDhcpAdditionalOptionsEntryOptionValue DisplayString
}

-- {COLUMN} 310.2.10.21.1.1
lcsSetupDhcpAdditionalOptionsEntryOptionNumber OBJECT-TYPE
    SYNTAX     INTEGER (0..255)
    MAX-ACCESS read-write
    STATUS     current
    DESCRIPTION
        "-- empty --"
    ::= { lcsSetupDhcpAdditionalOptionsEntry 1 }

-- {COLUMN} 310.2.10.21.1.2
lcsSetupDhcpAdditionalOptionsEntryNetworkName OBJECT-TYPE
    SYNTAX     DisplayString (SIZE(0..16))
    MAX-ACCESS read-write
    STATUS     current
    DESCRIPTION
        "-- empty --"
    ::= { lcsSetupDhcpAdditionalOptionsEntry 2 }

-- {COLUMN} 310.2.10.21.1.4
lcsSetupDhcpAdditionalOptionsEntryOptionType OBJECT-TYPE
    SYNTAX     INTEGER
      {
        eString (0),
        eInteger32 (1),
        eInteger16 (3),
        eInteger8 (4),
        eIpAddress (2)
      }
    MAX-ACCESS read-write
    STATUS     current
    DESCRIPTION
        "-- empty --"
    ::= { lcsSetupDhcpAdditionalOptionsEntry 4 }

-- {COLUMN} 310.2.10.21.1.3
lcsSetupDhcpAdditionalOptionsEntryOptionValue OBJECT-TYPE
    SYNTAX     DisplayString (SIZE(0..128))
    MAX-ACCESS read-write
    STATUS     current
    DESCRIPTION
        "-- empty --"
    ::= { lcsSetupDhcpAdditionalOptionsEntry 3 }

-- {SCALAR} 310.2.10.19
lcsSetupDhcpUserClassIdentifer OBJECT-TYPE
    SYNTAX     DisplayString (SIZE(0..63))
    MAX-ACCESS read-write
    STATUS     current
    DESCRIPTION
        "-- empty --"
    ::= { lcsSetupDhcp 19 }

-- {SCALAR} 310.2.10.22
lcsSetupDhcpVendorClassIdentifer OBJECT-TYPE
    SYNTAX     DisplayString (SIZE(0..63))
    MAX-ACCESS read-write
    STATUS     current
    DESCRIPTION
        "-- empty --"
    ::= { lcsSetupDhcp 22 }

-- {OID} 310.2.17
lcsSetupDns OBJECT IDENTIFIER ::= { lcsSetup 17 }

-- {SCALAR} 310.2.17.1
lcsSetupDnsOperating OBJECT-TYPE
    SYNTAX     INTEGER
      {
        eNo (0),
        eYes (1)
      }
    MAX-ACCESS read-only
    STATUS     current
    DESCRIPTION
        "-- empty --"
    ::= { lcsSetupDns 1 }

-- {SCALAR} 310.2.17.14
lcsSetupDnsForwarder OBJECT-TYPE
    SYNTAX     INTEGER
      {
        eNo (0),
        eYes (1)
      }
    MAX-ACCESS read-only
    STATUS     current
    DESCRIPTION
        "-- empty --"
    ::= { lcsSetupDns 14 }

-- {SCALAR} 310.2.17.2
lcsSetupDnsDomain OBJECT-TYPE
    SYNTAX     DisplayString (SIZE(0..64))
    MAX-ACCESS read-only
    STATUS     current
    DESCRIPTION
        "-- empty --"
    ::= { lcsSetupDns 2 }

-- {TABLE} 310.2.17.13
lcsSetupDnsSubDomainsTable OBJECT-TYPE
    SYNTAX     SEQUENCE OF LcsSetupDnsSubDomainsEntry
    MAX-ACCESS not-accessible
    STATUS     current
    DESCRIPTION
        "-- empty --"
    ::= { lcsSetupDns 13 }

-- {ENTRY} 310.2.17.13.1
lcsSetupDnsSubDomainsEntry OBJECT-TYPE
    SYNTAX     LcsSetupDnsSubDomainsEntry
    MAX-ACCESS not-accessible
    STATUS     current
    DESCRIPTION
        ""
    INDEX {
        lcsSetupDnsSubDomainsEntryNetworkName
    }
    ::= { lcsSetupDnsSubDomainsTable 1 }

-- {SEQUENCE}
LcsSetupDnsSubDomainsEntry ::= SEQUENCE {
    lcsSetupDnsSubDomainsEntryNetworkName DisplayString,
    lcsSetupDnsSubDomainsEntrySubDomain DisplayString
}

-- {COLUMN} 310.2.17.13.1.1
lcsSetupDnsSubDomainsEntryNetworkName OBJECT-TYPE
    SYNTAX     DisplayString (SIZE(0..16))
    MAX-ACCESS read-write
    STATUS     current
    DESCRIPTION
        "-- empty --"
    ::= { lcsSetupDnsSubDomainsEntry 1 }

-- {COLUMN} 310.2.17.13.1.2
lcsSetupDnsSubDomainsEntrySubDomain OBJECT-TYPE
    SYNTAX     DisplayString (SIZE(0..64))
    MAX-ACCESS read-write
    STATUS     current
    DESCRIPTION
        "-- empty --"
    ::= { lcsSetupDnsSubDomainsEntry 2 }

-- {SCALAR} 310.2.17.12
lcsSetupDnsResolveDomain OBJECT-TYPE
    SYNTAX     INTEGER
      {
        eNo (0),
        eYes (1)
      }
    MAX-ACCESS read-only
    STATUS     current
    DESCRIPTION
        "-- empty --"
    ::= { lcsSetupDns 12 }

-- {SCALAR} 310.2.17.3
lcsSetupDnsDhcpUsage OBJECT-TYPE
    SYNTAX     INTEGER
      {
        eNo (0),
        eYes (1)
      }
    MAX-ACCESS read-only
    STATUS     current
    DESCRIPTION
        "-- empty --"
    ::= { lcsSetupDns 3 }

-- {SCALAR} 310.2.17.4
lcsSetupDnsNetbiosUsage OBJECT-TYPE
    SYNTAX     INTEGER
      {
        eNo (0),
        eYes (1)
      }
    MAX-ACCESS read-only
    STATUS     current
    DESCRIPTION
        "-- empty --"
    ::= { lcsSetupDns 4 }

-- {TABLE} 310.2.17.5
lcsSetupDnsDnsListTable OBJECT-TYPE
    SYNTAX     SEQUENCE OF LcsSetupDnsDnsListEntry
    MAX-ACCESS not-accessible
    STATUS     current
    DESCRIPTION
        "-- empty --"
    ::= { lcsSetupDns 5 }

-- {ENTRY} 310.2.17.5.1
lcsSetupDnsDnsListEntry OBJECT-TYPE
    SYNTAX     LcsSetupDnsDnsListEntry
    MAX-ACCESS not-accessible
    STATUS     current
    DESCRIPTION
        ""
    INDEX {
        lcsSetupDnsDnsListEntryHostName
    }
    ::= { lcsSetupDnsDnsListTable 1 }

-- {SEQUENCE}
LcsSetupDnsDnsListEntry ::= SEQUENCE {
    lcsSetupDnsDnsListEntryHostName DisplayString,
    lcsSetupDnsDnsListEntryIpAddress IpAddress
}

-- {COLUMN} 310.2.17.5.1.1
lcsSetupDnsDnsListEntryHostName OBJECT-TYPE
    SYNTAX     DisplayString (SIZE(0..64))
    MAX-ACCESS read-write
    STATUS     current
    DESCRIPTION
        "-- empty --"
    ::= { lcsSetupDnsDnsListEntry 1 }

-- {COLUMN} 310.2.17.5.1.2
lcsSetupDnsDnsListEntryIpAddress OBJECT-TYPE
    SYNTAX     IpAddress
    MAX-ACCESS read-write
    STATUS     current
    DESCRIPTION
        "-- empty --"
    ::= { lcsSetupDnsDnsListEntry 2 }

-- {TABLE} 310.2.17.6
lcsSetupDnsFilterListTable OBJECT-TYPE
    SYNTAX     SEQUENCE OF LcsSetupDnsFilterListEntry
    MAX-ACCESS not-accessible
    STATUS     current
    DESCRIPTION
        "-- empty --"
    ::= { lcsSetupDns 6 }

-- {ENTRY} 310.2.17.6.1
lcsSetupDnsFilterListEntry OBJECT-TYPE
    SYNTAX     LcsSetupDnsFilterListEntry
    MAX-ACCESS not-accessible
    STATUS     current
    DESCRIPTION
        ""
    INDEX {
        lcsSetupDnsFilterListEntryIdx
    }
    ::= { lcsSetupDnsFilterListTable 1 }

-- {SEQUENCE}
LcsSetupDnsFilterListEntry ::= SEQUENCE {
    lcsSetupDnsFilterListEntryIdx DisplayString,
    lcsSetupDnsFilterListEntryDomain DisplayString,
    lcsSetupDnsFilterListEntryIpAddress IpAddress,
    lcsSetupDnsFilterListEntryNetmask IpAddress
}

-- {COLUMN} 310.2.17.6.1.1
lcsSetupDnsFilterListEntryIdx OBJECT-TYPE
    SYNTAX     DisplayString (SIZE(0..4))
    MAX-ACCESS read-write
    STATUS     current
    DESCRIPTION
        "-- empty --"
    ::= { lcsSetupDnsFilterListEntry 1 }

-- {COLUMN} 310.2.17.6.1.2
lcsSetupDnsFilterListEntryDomain OBJECT-TYPE
    SYNTAX     DisplayString (SIZE(0..64))
    MAX-ACCESS read-write
    STATUS     current
    DESCRIPTION
        "-- empty --"
    ::= { lcsSetupDnsFilterListEntry 2 }

-- {COLUMN} 310.2.17.6.1.3
lcsSetupDnsFilterListEntryIpAddress OBJECT-TYPE
    SYNTAX     IpAddress
    MAX-ACCESS read-write
    STATUS     current
    DESCRIPTION
        "-- empty --"
    ::= { lcsSetupDnsFilterListEntry 3 }

-- {COLUMN} 310.2.17.6.1.4
lcsSetupDnsFilterListEntryNetmask OBJECT-TYPE
    SYNTAX     IpAddress
    MAX-ACCESS read-write
    STATUS     current
    DESCRIPTION
        "-- empty --"
    ::= { lcsSetupDnsFilterListEntry 4 }

-- {TABLE} 310.2.17.8
lcsSetupDnsDynDnsListTable OBJECT-TYPE
    SYNTAX     SEQUENCE OF LcsSetupDnsDynDnsListEntry
    MAX-ACCESS not-accessible
    STATUS     current
    DESCRIPTION
        "-- empty --"
    ::= { lcsSetupDns 8 }

-- {ENTRY} 310.2.17.8.1
lcsSetupDnsDynDnsListEntry OBJECT-TYPE
    SYNTAX     LcsSetupDnsDynDnsListEntry
    MAX-ACCESS not-accessible
    STATUS     current
    DESCRIPTION
        ""
    INDEX {
        lcsSetupDnsDynDnsListEntryHostName
    }
    ::= { lcsSetupDnsDynDnsListTable 1 }

-- {SEQUENCE}
LcsSetupDnsDynDnsListEntry ::= SEQUENCE {
    lcsSetupDnsDynDnsListEntryHostName DisplayString,
    lcsSetupDnsDynDnsListEntryIpAddress IpAddress,
    lcsSetupDnsDynDnsListEntryTimeout INTEGER
}

-- {COLUMN} 310.2.17.8.1.1
lcsSetupDnsDynDnsListEntryHostName OBJECT-TYPE
    SYNTAX     DisplayString (SIZE(0..64))
    MAX-ACCESS read-only
    STATUS     current
    DESCRIPTION
        "-- empty --"
    ::= { lcsSetupDnsDynDnsListEntry 1 }

-- {COLUMN} 310.2.17.8.1.2
lcsSetupDnsDynDnsListEntryIpAddress OBJECT-TYPE
    SYNTAX     IpAddress
    MAX-ACCESS read-only
    STATUS     current
    DESCRIPTION
        "-- empty --"
    ::= { lcsSetupDnsDynDnsListEntry 2 }

-- {COLUMN} 310.2.17.8.1.3
lcsSetupDnsDynDnsListEntryTimeout OBJECT-TYPE
    SYNTAX     INTEGER (0..2147483647)
    MAX-ACCESS read-only
    STATUS     current
    DESCRIPTION
        "-- empty --"
    ::= { lcsSetupDnsDynDnsListEntry 3 }

-- {TABLE} 310.2.17.9
lcsSetupDnsDnsDestinationsTable OBJECT-TYPE
    SYNTAX     SEQUENCE OF LcsSetupDnsDnsDestinationsEntry
    MAX-ACCESS not-accessible
    STATUS     current
    DESCRIPTION
        "-- empty --"
    ::= { lcsSetupDns 9 }

-- {ENTRY} 310.2.17.9.1
lcsSetupDnsDnsDestinationsEntry OBJECT-TYPE
    SYNTAX     LcsSetupDnsDnsDestinationsEntry
    MAX-ACCESS not-accessible
    STATUS     current
    DESCRIPTION
        ""
    INDEX {
        lcsSetupDnsDnsDestinationsEntryDomainName
    }
    ::= { lcsSetupDnsDnsDestinationsTable 1 }

-- {SEQUENCE}
LcsSetupDnsDnsDestinationsEntry ::= SEQUENCE {
    lcsSetupDnsDnsDestinationsEntryDomainName DisplayString,
    lcsSetupDnsDnsDestinationsEntryDestination DisplayString
}

-- {COLUMN} 310.2.17.9.1.1
lcsSetupDnsDnsDestinationsEntryDomainName OBJECT-TYPE
    SYNTAX     DisplayString (SIZE(0..64))
    MAX-ACCESS read-write
    STATUS     current
    DESCRIPTION
        "-- empty --"
    ::= { lcsSetupDnsDnsDestinationsEntry 1 }

-- {COLUMN} 310.2.17.9.1.2
lcsSetupDnsDnsDestinationsEntryDestination OBJECT-TYPE
    SYNTAX     DisplayString (SIZE(0..81))
    MAX-ACCESS read-write
    STATUS     current
    DESCRIPTION
        "-- empty --"
    ::= { lcsSetupDnsDnsDestinationsEntry 2 }

-- {SCALAR} 310.2.17.7
lcsSetupDnsLeasetime OBJECT-TYPE
    SYNTAX     INTEGER (0..65535)
    MAX-ACCESS read-only
    STATUS     current
    DESCRIPTION
        "-- empty --"
    ::= { lcsSetupDns 7 }

-- {TABLE} 310.2.17.10
lcsSetupDnsServiceLocationListTable OBJECT-TYPE
    SYNTAX     SEQUENCE OF LcsSetupDnsServiceLocationListEntry
    MAX-ACCESS not-accessible
    STATUS     current
    DESCRIPTION
        "-- empty --"
    ::= { lcsSetupDns 10 }

-- {ENTRY} 310.2.17.10.1
lcsSetupDnsServiceLocationListEntry OBJECT-TYPE
    SYNTAX     LcsSetupDnsServiceLocationListEntry
    MAX-ACCESS not-accessible
    STATUS     current
    DESCRIPTION
        ""
    INDEX {
        lcsSetupDnsServiceLocationListEntryServiceName
    }
    ::= { lcsSetupDnsServiceLocationListTable 1 }

-- {SEQUENCE}
LcsSetupDnsServiceLocationListEntry ::= SEQUENCE {
    lcsSetupDnsServiceLocationListEntryServiceName DisplayString,
    lcsSetupDnsServiceLocationListEntryHostName DisplayString,
    lcsSetupDnsServiceLocationListEntryPort INTEGER
}

-- {COLUMN} 310.2.17.10.1.1
lcsSetupDnsServiceLocationListEntryServiceName OBJECT-TYPE
    SYNTAX     DisplayString (SIZE(0..64))
    MAX-ACCESS read-write
    STATUS     current
    DESCRIPTION
        "-- empty --"
    ::= { lcsSetupDnsServiceLocationListEntry 1 }

-- {COLUMN} 310.2.17.10.1.2
lcsSetupDnsServiceLocationListEntryHostName OBJECT-TYPE
    SYNTAX     DisplayString (SIZE(0..64))
    MAX-ACCESS read-write
    STATUS     current
    DESCRIPTION
        "-- empty --"
    ::= { lcsSetupDnsServiceLocationListEntry 2 }

-- {COLUMN} 310.2.17.10.1.3
lcsSetupDnsServiceLocationListEntryPort OBJECT-TYPE
    SYNTAX     INTEGER (0..65535)
    MAX-ACCESS read-write
    STATUS     current
    DESCRIPTION
        "-- empty --"
    ::= { lcsSetupDnsServiceLocationListEntry 3 }

-- {TABLE} 310.2.17.11
lcsSetupDnsDynamicSrvListTable OBJECT-TYPE
    SYNTAX     SEQUENCE OF LcsSetupDnsDynamicSrvListEntry
    MAX-ACCESS not-accessible
    STATUS     current
    DESCRIPTION
        "-- empty --"
    ::= { lcsSetupDns 11 }

-- {ENTRY} 310.2.17.11.1
lcsSetupDnsDynamicSrvListEntry OBJECT-TYPE
    SYNTAX     LcsSetupDnsDynamicSrvListEntry
    MAX-ACCESS not-accessible
    STATUS     current
    DESCRIPTION
        ""
    INDEX {
        lcsSetupDnsDynamicSrvListEntryServiceName
    }
    ::= { lcsSetupDnsDynamicSrvListTable 1 }

-- {SEQUENCE}
LcsSetupDnsDynamicSrvListEntry ::= SEQUENCE {
    lcsSetupDnsDynamicSrvListEntryServiceName DisplayString,
    lcsSetupDnsDynamicSrvListEntryHostName DisplayString,
    lcsSetupDnsDynamicSrvListEntryPort INTEGER
}

-- {COLUMN} 310.2.17.11.1.1
lcsSetupDnsDynamicSrvListEntryServiceName OBJECT-TYPE
    SYNTAX     DisplayString (SIZE(0..64))
    MAX-ACCESS read-only
    STATUS     current
    DESCRIPTION
        "-- empty --"
    ::= { lcsSetupDnsDynamicSrvListEntry 1 }

-- {COLUMN} 310.2.17.11.1.2
lcsSetupDnsDynamicSrvListEntryHostName OBJECT-TYPE
    SYNTAX     DisplayString (SIZE(0..64))
    MAX-ACCESS read-only
    STATUS     current
    DESCRIPTION
        "-- empty --"
    ::= { lcsSetupDnsDynamicSrvListEntry 2 }

-- {COLUMN} 310.2.17.11.1.3
lcsSetupDnsDynamicSrvListEntryPort OBJECT-TYPE
    SYNTAX     INTEGER (0..65535)
    MAX-ACCESS read-only
    STATUS     current
    DESCRIPTION
        "-- empty --"
    ::= { lcsSetupDnsDynamicSrvListEntry 3 }

-- {OID} 310.2.20
lcsSetupLanBridge OBJECT IDENTIFIER ::= { lcsSetup 20 }

-- {SCALAR} 310.2.20.8
lcsSetupLanBridgeIsolatedMode OBJECT-TYPE
    SYNTAX     INTEGER
      {
        eNo (0),
        eYes (1)
      }
    MAX-ACCESS read-only
    STATUS     current
    DESCRIPTION
        "-- empty --"
    ::= { lcsSetupLanBridge 8 }

-- {TABLE} 310.2.20.11
lcsSetupLanBridgePortDataTable OBJECT-TYPE
    SYNTAX     SEQUENCE OF LcsSetupLanBridgePortDataEntry
    MAX-ACCESS not-accessible
    STATUS     current
    DESCRIPTION
        "-- empty --"
    ::= { lcsSetupLanBridge 11 }

-- {ENTRY} 310.2.20.11.1
lcsSetupLanBridgePortDataEntry OBJECT-TYPE
    SYNTAX     LcsSetupLanBridgePortDataEntry
    MAX-ACCESS not-accessible
    STATUS     current
    DESCRIPTION
        ""
    INDEX {
        lcsSetupLanBridgePortDataEntryPort
    }
    ::= { lcsSetupLanBridgePortDataTable 1 }

-- {SEQUENCE}
LcsSetupLanBridgePortDataEntry ::= SEQUENCE {
    lcsSetupLanBridgePortDataEntryPort DisplayString,
    lcsSetupLanBridgePortDataEntryActive INTEGER,
    lcsSetupLanBridgePortDataEntryBridgeGroup INTEGER,
    lcsSetupLanBridgePortDataEntryDhcpLimit INTEGER,
    lcsSetupLanBridgePortDataEntryPointToPointPort INTEGER
}

-- {COLUMN} 310.2.20.11.1.2
lcsSetupLanBridgePortDataEntryPort OBJECT-TYPE
    SYNTAX     DisplayString (SIZE(0..13))
    MAX-ACCESS read-only
    STATUS     current
    DESCRIPTION
        "-- empty --"
    ::= { lcsSetupLanBridgePortDataEntry 2 }

-- {COLUMN} 310.2.20.11.1.3
lcsSetupLanBridgePortDataEntryActive OBJECT-TYPE
    SYNTAX     INTEGER
      {
        eNo (0),
        eYes (1)
      }
    MAX-ACCESS read-write
    STATUS     current
    DESCRIPTION
        "-- empty --"
    ::= { lcsSetupLanBridgePortDataEntry 3 }

-- {COLUMN} 310.2.20.11.1.5
lcsSetupLanBridgePortDataEntryBridgeGroup OBJECT-TYPE
    SYNTAX     INTEGER
      {
        eBrg1 (0),
        eBrg2 (1),
        eBrg3 (2),
        eBrg4 (3),
        eBrg5 (4),
        eBrg6 (5),
        eBrg7 (6),
        eBrg8 (7),
        eNone (255)
      }
    MAX-ACCESS read-write
    STATUS     current
    DESCRIPTION
        "-- empty --"
    ::= { lcsSetupLanBridgePortDataEntry 5 }

-- {COLUMN} 310.2.20.11.1.6
lcsSetupLanBridgePortDataEntryDhcpLimit OBJECT-TYPE
    SYNTAX     INTEGER (0..255)
    MAX-ACCESS read-write
    STATUS     current
    DESCRIPTION
        "-- empty --"
    ::= { lcsSetupLanBridgePortDataEntry 6 }

-- {COLUMN} 310.2.20.11.1.7
lcsSetupLanBridgePortDataEntryPointToPointPort OBJECT-TYPE
    SYNTAX     INTEGER
      {
        eAuto (0),
        eForceTrue (1),
        eForceFalse (2)
      }
    MAX-ACCESS read-write
    STATUS     current
    DESCRIPTION
        "-- empty --"
    ::= { lcsSetupLanBridgePortDataEntry 7 }

-- {SCALAR} 310.2.20.12
lcsSetupLanBridgeAgingTime OBJECT-TYPE
    SYNTAX     INTEGER (0..2147483647)
    MAX-ACCESS read-only
    STATUS     current
    DESCRIPTION
        "-- empty --"
    ::= { lcsSetupLanBridge 12 }

-- {SCALAR} 310.2.20.1
lcsSetupLanBridgeProtocolVersion OBJECT-TYPE
    SYNTAX     INTEGER
      {
        eNo (0),
        eYes (1)
      }
    MAX-ACCESS read-only
    STATUS     current
    DESCRIPTION
        "-- empty --"
    ::= { lcsSetupLanBridge 1 }

-- {SCALAR} 310.2.20.2
lcsSetupLanBridgeBridgePriority OBJECT-TYPE
    SYNTAX     INTEGER (0..65535)
    MAX-ACCESS read-write
    STATUS     current
    DESCRIPTION
        "-- empty --"
    ::= { lcsSetupLanBridge 2 }

-- {SCALAR} 310.2.20.5
lcsSetupLanBridgeMaxAge OBJECT-TYPE
    SYNTAX     INTEGER (0..65535)
    MAX-ACCESS read-write
    STATUS     current
    DESCRIPTION
        "-- empty --"
    ::= { lcsSetupLanBridge 5 }

-- {SCALAR} 310.2.20.6
lcsSetupLanBridgeHelloTime OBJECT-TYPE
    SYNTAX     INTEGER (0..65535)
    MAX-ACCESS read-write
    STATUS     current
    DESCRIPTION
        "-- empty --"
    ::= { lcsSetupLanBridge 6 }

-- {SCALAR} 310.2.20.7
lcsSetupLanBridgeForwardDelay OBJECT-TYPE
    SYNTAX     INTEGER (0..65535)
    MAX-ACCESS read-write
    STATUS     current
    DESCRIPTION
        "-- empty --"
    ::= { lcsSetupLanBridge 7 }

-- {TABLE} 310.2.20.13
lcsSetupLanBridgePriorityMappingTable OBJECT-TYPE
    SYNTAX     SEQUENCE OF LcsSetupLanBridgePriorityMappingEntry
    MAX-ACCESS not-accessible
    STATUS     current
    DESCRIPTION
        "-- empty --"
    ::= { lcsSetupLanBridge 13 }

-- {ENTRY} 310.2.20.13.1
lcsSetupLanBridgePriorityMappingEntry OBJECT-TYPE
    SYNTAX     LcsSetupLanBridgePriorityMappingEntry
    MAX-ACCESS not-accessible
    STATUS     current
    DESCRIPTION
        ""
    INDEX {
        lcsSetupLanBridgePriorityMappingEntryName
    }
    ::= { lcsSetupLanBridgePriorityMappingTable 1 }

-- {SEQUENCE}
LcsSetupLanBridgePriorityMappingEntry ::= SEQUENCE {
    lcsSetupLanBridgePriorityMappingEntryName DisplayString,
    lcsSetupLanBridgePriorityMappingEntryDscpValue INTEGER,
    lcsSetupLanBridgePriorityMappingEntryPriority INTEGER
}

-- {COLUMN} 310.2.20.13.1.1
lcsSetupLanBridgePriorityMappingEntryName OBJECT-TYPE
    SYNTAX     DisplayString (SIZE(0..16))
    MAX-ACCESS read-write
    STATUS     current
    DESCRIPTION
        "-- empty --"
    ::= { lcsSetupLanBridgePriorityMappingEntry 1 }

-- {COLUMN} 310.2.20.13.1.2
lcsSetupLanBridgePriorityMappingEntryDscpValue OBJECT-TYPE
    SYNTAX     INTEGER (0..255)
    MAX-ACCESS read-write
    STATUS     current
    DESCRIPTION
        "-- empty --"
    ::= { lcsSetupLanBridgePriorityMappingEntry 2 }

-- {COLUMN} 310.2.20.13.1.3
lcsSetupLanBridgePriorityMappingEntryPriority OBJECT-TYPE
    SYNTAX     INTEGER
      {
        eBestEffort (0),
        eBackground (1),
        eTwo (2),
        eExcellentEffort (3),
        eControlledLatency (4),
        eVideo (5),
        eVoice (6),
        eNetworkControl (7)
      }
    MAX-ACCESS read-write
    STATUS     current
    DESCRIPTION
        "-- empty --"
    ::= { lcsSetupLanBridgePriorityMappingEntry 3 }

-- {TABLE} 310.2.20.10
lcsSetupLanBridgeProtocolTableTable OBJECT-TYPE
    SYNTAX     SEQUENCE OF LcsSetupLanBridgeProtocolTableEntry
    MAX-ACCESS not-accessible
    STATUS     current
    DESCRIPTION
        "-- empty --"
    ::= { lcsSetupLanBridge 10 }

-- {ENTRY} 310.2.20.10.1
lcsSetupLanBridgeProtocolTableEntry OBJECT-TYPE
    SYNTAX     LcsSetupLanBridgeProtocolTableEntry
    MAX-ACCESS not-accessible
    STATUS     current
    DESCRIPTION
        ""
    INDEX {
        lcsSetupLanBridgeProtocolTableEntryName
    }
    ::= { lcsSetupLanBridgeProtocolTableTable 1 }

-- {SEQUENCE}
LcsSetupLanBridgeProtocolTableEntry ::= SEQUENCE {
    lcsSetupLanBridgeProtocolTableEntryName DisplayString,
    lcsSetupLanBridgeProtocolTableEntryDhcpSrcMac INTEGER,
    lcsSetupLanBridgeProtocolTableEntryDestMacAddr MacAddress,
    lcsSetupLanBridgeProtocolTableEntryProtocol DisplayString,
    lcsSetupLanBridgeProtocolTableEntryIpNetwork IpAddress,
    lcsSetupLanBridgeProtocolTableEntryIpNetmask IpAddress,
    lcsSetupLanBridgeProtocolTableEntrySubProtocol INTEGER,
    lcsSetupLanBridgeProtocolTableEntryPort INTEGER,
    lcsSetupLanBridgeProtocolTableEntryPortEnd INTEGER,
    lcsSetupLanBridgeProtocolTableEntryIfcList DisplayString,
    lcsSetupLanBridgeProtocolTableEntryAction INTEGER,
    lcsSetupLanBridgeProtocolTableEntryRedirectIpAddress IpAddress
}

-- {COLUMN} 310.2.20.10.1.1
lcsSetupLanBridgeProtocolTableEntryName OBJECT-TYPE
    SYNTAX     DisplayString (SIZE(0..15))
    MAX-ACCESS read-write
    STATUS     current
    DESCRIPTION
        "-- empty --"
    ::= { lcsSetupLanBridgeProtocolTableEntry 1 }

-- {COLUMN} 310.2.20.10.1.12
lcsSetupLanBridgeProtocolTableEntryDhcpSrcMac OBJECT-TYPE
    SYNTAX     INTEGER
      {
        eIrrelevant (0),
        eNo (1),
        eYes (2)
      }
    MAX-ACCESS read-write
    STATUS     current
    DESCRIPTION
        "-- empty --"
    ::= { lcsSetupLanBridgeProtocolTableEntry 12 }

-- {COLUMN} 310.2.20.10.1.9
lcsSetupLanBridgeProtocolTableEntryDestMacAddr OBJECT-TYPE
    SYNTAX     MacAddress
    MAX-ACCESS read-write
    STATUS     current
    DESCRIPTION
        "-- empty --"
    ::= { lcsSetupLanBridgeProtocolTableEntry 9 }

-- {COLUMN} 310.2.20.10.1.2
lcsSetupLanBridgeProtocolTableEntryProtocol OBJECT-TYPE
    SYNTAX     DisplayString (SIZE(0..4))
    MAX-ACCESS read-write
    STATUS     current
    DESCRIPTION
        "-- empty --"
    ::= { lcsSetupLanBridgeProtocolTableEntry 2 }

-- {COLUMN} 310.2.20.10.1.10
lcsSetupLanBridgeProtocolTableEntryIpNetwork OBJECT-TYPE
    SYNTAX     IpAddress
    MAX-ACCESS read-write
    STATUS     current
    DESCRIPTION
        "-- empty --"
    ::= { lcsSetupLanBridgeProtocolTableEntry 10 }

-- {COLUMN} 310.2.20.10.1.11
lcsSetupLanBridgeProtocolTableEntryIpNetmask OBJECT-TYPE
    SYNTAX     IpAddress
    MAX-ACCESS read-write
    STATUS     current
    DESCRIPTION
        "-- empty --"
    ::= { lcsSetupLanBridgeProtocolTableEntry 11 }

-- {COLUMN} 310.2.20.10.1.3
lcsSetupLanBridgeProtocolTableEntrySubProtocol OBJECT-TYPE
    SYNTAX     INTEGER (0..65535)
    MAX-ACCESS read-write
    STATUS     current
    DESCRIPTION
        "-- empty --"
    ::= { lcsSetupLanBridgeProtocolTableEntry 3 }

-- {COLUMN} 310.2.20.10.1.4
lcsSetupLanBridgeProtocolTableEntryPort OBJECT-TYPE
    SYNTAX     INTEGER (0..65535)
    MAX-ACCESS read-write
    STATUS     current
    DESCRIPTION
        "-- empty --"
    ::= { lcsSetupLanBridgeProtocolTableEntry 4 }

-- {COLUMN} 310.2.20.10.1.5
lcsSetupLanBridgeProtocolTableEntryPortEnd OBJECT-TYPE
    SYNTAX     INTEGER (0..65535)
    MAX-ACCESS read-write
    STATUS     current
    DESCRIPTION
        "-- empty --"
    ::= { lcsSetupLanBridgeProtocolTableEntry 5 }

-- {COLUMN} 310.2.20.10.1.6
lcsSetupLanBridgeProtocolTableEntryIfcList OBJECT-TYPE
    SYNTAX     DisplayString (SIZE(0..251))
    MAX-ACCESS read-write
    STATUS     current
    DESCRIPTION
        "-- empty --"
    ::= { lcsSetupLanBridgeProtocolTableEntry 6 }

-- {COLUMN} 310.2.20.10.1.7
lcsSetupLanBridgeProtocolTableEntryAction OBJECT-TYPE
    SYNTAX     INTEGER
      {
        eDrop (0),
        ePass (1),
        eRedirect (2)
      }
    MAX-ACCESS read-write
    STATUS     current
    DESCRIPTION
        "-- empty --"
    ::= { lcsSetupLanBridgeProtocolTableEntry 7 }

-- {COLUMN} 310.2.20.10.1.8
lcsSetupLanBridgeProtocolTableEntryRedirectIpAddress OBJECT-TYPE
    SYNTAX     IpAddress
    MAX-ACCESS read-write
    STATUS     current
    DESCRIPTION
        "-- empty --"
    ::= { lcsSetupLanBridgeProtocolTableEntry 8 }

-- {OID} 310.2.20.20
lcsSetupLanBridgeSpanningTree OBJECT IDENTIFIER ::= { lcsSetupLanBridge 20 }

-- {SCALAR} 310.2.20.20.1
lcsSetupLanBridgeSpanningTreeOperating OBJECT-TYPE
    SYNTAX     INTEGER
      {
        eNo (0),
        eYes (1)
      }
    MAX-ACCESS read-only
    STATUS     current
    DESCRIPTION
        "-- empty --"
    ::= { lcsSetupLanBridgeSpanningTree 1 }

-- {SCALAR} 310.2.20.20.12
lcsSetupLanBridgeSpanningTreeProtocolVersion OBJECT-TYPE
    SYNTAX     INTEGER
      {
        eClassic (0),
        eRapid (1)
      }
    MAX-ACCESS read-only
    STATUS     current
    DESCRIPTION
        "-- empty --"
    ::= { lcsSetupLanBridgeSpanningTree 12 }

-- {SCALAR} 310.2.20.20.14
lcsSetupLanBridgeSpanningTreePathCostComputation OBJECT-TYPE
    SYNTAX     INTEGER
      {
        eClassic (0),
        eRapid (1)
      }
    MAX-ACCESS read-only
    STATUS     current
    DESCRIPTION
        "-- empty --"
    ::= { lcsSetupLanBridgeSpanningTree 14 }

-- {SCALAR} 310.2.20.20.2
lcsSetupLanBridgeSpanningTreeBridgePriority OBJECT-TYPE
    SYNTAX     INTEGER (0..65535)
    MAX-ACCESS read-write
    STATUS     current
    DESCRIPTION
        "-- empty --"
    ::= { lcsSetupLanBridgeSpanningTree 2 }

-- {TABLE} 310.2.20.20.11
lcsSetupLanBridgeSpanningTreePortDataTable OBJECT-TYPE
    SYNTAX     SEQUENCE OF LcsSetupLanBridgeSpanningTreePortDataEntry
    MAX-ACCESS not-accessible
    STATUS     current
    DESCRIPTION
        "-- empty --"
    ::= { lcsSetupLanBridgeSpanningTree 11 }

-- {ENTRY} 310.2.20.20.11.1
lcsSetupLanBridgeSpanningTreePortDataEntry OBJECT-TYPE
    SYNTAX     LcsSetupLanBridgeSpanningTreePortDataEntry
    MAX-ACCESS not-accessible
    STATUS     current
    DESCRIPTION
        ""
    INDEX {
        lcsSetupLanBridgeSpanningTreePortDataEntryPort
    }
    ::= { lcsSetupLanBridgeSpanningTreePortDataTable 1 }

-- {SEQUENCE}
LcsSetupLanBridgeSpanningTreePortDataEntry ::= SEQUENCE {
    lcsSetupLanBridgeSpanningTreePortDataEntryPort DisplayString,
    lcsSetupLanBridgeSpanningTreePortDataEntryPriority INTEGER,
    lcsSetupLanBridgeSpanningTreePortDataEntryEdgePort INTEGER,
    lcsSetupLanBridgeSpanningTreePortDataEntryPathCostOverride INTEGER
}

-- {COLUMN} 310.2.20.20.11.1.2
lcsSetupLanBridgeSpanningTreePortDataEntryPort OBJECT-TYPE
    SYNTAX     DisplayString (SIZE(0..13))
    MAX-ACCESS read-only
    STATUS     current
    DESCRIPTION
        "-- empty --"
    ::= { lcsSetupLanBridgeSpanningTreePortDataEntry 2 }

-- {COLUMN} 310.2.20.20.11.1.4
lcsSetupLanBridgeSpanningTreePortDataEntryPriority OBJECT-TYPE
    SYNTAX     INTEGER (0..255)
    MAX-ACCESS read-write
    STATUS     current
    DESCRIPTION
        "-- empty --"
    ::= { lcsSetupLanBridgeSpanningTreePortDataEntry 4 }

-- {COLUMN} 310.2.20.20.11.1.6
lcsSetupLanBridgeSpanningTreePortDataEntryEdgePort OBJECT-TYPE
    SYNTAX     INTEGER
      {
        eNo (0),
        eYes (1)
      }
    MAX-ACCESS read-write
    STATUS     current
    DESCRIPTION
        "-- empty --"
    ::= { lcsSetupLanBridgeSpanningTreePortDataEntry 6 }

-- {COLUMN} 310.2.20.20.11.1.7
lcsSetupLanBridgeSpanningTreePortDataEntryPathCostOverride OBJECT-TYPE
    SYNTAX     INTEGER (0..2147483647)
    MAX-ACCESS read-write
    STATUS     current
    DESCRIPTION
        "-- empty --"
    ::= { lcsSetupLanBridgeSpanningTreePortDataEntry 7 }

-- {SCALAR} 310.2.20.20.5
lcsSetupLanBridgeSpanningTreeMaxAge OBJECT-TYPE
    SYNTAX     INTEGER (0..65535)
    MAX-ACCESS read-write
    STATUS     current
    DESCRIPTION
        "-- empty --"
    ::= { lcsSetupLanBridgeSpanningTree 5 }

-- {SCALAR} 310.2.20.20.6
lcsSetupLanBridgeSpanningTreeHelloTime OBJECT-TYPE
    SYNTAX     INTEGER (0..65535)
    MAX-ACCESS read-write
    STATUS     current
    DESCRIPTION
        "-- empty --"
    ::= { lcsSetupLanBridgeSpanningTree 6 }

-- {SCALAR} 310.2.20.20.7
lcsSetupLanBridgeSpanningTreeForwardDelay OBJECT-TYPE
    SYNTAX     INTEGER (0..65535)
    MAX-ACCESS read-write
    STATUS     current
    DESCRIPTION
        "-- empty --"
    ::= { lcsSetupLanBridgeSpanningTree 7 }

-- {SCALAR} 310.2.20.20.13
lcsSetupLanBridgeSpanningTreeTransmitHoldCount OBJECT-TYPE
    SYNTAX     INTEGER (0..255)
    MAX-ACCESS read-write
    STATUS     current
    DESCRIPTION
        "-- empty --"
    ::= { lcsSetupLanBridgeSpanningTree 13 }

-- {OID} 310.2.20.30
lcsSetupLanBridgeIgmpSnooping OBJECT IDENTIFIER ::= { lcsSetupLanBridge 30 }

-- {SCALAR} 310.2.20.30.1
lcsSetupLanBridgeIgmpSnoopingOperating OBJECT-TYPE
    SYNTAX     INTEGER
      {
        eNo (0),
        eYes (1)
      }
    MAX-ACCESS read-write
    STATUS     current
    DESCRIPTION
        "-- empty --"
    ::= { lcsSetupLanBridgeIgmpSnooping 1 }

-- {TABLE} 310.2.20.30.2
lcsSetupLanBridgeIgmpSnoopingPortSettingsTable OBJECT-TYPE
    SYNTAX     SEQUENCE OF LcsSetupLanBridgeIgmpSnoopingPortSettingsEntry
    MAX-ACCESS not-accessible
    STATUS     current
    DESCRIPTION
        "-- empty --"
    ::= { lcsSetupLanBridgeIgmpSnooping 2 }

-- {ENTRY} 310.2.20.30.2.1
lcsSetupLanBridgeIgmpSnoopingPortSettingsEntry OBJECT-TYPE
    SYNTAX     LcsSetupLanBridgeIgmpSnoopingPortSettingsEntry
    MAX-ACCESS not-accessible
    STATUS     current
    DESCRIPTION
        ""
    INDEX {
        lcsSetupLanBridgeIgmpSnoopingPortSettingsEntryPort
    }
    ::= { lcsSetupLanBridgeIgmpSnoopingPortSettingsTable 1 }

-- {SEQUENCE}
LcsSetupLanBridgeIgmpSnoopingPortSettingsEntry ::= SEQUENCE {
    lcsSetupLanBridgeIgmpSnoopingPortSettingsEntryPort DisplayString,
    lcsSetupLanBridgeIgmpSnoopingPortSettingsEntryRouterPort INTEGER
}

-- {COLUMN} 310.2.20.30.2.1.1
lcsSetupLanBridgeIgmpSnoopingPortSettingsEntryPort OBJECT-TYPE
    SYNTAX     DisplayString (SIZE(0..13))
    MAX-ACCESS read-write
    STATUS     current
    DESCRIPTION
        "-- empty --"
    ::= { lcsSetupLanBridgeIgmpSnoopingPortSettingsEntry 1 }

-- {COLUMN} 310.2.20.30.2.1.2
lcsSetupLanBridgeIgmpSnoopingPortSettingsEntryRouterPort OBJECT-TYPE
    SYNTAX     INTEGER
      {
        eNo (0),
        eAuto (1),
        eYes (2)
      }
    MAX-ACCESS read-write
    STATUS     current
    DESCRIPTION
        "-- empty --"
    ::= { lcsSetupLanBridgeIgmpSnoopingPortSettingsEntry 2 }

-- {SCALAR} 310.2.20.30.3
lcsSetupLanBridgeIgmpSnoopingUnregisteredDataPacketHandling OBJECT-TYPE
    SYNTAX     INTEGER
      {
        eRouterPortsOnly (0),
        eFlood (1),
        eDiscard (2)
      }
    MAX-ACCESS read-write
    STATUS     current
    DESCRIPTION
        "-- empty --"
    ::= { lcsSetupLanBridgeIgmpSnooping 3 }

-- {TABLE} 310.2.20.30.8
lcsSetupLanBridgeIgmpSnoopingStaticMembersTable OBJECT-TYPE
    SYNTAX     SEQUENCE OF LcsSetupLanBridgeIgmpSnoopingStaticMembersEntry
    MAX-ACCESS not-accessible
    STATUS     current
    DESCRIPTION
        "-- empty --"
    ::= { lcsSetupLanBridgeIgmpSnooping 8 }

-- {ENTRY} 310.2.20.30.8.1
lcsSetupLanBridgeIgmpSnoopingStaticMembersEntry OBJECT-TYPE
    SYNTAX     LcsSetupLanBridgeIgmpSnoopingStaticMembersEntry
    MAX-ACCESS not-accessible
    STATUS     current
    DESCRIPTION
        ""
    INDEX {
        lcsSetupLanBridgeIgmpSnoopingStaticMembersEntryAddress,
        lcsSetupLanBridgeIgmpSnoopingStaticMembersEntryVlanId
    }
    ::= { lcsSetupLanBridgeIgmpSnoopingStaticMembersTable 1 }

-- {SEQUENCE}
LcsSetupLanBridgeIgmpSnoopingStaticMembersEntry ::= SEQUENCE {
    lcsSetupLanBridgeIgmpSnoopingStaticMembersEntryAddress IpAddress,
    lcsSetupLanBridgeIgmpSnoopingStaticMembersEntryVlanId INTEGER,
    lcsSetupLanBridgeIgmpSnoopingStaticMembersEntryAllowLearning INTEGER,
    lcsSetupLanBridgeIgmpSnoopingStaticMembersEntryStaticMembers DisplayString
}

-- {COLUMN} 310.2.20.30.8.1.1
lcsSetupLanBridgeIgmpSnoopingStaticMembersEntryAddress OBJECT-TYPE
    SYNTAX     IpAddress
    MAX-ACCESS read-write
    STATUS     current
    DESCRIPTION
        "-- empty --"
    ::= { lcsSetupLanBridgeIgmpSnoopingStaticMembersEntry 1 }

-- {COLUMN} 310.2.20.30.8.1.3
lcsSetupLanBridgeIgmpSnoopingStaticMembersEntryVlanId OBJECT-TYPE
    SYNTAX     INTEGER (0..65535)
    MAX-ACCESS read-write
    STATUS     current
    DESCRIPTION
        "-- empty --"
    ::= { lcsSetupLanBridgeIgmpSnoopingStaticMembersEntry 3 }

-- {COLUMN} 310.2.20.30.8.1.4
lcsSetupLanBridgeIgmpSnoopingStaticMembersEntryAllowLearning OBJECT-TYPE
    SYNTAX     INTEGER
      {
        eYes (0),
        eNo (1)
      }
    MAX-ACCESS read-write
    STATUS     current
    DESCRIPTION
        "-- empty --"
    ::= { lcsSetupLanBridgeIgmpSnoopingStaticMembersEntry 4 }

-- {COLUMN} 310.2.20.30.8.1.2
lcsSetupLanBridgeIgmpSnoopingStaticMembersEntryStaticMembers OBJECT-TYPE
    SYNTAX     DisplayString (SIZE(0..251))
    MAX-ACCESS read-write
    STATUS     current
    DESCRIPTION
        "-- empty --"
    ::= { lcsSetupLanBridgeIgmpSnoopingStaticMembersEntry 2 }

-- {TABLE} 310.2.20.30.4
lcsSetupLanBridgeIgmpSnoopingSimulatedQueriersTable OBJECT-TYPE
    SYNTAX     SEQUENCE OF LcsSetupLanBridgeIgmpSnoopingSimulatedQueriersEntry
    MAX-ACCESS not-accessible
    STATUS     current
    DESCRIPTION
        "-- empty --"
    ::= { lcsSetupLanBridgeIgmpSnooping 4 }

-- {ENTRY} 310.2.20.30.4.1
lcsSetupLanBridgeIgmpSnoopingSimulatedQueriersEntry OBJECT-TYPE
    SYNTAX     LcsSetupLanBridgeIgmpSnoopingSimulatedQueriersEntry
    MAX-ACCESS not-accessible
    STATUS     current
    DESCRIPTION
        ""
    INDEX {
        lcsSetupLanBridgeIgmpSnoopingSimulatedQueriersEntryName
    }
    ::= { lcsSetupLanBridgeIgmpSnoopingSimulatedQueriersTable 1 }

-- {SEQUENCE}
LcsSetupLanBridgeIgmpSnoopingSimulatedQueriersEntry ::= SEQUENCE {
    lcsSetupLanBridgeIgmpSnoopingSimulatedQueriersEntryName DisplayString,
    lcsSetupLanBridgeIgmpSnoopingSimulatedQueriersEntryOperating INTEGER,
    lcsSetupLanBridgeIgmpSnoopingSimulatedQueriersEntryBridgeGroup INTEGER,
    lcsSetupLanBridgeIgmpSnoopingSimulatedQueriersEntryVlanId INTEGER
}

-- {COLUMN} 310.2.20.30.4.1.1
lcsSetupLanBridgeIgmpSnoopingSimulatedQueriersEntryName OBJECT-TYPE
    SYNTAX     DisplayString (SIZE(0..8))
    MAX-ACCESS read-write
    STATUS     current
    DESCRIPTION
        "-- empty --"
    ::= { lcsSetupLanBridgeIgmpSnoopingSimulatedQueriersEntry 1 }

-- {COLUMN} 310.2.20.30.4.1.2
lcsSetupLanBridgeIgmpSnoopingSimulatedQueriersEntryOperating OBJECT-TYPE
    SYNTAX     INTEGER
      {
        eNo (0),
        eYes (1)
      }
    MAX-ACCESS read-write
    STATUS     current
    DESCRIPTION
        "-- empty --"
    ::= { lcsSetupLanBridgeIgmpSnoopingSimulatedQueriersEntry 2 }

-- {COLUMN} 310.2.20.30.4.1.3
lcsSetupLanBridgeIgmpSnoopingSimulatedQueriersEntryBridgeGroup OBJECT-TYPE
    SYNTAX     INTEGER
      {
        eBrg1 (0),
        eBrg2 (1),
        eBrg3 (2),
        eBrg4 (3),
        eBrg5 (4),
        eBrg6 (5),
        eBrg7 (6),
        eBrg8 (7),
        eNone (255)
      }
    MAX-ACCESS read-write
    STATUS     current
    DESCRIPTION
        "-- empty --"
    ::= { lcsSetupLanBridgeIgmpSnoopingSimulatedQueriersEntry 3 }

-- {COLUMN} 310.2.20.30.4.1.4
lcsSetupLanBridgeIgmpSnoopingSimulatedQueriersEntryVlanId OBJECT-TYPE
    SYNTAX     INTEGER (0..65535)
    MAX-ACCESS read-write
    STATUS     current
    DESCRIPTION
        "-- empty --"
    ::= { lcsSetupLanBridgeIgmpSnoopingSimulatedQueriersEntry 4 }

-- {SCALAR} 310.2.20.30.5
lcsSetupLanBridgeIgmpSnoopingQueryInterval OBJECT-TYPE
    SYNTAX     INTEGER (0..2147483647)
    MAX-ACCESS read-write
    STATUS     current
    DESCRIPTION
        "-- empty --"
    ::= { lcsSetupLanBridgeIgmpSnooping 5 }

-- {SCALAR} 310.2.20.30.6
lcsSetupLanBridgeIgmpSnoopingQueryResponseInterval OBJECT-TYPE
    SYNTAX     INTEGER (0..2147483647)
    MAX-ACCESS read-write
    STATUS     current
    DESCRIPTION
        "-- empty --"
    ::= { lcsSetupLanBridgeIgmpSnooping 6 }

-- {SCALAR} 310.2.20.30.7
lcsSetupLanBridgeIgmpSnoopingRobustness OBJECT-TYPE
    SYNTAX     INTEGER (0..2147483647)
    MAX-ACCESS read-write
    STATUS     current
    DESCRIPTION
        "-- empty --"
    ::= { lcsSetupLanBridgeIgmpSnooping 7 }

-- {SCALAR} 310.2.20.30.9
lcsSetupLanBridgeIgmpSnoopingAdvertiseInterval OBJECT-TYPE
    SYNTAX     INTEGER (0..255)
    MAX-ACCESS read-write
    STATUS     current
    DESCRIPTION
        "-- empty --"
    ::= { lcsSetupLanBridgeIgmpSnooping 9 }

-- {TABLE} 310.2.20.4
lcsSetupLanBridgeEncapsulationTableTable OBJECT-TYPE
    SYNTAX     SEQUENCE OF LcsSetupLanBridgeEncapsulationTableEntry
    MAX-ACCESS not-accessible
    STATUS     current
    DESCRIPTION
        "-- empty --"
    ::= { lcsSetupLanBridge 4 }

-- {ENTRY} 310.2.20.4.1
lcsSetupLanBridgeEncapsulationTableEntry OBJECT-TYPE
    SYNTAX     LcsSetupLanBridgeEncapsulationTableEntry
    MAX-ACCESS not-accessible
    STATUS     current
    DESCRIPTION
        ""
    INDEX {
        lcsSetupLanBridgeEncapsulationTableEntryProtocol
    }
    ::= { lcsSetupLanBridgeEncapsulationTableTable 1 }

-- {SEQUENCE}
LcsSetupLanBridgeEncapsulationTableEntry ::= SEQUENCE {
    lcsSetupLanBridgeEncapsulationTableEntryProtocol INTEGER,
    lcsSetupLanBridgeEncapsulationTableEntryEncapsulation INTEGER
}

-- {COLUMN} 310.2.20.4.1.1
lcsSetupLanBridgeEncapsulationTableEntryProtocol OBJECT-TYPE
    SYNTAX     INTEGER (0..65535)
    MAX-ACCESS read-write
    STATUS     current
    DESCRIPTION
        "-- empty --"
    ::= { lcsSetupLanBridgeEncapsulationTableEntry 1 }

-- {COLUMN} 310.2.20.4.1.2
lcsSetupLanBridgeEncapsulationTableEntryEncapsulation OBJECT-TYPE
    SYNTAX     INTEGER
      {
        eEthIi (0),
        eSnap (1)
      }
    MAX-ACCESS read-write
    STATUS     current
    DESCRIPTION
        "-- empty --"
    ::= { lcsSetupLanBridgeEncapsulationTableEntry 2 }

-- {OID} 310.2.21
lcsSetupHttp OBJECT IDENTIFIER ::= { lcsSetup 21 }

-- {SCALAR} 310.2.21.1
lcsSetupHttpDocumentRoot OBJECT-TYPE
    SYNTAX     DisplayString (SIZE(0..99))
    MAX-ACCESS read-only
    STATUS     current
    DESCRIPTION
        "-- empty --"
    ::= { lcsSetupHttp 1 }

-- {SCALAR} 310.2.21.2
lcsSetupHttpUseCss OBJECT-TYPE
    SYNTAX     INTEGER
      {
        eNo (0),
        eYes (1)
      }
    MAX-ACCESS read-only
    STATUS     current
    DESCRIPTION
        "-- empty --"
    ::= { lcsSetupHttp 2 }

-- {SCALAR} 310.2.21.3
lcsSetupHttpFontFamily OBJECT-TYPE
    SYNTAX     DisplayString (SIZE(0..39))
    MAX-ACCESS read-only
    STATUS     current
    DESCRIPTION
        "-- empty --"
    ::= { lcsSetupHttp 3 }

-- {SCALAR} 310.2.21.5
lcsSetupHttpPageHeaders OBJECT-TYPE
    SYNTAX     INTEGER
      {
        eImages (0),
        eTexts (1)
      }
    MAX-ACCESS read-only
    STATUS     current
    DESCRIPTION
        "-- empty --"
    ::= { lcsSetupHttp 5 }

-- {SCALAR} 310.2.21.6
lcsSetupHttpErrorPageStyle OBJECT-TYPE
    SYNTAX     INTEGER
      {
        eStandard (0),
        eNifty (1)
      }
    MAX-ACCESS read-only
    STATUS     current
    DESCRIPTION
        "-- empty --"
    ::= { lcsSetupHttp 6 }

-- {SCALAR} 310.2.21.7
lcsSetupHttpPort OBJECT-TYPE
    SYNTAX     INTEGER (0..65535)
    MAX-ACCESS read-write
    STATUS     current
    DESCRIPTION
        "-- empty --"
    ::= { lcsSetupHttp 7 }

-- {SCALAR} 310.2.21.8
lcsSetupHttpSslPort OBJECT-TYPE
    SYNTAX     INTEGER (0..65535)
    MAX-ACCESS read-write
    STATUS     current
    DESCRIPTION
        "-- empty --"
    ::= { lcsSetupHttp 8 }

-- {SCALAR} 310.2.21.17
lcsSetupHttpUseUserProvidedCertificate OBJECT-TYPE
    SYNTAX     INTEGER
      {
        eNo (0),
        eYes (1)
      }
    MAX-ACCESS read-write
    STATUS     current
    DESCRIPTION
        "-- empty --"
    ::= { lcsSetupHttp 17 }

-- {SCALAR} 310.2.21.18
lcsSetupHttpSslVersions OBJECT-TYPE
    SYNTAX     BITS
      {
        eSslv3 (7),
        eTlsv1 (6),
        eTlsv11 (5),
        eTlsv12 (4)
      }
    MAX-ACCESS read-write
    STATUS     current
    DESCRIPTION
        "-- empty --"
    ::= { lcsSetupHttp 18 }

-- {SCALAR} 310.2.21.11
lcsSetupHttpSessionTimeout OBJECT-TYPE
    SYNTAX     INTEGER (0..2147483647)
    MAX-ACCESS read-only
    STATUS     current
    DESCRIPTION
        "-- empty --"
    ::= { lcsSetupHttp 11 }

-- {SCALAR} 310.2.21.13
lcsSetupHttpStandardDesign OBJECT-TYPE
    SYNTAX     INTEGER
      {
        eNormalDesign (0),
        eDesignForSmallResolutions (1),
        eDesignWithHighContrast (2)
      }
    MAX-ACCESS read-only
    STATUS     current
    DESCRIPTION
        "-- empty --"
    ::= { lcsSetupHttp 13 }

-- {TABLE} 310.2.21.14
lcsSetupHttpShowDeviceInformationTable OBJECT-TYPE
    SYNTAX     SEQUENCE OF LcsSetupHttpShowDeviceInformationEntry
    MAX-ACCESS not-accessible
    STATUS     current
    DESCRIPTION
        "-- empty --"
    ::= { lcsSetupHttp 14 }

-- {ENTRY} 310.2.21.14.1
lcsSetupHttpShowDeviceInformationEntry OBJECT-TYPE
    SYNTAX     LcsSetupHttpShowDeviceInformationEntry
    MAX-ACCESS not-accessible
    STATUS     current
    DESCRIPTION
        ""
    INDEX {
        lcsSetupHttpShowDeviceInformationEntryDeviceInformation
    }
    ::= { lcsSetupHttpShowDeviceInformationTable 1 }

-- {SEQUENCE}
LcsSetupHttpShowDeviceInformationEntry ::= SEQUENCE {
    lcsSetupHttpShowDeviceInformationEntryDeviceInformation INTEGER,
    lcsSetupHttpShowDeviceInformationEntryPosition INTEGER
}

-- {COLUMN} 310.2.21.14.1.1
lcsSetupHttpShowDeviceInformationEntryDeviceInformation OBJECT-TYPE
    SYNTAX     INTEGER
      {
        eCpu (1),
        eMemory (2),
        eWlan (3),
        eP2pConnections (4),
        eEthernetPorts (5),
        eTroughputEthernet (6),
        eUmtsModemInterface (7),
        eRouter (8),
        eFirewall (9),
        eDhcp (10),
        eDns (11),
        eDSLDSLoL (15), -- deprecated value
        eTime (18),
        eIpv4Addresses (19),
        eOperatingTime (20),
        eConnections (22)
      }
    MAX-ACCESS read-write
    STATUS     current
    DESCRIPTION
        "-- empty --"
    ::= { lcsSetupHttpShowDeviceInformationEntry 1 }

-- {COLUMN} 310.2.21.14.1.2
lcsSetupHttpShowDeviceInformationEntryPosition OBJECT-TYPE
    SYNTAX     INTEGER (0..2147483647)
    MAX-ACCESS read-write
    STATUS     current
    DESCRIPTION
        "-- empty --"
    ::= { lcsSetupHttpShowDeviceInformationEntry 2 }

-- {SCALAR} 310.2.21.15
lcsSetupHttpHttpCompression OBJECT-TYPE
    SYNTAX     INTEGER
      {
        eActivated (0),
        eOnlyForWan (1),
        eDeactivated (2)
      }
    MAX-ACCESS read-only
    STATUS     current
    DESCRIPTION
        "-- empty --"
    ::= { lcsSetupHttp 15 }

-- {TABLE} 310.2.21.16
lcsSetupHttpKeepServerPortsOpenTable OBJECT-TYPE
    SYNTAX     SEQUENCE OF LcsSetupHttpKeepServerPortsOpenEntry
    MAX-ACCESS not-accessible
    STATUS     current
    DESCRIPTION
        "-- empty --"
    ::= { lcsSetupHttp 16 }

-- {ENTRY} 310.2.21.16.1
lcsSetupHttpKeepServerPortsOpenEntry OBJECT-TYPE
    SYNTAX     LcsSetupHttpKeepServerPortsOpenEntry
    MAX-ACCESS not-accessible
    STATUS     current
    DESCRIPTION
        ""
    INDEX {
        lcsSetupHttpKeepServerPortsOpenEntryIfc
    }
    ::= { lcsSetupHttpKeepServerPortsOpenTable 1 }

-- {SEQUENCE}
LcsSetupHttpKeepServerPortsOpenEntry ::= SEQUENCE {
    lcsSetupHttpKeepServerPortsOpenEntryIfc INTEGER,
    lcsSetupHttpKeepServerPortsOpenEntryKeepServerPortsOpen INTEGER
}

-- {COLUMN} 310.2.21.16.1.1
lcsSetupHttpKeepServerPortsOpenEntryIfc OBJECT-TYPE
    SYNTAX     INTEGER
      {
        eLan (1),
        eWan (2),
        eWlan (4)
      }
    MAX-ACCESS read-only
    STATUS     current
    DESCRIPTION
        "-- empty --"
    ::= { lcsSetupHttpKeepServerPortsOpenEntry 1 }

-- {COLUMN} 310.2.21.16.1.2
lcsSetupHttpKeepServerPortsOpenEntryKeepServerPortsOpen OBJECT-TYPE
    SYNTAX     INTEGER
      {
        eAutomatic (0),
        eEnabled (1),
        eDisabled (2)
      }
    MAX-ACCESS read-write
    STATUS     current
    DESCRIPTION
        "-- empty --"
    ::= { lcsSetupHttpKeepServerPortsOpenEntry 2 }

-- {SCALAR} 310.2.21.21
lcsSetupHttpMaxHttpJobCount OBJECT-TYPE
    SYNTAX     INTEGER (0..2147483647)
    MAX-ACCESS read-only
    STATUS     current
    DESCRIPTION
        "-- empty --"
    ::= { lcsSetupHttp 21 }

-- {SCALAR} 310.2.21.9
lcsSetupHttpMaxTunnelConnections OBJECT-TYPE
    SYNTAX     INTEGER (0..255)
    MAX-ACCESS read-only
    STATUS     current
    DESCRIPTION
        "-- empty --"
    ::= { lcsSetupHttp 9 }

-- {SCALAR} 310.2.21.10
lcsSetupHttpTunnelIdleTimeout OBJECT-TYPE
    SYNTAX     INTEGER (0..2147483647)
    MAX-ACCESS read-only
    STATUS     current
    DESCRIPTION
        "-- empty --"
    ::= { lcsSetupHttp 10 }

-- {OID} 310.2.21.20
lcsSetupHttpRolloutWizard OBJECT IDENTIFIER ::= { lcsSetupHttp 20 }

-- {SCALAR} 310.2.21.20.1
lcsSetupHttpRolloutWizardOperating OBJECT-TYPE
    SYNTAX     INTEGER
      {
        eNo (0),
        eYes (1)
      }
    MAX-ACCESS read-only
    STATUS     current
    DESCRIPTION
        "-- empty --"
    ::= { lcsSetupHttpRolloutWizard 1 }

-- {SCALAR} 310.2.21.20.2
lcsSetupHttpRolloutWizardTitle OBJECT-TYPE
    SYNTAX     DisplayString (SIZE(0..50))
    MAX-ACCESS read-only
    STATUS     current
    DESCRIPTION
        "-- empty --"
    ::= { lcsSetupHttpRolloutWizard 2 }

-- {TABLE} 310.2.21.20.3
lcsSetupHttpRolloutWizardVariablesTable OBJECT-TYPE
    SYNTAX     SEQUENCE OF LcsSetupHttpRolloutWizardVariablesEntry
    MAX-ACCESS not-accessible
    STATUS     current
    DESCRIPTION
        "-- empty --"
    ::= { lcsSetupHttpRolloutWizard 3 }

-- {ENTRY} 310.2.21.20.3.1
lcsSetupHttpRolloutWizardVariablesEntry OBJECT-TYPE
    SYNTAX     LcsSetupHttpRolloutWizardVariablesEntry
    MAX-ACCESS not-accessible
    STATUS     current
    DESCRIPTION
        ""
    INDEX {
        lcsSetupHttpRolloutWizardVariablesEntryIndex
    }
    ::= { lcsSetupHttpRolloutWizardVariablesTable 1 }

-- {SEQUENCE}
LcsSetupHttpRolloutWizardVariablesEntry ::= SEQUENCE {
    lcsSetupHttpRolloutWizardVariablesEntryIndex INTEGER,
    lcsSetupHttpRolloutWizardVariablesEntryIdent DisplayString,
    lcsSetupHttpRolloutWizardVariablesEntryTitle DisplayString,
    lcsSetupHttpRolloutWizardVariablesEntryType INTEGER,
    lcsSetupHttpRolloutWizardVariablesEntryMinValue INTEGER,
    lcsSetupHttpRolloutWizardVariablesEntryMaxValue INTEGER,
    lcsSetupHttpRolloutWizardVariablesEntryDefaultValue DisplayString
}

-- {COLUMN} 310.2.21.20.3.1.1
lcsSetupHttpRolloutWizardVariablesEntryIndex OBJECT-TYPE
    SYNTAX     INTEGER (0..2147483647)
    MAX-ACCESS read-write
    STATUS     current
    DESCRIPTION
        "-- empty --"
    ::= { lcsSetupHttpRolloutWizardVariablesEntry 1 }

-- {COLUMN} 310.2.21.20.3.1.2
lcsSetupHttpRolloutWizardVariablesEntryIdent OBJECT-TYPE
    SYNTAX     DisplayString (SIZE(0..16))
    MAX-ACCESS read-write
    STATUS     current
    DESCRIPTION
        "-- empty --"
    ::= { lcsSetupHttpRolloutWizardVariablesEntry 2 }

-- {COLUMN} 310.2.21.20.3.1.3
lcsSetupHttpRolloutWizardVariablesEntryTitle OBJECT-TYPE
    SYNTAX     DisplayString (SIZE(0..40))
    MAX-ACCESS read-write
    STATUS     current
    DESCRIPTION
        "-- empty --"
    ::= { lcsSetupHttpRolloutWizardVariablesEntry 3 }

-- {COLUMN} 310.2.21.20.3.1.4
lcsSetupHttpRolloutWizardVariablesEntryType OBJECT-TYPE
    SYNTAX     INTEGER
      {
        eLabel (0),
        eInteger (1),
        eString (2),
        ePassword (3),
        eCheckmark (4)
      }
    MAX-ACCESS read-write
    STATUS     current
    DESCRIPTION
        "-- empty --"
    ::= { lcsSetupHttpRolloutWizardVariablesEntry 4 }

-- {COLUMN} 310.2.21.20.3.1.5
lcsSetupHttpRolloutWizardVariablesEntryMinValue OBJECT-TYPE
    SYNTAX     INTEGER (0..2147483647)
    MAX-ACCESS read-write
    STATUS     current
    DESCRIPTION
        "-- empty --"
    ::= { lcsSetupHttpRolloutWizardVariablesEntry 5 }

-- {COLUMN} 310.2.21.20.3.1.6
lcsSetupHttpRolloutWizardVariablesEntryMaxValue OBJECT-TYPE
    SYNTAX     INTEGER (0..2147483647)
    MAX-ACCESS read-write
    STATUS     current
    DESCRIPTION
        "-- empty --"
    ::= { lcsSetupHttpRolloutWizardVariablesEntry 6 }

-- {COLUMN} 310.2.21.20.3.1.7
lcsSetupHttpRolloutWizardVariablesEntryDefaultValue OBJECT-TYPE
    SYNTAX     DisplayString (SIZE(0..30))
    MAX-ACCESS read-write
    STATUS     current
    DESCRIPTION
        "-- empty --"
    ::= { lcsSetupHttpRolloutWizardVariablesEntry 7 }

-- {SCALAR} 310.2.21.20.5
lcsSetupHttpRolloutWizardRenumberVariables OBJECT-TYPE
    SYNTAX     DisplayString
    MAX-ACCESS read-write
    STATUS     current
    DESCRIPTION
        "-- empty --"
    ::= { lcsSetupHttpRolloutWizard 5 }

-- {TABLE} 310.2.21.20.4
lcsSetupHttpRolloutWizardActionsTable OBJECT-TYPE
    SYNTAX     SEQUENCE OF LcsSetupHttpRolloutWizardActionsEntry
    MAX-ACCESS not-accessible
    STATUS     current
    DESCRIPTION
        "-- empty --"
    ::= { lcsSetupHttpRolloutWizard 4 }

-- {ENTRY} 310.2.21.20.4.1
lcsSetupHttpRolloutWizardActionsEntry OBJECT-TYPE
    SYNTAX     LcsSetupHttpRolloutWizardActionsEntry
    MAX-ACCESS not-accessible
    STATUS     current
    DESCRIPTION
        ""
    INDEX {
        lcsSetupHttpRolloutWizardActionsEntryIndex
    }
    ::= { lcsSetupHttpRolloutWizardActionsTable 1 }

-- {SEQUENCE}
LcsSetupHttpRolloutWizardActionsEntry ::= SEQUENCE {
    lcsSetupHttpRolloutWizardActionsEntryIndex INTEGER,
    lcsSetupHttpRolloutWizardActionsEntryAction DisplayString,
    lcsSetupHttpRolloutWizardActionsEntryDescription DisplayString
}

-- {COLUMN} 310.2.21.20.4.1.1
lcsSetupHttpRolloutWizardActionsEntryIndex OBJECT-TYPE
    SYNTAX     INTEGER (0..2147483647)
    MAX-ACCESS read-write
    STATUS     current
    DESCRIPTION
        "-- empty --"
    ::= { lcsSetupHttpRolloutWizardActionsEntry 1 }

-- {COLUMN} 310.2.21.20.4.1.2
lcsSetupHttpRolloutWizardActionsEntryAction OBJECT-TYPE
    SYNTAX     DisplayString (SIZE(0..251))
    MAX-ACCESS read-write
    STATUS     current
    DESCRIPTION
        "-- empty --"
    ::= { lcsSetupHttpRolloutWizardActionsEntry 2 }

-- {COLUMN} 310.2.21.20.4.1.3
lcsSetupHttpRolloutWizardActionsEntryDescription OBJECT-TYPE
    SYNTAX     DisplayString (SIZE(0..251))
    MAX-ACCESS read-write
    STATUS     current
    DESCRIPTION
        "-- empty --"
    ::= { lcsSetupHttpRolloutWizardActionsEntry 3 }

-- {SCALAR} 310.2.21.20.6
lcsSetupHttpRolloutWizardRenumberActions OBJECT-TYPE
    SYNTAX     DisplayString
    MAX-ACCESS read-write
    STATUS     current
    DESCRIPTION
        "-- empty --"
    ::= { lcsSetupHttpRolloutWizard 6 }

-- {SCALAR} 310.2.21.20.7
lcsSetupHttpRolloutWizardDisplayConnectionStatusFor OBJECT-TYPE
    SYNTAX     BITS
      {
        eNothing (0),
        eDsl (28)
      }
    MAX-ACCESS read-only
    STATUS     current
    DESCRIPTION
        "-- empty --"
    ::= { lcsSetupHttpRolloutWizard 7 }

-- {OID} 310.2.21.30
lcsSetupHttpFileServer OBJECT IDENTIFIER ::= { lcsSetupHttp 30 }

-- {SCALAR} 310.2.21.30.2
lcsSetupHttpFileServerOperating OBJECT-TYPE
    SYNTAX     INTEGER
      {
        eNo (0),
        eYes (1)
      }
    MAX-ACCESS read-write
    STATUS     current
    DESCRIPTION
        "-- empty --"
    ::= { lcsSetupHttpFileServer 2 }

-- {SCALAR} 310.2.21.30.1
lcsSetupHttpFileServerPublicSubdir OBJECT-TYPE
    SYNTAX     DisplayString (SIZE(0..64))
    MAX-ACCESS read-write
    STATUS     current
    DESCRIPTION
        "-- empty --"
    ::= { lcsSetupHttpFileServer 1 }

-- {OID} 310.2.22
lcsSetupSyslog OBJECT IDENTIFIER ::= { lcsSetup 22 }

-- {SCALAR} 310.2.22.1
lcsSetupSyslogOperating OBJECT-TYPE
    SYNTAX     INTEGER
      {
        eNo (0),
        eYes (1)
      }
    MAX-ACCESS read-write
    STATUS     current
    DESCRIPTION
        "-- empty --"
    ::= { lcsSetupSyslog 1 }

-- {TABLE} 310.2.22.2
lcsSetupSyslogServerTable OBJECT-TYPE
    SYNTAX     SEQUENCE OF LcsSetupSyslogServerEntry
    MAX-ACCESS not-accessible
    STATUS     current
    DESCRIPTION
        "-- empty --"
    ::= { lcsSetupSyslog 2 }

-- {ENTRY} 310.2.22.2.1
lcsSetupSyslogServerEntry OBJECT-TYPE
    SYNTAX     LcsSetupSyslogServerEntry
    MAX-ACCESS not-accessible
    STATUS     current
    DESCRIPTION
        ""
    INDEX {
        lcsSetupSyslogServerEntryIdx
    }
    ::= { lcsSetupSyslogServerTable 1 }

-- {SEQUENCE}
LcsSetupSyslogServerEntry ::= SEQUENCE {
    lcsSetupSyslogServerEntryIdx DisplayString,
    lcsSetupSyslogServerEntryIpAddress IpAddress,
    lcsSetupSyslogServerEntrySource INTEGER,
    lcsSetupSyslogServerEntryLevel INTEGER,
    lcsSetupSyslogServerEntryLoopbackAddr DisplayString
}

-- {COLUMN} 310.2.22.2.1.1
lcsSetupSyslogServerEntryIdx OBJECT-TYPE
    SYNTAX     DisplayString (SIZE(0..4))
    MAX-ACCESS read-write
    STATUS     current
    DESCRIPTION
        "-- empty --"
    ::= { lcsSetupSyslogServerEntry 1 }

-- {COLUMN} 310.2.22.2.1.2
lcsSetupSyslogServerEntryIpAddress OBJECT-TYPE
    SYNTAX     IpAddress
    MAX-ACCESS read-write
    STATUS     current
    DESCRIPTION
        "-- empty --"
    ::= { lcsSetupSyslogServerEntry 2 }

-- {COLUMN} 310.2.22.2.1.3
lcsSetupSyslogServerEntrySource OBJECT-TYPE
    SYNTAX     INTEGER (0..255)
    MAX-ACCESS read-write
    STATUS     current
    DESCRIPTION
        "-- empty --"
    ::= { lcsSetupSyslogServerEntry 3 }

-- {COLUMN} 310.2.22.2.1.4
lcsSetupSyslogServerEntryLevel OBJECT-TYPE
    SYNTAX     INTEGER (0..255)
    MAX-ACCESS read-write
    STATUS     current
    DESCRIPTION
        "-- empty --"
    ::= { lcsSetupSyslogServerEntry 4 }

-- {COLUMN} 310.2.22.2.1.6
lcsSetupSyslogServerEntryLoopbackAddr OBJECT-TYPE
    SYNTAX     DisplayString (SIZE(0..16))
    MAX-ACCESS read-write
    STATUS     current
    DESCRIPTION
        "-- empty --"
    ::= { lcsSetupSyslogServerEntry 6 }

-- {TABLE} 310.2.22.3
lcsSetupSyslogFacilityMapperTable OBJECT-TYPE
    SYNTAX     SEQUENCE OF LcsSetupSyslogFacilityMapperEntry
    MAX-ACCESS not-accessible
    STATUS     current
    DESCRIPTION
        "-- empty --"
    ::= { lcsSetupSyslog 3 }

-- {ENTRY} 310.2.22.3.1
lcsSetupSyslogFacilityMapperEntry OBJECT-TYPE
    SYNTAX     LcsSetupSyslogFacilityMapperEntry
    MAX-ACCESS not-accessible
    STATUS     current
    DESCRIPTION
        ""
    INDEX {
        lcsSetupSyslogFacilityMapperEntrySource
    }
    ::= { lcsSetupSyslogFacilityMapperTable 1 }

-- {SEQUENCE}
LcsSetupSyslogFacilityMapperEntry ::= SEQUENCE {
    lcsSetupSyslogFacilityMapperEntrySource INTEGER,
    lcsSetupSyslogFacilityMapperEntryFacility INTEGER
}

-- {COLUMN} 310.2.22.3.1.1
lcsSetupSyslogFacilityMapperEntrySource OBJECT-TYPE
    SYNTAX     INTEGER
      {
        eSystem (1),
        eLogin (2),
        eSystemtime (4),
        eConsoleLogin (8),
        eConnections (16),
        eAccounting (32),
        eAdministration (64),
        eRouter (128)
      }
    MAX-ACCESS read-only
    STATUS     current
    DESCRIPTION
        "-- empty --"
    ::= { lcsSetupSyslogFacilityMapperEntry 1 }

-- {COLUMN} 310.2.22.3.1.2
lcsSetupSyslogFacilityMapperEntryFacility OBJECT-TYPE
    SYNTAX     INTEGER
      {
        eKern (0),
        eUser (1),
        eMail (2),
        eDaemon (3),
        eAuth (4),
        eSyslog (5),
        eLpr (6),
        eNews (7),
        eUucp (8),
        eCron (9),
        eAuthpriv (10),
        eLocal0 (16),
        eLocal1 (17),
        eLocal2 (18),
        eLocal3 (19),
        eLocal4 (20),
        eLocal5 (21),
        eLocal6 (22),
        eLocal7 (23)
      }
    MAX-ACCESS read-write
    STATUS     current
    DESCRIPTION
        "-- empty --"
    ::= { lcsSetupSyslogFacilityMapperEntry 2 }

-- {SCALAR} 310.2.22.4
lcsSetupSyslogPort OBJECT-TYPE
    SYNTAX     INTEGER (0..65535)
    MAX-ACCESS read-write
    STATUS     current
    DESCRIPTION
        "-- empty --"
    ::= { lcsSetupSyslog 4 }

-- {SCALAR} 310.2.22.5
lcsSetupSyslogMessagesTableOrder OBJECT-TYPE
    SYNTAX     INTEGER
      {
        eOldestOnTop (0),
        eNewestOnTop (1)
      }
    MAX-ACCESS read-write
    STATUS     current
    DESCRIPTION
        "-- empty --"
    ::= { lcsSetupSyslog 5 }

-- {SCALAR} 310.2.22.8
lcsSetupSyslogLogCliChanges OBJECT-TYPE
    SYNTAX     INTEGER
      {
        eNo (0),
        eYes (1)
      }
    MAX-ACCESS read-write
    STATUS     current
    DESCRIPTION
        "-- empty --"
    ::= { lcsSetupSyslog 8 }

-- {SCALAR} 310.2.22.9
lcsSetupSyslogMaxMessageAgeHours OBJECT-TYPE
    SYNTAX     INTEGER (0..2147483647)
    MAX-ACCESS read-write
    STATUS     current
    DESCRIPTION
        "-- empty --"
    ::= { lcsSetupSyslog 9 }

-- {SCALAR} 310.2.22.10
lcsSetupSyslogRemoveOldMessages OBJECT-TYPE
    SYNTAX     INTEGER
      {
        eNo (0),
        eYes (1)
      }
    MAX-ACCESS read-write
    STATUS     current
    DESCRIPTION
        "-- empty --"
    ::= { lcsSetupSyslog 10 }

-- {OID} 310.2.16
lcsSetupNetbios OBJECT IDENTIFIER ::= { lcsSetup 16 }

-- {SCALAR} 310.2.16.1
lcsSetupNetbiosOperating OBJECT-TYPE
    SYNTAX     INTEGER
      {
        eNo (0),
        eYes (1)
      }
    MAX-ACCESS read-only
    STATUS     current
    DESCRIPTION
        "-- empty --"
    ::= { lcsSetupNetbios 1 }

-- {TABLE} 310.2.16.12
lcsSetupNetbiosNetworksTable OBJECT-TYPE
    SYNTAX     SEQUENCE OF LcsSetupNetbiosNetworksEntry
    MAX-ACCESS not-accessible
    STATUS     current
    DESCRIPTION
        "-- empty --"
    ::= { lcsSetupNetbios 12 }

-- {ENTRY} 310.2.16.12.1
lcsSetupNetbiosNetworksEntry OBJECT-TYPE
    SYNTAX     LcsSetupNetbiosNetworksEntry
    MAX-ACCESS not-accessible
    STATUS     current
    DESCRIPTION
        ""
    INDEX {
        lcsSetupNetbiosNetworksEntryNetworkName
    }
    ::= { lcsSetupNetbiosNetworksTable 1 }

-- {SEQUENCE}
LcsSetupNetbiosNetworksEntry ::= SEQUENCE {
    lcsSetupNetbiosNetworksEntryNetworkName DisplayString,
    lcsSetupNetbiosNetworksEntryOperating INTEGER,
    lcsSetupNetbiosNetworksEntryNtDomain DisplayString
}

-- {COLUMN} 310.2.16.12.1.1
lcsSetupNetbiosNetworksEntryNetworkName OBJECT-TYPE
    SYNTAX     DisplayString (SIZE(0..16))
    MAX-ACCESS read-write
    STATUS     current
    DESCRIPTION
        "-- empty --"
    ::= { lcsSetupNetbiosNetworksEntry 1 }

-- {COLUMN} 310.2.16.12.1.2
lcsSetupNetbiosNetworksEntryOperating OBJECT-TYPE
    SYNTAX     INTEGER
      {
        eNo (0),
        eYes (1)
      }
    MAX-ACCESS read-write
    STATUS     current
    DESCRIPTION
        "-- empty --"
    ::= { lcsSetupNetbiosNetworksEntry 2 }

-- {COLUMN} 310.2.16.12.1.3
lcsSetupNetbiosNetworksEntryNtDomain OBJECT-TYPE
    SYNTAX     DisplayString (SIZE(0..15))
    MAX-ACCESS read-write
    STATUS     current
    DESCRIPTION
        "-- empty --"
    ::= { lcsSetupNetbiosNetworksEntry 3 }

-- {SCALAR} 310.2.16.2
lcsSetupNetbiosScopeId OBJECT-TYPE
    SYNTAX     DisplayString (SIZE(0..64))
    MAX-ACCESS read-only
    STATUS     current
    DESCRIPTION
        "-- empty --"
    ::= { lcsSetupNetbios 2 }

-- {TABLE} 310.2.16.4
lcsSetupNetbiosPeersTable OBJECT-TYPE
    SYNTAX     SEQUENCE OF LcsSetupNetbiosPeersEntry
    MAX-ACCESS not-accessible
    STATUS     current
    DESCRIPTION
        "-- empty --"
    ::= { lcsSetupNetbios 4 }

-- {ENTRY} 310.2.16.4.1
lcsSetupNetbiosPeersEntry OBJECT-TYPE
    SYNTAX     LcsSetupNetbiosPeersEntry
    MAX-ACCESS not-accessible
    STATUS     current
    DESCRIPTION
        ""
    INDEX {
        lcsSetupNetbiosPeersEntryName
    }
    ::= { lcsSetupNetbiosPeersTable 1 }

-- {SEQUENCE}
LcsSetupNetbiosPeersEntry ::= SEQUENCE {
    lcsSetupNetbiosPeersEntryName DisplayString,
    lcsSetupNetbiosPeersEntryType INTEGER
}

-- {COLUMN} 310.2.16.4.1.1
lcsSetupNetbiosPeersEntryName OBJECT-TYPE
    SYNTAX     DisplayString (SIZE(0..16))
    MAX-ACCESS read-write
    STATUS     current
    DESCRIPTION
        "-- empty --"
    ::= { lcsSetupNetbiosPeersEntry 1 }

-- {COLUMN} 310.2.16.4.1.3
lcsSetupNetbiosPeersEntryType OBJECT-TYPE
    SYNTAX     INTEGER
      {
        eWorkstation (1),
        eRouter (0)
      }
    MAX-ACCESS read-write
    STATUS     current
    DESCRIPTION
        "-- empty --"
    ::= { lcsSetupNetbiosPeersEntry 3 }

-- {TABLE} 310.2.16.5
lcsSetupNetbiosGroupListTable OBJECT-TYPE
    SYNTAX     SEQUENCE OF LcsSetupNetbiosGroupListEntry
    MAX-ACCESS not-accessible
    STATUS     current
    DESCRIPTION
        "-- empty --"
    ::= { lcsSetupNetbios 5 }

-- {ENTRY} 310.2.16.5.1
lcsSetupNetbiosGroupListEntry OBJECT-TYPE
    SYNTAX     LcsSetupNetbiosGroupListEntry
    MAX-ACCESS not-accessible
    STATUS     current
    DESCRIPTION
        ""
    INDEX {
        lcsSetupNetbiosGroupListEntryGroupDomain,
        lcsSetupNetbiosGroupListEntryType,
        lcsSetupNetbiosGroupListEntryIpAddress,
        lcsSetupNetbiosGroupListEntryRtgTag
    }
    ::= { lcsSetupNetbiosGroupListTable 1 }

-- {SEQUENCE}
LcsSetupNetbiosGroupListEntry ::= SEQUENCE {
    lcsSetupNetbiosGroupListEntryGroupDomain DisplayString,
    lcsSetupNetbiosGroupListEntryType DisplayString,
    lcsSetupNetbiosGroupListEntryIpAddress IpAddress,
    lcsSetupNetbiosGroupListEntryRtgTag INTEGER,
    lcsSetupNetbiosGroupListEntryPeer DisplayString,
    lcsSetupNetbiosGroupListEntryNetworkName DisplayString,
    lcsSetupNetbiosGroupListEntryTimeout INTEGER,
    lcsSetupNetbiosGroupListEntryFlags DisplayString
}

-- {COLUMN} 310.2.16.5.1.1
lcsSetupNetbiosGroupListEntryGroupDomain OBJECT-TYPE
    SYNTAX     DisplayString (SIZE(0..15))
    MAX-ACCESS read-only
    STATUS     current
    DESCRIPTION
        "-- empty --"
    ::= { lcsSetupNetbiosGroupListEntry 1 }

-- {COLUMN} 310.2.16.5.1.2
lcsSetupNetbiosGroupListEntryType OBJECT-TYPE
    SYNTAX     DisplayString (SIZE(0..1))
    MAX-ACCESS read-only
    STATUS     current
    DESCRIPTION
        "-- empty --"
    ::= { lcsSetupNetbiosGroupListEntry 2 }

-- {COLUMN} 310.2.16.5.1.3
lcsSetupNetbiosGroupListEntryIpAddress OBJECT-TYPE
    SYNTAX     IpAddress
    MAX-ACCESS read-only
    STATUS     current
    DESCRIPTION
        "-- empty --"
    ::= { lcsSetupNetbiosGroupListEntry 3 }

-- {COLUMN} 310.2.16.5.1.8
lcsSetupNetbiosGroupListEntryRtgTag OBJECT-TYPE
    SYNTAX     INTEGER (0..65535)
    MAX-ACCESS read-only
    STATUS     current
    DESCRIPTION
        "-- empty --"
    ::= { lcsSetupNetbiosGroupListEntry 8 }

-- {COLUMN} 310.2.16.5.1.4
lcsSetupNetbiosGroupListEntryPeer OBJECT-TYPE
    SYNTAX     DisplayString (SIZE(0..16))
    MAX-ACCESS read-only
    STATUS     current
    DESCRIPTION
        "-- empty --"
    ::= { lcsSetupNetbiosGroupListEntry 4 }

-- {COLUMN} 310.2.16.5.1.7
lcsSetupNetbiosGroupListEntryNetworkName OBJECT-TYPE
    SYNTAX     DisplayString (SIZE(0..16))
    MAX-ACCESS read-only
    STATUS     current
    DESCRIPTION
        "-- empty --"
    ::= { lcsSetupNetbiosGroupListEntry 7 }

-- {COLUMN} 310.2.16.5.1.5
lcsSetupNetbiosGroupListEntryTimeout OBJECT-TYPE
    SYNTAX     INTEGER (0..2147483647)
    MAX-ACCESS read-only
    STATUS     current
    DESCRIPTION
        "-- empty --"
    ::= { lcsSetupNetbiosGroupListEntry 5 }

-- {COLUMN} 310.2.16.5.1.6
lcsSetupNetbiosGroupListEntryFlags OBJECT-TYPE
    SYNTAX     DisplayString (SIZE(0..2))
    MAX-ACCESS read-only
    STATUS     current
    DESCRIPTION
        "-- empty --"
    ::= { lcsSetupNetbiosGroupListEntry 6 }

-- {TABLE} 310.2.16.6
lcsSetupNetbiosHostListTable OBJECT-TYPE
    SYNTAX     SEQUENCE OF LcsSetupNetbiosHostListEntry
    MAX-ACCESS not-accessible
    STATUS     current
    DESCRIPTION
        "-- empty --"
    ::= { lcsSetupNetbios 6 }

-- {ENTRY} 310.2.16.6.1
lcsSetupNetbiosHostListEntry OBJECT-TYPE
    SYNTAX     LcsSetupNetbiosHostListEntry
    MAX-ACCESS not-accessible
    STATUS     current
    DESCRIPTION
        ""
    INDEX {
        lcsSetupNetbiosHostListEntryName,
        lcsSetupNetbiosHostListEntryType,
        lcsSetupNetbiosHostListEntryIpAddress,
        lcsSetupNetbiosHostListEntryRtgTag
    }
    ::= { lcsSetupNetbiosHostListTable 1 }

-- {SEQUENCE}
LcsSetupNetbiosHostListEntry ::= SEQUENCE {
    lcsSetupNetbiosHostListEntryName DisplayString,
    lcsSetupNetbiosHostListEntryType DisplayString,
    lcsSetupNetbiosHostListEntryIpAddress IpAddress,
    lcsSetupNetbiosHostListEntryRtgTag INTEGER,
    lcsSetupNetbiosHostListEntryPeer DisplayString,
    lcsSetupNetbiosHostListEntryNetworkName DisplayString,
    lcsSetupNetbiosHostListEntryTimeout INTEGER,
    lcsSetupNetbiosHostListEntryFlags DisplayString
}

-- {COLUMN} 310.2.16.6.1.1
lcsSetupNetbiosHostListEntryName OBJECT-TYPE
    SYNTAX     DisplayString (SIZE(0..15))
    MAX-ACCESS read-only
    STATUS     current
    DESCRIPTION
        "-- empty --"
    ::= { lcsSetupNetbiosHostListEntry 1 }

-- {COLUMN} 310.2.16.6.1.2
lcsSetupNetbiosHostListEntryType OBJECT-TYPE
    SYNTAX     DisplayString (SIZE(0..1))
    MAX-ACCESS read-only
    STATUS     current
    DESCRIPTION
        "-- empty --"
    ::= { lcsSetupNetbiosHostListEntry 2 }

-- {COLUMN} 310.2.16.6.1.3
lcsSetupNetbiosHostListEntryIpAddress OBJECT-TYPE
    SYNTAX     IpAddress
    MAX-ACCESS read-only
    STATUS     current
    DESCRIPTION
        "-- empty --"
    ::= { lcsSetupNetbiosHostListEntry 3 }

-- {COLUMN} 310.2.16.6.1.8
lcsSetupNetbiosHostListEntryRtgTag OBJECT-TYPE
    SYNTAX     INTEGER (0..65535)
    MAX-ACCESS read-only
    STATUS     current
    DESCRIPTION
        "-- empty --"
    ::= { lcsSetupNetbiosHostListEntry 8 }

-- {COLUMN} 310.2.16.6.1.4
lcsSetupNetbiosHostListEntryPeer OBJECT-TYPE
    SYNTAX     DisplayString (SIZE(0..16))
    MAX-ACCESS read-only
    STATUS     current
    DESCRIPTION
        "-- empty --"
    ::= { lcsSetupNetbiosHostListEntry 4 }

-- {COLUMN} 310.2.16.6.1.7
lcsSetupNetbiosHostListEntryNetworkName OBJECT-TYPE
    SYNTAX     DisplayString (SIZE(0..16))
    MAX-ACCESS read-only
    STATUS     current
    DESCRIPTION
        "-- empty --"
    ::= { lcsSetupNetbiosHostListEntry 7 }

-- {COLUMN} 310.2.16.6.1.5
lcsSetupNetbiosHostListEntryTimeout OBJECT-TYPE
    SYNTAX     INTEGER (0..2147483647)
    MAX-ACCESS read-only
    STATUS     current
    DESCRIPTION
        "-- empty --"
    ::= { lcsSetupNetbiosHostListEntry 5 }

-- {COLUMN} 310.2.16.6.1.6
lcsSetupNetbiosHostListEntryFlags OBJECT-TYPE
    SYNTAX     DisplayString (SIZE(0..2))
    MAX-ACCESS read-only
    STATUS     current
    DESCRIPTION
        "-- empty --"
    ::= { lcsSetupNetbiosHostListEntry 6 }

-- {TABLE} 310.2.16.7
lcsSetupNetbiosServerListTable OBJECT-TYPE
    SYNTAX     SEQUENCE OF LcsSetupNetbiosServerListEntry
    MAX-ACCESS not-accessible
    STATUS     current
    DESCRIPTION
        "-- empty --"
    ::= { lcsSetupNetbios 7 }

-- {ENTRY} 310.2.16.7.1
lcsSetupNetbiosServerListEntry OBJECT-TYPE
    SYNTAX     LcsSetupNetbiosServerListEntry
    MAX-ACCESS not-accessible
    STATUS     current
    DESCRIPTION
        ""
    INDEX {
        lcsSetupNetbiosServerListEntryHost,
        lcsSetupNetbiosServerListEntryGroupDomain,
        lcsSetupNetbiosServerListEntryIpAddress,
        lcsSetupNetbiosServerListEntryRtgTag
    }
    ::= { lcsSetupNetbiosServerListTable 1 }

-- {SEQUENCE}
LcsSetupNetbiosServerListEntry ::= SEQUENCE {
    lcsSetupNetbiosServerListEntryHost DisplayString,
    lcsSetupNetbiosServerListEntryGroupDomain DisplayString,
    lcsSetupNetbiosServerListEntryIpAddress DisplayString,
    lcsSetupNetbiosServerListEntryRtgTag INTEGER,
    lcsSetupNetbiosServerListEntryOsVer DisplayString,
    lcsSetupNetbiosServerListEntrySmbVer DisplayString,
    lcsSetupNetbiosServerListEntryServerTyp DisplayString,
    lcsSetupNetbiosServerListEntryPeer DisplayString,
    lcsSetupNetbiosServerListEntryNetworkName DisplayString,
    lcsSetupNetbiosServerListEntryTimeout INTEGER,
    lcsSetupNetbiosServerListEntryFlags DisplayString
}

-- {COLUMN} 310.2.16.7.1.1
lcsSetupNetbiosServerListEntryHost OBJECT-TYPE
    SYNTAX     DisplayString (SIZE(0..15))
    MAX-ACCESS read-only
    STATUS     current
    DESCRIPTION
        "-- empty --"
    ::= { lcsSetupNetbiosServerListEntry 1 }

-- {COLUMN} 310.2.16.7.1.2
lcsSetupNetbiosServerListEntryGroupDomain OBJECT-TYPE
    SYNTAX     DisplayString (SIZE(0..16))
    MAX-ACCESS read-only
    STATUS     current
    DESCRIPTION
        "-- empty --"
    ::= { lcsSetupNetbiosServerListEntry 2 }

-- {COLUMN} 310.2.16.7.1.4
lcsSetupNetbiosServerListEntryIpAddress OBJECT-TYPE
    SYNTAX     DisplayString (SIZE(0..15))
    MAX-ACCESS read-only
    STATUS     current
    DESCRIPTION
        "-- empty --"
    ::= { lcsSetupNetbiosServerListEntry 4 }

-- {COLUMN} 310.2.16.7.1.12
lcsSetupNetbiosServerListEntryRtgTag OBJECT-TYPE
    SYNTAX     INTEGER (0..65535)
    MAX-ACCESS read-only
    STATUS     current
    DESCRIPTION
        "-- empty --"
    ::= { lcsSetupNetbiosServerListEntry 12 }

-- {COLUMN} 310.2.16.7.1.5
lcsSetupNetbiosServerListEntryOsVer OBJECT-TYPE
    SYNTAX     DisplayString (SIZE(0..2))
    MAX-ACCESS read-only
    STATUS     current
    DESCRIPTION
        "-- empty --"
    ::= { lcsSetupNetbiosServerListEntry 5 }

-- {COLUMN} 310.2.16.7.1.6
lcsSetupNetbiosServerListEntrySmbVer OBJECT-TYPE
    SYNTAX     DisplayString (SIZE(0..2))
    MAX-ACCESS read-only
    STATUS     current
    DESCRIPTION
        "-- empty --"
    ::= { lcsSetupNetbiosServerListEntry 6 }

-- {COLUMN} 310.2.16.7.1.7
lcsSetupNetbiosServerListEntryServerTyp OBJECT-TYPE
    SYNTAX     DisplayString (SIZE(0..4))
    MAX-ACCESS read-only
    STATUS     current
    DESCRIPTION
        "-- empty --"
    ::= { lcsSetupNetbiosServerListEntry 7 }

-- {COLUMN} 310.2.16.7.1.8
lcsSetupNetbiosServerListEntryPeer OBJECT-TYPE
    SYNTAX     DisplayString (SIZE(0..16))
    MAX-ACCESS read-only
    STATUS     current
    DESCRIPTION
        "-- empty --"
    ::= { lcsSetupNetbiosServerListEntry 8 }

-- {COLUMN} 310.2.16.7.1.11
lcsSetupNetbiosServerListEntryNetworkName OBJECT-TYPE
    SYNTAX     DisplayString (SIZE(0..16))
    MAX-ACCESS read-only
    STATUS     current
    DESCRIPTION
        "-- empty --"
    ::= { lcsSetupNetbiosServerListEntry 11 }

-- {COLUMN} 310.2.16.7.1.9
lcsSetupNetbiosServerListEntryTimeout OBJECT-TYPE
    SYNTAX     INTEGER (0..2147483647)
    MAX-ACCESS read-only
    STATUS     current
    DESCRIPTION
        "-- empty --"
    ::= { lcsSetupNetbiosServerListEntry 9 }

-- {COLUMN} 310.2.16.7.1.10
lcsSetupNetbiosServerListEntryFlags OBJECT-TYPE
    SYNTAX     DisplayString (SIZE(0..2))
    MAX-ACCESS read-only
    STATUS     current
    DESCRIPTION
        "-- empty --"
    ::= { lcsSetupNetbiosServerListEntry 10 }

-- {TABLE} 310.2.16.13
lcsSetupNetbiosBrowserListTable OBJECT-TYPE
    SYNTAX     SEQUENCE OF LcsSetupNetbiosBrowserListEntry
    MAX-ACCESS not-accessible
    STATUS     current
    DESCRIPTION
        "-- empty --"
    ::= { lcsSetupNetbios 13 }

-- {ENTRY} 310.2.16.13.1
lcsSetupNetbiosBrowserListEntry OBJECT-TYPE
    SYNTAX     LcsSetupNetbiosBrowserListEntry
    MAX-ACCESS not-accessible
    STATUS     current
    DESCRIPTION
        ""
    INDEX {
        lcsSetupNetbiosBrowserListEntryBrowser,
        lcsSetupNetbiosBrowserListEntryGroupDomain,
        lcsSetupNetbiosBrowserListEntryIpAddress,
        lcsSetupNetbiosBrowserListEntryRtgTag
    }
    ::= { lcsSetupNetbiosBrowserListTable 1 }

-- {SEQUENCE}
LcsSetupNetbiosBrowserListEntry ::= SEQUENCE {
    lcsSetupNetbiosBrowserListEntryBrowser DisplayString,
    lcsSetupNetbiosBrowserListEntryGroupDomain DisplayString,
    lcsSetupNetbiosBrowserListEntryIpAddress DisplayString,
    lcsSetupNetbiosBrowserListEntryRtgTag INTEGER,
    lcsSetupNetbiosBrowserListEntryOsVer DisplayString,
    lcsSetupNetbiosBrowserListEntryServerTyp DisplayString,
    lcsSetupNetbiosBrowserListEntryPeer DisplayString,
    lcsSetupNetbiosBrowserListEntryNetworkName DisplayString,
    lcsSetupNetbiosBrowserListEntryTimeout INTEGER,
    lcsSetupNetbiosBrowserListEntryFlags DisplayString
}

-- {COLUMN} 310.2.16.13.1.1
lcsSetupNetbiosBrowserListEntryBrowser OBJECT-TYPE
    SYNTAX     DisplayString (SIZE(0..15))
    MAX-ACCESS read-only
    STATUS     current
    DESCRIPTION
        "-- empty --"
    ::= { lcsSetupNetbiosBrowserListEntry 1 }

-- {COLUMN} 310.2.16.13.1.2
lcsSetupNetbiosBrowserListEntryGroupDomain OBJECT-TYPE
    SYNTAX     DisplayString (SIZE(0..16))
    MAX-ACCESS read-only
    STATUS     current
    DESCRIPTION
        "-- empty --"
    ::= { lcsSetupNetbiosBrowserListEntry 2 }

-- {COLUMN} 310.2.16.13.1.4
lcsSetupNetbiosBrowserListEntryIpAddress OBJECT-TYPE
    SYNTAX     DisplayString (SIZE(0..15))
    MAX-ACCESS read-only
    STATUS     current
    DESCRIPTION
        "-- empty --"
    ::= { lcsSetupNetbiosBrowserListEntry 4 }

-- {COLUMN} 310.2.16.13.1.12
lcsSetupNetbiosBrowserListEntryRtgTag OBJECT-TYPE
    SYNTAX     INTEGER (0..65535)
    MAX-ACCESS read-only
    STATUS     current
    DESCRIPTION
        "-- empty --"
    ::= { lcsSetupNetbiosBrowserListEntry 12 }

-- {COLUMN} 310.2.16.13.1.5
lcsSetupNetbiosBrowserListEntryOsVer OBJECT-TYPE
    SYNTAX     DisplayString (SIZE(0..2))
    MAX-ACCESS read-only
    STATUS     current
    DESCRIPTION
        "-- empty --"
    ::= { lcsSetupNetbiosBrowserListEntry 5 }

-- {COLUMN} 310.2.16.13.1.7
lcsSetupNetbiosBrowserListEntryServerTyp OBJECT-TYPE
    SYNTAX     DisplayString (SIZE(0..4))
    MAX-ACCESS read-only
    STATUS     current
    DESCRIPTION
        "-- empty --"
    ::= { lcsSetupNetbiosBrowserListEntry 7 }

-- {COLUMN} 310.2.16.13.1.8
lcsSetupNetbiosBrowserListEntryPeer OBJECT-TYPE
    SYNTAX     DisplayString (SIZE(0..16))
    MAX-ACCESS read-only
    STATUS     current
    DESCRIPTION
        "-- empty --"
    ::= { lcsSetupNetbiosBrowserListEntry 8 }

-- {COLUMN} 310.2.16.13.1.11
lcsSetupNetbiosBrowserListEntryNetworkName OBJECT-TYPE
    SYNTAX     DisplayString (SIZE(0..16))
    MAX-ACCESS read-only
    STATUS     current
    DESCRIPTION
        "-- empty --"
    ::= { lcsSetupNetbiosBrowserListEntry 11 }

-- {COLUMN} 310.2.16.13.1.9
lcsSetupNetbiosBrowserListEntryTimeout OBJECT-TYPE
    SYNTAX     INTEGER (0..2147483647)
    MAX-ACCESS read-only
    STATUS     current
    DESCRIPTION
        "-- empty --"
    ::= { lcsSetupNetbiosBrowserListEntry 9 }

-- {COLUMN} 310.2.16.13.1.10
lcsSetupNetbiosBrowserListEntryFlags OBJECT-TYPE
    SYNTAX     DisplayString (SIZE(0..2))
    MAX-ACCESS read-only
    STATUS     current
    DESCRIPTION
        "-- empty --"
    ::= { lcsSetupNetbiosBrowserListEntry 10 }

-- {SCALAR} 310.2.16.14
lcsSetupNetbiosSupportBrowsing OBJECT-TYPE
    SYNTAX     INTEGER
      {
        eNo (0),
        eYes (1)
      }
    MAX-ACCESS read-only
    STATUS     current
    DESCRIPTION
        "-- empty --"
    ::= { lcsSetupNetbios 14 }

-- {SCALAR} 310.2.16.8
lcsSetupNetbiosWatchdogs OBJECT-TYPE
    SYNTAX     INTEGER
      {
        eSpoof (1),
        eRoute (0)
      }
    MAX-ACCESS read-only
    STATUS     current
    DESCRIPTION
        "-- empty --"
    ::= { lcsSetupNetbios 8 }

-- {SCALAR} 310.2.16.9
lcsSetupNetbiosUpdate OBJECT-TYPE
    SYNTAX     INTEGER
      {
        ePback (0),
        eTrig (1),
        eTime (2)
      }
    MAX-ACCESS read-only
    STATUS     current
    DESCRIPTION
        "-- empty --"
    ::= { lcsSetupNetbios 9 }

-- {SCALAR} 310.2.16.10
lcsSetupNetbiosWanUpdateMinutes OBJECT-TYPE
    SYNTAX     INTEGER (0..65535)
    MAX-ACCESS read-only
    STATUS     current
    DESCRIPTION
        "-- empty --"
    ::= { lcsSetupNetbios 10 }

-- {SCALAR} 310.2.16.11
lcsSetupNetbiosLeasetime OBJECT-TYPE
    SYNTAX     INTEGER (0..65535)
    MAX-ACCESS read-only
    STATUS     current
    DESCRIPTION
        "-- empty --"
    ::= { lcsSetupNetbios 11 }

-- {OID} 310.2.11
lcsSetupConfig OBJECT IDENTIFIER ::= { lcsSetup 11 }

-- {SCALAR} 310.2.11.3
lcsSetupConfigPasswordRequiredForSnmpReadAccess OBJECT-TYPE
    SYNTAX     INTEGER
      {
        eNo (0),
        eYes (1)
      }
    MAX-ACCESS read-only
    STATUS     current
    DESCRIPTION
        "-- empty --"
    ::= { lcsSetupConfig 3 }

-- {SCALAR} 310.2.11.60
lcsSetupConfigCpuLoadInterval OBJECT-TYPE
    SYNTAX     INTEGER
      {
        eT1s (1),
        eT5s (5),
        eT60s (60),
        eT300s (300)
      }
    MAX-ACCESS read-write
    STATUS     current
    DESCRIPTION
        "-- empty --"
    ::= { lcsSetupConfig 60 }

-- {SCALAR} 310.2.11.4
lcsSetupConfigMaximumConnections OBJECT-TYPE
    SYNTAX     INTEGER (0..255)
    MAX-ACCESS read-write
    STATUS     current
    DESCRIPTION
        "-- empty --"
    ::= { lcsSetupConfig 4 }

-- {SCALAR} 310.2.11.5
lcsSetupConfigConfigAgingMinutes OBJECT-TYPE
    SYNTAX     INTEGER (0..255)
    MAX-ACCESS read-only
    STATUS     current
    DESCRIPTION
        "-- empty --"
    ::= { lcsSetupConfig 5 }

-- {SCALAR} 310.2.11.33
lcsSetupConfigOutbandAgingMinutes OBJECT-TYPE
    SYNTAX     INTEGER (0..255)
    MAX-ACCESS read-only
    STATUS     current
    DESCRIPTION
        "-- empty --"
    ::= { lcsSetupConfig 33 }

-- {SCALAR} 310.2.11.7
lcsSetupConfigLoginErrors OBJECT-TYPE
    SYNTAX     INTEGER (0..255)
    MAX-ACCESS read-only
    STATUS     current
    DESCRIPTION
        "-- empty --"
    ::= { lcsSetupConfig 7 }

-- {SCALAR} 310.2.11.8
lcsSetupConfigLockMinutes OBJECT-TYPE
    SYNTAX     INTEGER (0..255)
    MAX-ACCESS read-only
    STATUS     current
    DESCRIPTION
        "-- empty --"
    ::= { lcsSetupConfig 8 }

-- {SCALAR} 310.2.11.12
lcsSetupConfigWlanAuthenticationPagesOnly OBJECT-TYPE
    SYNTAX     INTEGER
      {
        eNo (0),
        eYes (1)
      }
    MAX-ACCESS read-only
    STATUS     current
    DESCRIPTION
        "-- empty --"
    ::= { lcsSetupConfig 12 }

-- {SCALAR} 310.2.11.6
lcsSetupConfigLanguage OBJECT-TYPE
    SYNTAX     INTEGER
      {
        eEnglish (1),
        eDeutsch (2)
      }
    MAX-ACCESS read-only
    STATUS     current
    DESCRIPTION
        "-- empty --"
    ::= { lcsSetupConfig 6 }

-- {TABLE} 310.2.11.15
lcsSetupConfigAccessTableTable OBJECT-TYPE
    SYNTAX     SEQUENCE OF LcsSetupConfigAccessTableEntry
    MAX-ACCESS not-accessible
    STATUS     current
    DESCRIPTION
        "-- empty --"
    ::= { lcsSetupConfig 15 }

-- {ENTRY} 310.2.11.15.1
lcsSetupConfigAccessTableEntry OBJECT-TYPE
    SYNTAX     LcsSetupConfigAccessTableEntry
    MAX-ACCESS not-accessible
    STATUS     current
    DESCRIPTION
        ""
    INDEX {
        lcsSetupConfigAccessTableEntryIfc
    }
    ::= { lcsSetupConfigAccessTableTable 1 }

-- {SEQUENCE}
LcsSetupConfigAccessTableEntry ::= SEQUENCE {
    lcsSetupConfigAccessTableEntryIfc INTEGER,
    lcsSetupConfigAccessTableEntryTelnet INTEGER,
    lcsSetupConfigAccessTableEntryTftp INTEGER,
    lcsSetupConfigAccessTableEntryHttp INTEGER,
    lcsSetupConfigAccessTableEntrySnmp INTEGER,
    lcsSetupConfigAccessTableEntryHttps INTEGER,
    lcsSetupConfigAccessTableEntryTelnetSsl INTEGER,
    lcsSetupConfigAccessTableEntrySsh INTEGER
}

-- {COLUMN} 310.2.11.15.1.1
lcsSetupConfigAccessTableEntryIfc OBJECT-TYPE
    SYNTAX     INTEGER
      {
        eLan (1),
        eWan (2),
        eWlan (3)
      }
    MAX-ACCESS read-only
    STATUS     current
    DESCRIPTION
        "-- empty --"
    ::= { lcsSetupConfigAccessTableEntry 1 }

-- {COLUMN} 310.2.11.15.1.2
lcsSetupConfigAccessTableEntryTelnet OBJECT-TYPE
    SYNTAX     INTEGER
      {
        eYes (1),
        eRead (4),
        eNo (0)
      }
    MAX-ACCESS read-write
    STATUS     current
    DESCRIPTION
        "-- empty --"
    ::= { lcsSetupConfigAccessTableEntry 2 }

-- {COLUMN} 310.2.11.15.1.3
lcsSetupConfigAccessTableEntryTftp OBJECT-TYPE
    SYNTAX     INTEGER
      {
        eYes (1),
        eRead (4),
        eNo (0)
      }
    MAX-ACCESS read-write
    STATUS     current
    DESCRIPTION
        "-- empty --"
    ::= { lcsSetupConfigAccessTableEntry 3 }

-- {COLUMN} 310.2.11.15.1.4
lcsSetupConfigAccessTableEntryHttp OBJECT-TYPE
    SYNTAX     INTEGER
      {
        eYes (1),
        eRead (4),
        eNo (0)
      }
    MAX-ACCESS read-write
    STATUS     current
    DESCRIPTION
        "-- empty --"
    ::= { lcsSetupConfigAccessTableEntry 4 }

-- {COLUMN} 310.2.11.15.1.5
lcsSetupConfigAccessTableEntrySnmp OBJECT-TYPE
    SYNTAX     INTEGER
      {
        eYes (1),
        eRead (4),
        eNo (0)
      }
    MAX-ACCESS read-write
    STATUS     current
    DESCRIPTION
        "-- empty --"
    ::= { lcsSetupConfigAccessTableEntry 5 }

-- {COLUMN} 310.2.11.15.1.6
lcsSetupConfigAccessTableEntryHttps OBJECT-TYPE
    SYNTAX     INTEGER
      {
        eYes (1),
        eRead (4),
        eNo (0)
      }
    MAX-ACCESS read-write
    STATUS     current
    DESCRIPTION
        "-- empty --"
    ::= { lcsSetupConfigAccessTableEntry 6 }

-- {COLUMN} 310.2.11.15.1.7
lcsSetupConfigAccessTableEntryTelnetSsl OBJECT-TYPE
    SYNTAX     INTEGER
      {
        eYes (1),
        eRead (4),
        eNo (0)
      }
    MAX-ACCESS read-write
    STATUS     current
    DESCRIPTION
        "-- empty --"
    ::= { lcsSetupConfigAccessTableEntry 7 }

-- {COLUMN} 310.2.11.15.1.8
lcsSetupConfigAccessTableEntrySsh OBJECT-TYPE
    SYNTAX     INTEGER
      {
        eYes (1),
        eRead (4),
        eNo (0)
      }
    MAX-ACCESS read-write
    STATUS     current
    DESCRIPTION
        "-- empty --"
    ::= { lcsSetupConfigAccessTableEntry 8 }

-- {SCALAR} 310.2.11.16
lcsSetupConfigScreenHeight OBJECT-TYPE
    SYNTAX     INTEGER (0..65535)
    MAX-ACCESS read-only
    STATUS     current
    DESCRIPTION
        "-- empty --"
    ::= { lcsSetupConfig 16 }

-- {TABLE} 310.2.11.43
lcsSetupConfigFunctionKeysTable OBJECT-TYPE
    SYNTAX     SEQUENCE OF LcsSetupConfigFunctionKeysEntry
    MAX-ACCESS not-accessible
    STATUS     current
    DESCRIPTION
        "-- empty --"
    ::= { lcsSetupConfig 43 }

-- {ENTRY} 310.2.11.43.1
lcsSetupConfigFunctionKeysEntry OBJECT-TYPE
    SYNTAX     LcsSetupConfigFunctionKeysEntry
    MAX-ACCESS not-accessible
    STATUS     current
    DESCRIPTION
        ""
    INDEX {
        lcsSetupConfigFunctionKeysEntryKey
    }
    ::= { lcsSetupConfigFunctionKeysTable 1 }

-- {SEQUENCE}
LcsSetupConfigFunctionKeysEntry ::= SEQUENCE {
    lcsSetupConfigFunctionKeysEntryKey INTEGER,
    lcsSetupConfigFunctionKeysEntryMapping DisplayString
}

-- {COLUMN} 310.2.11.43.1.1
lcsSetupConfigFunctionKeysEntryKey OBJECT-TYPE
    SYNTAX     INTEGER
      {
        eF1 (1),
        eF2 (2),
        eF3 (3),
        eF4 (4),
        eF5 (5),
        eF6 (6),
        eF7 (7),
        eF8 (8),
        eF9 (9),
        eF10 (10),
        eF11 (11),
        eF12 (12)
      }
    MAX-ACCESS read-write
    STATUS     current
    DESCRIPTION
        "-- empty --"
    ::= { lcsSetupConfigFunctionKeysEntry 1 }

-- {COLUMN} 310.2.11.43.1.2
lcsSetupConfigFunctionKeysEntryMapping OBJECT-TYPE
    SYNTAX     DisplayString (SIZE(0..99))
    MAX-ACCESS read-write
    STATUS     current
    DESCRIPTION
        "-- empty --"
    ::= { lcsSetupConfigFunctionKeysEntry 2 }

-- {OID} 310.2.11.50
lcsSetupConfigLl2m OBJECT IDENTIFIER ::= { lcsSetupConfig 50 }

-- {SCALAR} 310.2.11.50.1
lcsSetupConfigLl2mOperating OBJECT-TYPE
    SYNTAX     INTEGER
      {
        eNo (0),
        eYes (1)
      }
    MAX-ACCESS read-write
    STATUS     current
    DESCRIPTION
        "-- empty --"
    ::= { lcsSetupConfigLl2m 1 }

-- {SCALAR} 310.2.11.50.2
lcsSetupConfigLl2mTimeLimit OBJECT-TYPE
    SYNTAX     INTEGER (0..2147483647)
    MAX-ACCESS read-write
    STATUS     current
    DESCRIPTION
        "-- empty --"
    ::= { lcsSetupConfigLl2m 2 }

-- {SCALAR} 310.2.11.40
lcsSetupConfigCrashMessage OBJECT-TYPE
    SYNTAX     DisplayString (SIZE(0..32))
    MAX-ACCESS read-only
    STATUS     current
    DESCRIPTION
        "-- empty --"
    ::= { lcsSetupConfig 40 }

-- {SCALAR} 310.2.11.41
lcsSetupConfigAdminGender OBJECT-TYPE
    SYNTAX     INTEGER
      {
        eUnknown (0),
        eMale (1),
        eFemale (2),
        eGeek (3)
      }
    MAX-ACCESS read-only
    STATUS     current
    DESCRIPTION
        "-- empty --"
    ::= { lcsSetupConfig 41 }

-- {SCALAR} 310.2.11.42
lcsSetupConfigAssertAction OBJECT-TYPE
    SYNTAX     INTEGER
      {
        eLogOnly (0),
        eReboot (1)
      }
    MAX-ACCESS read-only
    STATUS     current
    DESCRIPTION
        "-- empty --"
    ::= { lcsSetupConfig 42 }

-- {SCALAR} 310.2.11.17
lcsSetupConfigPrompt OBJECT-TYPE
    SYNTAX     DisplayString (SIZE(0..31))
    MAX-ACCESS read-only
    STATUS     current
    DESCRIPTION
        "-- empty --"
    ::= { lcsSetupConfig 17 }

-- {SCALAR} 310.2.11.18
lcsSetupConfigLedTest OBJECT-TYPE
    SYNTAX     INTEGER
      {
        eOff (0),
        eGreen (2),
        eRed (1),
        eOrange (3),
        eNoTest (255)
      }
    MAX-ACCESS read-only
    STATUS     current
    DESCRIPTION
        "-- empty --"
    ::= { lcsSetupConfig 18 }

-- {TABLE} 310.2.11.20
lcsSetupConfigCronTableTable OBJECT-TYPE
    SYNTAX     SEQUENCE OF LcsSetupConfigCronTableEntry
    MAX-ACCESS not-accessible
    STATUS     current
    DESCRIPTION
        "-- empty --"
    ::= { lcsSetupConfig 20 }

-- {ENTRY} 310.2.11.20.1
lcsSetupConfigCronTableEntry OBJECT-TYPE
    SYNTAX     LcsSetupConfigCronTableEntry
    MAX-ACCESS not-accessible
    STATUS     current
    DESCRIPTION
        ""
    INDEX {
        lcsSetupConfigCronTableEntryIndex
    }
    ::= { lcsSetupConfigCronTableTable 1 }

-- {SEQUENCE}
LcsSetupConfigCronTableEntry ::= SEQUENCE {
    lcsSetupConfigCronTableEntryIndex INTEGER,
    lcsSetupConfigCronTableEntryActive INTEGER,
    lcsSetupConfigCronTableEntryBase INTEGER,
    lcsSetupConfigCronTableEntryVariation INTEGER,
    lcsSetupConfigCronTableEntryMinute DisplayString,
    lcsSetupConfigCronTableEntryHour DisplayString,
    lcsSetupConfigCronTableEntryDayofweek DisplayString,
    lcsSetupConfigCronTableEntryDay DisplayString,
    lcsSetupConfigCronTableEntryMonth DisplayString,
    lcsSetupConfigCronTableEntryCommand DisplayString,
    lcsSetupConfigCronTableEntryOwner DisplayString
}

-- {COLUMN} 310.2.11.20.1.1
lcsSetupConfigCronTableEntryIndex OBJECT-TYPE
    SYNTAX     INTEGER (0..65535)
    MAX-ACCESS read-write
    STATUS     current
    DESCRIPTION
        "-- empty --"
    ::= { lcsSetupConfigCronTableEntry 1 }

-- {COLUMN} 310.2.11.20.1.9
lcsSetupConfigCronTableEntryActive OBJECT-TYPE
    SYNTAX     INTEGER
      {
        eYes (0),
        eNo (1)
      }
    MAX-ACCESS read-write
    STATUS     current
    DESCRIPTION
        "-- empty --"
    ::= { lcsSetupConfigCronTableEntry 9 }

-- {COLUMN} 310.2.11.20.1.8
lcsSetupConfigCronTableEntryBase OBJECT-TYPE
    SYNTAX     INTEGER
      {
        eRealTime (0),
        eOperationTime (1)
      }
    MAX-ACCESS read-write
    STATUS     current
    DESCRIPTION
        "-- empty --"
    ::= { lcsSetupConfigCronTableEntry 8 }

-- {COLUMN} 310.2.11.20.1.11
lcsSetupConfigCronTableEntryVariation OBJECT-TYPE
    SYNTAX     INTEGER (0..65535)
    MAX-ACCESS read-write
    STATUS     current
    DESCRIPTION
        "-- empty --"
    ::= { lcsSetupConfigCronTableEntry 11 }

-- {COLUMN} 310.2.11.20.1.2
lcsSetupConfigCronTableEntryMinute OBJECT-TYPE
    SYNTAX     DisplayString (SIZE(0..50))
    MAX-ACCESS read-write
    STATUS     current
    DESCRIPTION
        "-- empty --"
    ::= { lcsSetupConfigCronTableEntry 2 }

-- {COLUMN} 310.2.11.20.1.3
lcsSetupConfigCronTableEntryHour OBJECT-TYPE
    SYNTAX     DisplayString (SIZE(0..50))
    MAX-ACCESS read-write
    STATUS     current
    DESCRIPTION
        "-- empty --"
    ::= { lcsSetupConfigCronTableEntry 3 }

-- {COLUMN} 310.2.11.20.1.4
lcsSetupConfigCronTableEntryDayofweek OBJECT-TYPE
    SYNTAX     DisplayString (SIZE(0..50))
    MAX-ACCESS read-write
    STATUS     current
    DESCRIPTION
        "-- empty --"
    ::= { lcsSetupConfigCronTableEntry 4 }

-- {COLUMN} 310.2.11.20.1.5
lcsSetupConfigCronTableEntryDay OBJECT-TYPE
    SYNTAX     DisplayString (SIZE(0..50))
    MAX-ACCESS read-write
    STATUS     current
    DESCRIPTION
        "-- empty --"
    ::= { lcsSetupConfigCronTableEntry 5 }

-- {COLUMN} 310.2.11.20.1.6
lcsSetupConfigCronTableEntryMonth OBJECT-TYPE
    SYNTAX     DisplayString (SIZE(0..50))
    MAX-ACCESS read-write
    STATUS     current
    DESCRIPTION
        "-- empty --"
    ::= { lcsSetupConfigCronTableEntry 6 }

-- {COLUMN} 310.2.11.20.1.7
lcsSetupConfigCronTableEntryCommand OBJECT-TYPE
    SYNTAX     DisplayString (SIZE(0..252))
    MAX-ACCESS read-write
    STATUS     current
    DESCRIPTION
        "-- empty --"
    ::= { lcsSetupConfigCronTableEntry 7 }

-- {COLUMN} 310.2.11.20.1.10
lcsSetupConfigCronTableEntryOwner OBJECT-TYPE
    SYNTAX     DisplayString (SIZE(0..16))
    MAX-ACCESS read-write
    STATUS     current
    DESCRIPTION
        "-- empty --"
    ::= { lcsSetupConfigCronTableEntry 10 }

-- {TABLE} 310.2.11.21
lcsSetupConfigAdminsTable OBJECT-TYPE
    SYNTAX     SEQUENCE OF LcsSetupConfigAdminsEntry
    MAX-ACCESS not-accessible
    STATUS     current
    DESCRIPTION
        "-- empty --"
    ::= { lcsSetupConfig 21 }

-- {ENTRY} 310.2.11.21.1
lcsSetupConfigAdminsEntry OBJECT-TYPE
    SYNTAX     LcsSetupConfigAdminsEntry
    MAX-ACCESS not-accessible
    STATUS     current
    DESCRIPTION
        ""
    INDEX {
        lcsSetupConfigAdminsEntryAdministrator
    }
    ::= { lcsSetupConfigAdminsTable 1 }

-- {SEQUENCE}
LcsSetupConfigAdminsEntry ::= SEQUENCE {
    lcsSetupConfigAdminsEntryAdministrator DisplayString,
    lcsSetupConfigAdminsEntryPassword DisplayString,
    lcsSetupConfigAdminsEntryActive INTEGER,
    lcsSetupConfigAdminsEntryAccessRights INTEGER,
    lcsSetupConfigAdminsEntryFunctionRights BITS
}

-- {COLUMN} 310.2.11.21.1.1
lcsSetupConfigAdminsEntryAdministrator OBJECT-TYPE
    SYNTAX     DisplayString (SIZE(0..16))
    MAX-ACCESS read-write
    STATUS     current
    DESCRIPTION
        "-- empty --"
    ::= { lcsSetupConfigAdminsEntry 1 }

-- {COLUMN} 310.2.11.21.1.2
lcsSetupConfigAdminsEntryPassword OBJECT-TYPE
    SYNTAX     DisplayString (SIZE(0..16))
    MAX-ACCESS read-write
    STATUS     current
    DESCRIPTION
        "-- empty --"
    ::= { lcsSetupConfigAdminsEntry 2 }

-- {COLUMN} 310.2.11.21.1.4
lcsSetupConfigAdminsEntryActive OBJECT-TYPE
    SYNTAX     INTEGER
      {
        eNo (1),
        eYes (0)
      }
    MAX-ACCESS read-write
    STATUS     current
    DESCRIPTION
        "-- empty --"
    ::= { lcsSetupConfigAdminsEntry 4 }

-- {COLUMN} 310.2.11.21.1.5
lcsSetupConfigAdminsEntryAccessRights OBJECT-TYPE
    SYNTAX     INTEGER
      {
        eNone (0),
        eAdminRoLimit (8388608),
        eAdminRwLimit (8388864),
        eAdminRo (16777216),
        eAdminRw (16777472),
        eSupervisor (-1)
      }
    MAX-ACCESS read-write
    STATUS     current
    DESCRIPTION
        "-- empty --"
    ::= { lcsSetupConfigAdminsEntry 5 }

-- {COLUMN} 310.2.11.21.1.3
lcsSetupConfigAdminsEntryFunctionRights OBJECT-TYPE
    SYNTAX     BITS
      {
        eBasicWizard (31),
        eSecurityWizard (30),
        eInternetWizard (29),
        eRasWizard (27),
        eProviderSelection (28),
        eLanlanWizard (26),
        eTimeSetting (25),
        eDeviceSearch (24),
        eWlanLinktest (23),
        eRolloutWizard (18),
        ePublicSpotWizard (20),
        eWlanWizard (19),
        eDynamicDnsWizard (17),
        eSshCommand (14),
        ePublicSpotXmlInterface (12),
        ePublicSpotUserManagementWizard (11),
        ePublicSpotConfigurationWizard (10)
      }
    MAX-ACCESS read-write
    STATUS     current
    DESCRIPTION
        "-- empty --"
    ::= { lcsSetupConfigAdminsEntry 3 }

-- {TABLE} 310.2.11.27
lcsSetupConfigPredefAdminsTable OBJECT-TYPE
    SYNTAX     SEQUENCE OF LcsSetupConfigPredefAdminsEntry
    MAX-ACCESS not-accessible
    STATUS     current
    DESCRIPTION
        "-- empty --"
    ::= { lcsSetupConfig 27 }

-- {ENTRY} 310.2.11.27.1
lcsSetupConfigPredefAdminsEntry OBJECT-TYPE
    SYNTAX     LcsSetupConfigPredefAdminsEntry
    MAX-ACCESS not-accessible
    STATUS     current
    DESCRIPTION
        ""
    INDEX {
        lcsSetupConfigPredefAdminsEntryName
    }
    ::= { lcsSetupConfigPredefAdminsTable 1 }

-- {SEQUENCE}
LcsSetupConfigPredefAdminsEntry ::= SEQUENCE {
    lcsSetupConfigPredefAdminsEntryName DisplayString
}

-- {COLUMN} 310.2.11.27.1.1
lcsSetupConfigPredefAdminsEntryName OBJECT-TYPE
    SYNTAX     DisplayString (SIZE(0..15))
    MAX-ACCESS read-only
    STATUS     current
    DESCRIPTION
        "-- empty --"
    ::= { lcsSetupConfigPredefAdminsEntry 1 }

-- {SCALAR} 310.2.11.45
lcsSetupConfigConfigDateNew OBJECT-TYPE
    SYNTAX     Counter32
    MAX-ACCESS read-only
    STATUS     current
    DESCRIPTION
        ""
    ::= { lcsSetupConfig 45 }

-- {SCALAR} 310.2.11.1
lcsSetupConfigLan OBJECT-TYPE
    SYNTAX     INTEGER (0..255)
    MAX-ACCESS read-only
    STATUS     current
    DESCRIPTION
        "-- empty --"
    ::= { lcsSetupConfig 1 }

-- {SCALAR} 310.2.11.11
lcsSetupConfigWlanConfig OBJECT-TYPE
    SYNTAX     INTEGER (0..255)
    MAX-ACCESS read-only
    STATUS     current
    DESCRIPTION
        "-- empty --"
    ::= { lcsSetupConfig 11 }

-- {SCALAR} 310.2.11.2
lcsSetupConfigWan OBJECT-TYPE
    SYNTAX     INTEGER (0..255)
    MAX-ACCESS read-only
    STATUS     current
    DESCRIPTION
        "-- empty --"
    ::= { lcsSetupConfig 2 }

-- {SCALAR} 310.2.11.23
lcsSetupConfigTelnetPort OBJECT-TYPE
    SYNTAX     INTEGER (0..65535)
    MAX-ACCESS read-write
    STATUS     current
    DESCRIPTION
        "-- empty --"
    ::= { lcsSetupConfig 23 }

-- {SCALAR} 310.2.11.24
lcsSetupConfigTelnetSslPort OBJECT-TYPE
    SYNTAX     INTEGER (0..65535)
    MAX-ACCESS read-write
    STATUS     current
    DESCRIPTION
        "-- empty --"
    ::= { lcsSetupConfig 24 }

-- {SCALAR} 310.2.11.32
lcsSetupConfigResetButton OBJECT-TYPE
    SYNTAX     INTEGER
      {
        eIgnore (0),
        eBootOnly (1),
        eResetOrBoot (2)
      }
    MAX-ACCESS read-only
    STATUS     current
    DESCRIPTION
        "-- empty --"
    ::= { lcsSetupConfig 32 }

-- {OID} 310.2.11.35
lcsSetupConfigMonitortrace OBJECT IDENTIFIER ::= { lcsSetupConfig 35 }

-- {SCALAR} 310.2.11.35.1
lcsSetupConfigMonitortraceTracemask1 OBJECT-TYPE
    SYNTAX     INTEGER (0..2147483647)
    MAX-ACCESS read-only
    STATUS     current
    DESCRIPTION
        "-- empty --"
    ::= { lcsSetupConfigMonitortrace 1 }

-- {SCALAR} 310.2.11.35.2
lcsSetupConfigMonitortraceTracemask2 OBJECT-TYPE
    SYNTAX     INTEGER (0..2147483647)
    MAX-ACCESS read-only
    STATUS     current
    DESCRIPTION
        "-- empty --"
    ::= { lcsSetupConfigMonitortrace 2 }

-- {SCALAR} 310.2.11.39
lcsSetupConfigLicenseExpiryEmail OBJECT-TYPE
    SYNTAX     DisplayString (SIZE(0..63))
    MAX-ACCESS read-only
    STATUS     current
    DESCRIPTION
        "-- empty --"
    ::= { lcsSetupConfig 39 }

-- {OID} 310.2.11.13
lcsSetupConfigTftpClient OBJECT IDENTIFIER ::= { lcsSetupConfig 13 }

-- {SCALAR} 310.2.11.13.1
lcsSetupConfigTftpClientConfigAddress OBJECT-TYPE
    SYNTAX     DisplayString (SIZE(0..31))
    MAX-ACCESS read-only
    STATUS     current
    DESCRIPTION
        "-- empty --"
    ::= { lcsSetupConfigTftpClient 1 }

-- {SCALAR} 310.2.11.13.2
lcsSetupConfigTftpClientConfigFilename OBJECT-TYPE
    SYNTAX     DisplayString (SIZE(0..63))
    MAX-ACCESS read-only
    STATUS     current
    DESCRIPTION
        "-- empty --"
    ::= { lcsSetupConfigTftpClient 2 }

-- {SCALAR} 310.2.11.13.3
lcsSetupConfigTftpClientFirmwareAddress OBJECT-TYPE
    SYNTAX     DisplayString (SIZE(0..31))
    MAX-ACCESS read-only
    STATUS     current
    DESCRIPTION
        "-- empty --"
    ::= { lcsSetupConfigTftpClient 3 }

-- {SCALAR} 310.2.11.13.4
lcsSetupConfigTftpClientFirmwareFilename OBJECT-TYPE
    SYNTAX     DisplayString (SIZE(0..63))
    MAX-ACCESS read-only
    STATUS     current
    DESCRIPTION
        "-- empty --"
    ::= { lcsSetupConfigTftpClient 4 }

-- {SCALAR} 310.2.11.13.6
lcsSetupConfigTftpClientScriptAddress OBJECT-TYPE
    SYNTAX     DisplayString (SIZE(0..31))
    MAX-ACCESS read-only
    STATUS     current
    DESCRIPTION
        "-- empty --"
    ::= { lcsSetupConfigTftpClient 6 }

-- {SCALAR} 310.2.11.13.7
lcsSetupConfigTftpClientScriptFilename OBJECT-TYPE
    SYNTAX     DisplayString (SIZE(0..63))
    MAX-ACCESS read-only
    STATUS     current
    DESCRIPTION
        "-- empty --"
    ::= { lcsSetupConfigTftpClient 7 }

-- {SCALAR} 310.2.11.13.5
lcsSetupConfigTftpClientBytesPerHashmark OBJECT-TYPE
    SYNTAX     INTEGER (0..2147483647)
    MAX-ACCESS read-only
    STATUS     current
    DESCRIPTION
        "-- empty --"
    ::= { lcsSetupConfigTftpClient 5 }

-- {SCALAR} 310.2.11.25
lcsSetupConfigSshPort OBJECT-TYPE
    SYNTAX     INTEGER (0..65535)
    MAX-ACCESS read-write
    STATUS     current
    DESCRIPTION
        "-- empty --"
    ::= { lcsSetupConfig 25 }

-- {TABLE} 310.2.11.26
lcsSetupConfigSshAuthenticationMethodsTable OBJECT-TYPE
    SYNTAX     SEQUENCE OF LcsSetupConfigSshAuthenticationMethodsEntry
    MAX-ACCESS not-accessible
    STATUS     current
    DESCRIPTION
        "-- empty --"
    ::= { lcsSetupConfig 26 }

-- {ENTRY} 310.2.11.26.1
lcsSetupConfigSshAuthenticationMethodsEntry OBJECT-TYPE
    SYNTAX     LcsSetupConfigSshAuthenticationMethodsEntry
    MAX-ACCESS not-accessible
    STATUS     current
    DESCRIPTION
        ""
    INDEX {
        lcsSetupConfigSshAuthenticationMethodsEntryIfc
    }
    ::= { lcsSetupConfigSshAuthenticationMethodsTable 1 }

-- {SEQUENCE}
LcsSetupConfigSshAuthenticationMethodsEntry ::= SEQUENCE {
    lcsSetupConfigSshAuthenticationMethodsEntryIfc INTEGER,
    lcsSetupConfigSshAuthenticationMethodsEntryMethods INTEGER
}

-- {COLUMN} 310.2.11.26.1.1
lcsSetupConfigSshAuthenticationMethodsEntryIfc OBJECT-TYPE
    SYNTAX     INTEGER
      {
        eLan (1),
        eWan (2),
        eWlan (3)
      }
    MAX-ACCESS read-only
    STATUS     current
    DESCRIPTION
        "-- empty --"
    ::= { lcsSetupConfigSshAuthenticationMethodsEntry 1 }

-- {COLUMN} 310.2.11.26.1.2
lcsSetupConfigSshAuthenticationMethodsEntryMethods OBJECT-TYPE
    SYNTAX     INTEGER
      {
        ePublicKey (1),
        eKeyboardInteractive (4),
        ePassword (2),
        ePasswordPlusKeyboardInteractive (6),
        ePasswordPlusPublicKey (3),
        eKeyboardInteractivePlusPublicKey (5),
        eAll (255)
      }
    MAX-ACCESS read-write
    STATUS     current
    DESCRIPTION
        "-- empty --"
    ::= { lcsSetupConfigSshAuthenticationMethodsEntry 2 }

-- {OID} 310.2.11.28
lcsSetupConfigSsh OBJECT IDENTIFIER ::= { lcsSetupConfig 28 }

-- {SCALAR} 310.2.11.28.1
lcsSetupConfigSshCipherAlgorithms OBJECT-TYPE
    SYNTAX     BITS
      {
        e3desCbc (31),
        e3desCtr (30),
        eArcfour (29),
        eArcfour128 (28),
        eArcfour256 (27),
        eBlowfishCbc (26),
        eBlowfishCtr (25),
        eAes128Cbc (24),
        eAes192Cbc (23),
        eAes256Cbc (22),
        eAes128Ctr (21),
        eAes192Ctr (20),
        eAes256Ctr (19)
      }
    MAX-ACCESS read-write
    STATUS     current
    DESCRIPTION
        "-- empty --"
    ::= { lcsSetupConfigSsh 1 }

-- {SCALAR} 310.2.11.28.2
lcsSetupConfigSshMacAlgorithms OBJECT-TYPE
    SYNTAX     BITS
      {
        eHmacMd596 (31),
        eHmacMd5 (30),
        eHmacSha196 (29),
        eHmacSha1 (28),
        eHmacSha225696 (27),
        eHmacSha2256 (26),
        eHmacSha251296 (25),
        eHmacSha2512 (24)
      }
    MAX-ACCESS read-write
    STATUS     current
    DESCRIPTION
        "-- empty --"
    ::= { lcsSetupConfigSsh 2 }

-- {SCALAR} 310.2.11.28.3
lcsSetupConfigSshKeyExchangeAlgorithms OBJECT-TYPE
    SYNTAX     BITS
      {
        eDiffieHellmanGroup1Sha1 (31),
        eDiffieHellmanGroup14Sha1 (30),
        eDiffieHellmanGroupExchangeSha1 (29),
        eDiffieHellmanGroupExchangeSha256 (28)
      }
    MAX-ACCESS read-write
    STATUS     current
    DESCRIPTION
        "-- empty --"
    ::= { lcsSetupConfigSsh 3 }

-- {SCALAR} 310.2.11.28.7
lcsSetupConfigSshDhGroups OBJECT-TYPE
    SYNTAX     BITS
      {
        eGroup1 (31),
        eGroup5 (30),
        eGroup14 (29),
        eGroup15 (28),
        eGroup16 (27)
      }
    MAX-ACCESS read-write
    STATUS     current
    DESCRIPTION
        "-- empty --"
    ::= { lcsSetupConfigSsh 7 }

-- {SCALAR} 310.2.11.28.4
lcsSetupConfigSshHostkeyAlgorithms OBJECT-TYPE
    SYNTAX     BITS
      {
        eSshRsa (31),
        eSshDss (30)
      }
    MAX-ACCESS read-write
    STATUS     current
    DESCRIPTION
        "-- empty --"
    ::= { lcsSetupConfigSsh 4 }

-- {SCALAR} 310.2.11.28.5
lcsSetupConfigSshMinHostkeyLength OBJECT-TYPE
    SYNTAX     INTEGER (0..65535)
    MAX-ACCESS read-write
    STATUS     current
    DESCRIPTION
        "-- empty --"
    ::= { lcsSetupConfigSsh 5 }

-- {SCALAR} 310.2.11.28.6
lcsSetupConfigSshMaxHostkeyLength OBJECT-TYPE
    SYNTAX     INTEGER (0..65535)
    MAX-ACCESS read-write
    STATUS     current
    DESCRIPTION
        "-- empty --"
    ::= { lcsSetupConfigSsh 6 }

-- {SCALAR} 310.2.11.28.8
lcsSetupConfigSshCompression OBJECT-TYPE
    SYNTAX     INTEGER
      {
        eNo (0),
        eYes (1)
      }
    MAX-ACCESS read-write
    STATUS     current
    DESCRIPTION
        "-- empty --"
    ::= { lcsSetupConfigSsh 8 }

-- {OID} 310.2.11.28.10
lcsSetupConfigSshSftpServer OBJECT IDENTIFIER ::= { lcsSetupConfigSsh 10 }

-- {SCALAR} 310.2.11.28.10.1
lcsSetupConfigSshSftpServerOperating OBJECT-TYPE
    SYNTAX     INTEGER
      {
        eNo (0),
        eYes (1)
      }
    MAX-ACCESS read-write
    STATUS     current
    DESCRIPTION
        "-- empty --"
    ::= { lcsSetupConfigSshSftpServer 1 }

-- {OID} 310.2.12
lcsSetupWlan OBJECT IDENTIFIER ::= { lcsSetup 12 }

-- {SCALAR} 310.2.12.3
lcsSetupWlanSpareHeap OBJECT-TYPE
    SYNTAX     INTEGER (0..65535)
    MAX-ACCESS read-write
    STATUS     current
    DESCRIPTION
        "-- empty --"
    ::= { lcsSetupWlan 3 }

-- {SCALAR} 310.2.12.12
lcsSetupWlanIappProtocol OBJECT-TYPE
    SYNTAX     INTEGER
      {
        eNo (0),
        eYes (1)
      }
    MAX-ACCESS read-write
    STATUS     current
    DESCRIPTION
        "-- empty --"
    ::= { lcsSetupWlan 12 }

-- {SCALAR} 310.2.12.13
lcsSetupWlanIappAnnounceInterval OBJECT-TYPE
    SYNTAX     INTEGER (0..65535)
    MAX-ACCESS read-write
    STATUS     current
    DESCRIPTION
        "-- empty --"
    ::= { lcsSetupWlan 13 }

-- {SCALAR} 310.2.12.14
lcsSetupWlanIappHandoverTimeout OBJECT-TYPE
    SYNTAX     INTEGER (0..65535)
    MAX-ACCESS read-write
    STATUS     current
    DESCRIPTION
        "-- empty --"
    ::= { lcsSetupWlan 14 }

-- {SCALAR} 310.2.12.60
lcsSetupWlanIappIpNetwork OBJECT-TYPE
    SYNTAX     DisplayString (SIZE(0..16))
    MAX-ACCESS read-write
    STATUS     current
    DESCRIPTION
        "-- empty --"
    ::= { lcsSetupWlan 60 }

-- {SCALAR} 310.2.12.36
lcsSetupWlanCountry OBJECT-TYPE
    SYNTAX     INTEGER
      {
        eUnknown (0),
        eAlbania (8),
        eAlgeria (12),
        eArgentina (32),
        eAustralia (36),
        eAustria (40),
        eBahrain (48),
        eBangladesh (50),
        eBelarus (112),
        eBelgium (56),
        eBosniaHerzegovina (70),
        eBrazil (76),
        eBruneiDarussalam (96),
        eBulgaria (100),
        eCanada (124),
        eChile (152),
        eChina (156),
        eColombia (170),
        eCostaRica (188),
        eCroatia (191),
        eCyprus (196),
        eCzech (203),
        eDenmark (208),
        eEcuador (218),
        eEgalistan (999),
        eEgypt (818),
        eEstonia (233),
        eEurope (998),
        eFinland (246),
        eFrance (250),
        eGermany (276),
        eGhana (288),
        eGreece (300),
        eGuatemala (320),
        eHonduras (340),
        eHongKong (344),
        eHungary (348),
        eIceland (352),
        eIndia (356),
        eIndonesia (360),
        eIreland (372),
        eIsrael (376),
        eItaly (380),
        eJapan (392),
        eJordan (400),
        eSouthKorea (410),
        eKuwait (414),
        eLatvia (428),
        eLebanon (422),
        eLiechtenstein (438),
        eLithuania (440),
        eLuxembourg (442),
        eMacau (446),
        eMacedonia (807),
        eMalaysia (458),
        eMalta (470),
        eMexico (484),
        eMoldavia (498),
        eMorocco (504),
        eNetherlands (528),
        eNewZealand (554),
        eNicaragua (558),
        eNorway (578),
        eOman (512),
        ePakistan (586),
        ePanama (591),
        eParaguay (600),
        ePeru (604),
        ePhilippines (608),
        ePoland (616),
        ePortugal (620),
        ePuertoRico (630),
        eQatar (634),
        eRomania (642),
        eRussia (643),
        eSaudiArabia (682),
        eSingapore (702),
        eSlovak (703),
        eSlovenia (705),
        eSouthAfrica (710),
        eSpain (724),
        eSweden (752),
        eSwitzerland (756),
        eTaiwan (158),
        eTanzania (834),
        eThailand (764),
        eTunisia (788),
        eTurkey (792),
        eUganda (800),
        eUkraine (804),
        eUnitedArabEmirates (784),
        eUnitedKingdom (826),
        eUnitedStatesFcc (840),
        eUruguay (858),
        eVenezuela (862)
      }
    MAX-ACCESS read-write
    STATUS     current
    DESCRIPTION
        "-- empty --"
    ::= { lcsSetupWlan 36 }

-- {SCALAR} 310.2.12.46
lcsSetupWlanIndoorOnlyOperation OBJECT-TYPE
    SYNTAX     INTEGER
      {
        eNo (0),
        eYes (1)
      }
    MAX-ACCESS read-write
    STATUS     current
    DESCRIPTION
        "-- empty --"
    ::= { lcsSetupWlan 46 }

-- {SCALAR} 310.2.12.48
lcsSetupWlanUseFullChannelset OBJECT-TYPE
    SYNTAX     INTEGER
      {
        eNo (0),
        eYes (1)
      }
    MAX-ACCESS read-write
    STATUS     current
    DESCRIPTION
        "-- empty --"
    ::= { lcsSetupWlan 48 }

-- {SCALAR} 310.2.12.41
lcsSetupWlanMailAddress OBJECT-TYPE
    SYNTAX     DisplayString (SIZE(0..254))
    MAX-ACCESS read-write
    STATUS     current
    DESCRIPTION
        "-- empty --"
    ::= { lcsSetupWlan 41 }

-- {SCALAR} 310.2.12.100
lcsSetupWlanCardReinitCycle OBJECT-TYPE
    SYNTAX     INTEGER (0..2147483647)
    MAX-ACCESS read-write
    STATUS     current
    DESCRIPTION
        "-- empty --"
    ::= { lcsSetupWlan 100 }

-- {SCALAR} 310.2.12.101
lcsSetupWlanNoiseCalibrationCycle OBJECT-TYPE
    SYNTAX     INTEGER (0..2147483647)
    MAX-ACCESS read-write
    STATUS     current
    DESCRIPTION
        "-- empty --"
    ::= { lcsSetupWlan 101 }

-- {TABLE} 310.2.12.109
lcsSetupWlanNoiseOffsetsTable OBJECT-TYPE
    SYNTAX     SEQUENCE OF LcsSetupWlanNoiseOffsetsEntry
    MAX-ACCESS not-accessible
    STATUS     current
    DESCRIPTION
        "-- empty --"
    ::= { lcsSetupWlan 109 }

-- {ENTRY} 310.2.12.109.1
lcsSetupWlanNoiseOffsetsEntry OBJECT-TYPE
    SYNTAX     LcsSetupWlanNoiseOffsetsEntry
    MAX-ACCESS not-accessible
    STATUS     current
    DESCRIPTION
        ""
    INDEX {
        lcsSetupWlanNoiseOffsetsEntryBand,
        lcsSetupWlanNoiseOffsetsEntryChannel,
        lcsSetupWlanNoiseOffsetsEntryInterface
    }
    ::= { lcsSetupWlanNoiseOffsetsTable 1 }

-- {SEQUENCE}
LcsSetupWlanNoiseOffsetsEntry ::= SEQUENCE {
    lcsSetupWlanNoiseOffsetsEntryBand INTEGER,
    lcsSetupWlanNoiseOffsetsEntryChannel INTEGER,
    lcsSetupWlanNoiseOffsetsEntryInterface INTEGER,
    lcsSetupWlanNoiseOffsetsEntryValue INTEGER
}

-- {COLUMN} 310.2.12.109.1.1
lcsSetupWlanNoiseOffsetsEntryBand OBJECT-TYPE
    SYNTAX     INTEGER
      {
        e24ghz (1),
        e5ghz (2)
      }
    MAX-ACCESS read-write
    STATUS     current
    DESCRIPTION
        "-- empty --"
    ::= { lcsSetupWlanNoiseOffsetsEntry 1 }

-- {COLUMN} 310.2.12.109.1.2
lcsSetupWlanNoiseOffsetsEntryChannel OBJECT-TYPE
    SYNTAX     INTEGER (0..65535)
    MAX-ACCESS read-write
    STATUS     current
    DESCRIPTION
        "-- empty --"
    ::= { lcsSetupWlanNoiseOffsetsEntry 2 }

-- {COLUMN} 310.2.12.109.1.3
lcsSetupWlanNoiseOffsetsEntryInterface OBJECT-TYPE
    SYNTAX     INTEGER
      {
        eWlan1 (1)
      }
    MAX-ACCESS read-write
    STATUS     current
    DESCRIPTION
        "-- empty --"
    ::= { lcsSetupWlanNoiseOffsetsEntry 3 }

-- {COLUMN} 310.2.12.109.1.4
lcsSetupWlanNoiseOffsetsEntryValue OBJECT-TYPE
    SYNTAX     INTEGER (-128..127)
    MAX-ACCESS read-write
    STATUS     current
    DESCRIPTION
        "-- empty --"
    ::= { lcsSetupWlanNoiseOffsetsEntry 4 }

-- {SCALAR} 310.2.12.105
lcsSetupWlanThermRecalCycle OBJECT-TYPE
    SYNTAX     INTEGER (0..2147483647)
    MAX-ACCESS read-write
    STATUS     current
    DESCRIPTION
        "-- empty --"
    ::= { lcsSetupWlan 105 }

-- {SCALAR} 310.2.12.103
lcsSetupWlanTraceMac OBJECT-TYPE
    SYNTAX     MacAddress
    MAX-ACCESS read-write
    STATUS     current
    DESCRIPTION
        "-- empty --"
    ::= { lcsSetupWlan 103 }

-- {SCALAR} 310.2.12.110
lcsSetupWlanTraceLevel OBJECT-TYPE
    SYNTAX     INTEGER (0..255)
    MAX-ACCESS read-write
    STATUS     current
    DESCRIPTION
        "-- empty --"
    ::= { lcsSetupWlan 110 }

-- {SCALAR} 310.2.12.116
lcsSetupWlanTracePackets OBJECT-TYPE
    SYNTAX     BITS
      {
        eManagement (7),
        eControl (6),
        eData (5),
        eEapol (4),
        eAll (0)
      }
    MAX-ACCESS read-write
    STATUS     current
    DESCRIPTION
        "-- empty --"
    ::= { lcsSetupWlan 116 }

-- {SCALAR} 310.2.12.119
lcsSetupWlanTraceBeacons OBJECT-TYPE
    SYNTAX     INTEGER
      {
        eNo (0),
        eYes (1)
      }
    MAX-ACCESS read-write
    STATUS     current
    DESCRIPTION
        "-- empty --"
    ::= { lcsSetupWlan 119 }

-- {SCALAR} 310.2.12.115
lcsSetupWlanOmitGlobalCryptoSequenceCheck OBJECT-TYPE
    SYNTAX     INTEGER
      {
        eAuto (0),
        eNo (1),
        eYes (2)
      }
    MAX-ACCESS read-write
    STATUS     current
    DESCRIPTION
        "-- empty --"
    ::= { lcsSetupWlan 115 }

-- {SCALAR} 310.2.12.117
lcsSetupWlanWpaHandshakeDelayMs OBJECT-TYPE
    SYNTAX     INTEGER (0..2147483647)
    MAX-ACCESS read-write
    STATUS     current
    DESCRIPTION
        "-- empty --"
    ::= { lcsSetupWlan 117 }

-- {SCALAR} 310.2.12.118
lcsSetupWlanWpaHandshakeTimeoutOverrideMs OBJECT-TYPE
    SYNTAX     INTEGER (0..2147483647)
    MAX-ACCESS read-write
    STATUS     current
    DESCRIPTION
        "-- empty --"
    ::= { lcsSetupWlan 118 }

-- {OID} 310.2.12.111
lcsSetupWlanNoiseImmunity OBJECT IDENTIFIER ::= { lcsSetupWlan 111 }

-- {SCALAR} 310.2.12.111.1
lcsSetupWlanNoiseImmunityNoiseImmunityLevel OBJECT-TYPE
    SYNTAX     INTEGER (0..255)
    MAX-ACCESS read-write
    STATUS     current
    DESCRIPTION
        "-- empty --"
    ::= { lcsSetupWlanNoiseImmunity 1 }

-- {SCALAR} 310.2.12.111.2
lcsSetupWlanNoiseImmunityOfdmWeakSignalDetection OBJECT-TYPE
    SYNTAX     INTEGER (0..255)
    MAX-ACCESS read-write
    STATUS     current
    DESCRIPTION
        "-- empty --"
    ::= { lcsSetupWlanNoiseImmunity 2 }

-- {SCALAR} 310.2.12.111.3
lcsSetupWlanNoiseImmunityCckWeakSignalDetectionThreshold OBJECT-TYPE
    SYNTAX     INTEGER (0..255)
    MAX-ACCESS read-write
    STATUS     current
    DESCRIPTION
        "-- empty --"
    ::= { lcsSetupWlanNoiseImmunity 3 }

-- {SCALAR} 310.2.12.111.4
lcsSetupWlanNoiseImmunityFirStepLevel OBJECT-TYPE
    SYNTAX     INTEGER (0..255)
    MAX-ACCESS read-write
    STATUS     current
    DESCRIPTION
        "-- empty --"
    ::= { lcsSetupWlanNoiseImmunity 4 }

-- {SCALAR} 310.2.12.111.5
lcsSetupWlanNoiseImmunitySpuriousImmunityLevel OBJECT-TYPE
    SYNTAX     INTEGER (0..255)
    MAX-ACCESS read-write
    STATUS     current
    DESCRIPTION
        "-- empty --"
    ::= { lcsSetupWlanNoiseImmunity 5 }

-- {SCALAR} 310.2.12.111.6
lcsSetupWlanNoiseImmunityMrcCck OBJECT-TYPE
    SYNTAX     INTEGER (0..255)
    MAX-ACCESS read-write
    STATUS     current
    DESCRIPTION
        "-- empty --"
    ::= { lcsSetupWlanNoiseImmunity 6 }

-- {SCALAR} 310.2.12.114
lcsSetupWlanAggregateRetryLimit OBJECT-TYPE
    SYNTAX     INTEGER (0..255)
    MAX-ACCESS read-write
    STATUS     current
    DESCRIPTION
        "-- empty --"
    ::= { lcsSetupWlan 114 }

-- {SCALAR} 310.2.12.120
lcsSetupWlanRxAggregateFlushTimeoutMs OBJECT-TYPE
    SYNTAX     INTEGER (0..2147483647)
    MAX-ACCESS read-write
    STATUS     current
    DESCRIPTION
        "-- empty --"
    ::= { lcsSetupWlan 120 }

-- {SCALAR} 310.2.12.121
lcsSetupWlanHtFairness OBJECT-TYPE
    SYNTAX     INTEGER
      {
        eNo (0),
        eYes (1)
      }
    MAX-ACCESS read-write
    STATUS     current
    DESCRIPTION
        "-- empty --"
    ::= { lcsSetupWlan 121 }

-- {OID} 310.2.12.86
lcsSetupWlanPacketCapture OBJECT IDENTIFIER ::= { lcsSetupWlan 86 }

-- {SCALAR} 310.2.12.86.1
lcsSetupWlanPacketCaptureWlanCaptureFormat OBJECT-TYPE
    SYNTAX     INTEGER
      {
        eRadiotap (127),
        eAvs (163),
        ePpi (192),
        ePrism (119),
        ePlain (105)
      }
    MAX-ACCESS read-write
    STATUS     current
    DESCRIPTION
        "-- empty --"
    ::= { lcsSetupWlanPacketCapture 1 }

-- {OID} 310.2.12.85
lcsSetupWlanPmkCaching OBJECT IDENTIFIER ::= { lcsSetupWlan 85 }

-- {SCALAR} 310.2.12.85.1
lcsSetupWlanPmkCachingDefaultLifetime OBJECT-TYPE
    SYNTAX     INTEGER (0..2147483647)
    MAX-ACCESS read-write
    STATUS     current
    DESCRIPTION
        "-- empty --"
    ::= { lcsSetupWlanPmkCaching 1 }

-- {OID} 310.2.12.51
lcsSetupWlanRateAdaption OBJECT IDENTIFIER ::= { lcsSetupWlan 51 }

-- {SCALAR} 310.2.12.51.5
lcsSetupWlanRateAdaptionMethod OBJECT-TYPE
    SYNTAX     INTEGER
      {
        eStandard (0),
        eMinstrel (1)
      }
    MAX-ACCESS read-write
    STATUS     current
    DESCRIPTION
        "-- empty --"
    ::= { lcsSetupWlanRateAdaption 5 }

-- {SCALAR} 310.2.12.51.2
lcsSetupWlanRateAdaptionInitialRate OBJECT-TYPE
    SYNTAX     INTEGER
      {
        eMinimum (0),
        eRssiDerived (1)
      }
    MAX-ACCESS read-write
    STATUS     current
    DESCRIPTION
        "-- empty --"
    ::= { lcsSetupWlanRateAdaption 2 }

-- {SCALAR} 310.2.12.51.4
lcsSetupWlanRateAdaptionStandardAveragingFactor OBJECT-TYPE
    SYNTAX     INTEGER (0..255)
    MAX-ACCESS read-write
    STATUS     current
    DESCRIPTION
        "-- empty --"
    ::= { lcsSetupWlanRateAdaption 4 }

-- {SCALAR} 310.2.12.51.3
lcsSetupWlanRateAdaptionMinstrelAveragingFactor OBJECT-TYPE
    SYNTAX     INTEGER (0..255)
    MAX-ACCESS read-write
    STATUS     current
    DESCRIPTION
        "-- empty --"
    ::= { lcsSetupWlanRateAdaption 3 }

-- {SCALAR} 310.2.12.26
lcsSetupWlanInterSsidTraffic OBJECT-TYPE
    SYNTAX     INTEGER
      {
        eYes (1),
        eLocallyOff (0),
        eGloballyOff (2)
      }
    MAX-ACCESS read-write
    STATUS     current
    DESCRIPTION
        "-- empty --"
    ::= { lcsSetupWlan 26 }

-- {SCALAR} 310.2.12.47
lcsSetupWlanIdleTimeout OBJECT-TYPE
    SYNTAX     INTEGER (0..2147483647)
    MAX-ACCESS read-write
    STATUS     current
    DESCRIPTION
        "-- empty --"
    ::= { lcsSetupWlan 47 }

-- {SCALAR} 310.2.12.27
lcsSetupWlanSuperviseStations OBJECT-TYPE
    SYNTAX     INTEGER
      {
        eNo (0),
        eYes (1)
      }
    MAX-ACCESS read-write
    STATUS     current
    DESCRIPTION
        "-- empty --"
    ::= { lcsSetupWlan 27 }

-- {SCALAR} 310.2.12.38
lcsSetupWlanArpHandling OBJECT-TYPE
    SYNTAX     INTEGER
      {
        eNo (0),
        eYes (1)
      }
    MAX-ACCESS read-write
    STATUS     current
    DESCRIPTION
        "-- empty --"
    ::= { lcsSetupWlan 38 }

-- {SCALAR} 310.2.12.44
lcsSetupWlanAllowIllegalAssociationWithoutAuthentication OBJECT-TYPE
    SYNTAX     INTEGER
      {
        eNo (0),
        eYes (1)
      }
    MAX-ACCESS read-write
    STATUS     current
    DESCRIPTION
        "-- empty --"
    ::= { lcsSetupWlan 44 }

-- {TABLE} 310.2.12.70
lcsSetupWlanVlanGroupkeyMappingTable OBJECT-TYPE
    SYNTAX     SEQUENCE OF LcsSetupWlanVlanGroupkeyMappingEntry
    MAX-ACCESS not-accessible
    STATUS     current
    DESCRIPTION
        "-- empty --"
    ::= { lcsSetupWlan 70 }

-- {ENTRY} 310.2.12.70.1
lcsSetupWlanVlanGroupkeyMappingEntry OBJECT-TYPE
    SYNTAX     LcsSetupWlanVlanGroupkeyMappingEntry
    MAX-ACCESS not-accessible
    STATUS     current
    DESCRIPTION
        ""
    INDEX {
        lcsSetupWlanVlanGroupkeyMappingEntryNetwork,
        lcsSetupWlanVlanGroupkeyMappingEntryVlanId
    }
    ::= { lcsSetupWlanVlanGroupkeyMappingTable 1 }

-- {SEQUENCE}
LcsSetupWlanVlanGroupkeyMappingEntry ::= SEQUENCE {
    lcsSetupWlanVlanGroupkeyMappingEntryNetwork INTEGER,
    lcsSetupWlanVlanGroupkeyMappingEntryVlanId INTEGER,
    lcsSetupWlanVlanGroupkeyMappingEntryGroupkeyIndex INTEGER
}

-- {COLUMN} 310.2.12.70.1.1
lcsSetupWlanVlanGroupkeyMappingEntryNetwork OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-write
    STATUS     current
    DESCRIPTION
        "-- empty --"
    ::= { lcsSetupWlanVlanGroupkeyMappingEntry 1 }

-- {COLUMN} 310.2.12.70.1.2
lcsSetupWlanVlanGroupkeyMappingEntryVlanId OBJECT-TYPE
    SYNTAX     INTEGER (0..65535)
    MAX-ACCESS read-write
    STATUS     current
    DESCRIPTION
        "-- empty --"
    ::= { lcsSetupWlanVlanGroupkeyMappingEntry 2 }

-- {COLUMN} 310.2.12.70.1.3
lcsSetupWlanVlanGroupkeyMappingEntryGroupkeyIndex OBJECT-TYPE
    SYNTAX     INTEGER (0..255)
    MAX-ACCESS read-write
    STATUS     current
    DESCRIPTION
        "-- empty --"
    ::= { lcsSetupWlanVlanGroupkeyMappingEntry 3 }

-- {TABLE} 310.2.12.7
lcsSetupWlanAccessListTable OBJECT-TYPE
    SYNTAX     SEQUENCE OF LcsSetupWlanAccessListEntry
    MAX-ACCESS not-accessible
    STATUS     current
    DESCRIPTION
        "-- empty --"
    ::= { lcsSetupWlan 7 }

-- {ENTRY} 310.2.12.7.1
lcsSetupWlanAccessListEntry OBJECT-TYPE
    SYNTAX     LcsSetupWlanAccessListEntry
    MAX-ACCESS not-accessible
    STATUS     current
    DESCRIPTION
        ""
    INDEX {
        lcsSetupWlanAccessListEntryMacAddress
    }
    ::= { lcsSetupWlanAccessListTable 1 }

-- {SEQUENCE}
LcsSetupWlanAccessListEntry ::= SEQUENCE {
    lcsSetupWlanAccessListEntryMacAddress MacAddress,
    lcsSetupWlanAccessListEntryName DisplayString,
    lcsSetupWlanAccessListEntryWpaPassphrase DisplayString,
    lcsSetupWlanAccessListEntryTxLimit INTEGER,
    lcsSetupWlanAccessListEntryRxLimit INTEGER,
    lcsSetupWlanAccessListEntryVlanId INTEGER,
    lcsSetupWlanAccessListEntryComment DisplayString
}

-- {COLUMN} 310.2.12.7.1.1
lcsSetupWlanAccessListEntryMacAddress OBJECT-TYPE
    SYNTAX     MacAddress
    MAX-ACCESS read-write
    STATUS     current
    DESCRIPTION
        "-- empty --"
    ::= { lcsSetupWlanAccessListEntry 1 }

-- {COLUMN} 310.2.12.7.1.2
lcsSetupWlanAccessListEntryName OBJECT-TYPE
    SYNTAX     DisplayString (SIZE(0..32))
    MAX-ACCESS read-write
    STATUS     current
    DESCRIPTION
        "-- empty --"
    ::= { lcsSetupWlanAccessListEntry 2 }

-- {COLUMN} 310.2.12.7.1.4
lcsSetupWlanAccessListEntryWpaPassphrase OBJECT-TYPE
    SYNTAX     DisplayString (SIZE(0..63))
    MAX-ACCESS read-write
    STATUS     current
    DESCRIPTION
        "-- empty --"
    ::= { lcsSetupWlanAccessListEntry 4 }

-- {COLUMN} 310.2.12.7.1.5
lcsSetupWlanAccessListEntryTxLimit OBJECT-TYPE
    SYNTAX     INTEGER (0..2147483647)
    MAX-ACCESS read-write
    STATUS     current
    DESCRIPTION
        "-- empty --"
    ::= { lcsSetupWlanAccessListEntry 5 }

-- {COLUMN} 310.2.12.7.1.6
lcsSetupWlanAccessListEntryRxLimit OBJECT-TYPE
    SYNTAX     INTEGER (0..2147483647)
    MAX-ACCESS read-write
    STATUS     current
    DESCRIPTION
        "-- empty --"
    ::= { lcsSetupWlanAccessListEntry 6 }

-- {COLUMN} 310.2.12.7.1.7
lcsSetupWlanAccessListEntryVlanId OBJECT-TYPE
    SYNTAX     INTEGER (0..65535)
    MAX-ACCESS read-write
    STATUS     current
    DESCRIPTION
        "-- empty --"
    ::= { lcsSetupWlanAccessListEntry 7 }

-- {COLUMN} 310.2.12.7.1.3
lcsSetupWlanAccessListEntryComment OBJECT-TYPE
    SYNTAX     DisplayString (SIZE(0..30))
    MAX-ACCESS read-write
    STATUS     current
    DESCRIPTION
        "-- empty --"
    ::= { lcsSetupWlanAccessListEntry 3 }

-- {SCALAR} 310.2.12.8
lcsSetupWlanAccessMode OBJECT-TYPE
    SYNTAX     INTEGER
      {
        eNegative (0),
        ePositive (1)
      }
    MAX-ACCESS read-write
    STATUS     current
    DESCRIPTION
        "-- empty --"
    ::= { lcsSetupWlan 8 }

-- {OID} 310.2.12.29
lcsSetupWlanRadiusAccessCheck OBJECT IDENTIFIER ::= { lcsSetupWlan 29 }

-- {SCALAR} 310.2.12.29.1
lcsSetupWlanRadiusAccessCheckServerAddress OBJECT-TYPE
    SYNTAX     IpAddress
    MAX-ACCESS read-write
    STATUS     current
    DESCRIPTION
        "-- empty --"
    ::= { lcsSetupWlanRadiusAccessCheck 1 }

-- {SCALAR} 310.2.12.29.2
lcsSetupWlanRadiusAccessCheckAuthPort OBJECT-TYPE
    SYNTAX     INTEGER (0..65535)
    MAX-ACCESS read-write
    STATUS     current
    DESCRIPTION
        "-- empty --"
    ::= { lcsSetupWlanRadiusAccessCheck 2 }

-- {SCALAR} 310.2.12.29.3
lcsSetupWlanRadiusAccessCheckSecret OBJECT-TYPE
    SYNTAX     DisplayString (SIZE(0..64))
    MAX-ACCESS read-write
    STATUS     current
    DESCRIPTION
        "-- empty --"
    ::= { lcsSetupWlanRadiusAccessCheck 3 }

-- {SCALAR} 310.2.12.29.11
lcsSetupWlanRadiusAccessCheckLoopbackAddress OBJECT-TYPE
    SYNTAX     DisplayString (SIZE(0..16))
    MAX-ACCESS read-write
    STATUS     current
    DESCRIPTION
        "-- empty --"
    ::= { lcsSetupWlanRadiusAccessCheck 11 }

-- {SCALAR} 310.2.12.29.13
lcsSetupWlanRadiusAccessCheckProtocol OBJECT-TYPE
    SYNTAX     INTEGER
      {
        eRadius (0),
        eRadsec (1)
      }
    MAX-ACCESS read-write
    STATUS     current
    DESCRIPTION
        "-- empty --"
    ::= { lcsSetupWlanRadiusAccessCheck 13 }

-- {SCALAR} 310.2.12.29.4
lcsSetupWlanRadiusAccessCheckBackupServerIpAddress OBJECT-TYPE
    SYNTAX     IpAddress
    MAX-ACCESS read-write
    STATUS     current
    DESCRIPTION
        "-- empty --"
    ::= { lcsSetupWlanRadiusAccessCheck 4 }

-- {SCALAR} 310.2.12.29.5
lcsSetupWlanRadiusAccessCheckBackupAuthPort OBJECT-TYPE
    SYNTAX     INTEGER (0..65535)
    MAX-ACCESS read-write
    STATUS     current
    DESCRIPTION
        "-- empty --"
    ::= { lcsSetupWlanRadiusAccessCheck 5 }

-- {SCALAR} 310.2.12.29.6
lcsSetupWlanRadiusAccessCheckBackupSecret OBJECT-TYPE
    SYNTAX     DisplayString (SIZE(0..64))
    MAX-ACCESS read-write
    STATUS     current
    DESCRIPTION
        "-- empty --"
    ::= { lcsSetupWlanRadiusAccessCheck 6 }

-- {SCALAR} 310.2.12.29.12
lcsSetupWlanRadiusAccessCheckBackupLoopbackAddress OBJECT-TYPE
    SYNTAX     DisplayString (SIZE(0..16))
    MAX-ACCESS read-write
    STATUS     current
    DESCRIPTION
        "-- empty --"
    ::= { lcsSetupWlanRadiusAccessCheck 12 }

-- {SCALAR} 310.2.12.29.14
lcsSetupWlanRadiusAccessCheckBackupProtocol OBJECT-TYPE
    SYNTAX     INTEGER
      {
        eRadius (0),
        eRadsec (1)
      }
    MAX-ACCESS read-write
    STATUS     current
    DESCRIPTION
        "-- empty --"
    ::= { lcsSetupWlanRadiusAccessCheck 14 }

-- {SCALAR} 310.2.12.29.7
lcsSetupWlanRadiusAccessCheckResponseLifetime OBJECT-TYPE
    SYNTAX     INTEGER (0..2147483647)
    MAX-ACCESS read-write
    STATUS     current
    DESCRIPTION
        "-- empty --"
    ::= { lcsSetupWlanRadiusAccessCheck 7 }

-- {SCALAR} 310.2.12.29.8
lcsSetupWlanRadiusAccessCheckPasswordSource OBJECT-TYPE
    SYNTAX     INTEGER
      {
        eSecret (0),
        eMacAddress (1)
      }
    MAX-ACCESS read-write
    STATUS     current
    DESCRIPTION
        "-- empty --"
    ::= { lcsSetupWlanRadiusAccessCheck 8 }

-- {SCALAR} 310.2.12.29.9
lcsSetupWlanRadiusAccessCheckRecheckCycle OBJECT-TYPE
    SYNTAX     INTEGER (0..2147483647)
    MAX-ACCESS read-write
    STATUS     current
    DESCRIPTION
        "-- empty --"
    ::= { lcsSetupWlanRadiusAccessCheck 9 }

-- {SCALAR} 310.2.12.29.15
lcsSetupWlanRadiusAccessCheckForceRecheck OBJECT-TYPE
    SYNTAX     DisplayString
    MAX-ACCESS read-write
    STATUS     current
    DESCRIPTION
        "-- empty --"
    ::= { lcsSetupWlanRadiusAccessCheck 15 }

-- {SCALAR} 310.2.12.29.10
lcsSetupWlanRadiusAccessCheckProvideServerDatabase OBJECT-TYPE
    SYNTAX     INTEGER
      {
        eNo (0),
        eYes (1)
      }
    MAX-ACCESS read-write
    STATUS     current
    DESCRIPTION
        "-- empty --"
    ::= { lcsSetupWlanRadiusAccessCheck 10 }

-- {OID} 310.2.12.45
lcsSetupWlanRadiusAccounting OBJECT IDENTIFIER ::= { lcsSetupWlan 45 }

-- {SCALAR} 310.2.12.45.1
lcsSetupWlanRadiusAccountingServerAddress OBJECT-TYPE
    SYNTAX     IpAddress
    MAX-ACCESS read-write
    STATUS     current
    DESCRIPTION
        "-- empty --"
    ::= { lcsSetupWlanRadiusAccounting 1 }

-- {SCALAR} 310.2.12.45.2
lcsSetupWlanRadiusAccountingAccntPort OBJECT-TYPE
    SYNTAX     INTEGER (0..65535)
    MAX-ACCESS read-write
    STATUS     current
    DESCRIPTION
        "-- empty --"
    ::= { lcsSetupWlanRadiusAccounting 2 }

-- {SCALAR} 310.2.12.45.3
lcsSetupWlanRadiusAccountingSecret OBJECT-TYPE
    SYNTAX     DisplayString (SIZE(0..64))
    MAX-ACCESS read-write
    STATUS     current
    DESCRIPTION
        "-- empty --"
    ::= { lcsSetupWlanRadiusAccounting 3 }

-- {SCALAR} 310.2.12.45.10
lcsSetupWlanRadiusAccountingLoopbackAddress OBJECT-TYPE
    SYNTAX     DisplayString (SIZE(0..16))
    MAX-ACCESS read-write
    STATUS     current
    DESCRIPTION
        "-- empty --"
    ::= { lcsSetupWlanRadiusAccounting 10 }

-- {SCALAR} 310.2.12.45.12
lcsSetupWlanRadiusAccountingProtocol OBJECT-TYPE
    SYNTAX     INTEGER
      {
        eRadius (0),
        eRadsec (1)
      }
    MAX-ACCESS read-write
    STATUS     current
    DESCRIPTION
        "-- empty --"
    ::= { lcsSetupWlanRadiusAccounting 12 }

-- {SCALAR} 310.2.12.45.4
lcsSetupWlanRadiusAccountingBackupServerIpAddress OBJECT-TYPE
    SYNTAX     IpAddress
    MAX-ACCESS read-write
    STATUS     current
    DESCRIPTION
        "-- empty --"
    ::= { lcsSetupWlanRadiusAccounting 4 }

-- {SCALAR} 310.2.12.45.5
lcsSetupWlanRadiusAccountingBackupAccntPort OBJECT-TYPE
    SYNTAX     INTEGER (0..65535)
    MAX-ACCESS read-write
    STATUS     current
    DESCRIPTION
        "-- empty --"
    ::= { lcsSetupWlanRadiusAccounting 5 }

-- {SCALAR} 310.2.12.45.6
lcsSetupWlanRadiusAccountingBackupSecret OBJECT-TYPE
    SYNTAX     DisplayString (SIZE(0..64))
    MAX-ACCESS read-write
    STATUS     current
    DESCRIPTION
        "-- empty --"
    ::= { lcsSetupWlanRadiusAccounting 6 }

-- {SCALAR} 310.2.12.45.11
lcsSetupWlanRadiusAccountingBackupLoopbackAddress OBJECT-TYPE
    SYNTAX     DisplayString (SIZE(0..16))
    MAX-ACCESS read-write
    STATUS     current
    DESCRIPTION
        "-- empty --"
    ::= { lcsSetupWlanRadiusAccounting 11 }

-- {SCALAR} 310.2.12.45.13
lcsSetupWlanRadiusAccountingBackupProtocol OBJECT-TYPE
    SYNTAX     INTEGER
      {
        eRadius (0),
        eRadsec (1)
      }
    MAX-ACCESS read-write
    STATUS     current
    DESCRIPTION
        "-- empty --"
    ::= { lcsSetupWlanRadiusAccounting 13 }

-- {SCALAR} 310.2.12.45.7
lcsSetupWlanRadiusAccountingClientBrgHandling OBJECT-TYPE
    SYNTAX     INTEGER
      {
        eAllTraffic (0),
        eBridgeTrafficOnly (1),
        eClientTrafficOnly (2),
        eSeparateAccounting (3)
      }
    MAX-ACCESS read-write
    STATUS     current
    DESCRIPTION
        "-- empty --"
    ::= { lcsSetupWlanRadiusAccounting 7 }

-- {SCALAR} 310.2.12.45.8
lcsSetupWlanRadiusAccountingInterimUpdatePeriod OBJECT-TYPE
    SYNTAX     INTEGER (0..2147483647)
    MAX-ACCESS read-write
    STATUS     current
    DESCRIPTION
        "-- empty --"
    ::= { lcsSetupWlanRadiusAccounting 8 }

-- {SCALAR} 310.2.12.45.14
lcsSetupWlanRadiusAccountingRestartAccounting OBJECT-TYPE
    SYNTAX     DisplayString
    MAX-ACCESS read-write
    STATUS     current
    DESCRIPTION
        "-- empty --"
    ::= { lcsSetupWlanRadiusAccounting 14 }

-- {SCALAR} 310.2.12.45.9
lcsSetupWlanRadiusAccountingExcludedVlan OBJECT-TYPE
    SYNTAX     INTEGER (0..65535)
    MAX-ACCESS read-write
    STATUS     current
    DESCRIPTION
        "-- empty --"
    ::= { lcsSetupWlanRadiusAccounting 9 }

-- {SCALAR} 310.2.12.108
lcsSetupWlanRadarLoadThreshold OBJECT-TYPE
    SYNTAX     INTEGER (0..255)
    MAX-ACCESS read-write
    STATUS     current
    DESCRIPTION
        "-- empty --"
    ::= { lcsSetupWlan 108 }

-- {SCALAR} 310.2.12.122
lcsSetupWlanDfsTestmode OBJECT-TYPE
    SYNTAX     INTEGER
      {
        eNo (0),
        eYes (1)
      }
    MAX-ACCESS read-write
    STATUS     current
    DESCRIPTION
        "-- empty --"
    ::= { lcsSetupWlan 122 }

-- {TABLE} 310.2.12.107
lcsSetupWlanRadarPatternThresholdsTable OBJECT-TYPE
    SYNTAX     SEQUENCE OF LcsSetupWlanRadarPatternThresholdsEntry
    MAX-ACCESS not-accessible
    STATUS     current
    DESCRIPTION
        "-- empty --"
    ::= { lcsSetupWlan 107 }

-- {ENTRY} 310.2.12.107.1
lcsSetupWlanRadarPatternThresholdsEntry OBJECT-TYPE
    SYNTAX     LcsSetupWlanRadarPatternThresholdsEntry
    MAX-ACCESS not-accessible
    STATUS     current
    DESCRIPTION
        ""
    INDEX {
        lcsSetupWlanRadarPatternThresholdsEntryPatternPps
    }
    ::= { lcsSetupWlanRadarPatternThresholdsTable 1 }

-- {SEQUENCE}
LcsSetupWlanRadarPatternThresholdsEntry ::= SEQUENCE {
    lcsSetupWlanRadarPatternThresholdsEntryPatternPps INTEGER,
    lcsSetupWlanRadarPatternThresholdsEntryThreshold INTEGER
}

-- {COLUMN} 310.2.12.107.1.1
lcsSetupWlanRadarPatternThresholdsEntryPatternPps OBJECT-TYPE
    SYNTAX     INTEGER
      {
        eEn30189312700pps (700),
        eEn301893121800pps (1800),
        eEn30189312330pps (330),
        eEn30189313750pps (750),
        eEn30189313200pps (200),
        eEn30189313300pps (300),
        eEn30189313500pps (500),
        eEn30189313800pps (800),
        eEn301893131000pps (1000),
        eEn301893131200pps (1200),
        eEn301893131500pps (1500),
        eEn301893131600pps (1600),
        eEn301893132000pps (2000),
        eEn301893132300pps (2300),
        eEn301893133000pps (3000),
        eEn301893133500pps (3500),
        eEn301893134000pps (4000),
        eEn302502200pps (262344),
        eEn302502300pps (262444),
        eEn302502500pps (262644),
        eEn302502750pps (262894),
        eEn302502800pps (262944),
        eEn3025021000pps (263144),
        eEn3025021200pps (263344),
        eEn3025021500pps (263644),
        eEn3025021600pps (263744),
        eEn3025022000pps (264144),
        eEn3025022300pps (264444),
        eEn3025023000pps (265144),
        eEn3025023500pps (265644),
        eEn3025024000pps (266144),
        eEn3025024500pps (266644)
      }
    MAX-ACCESS read-write
    STATUS     current
    DESCRIPTION
        "-- empty --"
    ::= { lcsSetupWlanRadarPatternThresholdsEntry 1 }

-- {COLUMN} 310.2.12.107.1.2
lcsSetupWlanRadarPatternThresholdsEntryThreshold OBJECT-TYPE
    SYNTAX     INTEGER (0..2147483647)
    MAX-ACCESS read-write
    STATUS     current
    DESCRIPTION
        "-- empty --"
    ::= { lcsSetupWlanRadarPatternThresholdsEntry 2 }

-- {OID} 310.2.12.50
lcsSetupWlanSigAvrg OBJECT IDENTIFIER ::= { lcsSetupWlan 50 }

-- {SCALAR} 310.2.12.50.1
lcsSetupWlanSigAvrgMeth OBJECT-TYPE
    SYNTAX     INTEGER
      {
        eStd (0)
      }
    MAX-ACCESS read-write
    STATUS     current
    DESCRIPTION
        ""
    ::= { lcsSetupWlanSigAvrg 1 }

-- {OID} 310.2.12.50.2
lcsSetupWlanSigAvrgStdParams OBJECT IDENTIFIER ::= { lcsSetupWlanSigAvrg 2 }

-- {SCALAR} 310.2.12.50.2.1
lcsSetupWlanSigAvrgStdParamsFactor OBJECT-TYPE
    SYNTAX     INTEGER (0..255)
    MAX-ACCESS read-write
    STATUS     current
    DESCRIPTION
        ""
    ::= { lcsSetupWlanSigAvrgStdParams 1 }

-- {OID} 310.2.15
lcsSetupLcr OBJECT IDENTIFIER ::= { lcsSetup 15 }

-- {SCALAR} 310.2.15.1
lcsSetupLcrRouterUsage OBJECT-TYPE
    SYNTAX     INTEGER
      {
        eNo (0),
        eYes (1)
      }
    MAX-ACCESS read-only
    STATUS     current
    DESCRIPTION
        "-- empty --"
    ::= { lcsSetupLcr 1 }

-- {TABLE} 310.2.15.4
lcsSetupLcrTimeListTable OBJECT-TYPE
    SYNTAX     SEQUENCE OF LcsSetupLcrTimeListEntry
    MAX-ACCESS not-accessible
    STATUS     current
    DESCRIPTION
        "-- empty --"
    ::= { lcsSetupLcr 4 }

-- {ENTRY} 310.2.15.4.1
lcsSetupLcrTimeListEntry OBJECT-TYPE
    SYNTAX     LcsSetupLcrTimeListEntry
    MAX-ACCESS not-accessible
    STATUS     current
    DESCRIPTION
        ""
    INDEX {
        lcsSetupLcrTimeListEntryIndex
    }
    ::= { lcsSetupLcrTimeListTable 1 }

-- {SEQUENCE}
LcsSetupLcrTimeListEntry ::= SEQUENCE {
    lcsSetupLcrTimeListEntryIndex INTEGER,
    lcsSetupLcrTimeListEntryPrefix DisplayString,
    lcsSetupLcrTimeListEntryDays BITS,
    lcsSetupLcrTimeListEntryStart DisplayString,
    lcsSetupLcrTimeListEntryStop DisplayString,
    lcsSetupLcrTimeListEntryNumberList DisplayString,
    lcsSetupLcrTimeListEntryFallback INTEGER
}

-- {COLUMN} 310.2.15.4.1.1
lcsSetupLcrTimeListEntryIndex OBJECT-TYPE
    SYNTAX     INTEGER (0..65535)
    MAX-ACCESS read-write
    STATUS     current
    DESCRIPTION
        "-- empty --"
    ::= { lcsSetupLcrTimeListEntry 1 }

-- {COLUMN} 310.2.15.4.1.2
lcsSetupLcrTimeListEntryPrefix OBJECT-TYPE
    SYNTAX     DisplayString (SIZE(0..10))
    MAX-ACCESS read-write
    STATUS     current
    DESCRIPTION
        "-- empty --"
    ::= { lcsSetupLcrTimeListEntry 2 }

-- {COLUMN} 310.2.15.4.1.3
lcsSetupLcrTimeListEntryDays OBJECT-TYPE
    SYNTAX     BITS
      {
        eMonday (7),
        eTuesday (6),
        eWednesday (5),
        eThursday (4),
        eFriday (3),
        eSaturday (2),
        eSunday (1),
        eHoliday (0)
      }
    MAX-ACCESS read-write
    STATUS     current
    DESCRIPTION
        "-- empty --"
    ::= { lcsSetupLcrTimeListEntry 3 }

-- {COLUMN} 310.2.15.4.1.4
lcsSetupLcrTimeListEntryStart OBJECT-TYPE
    SYNTAX     DisplayString (SIZE(0..5))
    MAX-ACCESS read-write
    STATUS     current
    DESCRIPTION
        "-- empty --"
    ::= { lcsSetupLcrTimeListEntry 4 }

-- {COLUMN} 310.2.15.4.1.5
lcsSetupLcrTimeListEntryStop OBJECT-TYPE
    SYNTAX     DisplayString (SIZE(0..5))
    MAX-ACCESS read-write
    STATUS     current
    DESCRIPTION
        "-- empty --"
    ::= { lcsSetupLcrTimeListEntry 5 }

-- {COLUMN} 310.2.15.4.1.6
lcsSetupLcrTimeListEntryNumberList OBJECT-TYPE
    SYNTAX     DisplayString (SIZE(0..29))
    MAX-ACCESS read-write
    STATUS     current
    DESCRIPTION
        "-- empty --"
    ::= { lcsSetupLcrTimeListEntry 6 }

-- {COLUMN} 310.2.15.4.1.7
lcsSetupLcrTimeListEntryFallback OBJECT-TYPE
    SYNTAX     INTEGER
      {
        eNo (0),
        eYes (1)
      }
    MAX-ACCESS read-write
    STATUS     current
    DESCRIPTION
        "-- empty --"
    ::= { lcsSetupLcrTimeListEntry 7 }

-- {OID} 310.2.14
lcsSetupTime OBJECT IDENTIFIER ::= { lcsSetup 14 }

-- {SCALAR} 310.2.14.1
lcsSetupTimeFetchMethod OBJECT-TYPE
    SYNTAX     INTEGER
      {
        eNone (0),
        eNtp (2)
      }
    MAX-ACCESS read-only
    STATUS     current
    DESCRIPTION
        "-- empty --"
    ::= { lcsSetupTime 1 }

-- {SCALAR} 310.2.14.2
lcsSetupTimeCurrentTime OBJECT-TYPE
    SYNTAX     DisplayString
    MAX-ACCESS read-only
    STATUS     current
    DESCRIPTION
        "-- empty --"
    ::= { lcsSetupTime 2 }

-- {SCALAR} 310.2.14.7
lcsSetupTimeUtcInSeconds OBJECT-TYPE
    SYNTAX     Counter32
    MAX-ACCESS read-only
    STATUS     current
    DESCRIPTION
        "-- empty --"
    ::= { lcsSetupTime 7 }

-- {SCALAR} 310.2.14.10
lcsSetupTimeTimezone OBJECT-TYPE
    SYNTAX     INTEGER
      {
        e0 (0),
        eplus1 (1), -- plus 1 hour
        eplus2 (2), -- plus 2 hours
        eplus3 (3), -- plus 3 hours
        eplus4 (4), -- plus 4 hours
        eplus5 (5), -- plus 5 hours
        eplus6 (6), -- plus 6 hours
        eplus7 (7), -- plus 7 hours
        eplus8 (8), -- plus 8 hours
        eplus9 (9), -- plus 9 hours
        eplus10 (10), -- plus 10 hours
        eplus11 (11), -- plus 11 hours
        eplus12 (12), -- plus 12 hours
        eplus13 (13), -- plus 13 hours
        eplus14 (14), -- plus 14 hours
        eminus1 (255), -- minus 1 hour
        eminus2 (254), -- minus 2 hours
        eminus3 (253), -- minus 3 hours
        eminus4 (252), -- minus 4 hours
        eminus5 (251), -- minus 5 hours
        eminus6 (250), -- minus 6 hours
        eminus7 (249), -- minus 7 hours
        eminus8 (248), -- minus 8 hours
        eminus9 (247), -- minus 9 hours
        eminus10 (246), -- minus 10 hours
        eminus11 (245), -- minus 11 hours
        eminus12 (244) -- minus 12 hours
      }
    MAX-ACCESS read-only
    STATUS     current
    DESCRIPTION
        "-- empty --"
    ::= { lcsSetupTime 10 }

-- {SCALAR} 310.2.14.11
lcsSetupTimeDaylightSavingTime OBJECT-TYPE
    SYNTAX     INTEGER
      {
        eNo (0),
        eYes (1),
        eEuropeEu (2),
        eUsa (4),
        eUserDefined (255)
      }
    MAX-ACCESS read-only
    STATUS     current
    DESCRIPTION
        "-- empty --"
    ::= { lcsSetupTime 11 }

-- {TABLE} 310.2.14.12
lcsSetupTimeDstClockChangesTable OBJECT-TYPE
    SYNTAX     SEQUENCE OF LcsSetupTimeDstClockChangesEntry
    MAX-ACCESS not-accessible
    STATUS     current
    DESCRIPTION
        "-- empty --"
    ::= { lcsSetupTime 12 }

-- {ENTRY} 310.2.14.12.1
lcsSetupTimeDstClockChangesEntry OBJECT-TYPE
    SYNTAX     LcsSetupTimeDstClockChangesEntry
    MAX-ACCESS not-accessible
    STATUS     current
    DESCRIPTION
        ""
    INDEX {
        lcsSetupTimeDstClockChangesEntryEvent
    }
    ::= { lcsSetupTimeDstClockChangesTable 1 }

-- {SEQUENCE}
LcsSetupTimeDstClockChangesEntry ::= SEQUENCE {
    lcsSetupTimeDstClockChangesEntryEvent INTEGER,
    lcsSetupTimeDstClockChangesEntryIndex INTEGER,
    lcsSetupTimeDstClockChangesEntryDay INTEGER,
    lcsSetupTimeDstClockChangesEntryMonth INTEGER,
    lcsSetupTimeDstClockChangesEntryHour INTEGER,
    lcsSetupTimeDstClockChangesEntryMinute INTEGER,
    lcsSetupTimeDstClockChangesEntryTimeType INTEGER
}

-- {COLUMN} 310.2.14.12.1.1
lcsSetupTimeDstClockChangesEntryEvent OBJECT-TYPE
    SYNTAX     INTEGER
      {
        eStart (1),
        eEnd (2)
      }
    MAX-ACCESS read-only
    STATUS     current
    DESCRIPTION
        "-- empty --"
    ::= { lcsSetupTimeDstClockChangesEntry 1 }

-- {COLUMN} 310.2.14.12.1.2
lcsSetupTimeDstClockChangesEntryIndex OBJECT-TYPE
    SYNTAX     INTEGER
      {
        e4Last (252),
        e3Last (253),
        e2Last (254),
        eLast (255),
        eFirst (1),
        eSecond (2),
        eThird (3),
        eFourth (4)
      }
    MAX-ACCESS read-write
    STATUS     current
    DESCRIPTION
        "-- empty --"
    ::= { lcsSetupTimeDstClockChangesEntry 2 }

-- {COLUMN} 310.2.14.12.1.3
lcsSetupTimeDstClockChangesEntryDay OBJECT-TYPE
    SYNTAX     INTEGER
      {
        eSunday (0),
        eMonday (1),
        eTuesday (2),
        eWednesday (3),
        eThursday (4),
        eFriday (5),
        eSaturday (6)
      }
    MAX-ACCESS read-write
    STATUS     current
    DESCRIPTION
        "-- empty --"
    ::= { lcsSetupTimeDstClockChangesEntry 3 }

-- {COLUMN} 310.2.14.12.1.4
lcsSetupTimeDstClockChangesEntryMonth OBJECT-TYPE
    SYNTAX     INTEGER
      {
        eJanuary (1),
        eFebruary (2),
        eMarch (3),
        eApril (4),
        eMay (5),
        eJune (6),
        eJuly (7),
        eAugust (8),
        eSeptember (9),
        eOctober (10),
        eNovember (11),
        eDecember (12)
      }
    MAX-ACCESS read-write
    STATUS     current
    DESCRIPTION
        "-- empty --"
    ::= { lcsSetupTimeDstClockChangesEntry 4 }

-- {COLUMN} 310.2.14.12.1.5
lcsSetupTimeDstClockChangesEntryHour OBJECT-TYPE
    SYNTAX     INTEGER (0..255)
    MAX-ACCESS read-write
    STATUS     current
    DESCRIPTION
        "-- empty --"
    ::= { lcsSetupTimeDstClockChangesEntry 5 }

-- {COLUMN} 310.2.14.12.1.6
lcsSetupTimeDstClockChangesEntryMinute OBJECT-TYPE
    SYNTAX     INTEGER (0..255)
    MAX-ACCESS read-write
    STATUS     current
    DESCRIPTION
        "-- empty --"
    ::= { lcsSetupTimeDstClockChangesEntry 6 }

-- {COLUMN} 310.2.14.12.1.7
lcsSetupTimeDstClockChangesEntryTimeType OBJECT-TYPE
    SYNTAX     INTEGER
      {
        eUtc (1),
        eLst (0)
      }
    MAX-ACCESS read-write
    STATUS     current
    DESCRIPTION
        "-- empty --"
    ::= { lcsSetupTimeDstClockChangesEntry 7 }

-- {TABLE} 310.2.14.15
lcsSetupTimeHolidaysTable OBJECT-TYPE
    SYNTAX     SEQUENCE OF LcsSetupTimeHolidaysEntry
    MAX-ACCESS not-accessible
    STATUS     current
    DESCRIPTION
        "-- empty --"
    ::= { lcsSetupTime 15 }

-- {ENTRY} 310.2.14.15.1
lcsSetupTimeHolidaysEntry OBJECT-TYPE
    SYNTAX     LcsSetupTimeHolidaysEntry
    MAX-ACCESS not-accessible
    STATUS     current
    DESCRIPTION
        ""
    INDEX {
        lcsSetupTimeHolidaysEntryIndex
    }
    ::= { lcsSetupTimeHolidaysTable 1 }

-- {SEQUENCE}
LcsSetupTimeHolidaysEntry ::= SEQUENCE {
    lcsSetupTimeHolidaysEntryIndex INTEGER,
    lcsSetupTimeHolidaysEntryDate DisplayString
}

-- {COLUMN} 310.2.14.15.1.1
lcsSetupTimeHolidaysEntryIndex OBJECT-TYPE
    SYNTAX     INTEGER (0..65535)
    MAX-ACCESS read-write
    STATUS     current
    DESCRIPTION
        "-- empty --"
    ::= { lcsSetupTimeHolidaysEntry 1 }

-- {COLUMN} 310.2.14.15.1.2
lcsSetupTimeHolidaysEntryDate OBJECT-TYPE
    SYNTAX     DisplayString (SIZE(0..13))
    MAX-ACCESS read-write
    STATUS     current
    DESCRIPTION
        "-- empty --"
    ::= { lcsSetupTimeHolidaysEntry 2 }

-- {TABLE} 310.2.14.16
lcsSetupTimeTimeframeTable OBJECT-TYPE
    SYNTAX     SEQUENCE OF LcsSetupTimeTimeframeEntry
    MAX-ACCESS not-accessible
    STATUS     current
    DESCRIPTION
        "-- empty --"
    ::= { lcsSetupTime 16 }

-- {ENTRY} 310.2.14.16.1
lcsSetupTimeTimeframeEntry OBJECT-TYPE
    SYNTAX     LcsSetupTimeTimeframeEntry
    MAX-ACCESS not-accessible
    STATUS     current
    DESCRIPTION
        ""
    INDEX {
        lcsSetupTimeTimeframeEntryName,
        lcsSetupTimeTimeframeEntryStart,
        lcsSetupTimeTimeframeEntryStop,
        lcsSetupTimeTimeframeEntryWeekdays
    }
    ::= { lcsSetupTimeTimeframeTable 1 }

-- {SEQUENCE}
LcsSetupTimeTimeframeEntry ::= SEQUENCE {
    lcsSetupTimeTimeframeEntryName DisplayString,
    lcsSetupTimeTimeframeEntryStart DisplayString,
    lcsSetupTimeTimeframeEntryStop DisplayString,
    lcsSetupTimeTimeframeEntryWeekdays BITS
}

-- {COLUMN} 310.2.14.16.1.1
lcsSetupTimeTimeframeEntryName OBJECT-TYPE
    SYNTAX     DisplayString (SIZE(0..31))
    MAX-ACCESS read-write
    STATUS     current
    DESCRIPTION
        "-- empty --"
    ::= { lcsSetupTimeTimeframeEntry 1 }

-- {COLUMN} 310.2.14.16.1.2
lcsSetupTimeTimeframeEntryStart OBJECT-TYPE
    SYNTAX     DisplayString (SIZE(0..5))
    MAX-ACCESS read-write
    STATUS     current
    DESCRIPTION
        "-- empty --"
    ::= { lcsSetupTimeTimeframeEntry 2 }

-- {COLUMN} 310.2.14.16.1.3
lcsSetupTimeTimeframeEntryStop OBJECT-TYPE
    SYNTAX     DisplayString (SIZE(0..5))
    MAX-ACCESS read-write
    STATUS     current
    DESCRIPTION
        "-- empty --"
    ::= { lcsSetupTimeTimeframeEntry 3 }

-- {COLUMN} 310.2.14.16.1.4
lcsSetupTimeTimeframeEntryWeekdays OBJECT-TYPE
    SYNTAX     BITS
      {
        eSunday (7),
        eMonday (6),
        eTuesday (5),
        eWednesday (4),
        eThursday (3),
        eFriday (2),
        eSaturday (1),
        eHoliday (0)
      }
    MAX-ACCESS read-write
    STATUS     current
    DESCRIPTION
        "-- empty --"
    ::= { lcsSetupTimeTimeframeEntry 4 }

-- {SCALAR} 310.2.14.13
lcsSetupTimeGetTime OBJECT-TYPE
    SYNTAX     DisplayString
    MAX-ACCESS read-write
    STATUS     current
    DESCRIPTION
        "-- empty --"
    ::= { lcsSetupTime 13 }

-- {OID} 310.2.23
lcsSetupInterfaces OBJECT IDENTIFIER ::= { lcsSetup 23 }

-- {OID} 310.2.23.40
lcsSetupInterfacesModem OBJECT IDENTIFIER ::= { lcsSetupInterfaces 40 }

-- {SCALAR} 310.2.23.40.1
lcsSetupInterfacesModemRingCount OBJECT-TYPE
    SYNTAX     INTEGER (0..255)
    MAX-ACCESS read-only
    STATUS     current
    DESCRIPTION
        "-- empty --"
    ::= { lcsSetupInterfacesModem 1 }

-- {SCALAR} 310.2.23.40.2
lcsSetupInterfacesModemEchoOffCommand OBJECT-TYPE
    SYNTAX     DisplayString (SIZE(0..9))
    MAX-ACCESS read-write
    STATUS     current
    DESCRIPTION
        "-- empty --"
    ::= { lcsSetupInterfacesModem 2 }

-- {SCALAR} 310.2.23.40.3
lcsSetupInterfacesModemResetCommand OBJECT-TYPE
    SYNTAX     DisplayString (SIZE(0..9))
    MAX-ACCESS read-write
    STATUS     current
    DESCRIPTION
        "-- empty --"
    ::= { lcsSetupInterfacesModem 3 }

-- {SCALAR} 310.2.23.40.4
lcsSetupInterfacesModemInitCommand OBJECT-TYPE
    SYNTAX     DisplayString (SIZE(0..63))
    MAX-ACCESS read-write
    STATUS     current
    DESCRIPTION
        "-- empty --"
    ::= { lcsSetupInterfacesModem 4 }

-- {SCALAR} 310.2.23.40.6
lcsSetupInterfacesModemRequestId OBJECT-TYPE
    SYNTAX     DisplayString (SIZE(0..9))
    MAX-ACCESS read-write
    STATUS     current
    DESCRIPTION
        "-- empty --"
    ::= { lcsSetupInterfacesModem 6 }

-- {SCALAR} 310.2.23.40.11
lcsSetupInterfacesModemInitDial OBJECT-TYPE
    SYNTAX     DisplayString (SIZE(0..63))
    MAX-ACCESS read-write
    STATUS     current
    DESCRIPTION
        "-- empty --"
    ::= { lcsSetupInterfacesModem 11 }

-- {SCALAR} 310.2.23.40.5
lcsSetupInterfacesModemDialCommand OBJECT-TYPE
    SYNTAX     DisplayString (SIZE(0..31))
    MAX-ACCESS read-write
    STATUS     current
    DESCRIPTION
        "-- empty --"
    ::= { lcsSetupInterfacesModem 5 }

-- {SCALAR} 310.2.23.40.12
lcsSetupInterfacesModemInitAnswer OBJECT-TYPE
    SYNTAX     DisplayString (SIZE(0..63))
    MAX-ACCESS read-write
    STATUS     current
    DESCRIPTION
        "-- empty --"
    ::= { lcsSetupInterfacesModem 12 }

-- {SCALAR} 310.2.23.40.7
lcsSetupInterfacesModemAnswerCommand OBJECT-TYPE
    SYNTAX     DisplayString (SIZE(0..9))
    MAX-ACCESS read-write
    STATUS     current
    DESCRIPTION
        "-- empty --"
    ::= { lcsSetupInterfacesModem 7 }

-- {SCALAR} 310.2.23.40.8
lcsSetupInterfacesModemDisconnectCommand OBJECT-TYPE
    SYNTAX     DisplayString (SIZE(0..9))
    MAX-ACCESS read-write
    STATUS     current
    DESCRIPTION
        "-- empty --"
    ::= { lcsSetupInterfacesModem 8 }

-- {SCALAR} 310.2.23.40.9
lcsSetupInterfacesModemEscapeSequence OBJECT-TYPE
    SYNTAX     DisplayString (SIZE(0..9))
    MAX-ACCESS read-write
    STATUS     current
    DESCRIPTION
        "-- empty --"
    ::= { lcsSetupInterfacesModem 9 }

-- {SCALAR} 310.2.23.40.10
lcsSetupInterfacesModemEscapePromtDelayMs OBJECT-TYPE
    SYNTAX     INTEGER (0..65535)
    MAX-ACCESS read-only
    STATUS     current
    DESCRIPTION
        "-- empty --"
    ::= { lcsSetupInterfacesModem 10 }

-- {SCALAR} 310.2.23.40.13
lcsSetupInterfacesModemCycletimeAtPollS OBJECT-TYPE
    SYNTAX     INTEGER (0..255)
    MAX-ACCESS read-only
    STATUS     current
    DESCRIPTION
        "-- empty --"
    ::= { lcsSetupInterfacesModem 13 }

-- {SCALAR} 310.2.23.40.14
lcsSetupInterfacesModemAtPollCount OBJECT-TYPE
    SYNTAX     INTEGER (0..255)
    MAX-ACCESS read-only
    STATUS     current
    DESCRIPTION
        "-- empty --"
    ::= { lcsSetupInterfacesModem 14 }

-- {TABLE} 310.2.23.21
lcsSetupInterfacesLanInterfacesTable OBJECT-TYPE
    SYNTAX     SEQUENCE OF LcsSetupInterfacesLanInterfacesEntry
    MAX-ACCESS not-accessible
    STATUS     current
    DESCRIPTION
        "-- empty --"
    ::= { lcsSetupInterfaces 21 }

-- {ENTRY} 310.2.23.21.1
lcsSetupInterfacesLanInterfacesEntry OBJECT-TYPE
    SYNTAX     LcsSetupInterfacesLanInterfacesEntry
    MAX-ACCESS not-accessible
    STATUS     current
    DESCRIPTION
        ""
    INDEX {
        lcsSetupInterfacesLanInterfacesEntryIfc
    }
    ::= { lcsSetupInterfacesLanInterfacesTable 1 }

-- {SEQUENCE}
LcsSetupInterfacesLanInterfacesEntry ::= SEQUENCE {
    lcsSetupInterfacesLanInterfacesEntryIfc INTEGER,
    lcsSetupInterfacesLanInterfacesEntryOperating INTEGER,
    lcsSetupInterfacesLanInterfacesEntryConnector INTEGER,
    lcsSetupInterfacesLanInterfacesEntryMdiMode INTEGER,
    lcsSetupInterfacesLanInterfacesEntryClockRole INTEGER,
    lcsSetupInterfacesLanInterfacesEntryTxLimit INTEGER,
    lcsSetupInterfacesLanInterfacesEntryRxLimit INTEGER
}

-- {COLUMN} 310.2.23.21.1.1
lcsSetupInterfacesLanInterfacesEntryIfc OBJECT-TYPE
    SYNTAX     INTEGER
      {
        eLan1 (1)
      }
    MAX-ACCESS read-only
    STATUS     current
    DESCRIPTION
        "-- empty --"
    ::= { lcsSetupInterfacesLanInterfacesEntry 1 }

-- {COLUMN} 310.2.23.21.1.7
lcsSetupInterfacesLanInterfacesEntryOperating OBJECT-TYPE
    SYNTAX     INTEGER
      {
        eYes (0),
        eNo (1)
      }
    MAX-ACCESS read-write
    STATUS     current
    DESCRIPTION
        "-- empty --"
    ::= { lcsSetupInterfacesLanInterfacesEntry 7 }

-- {COLUMN} 310.2.23.21.1.2
lcsSetupInterfacesLanInterfacesEntryConnector OBJECT-TYPE
    SYNTAX     INTEGER
      {
        eAuto (0),
        eAuto100 (7),
        e10bT (1),
        eFd10bTx (2),
        e100bTx (3),
        eFd100bTx (4),
        eFd1000bTx (6),
        ePowerDown (255)
      }
    MAX-ACCESS read-write
    STATUS     current
    DESCRIPTION
        "-- empty --"
    ::= { lcsSetupInterfacesLanInterfacesEntry 2 }

-- {COLUMN} 310.2.23.21.1.3
lcsSetupInterfacesLanInterfacesEntryMdiMode OBJECT-TYPE
    SYNTAX     INTEGER
      {
        eAuto (0),
        eMdi (1)
      }
    MAX-ACCESS read-write
    STATUS     current
    DESCRIPTION
        "-- empty --"
    ::= { lcsSetupInterfacesLanInterfacesEntry 3 }

-- {COLUMN} 310.2.23.21.1.5
lcsSetupInterfacesLanInterfacesEntryClockRole OBJECT-TYPE
    SYNTAX     INTEGER
      {
        eSlavePreferred (0),
        eMasterPreferred (4),
        eSlave (2),
        eMaster (1)
      }
    MAX-ACCESS read-write
    STATUS     current
    DESCRIPTION
        "-- empty --"
    ::= { lcsSetupInterfacesLanInterfacesEntry 5 }

-- {COLUMN} 310.2.23.21.1.8
lcsSetupInterfacesLanInterfacesEntryTxLimit OBJECT-TYPE
    SYNTAX     INTEGER (0..2147483647)
    MAX-ACCESS read-write
    STATUS     current
    DESCRIPTION
        "-- empty --"
    ::= { lcsSetupInterfacesLanInterfacesEntry 8 }

-- {COLUMN} 310.2.23.21.1.9
lcsSetupInterfacesLanInterfacesEntryRxLimit OBJECT-TYPE
    SYNTAX     INTEGER (0..2147483647)
    MAX-ACCESS read-write
    STATUS     current
    DESCRIPTION
        "-- empty --"
    ::= { lcsSetupInterfacesLanInterfacesEntry 9 }

-- {OID} 310.2.23.20
lcsSetupInterfacesWlan OBJECT IDENTIFIER ::= { lcsSetupInterfaces 20 }

-- {TABLE} 310.2.23.20.7
lcsSetupInterfacesWlanOperationalTable OBJECT-TYPE
    SYNTAX     SEQUENCE OF LcsSetupInterfacesWlanOperationalEntry
    MAX-ACCESS not-accessible
    STATUS     current
    DESCRIPTION
        "-- empty --"
    ::= { lcsSetupInterfacesWlan 7 }

-- {ENTRY} 310.2.23.20.7.1
lcsSetupInterfacesWlanOperationalEntry OBJECT-TYPE
    SYNTAX     LcsSetupInterfacesWlanOperationalEntry
    MAX-ACCESS not-accessible
    STATUS     current
    DESCRIPTION
        ""
    INDEX {
        lcsSetupInterfacesWlanOperationalEntryIfc
    }
    ::= { lcsSetupInterfacesWlanOperationalTable 1 }

-- {SEQUENCE}
LcsSetupInterfacesWlanOperationalEntry ::= SEQUENCE {
    lcsSetupInterfacesWlanOperationalEntryIfc INTEGER,
    lcsSetupInterfacesWlanOperationalEntryOperating INTEGER,
    lcsSetupInterfacesWlanOperationalEntryOperationMode INTEGER,
    lcsSetupInterfacesWlanOperationalEntryLinkLedFunction INTEGER,
    lcsSetupInterfacesWlanOperationalEntryBrokenLinkDetection INTEGER
}

-- {COLUMN} 310.2.23.20.7.1.1
lcsSetupInterfacesWlanOperationalEntryIfc OBJECT-TYPE
    SYNTAX     INTEGER
      {
        eWlan1 (1)
      }
    MAX-ACCESS read-write
    STATUS     current
    DESCRIPTION
        "-- empty --"
    ::= { lcsSetupInterfacesWlanOperationalEntry 1 }

-- {COLUMN} 310.2.23.20.7.1.2
lcsSetupInterfacesWlanOperationalEntryOperating OBJECT-TYPE
    SYNTAX     INTEGER
      {
        eYes (0),
        eNo (1)
      }
    MAX-ACCESS read-write
    STATUS     current
    DESCRIPTION
        "-- empty --"
    ::= { lcsSetupInterfacesWlanOperationalEntry 2 }

-- {COLUMN} 310.2.23.20.7.1.3
lcsSetupInterfacesWlanOperationalEntryOperationMode OBJECT-TYPE
    SYNTAX     INTEGER
      {
        eAccessPoint (1),
        eManagedAp (4),
        eStation (0)
      }
    MAX-ACCESS read-write
    STATUS     current
    DESCRIPTION
        "lancom's description of operation mode"
    ::= { lcsSetupInterfacesWlanOperationalEntry 3 }

-- {COLUMN} 310.2.23.20.7.1.4
lcsSetupInterfacesWlanOperationalEntryLinkLedFunction OBJECT-TYPE
    SYNTAX     INTEGER
      {
        eNormal (0),
        eClientModeStrength (1),
        eP2p1Strength (8),
        eP2p2Strength (9),
        eP2p3Strength (10),
        eP2p4Strength (11),
        eP2p5Strength (12),
        eP2p6Strength (13),
        eP2p7Strength (14),
        eP2p8Strength (15),
        eP2p9Strength (16),
        eP2p10Strength (17),
        eP2p11Strength (18),
        eP2p12Strength (19),
        eP2p13Strength (20),
        eP2p14Strength (21),
        eP2p15Strength (22),
        eP2p16Strength (23)
      }
    MAX-ACCESS read-write
    STATUS     current
    DESCRIPTION
        "-- empty --"
    ::= { lcsSetupInterfacesWlanOperationalEntry 4 }

-- {COLUMN} 310.2.23.20.7.1.5
lcsSetupInterfacesWlanOperationalEntryBrokenLinkDetection OBJECT-TYPE
    SYNTAX     INTEGER
      {
        eNo (0),
        eLan1 (1)
      }
    MAX-ACCESS read-write
    STATUS     current
    DESCRIPTION
        "-- empty --"
    ::= { lcsSetupInterfacesWlanOperationalEntry 5 }

-- {TABLE} 310.2.23.20.1
lcsSetupInterfacesWlanNetworkTable OBJECT-TYPE
    SYNTAX     SEQUENCE OF LcsSetupInterfacesWlanNetworkEntry
    MAX-ACCESS not-accessible
    STATUS     current
    DESCRIPTION
        "-- empty --"
    ::= { lcsSetupInterfacesWlan 1 }

-- {ENTRY} 310.2.23.20.1.1
lcsSetupInterfacesWlanNetworkEntry OBJECT-TYPE
    SYNTAX     LcsSetupInterfacesWlanNetworkEntry
    MAX-ACCESS not-accessible
    STATUS     current
    DESCRIPTION
        ""
    INDEX {
        lcsSetupInterfacesWlanNetworkEntryIfc
    }
    ::= { lcsSetupInterfacesWlanNetworkTable 1 }

-- {SEQUENCE}
LcsSetupInterfacesWlanNetworkEntry ::= SEQUENCE {
    lcsSetupInterfacesWlanNetworkEntryIfc INTEGER,
    lcsSetupInterfacesWlanNetworkEntryOperating INTEGER,
    lcsSetupInterfacesWlanNetworkEntryNetworkName DisplayString,
    lcsSetupInterfacesWlanNetworkEntryMacFilter INTEGER,
    lcsSetupInterfacesWlanNetworkEntryRadiusAccounting INTEGER,
    lcsSetupInterfacesWlanNetworkEntryClosedNetwork INTEGER,
    lcsSetupInterfacesWlanNetworkEntryMaxStations INTEGER,
    lcsSetupInterfacesWlanNetworkEntryMinClientStrength INTEGER,
    lcsSetupInterfacesWlanNetworkEntryClBrgSupport INTEGER,
    lcsSetupInterfacesWlanNetworkEntryInterStationTraffic INTEGER,
    lcsSetupInterfacesWlanNetworkEntryApsd INTEGER,
    lcsSetupInterfacesWlanNetworkEntryAironetExtensions INTEGER,
    lcsSetupInterfacesWlanNetworkEntryIncludeUuid INTEGER
}

-- {COLUMN} 310.2.23.20.1.1.1
lcsSetupInterfacesWlanNetworkEntryIfc OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-write
    STATUS     current
    DESCRIPTION
        "-- empty --"
    ::= { lcsSetupInterfacesWlanNetworkEntry 1 }

-- {COLUMN} 310.2.23.20.1.1.8
lcsSetupInterfacesWlanNetworkEntryOperating OBJECT-TYPE
    SYNTAX     INTEGER
      {
        eYes (0),
        eNo (1)
      }
    MAX-ACCESS read-write
    STATUS     current
    DESCRIPTION
        "-- empty --"
    ::= { lcsSetupInterfacesWlanNetworkEntry 8 }

-- {COLUMN} 310.2.23.20.1.1.2
lcsSetupInterfacesWlanNetworkEntryNetworkName OBJECT-TYPE
    SYNTAX     DisplayString (SIZE(0..32))
    MAX-ACCESS read-write
    STATUS     current
    DESCRIPTION
        "-- empty --"
    ::= { lcsSetupInterfacesWlanNetworkEntry 2 }

-- {COLUMN} 310.2.23.20.1.1.9
lcsSetupInterfacesWlanNetworkEntryMacFilter OBJECT-TYPE
    SYNTAX     INTEGER
      {
        eYes (0),
        eNo (1),
        eLocalOnly (2),
        eRadiusOnly (3)
      }
    MAX-ACCESS read-write
    STATUS     current
    DESCRIPTION
        "-- empty --"
    ::= { lcsSetupInterfacesWlanNetworkEntry 9 }

-- {COLUMN} 310.2.23.20.1.1.12
lcsSetupInterfacesWlanNetworkEntryRadiusAccounting OBJECT-TYPE
    SYNTAX     INTEGER
      {
        eNo (0),
        eYes (1)
      }
    MAX-ACCESS read-write
    STATUS     current
    DESCRIPTION
        "-- empty --"
    ::= { lcsSetupInterfacesWlanNetworkEntry 12 }

-- {COLUMN} 310.2.23.20.1.1.4
lcsSetupInterfacesWlanNetworkEntryClosedNetwork OBJECT-TYPE
    SYNTAX     INTEGER
      {
        eNo (0),
        eYes (1),
        eTightened (2)
      }
    MAX-ACCESS read-write
    STATUS     current
    DESCRIPTION
        "-- empty --"
    ::= { lcsSetupInterfacesWlanNetworkEntry 4 }

-- {COLUMN} 310.2.23.20.1.1.10
lcsSetupInterfacesWlanNetworkEntryMaxStations OBJECT-TYPE
    SYNTAX     INTEGER (0..65535)
    MAX-ACCESS read-write
    STATUS     current
    DESCRIPTION
        "-- empty --"
    ::= { lcsSetupInterfacesWlanNetworkEntry 10 }

-- {COLUMN} 310.2.23.20.1.1.16
lcsSetupInterfacesWlanNetworkEntryMinClientStrength OBJECT-TYPE
    SYNTAX     INTEGER (0..255)
    MAX-ACCESS read-write
    STATUS     current
    DESCRIPTION
        "-- empty --"
    ::= { lcsSetupInterfacesWlanNetworkEntry 16 }

-- {COLUMN} 310.2.23.20.1.1.11
lcsSetupInterfacesWlanNetworkEntryClBrgSupport OBJECT-TYPE
    SYNTAX     INTEGER
      {
        eNo (0),
        eYes (1),
        eExclusive (2)
      }
    MAX-ACCESS read-write
    STATUS     current
    DESCRIPTION
        "-- empty --"
    ::= { lcsSetupInterfacesWlanNetworkEntry 11 }

-- {COLUMN} 310.2.23.20.1.1.13
lcsSetupInterfacesWlanNetworkEntryInterStationTraffic OBJECT-TYPE
    SYNTAX     INTEGER
      {
        eNo (0),
        eYes (1)
      }
    MAX-ACCESS read-write
    STATUS     current
    DESCRIPTION
        "-- empty --"
    ::= { lcsSetupInterfacesWlanNetworkEntry 13 }

-- {COLUMN} 310.2.23.20.1.1.14
lcsSetupInterfacesWlanNetworkEntryApsd OBJECT-TYPE
    SYNTAX     INTEGER
      {
        eNo (0),
        eYes (1)
      }
    MAX-ACCESS read-write
    STATUS     current
    DESCRIPTION
        "-- empty --"
    ::= { lcsSetupInterfacesWlanNetworkEntry 14 }

-- {COLUMN} 310.2.23.20.1.1.15
lcsSetupInterfacesWlanNetworkEntryAironetExtensions OBJECT-TYPE
    SYNTAX     INTEGER
      {
        eNo (0),
        eYes (1)
      }
    MAX-ACCESS read-write
    STATUS     current
    DESCRIPTION
        "-- empty --"
    ::= { lcsSetupInterfacesWlanNetworkEntry 15 }

-- {COLUMN} 310.2.23.20.1.1.17
lcsSetupInterfacesWlanNetworkEntryIncludeUuid OBJECT-TYPE
    SYNTAX     INTEGER
      {
        eNo (0),
        eYes (1)
      }
    MAX-ACCESS read-write
    STATUS     current
    DESCRIPTION
        "-- empty --"
    ::= { lcsSetupInterfacesWlanNetworkEntry 17 }

-- {TABLE} 310.2.23.20.8
lcsSetupInterfacesWlanRadioSettingsTable OBJECT-TYPE
    SYNTAX     SEQUENCE OF LcsSetupInterfacesWlanRadioSettingsEntry
    MAX-ACCESS not-accessible
    STATUS     current
    DESCRIPTION
        "-- empty --"
    ::= { lcsSetupInterfacesWlan 8 }

-- {ENTRY} 310.2.23.20.8.1
lcsSetupInterfacesWlanRadioSettingsEntry OBJECT-TYPE
    SYNTAX     LcsSetupInterfacesWlanRadioSettingsEntry
    MAX-ACCESS not-accessible
    STATUS     current
    DESCRIPTION
        ""
    INDEX {
        lcsSetupInterfacesWlanRadioSettingsEntryIfc
    }
    ::= { lcsSetupInterfacesWlanRadioSettingsTable 1 }

-- {SEQUENCE}
LcsSetupInterfacesWlanRadioSettingsEntry ::= SEQUENCE {
    lcsSetupInterfacesWlanRadioSettingsEntryIfc INTEGER,
    lcsSetupInterfacesWlanRadioSettingsEntryRadioBand INTEGER,
    lcsSetupInterfacesWlanRadioSettingsEntrySubbands INTEGER,
    lcsSetupInterfacesWlanRadioSettingsEntryRadioChannel INTEGER,
    lcsSetupInterfacesWlanRadioSettingsEntryChannelList DisplayString,
    lcsSetupInterfacesWlanRadioSettingsEntry24ghzMode INTEGER,
    lcsSetupInterfacesWlanRadioSettingsEntry5ghzMode INTEGER,
    lcsSetupInterfacesWlanRadioSettingsEntryAllow40mhz INTEGER,
    lcsSetupInterfacesWlanRadioSettingsEntryForce40mhz INTEGER,
    lcsSetupInterfacesWlanRadioSettingsEntryChannelPairing INTEGER,
    lcsSetupInterfacesWlanRadioSettingsEntryAntennaMask INTEGER,
    lcsSetupInterfacesWlanRadioSettingsEntryAntennaGain INTEGER,
    lcsSetupInterfacesWlanRadioSettingsEntryTxPowerReduction INTEGER,
    lcsSetupInterfacesWlanRadioSettingsEntryMaximumDistance INTEGER,
    lcsSetupInterfacesWlanRadioSettingsEntryApDensity INTEGER,
    lcsSetupInterfacesWlanRadioSettingsEntryBackgroundScan INTEGER,
    lcsSetupInterfacesWlanRadioSettingsEntryBackgroundScanUnit INTEGER,
    lcsSetupInterfacesWlanRadioSettingsEntryDfsRescanHours DisplayString,
    lcsSetupInterfacesWlanRadioSettingsEntryCacDuration INTEGER,
    lcsSetupInterfacesWlanRadioSettingsEntryPreferredDfsScheme INTEGER
}

-- {COLUMN} 310.2.23.20.8.1.1
lcsSetupInterfacesWlanRadioSettingsEntryIfc OBJECT-TYPE
    SYNTAX     INTEGER
      {
        eWlan1 (1)
      }
    MAX-ACCESS read-write
    STATUS     current
    DESCRIPTION
        "-- empty --"
    ::= { lcsSetupInterfacesWlanRadioSettingsEntry 1 }

-- {COLUMN} 310.2.23.20.8.1.6
lcsSetupInterfacesWlanRadioSettingsEntryRadioBand OBJECT-TYPE
    SYNTAX     INTEGER
      {
        e24ghz (1),
        e5ghz (2)
      }
    MAX-ACCESS read-write
    STATUS     current
    DESCRIPTION
        "-- empty --"
    ::= { lcsSetupInterfacesWlanRadioSettingsEntry 6 }

-- {COLUMN} 310.2.23.20.8.1.7
lcsSetupInterfacesWlanRadioSettingsEntrySubbands OBJECT-TYPE
    SYNTAX     INTEGER
      {
        eBand1 (1),
        eBand2 (2),
        eBand3 (4),
        eBand1Plus2 (3),
        eBand1Plus3 (5),
        eBand2Plus3 (6),
        eBand1Plus2Plus3 (7)
      }
    MAX-ACCESS read-write
    STATUS     current
    DESCRIPTION
        "-- empty --"
    ::= { lcsSetupInterfacesWlanRadioSettingsEntry 7 }

-- {COLUMN} 310.2.23.20.8.1.8
lcsSetupInterfacesWlanRadioSettingsEntryRadioChannel OBJECT-TYPE
    SYNTAX     INTEGER (0..255)
    MAX-ACCESS read-write
    STATUS     current
    DESCRIPTION
        "-- empty --"
    ::= { lcsSetupInterfacesWlanRadioSettingsEntry 8 }

-- {COLUMN} 310.2.23.20.8.1.13
lcsSetupInterfacesWlanRadioSettingsEntryChannelList OBJECT-TYPE
    SYNTAX     DisplayString (SIZE(0..48))
    MAX-ACCESS read-write
    STATUS     current
    DESCRIPTION
        "-- empty --"
    ::= { lcsSetupInterfacesWlanRadioSettingsEntry 13 }

-- {COLUMN} 310.2.23.20.8.1.9
lcsSetupInterfacesWlanRadioSettingsEntry24ghzMode OBJECT-TYPE
    SYNTAX     INTEGER
      {
        e11bgMixed (0),
        e11gOnly (1),
        e11bOnly (2),
        e2mMixed (3),
        e11bgnMixed (5),
        e2m11bgnMixed (6),
        e11gnMixed (7),
        eGreenfield (8)
      }
    MAX-ACCESS read-write
    STATUS     current
    DESCRIPTION
        "-- empty --"
    ::= { lcsSetupInterfacesWlanRadioSettingsEntry 9 }

-- {COLUMN} 310.2.23.20.8.1.3
lcsSetupInterfacesWlanRadioSettingsEntry5ghzMode OBJECT-TYPE
    SYNTAX     INTEGER
      {
        eNormal (0),
        e11anMixed (3),
        eGreenfield (4)
      }
    MAX-ACCESS read-write
    STATUS     current
    DESCRIPTION
        "-- empty --"
    ::= { lcsSetupInterfacesWlanRadioSettingsEntry 3 }

-- {COLUMN} 310.2.23.20.8.1.16
lcsSetupInterfacesWlanRadioSettingsEntryAllow40mhz OBJECT-TYPE
    SYNTAX     INTEGER
      {
        eAuto (0),
        eNo (1)
      }
    MAX-ACCESS read-write
    STATUS     current
    DESCRIPTION
        "-- empty --"
    ::= { lcsSetupInterfacesWlanRadioSettingsEntry 16 }

-- {COLUMN} 310.2.23.20.8.1.22
lcsSetupInterfacesWlanRadioSettingsEntryForce40mhz OBJECT-TYPE
    SYNTAX     INTEGER
      {
        eNo (0),
        eYes (1)
      }
    MAX-ACCESS read-write
    STATUS     current
    DESCRIPTION
        "-- empty --"
    ::= { lcsSetupInterfacesWlanRadioSettingsEntry 22 }

-- {COLUMN} 310.2.23.20.8.1.19
lcsSetupInterfacesWlanRadioSettingsEntryChannelPairing OBJECT-TYPE
    SYNTAX     INTEGER
      {
        e11nCompliant (0),
        eLegacyTurboFriendly (1)
      }
    MAX-ACCESS read-write
    STATUS     current
    DESCRIPTION
        "-- empty --"
    ::= { lcsSetupInterfacesWlanRadioSettingsEntry 19 }

-- {COLUMN} 310.2.23.20.8.1.17
lcsSetupInterfacesWlanRadioSettingsEntryAntennaMask OBJECT-TYPE
    SYNTAX     INTEGER
      {
        eAuto (0),
        eAntenna1 (1),
        eAntenna1Plus2 (3),
        eAntenna1Plus3 (5),
        eAntenna1Plus2Plus3 (7)
      }
    MAX-ACCESS read-write
    STATUS     current
    DESCRIPTION
        "-- empty --"
    ::= { lcsSetupInterfacesWlanRadioSettingsEntry 17 }

-- {COLUMN} 310.2.23.20.8.1.12
lcsSetupInterfacesWlanRadioSettingsEntryAntennaGain OBJECT-TYPE
    SYNTAX     INTEGER (-128..127)
    MAX-ACCESS read-write
    STATUS     current
    DESCRIPTION
        "-- empty --"
    ::= { lcsSetupInterfacesWlanRadioSettingsEntry 12 }

-- {COLUMN} 310.2.23.20.8.1.2
lcsSetupInterfacesWlanRadioSettingsEntryTxPowerReduction OBJECT-TYPE
    SYNTAX     INTEGER (0..255)
    MAX-ACCESS read-write
    STATUS     current
    DESCRIPTION
        "-- empty --"
    ::= { lcsSetupInterfacesWlanRadioSettingsEntry 2 }

-- {COLUMN} 310.2.23.20.8.1.4
lcsSetupInterfacesWlanRadioSettingsEntryMaximumDistance OBJECT-TYPE
    SYNTAX     INTEGER (0..65535)
    MAX-ACCESS read-write
    STATUS     current
    DESCRIPTION
        "-- empty --"
    ::= { lcsSetupInterfacesWlanRadioSettingsEntry 4 }

-- {COLUMN} 310.2.23.20.8.1.10
lcsSetupInterfacesWlanRadioSettingsEntryApDensity OBJECT-TYPE
    SYNTAX     INTEGER
      {
        eLow (1),
        eMedium (2),
        eHigh (3),
        eMinicell (4),
        eMicrocell (5),
        eOff (0)
      }
    MAX-ACCESS read-write
    STATUS     current
    DESCRIPTION
        "-- empty --"
    ::= { lcsSetupInterfacesWlanRadioSettingsEntry 10 }

-- {COLUMN} 310.2.23.20.8.1.14
lcsSetupInterfacesWlanRadioSettingsEntryBackgroundScan OBJECT-TYPE
    SYNTAX     INTEGER (0..2147483647)
    MAX-ACCESS read-write
    STATUS     current
    DESCRIPTION
        "-- empty --"
    ::= { lcsSetupInterfacesWlanRadioSettingsEntry 14 }

-- {COLUMN} 310.2.23.20.8.1.18
lcsSetupInterfacesWlanRadioSettingsEntryBackgroundScanUnit OBJECT-TYPE
    SYNTAX     INTEGER
      {
        eSeconds (0),
        eMilliseconds (1),
        eMicroseconds (2),
        eMinutes (3),
        eHours (4),
        eDays (5),
        eWeeks (6),
        eFortnights (7)
      }
    MAX-ACCESS read-write
    STATUS     current
    DESCRIPTION
        "-- empty --"
    ::= { lcsSetupInterfacesWlanRadioSettingsEntry 18 }

-- {COLUMN} 310.2.23.20.8.1.15
lcsSetupInterfacesWlanRadioSettingsEntryDfsRescanHours OBJECT-TYPE
    SYNTAX     DisplayString (SIZE(0..19))
    MAX-ACCESS read-write
    STATUS     current
    DESCRIPTION
        "-- empty --"
    ::= { lcsSetupInterfacesWlanRadioSettingsEntry 15 }

-- {COLUMN} 310.2.23.20.8.1.21
lcsSetupInterfacesWlanRadioSettingsEntryCacDuration OBJECT-TYPE
    SYNTAX     INTEGER (0..2147483647)
    MAX-ACCESS read-write
    STATUS     current
    DESCRIPTION
        "-- empty --"
    ::= { lcsSetupInterfacesWlanRadioSettingsEntry 21 }

-- {COLUMN} 310.2.23.20.8.1.20
lcsSetupInterfacesWlanRadioSettingsEntryPreferredDfsScheme OBJECT-TYPE
    SYNTAX     INTEGER
      {
        eEn301893V13 (2),
        eEn301893V15 (32),
        eEn301893V16 (64)
      }
    MAX-ACCESS read-write
    STATUS     current
    DESCRIPTION
        "-- empty --"
    ::= { lcsSetupInterfacesWlanRadioSettingsEntry 20 }

-- {TABLE} 310.2.23.20.2
lcsSetupInterfacesWlanTransmissionTable OBJECT-TYPE
    SYNTAX     SEQUENCE OF LcsSetupInterfacesWlanTransmissionEntry
    MAX-ACCESS not-accessible
    STATUS     current
    DESCRIPTION
        "-- empty --"
    ::= { lcsSetupInterfacesWlan 2 }

-- {ENTRY} 310.2.23.20.2.1
lcsSetupInterfacesWlanTransmissionEntry OBJECT-TYPE
    SYNTAX     LcsSetupInterfacesWlanTransmissionEntry
    MAX-ACCESS not-accessible
    STATUS     current
    DESCRIPTION
        ""
    INDEX {
        lcsSetupInterfacesWlanTransmissionEntryIfc
    }
    ::= { lcsSetupInterfacesWlanTransmissionTable 1 }

-- {SEQUENCE}
LcsSetupInterfacesWlanTransmissionEntry ::= SEQUENCE {
    lcsSetupInterfacesWlanTransmissionEntryIfc INTEGER,
    lcsSetupInterfacesWlanTransmissionEntryPacketSize INTEGER,
    lcsSetupInterfacesWlanTransmissionEntryMinTxRate INTEGER,
    lcsSetupInterfacesWlanTransmissionEntryMaxTxRate INTEGER,
    lcsSetupInterfacesWlanTransmissionEntryBasicRate INTEGER,
    lcsSetupInterfacesWlanTransmissionEntryEapolRate INTEGER,
    lcsSetupInterfacesWlanTransmissionEntryHardRetries INTEGER,
    lcsSetupInterfacesWlanTransmissionEntrySoftRetries INTEGER,
    lcsSetupInterfacesWlanTransmissionEntry11bPreamble INTEGER,
    lcsSetupInterfacesWlanTransmissionEntryMinHtMcs INTEGER,
    lcsSetupInterfacesWlanTransmissionEntryMaxHtMcs INTEGER,
    lcsSetupInterfacesWlanTransmissionEntryShortGuardInterval INTEGER,
    lcsSetupInterfacesWlanTransmissionEntryMinSpatialStreams INTEGER,
    lcsSetupInterfacesWlanTransmissionEntryMaxSpatialStreams INTEGER,
    lcsSetupInterfacesWlanTransmissionEntrySendAggregates INTEGER,
    lcsSetupInterfacesWlanTransmissionEntryReceiveAggregates INTEGER,
    lcsSetupInterfacesWlanTransmissionEntryMaxAggrPacketCount INTEGER,
    lcsSetupInterfacesWlanTransmissionEntryRtsThreshold INTEGER,
    lcsSetupInterfacesWlanTransmissionEntryMinFragLen INTEGER,
    lcsSetupInterfacesWlanTransmissionEntryProberspRetries INTEGER
}

-- {COLUMN} 310.2.23.20.2.1.1
lcsSetupInterfacesWlanTransmissionEntryIfc OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-write
    STATUS     current
    DESCRIPTION
        "-- empty --"
    ::= { lcsSetupInterfacesWlanTransmissionEntry 1 }

-- {COLUMN} 310.2.23.20.2.1.2
lcsSetupInterfacesWlanTransmissionEntryPacketSize OBJECT-TYPE
    SYNTAX     INTEGER (0..65535)
    MAX-ACCESS read-write
    STATUS     current
    DESCRIPTION
        "-- empty --"
    ::= { lcsSetupInterfacesWlanTransmissionEntry 2 }

-- {COLUMN} 310.2.23.20.2.1.3
lcsSetupInterfacesWlanTransmissionEntryMinTxRate OBJECT-TYPE
    SYNTAX     INTEGER
      {
        eAuto (0),
        e1M (1), -- 1Mbit/s
        e2M (2), -- 2Mbit/s
        e5M5 (4), -- 5.5Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15) -- 54Mbit/s
      }
    MAX-ACCESS read-write
    STATUS     current
    DESCRIPTION
        "-- empty --"
    ::= { lcsSetupInterfacesWlanTransmissionEntry 3 }

-- {COLUMN} 310.2.23.20.2.1.9
lcsSetupInterfacesWlanTransmissionEntryMaxTxRate OBJECT-TYPE
    SYNTAX     INTEGER
      {
        eAuto (0),
        e1M (1), -- 1Mbit/s
        e2M (2), -- 2Mbit/s
        e5M5 (4), -- 5.5Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15) -- 54Mbit/s
      }
    MAX-ACCESS read-write
    STATUS     current
    DESCRIPTION
        "-- empty --"
    ::= { lcsSetupInterfacesWlanTransmissionEntry 9 }

-- {COLUMN} 310.2.23.20.2.1.4
lcsSetupInterfacesWlanTransmissionEntryBasicRate OBJECT-TYPE
    SYNTAX     INTEGER
      {
        e1M (1), -- 1Mbit/s
        e2M (2), -- 2Mbit/s
        e5M5 (4), -- 5.5Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15) -- 54Mbit/s
      }
    MAX-ACCESS read-write
    STATUS     current
    DESCRIPTION
        "-- empty --"
    ::= { lcsSetupInterfacesWlanTransmissionEntry 4 }

-- {COLUMN} 310.2.23.20.2.1.19
lcsSetupInterfacesWlanTransmissionEntryEapolRate OBJECT-TYPE
    SYNTAX     INTEGER
      {
        eLikeData (0),
        e1M (1), -- 1Mbit/s
        e2M (2), -- 2Mbit/s
        e5M5 (4), -- 5.5Mbit/s
        e11M (6), -- 11Mbit/s
        e6M (8), -- 6Mbit/s
        e9M (9), -- 9Mbit/s
        e12M (10), -- 12Mbit/s
        e18M (11), -- 18Mbit/s
        e24M (12), -- 24Mbit/s
        e36M (13), -- 36Mbit/s
        e48M (14), -- 48Mbit/s
        e54M (15), -- 54Mbit/s
        eHT1S6M5 (28), -- High throughput 1 stream 6.5Mbit/s
        eHT1S13M (29), -- High throughput 1 stream 13Mbit/s
        eHT1S19M5 (30), -- High throughput 1 stream 19.5Mbit/s
        eHT1S26M (31), -- High throughput 1 stream 26Mbit/s
        eHT1S39M (32), -- High throughput 1 stream 39Mbit/s
        eHT1S52M (33), -- High throughput 1 stream 52Mbit/s
        eHT1S58M5 (34), -- High throughput 1 stream 58.5Mbit/s
        eHT1S65M (35), -- High throughput 1 stream 65Mbit/s
        eHT2S13M (36), -- High throughput 2 streams 13Mbit/s
        eHT2S26M (37), -- High throughput 2 streams 26Mbit/s
        eHT2S39M (38), -- High throughput 2 streams 39Mbit/s
        eHT2S52M (39), -- High throughput 2 streams 52Mbit/s
        eHT2S78M (40), -- High throughput 2 streams 78Mbit/s
        eHT2S104M (41), -- High throughput 2 streams 104Mbit/s
        eHT2S117M (42), -- High throughput 2 streams 117Mbit/s
        eHT2S130M (43) -- High throughput 2 streams 130Mbit/s
      }
    MAX-ACCESS read-write
    STATUS     current
    DESCRIPTION
        "-- empty --"
    ::= { lcsSetupInterfacesWlanTransmissionEntry 19 }

-- {COLUMN} 310.2.23.20.2.1.12
lcsSetupInterfacesWlanTransmissionEntryHardRetries OBJECT-TYPE
    SYNTAX     INTEGER (0..255)
    MAX-ACCESS read-write
    STATUS     current
    DESCRIPTION
        "-- empty --"
    ::= { lcsSetupInterfacesWlanTransmissionEntry 12 }

-- {COLUMN} 310.2.23.20.2.1.11
lcsSetupInterfacesWlanTransmissionEntrySoftRetries OBJECT-TYPE
    SYNTAX     INTEGER (0..255)
    MAX-ACCESS read-write
    STATUS     current
    DESCRIPTION
        "-- empty --"
    ::= { lcsSetupInterfacesWlanTransmissionEntry 11 }

-- {COLUMN} 310.2.23.20.2.1.7
lcsSetupInterfacesWlanTransmissionEntry11bPreamble OBJECT-TYPE
    SYNTAX     INTEGER
      {
        eAuto (0),
        eLong (1)
      }
    MAX-ACCESS read-write
    STATUS     current
    DESCRIPTION
        "-- empty --"
    ::= { lcsSetupInterfacesWlanTransmissionEntry 7 }

-- {COLUMN} 310.2.23.20.2.1.16
lcsSetupInterfacesWlanTransmissionEntryMinHtMcs OBJECT-TYPE
    SYNTAX     INTEGER
      {
        eAuto (0),
        eMcs08 (1),
        eMcs19 (2),
        eMcs210 (3),
        eMcs311 (4),
        eMcs412 (5),
        eMcs513 (6),
        eMcs614 (7),
        eMcs715 (8)
      }
    MAX-ACCESS read-write
    STATUS     current
    DESCRIPTION
        "-- empty --"
    ::= { lcsSetupInterfacesWlanTransmissionEntry 16 }

-- {COLUMN} 310.2.23.20.2.1.17
lcsSetupInterfacesWlanTransmissionEntryMaxHtMcs OBJECT-TYPE
    SYNTAX     INTEGER
      {
        eAuto (0),
        eMcs08 (1),
        eMcs19 (2),
        eMcs210 (3),
        eMcs311 (4),
        eMcs412 (5),
        eMcs513 (6),
        eMcs614 (7),
        eMcs715 (8)
      }
    MAX-ACCESS read-write
    STATUS     current
    DESCRIPTION
        "-- empty --"
    ::= { lcsSetupInterfacesWlanTransmissionEntry 17 }

-- {COLUMN} 310.2.23.20.2.1.13
lcsSetupInterfacesWlanTransmissionEntryShortGuardInterval OBJECT-TYPE
    SYNTAX     INTEGER
      {
        eAuto (0),
        eNo (1)
      }
    MAX-ACCESS read-write
    STATUS     current
    DESCRIPTION
        "-- empty --"
    ::= { lcsSetupInterfacesWlanTransmissionEntry 13 }

-- {COLUMN} 310.2.23.20.2.1.18
lcsSetupInterfacesWlanTransmissionEntryMinSpatialStreams OBJECT-TYPE
    SYNTAX     INTEGER
      {
        eAuto (0),
        eOne (1),
        eTwo (2)
      }
    MAX-ACCESS read-write
    STATUS     current
    DESCRIPTION
        "-- empty --"
    ::= { lcsSetupInterfacesWlanTransmissionEntry 18 }

-- {COLUMN} 310.2.23.20.2.1.14
lcsSetupInterfacesWlanTransmissionEntryMaxSpatialStreams OBJECT-TYPE
    SYNTAX     INTEGER
      {
        eAuto (0),
        eOne (1),
        eTwo (2)
      }
    MAX-ACCESS read-write
    STATUS     current
    DESCRIPTION
        "-- empty --"
    ::= { lcsSetupInterfacesWlanTransmissionEntry 14 }

-- {COLUMN} 310.2.23.20.2.1.15
lcsSetupInterfacesWlanTransmissionEntrySendAggregates OBJECT-TYPE
    SYNTAX     INTEGER
      {
        eNo (0),
        eYes (1)
      }
    MAX-ACCESS read-write
    STATUS     current
    DESCRIPTION
        "-- empty --"
    ::= { lcsSetupInterfacesWlanTransmissionEntry 15 }

-- {COLUMN} 310.2.23.20.2.1.22
lcsSetupInterfacesWlanTransmissionEntryReceiveAggregates OBJECT-TYPE
    SYNTAX     INTEGER
      {
        eNo (0),
        eYes (1)
      }
    MAX-ACCESS read-write
    STATUS     current
    DESCRIPTION
        "-- empty --"
    ::= { lcsSetupInterfacesWlanTransmissionEntry 22 }

-- {COLUMN} 310.2.23.20.2.1.20
lcsSetupInterfacesWlanTransmissionEntryMaxAggrPacketCount OBJECT-TYPE
    SYNTAX     INTEGER (0..255)
    MAX-ACCESS read-write
    STATUS     current
    DESCRIPTION
        "-- empty --"
    ::= { lcsSetupInterfacesWlanTransmissionEntry 20 }

-- {COLUMN} 310.2.23.20.2.1.6
lcsSetupInterfacesWlanTransmissionEntryRtsThreshold OBJECT-TYPE
    SYNTAX     INTEGER (0..65535)
    MAX-ACCESS read-write
    STATUS     current
    DESCRIPTION
        "-- empty --"
    ::= { lcsSetupInterfacesWlanTransmissionEntry 6 }

-- {COLUMN} 310.2.23.20.2.1.10
lcsSetupInterfacesWlanTransmissionEntryMinFragLen OBJECT-TYPE
    SYNTAX     INTEGER (0..65535)
    MAX-ACCESS read-write
    STATUS     current
    DESCRIPTION
        "-- empty --"
    ::= { lcsSetupInterfacesWlanTransmissionEntry 10 }

-- {COLUMN} 310.2.23.20.2.1.21
lcsSetupInterfacesWlanTransmissionEntryProberspRetries OBJECT-TYPE
    SYNTAX     INTEGER (0..255)
    MAX-ACCESS read-write
    STATUS     current
    DESCRIPTION
        "-- empty --"
    ::= { lcsSetupInterfacesWlanTransmissionEntry 21 }

-- {TABLE} 310.2.23.20.13
lcsSetupInterfacesWlanNetworkAlarmLimitsTable OBJECT-TYPE
    SYNTAX     SEQUENCE OF LcsSetupInterfacesWlanNetworkAlarmLimitsEntry
    MAX-ACCESS not-accessible
    STATUS     current
    DESCRIPTION
        "-- empty --"
    ::= { lcsSetupInterfacesWlan 13 }

-- {ENTRY} 310.2.23.20.13.1
lcsSetupInterfacesWlanNetworkAlarmLimitsEntry OBJECT-TYPE
    SYNTAX     LcsSetupInterfacesWlanNetworkAlarmLimitsEntry
    MAX-ACCESS not-accessible
    STATUS     current
    DESCRIPTION
        ""
    INDEX {
        lcsSetupInterfacesWlanNetworkAlarmLimitsEntryIfc
    }
    ::= { lcsSetupInterfacesWlanNetworkAlarmLimitsTable 1 }

-- {SEQUENCE}
LcsSetupInterfacesWlanNetworkAlarmLimitsEntry ::= SEQUENCE {
    lcsSetupInterfacesWlanNetworkAlarmLimitsEntryIfc INTEGER,
    lcsSetupInterfacesWlanNetworkAlarmLimitsEntryPhySignal INTEGER,
    lcsSetupInterfacesWlanNetworkAlarmLimitsEntryTotalRetries INTEGER,
    lcsSetupInterfacesWlanNetworkAlarmLimitsEntryTxErrors INTEGER
}

-- {COLUMN} 310.2.23.20.13.1.1
lcsSetupInterfacesWlanNetworkAlarmLimitsEntryIfc OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-write
    STATUS     current
    DESCRIPTION
        "-- empty --"
    ::= { lcsSetupInterfacesWlanNetworkAlarmLimitsEntry 1 }

-- {COLUMN} 310.2.23.20.13.1.2
lcsSetupInterfacesWlanNetworkAlarmLimitsEntryPhySignal OBJECT-TYPE
    SYNTAX     INTEGER (0..65535)
    MAX-ACCESS read-write
    STATUS     current
    DESCRIPTION
        "-- empty --"
    ::= { lcsSetupInterfacesWlanNetworkAlarmLimitsEntry 2 }

-- {COLUMN} 310.2.23.20.13.1.3
lcsSetupInterfacesWlanNetworkAlarmLimitsEntryTotalRetries OBJECT-TYPE
    SYNTAX     INTEGER (0..65535)
    MAX-ACCESS read-write
    STATUS     current
    DESCRIPTION
        "-- empty --"
    ::= { lcsSetupInterfacesWlanNetworkAlarmLimitsEntry 3 }

-- {COLUMN} 310.2.23.20.13.1.4
lcsSetupInterfacesWlanNetworkAlarmLimitsEntryTxErrors OBJECT-TYPE
    SYNTAX     INTEGER (0..65535)
    MAX-ACCESS read-write
    STATUS     current
    DESCRIPTION
        "-- empty --"
    ::= { lcsSetupInterfacesWlanNetworkAlarmLimitsEntry 4 }

-- {TABLE} 310.2.23.20.9
lcsSetupInterfacesWlanPerformanceTable OBJECT-TYPE
    SYNTAX     SEQUENCE OF LcsSetupInterfacesWlanPerformanceEntry
    MAX-ACCESS not-accessible
    STATUS     current
    DESCRIPTION
        "-- empty --"
    ::= { lcsSetupInterfacesWlan 9 }

-- {ENTRY} 310.2.23.20.9.1
lcsSetupInterfacesWlanPerformanceEntry OBJECT-TYPE
    SYNTAX     LcsSetupInterfacesWlanPerformanceEntry
    MAX-ACCESS not-accessible
    STATUS     current
    DESCRIPTION
        ""
    INDEX {
        lcsSetupInterfacesWlanPerformanceEntryIfc
    }
    ::= { lcsSetupInterfacesWlanPerformanceTable 1 }

-- {SEQUENCE}
LcsSetupInterfacesWlanPerformanceEntry ::= SEQUENCE {
    lcsSetupInterfacesWlanPerformanceEntryIfc INTEGER,
    lcsSetupInterfacesWlanPerformanceEntryQos INTEGER,
    lcsSetupInterfacesWlanPerformanceEntryTxBursting INTEGER
}

-- {COLUMN} 310.2.23.20.9.1.1
lcsSetupInterfacesWlanPerformanceEntryIfc OBJECT-TYPE
    SYNTAX     INTEGER
      {
        eWlan1 (1)
      }
    MAX-ACCESS read-write
    STATUS     current
    DESCRIPTION
        "-- empty --"
    ::= { lcsSetupInterfacesWlanPerformanceEntry 1 }

-- {COLUMN} 310.2.23.20.9.1.5
lcsSetupInterfacesWlanPerformanceEntryQos OBJECT-TYPE
    SYNTAX     INTEGER
      {
        eNo (0),
        eYes (1)
      }
    MAX-ACCESS read-write
    STATUS     current
    DESCRIPTION
        "-- empty --"
    ::= { lcsSetupInterfacesWlanPerformanceEntry 5 }

-- {COLUMN} 310.2.23.20.9.1.2
lcsSetupInterfacesWlanPerformanceEntryTxBursting OBJECT-TYPE
    SYNTAX     INTEGER (0..65535)
    MAX-ACCESS read-write
    STATUS     current
    DESCRIPTION
        "-- empty --"
    ::= { lcsSetupInterfacesWlanPerformanceEntry 2 }

-- {TABLE} 310.2.23.20.3
lcsSetupInterfacesWlanEncryptionTable OBJECT-TYPE
    SYNTAX     SEQUENCE OF LcsSetupInterfacesWlanEncryptionEntry
    MAX-ACCESS not-accessible
    STATUS     current
    DESCRIPTION
        "-- empty --"
    ::= { lcsSetupInterfacesWlan 3 }

-- {ENTRY} 310.2.23.20.3.1
lcsSetupInterfacesWlanEncryptionEntry OBJECT-TYPE
    SYNTAX     LcsSetupInterfacesWlanEncryptionEntry
    MAX-ACCESS not-accessible
    STATUS     current
    DESCRIPTION
        ""
    INDEX {
        lcsSetupInterfacesWlanEncryptionEntryIfc
    }
    ::= { lcsSetupInterfacesWlanEncryptionTable 1 }

-- {SEQUENCE}
LcsSetupInterfacesWlanEncryptionEntry ::= SEQUENCE {
    lcsSetupInterfacesWlanEncryptionEntryIfc INTEGER,
    lcsSetupInterfacesWlanEncryptionEntryEncryption INTEGER,
    lcsSetupInterfacesWlanEncryptionEntryDefaultKey INTEGER,
    lcsSetupInterfacesWlanEncryptionEntryMethod INTEGER,
    lcsSetupInterfacesWlanEncryptionEntryKey DisplayString,
    lcsSetupInterfacesWlanEncryptionEntryWpaVersion INTEGER,
    lcsSetupInterfacesWlanEncryptionEntryWpa1SessionKeytypes INTEGER,
    lcsSetupInterfacesWlanEncryptionEntryWpa2SessionKeytypes INTEGER,
    lcsSetupInterfacesWlanEncryptionEntryWpaRekeyingCycle INTEGER,
    lcsSetupInterfacesWlanEncryptionEntryClientEapMethod INTEGER,
    lcsSetupInterfacesWlanEncryptionEntryPmkCaching INTEGER,
    lcsSetupInterfacesWlanEncryptionEntryPreAuthentication INTEGER,
    lcsSetupInterfacesWlanEncryptionEntryAuthentication INTEGER
}

-- {COLUMN} 310.2.23.20.3.1.1
lcsSetupInterfacesWlanEncryptionEntryIfc OBJECT-TYPE
    SYNTAX     INTEGER
      {
        eWlan1 (1),
        eWlan12 (16),
        eWlan13 (17),
        eWlan14 (18),
        eWlan15 (19),
        eWlan16 (20),
        eWlan17 (21),
        eWlan18 (22)
      }
    MAX-ACCESS read-write
    STATUS     current
    DESCRIPTION
        "-- empty --"
    ::= { lcsSetupInterfacesWlanEncryptionEntry 1 }

-- {COLUMN} 310.2.23.20.3.1.2
lcsSetupInterfacesWlanEncryptionEntryEncryption OBJECT-TYPE
    SYNTAX     INTEGER
      {
        eNo (0),
        eYes (2)
      }
    MAX-ACCESS read-write
    STATUS     current
    DESCRIPTION
        "-- empty --"
    ::= { lcsSetupInterfacesWlanEncryptionEntry 2 }

-- {COLUMN} 310.2.23.20.3.1.3
lcsSetupInterfacesWlanEncryptionEntryDefaultKey OBJECT-TYPE
    SYNTAX     INTEGER (0..255)
    MAX-ACCESS read-write
    STATUS     current
    DESCRIPTION
        "-- empty --"
    ::= { lcsSetupInterfacesWlanEncryptionEntry 3 }

-- {COLUMN} 310.2.23.20.3.1.4
lcsSetupInterfacesWlanEncryptionEntryMethod OBJECT-TYPE
    SYNTAX     INTEGER
      {
        e80211iWpaPsk (32),
        eWep128Bits (16),
        eWep104Bits (13),
        eWep40Bits (5),
        e80211iWpa8021x (33),
        eWep128Bits8021x (36),
        eWep104Bits8021x (35),
        eWep40Bits8021x (34)
      }
    MAX-ACCESS read-write
    STATUS     current
    DESCRIPTION
        "-- empty --"
    ::= { lcsSetupInterfacesWlanEncryptionEntry 4 }

-- {COLUMN} 310.2.23.20.3.1.6
lcsSetupInterfacesWlanEncryptionEntryKey OBJECT-TYPE
    SYNTAX     DisplayString (SIZE(0..63))
    MAX-ACCESS read-write
    STATUS     current
    DESCRIPTION
        "-- empty --"
    ::= { lcsSetupInterfacesWlanEncryptionEntry 6 }

-- {COLUMN} 310.2.23.20.3.1.9
lcsSetupInterfacesWlanEncryptionEntryWpaVersion OBJECT-TYPE
    SYNTAX     INTEGER
      {
        eWpa1 (2),
        eWpa2 (4),
        eWpa12 (6)
      }
    MAX-ACCESS read-write
    STATUS     current
    DESCRIPTION
        "-- empty --"
    ::= { lcsSetupInterfacesWlanEncryptionEntry 9 }

-- {COLUMN} 310.2.23.20.3.1.12
lcsSetupInterfacesWlanEncryptionEntryWpa1SessionKeytypes OBJECT-TYPE
    SYNTAX     INTEGER
      {
        eTkip (1),
        eAes (2),
        eTkipAes (3)
      }
    MAX-ACCESS read-write
    STATUS     current
    DESCRIPTION
        "-- empty --"
    ::= { lcsSetupInterfacesWlanEncryptionEntry 12 }

-- {COLUMN} 310.2.23.20.3.1.13
lcsSetupInterfacesWlanEncryptionEntryWpa2SessionKeytypes OBJECT-TYPE
    SYNTAX     INTEGER
      {
        eTkip (1),
        eAes (2),
        eTkipAes (3)
      }
    MAX-ACCESS read-write
    STATUS     current
    DESCRIPTION
        "-- empty --"
    ::= { lcsSetupInterfacesWlanEncryptionEntry 13 }

-- {COLUMN} 310.2.23.20.3.1.11
lcsSetupInterfacesWlanEncryptionEntryWpaRekeyingCycle OBJECT-TYPE
    SYNTAX     INTEGER (0..2147483647)
    MAX-ACCESS read-write
    STATUS     current
    DESCRIPTION
        "-- empty --"
    ::= { lcsSetupInterfacesWlanEncryptionEntry 11 }

-- {COLUMN} 310.2.23.20.3.1.10
lcsSetupInterfacesWlanEncryptionEntryClientEapMethod OBJECT-TYPE
    SYNTAX     INTEGER
      {
        eTls (3328),
        eTtlsPap (5383),
        eTtlsChap (5384),
        eTtlsMschap (5567),
        eTtlsMschapv2 (5402),
        eTtlsMd5 (5380),
        ePeapMschapv2 (6426),
        ePeapGtc (6406)
      }
    MAX-ACCESS read-write
    STATUS     current
    DESCRIPTION
        "-- empty --"
    ::= { lcsSetupInterfacesWlanEncryptionEntry 10 }

-- {COLUMN} 310.2.23.20.3.1.15
lcsSetupInterfacesWlanEncryptionEntryPmkCaching OBJECT-TYPE
    SYNTAX     INTEGER
      {
        eNo (0),
        eYes (1)
      }
    MAX-ACCESS read-write
    STATUS     current
    DESCRIPTION
        "-- empty --"
    ::= { lcsSetupInterfacesWlanEncryptionEntry 15 }

-- {COLUMN} 310.2.23.20.3.1.16
lcsSetupInterfacesWlanEncryptionEntryPreAuthentication OBJECT-TYPE
    SYNTAX     INTEGER
      {
        eNo (0),
        eYes (1)
      }
    MAX-ACCESS read-write
    STATUS     current
    DESCRIPTION
        "-- empty --"
    ::= { lcsSetupInterfacesWlanEncryptionEntry 16 }

-- {COLUMN} 310.2.23.20.3.1.5
lcsSetupInterfacesWlanEncryptionEntryAuthentication OBJECT-TYPE
    SYNTAX     INTEGER
      {
        eOpenSystem (0),
        eSharedKey (1)
      }
    MAX-ACCESS read-write
    STATUS     current
    DESCRIPTION
        "-- empty --"
    ::= { lcsSetupInterfacesWlanEncryptionEntry 5 }

-- {TABLE} 310.2.23.20.4
lcsSetupInterfacesWlanGroupEncryptionKeysTable OBJECT-TYPE
    SYNTAX     SEQUENCE OF LcsSetupInterfacesWlanGroupEncryptionKeysEntry
    MAX-ACCESS not-accessible
    STATUS     current
    DESCRIPTION
        "-- empty --"
    ::= { lcsSetupInterfacesWlan 4 }

-- {ENTRY} 310.2.23.20.4.1
lcsSetupInterfacesWlanGroupEncryptionKeysEntry OBJECT-TYPE
    SYNTAX     LcsSetupInterfacesWlanGroupEncryptionKeysEntry
    MAX-ACCESS not-accessible
    STATUS     current
    DESCRIPTION
        ""
    INDEX {
        lcsSetupInterfacesWlanGroupEncryptionKeysEntryIfc
    }
    ::= { lcsSetupInterfacesWlanGroupEncryptionKeysTable 1 }

-- {SEQUENCE}
LcsSetupInterfacesWlanGroupEncryptionKeysEntry ::= SEQUENCE {
    lcsSetupInterfacesWlanGroupEncryptionKeysEntryIfc INTEGER,
    lcsSetupInterfacesWlanGroupEncryptionKeysEntryKeytype2 INTEGER,
    lcsSetupInterfacesWlanGroupEncryptionKeysEntryKey2 DisplayString,
    lcsSetupInterfacesWlanGroupEncryptionKeysEntryKeytype3 INTEGER,
    lcsSetupInterfacesWlanGroupEncryptionKeysEntryKey3 DisplayString,
    lcsSetupInterfacesWlanGroupEncryptionKeysEntryKeytype4 INTEGER,
    lcsSetupInterfacesWlanGroupEncryptionKeysEntryKey4 DisplayString
}

-- {COLUMN} 310.2.23.20.4.1.1
lcsSetupInterfacesWlanGroupEncryptionKeysEntryIfc OBJECT-TYPE
    SYNTAX     INTEGER
      {
        eWlan1 (1)
      }
    MAX-ACCESS read-write
    STATUS     current
    DESCRIPTION
        "-- empty --"
    ::= { lcsSetupInterfacesWlanGroupEncryptionKeysEntry 1 }

-- {COLUMN} 310.2.23.20.4.1.7
lcsSetupInterfacesWlanGroupEncryptionKeysEntryKeytype2 OBJECT-TYPE
    SYNTAX     INTEGER
      {
        eWep40Bits (5),
        eWep104Bits (13),
        eWep128Bits (16)
      }
    MAX-ACCESS read-write
    STATUS     current
    DESCRIPTION
        "-- empty --"
    ::= { lcsSetupInterfacesWlanGroupEncryptionKeysEntry 7 }

-- {COLUMN} 310.2.23.20.4.1.3
lcsSetupInterfacesWlanGroupEncryptionKeysEntryKey2 OBJECT-TYPE
    SYNTAX     DisplayString (SIZE(0..63))
    MAX-ACCESS read-write
    STATUS     current
    DESCRIPTION
        "-- empty --"
    ::= { lcsSetupInterfacesWlanGroupEncryptionKeysEntry 3 }

-- {COLUMN} 310.2.23.20.4.1.8
lcsSetupInterfacesWlanGroupEncryptionKeysEntryKeytype3 OBJECT-TYPE
    SYNTAX     INTEGER
      {
        eWep40Bits (5),
        eWep104Bits (13),
        eWep128Bits (16)
      }
    MAX-ACCESS read-write
    STATUS     current
    DESCRIPTION
        "-- empty --"
    ::= { lcsSetupInterfacesWlanGroupEncryptionKeysEntry 8 }

-- {COLUMN} 310.2.23.20.4.1.4
lcsSetupInterfacesWlanGroupEncryptionKeysEntryKey3 OBJECT-TYPE
    SYNTAX     DisplayString (SIZE(0..63))
    MAX-ACCESS read-write
    STATUS     current
    DESCRIPTION
        "-- empty --"
    ::= { lcsSetupInterfacesWlanGroupEncryptionKeysEntry 4 }

-- {COLUMN} 310.2.23.20.4.1.9
lcsSetupInterfacesWlanGroupEncryptionKeysEntryKeytype4 OBJECT-TYPE
    SYNTAX     INTEGER
      {
        eWep40Bits (5),
        eWep104Bits (13),
        eWep128Bits (16)
      }
    MAX-ACCESS read-write
    STATUS     current
    DESCRIPTION
        "-- empty --"
    ::= { lcsSetupInterfacesWlanGroupEncryptionKeysEntry 9 }

-- {COLUMN} 310.2.23.20.4.1.5
lcsSetupInterfacesWlanGroupEncryptionKeysEntryKey4 OBJECT-TYPE
    SYNTAX     DisplayString (SIZE(0..63))
    MAX-ACCESS read-write
    STATUS     current
    DESCRIPTION
        "-- empty --"
    ::= { lcsSetupInterfacesWlanGroupEncryptionKeysEntry 5 }

-- {TABLE} 310.2.23.20.5
lcsSetupInterfacesWlanIntpntSetTable OBJECT-TYPE
    SYNTAX     SEQUENCE OF LcsSetupInterfacesWlanIntpntSetEntry
    MAX-ACCESS not-accessible
    STATUS     current
    DESCRIPTION
        ""
    ::= { lcsSetupInterfacesWlan 5 }

-- {ENTRY} 310.2.23.20.5.1
lcsSetupInterfacesWlanIntpntSetEntry OBJECT-TYPE
    SYNTAX     LcsSetupInterfacesWlanIntpntSetEntry
    MAX-ACCESS not-accessible
    STATUS     current
    DESCRIPTION
        ""
    INDEX {
        lcsSetupInterfacesWlanIntpntSetEntryIfc
    }
    ::= { lcsSetupInterfacesWlanIntpntSetTable 1 }

-- {SEQUENCE}
LcsSetupInterfacesWlanIntpntSetEntry ::= SEQUENCE {
    lcsSetupInterfacesWlanIntpntSetEntryIfc INTEGER,
    lcsSetupInterfacesWlanIntpntSetEntryEnable INTEGER,
    lcsSetupInterfacesWlanIntpntSetEntryLocalName DisplayString,
    lcsSetupInterfacesWlanIntpntSetEntryIsolatedMode INTEGER,
    lcsSetupInterfacesWlanIntpntSetEntryChanSelScheme INTEGER,
    lcsSetupInterfacesWlanIntpntSetEntryKeyHandshakeRole INTEGER,
    lcsSetupInterfacesWlanIntpntSetEntryLinkLossTimeout INTEGER
}

-- {COLUMN} 310.2.23.20.5.1.1
lcsSetupInterfacesWlanIntpntSetEntryIfc OBJECT-TYPE
    SYNTAX     INTEGER
      {
        eWlan1 (1)
      }
    MAX-ACCESS read-write
    STATUS     current
    DESCRIPTION
        "-- empty --"
    ::= { lcsSetupInterfacesWlanIntpntSetEntry 1 }

-- {COLUMN} 310.2.23.20.5.1.2
lcsSetupInterfacesWlanIntpntSetEntryEnable OBJECT-TYPE
    SYNTAX     INTEGER
      {
        eNo (0),
        eYes (1),
        eExclusive (2)
      }
    MAX-ACCESS read-write
    STATUS     current
    DESCRIPTION
        "-- empty --"
    ::= { lcsSetupInterfacesWlanIntpntSetEntry 2 }

-- {COLUMN} 310.2.23.20.5.1.13
lcsSetupInterfacesWlanIntpntSetEntryLocalName OBJECT-TYPE
    SYNTAX     DisplayString (SIZE(0..16))
    MAX-ACCESS read-write
    STATUS     current
    DESCRIPTION
        "-- empty --"
    ::= { lcsSetupInterfacesWlanIntpntSetEntry 13 }

-- {COLUMN} 310.2.23.20.5.1.9
lcsSetupInterfacesWlanIntpntSetEntryIsolatedMode OBJECT-TYPE
    SYNTAX     INTEGER
      {
        eNo (0),
        eYes (1)
      }
    MAX-ACCESS read-write
    STATUS     current
    DESCRIPTION
        "-- empty --"
    ::= { lcsSetupInterfacesWlanIntpntSetEntry 9 }

-- {COLUMN} 310.2.23.20.5.1.10
lcsSetupInterfacesWlanIntpntSetEntryChanSelScheme OBJECT-TYPE
    SYNTAX     INTEGER
      {
        eMaster (0),
        eSlave (1)
      }
    MAX-ACCESS read-write
    STATUS     current
    DESCRIPTION
        ""
    ::= { lcsSetupInterfacesWlanIntpntSetEntry 10 }

-- {COLUMN} 310.2.23.20.5.1.12
lcsSetupInterfacesWlanIntpntSetEntryKeyHandshakeRole OBJECT-TYPE
    SYNTAX     INTEGER
      {
        eDefault (0),
        eAuto (3)
      }
    MAX-ACCESS read-write
    STATUS     current
    DESCRIPTION
        "-- empty --"
    ::= { lcsSetupInterfacesWlanIntpntSetEntry 12 }

-- {COLUMN} 310.2.23.20.5.1.11
lcsSetupInterfacesWlanIntpntSetEntryLinkLossTimeout OBJECT-TYPE
    SYNTAX     INTEGER (0..2147483647)
    MAX-ACCESS read-write
    STATUS     current
    DESCRIPTION
        "-- empty --"
    ::= { lcsSetupInterfacesWlanIntpntSetEntry 11 }

-- {TABLE} 310.2.23.20.12
lcsSetupInterfacesWlanIntpntPeersTable OBJECT-TYPE
    SYNTAX     SEQUENCE OF LcsSetupInterfacesWlanIntpntPeersEntry
    MAX-ACCESS not-accessible
    STATUS     current
    DESCRIPTION
        ""
    ::= { lcsSetupInterfacesWlan 12 }

-- {ENTRY} 310.2.23.20.12.1
lcsSetupInterfacesWlanIntpntPeersEntry OBJECT-TYPE
    SYNTAX     LcsSetupInterfacesWlanIntpntPeersEntry
    MAX-ACCESS not-accessible
    STATUS     current
    DESCRIPTION
        ""
    INDEX {
        lcsSetupInterfacesWlanIntpntPeersEntryIfc
    }
    ::= { lcsSetupInterfacesWlanIntpntPeersTable 1 }

-- {SEQUENCE}
LcsSetupInterfacesWlanIntpntPeersEntry ::= SEQUENCE {
    lcsSetupInterfacesWlanIntpntPeersEntryIfc INTEGER,
    lcsSetupInterfacesWlanIntpntPeersEntryOperating INTEGER,
    lcsSetupInterfacesWlanIntpntPeersEntryRecognizeBy INTEGER,
    lcsSetupInterfacesWlanIntpntPeersEntryMacAddress MacAddress,
    lcsSetupInterfacesWlanIntpntPeersEntryPeerName DisplayString,
    lcsSetupInterfacesWlanIntpntPeersEntryTxLimit INTEGER,
    lcsSetupInterfacesWlanIntpntPeersEntryRxLimit INTEGER,
    lcsSetupInterfacesWlanIntpntPeersEntryConnectThreshold INTEGER,
    lcsSetupInterfacesWlanIntpntPeersEntryConnectHoldThreshold INTEGER
}

-- {COLUMN} 310.2.23.20.12.1.1
lcsSetupInterfacesWlanIntpntPeersEntryIfc OBJECT-TYPE
    SYNTAX     INTEGER
      {
        eP2p11 (1),
        eP2p12 (2),
        eP2p13 (3),
        eP2p14 (4),
        eP2p15 (5),
        eP2p16 (6),
        eP2p17 (32),
        eP2p18 (33),
        eP2p19 (34),
        eP2p110 (35),
        eP2p111 (36),
        eP2p112 (37),
        eP2p113 (38),
        eP2p114 (39),
        eP2p115 (40),
        eP2p116 (41)
      }
    MAX-ACCESS read-write
    STATUS     current
    DESCRIPTION
        "-- empty --"
    ::= { lcsSetupInterfacesWlanIntpntPeersEntry 1 }

-- {COLUMN} 310.2.23.20.12.1.5
lcsSetupInterfacesWlanIntpntPeersEntryOperating OBJECT-TYPE
    SYNTAX     INTEGER
      {
        eNo (0),
        eYes (1)
      }
    MAX-ACCESS read-write
    STATUS     current
    DESCRIPTION
        "-- empty --"
    ::= { lcsSetupInterfacesWlanIntpntPeersEntry 5 }

-- {COLUMN} 310.2.23.20.12.1.2
lcsSetupInterfacesWlanIntpntPeersEntryRecognizeBy OBJECT-TYPE
    SYNTAX     INTEGER
      {
        eMacAddress (0),
        eName (1)
      }
    MAX-ACCESS read-write
    STATUS     current
    DESCRIPTION
        "-- empty --"
    ::= { lcsSetupInterfacesWlanIntpntPeersEntry 2 }

-- {COLUMN} 310.2.23.20.12.1.3
lcsSetupInterfacesWlanIntpntPeersEntryMacAddress OBJECT-TYPE
    SYNTAX     MacAddress
    MAX-ACCESS read-write
    STATUS     current
    DESCRIPTION
        "-- empty --"
    ::= { lcsSetupInterfacesWlanIntpntPeersEntry 3 }

-- {COLUMN} 310.2.23.20.12.1.4
lcsSetupInterfacesWlanIntpntPeersEntryPeerName OBJECT-TYPE
    SYNTAX     DisplayString (SIZE(0..16))
    MAX-ACCESS read-write
    STATUS     current
    DESCRIPTION
        "-- empty --"
    ::= { lcsSetupInterfacesWlanIntpntPeersEntry 4 }

-- {COLUMN} 310.2.23.20.12.1.6
lcsSetupInterfacesWlanIntpntPeersEntryTxLimit OBJECT-TYPE
    SYNTAX     INTEGER (0..2147483647)
    MAX-ACCESS read-write
    STATUS     current
    DESCRIPTION
        "-- empty --"
    ::= { lcsSetupInterfacesWlanIntpntPeersEntry 6 }

-- {COLUMN} 310.2.23.20.12.1.7
lcsSetupInterfacesWlanIntpntPeersEntryRxLimit OBJECT-TYPE
    SYNTAX     INTEGER (0..2147483647)
    MAX-ACCESS read-write
    STATUS     current
    DESCRIPTION
        "-- empty --"
    ::= { lcsSetupInterfacesWlanIntpntPeersEntry 7 }

-- {COLUMN} 310.2.23.20.12.1.9
lcsSetupInterfacesWlanIntpntPeersEntryConnectThreshold OBJECT-TYPE
    SYNTAX     INTEGER (0..255)
    MAX-ACCESS read-write
    STATUS     current
    DESCRIPTION
        "-- empty --"
    ::= { lcsSetupInterfacesWlanIntpntPeersEntry 9 }

-- {COLUMN} 310.2.23.20.12.1.10
lcsSetupInterfacesWlanIntpntPeersEntryConnectHoldThreshold OBJECT-TYPE
    SYNTAX     INTEGER (0..255)
    MAX-ACCESS read-write
    STATUS     current
    DESCRIPTION
        "-- empty --"
    ::= { lcsSetupInterfacesWlanIntpntPeersEntry 10 }

-- {TABLE} 310.2.23.20.14
lcsSetupInterfacesWlanInterpointAlarmLimitsTable OBJECT-TYPE
    SYNTAX     SEQUENCE OF LcsSetupInterfacesWlanInterpointAlarmLimitsEntry
    MAX-ACCESS not-accessible
    STATUS     current
    DESCRIPTION
        "-- empty --"
    ::= { lcsSetupInterfacesWlan 14 }

-- {ENTRY} 310.2.23.20.14.1
lcsSetupInterfacesWlanInterpointAlarmLimitsEntry OBJECT-TYPE
    SYNTAX     LcsSetupInterfacesWlanInterpointAlarmLimitsEntry
    MAX-ACCESS not-accessible
    STATUS     current
    DESCRIPTION
        ""
    INDEX {
        lcsSetupInterfacesWlanInterpointAlarmLimitsEntryIfc
    }
    ::= { lcsSetupInterfacesWlanInterpointAlarmLimitsTable 1 }

-- {SEQUENCE}
LcsSetupInterfacesWlanInterpointAlarmLimitsEntry ::= SEQUENCE {
    lcsSetupInterfacesWlanInterpointAlarmLimitsEntryIfc INTEGER,
    lcsSetupInterfacesWlanInterpointAlarmLimitsEntryPhySignal INTEGER,
    lcsSetupInterfacesWlanInterpointAlarmLimitsEntryTotalRetries INTEGER,
    lcsSetupInterfacesWlanInterpointAlarmLimitsEntryTxErrors INTEGER
}

-- {COLUMN} 310.2.23.20.14.1.1
lcsSetupInterfacesWlanInterpointAlarmLimitsEntryIfc OBJECT-TYPE
    SYNTAX     INTEGER
      {
        eP2p11 (1),
        eP2p12 (2),
        eP2p13 (3),
        eP2p14 (4),
        eP2p15 (5),
        eP2p16 (6),
        eP2p17 (32),
        eP2p18 (33),
        eP2p19 (34),
        eP2p110 (35),
        eP2p111 (36),
        eP2p112 (37),
        eP2p113 (38),
        eP2p114 (39),
        eP2p115 (40),
        eP2p116 (41)
      }
    MAX-ACCESS read-write
    STATUS     current
    DESCRIPTION
        "-- empty --"
    ::= { lcsSetupInterfacesWlanInterpointAlarmLimitsEntry 1 }

-- {COLUMN} 310.2.23.20.14.1.2
lcsSetupInterfacesWlanInterpointAlarmLimitsEntryPhySignal OBJECT-TYPE
    SYNTAX     INTEGER (0..65535)
    MAX-ACCESS read-write
    STATUS     current
    DESCRIPTION
        "-- empty --"
    ::= { lcsSetupInterfacesWlanInterpointAlarmLimitsEntry 2 }

-- {COLUMN} 310.2.23.20.14.1.3
lcsSetupInterfacesWlanInterpointAlarmLimitsEntryTotalRetries OBJECT-TYPE
    SYNTAX     INTEGER (0..65535)
    MAX-ACCESS read-write
    STATUS     current
    DESCRIPTION
        "-- empty --"
    ::= { lcsSetupInterfacesWlanInterpointAlarmLimitsEntry 3 }

-- {COLUMN} 310.2.23.20.14.1.4
lcsSetupInterfacesWlanInterpointAlarmLimitsEntryTxErrors OBJECT-TYPE
    SYNTAX     INTEGER (0..65535)
    MAX-ACCESS read-write
    STATUS     current
    DESCRIPTION
        "-- empty --"
    ::= { lcsSetupInterfacesWlanInterpointAlarmLimitsEntry 4 }

-- {TABLE} 310.2.23.20.10
lcsSetupInterfacesWlanBeaconingTable OBJECT-TYPE
    SYNTAX     SEQUENCE OF LcsSetupInterfacesWlanBeaconingEntry
    MAX-ACCESS not-accessible
    STATUS     current
    DESCRIPTION
        "-- empty --"
    ::= { lcsSetupInterfacesWlan 10 }

-- {ENTRY} 310.2.23.20.10.1
lcsSetupInterfacesWlanBeaconingEntry OBJECT-TYPE
    SYNTAX     LcsSetupInterfacesWlanBeaconingEntry
    MAX-ACCESS not-accessible
    STATUS     current
    DESCRIPTION
        ""
    INDEX {
        lcsSetupInterfacesWlanBeaconingEntryIfc
    }
    ::= { lcsSetupInterfacesWlanBeaconingTable 1 }

-- {SEQUENCE}
LcsSetupInterfacesWlanBeaconingEntry ::= SEQUENCE {
    lcsSetupInterfacesWlanBeaconingEntryIfc INTEGER,
    lcsSetupInterfacesWlanBeaconingEntryBeaconPeriod INTEGER,
    lcsSetupInterfacesWlanBeaconingEntryDtimPeriod INTEGER,
    lcsSetupInterfacesWlanBeaconingEntryBeaconOrder INTEGER
}

-- {COLUMN} 310.2.23.20.10.1.1
lcsSetupInterfacesWlanBeaconingEntryIfc OBJECT-TYPE
    SYNTAX     INTEGER
      {
        eWlan1 (1)
      }
    MAX-ACCESS read-write
    STATUS     current
    DESCRIPTION
        "-- empty --"
    ::= { lcsSetupInterfacesWlanBeaconingEntry 1 }

-- {COLUMN} 310.2.23.20.10.1.2
lcsSetupInterfacesWlanBeaconingEntryBeaconPeriod OBJECT-TYPE
    SYNTAX     INTEGER (0..65535)
    MAX-ACCESS read-write
    STATUS     current
    DESCRIPTION
        "-- empty --"
    ::= { lcsSetupInterfacesWlanBeaconingEntry 2 }

-- {COLUMN} 310.2.23.20.10.1.3
lcsSetupInterfacesWlanBeaconingEntryDtimPeriod OBJECT-TYPE
    SYNTAX     INTEGER (0..255)
    MAX-ACCESS read-write
    STATUS     current
    DESCRIPTION
        "-- empty --"
    ::= { lcsSetupInterfacesWlanBeaconingEntry 3 }

-- {COLUMN} 310.2.23.20.10.1.4
lcsSetupInterfacesWlanBeaconingEntryBeaconOrder OBJECT-TYPE
    SYNTAX     INTEGER
      {
        eCyclic (0),
        eStaggered (1),
        eSimpleBurst (2)
      }
    MAX-ACCESS read-write
    STATUS     current
    DESCRIPTION
        "-- empty --"
    ::= { lcsSetupInterfacesWlanBeaconingEntry 4 }

-- {TABLE} 310.2.23.20.6
lcsSetupInterfacesWlanClientModesTable OBJECT-TYPE
    SYNTAX     SEQUENCE OF LcsSetupInterfacesWlanClientModesEntry
    MAX-ACCESS not-accessible
    STATUS     current
    DESCRIPTION
        "-- empty --"
    ::= { lcsSetupInterfacesWlan 6 }

-- {ENTRY} 310.2.23.20.6.1
lcsSetupInterfacesWlanClientModesEntry OBJECT-TYPE
    SYNTAX     LcsSetupInterfacesWlanClientModesEntry
    MAX-ACCESS not-accessible
    STATUS     current
    DESCRIPTION
        ""
    INDEX {
        lcsSetupInterfacesWlanClientModesEntryIfc
    }
    ::= { lcsSetupInterfacesWlanClientModesTable 1 }

-- {SEQUENCE}
LcsSetupInterfacesWlanClientModesEntry ::= SEQUENCE {
    lcsSetupInterfacesWlanClientModesEntryIfc INTEGER,
    lcsSetupInterfacesWlanClientModesEntryConnectionKeepalive INTEGER,
    lcsSetupInterfacesWlanClientModesEntryNetworkTypes INTEGER,
    lcsSetupInterfacesWlanClientModesEntryScanBands INTEGER,
    lcsSetupInterfacesWlanClientModesEntrySelectionPreference INTEGER,
    lcsSetupInterfacesWlanClientModesEntryPreferredBss MacAddress,
    lcsSetupInterfacesWlanClientModesEntryAddressAdaption INTEGER,
    lcsSetupInterfacesWlanClientModesEntryClBrgSupport INTEGER,
    lcsSetupInterfacesWlanClientModesEntryTxLimit INTEGER,
    lcsSetupInterfacesWlanClientModesEntryRxLimit INTEGER
}

-- {COLUMN} 310.2.23.20.6.1.1
lcsSetupInterfacesWlanClientModesEntryIfc OBJECT-TYPE
    SYNTAX     INTEGER
      {
        eWlan1 (1)
      }
    MAX-ACCESS read-write
    STATUS     current
    DESCRIPTION
        "-- empty --"
    ::= { lcsSetupInterfacesWlanClientModesEntry 1 }

-- {COLUMN} 310.2.23.20.6.1.3
lcsSetupInterfacesWlanClientModesEntryConnectionKeepalive OBJECT-TYPE
    SYNTAX     INTEGER
      {
        eNo (0),
        eYes (1)
      }
    MAX-ACCESS read-write
    STATUS     current
    DESCRIPTION
        "-- empty --"
    ::= { lcsSetupInterfacesWlanClientModesEntry 3 }

-- {COLUMN} 310.2.23.20.6.1.4
lcsSetupInterfacesWlanClientModesEntryNetworkTypes OBJECT-TYPE
    SYNTAX     INTEGER
      {
        eInfrastructure (4) -- lancom's description of Infrastructure
      }
    MAX-ACCESS read-write
    STATUS     current
    DESCRIPTION
        "-- empty --"
    ::= { lcsSetupInterfacesWlanClientModesEntry 4 }

-- {COLUMN} 310.2.23.20.6.1.5
lcsSetupInterfacesWlanClientModesEntryScanBands OBJECT-TYPE
    SYNTAX     INTEGER
      {
        e24ghz (1),
        e5ghz (2),
        e24ghz5ghz (3)
      }
    MAX-ACCESS read-write
    STATUS     current
    DESCRIPTION
        "-- empty --"
    ::= { lcsSetupInterfacesWlanClientModesEntry 5 }

-- {COLUMN} 310.2.23.20.6.1.12
lcsSetupInterfacesWlanClientModesEntrySelectionPreference OBJECT-TYPE
    SYNTAX     INTEGER
      {
        eSignalStrength (0),
        eProfile (1)
      }
    MAX-ACCESS read-write
    STATUS     current
    DESCRIPTION
        "-- empty --"
    ::= { lcsSetupInterfacesWlanClientModesEntry 12 }

-- {COLUMN} 310.2.23.20.6.1.6
lcsSetupInterfacesWlanClientModesEntryPreferredBss OBJECT-TYPE
    SYNTAX     MacAddress
    MAX-ACCESS read-write
    STATUS     current
    DESCRIPTION
        "-- empty --"
    ::= { lcsSetupInterfacesWlanClientModesEntry 6 }

-- {COLUMN} 310.2.23.20.6.1.7
lcsSetupInterfacesWlanClientModesEntryAddressAdaption OBJECT-TYPE
    SYNTAX     INTEGER
      {
        eNo (0),
        eYes (1)
      }
    MAX-ACCESS read-write
    STATUS     current
    DESCRIPTION
        "-- empty --"
    ::= { lcsSetupInterfacesWlanClientModesEntry 7 }

-- {COLUMN} 310.2.23.20.6.1.8
lcsSetupInterfacesWlanClientModesEntryClBrgSupport OBJECT-TYPE
    SYNTAX     INTEGER
      {
        eNo (0),
        eYes (1)
      }
    MAX-ACCESS read-write
    STATUS     current
    DESCRIPTION
        "-- empty --"
    ::= { lcsSetupInterfacesWlanClientModesEntry 8 }

-- {COLUMN} 310.2.23.20.6.1.9
lcsSetupInterfacesWlanClientModesEntryTxLimit OBJECT-TYPE
    SYNTAX     INTEGER (0..2147483647)
    MAX-ACCESS read-write
    STATUS     current
    DESCRIPTION
        "-- empty --"
    ::= { lcsSetupInterfacesWlanClientModesEntry 9 }

-- {COLUMN} 310.2.23.20.6.1.10
lcsSetupInterfacesWlanClientModesEntryRxLimit OBJECT-TYPE
    SYNTAX     INTEGER (0..2147483647)
    MAX-ACCESS read-write
    STATUS     current
    DESCRIPTION
        "-- empty --"
    ::= { lcsSetupInterfacesWlanClientModesEntry 10 }

-- {TABLE} 310.2.23.20.11
lcsSetupInterfacesWlanRoamingTable OBJECT-TYPE
    SYNTAX     SEQUENCE OF LcsSetupInterfacesWlanRoamingEntry
    MAX-ACCESS not-accessible
    STATUS     current
    DESCRIPTION
        "-- empty --"
    ::= { lcsSetupInterfacesWlan 11 }

-- {ENTRY} 310.2.23.20.11.1
lcsSetupInterfacesWlanRoamingEntry OBJECT-TYPE
    SYNTAX     LcsSetupInterfacesWlanRoamingEntry
    MAX-ACCESS not-accessible
    STATUS     current
    DESCRIPTION
        ""
    INDEX {
        lcsSetupInterfacesWlanRoamingEntryIfc
    }
    ::= { lcsSetupInterfacesWlanRoamingTable 1 }

-- {SEQUENCE}
LcsSetupInterfacesWlanRoamingEntry ::= SEQUENCE {
    lcsSetupInterfacesWlanRoamingEntryIfc INTEGER,
    lcsSetupInterfacesWlanRoamingEntrySoftRoaming INTEGER,
    lcsSetupInterfacesWlanRoamingEntryBlockTime Gauge32,
    lcsSetupInterfacesWlanRoamingEntryBeaconMissThreshold INTEGER,
    lcsSetupInterfacesWlanRoamingEntryRoamingThreshold INTEGER,
    lcsSetupInterfacesWlanRoamingEntryNoRoamingThreshold INTEGER,
    lcsSetupInterfacesWlanRoamingEntryForceRoamingThreshold INTEGER,
    lcsSetupInterfacesWlanRoamingEntryConnectThreshold INTEGER,
    lcsSetupInterfacesWlanRoamingEntryConnectHoldThreshold INTEGER,
    lcsSetupInterfacesWlanRoamingEntryMinConnectSignalLevel INTEGER,
    lcsSetupInterfacesWlanRoamingEntryMinConnectHoldSignalLevel INTEGER
}

-- {COLUMN} 310.2.23.20.11.1.1
lcsSetupInterfacesWlanRoamingEntryIfc OBJECT-TYPE
    SYNTAX     INTEGER
      {
        eWlan1 (1)
      }
    MAX-ACCESS read-write
    STATUS     current
    DESCRIPTION
        "-- empty --"
    ::= { lcsSetupInterfacesWlanRoamingEntry 1 }

-- {COLUMN} 310.2.23.20.11.1.6
lcsSetupInterfacesWlanRoamingEntrySoftRoaming OBJECT-TYPE
    SYNTAX     INTEGER
      {
        eNo (0),
        eYes (1)
      }
    MAX-ACCESS read-write
    STATUS     current
    DESCRIPTION
        "-- empty --"
    ::= { lcsSetupInterfacesWlanRoamingEntry 6 }

-- {COLUMN} 310.2.23.20.11.1.11
lcsSetupInterfacesWlanRoamingEntryBlockTime OBJECT-TYPE
    SYNTAX     Gauge32
    MAX-ACCESS read-write
    STATUS     current
    DESCRIPTION
        "-- empty --"
    ::= { lcsSetupInterfacesWlanRoamingEntry 11 }

-- {COLUMN} 310.2.23.20.11.1.2
lcsSetupInterfacesWlanRoamingEntryBeaconMissThreshold OBJECT-TYPE
    SYNTAX     INTEGER (0..255)
    MAX-ACCESS read-write
    STATUS     current
    DESCRIPTION
        "-- empty --"
    ::= { lcsSetupInterfacesWlanRoamingEntry 2 }

-- {COLUMN} 310.2.23.20.11.1.3
lcsSetupInterfacesWlanRoamingEntryRoamingThreshold OBJECT-TYPE
    SYNTAX     INTEGER (0..255)
    MAX-ACCESS read-write
    STATUS     current
    DESCRIPTION
        "-- empty --"
    ::= { lcsSetupInterfacesWlanRoamingEntry 3 }

-- {COLUMN} 310.2.23.20.11.1.4
lcsSetupInterfacesWlanRoamingEntryNoRoamingThreshold OBJECT-TYPE
    SYNTAX     INTEGER (0..255)
    MAX-ACCESS read-write
    STATUS     current
    DESCRIPTION
        "-- empty --"
    ::= { lcsSetupInterfacesWlanRoamingEntry 4 }

-- {COLUMN} 310.2.23.20.11.1.5
lcsSetupInterfacesWlanRoamingEntryForceRoamingThreshold OBJECT-TYPE
    SYNTAX     INTEGER (0..255)
    MAX-ACCESS read-write
    STATUS     current
    DESCRIPTION
        "-- empty --"
    ::= { lcsSetupInterfacesWlanRoamingEntry 5 }

-- {COLUMN} 310.2.23.20.11.1.7
lcsSetupInterfacesWlanRoamingEntryConnectThreshold OBJECT-TYPE
    SYNTAX     INTEGER (0..255)
    MAX-ACCESS read-write
    STATUS     current
    DESCRIPTION
        "-- empty --"
    ::= { lcsSetupInterfacesWlanRoamingEntry 7 }

-- {COLUMN} 310.2.23.20.11.1.8
lcsSetupInterfacesWlanRoamingEntryConnectHoldThreshold OBJECT-TYPE
    SYNTAX     INTEGER (0..255)
    MAX-ACCESS read-write
    STATUS     current
    DESCRIPTION
        "-- empty --"
    ::= { lcsSetupInterfacesWlanRoamingEntry 8 }

-- {COLUMN} 310.2.23.20.11.1.9
lcsSetupInterfacesWlanRoamingEntryMinConnectSignalLevel OBJECT-TYPE
    SYNTAX     INTEGER (-128..127)
    MAX-ACCESS read-write
    STATUS     current
    DESCRIPTION
        "-- empty --"
    ::= { lcsSetupInterfacesWlanRoamingEntry 9 }

-- {COLUMN} 310.2.23.20.11.1.10
lcsSetupInterfacesWlanRoamingEntryMinConnectHoldSignalLevel OBJECT-TYPE
    SYNTAX     INTEGER (-128..127)
    MAX-ACCESS read-write
    STATUS     current
    DESCRIPTION
        "-- empty --"
    ::= { lcsSetupInterfacesWlanRoamingEntry 10 }

-- {TABLE} 310.2.23.4
lcsSetupInterfacesDslTable OBJECT-TYPE
    SYNTAX     SEQUENCE OF LcsSetupInterfacesDslEntry
    MAX-ACCESS not-accessible
    STATUS     current
    DESCRIPTION
        "DSL or DSLoL interface"
    ::= { lcsSetupInterfaces 4 }

-- {ENTRY} 310.2.23.4.1
lcsSetupInterfacesDslEntry OBJECT-TYPE
    SYNTAX     LcsSetupInterfacesDslEntry
    MAX-ACCESS not-accessible
    STATUS     current
    DESCRIPTION
        ""
    INDEX {
        lcsSetupInterfacesDslEntryIfc
    }
    ::= { lcsSetupInterfacesDslTable 1 }

-- {SEQUENCE}
LcsSetupInterfacesDslEntry ::= SEQUENCE {
    lcsSetupInterfacesDslEntryIfc INTEGER,
    lcsSetupInterfacesDslEntryOperating INTEGER,
    lcsSetupInterfacesDslEntryConnector INTEGER,
    lcsSetupInterfacesDslEntryUpstreamRate INTEGER,
    lcsSetupInterfacesDslEntryExtOverhead INTEGER,
    lcsSetupInterfacesDslEntryDownstreamRate INTEGER,
    lcsSetupInterfacesDslEntryTypeOfInterface INTEGER,
    lcsSetupInterfacesDslEntryLanIfc INTEGER
}

-- {COLUMN} 310.2.23.4.1.1
lcsSetupInterfacesDslEntryIfc OBJECT-TYPE
    SYNTAX     INTEGER
      {
        eDsl1 (1),
        eModem (2)
      }
    MAX-ACCESS read-only
    STATUS     current
    DESCRIPTION
        "-- empty --"
    ::= { lcsSetupInterfacesDslEntry 1 }

-- {COLUMN} 310.2.23.4.1.2
lcsSetupInterfacesDslEntryOperating OBJECT-TYPE
    SYNTAX     INTEGER
      {
        eNo (0),
        eYes (16)
      }
    MAX-ACCESS read-write
    STATUS     current
    DESCRIPTION
        "-- empty --"
    ::= { lcsSetupInterfacesDslEntry 2 }

-- {COLUMN} 310.2.23.4.1.6
lcsSetupInterfacesDslEntryConnector OBJECT-TYPE
    SYNTAX     INTEGER
      {
        eAuto (0),
        eExclusive (1)
      }
    MAX-ACCESS read-write
    STATUS     current
    DESCRIPTION
        ""
    ::= { lcsSetupInterfacesDslEntry 6 }

-- {COLUMN} 310.2.23.4.1.16
lcsSetupInterfacesDslEntryUpstreamRate OBJECT-TYPE
    SYNTAX     INTEGER (0..2147483647)
    MAX-ACCESS read-write
    STATUS     current
    DESCRIPTION
        "-- empty --"
    ::= { lcsSetupInterfacesDslEntry 16 }

-- {COLUMN} 310.2.23.4.1.17
lcsSetupInterfacesDslEntryExtOverhead OBJECT-TYPE
    SYNTAX     INTEGER (0..2147483647)
    MAX-ACCESS read-write
    STATUS     current
    DESCRIPTION
        "-- empty --"
    ::= { lcsSetupInterfacesDslEntry 17 }

-- {COLUMN} 310.2.23.4.1.18
lcsSetupInterfacesDslEntryDownstreamRate OBJECT-TYPE
    SYNTAX     INTEGER (0..2147483647)
    MAX-ACCESS read-write
    STATUS     current
    DESCRIPTION
        "-- empty --"
    ::= { lcsSetupInterfacesDslEntry 18 }

-- {COLUMN} 310.2.23.4.1.15
lcsSetupInterfacesDslEntryTypeOfInterface OBJECT-TYPE
    SYNTAX     INTEGER (0..2147483647)
    MAX-ACCESS read-only
    STATUS     current
    DESCRIPTION
        "-- empty --"
    ::= { lcsSetupInterfacesDslEntry 15 }

-- {COLUMN} 310.2.23.4.1.23
lcsSetupInterfacesDslEntryLanIfc OBJECT-TYPE
    SYNTAX     INTEGER
      {
        eLan1 (256),
        eWlan1 (512),
        eP2p11 (768),
        eP2p12 (769),
        eP2p13 (770),
        eP2p14 (771),
        eP2p15 (772),
        eP2p16 (773),
        eP2p17 (799),
        eP2p18 (800),
        eP2p19 (801),
        eP2p110 (802),
        eP2p111 (803),
        eP2p112 (804),
        eP2p113 (805),
        eP2p114 (806),
        eP2p115 (807),
        eP2p116 (808),
        eWlan12 (1024),
        eWlan13 (1025),
        eWlan14 (1026),
        eWlan15 (1027),
        eWlan16 (1028),
        eWlan17 (1029),
        eWlan18 (1030),
        eAny (65535)
      }
    MAX-ACCESS read-write
    STATUS     current
    DESCRIPTION
        "-- empty --"
    ::= { lcsSetupInterfacesDslEntry 23 }

-- {TABLE} 310.2.23.7
lcsSetupInterfacesModemMobileTable OBJECT-TYPE
    SYNTAX     SEQUENCE OF LcsSetupInterfacesModemMobileEntry
    MAX-ACCESS not-accessible
    STATUS     current
    DESCRIPTION
        "-- empty --"
    ::= { lcsSetupInterfaces 7 }

-- {ENTRY} 310.2.23.7.1
lcsSetupInterfacesModemMobileEntry OBJECT-TYPE
    SYNTAX     LcsSetupInterfacesModemMobileEntry
    MAX-ACCESS not-accessible
    STATUS     current
    DESCRIPTION
        ""
    INDEX {
        lcsSetupInterfacesModemMobileEntryIfc
    }
    ::= { lcsSetupInterfacesModemMobileTable 1 }

-- {SEQUENCE}
LcsSetupInterfacesModemMobileEntry ::= SEQUENCE {
    lcsSetupInterfacesModemMobileEntryIfc INTEGER,
    lcsSetupInterfacesModemMobileEntryOperating INTEGER,
    lcsSetupInterfacesModemMobileEntryTypeOfInterface INTEGER,
    lcsSetupInterfacesModemMobileEntryDataRate INTEGER
}

-- {COLUMN} 310.2.23.7.1.1
lcsSetupInterfacesModemMobileEntryIfc OBJECT-TYPE
    SYNTAX     INTEGER
      {
        eDsl1 (1),
        eModem (2)
      }
    MAX-ACCESS read-only
    STATUS     current
    DESCRIPTION
        "-- empty --"
    ::= { lcsSetupInterfacesModemMobileEntry 1 }

-- {COLUMN} 310.2.23.7.1.2
lcsSetupInterfacesModemMobileEntryOperating OBJECT-TYPE
    SYNTAX     INTEGER
      {
        eNo (0),
        eModem (1)
      }
    MAX-ACCESS read-write
    STATUS     current
    DESCRIPTION
        "-- empty --"
    ::= { lcsSetupInterfacesModemMobileEntry 2 }

-- {COLUMN} 310.2.23.7.1.15
lcsSetupInterfacesModemMobileEntryTypeOfInterface OBJECT-TYPE
    SYNTAX     INTEGER (0..2147483647)
    MAX-ACCESS read-only
    STATUS     current
    DESCRIPTION
        "-- empty --"
    ::= { lcsSetupInterfacesModemMobileEntry 15 }

-- {COLUMN} 310.2.23.7.1.21
lcsSetupInterfacesModemMobileEntryDataRate OBJECT-TYPE
    SYNTAX     INTEGER
      {
        e19200 (19200),
        e38400 (38400),
        e57600 (57600),
        e115200 (115200)
      }
    MAX-ACCESS read-write
    STATUS     current
    DESCRIPTION
        "-- empty --"
    ::= { lcsSetupInterfacesModemMobileEntry 21 }

-- {OID} 310.2.24
lcsSetupPublicSpotModule OBJECT IDENTIFIER ::= { lcsSetup 24 }

-- {SCALAR} 310.2.24.1
lcsSetupPublicSpotModuleAuthenticationMode OBJECT-TYPE
    SYNTAX     INTEGER
      {
        eNone (0),
        eUserPlusPassword (1),
        eMacPlusUserPlusPassword (2),
        eEMail (3),
        eEMail2sms (4)
      }
    MAX-ACCESS read-write
    STATUS     current
    DESCRIPTION
        "-- empty --"
    ::= { lcsSetupPublicSpotModule 1 }

-- {TABLE} 310.2.24.2
lcsSetupPublicSpotModuleUserTableTable OBJECT-TYPE
    SYNTAX     SEQUENCE OF LcsSetupPublicSpotModuleUserTableEntry
    MAX-ACCESS not-accessible
    STATUS     current
    DESCRIPTION
        "-- empty --"
    ::= { lcsSetupPublicSpotModule 2 }

-- {ENTRY} 310.2.24.2.1
lcsSetupPublicSpotModuleUserTableEntry OBJECT-TYPE
    SYNTAX     LcsSetupPublicSpotModuleUserTableEntry
    MAX-ACCESS not-accessible
    STATUS     current
    DESCRIPTION
        ""
    INDEX {
        lcsSetupPublicSpotModuleUserTableEntryName
    }
    ::= { lcsSetupPublicSpotModuleUserTableTable 1 }

-- {SEQUENCE}
LcsSetupPublicSpotModuleUserTableEntry ::= SEQUENCE {
    lcsSetupPublicSpotModuleUserTableEntryName DisplayString,
    lcsSetupPublicSpotModuleUserTableEntryPassword DisplayString,
    lcsSetupPublicSpotModuleUserTableEntryMacAddress MacAddress,
    lcsSetupPublicSpotModuleUserTableEntryComment DisplayString,
    lcsSetupPublicSpotModuleUserTableEntryProvider DisplayString,
    lcsSetupPublicSpotModuleUserTableEntryExpiry DisplayString
}

-- {COLUMN} 310.2.24.2.1.1
lcsSetupPublicSpotModuleUserTableEntryName OBJECT-TYPE
    SYNTAX     DisplayString (SIZE(0..64))
    MAX-ACCESS read-write
    STATUS     current
    DESCRIPTION
        "-- empty --"
    ::= { lcsSetupPublicSpotModuleUserTableEntry 1 }

-- {COLUMN} 310.2.24.2.1.2
lcsSetupPublicSpotModuleUserTableEntryPassword OBJECT-TYPE
    SYNTAX     DisplayString (SIZE(0..16))
    MAX-ACCESS read-write
    STATUS     current
    DESCRIPTION
        "-- empty --"
    ::= { lcsSetupPublicSpotModuleUserTableEntry 2 }

-- {COLUMN} 310.2.24.2.1.3
lcsSetupPublicSpotModuleUserTableEntryMacAddress OBJECT-TYPE
    SYNTAX     MacAddress
    MAX-ACCESS read-write
    STATUS     current
    DESCRIPTION
        "-- empty --"
    ::= { lcsSetupPublicSpotModuleUserTableEntry 3 }

-- {COLUMN} 310.2.24.2.1.4
lcsSetupPublicSpotModuleUserTableEntryComment OBJECT-TYPE
    SYNTAX     DisplayString (SIZE(0..80))
    MAX-ACCESS read-write
    STATUS     current
    DESCRIPTION
        "-- empty --"
    ::= { lcsSetupPublicSpotModuleUserTableEntry 4 }

-- {COLUMN} 310.2.24.2.1.5
lcsSetupPublicSpotModuleUserTableEntryProvider OBJECT-TYPE
    SYNTAX     DisplayString (SIZE(0..16))
    MAX-ACCESS read-write
    STATUS     current
    DESCRIPTION
        "-- empty --"
    ::= { lcsSetupPublicSpotModuleUserTableEntry 5 }

-- {COLUMN} 310.2.24.2.1.6
lcsSetupPublicSpotModuleUserTableEntryExpiry OBJECT-TYPE
    SYNTAX     DisplayString (SIZE(0..21))
    MAX-ACCESS read-write
    STATUS     current
    DESCRIPTION
        "-- empty --"
    ::= { lcsSetupPublicSpotModuleUserTableEntry 6 }

-- {SCALAR} 310.2.24.16
lcsSetupPublicSpotModuleAutoCleanupUserTable OBJECT-TYPE
    SYNTAX     INTEGER
      {
        eNo (0),
        eYes (1)
      }
    MAX-ACCESS read-write
    STATUS     current
    DESCRIPTION
        "-- empty --"
    ::= { lcsSetupPublicSpotModule 16 }

-- {TABLE} 310.2.24.23
lcsSetupPublicSpotModuleMacAddressTableTable OBJECT-TYPE
    SYNTAX     SEQUENCE OF LcsSetupPublicSpotModuleMacAddressTableEntry
    MAX-ACCESS not-accessible
    STATUS     current
    DESCRIPTION
        "-- empty --"
    ::= { lcsSetupPublicSpotModule 23 }

-- {ENTRY} 310.2.24.23.1
lcsSetupPublicSpotModuleMacAddressTableEntry OBJECT-TYPE
    SYNTAX     LcsSetupPublicSpotModuleMacAddressTableEntry
    MAX-ACCESS not-accessible
    STATUS     current
    DESCRIPTION
        ""
    INDEX {
        lcsSetupPublicSpotModuleMacAddressTableEntryMacAddress
    }
    ::= { lcsSetupPublicSpotModuleMacAddressTableTable 1 }

-- {SEQUENCE}
LcsSetupPublicSpotModuleMacAddressTableEntry ::= SEQUENCE {
    lcsSetupPublicSpotModuleMacAddressTableEntryMacAddress MacAddress,
    lcsSetupPublicSpotModuleMacAddressTableEntryUserName DisplayString,
    lcsSetupPublicSpotModuleMacAddressTableEntryProvider DisplayString
}

-- {COLUMN} 310.2.24.23.1.1
lcsSetupPublicSpotModuleMacAddressTableEntryMacAddress OBJECT-TYPE
    SYNTAX     MacAddress
    MAX-ACCESS read-write
    STATUS     current
    DESCRIPTION
        "-- empty --"
    ::= { lcsSetupPublicSpotModuleMacAddressTableEntry 1 }

-- {COLUMN} 310.2.24.23.1.2
lcsSetupPublicSpotModuleMacAddressTableEntryUserName OBJECT-TYPE
    SYNTAX     DisplayString (SIZE(0..64))
    MAX-ACCESS read-write
    STATUS     current
    DESCRIPTION
        "-- empty --"
    ::= { lcsSetupPublicSpotModuleMacAddressTableEntry 2 }

-- {COLUMN} 310.2.24.23.1.3
lcsSetupPublicSpotModuleMacAddressTableEntryProvider OBJECT-TYPE
    SYNTAX     DisplayString (SIZE(0..16))
    MAX-ACCESS read-write
    STATUS     current
    DESCRIPTION
        "-- empty --"
    ::= { lcsSetupPublicSpotModuleMacAddressTableEntry 3 }

-- {SCALAR} 310.2.24.24
lcsSetupPublicSpotModuleMacAddressCheckProvider OBJECT-TYPE
    SYNTAX     DisplayString (SIZE(0..16))
    MAX-ACCESS read-write
    STATUS     current
    DESCRIPTION
        "-- empty --"
    ::= { lcsSetupPublicSpotModule 24 }

-- {SCALAR} 310.2.24.25
lcsSetupPublicSpotModuleMacAddressCheckCacheTime OBJECT-TYPE
    SYNTAX     INTEGER (0..2147483647)
    MAX-ACCESS read-write
    STATUS     current
    DESCRIPTION
        "-- empty --"
    ::= { lcsSetupPublicSpotModule 25 }

-- {SCALAR} 310.2.24.26
lcsSetupPublicSpotModuleStationTableLimit OBJECT-TYPE
    SYNTAX     INTEGER (0..2147483647)
    MAX-ACCESS read-write
    STATUS     current
    DESCRIPTION
        "-- empty --"
    ::= { lcsSetupPublicSpotModule 26 }

-- {SCALAR} 310.2.24.30
lcsSetupPublicSpotModuleFreeServer OBJECT-TYPE
    SYNTAX     DisplayString (SIZE(0..64))
    MAX-ACCESS read-write
    STATUS     current
    DESCRIPTION
        "-- empty --"
    ::= { lcsSetupPublicSpotModule 30 }

-- {SCALAR} 310.2.24.6
lcsSetupPublicSpotModuleServerSubdir OBJECT-TYPE
    SYNTAX     DisplayString (SIZE(0..127))
    MAX-ACCESS read-write
    STATUS     current
    DESCRIPTION
        "-- empty --"
    ::= { lcsSetupPublicSpotModule 6 }

-- {SCALAR} 310.2.24.5
lcsSetupPublicSpotModuleTrafficLimitBytes OBJECT-TYPE
    SYNTAX     INTEGER (0..2147483647)
    MAX-ACCESS read-write
    STATUS     current
    DESCRIPTION
        "-- empty --"
    ::= { lcsSetupPublicSpotModule 5 }

-- {TABLE} 310.2.24.8
lcsSetupPublicSpotModulePageTableTable OBJECT-TYPE
    SYNTAX     SEQUENCE OF LcsSetupPublicSpotModulePageTableEntry
    MAX-ACCESS not-accessible
    STATUS     current
    DESCRIPTION
        "-- empty --"
    ::= { lcsSetupPublicSpotModule 8 }

-- {ENTRY} 310.2.24.8.1
lcsSetupPublicSpotModulePageTableEntry OBJECT-TYPE
    SYNTAX     LcsSetupPublicSpotModulePageTableEntry
    MAX-ACCESS not-accessible
    STATUS     current
    DESCRIPTION
        ""
    INDEX {
        lcsSetupPublicSpotModulePageTableEntryPage
    }
    ::= { lcsSetupPublicSpotModulePageTableTable 1 }

-- {SEQUENCE}
LcsSetupPublicSpotModulePageTableEntry ::= SEQUENCE {
    lcsSetupPublicSpotModulePageTableEntryPage INTEGER,
    lcsSetupPublicSpotModulePageTableEntryUrl DisplayString,
    lcsSetupPublicSpotModulePageTableEntryType INTEGER,
    lcsSetupPublicSpotModulePageTableEntryFallback INTEGER,
    lcsSetupPublicSpotModulePageTableEntryLoopbackAddr DisplayString
}

-- {COLUMN} 310.2.24.8.1.1
lcsSetupPublicSpotModulePageTableEntryPage OBJECT-TYPE
    SYNTAX     INTEGER
      {
        eWelcome (1),
        eLogin (2),
        eError (3),
        eStart (4),
        eStatus (5),
        eLogoff (6),
        eHelp (7),
        eNoProxy (8),
        eVoucher (9),
        eGtc (10)
      }
    MAX-ACCESS read-only
    STATUS     current
    DESCRIPTION
        "-- empty --"
    ::= { lcsSetupPublicSpotModulePageTableEntry 1 }

-- {COLUMN} 310.2.24.8.1.2
lcsSetupPublicSpotModulePageTableEntryUrl OBJECT-TYPE
    SYNTAX     DisplayString (SIZE(0..251))
    MAX-ACCESS read-write
    STATUS     current
    DESCRIPTION
        "-- empty --"
    ::= { lcsSetupPublicSpotModulePageTableEntry 2 }

-- {COLUMN} 310.2.24.8.1.4
lcsSetupPublicSpotModulePageTableEntryType OBJECT-TYPE
    SYNTAX     INTEGER
      {
        eTemplate (0),
        eRedirect (1)
      }
    MAX-ACCESS read-write
    STATUS     current
    DESCRIPTION
        "-- empty --"
    ::= { lcsSetupPublicSpotModulePageTableEntry 4 }

-- {COLUMN} 310.2.24.8.1.3
lcsSetupPublicSpotModulePageTableEntryFallback OBJECT-TYPE
    SYNTAX     INTEGER
      {
        eNo (0),
        eYes (1)
      }
    MAX-ACCESS read-write
    STATUS     current
    DESCRIPTION
        "-- empty --"
    ::= { lcsSetupPublicSpotModulePageTableEntry 3 }

-- {COLUMN} 310.2.24.8.1.5
lcsSetupPublicSpotModulePageTableEntryLoopbackAddr OBJECT-TYPE
    SYNTAX     DisplayString (SIZE(0..16))
    MAX-ACCESS read-write
    STATUS     current
    DESCRIPTION
        "-- empty --"
    ::= { lcsSetupPublicSpotModulePageTableEntry 5 }

-- {TABLE} 310.2.24.31
lcsSetupPublicSpotModuleFreeNetworksTable OBJECT-TYPE
    SYNTAX     SEQUENCE OF LcsSetupPublicSpotModuleFreeNetworksEntry
    MAX-ACCESS not-accessible
    STATUS     current
    DESCRIPTION
        "-- empty --"
    ::= { lcsSetupPublicSpotModule 31 }

-- {ENTRY} 310.2.24.31.1
lcsSetupPublicSpotModuleFreeNetworksEntry OBJECT-TYPE
    SYNTAX     LcsSetupPublicSpotModuleFreeNetworksEntry
    MAX-ACCESS not-accessible
    STATUS     current
    DESCRIPTION
        ""
    INDEX {
        lcsSetupPublicSpotModuleFreeNetworksEntryHostName
    }
    ::= { lcsSetupPublicSpotModuleFreeNetworksTable 1 }

-- {SEQUENCE}
LcsSetupPublicSpotModuleFreeNetworksEntry ::= SEQUENCE {
    lcsSetupPublicSpotModuleFreeNetworksEntryHostName DisplayString,
    lcsSetupPublicSpotModuleFreeNetworksEntryMask IpAddress
}

-- {COLUMN} 310.2.24.31.1.1
lcsSetupPublicSpotModuleFreeNetworksEntryHostName OBJECT-TYPE
    SYNTAX     DisplayString (SIZE(0..64))
    MAX-ACCESS read-write
    STATUS     current
    DESCRIPTION
        "-- empty --"
    ::= { lcsSetupPublicSpotModuleFreeNetworksEntry 1 }

-- {COLUMN} 310.2.24.31.1.2
lcsSetupPublicSpotModuleFreeNetworksEntryMask OBJECT-TYPE
    SYNTAX     IpAddress
    MAX-ACCESS read-write
    STATUS     current
    DESCRIPTION
        "-- empty --"
    ::= { lcsSetupPublicSpotModuleFreeNetworksEntry 2 }

-- {SCALAR} 310.2.24.32
lcsSetupPublicSpotModuleFreeHostsMinimumTtl OBJECT-TYPE
    SYNTAX     INTEGER (0..2147483647)
    MAX-ACCESS read-write
    STATUS     current
    DESCRIPTION
        "-- empty --"
    ::= { lcsSetupPublicSpotModule 32 }

-- {SCALAR} 310.2.24.21
lcsSetupPublicSpotModuleLoginPageType OBJECT-TYPE
    SYNTAX     INTEGER
      {
        eHttps (0),
        eHttp (1)
      }
    MAX-ACCESS read-write
    STATUS     current
    DESCRIPTION
        "-- empty --"
    ::= { lcsSetupPublicSpotModule 21 }

-- {SCALAR} 310.2.24.22
lcsSetupPublicSpotModuleDeviceHostname OBJECT-TYPE
    SYNTAX     DisplayString (SIZE(0..31))
    MAX-ACCESS read-write
    STATUS     current
    DESCRIPTION
        "-- empty --"
    ::= { lcsSetupPublicSpotModule 22 }

-- {SCALAR} 310.2.24.18
lcsSetupPublicSpotModuleDisallowMultipleLogin OBJECT-TYPE
    SYNTAX     INTEGER
      {
        eNo (0),
        eYes (1)
      }
    MAX-ACCESS read-write
    STATUS     current
    DESCRIPTION
        "-- empty --"
    ::= { lcsSetupPublicSpotModule 18 }

-- {TABLE} 310.2.24.3
lcsSetupPublicSpotModuleProviderTableTable OBJECT-TYPE
    SYNTAX     SEQUENCE OF LcsSetupPublicSpotModuleProviderTableEntry
    MAX-ACCESS not-accessible
    STATUS     current
    DESCRIPTION
        "-- empty --"
    ::= { lcsSetupPublicSpotModule 3 }

-- {ENTRY} 310.2.24.3.1
lcsSetupPublicSpotModuleProviderTableEntry OBJECT-TYPE
    SYNTAX     LcsSetupPublicSpotModuleProviderTableEntry
    MAX-ACCESS not-accessible
    STATUS     current
    DESCRIPTION
        ""
    INDEX {
        lcsSetupPublicSpotModuleProviderTableEntryProvider
    }
    ::= { lcsSetupPublicSpotModuleProviderTableTable 1 }

-- {SEQUENCE}
LcsSetupPublicSpotModuleProviderTableEntry ::= SEQUENCE {
    lcsSetupPublicSpotModuleProviderTableEntryProvider DisplayString,
    lcsSetupPublicSpotModuleProviderTableEntryAuthServerAddress IpAddress,
    lcsSetupPublicSpotModuleProviderTableEntryAuthServerPort INTEGER,
    lcsSetupPublicSpotModuleProviderTableEntryAuthServerSecret DisplayString,
    lcsSetupPublicSpotModuleProviderTableEntryAuthServerLoopbackAddr DisplayString,
    lcsSetupPublicSpotModuleProviderTableEntryAuthServerProtocol INTEGER,
    lcsSetupPublicSpotModuleProviderTableEntryAccServerAddress IpAddress,
    lcsSetupPublicSpotModuleProviderTableEntryAccServerPort INTEGER,
    lcsSetupPublicSpotModuleProviderTableEntryAccServerSecret DisplayString,
    lcsSetupPublicSpotModuleProviderTableEntryAccServerLoopbackAddr DisplayString,
    lcsSetupPublicSpotModuleProviderTableEntryAccServerProtocol INTEGER,
    lcsSetupPublicSpotModuleProviderTableEntryBackup DisplayString
}

-- {COLUMN} 310.2.24.3.1.1
lcsSetupPublicSpotModuleProviderTableEntryProvider OBJECT-TYPE
    SYNTAX     DisplayString (SIZE(0..16))
    MAX-ACCESS read-write
    STATUS     current
    DESCRIPTION
        "-- empty --"
    ::= { lcsSetupPublicSpotModuleProviderTableEntry 1 }

-- {COLUMN} 310.2.24.3.1.2
lcsSetupPublicSpotModuleProviderTableEntryAuthServerAddress OBJECT-TYPE
    SYNTAX     IpAddress
    MAX-ACCESS read-write
    STATUS     current
    DESCRIPTION
        "-- empty --"
    ::= { lcsSetupPublicSpotModuleProviderTableEntry 2 }

-- {COLUMN} 310.2.24.3.1.3
lcsSetupPublicSpotModuleProviderTableEntryAuthServerPort OBJECT-TYPE
    SYNTAX     INTEGER (0..65535)
    MAX-ACCESS read-write
    STATUS     current
    DESCRIPTION
        "-- empty --"
    ::= { lcsSetupPublicSpotModuleProviderTableEntry 3 }

-- {COLUMN} 310.2.24.3.1.4
lcsSetupPublicSpotModuleProviderTableEntryAuthServerSecret OBJECT-TYPE
    SYNTAX     DisplayString (SIZE(0..64))
    MAX-ACCESS read-write
    STATUS     current
    DESCRIPTION
        "-- empty --"
    ::= { lcsSetupPublicSpotModuleProviderTableEntry 4 }

-- {COLUMN} 310.2.24.3.1.9
lcsSetupPublicSpotModuleProviderTableEntryAuthServerLoopbackAddr OBJECT-TYPE
    SYNTAX     DisplayString (SIZE(0..16))
    MAX-ACCESS read-write
    STATUS     current
    DESCRIPTION
        "-- empty --"
    ::= { lcsSetupPublicSpotModuleProviderTableEntry 9 }

-- {COLUMN} 310.2.24.3.1.11
lcsSetupPublicSpotModuleProviderTableEntryAuthServerProtocol OBJECT-TYPE
    SYNTAX     INTEGER
      {
        eRadius (0),
        eRadsec (1)
      }
    MAX-ACCESS read-write
    STATUS     current
    DESCRIPTION
        "-- empty --"
    ::= { lcsSetupPublicSpotModuleProviderTableEntry 11 }

-- {COLUMN} 310.2.24.3.1.5
lcsSetupPublicSpotModuleProviderTableEntryAccServerAddress OBJECT-TYPE
    SYNTAX     IpAddress
    MAX-ACCESS read-write
    STATUS     current
    DESCRIPTION
        "-- empty --"
    ::= { lcsSetupPublicSpotModuleProviderTableEntry 5 }

-- {COLUMN} 310.2.24.3.1.6
lcsSetupPublicSpotModuleProviderTableEntryAccServerPort OBJECT-TYPE
    SYNTAX     INTEGER (0..65535)
    MAX-ACCESS read-write
    STATUS     current
    DESCRIPTION
        "-- empty --"
    ::= { lcsSetupPublicSpotModuleProviderTableEntry 6 }

-- {COLUMN} 310.2.24.3.1.7
lcsSetupPublicSpotModuleProviderTableEntryAccServerSecret OBJECT-TYPE
    SYNTAX     DisplayString (SIZE(0..64))
    MAX-ACCESS read-write
    STATUS     current
    DESCRIPTION
        "-- empty --"
    ::= { lcsSetupPublicSpotModuleProviderTableEntry 7 }

-- {COLUMN} 310.2.24.3.1.10
lcsSetupPublicSpotModuleProviderTableEntryAccServerLoopbackAddr OBJECT-TYPE
    SYNTAX     DisplayString (SIZE(0..16))
    MAX-ACCESS read-write
    STATUS     current
    DESCRIPTION
        "-- empty --"
    ::= { lcsSetupPublicSpotModuleProviderTableEntry 10 }

-- {COLUMN} 310.2.24.3.1.12
lcsSetupPublicSpotModuleProviderTableEntryAccServerProtocol OBJECT-TYPE
    SYNTAX     INTEGER
      {
        eRadius (0),
        eRadsec (1)
      }
    MAX-ACCESS read-write
    STATUS     current
    DESCRIPTION
        "-- empty --"
    ::= { lcsSetupPublicSpotModuleProviderTableEntry 12 }

-- {COLUMN} 310.2.24.3.1.8
lcsSetupPublicSpotModuleProviderTableEntryBackup OBJECT-TYPE
    SYNTAX     DisplayString (SIZE(0..16))
    MAX-ACCESS read-write
    STATUS     current
    DESCRIPTION
        "-- empty --"
    ::= { lcsSetupPublicSpotModuleProviderTableEntry 8 }

-- {SCALAR} 310.2.24.7
lcsSetupPublicSpotModuleAccountingCycle OBJECT-TYPE
    SYNTAX     INTEGER (0..2147483647)
    MAX-ACCESS read-write
    STATUS     current
    DESCRIPTION
        "-- empty --"
    ::= { lcsSetupPublicSpotModule 7 }

-- {SCALAR} 310.2.24.14
lcsSetupPublicSpotModuleIdleTimeout OBJECT-TYPE
    SYNTAX     INTEGER (0..2147483647)
    MAX-ACCESS read-write
    STATUS     current
    DESCRIPTION
        "-- empty --"
    ::= { lcsSetupPublicSpotModule 14 }

-- {SCALAR} 310.2.24.17
lcsSetupPublicSpotModuleProvideServerDatabase OBJECT-TYPE
    SYNTAX     INTEGER
      {
        eNo (0),
        eYes (1)
      }
    MAX-ACCESS read-write
    STATUS     current
    DESCRIPTION
        "-- empty --"
    ::= { lcsSetupPublicSpotModule 17 }

-- {SCALAR} 310.2.24.9
lcsSetupPublicSpotModuleRoamingSecret OBJECT-TYPE
    SYNTAX     DisplayString (SIZE(0..32))
    MAX-ACCESS read-write
    STATUS     current
    DESCRIPTION
        "-- empty --"
    ::= { lcsSetupPublicSpotModule 9 }

-- {TABLE} 310.2.24.15
lcsSetupPublicSpotModulePortTableTable OBJECT-TYPE
    SYNTAX     SEQUENCE OF LcsSetupPublicSpotModulePortTableEntry
    MAX-ACCESS not-accessible
    STATUS     current
    DESCRIPTION
        "-- empty --"
    ::= { lcsSetupPublicSpotModule 15 }

-- {ENTRY} 310.2.24.15.1
lcsSetupPublicSpotModulePortTableEntry OBJECT-TYPE
    SYNTAX     LcsSetupPublicSpotModulePortTableEntry
    MAX-ACCESS not-accessible
    STATUS     current
    DESCRIPTION
        ""
    INDEX {
        lcsSetupPublicSpotModulePortTableEntryPort
    }
    ::= { lcsSetupPublicSpotModulePortTableTable 1 }

-- {SEQUENCE}
LcsSetupPublicSpotModulePortTableEntry ::= SEQUENCE {
    lcsSetupPublicSpotModulePortTableEntryPort DisplayString,
    lcsSetupPublicSpotModulePortTableEntryAuthenticationNecessary INTEGER
}

-- {COLUMN} 310.2.24.15.1.2
lcsSetupPublicSpotModulePortTableEntryPort OBJECT-TYPE
    SYNTAX     DisplayString (SIZE(0..15))
    MAX-ACCESS read-only
    STATUS     current
    DESCRIPTION
        "-- empty --"
    ::= { lcsSetupPublicSpotModulePortTableEntry 2 }

-- {COLUMN} 310.2.24.15.1.3
lcsSetupPublicSpotModulePortTableEntryAuthenticationNecessary OBJECT-TYPE
    SYNTAX     INTEGER
      {
        eNo (0),
        eYes (1)
      }
    MAX-ACCESS read-write
    STATUS     current
    DESCRIPTION
        "-- empty --"
    ::= { lcsSetupPublicSpotModulePortTableEntry 3 }

-- {TABLE} 310.2.24.20
lcsSetupPublicSpotModuleVlanTableTable OBJECT-TYPE
    SYNTAX     SEQUENCE OF LcsSetupPublicSpotModuleVlanTableEntry
    MAX-ACCESS not-accessible
    STATUS     current
    DESCRIPTION
        "-- empty --"
    ::= { lcsSetupPublicSpotModule 20 }

-- {ENTRY} 310.2.24.20.1
lcsSetupPublicSpotModuleVlanTableEntry OBJECT-TYPE
    SYNTAX     LcsSetupPublicSpotModuleVlanTableEntry
    MAX-ACCESS not-accessible
    STATUS     current
    DESCRIPTION
        ""
    INDEX {
        lcsSetupPublicSpotModuleVlanTableEntryVlanId
    }
    ::= { lcsSetupPublicSpotModuleVlanTableTable 1 }

-- {SEQUENCE}
LcsSetupPublicSpotModuleVlanTableEntry ::= SEQUENCE {
    lcsSetupPublicSpotModuleVlanTableEntryVlanId INTEGER
}

-- {COLUMN} 310.2.24.20.1.1
lcsSetupPublicSpotModuleVlanTableEntryVlanId OBJECT-TYPE
    SYNTAX     INTEGER (0..65535)
    MAX-ACCESS read-write
    STATUS     current
    DESCRIPTION
        "-- empty --"
    ::= { lcsSetupPublicSpotModuleVlanTableEntry 1 }

-- {SCALAR} 310.2.24.12
lcsSetupPublicSpotModuleCommunicationPort OBJECT-TYPE
    SYNTAX     INTEGER (0..65535)
    MAX-ACCESS read-write
    STATUS     current
    DESCRIPTION
        "-- empty --"
    ::= { lcsSetupPublicSpotModule 12 }

-- {OID} 310.2.24.19
lcsSetupPublicSpotModuleAddUserWizard OBJECT IDENTIFIER ::= { lcsSetupPublicSpotModule 19 }

-- {TABLE} 310.2.24.19.5
lcsSetupPublicSpotModuleAddUserWizardDefaultRuntimeTable OBJECT-TYPE
    SYNTAX     SEQUENCE OF LcsSetupPublicSpotModuleAddUserWizardDefaultRuntimeEntry
    MAX-ACCESS not-accessible
    STATUS     current
    DESCRIPTION
        "-- empty --"
    ::= { lcsSetupPublicSpotModuleAddUserWizard 5 }

-- {ENTRY} 310.2.24.19.5.1
lcsSetupPublicSpotModuleAddUserWizardDefaultRuntimeEntry OBJECT-TYPE
    SYNTAX     LcsSetupPublicSpotModuleAddUserWizardDefaultRuntimeEntry
    MAX-ACCESS not-accessible
    STATUS     current
    DESCRIPTION
        ""
    INDEX {
        lcsSetupPublicSpotModuleAddUserWizardDefaultRuntimeEntryRuntime,
        lcsSetupPublicSpotModuleAddUserWizardDefaultRuntimeEntryUnit
    }
    ::= { lcsSetupPublicSpotModuleAddUserWizardDefaultRuntimeTable 1 }

-- {SEQUENCE}
LcsSetupPublicSpotModuleAddUserWizardDefaultRuntimeEntry ::= SEQUENCE {
    lcsSetupPublicSpotModuleAddUserWizardDefaultRuntimeEntryRuntime INTEGER,
    lcsSetupPublicSpotModuleAddUserWizardDefaultRuntimeEntryUnit INTEGER
}

-- {COLUMN} 310.2.24.19.5.1.1
lcsSetupPublicSpotModuleAddUserWizardDefaultRuntimeEntryRuntime OBJECT-TYPE
    SYNTAX     INTEGER (0..65535)
    MAX-ACCESS read-write
    STATUS     current
    DESCRIPTION
        "-- empty --"
    ::= { lcsSetupPublicSpotModuleAddUserWizardDefaultRuntimeEntry 1 }

-- {COLUMN} 310.2.24.19.5.1.2
lcsSetupPublicSpotModuleAddUserWizardDefaultRuntimeEntryUnit OBJECT-TYPE
    SYNTAX     INTEGER
      {
        eMinuteS (2),
        eHourS (0),
        eDayS (1)
      }
    MAX-ACCESS read-write
    STATUS     current
    DESCRIPTION
        "-- empty --"
    ::= { lcsSetupPublicSpotModuleAddUserWizardDefaultRuntimeEntry 2 }

-- {SCALAR} 310.2.24.19.2
lcsSetupPublicSpotModuleAddUserWizardUsernamePattern OBJECT-TYPE
    SYNTAX     DisplayString (SIZE(0..19))
    MAX-ACCESS read-write
    STATUS     current
    DESCRIPTION
        "-- empty --"
    ::= { lcsSetupPublicSpotModuleAddUserWizard 2 }

-- {SCALAR} 310.2.24.19.3
lcsSetupPublicSpotModuleAddUserWizardPasswordLength OBJECT-TYPE
    SYNTAX     INTEGER (0..255)
    MAX-ACCESS read-write
    STATUS     current
    DESCRIPTION
        "-- empty --"
    ::= { lcsSetupPublicSpotModuleAddUserWizard 3 }

-- {SCALAR} 310.2.24.19.4
lcsSetupPublicSpotModuleAddUserWizardSsid OBJECT-TYPE
    SYNTAX     DisplayString (SIZE(0..32))
    MAX-ACCESS read-write
    STATUS     current
    DESCRIPTION
        "-- empty --"
    ::= { lcsSetupPublicSpotModuleAddUserWizard 4 }

-- {TABLE} 310.2.24.19.11
lcsSetupPublicSpotModuleAddUserWizardSsidTableTable OBJECT-TYPE
    SYNTAX     SEQUENCE OF LcsSetupPublicSpotModuleAddUserWizardSsidTableEntry
    MAX-ACCESS not-accessible
    STATUS     current
    DESCRIPTION
        "-- empty --"
    ::= { lcsSetupPublicSpotModuleAddUserWizard 11 }

-- {ENTRY} 310.2.24.19.11.1
lcsSetupPublicSpotModuleAddUserWizardSsidTableEntry OBJECT-TYPE
    SYNTAX     LcsSetupPublicSpotModuleAddUserWizardSsidTableEntry
    MAX-ACCESS not-accessible
    STATUS     current
    DESCRIPTION
        ""
    INDEX {
        lcsSetupPublicSpotModuleAddUserWizardSsidTableEntryNetworkName
    }
    ::= { lcsSetupPublicSpotModuleAddUserWizardSsidTableTable 1 }

-- {SEQUENCE}
LcsSetupPublicSpotModuleAddUserWizardSsidTableEntry ::= SEQUENCE {
    lcsSetupPublicSpotModuleAddUserWizardSsidTableEntryNetworkName DisplayString,
    lcsSetupPublicSpotModuleAddUserWizardSsidTableEntryDefault INTEGER
}

-- {COLUMN} 310.2.24.19.11.1.1
lcsSetupPublicSpotModuleAddUserWizardSsidTableEntryNetworkName OBJECT-TYPE
    SYNTAX     DisplayString (SIZE(0..32))
    MAX-ACCESS read-write
    STATUS     current
    DESCRIPTION
        "-- empty --"
    ::= { lcsSetupPublicSpotModuleAddUserWizardSsidTableEntry 1 }

-- {COLUMN} 310.2.24.19.11.1.2
lcsSetupPublicSpotModuleAddUserWizardSsidTableEntryDefault OBJECT-TYPE
    SYNTAX     INTEGER
      {
        eNo (0),
        eYes (1)
      }
    MAX-ACCESS read-write
    STATUS     current
    DESCRIPTION
        "-- empty --"
    ::= { lcsSetupPublicSpotModuleAddUserWizardSsidTableEntry 2 }

-- {SCALAR} 310.2.24.19.8
lcsSetupPublicSpotModuleAddUserWizardPrintCommentsOnVoucher OBJECT-TYPE
    SYNTAX     INTEGER
      {
        eNo (0),
        eYes (1)
      }
    MAX-ACCESS read-write
    STATUS     current
    DESCRIPTION
        "-- empty --"
    ::= { lcsSetupPublicSpotModuleAddUserWizard 8 }

-- {TABLE} 310.2.24.19.6
lcsSetupPublicSpotModuleAddUserWizardCommentFieldsTable OBJECT-TYPE
    SYNTAX     SEQUENCE OF LcsSetupPublicSpotModuleAddUserWizardCommentFieldsEntry
    MAX-ACCESS not-accessible
    STATUS     current
    DESCRIPTION
        "-- empty --"
    ::= { lcsSetupPublicSpotModuleAddUserWizard 6 }

-- {ENTRY} 310.2.24.19.6.1
lcsSetupPublicSpotModuleAddUserWizardCommentFieldsEntry OBJECT-TYPE
    SYNTAX     LcsSetupPublicSpotModuleAddUserWizardCommentFieldsEntry
    MAX-ACCESS not-accessible
    STATUS     current
    DESCRIPTION
        ""
    INDEX {
        lcsSetupPublicSpotModuleAddUserWizardCommentFieldsEntryFieldName
    }
    ::= { lcsSetupPublicSpotModuleAddUserWizardCommentFieldsTable 1 }

-- {SEQUENCE}
LcsSetupPublicSpotModuleAddUserWizardCommentFieldsEntry ::= SEQUENCE {
    lcsSetupPublicSpotModuleAddUserWizardCommentFieldsEntryFieldName DisplayString
}

-- {COLUMN} 310.2.24.19.6.1.1
lcsSetupPublicSpotModuleAddUserWizardCommentFieldsEntryFieldName OBJECT-TYPE
    SYNTAX     DisplayString (SIZE(0..31))
    MAX-ACCESS read-write
    STATUS     current
    DESCRIPTION
        "-- empty --"
    ::= { lcsSetupPublicSpotModuleAddUserWizardCommentFieldsEntry 1 }

-- {SCALAR} 310.2.24.19.7
lcsSetupPublicSpotModuleAddUserWizardDefaultStartingTime OBJECT-TYPE
    SYNTAX     INTEGER
      {
        eImmediately (1),
        eFirstLogin (3)
      }
    MAX-ACCESS read-write
    STATUS     current
    DESCRIPTION
        "-- empty --"
    ::= { lcsSetupPublicSpotModuleAddUserWizard 7 }

-- {SCALAR} 310.2.24.19.9
lcsSetupPublicSpotModuleAddUserWizardMaxVoucherValPeriod OBJECT-TYPE
    SYNTAX     INTEGER (0..2147483647)
    MAX-ACCESS read-write
    STATUS     current
    DESCRIPTION
        "Maximal voucher validate period"
    ::= { lcsSetupPublicSpotModuleAddUserWizard 9 }

-- {SCALAR} 310.2.24.19.10
lcsSetupPublicSpotModuleAddUserWizardAvailableExpiryMethods OBJECT-TYPE
    SYNTAX     INTEGER
      {
        eAllMethods (0),
        eCurrentTimeMethod (1),
        eLoginTimeMethod (2)
      }
    MAX-ACCESS read-write
    STATUS     current
    DESCRIPTION
        "-- empty --"
    ::= { lcsSetupPublicSpotModuleAddUserWizard 10 }

-- {SCALAR} 310.2.24.19.12
lcsSetupPublicSpotModuleAddUserWizardUserNameCaseSensitive OBJECT-TYPE
    SYNTAX     INTEGER
      {
        eNo (0),
        eYes (1)
      }
    MAX-ACCESS read-only
    STATUS     current
    DESCRIPTION
        "-- empty --"
    ::= { lcsSetupPublicSpotModuleAddUserWizard 12 }

-- {SCALAR} 310.2.24.19.13
lcsSetupPublicSpotModuleAddUserWizardHideCaseSensitiveCheckbox OBJECT-TYPE
    SYNTAX     INTEGER
      {
        eNo (0),
        eYes (1)
      }
    MAX-ACCESS read-only
    STATUS     current
    DESCRIPTION
        "-- empty --"
    ::= { lcsSetupPublicSpotModuleAddUserWizard 13 }

-- {TABLE} 310.2.24.19.14
lcsSetupPublicSpotModuleAddUserWizardMaxConcLoginsTable OBJECT-TYPE
    SYNTAX     SEQUENCE OF LcsSetupPublicSpotModuleAddUserWizardMaxConcLoginsEntry
    MAX-ACCESS not-accessible
    STATUS     current
    DESCRIPTION
        ""
    ::= { lcsSetupPublicSpotModuleAddUserWizard 14 }

-- {ENTRY} 310.2.24.19.14.1
lcsSetupPublicSpotModuleAddUserWizardMaxConcLoginsEntry OBJECT-TYPE
    SYNTAX     LcsSetupPublicSpotModuleAddUserWizardMaxConcLoginsEntry
    MAX-ACCESS not-accessible
    STATUS     current
    DESCRIPTION
        ""
    INDEX {
        lcsSetupPublicSpotModuleAddUserWizardMaxConcLoginsEntryValue
    }
    ::= { lcsSetupPublicSpotModuleAddUserWizardMaxConcLoginsTable 1 }

-- {SEQUENCE}
LcsSetupPublicSpotModuleAddUserWizardMaxConcLoginsEntry ::= SEQUENCE {
    lcsSetupPublicSpotModuleAddUserWizardMaxConcLoginsEntryValue DisplayString
}

-- {COLUMN} 310.2.24.19.14.1.1
lcsSetupPublicSpotModuleAddUserWizardMaxConcLoginsEntryValue OBJECT-TYPE
    SYNTAX     DisplayString (SIZE(0..5))
    MAX-ACCESS read-write
    STATUS     current
    DESCRIPTION
        "-- empty --"
    ::= { lcsSetupPublicSpotModuleAddUserWizardMaxConcLoginsEntry 1 }

-- {SCALAR} 310.2.24.19.15
lcsSetupPublicSpotModuleAddUserWizardMultiLogin OBJECT-TYPE
    SYNTAX     INTEGER
      {
        eNo (0),
        eYes (1)
      }
    MAX-ACCESS read-only
    STATUS     current
    DESCRIPTION
        "-- empty --"
    ::= { lcsSetupPublicSpotModuleAddUserWizard 15 }

-- {SCALAR} 310.2.24.19.16
lcsSetupPublicSpotModuleAddUserWizardHideMultiLoginCheckbox OBJECT-TYPE
    SYNTAX     INTEGER
      {
        eNo (0),
        eYes (1)
      }
    MAX-ACCESS read-only
    STATUS     current
    DESCRIPTION
        "-- empty --"
    ::= { lcsSetupPublicSpotModuleAddUserWizard 16 }

-- {OID} 310.2.24.40
lcsSetupPublicSpotModuleXmlInterface OBJECT IDENTIFIER ::= { lcsSetupPublicSpotModule 40 }

-- {SCALAR} 310.2.24.40.1
lcsSetupPublicSpotModuleXmlInterfaceOperating OBJECT-TYPE
    SYNTAX     INTEGER
      {
        eNo (0),
        eYes (1)
      }
    MAX-ACCESS read-only
    STATUS     current
    DESCRIPTION
        "-- empty --"
    ::= { lcsSetupPublicSpotModuleXmlInterface 1 }

-- {SCALAR} 310.2.24.40.2
lcsSetupPublicSpotModuleXmlInterfaceRadiusAuthentication OBJECT-TYPE
    SYNTAX     INTEGER
      {
        eNo (0),
        eYes (1)
      }
    MAX-ACCESS read-only
    STATUS     current
    DESCRIPTION
        "-- empty --"
    ::= { lcsSetupPublicSpotModuleXmlInterface 2 }

-- {OID} 310.2.24.41
lcsSetupPublicSpotModuleAuthMod OBJECT IDENTIFIER ::= { lcsSetupPublicSpotModule 41 }

-- {OID} 310.2.24.41.1
lcsSetupPublicSpotModuleAuthModEmlAuth OBJECT IDENTIFIER ::= { lcsSetupPublicSpotModuleAuthMod 1 }

-- {SCALAR} 310.2.24.41.1.1
lcsSetupPublicSpotModuleAuthModEmlAuthLimitEMailsPerHour OBJECT-TYPE
    SYNTAX     INTEGER (0..65535)
    MAX-ACCESS read-write
    STATUS     current
    DESCRIPTION
        "-- empty --"
    ::= { lcsSetupPublicSpotModuleAuthModEmlAuth 1 }

-- {SCALAR} 310.2.24.41.1.2
lcsSetupPublicSpotModuleAuthModEmlAuthUserMustAcceptGtc OBJECT-TYPE
    SYNTAX     INTEGER
      {
        eNo (0),
        eYes (1)
      }
    MAX-ACCESS read-only
    STATUS     current
    DESCRIPTION
        "-- empty --"
    ::= { lcsSetupPublicSpotModuleAuthModEmlAuth 2 }

-- {SCALAR} 310.2.24.41.1.3
lcsSetupPublicSpotModuleAuthModEmlAuthSubject OBJECT-TYPE
    SYNTAX     DisplayString (SIZE(0..256))
    MAX-ACCESS read-write
    STATUS     current
    DESCRIPTION
        "-- empty --"
    ::= { lcsSetupPublicSpotModuleAuthModEmlAuth 3 }

-- {SCALAR} 310.2.24.41.1.4
lcsSetupPublicSpotModuleAuthModEmlAuthBody OBJECT-TYPE
    SYNTAX     DisplayString (SIZE(0..256))
    MAX-ACCESS read-write
    STATUS     current
    DESCRIPTION
        "-- empty --"
    ::= { lcsSetupPublicSpotModuleAuthModEmlAuth 4 }

-- {SCALAR} 310.2.24.41.1.5
lcsSetupPublicSpotModuleAuthModEmlAuthMaxRequestAttempts OBJECT-TYPE
    SYNTAX     INTEGER (0..65535)
    MAX-ACCESS read-write
    STATUS     current
    DESCRIPTION
        "-- empty --"
    ::= { lcsSetupPublicSpotModuleAuthModEmlAuth 5 }

-- {SCALAR} 310.2.24.41.1.6
lcsSetupPublicSpotModuleAuthModEmlAuthLocalEMailAddress OBJECT-TYPE
    SYNTAX     DisplayString (SIZE(0..150))
    MAX-ACCESS read-write
    STATUS     current
    DESCRIPTION
        "-- empty --"
    ::= { lcsSetupPublicSpotModuleAuthModEmlAuth 6 }

-- {SCALAR} 310.2.24.41.1.7
lcsSetupPublicSpotModuleAuthModEmlAuthRealName OBJECT-TYPE
    SYNTAX     DisplayString (SIZE(0..150))
    MAX-ACCESS read-write
    STATUS     current
    DESCRIPTION
        "-- empty --"
    ::= { lcsSetupPublicSpotModuleAuthModEmlAuth 7 }

-- {SCALAR} 310.2.24.41.1.8
lcsSetupPublicSpotModuleAuthModEmlAuthBlackWhiteDomainList OBJECT-TYPE
    SYNTAX     INTEGER
      {
        eBlacklist (0),
        eWhitelist (1)
      }
    MAX-ACCESS read-only
    STATUS     current
    DESCRIPTION
        "-- empty --"
    ::= { lcsSetupPublicSpotModuleAuthModEmlAuth 8 }

-- {TABLE} 310.2.24.41.1.9
lcsSetupPublicSpotModuleAuthModEmlAuthDomainListTable OBJECT-TYPE
    SYNTAX     SEQUENCE OF LcsSetupPublicSpotModuleAuthModEmlAuthDomainListEntry
    MAX-ACCESS not-accessible
    STATUS     current
    DESCRIPTION
        "-- empty --"
    ::= { lcsSetupPublicSpotModuleAuthModEmlAuth 9 }

-- {ENTRY} 310.2.24.41.1.9.1
lcsSetupPublicSpotModuleAuthModEmlAuthDomainListEntry OBJECT-TYPE
    SYNTAX     LcsSetupPublicSpotModuleAuthModEmlAuthDomainListEntry
    MAX-ACCESS not-accessible
    STATUS     current
    DESCRIPTION
        ""
    INDEX {
        lcsSetupPublicSpotModuleAuthModEmlAuthDomainListEntryDomain
    }
    ::= { lcsSetupPublicSpotModuleAuthModEmlAuthDomainListTable 1 }

-- {SEQUENCE}
LcsSetupPublicSpotModuleAuthModEmlAuthDomainListEntry ::= SEQUENCE {
    lcsSetupPublicSpotModuleAuthModEmlAuthDomainListEntryDomain DisplayString
}

-- {COLUMN} 310.2.24.41.1.9.1.1
lcsSetupPublicSpotModuleAuthModEmlAuthDomainListEntryDomain OBJECT-TYPE
    SYNTAX     DisplayString (SIZE(0..150))
    MAX-ACCESS read-write
    STATUS     current
    DESCRIPTION
        "-- empty --"
    ::= { lcsSetupPublicSpotModuleAuthModEmlAuthDomainListEntry 1 }

-- {OID} 310.2.24.41.2
lcsSetupPublicSpotModuleAuthModEmlSmsAuth OBJECT IDENTIFIER ::= { lcsSetupPublicSpotModuleAuthMod 2 }

-- {SCALAR} 310.2.24.41.2.1
lcsSetupPublicSpotModuleAuthModEmlSmsAuthLimitEMailsPerHour OBJECT-TYPE
    SYNTAX     INTEGER (0..65535)
    MAX-ACCESS read-write
    STATUS     current
    DESCRIPTION
        "-- empty --"
    ::= { lcsSetupPublicSpotModuleAuthModEmlSmsAuth 1 }

-- {SCALAR} 310.2.24.41.2.2
lcsSetupPublicSpotModuleAuthModEmlSmsAuthUserMustAcceptGtc OBJECT-TYPE
    SYNTAX     INTEGER
      {
        eNo (0),
        eYes (1)
      }
    MAX-ACCESS read-only
    STATUS     current
    DESCRIPTION
        "-- empty --"
    ::= { lcsSetupPublicSpotModuleAuthModEmlSmsAuth 2 }

-- {SCALAR} 310.2.24.41.2.3
lcsSetupPublicSpotModuleAuthModEmlSmsAuthSubject OBJECT-TYPE
    SYNTAX     DisplayString (SIZE(0..256))
    MAX-ACCESS read-write
    STATUS     current
    DESCRIPTION
        "-- empty --"
    ::= { lcsSetupPublicSpotModuleAuthModEmlSmsAuth 3 }

-- {SCALAR} 310.2.24.41.2.4
lcsSetupPublicSpotModuleAuthModEmlSmsAuthMaxRequestAttempts OBJECT-TYPE
    SYNTAX     INTEGER (0..65535)
    MAX-ACCESS read-write
    STATUS     current
    DESCRIPTION
        "-- empty --"
    ::= { lcsSetupPublicSpotModuleAuthModEmlSmsAuth 4 }

-- {SCALAR} 310.2.24.41.2.5
lcsSetupPublicSpotModuleAuthModEmlSmsAuthLocalEMailAddress OBJECT-TYPE
    SYNTAX     DisplayString (SIZE(0..150))
    MAX-ACCESS read-write
    STATUS     current
    DESCRIPTION
        "-- empty --"
    ::= { lcsSetupPublicSpotModuleAuthModEmlSmsAuth 5 }

-- {SCALAR} 310.2.24.41.2.6
lcsSetupPublicSpotModuleAuthModEmlSmsAuthRealName OBJECT-TYPE
    SYNTAX     DisplayString (SIZE(0..150))
    MAX-ACCESS read-write
    STATUS     current
    DESCRIPTION
        "-- empty --"
    ::= { lcsSetupPublicSpotModuleAuthModEmlSmsAuth 6 }

-- {SCALAR} 310.2.24.41.2.12
lcsSetupPublicSpotModuleAuthModEmlSmsAuthBody OBJECT-TYPE
    SYNTAX     DisplayString (SIZE(0..256))
    MAX-ACCESS read-write
    STATUS     current
    DESCRIPTION
        "-- empty --"
    ::= { lcsSetupPublicSpotModuleAuthModEmlSmsAuth 12 }

-- {SCALAR} 310.2.24.41.2.13
lcsSetupPublicSpotModuleAuthModEmlSmsAuthGatewayEMailAddress OBJECT-TYPE
    SYNTAX     DisplayString (SIZE(0..150))
    MAX-ACCESS read-write
    STATUS     current
    DESCRIPTION
        "-- empty --"
    ::= { lcsSetupPublicSpotModuleAuthModEmlSmsAuth 13 }

-- {TABLE} 310.2.24.41.2.14
lcsSetupPublicSpotModuleAuthModEmlSmsAuthAlldCtryCodsTable OBJECT-TYPE
    SYNTAX     SEQUENCE OF LcsSetupPublicSpotModuleAuthModEmlSmsAuthAlldCtryCodsEntry
    MAX-ACCESS not-accessible
    STATUS     current
    DESCRIPTION
        ""
    ::= { lcsSetupPublicSpotModuleAuthModEmlSmsAuth 14 }

-- {ENTRY} 310.2.24.41.2.14.1
lcsSetupPublicSpotModuleAuthModEmlSmsAuthAlldCtryCodsEntry OBJECT-TYPE
    SYNTAX     LcsSetupPublicSpotModuleAuthModEmlSmsAuthAlldCtryCodsEntry
    MAX-ACCESS not-accessible
    STATUS     current
    DESCRIPTION
        ""
    INDEX {
        lcsSetupPublicSpotModuleAuthModEmlSmsAuthAlldCtryCodsEntryName
    }
    ::= { lcsSetupPublicSpotModuleAuthModEmlSmsAuthAlldCtryCodsTable 1 }

-- {SEQUENCE}
LcsSetupPublicSpotModuleAuthModEmlSmsAuthAlldCtryCodsEntry ::= SEQUENCE {
    lcsSetupPublicSpotModuleAuthModEmlSmsAuthAlldCtryCodsEntryName DisplayString,
    lcsSetupPublicSpotModuleAuthModEmlSmsAuthAlldCtryCodsEntryCode INTEGER
}

-- {COLUMN} 310.2.24.41.2.14.1.1
lcsSetupPublicSpotModuleAuthModEmlSmsAuthAlldCtryCodsEntryName OBJECT-TYPE
    SYNTAX     DisplayString (SIZE(0..150))
    MAX-ACCESS read-write
    STATUS     current
    DESCRIPTION
        "-- empty --"
    ::= { lcsSetupPublicSpotModuleAuthModEmlSmsAuthAlldCtryCodsEntry 1 }

-- {COLUMN} 310.2.24.41.2.14.1.2
lcsSetupPublicSpotModuleAuthModEmlSmsAuthAlldCtryCodsEntryCode OBJECT-TYPE
    SYNTAX     INTEGER (0..65535)
    MAX-ACCESS read-write
    STATUS     current
    DESCRIPTION
        "-- empty --"
    ::= { lcsSetupPublicSpotModuleAuthModEmlSmsAuthAlldCtryCodsEntry 2 }

-- {OID} 310.2.24.41.3
lcsSetupPublicSpotModuleAuthModUserTemplate OBJECT IDENTIFIER ::= { lcsSetupPublicSpotModuleAuthMod 3 }

-- {SCALAR} 310.2.24.41.3.2
lcsSetupPublicSpotModuleAuthModUserTemplateComment OBJECT-TYPE
    SYNTAX     DisplayString (SIZE(0..251))
    MAX-ACCESS read-write
    STATUS     current
    DESCRIPTION
        "-- empty --"
    ::= { lcsSetupPublicSpotModuleAuthModUserTemplate 2 }

-- {SCALAR} 310.2.24.41.3.3
lcsSetupPublicSpotModuleAuthModUserTemplateVolumeBudget OBJECT-TYPE
    SYNTAX     INTEGER (0..2147483647)
    MAX-ACCESS read-write
    STATUS     current
    DESCRIPTION
        "-- empty --"
    ::= { lcsSetupPublicSpotModuleAuthModUserTemplate 3 }

-- {SCALAR} 310.2.24.41.3.4
lcsSetupPublicSpotModuleAuthModUserTemplateTimeBudget OBJECT-TYPE
    SYNTAX     INTEGER (0..2147483647)
    MAX-ACCESS read-write
    STATUS     current
    DESCRIPTION
        "-- empty --"
    ::= { lcsSetupPublicSpotModuleAuthModUserTemplate 4 }

-- {SCALAR} 310.2.24.41.3.5
lcsSetupPublicSpotModuleAuthModUserTemplateRelExpiry OBJECT-TYPE
    SYNTAX     INTEGER (0..2147483647)
    MAX-ACCESS read-write
    STATUS     current
    DESCRIPTION
        "-- empty --"
    ::= { lcsSetupPublicSpotModuleAuthModUserTemplate 5 }

-- {SCALAR} 310.2.24.41.3.6
lcsSetupPublicSpotModuleAuthModUserTemplateAbsExpiry OBJECT-TYPE
    SYNTAX     INTEGER (0..2147483647)
    MAX-ACCESS read-write
    STATUS     current
    DESCRIPTION
        "-- empty --"
    ::= { lcsSetupPublicSpotModuleAuthModUserTemplate 6 }

-- {SCALAR} 310.2.24.41.3.7
lcsSetupPublicSpotModuleAuthModUserTemplateExpiryType OBJECT-TYPE
    SYNTAX     BITS
      {
        eAbsolute (7),
        eRelative (6),
        eNone (0)
      }
    MAX-ACCESS read-write
    STATUS     current
    DESCRIPTION
        "-- empty --"
    ::= { lcsSetupPublicSpotModuleAuthModUserTemplate 7 }

-- {SCALAR} 310.2.24.41.3.8
lcsSetupPublicSpotModuleAuthModUserTemplateMaxConcurrentLogins OBJECT-TYPE
    SYNTAX     INTEGER (0..2147483647)
    MAX-ACCESS read-write
    STATUS     current
    DESCRIPTION
        "-- empty --"
    ::= { lcsSetupPublicSpotModuleAuthModUserTemplate 8 }

-- {SCALAR} 310.2.24.41.3.9
lcsSetupPublicSpotModuleAuthModUserTemplateMultipleLogin OBJECT-TYPE
    SYNTAX     INTEGER
      {
        eYes (0),
        eNo (1)
      }
    MAX-ACCESS read-only
    STATUS     current
    DESCRIPTION
        "-- empty --"
    ::= { lcsSetupPublicSpotModuleAuthModUserTemplate 9 }

-- {OID} 310.2.25
lcsSetupRadius OBJECT IDENTIFIER ::= { lcsSetup 25 }

-- {SCALAR} 310.2.25.4
lcsSetupRadiusAuthTimeout OBJECT-TYPE
    SYNTAX     INTEGER (0..65535)
    MAX-ACCESS read-only
    STATUS     current
    DESCRIPTION
        "-- empty --"
    ::= { lcsSetupRadius 4 }

-- {SCALAR} 310.2.25.5
lcsSetupRadiusAuthRetry OBJECT-TYPE
    SYNTAX     INTEGER (0..255)
    MAX-ACCESS read-only
    STATUS     current
    DESCRIPTION
        "-- empty --"
    ::= { lcsSetupRadius 5 }

-- {SCALAR} 310.2.25.9
lcsSetupRadiusBackupQueryStrategy OBJECT-TYPE
    SYNTAX     INTEGER
      {
        eBlock (0),
        eCyclic (1)
      }
    MAX-ACCESS read-write
    STATUS     current
    DESCRIPTION
        "-- empty --"
    ::= { lcsSetupRadius 9 }

-- {OID} 310.2.25.10
lcsSetupRadiusServer OBJECT IDENTIFIER ::= { lcsSetupRadius 10 }

-- {SCALAR} 310.2.25.10.1
lcsSetupRadiusServerAuthentificationPort OBJECT-TYPE
    SYNTAX     INTEGER (0..65535)
    MAX-ACCESS read-write
    STATUS     current
    DESCRIPTION
        "-- empty --"
    ::= { lcsSetupRadiusServer 1 }

-- {SCALAR} 310.2.25.10.11
lcsSetupRadiusServerAccountingPort OBJECT-TYPE
    SYNTAX     INTEGER (0..65535)
    MAX-ACCESS read-write
    STATUS     current
    DESCRIPTION
        "-- empty --"
    ::= { lcsSetupRadiusServer 11 }

-- {SCALAR} 310.2.25.10.13
lcsSetupRadiusServerRadsecPort OBJECT-TYPE
    SYNTAX     INTEGER (0..65535)
    MAX-ACCESS read-write
    STATUS     current
    DESCRIPTION
        "-- empty --"
    ::= { lcsSetupRadiusServer 13 }

-- {SCALAR} 310.2.25.10.15
lcsSetupRadiusServerAllowStatusRequests OBJECT-TYPE
    SYNTAX     INTEGER
      {
        eNo (0),
        eYes (1)
      }
    MAX-ACCESS read-write
    STATUS     current
    DESCRIPTION
        "-- empty --"
    ::= { lcsSetupRadiusServer 15 }

-- {TABLE} 310.2.25.10.2
lcsSetupRadiusServerClientsTable OBJECT-TYPE
    SYNTAX     SEQUENCE OF LcsSetupRadiusServerClientsEntry
    MAX-ACCESS not-accessible
    STATUS     current
    DESCRIPTION
        "-- empty --"
    ::= { lcsSetupRadiusServer 2 }

-- {ENTRY} 310.2.25.10.2.1
lcsSetupRadiusServerClientsEntry OBJECT-TYPE
    SYNTAX     LcsSetupRadiusServerClientsEntry
    MAX-ACCESS not-accessible
    STATUS     current
    DESCRIPTION
        ""
    INDEX {
        lcsSetupRadiusServerClientsEntryIpNetwork,
        lcsSetupRadiusServerClientsEntryIpNetmask
    }
    ::= { lcsSetupRadiusServerClientsTable 1 }

-- {SEQUENCE}
LcsSetupRadiusServerClientsEntry ::= SEQUENCE {
    lcsSetupRadiusServerClientsEntryIpNetwork IpAddress,
    lcsSetupRadiusServerClientsEntryIpNetmask IpAddress,
    lcsSetupRadiusServerClientsEntryProtocols INTEGER,
    lcsSetupRadiusServerClientsEntrySecret DisplayString
}

-- {COLUMN} 310.2.25.10.2.1.1
lcsSetupRadiusServerClientsEntryIpNetwork OBJECT-TYPE
    SYNTAX     IpAddress
    MAX-ACCESS read-write
    STATUS     current
    DESCRIPTION
        "-- empty --"
    ::= { lcsSetupRadiusServerClientsEntry 1 }

-- {COLUMN} 310.2.25.10.2.1.3
lcsSetupRadiusServerClientsEntryIpNetmask OBJECT-TYPE
    SYNTAX     IpAddress
    MAX-ACCESS read-write
    STATUS     current
    DESCRIPTION
        "-- empty --"
    ::= { lcsSetupRadiusServerClientsEntry 3 }

-- {COLUMN} 310.2.25.10.2.1.4
lcsSetupRadiusServerClientsEntryProtocols OBJECT-TYPE
    SYNTAX     INTEGER
      {
        eRadius (0),
        eRadsec (1),
        eAll (255)
      }
    MAX-ACCESS read-write
    STATUS     current
    DESCRIPTION
        "-- empty --"
    ::= { lcsSetupRadiusServerClientsEntry 4 }

-- {COLUMN} 310.2.25.10.2.1.2
lcsSetupRadiusServerClientsEntrySecret OBJECT-TYPE
    SYNTAX     DisplayString (SIZE(0..64))
    MAX-ACCESS read-write
    STATUS     current
    DESCRIPTION
        "-- empty --"
    ::= { lcsSetupRadiusServerClientsEntry 2 }

-- {TABLE} 310.2.25.10.7
lcsSetupRadiusServerUsersTable OBJECT-TYPE
    SYNTAX     SEQUENCE OF LcsSetupRadiusServerUsersEntry
    MAX-ACCESS not-accessible
    STATUS     current
    DESCRIPTION
        "-- empty --"
    ::= { lcsSetupRadiusServer 7 }

-- {ENTRY} 310.2.25.10.7.1
lcsSetupRadiusServerUsersEntry OBJECT-TYPE
    SYNTAX     LcsSetupRadiusServerUsersEntry
    MAX-ACCESS not-accessible
    STATUS     current
    DESCRIPTION
        ""
    INDEX {
        lcsSetupRadiusServerUsersEntryUserName,
        lcsSetupRadiusServerUsersEntryCallingStationIdMask,
        lcsSetupRadiusServerUsersEntryCalledStationIdMask
    }
    ::= { lcsSetupRadiusServerUsersTable 1 }

-- {SEQUENCE}
LcsSetupRadiusServerUsersEntry ::= SEQUENCE {
    lcsSetupRadiusServerUsersEntryUserName DisplayString,
    lcsSetupRadiusServerUsersEntryCallingStationIdMask DisplayString,
    lcsSetupRadiusServerUsersEntryCalledStationIdMask DisplayString,
    lcsSetupRadiusServerUsersEntryCaseSensitive INTEGER,
    lcsSetupRadiusServerUsersEntryPassword DisplayString,
    lcsSetupRadiusServerUsersEntryMultipleLogin INTEGER,
    lcsSetupRadiusServerUsersEntryMaxConcurrentLogins INTEGER,
    lcsSetupRadiusServerUsersEntryExpiryType BITS,
    lcsSetupRadiusServerUsersEntryAbsExpiry DisplayString,
    lcsSetupRadiusServerUsersEntryRelExpiry INTEGER,
    lcsSetupRadiusServerUsersEntryTimeBudget INTEGER,
    lcsSetupRadiusServerUsersEntryVolumeBudget INTEGER,
    lcsSetupRadiusServerUsersEntryComment DisplayString,
    lcsSetupRadiusServerUsersEntryServiceType INTEGER,
    lcsSetupRadiusServerUsersEntryLimitAuthMethods BITS,
    lcsSetupRadiusServerUsersEntryVlanId INTEGER,
    lcsSetupRadiusServerUsersEntryTxLimit INTEGER,
    lcsSetupRadiusServerUsersEntryRxLimit INTEGER,
    lcsSetupRadiusServerUsersEntryWpaPassphrase DisplayString
}

-- {COLUMN} 310.2.25.10.7.1.1
lcsSetupRadiusServerUsersEntryUserName OBJECT-TYPE
    SYNTAX     DisplayString (SIZE(0..48))
    MAX-ACCESS read-write
    STATUS     current
    DESCRIPTION
        "-- empty --"
    ::= { lcsSetupRadiusServerUsersEntry 1 }

-- {COLUMN} 310.2.25.10.7.1.5
lcsSetupRadiusServerUsersEntryCallingStationIdMask OBJECT-TYPE
    SYNTAX     DisplayString (SIZE(0..64))
    MAX-ACCESS read-write
    STATUS     current
    DESCRIPTION
        "-- empty --"
    ::= { lcsSetupRadiusServerUsersEntry 5 }

-- {COLUMN} 310.2.25.10.7.1.6
lcsSetupRadiusServerUsersEntryCalledStationIdMask OBJECT-TYPE
    SYNTAX     DisplayString (SIZE(0..64))
    MAX-ACCESS read-write
    STATUS     current
    DESCRIPTION
        "-- empty --"
    ::= { lcsSetupRadiusServerUsersEntry 6 }

-- {COLUMN} 310.2.25.10.7.1.17
lcsSetupRadiusServerUsersEntryCaseSensitive OBJECT-TYPE
    SYNTAX     INTEGER
      {
        eYes (0),
        eNo (1)
      }
    MAX-ACCESS read-write
    STATUS     current
    DESCRIPTION
        "-- empty --"
    ::= { lcsSetupRadiusServerUsersEntry 17 }

-- {COLUMN} 310.2.25.10.7.1.2
lcsSetupRadiusServerUsersEntryPassword OBJECT-TYPE
    SYNTAX     DisplayString (SIZE(0..32))
    MAX-ACCESS read-write
    STATUS     current
    DESCRIPTION
        "-- empty --"
    ::= { lcsSetupRadiusServerUsersEntry 2 }

-- {COLUMN} 310.2.25.10.7.1.9
lcsSetupRadiusServerUsersEntryMultipleLogin OBJECT-TYPE
    SYNTAX     INTEGER
      {
        eYes (0),
        eNo (1)
      }
    MAX-ACCESS read-write
    STATUS     current
    DESCRIPTION
        "-- empty --"
    ::= { lcsSetupRadiusServerUsersEntry 9 }

-- {COLUMN} 310.2.25.10.7.1.19
lcsSetupRadiusServerUsersEntryMaxConcurrentLogins OBJECT-TYPE
    SYNTAX     INTEGER (0..2147483647)
    MAX-ACCESS read-write
    STATUS     current
    DESCRIPTION
        "-- empty --"
    ::= { lcsSetupRadiusServerUsersEntry 19 }

-- {COLUMN} 310.2.25.10.7.1.13
lcsSetupRadiusServerUsersEntryExpiryType OBJECT-TYPE
    SYNTAX     BITS
      {
        eAbsolute (7),
        eRelative (6),
        eNone (0)
      }
    MAX-ACCESS read-write
    STATUS     current
    DESCRIPTION
        "-- empty --"
    ::= { lcsSetupRadiusServerUsersEntry 13 }

-- {COLUMN} 310.2.25.10.7.1.10
lcsSetupRadiusServerUsersEntryAbsExpiry OBJECT-TYPE
    SYNTAX     DisplayString (SIZE(0..21))
    MAX-ACCESS read-write
    STATUS     current
    DESCRIPTION
        "-- empty --"
    ::= { lcsSetupRadiusServerUsersEntry 10 }

-- {COLUMN} 310.2.25.10.7.1.14
lcsSetupRadiusServerUsersEntryRelExpiry OBJECT-TYPE
    SYNTAX     INTEGER (0..2147483647)
    MAX-ACCESS read-write
    STATUS     current
    DESCRIPTION
        "-- empty --"
    ::= { lcsSetupRadiusServerUsersEntry 14 }

-- {COLUMN} 310.2.25.10.7.1.11
lcsSetupRadiusServerUsersEntryTimeBudget OBJECT-TYPE
    SYNTAX     INTEGER (0..2147483647)
    MAX-ACCESS read-write
    STATUS     current
    DESCRIPTION
        "-- empty --"
    ::= { lcsSetupRadiusServerUsersEntry 11 }

-- {COLUMN} 310.2.25.10.7.1.12
lcsSetupRadiusServerUsersEntryVolumeBudget OBJECT-TYPE
    SYNTAX     INTEGER (0..2147483647)
    MAX-ACCESS read-write
    STATUS     current
    DESCRIPTION
        "-- empty --"
    ::= { lcsSetupRadiusServerUsersEntry 12 }

-- {COLUMN} 310.2.25.10.7.1.15
lcsSetupRadiusServerUsersEntryComment OBJECT-TYPE
    SYNTAX     DisplayString (SIZE(0..251))
    MAX-ACCESS read-write
    STATUS     current
    DESCRIPTION
        "-- empty --"
    ::= { lcsSetupRadiusServerUsersEntry 15 }

-- {COLUMN} 310.2.25.10.7.1.16
lcsSetupRadiusServerUsersEntryServiceType OBJECT-TYPE
    SYNTAX     INTEGER
      {
        eAny (0),
        eFramed (2),
        eLogin (1),
        eAuthOnly (8)
      }
    MAX-ACCESS read-write
    STATUS     current
    DESCRIPTION
        "-- empty --"
    ::= { lcsSetupRadiusServerUsersEntry 16 }

-- {COLUMN} 310.2.25.10.7.1.3
lcsSetupRadiusServerUsersEntryLimitAuthMethods OBJECT-TYPE
    SYNTAX     BITS
      {
        ePap (15),
        eChap (14),
        eMschap (13),
        eMschapv2 (12),
        eEap (11),
        eAll (0)
      }
    MAX-ACCESS read-write
    STATUS     current
    DESCRIPTION
        "-- empty --"
    ::= { lcsSetupRadiusServerUsersEntry 3 }

-- {COLUMN} 310.2.25.10.7.1.4
lcsSetupRadiusServerUsersEntryVlanId OBJECT-TYPE
    SYNTAX     INTEGER (0..65535)
    MAX-ACCESS read-write
    STATUS     current
    DESCRIPTION
        "-- empty --"
    ::= { lcsSetupRadiusServerUsersEntry 4 }

-- {COLUMN} 310.2.25.10.7.1.7
lcsSetupRadiusServerUsersEntryTxLimit OBJECT-TYPE
    SYNTAX     INTEGER (0..2147483647)
    MAX-ACCESS read-write
    STATUS     current
    DESCRIPTION
        "-- empty --"
    ::= { lcsSetupRadiusServerUsersEntry 7 }

-- {COLUMN} 310.2.25.10.7.1.8
lcsSetupRadiusServerUsersEntryRxLimit OBJECT-TYPE
    SYNTAX     INTEGER (0..2147483647)
    MAX-ACCESS read-write
    STATUS     current
    DESCRIPTION
        "-- empty --"
    ::= { lcsSetupRadiusServerUsersEntry 8 }

-- {COLUMN} 310.2.25.10.7.1.18
lcsSetupRadiusServerUsersEntryWpaPassphrase OBJECT-TYPE
    SYNTAX     DisplayString (SIZE(0..63))
    MAX-ACCESS read-write
    STATUS     current
    DESCRIPTION
        "-- empty --"
    ::= { lcsSetupRadiusServerUsersEntry 18 }

-- {TABLE} 310.2.25.10.3
lcsSetupRadiusServerForwardServersTable OBJECT-TYPE
    SYNTAX     SEQUENCE OF LcsSetupRadiusServerForwardServersEntry
    MAX-ACCESS not-accessible
    STATUS     current
    DESCRIPTION
        "-- empty --"
    ::= { lcsSetupRadiusServer 3 }

-- {ENTRY} 310.2.25.10.3.1
lcsSetupRadiusServerForwardServersEntry OBJECT-TYPE
    SYNTAX     LcsSetupRadiusServerForwardServersEntry
    MAX-ACCESS not-accessible
    STATUS     current
    DESCRIPTION
        ""
    INDEX {
        lcsSetupRadiusServerForwardServersEntryRealm
    }
    ::= { lcsSetupRadiusServerForwardServersTable 1 }

-- {SEQUENCE}
LcsSetupRadiusServerForwardServersEntry ::= SEQUENCE {
    lcsSetupRadiusServerForwardServersEntryRealm DisplayString,
    lcsSetupRadiusServerForwardServersEntryIpAddress IpAddress,
    lcsSetupRadiusServerForwardServersEntryPort INTEGER,
    lcsSetupRadiusServerForwardServersEntrySecret DisplayString,
    lcsSetupRadiusServerForwardServersEntryLoopbackAddr DisplayString,
    lcsSetupRadiusServerForwardServersEntryProtocol INTEGER,
    lcsSetupRadiusServerForwardServersEntryAccntIpAddress IpAddress,
    lcsSetupRadiusServerForwardServersEntryAccntPort INTEGER,
    lcsSetupRadiusServerForwardServersEntryAccntSecret DisplayString,
    lcsSetupRadiusServerForwardServersEntryAccntLoopbackAddr DisplayString,
    lcsSetupRadiusServerForwardServersEntryAccntProtocol INTEGER,
    lcsSetupRadiusServerForwardServersEntryBackup DisplayString
}

-- {COLUMN} 310.2.25.10.3.1.1
lcsSetupRadiusServerForwardServersEntryRealm OBJECT-TYPE
    SYNTAX     DisplayString (SIZE(0..24))
    MAX-ACCESS read-write
    STATUS     current
    DESCRIPTION
        "-- empty --"
    ::= { lcsSetupRadiusServerForwardServersEntry 1 }

-- {COLUMN} 310.2.25.10.3.1.2
lcsSetupRadiusServerForwardServersEntryIpAddress OBJECT-TYPE
    SYNTAX     IpAddress
    MAX-ACCESS read-write
    STATUS     current
    DESCRIPTION
        "-- empty --"
    ::= { lcsSetupRadiusServerForwardServersEntry 2 }

-- {COLUMN} 310.2.25.10.3.1.3
lcsSetupRadiusServerForwardServersEntryPort OBJECT-TYPE
    SYNTAX     INTEGER (0..65535)
    MAX-ACCESS read-write
    STATUS     current
    DESCRIPTION
        "-- empty --"
    ::= { lcsSetupRadiusServerForwardServersEntry 3 }

-- {COLUMN} 310.2.25.10.3.1.4
lcsSetupRadiusServerForwardServersEntrySecret OBJECT-TYPE
    SYNTAX     DisplayString (SIZE(0..64))
    MAX-ACCESS read-write
    STATUS     current
    DESCRIPTION
        "-- empty --"
    ::= { lcsSetupRadiusServerForwardServersEntry 4 }

-- {COLUMN} 310.2.25.10.3.1.6
lcsSetupRadiusServerForwardServersEntryLoopbackAddr OBJECT-TYPE
    SYNTAX     DisplayString (SIZE(0..16))
    MAX-ACCESS read-write
    STATUS     current
    DESCRIPTION
        "-- empty --"
    ::= { lcsSetupRadiusServerForwardServersEntry 6 }

-- {COLUMN} 310.2.25.10.3.1.7
lcsSetupRadiusServerForwardServersEntryProtocol OBJECT-TYPE
    SYNTAX     INTEGER
      {
        eRadius (0),
        eRadsec (1)
      }
    MAX-ACCESS read-write
    STATUS     current
    DESCRIPTION
        "-- empty --"
    ::= { lcsSetupRadiusServerForwardServersEntry 7 }

-- {COLUMN} 310.2.25.10.3.1.8
lcsSetupRadiusServerForwardServersEntryAccntIpAddress OBJECT-TYPE
    SYNTAX     IpAddress
    MAX-ACCESS read-write
    STATUS     current
    DESCRIPTION
        "-- empty --"
    ::= { lcsSetupRadiusServerForwardServersEntry 8 }

-- {COLUMN} 310.2.25.10.3.1.9
lcsSetupRadiusServerForwardServersEntryAccntPort OBJECT-TYPE
    SYNTAX     INTEGER (0..65535)
    MAX-ACCESS read-write
    STATUS     current
    DESCRIPTION
        "-- empty --"
    ::= { lcsSetupRadiusServerForwardServersEntry 9 }

-- {COLUMN} 310.2.25.10.3.1.10
lcsSetupRadiusServerForwardServersEntryAccntSecret OBJECT-TYPE
    SYNTAX     DisplayString (SIZE(0..64))
    MAX-ACCESS read-write
    STATUS     current
    DESCRIPTION
        "-- empty --"
    ::= { lcsSetupRadiusServerForwardServersEntry 10 }

-- {COLUMN} 310.2.25.10.3.1.11
lcsSetupRadiusServerForwardServersEntryAccntLoopbackAddr OBJECT-TYPE
    SYNTAX     DisplayString (SIZE(0..16))
    MAX-ACCESS read-write
    STATUS     current
    DESCRIPTION
        "-- empty --"
    ::= { lcsSetupRadiusServerForwardServersEntry 11 }

-- {COLUMN} 310.2.25.10.3.1.12
lcsSetupRadiusServerForwardServersEntryAccntProtocol OBJECT-TYPE
    SYNTAX     INTEGER
      {
        eRadius (0),
        eRadsec (1)
      }
    MAX-ACCESS read-write
    STATUS     current
    DESCRIPTION
        "-- empty --"
    ::= { lcsSetupRadiusServerForwardServersEntry 12 }

-- {COLUMN} 310.2.25.10.3.1.5
lcsSetupRadiusServerForwardServersEntryBackup OBJECT-TYPE
    SYNTAX     DisplayString (SIZE(0..24))
    MAX-ACCESS read-write
    STATUS     current
    DESCRIPTION
        "-- empty --"
    ::= { lcsSetupRadiusServerForwardServersEntry 5 }

-- {SCALAR} 310.2.25.10.5
lcsSetupRadiusServerDefaultRealm OBJECT-TYPE
    SYNTAX     DisplayString (SIZE(0..24))
    MAX-ACCESS read-write
    STATUS     current
    DESCRIPTION
        "-- empty --"
    ::= { lcsSetupRadiusServer 5 }

-- {SCALAR} 310.2.25.10.6
lcsSetupRadiusServerEmptyRealm OBJECT-TYPE
    SYNTAX     DisplayString (SIZE(0..24))
    MAX-ACCESS read-write
    STATUS     current
    DESCRIPTION
        "-- empty --"
    ::= { lcsSetupRadiusServer 6 }

-- {SCALAR} 310.2.25.10.12
lcsSetupRadiusServerAccountingInterimInterval OBJECT-TYPE
    SYNTAX     INTEGER (0..2147483647)
    MAX-ACCESS read-write
    STATUS     current
    DESCRIPTION
        "-- empty --"
    ::= { lcsSetupRadiusServer 12 }

-- {SCALAR} 310.2.25.10.14
lcsSetupRadiusServerAutoCleanupUserTable OBJECT-TYPE
    SYNTAX     INTEGER
      {
        eNo (0),
        eYes (1)
      }
    MAX-ACCESS read-write
    STATUS     current
    DESCRIPTION
        "-- empty --"
    ::= { lcsSetupRadiusServer 14 }

-- {OID} 310.2.25.10.10
lcsSetupRadiusServerEap OBJECT IDENTIFIER ::= { lcsSetupRadiusServer 10 }

-- {SCALAR} 310.2.25.10.10.7
lcsSetupRadiusServerEapDefaultMethod OBJECT-TYPE
    SYNTAX     INTEGER
      {
        eMd5 (4),
        eGtc (6),
        eMschapv2 (26),
        eTls (13),
        eTtls (21),
        ePeap (25)
      }
    MAX-ACCESS read-write
    STATUS     current
    DESCRIPTION
        "-- empty --"
    ::= { lcsSetupRadiusServerEap 7 }

-- {SCALAR} 310.2.25.10.10.10
lcsSetupRadiusServerEapMschapv2BackendServer OBJECT-TYPE
    SYNTAX     DisplayString (SIZE(0..24))
    MAX-ACCESS read-write
    STATUS     current
    DESCRIPTION
        "-- empty --"
    ::= { lcsSetupRadiusServerEap 10 }

-- {SCALAR} 310.2.25.10.10.1
lcsSetupRadiusServerEapTunnelServer OBJECT-TYPE
    SYNTAX     DisplayString (SIZE(0..24))
    MAX-ACCESS read-write
    STATUS     current
    DESCRIPTION
        "-- empty --"
    ::= { lcsSetupRadiusServerEap 1 }

-- {SCALAR} 310.2.25.10.10.2
lcsSetupRadiusServerEapTlsCheckUsername OBJECT-TYPE
    SYNTAX     INTEGER
      {
        eNo (0),
        eYes (1)
      }
    MAX-ACCESS read-write
    STATUS     current
    DESCRIPTION
        "-- empty --"
    ::= { lcsSetupRadiusServerEap 2 }

-- {SCALAR} 310.2.25.10.10.5
lcsSetupRadiusServerEapTtlsDefaultTunnelMethod OBJECT-TYPE
    SYNTAX     INTEGER
      {
        eNone (0),
        eMd5 (4),
        eGtc (6),
        eMschapv2 (26)
      }
    MAX-ACCESS read-write
    STATUS     current
    DESCRIPTION
        "-- empty --"
    ::= { lcsSetupRadiusServerEap 5 }

-- {SCALAR} 310.2.25.10.10.6
lcsSetupRadiusServerEapPeapDefaultTunnelMethod OBJECT-TYPE
    SYNTAX     INTEGER
      {
        eNone (0),
        eMd5 (4),
        eGtc (6),
        eMschapv2 (26)
      }
    MAX-ACCESS read-write
    STATUS     current
    DESCRIPTION
        "-- empty --"
    ::= { lcsSetupRadiusServerEap 6 }

-- {SCALAR} 310.2.25.10.10.3
lcsSetupRadiusServerEapReauthPeriod OBJECT-TYPE
    SYNTAX     INTEGER (0..2147483647)
    MAX-ACCESS read-write
    STATUS     current
    DESCRIPTION
        "-- empty --"
    ::= { lcsSetupRadiusServerEap 3 }

-- {SCALAR} 310.2.25.10.10.4
lcsSetupRadiusServerEapRetransmitTimeout OBJECT-TYPE
    SYNTAX     INTEGER (0..2147483647)
    MAX-ACCESS read-write
    STATUS     current
    DESCRIPTION
        "-- empty --"
    ::= { lcsSetupRadiusServerEap 4 }

-- {SCALAR} 310.2.25.10.10.8
lcsSetupRadiusServerEapDefaultMtu OBJECT-TYPE
    SYNTAX     INTEGER (0..65535)
    MAX-ACCESS read-write
    STATUS     current
    DESCRIPTION
        "-- empty --"
    ::= { lcsSetupRadiusServerEap 8 }

-- {TABLE} 310.2.25.10.10.9
lcsSetupRadiusServerEapAllowMethodsTable OBJECT-TYPE
    SYNTAX     SEQUENCE OF LcsSetupRadiusServerEapAllowMethodsEntry
    MAX-ACCESS not-accessible
    STATUS     current
    DESCRIPTION
        "-- empty --"
    ::= { lcsSetupRadiusServerEap 9 }

-- {ENTRY} 310.2.25.10.10.9.1
lcsSetupRadiusServerEapAllowMethodsEntry OBJECT-TYPE
    SYNTAX     LcsSetupRadiusServerEapAllowMethodsEntry
    MAX-ACCESS not-accessible
    STATUS     current
    DESCRIPTION
        ""
    INDEX {
        lcsSetupRadiusServerEapAllowMethodsEntryMethod
    }
    ::= { lcsSetupRadiusServerEapAllowMethodsTable 1 }

-- {SEQUENCE}
LcsSetupRadiusServerEapAllowMethodsEntry ::= SEQUENCE {
    lcsSetupRadiusServerEapAllowMethodsEntryMethod INTEGER,
    lcsSetupRadiusServerEapAllowMethodsEntryAllow INTEGER
}

-- {COLUMN} 310.2.25.10.10.9.1.1
lcsSetupRadiusServerEapAllowMethodsEntryMethod OBJECT-TYPE
    SYNTAX     INTEGER
      {
        eMd5 (4),
        eGtc (6),
        eMschapv2 (26),
        eTls (13),
        eTtls (21),
        ePeap (25)
      }
    MAX-ACCESS read-write
    STATUS     current
    DESCRIPTION
        "-- empty --"
    ::= { lcsSetupRadiusServerEapAllowMethodsEntry 1 }

-- {COLUMN} 310.2.25.10.10.9.1.2
lcsSetupRadiusServerEapAllowMethodsEntryAllow OBJECT-TYPE
    SYNTAX     INTEGER
      {
        eOff (0),
        eOn (1),
        eInternalOnly (2)
      }
    MAX-ACCESS read-write
    STATUS     current
    DESCRIPTION
        "-- empty --"
    ::= { lcsSetupRadiusServerEapAllowMethodsEntry 2 }

-- {OID} 310.2.26
lcsSetupNtp OBJECT IDENTIFIER ::= { lcsSetup 26 }

-- {SCALAR} 310.2.26.2
lcsSetupNtpServerOperating OBJECT-TYPE
    SYNTAX     INTEGER
      {
        eNo (0),
        eYes (1)
      }
    MAX-ACCESS read-only
    STATUS     current
    DESCRIPTION
        "-- empty --"
    ::= { lcsSetupNtp 2 }

-- {SCALAR} 310.2.26.3
lcsSetupNtpBcMode OBJECT-TYPE
    SYNTAX     INTEGER
      {
        eNo (0),
        eYes (1)
      }
    MAX-ACCESS read-only
    STATUS     current
    DESCRIPTION
        "-- empty --"
    ::= { lcsSetupNtp 3 }

-- {SCALAR} 310.2.26.4
lcsSetupNtpBcInterval OBJECT-TYPE
    SYNTAX     INTEGER (0..65535)
    MAX-ACCESS read-only
    STATUS     current
    DESCRIPTION
        "-- empty --"
    ::= { lcsSetupNtp 4 }

-- {SCALAR} 310.2.26.7
lcsSetupNtpRqInterval OBJECT-TYPE
    SYNTAX     INTEGER (0..2147483647)
    MAX-ACCESS read-only
    STATUS     current
    DESCRIPTION
        "-- empty --"
    ::= { lcsSetupNtp 7 }

-- {SCALAR} 310.2.26.12
lcsSetupNtpRqTries OBJECT-TYPE
    SYNTAX     INTEGER (0..2147483647)
    MAX-ACCESS read-only
    STATUS     current
    DESCRIPTION
        "-- empty --"
    ::= { lcsSetupNtp 12 }

-- {TABLE} 310.2.26.11
lcsSetupNtpRqAddressTable OBJECT-TYPE
    SYNTAX     SEQUENCE OF LcsSetupNtpRqAddressEntry
    MAX-ACCESS not-accessible
    STATUS     current
    DESCRIPTION
        "-- empty --"
    ::= { lcsSetupNtp 11 }

-- {ENTRY} 310.2.26.11.1
lcsSetupNtpRqAddressEntry OBJECT-TYPE
    SYNTAX     LcsSetupNtpRqAddressEntry
    MAX-ACCESS not-accessible
    STATUS     current
    DESCRIPTION
        ""
    INDEX {
        lcsSetupNtpRqAddressEntryRqAddress
    }
    ::= { lcsSetupNtpRqAddressTable 1 }

-- {SEQUENCE}
LcsSetupNtpRqAddressEntry ::= SEQUENCE {
    lcsSetupNtpRqAddressEntryRqAddress DisplayString,
    lcsSetupNtpRqAddressEntryLoopbackAddr DisplayString
}

-- {COLUMN} 310.2.26.11.1.1
lcsSetupNtpRqAddressEntryRqAddress OBJECT-TYPE
    SYNTAX     DisplayString (SIZE(0..31))
    MAX-ACCESS read-write
    STATUS     current
    DESCRIPTION
        "-- empty --"
    ::= { lcsSetupNtpRqAddressEntry 1 }

-- {COLUMN} 310.2.26.11.1.2
lcsSetupNtpRqAddressEntryLoopbackAddr OBJECT-TYPE
    SYNTAX     DisplayString (SIZE(0..16))
    MAX-ACCESS read-write
    STATUS     current
    DESCRIPTION
        "-- empty --"
    ::= { lcsSetupNtpRqAddressEntry 2 }

-- {OID} 310.2.27
lcsSetupMail OBJECT IDENTIFIER ::= { lcsSetup 27 }

-- {SCALAR} 310.2.27.1
lcsSetupMailSmtpServer OBJECT-TYPE
    SYNTAX     DisplayString (SIZE(0..31))
    MAX-ACCESS read-only
    STATUS     current
    DESCRIPTION
        "-- empty --"
    ::= { lcsSetupMail 1 }

-- {SCALAR} 310.2.27.2
lcsSetupMailSmtpPort OBJECT-TYPE
    SYNTAX     INTEGER (0..65535)
    MAX-ACCESS read-only
    STATUS     current
    DESCRIPTION
        "-- empty --"
    ::= { lcsSetupMail 2 }

-- {SCALAR} 310.2.27.3
lcsSetupMailPop3Server OBJECT-TYPE
    SYNTAX     DisplayString (SIZE(0..31))
    MAX-ACCESS read-only
    STATUS     current
    DESCRIPTION
        "-- empty --"
    ::= { lcsSetupMail 3 }

-- {SCALAR} 310.2.27.4
lcsSetupMailPop3Port OBJECT-TYPE
    SYNTAX     INTEGER (0..65535)
    MAX-ACCESS read-only
    STATUS     current
    DESCRIPTION
        "-- empty --"
    ::= { lcsSetupMail 4 }

-- {SCALAR} 310.2.27.11
lcsSetupMailLoopbackAddr OBJECT-TYPE
    SYNTAX     DisplayString (SIZE(0..16))
    MAX-ACCESS read-only
    STATUS     current
    DESCRIPTION
        "-- empty --"
    ::= { lcsSetupMail 11 }

-- {SCALAR} 310.2.27.5
lcsSetupMailUserName OBJECT-TYPE
    SYNTAX     DisplayString (SIZE(0..63))
    MAX-ACCESS read-only
    STATUS     current
    DESCRIPTION
        "-- empty --"
    ::= { lcsSetupMail 5 }

-- {SCALAR} 310.2.27.6
lcsSetupMailPassword OBJECT-TYPE
    SYNTAX     DisplayString (SIZE(0..31))
    MAX-ACCESS read-only
    STATUS     current
    DESCRIPTION
        "-- empty --"
    ::= { lcsSetupMail 6 }

-- {SCALAR} 310.2.27.7
lcsSetupMailEMailSender OBJECT-TYPE
    SYNTAX     DisplayString (SIZE(0..63))
    MAX-ACCESS read-only
    STATUS     current
    DESCRIPTION
        "-- empty --"
    ::= { lcsSetupMail 7 }

-- {SCALAR} 310.2.27.8
lcsSetupMailSendAgainMin OBJECT-TYPE
    SYNTAX     INTEGER (0..65535)
    MAX-ACCESS read-only
    STATUS     current
    DESCRIPTION
        "-- empty --"
    ::= { lcsSetupMail 8 }

-- {SCALAR} 310.2.27.9
lcsSetupMailHoldTimeHrs OBJECT-TYPE
    SYNTAX     INTEGER (0..65535)
    MAX-ACCESS read-only
    STATUS     current
    DESCRIPTION
        "-- empty --"
    ::= { lcsSetupMail 9 }

-- {SCALAR} 310.2.27.10
lcsSetupMailBuffers OBJECT-TYPE
    SYNTAX     INTEGER (0..65535)
    MAX-ACCESS read-only
    STATUS     current
    DESCRIPTION
        "-- empty --"
    ::= { lcsSetupMail 10 }

-- {OID} 310.2.31
lcsSetupPppoeServer OBJECT IDENTIFIER ::= { lcsSetup 31 }

-- {SCALAR} 310.2.31.1
lcsSetupPppoeServerOperating OBJECT-TYPE
    SYNTAX     INTEGER
      {
        eNo (0),
        eYes (1)
      }
    MAX-ACCESS read-only
    STATUS     current
    DESCRIPTION
        "-- empty --"
    ::= { lcsSetupPppoeServer 1 }

-- {TABLE} 310.2.31.2
lcsSetupPppoeServerNameListTable OBJECT-TYPE
    SYNTAX     SEQUENCE OF LcsSetupPppoeServerNameListEntry
    MAX-ACCESS not-accessible
    STATUS     current
    DESCRIPTION
        "-- empty --"
    ::= { lcsSetupPppoeServer 2 }

-- {ENTRY} 310.2.31.2.1
lcsSetupPppoeServerNameListEntry OBJECT-TYPE
    SYNTAX     LcsSetupPppoeServerNameListEntry
    MAX-ACCESS not-accessible
    STATUS     current
    DESCRIPTION
        ""
    INDEX {
        lcsSetupPppoeServerNameListEntryPeer
    }
    ::= { lcsSetupPppoeServerNameListTable 1 }

-- {SEQUENCE}
LcsSetupPppoeServerNameListEntry ::= SEQUENCE {
    lcsSetupPppoeServerNameListEntryPeer DisplayString,
    lcsSetupPppoeServerNameListEntryShTime INTEGER,
    lcsSetupPppoeServerNameListEntryMacAddress DisplayString
}

-- {COLUMN} 310.2.31.2.1.1
lcsSetupPppoeServerNameListEntryPeer OBJECT-TYPE
    SYNTAX     DisplayString (SIZE(0..16))
    MAX-ACCESS read-write
    STATUS     current
    DESCRIPTION
        "-- empty --"
    ::= { lcsSetupPppoeServerNameListEntry 1 }

-- {COLUMN} 310.2.31.2.1.2
lcsSetupPppoeServerNameListEntryShTime OBJECT-TYPE
    SYNTAX     INTEGER (0..65535)
    MAX-ACCESS read-write
    STATUS     current
    DESCRIPTION
        "-- empty --"
    ::= { lcsSetupPppoeServerNameListEntry 2 }

-- {COLUMN} 310.2.31.2.1.3
lcsSetupPppoeServerNameListEntryMacAddress OBJECT-TYPE
    SYNTAX     DisplayString (SIZE(0..12))
    MAX-ACCESS read-write
    STATUS     current
    DESCRIPTION
        "-- empty --"
    ::= { lcsSetupPppoeServerNameListEntry 3 }

-- {SCALAR} 310.2.31.3
lcsSetupPppoeServerService OBJECT-TYPE
    SYNTAX     DisplayString (SIZE(0..32))
    MAX-ACCESS read-only
    STATUS     current
    DESCRIPTION
        "-- empty --"
    ::= { lcsSetupPppoeServer 3 }

-- {SCALAR} 310.2.31.4
lcsSetupPppoeServerSessionLimit OBJECT-TYPE
    SYNTAX     INTEGER (0..2147483647)
    MAX-ACCESS read-only
    STATUS     current
    DESCRIPTION
        "-- empty --"
    ::= { lcsSetupPppoeServer 4 }

-- {TABLE} 310.2.31.5
lcsSetupPppoeServerPortsTable OBJECT-TYPE
    SYNTAX     SEQUENCE OF LcsSetupPppoeServerPortsEntry
    MAX-ACCESS not-accessible
    STATUS     current
    DESCRIPTION
        "-- empty --"
    ::= { lcsSetupPppoeServer 5 }

-- {ENTRY} 310.2.31.5.1
lcsSetupPppoeServerPortsEntry OBJECT-TYPE
    SYNTAX     LcsSetupPppoeServerPortsEntry
    MAX-ACCESS not-accessible
    STATUS     current
    DESCRIPTION
        ""
    INDEX {
        lcsSetupPppoeServerPortsEntryPort
    }
    ::= { lcsSetupPppoeServerPortsTable 1 }

-- {SEQUENCE}
LcsSetupPppoeServerPortsEntry ::= SEQUENCE {
    lcsSetupPppoeServerPortsEntryPort DisplayString,
    lcsSetupPppoeServerPortsEntryEnablePppoe INTEGER
}

-- {COLUMN} 310.2.31.5.1.2
lcsSetupPppoeServerPortsEntryPort OBJECT-TYPE
    SYNTAX     DisplayString (SIZE(0..13))
    MAX-ACCESS read-only
    STATUS     current
    DESCRIPTION
        "-- empty --"
    ::= { lcsSetupPppoeServerPortsEntry 2 }

-- {COLUMN} 310.2.31.5.1.3
lcsSetupPppoeServerPortsEntryEnablePppoe OBJECT-TYPE
    SYNTAX     INTEGER
      {
        eNo (0),
        eYes (1)
      }
    MAX-ACCESS read-write
    STATUS     current
    DESCRIPTION
        "-- empty --"
    ::= { lcsSetupPppoeServerPortsEntry 3 }

-- {OID} 310.2.32
lcsSetupVlan OBJECT IDENTIFIER ::= { lcsSetup 32 }

-- {SCALAR} 310.2.32.4
lcsSetupVlanOperating OBJECT-TYPE
    SYNTAX     INTEGER
      {
        eNo (0),
        eYes (1)
      }
    MAX-ACCESS read-write
    STATUS     current
    DESCRIPTION
        "-- empty --"
    ::= { lcsSetupVlan 4 }

-- {TABLE} 310.2.32.1
lcsSetupVlanNetworksTable OBJECT-TYPE
    SYNTAX     SEQUENCE OF LcsSetupVlanNetworksEntry
    MAX-ACCESS not-accessible
    STATUS     current
    DESCRIPTION
        "-- empty --"
    ::= { lcsSetupVlan 1 }

-- {ENTRY} 310.2.32.1.1
lcsSetupVlanNetworksEntry OBJECT-TYPE
    SYNTAX     LcsSetupVlanNetworksEntry
    MAX-ACCESS not-accessible
    STATUS     current
    DESCRIPTION
        ""
    INDEX {
        lcsSetupVlanNetworksEntryName
    }
    ::= { lcsSetupVlanNetworksTable 1 }

-- {SEQUENCE}
LcsSetupVlanNetworksEntry ::= SEQUENCE {
    lcsSetupVlanNetworksEntryName DisplayString,
    lcsSetupVlanNetworksEntryVlanId INTEGER,
    lcsSetupVlanNetworksEntryPorts DisplayString
}

-- {COLUMN} 310.2.32.1.1.1
lcsSetupVlanNetworksEntryName OBJECT-TYPE
    SYNTAX     DisplayString (SIZE(0..16))
    MAX-ACCESS read-write
    STATUS     current
    DESCRIPTION
        "-- empty --"
    ::= { lcsSetupVlanNetworksEntry 1 }

-- {COLUMN} 310.2.32.1.1.2
lcsSetupVlanNetworksEntryVlanId OBJECT-TYPE
    SYNTAX     INTEGER (0..65535)
    MAX-ACCESS read-write
    STATUS     current
    DESCRIPTION
        "-- empty --"
    ::= { lcsSetupVlanNetworksEntry 2 }

-- {COLUMN} 310.2.32.1.1.4
lcsSetupVlanNetworksEntryPorts OBJECT-TYPE
    SYNTAX     DisplayString (SIZE(0..251))
    MAX-ACCESS read-write
    STATUS     current
    DESCRIPTION
        "-- empty --"
    ::= { lcsSetupVlanNetworksEntry 4 }

-- {SCALAR} 310.2.32.5
lcsSetupVlanTagValue OBJECT-TYPE
    SYNTAX     DisplayString (SIZE(0..4))
    MAX-ACCESS read-write
    STATUS     current
    DESCRIPTION
        "-- empty --"
    ::= { lcsSetupVlan 5 }

-- {TABLE} 310.2.32.2
lcsSetupVlanPortTableTable OBJECT-TYPE
    SYNTAX     SEQUENCE OF LcsSetupVlanPortTableEntry
    MAX-ACCESS not-accessible
    STATUS     current
    DESCRIPTION
        "-- empty --"
    ::= { lcsSetupVlan 2 }

-- {ENTRY} 310.2.32.2.1
lcsSetupVlanPortTableEntry OBJECT-TYPE
    SYNTAX     LcsSetupVlanPortTableEntry
    MAX-ACCESS not-accessible
    STATUS     current
    DESCRIPTION
        ""
    INDEX {
        lcsSetupVlanPortTableEntryPort
    }
    ::= { lcsSetupVlanPortTableTable 1 }

-- {SEQUENCE}
LcsSetupVlanPortTableEntry ::= SEQUENCE {
    lcsSetupVlanPortTableEntryPort DisplayString,
    lcsSetupVlanPortTableEntryTaggingMode INTEGER,
    lcsSetupVlanPortTableEntryAllowAllVlans INTEGER,
    lcsSetupVlanPortTableEntryPortVlanId INTEGER
}

-- {COLUMN} 310.2.32.2.1.1
lcsSetupVlanPortTableEntryPort OBJECT-TYPE
    SYNTAX     DisplayString (SIZE(0..13))
    MAX-ACCESS read-only
    STATUS     current
    DESCRIPTION
        "-- empty --"
    ::= { lcsSetupVlanPortTableEntry 1 }

-- {COLUMN} 310.2.32.2.1.6
lcsSetupVlanPortTableEntryTaggingMode OBJECT-TYPE
    SYNTAX     INTEGER
      {
        eIngressMixed (0),
        eNever (1),
        eMixed (2),
        eAlways (3)
      }
    MAX-ACCESS read-write
    STATUS     current
    DESCRIPTION
        "-- empty --"
    ::= { lcsSetupVlanPortTableEntry 6 }

-- {COLUMN} 310.2.32.2.1.4
lcsSetupVlanPortTableEntryAllowAllVlans OBJECT-TYPE
    SYNTAX     INTEGER
      {
        eNo (0),
        eYes (1)
      }
    MAX-ACCESS read-write
    STATUS     current
    DESCRIPTION
        "-- empty --"
    ::= { lcsSetupVlanPortTableEntry 4 }

-- {COLUMN} 310.2.32.2.1.5
lcsSetupVlanPortTableEntryPortVlanId OBJECT-TYPE
    SYNTAX     INTEGER (0..65535)
    MAX-ACCESS read-write
    STATUS     current
    DESCRIPTION
        "-- empty --"
    ::= { lcsSetupVlanPortTableEntry 5 }

-- {OID} 310.2.63
lcsSetupPacketCapture OBJECT IDENTIFIER ::= { lcsSetup 63 }

-- {SCALAR} 310.2.63.1
lcsSetupPacketCaptureLcoscapOperating OBJECT-TYPE
    SYNTAX     INTEGER
      {
        eNo (0),
        eYes (1)
      }
    MAX-ACCESS read-write
    STATUS     current
    DESCRIPTION
        "-- empty --"
    ::= { lcsSetupPacketCapture 1 }

-- {SCALAR} 310.2.63.2
lcsSetupPacketCaptureLcoscapPort OBJECT-TYPE
    SYNTAX     INTEGER (0..65535)
    MAX-ACCESS read-write
    STATUS     current
    DESCRIPTION
        "-- empty --"
    ::= { lcsSetupPacketCapture 2 }

-- {SCALAR} 310.2.63.11
lcsSetupPacketCaptureRpcapOperating OBJECT-TYPE
    SYNTAX     INTEGER
      {
        eNo (0),
        eYes (1)
      }
    MAX-ACCESS read-write
    STATUS     current
    DESCRIPTION
        "-- empty --"
    ::= { lcsSetupPacketCapture 11 }

-- {SCALAR} 310.2.63.12
lcsSetupPacketCaptureRpcapPort OBJECT-TYPE
    SYNTAX     INTEGER (0..65535)
    MAX-ACCESS read-write
    STATUS     current
    DESCRIPTION
        "-- empty --"
    ::= { lcsSetupPacketCapture 12 }

-- {OID} 310.2.52
lcsSetupComPorts OBJECT IDENTIFIER ::= { lcsSetup 52 }

-- {TABLE} 310.2.52.1
lcsSetupComPortsDevTable OBJECT-TYPE
    SYNTAX     SEQUENCE OF LcsSetupComPortsDevEntry
    MAX-ACCESS not-accessible
    STATUS     current
    DESCRIPTION
        ""
    ::= { lcsSetupComPorts 1 }

-- {ENTRY} 310.2.52.1.1
lcsSetupComPortsDevEntry OBJECT-TYPE
    SYNTAX     LcsSetupComPortsDevEntry
    MAX-ACCESS not-accessible
    STATUS     current
    DESCRIPTION
        ""
    INDEX {
        lcsSetupComPortsDevEntryDeviceType
    }
    ::= { lcsSetupComPortsDevTable 1 }

-- {SEQUENCE}
LcsSetupComPortsDevEntry ::= SEQUENCE {
    lcsSetupComPortsDevEntryDeviceType INTEGER,
    lcsSetupComPortsDevEntryServ INTEGER
}

-- {COLUMN} 310.2.52.1.1.1
lcsSetupComPortsDevEntryDeviceType OBJECT-TYPE
    SYNTAX     INTEGER
      {
        eOutband (1)
      }
    MAX-ACCESS read-write
    STATUS     current
    DESCRIPTION
        "-- empty --"
    ::= { lcsSetupComPortsDevEntry 1 }

-- {COLUMN} 310.2.52.1.1.4
lcsSetupComPortsDevEntryServ OBJECT-TYPE
    SYNTAX     INTEGER
      {
        eWan (1),
        eCOMPortServ (2)
      }
    MAX-ACCESS read-write
    STATUS     current
    DESCRIPTION
        ""
    ::= { lcsSetupComPortsDevEntry 4 }

-- {OID} 310.2.52.3
lcsSetupComPortsWan OBJECT IDENTIFIER ::= { lcsSetupComPorts 3 }

-- {TABLE} 310.2.52.3.1
lcsSetupComPortsWanDevTable OBJECT-TYPE
    SYNTAX     SEQUENCE OF LcsSetupComPortsWanDevEntry
    MAX-ACCESS not-accessible
    STATUS     current
    DESCRIPTION
        ""
    ::= { lcsSetupComPortsWan 1 }

-- {ENTRY} 310.2.52.3.1.1
lcsSetupComPortsWanDevEntry OBJECT-TYPE
    SYNTAX     LcsSetupComPortsWanDevEntry
    MAX-ACCESS not-accessible
    STATUS     current
    DESCRIPTION
        ""
    INDEX {
        lcsSetupComPortsWanDevEntryDeviceType
    }
    ::= { lcsSetupComPortsWanDevTable 1 }

-- {SEQUENCE}
LcsSetupComPortsWanDevEntry ::= SEQUENCE {
    lcsSetupComPortsWanDevEntryDeviceType INTEGER,
    lcsSetupComPortsWanDevEntryOperating INTEGER
}

-- {COLUMN} 310.2.52.3.1.1.1
lcsSetupComPortsWanDevEntryDeviceType OBJECT-TYPE
    SYNTAX     INTEGER
      {
        eOutbandModem (2)
      }
    MAX-ACCESS read-write
    STATUS     current
    DESCRIPTION
        "-- empty --"
    ::= { lcsSetupComPortsWanDevEntry 1 }

-- {COLUMN} 310.2.52.3.1.1.3
lcsSetupComPortsWanDevEntryOperating OBJECT-TYPE
    SYNTAX     INTEGER
      {
        eNo (0),
        eYes (1)
      }
    MAX-ACCESS read-write
    STATUS     current
    DESCRIPTION
        "-- empty --"
    ::= { lcsSetupComPortsWanDevEntry 3 }

-- {OID} 310.2.52.2
lcsSetupComPortsCOMPortServ OBJECT IDENTIFIER ::= { lcsSetupComPorts 2 }

-- {TABLE} 310.2.52.2.1
lcsSetupComPortsCOMPortServOperTable OBJECT-TYPE
    SYNTAX     SEQUENCE OF LcsSetupComPortsCOMPortServOperEntry
    MAX-ACCESS not-accessible
    STATUS     current
    DESCRIPTION
        ""
    ::= { lcsSetupComPortsCOMPortServ 1 }

-- {ENTRY} 310.2.52.2.1.1
lcsSetupComPortsCOMPortServOperEntry OBJECT-TYPE
    SYNTAX     LcsSetupComPortsCOMPortServOperEntry
    MAX-ACCESS not-accessible
    STATUS     current
    DESCRIPTION
        ""
    INDEX {
        lcsSetupComPortsCOMPortServOperEntryDeviceType,
        lcsSetupComPortsCOMPortServOperEntryPortNumber
    }
    ::= { lcsSetupComPortsCOMPortServOperTable 1 }

-- {SEQUENCE}
LcsSetupComPortsCOMPortServOperEntry ::= SEQUENCE {
    lcsSetupComPortsCOMPortServOperEntryDeviceType INTEGER,
    lcsSetupComPortsCOMPortServOperEntryPortNumber INTEGER,
    lcsSetupComPortsCOMPortServOperEntryOperating INTEGER
}

-- {COLUMN} 310.2.52.2.1.1.1
lcsSetupComPortsCOMPortServOperEntryDeviceType OBJECT-TYPE
    SYNTAX     INTEGER
      {
        eOutband (1)
      }
    MAX-ACCESS read-write
    STATUS     current
    DESCRIPTION
        "-- empty --"
    ::= { lcsSetupComPortsCOMPortServOperEntry 1 }

-- {COLUMN} 310.2.52.2.1.1.2
lcsSetupComPortsCOMPortServOperEntryPortNumber OBJECT-TYPE
    SYNTAX     INTEGER (0..255)
    MAX-ACCESS read-write
    STATUS     current
    DESCRIPTION
        "-- empty --"
    ::= { lcsSetupComPortsCOMPortServOperEntry 2 }

-- {COLUMN} 310.2.52.2.1.1.4
lcsSetupComPortsCOMPortServOperEntryOperating OBJECT-TYPE
    SYNTAX     INTEGER
      {
        eNo (0),
        eYes (1)
      }
    MAX-ACCESS read-write
    STATUS     current
    DESCRIPTION
        "-- empty --"
    ::= { lcsSetupComPortsCOMPortServOperEntry 4 }

-- {TABLE} 310.2.52.2.2
lcsSetupComPortsCOMPortServCOMPortSetTable OBJECT-TYPE
    SYNTAX     SEQUENCE OF LcsSetupComPortsCOMPortServCOMPortSetEntry
    MAX-ACCESS not-accessible
    STATUS     current
    DESCRIPTION
        ""
    ::= { lcsSetupComPortsCOMPortServ 2 }

-- {ENTRY} 310.2.52.2.2.1
lcsSetupComPortsCOMPortServCOMPortSetEntry OBJECT-TYPE
    SYNTAX     LcsSetupComPortsCOMPortServCOMPortSetEntry
    MAX-ACCESS not-accessible
    STATUS     current
    DESCRIPTION
        ""
    INDEX {
        lcsSetupComPortsCOMPortServCOMPortSetEntryDeviceType,
        lcsSetupComPortsCOMPortServCOMPortSetEntryPortNumber
    }
    ::= { lcsSetupComPortsCOMPortServCOMPortSetTable 1 }

-- {SEQUENCE}
LcsSetupComPortsCOMPortServCOMPortSetEntry ::= SEQUENCE {
    lcsSetupComPortsCOMPortServCOMPortSetEntryDeviceType INTEGER,
    lcsSetupComPortsCOMPortServCOMPortSetEntryPortNumber INTEGER,
    lcsSetupComPortsCOMPortServCOMPortSetEntryBitRate INTEGER,
    lcsSetupComPortsCOMPortServCOMPortSetEntryDataBits INTEGER,
    lcsSetupComPortsCOMPortServCOMPortSetEntryParity INTEGER,
    lcsSetupComPortsCOMPortServCOMPortSetEntryStopBits INTEGER,
    lcsSetupComPortsCOMPortServCOMPortSetEntryHandshake INTEGER,
    lcsSetupComPortsCOMPortServCOMPortSetEntryReadyCondition INTEGER,
    lcsSetupComPortsCOMPortServCOMPortSetEntryReadyDataTimeout INTEGER
}

-- {COLUMN} 310.2.52.2.2.1.1
lcsSetupComPortsCOMPortServCOMPortSetEntryDeviceType OBJECT-TYPE
    SYNTAX     INTEGER
      {
        eOutband (1)
      }
    MAX-ACCESS read-write
    STATUS     current
    DESCRIPTION
        "-- empty --"
    ::= { lcsSetupComPortsCOMPortServCOMPortSetEntry 1 }

-- {COLUMN} 310.2.52.2.2.1.2
lcsSetupComPortsCOMPortServCOMPortSetEntryPortNumber OBJECT-TYPE
    SYNTAX     INTEGER (0..255)
    MAX-ACCESS read-write
    STATUS     current
    DESCRIPTION
        "-- empty --"
    ::= { lcsSetupComPortsCOMPortServCOMPortSetEntry 2 }

-- {COLUMN} 310.2.52.2.2.1.4
lcsSetupComPortsCOMPortServCOMPortSetEntryBitRate OBJECT-TYPE
    SYNTAX     INTEGER
      {
        e110 (110),
        e300 (300),
        e600 (600),
        e1200 (1200),
        e2400 (2400),
        e4800 (4800),
        e9600 (9600),
        e19200 (19200),
        e38400 (38400),
        e57600 (57600),
        e115200 (115200),
        e125000 (125000),
        e230400 (230400)
      }
    MAX-ACCESS read-write
    STATUS     current
    DESCRIPTION
        "-- empty --"
    ::= { lcsSetupComPortsCOMPortServCOMPortSetEntry 4 }

-- {COLUMN} 310.2.52.2.2.1.5
lcsSetupComPortsCOMPortServCOMPortSetEntryDataBits OBJECT-TYPE
    SYNTAX     INTEGER
      {
        e7 (7),
        e8 (8)
      }
    MAX-ACCESS read-write
    STATUS     current
    DESCRIPTION
        "-- empty --"
    ::= { lcsSetupComPortsCOMPortServCOMPortSetEntry 5 }

-- {COLUMN} 310.2.52.2.2.1.6
lcsSetupComPortsCOMPortServCOMPortSetEntryParity OBJECT-TYPE
    SYNTAX     INTEGER
      {
        eNone (1),
        eOdd (2),
        eEven (3)
      }
    MAX-ACCESS read-write
    STATUS     current
    DESCRIPTION
        "-- empty --"
    ::= { lcsSetupComPortsCOMPortServCOMPortSetEntry 6 }

-- {COLUMN} 310.2.52.2.2.1.7
lcsSetupComPortsCOMPortServCOMPortSetEntryStopBits OBJECT-TYPE
    SYNTAX     INTEGER
      {
        e1 (1),
        e2 (2)
      }
    MAX-ACCESS read-write
    STATUS     current
    DESCRIPTION
        "-- empty --"
    ::= { lcsSetupComPortsCOMPortServCOMPortSetEntry 7 }

-- {COLUMN} 310.2.52.2.2.1.8
lcsSetupComPortsCOMPortServCOMPortSetEntryHandshake OBJECT-TYPE
    SYNTAX     INTEGER
      {
        eNone (0),
        eRtsCts (1)
      }
    MAX-ACCESS read-write
    STATUS     current
    DESCRIPTION
        "-- empty --"
    ::= { lcsSetupComPortsCOMPortServCOMPortSetEntry 8 }

-- {COLUMN} 310.2.52.2.2.1.9
lcsSetupComPortsCOMPortServCOMPortSetEntryReadyCondition OBJECT-TYPE
    SYNTAX     INTEGER
      {
        eDtr (0),
        eData (1)
      }
    MAX-ACCESS read-write
    STATUS     current
    DESCRIPTION
        "-- empty --"
    ::= { lcsSetupComPortsCOMPortServCOMPortSetEntry 9 }

-- {COLUMN} 310.2.52.2.2.1.10
lcsSetupComPortsCOMPortServCOMPortSetEntryReadyDataTimeout OBJECT-TYPE
    SYNTAX     INTEGER (0..2147483647)
    MAX-ACCESS read-write
    STATUS     current
    DESCRIPTION
        "-- empty --"
    ::= { lcsSetupComPortsCOMPortServCOMPortSetEntry 10 }

-- {TABLE} 310.2.52.2.3
lcsSetupComPortsCOMPortServNetwSetTable OBJECT-TYPE
    SYNTAX     SEQUENCE OF LcsSetupComPortsCOMPortServNetwSetEntry
    MAX-ACCESS not-accessible
    STATUS     current
    DESCRIPTION
        ""
    ::= { lcsSetupComPortsCOMPortServ 3 }

-- {ENTRY} 310.2.52.2.3.1
lcsSetupComPortsCOMPortServNetwSetEntry OBJECT-TYPE
    SYNTAX     LcsSetupComPortsCOMPortServNetwSetEntry
    MAX-ACCESS not-accessible
    STATUS     current
    DESCRIPTION
        ""
    INDEX {
        lcsSetupComPortsCOMPortServNetwSetEntryDeviceType,
        lcsSetupComPortsCOMPortServNetwSetEntryPortNumber
    }
    ::= { lcsSetupComPortsCOMPortServNetwSetTable 1 }

-- {SEQUENCE}
LcsSetupComPortsCOMPortServNetwSetEntry ::= SEQUENCE {
    lcsSetupComPortsCOMPortServNetwSetEntryDeviceType INTEGER,
    lcsSetupComPortsCOMPortServNetwSetEntryPortNumber INTEGER,
    lcsSetupComPortsCOMPortServNetwSetEntryTcpMode INTEGER,
    lcsSetupComPortsCOMPortServNetwSetEntryListenPort INTEGER,
    lcsSetupComPortsCOMPortServNetwSetEntryConnectHostname DisplayString,
    lcsSetupComPortsCOMPortServNetwSetEntryConnectPort INTEGER,
    lcsSetupComPortsCOMPortServNetwSetEntryLoopbackAddr DisplayString,
    lcsSetupComPortsCOMPortServNetwSetEntryRfc2217Extensions INTEGER,
    lcsSetupComPortsCOMPortServNetwSetEntryBinaryMode INTEGER,
    lcsSetupComPortsCOMPortServNetwSetEntryNewlineConversion INTEGER,
    lcsSetupComPortsCOMPortServNetwSetEntryTcpKeepalive INTEGER,
    lcsSetupComPortsCOMPortServNetwSetEntryTcpKeepaliveInterval INTEGER,
    lcsSetupComPortsCOMPortServNetwSetEntryTcpRetransmitTimeout INTEGER,
    lcsSetupComPortsCOMPortServNetwSetEntryTcpRetryCount INTEGER
}

-- {COLUMN} 310.2.52.2.3.1.1
lcsSetupComPortsCOMPortServNetwSetEntryDeviceType OBJECT-TYPE
    SYNTAX     INTEGER
      {
        eOutband (1)
      }
    MAX-ACCESS read-write
    STATUS     current
    DESCRIPTION
        "-- empty --"
    ::= { lcsSetupComPortsCOMPortServNetwSetEntry 1 }

-- {COLUMN} 310.2.52.2.3.1.2
lcsSetupComPortsCOMPortServNetwSetEntryPortNumber OBJECT-TYPE
    SYNTAX     INTEGER (0..255)
    MAX-ACCESS read-write
    STATUS     current
    DESCRIPTION
        "-- empty --"
    ::= { lcsSetupComPortsCOMPortServNetwSetEntry 2 }

-- {COLUMN} 310.2.52.2.3.1.4
lcsSetupComPortsCOMPortServNetwSetEntryTcpMode OBJECT-TYPE
    SYNTAX     INTEGER
      {
        eServer (0),
        eClient (1)
      }
    MAX-ACCESS read-write
    STATUS     current
    DESCRIPTION
        "-- empty --"
    ::= { lcsSetupComPortsCOMPortServNetwSetEntry 4 }

-- {COLUMN} 310.2.52.2.3.1.5
lcsSetupComPortsCOMPortServNetwSetEntryListenPort OBJECT-TYPE
    SYNTAX     INTEGER (0..65535)
    MAX-ACCESS read-write
    STATUS     current
    DESCRIPTION
        "-- empty --"
    ::= { lcsSetupComPortsCOMPortServNetwSetEntry 5 }

-- {COLUMN} 310.2.52.2.3.1.6
lcsSetupComPortsCOMPortServNetwSetEntryConnectHostname OBJECT-TYPE
    SYNTAX     DisplayString (SIZE(0..48))
    MAX-ACCESS read-write
    STATUS     current
    DESCRIPTION
        "-- empty --"
    ::= { lcsSetupComPortsCOMPortServNetwSetEntry 6 }

-- {COLUMN} 310.2.52.2.3.1.7
lcsSetupComPortsCOMPortServNetwSetEntryConnectPort OBJECT-TYPE
    SYNTAX     INTEGER (0..65535)
    MAX-ACCESS read-write
    STATUS     current
    DESCRIPTION
        "-- empty --"
    ::= { lcsSetupComPortsCOMPortServNetwSetEntry 7 }

-- {COLUMN} 310.2.52.2.3.1.8
lcsSetupComPortsCOMPortServNetwSetEntryLoopbackAddr OBJECT-TYPE
    SYNTAX     DisplayString (SIZE(0..16))
    MAX-ACCESS read-write
    STATUS     current
    DESCRIPTION
        "-- empty --"
    ::= { lcsSetupComPortsCOMPortServNetwSetEntry 8 }

-- {COLUMN} 310.2.52.2.3.1.9
lcsSetupComPortsCOMPortServNetwSetEntryRfc2217Extensions OBJECT-TYPE
    SYNTAX     INTEGER
      {
        eNo (0),
        eYes (1)
      }
    MAX-ACCESS read-write
    STATUS     current
    DESCRIPTION
        "-- empty --"
    ::= { lcsSetupComPortsCOMPortServNetwSetEntry 9 }

-- {COLUMN} 310.2.52.2.3.1.16
lcsSetupComPortsCOMPortServNetwSetEntryBinaryMode OBJECT-TYPE
    SYNTAX     INTEGER
      {
        eAuto (0),
        eYes (1),
        eNo (2)
      }
    MAX-ACCESS read-write
    STATUS     current
    DESCRIPTION
        "-- empty --"
    ::= { lcsSetupComPortsCOMPortServNetwSetEntry 16 }

-- {COLUMN} 310.2.52.2.3.1.10
lcsSetupComPortsCOMPortServNetwSetEntryNewlineConversion OBJECT-TYPE
    SYNTAX     INTEGER
      {
        eCrlf (0),
        eCr (1),
        eLf (2)
      }
    MAX-ACCESS read-write
    STATUS     current
    DESCRIPTION
        "-- empty --"
    ::= { lcsSetupComPortsCOMPortServNetwSetEntry 10 }

-- {COLUMN} 310.2.52.2.3.1.14
lcsSetupComPortsCOMPortServNetwSetEntryTcpKeepalive OBJECT-TYPE
    SYNTAX     INTEGER
      {
        eInactive (0),
        eActive (1),
        eProactive (2)
      }
    MAX-ACCESS read-write
    STATUS     current
    DESCRIPTION
        "-- empty --"
    ::= { lcsSetupComPortsCOMPortServNetwSetEntry 14 }

-- {COLUMN} 310.2.52.2.3.1.15
lcsSetupComPortsCOMPortServNetwSetEntryTcpKeepaliveInterval OBJECT-TYPE
    SYNTAX     INTEGER (0..2147483647)
    MAX-ACCESS read-write
    STATUS     current
    DESCRIPTION
        "-- empty --"
    ::= { lcsSetupComPortsCOMPortServNetwSetEntry 15 }

-- {COLUMN} 310.2.52.2.3.1.12
lcsSetupComPortsCOMPortServNetwSetEntryTcpRetransmitTimeout OBJECT-TYPE
    SYNTAX     INTEGER (0..255)
    MAX-ACCESS read-write
    STATUS     current
    DESCRIPTION
        "-- empty --"
    ::= { lcsSetupComPortsCOMPortServNetwSetEntry 12 }

-- {COLUMN} 310.2.52.2.3.1.13
lcsSetupComPortsCOMPortServNetwSetEntryTcpRetryCount OBJECT-TYPE
    SYNTAX     INTEGER (0..255)
    MAX-ACCESS read-write
    STATUS     current
    DESCRIPTION
        "-- empty --"
    ::= { lcsSetupComPortsCOMPortServNetwSetEntry 13 }

-- {OID} 310.2.60
lcsSetupAutold OBJECT IDENTIFIER ::= { lcsSetup 60 }

-- {OID} 310.2.60.1
lcsSetupAutoldNetwork OBJECT IDENTIFIER ::= { lcsSetupAutold 1 }

-- {OID} 310.2.60.1.1
lcsSetupAutoldNetworkFirmware OBJECT IDENTIFIER ::= { lcsSetupAutoldNetwork 1 }

-- {SCALAR} 310.2.60.1.1.1
lcsSetupAutoldNetworkFirmwareCondition OBJECT-TYPE
    SYNTAX     INTEGER
      {
        eUnconditionally (0),
        eIfDifferent (1),
        eIfNewer (2)
      }
    MAX-ACCESS read-only
    STATUS     current
    DESCRIPTION
        "-- empty --"
    ::= { lcsSetupAutoldNetworkFirmware 1 }

-- {SCALAR} 310.2.60.1.1.2
lcsSetupAutoldNetworkFirmwareUrl OBJECT-TYPE
    SYNTAX     DisplayString (SIZE(0..127))
    MAX-ACCESS read-only
    STATUS     current
    DESCRIPTION
        "-- empty --"
    ::= { lcsSetupAutoldNetworkFirmware 2 }

-- {SCALAR} 310.2.60.1.1.3
lcsSetupAutoldNetworkFirmwareMinimumVersion OBJECT-TYPE
    SYNTAX     DisplayString (SIZE(0..14))
    MAX-ACCESS read-only
    STATUS     current
    DESCRIPTION
        "-- empty --"
    ::= { lcsSetupAutoldNetworkFirmware 3 }

-- {OID} 310.2.60.1.2
lcsSetupAutoldNetworkConfig OBJECT IDENTIFIER ::= { lcsSetupAutoldNetwork 2 }

-- {SCALAR} 310.2.60.1.2.1
lcsSetupAutoldNetworkConfigCondition OBJECT-TYPE
    SYNTAX     INTEGER
      {
        eUnconditionally (0),
        eIfDifferent (1)
      }
    MAX-ACCESS read-only
    STATUS     current
    DESCRIPTION
        "-- empty --"
    ::= { lcsSetupAutoldNetworkConfig 1 }

-- {SCALAR} 310.2.60.1.2.2
lcsSetupAutoldNetworkConfigUrl OBJECT-TYPE
    SYNTAX     DisplayString (SIZE(0..127))
    MAX-ACCESS read-only
    STATUS     current
    DESCRIPTION
        "-- empty --"
    ::= { lcsSetupAutoldNetworkConfig 2 }

-- {OID} 310.2.60.1.3
lcsSetupAutoldNetworkScript OBJECT IDENTIFIER ::= { lcsSetupAutoldNetwork 3 }

-- {SCALAR} 310.2.60.1.3.1
lcsSetupAutoldNetworkScriptCondition OBJECT-TYPE
    SYNTAX     INTEGER
      {
        eUnconditionally (0),
        eIfDifferent (1)
      }
    MAX-ACCESS read-only
    STATUS     current
    DESCRIPTION
        "-- empty --"
    ::= { lcsSetupAutoldNetworkScript 1 }

-- {SCALAR} 310.2.60.1.3.2
lcsSetupAutoldNetworkScriptUrl OBJECT-TYPE
    SYNTAX     DisplayString (SIZE(0..127))
    MAX-ACCESS read-only
    STATUS     current
    DESCRIPTION
        "-- empty --"
    ::= { lcsSetupAutoldNetworkScript 2 }

-- {OID} 310.2.60.1.4
lcsSetupAutoldNetworkTftpClient OBJECT IDENTIFIER ::= { lcsSetupAutoldNetwork 4 }

-- {SCALAR} 310.2.60.1.4.1
lcsSetupAutoldNetworkTftpClientBytesPerHashmark OBJECT-TYPE
    SYNTAX     INTEGER (0..2147483647)
    MAX-ACCESS read-only
    STATUS     current
    DESCRIPTION
        "-- empty --"
    ::= { lcsSetupAutoldNetworkTftpClient 1 }

-- {OID} 310.2.60.3
lcsSetupAutoldLicense OBJECT IDENTIFIER ::= { lcsSetupAutold 3 }

-- {SCALAR} 310.2.60.3.1
lcsSetupAutoldLicenseUrl OBJECT-TYPE
    SYNTAX     DisplayString (SIZE(0..127))
    MAX-ACCESS read-only
    STATUS     current
    DESCRIPTION
        "-- empty --"
    ::= { lcsSetupAutoldLicense 1 }

-- {SCALAR} 310.2.60.3.2
lcsSetupAutoldLicenseLoopbackAddress OBJECT-TYPE
    SYNTAX     DisplayString (SIZE(0..16))
    MAX-ACCESS read-only
    STATUS     current
    DESCRIPTION
        "-- empty --"
    ::= { lcsSetupAutoldLicense 2 }

-- {SCALAR} 310.2.60.3.10
lcsSetupAutoldLicenseCompany OBJECT-TYPE
    SYNTAX     DisplayString (SIZE(0..127))
    MAX-ACCESS read-only
    STATUS     current
    DESCRIPTION
        "-- empty --"
    ::= { lcsSetupAutoldLicense 10 }

-- {SCALAR} 310.2.60.3.11
lcsSetupAutoldLicenseLastName OBJECT-TYPE
    SYNTAX     DisplayString (SIZE(0..31))
    MAX-ACCESS read-only
    STATUS     current
    DESCRIPTION
        "-- empty --"
    ::= { lcsSetupAutoldLicense 11 }

-- {SCALAR} 310.2.60.3.12
lcsSetupAutoldLicenseFirstName OBJECT-TYPE
    SYNTAX     DisplayString (SIZE(0..31))
    MAX-ACCESS read-only
    STATUS     current
    DESCRIPTION
        "-- empty --"
    ::= { lcsSetupAutoldLicense 12 }

-- {SCALAR} 310.2.60.3.13
lcsSetupAutoldLicenseStreetAndNumber OBJECT-TYPE
    SYNTAX     DisplayString (SIZE(0..127))
    MAX-ACCESS read-only
    STATUS     current
    DESCRIPTION
        "-- empty --"
    ::= { lcsSetupAutoldLicense 13 }

-- {SCALAR} 310.2.60.3.14
lcsSetupAutoldLicensePostCode OBJECT-TYPE
    SYNTAX     DisplayString (SIZE(0..10))
    MAX-ACCESS read-only
    STATUS     current
    DESCRIPTION
        "-- empty --"
    ::= { lcsSetupAutoldLicense 14 }

-- {SCALAR} 310.2.60.3.15
lcsSetupAutoldLicenseCity OBJECT-TYPE
    SYNTAX     DisplayString (SIZE(0..63))
    MAX-ACCESS read-only
    STATUS     current
    DESCRIPTION
        "-- empty --"
    ::= { lcsSetupAutoldLicense 15 }

-- {SCALAR} 310.2.60.3.16
lcsSetupAutoldLicenseCountry OBJECT-TYPE
    SYNTAX     DisplayString (SIZE(0..63))
    MAX-ACCESS read-only
    STATUS     current
    DESCRIPTION
        "-- empty --"
    ::= { lcsSetupAutoldLicense 16 }

-- {SCALAR} 310.2.60.3.17
lcsSetupAutoldLicenseEmailAddress OBJECT-TYPE
    SYNTAX     DisplayString (SIZE(0..63))
    MAX-ACCESS read-only
    STATUS     current
    DESCRIPTION
        "-- empty --"
    ::= { lcsSetupAutoldLicense 17 }

-- {OID} 310.2.53
lcsSetupTemperatureMonitor OBJECT IDENTIFIER ::= { lcsSetup 53 }

-- {SCALAR} 310.2.53.1
lcsSetupTemperatureMonitorUpperLimitDegrees OBJECT-TYPE
    SYNTAX     INTEGER (-128..127)
    MAX-ACCESS read-write
    STATUS     current
    DESCRIPTION
        "-- empty --"
    ::= { lcsSetupTemperatureMonitor 1 }

-- {SCALAR} 310.2.53.2
lcsSetupTemperatureMonitorLowerLimitDegrees OBJECT-TYPE
    SYNTAX     INTEGER (-128..127)
    MAX-ACCESS read-write
    STATUS     current
    DESCRIPTION
        "-- empty --"
    ::= { lcsSetupTemperatureMonitor 2 }

-- {OID} 310.2.54
lcsSetupTacacsPlus OBJECT IDENTIFIER ::= { lcsSetup 54 }

-- {SCALAR} 310.2.54.1
lcsSetupTacacsPlusAuthentication OBJECT-TYPE
    SYNTAX     INTEGER
      {
        eDeactivated (0),
        eActivated (1)
      }
    MAX-ACCESS read-only
    STATUS     current
    DESCRIPTION
        "-- empty --"
    ::= { lcsSetupTacacsPlus 1 }

-- {SCALAR} 310.2.54.2
lcsSetupTacacsPlusAuthorisation OBJECT-TYPE
    SYNTAX     INTEGER
      {
        eDeactivated (0),
        eActivated (1)
      }
    MAX-ACCESS read-only
    STATUS     current
    DESCRIPTION
        "-- empty --"
    ::= { lcsSetupTacacsPlus 2 }

-- {SCALAR} 310.2.54.3
lcsSetupTacacsPlusAccounting OBJECT-TYPE
    SYNTAX     INTEGER
      {
        eDeactivated (0),
        eActivated (1)
      }
    MAX-ACCESS read-only
    STATUS     current
    DESCRIPTION
        "-- empty --"
    ::= { lcsSetupTacacsPlus 3 }

-- {TABLE} 310.2.54.9
lcsSetupTacacsPlusServerTable OBJECT-TYPE
    SYNTAX     SEQUENCE OF LcsSetupTacacsPlusServerEntry
    MAX-ACCESS not-accessible
    STATUS     current
    DESCRIPTION
        "-- empty --"
    ::= { lcsSetupTacacsPlus 9 }

-- {ENTRY} 310.2.54.9.1
lcsSetupTacacsPlusServerEntry OBJECT-TYPE
    SYNTAX     LcsSetupTacacsPlusServerEntry
    MAX-ACCESS not-accessible
    STATUS     current
    DESCRIPTION
        ""
    INDEX {
        lcsSetupTacacsPlusServerEntryServerAddress
    }
    ::= { lcsSetupTacacsPlusServerTable 1 }

-- {SEQUENCE}
LcsSetupTacacsPlusServerEntry ::= SEQUENCE {
    lcsSetupTacacsPlusServerEntryServerAddress DisplayString,
    lcsSetupTacacsPlusServerEntryLoopbackAddress DisplayString,
    lcsSetupTacacsPlusServerEntryCompatibilityMode INTEGER
}

-- {COLUMN} 310.2.54.9.1.1
lcsSetupTacacsPlusServerEntryServerAddress OBJECT-TYPE
    SYNTAX     DisplayString (SIZE(0..31))
    MAX-ACCESS read-write
    STATUS     current
    DESCRIPTION
        "-- empty --"
    ::= { lcsSetupTacacsPlusServerEntry 1 }

-- {COLUMN} 310.2.54.9.1.2
lcsSetupTacacsPlusServerEntryLoopbackAddress OBJECT-TYPE
    SYNTAX     DisplayString (SIZE(0..16))
    MAX-ACCESS read-write
    STATUS     current
    DESCRIPTION
        "-- empty --"
    ::= { lcsSetupTacacsPlusServerEntry 2 }

-- {COLUMN} 310.2.54.9.1.3
lcsSetupTacacsPlusServerEntryCompatibilityMode OBJECT-TYPE
    SYNTAX     INTEGER
      {
        eDeactivated (0),
        eActivated (1)
      }
    MAX-ACCESS read-write
    STATUS     current
    DESCRIPTION
        "-- empty --"
    ::= { lcsSetupTacacsPlusServerEntry 3 }

-- {SCALAR} 310.2.54.6
lcsSetupTacacsPlusSharedSecret OBJECT-TYPE
    SYNTAX     DisplayString (SIZE(0..31))
    MAX-ACCESS read-only
    STATUS     current
    DESCRIPTION
        "-- empty --"
    ::= { lcsSetupTacacsPlus 6 }

-- {SCALAR} 310.2.54.7
lcsSetupTacacsPlusEncryption OBJECT-TYPE
    SYNTAX     INTEGER
      {
        eDeactivated (0),
        eActivated (1)
      }
    MAX-ACCESS read-only
    STATUS     current
    DESCRIPTION
        "-- empty --"
    ::= { lcsSetupTacacsPlus 7 }

-- {SCALAR} 310.2.54.10
lcsSetupTacacsPlusFallbackToLocalUsers OBJECT-TYPE
    SYNTAX     INTEGER
      {
        eAllowed (0),
        eProhibited (1)
      }
    MAX-ACCESS read-only
    STATUS     current
    DESCRIPTION
        "-- empty --"
    ::= { lcsSetupTacacsPlus 10 }

-- {SCALAR} 310.2.54.11
lcsSetupTacacsPlusSnmpGetRequestsAuthorisation OBJECT-TYPE
    SYNTAX     INTEGER
      {
        eOnlyForSetupTree (0),
        eAll (1),
        eNone (2)
      }
    MAX-ACCESS read-only
    STATUS     current
    DESCRIPTION
        "-- empty --"
    ::= { lcsSetupTacacsPlus 11 }

-- {SCALAR} 310.2.54.12
lcsSetupTacacsPlusSnmpGetRequestsAccounting OBJECT-TYPE
    SYNTAX     INTEGER
      {
        eOnlyForSetupTree (0),
        eAll (1),
        eNone (2)
      }
    MAX-ACCESS read-only
    STATUS     current
    DESCRIPTION
        "-- empty --"
    ::= { lcsSetupTacacsPlus 12 }

-- {SCALAR} 310.2.54.13
lcsSetupTacacsPlusBypassTacacsForCronScriptsActionTable OBJECT-TYPE
    SYNTAX     INTEGER
      {
        eDeactivated (0),
        eActivated (1)
      }
    MAX-ACCESS read-only
    STATUS     current
    DESCRIPTION
        "-- empty --"
    ::= { lcsSetupTacacsPlus 13 }

-- {SCALAR} 310.2.54.14
lcsSetupTacacsPlusIncludeValueIntoAuthorisationRequest OBJECT-TYPE
    SYNTAX     INTEGER
      {
        eDeactivated (0),
        eActivated (1)
      }
    MAX-ACCESS read-only
    STATUS     current
    DESCRIPTION
        "-- empty --"
    ::= { lcsSetupTacacsPlus 14 }

-- {OID} 310.2.30
lcsSetupIeee8021x OBJECT IDENTIFIER ::= { lcsSetup 30 }

-- {TABLE} 310.2.30.4
lcsSetupIeee8021xPortsTable OBJECT-TYPE
    SYNTAX     SEQUENCE OF LcsSetupIeee8021xPortsEntry
    MAX-ACCESS not-accessible
    STATUS     current
    DESCRIPTION
        "-- empty --"
    ::= { lcsSetupIeee8021x 4 }

-- {ENTRY} 310.2.30.4.1
lcsSetupIeee8021xPortsEntry OBJECT-TYPE
    SYNTAX     LcsSetupIeee8021xPortsEntry
    MAX-ACCESS not-accessible
    STATUS     current
    DESCRIPTION
        ""
    INDEX {
        lcsSetupIeee8021xPortsEntryPort
    }
    ::= { lcsSetupIeee8021xPortsTable 1 }

-- {SEQUENCE}
LcsSetupIeee8021xPortsEntry ::= SEQUENCE {
    lcsSetupIeee8021xPortsEntryPort DisplayString,
    lcsSetupIeee8021xPortsEntryPortControl INTEGER,
    lcsSetupIeee8021xPortsEntryReAuthMax INTEGER,
    lcsSetupIeee8021xPortsEntryMaxReq INTEGER,
    lcsSetupIeee8021xPortsEntryTxPeriod INTEGER,
    lcsSetupIeee8021xPortsEntrySuppTimeout INTEGER,
    lcsSetupIeee8021xPortsEntryServerTimeout INTEGER,
    lcsSetupIeee8021xPortsEntryQuietPeriod INTEGER,
    lcsSetupIeee8021xPortsEntryReAuthentication INTEGER,
    lcsSetupIeee8021xPortsEntryReAuthInterval INTEGER,
    lcsSetupIeee8021xPortsEntryKeyTransmission INTEGER,
    lcsSetupIeee8021xPortsEntryKeyTxInterval INTEGER
}

-- {COLUMN} 310.2.30.4.1.2
lcsSetupIeee8021xPortsEntryPort OBJECT-TYPE
    SYNTAX     DisplayString (SIZE(0..15))
    MAX-ACCESS read-only
    STATUS     current
    DESCRIPTION
        "-- empty --"
    ::= { lcsSetupIeee8021xPortsEntry 2 }

-- {COLUMN} 310.2.30.4.1.3
lcsSetupIeee8021xPortsEntryPortControl OBJECT-TYPE
    SYNTAX     INTEGER
      {
        eForceUnauth (0),
        eForceAuth (1),
        eAuto (2)
      }
    MAX-ACCESS read-write
    STATUS     current
    DESCRIPTION
        "-- empty --"
    ::= { lcsSetupIeee8021xPortsEntry 3 }

-- {COLUMN} 310.2.30.4.1.4
lcsSetupIeee8021xPortsEntryReAuthMax OBJECT-TYPE
    SYNTAX     INTEGER (0..255)
    MAX-ACCESS read-write
    STATUS     current
    DESCRIPTION
        "-- empty --"
    ::= { lcsSetupIeee8021xPortsEntry 4 }

-- {COLUMN} 310.2.30.4.1.5
lcsSetupIeee8021xPortsEntryMaxReq OBJECT-TYPE
    SYNTAX     INTEGER (0..255)
    MAX-ACCESS read-write
    STATUS     current
    DESCRIPTION
        "-- empty --"
    ::= { lcsSetupIeee8021xPortsEntry 5 }

-- {COLUMN} 310.2.30.4.1.6
lcsSetupIeee8021xPortsEntryTxPeriod OBJECT-TYPE
    SYNTAX     INTEGER (0..65535)
    MAX-ACCESS read-write
    STATUS     current
    DESCRIPTION
        "-- empty --"
    ::= { lcsSetupIeee8021xPortsEntry 6 }

-- {COLUMN} 310.2.30.4.1.7
lcsSetupIeee8021xPortsEntrySuppTimeout OBJECT-TYPE
    SYNTAX     INTEGER (0..65535)
    MAX-ACCESS read-write
    STATUS     current
    DESCRIPTION
        "-- empty --"
    ::= { lcsSetupIeee8021xPortsEntry 7 }

-- {COLUMN} 310.2.30.4.1.8
lcsSetupIeee8021xPortsEntryServerTimeout OBJECT-TYPE
    SYNTAX     INTEGER (0..65535)
    MAX-ACCESS read-write
    STATUS     current
    DESCRIPTION
        "-- empty --"
    ::= { lcsSetupIeee8021xPortsEntry 8 }

-- {COLUMN} 310.2.30.4.1.9
lcsSetupIeee8021xPortsEntryQuietPeriod OBJECT-TYPE
    SYNTAX     INTEGER (0..65535)
    MAX-ACCESS read-write
    STATUS     current
    DESCRIPTION
        "-- empty --"
    ::= { lcsSetupIeee8021xPortsEntry 9 }

-- {COLUMN} 310.2.30.4.1.10
lcsSetupIeee8021xPortsEntryReAuthentication OBJECT-TYPE
    SYNTAX     INTEGER
      {
        eNo (0),
        eYes (1)
      }
    MAX-ACCESS read-write
    STATUS     current
    DESCRIPTION
        "-- empty --"
    ::= { lcsSetupIeee8021xPortsEntry 10 }

-- {COLUMN} 310.2.30.4.1.11
lcsSetupIeee8021xPortsEntryReAuthInterval OBJECT-TYPE
    SYNTAX     INTEGER (0..65535)
    MAX-ACCESS read-write
    STATUS     current
    DESCRIPTION
        "-- empty --"
    ::= { lcsSetupIeee8021xPortsEntry 11 }

-- {COLUMN} 310.2.30.4.1.12
lcsSetupIeee8021xPortsEntryKeyTransmission OBJECT-TYPE
    SYNTAX     INTEGER
      {
        eNo (0),
        eYes (1)
      }
    MAX-ACCESS read-write
    STATUS     current
    DESCRIPTION
        "-- empty --"
    ::= { lcsSetupIeee8021xPortsEntry 12 }

-- {COLUMN} 310.2.30.4.1.13
lcsSetupIeee8021xPortsEntryKeyTxInterval OBJECT-TYPE
    SYNTAX     INTEGER (0..65535)
    MAX-ACCESS read-write
    STATUS     current
    DESCRIPTION
        "-- empty --"
    ::= { lcsSetupIeee8021xPortsEntry 13 }

-- {TABLE} 310.2.30.3
lcsSetupIeee8021xRadiusServerTable OBJECT-TYPE
    SYNTAX     SEQUENCE OF LcsSetupIeee8021xRadiusServerEntry
    MAX-ACCESS not-accessible
    STATUS     current
    DESCRIPTION
        "-- empty --"
    ::= { lcsSetupIeee8021x 3 }

-- {ENTRY} 310.2.30.3.1
lcsSetupIeee8021xRadiusServerEntry OBJECT-TYPE
    SYNTAX     LcsSetupIeee8021xRadiusServerEntry
    MAX-ACCESS not-accessible
    STATUS     current
    DESCRIPTION
        ""
    INDEX {
        lcsSetupIeee8021xRadiusServerEntryName
    }
    ::= { lcsSetupIeee8021xRadiusServerTable 1 }

-- {SEQUENCE}
LcsSetupIeee8021xRadiusServerEntry ::= SEQUENCE {
    lcsSetupIeee8021xRadiusServerEntryName DisplayString,
    lcsSetupIeee8021xRadiusServerEntryIpAddress IpAddress,
    lcsSetupIeee8021xRadiusServerEntryPort INTEGER,
    lcsSetupIeee8021xRadiusServerEntrySecret DisplayString,
    lcsSetupIeee8021xRadiusServerEntryLoopbackAddr DisplayString,
    lcsSetupIeee8021xRadiusServerEntryProtocol INTEGER,
    lcsSetupIeee8021xRadiusServerEntryBackup DisplayString
}

-- {COLUMN} 310.2.30.3.1.1
lcsSetupIeee8021xRadiusServerEntryName OBJECT-TYPE
    SYNTAX     DisplayString (SIZE(0..16))
    MAX-ACCESS read-write
    STATUS     current
    DESCRIPTION
        "-- empty --"
    ::= { lcsSetupIeee8021xRadiusServerEntry 1 }

-- {COLUMN} 310.2.30.3.1.2
lcsSetupIeee8021xRadiusServerEntryIpAddress OBJECT-TYPE
    SYNTAX     IpAddress
    MAX-ACCESS read-write
    STATUS     current
    DESCRIPTION
        "-- empty --"
    ::= { lcsSetupIeee8021xRadiusServerEntry 2 }

-- {COLUMN} 310.2.30.3.1.3
lcsSetupIeee8021xRadiusServerEntryPort OBJECT-TYPE
    SYNTAX     INTEGER (0..65535)
    MAX-ACCESS read-write
    STATUS     current
    DESCRIPTION
        "-- empty --"
    ::= { lcsSetupIeee8021xRadiusServerEntry 3 }

-- {COLUMN} 310.2.30.3.1.4
lcsSetupIeee8021xRadiusServerEntrySecret OBJECT-TYPE
    SYNTAX     DisplayString (SIZE(0..64))
    MAX-ACCESS read-write
    STATUS     current
    DESCRIPTION
        "-- empty --"
    ::= { lcsSetupIeee8021xRadiusServerEntry 4 }

-- {COLUMN} 310.2.30.3.1.6
lcsSetupIeee8021xRadiusServerEntryLoopbackAddr OBJECT-TYPE
    SYNTAX     DisplayString (SIZE(0..16))
    MAX-ACCESS read-write
    STATUS     current
    DESCRIPTION
        "-- empty --"
    ::= { lcsSetupIeee8021xRadiusServerEntry 6 }

-- {COLUMN} 310.2.30.3.1.7
lcsSetupIeee8021xRadiusServerEntryProtocol OBJECT-TYPE
    SYNTAX     INTEGER
      {
        eRadius (0),
        eRadsec (1)
      }
    MAX-ACCESS read-write
    STATUS     current
    DESCRIPTION
        "-- empty --"
    ::= { lcsSetupIeee8021xRadiusServerEntry 7 }

-- {COLUMN} 310.2.30.3.1.5
lcsSetupIeee8021xRadiusServerEntryBackup OBJECT-TYPE
    SYNTAX     DisplayString (SIZE(0..16))
    MAX-ACCESS read-write
    STATUS     current
    DESCRIPTION
        "-- empty --"
    ::= { lcsSetupIeee8021xRadiusServerEntry 5 }

-- {OID} 310.2.59
lcsSetupWtpMngmt OBJECT IDENTIFIER ::= { lcsSetup 59 }

-- {TABLE} 310.2.59.1
lcsSetupWtpMngmtStaticWlcConfTable OBJECT-TYPE
    SYNTAX     SEQUENCE OF LcsSetupWtpMngmtStaticWlcConfEntry
    MAX-ACCESS not-accessible
    STATUS     current
    DESCRIPTION
        "static WLC configuration"
    ::= { lcsSetupWtpMngmt 1 }

-- {ENTRY} 310.2.59.1.1
lcsSetupWtpMngmtStaticWlcConfEntry OBJECT-TYPE
    SYNTAX     LcsSetupWtpMngmtStaticWlcConfEntry
    MAX-ACCESS not-accessible
    STATUS     current
    DESCRIPTION
        ""
    INDEX {
        lcsSetupWtpMngmtStaticWlcConfEntryIpAddress
    }
    ::= { lcsSetupWtpMngmtStaticWlcConfTable 1 }

-- {SEQUENCE}
LcsSetupWtpMngmtStaticWlcConfEntry ::= SEQUENCE {
    lcsSetupWtpMngmtStaticWlcConfEntryIpAddress DisplayString,
    lcsSetupWtpMngmtStaticWlcConfEntryPort INTEGER,
    lcsSetupWtpMngmtStaticWlcConfEntryLoopbackAddr DisplayString
}

-- {COLUMN} 310.2.59.1.1.1
lcsSetupWtpMngmtStaticWlcConfEntryIpAddress OBJECT-TYPE
    SYNTAX     DisplayString (SIZE(0..63))
    MAX-ACCESS read-write
    STATUS     current
    DESCRIPTION
        "-- empty --"
    ::= { lcsSetupWtpMngmtStaticWlcConfEntry 1 }

-- {COLUMN} 310.2.59.1.1.2
lcsSetupWtpMngmtStaticWlcConfEntryPort OBJECT-TYPE
    SYNTAX     INTEGER (0..65535)
    MAX-ACCESS read-write
    STATUS     current
    DESCRIPTION
        "-- empty --"
    ::= { lcsSetupWtpMngmtStaticWlcConfEntry 2 }

-- {COLUMN} 310.2.59.1.1.3
lcsSetupWtpMngmtStaticWlcConfEntryLoopbackAddr OBJECT-TYPE
    SYNTAX     DisplayString (SIZE(0..16))
    MAX-ACCESS read-write
    STATUS     current
    DESCRIPTION
        "-- empty --"
    ::= { lcsSetupWtpMngmtStaticWlcConfEntry 3 }

-- {SCALAR} 310.2.59.120
lcsSetupWtpMngmtLogEntries OBJECT-TYPE
    SYNTAX     INTEGER (0..2147483647)
    MAX-ACCESS read-only
    STATUS     current
    DESCRIPTION
        "-- empty --"
    ::= { lcsSetupWtpMngmt 120 }

-- {OID} 310.2.39
lcsSetupCerts OBJECT IDENTIFIER ::= { lcsSetup 39 }

-- {OID} 310.2.39.1
lcsSetupCertsScepClnt OBJECT IDENTIFIER ::= { lcsSetupCerts 1 }

-- {SCALAR} 310.2.39.1.1
lcsSetupCertsScepClntScepOperating OBJECT-TYPE
    SYNTAX     INTEGER
      {
        eNo (0),
        eYes (1)
      }
    MAX-ACCESS read-write
    STATUS     current
    DESCRIPTION
        "-- empty --"
    ::= { lcsSetupCertsScepClnt 1 }

-- {SCALAR} 310.2.39.1.11
lcsSetupCertsScepClntRetryAfterErrorInterval OBJECT-TYPE
    SYNTAX     INTEGER (0..2147483647)
    MAX-ACCESS read-only
    STATUS     current
    DESCRIPTION
        "-- empty --"
    ::= { lcsSetupCertsScepClnt 11 }

-- {SCALAR} 310.2.39.1.12
lcsSetupCertsScepClntCheckPendingRequestsInterval OBJECT-TYPE
    SYNTAX     INTEGER (0..2147483647)
    MAX-ACCESS read-only
    STATUS     current
    DESCRIPTION
        "-- empty --"
    ::= { lcsSetupCertsScepClnt 12 }

-- {SCALAR} 310.2.39.1.2
lcsSetupCertsScepClntDeviceCertificateUpdateBefore OBJECT-TYPE
    SYNTAX     INTEGER (0..2147483647)
    MAX-ACCESS read-only
    STATUS     current
    DESCRIPTION
        "-- empty --"
    ::= { lcsSetupCertsScepClnt 2 }

-- {SCALAR} 310.2.39.1.3
lcsSetupCertsScepClntCaCertificateUpdateBefore OBJECT-TYPE
    SYNTAX     INTEGER (0..2147483647)
    MAX-ACCESS read-only
    STATUS     current
    DESCRIPTION
        "-- empty --"
    ::= { lcsSetupCertsScepClnt 3 }

-- {TABLE} 310.2.39.1.14
lcsSetupCertsScepClntCasTable OBJECT-TYPE
    SYNTAX     SEQUENCE OF LcsSetupCertsScepClntCasEntry
    MAX-ACCESS not-accessible
    STATUS     current
    DESCRIPTION
        "-- empty --"
    ::= { lcsSetupCertsScepClnt 14 }

-- {ENTRY} 310.2.39.1.14.1
lcsSetupCertsScepClntCasEntry OBJECT-TYPE
    SYNTAX     LcsSetupCertsScepClntCasEntry
    MAX-ACCESS not-accessible
    STATUS     current
    DESCRIPTION
        ""
    INDEX {
        lcsSetupCertsScepClntCasEntryName
    }
    ::= { lcsSetupCertsScepClntCasTable 1 }

-- {SEQUENCE}
LcsSetupCertsScepClntCasEntry ::= SEQUENCE {
    lcsSetupCertsScepClntCasEntryName DisplayString,
    lcsSetupCertsScepClntCasEntryUrl DisplayString,
    lcsSetupCertsScepClntCasEntryDn DisplayString,
    lcsSetupCertsScepClntCasEntryEncAlg INTEGER,
    lcsSetupCertsScepClntCasEntryIdentifier DisplayString,
    lcsSetupCertsScepClntCasEntryRaAutoapprove INTEGER,
    lcsSetupCertsScepClntCasEntryCaSignatureAlgorithm INTEGER,
    lcsSetupCertsScepClntCasEntryCaFingerprintAlgorithm INTEGER,
    lcsSetupCertsScepClntCasEntryCaFingerprint DisplayString,
    lcsSetupCertsScepClntCasEntryLoopbackAddr DisplayString
}

-- {COLUMN} 310.2.39.1.14.1.1
lcsSetupCertsScepClntCasEntryName OBJECT-TYPE
    SYNTAX     DisplayString (SIZE(0..16))
    MAX-ACCESS read-write
    STATUS     current
    DESCRIPTION
        "-- empty --"
    ::= { lcsSetupCertsScepClntCasEntry 1 }

-- {COLUMN} 310.2.39.1.14.1.2
lcsSetupCertsScepClntCasEntryUrl OBJECT-TYPE
    SYNTAX     DisplayString (SIZE(0..251))
    MAX-ACCESS read-write
    STATUS     current
    DESCRIPTION
        "-- empty --"
    ::= { lcsSetupCertsScepClntCasEntry 2 }

-- {COLUMN} 310.2.39.1.14.1.3
lcsSetupCertsScepClntCasEntryDn OBJECT-TYPE
    SYNTAX     DisplayString (SIZE(0..251))
    MAX-ACCESS read-write
    STATUS     current
    DESCRIPTION
        "-- empty --"
    ::= { lcsSetupCertsScepClntCasEntry 3 }

-- {COLUMN} 310.2.39.1.14.1.4
lcsSetupCertsScepClntCasEntryEncAlg OBJECT-TYPE
    SYNTAX     INTEGER
      {
        eDes (0),
        e3des (1),
        eBlowfish (2),
        eAes128 (3)
      }
    MAX-ACCESS read-write
    STATUS     current
    DESCRIPTION
        "-- empty --"
    ::= { lcsSetupCertsScepClntCasEntry 4 }

-- {COLUMN} 310.2.39.1.14.1.5
lcsSetupCertsScepClntCasEntryIdentifier OBJECT-TYPE
    SYNTAX     DisplayString (SIZE(0..251))
    MAX-ACCESS read-write
    STATUS     current
    DESCRIPTION
        "-- empty --"
    ::= { lcsSetupCertsScepClntCasEntry 5 }

-- {COLUMN} 310.2.39.1.14.1.7
lcsSetupCertsScepClntCasEntryRaAutoapprove OBJECT-TYPE
    SYNTAX     INTEGER
      {
        eNo (0),
        eYes (1)
      }
    MAX-ACCESS read-write
    STATUS     current
    DESCRIPTION
        "-- empty --"
    ::= { lcsSetupCertsScepClntCasEntry 7 }

-- {COLUMN} 310.2.39.1.14.1.6
lcsSetupCertsScepClntCasEntryCaSignatureAlgorithm OBJECT-TYPE
    SYNTAX     INTEGER
      {
        eMd5 (0),
        eSha1 (1)
      }
    MAX-ACCESS read-write
    STATUS     current
    DESCRIPTION
        "-- empty --"
    ::= { lcsSetupCertsScepClntCasEntry 6 }

-- {COLUMN} 310.2.39.1.14.1.8
lcsSetupCertsScepClntCasEntryCaFingerprintAlgorithm OBJECT-TYPE
    SYNTAX     INTEGER
      {
        eOff (0),
        eSha1 (1),
        eMd5 (2)
      }
    MAX-ACCESS read-write
    STATUS     current
    DESCRIPTION
        "-- empty --"
    ::= { lcsSetupCertsScepClntCasEntry 8 }

-- {COLUMN} 310.2.39.1.14.1.9
lcsSetupCertsScepClntCasEntryCaFingerprint OBJECT-TYPE
    SYNTAX     DisplayString (SIZE(0..59))
    MAX-ACCESS read-write
    STATUS     current
    DESCRIPTION
        "-- empty --"
    ::= { lcsSetupCertsScepClntCasEntry 9 }

-- {COLUMN} 310.2.39.1.14.1.11
lcsSetupCertsScepClntCasEntryLoopbackAddr OBJECT-TYPE
    SYNTAX     DisplayString (SIZE(0..16))
    MAX-ACCESS read-write
    STATUS     current
    DESCRIPTION
        "-- empty --"
    ::= { lcsSetupCertsScepClntCasEntry 11 }

-- {TABLE} 310.2.39.1.7
lcsSetupCertsScepClntCertsTable OBJECT-TYPE
    SYNTAX     SEQUENCE OF LcsSetupCertsScepClntCertsEntry
    MAX-ACCESS not-accessible
    STATUS     current
    DESCRIPTION
        ""
    ::= { lcsSetupCertsScepClnt 7 }

-- {ENTRY} 310.2.39.1.7.1
lcsSetupCertsScepClntCertsEntry OBJECT-TYPE
    SYNTAX     LcsSetupCertsScepClntCertsEntry
    MAX-ACCESS not-accessible
    STATUS     current
    DESCRIPTION
        ""
    INDEX {
        lcsSetupCertsScepClntCertsEntryName
    }
    ::= { lcsSetupCertsScepClntCertsTable 1 }

-- {SEQUENCE}
LcsSetupCertsScepClntCertsEntry ::= SEQUENCE {
    lcsSetupCertsScepClntCertsEntryName DisplayString,
    lcsSetupCertsScepClntCertsEntryCadn DisplayString,
    lcsSetupCertsScepClntCertsEntrySubject DisplayString,
    lcsSetupCertsScepClntCertsEntryChallengepwd DisplayString,
    lcsSetupCertsScepClntCertsEntrySubjectaltname DisplayString,
    lcsSetupCertsScepClntCertsEntryKeyusage DisplayString,
    lcsSetupCertsScepClntCertsEntryExtendedKeyusage DisplayString,
    lcsSetupCertsScepClntCertsEntryDevCertKeyl INTEGER,
    lcsSetupCertsScepClntCertsEntryApplication INTEGER
}

-- {COLUMN} 310.2.39.1.7.1.1
lcsSetupCertsScepClntCertsEntryName OBJECT-TYPE
    SYNTAX     DisplayString (SIZE(0..16))
    MAX-ACCESS read-write
    STATUS     current
    DESCRIPTION
        "-- empty --"
    ::= { lcsSetupCertsScepClntCertsEntry 1 }

-- {COLUMN} 310.2.39.1.7.1.2
lcsSetupCertsScepClntCertsEntryCadn OBJECT-TYPE
    SYNTAX     DisplayString (SIZE(0..251))
    MAX-ACCESS read-write
    STATUS     current
    DESCRIPTION
        "-- empty --"
    ::= { lcsSetupCertsScepClntCertsEntry 2 }

-- {COLUMN} 310.2.39.1.7.1.3
lcsSetupCertsScepClntCertsEntrySubject OBJECT-TYPE
    SYNTAX     DisplayString (SIZE(0..251))
    MAX-ACCESS read-write
    STATUS     current
    DESCRIPTION
        "-- empty --"
    ::= { lcsSetupCertsScepClntCertsEntry 3 }

-- {COLUMN} 310.2.39.1.7.1.4
lcsSetupCertsScepClntCertsEntryChallengepwd OBJECT-TYPE
    SYNTAX     DisplayString (SIZE(0..251))
    MAX-ACCESS read-write
    STATUS     current
    DESCRIPTION
        "-- empty --"
    ::= { lcsSetupCertsScepClntCertsEntry 4 }

-- {COLUMN} 310.2.39.1.7.1.5
lcsSetupCertsScepClntCertsEntrySubjectaltname OBJECT-TYPE
    SYNTAX     DisplayString (SIZE(0..251))
    MAX-ACCESS read-write
    STATUS     current
    DESCRIPTION
        "-- empty --"
    ::= { lcsSetupCertsScepClntCertsEntry 5 }

-- {COLUMN} 310.2.39.1.7.1.6
lcsSetupCertsScepClntCertsEntryKeyusage OBJECT-TYPE
    SYNTAX     DisplayString (SIZE(0..251))
    MAX-ACCESS read-write
    STATUS     current
    DESCRIPTION
        "-- empty --"
    ::= { lcsSetupCertsScepClntCertsEntry 6 }

-- {COLUMN} 310.2.39.1.7.1.9
lcsSetupCertsScepClntCertsEntryExtendedKeyusage OBJECT-TYPE
    SYNTAX     DisplayString (SIZE(0..251))
    MAX-ACCESS read-write
    STATUS     current
    DESCRIPTION
        "-- empty --"
    ::= { lcsSetupCertsScepClntCertsEntry 9 }

-- {COLUMN} 310.2.39.1.7.1.7
lcsSetupCertsScepClntCertsEntryDevCertKeyl OBJECT-TYPE
    SYNTAX     INTEGER (0..2147483647)
    MAX-ACCESS read-write
    STATUS     current
    DESCRIPTION
        ""
    ::= { lcsSetupCertsScepClntCertsEntry 7 }

-- {COLUMN} 310.2.39.1.7.1.8
lcsSetupCertsScepClntCertsEntryApplication OBJECT-TYPE
    SYNTAX     INTEGER
      {
        eWlanController (1),
        eEapTls (3),
        eDefault (13),
        eUnconfigured (-1)
      }
    MAX-ACCESS read-write
    STATUS     current
    DESCRIPTION
        "-- empty --"
    ::= { lcsSetupCertsScepClntCertsEntry 8 }

-- {SCALAR} 310.2.39.1.8
lcsSetupCertsScepClntReinit OBJECT-TYPE
    SYNTAX     DisplayString
    MAX-ACCESS read-write
    STATUS     current
    DESCRIPTION
        "-- empty --"
    ::= { lcsSetupCertsScepClnt 8 }

-- {SCALAR} 310.2.39.1.9
lcsSetupCertsScepClntUpdate OBJECT-TYPE
    SYNTAX     DisplayString
    MAX-ACCESS read-write
    STATUS     current
    DESCRIPTION
        "-- empty --"
    ::= { lcsSetupCertsScepClnt 9 }

-- {SCALAR} 310.2.39.1.10
lcsSetupCertsScepClntClearScepFilesystem OBJECT-TYPE
    SYNTAX     DisplayString
    MAX-ACCESS read-write
    STATUS     current
    DESCRIPTION
        "-- empty --"
    ::= { lcsSetupCertsScepClnt 10 }

-- {SCALAR} 310.2.39.1.13
lcsSetupCertsScepClntTraceLevel OBJECT-TYPE
    SYNTAX     INTEGER
      {
        eAll (7),
        eReduced (6),
        eOnlyErrors (3)
      }
    MAX-ACCESS read-write
    STATUS     current
    DESCRIPTION
        "-- empty --"
    ::= { lcsSetupCertsScepClnt 13 }

-- {OID} 310.2.36
lcsSetupPerfmon OBJECT IDENTIFIER ::= { lcsSetup 36 }

-- {TABLE} 310.2.36.2
lcsSetupPerfmonRttmonadminTable OBJECT-TYPE
    SYNTAX     SEQUENCE OF LcsSetupPerfmonRttmonadminEntry
    MAX-ACCESS not-accessible
    STATUS     current
    DESCRIPTION
        "-- empty --"
    ::= { lcsSetupPerfmon 2 }

-- {ENTRY} 310.2.36.2.1
lcsSetupPerfmonRttmonadminEntry OBJECT-TYPE
    SYNTAX     LcsSetupPerfmonRttmonadminEntry
    MAX-ACCESS not-accessible
    STATUS     current
    DESCRIPTION
        ""
    INDEX {
        lcsSetupPerfmonRttmonadminEntryIndex
    }
    ::= { lcsSetupPerfmonRttmonadminTable 1 }

-- {SEQUENCE}
LcsSetupPerfmonRttmonadminEntry ::= SEQUENCE {
    lcsSetupPerfmonRttmonadminEntryIndex INTEGER,
    lcsSetupPerfmonRttmonadminEntryType INTEGER,
    lcsSetupPerfmonRttmonadminEntryFrequency INTEGER,
    lcsSetupPerfmonRttmonadminEntryTimeout INTEGER,
    lcsSetupPerfmonRttmonadminEntryStatus INTEGER
}

-- {COLUMN} 310.2.36.2.1.1
lcsSetupPerfmonRttmonadminEntryIndex OBJECT-TYPE
    SYNTAX     INTEGER (0..2147483647)
    MAX-ACCESS read-write
    STATUS     current
    DESCRIPTION
        "-- empty --"
    ::= { lcsSetupPerfmonRttmonadminEntry 1 }

-- {COLUMN} 310.2.36.2.1.4
lcsSetupPerfmonRttmonadminEntryType OBJECT-TYPE
    SYNTAX     INTEGER
      {
        eJitter (9)
      }
    MAX-ACCESS read-write
    STATUS     current
    DESCRIPTION
        "-- empty --"
    ::= { lcsSetupPerfmonRttmonadminEntry 4 }

-- {COLUMN} 310.2.36.2.1.6
lcsSetupPerfmonRttmonadminEntryFrequency OBJECT-TYPE
    SYNTAX     INTEGER (0..2147483647)
    MAX-ACCESS read-write
    STATUS     current
    DESCRIPTION
        "-- empty --"
    ::= { lcsSetupPerfmonRttmonadminEntry 6 }

-- {COLUMN} 310.2.36.2.1.7
lcsSetupPerfmonRttmonadminEntryTimeout OBJECT-TYPE
    SYNTAX     INTEGER (0..2147483647)
    MAX-ACCESS read-write
    STATUS     current
    DESCRIPTION
        "-- empty --"
    ::= { lcsSetupPerfmonRttmonadminEntry 7 }

-- {COLUMN} 310.2.36.2.1.9
lcsSetupPerfmonRttmonadminEntryStatus OBJECT-TYPE
    SYNTAX     INTEGER
      {
        eActive (1),
        eNotInService (2),
        eNotReady (3),
        eCreate (5),
        eDestroy (6)
      }
    MAX-ACCESS read-write
    STATUS     current
    DESCRIPTION
        "-- empty --"
    ::= { lcsSetupPerfmonRttmonadminEntry 9 }

-- {TABLE} 310.2.36.3
lcsSetupPerfmonRttmonechoadminTable OBJECT-TYPE
    SYNTAX     SEQUENCE OF LcsSetupPerfmonRttmonechoadminEntry
    MAX-ACCESS not-accessible
    STATUS     current
    DESCRIPTION
        "-- empty --"
    ::= { lcsSetupPerfmon 3 }

-- {ENTRY} 310.2.36.3.1
lcsSetupPerfmonRttmonechoadminEntry OBJECT-TYPE
    SYNTAX     LcsSetupPerfmonRttmonechoadminEntry
    MAX-ACCESS not-accessible
    STATUS     current
    DESCRIPTION
        ""
    INDEX {
        lcsSetupPerfmonRttmonechoadminEntryIndex
    }
    ::= { lcsSetupPerfmonRttmonechoadminTable 1 }

-- {SEQUENCE}
LcsSetupPerfmonRttmonechoadminEntry ::= SEQUENCE {
    lcsSetupPerfmonRttmonechoadminEntryIndex INTEGER,
    lcsSetupPerfmonRttmonechoadminEntryProtocol INTEGER,
    lcsSetupPerfmonRttmonechoadminEntryDestinationAddress IpAddress,
    lcsSetupPerfmonRttmonechoadminEntryPacketSize INTEGER,
    lcsSetupPerfmonRttmonechoadminEntryDestinationPort INTEGER,
    lcsSetupPerfmonRttmonechoadminEntryInterval INTEGER,
    lcsSetupPerfmonRttmonechoadminEntryPacketCount INTEGER
}

-- {COLUMN} 310.2.36.3.1.255
lcsSetupPerfmonRttmonechoadminEntryIndex OBJECT-TYPE
    SYNTAX     INTEGER (0..2147483647)
    MAX-ACCESS read-only
    STATUS     current
    DESCRIPTION
        "-- empty --"
    ::= { lcsSetupPerfmonRttmonechoadminEntry 255 }

-- {COLUMN} 310.2.36.3.1.1
lcsSetupPerfmonRttmonechoadminEntryProtocol OBJECT-TYPE
    SYNTAX     INTEGER
      {
        eEcho (3)
      }
    MAX-ACCESS read-write
    STATUS     current
    DESCRIPTION
        "-- empty --"
    ::= { lcsSetupPerfmonRttmonechoadminEntry 1 }

-- {COLUMN} 310.2.36.3.1.2
lcsSetupPerfmonRttmonechoadminEntryDestinationAddress OBJECT-TYPE
    SYNTAX     IpAddress
    MAX-ACCESS read-write
    STATUS     current
    DESCRIPTION
        "-- empty --"
    ::= { lcsSetupPerfmonRttmonechoadminEntry 2 }

-- {COLUMN} 310.2.36.3.1.3
lcsSetupPerfmonRttmonechoadminEntryPacketSize OBJECT-TYPE
    SYNTAX     INTEGER (0..65535)
    MAX-ACCESS read-write
    STATUS     current
    DESCRIPTION
        "-- empty --"
    ::= { lcsSetupPerfmonRttmonechoadminEntry 3 }

-- {COLUMN} 310.2.36.3.1.5
lcsSetupPerfmonRttmonechoadminEntryDestinationPort OBJECT-TYPE
    SYNTAX     INTEGER (0..65535)
    MAX-ACCESS read-write
    STATUS     current
    DESCRIPTION
        "-- empty --"
    ::= { lcsSetupPerfmonRttmonechoadminEntry 5 }

-- {COLUMN} 310.2.36.3.1.17
lcsSetupPerfmonRttmonechoadminEntryInterval OBJECT-TYPE
    SYNTAX     INTEGER (0..2147483647)
    MAX-ACCESS read-write
    STATUS     current
    DESCRIPTION
        "-- empty --"
    ::= { lcsSetupPerfmonRttmonechoadminEntry 17 }

-- {COLUMN} 310.2.36.3.1.18
lcsSetupPerfmonRttmonechoadminEntryPacketCount OBJECT-TYPE
    SYNTAX     INTEGER (0..2147483647)
    MAX-ACCESS read-write
    STATUS     current
    DESCRIPTION
        "-- empty --"
    ::= { lcsSetupPerfmonRttmonechoadminEntry 18 }

-- {TABLE} 310.2.36.4
lcsSetupPerfmonRttmonstatisticsTable OBJECT-TYPE
    SYNTAX     SEQUENCE OF LcsSetupPerfmonRttmonstatisticsEntry
    MAX-ACCESS not-accessible
    STATUS     current
    DESCRIPTION
        "-- empty --"
    ::= { lcsSetupPerfmon 4 }

-- {ENTRY} 310.2.36.4.1
lcsSetupPerfmonRttmonstatisticsEntry OBJECT-TYPE
    SYNTAX     LcsSetupPerfmonRttmonstatisticsEntry
    MAX-ACCESS not-accessible
    STATUS     current
    DESCRIPTION
        ""
    INDEX {
        lcsSetupPerfmonRttmonstatisticsEntryIndex
    }
    ::= { lcsSetupPerfmonRttmonstatisticsTable 1 }

-- {SEQUENCE}
LcsSetupPerfmonRttmonstatisticsEntry ::= SEQUENCE {
    lcsSetupPerfmonRttmonstatisticsEntryIndex INTEGER,
    lcsSetupPerfmonRttmonstatisticsEntryCompletions INTEGER,
    lcsSetupPerfmonRttmonstatisticsEntryRttCount INTEGER,
    lcsSetupPerfmonRttmonstatisticsEntryRttSum INTEGER,
    lcsSetupPerfmonRttmonstatisticsEntryRttMin INTEGER,
    lcsSetupPerfmonRttmonstatisticsEntryRttMax INTEGER,
    lcsSetupPerfmonRttmonstatisticsEntryJitterMinPosSd INTEGER,
    lcsSetupPerfmonRttmonstatisticsEntryJitterMaxPosSd INTEGER,
    lcsSetupPerfmonRttmonstatisticsEntryJitterCountPosSd INTEGER,
    lcsSetupPerfmonRttmonstatisticsEntryJitterSumPosSd INTEGER,
    lcsSetupPerfmonRttmonstatisticsEntryJitterMinPosDs INTEGER,
    lcsSetupPerfmonRttmonstatisticsEntryJitterMaxPosDs INTEGER,
    lcsSetupPerfmonRttmonstatisticsEntryJitterCountPosDs INTEGER,
    lcsSetupPerfmonRttmonstatisticsEntryJitterSumPosDs INTEGER,
    lcsSetupPerfmonRttmonstatisticsEntryJitterMinNegSd INTEGER,
    lcsSetupPerfmonRttmonstatisticsEntryJitterMaxNegSd INTEGER,
    lcsSetupPerfmonRttmonstatisticsEntryJitterCountNegSd INTEGER,
    lcsSetupPerfmonRttmonstatisticsEntryJitterSumNegSd INTEGER,
    lcsSetupPerfmonRttmonstatisticsEntryJitterMinNegDs INTEGER,
    lcsSetupPerfmonRttmonstatisticsEntryJitterMaxNegDs INTEGER,
    lcsSetupPerfmonRttmonstatisticsEntryJitterCountNegDs INTEGER,
    lcsSetupPerfmonRttmonstatisticsEntryJitterSumNegDs INTEGER,
    lcsSetupPerfmonRttmonstatisticsEntryPacketLossSd INTEGER,
    lcsSetupPerfmonRttmonstatisticsEntryPacketLossDs INTEGER,
    lcsSetupPerfmonRttmonstatisticsEntryAverageJitter INTEGER,
    lcsSetupPerfmonRttmonstatisticsEntryAverageJitterSd INTEGER,
    lcsSetupPerfmonRttmonstatisticsEntryAverageJitterDs INTEGER
}

-- {COLUMN} 310.2.36.4.1.255
lcsSetupPerfmonRttmonstatisticsEntryIndex OBJECT-TYPE
    SYNTAX     INTEGER (0..2147483647)
    MAX-ACCESS read-only
    STATUS     current
    DESCRIPTION
        "-- empty --"
    ::= { lcsSetupPerfmonRttmonstatisticsEntry 255 }

-- {COLUMN} 310.2.36.4.1.2
lcsSetupPerfmonRttmonstatisticsEntryCompletions OBJECT-TYPE
    SYNTAX     INTEGER (0..2147483647)
    MAX-ACCESS read-only
    STATUS     current
    DESCRIPTION
        "-- empty --"
    ::= { lcsSetupPerfmonRttmonstatisticsEntry 2 }

-- {COLUMN} 310.2.36.4.1.4
lcsSetupPerfmonRttmonstatisticsEntryRttCount OBJECT-TYPE
    SYNTAX     INTEGER (0..2147483647)
    MAX-ACCESS read-only
    STATUS     current
    DESCRIPTION
        "-- empty --"
    ::= { lcsSetupPerfmonRttmonstatisticsEntry 4 }

-- {COLUMN} 310.2.36.4.1.5
lcsSetupPerfmonRttmonstatisticsEntryRttSum OBJECT-TYPE
    SYNTAX     INTEGER (0..2147483647)
    MAX-ACCESS read-only
    STATUS     current
    DESCRIPTION
        "-- empty --"
    ::= { lcsSetupPerfmonRttmonstatisticsEntry 5 }

-- {COLUMN} 310.2.36.4.1.8
lcsSetupPerfmonRttmonstatisticsEntryRttMin OBJECT-TYPE
    SYNTAX     INTEGER (0..2147483647)
    MAX-ACCESS read-only
    STATUS     current
    DESCRIPTION
        "-- empty --"
    ::= { lcsSetupPerfmonRttmonstatisticsEntry 8 }

-- {COLUMN} 310.2.36.4.1.9
lcsSetupPerfmonRttmonstatisticsEntryRttMax OBJECT-TYPE
    SYNTAX     INTEGER (0..2147483647)
    MAX-ACCESS read-only
    STATUS     current
    DESCRIPTION
        "-- empty --"
    ::= { lcsSetupPerfmonRttmonstatisticsEntry 9 }

-- {COLUMN} 310.2.36.4.1.10
lcsSetupPerfmonRttmonstatisticsEntryJitterMinPosSd OBJECT-TYPE
    SYNTAX     INTEGER (0..2147483647)
    MAX-ACCESS read-only
    STATUS     current
    DESCRIPTION
        "-- empty --"
    ::= { lcsSetupPerfmonRttmonstatisticsEntry 10 }

-- {COLUMN} 310.2.36.4.1.11
lcsSetupPerfmonRttmonstatisticsEntryJitterMaxPosSd OBJECT-TYPE
    SYNTAX     INTEGER (0..2147483647)
    MAX-ACCESS read-only
    STATUS     current
    DESCRIPTION
        "-- empty --"
    ::= { lcsSetupPerfmonRttmonstatisticsEntry 11 }

-- {COLUMN} 310.2.36.4.1.12
lcsSetupPerfmonRttmonstatisticsEntryJitterCountPosSd OBJECT-TYPE
    SYNTAX     INTEGER (0..2147483647)
    MAX-ACCESS read-only
    STATUS     current
    DESCRIPTION
        "-- empty --"
    ::= { lcsSetupPerfmonRttmonstatisticsEntry 12 }

-- {COLUMN} 310.2.36.4.1.13
lcsSetupPerfmonRttmonstatisticsEntryJitterSumPosSd OBJECT-TYPE
    SYNTAX     INTEGER (0..2147483647)
    MAX-ACCESS read-only
    STATUS     current
    DESCRIPTION
        "-- empty --"
    ::= { lcsSetupPerfmonRttmonstatisticsEntry 13 }

-- {COLUMN} 310.2.36.4.1.16
lcsSetupPerfmonRttmonstatisticsEntryJitterMinPosDs OBJECT-TYPE
    SYNTAX     INTEGER (0..2147483647)
    MAX-ACCESS read-only
    STATUS     current
    DESCRIPTION
        "-- empty --"
    ::= { lcsSetupPerfmonRttmonstatisticsEntry 16 }

-- {COLUMN} 310.2.36.4.1.17
lcsSetupPerfmonRttmonstatisticsEntryJitterMaxPosDs OBJECT-TYPE
    SYNTAX     INTEGER (0..2147483647)
    MAX-ACCESS read-only
    STATUS     current
    DESCRIPTION
        "-- empty --"
    ::= { lcsSetupPerfmonRttmonstatisticsEntry 17 }

-- {COLUMN} 310.2.36.4.1.18
lcsSetupPerfmonRttmonstatisticsEntryJitterCountPosDs OBJECT-TYPE
    SYNTAX     INTEGER (0..2147483647)
    MAX-ACCESS read-only
    STATUS     current
    DESCRIPTION
        "-- empty --"
    ::= { lcsSetupPerfmonRttmonstatisticsEntry 18 }

-- {COLUMN} 310.2.36.4.1.19
lcsSetupPerfmonRttmonstatisticsEntryJitterSumPosDs OBJECT-TYPE
    SYNTAX     INTEGER (0..2147483647)
    MAX-ACCESS read-only
    STATUS     current
    DESCRIPTION
        "-- empty --"
    ::= { lcsSetupPerfmonRttmonstatisticsEntry 19 }

-- {COLUMN} 310.2.36.4.1.22
lcsSetupPerfmonRttmonstatisticsEntryJitterMinNegSd OBJECT-TYPE
    SYNTAX     INTEGER (0..2147483647)
    MAX-ACCESS read-only
    STATUS     current
    DESCRIPTION
        "-- empty --"
    ::= { lcsSetupPerfmonRttmonstatisticsEntry 22 }

-- {COLUMN} 310.2.36.4.1.23
lcsSetupPerfmonRttmonstatisticsEntryJitterMaxNegSd OBJECT-TYPE
    SYNTAX     INTEGER (0..2147483647)
    MAX-ACCESS read-only
    STATUS     current
    DESCRIPTION
        "-- empty --"
    ::= { lcsSetupPerfmonRttmonstatisticsEntry 23 }

-- {COLUMN} 310.2.36.4.1.24
lcsSetupPerfmonRttmonstatisticsEntryJitterCountNegSd OBJECT-TYPE
    SYNTAX     INTEGER (0..2147483647)
    MAX-ACCESS read-only
    STATUS     current
    DESCRIPTION
        "-- empty --"
    ::= { lcsSetupPerfmonRttmonstatisticsEntry 24 }

-- {COLUMN} 310.2.36.4.1.25
lcsSetupPerfmonRttmonstatisticsEntryJitterSumNegSd OBJECT-TYPE
    SYNTAX     INTEGER (0..2147483647)
    MAX-ACCESS read-only
    STATUS     current
    DESCRIPTION
        "-- empty --"
    ::= { lcsSetupPerfmonRttmonstatisticsEntry 25 }

-- {COLUMN} 310.2.36.4.1.28
lcsSetupPerfmonRttmonstatisticsEntryJitterMinNegDs OBJECT-TYPE
    SYNTAX     INTEGER (0..2147483647)
    MAX-ACCESS read-only
    STATUS     current
    DESCRIPTION
        "-- empty --"
    ::= { lcsSetupPerfmonRttmonstatisticsEntry 28 }

-- {COLUMN} 310.2.36.4.1.29
lcsSetupPerfmonRttmonstatisticsEntryJitterMaxNegDs OBJECT-TYPE
    SYNTAX     INTEGER (0..2147483647)
    MAX-ACCESS read-only
    STATUS     current
    DESCRIPTION
        "-- empty --"
    ::= { lcsSetupPerfmonRttmonstatisticsEntry 29 }

-- {COLUMN} 310.2.36.4.1.30
lcsSetupPerfmonRttmonstatisticsEntryJitterCountNegDs OBJECT-TYPE
    SYNTAX     INTEGER (0..2147483647)
    MAX-ACCESS read-only
    STATUS     current
    DESCRIPTION
        "-- empty --"
    ::= { lcsSetupPerfmonRttmonstatisticsEntry 30 }

-- {COLUMN} 310.2.36.4.1.31
lcsSetupPerfmonRttmonstatisticsEntryJitterSumNegDs OBJECT-TYPE
    SYNTAX     INTEGER (0..2147483647)
    MAX-ACCESS read-only
    STATUS     current
    DESCRIPTION
        "-- empty --"
    ::= { lcsSetupPerfmonRttmonstatisticsEntry 31 }

-- {COLUMN} 310.2.36.4.1.34
lcsSetupPerfmonRttmonstatisticsEntryPacketLossSd OBJECT-TYPE
    SYNTAX     INTEGER (0..2147483647)
    MAX-ACCESS read-only
    STATUS     current
    DESCRIPTION
        "-- empty --"
    ::= { lcsSetupPerfmonRttmonstatisticsEntry 34 }

-- {COLUMN} 310.2.36.4.1.35
lcsSetupPerfmonRttmonstatisticsEntryPacketLossDs OBJECT-TYPE
    SYNTAX     INTEGER (0..2147483647)
    MAX-ACCESS read-only
    STATUS     current
    DESCRIPTION
        "-- empty --"
    ::= { lcsSetupPerfmonRttmonstatisticsEntry 35 }

-- {COLUMN} 310.2.36.4.1.62
lcsSetupPerfmonRttmonstatisticsEntryAverageJitter OBJECT-TYPE
    SYNTAX     INTEGER (0..2147483647)
    MAX-ACCESS read-only
    STATUS     current
    DESCRIPTION
        "-- empty --"
    ::= { lcsSetupPerfmonRttmonstatisticsEntry 62 }

-- {COLUMN} 310.2.36.4.1.63
lcsSetupPerfmonRttmonstatisticsEntryAverageJitterSd OBJECT-TYPE
    SYNTAX     INTEGER (0..2147483647)
    MAX-ACCESS read-only
    STATUS     current
    DESCRIPTION
        "-- empty --"
    ::= { lcsSetupPerfmonRttmonstatisticsEntry 63 }

-- {COLUMN} 310.2.36.4.1.64
lcsSetupPerfmonRttmonstatisticsEntryAverageJitterDs OBJECT-TYPE
    SYNTAX     INTEGER (0..2147483647)
    MAX-ACCESS read-only
    STATUS     current
    DESCRIPTION
        "-- empty --"
    ::= { lcsSetupPerfmonRttmonstatisticsEntry 64 }

-- {OID} 310.2.35
lcsSetupEchoServer OBJECT IDENTIFIER ::= { lcsSetup 35 }

-- {SCALAR} 310.2.35.1
lcsSetupEchoServerOperating OBJECT-TYPE
    SYNTAX     INTEGER
      {
        eNo (0),
        eYes (1)
      }
    MAX-ACCESS read-only
    STATUS     current
    DESCRIPTION
        "-- empty --"
    ::= { lcsSetupEchoServer 1 }

-- {TABLE} 310.2.35.2
lcsSetupEchoServerAccessTableTable OBJECT-TYPE
    SYNTAX     SEQUENCE OF LcsSetupEchoServerAccessTableEntry
    MAX-ACCESS not-accessible
    STATUS     current
    DESCRIPTION
        "-- empty --"
    ::= { lcsSetupEchoServer 2 }

-- {ENTRY} 310.2.35.2.1
lcsSetupEchoServerAccessTableEntry OBJECT-TYPE
    SYNTAX     LcsSetupEchoServerAccessTableEntry
    MAX-ACCESS not-accessible
    STATUS     current
    DESCRIPTION
        ""
    INDEX {
        lcsSetupEchoServerAccessTableEntryIpAddress,
        lcsSetupEchoServerAccessTableEntryNetmask
    }
    ::= { lcsSetupEchoServerAccessTableTable 1 }

-- {SEQUENCE}
LcsSetupEchoServerAccessTableEntry ::= SEQUENCE {
    lcsSetupEchoServerAccessTableEntryIpAddress IpAddress,
    lcsSetupEchoServerAccessTableEntryNetmask IpAddress,
    lcsSetupEchoServerAccessTableEntryProtokoll INTEGER,
    lcsSetupEchoServerAccessTableEntryActive INTEGER,
    lcsSetupEchoServerAccessTableEntryComment DisplayString
}

-- {COLUMN} 310.2.35.2.1.1
lcsSetupEchoServerAccessTableEntryIpAddress OBJECT-TYPE
    SYNTAX     IpAddress
    MAX-ACCESS read-write
    STATUS     current
    DESCRIPTION
        "-- empty --"
    ::= { lcsSetupEchoServerAccessTableEntry 1 }

-- {COLUMN} 310.2.35.2.1.2
lcsSetupEchoServerAccessTableEntryNetmask OBJECT-TYPE
    SYNTAX     IpAddress
    MAX-ACCESS read-write
    STATUS     current
    DESCRIPTION
        "-- empty --"
    ::= { lcsSetupEchoServerAccessTableEntry 2 }

-- {COLUMN} 310.2.35.2.1.3
lcsSetupEchoServerAccessTableEntryProtokoll OBJECT-TYPE
    SYNTAX     INTEGER
      {
        eNone (0),
        eTcp (1),
        eUdp (2),
        eTcpPlusUdp (3)
      }
    MAX-ACCESS read-write
    STATUS     current
    DESCRIPTION
        "-- empty --"
    ::= { lcsSetupEchoServerAccessTableEntry 3 }

-- {COLUMN} 310.2.35.2.1.4
lcsSetupEchoServerAccessTableEntryActive OBJECT-TYPE
    SYNTAX     INTEGER
      {
        eYes (0),
        eNo (1)
      }
    MAX-ACCESS read-write
    STATUS     current
    DESCRIPTION
        "-- empty --"
    ::= { lcsSetupEchoServerAccessTableEntry 4 }

-- {COLUMN} 310.2.35.2.1.5
lcsSetupEchoServerAccessTableEntryComment OBJECT-TYPE
    SYNTAX     DisplayString (SIZE(0..31))
    MAX-ACCESS read-write
    STATUS     current
    DESCRIPTION
        "-- empty --"
    ::= { lcsSetupEchoServerAccessTableEntry 5 }

-- {SCALAR} 310.2.35.3
lcsSetupEchoServerTcpTimeout OBJECT-TYPE
    SYNTAX     INTEGER (0..2147483647)
    MAX-ACCESS read-only
    STATUS     current
    DESCRIPTION
        "-- empty --"
    ::= { lcsSetupEchoServer 3 }

-- {OID} 310.3
lcsFirmware OBJECT IDENTIFIER ::= { lancom-l310 3 }

-- {TABLE} 310.3.1
lcsFirmwareVersionTableTable OBJECT-TYPE
    SYNTAX     SEQUENCE OF LcsFirmwareVersionTableEntry
    MAX-ACCESS not-accessible
    STATUS     current
    DESCRIPTION
        "-- empty --"
    ::= { lcsFirmware 1 }

-- {ENTRY} 310.3.1.1
lcsFirmwareVersionTableEntry OBJECT-TYPE
    SYNTAX     LcsFirmwareVersionTableEntry
    MAX-ACCESS not-accessible
    STATUS     current
    DESCRIPTION
        ""
    INDEX {
        lcsFirmwareVersionTableEntryIfc
    }
    ::= { lcsFirmwareVersionTableTable 1 }

-- {SEQUENCE}
LcsFirmwareVersionTableEntry ::= SEQUENCE {
    lcsFirmwareVersionTableEntryIfc INTEGER,
    lcsFirmwareVersionTableEntryModule DisplayString,
    lcsFirmwareVersionTableEntryVersion DisplayString,
    lcsFirmwareVersionTableEntrySerialNumber DisplayString
}

-- {COLUMN} 310.3.1.1.1
lcsFirmwareVersionTableEntryIfc OBJECT-TYPE
    SYNTAX     INTEGER
      {
        eIfc (1)
      }
    MAX-ACCESS read-only
    STATUS     current
    DESCRIPTION
        "-- empty --"
    ::= { lcsFirmwareVersionTableEntry 1 }

-- {COLUMN} 310.3.1.1.2
lcsFirmwareVersionTableEntryModule OBJECT-TYPE
    SYNTAX     DisplayString (SIZE(0..64))
    MAX-ACCESS read-only
    STATUS     current
    DESCRIPTION
        "-- empty --"
    ::= { lcsFirmwareVersionTableEntry 2 }

-- {COLUMN} 310.3.1.1.3
lcsFirmwareVersionTableEntryVersion OBJECT-TYPE
    SYNTAX     DisplayString (SIZE(0..30))
    MAX-ACCESS read-only
    STATUS     current
    DESCRIPTION
        "-- empty --"
    ::= { lcsFirmwareVersionTableEntry 3 }

-- {COLUMN} 310.3.1.1.4
lcsFirmwareVersionTableEntrySerialNumber OBJECT-TYPE
    SYNTAX     DisplayString (SIZE(0..19))
    MAX-ACCESS read-only
    STATUS     current
    DESCRIPTION
        "-- empty --"
    ::= { lcsFirmwareVersionTableEntry 4 }

-- {TABLE} 310.3.2
lcsFirmwareTableFirmsafeTable OBJECT-TYPE
    SYNTAX     SEQUENCE OF LcsFirmwareTableFirmsafeEntry
    MAX-ACCESS not-accessible
    STATUS     current
    DESCRIPTION
        "-- empty --"
    ::= { lcsFirmware 2 }

-- {ENTRY} 310.3.2.1
lcsFirmwareTableFirmsafeEntry OBJECT-TYPE
    SYNTAX     LcsFirmwareTableFirmsafeEntry
    MAX-ACCESS not-accessible
    STATUS     current
    DESCRIPTION
        ""
    INDEX {
        lcsFirmwareTableFirmsafeEntryPosition
    }
    ::= { lcsFirmwareTableFirmsafeTable 1 }

-- {SEQUENCE}
LcsFirmwareTableFirmsafeEntry ::= SEQUENCE {
    lcsFirmwareTableFirmsafeEntryPosition INTEGER,
    lcsFirmwareTableFirmsafeEntryStatus INTEGER,
    lcsFirmwareTableFirmsafeEntryVersion DisplayString,
    lcsFirmwareTableFirmsafeEntryDate DisplayString,
    lcsFirmwareTableFirmsafeEntrySize INTEGER,
    lcsFirmwareTableFirmsafeEntryIndex INTEGER
}

-- {COLUMN} 310.3.2.1.1
lcsFirmwareTableFirmsafeEntryPosition OBJECT-TYPE
    SYNTAX     INTEGER (0..255)
    MAX-ACCESS read-only
    STATUS     current
    DESCRIPTION
        "-- empty --"
    ::= { lcsFirmwareTableFirmsafeEntry 1 }

-- {COLUMN} 310.3.2.1.2
lcsFirmwareTableFirmsafeEntryStatus OBJECT-TYPE
    SYNTAX     INTEGER
      {
        eLoader (2),
        eActive (1),
        eInactive (0),
        eMinimalPlusActive (5),
        eMinimalPlusInactive (4)
      }
    MAX-ACCESS read-write
    STATUS     current
    DESCRIPTION
        "-- empty --"
    ::= { lcsFirmwareTableFirmsafeEntry 2 }

-- {COLUMN} 310.3.2.1.3
lcsFirmwareTableFirmsafeEntryVersion OBJECT-TYPE
    SYNTAX     DisplayString (SIZE(0..17))
    MAX-ACCESS read-only
    STATUS     current
    DESCRIPTION
        "-- empty --"
    ::= { lcsFirmwareTableFirmsafeEntry 3 }

-- {COLUMN} 310.3.2.1.4
lcsFirmwareTableFirmsafeEntryDate OBJECT-TYPE
    SYNTAX     DisplayString (SIZE(0..9))
    MAX-ACCESS read-only
    STATUS     current
    DESCRIPTION
        "-- empty --"
    ::= { lcsFirmwareTableFirmsafeEntry 4 }

-- {COLUMN} 310.3.2.1.5
lcsFirmwareTableFirmsafeEntrySize OBJECT-TYPE
    SYNTAX     INTEGER (0..2147483647)
    MAX-ACCESS read-only
    STATUS     current
    DESCRIPTION
        "-- empty --"
    ::= { lcsFirmwareTableFirmsafeEntry 5 }

-- {COLUMN} 310.3.2.1.6
lcsFirmwareTableFirmsafeEntryIndex OBJECT-TYPE
    SYNTAX     INTEGER (0..2147483647)
    MAX-ACCESS read-only
    STATUS     current
    DESCRIPTION
        "-- empty --"
    ::= { lcsFirmwareTableFirmsafeEntry 6 }

-- {SCALAR} 310.3.3
lcsFirmwareModeFirmsafe OBJECT-TYPE
    SYNTAX     INTEGER
      {
        eImmediate (0),
        eLogin (1),
        eManual (2)
      }
    MAX-ACCESS read-only
    STATUS     current
    DESCRIPTION
        "-- empty --"
    ::= { lcsFirmware 3 }

-- {SCALAR} 310.3.4
lcsFirmwareTimeoutFirmsafe OBJECT-TYPE
    SYNTAX     INTEGER (0..65535)
    MAX-ACCESS read-only
    STATUS     current
    DESCRIPTION
        "-- empty --"
    ::= { lcsFirmware 4 }

-- {SCALAR} 310.3.7
lcsFirmwareFeatureWord OBJECT-TYPE
    SYNTAX     DisplayString (SIZE(0..34))
    MAX-ACCESS read-only
    STATUS     current
    DESCRIPTION
        "-- empty --"
    ::= { lcsFirmware 7 }

-- {OID} 310.4
lcsOther OBJECT IDENTIFIER ::= { lancom-l310 4 }

-- {OID} 310.4.1
lcsOtherManualDialing OBJECT IDENTIFIER ::= { lcsOther 1 }

-- {SCALAR} 310.4.1.1
lcsOtherManualDialingConnect OBJECT-TYPE
    SYNTAX     DisplayString
    MAX-ACCESS read-write
    STATUS     current
    DESCRIPTION
        "-- empty --"
    ::= { lcsOtherManualDialing 1 }

-- {SCALAR} 310.4.1.2
lcsOtherManualDialingDisconnect OBJECT-TYPE
    SYNTAX     DisplayString
    MAX-ACCESS read-write
    STATUS     current
    DESCRIPTION
        "-- empty --"
    ::= { lcsOtherManualDialing 2 }

-- {SCALAR} 310.4.2
lcsOtherBootSystem OBJECT-TYPE
    SYNTAX     DisplayString
    MAX-ACCESS read-write
    STATUS     current
    DESCRIPTION
        "-- empty --"
    ::= { lcsOther 2 }

-- {SCALAR} 310.4.5
lcsOtherColdBoot OBJECT-TYPE
    SYNTAX     DisplayString
    MAX-ACCESS read-write
    STATUS     current
    DESCRIPTION
        "-- empty --"
    ::= { lcsOther 5 }

-- notifications
-- {OID} 310.0
lcsTrapGrp OBJECT IDENTIFIER ::= { lancom-l310 0 }

-- {OID} 310.0.0
lcsTraps OBJECT IDENTIFIER ::= { lcsTrapGrp 0 }

-- {NOTIFICATION} 310.0.0.1
lcsTrapsStatChan NOTIFICATION-TYPE
    OBJECTS {
        sysDescr,
        sysName,
        lcsStatusSnmpEventEntryCount,
        lcsStatusWanConnections,
        lcsStatusChannelEntryState,
        lcsStatusChannelEntryApp,
        lcsStatusChannelEntryConnector,
        lcsStatusChannelEntryCause,
        lcsStatusChannelEntryNumber,
        lcsStatusChannelEntrySubaddress,
        lcsStatusChannelEntryCharge,
        lcsStatusChannelEntryExtra,
        lcsStatusChannelEntryConnTime,
        lcsStatusChannelEntryConnStart,
        lcsStatusChannelEntryIsdnDisplay,
        lcsStatusChannelEntryPhChan,
        lcsStatusChannelEntryPptpConns,
        lcsStatusChannelEntryVpnConns
    }
    STATUS     current
    DESCRIPTION
        "WAN connection status"
    ::= { lcsTraps 1 }

-- {NOTIFICATION} 310.0.0.4
lcsTrapsFwUplStart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Firmware upload was started"
    ::= { lcsTraps 4 }

-- {NOTIFICATION} 310.0.0.5
lcsTrapsUplsucc NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "Firmware or configuration upload successful"
    ::= { lcsTraps 5 }

-- {NOTIFICATION} 310.0.0.6
lcsTrapsUplfailto NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload the firmware or configuration failed: maximum time was exceeded"
    ::= { lcsTraps 6 }

-- {NOTIFICATION} 310.0.0.7
lcsTrapsUplfailincl NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload the firmware or configuration failed: incomplete configuration"
    ::= { lcsTraps 7 }

-- {NOTIFICATION} 310.0.0.8
lcsTrapsUplfailbaddev NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload the firmware or configuration failed: wrong device"
    ::= { lcsTraps 8 }

-- {NOTIFICATION} 310.0.0.9
lcsTrapsLogin NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Login to configuration successful"
    ::= { lcsTraps 9 }

-- {NOTIFICATION} 310.0.0.10
lcsTrapsLogout NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Logout from configuration was successful"
    ::= { lcsTraps 10 }

-- {NOTIFICATION} 310.0.0.11
lcsTrapsCnfuplstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Configuration upload was started"
    ::= { lcsTraps 11 }

-- {NOTIFICATION} 310.0.0.12
lcsTrapsCnfdnlstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Configuration download was started"
    ::= { lcsTraps 12 }

-- {NOTIFICATION} 310.0.0.13
lcsTrapsCnfdnlsucc NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "Configuration download successful"
    ::= { lcsTraps 13 }

-- {NOTIFICATION} 310.0.0.14
lcsTrapsBssscan NOTIFICATION-TYPE
    OBJECTS {
        sysDescr,
        sysName,
        lcsStatusSnmpEventEntryCount,
        lcsStatusWlanIfcsEntryIfc
    }
    STATUS     current
    DESCRIPTION
        "-- empty --"
    ::= { lcsTraps 14 }

-- {NOTIFICATION} 310.0.0.15
lcsTrapsBssstart NOTIFICATION-TYPE
    OBJECTS {
        sysDescr,
        sysName,
        lcsStatusSnmpEventEntryCount,
        lcsStatusWlanWlanParameterEntryIfc,
        lcsStatusWlanNetworksEntryBssid
    }
    STATUS     current
    DESCRIPTION
        "-- empty --"
    ::= { lcsTraps 15 }

-- {NOTIFICATION} 310.0.0.16
lcsTrapsBssjoin NOTIFICATION-TYPE
    OBJECTS {
        sysDescr,
        sysName,
        lcsStatusSnmpEventEntryCount,
        lcsStatusWlanWlanParameterEntryIfc,
        lcsStatusWlanNetworksEntryBssid
    }
    STATUS     current
    DESCRIPTION
        "-- empty --"
    ::= { lcsTraps 16 }

-- {NOTIFICATION} 310.0.0.17
lcsTrapsAuthstation NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 17 }

-- {NOTIFICATION} 310.0.0.18
lcsTrapsDeauthstation NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 18 }

-- {NOTIFICATION} 310.0.0.19
lcsTrapsAssstation NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 19 }

-- {NOTIFICATION} 310.0.0.20
lcsTrapsReassstation NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 20 }

-- {NOTIFICATION} 310.0.0.21
lcsTrapsDisassstation NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 21 }

-- {NOTIFICATION} 310.0.0.22
lcsTrapsAssrej NOTIFICATION-TYPE
    OBJECTS {
        sysDescr,
        sysName,
        lcsStatusSnmpEventEntryCount,
        lcsStatusWlanLogTableEntryAddress
    }
    STATUS     current
    DESCRIPTION
        "-- empty --"
    ::= { lcsTraps 22 }

-- {NOTIFICATION} 310.0.0.25
lcsTrapsCardhung NOTIFICATION-TYPE
    OBJECTS {
        sysDescr,
        sysName,
        lcsStatusSnmpEventEntryCount,
        lcsStatusWlanIfcsEntryIfc
    }
    STATUS     current
    DESCRIPTION
        "-- empty --"
    ::= { lcsTraps 25 }

-- {NOTIFICATION} 310.0.0.26
lcsTrapsIpfwflt NOTIFICATION-TYPE
    OBJECTS {
        sysDescr,
        sysName,
        lcsStatusSnmpEventEntryCount,
        lcsStatusIpRouterLogTableEntrySystemTime,
        lcsStatusIpRouterLogTableEntrySrcAddress,
        lcsStatusIpRouterLogTableEntryDstAddress,
        lcsStatusIpRouterLogTableEntryProt,
        lcsStatusIpRouterLogTableEntrySrcPort,
        lcsStatusIpRouterLogTableEntryDstPort,
        lcsStatusIpRouterLogTableEntryFilterRule,
        lcsStatusIpRouterLogTableEntryLimit,
        lcsStatusIpRouterLogTableEntryThreshold,
        lcsStatusIpRouterLogTableEntryAction
    }
    STATUS     current
    DESCRIPTION
        "Information about a firewall event"
    ::= { lcsTraps 26 }

-- {NOTIFICATION} 310.0.0.28
lcsTrapsPptpconn NOTIFICATION-TYPE
    OBJECTS {
        sysDescr,
        sysName,
        lcsStatusSnmpEventEntryCount,
        lcsStatusPptpTunnel,
        lcsStatusPptpConnectionsEntryChannel,
        lcsStatusPptpConnectionsEntryState,
        lcsStatusPptpConnectionsEntryMode,
        lcsStatusPptpConnectionsEntryShTime,
        lcsStatusPptpConnectionsEntryPhysConnection,
        lcsStatusPptpConnectionsEntryPeerAddress,
        lcsStatusPptpConnectionsEntryIpAddress,
        lcsStatusPptpConnectionsEntryDnsDefault,
        lcsStatusPptpConnectionsEntryNbnsDefault,
        lcsStatusPptpConnectionsEntryLastError,
        lcsStatusPptpConnectionsEntryDnsBackup,
        lcsStatusPptpConnectionsEntryNbnsBackup
    }
    STATUS     current
    DESCRIPTION
        "Status of PPTP connection"
    ::= { lcsTraps 28 }

-- {NOTIFICATION} 310.0.0.29
lcsTrapsErrlogin NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Error during login to configuration"
    ::= { lcsTraps 29 }

-- {NOTIFICATION} 310.0.0.33
lcsTrapsKeyhandshakeTimeout NOTIFICATION-TYPE
    OBJECTS {
        sysDescr,
        sysName,
        lcsStatusSnmpEventEntryCount
    }
    STATUS     current
    DESCRIPTION
        "-- empty --"
    ::= { lcsTraps 33 }

-- {NOTIFICATION} 310.0.0.35
lcsTrapsSupervision NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 35 }

-- {NOTIFICATION} 310.0.0.39
lcsTrapsPppoesconn NOTIFICATION-TYPE
    OBJECTS {
        sysDescr,
        sysName,
        lcsStatusSnmpEventEntryCount,
        lcsStatusPppoeServerNumConnections,
        lcsStatusPppoeServerConnectionsEntryChannel,
        lcsStatusPppoeServerConnectionsEntryMacAddress,
        lcsStatusPppoeServerConnectionsEntryState,
        lcsStatusPppoeServerConnectionsEntryLastError,
        lcsStatusPppoeServerConnectionsEntryShTime,
        lcsStatusPppoeServerConnectionsEntryPeerAddress
    }
    STATUS     current
    DESCRIPTION
        "-- empty --"
    ::= { lcsTraps 39 }

-- {NOTIFICATION} 310.0.0.41
lcsTrapsVrrp NOTIFICATION-TYPE
    OBJECTS {
        sysDescr,
        sysName,
        lcsStatusSnmpEventEntryCount,
        lcsStatusIpRouterVrrpEventLogEntrySystemTime,
        lcsStatusIpRouterVrrpEventLogEntrySrcAddress,
        lcsStatusIpRouterVrrpEventLogEntryVrid,
        lcsStatusIpRouterVrrpEventLogEntryEvent,
        lcsStatusIpRouterVrrpEventLogEntryInfo
    }
    STATUS     current
    DESCRIPTION
        "-- empty --"
    ::= { lcsTraps 41 }

-- {NOTIFICATION} 310.0.0.42
lcsTrapsExceirp NOTIFICATION-TYPE
    OBJECTS {
        sysDescr,
        sysName,
        lcsStatusSnmpEventEntryCount,
        lcsStatusWlanWlanParameterEntryIfc,
        lcsStatusWlanWlanParameterEntryEirp
    }
    STATUS     current
    DESCRIPTION
        "-- empty --"
    ::= { lcsTraps 42 }

-- {NOTIFICATION} 310.0.0.46
lcsTrapsIdleTimeout NOTIFICATION-TYPE
    OBJECTS {
        sysDescr,
        sysName,
        lcsStatusSnmpEventEntryCount
    }
    STATUS     current
    DESCRIPTION
        "-- empty --"
    ::= { lcsTraps 46 }

-- {NOTIFICATION} 310.0.0.47
lcsTrapsAdminDeassoc NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 47 }

-- {NOTIFICATION} 310.0.0.48
lcsTrapsWlanovertemp NOTIFICATION-TYPE
    OBJECTS {
        sysDescr,
        sysName,
        lcsStatusSnmpEventEntryCount,
        lcsStatusHardwareInfoTemperatureDegrees
    }
    STATUS     current
    DESCRIPTION
        "-- empty --"
    ::= { lcsTraps 48 }

-- {NOTIFICATION} 310.0.0.49
lcsTrapsWlanovertempend NOTIFICATION-TYPE
    OBJECTS {
        sysDescr,
        sysName,
        lcsStatusSnmpEventEntryCount,
        lcsStatusHardwareInfoTemperatureDegrees
    }
    STATUS     current
    DESCRIPTION
        "-- empty --"
    ::= { lcsTraps 49 }

-- {NOTIFICATION} 310.0.0.50
lcsTrapsWlanundertemp NOTIFICATION-TYPE
    OBJECTS {
        sysDescr,
        sysName,
        lcsStatusSnmpEventEntryCount,
        lcsStatusHardwareInfoTemperatureDegrees
    }
    STATUS     current
    DESCRIPTION
        "-- empty --"
    ::= { lcsTraps 50 }

-- {NOTIFICATION} 310.0.0.51
lcsTrapsWlanundertempend NOTIFICATION-TYPE
    OBJECTS {
        sysDescr,
        sysName,
        lcsStatusSnmpEventEntryCount,
        lcsStatusHardwareInfoTemperatureDegrees
    }
    STATUS     current
    DESCRIPTION
        "-- empty --"
    ::= { lcsTraps 51 }

-- {NOTIFICATION} 310.0.0.52
lcsTrapsMacchkfail NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 52 }

-- {NOTIFICATION} 310.0.0.53
lcsTrapsRoamed NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 53 }

-- {NOTIFICATION} 310.0.0.54
lcsTrapsConnected NOTIFICATION-TYPE
    OBJECTS {
        sysDescr,
        sysName,
        lcsStatusSnmpEventEntryCount,
        lcsStatusWlanStationTableEntryMacAddress,
        lcsStatusWlanStationTableEntryIdentification
    }
    STATUS     current
    DESCRIPTION
        "-- empty --"
    ::= { lcsTraps 54 }

-- {NOTIFICATION} 310.0.0.55
lcsTrapsClLostconn NOTIFICATION-TYPE
    OBJECTS {
        sysDescr,
        sysName,
        lcsStatusSnmpEventEntryCount,
        lcsStatusWlanClientIfcsEntryIfc,
        lcsStatusWlanClientIfcsEntryState
    }
    STATUS     current
    DESCRIPTION
        "-- empty --"
    ::= { lcsTraps 55 }

-- {NOTIFICATION} 310.0.0.56
lcsTrapsClAuthfail NOTIFICATION-TYPE
    OBJECTS {
        sysDescr,
        sysName,
        lcsStatusSnmpEventEntryCount,
        lcsStatusWlanClientIfcsEntryIfc,
        lcsStatusWlanClientIfcsEntryState
    }
    STATUS     current
    DESCRIPTION
        "-- empty --"
    ::= { lcsTraps 56 }

-- {NOTIFICATION} 310.0.0.57
lcsTrapsClAssocfail NOTIFICATION-TYPE
    OBJECTS {
        sysDescr,
        sysName,
        lcsStatusSnmpEventEntryCount,
        lcsStatusWlanClientIfcsEntryIfc,
        lcsStatusWlanClientIfcsEntryState
    }
    STATUS     current
    DESCRIPTION
        "-- empty --"
    ::= { lcsTraps 57 }

-- {NOTIFICATION} 310.0.0.58
lcsTrapsClConnected NOTIFICATION-TYPE
    OBJECTS {
        sysDescr,
        sysName,
        lcsStatusSnmpEventEntryCount,
        lcsStatusWlanClientIfcsEntryIfc,
        lcsStatusWlanClientIfcsEntryState
    }
    STATUS     current
    DESCRIPTION
        "-- empty --"
    ::= { lcsTraps 58 }

-- {NOTIFICATION} 310.0.0.59
lcsTrapsCl8021xFail NOTIFICATION-TYPE
    OBJECTS {
        sysDescr,
        sysName,
        lcsStatusSnmpEventEntryCount,
        lcsStatusWlanClientIfcsEntryIfc,
        lcsStatusWlanClientIfcsEntryState
    }
    STATUS     current
    DESCRIPTION
        "-- empty --"
    ::= { lcsTraps 59 }

-- {NOTIFICATION} 310.0.0.77
lcsTrapsLicensemgtexpire NOTIFICATION-TYPE
    OBJECTS {
        sysDescr,
        sysName,
        lcsStatusSnmpEventEntryCount,
        lcsStatusConfigFeaturesEntryFeature,
        lcsStatusConfigFeaturesEntryExpires,
        lcsStatusConfigFeaturesEntryExpire,
        lcsStatusConfigFeaturesEntryState,
        lcsStatusConfigFeaturesEntryIndex,
        lcsStatusConfigFeaturesEntryCount
    }
    STATUS     current
    DESCRIPTION
        "-- empty --"
    ::= { lcsTraps 77 }

-- {NOTIFICATION} 310.0.0.79
lcsTrapsScrptuplstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "-- empty --"
    ::= { lcsTraps 79 }

-- {NOTIFICATION} 310.0.0.80
lcsTrapsScrptdnlstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "-- empty --"
    ::= { lcsTraps 80 }

-- {NOTIFICATION} 310.0.0.1000
lcsTrapsSpgtreePortstatchg NOTIFICATION-TYPE
    OBJECTS {
        sysDescr,
        sysName,
        lcsStatusSnmpEventEntryCount,
        lcsStatusLanBridgeSpanningTreePortTableEntryDescription,
        lcsStatusLanBridgeSpanningTreePortTableEntryState,
        lcsStatusLanBridgeSpanningTreePortTableEntryPathCost
    }
    STATUS     current
    DESCRIPTION
        "-- empty --"
    ::= { lcsTraps 1000 }

-- {NOTIFICATION} 310.0.0.1001
lcsTrapsSpgtreeRstpstatchg NOTIFICATION-TYPE
    OBJECTS {
        sysDescr,
        sysName,
        lcsStatusSnmpEventEntryCount,
        lcsStatusLanBridgeSpanningTreeRstpPortTableEntryDescription,
        lcsStatusLanBridgeSpanningTreeRstpPortTableEntryRole,
        lcsStatusLanBridgeSpanningTreeRstpPortTableEntryLearning,
        lcsStatusLanBridgeSpanningTreeRstpPortTableEntryForwarding,
        lcsStatusLanBridgeSpanningTreeRstpPortTableEntryEdgePort,
        lcsStatusLanBridgeSpanningTreeRstpPortTableEntryProtocolVersion,
        lcsStatusLanBridgeSpanningTreeRstpPortTableEntryPathCost
    }
    STATUS     current
    DESCRIPTION
        "-- empty --"
    ::= { lcsTraps 1001 }

-- {NOTIFICATION} 310.0.0.1002
lcsTrapsSpgtreeRootportchg NOTIFICATION-TYPE
    OBJECTS {
        sysDescr,
        sysName,
        lcsStatusSnmpEventEntryCount,
        lcsStatusLanBridgeSpanningTreeRootBridge,
        lcsStatusLanBridgeSpanningTreeRootPort,
        lcsStatusLanBridgeSpanningTreeRootPathCost
    }
    STATUS     current
    DESCRIPTION
        "-- empty --"
    ::= { lcsTraps 1002 }

-- {NOTIFICATION} 310.0.0.2000
lcsTrapsHttpTunnelOpen NOTIFICATION-TYPE
    OBJECTS {
        sysDescr,
        sysName,
        lcsStatusSnmpEventEntryCount,
        lcsStatusTcpIpHttpActiveTunnelsEntryIndex,
        lcsStatusTcpIpHttpActiveTunnelsEntryRemoteAddress,
        lcsStatusTcpIpHttpActiveTunnelsEntryRemotePort,
        lcsStatusTcpIpHttpActiveTunnelsEntryLocalHost,
        lcsStatusTcpIpHttpActiveTunnelsEntryLocalPort,
        lcsStatusTcpIpHttpActiveTunnelsEntryIdleTime,
        lcsStatusTcpIpHttpActiveTunnelsEntryLocalRtgTag
    }
    STATUS     current
    DESCRIPTION
        "HTTP tunnel opened successful"
    ::= { lcsTraps 2000 }

-- {NOTIFICATION} 310.0.0.2001
lcsTrapsHttpTunnelClose NOTIFICATION-TYPE
    OBJECTS {
        sysDescr,
        sysName,
        lcsStatusSnmpEventEntryCount,
        lcsStatusTcpIpHttpActiveTunnelsEntryIndex
    }
    STATUS     current
    DESCRIPTION
        "HTTP tunnel closed successful"
    ::= { lcsTraps 2001 }

-- {NOTIFICATION} 310.0.0.3000
lcsTrapsLanauthuseradd NOTIFICATION-TYPE
    OBJECTS {
        sysDescr,
        sysName,
        lcsStatusSnmpEventEntryCount,
        lcsSetupPublicSpotModuleUserTableEntryName,
        lcsSetupPublicSpotModuleUserTableEntryComment
    }
    STATUS     current
    DESCRIPTION
        "-- empty --"
    ::= { lcsTraps 3000 }

-- {NOTIFICATION} 310.0.0.3001
lcsTrapsLanauthuserdel NOTIFICATION-TYPE
    OBJECTS {
        sysDescr,
        sysName,
        lcsStatusSnmpEventEntryCount,
        lcsSetupPublicSpotModuleUserTableEntryName,
        lcsSetupPublicSpotModuleUserTableEntryComment
    }
    STATUS     current
    DESCRIPTION
        "-- empty --"
    ::= { lcsTraps 3001 }

-- {NOTIFICATION} 310.0.0.3002
lcsTrapsLanauthsessionstart NOTIFICATION-TYPE
    OBJECTS {
        sysDescr,
        sysName,
        lcsStatusSnmpEventEntryCount,
        lcsStatusPublicSpotStationTableEntryMacAddress,
        lcsStatusPublicSpotStationTableEntryName,
        lcsStatusPublicSpotStationTableEntrySessionId
    }
    STATUS     current
    DESCRIPTION
        "-- empty --"
    ::= { lcsTraps 3002 }

-- {NOTIFICATION} 310.0.0.3003
lcsTrapsLanauthsessionend NOTIFICATION-TYPE
    OBJECTS {
        sysDescr,
        sysName,
        lcsStatusSnmpEventEntryCount,
        lcsStatusPublicSpotStationTableEntryMacAddress,
        lcsStatusPublicSpotStationTableEntryName,
        lcsStatusPublicSpotStationTableEntrySessionId,
        lcsStatusPublicSpotStationTableEntryTxBytes,
        lcsStatusPublicSpotStationTableEntryRxBytes,
        lcsStatusPublicSpotStationTableEntryTxPackets,
        lcsStatusPublicSpotStationTableEntryRxPackets,
        lcsStatusPublicSpotStationTableEntryLoginTime
    }
    STATUS     current
    DESCRIPTION
        "-- empty --"
    ::= { lcsTraps 3003 }

-- {NOTIFICATION} 310.0.0.4000
lcsTrapsTempmonovertemp NOTIFICATION-TYPE
    OBJECTS {
        sysDescr,
        sysName,
        lcsStatusSnmpEventEntryCount,
        lcsStatusHardwareInfoTemperatureDegrees
    }
    STATUS     current
    DESCRIPTION
        "Device temperature exceeds the upper tempreature limit"
    ::= { lcsTraps 4000 }

-- {NOTIFICATION} 310.0.0.4001
lcsTrapsTempmonnoovertemp NOTIFICATION-TYPE
    OBJECTS {
        sysDescr,
        sysName,
        lcsStatusSnmpEventEntryCount,
        lcsStatusHardwareInfoTemperatureDegrees
    }
    STATUS     current
    DESCRIPTION
        "Device temperature falls below the upper temperature limit and is in the normal operating range again"
    ::= { lcsTraps 4001 }

-- {NOTIFICATION} 310.0.0.4002
lcsTrapsTempmonundertemp NOTIFICATION-TYPE
    OBJECTS {
        sysDescr,
        sysName,
        lcsStatusSnmpEventEntryCount,
        lcsStatusHardwareInfoTemperatureDegrees
    }
    STATUS     current
    DESCRIPTION
        "Device temperature under-runs the lower temperature limit"
    ::= { lcsTraps 4002 }

-- {NOTIFICATION} 310.0.0.4003
lcsTrapsTempmonnoundertemp NOTIFICATION-TYPE
    OBJECTS {
        sysDescr,
        sysName,
        lcsStatusSnmpEventEntryCount,
        lcsStatusHardwareInfoTemperatureDegrees
    }
    STATUS     current
    DESCRIPTION
        "Device temperature rises above the lower temperature limit and is in the normal operating range again"
    ::= { lcsTraps 4003 }

-- {NOTIFICATION} 310.0.0.5002
lcsTrapsLanOvertempThrottle NOTIFICATION-TYPE
    OBJECTS {
        sysDescr,
        sysName,
        lcsStatusSnmpEventEntryCount
    }
    STATUS     current
    DESCRIPTION
        "Throttling of LAN Speed due to temperature exceedance active"
    ::= { lcsTraps 5002 }

-- {NOTIFICATION} 310.0.0.5003
lcsTrapsLanOvertempThrottleEnd NOTIFICATION-TYPE
    OBJECTS {
        sysDescr,
        sysName,
        lcsStatusSnmpEventEntryCount
    }
    STATUS     current
    DESCRIPTION
        "Throttling of LAN Speed due to temperature exceedance stopped"
    ::= { lcsTraps 5003 }

-- {NOTIFICATION} 310.0.0.5004
lcsTrapsLanOvertempThrottleRecommend NOTIFICATION-TYPE
    OBJECTS {
        sysDescr,
        sysName,
        lcsStatusSnmpEventEntryCount
    }
    STATUS     current
    DESCRIPTION
        "Throttling of LAN Speed due to temperature exceedance recommended"
    ::= { lcsTraps 5004 }

-- {NOTIFICATION} 310.0.0.6100
lcsTrapsWlanConfadaptRadiochannel NOTIFICATION-TYPE
    OBJECTS {
        sysDescr,
        sysName,
        lcsStatusSnmpEventEntryCount
    }
    STATUS     current
    DESCRIPTION
        "-- empty --"
    ::= { lcsTraps 6100 }

-- {NOTIFICATION} 310.0.0.6101
lcsTrapsWlanConfadaptRadiomode NOTIFICATION-TYPE
    OBJECTS {
        sysDescr,
        sysName,
        lcsStatusSnmpEventEntryCount,
        lcsStatusWlanNetworksEntryRadioMode
    }
    STATUS     current
    DESCRIPTION
        "-- empty --"
    ::= { lcsTraps 6101 }

-- {NOTIFICATION} 310.0.0.6102
lcsTrapsWlanConfadaptBasicRate NOTIFICATION-TYPE
    OBJECTS {
        sysDescr,
        sysName,
        lcsStatusSnmpEventEntryCount
    }
    STATUS     current
    DESCRIPTION
        "-- empty --"
    ::= { lcsTraps 6102 }

-- {NOTIFICATION} 310.0.0.6103
lcsTrapsWlanConfadaptEapolRate NOTIFICATION-TYPE
    OBJECTS {
        sysDescr,
        sysName,
        lcsStatusSnmpEventEntryCount
    }
    STATUS     current
    DESCRIPTION
        "-- empty --"
    ::= { lcsTraps 6103 }

-- {NOTIFICATION} 310.0.0.6104
lcsTrapsWlanConfadaptEncryption NOTIFICATION-TYPE
    OBJECTS {
        sysDescr,
        sysName,
        lcsStatusSnmpEventEntryCount
    }
    STATUS     current
    DESCRIPTION
        "-- empty --"
    ::= { lcsTraps 6104 }

-- {NOTIFICATION} 310.0.0.6200
lcsTrapsWlanAlarmP2pSignal NOTIFICATION-TYPE
    OBJECTS {
        sysDescr,
        sysName,
        lcsStatusSnmpEventEntryCount,
        lcsStatusWlanInterpointsAccesspointListEntryAlarmState,
        lcsStatusWlanInterpointsAccesspointListEntryRxPhySignal,
        lcsStatusWlanInterpointsAccesspointListEntryLinkPhySignal
    }
    STATUS     current
    DESCRIPTION
        "-- empty --"
    ::= { lcsTraps 6200 }

-- {NOTIFICATION} 310.0.0.6201
lcsTrapsWlanAlarmP2pTxtotretries NOTIFICATION-TYPE
    OBJECTS {
        sysDescr,
        sysName,
        lcsStatusSnmpEventEntryCount,
        lcsStatusWlanInterpointsAccesspointListEntryAlarmState,
        lcsStatusWlanInterpointsAccesspointListEntryTxPackets,
        lcsStatusWlanInterpointsAccesspointListEntryTotalRetries
    }
    STATUS     current
    DESCRIPTION
        "-- empty --"
    ::= { lcsTraps 6201 }

-- {NOTIFICATION} 310.0.0.6202
lcsTrapsWlanAlarmP2pTxerrors NOTIFICATION-TYPE
    OBJECTS {
        sysDescr,
        sysName,
        lcsStatusSnmpEventEntryCount,
        lcsStatusWlanInterpointsAccesspointListEntryAlarmState,
        lcsStatusWlanInterpointsAccesspointListEntryTxPackets,
        lcsStatusWlanInterpointsAccesspointListEntryTxErrors
    }
    STATUS     current
    DESCRIPTION
        "-- empty --"
    ::= { lcsTraps 6202 }

-- {NOTIFICATION} 310.0.0.6203
lcsTrapsWlanAlarmNetwSignal NOTIFICATION-TYPE
    OBJECTS {
        sysDescr,
        sysName,
        lcsStatusSnmpEventEntryCount,
        lcsStatusWlanNetworksEntryAlarmState
    }
    STATUS     current
    DESCRIPTION
        "-- empty --"
    ::= { lcsTraps 6203 }

-- {NOTIFICATION} 310.0.0.6204
lcsTrapsWlanAlarmNetwTxtotretries NOTIFICATION-TYPE
    OBJECTS {
        sysDescr,
        sysName,
        lcsStatusSnmpEventEntryCount,
        lcsStatusWlanNetworksEntryAlarmState
    }
    STATUS     current
    DESCRIPTION
        "-- empty --"
    ::= { lcsTraps 6204 }

-- {NOTIFICATION} 310.0.0.6205
lcsTrapsWlanAlarmNetwTxerrors NOTIFICATION-TYPE
    OBJECTS {
        sysDescr,
        sysName,
        lcsStatusSnmpEventEntryCount,
        lcsStatusWlanNetworksEntryAlarmState
    }
    STATUS     current
    DESCRIPTION
        "-- empty --"
    ::= { lcsTraps 6205 }

-- {NOTIFICATION} 310.0.0.6206
lcsTrapsWlanAlarmClientSignal NOTIFICATION-TYPE
    OBJECTS {
        sysDescr,
        sysName,
        lcsStatusSnmpEventEntryCount,
        lcsStatusWlanClientIfcsEntryAlarmState,
        lcsStatusWlanClientIfcsEntryPhySignal,
        lcsStatusWlanClientIfcsEntryLinkPhySignal
    }
    STATUS     current
    DESCRIPTION
        "-- empty --"
    ::= { lcsTraps 6206 }

-- {NOTIFICATION} 310.0.0.6207
lcsTrapsWlanAlarmClientTxtotretries NOTIFICATION-TYPE
    OBJECTS {
        sysDescr,
        sysName,
        lcsStatusSnmpEventEntryCount,
        lcsStatusWlanClientIfcsEntryAlarmState,
        lcsStatusWlanClientIfcsEntryTxPackets,
        lcsStatusWlanClientIfcsEntryTotalRetries
    }
    STATUS     current
    DESCRIPTION
        "-- empty --"
    ::= { lcsTraps 6207 }

-- {NOTIFICATION} 310.0.0.6208
lcsTrapsWlanAlarmClientTxerrors NOTIFICATION-TYPE
    OBJECTS {
        sysDescr,
        sysName,
        lcsStatusSnmpEventEntryCount,
        lcsStatusWlanClientIfcsEntryAlarmState,
        lcsStatusWlanClientIfcsEntryTxPackets,
        lcsStatusWlanClientIfcsEntryTotalRetries
    }
    STATUS     current
    DESCRIPTION
        "-- empty --"
    ::= { lcsTraps 6208 }

-- {NOTIFICATION} 310.0.0.6300
lcsTrapsWlanDfsAllblocked NOTIFICATION-TYPE
    OBJECTS {
        sysDescr,
        sysName,
        lcsStatusSnmpEventEntryCount
    }
    STATUS     current
    DESCRIPTION
        "-- empty --"
    ::= { lcsTraps 6300 }

-- {NOTIFICATION} 310.0.0.7000
lcsTrapsUplinvversion NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "-- empty --"
    ::= { lcsTraps 7000 }

-- {NOTIFICATION} 310.0.0.7001
lcsTrapsUplfileexists NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "-- empty --"
    ::= { lcsTraps 7001 }
END
