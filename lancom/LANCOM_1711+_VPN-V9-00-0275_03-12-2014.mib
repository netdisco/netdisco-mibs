LANCOM-1711-PLUS-MIB DEFINITIONS ::= BEGIN

IMPORTS
    sysDescr, sysName
        FROM RFC1213-MIB
    DisplayString
        FROM SNMPv2-TC
    MacAddress
        FROM SNMPv2-TC
    CounterBasedGauge64
        FROM HCNUM-TC
    enterprises, OBJECT-TYPE,
    MODULE-IDENTITY, IpAddress, Counter32, Gauge32, TimeTicks, Counter64, NOTIFICATION-TYPE
        FROM SNMPv2-SMI;

lancom-1711-plus MODULE-IDENTITY
    LAST-UPDATED "201412031819Z"
    ORGANIZATION "LANCOM Systems GmbH"
    CONTACT-INFO "www.lancom.de"
    DESCRIPTION "Management information base definitions"
    REVISION "201412031819Z"
    DESCRIPTION "Auto-Generated on Mar 12, 2018"
    ::= { enterprises lancom-systems(2356) adsl-systems(500) lan-router(2)  1712 }


-- {OID} 1712.1
lcsStatus OBJECT IDENTIFIER ::= { lancom-1711-plus 1 }

-- {SCALAR} 1712.1.18
lcsStatusCurrentTime OBJECT-TYPE
    SYNTAX     DisplayString
    MAX-ACCESS read-only
    STATUS     current
    DESCRIPTION
        "-- empty --"
    ::= { lcsStatus 18 }

-- {OID} 1712.1.68
lcsStatusBlockDevices OBJECT IDENTIFIER ::= { lcsStatus 68 }

-- {TABLE} 1712.1.68.1
lcsStatusBlockDevicesDeviceListTable OBJECT-TYPE
    SYNTAX     SEQUENCE OF LcsStatusBlockDevicesDeviceListEntry
    MAX-ACCESS not-accessible
    STATUS     current
    DESCRIPTION
        "-- empty --"
    ::= { lcsStatusBlockDevices 1 }

-- {ENTRY} 1712.1.68.1.1
lcsStatusBlockDevicesDeviceListEntry OBJECT-TYPE
    SYNTAX     LcsStatusBlockDevicesDeviceListEntry
    MAX-ACCESS not-accessible
    STATUS     current
    DESCRIPTION
        ""
    INDEX {
        lcsStatusBlockDevicesDeviceListEntryId,
        lcsStatusBlockDevicesDeviceListEntryPartition
    }
    ::= { lcsStatusBlockDevicesDeviceListTable 1 }

-- {SEQUENCE}
LcsStatusBlockDevicesDeviceListEntry ::= SEQUENCE {
    lcsStatusBlockDevicesDeviceListEntryId INTEGER,
    lcsStatusBlockDevicesDeviceListEntryPartition INTEGER,
    lcsStatusBlockDevicesDeviceListEntryType DisplayString,
    lcsStatusBlockDevicesDeviceListEntryBlocksize INTEGER,
    lcsStatusBlockDevicesDeviceListEntryFirstBlock INTEGER,
    lcsStatusBlockDevicesDeviceListEntryBlockcount INTEGER
}

-- {COLUMN} 1712.1.68.1.1.1
lcsStatusBlockDevicesDeviceListEntryId OBJECT-TYPE
    SYNTAX     INTEGER (0..2147483647)
    MAX-ACCESS read-only
    STATUS     current
    DESCRIPTION
        "-- empty --"
    ::= { lcsStatusBlockDevicesDeviceListEntry 1 }

-- {COLUMN} 1712.1.68.1.1.5
lcsStatusBlockDevicesDeviceListEntryPartition OBJECT-TYPE
    SYNTAX     INTEGER (0..2147483647)
    MAX-ACCESS read-only
    STATUS     current
    DESCRIPTION
        "-- empty --"
    ::= { lcsStatusBlockDevicesDeviceListEntry 5 }

-- {COLUMN} 1712.1.68.1.1.2
lcsStatusBlockDevicesDeviceListEntryType OBJECT-TYPE
    SYNTAX     DisplayString (SIZE(0..255))
    MAX-ACCESS read-only
    STATUS     current
    DESCRIPTION
        "-- empty --"
    ::= { lcsStatusBlockDevicesDeviceListEntry 2 }

-- {COLUMN} 1712.1.68.1.1.3
lcsStatusBlockDevicesDeviceListEntryBlocksize OBJECT-TYPE
    SYNTAX     INTEGER (0..2147483647)
    MAX-ACCESS read-only
    STATUS     current
    DESCRIPTION
        "-- empty --"
    ::= { lcsStatusBlockDevicesDeviceListEntry 3 }

-- {COLUMN} 1712.1.68.1.1.6
lcsStatusBlockDevicesDeviceListEntryFirstBlock OBJECT-TYPE
    SYNTAX     INTEGER (0..2147483647)
    MAX-ACCESS read-only
    STATUS     current
    DESCRIPTION
        "-- empty --"
    ::= { lcsStatusBlockDevicesDeviceListEntry 6 }

-- {COLUMN} 1712.1.68.1.1.4
lcsStatusBlockDevicesDeviceListEntryBlockcount OBJECT-TYPE
    SYNTAX     INTEGER (0..2147483647)
    MAX-ACCESS read-only
    STATUS     current
    DESCRIPTION
        "-- empty --"
    ::= { lcsStatusBlockDevicesDeviceListEntry 4 }

-- {OID} 1712.1.69
lcsStatusTacacsPlus OBJECT IDENTIFIER ::= { lcsStatus 69 }

-- {SCALAR} 1712.1.69.1
lcsStatusTacacsPlusAuthenticationErrors OBJECT-TYPE
    SYNTAX     Counter32
    MAX-ACCESS read-only
    STATUS     current
    DESCRIPTION
        "-- empty --"
    ::= { lcsStatusTacacsPlus 1 }

-- {SCALAR} 1712.1.69.2
lcsStatusTacacsPlusAuthorisationErrors OBJECT-TYPE
    SYNTAX     Counter32
    MAX-ACCESS read-only
    STATUS     current
    DESCRIPTION
        "-- empty --"
    ::= { lcsStatusTacacsPlus 2 }

-- {SCALAR} 1712.1.69.3
lcsStatusTacacsPlusDeleteValues OBJECT-TYPE
    SYNTAX     DisplayString
    MAX-ACCESS read-write
    STATUS     current
    DESCRIPTION
        "-- empty --"
    ::= { lcsStatusTacacsPlus 3 }

-- {SCALAR} 1712.1.2
lcsStatusOperatingTime OBJECT-TYPE
    SYNTAX     DisplayString
    MAX-ACCESS read-only
    STATUS     current
    DESCRIPTION
        "-- empty --"
    ::= { lcsStatus 2 }

-- {OID} 1712.1.54
lcsStatusUsb OBJECT IDENTIFIER ::= { lcsStatus 54 }

-- {TABLE} 1712.1.54.1
lcsStatusUsbDevicesTable OBJECT-TYPE
    SYNTAX     SEQUENCE OF LcsStatusUsbDevicesEntry
    MAX-ACCESS not-accessible
    STATUS     current
    DESCRIPTION
        "-- empty --"
    ::= { lcsStatusUsb 1 }

-- {ENTRY} 1712.1.54.1.1
lcsStatusUsbDevicesEntry OBJECT-TYPE
    SYNTAX     LcsStatusUsbDevicesEntry
    MAX-ACCESS not-accessible
    STATUS     current
    DESCRIPTION
        ""
    INDEX {
        lcsStatusUsbDevicesEntryBus,
        lcsStatusUsbDevicesEntryAddress
    }
    ::= { lcsStatusUsbDevicesTable 1 }

-- {SEQUENCE}
LcsStatusUsbDevicesEntry ::= SEQUENCE {
    lcsStatusUsbDevicesEntryBus DisplayString,
    lcsStatusUsbDevicesEntryAddress INTEGER,
    lcsStatusUsbDevicesEntryVendor DisplayString,
    lcsStatusUsbDevicesEntryVendorId INTEGER,
    lcsStatusUsbDevicesEntryProduct DisplayString,
    lcsStatusUsbDevicesEntryProductId INTEGER,
    lcsStatusUsbDevicesEntryDepth INTEGER,
    lcsStatusUsbDevicesEntrySpeed INTEGER,
    lcsStatusUsbDevicesEntryInterfaces INTEGER,
    lcsStatusUsbDevicesEntryPower INTEGER,
    lcsStatusUsbDevicesEntryDriver DisplayString,
    lcsStatusUsbDevicesEntryParent DisplayString
}

-- {COLUMN} 1712.1.54.1.1.1
lcsStatusUsbDevicesEntryBus OBJECT-TYPE
    SYNTAX     DisplayString (SIZE(0..255))
    MAX-ACCESS read-only
    STATUS     current
    DESCRIPTION
        "-- empty --"
    ::= { lcsStatusUsbDevicesEntry 1 }

-- {COLUMN} 1712.1.54.1.1.2
lcsStatusUsbDevicesEntryAddress OBJECT-TYPE
    SYNTAX     INTEGER (0..255)
    MAX-ACCESS read-only
    STATUS     current
    DESCRIPTION
        "-- empty --"
    ::= { lcsStatusUsbDevicesEntry 2 }

-- {COLUMN} 1712.1.54.1.1.3
lcsStatusUsbDevicesEntryVendor OBJECT-TYPE
    SYNTAX     DisplayString (SIZE(0..255))
    MAX-ACCESS read-only
    STATUS     current
    DESCRIPTION
        "-- empty --"
    ::= { lcsStatusUsbDevicesEntry 3 }

-- {COLUMN} 1712.1.54.1.1.4
lcsStatusUsbDevicesEntryVendorId OBJECT-TYPE
    SYNTAX     INTEGER (0..65535)
    MAX-ACCESS read-only
    STATUS     current
    DESCRIPTION
        "-- empty --"
    ::= { lcsStatusUsbDevicesEntry 4 }

-- {COLUMN} 1712.1.54.1.1.5
lcsStatusUsbDevicesEntryProduct OBJECT-TYPE
    SYNTAX     DisplayString (SIZE(0..255))
    MAX-ACCESS read-only
    STATUS     current
    DESCRIPTION
        "-- empty --"
    ::= { lcsStatusUsbDevicesEntry 5 }

-- {COLUMN} 1712.1.54.1.1.6
lcsStatusUsbDevicesEntryProductId OBJECT-TYPE
    SYNTAX     INTEGER (0..65535)
    MAX-ACCESS read-only
    STATUS     current
    DESCRIPTION
        "-- empty --"
    ::= { lcsStatusUsbDevicesEntry 6 }

-- {COLUMN} 1712.1.54.1.1.8
lcsStatusUsbDevicesEntryDepth OBJECT-TYPE
    SYNTAX     INTEGER (0..255)
    MAX-ACCESS read-only
    STATUS     current
    DESCRIPTION
        "-- empty --"
    ::= { lcsStatusUsbDevicesEntry 8 }

-- {COLUMN} 1712.1.54.1.1.9
lcsStatusUsbDevicesEntrySpeed OBJECT-TYPE
    SYNTAX     INTEGER (0..255)
    MAX-ACCESS read-only
    STATUS     current
    DESCRIPTION
        "-- empty --"
    ::= { lcsStatusUsbDevicesEntry 9 }

-- {COLUMN} 1712.1.54.1.1.10
lcsStatusUsbDevicesEntryInterfaces OBJECT-TYPE
    SYNTAX     INTEGER (0..255)
    MAX-ACCESS read-only
    STATUS     current
    DESCRIPTION
        "-- empty --"
    ::= { lcsStatusUsbDevicesEntry 10 }

-- {COLUMN} 1712.1.54.1.1.11
lcsStatusUsbDevicesEntryPower OBJECT-TYPE
    SYNTAX     INTEGER (0..2147483647)
    MAX-ACCESS read-only
    STATUS     current
    DESCRIPTION
        "-- empty --"
    ::= { lcsStatusUsbDevicesEntry 11 }

-- {COLUMN} 1712.1.54.1.1.12
lcsStatusUsbDevicesEntryDriver OBJECT-TYPE
    SYNTAX     DisplayString (SIZE(0..255))
    MAX-ACCESS read-only
    STATUS     current
    DESCRIPTION
        "-- empty --"
    ::= { lcsStatusUsbDevicesEntry 12 }

-- {COLUMN} 1712.1.54.1.1.13
lcsStatusUsbDevicesEntryParent OBJECT-TYPE
    SYNTAX     DisplayString (SIZE(0..255))
    MAX-ACCESS read-only
    STATUS     current
    DESCRIPTION
        "-- empty --"
    ::= { lcsStatusUsbDevicesEntry 13 }

-- {SCALAR} 1712.1.54.2
lcsStatusUsbReinit OBJECT-TYPE
    SYNTAX     DisplayString
    MAX-ACCESS read-write
    STATUS     current
    DESCRIPTION
        "-- empty --"
    ::= { lcsStatusUsb 2 }

-- {TABLE} 1712.1.54.3
lcsStatusUsbStatisticsTable OBJECT-TYPE
    SYNTAX     SEQUENCE OF LcsStatusUsbStatisticsEntry
    MAX-ACCESS not-accessible
    STATUS     current
    DESCRIPTION
        "-- empty --"
    ::= { lcsStatusUsb 3 }

-- {ENTRY} 1712.1.54.3.1
lcsStatusUsbStatisticsEntry OBJECT-TYPE
    SYNTAX     LcsStatusUsbStatisticsEntry
    MAX-ACCESS not-accessible
    STATUS     current
    DESCRIPTION
        ""
    INDEX {
        lcsStatusUsbStatisticsEntryBus
    }
    ::= { lcsStatusUsbStatisticsTable 1 }

-- {SEQUENCE}
LcsStatusUsbStatisticsEntry ::= SEQUENCE {
    lcsStatusUsbStatisticsEntryBus DisplayString,
    lcsStatusUsbStatisticsEntryProduct DisplayString,
    lcsStatusUsbStatisticsEntryTransactions INTEGER,
    lcsStatusUsbStatisticsEntryInRetransmissions INTEGER,
    lcsStatusUsbStatisticsEntryInBabbles INTEGER,
    lcsStatusUsbStatisticsEntryInBufferErrors INTEGER,
    lcsStatusUsbStatisticsEntryOutRetransmissions INTEGER,
    lcsStatusUsbStatisticsEntryOutBabbles INTEGER,
    lcsStatusUsbStatisticsEntryOutBufferErrors INTEGER
}

-- {COLUMN} 1712.1.54.3.1.1
lcsStatusUsbStatisticsEntryBus OBJECT-TYPE
    SYNTAX     DisplayString (SIZE(0..255))
    MAX-ACCESS read-only
    STATUS     current
    DESCRIPTION
        "-- empty --"
    ::= { lcsStatusUsbStatisticsEntry 1 }

-- {COLUMN} 1712.1.54.3.1.2
lcsStatusUsbStatisticsEntryProduct OBJECT-TYPE
    SYNTAX     DisplayString (SIZE(0..255))
    MAX-ACCESS read-only
    STATUS     current
    DESCRIPTION
        "-- empty --"
    ::= { lcsStatusUsbStatisticsEntry 2 }

-- {COLUMN} 1712.1.54.3.1.3
lcsStatusUsbStatisticsEntryTransactions OBJECT-TYPE
    SYNTAX     INTEGER (-2147483648..2147483647)
    MAX-ACCESS read-only
    STATUS     current
    DESCRIPTION
        "-- empty --"
    ::= { lcsStatusUsbStatisticsEntry 3 }

-- {COLUMN} 1712.1.54.3.1.10
lcsStatusUsbStatisticsEntryInRetransmissions OBJECT-TYPE
    SYNTAX     INTEGER (-2147483648..2147483647)
    MAX-ACCESS read-only
    STATUS     current
    DESCRIPTION
        "-- empty --"
    ::= { lcsStatusUsbStatisticsEntry 10 }

-- {COLUMN} 1712.1.54.3.1.11
lcsStatusUsbStatisticsEntryInBabbles OBJECT-TYPE
    SYNTAX     INTEGER (-2147483648..2147483647)
    MAX-ACCESS read-only
    STATUS     current
    DESCRIPTION
        "-- empty --"
    ::= { lcsStatusUsbStatisticsEntry 11 }

-- {COLUMN} 1712.1.54.3.1.12
lcsStatusUsbStatisticsEntryInBufferErrors OBJECT-TYPE
    SYNTAX     INTEGER (-2147483648..2147483647)
    MAX-ACCESS read-only
    STATUS     current
    DESCRIPTION
        "-- empty --"
    ::= { lcsStatusUsbStatisticsEntry 12 }

-- {COLUMN} 1712.1.54.3.1.20
lcsStatusUsbStatisticsEntryOutRetransmissions OBJECT-TYPE
    SYNTAX     INTEGER (-2147483648..2147483647)
    MAX-ACCESS read-only
    STATUS     current
    DESCRIPTION
        "-- empty --"
    ::= { lcsStatusUsbStatisticsEntry 20 }

-- {COLUMN} 1712.1.54.3.1.21
lcsStatusUsbStatisticsEntryOutBabbles OBJECT-TYPE
    SYNTAX     INTEGER (-2147483648..2147483647)
    MAX-ACCESS read-only
    STATUS     current
    DESCRIPTION
        "-- empty --"
    ::= { lcsStatusUsbStatisticsEntry 21 }

-- {COLUMN} 1712.1.54.3.1.22
lcsStatusUsbStatisticsEntryOutBufferErrors OBJECT-TYPE
    SYNTAX     INTEGER (-2147483648..2147483647)
    MAX-ACCESS read-only
    STATUS     current
    DESCRIPTION
        "-- empty --"
    ::= { lcsStatusUsbStatisticsEntry 22 }

-- {SCALAR} 1712.1.54.4
lcsStatusUsbClearStatistics OBJECT-TYPE
    SYNTAX     DisplayString
    MAX-ACCESS read-write
    STATUS     current
    DESCRIPTION
        "-- empty --"
    ::= { lcsStatusUsb 4 }

-- {SCALAR} 1712.1.54.5
lcsStatusUsbQueryHubStatus OBJECT-TYPE
    SYNTAX     DisplayString
    MAX-ACCESS read-write
    STATUS     current
    DESCRIPTION
        "-- empty --"
    ::= { lcsStatusUsb 5 }

-- {OID} 1712.1.4
lcsStatusWan OBJECT IDENTIFIER ::= { lcsStatus 4 }

-- {TABLE} 1712.1.4.1
lcsStatusWanByteTransportTable OBJECT-TYPE
    SYNTAX     SEQUENCE OF LcsStatusWanByteTransportEntry
    MAX-ACCESS not-accessible
    STATUS     current
    DESCRIPTION
        "-- empty --"
    ::= { lcsStatusWan 1 }

-- {ENTRY} 1712.1.4.1.1
lcsStatusWanByteTransportEntry OBJECT-TYPE
    SYNTAX     LcsStatusWanByteTransportEntry
    MAX-ACCESS not-accessible
    STATUS     current
    DESCRIPTION
        ""
    INDEX {
        lcsStatusWanByteTransportEntryIfc
    }
    ::= { lcsStatusWanByteTransportTable 1 }

-- {SEQUENCE}
LcsStatusWanByteTransportEntry ::= SEQUENCE {
    lcsStatusWanByteTransportEntryIfc INTEGER,
    lcsStatusWanByteTransportEntryCrxBytes Counter32,
    lcsStatusWanByteTransportEntryRxBytes Counter32,
    lcsStatusWanByteTransportEntryTxBytes Counter32,
    lcsStatusWanByteTransportEntryCtxBytes Counter32
}

-- {COLUMN} 1712.1.4.1.1.1
lcsStatusWanByteTransportEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusWanByteTransportEntry 1 }

-- {COLUMN} 1712.1.4.1.1.2
lcsStatusWanByteTransportEntryCrxBytes OBJECT-TYPE
    SYNTAX     Counter32
    MAX-ACCESS read-only
    STATUS     current
    DESCRIPTION
        "-- empty --"
    ::= { lcsStatusWanByteTransportEntry 2 }

-- {COLUMN} 1712.1.4.1.1.3
lcsStatusWanByteTransportEntryRxBytes OBJECT-TYPE
    SYNTAX     Counter32
    MAX-ACCESS read-only
    STATUS     current
    DESCRIPTION
        "-- empty --"
    ::= { lcsStatusWanByteTransportEntry 3 }

-- {COLUMN} 1712.1.4.1.1.4
lcsStatusWanByteTransportEntryTxBytes OBJECT-TYPE
    SYNTAX     Counter32
    MAX-ACCESS read-only
    STATUS     current
    DESCRIPTION
        "-- empty --"
    ::= { lcsStatusWanByteTransportEntry 4 }

-- {COLUMN} 1712.1.4.1.1.5
lcsStatusWanByteTransportEntryCtxBytes OBJECT-TYPE
    SYNTAX     Counter32
    MAX-ACCESS read-only
    STATUS     current
    DESCRIPTION
        "-- empty --"
    ::= { lcsStatusWanByteTransportEntry 5 }

-- {TABLE} 1712.1.4.2
lcsStatusWanPacketTransportTable OBJECT-TYPE
    SYNTAX     SEQUENCE OF LcsStatusWanPacketTransportEntry
    MAX-ACCESS not-accessible
    STATUS     current
    DESCRIPTION
        "-- empty --"
    ::= { lcsStatusWan 2 }

-- {ENTRY} 1712.1.4.2.1
lcsStatusWanPacketTransportEntry OBJECT-TYPE
    SYNTAX     LcsStatusWanPacketTransportEntry
    MAX-ACCESS not-accessible
    STATUS     current
    DESCRIPTION
        ""
    INDEX {
        lcsStatusWanPacketTransportEntryIfc
    }
    ::= { lcsStatusWanPacketTransportTable 1 }

-- {SEQUENCE}
LcsStatusWanPacketTransportEntry ::= SEQUENCE {
    lcsStatusWanPacketTransportEntryIfc INTEGER,
    lcsStatusWanPacketTransportEntryRx Counter32,
    lcsStatusWanPacketTransportEntryTxTotal Counter32,
    lcsStatusWanPacketTransportEntryTxNormal Counter32,
    lcsStatusWanPacketTransportEntryTxReliable Counter32,
    lcsStatusWanPacketTransportEntryTxUrgent Counter32
}

-- {COLUMN} 1712.1.4.2.1.1
lcsStatusWanPacketTransportEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusWanPacketTransportEntry 1 }

-- {COLUMN} 1712.1.4.2.1.2
lcsStatusWanPacketTransportEntryRx OBJECT-TYPE
    SYNTAX     Counter32
    MAX-ACCESS read-only
    STATUS     current
    DESCRIPTION
        "-- empty --"
    ::= { lcsStatusWanPacketTransportEntry 2 }

-- {COLUMN} 1712.1.4.2.1.3
lcsStatusWanPacketTransportEntryTxTotal OBJECT-TYPE
    SYNTAX     Counter32
    MAX-ACCESS read-only
    STATUS     current
    DESCRIPTION
        "-- empty --"
    ::= { lcsStatusWanPacketTransportEntry 3 }

-- {COLUMN} 1712.1.4.2.1.4
lcsStatusWanPacketTransportEntryTxNormal OBJECT-TYPE
    SYNTAX     Counter32
    MAX-ACCESS read-only
    STATUS     current
    DESCRIPTION
        "-- empty --"
    ::= { lcsStatusWanPacketTransportEntry 4 }

-- {COLUMN} 1712.1.4.2.1.5
lcsStatusWanPacketTransportEntryTxReliable OBJECT-TYPE
    SYNTAX     Counter32
    MAX-ACCESS read-only
    STATUS     current
    DESCRIPTION
        "-- empty --"
    ::= { lcsStatusWanPacketTransportEntry 5 }

-- {COLUMN} 1712.1.4.2.1.6
lcsStatusWanPacketTransportEntryTxUrgent OBJECT-TYPE
    SYNTAX     Counter32
    MAX-ACCESS read-only
    STATUS     current
    DESCRIPTION
        "-- empty --"
    ::= { lcsStatusWanPacketTransportEntry 6 }

-- {TABLE} 1712.1.4.3
lcsStatusWanErrorsTable OBJECT-TYPE
    SYNTAX     SEQUENCE OF LcsStatusWanErrorsEntry
    MAX-ACCESS not-accessible
    STATUS     current
    DESCRIPTION
        "-- empty --"
    ::= { lcsStatusWan 3 }

-- {ENTRY} 1712.1.4.3.1
lcsStatusWanErrorsEntry OBJECT-TYPE
    SYNTAX     LcsStatusWanErrorsEntry
    MAX-ACCESS not-accessible
    STATUS     current
    DESCRIPTION
        ""
    INDEX {
        lcsStatusWanErrorsEntryIfc
    }
    ::= { lcsStatusWanErrorsTable 1 }

-- {SEQUENCE}
LcsStatusWanErrorsEntry ::= SEQUENCE {
    lcsStatusWanErrorsEntryIfc INTEGER,
    lcsStatusWanErrorsEntryRxL1Error Counter32,
    lcsStatusWanErrorsEntryRxL2Error Counter32,
    lcsStatusWanErrorsEntryRxL3Error Counter32,
    lcsStatusWanErrorsEntryStackError Counter32,
    lcsStatusWanErrorsEntryTxError Counter32,
    lcsStatusWanErrorsEntryQueueErrors Counter32
}

-- {COLUMN} 1712.1.4.3.1.1
lcsStatusWanErrorsEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusWanErrorsEntry 1 }

-- {COLUMN} 1712.1.4.3.1.2
lcsStatusWanErrorsEntryRxL1Error OBJECT-TYPE
    SYNTAX     Counter32
    MAX-ACCESS read-only
    STATUS     current
    DESCRIPTION
        "-- empty --"
    ::= { lcsStatusWanErrorsEntry 2 }

-- {COLUMN} 1712.1.4.3.1.3
lcsStatusWanErrorsEntryRxL2Error OBJECT-TYPE
    SYNTAX     Counter32
    MAX-ACCESS read-only
    STATUS     current
    DESCRIPTION
        "-- empty --"
    ::= { lcsStatusWanErrorsEntry 3 }

-- {COLUMN} 1712.1.4.3.1.4
lcsStatusWanErrorsEntryRxL3Error OBJECT-TYPE
    SYNTAX     Counter32
    MAX-ACCESS read-only
    STATUS     current
    DESCRIPTION
        "-- empty --"
    ::= { lcsStatusWanErrorsEntry 4 }

-- {COLUMN} 1712.1.4.3.1.5
lcsStatusWanErrorsEntryStackError OBJECT-TYPE
    SYNTAX     Counter32
    MAX-ACCESS read-only
    STATUS     current
    DESCRIPTION
        "-- empty --"
    ::= { lcsStatusWanErrorsEntry 5 }

-- {COLUMN} 1712.1.4.3.1.6
lcsStatusWanErrorsEntryTxError OBJECT-TYPE
    SYNTAX     Counter32
    MAX-ACCESS read-only
    STATUS     current
    DESCRIPTION
        "-- empty --"
    ::= { lcsStatusWanErrorsEntry 6 }

-- {COLUMN} 1712.1.4.3.1.7
lcsStatusWanErrorsEntryQueueErrors OBJECT-TYPE
    SYNTAX     Counter32
    MAX-ACCESS read-only
    STATUS     current
    DESCRIPTION
        "-- empty --"
    ::= { lcsStatusWanErrorsEntry 7 }

-- {SCALAR} 1712.1.4.4
lcsStatusWanWanTxDiscarded OBJECT-TYPE
    SYNTAX     Counter32
    MAX-ACCESS read-only
    STATUS     current
    DESCRIPTION
        "-- empty --"
    ::= { lcsStatusWan 4 }

-- {SCALAR} 1712.1.4.5
lcsStatusWanWanHeapPackets OBJECT-TYPE
    SYNTAX     INTEGER (0..2147483647)
    MAX-ACCESS read-only
    STATUS     current
    DESCRIPTION
        "-- empty --"
    ::= { lcsStatusWan 5 }

-- {SCALAR} 1712.1.4.6
lcsStatusWanWanQueuePackets OBJECT-TYPE
    SYNTAX     INTEGER (0..2147483647)
    MAX-ACCESS read-only
    STATUS     current
    DESCRIPTION
        "-- empty --"
    ::= { lcsStatusWan 6 }

-- {SCALAR} 1712.1.4.7
lcsStatusWanWanQueueErrors OBJECT-TYPE
    SYNTAX     Counter32
    MAX-ACCESS read-only
    STATUS     current
    DESCRIPTION
        "-- empty --"
    ::= { lcsStatusWan 7 }

-- {SCALAR} 1712.1.4.21
lcsStatusWanWanQueueMgtDrop OBJECT-TYPE
    SYNTAX     Counter32
    MAX-ACCESS read-only
    STATUS     current
    DESCRIPTION
        "-- empty --"
    ::= { lcsStatusWan 21 }

-- {TABLE} 1712.1.4.8
lcsStatusWanThroughputTable OBJECT-TYPE
    SYNTAX     SEQUENCE OF LcsStatusWanThroughputEntry
    MAX-ACCESS not-accessible
    STATUS     current
    DESCRIPTION
        "-- empty --"
    ::= { lcsStatusWan 8 }

-- {ENTRY} 1712.1.4.8.1
lcsStatusWanThroughputEntry OBJECT-TYPE
    SYNTAX     LcsStatusWanThroughputEntry
    MAX-ACCESS not-accessible
    STATUS     current
    DESCRIPTION
        ""
    INDEX {
        lcsStatusWanThroughputEntryIfc
    }
    ::= { lcsStatusWanThroughputTable 1 }

-- {SEQUENCE}
LcsStatusWanThroughputEntry ::= SEQUENCE {
    lcsStatusWanThroughputEntryIfc INTEGER,
    lcsStatusWanThroughputEntryRxSCurrent INTEGER,
    lcsStatusWanThroughputEntryTxSCurrent INTEGER,
    lcsStatusWanThroughputEntryRxSAverage INTEGER,
    lcsStatusWanThroughputEntryTxSAverage INTEGER
}

-- {COLUMN} 1712.1.4.8.1.1
lcsStatusWanThroughputEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusWanThroughputEntry 1 }

-- {COLUMN} 1712.1.4.8.1.2
lcsStatusWanThroughputEntryRxSCurrent OBJECT-TYPE
    SYNTAX     INTEGER (0..2147483647)
    MAX-ACCESS read-only
    STATUS     current
    DESCRIPTION
        "-- empty --"
    ::= { lcsStatusWanThroughputEntry 2 }

-- {COLUMN} 1712.1.4.8.1.3
lcsStatusWanThroughputEntryTxSCurrent OBJECT-TYPE
    SYNTAX     INTEGER (0..2147483647)
    MAX-ACCESS read-only
    STATUS     current
    DESCRIPTION
        "-- empty --"
    ::= { lcsStatusWanThroughputEntry 3 }

-- {COLUMN} 1712.1.4.8.1.4
lcsStatusWanThroughputEntryRxSAverage OBJECT-TYPE
    SYNTAX     INTEGER (0..2147483647)
    MAX-ACCESS read-only
    STATUS     current
    DESCRIPTION
        "-- empty --"
    ::= { lcsStatusWanThroughputEntry 4 }

-- {COLUMN} 1712.1.4.8.1.5
lcsStatusWanThroughputEntryTxSAverage OBJECT-TYPE
    SYNTAX     INTEGER (0..2147483647)
    MAX-ACCESS read-only
    STATUS     current
    DESCRIPTION
        "-- empty --"
    ::= { lcsStatusWanThroughputEntry 5 }

-- {SCALAR} 1712.1.4.9
lcsStatusWanDeleteValues OBJECT-TYPE
    SYNTAX     DisplayString
    MAX-ACCESS read-write
    STATUS     current
    DESCRIPTION
        "-- empty --"
    ::= { lcsStatusWan 9 }

-- {SCALAR} 1712.1.4.10
lcsStatusWanConnections OBJECT-TYPE
    SYNTAX     INTEGER (0..2147483647)
    MAX-ACCESS read-only
    STATUS     current
    DESCRIPTION
        "-- empty --"
    ::= { lcsStatusWan 10 }

-- {TABLE} 1712.1.4.11
lcsStatusWanMtuTable OBJECT-TYPE
    SYNTAX     SEQUENCE OF LcsStatusWanMtuEntry
    MAX-ACCESS not-accessible
    STATUS     current
    DESCRIPTION
        "-- empty --"
    ::= { lcsStatusWan 11 }

-- {ENTRY} 1712.1.4.11.1
lcsStatusWanMtuEntry OBJECT-TYPE
    SYNTAX     LcsStatusWanMtuEntry
    MAX-ACCESS not-accessible
    STATUS     current
    DESCRIPTION
        ""
    INDEX {
        lcsStatusWanMtuEntryPeer
    }
    ::= { lcsStatusWanMtuTable 1 }

-- {SEQUENCE}
LcsStatusWanMtuEntry ::= SEQUENCE {
    lcsStatusWanMtuEntryPeer DisplayString,
    lcsStatusWanMtuEntryMtu INTEGER
}

-- {COLUMN} 1712.1.4.11.1.1
lcsStatusWanMtuEntryPeer OBJECT-TYPE
    SYNTAX     DisplayString (SIZE(0..16))
    MAX-ACCESS read-only
    STATUS     current
    DESCRIPTION
        "-- empty --"
    ::= { lcsStatusWanMtuEntry 1 }

-- {COLUMN} 1712.1.4.11.1.2
lcsStatusWanMtuEntryMtu OBJECT-TYPE
    SYNTAX     INTEGER (0..65535)
    MAX-ACCESS read-only
    STATUS     current
    DESCRIPTION
        "-- empty --"
    ::= { lcsStatusWanMtuEntry 2 }

-- {SCALAR} 1712.1.4.12
lcsStatusWanEncryptedConnections OBJECT-TYPE
    SYNTAX     INTEGER (0..2147483647)
    MAX-ACCESS read-only
    STATUS     current
    DESCRIPTION
        "-- empty --"
    ::= { lcsStatusWan 12 }

-- {OID} 1712.1.4.13
lcsStatusWanIpAddresses OBJECT IDENTIFIER ::= { lcsStatusWan 13 }

-- {TABLE} 1712.1.4.13.1
lcsStatusWanIpAddressesIpv4Table OBJECT-TYPE
    SYNTAX     SEQUENCE OF LcsStatusWanIpAddressesIpv4Entry
    MAX-ACCESS not-accessible
    STATUS     current
    DESCRIPTION
        "-- empty --"
    ::= { lcsStatusWanIpAddresses 1 }

-- {ENTRY} 1712.1.4.13.1.1
lcsStatusWanIpAddressesIpv4Entry OBJECT-TYPE
    SYNTAX     LcsStatusWanIpAddressesIpv4Entry
    MAX-ACCESS not-accessible
    STATUS     current
    DESCRIPTION
        ""
    INDEX {
        lcsStatusWanIpAddressesIpv4EntryPeer
    }
    ::= { lcsStatusWanIpAddressesIpv4Table 1 }

-- {SEQUENCE}
LcsStatusWanIpAddressesIpv4Entry ::= SEQUENCE {
    lcsStatusWanIpAddressesIpv4EntryPeer DisplayString,
    lcsStatusWanIpAddressesIpv4EntryType INTEGER,
    lcsStatusWanIpAddressesIpv4EntryIpAddress IpAddress,
    lcsStatusWanIpAddressesIpv4EntryIpNetmask IpAddress,
    lcsStatusWanIpAddressesIpv4EntryGateway IpAddress,
    lcsStatusWanIpAddressesIpv4EntryDnsDefault IpAddress,
    lcsStatusWanIpAddressesIpv4EntryDnsBackup IpAddress,
    lcsStatusWanIpAddressesIpv4EntryNbnsDefault IpAddress,
    lcsStatusWanIpAddressesIpv4EntryNbnsBackup IpAddress,
    lcsStatusWanIpAddressesIpv4EntryDomain DisplayString
}

-- {COLUMN} 1712.1.4.13.1.1.1
lcsStatusWanIpAddressesIpv4EntryPeer OBJECT-TYPE
    SYNTAX     DisplayString (SIZE(0..16))
    MAX-ACCESS read-only
    STATUS     current
    DESCRIPTION
        "-- empty --"
    ::= { lcsStatusWanIpAddressesIpv4Entry 1 }

-- {COLUMN} 1712.1.4.13.1.1.2
lcsStatusWanIpAddressesIpv4EntryType OBJECT-TYPE
    SYNTAX     INTEGER
      {
        eStatic (1),
        eDhcp (2),
        ePpp (3),
        eAutoconfig (4)
      }
    MAX-ACCESS read-only
    STATUS     current
    DESCRIPTION
        "-- empty --"
    ::= { lcsStatusWanIpAddressesIpv4Entry 2 }

-- {COLUMN} 1712.1.4.13.1.1.3
lcsStatusWanIpAddressesIpv4EntryIpAddress OBJECT-TYPE
    SYNTAX     IpAddress
    MAX-ACCESS read-only
    STATUS     current
    DESCRIPTION
        "-- empty --"
    ::= { lcsStatusWanIpAddressesIpv4Entry 3 }

-- {COLUMN} 1712.1.4.13.1.1.4
lcsStatusWanIpAddressesIpv4EntryIpNetmask OBJECT-TYPE
    SYNTAX     IpAddress
    MAX-ACCESS read-only
    STATUS     current
    DESCRIPTION
        "-- empty --"
    ::= { lcsStatusWanIpAddressesIpv4Entry 4 }

-- {COLUMN} 1712.1.4.13.1.1.5
lcsStatusWanIpAddressesIpv4EntryGateway OBJECT-TYPE
    SYNTAX     IpAddress
    MAX-ACCESS read-only
    STATUS     current
    DESCRIPTION
        "-- empty --"
    ::= { lcsStatusWanIpAddressesIpv4Entry 5 }

-- {COLUMN} 1712.1.4.13.1.1.6
lcsStatusWanIpAddressesIpv4EntryDnsDefault OBJECT-TYPE
    SYNTAX     IpAddress
    MAX-ACCESS read-only
    STATUS     current
    DESCRIPTION
        "-- empty --"
    ::= { lcsStatusWanIpAddressesIpv4Entry 6 }

-- {COLUMN} 1712.1.4.13.1.1.7
lcsStatusWanIpAddressesIpv4EntryDnsBackup OBJECT-TYPE
    SYNTAX     IpAddress
    MAX-ACCESS read-only
    STATUS     current
    DESCRIPTION
        "-- empty --"
    ::= { lcsStatusWanIpAddressesIpv4Entry 7 }

-- {COLUMN} 1712.1.4.13.1.1.8
lcsStatusWanIpAddressesIpv4EntryNbnsDefault OBJECT-TYPE
    SYNTAX     IpAddress
    MAX-ACCESS read-only
    STATUS     current
    DESCRIPTION
        "-- empty --"
    ::= { lcsStatusWanIpAddressesIpv4Entry 8 }

-- {COLUMN} 1712.1.4.13.1.1.9
lcsStatusWanIpAddressesIpv4EntryNbnsBackup OBJECT-TYPE
    SYNTAX     IpAddress
    MAX-ACCESS read-only
    STATUS     current
    DESCRIPTION
        "-- empty --"
    ::= { lcsStatusWanIpAddressesIpv4Entry 9 }

-- {COLUMN} 1712.1.4.13.1.1.10
lcsStatusWanIpAddressesIpv4EntryDomain OBJECT-TYPE
    SYNTAX     DisplayString (SIZE(0..35))
    MAX-ACCESS read-only
    STATUS     current
    DESCRIPTION
        "-- empty --"
    ::= { lcsStatusWanIpAddressesIpv4Entry 10 }

-- {TABLE} 1712.1.4.13.2
lcsStatusWanIpAddressesIpv6Table OBJECT-TYPE
    SYNTAX     SEQUENCE OF LcsStatusWanIpAddressesIpv6Entry
    MAX-ACCESS not-accessible
    STATUS     current
    DESCRIPTION
        "-- empty --"
    ::= { lcsStatusWanIpAddresses 2 }

-- {ENTRY} 1712.1.4.13.2.1
lcsStatusWanIpAddressesIpv6Entry OBJECT-TYPE
    SYNTAX     LcsStatusWanIpAddressesIpv6Entry
    MAX-ACCESS not-accessible
    STATUS     current
    DESCRIPTION
        ""
    INDEX {
        lcsStatusWanIpAddressesIpv6EntryPeer
    }
    ::= { lcsStatusWanIpAddressesIpv6Table 1 }

-- {SEQUENCE}
LcsStatusWanIpAddressesIpv6Entry ::= SEQUENCE {
    lcsStatusWanIpAddressesIpv6EntryPeer DisplayString,
    lcsStatusWanIpAddressesIpv6EntryType INTEGER,
    lcsStatusWanIpAddressesIpv6EntryIpAddress DisplayString,
    lcsStatusWanIpAddressesIpv6EntryPrefixLength INTEGER,
    lcsStatusWanIpAddressesIpv6EntryPrefix DisplayString,
    lcsStatusWanIpAddressesIpv6EntryGateway DisplayString,
    lcsStatusWanIpAddressesIpv6EntryDnsDefault DisplayString,
    lcsStatusWanIpAddressesIpv6EntryDnsBackup DisplayString,
    lcsStatusWanIpAddressesIpv6EntryDomain DisplayString
}

-- {COLUMN} 1712.1.4.13.2.1.1
lcsStatusWanIpAddressesIpv6EntryPeer OBJECT-TYPE
    SYNTAX     DisplayString (SIZE(0..16))
    MAX-ACCESS read-only
    STATUS     current
    DESCRIPTION
        "-- empty --"
    ::= { lcsStatusWanIpAddressesIpv6Entry 1 }

-- {COLUMN} 1712.1.4.13.2.1.2
lcsStatusWanIpAddressesIpv6EntryType OBJECT-TYPE
    SYNTAX     INTEGER
      {
        eUnknown (0),
        eStatic (1),
        eDhcp (2),
        eAutoconfig (4),
        eTunnel (5)
      }
    MAX-ACCESS read-only
    STATUS     current
    DESCRIPTION
        "-- empty --"
    ::= { lcsStatusWanIpAddressesIpv6Entry 2 }

-- {COLUMN} 1712.1.4.13.2.1.3
lcsStatusWanIpAddressesIpv6EntryIpAddress OBJECT-TYPE
    SYNTAX     DisplayString (SIZE(0..255))
    MAX-ACCESS read-only
    STATUS     current
    DESCRIPTION
        "-- empty --"
    ::= { lcsStatusWanIpAddressesIpv6Entry 3 }

-- {COLUMN} 1712.1.4.13.2.1.4
lcsStatusWanIpAddressesIpv6EntryPrefixLength OBJECT-TYPE
    SYNTAX     INTEGER (0..2147483647)
    MAX-ACCESS read-only
    STATUS     current
    DESCRIPTION
        "-- empty --"
    ::= { lcsStatusWanIpAddressesIpv6Entry 4 }

-- {COLUMN} 1712.1.4.13.2.1.8
lcsStatusWanIpAddressesIpv6EntryPrefix OBJECT-TYPE
    SYNTAX     DisplayString (SIZE(0..255))
    MAX-ACCESS read-only
    STATUS     current
    DESCRIPTION
        "-- empty --"
    ::= { lcsStatusWanIpAddressesIpv6Entry 8 }

-- {COLUMN} 1712.1.4.13.2.1.5
lcsStatusWanIpAddressesIpv6EntryGateway OBJECT-TYPE
    SYNTAX     DisplayString (SIZE(0..255))
    MAX-ACCESS read-only
    STATUS     current
    DESCRIPTION
        "-- empty --"
    ::= { lcsStatusWanIpAddressesIpv6Entry 5 }

-- {COLUMN} 1712.1.4.13.2.1.6
lcsStatusWanIpAddressesIpv6EntryDnsDefault OBJECT-TYPE
    SYNTAX     DisplayString (SIZE(0..255))
    MAX-ACCESS read-only
    STATUS     current
    DESCRIPTION
        "-- empty --"
    ::= { lcsStatusWanIpAddressesIpv6Entry 6 }

-- {COLUMN} 1712.1.4.13.2.1.7
lcsStatusWanIpAddressesIpv6EntryDnsBackup OBJECT-TYPE
    SYNTAX     DisplayString (SIZE(0..255))
    MAX-ACCESS read-only
    STATUS     current
    DESCRIPTION
        "-- empty --"
    ::= { lcsStatusWanIpAddressesIpv6Entry 7 }

-- {COLUMN} 1712.1.4.13.2.1.10
lcsStatusWanIpAddressesIpv6EntryDomain OBJECT-TYPE
    SYNTAX     DisplayString (SIZE(0..35))
    MAX-ACCESS read-only
    STATUS     current
    DESCRIPTION
        "-- empty --"
    ::= { lcsStatusWanIpAddressesIpv6Entry 10 }

-- {OID} 1712.1.4.20
lcsStatusWanActions OBJECT IDENTIFIER ::= { lcsStatusWan 20 }

-- {TABLE} 1712.1.4.20.1
lcsStatusWanActionsActionTableTable OBJECT-TYPE
    SYNTAX     SEQUENCE OF LcsStatusWanActionsActionTableEntry
    MAX-ACCESS not-accessible
    STATUS     current
    DESCRIPTION
        "-- empty --"
    ::= { lcsStatusWanActions 1 }

-- {ENTRY} 1712.1.4.20.1.1
lcsStatusWanActionsActionTableEntry OBJECT-TYPE
    SYNTAX     LcsStatusWanActionsActionTableEntry
    MAX-ACCESS not-accessible
    STATUS     current
    DESCRIPTION
        ""
    INDEX {
        lcsStatusWanActionsActionTableEntryTime
    }
    ::= { lcsStatusWanActionsActionTableTable 1 }

-- {SEQUENCE}
LcsStatusWanActionsActionTableEntry ::= SEQUENCE {
    lcsStatusWanActionsActionTableEntryTime DisplayString,
    lcsStatusWanActionsActionTableEntryAction DisplayString,
    lcsStatusWanActionsActionTableEntryResult DisplayString
}

-- {COLUMN} 1712.1.4.20.1.1.1
lcsStatusWanActionsActionTableEntryTime OBJECT-TYPE
    SYNTAX     DisplayString (SIZE(0..19))
    MAX-ACCESS read-only
    STATUS     current
    DESCRIPTION
        "-- empty --"
    ::= { lcsStatusWanActionsActionTableEntry 1 }

-- {COLUMN} 1712.1.4.20.1.1.2
lcsStatusWanActionsActionTableEntryAction OBJECT-TYPE
    SYNTAX     DisplayString (SIZE(0..255))
    MAX-ACCESS read-only
    STATUS     current
    DESCRIPTION
        "-- empty --"
    ::= { lcsStatusWanActionsActionTableEntry 2 }

-- {COLUMN} 1712.1.4.20.1.1.3
lcsStatusWanActionsActionTableEntryResult OBJECT-TYPE
    SYNTAX     DisplayString (SIZE(0..100))
    MAX-ACCESS read-only
    STATUS     current
    DESCRIPTION
        "-- empty --"
    ::= { lcsStatusWanActionsActionTableEntry 3 }

-- {TABLE} 1712.1.4.20.2
lcsStatusWanActionsLockTableTable OBJECT-TYPE
    SYNTAX     SEQUENCE OF LcsStatusWanActionsLockTableEntry
    MAX-ACCESS not-accessible
    STATUS     current
    DESCRIPTION
        "-- empty --"
    ::= { lcsStatusWanActions 2 }

-- {ENTRY} 1712.1.4.20.2.1
lcsStatusWanActionsLockTableEntry OBJECT-TYPE
    SYNTAX     LcsStatusWanActionsLockTableEntry
    MAX-ACCESS not-accessible
    STATUS     current
    DESCRIPTION
        ""
    INDEX {
        lcsStatusWanActionsLockTableEntryIndex
    }
    ::= { lcsStatusWanActionsLockTableTable 1 }

-- {SEQUENCE}
LcsStatusWanActionsLockTableEntry ::= SEQUENCE {
    lcsStatusWanActionsLockTableEntryIndex INTEGER,
    lcsStatusWanActionsLockTableEntryRemainingLocktime INTEGER
}

-- {COLUMN} 1712.1.4.20.2.1.1
lcsStatusWanActionsLockTableEntryIndex OBJECT-TYPE
    SYNTAX     INTEGER (0..65535)
    MAX-ACCESS read-only
    STATUS     current
    DESCRIPTION
        "-- empty --"
    ::= { lcsStatusWanActionsLockTableEntry 1 }

-- {COLUMN} 1712.1.4.20.2.1.2
lcsStatusWanActionsLockTableEntryRemainingLocktime OBJECT-TYPE
    SYNTAX     INTEGER (0..2147483647)
    MAX-ACCESS read-only
    STATUS     current
    DESCRIPTION
        "-- empty --"
    ::= { lcsStatusWanActionsLockTableEntry 2 }

-- {OID} 1712.1.4.45
lcsStatusWanX25Bridge OBJECT IDENTIFIER ::= { lcsStatusWan 45 }

-- {TABLE} 1712.1.4.45.2
lcsStatusWanX25BridgeConnectionsTable OBJECT-TYPE
    SYNTAX     SEQUENCE OF LcsStatusWanX25BridgeConnectionsEntry
    MAX-ACCESS not-accessible
    STATUS     current
    DESCRIPTION
        "-- empty --"
    ::= { lcsStatusWanX25Bridge 2 }

-- {ENTRY} 1712.1.4.45.2.1
lcsStatusWanX25BridgeConnectionsEntry OBJECT-TYPE
    SYNTAX     LcsStatusWanX25BridgeConnectionsEntry
    MAX-ACCESS not-accessible
    STATUS     current
    DESCRIPTION
        ""
    INDEX {
        lcsStatusWanX25BridgeConnectionsEntryIndex
    }
    ::= { lcsStatusWanX25BridgeConnectionsTable 1 }

-- {SEQUENCE}
LcsStatusWanX25BridgeConnectionsEntry ::= SEQUENCE {
    lcsStatusWanX25BridgeConnectionsEntryIndex INTEGER,
    lcsStatusWanX25BridgeConnectionsEntryDirection INTEGER,
    lcsStatusWanX25BridgeConnectionsEntryTcpState INTEGER,
    lcsStatusWanX25BridgeConnectionsEntryIsdnState INTEGER,
    lcsStatusWanX25BridgeConnectionsEntryX25State INTEGER,
    lcsStatusWanX25BridgeConnectionsEntryTerminalIp IpAddress,
    lcsStatusWanX25BridgeConnectionsEntryTerminalPort INTEGER,
    lcsStatusWanX25BridgeConnectionsEntryLocalIp IpAddress,
    lcsStatusWanX25BridgeConnectionsEntryLocalPort INTEGER,
    lcsStatusWanX25BridgeConnectionsEntryRoutingTag INTEGER,
    lcsStatusWanX25BridgeConnectionsEntryIsdnRemote DisplayString,
    lcsStatusWanX25BridgeConnectionsEntryIsdnLocal DisplayString,
    lcsStatusWanX25BridgeConnectionsEntryX25Remote DisplayString,
    lcsStatusWanX25BridgeConnectionsEntryX25Local DisplayString,
    lcsStatusWanX25BridgeConnectionsEntryProtocolId INTEGER,
    lcsStatusWanX25BridgeConnectionsEntryUserdata DisplayString,
    lcsStatusWanX25BridgeConnectionsEntryPayloadSize INTEGER
}

-- {COLUMN} 1712.1.4.45.2.1.1
lcsStatusWanX25BridgeConnectionsEntryIndex OBJECT-TYPE
    SYNTAX     INTEGER (0..2147483647)
    MAX-ACCESS read-only
    STATUS     current
    DESCRIPTION
        "-- empty --"
    ::= { lcsStatusWanX25BridgeConnectionsEntry 1 }

-- {COLUMN} 1712.1.4.45.2.1.2
lcsStatusWanX25BridgeConnectionsEntryDirection OBJECT-TYPE
    SYNTAX     INTEGER
      {
        eOutgoing (0),
        eIncoming (1)
      }
    MAX-ACCESS read-only
    STATUS     current
    DESCRIPTION
        "-- empty --"
    ::= { lcsStatusWanX25BridgeConnectionsEntry 2 }

-- {COLUMN} 1712.1.4.45.2.1.3
lcsStatusWanX25BridgeConnectionsEntryTcpState OBJECT-TYPE
    SYNTAX     INTEGER
      {
        eListening (0),
        eConnecting (1),
        eConnected (2),
        eDisconnecting (3),
        eDisconnected (4)
      }
    MAX-ACCESS read-only
    STATUS     current
    DESCRIPTION
        "-- empty --"
    ::= { lcsStatusWanX25BridgeConnectionsEntry 3 }

-- {COLUMN} 1712.1.4.45.2.1.4
lcsStatusWanX25BridgeConnectionsEntryIsdnState OBJECT-TYPE
    SYNTAX     INTEGER
      {
        eListening (0),
        eConnecting (1),
        eConnected (2),
        eDisconnecting (3),
        eDisconnected (4)
      }
    MAX-ACCESS read-only
    STATUS     current
    DESCRIPTION
        "-- empty --"
    ::= { lcsStatusWanX25BridgeConnectionsEntry 4 }

-- {COLUMN} 1712.1.4.45.2.1.5
lcsStatusWanX25BridgeConnectionsEntryX25State OBJECT-TYPE
    SYNTAX     INTEGER
      {
        eListening (0),
        eConnecting (1),
        eConnected (2),
        eDisconnecting (3),
        eDisconnected (4)
      }
    MAX-ACCESS read-only
    STATUS     current
    DESCRIPTION
        "-- empty --"
    ::= { lcsStatusWanX25BridgeConnectionsEntry 5 }

-- {COLUMN} 1712.1.4.45.2.1.6
lcsStatusWanX25BridgeConnectionsEntryTerminalIp OBJECT-TYPE
    SYNTAX     IpAddress
    MAX-ACCESS read-only
    STATUS     current
    DESCRIPTION
        "-- empty --"
    ::= { lcsStatusWanX25BridgeConnectionsEntry 6 }

-- {COLUMN} 1712.1.4.45.2.1.7
lcsStatusWanX25BridgeConnectionsEntryTerminalPort OBJECT-TYPE
    SYNTAX     INTEGER (0..65535)
    MAX-ACCESS read-only
    STATUS     current
    DESCRIPTION
        "-- empty --"
    ::= { lcsStatusWanX25BridgeConnectionsEntry 7 }

-- {COLUMN} 1712.1.4.45.2.1.8
lcsStatusWanX25BridgeConnectionsEntryLocalIp OBJECT-TYPE
    SYNTAX     IpAddress
    MAX-ACCESS read-only
    STATUS     current
    DESCRIPTION
        "-- empty --"
    ::= { lcsStatusWanX25BridgeConnectionsEntry 8 }

-- {COLUMN} 1712.1.4.45.2.1.9
lcsStatusWanX25BridgeConnectionsEntryLocalPort OBJECT-TYPE
    SYNTAX     INTEGER (0..65535)
    MAX-ACCESS read-only
    STATUS     current
    DESCRIPTION
        "-- empty --"
    ::= { lcsStatusWanX25BridgeConnectionsEntry 9 }

-- {COLUMN} 1712.1.4.45.2.1.10
lcsStatusWanX25BridgeConnectionsEntryRoutingTag OBJECT-TYPE
    SYNTAX     INTEGER (0..2147483647)
    MAX-ACCESS read-only
    STATUS     current
    DESCRIPTION
        "-- empty --"
    ::= { lcsStatusWanX25BridgeConnectionsEntry 10 }

-- {COLUMN} 1712.1.4.45.2.1.11
lcsStatusWanX25BridgeConnectionsEntryIsdnRemote OBJECT-TYPE
    SYNTAX     DisplayString
    MAX-ACCESS read-only
    STATUS     current
    DESCRIPTION
        "-- empty --"
    ::= { lcsStatusWanX25BridgeConnectionsEntry 11 }

-- {COLUMN} 1712.1.4.45.2.1.12
lcsStatusWanX25BridgeConnectionsEntryIsdnLocal OBJECT-TYPE
    SYNTAX     DisplayString
    MAX-ACCESS read-only
    STATUS     current
    DESCRIPTION
        "-- empty --"
    ::= { lcsStatusWanX25BridgeConnectionsEntry 12 }

-- {COLUMN} 1712.1.4.45.2.1.13
lcsStatusWanX25BridgeConnectionsEntryX25Remote OBJECT-TYPE
    SYNTAX     DisplayString
    MAX-ACCESS read-only
    STATUS     current
    DESCRIPTION
        "-- empty --"
    ::= { lcsStatusWanX25BridgeConnectionsEntry 13 }

-- {COLUMN} 1712.1.4.45.2.1.14
lcsStatusWanX25BridgeConnectionsEntryX25Local OBJECT-TYPE
    SYNTAX     DisplayString
    MAX-ACCESS read-only
    STATUS     current
    DESCRIPTION
        "-- empty --"
    ::= { lcsStatusWanX25BridgeConnectionsEntry 14 }

-- {COLUMN} 1712.1.4.45.2.1.15
lcsStatusWanX25BridgeConnectionsEntryProtocolId OBJECT-TYPE
    SYNTAX     INTEGER (0..2147483647)
    MAX-ACCESS read-only
    STATUS     current
    DESCRIPTION
        "-- empty --"
    ::= { lcsStatusWanX25BridgeConnectionsEntry 15 }

-- {COLUMN} 1712.1.4.45.2.1.16
lcsStatusWanX25BridgeConnectionsEntryUserdata OBJECT-TYPE
    SYNTAX     DisplayString
    MAX-ACCESS read-only
    STATUS     current
    DESCRIPTION
        "-- empty --"
    ::= { lcsStatusWanX25BridgeConnectionsEntry 16 }

-- {COLUMN} 1712.1.4.45.2.1.17
lcsStatusWanX25BridgeConnectionsEntryPayloadSize OBJECT-TYPE
    SYNTAX     INTEGER (0..2147483647)
    MAX-ACCESS read-only
    STATUS     current
    DESCRIPTION
        "-- empty --"
    ::= { lcsStatusWanX25BridgeConnectionsEntry 17 }

-- {TABLE} 1712.1.4.45.3
lcsStatusWanX25BridgeTcpListenerPortsTable OBJECT-TYPE
    SYNTAX     SEQUENCE OF LcsStatusWanX25BridgeTcpListenerPortsEntry
    MAX-ACCESS not-accessible
    STATUS     current
    DESCRIPTION
        "-- empty --"
    ::= { lcsStatusWanX25Bridge 3 }

-- {ENTRY} 1712.1.4.45.3.1
lcsStatusWanX25BridgeTcpListenerPortsEntry OBJECT-TYPE
    SYNTAX     LcsStatusWanX25BridgeTcpListenerPortsEntry
    MAX-ACCESS not-accessible
    STATUS     current
    DESCRIPTION
        ""
    INDEX {
        lcsStatusWanX25BridgeTcpListenerPortsEntryLocalPort
    }
    ::= { lcsStatusWanX25BridgeTcpListenerPortsTable 1 }

-- {SEQUENCE}
LcsStatusWanX25BridgeTcpListenerPortsEntry ::= SEQUENCE {
    lcsStatusWanX25BridgeTcpListenerPortsEntryLocalPort INTEGER
}

-- {COLUMN} 1712.1.4.45.3.1.1
lcsStatusWanX25BridgeTcpListenerPortsEntryLocalPort OBJECT-TYPE
    SYNTAX     INTEGER (0..65535)
    MAX-ACCESS read-only
    STATUS     current
    DESCRIPTION
        "-- empty --"
    ::= { lcsStatusWanX25BridgeTcpListenerPortsEntry 1 }

-- {SCALAR} 1712.1.4.45.4
lcsStatusWanX25BridgeDisconnectAll OBJECT-TYPE
    SYNTAX     DisplayString
    MAX-ACCESS read-write
    STATUS     current
    DESCRIPTION
        "-- empty --"
    ::= { lcsStatusWanX25Bridge 4 }

-- {OID} 1712.1.5
lcsStatusLan OBJECT IDENTIFIER ::= { lcsStatus 5 }

-- {SCALAR} 1712.1.5.7
lcsStatusLanLanHeapPackets OBJECT-TYPE
    SYNTAX     INTEGER (0..2147483647)
    MAX-ACCESS read-only
    STATUS     current
    DESCRIPTION
        "-- empty --"
    ::= { lcsStatusLan 7 }

-- {SCALAR} 1712.1.5.11
lcsStatusLanDeleteValues OBJECT-TYPE
    SYNTAX     DisplayString
    MAX-ACCESS read-write
    STATUS     current
    DESCRIPTION
        "-- empty --"
    ::= { lcsStatusLan 11 }

-- {SCALAR} 1712.1.5.60
lcsStatusLanLanQueueMgtDrop OBJECT-TYPE
    SYNTAX     Counter32
    MAX-ACCESS read-only
    STATUS     current
    DESCRIPTION
        "-- empty --"
    ::= { lcsStatusLan 60 }

-- {OID} 1712.1.5.80
lcsStatusLanIeee8021x OBJECT IDENTIFIER ::= { lcsStatusLan 80 }

-- {TABLE} 1712.1.5.80.1
lcsStatusLanIeee8021xSupplicantIfcStateTable OBJECT-TYPE
    SYNTAX     SEQUENCE OF LcsStatusLanIeee8021xSupplicantIfcStateEntry
    MAX-ACCESS not-accessible
    STATUS     current
    DESCRIPTION
        "-- empty --"
    ::= { lcsStatusLanIeee8021x 1 }

-- {ENTRY} 1712.1.5.80.1.1
lcsStatusLanIeee8021xSupplicantIfcStateEntry OBJECT-TYPE
    SYNTAX     LcsStatusLanIeee8021xSupplicantIfcStateEntry
    MAX-ACCESS not-accessible
    STATUS     current
    DESCRIPTION
        ""
    INDEX {
        lcsStatusLanIeee8021xSupplicantIfcStateEntryIfc
    }
    ::= { lcsStatusLanIeee8021xSupplicantIfcStateTable 1 }

-- {SEQUENCE}
LcsStatusLanIeee8021xSupplicantIfcStateEntry ::= SEQUENCE {
    lcsStatusLanIeee8021xSupplicantIfcStateEntryIfc INTEGER,
    lcsStatusLanIeee8021xSupplicantIfcStateEntryMethod INTEGER,
    lcsStatusLanIeee8021xSupplicantIfcStateEntryState INTEGER,
    lcsStatusLanIeee8021xSupplicantIfcStateEntryAuthenticatorAddress MacAddress
}

-- {COLUMN} 1712.1.5.80.1.1.1
lcsStatusLanIeee8021xSupplicantIfcStateEntryIfc OBJECT-TYPE
    SYNTAX     INTEGER
      {
        eLan1 (1),
        eLan2 (2),
        eLan3 (3),
        eLan4 (4)
      }
    MAX-ACCESS read-only
    STATUS     current
    DESCRIPTION
        "-- empty --"
    ::= { lcsStatusLanIeee8021xSupplicantIfcStateEntry 1 }

-- {COLUMN} 1712.1.5.80.1.1.2
lcsStatusLanIeee8021xSupplicantIfcStateEntryMethod OBJECT-TYPE
    SYNTAX     INTEGER
      {
        eNone (0),
        eMd5 (1024),
        eTls (3328),
        eTtlsPap (5383),
        eTtlsChap (5384),
        eTtlsMschap (5567),
        eTtlsMschapv2 (5402),
        eTtlsMd5 (5380),
        ePeapMschapv2 (6426),
        ePeapGtc (6406)
      }
    MAX-ACCESS read-only
    STATUS     current
    DESCRIPTION
        "-- empty --"
    ::= { lcsStatusLanIeee8021xSupplicantIfcStateEntry 2 }

-- {COLUMN} 1712.1.5.80.1.1.3
lcsStatusLanIeee8021xSupplicantIfcStateEntryState OBJECT-TYPE
    SYNTAX     INTEGER
      {
        eIdle (0),
        eUnauthorized (1),
        eAuthorized (2)
      }
    MAX-ACCESS read-only
    STATUS     current
    DESCRIPTION
        "-- empty --"
    ::= { lcsStatusLanIeee8021xSupplicantIfcStateEntry 3 }

-- {COLUMN} 1712.1.5.80.1.1.4
lcsStatusLanIeee8021xSupplicantIfcStateEntryAuthenticatorAddress OBJECT-TYPE
    SYNTAX     MacAddress
    MAX-ACCESS read-only
    STATUS     current
    DESCRIPTION
        "-- empty --"
    ::= { lcsStatusLanIeee8021xSupplicantIfcStateEntry 4 }

-- {TABLE} 1712.1.5.51
lcsStatusLanInterfacesTable OBJECT-TYPE
    SYNTAX     SEQUENCE OF LcsStatusLanInterfacesEntry
    MAX-ACCESS not-accessible
    STATUS     current
    DESCRIPTION
        "-- empty --"
    ::= { lcsStatusLan 51 }

-- {ENTRY} 1712.1.5.51.1
lcsStatusLanInterfacesEntry OBJECT-TYPE
    SYNTAX     LcsStatusLanInterfacesEntry
    MAX-ACCESS not-accessible
    STATUS     current
    DESCRIPTION
        ""
    INDEX {
        lcsStatusLanInterfacesEntryIfc
    }
    ::= { lcsStatusLanInterfacesTable 1 }

-- {SEQUENCE}
LcsStatusLanInterfacesEntry ::= SEQUENCE {
    lcsStatusLanInterfacesEntryIfc DisplayString,
    lcsStatusLanInterfacesEntryQueuePackets INTEGER,
    lcsStatusLanInterfacesEntryLinkActive INTEGER
}

-- {COLUMN} 1712.1.5.51.1.1
lcsStatusLanInterfacesEntryIfc OBJECT-TYPE
    SYNTAX     DisplayString (SIZE(0..255))
    MAX-ACCESS read-only
    STATUS     current
    DESCRIPTION
        "-- empty --"
    ::= { lcsStatusLanInterfacesEntry 1 }

-- {COLUMN} 1712.1.5.51.1.2
lcsStatusLanInterfacesEntryQueuePackets OBJECT-TYPE
    SYNTAX     INTEGER (0..2147483647)
    MAX-ACCESS read-only
    STATUS     current
    DESCRIPTION
        "-- empty --"
    ::= { lcsStatusLanInterfacesEntry 2 }

-- {COLUMN} 1712.1.5.51.1.3
lcsStatusLanInterfacesEntryLinkActive OBJECT-TYPE
    SYNTAX     INTEGER
      {
        eNo (0),
        eYes (1)
      }
    MAX-ACCESS read-only
    STATUS     current
    DESCRIPTION
        "-- empty --"
    ::= { lcsStatusLanInterfacesEntry 3 }

-- {TABLE} 1712.1.5.52
lcsStatusLanByteTransportTable OBJECT-TYPE
    SYNTAX     SEQUENCE OF LcsStatusLanByteTransportEntry
    MAX-ACCESS not-accessible
    STATUS     current
    DESCRIPTION
        "-- empty --"
    ::= { lcsStatusLan 52 }

-- {ENTRY} 1712.1.5.52.1
lcsStatusLanByteTransportEntry OBJECT-TYPE
    SYNTAX     LcsStatusLanByteTransportEntry
    MAX-ACCESS not-accessible
    STATUS     current
    DESCRIPTION
        ""
    INDEX {
        lcsStatusLanByteTransportEntryIfc
    }
    ::= { lcsStatusLanByteTransportTable 1 }

-- {SEQUENCE}
LcsStatusLanByteTransportEntry ::= SEQUENCE {
    lcsStatusLanByteTransportEntryIfc DisplayString,
    lcsStatusLanByteTransportEntryTxBytes Counter64,
    lcsStatusLanByteTransportEntryRxBytes Counter64,
    lcsStatusLanByteTransportEntryThroughput DisplayString,
    lcsStatusLanByteTransportEntryMaxThroughput DisplayString,
    lcsStatusLanByteTransportEntryBytesThroughput INTEGER,
    lcsStatusLanByteTransportEntryBytesMaxThroughput INTEGER
}

-- {COLUMN} 1712.1.5.52.1.1
lcsStatusLanByteTransportEntryIfc OBJECT-TYPE
    SYNTAX     DisplayString (SIZE(0..255))
    MAX-ACCESS read-only
    STATUS     current
    DESCRIPTION
        "-- empty --"
    ::= { lcsStatusLanByteTransportEntry 1 }

-- {COLUMN} 1712.1.5.52.1.2
lcsStatusLanByteTransportEntryTxBytes OBJECT-TYPE
    SYNTAX     Counter64
    MAX-ACCESS read-only
    STATUS     current
    DESCRIPTION
        "-- empty --"
    ::= { lcsStatusLanByteTransportEntry 2 }

-- {COLUMN} 1712.1.5.52.1.3
lcsStatusLanByteTransportEntryRxBytes OBJECT-TYPE
    SYNTAX     Counter64
    MAX-ACCESS read-only
    STATUS     current
    DESCRIPTION
        "-- empty --"
    ::= { lcsStatusLanByteTransportEntry 3 }

-- {COLUMN} 1712.1.5.52.1.4
lcsStatusLanByteTransportEntryThroughput OBJECT-TYPE
    SYNTAX     DisplayString (SIZE(0..255))
    MAX-ACCESS read-only
    STATUS     current
    DESCRIPTION
        "-- empty --"
    ::= { lcsStatusLanByteTransportEntry 4 }

-- {COLUMN} 1712.1.5.52.1.5
lcsStatusLanByteTransportEntryMaxThroughput OBJECT-TYPE
    SYNTAX     DisplayString (SIZE(0..255))
    MAX-ACCESS read-only
    STATUS     current
    DESCRIPTION
        "-- empty --"
    ::= { lcsStatusLanByteTransportEntry 5 }

-- {COLUMN} 1712.1.5.52.1.6
lcsStatusLanByteTransportEntryBytesThroughput OBJECT-TYPE
    SYNTAX     INTEGER (0..2147483647)
    MAX-ACCESS read-only
    STATUS     current
    DESCRIPTION
        "-- empty --"
    ::= { lcsStatusLanByteTransportEntry 6 }

-- {COLUMN} 1712.1.5.52.1.7
lcsStatusLanByteTransportEntryBytesMaxThroughput OBJECT-TYPE
    SYNTAX     INTEGER (0..2147483647)
    MAX-ACCESS read-only
    STATUS     current
    DESCRIPTION
        "-- empty --"
    ::= { lcsStatusLanByteTransportEntry 7 }

-- {TABLE} 1712.1.5.53
lcsStatusLanPacketTransportTable OBJECT-TYPE
    SYNTAX     SEQUENCE OF LcsStatusLanPacketTransportEntry
    MAX-ACCESS not-accessible
    STATUS     current
    DESCRIPTION
        "-- empty --"
    ::= { lcsStatusLan 53 }

-- {ENTRY} 1712.1.5.53.1
lcsStatusLanPacketTransportEntry OBJECT-TYPE
    SYNTAX     LcsStatusLanPacketTransportEntry
    MAX-ACCESS not-accessible
    STATUS     current
    DESCRIPTION
        ""
    INDEX {
        lcsStatusLanPacketTransportEntryIfc
    }
    ::= { lcsStatusLanPacketTransportTable 1 }

-- {SEQUENCE}
LcsStatusLanPacketTransportEntry ::= SEQUENCE {
    lcsStatusLanPacketTransportEntryIfc DisplayString,
    lcsStatusLanPacketTransportEntryRxPackets Counter32,
    lcsStatusLanPacketTransportEntryTxPackets Counter32,
    lcsStatusLanPacketTransportEntryRxBroadcasts Counter32,
    lcsStatusLanPacketTransportEntryRxMulticasts Counter32,
    lcsStatusLanPacketTransportEntryRxUnicasts Counter32,
    lcsStatusLanPacketTransportEntryTxBroadcasts Counter32,
    lcsStatusLanPacketTransportEntryTxMulticasts Counter32,
    lcsStatusLanPacketTransportEntryTxUnicasts Counter32
}

-- {COLUMN} 1712.1.5.53.1.1
lcsStatusLanPacketTransportEntryIfc OBJECT-TYPE
    SYNTAX     DisplayString (SIZE(0..255))
    MAX-ACCESS read-only
    STATUS     current
    DESCRIPTION
        "-- empty --"
    ::= { lcsStatusLanPacketTransportEntry 1 }

-- {COLUMN} 1712.1.5.53.1.2
lcsStatusLanPacketTransportEntryRxPackets OBJECT-TYPE
    SYNTAX     Counter32
    MAX-ACCESS read-only
    STATUS     current
    DESCRIPTION
        "-- empty --"
    ::= { lcsStatusLanPacketTransportEntry 2 }

-- {COLUMN} 1712.1.5.53.1.3
lcsStatusLanPacketTransportEntryTxPackets OBJECT-TYPE
    SYNTAX     Counter32
    MAX-ACCESS read-only
    STATUS     current
    DESCRIPTION
        "-- empty --"
    ::= { lcsStatusLanPacketTransportEntry 3 }

-- {COLUMN} 1712.1.5.53.1.4
lcsStatusLanPacketTransportEntryRxBroadcasts OBJECT-TYPE
    SYNTAX     Counter32
    MAX-ACCESS read-only
    STATUS     current
    DESCRIPTION
        "-- empty --"
    ::= { lcsStatusLanPacketTransportEntry 4 }

-- {COLUMN} 1712.1.5.53.1.5
lcsStatusLanPacketTransportEntryRxMulticasts OBJECT-TYPE
    SYNTAX     Counter32
    MAX-ACCESS read-only
    STATUS     current
    DESCRIPTION
        "-- empty --"
    ::= { lcsStatusLanPacketTransportEntry 5 }

-- {COLUMN} 1712.1.5.53.1.6
lcsStatusLanPacketTransportEntryRxUnicasts OBJECT-TYPE
    SYNTAX     Counter32
    MAX-ACCESS read-only
    STATUS     current
    DESCRIPTION
        "-- empty --"
    ::= { lcsStatusLanPacketTransportEntry 6 }

-- {COLUMN} 1712.1.5.53.1.7
lcsStatusLanPacketTransportEntryTxBroadcasts OBJECT-TYPE
    SYNTAX     Counter32
    MAX-ACCESS read-only
    STATUS     current
    DESCRIPTION
        "-- empty --"
    ::= { lcsStatusLanPacketTransportEntry 7 }

-- {COLUMN} 1712.1.5.53.1.8
lcsStatusLanPacketTransportEntryTxMulticasts OBJECT-TYPE
    SYNTAX     Counter32
    MAX-ACCESS read-only
    STATUS     current
    DESCRIPTION
        "-- empty --"
    ::= { lcsStatusLanPacketTransportEntry 8 }

-- {COLUMN} 1712.1.5.53.1.9
lcsStatusLanPacketTransportEntryTxUnicasts OBJECT-TYPE
    SYNTAX     Counter32
    MAX-ACCESS read-only
    STATUS     current
    DESCRIPTION
        "-- empty --"
    ::= { lcsStatusLanPacketTransportEntry 9 }

-- {TABLE} 1712.1.5.54
lcsStatusLanErrorsTable OBJECT-TYPE
    SYNTAX     SEQUENCE OF LcsStatusLanErrorsEntry
    MAX-ACCESS not-accessible
    STATUS     current
    DESCRIPTION
        "-- empty --"
    ::= { lcsStatusLan 54 }

-- {ENTRY} 1712.1.5.54.1
lcsStatusLanErrorsEntry OBJECT-TYPE
    SYNTAX     LcsStatusLanErrorsEntry
    MAX-ACCESS not-accessible
    STATUS     current
    DESCRIPTION
        ""
    INDEX {
        lcsStatusLanErrorsEntryIfc
    }
    ::= { lcsStatusLanErrorsTable 1 }

-- {SEQUENCE}
LcsStatusLanErrorsEntry ::= SEQUENCE {
    lcsStatusLanErrorsEntryIfc DisplayString,
    lcsStatusLanErrorsEntryRxErrors Counter32,
    lcsStatusLanErrorsEntryTxErrors Counter32,
    lcsStatusLanErrorsEntryStackErrors Counter32,
    lcsStatusLanErrorsEntryNicErrors Counter32,
    lcsStatusLanErrorsEntryQueueErrors Counter32,
    lcsStatusLanErrorsEntryRxCrcErrors Counter32,
    lcsStatusLanErrorsEntryCollisions Counter32,
    lcsStatusLanErrorsEntrySingleCollisions Counter32,
    lcsStatusLanErrorsEntryMultipleCollisions Counter32,
    lcsStatusLanErrorsEntryLateCollisions Counter32,
    lcsStatusLanErrorsEntryExcessiveCollisions Counter32,
    lcsStatusLanErrorsEntryRxAlignErrors Counter32,
    lcsStatusLanErrorsEntryRxTooShort Counter32,
    lcsStatusLanErrorsEntryRxTooLong Counter32,
    lcsStatusLanErrorsEntryTxCarrier Counter32,
    lcsStatusLanErrorsEntryTxDeferred Counter32,
    lcsStatusLanErrorsEntryRxPhyErrors Counter32,
    lcsStatusLanErrorsEntryRxDscrUnderflow Counter32,
    lcsStatusLanErrorsEntryRxFifoOverflow Counter32,
    lcsStatusLanErrorsEntryTxDiscarded Counter32
}

-- {COLUMN} 1712.1.5.54.1.1
lcsStatusLanErrorsEntryIfc OBJECT-TYPE
    SYNTAX     DisplayString (SIZE(0..255))
    MAX-ACCESS read-only
    STATUS     current
    DESCRIPTION
        "-- empty --"
    ::= { lcsStatusLanErrorsEntry 1 }

-- {COLUMN} 1712.1.5.54.1.2
lcsStatusLanErrorsEntryRxErrors OBJECT-TYPE
    SYNTAX     Counter32
    MAX-ACCESS read-only
    STATUS     current
    DESCRIPTION
        "-- empty --"
    ::= { lcsStatusLanErrorsEntry 2 }

-- {COLUMN} 1712.1.5.54.1.3
lcsStatusLanErrorsEntryTxErrors OBJECT-TYPE
    SYNTAX     Counter32
    MAX-ACCESS read-only
    STATUS     current
    DESCRIPTION
        "-- empty --"
    ::= { lcsStatusLanErrorsEntry 3 }

-- {COLUMN} 1712.1.5.54.1.4
lcsStatusLanErrorsEntryStackErrors OBJECT-TYPE
    SYNTAX     Counter32
    MAX-ACCESS read-only
    STATUS     current
    DESCRIPTION
        "-- empty --"
    ::= { lcsStatusLanErrorsEntry 4 }

-- {COLUMN} 1712.1.5.54.1.5
lcsStatusLanErrorsEntryNicErrors OBJECT-TYPE
    SYNTAX     Counter32
    MAX-ACCESS read-only
    STATUS     current
    DESCRIPTION
        "-- empty --"
    ::= { lcsStatusLanErrorsEntry 5 }

-- {COLUMN} 1712.1.5.54.1.6
lcsStatusLanErrorsEntryQueueErrors OBJECT-TYPE
    SYNTAX     Counter32
    MAX-ACCESS read-only
    STATUS     current
    DESCRIPTION
        "-- empty --"
    ::= { lcsStatusLanErrorsEntry 6 }

-- {COLUMN} 1712.1.5.54.1.7
lcsStatusLanErrorsEntryRxCrcErrors OBJECT-TYPE
    SYNTAX     Counter32
    MAX-ACCESS read-only
    STATUS     current
    DESCRIPTION
        "-- empty --"
    ::= { lcsStatusLanErrorsEntry 7 }

-- {COLUMN} 1712.1.5.54.1.8
lcsStatusLanErrorsEntryCollisions OBJECT-TYPE
    SYNTAX     Counter32
    MAX-ACCESS read-only
    STATUS     current
    DESCRIPTION
        "-- empty --"
    ::= { lcsStatusLanErrorsEntry 8 }

-- {COLUMN} 1712.1.5.54.1.9
lcsStatusLanErrorsEntrySingleCollisions OBJECT-TYPE
    SYNTAX     Counter32
    MAX-ACCESS read-only
    STATUS     current
    DESCRIPTION
        "-- empty --"
    ::= { lcsStatusLanErrorsEntry 9 }

-- {COLUMN} 1712.1.5.54.1.10
lcsStatusLanErrorsEntryMultipleCollisions OBJECT-TYPE
    SYNTAX     Counter32
    MAX-ACCESS read-only
    STATUS     current
    DESCRIPTION
        "-- empty --"
    ::= { lcsStatusLanErrorsEntry 10 }

-- {COLUMN} 1712.1.5.54.1.11
lcsStatusLanErrorsEntryLateCollisions OBJECT-TYPE
    SYNTAX     Counter32
    MAX-ACCESS read-only
    STATUS     current
    DESCRIPTION
        "-- empty --"
    ::= { lcsStatusLanErrorsEntry 11 }

-- {COLUMN} 1712.1.5.54.1.12
lcsStatusLanErrorsEntryExcessiveCollisions OBJECT-TYPE
    SYNTAX     Counter32
    MAX-ACCESS read-only
    STATUS     current
    DESCRIPTION
        "-- empty --"
    ::= { lcsStatusLanErrorsEntry 12 }

-- {COLUMN} 1712.1.5.54.1.13
lcsStatusLanErrorsEntryRxAlignErrors OBJECT-TYPE
    SYNTAX     Counter32
    MAX-ACCESS read-only
    STATUS     current
    DESCRIPTION
        "-- empty --"
    ::= { lcsStatusLanErrorsEntry 13 }

-- {COLUMN} 1712.1.5.54.1.14
lcsStatusLanErrorsEntryRxTooShort OBJECT-TYPE
    SYNTAX     Counter32
    MAX-ACCESS read-only
    STATUS     current
    DESCRIPTION
        "-- empty --"
    ::= { lcsStatusLanErrorsEntry 14 }

-- {COLUMN} 1712.1.5.54.1.15
lcsStatusLanErrorsEntryRxTooLong OBJECT-TYPE
    SYNTAX     Counter32
    MAX-ACCESS read-only
    STATUS     current
    DESCRIPTION
        "-- empty --"
    ::= { lcsStatusLanErrorsEntry 15 }

-- {COLUMN} 1712.1.5.54.1.16
lcsStatusLanErrorsEntryTxCarrier OBJECT-TYPE
    SYNTAX     Counter32
    MAX-ACCESS read-only
    STATUS     current
    DESCRIPTION
        "-- empty --"
    ::= { lcsStatusLanErrorsEntry 16 }

-- {COLUMN} 1712.1.5.54.1.17
lcsStatusLanErrorsEntryTxDeferred OBJECT-TYPE
    SYNTAX     Counter32
    MAX-ACCESS read-only
    STATUS     current
    DESCRIPTION
        "-- empty --"
    ::= { lcsStatusLanErrorsEntry 17 }

-- {COLUMN} 1712.1.5.54.1.18
lcsStatusLanErrorsEntryRxPhyErrors OBJECT-TYPE
    SYNTAX     Counter32
    MAX-ACCESS read-only
    STATUS     current
    DESCRIPTION
        "-- empty --"
    ::= { lcsStatusLanErrorsEntry 18 }

-- {COLUMN} 1712.1.5.54.1.21
lcsStatusLanErrorsEntryRxDscrUnderflow OBJECT-TYPE
    SYNTAX     Counter32
    MAX-ACCESS read-only
    STATUS     current
    DESCRIPTION
        "-- empty --"
    ::= { lcsStatusLanErrorsEntry 21 }

-- {COLUMN} 1712.1.5.54.1.19
lcsStatusLanErrorsEntryRxFifoOverflow OBJECT-TYPE
    SYNTAX     Counter32
    MAX-ACCESS read-only
    STATUS     current
    DESCRIPTION
        "-- empty --"
    ::= { lcsStatusLanErrorsEntry 19 }

-- {COLUMN} 1712.1.5.54.1.20
lcsStatusLanErrorsEntryTxDiscarded OBJECT-TYPE
    SYNTAX     Counter32
    MAX-ACCESS read-only
    STATUS     current
    DESCRIPTION
        "-- empty --"
    ::= { lcsStatusLanErrorsEntry 20 }

-- {TABLE} 1712.1.5.90
lcsStatusLanStationTableTable OBJECT-TYPE
    SYNTAX     SEQUENCE OF LcsStatusLanStationTableEntry
    MAX-ACCESS not-accessible
    STATUS     current
    DESCRIPTION
        "-- empty --"
    ::= { lcsStatusLan 90 }

-- {ENTRY} 1712.1.5.90.1
lcsStatusLanStationTableEntry OBJECT-TYPE
    SYNTAX     LcsStatusLanStationTableEntry
    MAX-ACCESS not-accessible
    STATUS     current
    DESCRIPTION
        ""
    INDEX {
        lcsStatusLanStationTableEntryInterface,
        lcsStatusLanStationTableEntryMacAddress
    }
    ::= { lcsStatusLanStationTableTable 1 }

-- {SEQUENCE}
LcsStatusLanStationTableEntry ::= SEQUENCE {
    lcsStatusLanStationTableEntryInterface INTEGER,
    lcsStatusLanStationTableEntryMacAddress MacAddress,
    lcsStatusLanStationTableEntryTxLimit INTEGER,
    lcsStatusLanStationTableEntryRxLimit INTEGER,
    lcsStatusLanStationTableEntryVlanId INTEGER,
    lcsStatusLanStationTableEntryOrigVlanId INTEGER
}

-- {COLUMN} 1712.1.5.90.1.2
lcsStatusLanStationTableEntryInterface OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusLanStationTableEntry 2 }

-- {COLUMN} 1712.1.5.90.1.1
lcsStatusLanStationTableEntryMacAddress OBJECT-TYPE
    SYNTAX     MacAddress
    MAX-ACCESS read-only
    STATUS     current
    DESCRIPTION
        "-- empty --"
    ::= { lcsStatusLanStationTableEntry 1 }

-- {COLUMN} 1712.1.5.90.1.3
lcsStatusLanStationTableEntryTxLimit OBJECT-TYPE
    SYNTAX     INTEGER (0..2147483647)
    MAX-ACCESS read-only
    STATUS     current
    DESCRIPTION
        "-- empty --"
    ::= { lcsStatusLanStationTableEntry 3 }

-- {COLUMN} 1712.1.5.90.1.4
lcsStatusLanStationTableEntryRxLimit OBJECT-TYPE
    SYNTAX     INTEGER (0..2147483647)
    MAX-ACCESS read-only
    STATUS     current
    DESCRIPTION
        "-- empty --"
    ::= { lcsStatusLanStationTableEntry 4 }

-- {COLUMN} 1712.1.5.90.1.5
lcsStatusLanStationTableEntryVlanId OBJECT-TYPE
    SYNTAX     INTEGER (0..65535)
    MAX-ACCESS read-only
    STATUS     current
    DESCRIPTION
        "-- empty --"
    ::= { lcsStatusLanStationTableEntry 5 }

-- {COLUMN} 1712.1.5.90.1.6
lcsStatusLanStationTableEntryOrigVlanId OBJECT-TYPE
    SYNTAX     INTEGER (0..65535)
    MAX-ACCESS read-only
    STATUS     current
    DESCRIPTION
        "-- empty --"
    ::= { lcsStatusLanStationTableEntry 6 }

-- {OID} 1712.1.6
lcsStatusPpp OBJECT IDENTIFIER ::= { lcsStatus 6 }

-- {TABLE} 1712.1.6.1
lcsStatusPppPppPhasesTable OBJECT-TYPE
    SYNTAX     SEQUENCE OF LcsStatusPppPppPhasesEntry
    MAX-ACCESS not-accessible
    STATUS     current
    DESCRIPTION
        "-- empty --"
    ::= { lcsStatusPpp 1 }

-- {ENTRY} 1712.1.6.1.1
lcsStatusPppPppPhasesEntry OBJECT-TYPE
    SYNTAX     LcsStatusPppPppPhasesEntry
    MAX-ACCESS not-accessible
    STATUS     current
    DESCRIPTION
        ""
    INDEX {
        lcsStatusPppPppPhasesEntryIfc
    }
    ::= { lcsStatusPppPppPhasesTable 1 }

-- {SEQUENCE}
LcsStatusPppPppPhasesEntry ::= SEQUENCE {
    lcsStatusPppPppPhasesEntryIfc INTEGER,
    lcsStatusPppPppPhasesEntryPhase INTEGER,
    lcsStatusPppPppPhasesEntryLcp INTEGER,
    lcsStatusPppPppPhasesEntryIpcp INTEGER,
    lcsStatusPppPppPhasesEntryCcp INTEGER,
    lcsStatusPppPppPhasesEntryBacp INTEGER,
    lcsStatusPppPppPhasesEntryIpv6cp INTEGER
}

-- {COLUMN} 1712.1.6.1.1.1
lcsStatusPppPppPhasesEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppPppPhasesEntry 1 }

-- {COLUMN} 1712.1.6.1.1.2
lcsStatusPppPppPhasesEntryPhase OBJECT-TYPE
    SYNTAX     INTEGER
      {
        eDead (1),
        eEstablish (2),
        eTerminate (3),
        eAuthenticate (4),
        eCallback (5),
        eNetwork (6)
      }
    MAX-ACCESS read-only
    STATUS     current
    DESCRIPTION
        "-- empty --"
    ::= { lcsStatusPppPppPhasesEntry 2 }

-- {COLUMN} 1712.1.6.1.1.3
lcsStatusPppPppPhasesEntryLcp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 3 }

-- {COLUMN} 1712.1.6.1.1.4
lcsStatusPppPppPhasesEntryIpcp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 4 }

-- {COLUMN} 1712.1.6.1.1.6
lcsStatusPppPppPhasesEntryCcp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 6 }

-- {COLUMN} 1712.1.6.1.1.7
lcsStatusPppPppPhasesEntryBacp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 7 }

-- {COLUMN} 1712.1.6.1.1.8
lcsStatusPppPppPhasesEntryIpv6cp OBJECT-TYPE
    SYNTAX     INTEGER
      {
        eInitial (1),
        eStartng (2),
        eClosed (3),
        eStopped (4),
        eClosing (5),
        eStoppng (6),
        eReqsent (7),
        eAckrcvd (8),
        eAcksent (9),
        eOpened (10)
      }
    MAX-ACCESS read-only
    STATUS     current
    DESCRIPTION
        "-- empty --"
    ::= { lcsStatusPppPppPhasesEntry 8 }

-- {OID} 1712.1.6.2
lcsStatusPppLcp OBJECT IDENTIFIER ::= { lcsStatusPpp 2 }

-- {SCALAR} 1712.1.6.2.1
lcsStatusPppLcpRxErrors OBJECT-TYPE
    SYNTAX     Counter32
    MAX-ACCESS read-only
    STATUS     current
    DESCRIPTION
        "-- empty --"
    ::= { lcsStatusPppLcp 1 }

-- {SCALAR} 1712.1.6.2.2
lcsStatusPppLcpRxDiscarded OBJECT-TYPE
    SYNTAX     Counter32
    MAX-ACCESS read-only
    STATUS     current
    DESCRIPTION
        "-- empty --"
    ::= { lcsStatusPppLcp 2 }

-- {SCALAR} 1712.1.6.2.3
lcsStatusPppLcpRxConfigRequest OBJECT-TYPE
    SYNTAX     Counter32
    MAX-ACCESS read-only
    STATUS     current
    DESCRIPTION
        "-- empty --"
    ::= { lcsStatusPppLcp 3 }

-- {SCALAR} 1712.1.6.2.4
lcsStatusPppLcpRxConfigAck OBJECT-TYPE
    SYNTAX     Counter32
    MAX-ACCESS read-only
    STATUS     current
    DESCRIPTION
        "-- empty --"
    ::= { lcsStatusPppLcp 4 }

-- {SCALAR} 1712.1.6.2.5
lcsStatusPppLcpRxConfigNak OBJECT-TYPE
    SYNTAX     Counter32
    MAX-ACCESS read-only
    STATUS     current
    DESCRIPTION
        "-- empty --"
    ::= { lcsStatusPppLcp 5 }

-- {SCALAR} 1712.1.6.2.6
lcsStatusPppLcpRxConfigReject OBJECT-TYPE
    SYNTAX     Counter32
    MAX-ACCESS read-only
    STATUS     current
    DESCRIPTION
        "-- empty --"
    ::= { lcsStatusPppLcp 6 }

-- {SCALAR} 1712.1.6.2.7
lcsStatusPppLcpRxTerminateRequest OBJECT-TYPE
    SYNTAX     Counter32
    MAX-ACCESS read-only
    STATUS     current
    DESCRIPTION
        "-- empty --"
    ::= { lcsStatusPppLcp 7 }

-- {SCALAR} 1712.1.6.2.8
lcsStatusPppLcpRxTerminateAck OBJECT-TYPE
    SYNTAX     Counter32
    MAX-ACCESS read-only
    STATUS     current
    DESCRIPTION
        "-- empty --"
    ::= { lcsStatusPppLcp 8 }

-- {SCALAR} 1712.1.6.2.9
lcsStatusPppLcpRxCodeReject OBJECT-TYPE
    SYNTAX     Counter32
    MAX-ACCESS read-only
    STATUS     current
    DESCRIPTION
        "-- empty --"
    ::= { lcsStatusPppLcp 9 }

-- {SCALAR} 1712.1.6.2.10
lcsStatusPppLcpRxProtocolReject OBJECT-TYPE
    SYNTAX     Counter32
    MAX-ACCESS read-only
    STATUS     current
    DESCRIPTION
        "-- empty --"
    ::= { lcsStatusPppLcp 10 }

-- {SCALAR} 1712.1.6.2.11
lcsStatusPppLcpRxEchoRequest OBJECT-TYPE
    SYNTAX     Counter32
    MAX-ACCESS read-only
    STATUS     current
    DESCRIPTION
        "-- empty --"
    ::= { lcsStatusPppLcp 11 }

-- {SCALAR} 1712.1.6.2.12
lcsStatusPppLcpRxEchoReply OBJECT-TYPE
    SYNTAX     Counter32
    MAX-ACCESS read-only
    STATUS     current
    DESCRIPTION
        "-- empty --"
    ::= { lcsStatusPppLcp 12 }

-- {SCALAR} 1712.1.6.2.13
lcsStatusPppLcpRxDiscardRequest OBJECT-TYPE
    SYNTAX     Counter32
    MAX-ACCESS read-only
    STATUS     current
    DESCRIPTION
        "-- empty --"
    ::= { lcsStatusPppLcp 13 }

-- {SCALAR} 1712.1.6.2.14
lcsStatusPppLcpTxConfigRequest OBJECT-TYPE
    SYNTAX     Counter32
    MAX-ACCESS read-only
    STATUS     current
    DESCRIPTION
        "-- empty --"
    ::= { lcsStatusPppLcp 14 }

-- {SCALAR} 1712.1.6.2.15
lcsStatusPppLcpTxConfigAck OBJECT-TYPE
    SYNTAX     Counter32
    MAX-ACCESS read-only
    STATUS     current
    DESCRIPTION
        "-- empty --"
    ::= { lcsStatusPppLcp 15 }

-- {SCALAR} 1712.1.6.2.16
lcsStatusPppLcpTxConfigNak OBJECT-TYPE
    SYNTAX     Counter32
    MAX-ACCESS read-only
    STATUS     current
    DESCRIPTION
        "-- empty --"
    ::= { lcsStatusPppLcp 16 }

-- {SCALAR} 1712.1.6.2.17
lcsStatusPppLcpTxConfigReject OBJECT-TYPE
    SYNTAX     Counter32
    MAX-ACCESS read-only
    STATUS     current
    DESCRIPTION
        "-- empty --"
    ::= { lcsStatusPppLcp 17 }

-- {SCALAR} 1712.1.6.2.18
lcsStatusPppLcpTxTerminateRequest OBJECT-TYPE
    SYNTAX     Counter32
    MAX-ACCESS read-only
    STATUS     current
    DESCRIPTION
        "-- empty --"
    ::= { lcsStatusPppLcp 18 }

-- {SCALAR} 1712.1.6.2.19
lcsStatusPppLcpTxTerminateAck OBJECT-TYPE
    SYNTAX     Counter32
    MAX-ACCESS read-only
    STATUS     current
    DESCRIPTION
        "-- empty --"
    ::= { lcsStatusPppLcp 19 }

-- {SCALAR} 1712.1.6.2.20
lcsStatusPppLcpTxCodeReject OBJECT-TYPE
    SYNTAX     Counter32
    MAX-ACCESS read-only
    STATUS     current
    DESCRIPTION
        "-- empty --"
    ::= { lcsStatusPppLcp 20 }

-- {SCALAR} 1712.1.6.2.21
lcsStatusPppLcpTxProtocolReject OBJECT-TYPE
    SYNTAX     Counter32
    MAX-ACCESS read-only
    STATUS     current
    DESCRIPTION
        "-- empty --"
    ::= { lcsStatusPppLcp 21 }

-- {SCALAR} 1712.1.6.2.22
lcsStatusPppLcpTxEchoRequest OBJECT-TYPE
    SYNTAX     Counter32
    MAX-ACCESS read-only
    STATUS     current
    DESCRIPTION
        "-- empty --"
    ::= { lcsStatusPppLcp 22 }

-- {SCALAR} 1712.1.6.2.23
lcsStatusPppLcpTxEchoReply OBJECT-TYPE
    SYNTAX     Counter32
    MAX-ACCESS read-only
    STATUS     current
    DESCRIPTION
        "-- empty --"
    ::= { lcsStatusPppLcp 23 }

-- {SCALAR} 1712.1.6.2.24
lcsStatusPppLcpTxDiscardRequest OBJECT-TYPE
    SYNTAX     Counter32
    MAX-ACCESS read-only
    STATUS     current
    DESCRIPTION
        "-- empty --"
    ::= { lcsStatusPppLcp 24 }

-- {SCALAR} 1712.1.6.2.25
lcsStatusPppLcpDeleteValues OBJECT-TYPE
    SYNTAX     DisplayString
    MAX-ACCESS read-write
    STATUS     current
    DESCRIPTION
        "-- empty --"
    ::= { lcsStatusPppLcp 25 }

-- {OID} 1712.1.6.3
lcsStatusPppPap OBJECT IDENTIFIER ::= { lcsStatusPpp 3 }

-- {SCALAR} 1712.1.6.3.1
lcsStatusPppPapRxDiscarded OBJECT-TYPE
    SYNTAX     Counter32
    MAX-ACCESS read-only
    STATUS     current
    DESCRIPTION
        "-- empty --"
    ::= { lcsStatusPppPap 1 }

-- {SCALAR} 1712.1.6.3.2
lcsStatusPppPapRxRequest OBJECT-TYPE
    SYNTAX     Counter32
    MAX-ACCESS read-only
    STATUS     current
    DESCRIPTION
        "-- empty --"
    ::= { lcsStatusPppPap 2 }

-- {SCALAR} 1712.1.6.3.3
lcsStatusPppPapRxSuccess OBJECT-TYPE
    SYNTAX     Counter32
    MAX-ACCESS read-only
    STATUS     current
    DESCRIPTION
        "-- empty --"
    ::= { lcsStatusPppPap 3 }

-- {SCALAR} 1712.1.6.3.4
lcsStatusPppPapRxFailure OBJECT-TYPE
    SYNTAX     Counter32
    MAX-ACCESS read-only
    STATUS     current
    DESCRIPTION
        "-- empty --"
    ::= { lcsStatusPppPap 4 }

-- {SCALAR} 1712.1.6.3.5
lcsStatusPppPapTxRetry OBJECT-TYPE
    SYNTAX     Counter32
    MAX-ACCESS read-only
    STATUS     current
    DESCRIPTION
        "-- empty --"
    ::= { lcsStatusPppPap 5 }

-- {SCALAR} 1712.1.6.3.6
lcsStatusPppPapTxRequest OBJECT-TYPE
    SYNTAX     Counter32
    MAX-ACCESS read-only
    STATUS     current
    DESCRIPTION
        "-- empty --"
    ::= { lcsStatusPppPap 6 }

-- {SCALAR} 1712.1.6.3.7
lcsStatusPppPapTxSuccess OBJECT-TYPE
    SYNTAX     Counter32
    MAX-ACCESS read-only
    STATUS     current
    DESCRIPTION
        "-- empty --"
    ::= { lcsStatusPppPap 7 }

-- {SCALAR} 1712.1.6.3.8
lcsStatusPppPapTxFailure OBJECT-TYPE
    SYNTAX     Counter32
    MAX-ACCESS read-only
    STATUS     current
    DESCRIPTION
        "-- empty --"
    ::= { lcsStatusPppPap 8 }

-- {SCALAR} 1712.1.6.3.9
lcsStatusPppPapDeleteValues OBJECT-TYPE
    SYNTAX     DisplayString
    MAX-ACCESS read-write
    STATUS     current
    DESCRIPTION
        "-- empty --"
    ::= { lcsStatusPppPap 9 }

-- {OID} 1712.1.6.4
lcsStatusPppChap OBJECT IDENTIFIER ::= { lcsStatusPpp 4 }

-- {SCALAR} 1712.1.6.4.1
lcsStatusPppChapRxDiscarded OBJECT-TYPE
    SYNTAX     Counter32
    MAX-ACCESS read-only
    STATUS     current
    DESCRIPTION
        "-- empty --"
    ::= { lcsStatusPppChap 1 }

-- {SCALAR} 1712.1.6.4.2
lcsStatusPppChapRxChallenge OBJECT-TYPE
    SYNTAX     Counter32
    MAX-ACCESS read-only
    STATUS     current
    DESCRIPTION
        "-- empty --"
    ::= { lcsStatusPppChap 2 }

-- {SCALAR} 1712.1.6.4.3
lcsStatusPppChapRxResponse OBJECT-TYPE
    SYNTAX     Counter32
    MAX-ACCESS read-only
    STATUS     current
    DESCRIPTION
        "-- empty --"
    ::= { lcsStatusPppChap 3 }

-- {SCALAR} 1712.1.6.4.4
lcsStatusPppChapRxSuccess OBJECT-TYPE
    SYNTAX     Counter32
    MAX-ACCESS read-only
    STATUS     current
    DESCRIPTION
        "-- empty --"
    ::= { lcsStatusPppChap 4 }

-- {SCALAR} 1712.1.6.4.5
lcsStatusPppChapRxFailure OBJECT-TYPE
    SYNTAX     Counter32
    MAX-ACCESS read-only
    STATUS     current
    DESCRIPTION
        "-- empty --"
    ::= { lcsStatusPppChap 5 }

-- {SCALAR} 1712.1.6.4.6
lcsStatusPppChapTxRetry OBJECT-TYPE
    SYNTAX     Counter32
    MAX-ACCESS read-only
    STATUS     current
    DESCRIPTION
        "-- empty --"
    ::= { lcsStatusPppChap 6 }

-- {SCALAR} 1712.1.6.4.7
lcsStatusPppChapTxChallenge OBJECT-TYPE
    SYNTAX     Counter32
    MAX-ACCESS read-only
    STATUS     current
    DESCRIPTION
        "-- empty --"
    ::= { lcsStatusPppChap 7 }

-- {SCALAR} 1712.1.6.4.8
lcsStatusPppChapTxResponse OBJECT-TYPE
    SYNTAX     Counter32
    MAX-ACCESS read-only
    STATUS     current
    DESCRIPTION
        "-- empty --"
    ::= { lcsStatusPppChap 8 }

-- {SCALAR} 1712.1.6.4.9
lcsStatusPppChapTxSuccess OBJECT-TYPE
    SYNTAX     Counter32
    MAX-ACCESS read-only
    STATUS     current
    DESCRIPTION
        "-- empty --"
    ::= { lcsStatusPppChap 9 }

-- {SCALAR} 1712.1.6.4.10
lcsStatusPppChapTxFailure OBJECT-TYPE
    SYNTAX     Counter32
    MAX-ACCESS read-only
    STATUS     current
    DESCRIPTION
        "-- empty --"
    ::= { lcsStatusPppChap 10 }

-- {SCALAR} 1712.1.6.4.11
lcsStatusPppChapDeleteValues OBJECT-TYPE
    SYNTAX     DisplayString
    MAX-ACCESS read-write
    STATUS     current
    DESCRIPTION
        "-- empty --"
    ::= { lcsStatusPppChap 11 }

-- {OID} 1712.1.6.7
lcsStatusPppCbcp OBJECT IDENTIFIER ::= { lcsStatusPpp 7 }

-- {SCALAR} 1712.1.6.7.1
lcsStatusPppCbcpRxDiscarded OBJECT-TYPE
    SYNTAX     Counter32
    MAX-ACCESS read-only
    STATUS     current
    DESCRIPTION
        "-- empty --"
    ::= { lcsStatusPppCbcp 1 }

-- {SCALAR} 1712.1.6.7.2
lcsStatusPppCbcpRxRequest OBJECT-TYPE
    SYNTAX     Counter32
    MAX-ACCESS read-only
    STATUS     current
    DESCRIPTION
        "-- empty --"
    ::= { lcsStatusPppCbcp 2 }

-- {SCALAR} 1712.1.6.7.3
lcsStatusPppCbcpRxResponse OBJECT-TYPE
    SYNTAX     Counter32
    MAX-ACCESS read-only
    STATUS     current
    DESCRIPTION
        "-- empty --"
    ::= { lcsStatusPppCbcp 3 }

-- {SCALAR} 1712.1.6.7.4
lcsStatusPppCbcpRxAcknowledge OBJECT-TYPE
    SYNTAX     Counter32
    MAX-ACCESS read-only
    STATUS     current
    DESCRIPTION
        "-- empty --"
    ::= { lcsStatusPppCbcp 4 }

-- {SCALAR} 1712.1.6.7.5
lcsStatusPppCbcpTxRequest OBJECT-TYPE
    SYNTAX     Counter32
    MAX-ACCESS read-only
    STATUS     current
    DESCRIPTION
        "-- empty --"
    ::= { lcsStatusPppCbcp 5 }

-- {SCALAR} 1712.1.6.7.6
lcsStatusPppCbcpTxResponse OBJECT-TYPE
    SYNTAX     Counter32
    MAX-ACCESS read-only
    STATUS     current
    DESCRIPTION
        "-- empty --"
    ::= { lcsStatusPppCbcp 6 }

-- {SCALAR} 1712.1.6.7.7
lcsStatusPppCbcpTxAcknowledge OBJECT-TYPE
    SYNTAX     Counter32
    MAX-ACCESS read-only
    STATUS     current
    DESCRIPTION
        "-- empty --"
    ::= { lcsStatusPppCbcp 7 }

-- {SCALAR} 1712.1.6.7.8
lcsStatusPppCbcpDeleteValues OBJECT-TYPE
    SYNTAX     DisplayString
    MAX-ACCESS read-write
    STATUS     current
    DESCRIPTION
        "-- empty --"
    ::= { lcsStatusPppCbcp 8 }

-- {OID} 1712.1.6.6
lcsStatusPppIpcp OBJECT IDENTIFIER ::= { lcsStatusPpp 6 }

-- {SCALAR} 1712.1.6.6.1
lcsStatusPppIpcpRxDiscarded OBJECT-TYPE
    SYNTAX     Counter32
    MAX-ACCESS read-only
    STATUS     current
    DESCRIPTION
        "-- empty --"
    ::= { lcsStatusPppIpcp 1 }

-- {SCALAR} 1712.1.6.6.2
lcsStatusPppIpcpRxConfigRequest OBJECT-TYPE
    SYNTAX     Counter32
    MAX-ACCESS read-only
    STATUS     current
    DESCRIPTION
        "-- empty --"
    ::= { lcsStatusPppIpcp 2 }

-- {SCALAR} 1712.1.6.6.3
lcsStatusPppIpcpRxConfigAck OBJECT-TYPE
    SYNTAX     Counter32
    MAX-ACCESS read-only
    STATUS     current
    DESCRIPTION
        "-- empty --"
    ::= { lcsStatusPppIpcp 3 }

-- {SCALAR} 1712.1.6.6.4
lcsStatusPppIpcpRxConfigNak OBJECT-TYPE
    SYNTAX     Counter32
    MAX-ACCESS read-only
    STATUS     current
    DESCRIPTION
        "-- empty --"
    ::= { lcsStatusPppIpcp 4 }

-- {SCALAR} 1712.1.6.6.5
lcsStatusPppIpcpRxConfigReject OBJECT-TYPE
    SYNTAX     Counter32
    MAX-ACCESS read-only
    STATUS     current
    DESCRIPTION
        "-- empty --"
    ::= { lcsStatusPppIpcp 5 }

-- {SCALAR} 1712.1.6.6.6
lcsStatusPppIpcpRxTerminateRequest OBJECT-TYPE
    SYNTAX     Counter32
    MAX-ACCESS read-only
    STATUS     current
    DESCRIPTION
        "-- empty --"
    ::= { lcsStatusPppIpcp 6 }

-- {SCALAR} 1712.1.6.6.7
lcsStatusPppIpcpRxTerminateAck OBJECT-TYPE
    SYNTAX     Counter32
    MAX-ACCESS read-only
    STATUS     current
    DESCRIPTION
        "-- empty --"
    ::= { lcsStatusPppIpcp 7 }

-- {SCALAR} 1712.1.6.6.8
lcsStatusPppIpcpRxCodeReject OBJECT-TYPE
    SYNTAX     Counter32
    MAX-ACCESS read-only
    STATUS     current
    DESCRIPTION
        "-- empty --"
    ::= { lcsStatusPppIpcp 8 }

-- {SCALAR} 1712.1.6.6.9
lcsStatusPppIpcpTxConfigRequest OBJECT-TYPE
    SYNTAX     Counter32
    MAX-ACCESS read-only
    STATUS     current
    DESCRIPTION
        "-- empty --"
    ::= { lcsStatusPppIpcp 9 }

-- {SCALAR} 1712.1.6.6.10
lcsStatusPppIpcpTxConfigAck OBJECT-TYPE
    SYNTAX     Counter32
    MAX-ACCESS read-only
    STATUS     current
    DESCRIPTION
        "-- empty --"
    ::= { lcsStatusPppIpcp 10 }

-- {SCALAR} 1712.1.6.6.11
lcsStatusPppIpcpTxConfigNak OBJECT-TYPE
    SYNTAX     Counter32
    MAX-ACCESS read-only
    STATUS     current
    DESCRIPTION
        "-- empty --"
    ::= { lcsStatusPppIpcp 11 }

-- {SCALAR} 1712.1.6.6.12
lcsStatusPppIpcpTxConfigReject OBJECT-TYPE
    SYNTAX     Counter32
    MAX-ACCESS read-only
    STATUS     current
    DESCRIPTION
        "-- empty --"
    ::= { lcsStatusPppIpcp 12 }

-- {SCALAR} 1712.1.6.6.13
lcsStatusPppIpcpTxTerminateRequest OBJECT-TYPE
    SYNTAX     Counter32
    MAX-ACCESS read-only
    STATUS     current
    DESCRIPTION
        "-- empty --"
    ::= { lcsStatusPppIpcp 13 }

-- {SCALAR} 1712.1.6.6.14
lcsStatusPppIpcpTxTerminateAck OBJECT-TYPE
    SYNTAX     Counter32
    MAX-ACCESS read-only
    STATUS     current
    DESCRIPTION
        "-- empty --"
    ::= { lcsStatusPppIpcp 14 }

-- {SCALAR} 1712.1.6.6.15
lcsStatusPppIpcpTxCodeReject OBJECT-TYPE
    SYNTAX     Counter32
    MAX-ACCESS read-only
    STATUS     current
    DESCRIPTION
        "-- empty --"
    ::= { lcsStatusPppIpcp 15 }

-- {SCALAR} 1712.1.6.6.16
lcsStatusPppIpcpDeleteValues OBJECT-TYPE
    SYNTAX     DisplayString
    MAX-ACCESS read-write
    STATUS     current
    DESCRIPTION
        "-- empty --"
    ::= { lcsStatusPppIpcp 16 }

-- {OID} 1712.1.6.10
lcsStatusPppCcp OBJECT IDENTIFIER ::= { lcsStatusPpp 10 }

-- {SCALAR} 1712.1.6.10.1
lcsStatusPppCcpRxDiscarded OBJECT-TYPE
    SYNTAX     Counter32
    MAX-ACCESS read-only
    STATUS     current
    DESCRIPTION
        "-- empty --"
    ::= { lcsStatusPppCcp 1 }

-- {SCALAR} 1712.1.6.10.2
lcsStatusPppCcpRxConfigRequest OBJECT-TYPE
    SYNTAX     Counter32
    MAX-ACCESS read-only
    STATUS     current
    DESCRIPTION
        "-- empty --"
    ::= { lcsStatusPppCcp 2 }

-- {SCALAR} 1712.1.6.10.3
lcsStatusPppCcpRxConfigAck OBJECT-TYPE
    SYNTAX     Counter32
    MAX-ACCESS read-only
    STATUS     current
    DESCRIPTION
        "-- empty --"
    ::= { lcsStatusPppCcp 3 }

-- {SCALAR} 1712.1.6.10.4
lcsStatusPppCcpRxConfigNak OBJECT-TYPE
    SYNTAX     Counter32
    MAX-ACCESS read-only
    STATUS     current
    DESCRIPTION
        "-- empty --"
    ::= { lcsStatusPppCcp 4 }

-- {SCALAR} 1712.1.6.10.5
lcsStatusPppCcpRxConfigReject OBJECT-TYPE
    SYNTAX     Counter32
    MAX-ACCESS read-only
    STATUS     current
    DESCRIPTION
        "-- empty --"
    ::= { lcsStatusPppCcp 5 }

-- {SCALAR} 1712.1.6.10.6
lcsStatusPppCcpRxTerminateRequest OBJECT-TYPE
    SYNTAX     Counter32
    MAX-ACCESS read-only
    STATUS     current
    DESCRIPTION
        "-- empty --"
    ::= { lcsStatusPppCcp 6 }

-- {SCALAR} 1712.1.6.10.7
lcsStatusPppCcpRxTerminateAck OBJECT-TYPE
    SYNTAX     Counter32
    MAX-ACCESS read-only
    STATUS     current
    DESCRIPTION
        "-- empty --"
    ::= { lcsStatusPppCcp 7 }

-- {SCALAR} 1712.1.6.10.8
lcsStatusPppCcpRxCodeReject OBJECT-TYPE
    SYNTAX     Counter32
    MAX-ACCESS read-only
    STATUS     current
    DESCRIPTION
        "-- empty --"
    ::= { lcsStatusPppCcp 8 }

-- {SCALAR} 1712.1.6.10.9
lcsStatusPppCcpRxResetRequest OBJECT-TYPE
    SYNTAX     Counter32
    MAX-ACCESS read-only
    STATUS     current
    DESCRIPTION
        "-- empty --"
    ::= { lcsStatusPppCcp 9 }

-- {SCALAR} 1712.1.6.10.10
lcsStatusPppCcpRxResetAck OBJECT-TYPE
    SYNTAX     Counter32
    MAX-ACCESS read-only
    STATUS     current
    DESCRIPTION
        "-- empty --"
    ::= { lcsStatusPppCcp 10 }

-- {SCALAR} 1712.1.6.10.11
lcsStatusPppCcpTxConfigRequest OBJECT-TYPE
    SYNTAX     Counter32
    MAX-ACCESS read-only
    STATUS     current
    DESCRIPTION
        "-- empty --"
    ::= { lcsStatusPppCcp 11 }

-- {SCALAR} 1712.1.6.10.12
lcsStatusPppCcpTxConfigAck OBJECT-TYPE
    SYNTAX     Counter32
    MAX-ACCESS read-only
    STATUS     current
    DESCRIPTION
        "-- empty --"
    ::= { lcsStatusPppCcp 12 }

-- {SCALAR} 1712.1.6.10.13
lcsStatusPppCcpTxConfigNak OBJECT-TYPE
    SYNTAX     Counter32
    MAX-ACCESS read-only
    STATUS     current
    DESCRIPTION
        "-- empty --"
    ::= { lcsStatusPppCcp 13 }

-- {SCALAR} 1712.1.6.10.14
lcsStatusPppCcpTxConfigReject OBJECT-TYPE
    SYNTAX     Counter32
    MAX-ACCESS read-only
    STATUS     current
    DESCRIPTION
        "-- empty --"
    ::= { lcsStatusPppCcp 14 }

-- {SCALAR} 1712.1.6.10.15
lcsStatusPppCcpTxTerminateRequest OBJECT-TYPE
    SYNTAX     Counter32
    MAX-ACCESS read-only
    STATUS     current
    DESCRIPTION
        "-- empty --"
    ::= { lcsStatusPppCcp 15 }

-- {SCALAR} 1712.1.6.10.16
lcsStatusPppCcpTxTerminateAck OBJECT-TYPE
    SYNTAX     Counter32
    MAX-ACCESS read-only
    STATUS     current
    DESCRIPTION
        "-- empty --"
    ::= { lcsStatusPppCcp 16 }

-- {SCALAR} 1712.1.6.10.17
lcsStatusPppCcpTxCodeReject OBJECT-TYPE
    SYNTAX     Counter32
    MAX-ACCESS read-only
    STATUS     current
    DESCRIPTION
        "-- empty --"
    ::= { lcsStatusPppCcp 17 }

-- {SCALAR} 1712.1.6.10.19
lcsStatusPppCcpTxResetRequest OBJECT-TYPE
    SYNTAX     Counter32
    MAX-ACCESS read-only
    STATUS     current
    DESCRIPTION
        "-- empty --"
    ::= { lcsStatusPppCcp 19 }

-- {SCALAR} 1712.1.6.10.20
lcsStatusPppCcpTxResetAck OBJECT-TYPE
    SYNTAX     Counter32
    MAX-ACCESS read-only
    STATUS     current
    DESCRIPTION
        "-- empty --"
    ::= { lcsStatusPppCcp 20 }

-- {SCALAR} 1712.1.6.10.22
lcsStatusPppCcpCompressionErrors OBJECT-TYPE
    SYNTAX     Counter32
    MAX-ACCESS read-only
    STATUS     current
    DESCRIPTION
        "-- empty --"
    ::= { lcsStatusPppCcp 22 }

-- {SCALAR} 1712.1.6.10.21
lcsStatusPppCcpDeleteValues OBJECT-TYPE
    SYNTAX     DisplayString
    MAX-ACCESS read-write
    STATUS     current
    DESCRIPTION
        "-- empty --"
    ::= { lcsStatusPppCcp 21 }

-- {OID} 1712.1.6.11
lcsStatusPppMl OBJECT IDENTIFIER ::= { lcsStatusPpp 11 }

-- {SCALAR} 1712.1.6.11.1
lcsStatusPppMlBundleConnections OBJECT-TYPE
    SYNTAX     INTEGER (0..2147483647)
    MAX-ACCESS read-only
    STATUS     current
    DESCRIPTION
        "-- empty --"
    ::= { lcsStatusPppMl 1 }

-- {SCALAR} 1712.1.6.11.2
lcsStatusPppMlRxSeqLost OBJECT-TYPE
    SYNTAX     Counter32
    MAX-ACCESS read-only
    STATUS     current
    DESCRIPTION
        "-- empty --"
    ::= { lcsStatusPppMl 2 }

-- {SCALAR} 1712.1.6.11.3
lcsStatusPppMlRxSeqRepeat OBJECT-TYPE
    SYNTAX     Counter32
    MAX-ACCESS read-only
    STATUS     current
    DESCRIPTION
        "-- empty --"
    ::= { lcsStatusPppMl 3 }

-- {SCALAR} 1712.1.6.11.4
lcsStatusPppMlRxMrruExceeded OBJECT-TYPE
    SYNTAX     Counter32
    MAX-ACCESS read-only
    STATUS     current
    DESCRIPTION
        "-- empty --"
    ::= { lcsStatusPppMl 4 }

-- {SCALAR} 1712.1.6.11.5
lcsStatusPppMlRxHeaderError OBJECT-TYPE
    SYNTAX     Counter32
    MAX-ACCESS read-only
    STATUS     current
    DESCRIPTION
        "-- empty --"
    ::= { lcsStatusPppMl 5 }

-- {SCALAR} 1712.1.6.11.6
lcsStatusPppMlRxDiscarded OBJECT-TYPE
    SYNTAX     Counter32
    MAX-ACCESS read-only
    STATUS     current
    DESCRIPTION
        "-- empty --"
    ::= { lcsStatusPppMl 6 }

-- {SCALAR} 1712.1.6.11.7
lcsStatusPppMlRxFragStart OBJECT-TYPE
    SYNTAX     Counter32
    MAX-ACCESS read-only
    STATUS     current
    DESCRIPTION
        "-- empty --"
    ::= { lcsStatusPppMl 7 }

-- {SCALAR} 1712.1.6.11.8
lcsStatusPppMlRxFragMid OBJECT-TYPE
    SYNTAX     Counter32
    MAX-ACCESS read-only
    STATUS     current
    DESCRIPTION
        "-- empty --"
    ::= { lcsStatusPppMl 8 }

-- {SCALAR} 1712.1.6.11.9
lcsStatusPppMlRxFragEnd OBJECT-TYPE
    SYNTAX     Counter32
    MAX-ACCESS read-only
    STATUS     current
    DESCRIPTION
        "-- empty --"
    ::= { lcsStatusPppMl 9 }

-- {SCALAR} 1712.1.6.11.10
lcsStatusPppMlRxNotFragmented OBJECT-TYPE
    SYNTAX     Counter32
    MAX-ACCESS read-only
    STATUS     current
    DESCRIPTION
        "-- empty --"
    ::= { lcsStatusPppMl 10 }

-- {SCALAR} 1712.1.6.11.11
lcsStatusPppMlDeleteValues OBJECT-TYPE
    SYNTAX     DisplayString
    MAX-ACCESS read-write
    STATUS     current
    DESCRIPTION
        "-- empty --"
    ::= { lcsStatusPppMl 11 }

-- {OID} 1712.1.6.12
lcsStatusPppBacp OBJECT IDENTIFIER ::= { lcsStatusPpp 12 }

-- {SCALAR} 1712.1.6.12.1
lcsStatusPppBacpRxErrors OBJECT-TYPE
    SYNTAX     Counter32
    MAX-ACCESS read-only
    STATUS     current
    DESCRIPTION
        "-- empty --"
    ::= { lcsStatusPppBacp 1 }

-- {SCALAR} 1712.1.6.12.2
lcsStatusPppBacpRxDiscarded OBJECT-TYPE
    SYNTAX     Counter32
    MAX-ACCESS read-only
    STATUS     current
    DESCRIPTION
        "-- empty --"
    ::= { lcsStatusPppBacp 2 }

-- {SCALAR} 1712.1.6.12.3
lcsStatusPppBacpRxCallRequest OBJECT-TYPE
    SYNTAX     Counter32
    MAX-ACCESS read-only
    STATUS     current
    DESCRIPTION
        "-- empty --"
    ::= { lcsStatusPppBacp 3 }

-- {SCALAR} 1712.1.6.12.4
lcsStatusPppBacpRxCallResponse OBJECT-TYPE
    SYNTAX     Counter32
    MAX-ACCESS read-only
    STATUS     current
    DESCRIPTION
        "-- empty --"
    ::= { lcsStatusPppBacp 4 }

-- {SCALAR} 1712.1.6.12.5
lcsStatusPppBacpRxCallbackRequest OBJECT-TYPE
    SYNTAX     Counter32
    MAX-ACCESS read-only
    STATUS     current
    DESCRIPTION
        "-- empty --"
    ::= { lcsStatusPppBacp 5 }

-- {SCALAR} 1712.1.6.12.6
lcsStatusPppBacpRxCallbackResponse OBJECT-TYPE
    SYNTAX     Counter32
    MAX-ACCESS read-only
    STATUS     current
    DESCRIPTION
        "-- empty --"
    ::= { lcsStatusPppBacp 6 }

-- {SCALAR} 1712.1.6.12.7
lcsStatusPppBacpRxLinkDropRequest OBJECT-TYPE
    SYNTAX     Counter32
    MAX-ACCESS read-only
    STATUS     current
    DESCRIPTION
        "-- empty --"
    ::= { lcsStatusPppBacp 7 }

-- {SCALAR} 1712.1.6.12.8
lcsStatusPppBacpRxLinkDropResponse OBJECT-TYPE
    SYNTAX     Counter32
    MAX-ACCESS read-only
    STATUS     current
    DESCRIPTION
        "-- empty --"
    ::= { lcsStatusPppBacp 8 }

-- {SCALAR} 1712.1.6.12.9
lcsStatusPppBacpRxStatusIndication OBJECT-TYPE
    SYNTAX     Counter32
    MAX-ACCESS read-only
    STATUS     current
    DESCRIPTION
        "-- empty --"
    ::= { lcsStatusPppBacp 9 }

-- {SCALAR} 1712.1.6.12.10
lcsStatusPppBacpRxStatusResponse OBJECT-TYPE
    SYNTAX     Counter32
    MAX-ACCESS read-only
    STATUS     current
    DESCRIPTION
        "-- empty --"
    ::= { lcsStatusPppBacp 10 }

-- {SCALAR} 1712.1.6.12.11
lcsStatusPppBacpTxCallRequest OBJECT-TYPE
    SYNTAX     Counter32
    MAX-ACCESS read-only
    STATUS     current
    DESCRIPTION
        "-- empty --"
    ::= { lcsStatusPppBacp 11 }

-- {SCALAR} 1712.1.6.12.12
lcsStatusPppBacpTxCallResponse OBJECT-TYPE
    SYNTAX     Counter32
    MAX-ACCESS read-only
    STATUS     current
    DESCRIPTION
        "-- empty --"
    ::= { lcsStatusPppBacp 12 }

-- {SCALAR} 1712.1.6.12.13
lcsStatusPppBacpTxCallbackRequest OBJECT-TYPE
    SYNTAX     Counter32
    MAX-ACCESS read-only
    STATUS     current
    DESCRIPTION
        "-- empty --"
    ::= { lcsStatusPppBacp 13 }

-- {SCALAR} 1712.1.6.12.14
lcsStatusPppBacpTxCallbackResponse OBJECT-TYPE
    SYNTAX     Counter32
    MAX-ACCESS read-only
    STATUS     current
    DESCRIPTION
        "-- empty --"
    ::= { lcsStatusPppBacp 14 }

-- {SCALAR} 1712.1.6.12.15
lcsStatusPppBacpTxLinkDropRequest OBJECT-TYPE
    SYNTAX     Counter32
    MAX-ACCESS read-only
    STATUS     current
    DESCRIPTION
        "-- empty --"
    ::= { lcsStatusPppBacp 15 }

-- {SCALAR} 1712.1.6.12.16
lcsStatusPppBacpTxLinkDropResponse OBJECT-TYPE
    SYNTAX     Counter32
    MAX-ACCESS read-only
    STATUS     current
    DESCRIPTION
        "-- empty --"
    ::= { lcsStatusPppBacp 16 }

-- {SCALAR} 1712.1.6.12.17
lcsStatusPppBacpTxStatusIndication OBJECT-TYPE
    SYNTAX     Counter32
    MAX-ACCESS read-only
    STATUS     current
    DESCRIPTION
        "-- empty --"
    ::= { lcsStatusPppBacp 17 }

-- {SCALAR} 1712.1.6.12.18
lcsStatusPppBacpTxStatusResponse OBJECT-TYPE
    SYNTAX     Counter32
    MAX-ACCESS read-only
    STATUS     current
    DESCRIPTION
        "-- empty --"
    ::= { lcsStatusPppBacp 18 }

-- {SCALAR} 1712.1.6.12.19
lcsStatusPppBacpDeleteValues OBJECT-TYPE
    SYNTAX     DisplayString
    MAX-ACCESS read-write
    STATUS     current
    DESCRIPTION
        "-- empty --"
    ::= { lcsStatusPppBacp 19 }

-- {OID} 1712.1.6.8
lcsStatusPppRxOptions OBJECT IDENTIFIER ::= { lcsStatusPpp 8 }

-- {TABLE} 1712.1.6.8.1
lcsStatusPppRxOptionsLcpTable OBJECT-TYPE
    SYNTAX     SEQUENCE OF LcsStatusPppRxOptionsLcpEntry
    MAX-ACCESS not-accessible
    STATUS     current
    DESCRIPTION
        "-- empty --"
    ::= { lcsStatusPppRxOptions 1 }

-- {ENTRY} 1712.1.6.8.1.1
lcsStatusPppRxOptionsLcpEntry OBJECT-TYPE
    SYNTAX     LcsStatusPppRxOptionsLcpEntry
    MAX-ACCESS not-accessible
    STATUS     current
    DESCRIPTION
        ""
    INDEX {
        lcsStatusPppRxOptionsLcpEntryIfc
    }
    ::= { lcsStatusPppRxOptionsLcpTable 1 }

-- {SEQUENCE}
LcsStatusPppRxOptionsLcpEntry ::= SEQUENCE {
    lcsStatusPppRxOptionsLcpEntryIfc INTEGER,
    lcsStatusPppRxOptionsLcpEntryMru INTEGER,
    lcsStatusPppRxOptionsLcpEntryAccm DisplayString,
    lcsStatusPppRxOptionsLcpEntryAuthentRequest INTEGER,
    lcsStatusPppRxOptionsLcpEntryMagicNum DisplayString,
    lcsStatusPppRxOptionsLcpEntryPfc INTEGER,
    lcsStatusPppRxOptionsLcpEntryAcfc INTEGER,
    lcsStatusPppRxOptionsLcpEntryCallBack INTEGER
}

-- {COLUMN} 1712.1.6.8.1.1.1
lcsStatusPppRxOptionsLcpEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppRxOptionsLcpEntry 1 }

-- {COLUMN} 1712.1.6.8.1.1.2
lcsStatusPppRxOptionsLcpEntryMru OBJECT-TYPE
    SYNTAX     INTEGER (0..65535)
    MAX-ACCESS read-only
    STATUS     current
    DESCRIPTION
        "-- empty --"
    ::= { lcsStatusPppRxOptionsLcpEntry 2 }

-- {COLUMN} 1712.1.6.8.1.1.3
lcsStatusPppRxOptionsLcpEntryAccm OBJECT-TYPE
    SYNTAX     DisplayString (SIZE(0..8))
    MAX-ACCESS read-only
    STATUS     current
    DESCRIPTION
        "-- empty --"
    ::= { lcsStatusPppRxOptionsLcpEntry 3 }

-- {COLUMN} 1712.1.6.8.1.1.4
lcsStatusPppRxOptionsLcpEntryAuthentRequest OBJECT-TYPE
    SYNTAX     INTEGER
      {
        eNone (0),
        eMsChapv2 (32),
        eMsChap (16),
        eChap (8),
        ePap (4)
      }
    MAX-ACCESS read-only
    STATUS     current
    DESCRIPTION
        "-- empty --"
    ::= { lcsStatusPppRxOptionsLcpEntry 4 }

-- {COLUMN} 1712.1.6.8.1.1.6
lcsStatusPppRxOptionsLcpEntryMagicNum OBJECT-TYPE
    SYNTAX     DisplayString (SIZE(0..8))
    MAX-ACCESS read-only
    STATUS     current
    DESCRIPTION
        "-- empty --"
    ::= { lcsStatusPppRxOptionsLcpEntry 6 }

-- {COLUMN} 1712.1.6.8.1.1.7
lcsStatusPppRxOptionsLcpEntryPfc OBJECT-TYPE
    SYNTAX     INTEGER
      {
        eYes (1),
        eNo (0)
      }
    MAX-ACCESS read-only
    STATUS     current
    DESCRIPTION
        "-- empty --"
    ::= { lcsStatusPppRxOptionsLcpEntry 7 }

-- {COLUMN} 1712.1.6.8.1.1.8
lcsStatusPppRxOptionsLcpEntryAcfc OBJECT-TYPE
    SYNTAX     INTEGER
      {
        eYes (1),
        eNo (0)
      }
    MAX-ACCESS read-only
    STATUS     current
    DESCRIPTION
        "-- empty --"
    ::= { lcsStatusPppRxOptionsLcpEntry 8 }

-- {COLUMN} 1712.1.6.8.1.1.5
lcsStatusPppRxOptionsLcpEntryCallBack OBJECT-TYPE
    SYNTAX     INTEGER
      {
        eLcpCbAdm (0), -- callback after authentication
        eNone (255),
        eLcpCbUsr (1), -- callback to specified number
        eLcpCbNameAuth (2), -- callback to specified host after auth
        eLcpCbE164 (3), -- callback to specified E.164 number
        eLcpCbHost (4), -- callback to specified host
        eLcpCb (5),
        eLcpMsCBCP (6) -- callback via MS-CBCP
      }
    MAX-ACCESS read-only
    STATUS     current
    DESCRIPTION
        "-- empty --"
    ::= { lcsStatusPppRxOptionsLcpEntry 5 }

-- {TABLE} 1712.1.6.8.3
lcsStatusPppRxOptionsIpcpTable OBJECT-TYPE
    SYNTAX     SEQUENCE OF LcsStatusPppRxOptionsIpcpEntry
    MAX-ACCESS not-accessible
    STATUS     current
    DESCRIPTION
        "-- empty --"
    ::= { lcsStatusPppRxOptions 3 }

-- {ENTRY} 1712.1.6.8.3.1
lcsStatusPppRxOptionsIpcpEntry OBJECT-TYPE
    SYNTAX     LcsStatusPppRxOptionsIpcpEntry
    MAX-ACCESS not-accessible
    STATUS     current
    DESCRIPTION
        ""
    INDEX {
        lcsStatusPppRxOptionsIpcpEntryIfc
    }
    ::= { lcsStatusPppRxOptionsIpcpTable 1 }

-- {SEQUENCE}
LcsStatusPppRxOptionsIpcpEntry ::= SEQUENCE {
    lcsStatusPppRxOptionsIpcpEntryIfc INTEGER,
    lcsStatusPppRxOptionsIpcpEntryIpAddress IpAddress,
    lcsStatusPppRxOptionsIpcpEntryDnsDefault IpAddress,
    lcsStatusPppRxOptionsIpcpEntryDnsBackup IpAddress,
    lcsStatusPppRxOptionsIpcpEntryNbnsDefault IpAddress,
    lcsStatusPppRxOptionsIpcpEntryNbnsBackup IpAddress
}

-- {COLUMN} 1712.1.6.8.3.1.1
lcsStatusPppRxOptionsIpcpEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppRxOptionsIpcpEntry 1 }

-- {COLUMN} 1712.1.6.8.3.1.2
lcsStatusPppRxOptionsIpcpEntryIpAddress OBJECT-TYPE
    SYNTAX     IpAddress
    MAX-ACCESS read-only
    STATUS     current
    DESCRIPTION
        "-- empty --"
    ::= { lcsStatusPppRxOptionsIpcpEntry 2 }

-- {COLUMN} 1712.1.6.8.3.1.3
lcsStatusPppRxOptionsIpcpEntryDnsDefault OBJECT-TYPE
    SYNTAX     IpAddress
    MAX-ACCESS read-only
    STATUS     current
    DESCRIPTION
        "-- empty --"
    ::= { lcsStatusPppRxOptionsIpcpEntry 3 }

-- {COLUMN} 1712.1.6.8.3.1.5
lcsStatusPppRxOptionsIpcpEntryDnsBackup OBJECT-TYPE
    SYNTAX     IpAddress
    MAX-ACCESS read-only
    STATUS     current
    DESCRIPTION
        "-- empty --"
    ::= { lcsStatusPppRxOptionsIpcpEntry 5 }

-- {COLUMN} 1712.1.6.8.3.1.4
lcsStatusPppRxOptionsIpcpEntryNbnsDefault OBJECT-TYPE
    SYNTAX     IpAddress
    MAX-ACCESS read-only
    STATUS     current
    DESCRIPTION
        "-- empty --"
    ::= { lcsStatusPppRxOptionsIpcpEntry 4 }

-- {COLUMN} 1712.1.6.8.3.1.6
lcsStatusPppRxOptionsIpcpEntryNbnsBackup OBJECT-TYPE
    SYNTAX     IpAddress
    MAX-ACCESS read-only
    STATUS     current
    DESCRIPTION
        "-- empty --"
    ::= { lcsStatusPppRxOptionsIpcpEntry 6 }

-- {TABLE} 1712.1.6.8.4
lcsStatusPppRxOptionsIpv6cpTable OBJECT-TYPE
    SYNTAX     SEQUENCE OF LcsStatusPppRxOptionsIpv6cpEntry
    MAX-ACCESS not-accessible
    STATUS     current
    DESCRIPTION
        "-- empty --"
    ::= { lcsStatusPppRxOptions 4 }

-- {ENTRY} 1712.1.6.8.4.1
lcsStatusPppRxOptionsIpv6cpEntry OBJECT-TYPE
    SYNTAX     LcsStatusPppRxOptionsIpv6cpEntry
    MAX-ACCESS not-accessible
    STATUS     current
    DESCRIPTION
        ""
    INDEX {
        lcsStatusPppRxOptionsIpv6cpEntryIfc
    }
    ::= { lcsStatusPppRxOptionsIpv6cpTable 1 }

-- {SEQUENCE}
LcsStatusPppRxOptionsIpv6cpEntry ::= SEQUENCE {
    lcsStatusPppRxOptionsIpv6cpEntryIfc INTEGER,
    lcsStatusPppRxOptionsIpv6cpEntryIdentifier INTEGER
}

-- {COLUMN} 1712.1.6.8.4.1.1
lcsStatusPppRxOptionsIpv6cpEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppRxOptionsIpv6cpEntry 1 }

-- {COLUMN} 1712.1.6.8.4.1.2
lcsStatusPppRxOptionsIpv6cpEntryIdentifier OBJECT-TYPE
    SYNTAX     INTEGER (0..2147483647)
    MAX-ACCESS read-only
    STATUS     current
    DESCRIPTION
        "-- empty --"
    ::= { lcsStatusPppRxOptionsIpv6cpEntry 2 }

-- {OID} 1712.1.6.9
lcsStatusPppTxOptions OBJECT IDENTIFIER ::= { lcsStatusPpp 9 }

-- {TABLE} 1712.1.6.9.1
lcsStatusPppTxOptionsLcpTable OBJECT-TYPE
    SYNTAX     SEQUENCE OF LcsStatusPppTxOptionsLcpEntry
    MAX-ACCESS not-accessible
    STATUS     current
    DESCRIPTION
        "-- empty --"
    ::= { lcsStatusPppTxOptions 1 }

-- {ENTRY} 1712.1.6.9.1.1
lcsStatusPppTxOptionsLcpEntry OBJECT-TYPE
    SYNTAX     LcsStatusPppTxOptionsLcpEntry
    MAX-ACCESS not-accessible
    STATUS     current
    DESCRIPTION
        ""
    INDEX {
        lcsStatusPppTxOptionsLcpEntryIfc
    }
    ::= { lcsStatusPppTxOptionsLcpTable 1 }

-- {SEQUENCE}
LcsStatusPppTxOptionsLcpEntry ::= SEQUENCE {
    lcsStatusPppTxOptionsLcpEntryIfc INTEGER,
    lcsStatusPppTxOptionsLcpEntryMru INTEGER,
    lcsStatusPppTxOptionsLcpEntryAccm DisplayString,
    lcsStatusPppTxOptionsLcpEntryAuthentRequest INTEGER,
    lcsStatusPppTxOptionsLcpEntryMagicNum DisplayString,
    lcsStatusPppTxOptionsLcpEntryPfc INTEGER,
    lcsStatusPppTxOptionsLcpEntryAcfc INTEGER,
    lcsStatusPppTxOptionsLcpEntryCallBack INTEGER
}

-- {COLUMN} 1712.1.6.9.1.1.1
lcsStatusPppTxOptionsLcpEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppTxOptionsLcpEntry 1 }

-- {COLUMN} 1712.1.6.9.1.1.2
lcsStatusPppTxOptionsLcpEntryMru OBJECT-TYPE
    SYNTAX     INTEGER (0..65535)
    MAX-ACCESS read-only
    STATUS     current
    DESCRIPTION
        "-- empty --"
    ::= { lcsStatusPppTxOptionsLcpEntry 2 }

-- {COLUMN} 1712.1.6.9.1.1.3
lcsStatusPppTxOptionsLcpEntryAccm OBJECT-TYPE
    SYNTAX     DisplayString (SIZE(0..8))
    MAX-ACCESS read-only
    STATUS     current
    DESCRIPTION
        "-- empty --"
    ::= { lcsStatusPppTxOptionsLcpEntry 3 }

-- {COLUMN} 1712.1.6.9.1.1.4
lcsStatusPppTxOptionsLcpEntryAuthentRequest OBJECT-TYPE
    SYNTAX     INTEGER
      {
        eNone (0),
        eMsChapv2 (32),
        eMsChap (16),
        eChap (8),
        ePap (4)
      }
    MAX-ACCESS read-only
    STATUS     current
    DESCRIPTION
        "-- empty --"
    ::= { lcsStatusPppTxOptionsLcpEntry 4 }

-- {COLUMN} 1712.1.6.9.1.1.6
lcsStatusPppTxOptionsLcpEntryMagicNum OBJECT-TYPE
    SYNTAX     DisplayString (SIZE(0..8))
    MAX-ACCESS read-only
    STATUS     current
    DESCRIPTION
        "-- empty --"
    ::= { lcsStatusPppTxOptionsLcpEntry 6 }

-- {COLUMN} 1712.1.6.9.1.1.7
lcsStatusPppTxOptionsLcpEntryPfc OBJECT-TYPE
    SYNTAX     INTEGER
      {
        eYes (1),
        eNo (0)
      }
    MAX-ACCESS read-only
    STATUS     current
    DESCRIPTION
        "-- empty --"
    ::= { lcsStatusPppTxOptionsLcpEntry 7 }

-- {COLUMN} 1712.1.6.9.1.1.8
lcsStatusPppTxOptionsLcpEntryAcfc OBJECT-TYPE
    SYNTAX     INTEGER
      {
        eYes (1),
        eNo (0)
      }
    MAX-ACCESS read-only
    STATUS     current
    DESCRIPTION
        "-- empty --"
    ::= { lcsStatusPppTxOptionsLcpEntry 8 }

-- {COLUMN} 1712.1.6.9.1.1.5
lcsStatusPppTxOptionsLcpEntryCallBack OBJECT-TYPE
    SYNTAX     INTEGER
      {
        eLcpCbAdm (0), -- callback after authentication
        eNone (255),
        eLcpCbUsr (1), -- callback to specified number
        eLcpCbNameAuth (2), -- callback to specified host after auth
        eLcpCbE164 (3), -- callback to specified E.164 number
        eLcpCbHost (4), -- callback to specified host
        eLcpCb (5),
        eLcpMsCBCP (6) -- callback via MS-CBCP
      }
    MAX-ACCESS read-only
    STATUS     current
    DESCRIPTION
        "-- empty --"
    ::= { lcsStatusPppTxOptionsLcpEntry 5 }

-- {TABLE} 1712.1.6.9.3
lcsStatusPppTxOptionsIpcpTable OBJECT-TYPE
    SYNTAX     SEQUENCE OF LcsStatusPppTxOptionsIpcpEntry
    MAX-ACCESS not-accessible
    STATUS     current
    DESCRIPTION
        "-- empty --"
    ::= { lcsStatusPppTxOptions 3 }

-- {ENTRY} 1712.1.6.9.3.1
lcsStatusPppTxOptionsIpcpEntry OBJECT-TYPE
    SYNTAX     LcsStatusPppTxOptionsIpcpEntry
    MAX-ACCESS not-accessible
    STATUS     current
    DESCRIPTION
        ""
    INDEX {
        lcsStatusPppTxOptionsIpcpEntryIfc
    }
    ::= { lcsStatusPppTxOptionsIpcpTable 1 }

-- {SEQUENCE}
LcsStatusPppTxOptionsIpcpEntry ::= SEQUENCE {
    lcsStatusPppTxOptionsIpcpEntryIfc INTEGER,
    lcsStatusPppTxOptionsIpcpEntryIpAddress IpAddress,
    lcsStatusPppTxOptionsIpcpEntryDnsDefault IpAddress,
    lcsStatusPppTxOptionsIpcpEntryDnsBackup IpAddress,
    lcsStatusPppTxOptionsIpcpEntryNbnsDefault IpAddress,
    lcsStatusPppTxOptionsIpcpEntryNbnsBackup IpAddress
}

-- {COLUMN} 1712.1.6.9.3.1.1
lcsStatusPppTxOptionsIpcpEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppTxOptionsIpcpEntry 1 }

-- {COLUMN} 1712.1.6.9.3.1.2
lcsStatusPppTxOptionsIpcpEntryIpAddress OBJECT-TYPE
    SYNTAX     IpAddress
    MAX-ACCESS read-only
    STATUS     current
    DESCRIPTION
        "-- empty --"
    ::= { lcsStatusPppTxOptionsIpcpEntry 2 }

-- {COLUMN} 1712.1.6.9.3.1.3
lcsStatusPppTxOptionsIpcpEntryDnsDefault OBJECT-TYPE
    SYNTAX     IpAddress
    MAX-ACCESS read-only
    STATUS     current
    DESCRIPTION
        "-- empty --"
    ::= { lcsStatusPppTxOptionsIpcpEntry 3 }

-- {COLUMN} 1712.1.6.9.3.1.5
lcsStatusPppTxOptionsIpcpEntryDnsBackup OBJECT-TYPE
    SYNTAX     IpAddress
    MAX-ACCESS read-only
    STATUS     current
    DESCRIPTION
        "-- empty --"
    ::= { lcsStatusPppTxOptionsIpcpEntry 5 }

-- {COLUMN} 1712.1.6.9.3.1.4
lcsStatusPppTxOptionsIpcpEntryNbnsDefault OBJECT-TYPE
    SYNTAX     IpAddress
    MAX-ACCESS read-only
    STATUS     current
    DESCRIPTION
        "-- empty --"
    ::= { lcsStatusPppTxOptionsIpcpEntry 4 }

-- {COLUMN} 1712.1.6.9.3.1.6
lcsStatusPppTxOptionsIpcpEntryNbnsBackup OBJECT-TYPE
    SYNTAX     IpAddress
    MAX-ACCESS read-only
    STATUS     current
    DESCRIPTION
        "-- empty --"
    ::= { lcsStatusPppTxOptionsIpcpEntry 6 }

-- {TABLE} 1712.1.6.9.4
lcsStatusPppTxOptionsIpv6cpTable OBJECT-TYPE
    SYNTAX     SEQUENCE OF LcsStatusPppTxOptionsIpv6cpEntry
    MAX-ACCESS not-accessible
    STATUS     current
    DESCRIPTION
        "-- empty --"
    ::= { lcsStatusPppTxOptions 4 }

-- {ENTRY} 1712.1.6.9.4.1
lcsStatusPppTxOptionsIpv6cpEntry OBJECT-TYPE
    SYNTAX     LcsStatusPppTxOptionsIpv6cpEntry
    MAX-ACCESS not-accessible
    STATUS     current
    DESCRIPTION
        ""
    INDEX {
        lcsStatusPppTxOptionsIpv6cpEntryIfc
    }
    ::= { lcsStatusPppTxOptionsIpv6cpTable 1 }

-- {SEQUENCE}
LcsStatusPppTxOptionsIpv6cpEntry ::= SEQUENCE {
    lcsStatusPppTxOptionsIpv6cpEntryIfc INTEGER,
    lcsStatusPppTxOptionsIpv6cpEntryIdentifier INTEGER
}

-- {COLUMN} 1712.1.6.9.4.1.1
lcsStatusPppTxOptionsIpv6cpEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusPppTxOptionsIpv6cpEntry 1 }

-- {COLUMN} 1712.1.6.9.4.1.2
lcsStatusPppTxOptionsIpv6cpEntryIdentifier OBJECT-TYPE
    SYNTAX     INTEGER (0..2147483647)
    MAX-ACCESS read-only
    STATUS     current
    DESCRIPTION
        "-- empty --"
    ::= { lcsStatusPppTxOptionsIpv6cpEntry 2 }

-- {SCALAR} 1712.1.6.13
lcsStatusPppDeleteValues OBJECT-TYPE
    SYNTAX     DisplayString
    MAX-ACCESS read-write
    STATUS     current
    DESCRIPTION
        "-- empty --"
    ::= { lcsStatusPpp 13 }

-- {OID} 1712.1.6.14
lcsStatusPppIpv6cp OBJECT IDENTIFIER ::= { lcsStatusPpp 14 }

-- {SCALAR} 1712.1.6.14.1
lcsStatusPppIpv6cpRxDiscarded OBJECT-TYPE
    SYNTAX     Counter32
    MAX-ACCESS read-only
    STATUS     current
    DESCRIPTION
        "-- empty --"
    ::= { lcsStatusPppIpv6cp 1 }

-- {SCALAR} 1712.1.6.14.2
lcsStatusPppIpv6cpRxConfigRequest OBJECT-TYPE
    SYNTAX     Counter32
    MAX-ACCESS read-only
    STATUS     current
    DESCRIPTION
        "-- empty --"
    ::= { lcsStatusPppIpv6cp 2 }

-- {SCALAR} 1712.1.6.14.3
lcsStatusPppIpv6cpRxConfigAck OBJECT-TYPE
    SYNTAX     Counter32
    MAX-ACCESS read-only
    STATUS     current
    DESCRIPTION
        "-- empty --"
    ::= { lcsStatusPppIpv6cp 3 }

-- {SCALAR} 1712.1.6.14.4
lcsStatusPppIpv6cpRxConfigNak OBJECT-TYPE
    SYNTAX     Counter32
    MAX-ACCESS read-only
    STATUS     current
    DESCRIPTION
        "-- empty --"
    ::= { lcsStatusPppIpv6cp 4 }

-- {SCALAR} 1712.1.6.14.5
lcsStatusPppIpv6cpRxConfigReject OBJECT-TYPE
    SYNTAX     Counter32
    MAX-ACCESS read-only
    STATUS     current
    DESCRIPTION
        "-- empty --"
    ::= { lcsStatusPppIpv6cp 5 }

-- {SCALAR} 1712.1.6.14.6
lcsStatusPppIpv6cpRxTerminateRequest OBJECT-TYPE
    SYNTAX     Counter32
    MAX-ACCESS read-only
    STATUS     current
    DESCRIPTION
        "-- empty --"
    ::= { lcsStatusPppIpv6cp 6 }

-- {SCALAR} 1712.1.6.14.7
lcsStatusPppIpv6cpRxTerminateAck OBJECT-TYPE
    SYNTAX     Counter32
    MAX-ACCESS read-only
    STATUS     current
    DESCRIPTION
        "-- empty --"
    ::= { lcsStatusPppIpv6cp 7 }

-- {SCALAR} 1712.1.6.14.8
lcsStatusPppIpv6cpRxCodeReject OBJECT-TYPE
    SYNTAX     Counter32
    MAX-ACCESS read-only
    STATUS     current
    DESCRIPTION
        "-- empty --"
    ::= { lcsStatusPppIpv6cp 8 }

-- {SCALAR} 1712.1.6.14.9
lcsStatusPppIpv6cpTxConfigRequest OBJECT-TYPE
    SYNTAX     Counter32
    MAX-ACCESS read-only
    STATUS     current
    DESCRIPTION
        "-- empty --"
    ::= { lcsStatusPppIpv6cp 9 }

-- {SCALAR} 1712.1.6.14.10
lcsStatusPppIpv6cpTxConfigAck OBJECT-TYPE
    SYNTAX     Counter32
    MAX-ACCESS read-only
    STATUS     current
    DESCRIPTION
        "-- empty --"
    ::= { lcsStatusPppIpv6cp 10 }

-- {SCALAR} 1712.1.6.14.11
lcsStatusPppIpv6cpTxConfigNak OBJECT-TYPE
    SYNTAX     Counter32
    MAX-ACCESS read-only
    STATUS     current
    DESCRIPTION
        "-- empty --"
    ::= { lcsStatusPppIpv6cp 11 }

-- {SCALAR} 1712.1.6.14.12
lcsStatusPppIpv6cpTxConfigReject OBJECT-TYPE
    SYNTAX     Counter32
    MAX-ACCESS read-only
    STATUS     current
    DESCRIPTION
        "-- empty --"
    ::= { lcsStatusPppIpv6cp 12 }

-- {SCALAR} 1712.1.6.14.13
lcsStatusPppIpv6cpTxTerminateRequest OBJECT-TYPE
    SYNTAX     Counter32
    MAX-ACCESS read-only
    STATUS     current
    DESCRIPTION
        "-- empty --"
    ::= { lcsStatusPppIpv6cp 13 }

-- {SCALAR} 1712.1.6.14.14
lcsStatusPppIpv6cpTxTerminateAck OBJECT-TYPE
    SYNTAX     Counter32
    MAX-ACCESS read-only
    STATUS     current
    DESCRIPTION
        "-- empty --"
    ::= { lcsStatusPppIpv6cp 14 }

-- {SCALAR} 1712.1.6.14.15
lcsStatusPppIpv6cpTxCodeReject OBJECT-TYPE
    SYNTAX     Counter32
    MAX-ACCESS read-only
    STATUS     current
    DESCRIPTION
        "-- empty --"
    ::= { lcsStatusPppIpv6cp 15 }

-- {SCALAR} 1712.1.6.14.16
lcsStatusPppIpv6cpDeleteValues OBJECT-TYPE
    SYNTAX     DisplayString
    MAX-ACCESS read-write
    STATUS     current
    DESCRIPTION
        "-- empty --"
    ::= { lcsStatusPppIpv6cp 16 }

-- {OID} 1712.1.9
lcsStatusTcpIp OBJECT IDENTIFIER ::= { lcsStatus 9 }

-- {OID} 1712.1.9.1
lcsStatusTcpIpArp OBJECT IDENTIFIER ::= { lcsStatusTcpIp 1 }

-- {SCALAR} 1712.1.9.1.1
lcsStatusTcpIpArpLanRx OBJECT-TYPE
    SYNTAX     Counter32
    MAX-ACCESS read-only
    STATUS     current
    DESCRIPTION
        "-- empty --"
    ::= { lcsStatusTcpIpArp 1 }

-- {SCALAR} 1712.1.9.1.2
lcsStatusTcpIpArpLanTx OBJECT-TYPE
    SYNTAX     Counter32
    MAX-ACCESS read-only
    STATUS     current
    DESCRIPTION
        "-- empty --"
    ::= { lcsStatusTcpIpArp 2 }

-- {SCALAR} 1712.1.9.1.3
lcsStatusTcpIpArpLanErrors OBJECT-TYPE
    SYNTAX     Counter32
    MAX-ACCESS read-only
    STATUS     current
    DESCRIPTION
        "-- empty --"
    ::= { lcsStatusTcpIpArp 3 }

-- {SCALAR} 1712.1.9.1.4
lcsStatusTcpIpArpWanRx OBJECT-TYPE
    SYNTAX     Counter32
    MAX-ACCESS read-only
    STATUS     current
    DESCRIPTION
        "-- empty --"
    ::= { lcsStatusTcpIpArp 4 }

-- {SCALAR} 1712.1.9.1.5
lcsStatusTcpIpArpWanTx OBJECT-TYPE
    SYNTAX     Counter32
    MAX-ACCESS read-only
    STATUS     current
    DESCRIPTION
        "-- empty --"
    ::= { lcsStatusTcpIpArp 5 }

-- {SCALAR} 1712.1.9.1.6
lcsStatusTcpIpArpWanErrors OBJECT-TYPE
    SYNTAX     Counter32
    MAX-ACCESS read-only
    STATUS     current
    DESCRIPTION
        "-- empty --"
    ::= { lcsStatusTcpIpArp 6 }

-- {TABLE} 1712.1.9.1.7
lcsStatusTcpIpArpTableArpTable OBJECT-TYPE
    SYNTAX     SEQUENCE OF LcsStatusTcpIpArpTableArpEntry
    MAX-ACCESS not-accessible
    STATUS     current
    DESCRIPTION
        "-- empty --"
    ::= { lcsStatusTcpIpArp 7 }

-- {ENTRY} 1712.1.9.1.7.1
lcsStatusTcpIpArpTableArpEntry OBJECT-TYPE
    SYNTAX     LcsStatusTcpIpArpTableArpEntry
    MAX-ACCESS not-accessible
    STATUS     current
    DESCRIPTION
        ""
    INDEX {
        lcsStatusTcpIpArpTableArpEntryIpAddress
    }
    ::= { lcsStatusTcpIpArpTableArpTable 1 }

-- {SEQUENCE}
LcsStatusTcpIpArpTableArpEntry ::= SEQUENCE {
    lcsStatusTcpIpArpTableArpEntryIpAddress IpAddress,
    lcsStatusTcpIpArpTableArpEntryMacAddress MacAddress,
    lcsStatusTcpIpArpTableArpEntryLastAccess INTEGER,
    lcsStatusTcpIpArpTableArpEntryConnect INTEGER,
    lcsStatusTcpIpArpTableArpEntryEthernetPort INTEGER,
    lcsStatusTcpIpArpTableArpEntryVlanId INTEGER,
    lcsStatusTcpIpArpTableArpEntryPeer DisplayString
}

-- {COLUMN} 1712.1.9.1.7.1.1
lcsStatusTcpIpArpTableArpEntryIpAddress OBJECT-TYPE
    SYNTAX     IpAddress
    MAX-ACCESS read-only
    STATUS     current
    DESCRIPTION
        "-- empty --"
    ::= { lcsStatusTcpIpArpTableArpEntry 1 }

-- {COLUMN} 1712.1.9.1.7.1.2
lcsStatusTcpIpArpTableArpEntryMacAddress OBJECT-TYPE
    SYNTAX     MacAddress
    MAX-ACCESS read-only
    STATUS     current
    DESCRIPTION
        "-- empty --"
    ::= { lcsStatusTcpIpArpTableArpEntry 2 }

-- {COLUMN} 1712.1.9.1.7.1.3
lcsStatusTcpIpArpTableArpEntryLastAccess OBJECT-TYPE
    SYNTAX     INTEGER (0..2147483647)
    MAX-ACCESS read-only
    STATUS     current
    DESCRIPTION
        "-- empty --"
    ::= { lcsStatusTcpIpArpTableArpEntry 3 }

-- {COLUMN} 1712.1.9.1.7.1.8
lcsStatusTcpIpArpTableArpEntryConnect OBJECT-TYPE
    SYNTAX     INTEGER
      {
        eLan1 (256),
        eLan2 (257),
        eLan3 (258),
        eLan4 (259),
        eWan (32768)
      }
    MAX-ACCESS read-only
    STATUS     current
    DESCRIPTION
        "-- empty --"
    ::= { lcsStatusTcpIpArpTableArpEntry 8 }

-- {COLUMN} 1712.1.9.1.7.1.5
lcsStatusTcpIpArpTableArpEntryEthernetPort OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsStatusTcpIpArpTableArpEntry 5 }

-- {COLUMN} 1712.1.9.1.7.1.7
lcsStatusTcpIpArpTableArpEntryVlanId OBJECT-TYPE
    SYNTAX     INTEGER (0..65535)
    MAX-ACCESS read-only
    STATUS     current
    DESCRIPTION
        "-- empty --"
    ::= { lcsStatusTcpIpArpTableArpEntry 7 }

-- {COLUMN} 1712.1.9.1.7.1.6
lcsStatusTcpIpArpTableArpEntryPeer OBJECT-TYPE
    SYNTAX     DisplayString (SIZE(0..255))
    MAX-ACCESS read-only
    STATUS     current
    DESCRIPTION
        "-- empty --"
    ::= { lcsStatusTcpIpArpTableArpEntry 6 }

-- {SCALAR} 1712.1.9.1.8
lcsStatusTcpIpArpDeleteValues OBJECT-TYPE
    SYNTAX     DisplayString
    MAX-ACCESS read-write
    STATUS     current
    DESCRIPTION
        "-- empty --"
    ::= { lcsStatusTcpIpArp 8 }

-- {SCALAR} 1712.1.9.1.10
lcsStatusTcpIpArpLanProxyRules OBJECT-TYPE
    SYNTAX     INTEGER (0..2147483647)
    MAX-ACCESS read-only
    STATUS     current
    DESCRIPTION
        "-- empty --"
    ::= { lcsStatusTcpIpArp 10 }

-- {OID} 1712.1.9.2
lcsStatusTcpIpIp OBJECT IDENTIFIER ::= { lcsStatusTcpIp 2 }

-- {SCALAR} 1712.1.9.2.1
lcsStatusTcpIpIpLanRx OBJECT-TYPE
    SYNTAX     Counter32
    MAX-ACCESS read-only
    STATUS     current
    DESCRIPTION
        "-- empty --"
    ::= { lcsStatusTcpIpIp 1 }

-- {SCALAR} 1712.1.9.2.2
lcsStatusTcpIpIpLanTx OBJECT-TYPE
    SYNTAX     Counter32
    MAX-ACCESS read-only
    STATUS     current
    DESCRIPTION
        "-- empty --"
    ::= { lcsStatusTcpIpIp 2 }

-- {SCALAR} 1712.1.9.2.3
lcsStatusTcpIpIpLanChecksumErrors OBJECT-TYPE
    SYNTAX     Counter32
    MAX-ACCESS read-only
    STATUS     current
    DESCRIPTION
        "-- empty --"
    ::= { lcsStatusTcpIpIp 3 }

-- {SCALAR} 1712.1.9.2.4
lcsStatusTcpIpIpLanServiceErrors OBJECT-TYPE
    SYNTAX     Counter32
    MAX-ACCESS read-only
    STATUS     current
    DESCRIPTION
        "-- empty --"
    ::= { lcsStatusTcpIpIp 4 }

-- {SCALAR} 1712.1.9.2.10
lcsStatusTcpIpIpLanFragmentationErrors OBJECT-TYPE
    SYNTAX     Counter32
    MAX-ACCESS read-only
    STATUS     current
    DESCRIPTION
        "-- empty --"
    ::= { lcsStatusTcpIpIp 10 }

-- {SCALAR} 1712.1.9.2.13
lcsStatusTcpIpIpLanFragmentations OBJECT-TYPE
    SYNTAX     Counter32
    MAX-ACCESS read-only
    STATUS     current
    DESCRIPTION
        "-- empty --"
    ::= { lcsStatusTcpIpIp 13 }

-- {SCALAR} 1712.1.9.2.14
lcsStatusTcpIpIpLanFragmentationsForced OBJECT-TYPE
    SYNTAX     Counter32
    MAX-ACCESS read-only
    STATUS     current
    DESCRIPTION
        "-- empty --"
    ::= { lcsStatusTcpIpIp 14 }

-- {SCALAR} 1712.1.9.2.5
lcsStatusTcpIpIpWanRx OBJECT-TYPE
    SYNTAX     Counter32
    MAX-ACCESS read-only
    STATUS     current
    DESCRIPTION
        "-- empty --"
    ::= { lcsStatusTcpIpIp 5 }

-- {SCALAR} 1712.1.9.2.6
lcsStatusTcpIpIpWanTx OBJECT-TYPE
    SYNTAX     Counter32
    MAX-ACCESS read-only
    STATUS     current
    DESCRIPTION
        "-- empty --"
    ::= { lcsStatusTcpIpIp 6 }

-- {SCALAR} 1712.1.9.2.7
lcsStatusTcpIpIpWanChecksumErrors OBJECT-TYPE
    SYNTAX     Counter32
    MAX-ACCESS read-only
    STATUS     current
    DESCRIPTION
        "-- empty --"
    ::= { lcsStatusTcpIpIp 7 }

-- {SCALAR} 1712.1.9.2.8
lcsStatusTcpIpIpWanServiceErrors OBJECT-TYPE
    SYNTAX     Counter32
    MAX-ACCESS read-only
    STATUS     current
    DESCRIPTION
        "-- empty --"
    ::= { lcsStatusTcpIpIp 8 }

-- {SCALAR} 1712.1.9.2.11
lcsStatusTcpIpIpWanFragmentationErrors OBJECT-TYPE
    SYNTAX     Counter32
    MAX-ACCESS read-only
    STATUS     current
    DESCRIPTION
        "-- empty --"
    ::= { lcsStatusTcpIpIp 11 }

-- {SCALAR} 1712.1.9.2.15
lcsStatusTcpIpIpWanFragmentations OBJECT-TYPE
    SYNTAX     Counter32
    MAX-ACCESS read-only
    STATUS     current
    DESCRIPTION
        "-- empty --"
    ::= { lcsStatusTcpIpIp 15 }

-- {SCALAR} 1712.1.9.2.16
lcsStatusTcpIpIpWanFragmentationsForced OBJECT-TYPE
    SYNTAX     Counter32
    MAX-ACCESS read-only
    STATUS     current
    DESCRIPTION
        "-- empty --"
    ::= { lcsStatusTcpIpIp 16 }

-- {SCALAR} 1712.1.9.2.9
lcsStatusTcpIpIpWanRxDisconnect OBJECT-TYPE
    SYNTAX     Counter32
    MAX-ACCESS read-only
    STATUS     current
    DESCRIPTION
        "-- empty --"
    ::= { lcsStatusTcpIpIp 9 }

-- {SCALAR} 1712.1.9.2.17
lcsStatusTcpIpIpLoopError OBJECT-TYPE
    SYNTAX     Counter32
    MAX-ACCESS read-only
    STATUS     current
    DESCRIPTION
        "-- empty --"
    ::= { lcsStatusTcpIpIp 17 }

-- {SCALAR} 1712.1.9.2.12
lcsStatusTcpIpIpDeleteValues OBJECT-TYPE
    SYNTAX     DisplayString
    MAX-ACCESS read-write
    STATUS     current
    DESCRIPTION
        "-- empty --"
    ::= { lcsStatusTcpIpIp 12 }

-- {OID} 1712.1.9.3
lcsStatusTcpIpIcmp OBJECT IDENTIFIER ::= { lcsStatusTcpIp 3 }

-- {SCALAR} 1712.1.9.3.1
lcsStatusTcpIpIcmpLanRx OBJECT-TYPE
    SYNTAX     Counter32
    MAX-ACCESS read-only
    STATUS     current
    DESCRIPTION
        "-- empty --"
    ::= { lcsStatusTcpIpIcmp 1 }

-- {SCALAR} 1712.1.9.3.2
lcsStatusTcpIpIcmpLanTx OBJECT-TYPE
    SYNTAX     Counter32
    MAX-ACCESS read-only
    STATUS     current
    DESCRIPTION
        "-- empty --"
    ::= { lcsStatusTcpIpIcmp 2 }

-- {SCALAR} 1712.1.9.3.3
lcsStatusTcpIpIcmpLanChecksumErrors OBJECT-TYPE
    SYNTAX     Counter32
    MAX-ACCESS read-only
    STATUS     current
    DESCRIPTION
        "-- empty --"
    ::= { lcsStatusTcpIpIcmp 3 }

-- {SCALAR} 1712.1.9.3.4
lcsStatusTcpIpIcmpLanServiceErrors OBJECT-TYPE
    SYNTAX     Counter32
    MAX-ACCESS read-only
    STATUS     current
    DESCRIPTION
        "-- empty --"
    ::= { lcsStatusTcpIpIcmp 4 }

-- {SCALAR} 1712.1.9.3.5
lcsStatusTcpIpIcmpWanRx OBJECT-TYPE
    SYNTAX     Counter32
    MAX-ACCESS read-only
    STATUS     current
    DESCRIPTION
        "-- empty --"
    ::= { lcsStatusTcpIpIcmp 5 }

-- {SCALAR} 1712.1.9.3.6
lcsStatusTcpIpIcmpWanTx OBJECT-TYPE
    SYNTAX     Counter32
    MAX-ACCESS read-only
    STATUS     current
    DESCRIPTION
        "-- empty --"
    ::= { lcsStatusTcpIpIcmp 6 }

-- {SCALAR} 1712.1.9.3.7
lcsStatusTcpIpIcmpWanChecksumErrors OBJECT-TYPE
    SYNTAX     Counter32
    MAX-ACCESS read-only
    STATUS     current
    DESCRIPTION
        "-- empty --"
    ::= { lcsStatusTcpIpIcmp 7 }

-- {SCALAR} 1712.1.9.3.8
lcsStatusTcpIpIcmpWanServiceErrors OBJECT-TYPE
    SYNTAX     Counter32
    MAX-ACCESS read-only
    STATUS     current
    DESCRIPTION
        "-- empty --"
    ::= { lcsStatusTcpIpIcmp 8 }

-- {SCALAR} 1712.1.9.3.9
lcsStatusTcpIpIcmpDeleteValues OBJECT-TYPE
    SYNTAX     DisplayString
    MAX-ACCESS read-write
    STATUS     current
    DESCRIPTION
        "-- empty --"
    ::= { lcsStatusTcpIpIcmp 9 }

-- {OID} 1712.1.9.4
lcsStatusTcpIpTftp OBJECT IDENTIFIER ::= { lcsStatusTcpIp 4 }

-- {SCALAR} 1712.1.9.4.1
lcsStatusTcpIpTftpLanRx OBJECT-TYPE
    SYNTAX     Counter32
    MAX-ACCESS read-only
    STATUS     current
    DESCRIPTION
        "-- empty --"
    ::= { lcsStatusTcpIpTftp 1 }

-- {SCALAR} 1712.1.9.4.2
lcsStatusTcpIpTftpLanRxReadRequest OBJECT-TYPE
    SYNTAX     Counter32
    MAX-ACCESS read-only
    STATUS     current
    DESCRIPTION
        "-- empty --"
    ::= { lcsStatusTcpIpTftp 2 }

-- {SCALAR} 1712.1.9.4.3
lcsStatusTcpIpTftpLanRxWriteRequest OBJECT-TYPE
    SYNTAX     Counter32
    MAX-ACCESS read-only
    STATUS     current
    DESCRIPTION
        "-- empty --"
    ::= { lcsStatusTcpIpTftp 3 }

-- {SCALAR} 1712.1.9.4.4
lcsStatusTcpIpTftpLanRxData OBJECT-TYPE
    SYNTAX     Counter32
    MAX-ACCESS read-only
    STATUS     current
    DESCRIPTION
        "-- empty --"
    ::= { lcsStatusTcpIpTftp 4 }

-- {SCALAR} 1712.1.9.4.5
lcsStatusTcpIpTftpLanRxAck OBJECT-TYPE
    SYNTAX     Counter32
    MAX-ACCESS read-only
    STATUS     current
    DESCRIPTION
        "-- empty --"
    ::= { lcsStatusTcpIpTftp 5 }

-- {SCALAR} 1712.1.9.4.6
lcsStatusTcpIpTftpLanRxOptionAck OBJECT-TYPE
    SYNTAX     Counter32
    MAX-ACCESS read-only
    STATUS     current
    DESCRIPTION
        "-- empty --"
    ::= { lcsStatusTcpIpTftp 6 }

-- {SCALAR} 1712.1.9.4.7
lcsStatusTcpIpTftpLanRxErrors OBJECT-TYPE
    SYNTAX     Counter32
    MAX-ACCESS read-only
    STATUS     current
    DESCRIPTION
        "-- empty --"
    ::= { lcsStatusTcpIpTftp 7 }

-- {SCALAR} 1712.1.9.4.8
lcsStatusTcpIpTftpLanRxBadPackets OBJECT-TYPE
    SYNTAX     Counter32
    MAX-ACCESS read-only
    STATUS     current
    DESCRIPTION
        "-- empty --"
    ::= { lcsStatusTcpIpTftp 8 }

-- {SCALAR} 1712.1.9.4.9
lcsStatusTcpIpTftpLanTx OBJECT-TYPE
    SYNTAX     Counter32
    MAX-ACCESS read-only
    STATUS     current
    DESCRIPTION
        "-- empty --"
    ::= { lcsStatusTcpIpTftp 9 }

-- {SCALAR} 1712.1.9.4.10
lcsStatusTcpIpTftpLanTxData OBJECT-TYPE
    SYNTAX     Counter32
    MAX-ACCESS read-only
    STATUS     current
    DESCRIPTION
        "-- empty --"
    ::= { lcsStatusTcpIpTftp 10 }

-- {SCALAR} 1712.1.9.4.11
lcsStatusTcpIpTftpLanTxAck OBJECT-TYPE
    SYNTAX     Counter32
    MAX-ACCESS read-only
    STATUS     current
    DESCRIPTION
        "-- empty --"
    ::= { lcsStatusTcpIpTftp 11 }

-- {SCALAR} 1712.1.9.4.12
lcsStatusTcpIpTftpLanTxOptionAck OBJECT-TYPE
    SYNTAX     Counter32
    MAX-ACCESS read-only
    STATUS     current
    DESCRIPTION
        "-- empty --"
    ::= { lcsStatusTcpIpTftp 12 }

-- {SCALAR} 1712.1.9.4.13
lcsStatusTcpIpTftpLanTxErrors OBJECT-TYPE
    SYNTAX     Counter32
    MAX-ACCESS read-only
    STATUS     current
    DESCRIPTION
        "-- empty --"
    ::= { lcsStatusTcpIpTftp 13 }

-- {SCALAR} 1712.1.9.4.14
lcsStatusTcpIpTftpLanTxRepeats OBJECT-TYPE
    SYNTAX     Counter32
    MAX-ACCESS read-only
    STATUS     current
    DESCRIPTION
        "-- empty --"
    ::= { lcsStatusTcpIpTftp 14 }

-- {SCALAR} 1712.1.9.4.15
lcsStatusTcpIpTftpLanConnections OBJECT-TYPE
    SYNTAX     Counter32
    MAX-ACCESS read-only
    STATUS     current
    DESCRIPTION
        "-- empty --"
    ::= { lcsStatusTcpIpTftp 15 }

-- {SCALAR} 1712.1.9.4.16
lcsStatusTcpIpTftpWanRx OBJECT-TYPE
    SYNTAX     Counter32
    MAX-ACCESS read-only
    STATUS     current
    DESCRIPTION
        "-- empty --"
    ::= { lcsStatusTcpIpTftp 16 }

-- {SCALAR} 1712.1.9.4.17
lcsStatusTcpIpTftpWanRxReadRequest OBJECT-TYPE
    SYNTAX     Counter32
    MAX-ACCESS read-only
    STATUS     current
    DESCRIPTION
        "-- empty --"
    ::= { lcsStatusTcpIpTftp 17 }

-- {SCALAR} 1712.1.9.4.18
lcsStatusTcpIpTftpWanRxWriteRequest OBJECT-TYPE
    SYNTAX     Counter32
    MAX-ACCESS read-only
    STATUS     current
    DESCRIPTION
        "-- empty --"
    ::= { lcsStatusTcpIpTftp 18 }

-- {SCALAR} 1712.1.9.4.19
lcsStatusTcpIpTftpWanRxData OBJECT-TYPE
    SYNTAX     Counter32
    MAX-ACCESS read-only
    STATUS     current
    DESCRIPTION
        "-- empty --"
    ::= { lcsStatusTcpIpTftp 19 }

-- {SCALAR} 1712.1.9.4.20
lcsStatusTcpIpTftpWanRxAck OBJECT-TYPE
    SYNTAX     Counter32
    MAX-ACCESS read-only
    STATUS     current
    DESCRIPTION
        "-- empty --"
    ::= { lcsStatusTcpIpTftp 20 }

-- {SCALAR} 1712.1.9.4.21
lcsStatusTcpIpTftpWanRxOptionAck OBJECT-TYPE
    SYNTAX     Counter32
    MAX-ACCESS read-only
    STATUS     current
    DESCRIPTION
        "-- empty --"
    ::= { lcsStatusTcpIpTftp 21 }

-- {SCALAR} 1712.1.9.4.22
lcsStatusTcpIpTftpWanRxErrors OBJECT-TYPE
    SYNTAX     Counter32
    MAX-ACCESS read-only
    STATUS     current
    DESCRIPTION
        "-- empty --"
    ::= { lcsStatusTcpIpTftp 22 }

-- {SCALAR} 1712.1.9.4.23
lcsStatusTcpIpTftpWanRxBadPackets OBJECT-TYPE
    SYNTAX     Counter32
    MAX-ACCESS read-only
    STATUS     current
    DESCRIPTION
        "-- empty --"
    ::= { lcsStatusTcpIpTftp 23 }

-- {SCALAR} 1712.1.9.4.24
lcsStatusTcpIpTftpWanTx OBJECT-TYPE
    SYNTAX     Counter32
    MAX-ACCESS read-only
    STATUS     current
    DESCRIPTION
        "-- empty --"
    ::= { lcsStatusTcpIpTftp 24 }

-- {SCALAR} 1712.1.9.4.25
lcsStatusTcpIpTftpWanTxData OBJECT-TYPE
    SYNTAX     Counter32
    MAX-ACCESS read-only
    STATUS     current
    DESCRIPTION
        "-- empty --"
    ::= { lcsStatusTcpIpTftp 25 }

-- {SCALAR} 1712.1.9.4.26
lcsStatusTcpIpTftpWanTxAck OBJECT-TYPE
    SYNTAX     Counter32
    MAX-ACCESS read-only
    STATUS     current
    DESCRIPTION
        "-- empty --"
    ::= { lcsStatusTcpIpTftp 26 }

-- {SCALAR} 1712.1.9.4.27
lcsStatusTcpIpTftpWanTxOptionAck OBJECT-TYPE
    SYNTAX     Counter32
    MAX-ACCESS read-only
    STATUS     current
    DESCRIPTION
        "-- empty --"
    ::= { lcsStatusTcpIpTftp 27 }

-- {SCALAR} 1712.1.9.4.28
lcsStatusTcpIpTftpWanTxErrors OBJECT-TYPE
    SYNTAX     Counter32
    MAX-ACCESS read-only
    STATUS     current
    DESCRIPTION
        "-- empty --"
    ::= { lcsStatusTcpIpTftp 28 }

-- {SCALAR} 1712.1.9.4.29
lcsStatusTcpIpTftpWanTxRepeats OBJECT-TYPE
    SYNTAX     Counter32
    MAX-ACCESS read-only
    STATUS     current
    DESCRIPTION
        "-- empty --"
    ::= { lcsStatusTcpIpTftp 29 }

-- {SCALAR} 1712.1.9.4.30
lcsStatusTcpIpTftpWanConnections OBJECT-TYPE
    SYNTAX     Counter32
    MAX-ACCESS read-only
    STATUS     current
    DESCRIPTION
        "-- empty --"
    ::= { lcsStatusTcpIpTftp 30 }

-- {SCALAR} 1712.1.9.4.31
lcsStatusTcpIpTftpDeleteValues OBJECT-TYPE
    SYNTAX     DisplayString
    MAX-ACCESS read-write
    STATUS     current
    DESCRIPTION
        "-- empty --"
    ::= { lcsStatusTcpIpTftp 31 }

-- {OID} 1712.1.9.5
lcsStatusTcpIpTcp OBJECT IDENTIFIER ::= { lcsStatusTcpIp 5 }

-- {SCALAR} 1712.1.9.5.1
lcsStatusTcpIpTcpLanRx OBJECT-TYPE
    SYNTAX     Counter32
    MAX-ACCESS read-only
    STATUS     current
    DESCRIPTION
        "-- empty --"
    ::= { lcsStatusTcpIpTcp 1 }

-- {SCALAR} 1712.1.9.5.2
lcsStatusTcpIpTcpLanTx OBJECT-TYPE
    SYNTAX     Counter32
    MAX-ACCESS read-only
    STATUS     current
    DESCRIPTION
        "-- empty --"
    ::= { lcsStatusTcpIpTcp 2 }

-- {SCALAR} 1712.1.9.5.3
lcsStatusTcpIpTcpLanTxRepeats OBJECT-TYPE
    SYNTAX     Counter32
    MAX-ACCESS read-only
    STATUS     current
    DESCRIPTION
        "-- empty --"
    ::= { lcsStatusTcpIpTcp 3 }

-- {SCALAR} 1712.1.9.5.4
lcsStatusTcpIpTcpLanChecksumErrors OBJECT-TYPE
    SYNTAX     Counter32
    MAX-ACCESS read-only
    STATUS     current
    DESCRIPTION
        "-- empty --"
    ::= { lcsStatusTcpIpTcp 4 }

-- {SCALAR} 1712.1.9.5.5
lcsStatusTcpIpTcpLanServiceErrors OBJECT-TYPE
    SYNTAX     Counter32
    MAX-ACCESS read-only
    STATUS     current
    DESCRIPTION
        "-- empty --"
    ::= { lcsStatusTcpIpTcp 5 }

-- {SCALAR} 1712.1.9.5.6
lcsStatusTcpIpTcpLanConnections OBJECT-TYPE
    SYNTAX     Counter32
    MAX-ACCESS read-only
    STATUS     current
    DESCRIPTION
        "-- empty --"
    ::= { lcsStatusTcpIpTcp 6 }

-- {SCALAR} 1712.1.9.5.7
lcsStatusTcpIpTcpWanRx OBJECT-TYPE
    SYNTAX     Counter32
    MAX-ACCESS read-only
    STATUS     current
    DESCRIPTION
        "-- empty --"
    ::= { lcsStatusTcpIpTcp 7 }

-- {SCALAR} 1712.1.9.5.8
lcsStatusTcpIpTcpWanTx OBJECT-TYPE
    SYNTAX     Counter32
    MAX-ACCESS read-only
    STATUS     current
    DESCRIPTION
        "-- empty --"
    ::= { lcsStatusTcpIpTcp 8 }

-- {SCALAR} 1712.1.9.5.9
lcsStatusTcpIpTcpWanTxRepeats OBJECT-TYPE
    SYNTAX     Counter32
    MAX-ACCESS read-only
    STATUS     current
    DESCRIPTION
        "-- empty --"
    ::= { lcsStatusTcpIpTcp 9 }

-- {SCALAR} 1712.1.9.5.10
lcsStatusTcpIpTcpWanChecksumErrors OBJECT-TYPE
    SYNTAX     Counter32
    MAX-ACCESS read-only
    STATUS     current
    DESCRIPTION
        "-- empty --"
    ::= { lcsStatusTcpIpTcp 10 }

-- {SCALAR} 1712.1.9.5.11
lcsStatusTcpIpTcpWanServiceErrors OBJECT-TYPE
    SYNTAX     Counter32
    MAX-ACCESS read-only
    STATUS     current
    DESCRIPTION
        "-- empty --"
    ::= { lcsStatusTcpIpTcp 11 }

-- {SCALAR} 1712.1.9.5.12
lcsStatusTcpIpTcpWanConnections OBJECT-TYPE
    SYNTAX     Counter32
    MAX-ACCESS read-only
    STATUS     current
    DESCRIPTION
        "-- empty --"
    ::= { lcsStatusTcpIpTcp 12 }

-- {SCALAR} 1712.1.9.5.13
lcsStatusTcpIpTcpDeleteValues OBJECT-TYPE
    SYNTAX     DisplayString
    MAX-ACCESS read-write
    STATUS     current
    DESCRIPTION
        "-- empty --"
    ::= { lcsStatusTcpIpTcp 13 }

-- {OID} 1712.1.9.6
lcsStatusTcpIpDhcp OBJECT IDENTIFIER ::= { lcsStatusTcpIp 6 }

-- {SCALAR} 1712.1.9.6.1
lcsStatusTcpIpDhcpLanRx OBJECT-TYPE
    SYNTAX     Counter32
    MAX-ACCESS read-only
    STATUS     current
    DESCRIPTION
        "-- empty --"
    ::= { lcsStatusTcpIpDhcp 1 }

-- {SCALAR} 1712.1.9.6.2
lcsStatusTcpIpDhcpLanTx OBJECT-TYPE
    SYNTAX     Counter32
    MAX-ACCESS read-only
    STATUS     current
    DESCRIPTION
        "-- empty --"
    ::= { lcsStatusTcpIpDhcp 2 }

-- {SCALAR} 1712.1.9.6.3
lcsStatusTcpIpDhcpWanRx OBJECT-TYPE
    SYNTAX     Counter32
    MAX-ACCESS read-only
    STATUS     current
    DESCRIPTION
        "-- empty --"
    ::= { lcsStatusTcpIpDhcp 3 }

-- {SCALAR} 1712.1.9.6.19
lcsStatusTcpIpDhcpWanTx OBJECT-TYPE
    SYNTAX     Counter32
    MAX-ACCESS read-only
    STATUS     current
    DESCRIPTION
        "-- empty --"
    ::= { lcsStatusTcpIpDhcp 19 }

-- {SCALAR} 1712.1.9.6.4
lcsStatusTcpIpDhcpDiscard OBJECT-TYPE
    SYNTAX     Counter32
    MAX-ACCESS read-only
    STATUS     current
    DESCRIPTION
        "-- empty --"
    ::= { lcsStatusTcpIpDhcp 4 }

-- {SCALAR} 1712.1.9.6.5
lcsStatusTcpIpDhcpRxDiscover OBJECT-TYPE
    SYNTAX     Counter32
    MAX-ACCESS read-only
    STATUS     current
    DESCRIPTION
        "-- empty --"
    ::= { lcsStatusTcpIpDhcp 5 }

-- {SCALAR} 1712.1.9.6.6
lcsStatusTcpIpDhcpRxRequest OBJECT-TYPE
    SYNTAX     Counter32
    MAX-ACCESS read-only
    STATUS     current
    DESCRIPTION
        "-- empty --"
    ::= { lcsStatusTcpIpDhcp 6 }

-- {SCALAR} 1712.1.9.6.7
lcsStatusTcpIpDhcpRxDecline OBJECT-TYPE
    SYNTAX     Counter32
    MAX-ACCESS read-only
    STATUS     current
    DESCRIPTION
        "-- empty --"
    ::= { lcsStatusTcpIpDhcp 7 }

-- {SCALAR} 1712.1.9.6.8
lcsStatusTcpIpDhcpRxInform OBJECT-TYPE
    SYNTAX     Counter32
    MAX-ACCESS read-only
    STATUS     current
    DESCRIPTION
        "-- empty --"
    ::= { lcsStatusTcpIpDhcp 8 }

-- {SCALAR} 1712.1.9.6.9
lcsStatusTcpIpDhcpRxRelease OBJECT-TYPE
    SYNTAX     Counter32
    MAX-ACCESS read-only
    STATUS     current
    DESCRIPTION
        "-- empty --"
    ::= { lcsStatusTcpIpDhcp 9 }

-- {SCALAR} 1712.1.9.6.10
lcsStatusTcpIpDhcpTxOffer OBJECT-TYPE
    SYNTAX     Counter32
    MAX-ACCESS read-only
    STATUS     current
    DESCRIPTION
        "-- empty --"
    ::= { lcsStatusTcpIpDhcp 10 }

-- {SCALAR} 1712.1.9.6.11
lcsStatusTcpIpDhcpTxAck OBJECT-TYPE
    SYNTAX     Counter32
    MAX-ACCESS read-only
    STATUS     current
    DESCRIPTION
        "-- empty --"
    ::= { lcsStatusTcpIpDhcp 11 }

-- {SCALAR} 1712.1.9.6.12
lcsStatusTcpIpDhcpTxNak OBJECT-TYPE
    SYNTAX     Counter32
    MAX-ACCESS read-only
    STATUS     current
    DESCRIPTION
        "-- empty --"
    ::= { lcsStatusTcpIpDhcp 12 }

-- {SCALAR} 1712.1.9.6.13
lcsStatusTcpIpDhcpServerError OBJECT-TYPE
    SYNTAX     Counter32
    MAX-ACCESS read-only
    STATUS     current
    DESCRIPTION
        "-- empty --"
    ::= { lcsStatusTcpIpDhcp 13 }

-- {SCALAR} 1712.1.9.6.14
lcsStatusTcpIpDhcpAssigned OBJECT-TYPE
    SYNTAX     INTEGER (0..2147483647)
    MAX-ACCESS read-only
    STATUS     current
    DESCRIPTION
        "-- empty --"
    ::= { lcsStatusTcpIpDhcp 14 }

-- {SCALAR} 1712.1.9.6.15
lcsStatusTcpIpDhcpMacConflicts OBJECT-TYPE
    SYNTAX     Counter32
    MAX-ACCESS read-only
    STATUS     current
    DESCRIPTION
        "-- empty --"
    ::= { lcsStatusTcpIpDhcp 15 }

-- {TABLE} 1712.1.9.6.20
lcsStatusTcpIpDhcpNetworkListTable OBJECT-TYPE
    SYNTAX     SEQUENCE OF LcsStatusTcpIpDhcpNetworkListEntry
    MAX-ACCESS not-accessible
    STATUS     current
    DESCRIPTION
        "-- empty --"
    ::= { lcsStatusTcpIpDhcp 20 }

-- {ENTRY} 1712.1.9.6.20.1
lcsStatusTcpIpDhcpNetworkListEntry OBJECT-TYPE
    SYNTAX     LcsStatusTcpIpDhcpNetworkListEntry
    MAX-ACCESS not-accessible
    STATUS     current
    DESCRIPTION
        ""
    INDEX {
        lcsStatusTcpIpDhcpNetworkListEntryNetworkName
    }
    ::= { lcsStatusTcpIpDhcpNetworkListTable 1 }

-- {SEQUENCE}
LcsStatusTcpIpDhcpNetworkListEntry ::= SEQUENCE {
    lcsStatusTcpIpDhcpNetworkListEntryNetworkName DisplayString,
    lcsStatusTcpIpDhcpNetworkListEntryStartAddressPool IpAddress,
    lcsStatusTcpIpDhcpNetworkListEntryEndAddressPool IpAddress,
    lcsStatusTcpIpDhcpNetworkListEntryNetmask IpAddress,
    lcsStatusTcpIpDhcpNetworkListEntryBroadcastAddress IpAddress,
    lcsStatusTcpIpDhcpNetworkListEntryGatewayAddress IpAddress,
    lcsStatusTcpIpDhcpNetworkListEntryDnsDefault IpAddress,
    lcsStatusTcpIpDhcpNetworkListEntryDnsBackup IpAddress,
    lcsStatusTcpIpDhcpNetworkListEntryNbnsDefault IpAddress,
    lcsStatusTcpIpDhcpNetworkListEntryNbnsBackup IpAddress,
    lcsStatusTcpIpDhcpNetworkListEntryServerFlags DisplayString,
    lcsStatusTcpIpDhcpNetworkListEntryBroadcastBit INTEGER,
    lcsStatusTcpIpDhcpNetworkListEntryServerId IpAddress,
    lcsStatusTcpIpDhcpNetworkListEntryLanIfc INTEGER,
    lcsStatusTcpIpDhcpNetworkListEntryVlanId INTEGER,
    lcsStatusTcpIpDhcpNetworkListEntryMasterServer IpAddress,
    lcsStatusTcpIpDhcpNetworkListEntry2ndMasterServer IpAddress,
    lcsStatusTcpIpDhcpNetworkListEntry3rdMasterServer IpAddress,
    lcsStatusTcpIpDhcpNetworkListEntry4thMasterServer IpAddress,
    lcsStatusTcpIpDhcpNetworkListEntryCache INTEGER,
    lcsStatusTcpIpDhcpNetworkListEntryAdaption INTEGER,
    lcsStatusTcpIpDhcpNetworkListEntryCluster INTEGER
}

-- {COLUMN} 1712.1.9.6.20.1.1
lcsStatusTcpIpDhcpNetworkListEntryNetworkName OBJECT-TYPE
    SYNTAX     DisplayString (SIZE(0..16))
    MAX-ACCESS read-only
    STATUS     current
    DESCRIPTION
        "-- empty --"
    ::= { lcsStatusTcpIpDhcpNetworkListEntry 1 }

-- {COLUMN} 1712.1.9.6.20.1.2
lcsStatusTcpIpDhcpNetworkListEntryStartAddressPool OBJECT-TYPE
    SYNTAX     IpAddress
    MAX-ACCESS read-only
    STATUS     current
    DESCRIPTION
        "-- empty --"
    ::= { lcsStatusTcpIpDhcpNetworkListEntry 2 }

-- {COLUMN} 1712.1.9.6.20.1.3
lcsStatusTcpIpDhcpNetworkListEntryEndAddressPool OBJECT-TYPE
    SYNTAX     IpAddress
    MAX-ACCESS read-only
    STATUS     current
    DESCRIPTION
        "-- empty --"
    ::= { lcsStatusTcpIpDhcpNetworkListEntry 3 }

-- {COLUMN} 1712.1.9.6.20.1.4
lcsStatusTcpIpDhcpNetworkListEntryNetmask OBJECT-TYPE
    SYNTAX     IpAddress
    MAX-ACCESS read-only
    STATUS     current
    DESCRIPTION
        "-- empty --"
    ::= { lcsStatusTcpIpDhcpNetworkListEntry 4 }

-- {COLUMN} 1712.1.9.6.20.1.5
lcsStatusTcpIpDhcpNetworkListEntryBroadcastAddress OBJECT-TYPE
    SYNTAX     IpAddress
    MAX-ACCESS read-only
    STATUS     current
    DESCRIPTION
        "-- empty --"
    ::= { lcsStatusTcpIpDhcpNetworkListEntry 5 }

-- {COLUMN} 1712.1.9.6.20.1.6
lcsStatusTcpIpDhcpNetworkListEntryGatewayAddress OBJECT-TYPE
    SYNTAX     IpAddress
    MAX-ACCESS read-only
    STATUS     current
    DESCRIPTION
        "-- empty --"
    ::= { lcsStatusTcpIpDhcpNetworkListEntry 6 }

-- {COLUMN} 1712.1.9.6.20.1.7
lcsStatusTcpIpDhcpNetworkListEntryDnsDefault OBJECT-TYPE
    SYNTAX     IpAddress
    MAX-ACCESS read-only
    STATUS     current
    DESCRIPTION
        "-- empty --"
    ::= { lcsStatusTcpIpDhcpNetworkListEntry 7 }

-- {COLUMN} 1712.1.9.6.20.1.8
lcsStatusTcpIpDhcpNetworkListEntryDnsBackup OBJECT-TYPE
    SYNTAX     IpAddress
    MAX-ACCESS read-only
    STATUS     current
    DESCRIPTION
        "-- empty --"
    ::= { lcsStatusTcpIpDhcpNetworkListEntry 8 }

-- {COLUMN} 1712.1.9.6.20.1.9
lcsStatusTcpIpDhcpNetworkListEntryNbnsDefault OBJECT-TYPE
    SYNTAX     IpAddress
    MAX-ACCESS read-only
    STATUS     current
    DESCRIPTION
        "-- empty --"
    ::= { lcsStatusTcpIpDhcpNetworkListEntry 9 }

-- {COLUMN} 1712.1.9.6.20.1.10
lcsStatusTcpIpDhcpNetworkListEntryNbnsBackup OBJECT-TYPE
    SYNTAX     IpAddress
    MAX-ACCESS read-only
    STATUS     current
    DESCRIPTION
        "-- empty --"
    ::= { lcsStatusTcpIpDhcpNetworkListEntry 10 }

-- {COLUMN} 1712.1.9.6.20.1.11
lcsStatusTcpIpDhcpNetworkListEntryServerFlags OBJECT-TYPE
    SYNTAX     DisplayString (SIZE(0..255))
    MAX-ACCESS read-only
    STATUS     current
    DESCRIPTION
        "-- empty --"
    ::= { lcsStatusTcpIpDhcpNetworkListEntry 11 }

-- {COLUMN} 1712.1.9.6.20.1.13
lcsStatusTcpIpDhcpNetworkListEntryBroadcastBit OBJECT-TYPE
    SYNTAX     INTEGER
      {
        eNo (0),
        eYes (1)
      }
    MAX-ACCESS read-only
    STATUS     current
    DESCRIPTION
        "-- empty --"
    ::= { lcsStatusTcpIpDhcpNetworkListEntry 13 }

-- {COLUMN} 1712.1.9.6.20.1.14
lcsStatusTcpIpDhcpNetworkListEntryServerId OBJECT-TYPE
    SYNTAX     IpAddress
    MAX-ACCESS read-only
    STATUS     current
    DESCRIPTION
        "-- empty --"
    ::= { lcsStatusTcpIpDhcpNetworkListEntry 14 }

-- {COLUMN} 1712.1.9.6.20.1.24
lcsStatusTcpIpDhcpNetworkListEntryLanIfc OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusTcpIpDhcpNetworkListEntry 24 }

-- {COLUMN} 1712.1.9.6.20.1.16
lcsStatusTcpIpDhcpNetworkListEntryVlanId OBJECT-TYPE
    SYNTAX     INTEGER (0..65535)
    MAX-ACCESS read-only
    STATUS     current
    DESCRIPTION
        "-- empty --"
    ::= { lcsStatusTcpIpDhcpNetworkListEntry 16 }

-- {COLUMN} 1712.1.9.6.20.1.17
lcsStatusTcpIpDhcpNetworkListEntryMasterServer OBJECT-TYPE
    SYNTAX     IpAddress
    MAX-ACCESS read-only
    STATUS     current
    DESCRIPTION
        "-- empty --"
    ::= { lcsStatusTcpIpDhcpNetworkListEntry 17 }

-- {COLUMN} 1712.1.9.6.20.1.21
lcsStatusTcpIpDhcpNetworkListEntry2ndMasterServer OBJECT-TYPE
    SYNTAX     IpAddress
    MAX-ACCESS read-only
    STATUS     current
    DESCRIPTION
        "-- empty --"
    ::= { lcsStatusTcpIpDhcpNetworkListEntry 21 }

-- {COLUMN} 1712.1.9.6.20.1.22
lcsStatusTcpIpDhcpNetworkListEntry3rdMasterServer OBJECT-TYPE
    SYNTAX     IpAddress
    MAX-ACCESS read-only
    STATUS     current
    DESCRIPTION
        "-- empty --"
    ::= { lcsStatusTcpIpDhcpNetworkListEntry 22 }

-- {COLUMN} 1712.1.9.6.20.1.23
lcsStatusTcpIpDhcpNetworkListEntry4thMasterServer OBJECT-TYPE
    SYNTAX     IpAddress
    MAX-ACCESS read-only
    STATUS     current
    DESCRIPTION
        "-- empty --"
    ::= { lcsStatusTcpIpDhcpNetworkListEntry 23 }

-- {COLUMN} 1712.1.9.6.20.1.18
lcsStatusTcpIpDhcpNetworkListEntryCache OBJECT-TYPE
    SYNTAX     INTEGER
      {
        eNo (0),
        eYes (1)
      }
    MAX-ACCESS read-only
    STATUS     current
    DESCRIPTION
        "-- empty --"
    ::= { lcsStatusTcpIpDhcpNetworkListEntry 18 }

-- {COLUMN} 1712.1.9.6.20.1.19
lcsStatusTcpIpDhcpNetworkListEntryAdaption OBJECT-TYPE
    SYNTAX     INTEGER
      {
        eNo (0),
        eYes (1)
      }
    MAX-ACCESS read-only
    STATUS     current
    DESCRIPTION
        "-- empty --"
    ::= { lcsStatusTcpIpDhcpNetworkListEntry 19 }

-- {COLUMN} 1712.1.9.6.20.1.20
lcsStatusTcpIpDhcpNetworkListEntryCluster OBJECT-TYPE
    SYNTAX     INTEGER
      {
        eNo (0),
        eYes (1)
      }
    MAX-ACCESS read-only
    STATUS     current
    DESCRIPTION
        "-- empty --"
    ::= { lcsStatusTcpIpDhcpNetworkListEntry 20 }

-- {TABLE} 1712.1.9.6.16
lcsStatusTcpIpDhcpDhcpTableTable OBJECT-TYPE
    SYNTAX     SEQUENCE OF LcsStatusTcpIpDhcpDhcpTableEntry
    MAX-ACCESS not-accessible
    STATUS     current
    DESCRIPTION
        "-- empty --"
    ::= { lcsStatusTcpIpDhcp 16 }

-- {ENTRY} 1712.1.9.6.16.1
lcsStatusTcpIpDhcpDhcpTableEntry OBJECT-TYPE
    SYNTAX     LcsStatusTcpIpDhcpDhcpTableEntry
    MAX-ACCESS not-accessible
    STATUS     current
    DESCRIPTION
        ""
    INDEX {
        lcsStatusTcpIpDhcpDhcpTableEntryIpAddress,
        lcsStatusTcpIpDhcpDhcpTableEntryNetworkName
    }
    ::= { lcsStatusTcpIpDhcpDhcpTableTable 1 }

-- {SEQUENCE}
LcsStatusTcpIpDhcpDhcpTableEntry ::= SEQUENCE {
    lcsStatusTcpIpDhcpDhcpTableEntryIpAddress IpAddress,
    lcsStatusTcpIpDhcpDhcpTableEntryMacAddress DisplayString,
    lcsStatusTcpIpDhcpDhcpTableEntryTimeout INTEGER,
    lcsStatusTcpIpDhcpDhcpTableEntryHostname DisplayString,
    lcsStatusTcpIpDhcpDhcpTableEntryType BITS,
    lcsStatusTcpIpDhcpDhcpTableEntryLanIfc INTEGER,
    lcsStatusTcpIpDhcpDhcpTableEntryEthernetPort INTEGER,
    lcsStatusTcpIpDhcpDhcpTableEntryVlanId INTEGER,
    lcsStatusTcpIpDhcpDhcpTableEntryNetworkName DisplayString,
    lcsStatusTcpIpDhcpDhcpTableEntryAssignment DisplayString,
    lcsStatusTcpIpDhcpDhcpTableEntryAssignmentNumeric Gauge32
}

-- {COLUMN} 1712.1.9.6.16.1.1
lcsStatusTcpIpDhcpDhcpTableEntryIpAddress OBJECT-TYPE
    SYNTAX     IpAddress
    MAX-ACCESS read-only
    STATUS     current
    DESCRIPTION
        "-- empty --"
    ::= { lcsStatusTcpIpDhcpDhcpTableEntry 1 }

-- {COLUMN} 1712.1.9.6.16.1.2
lcsStatusTcpIpDhcpDhcpTableEntryMacAddress OBJECT-TYPE
    SYNTAX     DisplayString (SIZE(0..12))
    MAX-ACCESS read-only
    STATUS     current
    DESCRIPTION
        "-- empty --"
    ::= { lcsStatusTcpIpDhcpDhcpTableEntry 2 }

-- {COLUMN} 1712.1.9.6.16.1.3
lcsStatusTcpIpDhcpDhcpTableEntryTimeout OBJECT-TYPE
    SYNTAX     INTEGER (0..2147483647)
    MAX-ACCESS read-only
    STATUS     current
    DESCRIPTION
        "-- empty --"
    ::= { lcsStatusTcpIpDhcpDhcpTableEntry 3 }

-- {COLUMN} 1712.1.9.6.16.1.4
lcsStatusTcpIpDhcpDhcpTableEntryHostname OBJECT-TYPE
    SYNTAX     DisplayString (SIZE(0..65))
    MAX-ACCESS read-only
    STATUS     current
    DESCRIPTION
        "-- empty --"
    ::= { lcsStatusTcpIpDhcpDhcpTableEntry 4 }

-- {COLUMN} 1712.1.9.6.16.1.5
lcsStatusTcpIpDhcpDhcpTableEntryType OBJECT-TYPE
    SYNTAX     BITS
      {
        enew (15),
        enewreq (14),
        eDyn (11),
        eUnkn (13),
        eStat (12),
        eBootp (10),
        eRelay (4),
        eCache (8)
      }
    MAX-ACCESS read-only
    STATUS     current
    DESCRIPTION
        "-- empty --"
    ::= { lcsStatusTcpIpDhcpDhcpTableEntry 5 }

-- {COLUMN} 1712.1.9.6.16.1.10
lcsStatusTcpIpDhcpDhcpTableEntryLanIfc OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusTcpIpDhcpDhcpTableEntry 10 }

-- {COLUMN} 1712.1.9.6.16.1.7
lcsStatusTcpIpDhcpDhcpTableEntryEthernetPort OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsStatusTcpIpDhcpDhcpTableEntry 7 }

-- {COLUMN} 1712.1.9.6.16.1.8
lcsStatusTcpIpDhcpDhcpTableEntryVlanId OBJECT-TYPE
    SYNTAX     INTEGER (0..65535)
    MAX-ACCESS read-only
    STATUS     current
    DESCRIPTION
        "-- empty --"
    ::= { lcsStatusTcpIpDhcpDhcpTableEntry 8 }

-- {COLUMN} 1712.1.9.6.16.1.9
lcsStatusTcpIpDhcpDhcpTableEntryNetworkName OBJECT-TYPE
    SYNTAX     DisplayString (SIZE(0..17))
    MAX-ACCESS read-only
    STATUS     current
    DESCRIPTION
        "-- empty --"
    ::= { lcsStatusTcpIpDhcpDhcpTableEntry 9 }

-- {COLUMN} 1712.1.9.6.16.1.11
lcsStatusTcpIpDhcpDhcpTableEntryAssignment OBJECT-TYPE
    SYNTAX     DisplayString (SIZE(0..21))
    MAX-ACCESS read-only
    STATUS     current
    DESCRIPTION
        "-- empty --"
    ::= { lcsStatusTcpIpDhcpDhcpTableEntry 11 }

-- {COLUMN} 1712.1.9.6.16.1.12
lcsStatusTcpIpDhcpDhcpTableEntryAssignmentNumeric OBJECT-TYPE
    SYNTAX     Gauge32
    MAX-ACCESS read-only
    STATUS     current
    DESCRIPTION
        "-- empty --"
    ::= { lcsStatusTcpIpDhcpDhcpTableEntry 12 }

-- {SCALAR} 1712.1.9.6.18
lcsStatusTcpIpDhcpDeleteValues OBJECT-TYPE
    SYNTAX     DisplayString
    MAX-ACCESS read-write
    STATUS     current
    DESCRIPTION
        "-- empty --"
    ::= { lcsStatusTcpIpDhcp 18 }

-- {SCALAR} 1712.1.9.7
lcsStatusTcpIpDeleteValues OBJECT-TYPE
    SYNTAX     DisplayString
    MAX-ACCESS read-write
    STATUS     current
    DESCRIPTION
        "-- empty --"
    ::= { lcsStatusTcpIp 7 }

-- {OID} 1712.1.9.8
lcsStatusTcpIpNetbios OBJECT IDENTIFIER ::= { lcsStatusTcpIp 8 }

-- {SCALAR} 1712.1.9.8.1
lcsStatusTcpIpNetbiosLanRx OBJECT-TYPE
    SYNTAX     Counter32
    MAX-ACCESS read-only
    STATUS     current
    DESCRIPTION
        "-- empty --"
    ::= { lcsStatusTcpIpNetbios 1 }

-- {SCALAR} 1712.1.9.8.2
lcsStatusTcpIpNetbiosLanTx OBJECT-TYPE
    SYNTAX     Counter32
    MAX-ACCESS read-only
    STATUS     current
    DESCRIPTION
        "-- empty --"
    ::= { lcsStatusTcpIpNetbios 2 }

-- {SCALAR} 1712.1.9.8.3
lcsStatusTcpIpNetbiosWanRx OBJECT-TYPE
    SYNTAX     Counter32
    MAX-ACCESS read-only
    STATUS     current
    DESCRIPTION
        "-- empty --"
    ::= { lcsStatusTcpIpNetbios 3 }

-- {SCALAR} 1712.1.9.8.4
lcsStatusTcpIpNetbiosWanTx OBJECT-TYPE
    SYNTAX     Counter32
    MAX-ACCESS read-only
    STATUS     current
    DESCRIPTION
        "-- empty --"
    ::= { lcsStatusTcpIpNetbios 4 }

-- {SCALAR} 1712.1.9.8.5
lcsStatusTcpIpNetbiosRegisters OBJECT-TYPE
    SYNTAX     Counter32
    MAX-ACCESS read-only
    STATUS     current
    DESCRIPTION
        "-- empty --"
    ::= { lcsStatusTcpIpNetbios 5 }

-- {SCALAR} 1712.1.9.8.6
lcsStatusTcpIpNetbiosConflicts OBJECT-TYPE
    SYNTAX     Counter32
    MAX-ACCESS read-only
    STATUS     current
    DESCRIPTION
        "-- empty --"
    ::= { lcsStatusTcpIpNetbios 6 }

-- {SCALAR} 1712.1.9.8.7
lcsStatusTcpIpNetbiosReleases OBJECT-TYPE
    SYNTAX     Counter32
    MAX-ACCESS read-only
    STATUS     current
    DESCRIPTION
        "-- empty --"
    ::= { lcsStatusTcpIpNetbios 7 }

-- {SCALAR} 1712.1.9.8.8
lcsStatusTcpIpNetbiosRefreshs OBJECT-TYPE
    SYNTAX     Counter32
    MAX-ACCESS read-only
    STATUS     current
    DESCRIPTION
        "-- empty --"
    ::= { lcsStatusTcpIpNetbios 8 }

-- {SCALAR} 1712.1.9.8.9
lcsStatusTcpIpNetbiosTimeouts OBJECT-TYPE
    SYNTAX     Counter32
    MAX-ACCESS read-only
    STATUS     current
    DESCRIPTION
        "-- empty --"
    ::= { lcsStatusTcpIpNetbios 9 }

-- {SCALAR} 1712.1.9.8.10
lcsStatusTcpIpNetbiosHosts OBJECT-TYPE
    SYNTAX     INTEGER (0..2147483647)
    MAX-ACCESS read-only
    STATUS     current
    DESCRIPTION
        "-- empty --"
    ::= { lcsStatusTcpIpNetbios 10 }

-- {SCALAR} 1712.1.9.8.11
lcsStatusTcpIpNetbiosGroups OBJECT-TYPE
    SYNTAX     INTEGER (0..2147483647)
    MAX-ACCESS read-only
    STATUS     current
    DESCRIPTION
        "-- empty --"
    ::= { lcsStatusTcpIpNetbios 11 }

-- {SCALAR} 1712.1.9.8.12
lcsStatusTcpIpNetbiosBNodes OBJECT-TYPE
    SYNTAX     INTEGER (0..2147483647)
    MAX-ACCESS read-only
    STATUS     current
    DESCRIPTION
        "-- empty --"
    ::= { lcsStatusTcpIpNetbios 12 }

-- {SCALAR} 1712.1.9.8.13
lcsStatusTcpIpNetbiosPNodes OBJECT-TYPE
    SYNTAX     INTEGER (0..2147483647)
    MAX-ACCESS read-only
    STATUS     current
    DESCRIPTION
        "-- empty --"
    ::= { lcsStatusTcpIpNetbios 13 }

-- {SCALAR} 1712.1.9.8.14
lcsStatusTcpIpNetbiosMNodes OBJECT-TYPE
    SYNTAX     INTEGER (0..2147483647)
    MAX-ACCESS read-only
    STATUS     current
    DESCRIPTION
        "-- empty --"
    ::= { lcsStatusTcpIpNetbios 14 }

-- {SCALAR} 1712.1.9.8.15
lcsStatusTcpIpNetbiosWNodes OBJECT-TYPE
    SYNTAX     INTEGER (0..2147483647)
    MAX-ACCESS read-only
    STATUS     current
    DESCRIPTION
        "-- empty --"
    ::= { lcsStatusTcpIpNetbios 15 }

-- {TABLE} 1712.1.9.8.16
lcsStatusTcpIpNetbiosPeersTable OBJECT-TYPE
    SYNTAX     SEQUENCE OF LcsStatusTcpIpNetbiosPeersEntry
    MAX-ACCESS not-accessible
    STATUS     current
    DESCRIPTION
        "-- empty --"
    ::= { lcsStatusTcpIpNetbios 16 }

-- {ENTRY} 1712.1.9.8.16.1
lcsStatusTcpIpNetbiosPeersEntry OBJECT-TYPE
    SYNTAX     LcsStatusTcpIpNetbiosPeersEntry
    MAX-ACCESS not-accessible
    STATUS     current
    DESCRIPTION
        ""
    INDEX {
        lcsStatusTcpIpNetbiosPeersEntryName
    }
    ::= { lcsStatusTcpIpNetbiosPeersTable 1 }

-- {SEQUENCE}
LcsStatusTcpIpNetbiosPeersEntry ::= SEQUENCE {
    lcsStatusTcpIpNetbiosPeersEntryName DisplayString,
    lcsStatusTcpIpNetbiosPeersEntryType INTEGER,
    lcsStatusTcpIpNetbiosPeersEntryBackoff INTEGER,
    lcsStatusTcpIpNetbiosPeersEntryTime INTEGER
}

-- {COLUMN} 1712.1.9.8.16.1.1
lcsStatusTcpIpNetbiosPeersEntryName OBJECT-TYPE
    SYNTAX     DisplayString (SIZE(0..16))
    MAX-ACCESS read-only
    STATUS     current
    DESCRIPTION
        "-- empty --"
    ::= { lcsStatusTcpIpNetbiosPeersEntry 1 }

-- {COLUMN} 1712.1.9.8.16.1.2
lcsStatusTcpIpNetbiosPeersEntryType OBJECT-TYPE
    SYNTAX     INTEGER
      {
        eWorkstation (1),
        eRouter (0)
      }
    MAX-ACCESS read-only
    STATUS     current
    DESCRIPTION
        "-- empty --"
    ::= { lcsStatusTcpIpNetbiosPeersEntry 2 }

-- {COLUMN} 1712.1.9.8.16.1.3
lcsStatusTcpIpNetbiosPeersEntryBackoff OBJECT-TYPE
    SYNTAX     INTEGER (0..255)
    MAX-ACCESS read-only
    STATUS     current
    DESCRIPTION
        "-- empty --"
    ::= { lcsStatusTcpIpNetbiosPeersEntry 3 }

-- {COLUMN} 1712.1.9.8.16.1.4
lcsStatusTcpIpNetbiosPeersEntryTime OBJECT-TYPE
    SYNTAX     INTEGER (0..65535)
    MAX-ACCESS read-only
    STATUS     current
    DESCRIPTION
        "-- empty --"
    ::= { lcsStatusTcpIpNetbiosPeersEntry 4 }

-- {TABLE} 1712.1.9.8.18
lcsStatusTcpIpNetbiosNetworksTable OBJECT-TYPE
    SYNTAX     SEQUENCE OF LcsStatusTcpIpNetbiosNetworksEntry
    MAX-ACCESS not-accessible
    STATUS     current
    DESCRIPTION
        "-- empty --"
    ::= { lcsStatusTcpIpNetbios 18 }

-- {ENTRY} 1712.1.9.8.18.1
lcsStatusTcpIpNetbiosNetworksEntry OBJECT-TYPE
    SYNTAX     LcsStatusTcpIpNetbiosNetworksEntry
    MAX-ACCESS not-accessible
    STATUS     current
    DESCRIPTION
        ""
    INDEX {
        lcsStatusTcpIpNetbiosNetworksEntryNetworkName
    }
    ::= { lcsStatusTcpIpNetbiosNetworksTable 1 }

-- {SEQUENCE}
LcsStatusTcpIpNetbiosNetworksEntry ::= SEQUENCE {
    lcsStatusTcpIpNetbiosNetworksEntryNetworkName DisplayString,
    lcsStatusTcpIpNetbiosNetworksEntryNtDomain DisplayString,
    lcsStatusTcpIpNetbiosNetworksEntryRtgTag INTEGER,
    lcsStatusTcpIpNetbiosNetworksEntryInterface INTEGER,
    lcsStatusTcpIpNetbiosNetworksEntryVlanId INTEGER
}

-- {COLUMN} 1712.1.9.8.18.1.1
lcsStatusTcpIpNetbiosNetworksEntryNetworkName OBJECT-TYPE
    SYNTAX     DisplayString (SIZE(0..16))
    MAX-ACCESS read-only
    STATUS     current
    DESCRIPTION
        "-- empty --"
    ::= { lcsStatusTcpIpNetbiosNetworksEntry 1 }

-- {COLUMN} 1712.1.9.8.18.1.2
lcsStatusTcpIpNetbiosNetworksEntryNtDomain OBJECT-TYPE
    SYNTAX     DisplayString (SIZE(0..15))
    MAX-ACCESS read-only
    STATUS     current
    DESCRIPTION
        "-- empty --"
    ::= { lcsStatusTcpIpNetbiosNetworksEntry 2 }

-- {COLUMN} 1712.1.9.8.18.1.3
lcsStatusTcpIpNetbiosNetworksEntryRtgTag OBJECT-TYPE
    SYNTAX     INTEGER (0..65535)
    MAX-ACCESS read-only
    STATUS     current
    DESCRIPTION
        "-- empty --"
    ::= { lcsStatusTcpIpNetbiosNetworksEntry 3 }

-- {COLUMN} 1712.1.9.8.18.1.7
lcsStatusTcpIpNetbiosNetworksEntryInterface OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusTcpIpNetbiosNetworksEntry 7 }

-- {COLUMN} 1712.1.9.8.18.1.5
lcsStatusTcpIpNetbiosNetworksEntryVlanId OBJECT-TYPE
    SYNTAX     INTEGER (0..65535)
    MAX-ACCESS read-only
    STATUS     current
    DESCRIPTION
        "-- empty --"
    ::= { lcsStatusTcpIpNetbiosNetworksEntry 5 }

-- {TABLE} 1712.1.9.8.19
lcsStatusTcpIpNetbiosGroupListTable OBJECT-TYPE
    SYNTAX     SEQUENCE OF LcsStatusTcpIpNetbiosGroupListEntry
    MAX-ACCESS not-accessible
    STATUS     current
    DESCRIPTION
        "-- empty --"
    ::= { lcsStatusTcpIpNetbios 19 }

-- {ENTRY} 1712.1.9.8.19.1
lcsStatusTcpIpNetbiosGroupListEntry OBJECT-TYPE
    SYNTAX     LcsStatusTcpIpNetbiosGroupListEntry
    MAX-ACCESS not-accessible
    STATUS     current
    DESCRIPTION
        ""
    INDEX {
        lcsStatusTcpIpNetbiosGroupListEntryGroupDomain,
        lcsStatusTcpIpNetbiosGroupListEntryType,
        lcsStatusTcpIpNetbiosGroupListEntryIpAddress,
        lcsStatusTcpIpNetbiosGroupListEntryRtgTag
    }
    ::= { lcsStatusTcpIpNetbiosGroupListTable 1 }

-- {SEQUENCE}
LcsStatusTcpIpNetbiosGroupListEntry ::= SEQUENCE {
    lcsStatusTcpIpNetbiosGroupListEntryGroupDomain DisplayString,
    lcsStatusTcpIpNetbiosGroupListEntryType DisplayString,
    lcsStatusTcpIpNetbiosGroupListEntryIpAddress IpAddress,
    lcsStatusTcpIpNetbiosGroupListEntryRtgTag INTEGER,
    lcsStatusTcpIpNetbiosGroupListEntryPeer DisplayString,
    lcsStatusTcpIpNetbiosGroupListEntryNetworkName DisplayString,
    lcsStatusTcpIpNetbiosGroupListEntryTimeout INTEGER,
    lcsStatusTcpIpNetbiosGroupListEntryFlags DisplayString
}

-- {COLUMN} 1712.1.9.8.19.1.1
lcsStatusTcpIpNetbiosGroupListEntryGroupDomain OBJECT-TYPE
    SYNTAX     DisplayString (SIZE(0..15))
    MAX-ACCESS read-only
    STATUS     current
    DESCRIPTION
        "-- empty --"
    ::= { lcsStatusTcpIpNetbiosGroupListEntry 1 }

-- {COLUMN} 1712.1.9.8.19.1.2
lcsStatusTcpIpNetbiosGroupListEntryType OBJECT-TYPE
    SYNTAX     DisplayString (SIZE(0..1))
    MAX-ACCESS read-only
    STATUS     current
    DESCRIPTION
        "-- empty --"
    ::= { lcsStatusTcpIpNetbiosGroupListEntry 2 }

-- {COLUMN} 1712.1.9.8.19.1.3
lcsStatusTcpIpNetbiosGroupListEntryIpAddress OBJECT-TYPE
    SYNTAX     IpAddress
    MAX-ACCESS read-only
    STATUS     current
    DESCRIPTION
        "-- empty --"
    ::= { lcsStatusTcpIpNetbiosGroupListEntry 3 }

-- {COLUMN} 1712.1.9.8.19.1.8
lcsStatusTcpIpNetbiosGroupListEntryRtgTag OBJECT-TYPE
    SYNTAX     INTEGER (0..65535)
    MAX-ACCESS read-only
    STATUS     current
    DESCRIPTION
        "-- empty --"
    ::= { lcsStatusTcpIpNetbiosGroupListEntry 8 }

-- {COLUMN} 1712.1.9.8.19.1.4
lcsStatusTcpIpNetbiosGroupListEntryPeer OBJECT-TYPE
    SYNTAX     DisplayString (SIZE(0..16))
    MAX-ACCESS read-only
    STATUS     current
    DESCRIPTION
        "-- empty --"
    ::= { lcsStatusTcpIpNetbiosGroupListEntry 4 }

-- {COLUMN} 1712.1.9.8.19.1.7
lcsStatusTcpIpNetbiosGroupListEntryNetworkName OBJECT-TYPE
    SYNTAX     DisplayString (SIZE(0..16))
    MAX-ACCESS read-only
    STATUS     current
    DESCRIPTION
        "-- empty --"
    ::= { lcsStatusTcpIpNetbiosGroupListEntry 7 }

-- {COLUMN} 1712.1.9.8.19.1.5
lcsStatusTcpIpNetbiosGroupListEntryTimeout OBJECT-TYPE
    SYNTAX     INTEGER (0..2147483647)
    MAX-ACCESS read-only
    STATUS     current
    DESCRIPTION
        "-- empty --"
    ::= { lcsStatusTcpIpNetbiosGroupListEntry 5 }

-- {COLUMN} 1712.1.9.8.19.1.6
lcsStatusTcpIpNetbiosGroupListEntryFlags OBJECT-TYPE
    SYNTAX     DisplayString (SIZE(0..2))
    MAX-ACCESS read-only
    STATUS     current
    DESCRIPTION
        "-- empty --"
    ::= { lcsStatusTcpIpNetbiosGroupListEntry 6 }

-- {TABLE} 1712.1.9.8.20
lcsStatusTcpIpNetbiosHostListTable OBJECT-TYPE
    SYNTAX     SEQUENCE OF LcsStatusTcpIpNetbiosHostListEntry
    MAX-ACCESS not-accessible
    STATUS     current
    DESCRIPTION
        "-- empty --"
    ::= { lcsStatusTcpIpNetbios 20 }

-- {ENTRY} 1712.1.9.8.20.1
lcsStatusTcpIpNetbiosHostListEntry OBJECT-TYPE
    SYNTAX     LcsStatusTcpIpNetbiosHostListEntry
    MAX-ACCESS not-accessible
    STATUS     current
    DESCRIPTION
        ""
    INDEX {
        lcsStatusTcpIpNetbiosHostListEntryName,
        lcsStatusTcpIpNetbiosHostListEntryType,
        lcsStatusTcpIpNetbiosHostListEntryIpAddress,
        lcsStatusTcpIpNetbiosHostListEntryRtgTag
    }
    ::= { lcsStatusTcpIpNetbiosHostListTable 1 }

-- {SEQUENCE}
LcsStatusTcpIpNetbiosHostListEntry ::= SEQUENCE {
    lcsStatusTcpIpNetbiosHostListEntryName DisplayString,
    lcsStatusTcpIpNetbiosHostListEntryType DisplayString,
    lcsStatusTcpIpNetbiosHostListEntryIpAddress IpAddress,
    lcsStatusTcpIpNetbiosHostListEntryRtgTag INTEGER,
    lcsStatusTcpIpNetbiosHostListEntryPeer DisplayString,
    lcsStatusTcpIpNetbiosHostListEntryNetworkName DisplayString,
    lcsStatusTcpIpNetbiosHostListEntryTimeout INTEGER,
    lcsStatusTcpIpNetbiosHostListEntryFlags DisplayString
}

-- {COLUMN} 1712.1.9.8.20.1.1
lcsStatusTcpIpNetbiosHostListEntryName OBJECT-TYPE
    SYNTAX     DisplayString (SIZE(0..15))
    MAX-ACCESS read-only
    STATUS     current
    DESCRIPTION
        "-- empty --"
    ::= { lcsStatusTcpIpNetbiosHostListEntry 1 }

-- {COLUMN} 1712.1.9.8.20.1.2
lcsStatusTcpIpNetbiosHostListEntryType OBJECT-TYPE
    SYNTAX     DisplayString (SIZE(0..1))
    MAX-ACCESS read-only
    STATUS     current
    DESCRIPTION
        "-- empty --"
    ::= { lcsStatusTcpIpNetbiosHostListEntry 2 }

-- {COLUMN} 1712.1.9.8.20.1.3
lcsStatusTcpIpNetbiosHostListEntryIpAddress OBJECT-TYPE
    SYNTAX     IpAddress
    MAX-ACCESS read-only
    STATUS     current
    DESCRIPTION
        "-- empty --"
    ::= { lcsStatusTcpIpNetbiosHostListEntry 3 }

-- {COLUMN} 1712.1.9.8.20.1.8
lcsStatusTcpIpNetbiosHostListEntryRtgTag OBJECT-TYPE
    SYNTAX     INTEGER (0..65535)
    MAX-ACCESS read-only
    STATUS     current
    DESCRIPTION
        "-- empty --"
    ::= { lcsStatusTcpIpNetbiosHostListEntry 8 }

-- {COLUMN} 1712.1.9.8.20.1.4
lcsStatusTcpIpNetbiosHostListEntryPeer OBJECT-TYPE
    SYNTAX     DisplayString (SIZE(0..16))
    MAX-ACCESS read-only
    STATUS     current
    DESCRIPTION
        "-- empty --"
    ::= { lcsStatusTcpIpNetbiosHostListEntry 4 }

-- {COLUMN} 1712.1.9.8.20.1.7
lcsStatusTcpIpNetbiosHostListEntryNetworkName OBJECT-TYPE
    SYNTAX     DisplayString (SIZE(0..16))
    MAX-ACCESS read-only
    STATUS     current
    DESCRIPTION
        "-- empty --"
    ::= { lcsStatusTcpIpNetbiosHostListEntry 7 }

-- {COLUMN} 1712.1.9.8.20.1.5
lcsStatusTcpIpNetbiosHostListEntryTimeout OBJECT-TYPE
    SYNTAX     INTEGER (0..2147483647)
    MAX-ACCESS read-only
    STATUS     current
    DESCRIPTION
        "-- empty --"
    ::= { lcsStatusTcpIpNetbiosHostListEntry 5 }

-- {COLUMN} 1712.1.9.8.20.1.6
lcsStatusTcpIpNetbiosHostListEntryFlags OBJECT-TYPE
    SYNTAX     DisplayString (SIZE(0..2))
    MAX-ACCESS read-only
    STATUS     current
    DESCRIPTION
        "-- empty --"
    ::= { lcsStatusTcpIpNetbiosHostListEntry 6 }

-- {TABLE} 1712.1.9.8.21
lcsStatusTcpIpNetbiosServerListTable OBJECT-TYPE
    SYNTAX     SEQUENCE OF LcsStatusTcpIpNetbiosServerListEntry
    MAX-ACCESS not-accessible
    STATUS     current
    DESCRIPTION
        "-- empty --"
    ::= { lcsStatusTcpIpNetbios 21 }

-- {ENTRY} 1712.1.9.8.21.1
lcsStatusTcpIpNetbiosServerListEntry OBJECT-TYPE
    SYNTAX     LcsStatusTcpIpNetbiosServerListEntry
    MAX-ACCESS not-accessible
    STATUS     current
    DESCRIPTION
        ""
    INDEX {
        lcsStatusTcpIpNetbiosServerListEntryHost,
        lcsStatusTcpIpNetbiosServerListEntryGroupDomain,
        lcsStatusTcpIpNetbiosServerListEntryIpAddress,
        lcsStatusTcpIpNetbiosServerListEntryRtgTag
    }
    ::= { lcsStatusTcpIpNetbiosServerListTable 1 }

-- {SEQUENCE}
LcsStatusTcpIpNetbiosServerListEntry ::= SEQUENCE {
    lcsStatusTcpIpNetbiosServerListEntryHost DisplayString,
    lcsStatusTcpIpNetbiosServerListEntryGroupDomain DisplayString,
    lcsStatusTcpIpNetbiosServerListEntryIpAddress DisplayString,
    lcsStatusTcpIpNetbiosServerListEntryRtgTag INTEGER,
    lcsStatusTcpIpNetbiosServerListEntryOsVer DisplayString,
    lcsStatusTcpIpNetbiosServerListEntrySmbVer DisplayString,
    lcsStatusTcpIpNetbiosServerListEntryServerTyp DisplayString,
    lcsStatusTcpIpNetbiosServerListEntryPeer DisplayString,
    lcsStatusTcpIpNetbiosServerListEntryNetworkName DisplayString,
    lcsStatusTcpIpNetbiosServerListEntryTimeout INTEGER,
    lcsStatusTcpIpNetbiosServerListEntryFlags DisplayString
}

-- {COLUMN} 1712.1.9.8.21.1.1
lcsStatusTcpIpNetbiosServerListEntryHost OBJECT-TYPE
    SYNTAX     DisplayString (SIZE(0..15))
    MAX-ACCESS read-only
    STATUS     current
    DESCRIPTION
        "-- empty --"
    ::= { lcsStatusTcpIpNetbiosServerListEntry 1 }

-- {COLUMN} 1712.1.9.8.21.1.2
lcsStatusTcpIpNetbiosServerListEntryGroupDomain OBJECT-TYPE
    SYNTAX     DisplayString (SIZE(0..16))
    MAX-ACCESS read-only
    STATUS     current
    DESCRIPTION
        "-- empty --"
    ::= { lcsStatusTcpIpNetbiosServerListEntry 2 }

-- {COLUMN} 1712.1.9.8.21.1.4
lcsStatusTcpIpNetbiosServerListEntryIpAddress OBJECT-TYPE
    SYNTAX     DisplayString (SIZE(0..15))
    MAX-ACCESS read-only
    STATUS     current
    DESCRIPTION
        "-- empty --"
    ::= { lcsStatusTcpIpNetbiosServerListEntry 4 }

-- {COLUMN} 1712.1.9.8.21.1.12
lcsStatusTcpIpNetbiosServerListEntryRtgTag OBJECT-TYPE
    SYNTAX     INTEGER (0..65535)
    MAX-ACCESS read-only
    STATUS     current
    DESCRIPTION
        "-- empty --"
    ::= { lcsStatusTcpIpNetbiosServerListEntry 12 }

-- {COLUMN} 1712.1.9.8.21.1.5
lcsStatusTcpIpNetbiosServerListEntryOsVer OBJECT-TYPE
    SYNTAX     DisplayString (SIZE(0..2))
    MAX-ACCESS read-only
    STATUS     current
    DESCRIPTION
        "-- empty --"
    ::= { lcsStatusTcpIpNetbiosServerListEntry 5 }

-- {COLUMN} 1712.1.9.8.21.1.6
lcsStatusTcpIpNetbiosServerListEntrySmbVer OBJECT-TYPE
    SYNTAX     DisplayString (SIZE(0..2))
    MAX-ACCESS read-only
    STATUS     current
    DESCRIPTION
        "-- empty --"
    ::= { lcsStatusTcpIpNetbiosServerListEntry 6 }

-- {COLUMN} 1712.1.9.8.21.1.7
lcsStatusTcpIpNetbiosServerListEntryServerTyp OBJECT-TYPE
    SYNTAX     DisplayString (SIZE(0..4))
    MAX-ACCESS read-only
    STATUS     current
    DESCRIPTION
        "-- empty --"
    ::= { lcsStatusTcpIpNetbiosServerListEntry 7 }

-- {COLUMN} 1712.1.9.8.21.1.8
lcsStatusTcpIpNetbiosServerListEntryPeer OBJECT-TYPE
    SYNTAX     DisplayString (SIZE(0..16))
    MAX-ACCESS read-only
    STATUS     current
    DESCRIPTION
        "-- empty --"
    ::= { lcsStatusTcpIpNetbiosServerListEntry 8 }

-- {COLUMN} 1712.1.9.8.21.1.11
lcsStatusTcpIpNetbiosServerListEntryNetworkName OBJECT-TYPE
    SYNTAX     DisplayString (SIZE(0..16))
    MAX-ACCESS read-only
    STATUS     current
    DESCRIPTION
        "-- empty --"
    ::= { lcsStatusTcpIpNetbiosServerListEntry 11 }

-- {COLUMN} 1712.1.9.8.21.1.9
lcsStatusTcpIpNetbiosServerListEntryTimeout OBJECT-TYPE
    SYNTAX     INTEGER (0..2147483647)
    MAX-ACCESS read-only
    STATUS     current
    DESCRIPTION
        "-- empty --"
    ::= { lcsStatusTcpIpNetbiosServerListEntry 9 }

-- {COLUMN} 1712.1.9.8.21.1.10
lcsStatusTcpIpNetbiosServerListEntryFlags OBJECT-TYPE
    SYNTAX     DisplayString (SIZE(0..2))
    MAX-ACCESS read-only
    STATUS     current
    DESCRIPTION
        "-- empty --"
    ::= { lcsStatusTcpIpNetbiosServerListEntry 10 }

-- {TABLE} 1712.1.9.8.22
lcsStatusTcpIpNetbiosBrowserListTable OBJECT-TYPE
    SYNTAX     SEQUENCE OF LcsStatusTcpIpNetbiosBrowserListEntry
    MAX-ACCESS not-accessible
    STATUS     current
    DESCRIPTION
        "-- empty --"
    ::= { lcsStatusTcpIpNetbios 22 }

-- {ENTRY} 1712.1.9.8.22.1
lcsStatusTcpIpNetbiosBrowserListEntry OBJECT-TYPE
    SYNTAX     LcsStatusTcpIpNetbiosBrowserListEntry
    MAX-ACCESS not-accessible
    STATUS     current
    DESCRIPTION
        ""
    INDEX {
        lcsStatusTcpIpNetbiosBrowserListEntryBrowser,
        lcsStatusTcpIpNetbiosBrowserListEntryGroupDomain,
        lcsStatusTcpIpNetbiosBrowserListEntryIpAddress,
        lcsStatusTcpIpNetbiosBrowserListEntryRtgTag
    }
    ::= { lcsStatusTcpIpNetbiosBrowserListTable 1 }

-- {SEQUENCE}
LcsStatusTcpIpNetbiosBrowserListEntry ::= SEQUENCE {
    lcsStatusTcpIpNetbiosBrowserListEntryBrowser DisplayString,
    lcsStatusTcpIpNetbiosBrowserListEntryGroupDomain DisplayString,
    lcsStatusTcpIpNetbiosBrowserListEntryIpAddress DisplayString,
    lcsStatusTcpIpNetbiosBrowserListEntryRtgTag INTEGER,
    lcsStatusTcpIpNetbiosBrowserListEntryOsVer DisplayString,
    lcsStatusTcpIpNetbiosBrowserListEntryServerTyp DisplayString,
    lcsStatusTcpIpNetbiosBrowserListEntryPeer DisplayString,
    lcsStatusTcpIpNetbiosBrowserListEntryNetworkName DisplayString,
    lcsStatusTcpIpNetbiosBrowserListEntryTimeout INTEGER,
    lcsStatusTcpIpNetbiosBrowserListEntryFlags DisplayString
}

-- {COLUMN} 1712.1.9.8.22.1.1
lcsStatusTcpIpNetbiosBrowserListEntryBrowser OBJECT-TYPE
    SYNTAX     DisplayString (SIZE(0..15))
    MAX-ACCESS read-only
    STATUS     current
    DESCRIPTION
        "-- empty --"
    ::= { lcsStatusTcpIpNetbiosBrowserListEntry 1 }

-- {COLUMN} 1712.1.9.8.22.1.2
lcsStatusTcpIpNetbiosBrowserListEntryGroupDomain OBJECT-TYPE
    SYNTAX     DisplayString (SIZE(0..16))
    MAX-ACCESS read-only
    STATUS     current
    DESCRIPTION
        "-- empty --"
    ::= { lcsStatusTcpIpNetbiosBrowserListEntry 2 }

-- {COLUMN} 1712.1.9.8.22.1.4
lcsStatusTcpIpNetbiosBrowserListEntryIpAddress OBJECT-TYPE
    SYNTAX     DisplayString (SIZE(0..15))
    MAX-ACCESS read-only
    STATUS     current
    DESCRIPTION
        "-- empty --"
    ::= { lcsStatusTcpIpNetbiosBrowserListEntry 4 }

-- {COLUMN} 1712.1.9.8.22.1.12
lcsStatusTcpIpNetbiosBrowserListEntryRtgTag OBJECT-TYPE
    SYNTAX     INTEGER (0..65535)
    MAX-ACCESS read-only
    STATUS     current
    DESCRIPTION
        "-- empty --"
    ::= { lcsStatusTcpIpNetbiosBrowserListEntry 12 }

-- {COLUMN} 1712.1.9.8.22.1.5
lcsStatusTcpIpNetbiosBrowserListEntryOsVer OBJECT-TYPE
    SYNTAX     DisplayString (SIZE(0..2))
    MAX-ACCESS read-only
    STATUS     current
    DESCRIPTION
        "-- empty --"
    ::= { lcsStatusTcpIpNetbiosBrowserListEntry 5 }

-- {COLUMN} 1712.1.9.8.22.1.7
lcsStatusTcpIpNetbiosBrowserListEntryServerTyp OBJECT-TYPE
    SYNTAX     DisplayString (SIZE(0..4))
    MAX-ACCESS read-only
    STATUS     current
    DESCRIPTION
        "-- empty --"
    ::= { lcsStatusTcpIpNetbiosBrowserListEntry 7 }

-- {COLUMN} 1712.1.9.8.22.1.8
lcsStatusTcpIpNetbiosBrowserListEntryPeer OBJECT-TYPE
    SYNTAX     DisplayString (SIZE(0..16))
    MAX-ACCESS read-only
    STATUS     current
    DESCRIPTION
        "-- empty --"
    ::= { lcsStatusTcpIpNetbiosBrowserListEntry 8 }

-- {COLUMN} 1712.1.9.8.22.1.11
lcsStatusTcpIpNetbiosBrowserListEntryNetworkName OBJECT-TYPE
    SYNTAX     DisplayString (SIZE(0..16))
    MAX-ACCESS read-only
    STATUS     current
    DESCRIPTION
        "-- empty --"
    ::= { lcsStatusTcpIpNetbiosBrowserListEntry 11 }

-- {COLUMN} 1712.1.9.8.22.1.9
lcsStatusTcpIpNetbiosBrowserListEntryTimeout OBJECT-TYPE
    SYNTAX     INTEGER (0..2147483647)
    MAX-ACCESS read-only
    STATUS     current
    DESCRIPTION
        "-- empty --"
    ::= { lcsStatusTcpIpNetbiosBrowserListEntry 9 }

-- {COLUMN} 1712.1.9.8.22.1.10
lcsStatusTcpIpNetbiosBrowserListEntryFlags OBJECT-TYPE
    SYNTAX     DisplayString (SIZE(0..2))
    MAX-ACCESS read-only
    STATUS     current
    DESCRIPTION
        "-- empty --"
    ::= { lcsStatusTcpIpNetbiosBrowserListEntry 10 }

-- {SCALAR} 1712.1.9.8.17
lcsStatusTcpIpNetbiosDeleteValues OBJECT-TYPE
    SYNTAX     DisplayString
    MAX-ACCESS read-write
    STATUS     current
    DESCRIPTION
        "-- empty --"
    ::= { lcsStatusTcpIpNetbios 17 }

-- {OID} 1712.1.9.9
lcsStatusTcpIpDns OBJECT IDENTIFIER ::= { lcsStatusTcpIp 9 }

-- {SCALAR} 1712.1.9.9.1
lcsStatusTcpIpDnsLanRx OBJECT-TYPE
    SYNTAX     Counter32
    MAX-ACCESS read-only
    STATUS     current
    DESCRIPTION
        "-- empty --"
    ::= { lcsStatusTcpIpDns 1 }

-- {SCALAR} 1712.1.9.9.2
lcsStatusTcpIpDnsLanTx OBJECT-TYPE
    SYNTAX     Counter32
    MAX-ACCESS read-only
    STATUS     current
    DESCRIPTION
        "-- empty --"
    ::= { lcsStatusTcpIpDns 2 }

-- {SCALAR} 1712.1.9.9.3
lcsStatusTcpIpDnsWanRx OBJECT-TYPE
    SYNTAX     Counter32
    MAX-ACCESS read-only
    STATUS     current
    DESCRIPTION
        "-- empty --"
    ::= { lcsStatusTcpIpDns 3 }

-- {SCALAR} 1712.1.9.9.4
lcsStatusTcpIpDnsWanTx OBJECT-TYPE
    SYNTAX     Counter32
    MAX-ACCESS read-only
    STATUS     current
    DESCRIPTION
        "-- empty --"
    ::= { lcsStatusTcpIpDns 4 }

-- {SCALAR} 1712.1.9.9.5
lcsStatusTcpIpDnsForwarded OBJECT-TYPE
    SYNTAX     Counter32
    MAX-ACCESS read-only
    STATUS     current
    DESCRIPTION
        "-- empty --"
    ::= { lcsStatusTcpIpDns 5 }

-- {SCALAR} 1712.1.9.9.6
lcsStatusTcpIpDnsErrors OBJECT-TYPE
    SYNTAX     Counter32
    MAX-ACCESS read-only
    STATUS     current
    DESCRIPTION
        "-- empty --"
    ::= { lcsStatusTcpIpDns 6 }

-- {SCALAR} 1712.1.9.9.7
lcsStatusTcpIpDnsDnsAccess OBJECT-TYPE
    SYNTAX     Counter32
    MAX-ACCESS read-only
    STATUS     current
    DESCRIPTION
        "-- empty --"
    ::= { lcsStatusTcpIpDns 7 }

-- {SCALAR} 1712.1.9.9.8
lcsStatusTcpIpDnsDhcpAccess OBJECT-TYPE
    SYNTAX     Counter32
    MAX-ACCESS read-only
    STATUS     current
    DESCRIPTION
        "-- empty --"
    ::= { lcsStatusTcpIpDns 8 }

-- {SCALAR} 1712.1.9.9.9
lcsStatusTcpIpDnsNetbiosAccess OBJECT-TYPE
    SYNTAX     Counter32
    MAX-ACCESS read-only
    STATUS     current
    DESCRIPTION
        "-- empty --"
    ::= { lcsStatusTcpIpDns 9 }

-- {SCALAR} 1712.1.9.9.10
lcsStatusTcpIpDnsFilter OBJECT-TYPE
    SYNTAX     Counter32
    MAX-ACCESS read-only
    STATUS     current
    DESCRIPTION
        "-- empty --"
    ::= { lcsStatusTcpIpDns 10 }

-- {TABLE} 1712.1.9.9.11
lcsStatusTcpIpDnsHitListTable OBJECT-TYPE
    SYNTAX     SEQUENCE OF LcsStatusTcpIpDnsHitListEntry
    MAX-ACCESS not-accessible
    STATUS     current
    DESCRIPTION
        "-- empty --"
    ::= { lcsStatusTcpIpDns 11 }

-- {ENTRY} 1712.1.9.9.11.1
lcsStatusTcpIpDnsHitListEntry OBJECT-TYPE
    SYNTAX     LcsStatusTcpIpDnsHitListEntry
    MAX-ACCESS not-accessible
    STATUS     current
    DESCRIPTION
        ""
    INDEX {
        lcsStatusTcpIpDnsHitListEntryDomain
    }
    ::= { lcsStatusTcpIpDnsHitListTable 1 }

-- {SEQUENCE}
LcsStatusTcpIpDnsHitListEntry ::= SEQUENCE {
    lcsStatusTcpIpDnsHitListEntryDomain DisplayString,
    lcsStatusTcpIpDnsHitListEntryRequests INTEGER,
    lcsStatusTcpIpDnsHitListEntryTime DisplayString,
    lcsStatusTcpIpDnsHitListEntryIpAddress IpAddress,
    lcsStatusTcpIpDnsHitListEntryIpv6Address DisplayString
}

-- {COLUMN} 1712.1.9.9.11.1.1
lcsStatusTcpIpDnsHitListEntryDomain OBJECT-TYPE
    SYNTAX     DisplayString (SIZE(0..64))
    MAX-ACCESS read-only
    STATUS     current
    DESCRIPTION
        "-- empty --"
    ::= { lcsStatusTcpIpDnsHitListEntry 1 }

-- {COLUMN} 1712.1.9.9.11.1.2
lcsStatusTcpIpDnsHitListEntryRequests OBJECT-TYPE
    SYNTAX     INTEGER (0..2147483647)
    MAX-ACCESS read-only
    STATUS     current
    DESCRIPTION
        "-- empty --"
    ::= { lcsStatusTcpIpDnsHitListEntry 2 }

-- {COLUMN} 1712.1.9.9.11.1.3
lcsStatusTcpIpDnsHitListEntryTime OBJECT-TYPE
    SYNTAX     DisplayString (SIZE(0..20))
    MAX-ACCESS read-only
    STATUS     current
    DESCRIPTION
        "-- empty --"
    ::= { lcsStatusTcpIpDnsHitListEntry 3 }

-- {COLUMN} 1712.1.9.9.11.1.4
lcsStatusTcpIpDnsHitListEntryIpAddress OBJECT-TYPE
    SYNTAX     IpAddress
    MAX-ACCESS read-only
    STATUS     current
    DESCRIPTION
        "-- empty --"
    ::= { lcsStatusTcpIpDnsHitListEntry 4 }

-- {COLUMN} 1712.1.9.9.11.1.5
lcsStatusTcpIpDnsHitListEntryIpv6Address OBJECT-TYPE
    SYNTAX     DisplayString (SIZE(0..255))
    MAX-ACCESS read-only
    STATUS     current
    DESCRIPTION
        "-- empty --"
    ::= { lcsStatusTcpIpDnsHitListEntry 5 }

-- {SCALAR} 1712.1.9.9.12
lcsStatusTcpIpDnsDeleteValues OBJECT-TYPE
    SYNTAX     DisplayString
    MAX-ACCESS read-write
    STATUS     current
    DESCRIPTION
        "-- empty --"
    ::= { lcsStatusTcpIpDns 12 }

-- {OID} 1712.1.9.10
lcsStatusTcpIpHttp OBJECT IDENTIFIER ::= { lcsStatusTcpIp 10 }

-- {SCALAR} 1712.1.9.10.1
lcsStatusTcpIpHttpHttpAccesses OBJECT-TYPE
    SYNTAX     Counter32
    MAX-ACCESS read-only
    STATUS     current
    DESCRIPTION
        "-- empty --"
    ::= { lcsStatusTcpIpHttp 1 }

-- {SCALAR} 1712.1.9.10.6
lcsStatusTcpIpHttpHttpsAccesses OBJECT-TYPE
    SYNTAX     Counter32
    MAX-ACCESS read-only
    STATUS     current
    DESCRIPTION
        "-- empty --"
    ::= { lcsStatusTcpIpHttp 6 }

-- {SCALAR} 1712.1.9.10.2
lcsStatusTcpIpHttpHttpNotfoundErrors OBJECT-TYPE
    SYNTAX     Counter32
    MAX-ACCESS read-only
    STATUS     current
    DESCRIPTION
        "-- empty --"
    ::= { lcsStatusTcpIpHttp 2 }

-- {SCALAR} 1712.1.9.10.3
lcsStatusTcpIpHttpHttpAuthenticationErrors OBJECT-TYPE
    SYNTAX     Counter32
    MAX-ACCESS read-only
    STATUS     current
    DESCRIPTION
        "-- empty --"
    ::= { lcsStatusTcpIpHttp 3 }

-- {SCALAR} 1712.1.9.10.4
lcsStatusTcpIpHttpHttpProtocolErrors OBJECT-TYPE
    SYNTAX     Counter32
    MAX-ACCESS read-only
    STATUS     current
    DESCRIPTION
        "-- empty --"
    ::= { lcsStatusTcpIpHttp 4 }

-- {TABLE} 1712.1.9.10.7
lcsStatusTcpIpHttpAgentListTable OBJECT-TYPE
    SYNTAX     SEQUENCE OF LcsStatusTcpIpHttpAgentListEntry
    MAX-ACCESS not-accessible
    STATUS     current
    DESCRIPTION
        "-- empty --"
    ::= { lcsStatusTcpIpHttp 7 }

-- {ENTRY} 1712.1.9.10.7.1
lcsStatusTcpIpHttpAgentListEntry OBJECT-TYPE
    SYNTAX     LcsStatusTcpIpHttpAgentListEntry
    MAX-ACCESS not-accessible
    STATUS     current
    DESCRIPTION
        ""
    INDEX {
        lcsStatusTcpIpHttpAgentListEntryAgentName
    }
    ::= { lcsStatusTcpIpHttpAgentListTable 1 }

-- {SEQUENCE}
LcsStatusTcpIpHttpAgentListEntry ::= SEQUENCE {
    lcsStatusTcpIpHttpAgentListEntryAgentName DisplayString,
    lcsStatusTcpIpHttpAgentListEntryAccesses INTEGER
}

-- {COLUMN} 1712.1.9.10.7.1.1
lcsStatusTcpIpHttpAgentListEntryAgentName OBJECT-TYPE
    SYNTAX     DisplayString (SIZE(0..67))
    MAX-ACCESS read-only
    STATUS     current
    DESCRIPTION
        "-- empty --"
    ::= { lcsStatusTcpIpHttpAgentListEntry 1 }

-- {COLUMN} 1712.1.9.10.7.1.2
lcsStatusTcpIpHttpAgentListEntryAccesses OBJECT-TYPE
    SYNTAX     INTEGER (0..2147483647)
    MAX-ACCESS read-only
    STATUS     current
    DESCRIPTION
        "-- empty --"
    ::= { lcsStatusTcpIpHttpAgentListEntry 2 }

-- {SCALAR} 1712.1.9.10.5
lcsStatusTcpIpHttpDeleteValues OBJECT-TYPE
    SYNTAX     DisplayString
    MAX-ACCESS read-write
    STATUS     current
    DESCRIPTION
        "-- empty --"
    ::= { lcsStatusTcpIpHttp 5 }

-- {SCALAR} 1712.1.9.10.15
lcsStatusTcpIpHttpMaxHttpJobCount OBJECT-TYPE
    SYNTAX     INTEGER (0..2147483647)
    MAX-ACCESS read-only
    STATUS     current
    DESCRIPTION
        "-- empty --"
    ::= { lcsStatusTcpIpHttp 15 }

-- {SCALAR} 1712.1.9.10.16
lcsStatusTcpIpHttpJobCount OBJECT-TYPE
    SYNTAX     INTEGER (0..2147483647)
    MAX-ACCESS read-only
    STATUS     current
    DESCRIPTION
        "-- empty --"
    ::= { lcsStatusTcpIpHttp 16 }

-- {SCALAR} 1712.1.9.10.17
lcsStatusTcpIpHttpIdleJobs OBJECT-TYPE
    SYNTAX     INTEGER (0..2147483647)
    MAX-ACCESS read-only
    STATUS     current
    DESCRIPTION
        "-- empty --"
    ::= { lcsStatusTcpIpHttp 17 }

-- {TABLE} 1712.1.9.10.8
lcsStatusTcpIpHttpActiveTunnelsTable OBJECT-TYPE
    SYNTAX     SEQUENCE OF LcsStatusTcpIpHttpActiveTunnelsEntry
    MAX-ACCESS not-accessible
    STATUS     current
    DESCRIPTION
        "-- empty --"
    ::= { lcsStatusTcpIpHttp 8 }

-- {ENTRY} 1712.1.9.10.8.1
lcsStatusTcpIpHttpActiveTunnelsEntry OBJECT-TYPE
    SYNTAX     LcsStatusTcpIpHttpActiveTunnelsEntry
    MAX-ACCESS not-accessible
    STATUS     current
    DESCRIPTION
        ""
    INDEX {
        lcsStatusTcpIpHttpActiveTunnelsEntryIndex
    }
    ::= { lcsStatusTcpIpHttpActiveTunnelsTable 1 }

-- {SEQUENCE}
LcsStatusTcpIpHttpActiveTunnelsEntry ::= SEQUENCE {
    lcsStatusTcpIpHttpActiveTunnelsEntryIndex INTEGER,
    lcsStatusTcpIpHttpActiveTunnelsEntryRemoteAddress IpAddress,
    lcsStatusTcpIpHttpActiveTunnelsEntryRemotePort INTEGER,
    lcsStatusTcpIpHttpActiveTunnelsEntryLocalHost DisplayString,
    lcsStatusTcpIpHttpActiveTunnelsEntryLocalPort INTEGER,
    lcsStatusTcpIpHttpActiveTunnelsEntryLocalRtgTag INTEGER,
    lcsStatusTcpIpHttpActiveTunnelsEntryIdleTime INTEGER,
    lcsStatusTcpIpHttpActiveTunnelsEntryState INTEGER,
    lcsStatusTcpIpHttpActiveTunnelsEntryNumConnections INTEGER
}

-- {COLUMN} 1712.1.9.10.8.1.1
lcsStatusTcpIpHttpActiveTunnelsEntryIndex OBJECT-TYPE
    SYNTAX     INTEGER (0..2147483647)
    MAX-ACCESS read-only
    STATUS     current
    DESCRIPTION
        "-- empty --"
    ::= { lcsStatusTcpIpHttpActiveTunnelsEntry 1 }

-- {COLUMN} 1712.1.9.10.8.1.2
lcsStatusTcpIpHttpActiveTunnelsEntryRemoteAddress OBJECT-TYPE
    SYNTAX     IpAddress
    MAX-ACCESS read-only
    STATUS     current
    DESCRIPTION
        "-- empty --"
    ::= { lcsStatusTcpIpHttpActiveTunnelsEntry 2 }

-- {COLUMN} 1712.1.9.10.8.1.3
lcsStatusTcpIpHttpActiveTunnelsEntryRemotePort OBJECT-TYPE
    SYNTAX     INTEGER (0..65535)
    MAX-ACCESS read-only
    STATUS     current
    DESCRIPTION
        "-- empty --"
    ::= { lcsStatusTcpIpHttpActiveTunnelsEntry 3 }

-- {COLUMN} 1712.1.9.10.8.1.4
lcsStatusTcpIpHttpActiveTunnelsEntryLocalHost OBJECT-TYPE
    SYNTAX     DisplayString (SIZE(0..48))
    MAX-ACCESS read-only
    STATUS     current
    DESCRIPTION
        "-- empty --"
    ::= { lcsStatusTcpIpHttpActiveTunnelsEntry 4 }

-- {COLUMN} 1712.1.9.10.8.1.5
lcsStatusTcpIpHttpActiveTunnelsEntryLocalPort OBJECT-TYPE
    SYNTAX     INTEGER (0..65535)
    MAX-ACCESS read-only
    STATUS     current
    DESCRIPTION
        "-- empty --"
    ::= { lcsStatusTcpIpHttpActiveTunnelsEntry 5 }

-- {COLUMN} 1712.1.9.10.8.1.7
lcsStatusTcpIpHttpActiveTunnelsEntryLocalRtgTag OBJECT-TYPE
    SYNTAX     INTEGER (0..65535)
    MAX-ACCESS read-only
    STATUS     current
    DESCRIPTION
        "-- empty --"
    ::= { lcsStatusTcpIpHttpActiveTunnelsEntry 7 }

-- {COLUMN} 1712.1.9.10.8.1.6
lcsStatusTcpIpHttpActiveTunnelsEntryIdleTime OBJECT-TYPE
    SYNTAX     INTEGER (0..2147483647)
    MAX-ACCESS read-only
    STATUS     current
    DESCRIPTION
        "-- empty --"
    ::= { lcsStatusTcpIpHttpActiveTunnelsEntry 6 }

-- {COLUMN} 1712.1.9.10.8.1.9
lcsStatusTcpIpHttpActiveTunnelsEntryState OBJECT-TYPE
    SYNTAX     INTEGER
      {
        eActive (0),
        eClosing (1)
      }
    MAX-ACCESS read-only
    STATUS     current
    DESCRIPTION
        "-- empty --"
    ::= { lcsStatusTcpIpHttpActiveTunnelsEntry 9 }

-- {COLUMN} 1712.1.9.10.8.1.8
lcsStatusTcpIpHttpActiveTunnelsEntryNumConnections OBJECT-TYPE
    SYNTAX     INTEGER (0..2147483647)
    MAX-ACCESS read-only
    STATUS     current
    DESCRIPTION
        "-- empty --"
    ::= { lcsStatusTcpIpHttpActiveTunnelsEntry 8 }

-- {TABLE} 1712.1.9.20
lcsStatusTcpIpNetworkListTable OBJECT-TYPE
    SYNTAX     SEQUENCE OF LcsStatusTcpIpNetworkListEntry
    MAX-ACCESS not-accessible
    STATUS     current
    DESCRIPTION
        "-- empty --"
    ::= { lcsStatusTcpIp 20 }

-- {ENTRY} 1712.1.9.20.1
lcsStatusTcpIpNetworkListEntry OBJECT-TYPE
    SYNTAX     LcsStatusTcpIpNetworkListEntry
    MAX-ACCESS not-accessible
    STATUS     current
    DESCRIPTION
        ""
    INDEX {
        lcsStatusTcpIpNetworkListEntryNetworkName
    }
    ::= { lcsStatusTcpIpNetworkListTable 1 }

-- {SEQUENCE}
LcsStatusTcpIpNetworkListEntry ::= SEQUENCE {
    lcsStatusTcpIpNetworkListEntryNetworkName DisplayString,
    lcsStatusTcpIpNetworkListEntryIpAddress IpAddress,
    lcsStatusTcpIpNetworkListEntryIpNetmask IpAddress,
    lcsStatusTcpIpNetworkListEntryVlanId INTEGER,
    lcsStatusTcpIpNetworkListEntryInterface INTEGER,
    lcsStatusTcpIpNetworkListEntrySrcCheck INTEGER,
    lcsStatusTcpIpNetworkListEntryType INTEGER,
    lcsStatusTcpIpNetworkListEntryRtgTag INTEGER
}

-- {COLUMN} 1712.1.9.20.1.1
lcsStatusTcpIpNetworkListEntryNetworkName OBJECT-TYPE
    SYNTAX     DisplayString (SIZE(0..17))
    MAX-ACCESS read-only
    STATUS     current
    DESCRIPTION
        "-- empty --"
    ::= { lcsStatusTcpIpNetworkListEntry 1 }

-- {COLUMN} 1712.1.9.20.1.2
lcsStatusTcpIpNetworkListEntryIpAddress OBJECT-TYPE
    SYNTAX     IpAddress
    MAX-ACCESS read-only
    STATUS     current
    DESCRIPTION
        "-- empty --"
    ::= { lcsStatusTcpIpNetworkListEntry 2 }

-- {COLUMN} 1712.1.9.20.1.3
lcsStatusTcpIpNetworkListEntryIpNetmask OBJECT-TYPE
    SYNTAX     IpAddress
    MAX-ACCESS read-only
    STATUS     current
    DESCRIPTION
        "-- empty --"
    ::= { lcsStatusTcpIpNetworkListEntry 3 }

-- {COLUMN} 1712.1.9.20.1.4
lcsStatusTcpIpNetworkListEntryVlanId OBJECT-TYPE
    SYNTAX     INTEGER (0..65535)
    MAX-ACCESS read-only
    STATUS     current
    DESCRIPTION
        "-- empty --"
    ::= { lcsStatusTcpIpNetworkListEntry 4 }

-- {COLUMN} 1712.1.9.20.1.5
lcsStatusTcpIpNetworkListEntryInterface OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusTcpIpNetworkListEntry 5 }

-- {COLUMN} 1712.1.9.20.1.6
lcsStatusTcpIpNetworkListEntrySrcCheck OBJECT-TYPE
    SYNTAX     INTEGER
      {
        eStrict (1),
        eLoose (0)
      }
    MAX-ACCESS read-only
    STATUS     current
    DESCRIPTION
        "-- empty --"
    ::= { lcsStatusTcpIpNetworkListEntry 6 }

-- {COLUMN} 1712.1.9.20.1.7
lcsStatusTcpIpNetworkListEntryType OBJECT-TYPE
    SYNTAX     INTEGER
      {
        eDisabled (0),
        eIntranet (1),
        eDmz (2)
      }
    MAX-ACCESS read-only
    STATUS     current
    DESCRIPTION
        "-- empty --"
    ::= { lcsStatusTcpIpNetworkListEntry 7 }

-- {COLUMN} 1712.1.9.20.1.8
lcsStatusTcpIpNetworkListEntryRtgTag OBJECT-TYPE
    SYNTAX     INTEGER (0..65535)
    MAX-ACCESS read-only
    STATUS     current
    DESCRIPTION
        "-- empty --"
    ::= { lcsStatusTcpIpNetworkListEntry 8 }

-- {OID} 1712.1.9.13
lcsStatusTcpIpRadiusc OBJECT IDENTIFIER ::= { lcsStatusTcpIp 13 }

-- {SCALAR} 1712.1.9.13.1
lcsStatusTcpIpRadiuscInvalAuthAddrResp OBJECT-TYPE
    SYNTAX     Counter32
    MAX-ACCESS read-only
    STATUS     current
    DESCRIPTION
        ""
    ::= { lcsStatusTcpIpRadiusc 1 }

-- {TABLE} 1712.1.9.13.2
lcsStatusTcpIpRadiuscAuthServTable OBJECT-TYPE
    SYNTAX     SEQUENCE OF LcsStatusTcpIpRadiuscAuthServEntry
    MAX-ACCESS not-accessible
    STATUS     current
    DESCRIPTION
        ""
    ::= { lcsStatusTcpIpRadiusc 2 }

-- {ENTRY} 1712.1.9.13.2.1
lcsStatusTcpIpRadiuscAuthServEntry OBJECT-TYPE
    SYNTAX     LcsStatusTcpIpRadiuscAuthServEntry
    MAX-ACCESS not-accessible
    STATUS     current
    DESCRIPTION
        ""
    INDEX {
        lcsStatusTcpIpRadiuscAuthServEntryIpAddr,
        lcsStatusTcpIpRadiuscAuthServEntryPort
    }
    ::= { lcsStatusTcpIpRadiuscAuthServTable 1 }

-- {SEQUENCE}
LcsStatusTcpIpRadiuscAuthServEntry ::= SEQUENCE {
    lcsStatusTcpIpRadiuscAuthServEntryIpAddr IpAddress,
    lcsStatusTcpIpRadiuscAuthServEntryPort INTEGER,
    lcsStatusTcpIpRadiuscAuthServEntryLastRequest INTEGER,
    lcsStatusTcpIpRadiuscAuthServEntryRoundTripTime Counter32,
    lcsStatusTcpIpRadiuscAuthServEntryAccReq Counter32,
    lcsStatusTcpIpRadiuscAuthServEntryAccRetrs Counter32,
    lcsStatusTcpIpRadiuscAuthServEntryAccAccepts Counter32,
    lcsStatusTcpIpRadiuscAuthServEntryAccRej Counter32,
    lcsStatusTcpIpRadiuscAuthServEntryAccChallenges Counter32,
    lcsStatusTcpIpRadiuscAuthServEntryMalfAccResp Counter32,
    lcsStatusTcpIpRadiuscAuthServEntryBadAuth Counter32,
    lcsStatusTcpIpRadiuscAuthServEntryPendReq Counter32,
    lcsStatusTcpIpRadiuscAuthServEntryTimeouts Counter32,
    lcsStatusTcpIpRadiuscAuthServEntryUnknownTypes Counter32,
    lcsStatusTcpIpRadiuscAuthServEntryDropped Counter32
}

-- {COLUMN} 1712.1.9.13.2.1.1
lcsStatusTcpIpRadiuscAuthServEntryIpAddr OBJECT-TYPE
    SYNTAX     IpAddress
    MAX-ACCESS read-only
    STATUS     current
    DESCRIPTION
        ""
    ::= { lcsStatusTcpIpRadiuscAuthServEntry 1 }

-- {COLUMN} 1712.1.9.13.2.1.2
lcsStatusTcpIpRadiuscAuthServEntryPort OBJECT-TYPE
    SYNTAX     INTEGER (0..65535)
    MAX-ACCESS read-only
    STATUS     current
    DESCRIPTION
        ""
    ::= { lcsStatusTcpIpRadiuscAuthServEntry 2 }

-- {COLUMN} 1712.1.9.13.2.1.3
lcsStatusTcpIpRadiuscAuthServEntryLastRequest OBJECT-TYPE
    SYNTAX     INTEGER (0..2147483647)
    MAX-ACCESS read-only
    STATUS     current
    DESCRIPTION
        ""
    ::= { lcsStatusTcpIpRadiuscAuthServEntry 3 }

-- {COLUMN} 1712.1.9.13.2.1.4
lcsStatusTcpIpRadiuscAuthServEntryRoundTripTime OBJECT-TYPE
    SYNTAX     Counter32
    MAX-ACCESS read-only
    STATUS     current
    DESCRIPTION
        ""
    ::= { lcsStatusTcpIpRadiuscAuthServEntry 4 }

-- {COLUMN} 1712.1.9.13.2.1.5
lcsStatusTcpIpRadiuscAuthServEntryAccReq OBJECT-TYPE
    SYNTAX     Counter32
    MAX-ACCESS read-only
    STATUS     current
    DESCRIPTION
        ""
    ::= { lcsStatusTcpIpRadiuscAuthServEntry 5 }

-- {COLUMN} 1712.1.9.13.2.1.6
lcsStatusTcpIpRadiuscAuthServEntryAccRetrs OBJECT-TYPE
    SYNTAX     Counter32
    MAX-ACCESS read-only
    STATUS     current
    DESCRIPTION
        ""
    ::= { lcsStatusTcpIpRadiuscAuthServEntry 6 }

-- {COLUMN} 1712.1.9.13.2.1.7
lcsStatusTcpIpRadiuscAuthServEntryAccAccepts OBJECT-TYPE
    SYNTAX     Counter32
    MAX-ACCESS read-only
    STATUS     current
    DESCRIPTION
        ""
    ::= { lcsStatusTcpIpRadiuscAuthServEntry 7 }

-- {COLUMN} 1712.1.9.13.2.1.8
lcsStatusTcpIpRadiuscAuthServEntryAccRej OBJECT-TYPE
    SYNTAX     Counter32
    MAX-ACCESS read-only
    STATUS     current
    DESCRIPTION
        ""
    ::= { lcsStatusTcpIpRadiuscAuthServEntry 8 }

-- {COLUMN} 1712.1.9.13.2.1.9
lcsStatusTcpIpRadiuscAuthServEntryAccChallenges OBJECT-TYPE
    SYNTAX     Counter32
    MAX-ACCESS read-only
    STATUS     current
    DESCRIPTION
        ""
    ::= { lcsStatusTcpIpRadiuscAuthServEntry 9 }

-- {COLUMN} 1712.1.9.13.2.1.10
lcsStatusTcpIpRadiuscAuthServEntryMalfAccResp OBJECT-TYPE
    SYNTAX     Counter32
    MAX-ACCESS read-only
    STATUS     current
    DESCRIPTION
        ""
    ::= { lcsStatusTcpIpRadiuscAuthServEntry 10 }

-- {COLUMN} 1712.1.9.13.2.1.11
lcsStatusTcpIpRadiuscAuthServEntryBadAuth OBJECT-TYPE
    SYNTAX     Counter32
    MAX-ACCESS read-only
    STATUS     current
    DESCRIPTION
        ""
    ::= { lcsStatusTcpIpRadiuscAuthServEntry 11 }

-- {COLUMN} 1712.1.9.13.2.1.12
lcsStatusTcpIpRadiuscAuthServEntryPendReq OBJECT-TYPE
    SYNTAX     Counter32
    MAX-ACCESS read-only
    STATUS     current
    DESCRIPTION
        ""
    ::= { lcsStatusTcpIpRadiuscAuthServEntry 12 }

-- {COLUMN} 1712.1.9.13.2.1.13
lcsStatusTcpIpRadiuscAuthServEntryTimeouts OBJECT-TYPE
    SYNTAX     Counter32
    MAX-ACCESS read-only
    STATUS     current
    DESCRIPTION
        ""
    ::= { lcsStatusTcpIpRadiuscAuthServEntry 13 }

-- {COLUMN} 1712.1.9.13.2.1.14
lcsStatusTcpIpRadiuscAuthServEntryUnknownTypes OBJECT-TYPE
    SYNTAX     Counter32
    MAX-ACCESS read-only
    STATUS     current
    DESCRIPTION
        ""
    ::= { lcsStatusTcpIpRadiuscAuthServEntry 14 }

-- {COLUMN} 1712.1.9.13.2.1.15
lcsStatusTcpIpRadiuscAuthServEntryDropped OBJECT-TYPE
    SYNTAX     Counter32
    MAX-ACCESS read-only
    STATUS     current
    DESCRIPTION
        ""
    ::= { lcsStatusTcpIpRadiuscAuthServEntry 15 }

-- {TABLE} 1712.1.9.13.3
lcsStatusTcpIpRadiuscIpv6AuthenticationServersTable OBJECT-TYPE
    SYNTAX     SEQUENCE OF LcsStatusTcpIpRadiuscIpv6AuthenticationServersEntry
    MAX-ACCESS not-accessible
    STATUS     current
    DESCRIPTION
        "-- empty --"
    ::= { lcsStatusTcpIpRadiusc 3 }

-- {ENTRY} 1712.1.9.13.3.1
lcsStatusTcpIpRadiuscIpv6AuthenticationServersEntry OBJECT-TYPE
    SYNTAX     LcsStatusTcpIpRadiuscIpv6AuthenticationServersEntry
    MAX-ACCESS not-accessible
    STATUS     current
    DESCRIPTION
        ""
    INDEX {
        lcsStatusTcpIpRadiuscIpv6AuthenticationServersEntryIpAddr,
        lcsStatusTcpIpRadiuscIpv6AuthenticationServersEntryPort
    }
    ::= { lcsStatusTcpIpRadiuscIpv6AuthenticationServersTable 1 }

-- {SEQUENCE}
LcsStatusTcpIpRadiuscIpv6AuthenticationServersEntry ::= SEQUENCE {
    lcsStatusTcpIpRadiuscIpv6AuthenticationServersEntryIpAddr IpAddress,
    lcsStatusTcpIpRadiuscIpv6AuthenticationServersEntryPort INTEGER,
    lcsStatusTcpIpRadiuscIpv6AuthenticationServersEntryLastRequest INTEGER,
    lcsStatusTcpIpRadiuscIpv6AuthenticationServersEntryRoundTripTime Counter32,
    lcsStatusTcpIpRadiuscIpv6AuthenticationServersEntryAccReq Counter32,
    lcsStatusTcpIpRadiuscIpv6AuthenticationServersEntryAccRetrs Counter32,
    lcsStatusTcpIpRadiuscIpv6AuthenticationServersEntryAccAccepts Counter32,
    lcsStatusTcpIpRadiuscIpv6AuthenticationServersEntryAccRej Counter32,
    lcsStatusTcpIpRadiuscIpv6AuthenticationServersEntryAccChallenges Counter32,
    lcsStatusTcpIpRadiuscIpv6AuthenticationServersEntryMalfAccResp Counter32,
    lcsStatusTcpIpRadiuscIpv6AuthenticationServersEntryBadAuth Counter32,
    lcsStatusTcpIpRadiuscIpv6AuthenticationServersEntryPendReq Counter32,
    lcsStatusTcpIpRadiuscIpv6AuthenticationServersEntryTimeouts Counter32,
    lcsStatusTcpIpRadiuscIpv6AuthenticationServersEntryUnknownTypes Counter32,
    lcsStatusTcpIpRadiuscIpv6AuthenticationServersEntryDropped Counter32
}

-- {COLUMN} 1712.1.9.13.3.1.1
lcsStatusTcpIpRadiuscIpv6AuthenticationServersEntryIpAddr OBJECT-TYPE
    SYNTAX     IpAddress
    MAX-ACCESS read-only
    STATUS     current
    DESCRIPTION
        ""
    ::= { lcsStatusTcpIpRadiuscIpv6AuthenticationServersEntry 1 }

-- {COLUMN} 1712.1.9.13.3.1.2
lcsStatusTcpIpRadiuscIpv6AuthenticationServersEntryPort OBJECT-TYPE
    SYNTAX     INTEGER (0..65535)
    MAX-ACCESS read-only
    STATUS     current
    DESCRIPTION
        ""
    ::= { lcsStatusTcpIpRadiuscIpv6AuthenticationServersEntry 2 }

-- {COLUMN} 1712.1.9.13.3.1.3
lcsStatusTcpIpRadiuscIpv6AuthenticationServersEntryLastRequest OBJECT-TYPE
    SYNTAX     INTEGER (0..2147483647)
    MAX-ACCESS read-only
    STATUS     current
    DESCRIPTION
        ""
    ::= { lcsStatusTcpIpRadiuscIpv6AuthenticationServersEntry 3 }

-- {COLUMN} 1712.1.9.13.3.1.4
lcsStatusTcpIpRadiuscIpv6AuthenticationServersEntryRoundTripTime OBJECT-TYPE
    SYNTAX     Counter32
    MAX-ACCESS read-only
    STATUS     current
    DESCRIPTION
        ""
    ::= { lcsStatusTcpIpRadiuscIpv6AuthenticationServersEntry 4 }

-- {COLUMN} 1712.1.9.13.3.1.5
lcsStatusTcpIpRadiuscIpv6AuthenticationServersEntryAccReq OBJECT-TYPE
    SYNTAX     Counter32
    MAX-ACCESS read-only
    STATUS     current
    DESCRIPTION
        ""
    ::= { lcsStatusTcpIpRadiuscIpv6AuthenticationServersEntry 5 }

-- {COLUMN} 1712.1.9.13.3.1.6
lcsStatusTcpIpRadiuscIpv6AuthenticationServersEntryAccRetrs OBJECT-TYPE
    SYNTAX     Counter32
    MAX-ACCESS read-only
    STATUS     current
    DESCRIPTION
        ""
    ::= { lcsStatusTcpIpRadiuscIpv6AuthenticationServersEntry 6 }

-- {COLUMN} 1712.1.9.13.3.1.7
lcsStatusTcpIpRadiuscIpv6AuthenticationServersEntryAccAccepts OBJECT-TYPE
    SYNTAX     Counter32
    MAX-ACCESS read-only
    STATUS     current
    DESCRIPTION
        ""
    ::= { lcsStatusTcpIpRadiuscIpv6AuthenticationServersEntry 7 }

-- {COLUMN} 1712.1.9.13.3.1.8
lcsStatusTcpIpRadiuscIpv6AuthenticationServersEntryAccRej OBJECT-TYPE
    SYNTAX     Counter32
    MAX-ACCESS read-only
    STATUS     current
    DESCRIPTION
        ""
    ::= { lcsStatusTcpIpRadiuscIpv6AuthenticationServersEntry 8 }

-- {COLUMN} 1712.1.9.13.3.1.9
lcsStatusTcpIpRadiuscIpv6AuthenticationServersEntryAccChallenges OBJECT-TYPE
    SYNTAX     Counter32
    MAX-ACCESS read-only
    STATUS     current
    DESCRIPTION
        ""
    ::= { lcsStatusTcpIpRadiuscIpv6AuthenticationServersEntry 9 }

-- {COLUMN} 1712.1.9.13.3.1.10
lcsStatusTcpIpRadiuscIpv6AuthenticationServersEntryMalfAccResp OBJECT-TYPE
    SYNTAX     Counter32
    MAX-ACCESS read-only
    STATUS     current
    DESCRIPTION
        ""
    ::= { lcsStatusTcpIpRadiuscIpv6AuthenticationServersEntry 10 }

-- {COLUMN} 1712.1.9.13.3.1.11
lcsStatusTcpIpRadiuscIpv6AuthenticationServersEntryBadAuth OBJECT-TYPE
    SYNTAX     Counter32
    MAX-ACCESS read-only
    STATUS     current
    DESCRIPTION
        ""
    ::= { lcsStatusTcpIpRadiuscIpv6AuthenticationServersEntry 11 }

-- {COLUMN} 1712.1.9.13.3.1.12
lcsStatusTcpIpRadiuscIpv6AuthenticationServersEntryPendReq OBJECT-TYPE
    SYNTAX     Counter32
    MAX-ACCESS read-only
    STATUS     current
    DESCRIPTION
        ""
    ::= { lcsStatusTcpIpRadiuscIpv6AuthenticationServersEntry 12 }

-- {COLUMN} 1712.1.9.13.3.1.13
lcsStatusTcpIpRadiuscIpv6AuthenticationServersEntryTimeouts OBJECT-TYPE
    SYNTAX     Counter32
    MAX-ACCESS read-only
    STATUS     current
    DESCRIPTION
        ""
    ::= { lcsStatusTcpIpRadiuscIpv6AuthenticationServersEntry 13 }

-- {COLUMN} 1712.1.9.13.3.1.14
lcsStatusTcpIpRadiuscIpv6AuthenticationServersEntryUnknownTypes OBJECT-TYPE
    SYNTAX     Counter32
    MAX-ACCESS read-only
    STATUS     current
    DESCRIPTION
        ""
    ::= { lcsStatusTcpIpRadiuscIpv6AuthenticationServersEntry 14 }

-- {COLUMN} 1712.1.9.13.3.1.15
lcsStatusTcpIpRadiuscIpv6AuthenticationServersEntryDropped OBJECT-TYPE
    SYNTAX     Counter32
    MAX-ACCESS read-only
    STATUS     current
    DESCRIPTION
        ""
    ::= { lcsStatusTcpIpRadiuscIpv6AuthenticationServersEntry 15 }

-- {SCALAR} 1712.1.9.13.11
lcsStatusTcpIpRadiuscInvalAccntAddrResp OBJECT-TYPE
    SYNTAX     Counter32
    MAX-ACCESS read-only
    STATUS     current
    DESCRIPTION
        ""
    ::= { lcsStatusTcpIpRadiusc 11 }

-- {TABLE} 1712.1.9.13.12
lcsStatusTcpIpRadiuscAccntServTable OBJECT-TYPE
    SYNTAX     SEQUENCE OF LcsStatusTcpIpRadiuscAccntServEntry
    MAX-ACCESS not-accessible
    STATUS     current
    DESCRIPTION
        ""
    ::= { lcsStatusTcpIpRadiusc 12 }

-- {ENTRY} 1712.1.9.13.12.1
lcsStatusTcpIpRadiuscAccntServEntry OBJECT-TYPE
    SYNTAX     LcsStatusTcpIpRadiuscAccntServEntry
    MAX-ACCESS not-accessible
    STATUS     current
    DESCRIPTION
        ""
    INDEX {
        lcsStatusTcpIpRadiuscAccntServEntryIpAddr,
        lcsStatusTcpIpRadiuscAccntServEntryPort
    }
    ::= { lcsStatusTcpIpRadiuscAccntServTable 1 }

-- {SEQUENCE}
LcsStatusTcpIpRadiuscAccntServEntry ::= SEQUENCE {
    lcsStatusTcpIpRadiuscAccntServEntryIpAddr IpAddress,
    lcsStatusTcpIpRadiuscAccntServEntryPort INTEGER,
    lcsStatusTcpIpRadiuscAccntServEntryLastRequest INTEGER,
    lcsStatusTcpIpRadiuscAccntServEntryRoundTripTime Counter32,
    lcsStatusTcpIpRadiuscAccntServEntryAccntReq Counter32,
    lcsStatusTcpIpRadiuscAccntServEntryAccntRetrans Counter32,
    lcsStatusTcpIpRadiuscAccntServEntryAccntResp Counter32,
    lcsStatusTcpIpRadiuscAccntServEntryMalfAccntResp Counter32,
    lcsStatusTcpIpRadiuscAccntServEntryBadAuth Counter32,
    lcsStatusTcpIpRadiuscAccntServEntryPendReq Counter32,
    lcsStatusTcpIpRadiuscAccntServEntryTimeouts Counter32,
    lcsStatusTcpIpRadiuscAccntServEntryUnknownTypes Counter32,
    lcsStatusTcpIpRadiuscAccntServEntryDropped Counter32
}

-- {COLUMN} 1712.1.9.13.12.1.1
lcsStatusTcpIpRadiuscAccntServEntryIpAddr OBJECT-TYPE
    SYNTAX     IpAddress
    MAX-ACCESS read-only
    STATUS     current
    DESCRIPTION
        ""
    ::= { lcsStatusTcpIpRadiuscAccntServEntry 1 }

-- {COLUMN} 1712.1.9.13.12.1.2
lcsStatusTcpIpRadiuscAccntServEntryPort OBJECT-TYPE
    SYNTAX     INTEGER (0..65535)
    MAX-ACCESS read-only
    STATUS     current
    DESCRIPTION
        ""
    ::= { lcsStatusTcpIpRadiuscAccntServEntry 2 }

-- {COLUMN} 1712.1.9.13.12.1.3
lcsStatusTcpIpRadiuscAccntServEntryLastRequest OBJECT-TYPE
    SYNTAX     INTEGER (0..2147483647)
    MAX-ACCESS read-only
    STATUS     current
    DESCRIPTION
        ""
    ::= { lcsStatusTcpIpRadiuscAccntServEntry 3 }

-- {COLUMN} 1712.1.9.13.12.1.4
lcsStatusTcpIpRadiuscAccntServEntryRoundTripTime OBJECT-TYPE
    SYNTAX     Counter32
    MAX-ACCESS read-only
    STATUS     current
    DESCRIPTION
        ""
    ::= { lcsStatusTcpIpRadiuscAccntServEntry 4 }

-- {COLUMN} 1712.1.9.13.12.1.5
lcsStatusTcpIpRadiuscAccntServEntryAccntReq OBJECT-TYPE
    SYNTAX     Counter32
    MAX-ACCESS read-only
    STATUS     current
    DESCRIPTION
        ""
    ::= { lcsStatusTcpIpRadiuscAccntServEntry 5 }

-- {COLUMN} 1712.1.9.13.12.1.6
lcsStatusTcpIpRadiuscAccntServEntryAccntRetrans OBJECT-TYPE
    SYNTAX     Counter32
    MAX-ACCESS read-only
    STATUS     current
    DESCRIPTION
        ""
    ::= { lcsStatusTcpIpRadiuscAccntServEntry 6 }

-- {COLUMN} 1712.1.9.13.12.1.7
lcsStatusTcpIpRadiuscAccntServEntryAccntResp OBJECT-TYPE
    SYNTAX     Counter32
    MAX-ACCESS read-only
    STATUS     current
    DESCRIPTION
        ""
    ::= { lcsStatusTcpIpRadiuscAccntServEntry 7 }

-- {COLUMN} 1712.1.9.13.12.1.8
lcsStatusTcpIpRadiuscAccntServEntryMalfAccntResp OBJECT-TYPE
    SYNTAX     Counter32
    MAX-ACCESS read-only
    STATUS     current
    DESCRIPTION
        ""
    ::= { lcsStatusTcpIpRadiuscAccntServEntry 8 }

-- {COLUMN} 1712.1.9.13.12.1.9
lcsStatusTcpIpRadiuscAccntServEntryBadAuth OBJECT-TYPE
    SYNTAX     Counter32
    MAX-ACCESS read-only
    STATUS     current
    DESCRIPTION
        ""
    ::= { lcsStatusTcpIpRadiuscAccntServEntry 9 }

-- {COLUMN} 1712.1.9.13.12.1.10
lcsStatusTcpIpRadiuscAccntServEntryPendReq OBJECT-TYPE
    SYNTAX     Counter32
    MAX-ACCESS read-only
    STATUS     current
    DESCRIPTION
        ""
    ::= { lcsStatusTcpIpRadiuscAccntServEntry 10 }

-- {COLUMN} 1712.1.9.13.12.1.11
lcsStatusTcpIpRadiuscAccntServEntryTimeouts OBJECT-TYPE
    SYNTAX     Counter32
    MAX-ACCESS read-only
    STATUS     current
    DESCRIPTION
        ""
    ::= { lcsStatusTcpIpRadiuscAccntServEntry 11 }

-- {COLUMN} 1712.1.9.13.12.1.12
lcsStatusTcpIpRadiuscAccntServEntryUnknownTypes OBJECT-TYPE
    SYNTAX     Counter32
    MAX-ACCESS read-only
    STATUS     current
    DESCRIPTION
        ""
    ::= { lcsStatusTcpIpRadiuscAccntServEntry 12 }

-- {COLUMN} 1712.1.9.13.12.1.13
lcsStatusTcpIpRadiuscAccntServEntryDropped OBJECT-TYPE
    SYNTAX     Counter32
    MAX-ACCESS read-only
    STATUS     current
    DESCRIPTION
        ""
    ::= { lcsStatusTcpIpRadiuscAccntServEntry 13 }

-- {TABLE} 1712.1.9.13.13
lcsStatusTcpIpRadiuscIpv6AccountingServersTable OBJECT-TYPE
    SYNTAX     SEQUENCE OF LcsStatusTcpIpRadiuscIpv6AccountingServersEntry
    MAX-ACCESS not-accessible
    STATUS     current
    DESCRIPTION
        "-- empty --"
    ::= { lcsStatusTcpIpRadiusc 13 }

-- {ENTRY} 1712.1.9.13.13.1
lcsStatusTcpIpRadiuscIpv6AccountingServersEntry OBJECT-TYPE
    SYNTAX     LcsStatusTcpIpRadiuscIpv6AccountingServersEntry
    MAX-ACCESS not-accessible
    STATUS     current
    DESCRIPTION
        ""
    INDEX {
        lcsStatusTcpIpRadiuscIpv6AccountingServersEntryIpAddr,
        lcsStatusTcpIpRadiuscIpv6AccountingServersEntryPort
    }
    ::= { lcsStatusTcpIpRadiuscIpv6AccountingServersTable 1 }

-- {SEQUENCE}
LcsStatusTcpIpRadiuscIpv6AccountingServersEntry ::= SEQUENCE {
    lcsStatusTcpIpRadiuscIpv6AccountingServersEntryIpAddr IpAddress,
    lcsStatusTcpIpRadiuscIpv6AccountingServersEntryPort INTEGER,
    lcsStatusTcpIpRadiuscIpv6AccountingServersEntryLastRequest INTEGER,
    lcsStatusTcpIpRadiuscIpv6AccountingServersEntryRoundTripTime Counter32,
    lcsStatusTcpIpRadiuscIpv6AccountingServersEntryAccntReq Counter32,
    lcsStatusTcpIpRadiuscIpv6AccountingServersEntryAccntRetrans Counter32,
    lcsStatusTcpIpRadiuscIpv6AccountingServersEntryAccntResp Counter32,
    lcsStatusTcpIpRadiuscIpv6AccountingServersEntryMalfAccntResp Counter32,
    lcsStatusTcpIpRadiuscIpv6AccountingServersEntryBadAuth Counter32,
    lcsStatusTcpIpRadiuscIpv6AccountingServersEntryPendReq Counter32,
    lcsStatusTcpIpRadiuscIpv6AccountingServersEntryTimeouts Counter32,
    lcsStatusTcpIpRadiuscIpv6AccountingServersEntryUnknownTypes Counter32,
    lcsStatusTcpIpRadiuscIpv6AccountingServersEntryDropped Counter32
}

-- {COLUMN} 1712.1.9.13.13.1.1
lcsStatusTcpIpRadiuscIpv6AccountingServersEntryIpAddr OBJECT-TYPE
    SYNTAX     IpAddress
    MAX-ACCESS read-only
    STATUS     current
    DESCRIPTION
        ""
    ::= { lcsStatusTcpIpRadiuscIpv6AccountingServersEntry 1 }

-- {COLUMN} 1712.1.9.13.13.1.2
lcsStatusTcpIpRadiuscIpv6AccountingServersEntryPort OBJECT-TYPE
    SYNTAX     INTEGER (0..65535)
    MAX-ACCESS read-only
    STATUS     current
    DESCRIPTION
        ""
    ::= { lcsStatusTcpIpRadiuscIpv6AccountingServersEntry 2 }

-- {COLUMN} 1712.1.9.13.13.1.3
lcsStatusTcpIpRadiuscIpv6AccountingServersEntryLastRequest OBJECT-TYPE
    SYNTAX     INTEGER (0..2147483647)
    MAX-ACCESS read-only
    STATUS     current
    DESCRIPTION
        ""
    ::= { lcsStatusTcpIpRadiuscIpv6AccountingServersEntry 3 }

-- {COLUMN} 1712.1.9.13.13.1.4
lcsStatusTcpIpRadiuscIpv6AccountingServersEntryRoundTripTime OBJECT-TYPE
    SYNTAX     Counter32
    MAX-ACCESS read-only
    STATUS     current
    DESCRIPTION
        ""
    ::= { lcsStatusTcpIpRadiuscIpv6AccountingServersEntry 4 }

-- {COLUMN} 1712.1.9.13.13.1.5
lcsStatusTcpIpRadiuscIpv6AccountingServersEntryAccntReq OBJECT-TYPE
    SYNTAX     Counter32
    MAX-ACCESS read-only
    STATUS     current
    DESCRIPTION
        ""
    ::= { lcsStatusTcpIpRadiuscIpv6AccountingServersEntry 5 }

-- {COLUMN} 1712.1.9.13.13.1.6
lcsStatusTcpIpRadiuscIpv6AccountingServersEntryAccntRetrans OBJECT-TYPE
    SYNTAX     Counter32
    MAX-ACCESS read-only
    STATUS     current
    DESCRIPTION
        ""
    ::= { lcsStatusTcpIpRadiuscIpv6AccountingServersEntry 6 }

-- {COLUMN} 1712.1.9.13.13.1.7
lcsStatusTcpIpRadiuscIpv6AccountingServersEntryAccntResp OBJECT-TYPE
    SYNTAX     Counter32
    MAX-ACCESS read-only
    STATUS     current
    DESCRIPTION
        ""
    ::= { lcsStatusTcpIpRadiuscIpv6AccountingServersEntry 7 }

-- {COLUMN} 1712.1.9.13.13.1.8
lcsStatusTcpIpRadiuscIpv6AccountingServersEntryMalfAccntResp OBJECT-TYPE
    SYNTAX     Counter32
    MAX-ACCESS read-only
    STATUS     current
    DESCRIPTION
        ""
    ::= { lcsStatusTcpIpRadiuscIpv6AccountingServersEntry 8 }

-- {COLUMN} 1712.1.9.13.13.1.9
lcsStatusTcpIpRadiuscIpv6AccountingServersEntryBadAuth OBJECT-TYPE
    SYNTAX     Counter32
    MAX-ACCESS read-only
    STATUS     current
    DESCRIPTION
        ""
    ::= { lcsStatusTcpIpRadiuscIpv6AccountingServersEntry 9 }

-- {COLUMN} 1712.1.9.13.13.1.10
lcsStatusTcpIpRadiuscIpv6AccountingServersEntryPendReq OBJECT-TYPE
    SYNTAX     Counter32
    MAX-ACCESS read-only
    STATUS     current
    DESCRIPTION
        ""
    ::= { lcsStatusTcpIpRadiuscIpv6AccountingServersEntry 10 }

-- {COLUMN} 1712.1.9.13.13.1.11
lcsStatusTcpIpRadiuscIpv6AccountingServersEntryTimeouts OBJECT-TYPE
    SYNTAX     Counter32
    MAX-ACCESS read-only
    STATUS     current
    DESCRIPTION
        ""
    ::= { lcsStatusTcpIpRadiuscIpv6AccountingServersEntry 11 }

-- {COLUMN} 1712.1.9.13.13.1.12
lcsStatusTcpIpRadiuscIpv6AccountingServersEntryUnknownTypes OBJECT-TYPE
    SYNTAX     Counter32
    MAX-ACCESS read-only
    STATUS     current
    DESCRIPTION
        ""
    ::= { lcsStatusTcpIpRadiuscIpv6AccountingServersEntry 12 }

-- {COLUMN} 1712.1.9.13.13.1.13
lcsStatusTcpIpRadiuscIpv6AccountingServersEntryDropped OBJECT-TYPE
    SYNTAX     Counter32
    MAX-ACCESS read-only
    STATUS     current
    DESCRIPTION
        ""
    ::= { lcsStatusTcpIpRadiuscIpv6AccountingServersEntry 13 }

-- {SCALAR} 1712.1.9.13.100
lcsStatusTcpIpRadiuscDeleteValues OBJECT-TYPE
    SYNTAX     DisplayString
    MAX-ACCESS read-write
    STATUS     current
    DESCRIPTION
        "-- empty --"
    ::= { lcsStatusTcpIpRadiusc 100 }

-- {OID} 1712.1.9.12
lcsStatusTcpIpRadiuss OBJECT IDENTIFIER ::= { lcsStatusTcpIp 12 }

-- {OID} 1712.1.9.12.1
lcsStatusTcpIpRadiussAccess OBJECT IDENTIFIER ::= { lcsStatusTcpIpRadiuss 1 }

-- {SCALAR} 1712.1.9.12.1.100
lcsStatusTcpIpRadiussAccessDeleteValues OBJECT-TYPE
    SYNTAX     DisplayString
    MAX-ACCESS read-write
    STATUS     current
    DESCRIPTION
        "-- empty --"
    ::= { lcsStatusTcpIpRadiussAccess 100 }

-- {TABLE} 1712.1.9.12.1.15
lcsStatusTcpIpRadiussAccessClientsTable OBJECT-TYPE
    SYNTAX     SEQUENCE OF LcsStatusTcpIpRadiussAccessClientsEntry
    MAX-ACCESS not-accessible
    STATUS     current
    DESCRIPTION
        "-- empty --"
    ::= { lcsStatusTcpIpRadiussAccess 15 }

-- {ENTRY} 1712.1.9.12.1.15.1
lcsStatusTcpIpRadiussAccessClientsEntry OBJECT-TYPE
    SYNTAX     LcsStatusTcpIpRadiussAccessClientsEntry
    MAX-ACCESS not-accessible
    STATUS     current
    DESCRIPTION
        ""
    INDEX {
        lcsStatusTcpIpRadiussAccessClientsEntryIpAddress
    }
    ::= { lcsStatusTcpIpRadiussAccessClientsTable 1 }

-- {SEQUENCE}
LcsStatusTcpIpRadiussAccessClientsEntry ::= SEQUENCE {
    lcsStatusTcpIpRadiussAccessClientsEntryIpAddress IpAddress,
    lcsStatusTcpIpRadiussAccessClientsEntryLastRequest INTEGER,
    lcsStatusTcpIpRadiussAccessClientsEntryLastStatusRequest INTEGER,
    lcsStatusTcpIpRadiussAccessClientsEntryNasIdent DisplayString,
    lcsStatusTcpIpRadiussAccessClientsEntryAccessRequests Counter32,
    lcsStatusTcpIpRadiussAccessClientsEntryStatusRequests Counter32,
    lcsStatusTcpIpRadiussAccessClientsEntryDuplicateRequests Counter32,
    lcsStatusTcpIpRadiussAccessClientsEntryAccessAccepts Counter32,
    lcsStatusTcpIpRadiussAccessClientsEntryAccessRejects Counter32,
    lcsStatusTcpIpRadiussAccessClientsEntryAccessChallenges Counter32,
    lcsStatusTcpIpRadiussAccessClientsEntryStatusResponses Counter32,
    lcsStatusTcpIpRadiussAccessClientsEntryMalfAccReq Counter32,
    lcsStatusTcpIpRadiussAccessClientsEntryBadAuthenticator Counter32,
    lcsStatusTcpIpRadiussAccessClientsEntryDropped Counter32,
    lcsStatusTcpIpRadiussAccessClientsEntryUnknownType Counter32
}

-- {COLUMN} 1712.1.9.12.1.15.1.1
lcsStatusTcpIpRadiussAccessClientsEntryIpAddress OBJECT-TYPE
    SYNTAX     IpAddress
    MAX-ACCESS read-only
    STATUS     current
    DESCRIPTION
        "-- empty --"
    ::= { lcsStatusTcpIpRadiussAccessClientsEntry 1 }

-- {COLUMN} 1712.1.9.12.1.15.1.13
lcsStatusTcpIpRadiussAccessClientsEntryLastRequest OBJECT-TYPE
    SYNTAX     INTEGER (0..2147483647)
    MAX-ACCESS read-only
    STATUS     current
    DESCRIPTION
        "-- empty --"
    ::= { lcsStatusTcpIpRadiussAccessClientsEntry 13 }

-- {COLUMN} 1712.1.9.12.1.15.1.32
lcsStatusTcpIpRadiussAccessClientsEntryLastStatusRequest OBJECT-TYPE
    SYNTAX     INTEGER (0..2147483647)
    MAX-ACCESS read-only
    STATUS     current
    DESCRIPTION
        "-- empty --"
    ::= { lcsStatusTcpIpRadiussAccessClientsEntry 32 }

-- {COLUMN} 1712.1.9.12.1.15.1.14
lcsStatusTcpIpRadiussAccessClientsEntryNasIdent OBJECT-TYPE
    SYNTAX     DisplayString (SIZE(0..64))
    MAX-ACCESS read-only
    STATUS     current
    DESCRIPTION
        "-- empty --"
    ::= { lcsStatusTcpIpRadiussAccessClientsEntry 14 }

-- {COLUMN} 1712.1.9.12.1.15.1.4
lcsStatusTcpIpRadiussAccessClientsEntryAccessRequests OBJECT-TYPE
    SYNTAX     Counter32
    MAX-ACCESS read-only
    STATUS     current
    DESCRIPTION
        "-- empty --"
    ::= { lcsStatusTcpIpRadiussAccessClientsEntry 4 }

-- {COLUMN} 1712.1.9.12.1.15.1.30
lcsStatusTcpIpRadiussAccessClientsEntryStatusRequests OBJECT-TYPE
    SYNTAX     Counter32
    MAX-ACCESS read-only
    STATUS     current
    DESCRIPTION
        "-- empty --"
    ::= { lcsStatusTcpIpRadiussAccessClientsEntry 30 }

-- {COLUMN} 1712.1.9.12.1.15.1.5
lcsStatusTcpIpRadiussAccessClientsEntryDuplicateRequests OBJECT-TYPE
    SYNTAX     Counter32
    MAX-ACCESS read-only
    STATUS     current
    DESCRIPTION
        "-- empty --"
    ::= { lcsStatusTcpIpRadiussAccessClientsEntry 5 }

-- {COLUMN} 1712.1.9.12.1.15.1.6
lcsStatusTcpIpRadiussAccessClientsEntryAccessAccepts OBJECT-TYPE
    SYNTAX     Counter32
    MAX-ACCESS read-only
    STATUS     current
    DESCRIPTION
        "-- empty --"
    ::= { lcsStatusTcpIpRadiussAccessClientsEntry 6 }

-- {COLUMN} 1712.1.9.12.1.15.1.7
lcsStatusTcpIpRadiussAccessClientsEntryAccessRejects OBJECT-TYPE
    SYNTAX     Counter32
    MAX-ACCESS read-only
    STATUS     current
    DESCRIPTION
        "-- empty --"
    ::= { lcsStatusTcpIpRadiussAccessClientsEntry 7 }

-- {COLUMN} 1712.1.9.12.1.15.1.8
lcsStatusTcpIpRadiussAccessClientsEntryAccessChallenges OBJECT-TYPE
    SYNTAX     Counter32
    MAX-ACCESS read-only
    STATUS     current
    DESCRIPTION
        "-- empty --"
    ::= { lcsStatusTcpIpRadiussAccessClientsEntry 8 }

-- {COLUMN} 1712.1.9.12.1.15.1.31
lcsStatusTcpIpRadiussAccessClientsEntryStatusResponses OBJECT-TYPE
    SYNTAX     Counter32
    MAX-ACCESS read-only
    STATUS     current
    DESCRIPTION
        "-- empty --"
    ::= { lcsStatusTcpIpRadiussAccessClientsEntry 31 }

-- {COLUMN} 1712.1.9.12.1.15.1.9
lcsStatusTcpIpRadiussAccessClientsEntryMalfAccReq OBJECT-TYPE
    SYNTAX     Counter32
    MAX-ACCESS read-only
    STATUS     current
    DESCRIPTION
        ""
    ::= { lcsStatusTcpIpRadiussAccessClientsEntry 9 }

-- {COLUMN} 1712.1.9.12.1.15.1.10
lcsStatusTcpIpRadiussAccessClientsEntryBadAuthenticator OBJECT-TYPE
    SYNTAX     Counter32
    MAX-ACCESS read-only
    STATUS     current
    DESCRIPTION
        "-- empty --"
    ::= { lcsStatusTcpIpRadiussAccessClientsEntry 10 }

-- {COLUMN} 1712.1.9.12.1.15.1.11
lcsStatusTcpIpRadiussAccessClientsEntryDropped OBJECT-TYPE
    SYNTAX     Counter32
    MAX-ACCESS read-only
    STATUS     current
    DESCRIPTION
        "-- empty --"
    ::= { lcsStatusTcpIpRadiussAccessClientsEntry 11 }

-- {COLUMN} 1712.1.9.12.1.15.1.12
lcsStatusTcpIpRadiussAccessClientsEntryUnknownType OBJECT-TYPE
    SYNTAX     Counter32
    MAX-ACCESS read-only
    STATUS     current
    DESCRIPTION
        "-- empty --"
    ::= { lcsStatusTcpIpRadiussAccessClientsEntry 12 }

-- {TABLE} 1712.1.9.12.1.20
lcsStatusTcpIpRadiussAccessIpv6ClientsTable OBJECT-TYPE
    SYNTAX     SEQUENCE OF LcsStatusTcpIpRadiussAccessIpv6ClientsEntry
    MAX-ACCESS not-accessible
    STATUS     current
    DESCRIPTION
        "-- empty --"
    ::= { lcsStatusTcpIpRadiussAccess 20 }

-- {ENTRY} 1712.1.9.12.1.20.1
lcsStatusTcpIpRadiussAccessIpv6ClientsEntry OBJECT-TYPE
    SYNTAX     LcsStatusTcpIpRadiussAccessIpv6ClientsEntry
    MAX-ACCESS not-accessible
    STATUS     current
    DESCRIPTION
        ""
    INDEX {
        lcsStatusTcpIpRadiussAccessIpv6ClientsEntryIpAddress
    }
    ::= { lcsStatusTcpIpRadiussAccessIpv6ClientsTable 1 }

-- {SEQUENCE}
LcsStatusTcpIpRadiussAccessIpv6ClientsEntry ::= SEQUENCE {
    lcsStatusTcpIpRadiussAccessIpv6ClientsEntryIpAddress IpAddress,
    lcsStatusTcpIpRadiussAccessIpv6ClientsEntryLastRequest INTEGER,
    lcsStatusTcpIpRadiussAccessIpv6ClientsEntryLastStatusRequest INTEGER,
    lcsStatusTcpIpRadiussAccessIpv6ClientsEntryNasIdent DisplayString,
    lcsStatusTcpIpRadiussAccessIpv6ClientsEntryAccessRequests Counter32,
    lcsStatusTcpIpRadiussAccessIpv6ClientsEntryStatusRequests Counter32,
    lcsStatusTcpIpRadiussAccessIpv6ClientsEntryDuplicateRequests Counter32,
    lcsStatusTcpIpRadiussAccessIpv6ClientsEntryAccessAccepts Counter32,
    lcsStatusTcpIpRadiussAccessIpv6ClientsEntryAccessRejects Counter32,
    lcsStatusTcpIpRadiussAccessIpv6ClientsEntryAccessChallenges Counter32,
    lcsStatusTcpIpRadiussAccessIpv6ClientsEntryStatusResponses Counter32,
    lcsStatusTcpIpRadiussAccessIpv6ClientsEntryMalfAccReq Counter32,
    lcsStatusTcpIpRadiussAccessIpv6ClientsEntryBadAuthenticator Counter32,
    lcsStatusTcpIpRadiussAccessIpv6ClientsEntryDropped Counter32,
    lcsStatusTcpIpRadiussAccessIpv6ClientsEntryUnknownType Counter32
}

-- {COLUMN} 1712.1.9.12.1.20.1.1
lcsStatusTcpIpRadiussAccessIpv6ClientsEntryIpAddress OBJECT-TYPE
    SYNTAX     IpAddress
    MAX-ACCESS read-only
    STATUS     current
    DESCRIPTION
        "-- empty --"
    ::= { lcsStatusTcpIpRadiussAccessIpv6ClientsEntry 1 }

-- {COLUMN} 1712.1.9.12.1.20.1.13
lcsStatusTcpIpRadiussAccessIpv6ClientsEntryLastRequest OBJECT-TYPE
    SYNTAX     INTEGER (0..2147483647)
    MAX-ACCESS read-only
    STATUS     current
    DESCRIPTION
        "-- empty --"
    ::= { lcsStatusTcpIpRadiussAccessIpv6ClientsEntry 13 }

-- {COLUMN} 1712.1.9.12.1.20.1.32
lcsStatusTcpIpRadiussAccessIpv6ClientsEntryLastStatusRequest OBJECT-TYPE
    SYNTAX     INTEGER (0..2147483647)
    MAX-ACCESS read-only
    STATUS     current
    DESCRIPTION
        "-- empty --"
    ::= { lcsStatusTcpIpRadiussAccessIpv6ClientsEntry 32 }

-- {COLUMN} 1712.1.9.12.1.20.1.14
lcsStatusTcpIpRadiussAccessIpv6ClientsEntryNasIdent OBJECT-TYPE
    SYNTAX     DisplayString (SIZE(0..64))
    MAX-ACCESS read-only
    STATUS     current
    DESCRIPTION
        "-- empty --"
    ::= { lcsStatusTcpIpRadiussAccessIpv6ClientsEntry 14 }

-- {COLUMN} 1712.1.9.12.1.20.1.4
lcsStatusTcpIpRadiussAccessIpv6ClientsEntryAccessRequests OBJECT-TYPE
    SYNTAX     Counter32
    MAX-ACCESS read-only
    STATUS     current
    DESCRIPTION
        "-- empty --"
    ::= { lcsStatusTcpIpRadiussAccessIpv6ClientsEntry 4 }

-- {COLUMN} 1712.1.9.12.1.20.1.30
lcsStatusTcpIpRadiussAccessIpv6ClientsEntryStatusRequests OBJECT-TYPE
    SYNTAX     Counter32
    MAX-ACCESS read-only
    STATUS     current
    DESCRIPTION
        "-- empty --"
    ::= { lcsStatusTcpIpRadiussAccessIpv6ClientsEntry 30 }

-- {COLUMN} 1712.1.9.12.1.20.1.5
lcsStatusTcpIpRadiussAccessIpv6ClientsEntryDuplicateRequests OBJECT-TYPE
    SYNTAX     Counter32
    MAX-ACCESS read-only
    STATUS     current
    DESCRIPTION
        "-- empty --"
    ::= { lcsStatusTcpIpRadiussAccessIpv6ClientsEntry 5 }

-- {COLUMN} 1712.1.9.12.1.20.1.6
lcsStatusTcpIpRadiussAccessIpv6ClientsEntryAccessAccepts OBJECT-TYPE
    SYNTAX     Counter32
    MAX-ACCESS read-only
    STATUS     current
    DESCRIPTION
        "-- empty --"
    ::= { lcsStatusTcpIpRadiussAccessIpv6ClientsEntry 6 }

-- {COLUMN} 1712.1.9.12.1.20.1.7
lcsStatusTcpIpRadiussAccessIpv6ClientsEntryAccessRejects OBJECT-TYPE
    SYNTAX     Counter32
    MAX-ACCESS read-only
    STATUS     current
    DESCRIPTION
        "-- empty --"
    ::= { lcsStatusTcpIpRadiussAccessIpv6ClientsEntry 7 }

-- {COLUMN} 1712.1.9.12.1.20.1.8
lcsStatusTcpIpRadiussAccessIpv6ClientsEntryAccessChallenges OBJECT-TYPE
    SYNTAX     Counter32
    MAX-ACCESS read-only
    STATUS     current
    DESCRIPTION
        "-- empty --"
    ::= { lcsStatusTcpIpRadiussAccessIpv6ClientsEntry 8 }

-- {COLUMN} 1712.1.9.12.1.20.1.31
lcsStatusTcpIpRadiussAccessIpv6ClientsEntryStatusResponses OBJECT-TYPE
    SYNTAX     Counter32
    MAX-ACCESS read-only
    STATUS     current
    DESCRIPTION
        "-- empty --"
    ::= { lcsStatusTcpIpRadiussAccessIpv6ClientsEntry 31 }

-- {COLUMN} 1712.1.9.12.1.20.1.9
lcsStatusTcpIpRadiussAccessIpv6ClientsEntryMalfAccReq OBJECT-TYPE
    SYNTAX     Counter32
    MAX-ACCESS read-only
    STATUS     current
    DESCRIPTION
        ""
    ::= { lcsStatusTcpIpRadiussAccessIpv6ClientsEntry 9 }

-- {COLUMN} 1712.1.9.12.1.20.1.10
lcsStatusTcpIpRadiussAccessIpv6ClientsEntryBadAuthenticator OBJECT-TYPE
    SYNTAX     Counter32
    MAX-ACCESS read-only
    STATUS     current
    DESCRIPTION
        "-- empty --"
    ::= { lcsStatusTcpIpRadiussAccessIpv6ClientsEntry 10 }

-- {COLUMN} 1712.1.9.12.1.20.1.11
lcsStatusTcpIpRadiussAccessIpv6ClientsEntryDropped OBJECT-TYPE
    SYNTAX     Counter32
    MAX-ACCESS read-only
    STATUS     current
    DESCRIPTION
        "-- empty --"
    ::= { lcsStatusTcpIpRadiussAccessIpv6ClientsEntry 11 }

-- {COLUMN} 1712.1.9.12.1.20.1.12
lcsStatusTcpIpRadiussAccessIpv6ClientsEntryUnknownType OBJECT-TYPE
    SYNTAX     Counter32
    MAX-ACCESS read-only
    STATUS     current
    DESCRIPTION
        "-- empty --"
    ::= { lcsStatusTcpIpRadiussAccessIpv6ClientsEntry 12 }

-- {SCALAR} 1712.1.9.12.1.30
lcsStatusTcpIpRadiussAccessTotalStatusRequests OBJECT-TYPE
    SYNTAX     Counter32
    MAX-ACCESS read-only
    STATUS     current
    DESCRIPTION
        "-- empty --"
    ::= { lcsStatusTcpIpRadiussAccess 30 }

-- {SCALAR} 1712.1.9.12.1.31
lcsStatusTcpIpRadiussAccessTotalStatusResponses OBJECT-TYPE
    SYNTAX     Counter32
    MAX-ACCESS read-only
    STATUS     current
    DESCRIPTION
        "-- empty --"
    ::= { lcsStatusTcpIpRadiussAccess 31 }

-- {SCALAR} 1712.1.9.12.1.5
lcsStatusTcpIpRadiussAccessTotalAccessRequests OBJECT-TYPE
    SYNTAX     Counter32
    MAX-ACCESS read-only
    STATUS     current
    DESCRIPTION
        "-- empty --"
    ::= { lcsStatusTcpIpRadiussAccess 5 }

-- {SCALAR} 1712.1.9.12.1.6
lcsStatusTcpIpRadiussAccessTotalInvalidAccessRequests OBJECT-TYPE
    SYNTAX     Counter32
    MAX-ACCESS read-only
    STATUS     current
    DESCRIPTION
        "-- empty --"
    ::= { lcsStatusTcpIpRadiussAccess 6 }

-- {SCALAR} 1712.1.9.12.1.7
lcsStatusTcpIpRadiussAccessTotalDuplicateAccessRequests OBJECT-TYPE
    SYNTAX     Counter32
    MAX-ACCESS read-only
    STATUS     current
    DESCRIPTION
        "-- empty --"
    ::= { lcsStatusTcpIpRadiussAccess 7 }

-- {SCALAR} 1712.1.9.12.1.8
lcsStatusTcpIpRadiussAccessTotalAccessAccepts OBJECT-TYPE
    SYNTAX     Counter32
    MAX-ACCESS read-only
    STATUS     current
    DESCRIPTION
        "-- empty --"
    ::= { lcsStatusTcpIpRadiussAccess 8 }

-- {SCALAR} 1712.1.9.12.1.9
lcsStatusTcpIpRadiussAccessTotalAccessRejects OBJECT-TYPE
    SYNTAX     Counter32
    MAX-ACCESS read-only
    STATUS     current
    DESCRIPTION
        "-- empty --"
    ::= { lcsStatusTcpIpRadiussAccess 9 }

-- {SCALAR} 1712.1.9.12.1.10
lcsStatusTcpIpRadiussAccessTotalAccessChallenges OBJECT-TYPE
    SYNTAX     Counter32
    MAX-ACCESS read-only
    STATUS     current
    DESCRIPTION
        "-- empty --"
    ::= { lcsStatusTcpIpRadiussAccess 10 }

-- {SCALAR} 1712.1.9.12.1.11
lcsStatusTcpIpRadiussAccessTotalMalformedAccessRequests OBJECT-TYPE
    SYNTAX     Counter32
    MAX-ACCESS read-only
    STATUS     current
    DESCRIPTION
        "-- empty --"
    ::= { lcsStatusTcpIpRadiussAccess 11 }

-- {SCALAR} 1712.1.9.12.1.12
lcsStatusTcpIpRadiussAccessTotalAccessBadAuthenticator OBJECT-TYPE
    SYNTAX     Counter32
    MAX-ACCESS read-only
    STATUS     current
    DESCRIPTION
        "-- empty --"
    ::= { lcsStatusTcpIpRadiussAccess 12 }

-- {SCALAR} 1712.1.9.12.1.13
lcsStatusTcpIpRadiussAccessTotalAccessDropped OBJECT-TYPE
    SYNTAX     Counter32
    MAX-ACCESS read-only
    STATUS     current
    DESCRIPTION
        "-- empty --"
    ::= { lcsStatusTcpIpRadiussAccess 13 }

-- {SCALAR} 1712.1.9.12.1.14
lcsStatusTcpIpRadiussAccessTotalAccessUnknownType OBJECT-TYPE
    SYNTAX     Counter32
    MAX-ACCESS read-only
    STATUS     current
    DESCRIPTION
        "-- empty --"
    ::= { lcsStatusTcpIpRadiussAccess 14 }

-- {OID} 1712.1.9.12.2
lcsStatusTcpIpRadiussAccnt OBJECT IDENTIFIER ::= { lcsStatusTcpIpRadiuss 2 }

-- {SCALAR} 1712.1.9.12.2.100
lcsStatusTcpIpRadiussAccntDeleteValues OBJECT-TYPE
    SYNTAX     DisplayString
    MAX-ACCESS read-write
    STATUS     current
    DESCRIPTION
        "-- empty --"
    ::= { lcsStatusTcpIpRadiussAccnt 100 }

-- {TABLE} 1712.1.9.12.2.15
lcsStatusTcpIpRadiussAccntClientsTable OBJECT-TYPE
    SYNTAX     SEQUENCE OF LcsStatusTcpIpRadiussAccntClientsEntry
    MAX-ACCESS not-accessible
    STATUS     current
    DESCRIPTION
        "-- empty --"
    ::= { lcsStatusTcpIpRadiussAccnt 15 }

-- {ENTRY} 1712.1.9.12.2.15.1
lcsStatusTcpIpRadiussAccntClientsEntry OBJECT-TYPE
    SYNTAX     LcsStatusTcpIpRadiussAccntClientsEntry
    MAX-ACCESS not-accessible
    STATUS     current
    DESCRIPTION
        ""
    INDEX {
        lcsStatusTcpIpRadiussAccntClientsEntryIpAddress
    }
    ::= { lcsStatusTcpIpRadiussAccntClientsTable 1 }

-- {SEQUENCE}
LcsStatusTcpIpRadiussAccntClientsEntry ::= SEQUENCE {
    lcsStatusTcpIpRadiussAccntClientsEntryIpAddress IpAddress,
    lcsStatusTcpIpRadiussAccntClientsEntryLastRequest INTEGER,
    lcsStatusTcpIpRadiussAccntClientsEntryLastStatusRequest INTEGER,
    lcsStatusTcpIpRadiussAccntClientsEntryNasIdent DisplayString,
    lcsStatusTcpIpRadiussAccntClientsEntryAccountRequests Counter32,
    lcsStatusTcpIpRadiussAccntClientsEntryStatusRequests Counter32,
    lcsStatusTcpIpRadiussAccntClientsEntryDuplicateRequests Counter32,
    lcsStatusTcpIpRadiussAccntClientsEntryAccountResponses Counter32,
    lcsStatusTcpIpRadiussAccntClientsEntryAccountNorecords Counter32,
    lcsStatusTcpIpRadiussAccntClientsEntryStatusResponses Counter32,
    lcsStatusTcpIpRadiussAccntClientsEntryMalfAccReq Counter32,
    lcsStatusTcpIpRadiussAccntClientsEntryBadAuthenticator Counter32,
    lcsStatusTcpIpRadiussAccntClientsEntryDropped Counter32,
    lcsStatusTcpIpRadiussAccntClientsEntryUnknownType Counter32
}

-- {COLUMN} 1712.1.9.12.2.15.1.1
lcsStatusTcpIpRadiussAccntClientsEntryIpAddress OBJECT-TYPE
    SYNTAX     IpAddress
    MAX-ACCESS read-only
    STATUS     current
    DESCRIPTION
        "-- empty --"
    ::= { lcsStatusTcpIpRadiussAccntClientsEntry 1 }

-- {COLUMN} 1712.1.9.12.2.15.1.13
lcsStatusTcpIpRadiussAccntClientsEntryLastRequest OBJECT-TYPE
    SYNTAX     INTEGER (0..2147483647)
    MAX-ACCESS read-only
    STATUS     current
    DESCRIPTION
        "-- empty --"
    ::= { lcsStatusTcpIpRadiussAccntClientsEntry 13 }

-- {COLUMN} 1712.1.9.12.2.15.1.32
lcsStatusTcpIpRadiussAccntClientsEntryLastStatusRequest OBJECT-TYPE
    SYNTAX     INTEGER (0..2147483647)
    MAX-ACCESS read-only
    STATUS     current
    DESCRIPTION
        "-- empty --"
    ::= { lcsStatusTcpIpRadiussAccntClientsEntry 32 }

-- {COLUMN} 1712.1.9.12.2.15.1.14
lcsStatusTcpIpRadiussAccntClientsEntryNasIdent OBJECT-TYPE
    SYNTAX     DisplayString (SIZE(0..64))
    MAX-ACCESS read-only
    STATUS     current
    DESCRIPTION
        "-- empty --"
    ::= { lcsStatusTcpIpRadiussAccntClientsEntry 14 }

-- {COLUMN} 1712.1.9.12.2.15.1.4
lcsStatusTcpIpRadiussAccntClientsEntryAccountRequests OBJECT-TYPE
    SYNTAX     Counter32
    MAX-ACCESS read-only
    STATUS     current
    DESCRIPTION
        "-- empty --"
    ::= { lcsStatusTcpIpRadiussAccntClientsEntry 4 }

-- {COLUMN} 1712.1.9.12.2.15.1.30
lcsStatusTcpIpRadiussAccntClientsEntryStatusRequests OBJECT-TYPE
    SYNTAX     Counter32
    MAX-ACCESS read-only
    STATUS     current
    DESCRIPTION
        "-- empty --"
    ::= { lcsStatusTcpIpRadiussAccntClientsEntry 30 }

-- {COLUMN} 1712.1.9.12.2.15.1.5
lcsStatusTcpIpRadiussAccntClientsEntryDuplicateRequests OBJECT-TYPE
    SYNTAX     Counter32
    MAX-ACCESS read-only
    STATUS     current
    DESCRIPTION
        "-- empty --"
    ::= { lcsStatusTcpIpRadiussAccntClientsEntry 5 }

-- {COLUMN} 1712.1.9.12.2.15.1.6
lcsStatusTcpIpRadiussAccntClientsEntryAccountResponses OBJECT-TYPE
    SYNTAX     Counter32
    MAX-ACCESS read-only
    STATUS     current
    DESCRIPTION
        "-- empty --"
    ::= { lcsStatusTcpIpRadiussAccntClientsEntry 6 }

-- {COLUMN} 1712.1.9.12.2.15.1.7
lcsStatusTcpIpRadiussAccntClientsEntryAccountNorecords OBJECT-TYPE
    SYNTAX     Counter32
    MAX-ACCESS read-only
    STATUS     current
    DESCRIPTION
        "-- empty --"
    ::= { lcsStatusTcpIpRadiussAccntClientsEntry 7 }

-- {COLUMN} 1712.1.9.12.2.15.1.31
lcsStatusTcpIpRadiussAccntClientsEntryStatusResponses OBJECT-TYPE
    SYNTAX     Counter32
    MAX-ACCESS read-only
    STATUS     current
    DESCRIPTION
        "-- empty --"
    ::= { lcsStatusTcpIpRadiussAccntClientsEntry 31 }

-- {COLUMN} 1712.1.9.12.2.15.1.9
lcsStatusTcpIpRadiussAccntClientsEntryMalfAccReq OBJECT-TYPE
    SYNTAX     Counter32
    MAX-ACCESS read-only
    STATUS     current
    DESCRIPTION
        ""
    ::= { lcsStatusTcpIpRadiussAccntClientsEntry 9 }

-- {COLUMN} 1712.1.9.12.2.15.1.10
lcsStatusTcpIpRadiussAccntClientsEntryBadAuthenticator OBJECT-TYPE
    SYNTAX     Counter32
    MAX-ACCESS read-only
    STATUS     current
    DESCRIPTION
        "-- empty --"
    ::= { lcsStatusTcpIpRadiussAccntClientsEntry 10 }

-- {COLUMN} 1712.1.9.12.2.15.1.11
lcsStatusTcpIpRadiussAccntClientsEntryDropped OBJECT-TYPE
    SYNTAX     Counter32
    MAX-ACCESS read-only
    STATUS     current
    DESCRIPTION
        "-- empty --"
    ::= { lcsStatusTcpIpRadiussAccntClientsEntry 11 }

-- {COLUMN} 1712.1.9.12.2.15.1.12
lcsStatusTcpIpRadiussAccntClientsEntryUnknownType OBJECT-TYPE
    SYNTAX     Counter32
    MAX-ACCESS read-only
    STATUS     current
    DESCRIPTION
        "-- empty --"
    ::= { lcsStatusTcpIpRadiussAccntClientsEntry 12 }

-- {TABLE} 1712.1.9.12.2.20
lcsStatusTcpIpRadiussAccntIpv6ClientsTable OBJECT-TYPE
    SYNTAX     SEQUENCE OF LcsStatusTcpIpRadiussAccntIpv6ClientsEntry
    MAX-ACCESS not-accessible
    STATUS     current
    DESCRIPTION
        "-- empty --"
    ::= { lcsStatusTcpIpRadiussAccnt 20 }

-- {ENTRY} 1712.1.9.12.2.20.1
lcsStatusTcpIpRadiussAccntIpv6ClientsEntry OBJECT-TYPE
    SYNTAX     LcsStatusTcpIpRadiussAccntIpv6ClientsEntry
    MAX-ACCESS not-accessible
    STATUS     current
    DESCRIPTION
        ""
    INDEX {
        lcsStatusTcpIpRadiussAccntIpv6ClientsEntryIpAddress
    }
    ::= { lcsStatusTcpIpRadiussAccntIpv6ClientsTable 1 }

-- {SEQUENCE}
LcsStatusTcpIpRadiussAccntIpv6ClientsEntry ::= SEQUENCE {
    lcsStatusTcpIpRadiussAccntIpv6ClientsEntryIpAddress IpAddress,
    lcsStatusTcpIpRadiussAccntIpv6ClientsEntryLastRequest INTEGER,
    lcsStatusTcpIpRadiussAccntIpv6ClientsEntryLastStatusRequest INTEGER,
    lcsStatusTcpIpRadiussAccntIpv6ClientsEntryNasIdent DisplayString,
    lcsStatusTcpIpRadiussAccntIpv6ClientsEntryAccountRequests Counter32,
    lcsStatusTcpIpRadiussAccntIpv6ClientsEntryStatusRequests Counter32,
    lcsStatusTcpIpRadiussAccntIpv6ClientsEntryDuplicateRequests Counter32,
    lcsStatusTcpIpRadiussAccntIpv6ClientsEntryAccountResponses Counter32,
    lcsStatusTcpIpRadiussAccntIpv6ClientsEntryAccountNorecords Counter32,
    lcsStatusTcpIpRadiussAccntIpv6ClientsEntryStatusResponses Counter32,
    lcsStatusTcpIpRadiussAccntIpv6ClientsEntryMalfAccReq Counter32,
    lcsStatusTcpIpRadiussAccntIpv6ClientsEntryBadAuthenticator Counter32,
    lcsStatusTcpIpRadiussAccntIpv6ClientsEntryDropped Counter32,
    lcsStatusTcpIpRadiussAccntIpv6ClientsEntryUnknownType Counter32
}

-- {COLUMN} 1712.1.9.12.2.20.1.1
lcsStatusTcpIpRadiussAccntIpv6ClientsEntryIpAddress OBJECT-TYPE
    SYNTAX     IpAddress
    MAX-ACCESS read-only
    STATUS     current
    DESCRIPTION
        "-- empty --"
    ::= { lcsStatusTcpIpRadiussAccntIpv6ClientsEntry 1 }

-- {COLUMN} 1712.1.9.12.2.20.1.13
lcsStatusTcpIpRadiussAccntIpv6ClientsEntryLastRequest OBJECT-TYPE
    SYNTAX     INTEGER (0..2147483647)
    MAX-ACCESS read-only
    STATUS     current
    DESCRIPTION
        "-- empty --"
    ::= { lcsStatusTcpIpRadiussAccntIpv6ClientsEntry 13 }

-- {COLUMN} 1712.1.9.12.2.20.1.32
lcsStatusTcpIpRadiussAccntIpv6ClientsEntryLastStatusRequest OBJECT-TYPE
    SYNTAX     INTEGER (0..2147483647)
    MAX-ACCESS read-only
    STATUS     current
    DESCRIPTION
        "-- empty --"
    ::= { lcsStatusTcpIpRadiussAccntIpv6ClientsEntry 32 }

-- {COLUMN} 1712.1.9.12.2.20.1.14
lcsStatusTcpIpRadiussAccntIpv6ClientsEntryNasIdent OBJECT-TYPE
    SYNTAX     DisplayString (SIZE(0..64))
    MAX-ACCESS read-only
    STATUS     current
    DESCRIPTION
        "-- empty --"
    ::= { lcsStatusTcpIpRadiussAccntIpv6ClientsEntry 14 }

-- {COLUMN} 1712.1.9.12.2.20.1.4
lcsStatusTcpIpRadiussAccntIpv6ClientsEntryAccountRequests OBJECT-TYPE
    SYNTAX     Counter32
    MAX-ACCESS read-only
    STATUS     current
    DESCRIPTION
        "-- empty --"
    ::= { lcsStatusTcpIpRadiussAccntIpv6ClientsEntry 4 }

-- {COLUMN} 1712.1.9.12.2.20.1.30
lcsStatusTcpIpRadiussAccntIpv6ClientsEntryStatusRequests OBJECT-TYPE
    SYNTAX     Counter32
    MAX-ACCESS read-only
    STATUS     current
    DESCRIPTION
        "-- empty --"
    ::= { lcsStatusTcpIpRadiussAccntIpv6ClientsEntry 30 }

-- {COLUMN} 1712.1.9.12.2.20.1.5
lcsStatusTcpIpRadiussAccntIpv6ClientsEntryDuplicateRequests OBJECT-TYPE
    SYNTAX     Counter32
    MAX-ACCESS read-only
    STATUS     current
    DESCRIPTION
        "-- empty --"
    ::= { lcsStatusTcpIpRadiussAccntIpv6ClientsEntry 5 }

-- {COLUMN} 1712.1.9.12.2.20.1.6
lcsStatusTcpIpRadiussAccntIpv6ClientsEntryAccountResponses OBJECT-TYPE
    SYNTAX     Counter32
    MAX-ACCESS read-only
    STATUS     current
    DESCRIPTION
        "-- empty --"
    ::= { lcsStatusTcpIpRadiussAccntIpv6ClientsEntry 6 }

-- {COLUMN} 1712.1.9.12.2.20.1.7
lcsStatusTcpIpRadiussAccntIpv6ClientsEntryAccountNorecords OBJECT-TYPE
    SYNTAX     Counter32
    MAX-ACCESS read-only
    STATUS     current
    DESCRIPTION
        "-- empty --"
    ::= { lcsStatusTcpIpRadiussAccntIpv6ClientsEntry 7 }

-- {COLUMN} 1712.1.9.12.2.20.1.31
lcsStatusTcpIpRadiussAccntIpv6ClientsEntryStatusResponses OBJECT-TYPE
    SYNTAX     Counter32
    MAX-ACCESS read-only
    STATUS     current
    DESCRIPTION
        "-- empty --"
    ::= { lcsStatusTcpIpRadiussAccntIpv6ClientsEntry 31 }

-- {COLUMN} 1712.1.9.12.2.20.1.9
lcsStatusTcpIpRadiussAccntIpv6ClientsEntryMalfAccReq OBJECT-TYPE
    SYNTAX     Counter32
    MAX-ACCESS read-only
    STATUS     current
    DESCRIPTION
        ""
    ::= { lcsStatusTcpIpRadiussAccntIpv6ClientsEntry 9 }

-- {COLUMN} 1712.1.9.12.2.20.1.10
lcsStatusTcpIpRadiussAccntIpv6ClientsEntryBadAuthenticator OBJECT-TYPE
    SYNTAX     Counter32
    MAX-ACCESS read-only
    STATUS     current
    DESCRIPTION
        "-- empty --"
    ::= { lcsStatusTcpIpRadiussAccntIpv6ClientsEntry 10 }

-- {COLUMN} 1712.1.9.12.2.20.1.11
lcsStatusTcpIpRadiussAccntIpv6ClientsEntryDropped OBJECT-TYPE
    SYNTAX     Counter32
    MAX-ACCESS read-only
    STATUS     current
    DESCRIPTION
        "-- empty --"
    ::= { lcsStatusTcpIpRadiussAccntIpv6ClientsEntry 11 }

-- {COLUMN} 1712.1.9.12.2.20.1.12
lcsStatusTcpIpRadiussAccntIpv6ClientsEntryUnknownType OBJECT-TYPE
    SYNTAX     Counter32
    MAX-ACCESS read-only
    STATUS     current
    DESCRIPTION
        "-- empty --"
    ::= { lcsStatusTcpIpRadiussAccntIpv6ClientsEntry 12 }

-- {TABLE} 1712.1.9.12.2.16
lcsStatusTcpIpRadiussAccntActAccntSessTable OBJECT-TYPE
    SYNTAX     SEQUENCE OF LcsStatusTcpIpRadiussAccntActAccntSessEntry
    MAX-ACCESS not-accessible
    STATUS     current
    DESCRIPTION
        ""
    ::= { lcsStatusTcpIpRadiussAccnt 16 }

-- {ENTRY} 1712.1.9.12.2.16.1
lcsStatusTcpIpRadiussAccntActAccntSessEntry OBJECT-TYPE
    SYNTAX     LcsStatusTcpIpRadiussAccntActAccntSessEntry
    MAX-ACCESS not-accessible
    STATUS     current
    DESCRIPTION
        ""
    INDEX {
        lcsStatusTcpIpRadiussAccntActAccntSessEntryIndex
    }
    ::= { lcsStatusTcpIpRadiussAccntActAccntSessTable 1 }

-- {SEQUENCE}
LcsStatusTcpIpRadiussAccntActAccntSessEntry ::= SEQUENCE {
    lcsStatusTcpIpRadiussAccntActAccntSessEntryIndex INTEGER,
    lcsStatusTcpIpRadiussAccntActAccntSessEntryStartTime DisplayString,
    lcsStatusTcpIpRadiussAccntActAccntSessEntryLastUpdate INTEGER,
    lcsStatusTcpIpRadiussAccntActAccntSessEntryUpdateDelta INTEGER,
    lcsStatusTcpIpRadiussAccntActAccntSessEntryNasIpAddress IpAddress,
    lcsStatusTcpIpRadiussAccntActAccntSessEntryNasIpv6Address IpAddress,
    lcsStatusTcpIpRadiussAccntActAccntSessEntryNasIdent DisplayString,
    lcsStatusTcpIpRadiussAccntActAccntSessEntryNasPortType INTEGER,
    lcsStatusTcpIpRadiussAccntActAccntSessEntryNasPortId INTEGER,
    lcsStatusTcpIpRadiussAccntActAccntSessEntrySessionId DisplayString,
    lcsStatusTcpIpRadiussAccntActAccntSessEntryCalledStationId DisplayString,
    lcsStatusTcpIpRadiussAccntActAccntSessEntryCallingStationId DisplayString,
    lcsStatusTcpIpRadiussAccntActAccntSessEntryUserName DisplayString,
    lcsStatusTcpIpRadiussAccntActAccntSessEntrySessionTime INTEGER,
    lcsStatusTcpIpRadiussAccntActAccntSessEntryInputPackets Counter32,
    lcsStatusTcpIpRadiussAccntActAccntSessEntryOutputPackets Counter32,
    lcsStatusTcpIpRadiussAccntActAccntSessEntryInputOctets Counter64,
    lcsStatusTcpIpRadiussAccntActAccntSessEntryOutputOctets Counter64,
    lcsStatusTcpIpRadiussAccntActAccntSessEntryIpAddress IpAddress
}

-- {COLUMN} 1712.1.9.12.2.16.1.1
lcsStatusTcpIpRadiussAccntActAccntSessEntryIndex OBJECT-TYPE
    SYNTAX     INTEGER (0..2147483647)
    MAX-ACCESS read-only
    STATUS     current
    DESCRIPTION
        "-- empty --"
    ::= { lcsStatusTcpIpRadiussAccntActAccntSessEntry 1 }

-- {COLUMN} 1712.1.9.12.2.16.1.12
lcsStatusTcpIpRadiussAccntActAccntSessEntryStartTime OBJECT-TYPE
    SYNTAX     DisplayString (SIZE(0..19))
    MAX-ACCESS read-only
    STATUS     current
    DESCRIPTION
        "-- empty --"
    ::= { lcsStatusTcpIpRadiussAccntActAccntSessEntry 12 }

-- {COLUMN} 1712.1.9.12.2.16.1.15
lcsStatusTcpIpRadiussAccntActAccntSessEntryLastUpdate OBJECT-TYPE
    SYNTAX     INTEGER (0..2147483647)
    MAX-ACCESS read-only
    STATUS     current
    DESCRIPTION
        "-- empty --"
    ::= { lcsStatusTcpIpRadiussAccntActAccntSessEntry 15 }

-- {COLUMN} 1712.1.9.12.2.16.1.16
lcsStatusTcpIpRadiussAccntActAccntSessEntryUpdateDelta OBJECT-TYPE
    SYNTAX     INTEGER (0..2147483647)
    MAX-ACCESS read-only
    STATUS     current
    DESCRIPTION
        "-- empty --"
    ::= { lcsStatusTcpIpRadiussAccntActAccntSessEntry 16 }

-- {COLUMN} 1712.1.9.12.2.16.1.2
lcsStatusTcpIpRadiussAccntActAccntSessEntryNasIpAddress OBJECT-TYPE
    SYNTAX     IpAddress
    MAX-ACCESS read-only
    STATUS     current
    DESCRIPTION
        "-- empty --"
    ::= { lcsStatusTcpIpRadiussAccntActAccntSessEntry 2 }

-- {COLUMN} 1712.1.9.12.2.16.1.21
lcsStatusTcpIpRadiussAccntActAccntSessEntryNasIpv6Address OBJECT-TYPE
    SYNTAX     IpAddress
    MAX-ACCESS read-only
    STATUS     current
    DESCRIPTION
        "-- empty --"
    ::= { lcsStatusTcpIpRadiussAccntActAccntSessEntry 21 }

-- {COLUMN} 1712.1.9.12.2.16.1.3
lcsStatusTcpIpRadiussAccntActAccntSessEntryNasIdent OBJECT-TYPE
    SYNTAX     DisplayString (SIZE(0..64))
    MAX-ACCESS read-only
    STATUS     current
    DESCRIPTION
        "-- empty --"
    ::= { lcsStatusTcpIpRadiussAccntActAccntSessEntry 3 }

-- {COLUMN} 1712.1.9.12.2.16.1.17
lcsStatusTcpIpRadiussAccntActAccntSessEntryNasPortType OBJECT-TYPE
    SYNTAX     INTEGER
      {
        eAsync (0),
        eSync (1),
        eIsdnSync (2),
        eV120 (3),
        eV110 (4),
        eVirtual (5),
        ePiafs (6),
        eHdlcClearChannel (7),
        eX25 (8),
        eX75 (9),
        eG3Fax (10),
        eSdsl (11),
        eAdslCap (12),
        eAdslDmt (13),
        eIdsl (14),
        eEthernet (15),
        eXdsl (16),
        eCable (17),
        eWirelessOther (18),
        eWireless80211 (19),
        eTokenRing (20),
        eFddi (21),
        eWirelessCdma2000 (22),
        eWirelessUmts (23),
        eWireless1xEv (24),
        eIapp (25),
        eFttp (26),
        eWireless80216 (27),
        eWireless80220 (28),
        eWireless80222 (29),
        ePppoa (30),
        ePppoeoa (31),
        ePppoeoe (32),
        ePppoeovlan (33),
        ePppoeoqinq (34),
        eXpon (35),
        eUnknown (-1)
      }
    MAX-ACCESS read-only
    STATUS     current
    DESCRIPTION
        "-- empty --"
    ::= { lcsStatusTcpIpRadiussAccntActAccntSessEntry 17 }

-- {COLUMN} 1712.1.9.12.2.16.1.18
lcsStatusTcpIpRadiussAccntActAccntSessEntryNasPortId OBJECT-TYPE
    SYNTAX     INTEGER (0..2147483647)
    MAX-ACCESS read-only
    STATUS     current
    DESCRIPTION
        "-- empty --"
    ::= { lcsStatusTcpIpRadiussAccntActAccntSessEntry 18 }

-- {COLUMN} 1712.1.9.12.2.16.1.4
lcsStatusTcpIpRadiussAccntActAccntSessEntrySessionId OBJECT-TYPE
    SYNTAX     DisplayString (SIZE(0..128))
    MAX-ACCESS read-only
    STATUS     current
    DESCRIPTION
        "-- empty --"
    ::= { lcsStatusTcpIpRadiussAccntActAccntSessEntry 4 }

-- {COLUMN} 1712.1.9.12.2.16.1.19
lcsStatusTcpIpRadiussAccntActAccntSessEntryCalledStationId OBJECT-TYPE
    SYNTAX     DisplayString (SIZE(0..48))
    MAX-ACCESS read-only
    STATUS     current
    DESCRIPTION
        "-- empty --"
    ::= { lcsStatusTcpIpRadiussAccntActAccntSessEntry 19 }

-- {COLUMN} 1712.1.9.12.2.16.1.20
lcsStatusTcpIpRadiussAccntActAccntSessEntryCallingStationId OBJECT-TYPE
    SYNTAX     DisplayString (SIZE(0..48))
    MAX-ACCESS read-only
    STATUS     current
    DESCRIPTION
        "-- empty --"
    ::= { lcsStatusTcpIpRadiussAccntActAccntSessEntry 20 }

-- {COLUMN} 1712.1.9.12.2.16.1.5
lcsStatusTcpIpRadiussAccntActAccntSessEntryUserName OBJECT-TYPE
    SYNTAX     DisplayString (SIZE(0..48))
    MAX-ACCESS read-only
    STATUS     current
    DESCRIPTION
        "-- empty --"
    ::= { lcsStatusTcpIpRadiussAccntActAccntSessEntry 5 }

-- {COLUMN} 1712.1.9.12.2.16.1.6
lcsStatusTcpIpRadiussAccntActAccntSessEntrySessionTime OBJECT-TYPE
    SYNTAX     INTEGER (0..2147483647)
    MAX-ACCESS read-only
    STATUS     current
    DESCRIPTION
        "-- empty --"
    ::= { lcsStatusTcpIpRadiussAccntActAccntSessEntry 6 }

-- {COLUMN} 1712.1.9.12.2.16.1.7
lcsStatusTcpIpRadiussAccntActAccntSessEntryInputPackets OBJECT-TYPE
    SYNTAX     Counter32
    MAX-ACCESS read-only
    STATUS     current
    DESCRIPTION
        "-- empty --"
    ::= { lcsStatusTcpIpRadiussAccntActAccntSessEntry 7 }

-- {COLUMN} 1712.1.9.12.2.16.1.8
lcsStatusTcpIpRadiussAccntActAccntSessEntryOutputPackets OBJECT-TYPE
    SYNTAX     Counter32
    MAX-ACCESS read-only
    STATUS     current
    DESCRIPTION
        "-- empty --"
    ::= { lcsStatusTcpIpRadiussAccntActAccntSessEntry 8 }

-- {COLUMN} 1712.1.9.12.2.16.1.9
lcsStatusTcpIpRadiussAccntActAccntSessEntryInputOctets OBJECT-TYPE
    SYNTAX     Counter64
    MAX-ACCESS read-only
    STATUS     current
    DESCRIPTION
        "-- empty --"
    ::= { lcsStatusTcpIpRadiussAccntActAccntSessEntry 9 }

-- {COLUMN} 1712.1.9.12.2.16.1.10
lcsStatusTcpIpRadiussAccntActAccntSessEntryOutputOctets OBJECT-TYPE
    SYNTAX     Counter64
    MAX-ACCESS read-only
    STATUS     current
    DESCRIPTION
        "-- empty --"
    ::= { lcsStatusTcpIpRadiussAccntActAccntSessEntry 10 }

-- {COLUMN} 1712.1.9.12.2.16.1.11
lcsStatusTcpIpRadiussAccntActAccntSessEntryIpAddress OBJECT-TYPE
    SYNTAX     IpAddress
    MAX-ACCESS read-only
    STATUS     current
    DESCRIPTION
        "-- empty --"
    ::= { lcsStatusTcpIpRadiussAccntActAccntSessEntry 11 }

-- {TABLE} 1712.1.9.12.2.17
lcsStatusTcpIpRadiussAccntComplAccntSessTable OBJECT-TYPE
    SYNTAX     SEQUENCE OF LcsStatusTcpIpRadiussAccntComplAccntSessEntry
    MAX-ACCESS not-accessible
    STATUS     current
    DESCRIPTION
        ""
    ::= { lcsStatusTcpIpRadiussAccnt 17 }

-- {ENTRY} 1712.1.9.12.2.17.1
lcsStatusTcpIpRadiussAccntComplAccntSessEntry OBJECT-TYPE
    SYNTAX     LcsStatusTcpIpRadiussAccntComplAccntSessEntry
    MAX-ACCESS not-accessible
    STATUS     current
    DESCRIPTION
        ""
    INDEX {
        lcsStatusTcpIpRadiussAccntComplAccntSessEntryIndex
    }
    ::= { lcsStatusTcpIpRadiussAccntComplAccntSessTable 1 }

-- {SEQUENCE}
LcsStatusTcpIpRadiussAccntComplAccntSessEntry ::= SEQUENCE {
    lcsStatusTcpIpRadiussAccntComplAccntSessEntryIndex INTEGER,
    lcsStatusTcpIpRadiussAccntComplAccntSessEntryStartTime DisplayString,
    lcsStatusTcpIpRadiussAccntComplAccntSessEntryStopTime DisplayString,
    lcsStatusTcpIpRadiussAccntComplAccntSessEntryTerminateCause INTEGER,
    lcsStatusTcpIpRadiussAccntComplAccntSessEntryNasIpAddress IpAddress,
    lcsStatusTcpIpRadiussAccntComplAccntSessEntryNasIpv6Address IpAddress,
    lcsStatusTcpIpRadiussAccntComplAccntSessEntryNasIdent DisplayString,
    lcsStatusTcpIpRadiussAccntComplAccntSessEntryNasPortType INTEGER,
    lcsStatusTcpIpRadiussAccntComplAccntSessEntryNasPortId INTEGER,
    lcsStatusTcpIpRadiussAccntComplAccntSessEntrySessionId DisplayString,
    lcsStatusTcpIpRadiussAccntComplAccntSessEntryCalledStationId DisplayString,
    lcsStatusTcpIpRadiussAccntComplAccntSessEntryCallingStationId DisplayString,
    lcsStatusTcpIpRadiussAccntComplAccntSessEntryUserName DisplayString,
    lcsStatusTcpIpRadiussAccntComplAccntSessEntrySessionTime INTEGER,
    lcsStatusTcpIpRadiussAccntComplAccntSessEntryInputPackets Counter32,
    lcsStatusTcpIpRadiussAccntComplAccntSessEntryOutputPackets Counter32,
    lcsStatusTcpIpRadiussAccntComplAccntSessEntryInputOctets Counter64,
    lcsStatusTcpIpRadiussAccntComplAccntSessEntryOutputOctets Counter64,
    lcsStatusTcpIpRadiussAccntComplAccntSessEntryIpAddress IpAddress
}

-- {COLUMN} 1712.1.9.12.2.17.1.1
lcsStatusTcpIpRadiussAccntComplAccntSessEntryIndex OBJECT-TYPE
    SYNTAX     INTEGER (0..2147483647)
    MAX-ACCESS read-only
    STATUS     current
    DESCRIPTION
        "-- empty --"
    ::= { lcsStatusTcpIpRadiussAccntComplAccntSessEntry 1 }

-- {COLUMN} 1712.1.9.12.2.17.1.12
lcsStatusTcpIpRadiussAccntComplAccntSessEntryStartTime OBJECT-TYPE
    SYNTAX     DisplayString (SIZE(0..19))
    MAX-ACCESS read-only
    STATUS     current
    DESCRIPTION
        "-- empty --"
    ::= { lcsStatusTcpIpRadiussAccntComplAccntSessEntry 12 }

-- {COLUMN} 1712.1.9.12.2.17.1.13
lcsStatusTcpIpRadiussAccntComplAccntSessEntryStopTime OBJECT-TYPE
    SYNTAX     DisplayString (SIZE(0..19))
    MAX-ACCESS read-only
    STATUS     current
    DESCRIPTION
        "-- empty --"
    ::= { lcsStatusTcpIpRadiussAccntComplAccntSessEntry 13 }

-- {COLUMN} 1712.1.9.12.2.17.1.14
lcsStatusTcpIpRadiussAccntComplAccntSessEntryTerminateCause OBJECT-TYPE
    SYNTAX     INTEGER
      {
        eUserRequest (1),
        eLostCarrier (2),
        eLostService (3),
        eIdleTimeout (4),
        eSessionTimeout (5),
        eAdminReset (6),
        eAdminReboot (7),
        ePortError (8),
        eNasError (9),
        eNasRequest (10),
        eNasReboot (11),
        ePortUnneeded (12),
        ePortPreempted (13),
        ePortSuspended (14),
        eServiceUnavailable (15),
        eCallback (16),
        eUserError (17),
        eHostRequest (18),
        eSupplicantRestart (19),
        eReauthenticationFailure (20),
        ePortReinit (21),
        ePortAdminDisabled (22)
      }
    MAX-ACCESS read-only
    STATUS     current
    DESCRIPTION
        "-- empty --"
    ::= { lcsStatusTcpIpRadiussAccntComplAccntSessEntry 14 }

-- {COLUMN} 1712.1.9.12.2.17.1.2
lcsStatusTcpIpRadiussAccntComplAccntSessEntryNasIpAddress OBJECT-TYPE
    SYNTAX     IpAddress
    MAX-ACCESS read-only
    STATUS     current
    DESCRIPTION
        "-- empty --"
    ::= { lcsStatusTcpIpRadiussAccntComplAccntSessEntry 2 }

-- {COLUMN} 1712.1.9.12.2.17.1.21
lcsStatusTcpIpRadiussAccntComplAccntSessEntryNasIpv6Address OBJECT-TYPE
    SYNTAX     IpAddress
    MAX-ACCESS read-only
    STATUS     current
    DESCRIPTION
        "-- empty --"
    ::= { lcsStatusTcpIpRadiussAccntComplAccntSessEntry 21 }

-- {COLUMN} 1712.1.9.12.2.17.1.3
lcsStatusTcpIpRadiussAccntComplAccntSessEntryNasIdent OBJECT-TYPE
    SYNTAX     DisplayString (SIZE(0..64))
    MAX-ACCESS read-only
    STATUS     current
    DESCRIPTION
        "-- empty --"
    ::= { lcsStatusTcpIpRadiussAccntComplAccntSessEntry 3 }

-- {COLUMN} 1712.1.9.12.2.17.1.17
lcsStatusTcpIpRadiussAccntComplAccntSessEntryNasPortType OBJECT-TYPE
    SYNTAX     INTEGER
      {
        eAsync (0),
        eSync (1),
        eIsdnSync (2),
        eV120 (3),
        eV110 (4),
        eVirtual (5),
        ePiafs (6),
        eHdlcClearChannel (7),
        eX25 (8),
        eX75 (9),
        eG3Fax (10),
        eSdsl (11),
        eAdslCap (12),
        eAdslDmt (13),
        eIdsl (14),
        eEthernet (15),
        eXdsl (16),
        eCable (17),
        eWirelessOther (18),
        eWireless80211 (19),
        eTokenRing (20),
        eFddi (21),
        eWirelessCdma2000 (22),
        eWirelessUmts (23),
        eWireless1xEv (24),
        eIapp (25),
        eFttp (26),
        eWireless80216 (27),
        eWireless80220 (28),
        eWireless80222 (29),
        ePppoa (30),
        ePppoeoa (31),
        ePppoeoe (32),
        ePppoeovlan (33),
        ePppoeoqinq (34),
        eXpon (35),
        eUnknown (-1)
      }
    MAX-ACCESS read-only
    STATUS     current
    DESCRIPTION
        "-- empty --"
    ::= { lcsStatusTcpIpRadiussAccntComplAccntSessEntry 17 }

-- {COLUMN} 1712.1.9.12.2.17.1.18
lcsStatusTcpIpRadiussAccntComplAccntSessEntryNasPortId OBJECT-TYPE
    SYNTAX     INTEGER (0..2147483647)
    MAX-ACCESS read-only
    STATUS     current
    DESCRIPTION
        "-- empty --"
    ::= { lcsStatusTcpIpRadiussAccntComplAccntSessEntry 18 }

-- {COLUMN} 1712.1.9.12.2.17.1.4
lcsStatusTcpIpRadiussAccntComplAccntSessEntrySessionId OBJECT-TYPE
    SYNTAX     DisplayString (SIZE(0..128))
    MAX-ACCESS read-only
    STATUS     current
    DESCRIPTION
        "-- empty --"
    ::= { lcsStatusTcpIpRadiussAccntComplAccntSessEntry 4 }

-- {COLUMN} 1712.1.9.12.2.17.1.19
lcsStatusTcpIpRadiussAccntComplAccntSessEntryCalledStationId OBJECT-TYPE
    SYNTAX     DisplayString (SIZE(0..48))
    MAX-ACCESS read-only
    STATUS     current
    DESCRIPTION
        "-- empty --"
    ::= { lcsStatusTcpIpRadiussAccntComplAccntSessEntry 19 }

-- {COLUMN} 1712.1.9.12.2.17.1.20
lcsStatusTcpIpRadiussAccntComplAccntSessEntryCallingStationId OBJECT-TYPE
    SYNTAX     DisplayString (SIZE(0..48))
    MAX-ACCESS read-only
    STATUS     current
    DESCRIPTION
        "-- empty --"
    ::= { lcsStatusTcpIpRadiussAccntComplAccntSessEntry 20 }

-- {COLUMN} 1712.1.9.12.2.17.1.5
lcsStatusTcpIpRadiussAccntComplAccntSessEntryUserName OBJECT-TYPE
    SYNTAX     DisplayString (SIZE(0..48))
    MAX-ACCESS read-only
    STATUS     current
    DESCRIPTION
        "-- empty --"
    ::= { lcsStatusTcpIpRadiussAccntComplAccntSessEntry 5 }

-- {COLUMN} 1712.1.9.12.2.17.1.6
lcsStatusTcpIpRadiussAccntComplAccntSessEntrySessionTime OBJECT-TYPE
    SYNTAX     INTEGER (0..2147483647)
    MAX-ACCESS read-only
    STATUS     current
    DESCRIPTION
        "-- empty --"
    ::= { lcsStatusTcpIpRadiussAccntComplAccntSessEntry 6 }

-- {COLUMN} 1712.1.9.12.2.17.1.7
lcsStatusTcpIpRadiussAccntComplAccntSessEntryInputPackets OBJECT-TYPE
    SYNTAX     Counter32
    MAX-ACCESS read-only
    STATUS     current
    DESCRIPTION
        "-- empty --"
    ::= { lcsStatusTcpIpRadiussAccntComplAccntSessEntry 7 }

-- {COLUMN} 1712.1.9.12.2.17.1.8
lcsStatusTcpIpRadiussAccntComplAccntSessEntryOutputPackets OBJECT-TYPE
    SYNTAX     Counter32
    MAX-ACCESS read-only
    STATUS     current
    DESCRIPTION
        "-- empty --"
    ::= { lcsStatusTcpIpRadiussAccntComplAccntSessEntry 8 }

-- {COLUMN} 1712.1.9.12.2.17.1.9
lcsStatusTcpIpRadiussAccntComplAccntSessEntryInputOctets OBJECT-TYPE
    SYNTAX     Counter64
    MAX-ACCESS read-only
    STATUS     current
    DESCRIPTION
        "-- empty --"
    ::= { lcsStatusTcpIpRadiussAccntComplAccntSessEntry 9 }

-- {COLUMN} 1712.1.9.12.2.17.1.10
lcsStatusTcpIpRadiussAccntComplAccntSessEntryOutputOctets OBJECT-TYPE
    SYNTAX     Counter64
    MAX-ACCESS read-only
    STATUS     current
    DESCRIPTION
        "-- empty --"
    ::= { lcsStatusTcpIpRadiussAccntComplAccntSessEntry 10 }

-- {COLUMN} 1712.1.9.12.2.17.1.11
lcsStatusTcpIpRadiussAccntComplAccntSessEntryIpAddress OBJECT-TYPE
    SYNTAX     IpAddress
    MAX-ACCESS read-only
    STATUS     current
    DESCRIPTION
        "-- empty --"
    ::= { lcsStatusTcpIpRadiussAccntComplAccntSessEntry 11 }

-- {TABLE} 1712.1.9.12.2.18
lcsStatusTcpIpRadiussAccntAccountingTotalTable OBJECT-TYPE
    SYNTAX     SEQUENCE OF LcsStatusTcpIpRadiussAccntAccountingTotalEntry
    MAX-ACCESS not-accessible
    STATUS     current
    DESCRIPTION
        "-- empty --"
    ::= { lcsStatusTcpIpRadiussAccnt 18 }

-- {ENTRY} 1712.1.9.12.2.18.1
lcsStatusTcpIpRadiussAccntAccountingTotalEntry OBJECT-TYPE
    SYNTAX     LcsStatusTcpIpRadiussAccntAccountingTotalEntry
    MAX-ACCESS not-accessible
    STATUS     current
    DESCRIPTION
        ""
    INDEX {
        lcsStatusTcpIpRadiussAccntAccountingTotalEntryUserName
    }
    ::= { lcsStatusTcpIpRadiussAccntAccountingTotalTable 1 }

-- {SEQUENCE}
LcsStatusTcpIpRadiussAccntAccountingTotalEntry ::= SEQUENCE {
    lcsStatusTcpIpRadiussAccntAccountingTotalEntryUserName DisplayString,
    lcsStatusTcpIpRadiussAccntAccountingTotalEntryTime INTEGER,
    lcsStatusTcpIpRadiussAccntAccountingTotalEntryInputPackets INTEGER,
    lcsStatusTcpIpRadiussAccntAccountingTotalEntryOutputPackets INTEGER,
    lcsStatusTcpIpRadiussAccntAccountingTotalEntryInputOctets INTEGER,
    lcsStatusTcpIpRadiussAccntAccountingTotalEntryOutputOctets INTEGER,
    lcsStatusTcpIpRadiussAccntAccountingTotalEntryFirstLogin DisplayString
}

-- {COLUMN} 1712.1.9.12.2.18.1.1
lcsStatusTcpIpRadiussAccntAccountingTotalEntryUserName OBJECT-TYPE
    SYNTAX     DisplayString (SIZE(0..48))
    MAX-ACCESS read-only
    STATUS     current
    DESCRIPTION
        "-- empty --"
    ::= { lcsStatusTcpIpRadiussAccntAccountingTotalEntry 1 }

-- {COLUMN} 1712.1.9.12.2.18.1.2
lcsStatusTcpIpRadiussAccntAccountingTotalEntryTime OBJECT-TYPE
    SYNTAX     INTEGER (0..2147483647)
    MAX-ACCESS read-only
    STATUS     current
    DESCRIPTION
        "-- empty --"
    ::= { lcsStatusTcpIpRadiussAccntAccountingTotalEntry 2 }

-- {COLUMN} 1712.1.9.12.2.18.1.3
lcsStatusTcpIpRadiussAccntAccountingTotalEntryInputPackets OBJECT-TYPE
    SYNTAX     INTEGER (0..2147483647)
    MAX-ACCESS read-only
    STATUS     current
    DESCRIPTION
        "-- empty --"
    ::= { lcsStatusTcpIpRadiussAccntAccountingTotalEntry 3 }

-- {COLUMN} 1712.1.9.12.2.18.1.4
lcsStatusTcpIpRadiussAccntAccountingTotalEntryOutputPackets OBJECT-TYPE
    SYNTAX     INTEGER (0..2147483647)
    MAX-ACCESS read-only
    STATUS     current
    DESCRIPTION
        "-- empty --"
    ::= { lcsStatusTcpIpRadiussAccntAccountingTotalEntry 4 }

-- {COLUMN} 1712.1.9.12.2.18.1.5
lcsStatusTcpIpRadiussAccntAccountingTotalEntryInputOctets OBJECT-TYPE
    SYNTAX     INTEGER (0..2147483647)
    MAX-ACCESS read-only
    STATUS     current
    DESCRIPTION
        "-- empty --"
    ::= { lcsStatusTcpIpRadiussAccntAccountingTotalEntry 5 }

-- {COLUMN} 1712.1.9.12.2.18.1.6
lcsStatusTcpIpRadiussAccntAccountingTotalEntryOutputOctets OBJECT-TYPE
    SYNTAX     INTEGER (0..2147483647)
    MAX-ACCESS read-only
    STATUS     current
    DESCRIPTION
        "-- empty --"
    ::= { lcsStatusTcpIpRadiussAccntAccountingTotalEntry 6 }

-- {COLUMN} 1712.1.9.12.2.18.1.7
lcsStatusTcpIpRadiussAccntAccountingTotalEntryFirstLogin OBJECT-TYPE
    SYNTAX     DisplayString (SIZE(0..21))
    MAX-ACCESS read-only
    STATUS     current
    DESCRIPTION
        "-- empty --"
    ::= { lcsStatusTcpIpRadiussAccntAccountingTotalEntry 7 }

-- {SCALAR} 1712.1.9.12.2.19
lcsStatusTcpIpRadiussAccntDeleteAccountingTotal OBJECT-TYPE
    SYNTAX     DisplayString
    MAX-ACCESS read-write
    STATUS     current
    DESCRIPTION
        "-- empty --"
    ::= { lcsStatusTcpIpRadiussAccnt 19 }

-- {SCALAR} 1712.1.9.12.2.30
lcsStatusTcpIpRadiussAccntTotalStatusRequests OBJECT-TYPE
    SYNTAX     Counter32
    MAX-ACCESS read-only
    STATUS     current
    DESCRIPTION
        "-- empty --"
    ::= { lcsStatusTcpIpRadiussAccnt 30 }

-- {SCALAR} 1712.1.9.12.2.31
lcsStatusTcpIpRadiussAccntTotalStatusResponses OBJECT-TYPE
    SYNTAX     Counter32
    MAX-ACCESS read-only
    STATUS     current
    DESCRIPTION
        "-- empty --"
    ::= { lcsStatusTcpIpRadiussAccnt 31 }

-- {SCALAR} 1712.1.9.12.2.5
lcsStatusTcpIpRadiussAccntTotalAccountRequests OBJECT-TYPE
    SYNTAX     Counter32
    MAX-ACCESS read-only
    STATUS     current
    DESCRIPTION
        "-- empty --"
    ::= { lcsStatusTcpIpRadiussAccnt 5 }

-- {SCALAR} 1712.1.9.12.2.6
lcsStatusTcpIpRadiussAccntTotalInvalidAccountRequests OBJECT-TYPE
    SYNTAX     Counter32
    MAX-ACCESS read-only
    STATUS     current
    DESCRIPTION
        "-- empty --"
    ::= { lcsStatusTcpIpRadiussAccnt 6 }

-- {SCALAR} 1712.1.9.12.2.7
lcsStatusTcpIpRadiussAccntTotalDuplicateAccountRequests OBJECT-TYPE
    SYNTAX     Counter32
    MAX-ACCESS read-only
    STATUS     current
    DESCRIPTION
        "-- empty --"
    ::= { lcsStatusTcpIpRadiussAccnt 7 }

-- {SCALAR} 1712.1.9.12.2.8
lcsStatusTcpIpRadiussAccntTotalAccountResponses OBJECT-TYPE
    SYNTAX     Counter32
    MAX-ACCESS read-only
    STATUS     current
    DESCRIPTION
        "-- empty --"
    ::= { lcsStatusTcpIpRadiussAccnt 8 }

-- {SCALAR} 1712.1.9.12.2.9
lcsStatusTcpIpRadiussAccntTotalMalformedAccountRequests OBJECT-TYPE
    SYNTAX     Counter32
    MAX-ACCESS read-only
    STATUS     current
    DESCRIPTION
        "-- empty --"
    ::= { lcsStatusTcpIpRadiussAccnt 9 }

-- {SCALAR} 1712.1.9.12.2.10
lcsStatusTcpIpRadiussAccntTotalAccountBadAuthenticator OBJECT-TYPE
    SYNTAX     Counter32
    MAX-ACCESS read-only
    STATUS     current
    DESCRIPTION
        "-- empty --"
    ::= { lcsStatusTcpIpRadiussAccnt 10 }

-- {SCALAR} 1712.1.9.12.2.11
lcsStatusTcpIpRadiussAccntTotalAccountDropped OBJECT-TYPE
    SYNTAX     Counter32
    MAX-ACCESS read-only
    STATUS     current
    DESCRIPTION
        "-- empty --"
    ::= { lcsStatusTcpIpRadiussAccnt 11 }

-- {SCALAR} 1712.1.9.12.2.12
lcsStatusTcpIpRadiussAccntTotalAccountNorecord OBJECT-TYPE
    SYNTAX     Counter32
    MAX-ACCESS read-only
    STATUS     current
    DESCRIPTION
        "-- empty --"
    ::= { lcsStatusTcpIpRadiussAccnt 12 }

-- {SCALAR} 1712.1.9.12.2.13
lcsStatusTcpIpRadiussAccntTotalAccountUnknownType OBJECT-TYPE
    SYNTAX     Counter32
    MAX-ACCESS read-only
    STATUS     current
    DESCRIPTION
        "-- empty --"
    ::= { lcsStatusTcpIpRadiussAccnt 13 }

-- {TABLE} 1712.1.9.12.10
lcsStatusTcpIpRadiussLogTableTable OBJECT-TYPE
    SYNTAX     SEQUENCE OF LcsStatusTcpIpRadiussLogTableEntry
    MAX-ACCESS not-accessible
    STATUS     current
    DESCRIPTION
        "-- empty --"
    ::= { lcsStatusTcpIpRadiuss 10 }

-- {ENTRY} 1712.1.9.12.10.1
lcsStatusTcpIpRadiussLogTableEntry OBJECT-TYPE
    SYNTAX     LcsStatusTcpIpRadiussLogTableEntry
    MAX-ACCESS not-accessible
    STATUS     current
    DESCRIPTION
        ""
    INDEX {
        lcsStatusTcpIpRadiussLogTableEntryIndex
    }
    ::= { lcsStatusTcpIpRadiussLogTableTable 1 }

-- {SEQUENCE}
LcsStatusTcpIpRadiussLogTableEntry ::= SEQUENCE {
    lcsStatusTcpIpRadiussLogTableEntryIndex INTEGER,
    lcsStatusTcpIpRadiussLogTableEntryTime DisplayString,
    lcsStatusTcpIpRadiussLogTableEntryEvent DisplayString
}

-- {COLUMN} 1712.1.9.12.10.1.1
lcsStatusTcpIpRadiussLogTableEntryIndex OBJECT-TYPE
    SYNTAX     INTEGER (0..2147483647)
    MAX-ACCESS read-only
    STATUS     current
    DESCRIPTION
        "-- empty --"
    ::= { lcsStatusTcpIpRadiussLogTableEntry 1 }

-- {COLUMN} 1712.1.9.12.10.1.2
lcsStatusTcpIpRadiussLogTableEntryTime OBJECT-TYPE
    SYNTAX     DisplayString (SIZE(0..21))
    MAX-ACCESS read-only
    STATUS     current
    DESCRIPTION
        "-- empty --"
    ::= { lcsStatusTcpIpRadiussLogTableEntry 2 }

-- {COLUMN} 1712.1.9.12.10.1.3
lcsStatusTcpIpRadiussLogTableEntryEvent OBJECT-TYPE
    SYNTAX     DisplayString (SIZE(0..128))
    MAX-ACCESS read-only
    STATUS     current
    DESCRIPTION
        "-- empty --"
    ::= { lcsStatusTcpIpRadiussLogTableEntry 3 }

-- {SCALAR} 1712.1.9.12.100
lcsStatusTcpIpRadiussDeleteValues OBJECT-TYPE
    SYNTAX     DisplayString
    MAX-ACCESS read-write
    STATUS     current
    DESCRIPTION
        "-- empty --"
    ::= { lcsStatusTcpIpRadiuss 100 }

-- {OID} 1712.1.9.11
lcsStatusTcpIpSyslog OBJECT IDENTIFIER ::= { lcsStatusTcpIp 11 }

-- {TABLE} 1712.1.9.11.11
lcsStatusTcpIpSyslogLastMessagesTable OBJECT-TYPE
    SYNTAX     SEQUENCE OF LcsStatusTcpIpSyslogLastMessagesEntry
    MAX-ACCESS not-accessible
    STATUS     current
    DESCRIPTION
        "-- empty --"
    ::= { lcsStatusTcpIpSyslog 11 }

-- {ENTRY} 1712.1.9.11.11.1
lcsStatusTcpIpSyslogLastMessagesEntry OBJECT-TYPE
    SYNTAX     LcsStatusTcpIpSyslogLastMessagesEntry
    MAX-ACCESS not-accessible
    STATUS     current
    DESCRIPTION
        ""
    INDEX {
        lcsStatusTcpIpSyslogLastMessagesEntryIdx
    }
    ::= { lcsStatusTcpIpSyslogLastMessagesTable 1 }

-- {SEQUENCE}
LcsStatusTcpIpSyslogLastMessagesEntry ::= SEQUENCE {
    lcsStatusTcpIpSyslogLastMessagesEntryIdx INTEGER,
    lcsStatusTcpIpSyslogLastMessagesEntryTime DisplayString,
    lcsStatusTcpIpSyslogLastMessagesEntrySource INTEGER,
    lcsStatusTcpIpSyslogLastMessagesEntryLevel INTEGER,
    lcsStatusTcpIpSyslogLastMessagesEntryMessage DisplayString
}

-- {COLUMN} 1712.1.9.11.11.1.1
lcsStatusTcpIpSyslogLastMessagesEntryIdx OBJECT-TYPE
    SYNTAX     INTEGER (0..2147483647)
    MAX-ACCESS read-only
    STATUS     current
    DESCRIPTION
        "-- empty --"
    ::= { lcsStatusTcpIpSyslogLastMessagesEntry 1 }

-- {COLUMN} 1712.1.9.11.11.1.2
lcsStatusTcpIpSyslogLastMessagesEntryTime OBJECT-TYPE
    SYNTAX     DisplayString (SIZE(0..255))
    MAX-ACCESS read-only
    STATUS     current
    DESCRIPTION
        "-- empty --"
    ::= { lcsStatusTcpIpSyslogLastMessagesEntry 2 }

-- {COLUMN} 1712.1.9.11.11.1.3
lcsStatusTcpIpSyslogLastMessagesEntrySource OBJECT-TYPE
    SYNTAX     INTEGER
      {
        eKern (0),
        eUser (1),
        eMail (2),
        eDaemon (3),
        eAuth (4),
        eSyslog (5),
        eLpr (6),
        eNews (7),
        eUucp (8),
        eCron (9),
        eAuthpriv (10),
        eLocal0 (16),
        eLocal1 (17),
        eLocal2 (18),
        eLocal3 (19),
        eLocal4 (20),
        eLocal5 (21),
        eLocal6 (22),
        eLocal7 (23)
      }
    MAX-ACCESS read-only
    STATUS     current
    DESCRIPTION
        "-- empty --"
    ::= { lcsStatusTcpIpSyslogLastMessagesEntry 3 }

-- {COLUMN} 1712.1.9.11.11.1.4
lcsStatusTcpIpSyslogLastMessagesEntryLevel OBJECT-TYPE
    SYNTAX     INTEGER
      {
        eEmergency (0),
        eAlarm (1),
        eCritical (2),
        eError (3),
        eWarning (4),
        eNotice (5),
        eInfo (6),
        eDebug (7)
      }
    MAX-ACCESS read-only
    STATUS     current
    DESCRIPTION
        "-- empty --"
    ::= { lcsStatusTcpIpSyslogLastMessagesEntry 4 }

-- {COLUMN} 1712.1.9.11.11.1.5
lcsStatusTcpIpSyslogLastMessagesEntryMessage OBJECT-TYPE
    SYNTAX     DisplayString (SIZE(0..255))
    MAX-ACCESS read-only
    STATUS     current
    DESCRIPTION
        "-- empty --"
    ::= { lcsStatusTcpIpSyslogLastMessagesEntry 5 }

-- {SCALAR} 1712.1.9.11.12
lcsStatusTcpIpSyslogSyslogCritical OBJECT-TYPE
    SYNTAX     INTEGER
      {
        eNo (0),
        eYes (1)
      }
    MAX-ACCESS read-only
    STATUS     current
    DESCRIPTION
        "-- empty --"
    ::= { lcsStatusTcpIpSyslog 12 }

-- {SCALAR} 1712.1.9.11.99
lcsStatusTcpIpSyslogDeleteValues OBJECT-TYPE
    SYNTAX     DisplayString
    MAX-ACCESS read-write
    STATUS     current
    DESCRIPTION
        "-- empty --"
    ::= { lcsStatusTcpIpSyslog 99 }

-- {OID} 1712.1.10
lcsStatusIpRouter OBJECT IDENTIFIER ::= { lcsStatus 10 }

-- {SCALAR} 1712.1.10.1
lcsStatusIpRouterLanRx OBJECT-TYPE
    SYNTAX     Counter32
    MAX-ACCESS read-only
    STATUS     current
    DESCRIPTION
        "-- empty --"
    ::= { lcsStatusIpRouter 1 }

-- {SCALAR} 1712.1.10.2
lcsStatusIpRouterLanTx OBJECT-TYPE
    SYNTAX     Counter32
    MAX-ACCESS read-only
    STATUS     current
    DESCRIPTION
        "-- empty --"
    ::= { lcsStatusIpRouter 2 }

-- {SCALAR} 1712.1.10.3
lcsStatusIpRouterLanLocalRoutings OBJECT-TYPE
    SYNTAX     Counter32
    MAX-ACCESS read-only
    STATUS     current
    DESCRIPTION
        "-- empty --"
    ::= { lcsStatusIpRouter 3 }

-- {SCALAR} 1712.1.10.4
lcsStatusIpRouterLanNetworkErrors OBJECT-TYPE
    SYNTAX     Counter32
    MAX-ACCESS read-only
    STATUS     current
    DESCRIPTION
        "-- empty --"
    ::= { lcsStatusIpRouter 4 }

-- {SCALAR} 1712.1.10.5
lcsStatusIpRouterLanRoutingErrors OBJECT-TYPE
    SYNTAX     Counter32
    MAX-ACCESS read-only
    STATUS     current
    DESCRIPTION
        "-- empty --"
    ::= { lcsStatusIpRouter 5 }

-- {SCALAR} 1712.1.10.6
lcsStatusIpRouterLanTtlErrors OBJECT-TYPE
    SYNTAX     Counter32
    MAX-ACCESS read-only
    STATUS     current
    DESCRIPTION
        "-- empty --"
    ::= { lcsStatusIpRouter 6 }

-- {SCALAR} 1712.1.10.7
lcsStatusIpRouterLanFilters OBJECT-TYPE
    SYNTAX     Counter32
    MAX-ACCESS read-only
    STATUS     current
    DESCRIPTION
        "-- empty --"
    ::= { lcsStatusIpRouter 7 }

-- {SCALAR} 1712.1.10.8
lcsStatusIpRouterLanDiscards OBJECT-TYPE
    SYNTAX     Counter32
    MAX-ACCESS read-only
    STATUS     current
    DESCRIPTION
        "-- empty --"
    ::= { lcsStatusIpRouter 8 }

-- {SCALAR} 1712.1.10.9
lcsStatusIpRouterWanRx OBJECT-TYPE
    SYNTAX     Counter32
    MAX-ACCESS read-only
    STATUS     current
    DESCRIPTION
        "-- empty --"
    ::= { lcsStatusIpRouter 9 }

-- {SCALAR} 1712.1.10.10
lcsStatusIpRouterWanTx OBJECT-TYPE
    SYNTAX     Counter32
    MAX-ACCESS read-only
    STATUS     current
    DESCRIPTION
        "-- empty --"
    ::= { lcsStatusIpRouter 10 }

-- {SCALAR} 1712.1.10.11
lcsStatusIpRouterWanNetworkErrors OBJECT-TYPE
    SYNTAX     Counter32
    MAX-ACCESS read-only
    STATUS     current
    DESCRIPTION
        "-- empty --"
    ::= { lcsStatusIpRouter 11 }

-- {SCALAR} 1712.1.10.12
lcsStatusIpRouterWanTtlErrors OBJECT-TYPE
    SYNTAX     Counter32
    MAX-ACCESS read-only
    STATUS     current
    DESCRIPTION
        "-- empty --"
    ::= { lcsStatusIpRouter 12 }

-- {SCALAR} 1712.1.10.13
lcsStatusIpRouterWanFilters OBJECT-TYPE
    SYNTAX     Counter32
    MAX-ACCESS read-only
    STATUS     current
    DESCRIPTION
        "-- empty --"
    ::= { lcsStatusIpRouter 13 }

-- {SCALAR} 1712.1.10.14
lcsStatusIpRouterWanDiscards OBJECT-TYPE
    SYNTAX     Counter32
    MAX-ACCESS read-only
    STATUS     current
    DESCRIPTION
        "-- empty --"
    ::= { lcsStatusIpRouter 14 }

-- {SCALAR} 1712.1.10.15
lcsStatusIpRouterWanTypeErrors OBJECT-TYPE
    SYNTAX     Counter32
    MAX-ACCESS read-only
    STATUS     current
    DESCRIPTION
        "-- empty --"
    ::= { lcsStatusIpRouter 15 }

-- {SCALAR} 1712.1.10.16
lcsStatusIpRouterArpErrors OBJECT-TYPE
    SYNTAX     Counter32
    MAX-ACCESS read-only
    STATUS     current
    DESCRIPTION
        "-- empty --"
    ::= { lcsStatusIpRouter 16 }

-- {TABLE} 1712.1.10.17
lcsStatusIpRouterEstablishTableTable OBJECT-TYPE
    SYNTAX     SEQUENCE OF LcsStatusIpRouterEstablishTableEntry
    MAX-ACCESS not-accessible
    STATUS     current
    DESCRIPTION
        "-- empty --"
    ::= { lcsStatusIpRouter 17 }

-- {ENTRY} 1712.1.10.17.1
lcsStatusIpRouterEstablishTableEntry OBJECT-TYPE
    SYNTAX     LcsStatusIpRouterEstablishTableEntry
    MAX-ACCESS not-accessible
    STATUS     current
    DESCRIPTION
        ""
    INDEX {
        lcsStatusIpRouterEstablishTableEntryTime,
        lcsStatusIpRouterEstablishTableEntryCounter
    }
    ::= { lcsStatusIpRouterEstablishTableTable 1 }

-- {SEQUENCE}
LcsStatusIpRouterEstablishTableEntry ::= SEQUENCE {
    lcsStatusIpRouterEstablishTableEntryTime DisplayString,
    lcsStatusIpRouterEstablishTableEntryDestAddress IpAddress,
    lcsStatusIpRouterEstablishTableEntrySrcAddress IpAddress,
    lcsStatusIpRouterEstablishTableEntryProt INTEGER,
    lcsStatusIpRouterEstablishTableEntryDstPort INTEGER,
    lcsStatusIpRouterEstablishTableEntrySrcPort INTEGER,
    lcsStatusIpRouterEstablishTableEntryCounter INTEGER
}

-- {COLUMN} 1712.1.10.17.1.1
lcsStatusIpRouterEstablishTableEntryTime OBJECT-TYPE
    SYNTAX     DisplayString (SIZE(0..19))
    MAX-ACCESS read-only
    STATUS     current
    DESCRIPTION
        "-- empty --"
    ::= { lcsStatusIpRouterEstablishTableEntry 1 }

-- {COLUMN} 1712.1.10.17.1.2
lcsStatusIpRouterEstablishTableEntryDestAddress OBJECT-TYPE
    SYNTAX     IpAddress
    MAX-ACCESS read-only
    STATUS     current
    DESCRIPTION
        "-- empty --"
    ::= { lcsStatusIpRouterEstablishTableEntry 2 }

-- {COLUMN} 1712.1.10.17.1.3
lcsStatusIpRouterEstablishTableEntrySrcAddress OBJECT-TYPE
    SYNTAX     IpAddress
    MAX-ACCESS read-only
    STATUS     current
    DESCRIPTION
        "-- empty --"
    ::= { lcsStatusIpRouterEstablishTableEntry 3 }

-- {COLUMN} 1712.1.10.17.1.4
lcsStatusIpRouterEstablishTableEntryProt OBJECT-TYPE
    SYNTAX     INTEGER
      {
        eIcmp (1),
        eIgmp (2),
        eGgt (3),
        eIpip (4),
        eTcp (6),
        eEgp (8),
        eUdp (17),
        eGre (47),
        eEsp (50),
        eAh (51),
        eCftp (62),
        eIpcomp (108),
        eVrrp (112),
        eSrp (119)
      }
    MAX-ACCESS read-only
    STATUS     current
    DESCRIPTION
        "-- empty --"
    ::= { lcsStatusIpRouterEstablishTableEntry 4 }

-- {COLUMN} 1712.1.10.17.1.5
lcsStatusIpRouterEstablishTableEntryDstPort OBJECT-TYPE
    SYNTAX     INTEGER (0..65535)
    MAX-ACCESS read-only
    STATUS     current
    DESCRIPTION
        "-- empty --"
    ::= { lcsStatusIpRouterEstablishTableEntry 5 }

-- {COLUMN} 1712.1.10.17.1.6
lcsStatusIpRouterEstablishTableEntrySrcPort OBJECT-TYPE
    SYNTAX     INTEGER (0..65535)
    MAX-ACCESS read-only
    STATUS     current
    DESCRIPTION
        "-- empty --"
    ::= { lcsStatusIpRouterEstablishTableEntry 6 }

-- {COLUMN} 1712.1.10.17.1.7
lcsStatusIpRouterEstablishTableEntryCounter OBJECT-TYPE
    SYNTAX     INTEGER (0..2147483647)
    MAX-ACCESS read-only
    STATUS     current
    DESCRIPTION
        "-- empty --"
    ::= { lcsStatusIpRouterEstablishTableEntry 7 }

-- {TABLE} 1712.1.10.18
lcsStatusIpRouterProtocolTableTable OBJECT-TYPE
    SYNTAX     SEQUENCE OF LcsStatusIpRouterProtocolTableEntry
    MAX-ACCESS not-accessible
    STATUS     current
    DESCRIPTION
        "-- empty --"
    ::= { lcsStatusIpRouter 18 }

-- {ENTRY} 1712.1.10.18.1
lcsStatusIpRouterProtocolTableEntry OBJECT-TYPE
    SYNTAX     LcsStatusIpRouterProtocolTableEntry
    MAX-ACCESS not-accessible
    STATUS     current
    DESCRIPTION
        ""
    INDEX {
        lcsStatusIpRouterProtocolTableEntryProt
    }
    ::= { lcsStatusIpRouterProtocolTableTable 1 }

-- {SEQUENCE}
LcsStatusIpRouterProtocolTableEntry ::= SEQUENCE {
    lcsStatusIpRouterProtocolTableEntryProt INTEGER,
    lcsStatusIpRouterProtocolTableEntryLanTx Counter32,
    lcsStatusIpRouterProtocolTableEntryWanTx Counter32
}

-- {COLUMN} 1712.1.10.18.1.1
lcsStatusIpRouterProtocolTableEntryProt OBJECT-TYPE
    SYNTAX     INTEGER
      {
        eIcmp (1),
        eIgmp (2),
        eGgt (3),
        eIpip (4),
        eTcp (6),
        eEgp (8),
        eUdp (17),
        eGre (47),
        eEsp (50),
        eAh (51),
        eCftp (62),
        eIpcomp (108),
        eVrrp (112),
        eSrp (119)
      }
    MAX-ACCESS read-only
    STATUS     current
    DESCRIPTION
        "-- empty --"
    ::= { lcsStatusIpRouterProtocolTableEntry 1 }

-- {COLUMN} 1712.1.10.18.1.2
lcsStatusIpRouterProtocolTableEntryLanTx OBJECT-TYPE
    SYNTAX     Counter32
    MAX-ACCESS read-only
    STATUS     current
    DESCRIPTION
        "-- empty --"
    ::= { lcsStatusIpRouterProtocolTableEntry 2 }

-- {COLUMN} 1712.1.10.18.1.3
lcsStatusIpRouterProtocolTableEntryWanTx OBJECT-TYPE
    SYNTAX     Counter32
    MAX-ACCESS read-only
    STATUS     current
    DESCRIPTION
        "-- empty --"
    ::= { lcsStatusIpRouterProtocolTableEntry 3 }

-- {OID} 1712.1.10.19
lcsStatusIpRouterRip OBJECT IDENTIFIER ::= { lcsStatusIpRouter 19 }

-- {SCALAR} 1712.1.10.19.1
lcsStatusIpRouterRipRx OBJECT-TYPE
    SYNTAX     Counter32
    MAX-ACCESS read-only
    STATUS     current
    DESCRIPTION
        "-- empty --"
    ::= { lcsStatusIpRouterRip 1 }

-- {SCALAR} 1712.1.10.19.2
lcsStatusIpRouterRipRequests OBJECT-TYPE
    SYNTAX     Counter32
    MAX-ACCESS read-only
    STATUS     current
    DESCRIPTION
        "-- empty --"
    ::= { lcsStatusIpRouterRip 2 }

-- {SCALAR} 1712.1.10.19.3
lcsStatusIpRouterRipResponse OBJECT-TYPE
    SYNTAX     Counter32
    MAX-ACCESS read-only
    STATUS     current
    DESCRIPTION
        "-- empty --"
    ::= { lcsStatusIpRouterRip 3 }

-- {SCALAR} 1712.1.10.19.4
lcsStatusIpRouterRipDiscards OBJECT-TYPE
    SYNTAX     Counter32
    MAX-ACCESS read-only
    STATUS     current
    DESCRIPTION
        "-- empty --"
    ::= { lcsStatusIpRouterRip 4 }

-- {SCALAR} 1712.1.10.19.5
lcsStatusIpRouterRipErrors OBJECT-TYPE
    SYNTAX     Counter32
    MAX-ACCESS read-only
    STATUS     current
    DESCRIPTION
        "-- empty --"
    ::= { lcsStatusIpRouterRip 5 }

-- {SCALAR} 1712.1.10.19.6
lcsStatusIpRouterRipEntryErrors OBJECT-TYPE
    SYNTAX     Counter32
    MAX-ACCESS read-only
    STATUS     current
    DESCRIPTION
        "-- empty --"
    ::= { lcsStatusIpRouterRip 6 }

-- {SCALAR} 1712.1.10.19.7
lcsStatusIpRouterRipTx OBJECT-TYPE
    SYNTAX     Counter32
    MAX-ACCESS read-only
    STATUS     current
    DESCRIPTION
        "-- empty --"
    ::= { lcsStatusIpRouterRip 7 }

-- {TABLE} 1712.1.10.19.8
lcsStatusIpRouterRipBestRoutesTable OBJECT-TYPE
    SYNTAX     SEQUENCE OF LcsStatusIpRouterRipBestRoutesEntry
    MAX-ACCESS not-accessible
    STATUS     current
    DESCRIPTION
        "-- empty --"
    ::= { lcsStatusIpRouterRip 8 }

-- {ENTRY} 1712.1.10.19.8.1
lcsStatusIpRouterRipBestRoutesEntry OBJECT-TYPE
    SYNTAX     LcsStatusIpRouterRipBestRoutesEntry
    MAX-ACCESS not-accessible
    STATUS     current
    DESCRIPTION
        ""
    INDEX {
        lcsStatusIpRouterRipBestRoutesEntryIpAddress,
        lcsStatusIpRouterRipBestRoutesEntryIpNetmask,
        lcsStatusIpRouterRipBestRoutesEntryRtgTag,
        lcsStatusIpRouterRipBestRoutesEntryGateway
    }
    ::= { lcsStatusIpRouterRipBestRoutesTable 1 }

-- {SEQUENCE}
LcsStatusIpRouterRipBestRoutesEntry ::= SEQUENCE {
    lcsStatusIpRouterRipBestRoutesEntryIpAddress IpAddress,
    lcsStatusIpRouterRipBestRoutesEntryIpNetmask IpAddress,
    lcsStatusIpRouterRipBestRoutesEntryRtgTag INTEGER,
    lcsStatusIpRouterRipBestRoutesEntryGateway IpAddress,
    lcsStatusIpRouterRipBestRoutesEntryDistance INTEGER,
    lcsStatusIpRouterRipBestRoutesEntryTime INTEGER,
    lcsStatusIpRouterRipBestRoutesEntryPeer DisplayString,
    lcsStatusIpRouterRipBestRoutesEntryPort INTEGER,
    lcsStatusIpRouterRipBestRoutesEntryVlanId INTEGER,
    lcsStatusIpRouterRipBestRoutesEntryNetworkName DisplayString
}

-- {COLUMN} 1712.1.10.19.8.1.1
lcsStatusIpRouterRipBestRoutesEntryIpAddress OBJECT-TYPE
    SYNTAX     IpAddress
    MAX-ACCESS read-only
    STATUS     current
    DESCRIPTION
        "-- empty --"
    ::= { lcsStatusIpRouterRipBestRoutesEntry 1 }

-- {COLUMN} 1712.1.10.19.8.1.2
lcsStatusIpRouterRipBestRoutesEntryIpNetmask OBJECT-TYPE
    SYNTAX     IpAddress
    MAX-ACCESS read-only
    STATUS     current
    DESCRIPTION
        "-- empty --"
    ::= { lcsStatusIpRouterRipBestRoutesEntry 2 }

-- {COLUMN} 1712.1.10.19.8.1.6
lcsStatusIpRouterRipBestRoutesEntryRtgTag OBJECT-TYPE
    SYNTAX     INTEGER (0..65535)
    MAX-ACCESS read-only
    STATUS     current
    DESCRIPTION
        "-- empty --"
    ::= { lcsStatusIpRouterRipBestRoutesEntry 6 }

-- {COLUMN} 1712.1.10.19.8.1.5
lcsStatusIpRouterRipBestRoutesEntryGateway OBJECT-TYPE
    SYNTAX     IpAddress
    MAX-ACCESS read-only
    STATUS     current
    DESCRIPTION
        "-- empty --"
    ::= { lcsStatusIpRouterRipBestRoutesEntry 5 }

-- {COLUMN} 1712.1.10.19.8.1.4
lcsStatusIpRouterRipBestRoutesEntryDistance OBJECT-TYPE
    SYNTAX     INTEGER (0..65535)
    MAX-ACCESS read-only
    STATUS     current
    DESCRIPTION
        "-- empty --"
    ::= { lcsStatusIpRouterRipBestRoutesEntry 4 }

-- {COLUMN} 1712.1.10.19.8.1.3
lcsStatusIpRouterRipBestRoutesEntryTime OBJECT-TYPE
    SYNTAX     INTEGER (0..65535)
    MAX-ACCESS read-only
    STATUS     current
    DESCRIPTION
        "-- empty --"
    ::= { lcsStatusIpRouterRipBestRoutesEntry 3 }

-- {COLUMN} 1712.1.10.19.8.1.8
lcsStatusIpRouterRipBestRoutesEntryPeer OBJECT-TYPE
    SYNTAX     DisplayString (SIZE(0..255))
    MAX-ACCESS read-only
    STATUS     current
    DESCRIPTION
        "-- empty --"
    ::= { lcsStatusIpRouterRipBestRoutesEntry 8 }

-- {COLUMN} 1712.1.10.19.8.1.12
lcsStatusIpRouterRipBestRoutesEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusIpRouterRipBestRoutesEntry 12 }

-- {COLUMN} 1712.1.10.19.8.1.10
lcsStatusIpRouterRipBestRoutesEntryVlanId OBJECT-TYPE
    SYNTAX     INTEGER (0..65535)
    MAX-ACCESS read-only
    STATUS     current
    DESCRIPTION
        "-- empty --"
    ::= { lcsStatusIpRouterRipBestRoutesEntry 10 }

-- {COLUMN} 1712.1.10.19.8.1.11
lcsStatusIpRouterRipBestRoutesEntryNetworkName OBJECT-TYPE
    SYNTAX     DisplayString (SIZE(0..255))
    MAX-ACCESS read-only
    STATUS     current
    DESCRIPTION
        "-- empty --"
    ::= { lcsStatusIpRouterRipBestRoutesEntry 11 }

-- {TABLE} 1712.1.10.19.20
lcsStatusIpRouterRipAllRoutesTable OBJECT-TYPE
    SYNTAX     SEQUENCE OF LcsStatusIpRouterRipAllRoutesEntry
    MAX-ACCESS not-accessible
    STATUS     current
    DESCRIPTION
        "-- empty --"
    ::= { lcsStatusIpRouterRip 20 }

-- {ENTRY} 1712.1.10.19.20.1
lcsStatusIpRouterRipAllRoutesEntry OBJECT-TYPE
    SYNTAX     LcsStatusIpRouterRipAllRoutesEntry
    MAX-ACCESS not-accessible
    STATUS     current
    DESCRIPTION
        ""
    INDEX {
        lcsStatusIpRouterRipAllRoutesEntryIpAddress,
        lcsStatusIpRouterRipAllRoutesEntryIpNetmask,
        lcsStatusIpRouterRipAllRoutesEntryRtgTag,
        lcsStatusIpRouterRipAllRoutesEntryGateway
    }
    ::= { lcsStatusIpRouterRipAllRoutesTable 1 }

-- {SEQUENCE}
LcsStatusIpRouterRipAllRoutesEntry ::= SEQUENCE {
    lcsStatusIpRouterRipAllRoutesEntryIpAddress IpAddress,
    lcsStatusIpRouterRipAllRoutesEntryIpNetmask IpAddress,
    lcsStatusIpRouterRipAllRoutesEntryRtgTag INTEGER,
    lcsStatusIpRouterRipAllRoutesEntryGateway IpAddress,
    lcsStatusIpRouterRipAllRoutesEntryDistance INTEGER,
    lcsStatusIpRouterRipAllRoutesEntryTime INTEGER,
    lcsStatusIpRouterRipAllRoutesEntryPeer DisplayString,
    lcsStatusIpRouterRipAllRoutesEntryPort INTEGER,
    lcsStatusIpRouterRipAllRoutesEntryVlanId INTEGER,
    lcsStatusIpRouterRipAllRoutesEntryNetworkName DisplayString
}

-- {COLUMN} 1712.1.10.19.20.1.1
lcsStatusIpRouterRipAllRoutesEntryIpAddress OBJECT-TYPE
    SYNTAX     IpAddress
    MAX-ACCESS read-only
    STATUS     current
    DESCRIPTION
        "-- empty --"
    ::= { lcsStatusIpRouterRipAllRoutesEntry 1 }

-- {COLUMN} 1712.1.10.19.20.1.2
lcsStatusIpRouterRipAllRoutesEntryIpNetmask OBJECT-TYPE
    SYNTAX     IpAddress
    MAX-ACCESS read-only
    STATUS     current
    DESCRIPTION
        "-- empty --"
    ::= { lcsStatusIpRouterRipAllRoutesEntry 2 }

-- {COLUMN} 1712.1.10.19.20.1.6
lcsStatusIpRouterRipAllRoutesEntryRtgTag OBJECT-TYPE
    SYNTAX     INTEGER (0..65535)
    MAX-ACCESS read-only
    STATUS     current
    DESCRIPTION
        "-- empty --"
    ::= { lcsStatusIpRouterRipAllRoutesEntry 6 }

-- {COLUMN} 1712.1.10.19.20.1.5
lcsStatusIpRouterRipAllRoutesEntryGateway OBJECT-TYPE
    SYNTAX     IpAddress
    MAX-ACCESS read-only
    STATUS     current
    DESCRIPTION
        "-- empty --"
    ::= { lcsStatusIpRouterRipAllRoutesEntry 5 }

-- {COLUMN} 1712.1.10.19.20.1.4
lcsStatusIpRouterRipAllRoutesEntryDistance OBJECT-TYPE
    SYNTAX     INTEGER (0..65535)
    MAX-ACCESS read-only
    STATUS     current
    DESCRIPTION
        "-- empty --"
    ::= { lcsStatusIpRouterRipAllRoutesEntry 4 }

-- {COLUMN} 1712.1.10.19.20.1.3
lcsStatusIpRouterRipAllRoutesEntryTime OBJECT-TYPE
    SYNTAX     INTEGER (0..65535)
    MAX-ACCESS read-only
    STATUS     current
    DESCRIPTION
        "-- empty --"
    ::= { lcsStatusIpRouterRipAllRoutesEntry 3 }

-- {COLUMN} 1712.1.10.19.20.1.8
lcsStatusIpRouterRipAllRoutesEntryPeer OBJECT-TYPE
    SYNTAX     DisplayString (SIZE(0..255))
    MAX-ACCESS read-only
    STATUS     current
    DESCRIPTION
        "-- empty --"
    ::= { lcsStatusIpRouterRipAllRoutesEntry 8 }

-- {COLUMN} 1712.1.10.19.20.1.12
lcsStatusIpRouterRipAllRoutesEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusIpRouterRipAllRoutesEntry 12 }

-- {COLUMN} 1712.1.10.19.20.1.10
lcsStatusIpRouterRipAllRoutesEntryVlanId OBJECT-TYPE
    SYNTAX     INTEGER (0..65535)
    MAX-ACCESS read-only
    STATUS     current
    DESCRIPTION
        "-- empty --"
    ::= { lcsStatusIpRouterRipAllRoutesEntry 10 }

-- {COLUMN} 1712.1.10.19.20.1.11
lcsStatusIpRouterRipAllRoutesEntryNetworkName OBJECT-TYPE
    SYNTAX     DisplayString (SIZE(0..255))
    MAX-ACCESS read-only
    STATUS     current
    DESCRIPTION
        "-- empty --"
    ::= { lcsStatusIpRouterRipAllRoutesEntry 11 }

-- {SCALAR} 1712.1.10.19.9
lcsStatusIpRouterRipDeleteValues OBJECT-TYPE
    SYNTAX     DisplayString
    MAX-ACCESS read-write
    STATUS     current
    DESCRIPTION
        "-- empty --"
    ::= { lcsStatusIpRouterRip 9 }

-- {TABLE} 1712.1.10.19.10
lcsStatusIpRouterRipLanSitesTable OBJECT-TYPE
    SYNTAX     SEQUENCE OF LcsStatusIpRouterRipLanSitesEntry
    MAX-ACCESS not-accessible
    STATUS     current
    DESCRIPTION
        "-- empty --"
    ::= { lcsStatusIpRouterRip 10 }

-- {ENTRY} 1712.1.10.19.10.1
lcsStatusIpRouterRipLanSitesEntry OBJECT-TYPE
    SYNTAX     LcsStatusIpRouterRipLanSitesEntry
    MAX-ACCESS not-accessible
    STATUS     current
    DESCRIPTION
        ""
    INDEX {
        lcsStatusIpRouterRipLanSitesEntryNetworkName
    }
    ::= { lcsStatusIpRouterRipLanSitesTable 1 }

-- {SEQUENCE}
LcsStatusIpRouterRipLanSitesEntry ::= SEQUENCE {
    lcsStatusIpRouterRipLanSitesEntryNetworkName DisplayString,
    lcsStatusIpRouterRipLanSitesEntryRipType INTEGER,
    lcsStatusIpRouterRipLanSitesEntryRipSend INTEGER,
    lcsStatusIpRouterRipLanSitesEntryRipAccept INTEGER,
    lcsStatusIpRouterRipLanSitesEntryPropagate INTEGER,
    lcsStatusIpRouterRipLanSitesEntryPoisonedReverse INTEGER,
    lcsStatusIpRouterRipLanSitesEntryDftRtgTag INTEGER,
    lcsStatusIpRouterRipLanSitesEntryRtgTagList DisplayString,
    lcsStatusIpRouterRipLanSitesEntryRxFilter DisplayString,
    lcsStatusIpRouterRipLanSitesEntryTxFilter DisplayString,
    lcsStatusIpRouterRipLanSitesEntryPort INTEGER,
    lcsStatusIpRouterRipLanSitesEntryVlanId INTEGER
}

-- {COLUMN} 1712.1.10.19.10.1.1
lcsStatusIpRouterRipLanSitesEntryNetworkName OBJECT-TYPE
    SYNTAX     DisplayString (SIZE(0..16))
    MAX-ACCESS read-only
    STATUS     current
    DESCRIPTION
        "-- empty --"
    ::= { lcsStatusIpRouterRipLanSitesEntry 1 }

-- {COLUMN} 1712.1.10.19.10.1.2
lcsStatusIpRouterRipLanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipLanSitesEntry 2 }

-- {COLUMN} 1712.1.10.19.10.1.12
lcsStatusIpRouterRipLanSitesEntryRipSend OBJECT-TYPE
    SYNTAX     INTEGER
      {
        eNo (0),
        eYes (1)
      }
    MAX-ACCESS read-only
    STATUS     current
    DESCRIPTION
        "-- empty --"
    ::= { lcsStatusIpRouterRipLanSitesEntry 12 }

-- {COLUMN} 1712.1.10.19.10.1.3
lcsStatusIpRouterRipLanSitesEntryRipAccept OBJECT-TYPE
    SYNTAX     INTEGER
      {
        eNo (0),
        eYes (1)
      }
    MAX-ACCESS read-only
    STATUS     current
    DESCRIPTION
        "-- empty --"
    ::= { lcsStatusIpRouterRipLanSitesEntry 3 }

-- {COLUMN} 1712.1.10.19.10.1.4
lcsStatusIpRouterRipLanSitesEntryPropagate OBJECT-TYPE
    SYNTAX     INTEGER
      {
        eNo (0),
        eYes (1)
      }
    MAX-ACCESS read-only
    STATUS     current
    DESCRIPTION
        "-- empty --"
    ::= { lcsStatusIpRouterRipLanSitesEntry 4 }

-- {COLUMN} 1712.1.10.19.10.1.9
lcsStatusIpRouterRipLanSitesEntryPoisonedReverse OBJECT-TYPE
    SYNTAX     INTEGER
      {
        eNo (0),
        eYes (1)
      }
    MAX-ACCESS read-only
    STATUS     current
    DESCRIPTION
        "-- empty --"
    ::= { lcsStatusIpRouterRipLanSitesEntry 9 }

-- {COLUMN} 1712.1.10.19.10.1.5
lcsStatusIpRouterRipLanSitesEntryDftRtgTag OBJECT-TYPE
    SYNTAX     INTEGER (0..65535)
    MAX-ACCESS read-only
    STATUS     current
    DESCRIPTION
        "-- empty --"
    ::= { lcsStatusIpRouterRipLanSitesEntry 5 }

-- {COLUMN} 1712.1.10.19.10.1.6
lcsStatusIpRouterRipLanSitesEntryRtgTagList OBJECT-TYPE
    SYNTAX     DisplayString (SIZE(0..33))
    MAX-ACCESS read-only
    STATUS     current
    DESCRIPTION
        "-- empty --"
    ::= { lcsStatusIpRouterRipLanSitesEntry 6 }

-- {COLUMN} 1712.1.10.19.10.1.10
lcsStatusIpRouterRipLanSitesEntryRxFilter OBJECT-TYPE
    SYNTAX     DisplayString (SIZE(0..16))
    MAX-ACCESS read-only
    STATUS     current
    DESCRIPTION
        "-- empty --"
    ::= { lcsStatusIpRouterRipLanSitesEntry 10 }

-- {COLUMN} 1712.1.10.19.10.1.11
lcsStatusIpRouterRipLanSitesEntryTxFilter OBJECT-TYPE
    SYNTAX     DisplayString (SIZE(0..16))
    MAX-ACCESS read-only
    STATUS     current
    DESCRIPTION
        "-- empty --"
    ::= { lcsStatusIpRouterRipLanSitesEntry 11 }

-- {COLUMN} 1712.1.10.19.10.1.31
lcsStatusIpRouterRipLanSitesEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusIpRouterRipLanSitesEntry 31 }

-- {COLUMN} 1712.1.10.19.10.1.8
lcsStatusIpRouterRipLanSitesEntryVlanId OBJECT-TYPE
    SYNTAX     INTEGER (0..65535)
    MAX-ACCESS read-only
    STATUS     current
    DESCRIPTION
        "-- empty --"
    ::= { lcsStatusIpRouterRipLanSitesEntry 8 }

-- {TABLE} 1712.1.10.19.12
lcsStatusIpRouterRipVrrpSitesTable OBJECT-TYPE
    SYNTAX     SEQUENCE OF LcsStatusIpRouterRipVrrpSitesEntry
    MAX-ACCESS not-accessible
    STATUS     current
    DESCRIPTION
        "-- empty --"
    ::= { lcsStatusIpRouterRip 12 }

-- {ENTRY} 1712.1.10.19.12.1
lcsStatusIpRouterRipVrrpSitesEntry OBJECT-TYPE
    SYNTAX     LcsStatusIpRouterRipVrrpSitesEntry
    MAX-ACCESS not-accessible
    STATUS     current
    DESCRIPTION
        ""
    INDEX {
        lcsStatusIpRouterRipVrrpSitesEntryNetworkName,
        lcsStatusIpRouterRipVrrpSitesEntryRouterId
    }
    ::= { lcsStatusIpRouterRipVrrpSitesTable 1 }

-- {SEQUENCE}
LcsStatusIpRouterRipVrrpSitesEntry ::= SEQUENCE {
    lcsStatusIpRouterRipVrrpSitesEntryNetworkName DisplayString,
    lcsStatusIpRouterRipVrrpSitesEntryRipType INTEGER,
    lcsStatusIpRouterRipVrrpSitesEntryRouterId INTEGER
}

-- {COLUMN} 1712.1.10.19.12.1.1
lcsStatusIpRouterRipVrrpSitesEntryNetworkName OBJECT-TYPE
    SYNTAX     DisplayString (SIZE(0..16))
    MAX-ACCESS read-only
    STATUS     current
    DESCRIPTION
        "-- empty --"
    ::= { lcsStatusIpRouterRipVrrpSitesEntry 1 }

-- {COLUMN} 1712.1.10.19.12.1.2
lcsStatusIpRouterRipVrrpSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipVrrpSitesEntry 2 }

-- {COLUMN} 1712.1.10.19.12.1.3
lcsStatusIpRouterRipVrrpSitesEntryRouterId OBJECT-TYPE
    SYNTAX     INTEGER (0..255)
    MAX-ACCESS read-only
    STATUS     current
    DESCRIPTION
        "-- empty --"
    ::= { lcsStatusIpRouterRipVrrpSitesEntry 3 }

-- {TABLE} 1712.1.10.19.11
lcsStatusIpRouterRipWanSitesTable OBJECT-TYPE
    SYNTAX     SEQUENCE OF LcsStatusIpRouterRipWanSitesEntry
    MAX-ACCESS not-accessible
    STATUS     current
    DESCRIPTION
        "-- empty --"
    ::= { lcsStatusIpRouterRip 11 }

-- {ENTRY} 1712.1.10.19.11.1
lcsStatusIpRouterRipWanSitesEntry OBJECT-TYPE
    SYNTAX     LcsStatusIpRouterRipWanSitesEntry
    MAX-ACCESS not-accessible
    STATUS     current
    DESCRIPTION
        ""
    INDEX {
        lcsStatusIpRouterRipWanSitesEntryPeer
    }
    ::= { lcsStatusIpRouterRipWanSitesTable 1 }

-- {SEQUENCE}
LcsStatusIpRouterRipWanSitesEntry ::= SEQUENCE {
    lcsStatusIpRouterRipWanSitesEntryPeer DisplayString,
    lcsStatusIpRouterRipWanSitesEntryRipType INTEGER,
    lcsStatusIpRouterRipWanSitesEntryRipSend INTEGER,
    lcsStatusIpRouterRipWanSitesEntryRipAccept INTEGER,
    lcsStatusIpRouterRipWanSitesEntryMasquerade INTEGER,
    lcsStatusIpRouterRipWanSitesEntryPoisonedReverse INTEGER,
    lcsStatusIpRouterRipWanSitesEntryRfc2091 INTEGER,
    lcsStatusIpRouterRipWanSitesEntryGateway IpAddress,
    lcsStatusIpRouterRipWanSitesEntryDftRtgTag INTEGER,
    lcsStatusIpRouterRipWanSitesEntryRtgTagList DisplayString,
    lcsStatusIpRouterRipWanSitesEntryRxFilter DisplayString,
    lcsStatusIpRouterRipWanSitesEntryTxFilter DisplayString
}

-- {COLUMN} 1712.1.10.19.11.1.1
lcsStatusIpRouterRipWanSitesEntryPeer OBJECT-TYPE
    SYNTAX     DisplayString (SIZE(0..16))
    MAX-ACCESS read-only
    STATUS     current
    DESCRIPTION
        "-- empty --"
    ::= { lcsStatusIpRouterRipWanSitesEntry 1 }

-- {COLUMN} 1712.1.10.19.11.1.2
lcsStatusIpRouterRipWanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipWanSitesEntry 2 }

-- {COLUMN} 1712.1.10.19.11.1.12
lcsStatusIpRouterRipWanSitesEntryRipSend OBJECT-TYPE
    SYNTAX     INTEGER
      {
        eNo (0),
        eYes (1)
      }
    MAX-ACCESS read-only
    STATUS     current
    DESCRIPTION
        "-- empty --"
    ::= { lcsStatusIpRouterRipWanSitesEntry 12 }

-- {COLUMN} 1712.1.10.19.11.1.3
lcsStatusIpRouterRipWanSitesEntryRipAccept OBJECT-TYPE
    SYNTAX     INTEGER
      {
        eNo (0),
        eYes (1)
      }
    MAX-ACCESS read-only
    STATUS     current
    DESCRIPTION
        "-- empty --"
    ::= { lcsStatusIpRouterRipWanSitesEntry 3 }

-- {COLUMN} 1712.1.10.19.11.1.4
lcsStatusIpRouterRipWanSitesEntryMasquerade OBJECT-TYPE
    SYNTAX     INTEGER
      {
        eAuto (0),
        eOn (1),
        eIntranet (2)
      }
    MAX-ACCESS read-only
    STATUS     current
    DESCRIPTION
        "-- empty --"
    ::= { lcsStatusIpRouterRipWanSitesEntry 4 }

-- {COLUMN} 1712.1.10.19.11.1.7
lcsStatusIpRouterRipWanSitesEntryPoisonedReverse OBJECT-TYPE
    SYNTAX     INTEGER
      {
        eNo (0),
        eYes (1)
      }
    MAX-ACCESS read-only
    STATUS     current
    DESCRIPTION
        "-- empty --"
    ::= { lcsStatusIpRouterRipWanSitesEntry 7 }

-- {COLUMN} 1712.1.10.19.11.1.8
lcsStatusIpRouterRipWanSitesEntryRfc2091 OBJECT-TYPE
    SYNTAX     INTEGER
      {
        eNo (0),
        eYes (1)
      }
    MAX-ACCESS read-only
    STATUS     current
    DESCRIPTION
        "-- empty --"
    ::= { lcsStatusIpRouterRipWanSitesEntry 8 }

-- {COLUMN} 1712.1.10.19.11.1.9
lcsStatusIpRouterRipWanSitesEntryGateway OBJECT-TYPE
    SYNTAX     IpAddress
    MAX-ACCESS read-only
    STATUS     current
    DESCRIPTION
        "-- empty --"
    ::= { lcsStatusIpRouterRipWanSitesEntry 9 }

-- {COLUMN} 1712.1.10.19.11.1.5
lcsStatusIpRouterRipWanSitesEntryDftRtgTag OBJECT-TYPE
    SYNTAX     INTEGER (0..65535)
    MAX-ACCESS read-only
    STATUS     current
    DESCRIPTION
        "-- empty --"
    ::= { lcsStatusIpRouterRipWanSitesEntry 5 }

-- {COLUMN} 1712.1.10.19.11.1.6
lcsStatusIpRouterRipWanSitesEntryRtgTagList OBJECT-TYPE
    SYNTAX     DisplayString (SIZE(0..33))
    MAX-ACCESS read-only
    STATUS     current
    DESCRIPTION
        "-- empty --"
    ::= { lcsStatusIpRouterRipWanSitesEntry 6 }

-- {COLUMN} 1712.1.10.19.11.1.10
lcsStatusIpRouterRipWanSitesEntryRxFilter OBJECT-TYPE
    SYNTAX     DisplayString (SIZE(0..16))
    MAX-ACCESS read-only
    STATUS     current
    DESCRIPTION
        "-- empty --"
    ::= { lcsStatusIpRouterRipWanSitesEntry 10 }

-- {COLUMN} 1712.1.10.19.11.1.11
lcsStatusIpRouterRipWanSitesEntryTxFilter OBJECT-TYPE
    SYNTAX     DisplayString (SIZE(0..16))
    MAX-ACCESS read-only
    STATUS     current
    DESCRIPTION
        "-- empty --"
    ::= { lcsStatusIpRouterRipWanSitesEntry 11 }

-- {TABLE} 1712.1.10.19.13
lcsStatusIpRouterRipDynLanSitesTable OBJECT-TYPE
    SYNTAX     SEQUENCE OF LcsStatusIpRouterRipDynLanSitesEntry
    MAX-ACCESS not-accessible
    STATUS     current
    DESCRIPTION
        "-- empty --"
    ::= { lcsStatusIpRouterRip 13 }

-- {ENTRY} 1712.1.10.19.13.1
lcsStatusIpRouterRipDynLanSitesEntry OBJECT-TYPE
    SYNTAX     LcsStatusIpRouterRipDynLanSitesEntry
    MAX-ACCESS not-accessible
    STATUS     current
    DESCRIPTION
        ""
    INDEX {
        lcsStatusIpRouterRipDynLanSitesEntryGateway
    }
    ::= { lcsStatusIpRouterRipDynLanSitesTable 1 }

-- {SEQUENCE}
LcsStatusIpRouterRipDynLanSitesEntry ::= SEQUENCE {
    lcsStatusIpRouterRipDynLanSitesEntryGateway DisplayString,
    lcsStatusIpRouterRipDynLanSitesEntryRipType INTEGER,
    lcsStatusIpRouterRipDynLanSitesEntryRipSend INTEGER,
    lcsStatusIpRouterRipDynLanSitesEntryRipAccept INTEGER,
    lcsStatusIpRouterRipDynLanSitesEntryPoisonedReverse INTEGER,
    lcsStatusIpRouterRipDynLanSitesEntryDftRtgTag INTEGER,
    lcsStatusIpRouterRipDynLanSitesEntryRtgTagList DisplayString,
    lcsStatusIpRouterRipDynLanSitesEntryRxFilter DisplayString,
    lcsStatusIpRouterRipDynLanSitesEntryTxFilter DisplayString,
    lcsStatusIpRouterRipDynLanSitesEntryPort INTEGER,
    lcsStatusIpRouterRipDynLanSitesEntryVlanId INTEGER
}

-- {COLUMN} 1712.1.10.19.13.1.1
lcsStatusIpRouterRipDynLanSitesEntryGateway OBJECT-TYPE
    SYNTAX     DisplayString (SIZE(0..16))
    MAX-ACCESS read-only
    STATUS     current
    DESCRIPTION
        "-- empty --"
    ::= { lcsStatusIpRouterRipDynLanSitesEntry 1 }

-- {COLUMN} 1712.1.10.19.13.1.2
lcsStatusIpRouterRipDynLanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipDynLanSitesEntry 2 }

-- {COLUMN} 1712.1.10.19.13.1.12
lcsStatusIpRouterRipDynLanSitesEntryRipSend OBJECT-TYPE
    SYNTAX     INTEGER
      {
        eNo (0),
        eYes (1)
      }
    MAX-ACCESS read-only
    STATUS     current
    DESCRIPTION
        "-- empty --"
    ::= { lcsStatusIpRouterRipDynLanSitesEntry 12 }

-- {COLUMN} 1712.1.10.19.13.1.3
lcsStatusIpRouterRipDynLanSitesEntryRipAccept OBJECT-TYPE
    SYNTAX     INTEGER
      {
        eNo (0),
        eYes (1)
      }
    MAX-ACCESS read-only
    STATUS     current
    DESCRIPTION
        "-- empty --"
    ::= { lcsStatusIpRouterRipDynLanSitesEntry 3 }

-- {COLUMN} 1712.1.10.19.13.1.4
lcsStatusIpRouterRipDynLanSitesEntryPoisonedReverse OBJECT-TYPE
    SYNTAX     INTEGER
      {
        eNo (0),
        eYes (1)
      }
    MAX-ACCESS read-only
    STATUS     current
    DESCRIPTION
        "-- empty --"
    ::= { lcsStatusIpRouterRipDynLanSitesEntry 4 }

-- {COLUMN} 1712.1.10.19.13.1.5
lcsStatusIpRouterRipDynLanSitesEntryDftRtgTag OBJECT-TYPE
    SYNTAX     INTEGER (0..65535)
    MAX-ACCESS read-only
    STATUS     current
    DESCRIPTION
        "-- empty --"
    ::= { lcsStatusIpRouterRipDynLanSitesEntry 5 }

-- {COLUMN} 1712.1.10.19.13.1.6
lcsStatusIpRouterRipDynLanSitesEntryRtgTagList OBJECT-TYPE
    SYNTAX     DisplayString (SIZE(0..33))
    MAX-ACCESS read-only
    STATUS     current
    DESCRIPTION
        "-- empty --"
    ::= { lcsStatusIpRouterRipDynLanSitesEntry 6 }

-- {COLUMN} 1712.1.10.19.13.1.10
lcsStatusIpRouterRipDynLanSitesEntryRxFilter OBJECT-TYPE
    SYNTAX     DisplayString (SIZE(0..16))
    MAX-ACCESS read-only
    STATUS     current
    DESCRIPTION
        "-- empty --"
    ::= { lcsStatusIpRouterRipDynLanSitesEntry 10 }

-- {COLUMN} 1712.1.10.19.13.1.11
lcsStatusIpRouterRipDynLanSitesEntryTxFilter OBJECT-TYPE
    SYNTAX     DisplayString (SIZE(0..16))
    MAX-ACCESS read-only
    STATUS     current
    DESCRIPTION
        "-- empty --"
    ::= { lcsStatusIpRouterRipDynLanSitesEntry 11 }

-- {COLUMN} 1712.1.10.19.13.1.31
lcsStatusIpRouterRipDynLanSitesEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusIpRouterRipDynLanSitesEntry 31 }

-- {COLUMN} 1712.1.10.19.13.1.8
lcsStatusIpRouterRipDynLanSitesEntryVlanId OBJECT-TYPE
    SYNTAX     INTEGER (0..65535)
    MAX-ACCESS read-only
    STATUS     current
    DESCRIPTION
        "-- empty --"
    ::= { lcsStatusIpRouterRipDynLanSitesEntry 8 }

-- {TABLE} 1712.1.10.19.14
lcsStatusIpRouterRipDynWanSitesTable OBJECT-TYPE
    SYNTAX     SEQUENCE OF LcsStatusIpRouterRipDynWanSitesEntry
    MAX-ACCESS not-accessible
    STATUS     current
    DESCRIPTION
        "-- empty --"
    ::= { lcsStatusIpRouterRip 14 }

-- {ENTRY} 1712.1.10.19.14.1
lcsStatusIpRouterRipDynWanSitesEntry OBJECT-TYPE
    SYNTAX     LcsStatusIpRouterRipDynWanSitesEntry
    MAX-ACCESS not-accessible
    STATUS     current
    DESCRIPTION
        ""
    INDEX {
        lcsStatusIpRouterRipDynWanSitesEntryPeer
    }
    ::= { lcsStatusIpRouterRipDynWanSitesTable 1 }

-- {SEQUENCE}
LcsStatusIpRouterRipDynWanSitesEntry ::= SEQUENCE {
    lcsStatusIpRouterRipDynWanSitesEntryPeer DisplayString,
    lcsStatusIpRouterRipDynWanSitesEntryRipType INTEGER,
    lcsStatusIpRouterRipDynWanSitesEntryRipSend INTEGER,
    lcsStatusIpRouterRipDynWanSitesEntryRipAccept INTEGER,
    lcsStatusIpRouterRipDynWanSitesEntryMasquerade INTEGER,
    lcsStatusIpRouterRipDynWanSitesEntryPoisonedReverse INTEGER,
    lcsStatusIpRouterRipDynWanSitesEntryRfc2091 INTEGER,
    lcsStatusIpRouterRipDynWanSitesEntryGateway IpAddress,
    lcsStatusIpRouterRipDynWanSitesEntryDftRtgTag INTEGER,
    lcsStatusIpRouterRipDynWanSitesEntryRtgTagList DisplayString,
    lcsStatusIpRouterRipDynWanSitesEntryRxFilter DisplayString,
    lcsStatusIpRouterRipDynWanSitesEntryTxFilter DisplayString
}

-- {COLUMN} 1712.1.10.19.14.1.1
lcsStatusIpRouterRipDynWanSitesEntryPeer OBJECT-TYPE
    SYNTAX     DisplayString (SIZE(0..16))
    MAX-ACCESS read-only
    STATUS     current
    DESCRIPTION
        "-- empty --"
    ::= { lcsStatusIpRouterRipDynWanSitesEntry 1 }

-- {COLUMN} 1712.1.10.19.14.1.2
lcsStatusIpRouterRipDynWanSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipDynWanSitesEntry 2 }

-- {COLUMN} 1712.1.10.19.14.1.12
lcsStatusIpRouterRipDynWanSitesEntryRipSend OBJECT-TYPE
    SYNTAX     INTEGER
      {
        eNo (0),
        eYes (1)
      }
    MAX-ACCESS read-only
    STATUS     current
    DESCRIPTION
        "-- empty --"
    ::= { lcsStatusIpRouterRipDynWanSitesEntry 12 }

-- {COLUMN} 1712.1.10.19.14.1.3
lcsStatusIpRouterRipDynWanSitesEntryRipAccept OBJECT-TYPE
    SYNTAX     INTEGER
      {
        eNo (0),
        eYes (1)
      }
    MAX-ACCESS read-only
    STATUS     current
    DESCRIPTION
        "-- empty --"
    ::= { lcsStatusIpRouterRipDynWanSitesEntry 3 }

-- {COLUMN} 1712.1.10.19.14.1.4
lcsStatusIpRouterRipDynWanSitesEntryMasquerade OBJECT-TYPE
    SYNTAX     INTEGER
      {
        eAuto (0),
        eOn (1),
        eIntranet (2)
      }
    MAX-ACCESS read-only
    STATUS     current
    DESCRIPTION
        "-- empty --"
    ::= { lcsStatusIpRouterRipDynWanSitesEntry 4 }

-- {COLUMN} 1712.1.10.19.14.1.7
lcsStatusIpRouterRipDynWanSitesEntryPoisonedReverse OBJECT-TYPE
    SYNTAX     INTEGER
      {
        eNo (0),
        eYes (1)
      }
    MAX-ACCESS read-only
    STATUS     current
    DESCRIPTION
        "-- empty --"
    ::= { lcsStatusIpRouterRipDynWanSitesEntry 7 }

-- {COLUMN} 1712.1.10.19.14.1.8
lcsStatusIpRouterRipDynWanSitesEntryRfc2091 OBJECT-TYPE
    SYNTAX     INTEGER
      {
        eNo (0),
        eYes (1)
      }
    MAX-ACCESS read-only
    STATUS     current
    DESCRIPTION
        "-- empty --"
    ::= { lcsStatusIpRouterRipDynWanSitesEntry 8 }

-- {COLUMN} 1712.1.10.19.14.1.9
lcsStatusIpRouterRipDynWanSitesEntryGateway OBJECT-TYPE
    SYNTAX     IpAddress
    MAX-ACCESS read-only
    STATUS     current
    DESCRIPTION
        "-- empty --"
    ::= { lcsStatusIpRouterRipDynWanSitesEntry 9 }

-- {COLUMN} 1712.1.10.19.14.1.5
lcsStatusIpRouterRipDynWanSitesEntryDftRtgTag OBJECT-TYPE
    SYNTAX     INTEGER (0..65535)
    MAX-ACCESS read-only
    STATUS     current
    DESCRIPTION
        "-- empty --"
    ::= { lcsStatusIpRouterRipDynWanSitesEntry 5 }

-- {COLUMN} 1712.1.10.19.14.1.6
lcsStatusIpRouterRipDynWanSitesEntryRtgTagList OBJECT-TYPE
    SYNTAX     DisplayString (SIZE(0..33))
    MAX-ACCESS read-only
    STATUS     current
    DESCRIPTION
        "-- empty --"
    ::= { lcsStatusIpRouterRipDynWanSitesEntry 6 }

-- {COLUMN} 1712.1.10.19.14.1.10
lcsStatusIpRouterRipDynWanSitesEntryRxFilter OBJECT-TYPE
    SYNTAX     DisplayString (SIZE(0..16))
    MAX-ACCESS read-only
    STATUS     current
    DESCRIPTION
        "-- empty --"
    ::= { lcsStatusIpRouterRipDynWanSitesEntry 10 }

-- {COLUMN} 1712.1.10.19.14.1.11
lcsStatusIpRouterRipDynWanSitesEntryTxFilter OBJECT-TYPE
    SYNTAX     DisplayString (SIZE(0..16))
    MAX-ACCESS read-only
    STATUS     current
    DESCRIPTION
        "-- empty --"
    ::= { lcsStatusIpRouterRipDynWanSitesEntry 11 }

-- {TABLE} 1712.1.10.19.16
lcsStatusIpRouterRipWildcardSitesTable OBJECT-TYPE
    SYNTAX     SEQUENCE OF LcsStatusIpRouterRipWildcardSitesEntry
    MAX-ACCESS not-accessible
    STATUS     current
    DESCRIPTION
        "-- empty --"
    ::= { lcsStatusIpRouterRip 16 }

-- {ENTRY} 1712.1.10.19.16.1
lcsStatusIpRouterRipWildcardSitesEntry OBJECT-TYPE
    SYNTAX     LcsStatusIpRouterRipWildcardSitesEntry
    MAX-ACCESS not-accessible
    STATUS     current
    DESCRIPTION
        ""
    INDEX {
        lcsStatusIpRouterRipWildcardSitesEntryPeer
    }
    ::= { lcsStatusIpRouterRipWildcardSitesTable 1 }

-- {SEQUENCE}
LcsStatusIpRouterRipWildcardSitesEntry ::= SEQUENCE {
    lcsStatusIpRouterRipWildcardSitesEntryPeer DisplayString,
    lcsStatusIpRouterRipWildcardSitesEntryRipType INTEGER,
    lcsStatusIpRouterRipWildcardSitesEntryRipSend INTEGER,
    lcsStatusIpRouterRipWildcardSitesEntryRipAccept INTEGER,
    lcsStatusIpRouterRipWildcardSitesEntryMasquerade INTEGER,
    lcsStatusIpRouterRipWildcardSitesEntryPoisonedReverse INTEGER,
    lcsStatusIpRouterRipWildcardSitesEntryRfc2091 INTEGER,
    lcsStatusIpRouterRipWildcardSitesEntryGateway IpAddress,
    lcsStatusIpRouterRipWildcardSitesEntryDftRtgTag INTEGER,
    lcsStatusIpRouterRipWildcardSitesEntryRtgTagList DisplayString,
    lcsStatusIpRouterRipWildcardSitesEntryRxFilter DisplayString,
    lcsStatusIpRouterRipWildcardSitesEntryTxFilter DisplayString
}

-- {COLUMN} 1712.1.10.19.16.1.1
lcsStatusIpRouterRipWildcardSitesEntryPeer OBJECT-TYPE
    SYNTAX     DisplayString (SIZE(0..16))
    MAX-ACCESS read-only
    STATUS     current
    DESCRIPTION
        "-- empty --"
    ::= { lcsStatusIpRouterRipWildcardSitesEntry 1 }

-- {COLUMN} 1712.1.10.19.16.1.2
lcsStatusIpRouterRipWildcardSitesEntryRipType OBJECT-TYPE
    SYNTAX     INTEGER
      {
        eOff (0),
        eRip1 (1),
        eR1Comp (2),
        eRip2 (3)
      }
    MAX-ACCESS read-only
    STATUS     current
    DESCRIPTION
        "-- empty --"
    ::= { lcsStatusIpRouterRipWildcardSitesEntry 2 }

-- {COLUMN} 1712.1.10.19.16.1.12
lcsStatusIpRouterRipWildcardSitesEntryRipSend OBJECT-TYPE
    SYNTAX     INTEGER
      {
        eNo (0),
        eYes (1)
      }
    MAX-ACCESS read-only
    STATUS     current
    DESCRIPTION
        "-- empty --"
    ::= { lcsStatusIpRouterRipWildcardSitesEntry 12 }

-- {COLUMN} 1712.1.10.19.16.1.3
lcsStatusIpRouterRipWildcardSitesEntryRipAccept OBJECT-TYPE
    SYNTAX     INTEGER
      {
        eNo (0),
        eYes (1)
      }
    MAX-ACCESS read-only
    STATUS     current
    DESCRIPTION
        "-- empty --"
    ::= { lcsStatusIpRouterRipWildcardSitesEntry 3 }

-- {COLUMN} 1712.1.10.19.16.1.4
lcsStatusIpRouterRipWildcardSitesEntryMasquerade OBJECT-TYPE
    SYNTAX     INTEGER
      {
        eAuto (0),
        eOn (1),
        eIntranet (2)
      }
    MAX-ACCESS read-only
    STATUS     current
    DESCRIPTION
        "-- empty --"
    ::= { lcsStatusIpRouterRipWildcardSitesEntry 4 }

-- {COLUMN} 1712.1.10.19.16.1.7
lcsStatusIpRouterRipWildcardSitesEntryPoisonedReverse OBJECT-TYPE
    SYNTAX     INTEGER
      {
        eNo (0),
        eYes (1)
      }
    MAX-ACCESS read-only
    STATUS     current
    DESCRIPTION
        "-- empty --"
    ::= { lcsStatusIpRouterRipWildcardSitesEntry 7 }

-- {COLUMN} 1712.1.10.19.16.1.8
lcsStatusIpRouterRipWildcardSitesEntryRfc2091 OBJECT-TYPE
    SYNTAX     INTEGER
      {
        eNo (0),
        eYes (1)
      }
    MAX-ACCESS read-only
    STATUS     current
    DESCRIPTION
        "-- empty --"
    ::= { lcsStatusIpRouterRipWildcardSitesEntry 8 }

-- {COLUMN} 1712.1.10.19.16.1.9
lcsStatusIpRouterRipWildcardSitesEntryGateway OBJECT-TYPE
    SYNTAX     IpAddress
    MAX-ACCESS read-only
    STATUS     current
    DESCRIPTION
        "-- empty --"
    ::= { lcsStatusIpRouterRipWildcardSitesEntry 9 }

-- {COLUMN} 1712.1.10.19.16.1.5
lcsStatusIpRouterRipWildcardSitesEntryDftRtgTag OBJECT-TYPE
    SYNTAX     INTEGER (0..65535)
    MAX-ACCESS read-only
    STATUS     current
    DESCRIPTION
        "-- empty --"
    ::= { lcsStatusIpRouterRipWildcardSitesEntry 5 }

-- {COLUMN} 1712.1.10.19.16.1.6
lcsStatusIpRouterRipWildcardSitesEntryRtgTagList OBJECT-TYPE
    SYNTAX     DisplayString (SIZE(0..33))
    MAX-ACCESS read-only
    STATUS     current
    DESCRIPTION
        "-- empty --"
    ::= { lcsStatusIpRouterRipWildcardSitesEntry 6 }

-- {COLUMN} 1712.1.10.19.16.1.10
lcsStatusIpRouterRipWildcardSitesEntryRxFilter OBJECT-TYPE
    SYNTAX     DisplayString (SIZE(0..16))
    MAX-ACCESS read-only
    STATUS     current
    DESCRIPTION
        "-- empty --"
    ::= { lcsStatusIpRouterRipWildcardSitesEntry 10 }

-- {COLUMN} 1712.1.10.19.16.1.11
lcsStatusIpRouterRipWildcardSitesEntryTxFilter OBJECT-TYPE
    SYNTAX     DisplayString (SIZE(0..16))
    MAX-ACCESS read-only
    STATUS     current
    DESCRIPTION
        "-- empty --"
    ::= { lcsStatusIpRouterRipWildcardSitesEntry 11 }

-- {TABLE} 1712.1.10.19.15
lcsStatusIpRouterRipFilterTable OBJECT-TYPE
    SYNTAX     SEQUENCE OF LcsStatusIpRouterRipFilterEntry
    MAX-ACCESS not-accessible
    STATUS     current
    DESCRIPTION
        "-- empty --"
    ::= { lcsStatusIpRouterRip 15 }

-- {ENTRY} 1712.1.10.19.15.1
lcsStatusIpRouterRipFilterEntry OBJECT-TYPE
    SYNTAX     LcsStatusIpRouterRipFilterEntry
    MAX-ACCESS not-accessible
    STATUS     current
    DESCRIPTION
        ""
    INDEX {
        lcsStatusIpRouterRipFilterEntryIdx
    }
    ::= { lcsStatusIpRouterRipFilterTable 1 }

-- {SEQUENCE}
LcsStatusIpRouterRipFilterEntry ::= SEQUENCE {
    lcsStatusIpRouterRipFilterEntryIdx INTEGER,
    lcsStatusIpRouterRipFilterEntryName DisplayString,
    lcsStatusIpRouterRipFilterEntryIpAddress IpAddress,
    lcsStatusIpRouterRipFilterEntryIpNetmask IpAddress,
    lcsStatusIpRouterRipFilterEntryType INTEGER
}

-- {COLUMN} 1712.1.10.19.15.1.1
lcsStatusIpRouterRipFilterEntryIdx OBJECT-TYPE
    SYNTAX     INTEGER (0..65535)
    MAX-ACCESS read-only
    STATUS     current
    DESCRIPTION
        "-- empty --"
    ::= { lcsStatusIpRouterRipFilterEntry 1 }

-- {COLUMN} 1712.1.10.19.15.1.3
lcsStatusIpRouterRipFilterEntryName OBJECT-TYPE
    SYNTAX     DisplayString (SIZE(0..255))
    MAX-ACCESS read-only
    STATUS     current
    DESCRIPTION
        "-- empty --"
    ::= { lcsStatusIpRouterRipFilterEntry 3 }

-- {COLUMN} 1712.1.10.19.15.1.4
lcsStatusIpRouterRipFilterEntryIpAddress OBJECT-TYPE
    SYNTAX     IpAddress
    MAX-ACCESS read-only
    STATUS     current
    DESCRIPTION
        "-- empty --"
    ::= { lcsStatusIpRouterRipFilterEntry 4 }

-- {COLUMN} 1712.1.10.19.15.1.5
lcsStatusIpRouterRipFilterEntryIpNetmask OBJECT-TYPE
    SYNTAX     IpAddress
    MAX-ACCESS read-only
    STATUS     current
    DESCRIPTION
        "-- empty --"
    ::= { lcsStatusIpRouterRipFilterEntry 5 }

-- {COLUMN} 1712.1.10.19.15.1.2
lcsStatusIpRouterRipFilterEntryType OBJECT-TYPE
    SYNTAX     INTEGER
      {
        eUnknown (0),
        ePositive (1),
        eNegative (2)
      }
    MAX-ACCESS read-only
    STATUS     current
    DESCRIPTION
        "-- empty --"
    ::= { lcsStatusIpRouterRipFilterEntry 2 }

-- {SCALAR} 1712.1.10.20
lcsStatusIpRouterDeleteValues OBJECT-TYPE
    SYNTAX     DisplayString
    MAX-ACCESS read-write
    STATUS     current
    DESCRIPTION
        "-- empty --"
    ::= { lcsStatusIpRouter 20 }

-- {TABLE} 1712.1.10.21
lcsStatusIpRouterServiceTableTable OBJECT-TYPE
    SYNTAX     SEQUENCE OF LcsStatusIpRouterServiceTableEntry
    MAX-ACCESS not-accessible
    STATUS     current
    DESCRIPTION
        "-- empty --"
    ::= { lcsStatusIpRouter 21 }

-- {ENTRY} 1712.1.10.21.1
lcsStatusIpRouterServiceTableEntry OBJECT-TYPE
    SYNTAX     LcsStatusIpRouterServiceTableEntry
    MAX-ACCESS not-accessible
    STATUS     current
    DESCRIPTION
        ""
    INDEX {
        lcsStatusIpRouterServiceTableEntryService
    }
    ::= { lcsStatusIpRouterServiceTableTable 1 }

-- {SEQUENCE}
LcsStatusIpRouterServiceTableEntry ::= SEQUENCE {
    lcsStatusIpRouterServiceTableEntryService INTEGER,
    lcsStatusIpRouterServiceTableEntryPacketRx Counter32,
    lcsStatusIpRouterServiceTableEntryPacketTx Counter32,
    lcsStatusIpRouterServiceTableEntryPacketRel DisplayString,
    lcsStatusIpRouterServiceTableEntryKbytesRx Counter32,
    lcsStatusIpRouterServiceTableEntryKbytesTx Counter32,
    lcsStatusIpRouterServiceTableEntryKbytesRel DisplayString
}

-- {COLUMN} 1712.1.10.21.1.1
lcsStatusIpRouterServiceTableEntryService OBJECT-TYPE
    SYNTAX     INTEGER
      {
        eIcmp (1),
        eFtp (2),
        eHttp (3),
        eSmtp (4),
        eDns (5),
        eTelnet (6),
        eTftp (7),
        eDhcp (8),
        ePop3 (9),
        eNetbios (10),
        eImap2 (11),
        eNews (12),
        eIrc (13),
        eSnmp (14),
        eOther (15),
        eTotal (16)
      }
    MAX-ACCESS read-only
    STATUS     current
    DESCRIPTION
        "-- empty --"
    ::= { lcsStatusIpRouterServiceTableEntry 1 }

-- {COLUMN} 1712.1.10.21.1.2
lcsStatusIpRouterServiceTableEntryPacketRx OBJECT-TYPE
    SYNTAX     Counter32
    MAX-ACCESS read-only
    STATUS     current
    DESCRIPTION
        "-- empty --"
    ::= { lcsStatusIpRouterServiceTableEntry 2 }

-- {COLUMN} 1712.1.10.21.1.3
lcsStatusIpRouterServiceTableEntryPacketTx OBJECT-TYPE
    SYNTAX     Counter32
    MAX-ACCESS read-only
    STATUS     current
    DESCRIPTION
        "-- empty --"
    ::= { lcsStatusIpRouterServiceTableEntry 3 }

-- {COLUMN} 1712.1.10.21.1.4
lcsStatusIpRouterServiceTableEntryPacketRel OBJECT-TYPE
    SYNTAX     DisplayString (SIZE(0..255))
    MAX-ACCESS read-only
    STATUS     current
    DESCRIPTION
        "-- empty --"
    ::= { lcsStatusIpRouterServiceTableEntry 4 }

-- {COLUMN} 1712.1.10.21.1.5
lcsStatusIpRouterServiceTableEntryKbytesRx OBJECT-TYPE
    SYNTAX     Counter32
    MAX-ACCESS read-only
    STATUS     current
    DESCRIPTION
        "-- empty --"
    ::= { lcsStatusIpRouterServiceTableEntry 5 }

-- {COLUMN} 1712.1.10.21.1.6
lcsStatusIpRouterServiceTableEntryKbytesTx OBJECT-TYPE
    SYNTAX     Counter32
    MAX-ACCESS read-only
    STATUS     current
    DESCRIPTION
        "-- empty --"
    ::= { lcsStatusIpRouterServiceTableEntry 6 }

-- {COLUMN} 1712.1.10.21.1.7
lcsStatusIpRouterServiceTableEntryKbytesRel OBJECT-TYPE
    SYNTAX     DisplayString (SIZE(0..255))
    MAX-ACCESS read-only
    STATUS     current
    DESCRIPTION
        "-- empty --"
    ::= { lcsStatusIpRouterServiceTableEntry 7 }

-- {TABLE} 1712.1.10.22
lcsStatusIpRouterFilterListTable OBJECT-TYPE
    SYNTAX     SEQUENCE OF LcsStatusIpRouterFilterListEntry
    MAX-ACCESS not-accessible
    STATUS     current
    DESCRIPTION
        "-- empty --"
    ::= { lcsStatusIpRouter 22 }

-- {ENTRY} 1712.1.10.22.1
lcsStatusIpRouterFilterListEntry OBJECT-TYPE
    SYNTAX     LcsStatusIpRouterFilterListEntry
    MAX-ACCESS not-accessible
    STATUS     current
    DESCRIPTION
        ""
    INDEX {
        lcsStatusIpRouterFilterListEntryIdx
    }
    ::= { lcsStatusIpRouterFilterListTable 1 }

-- {SEQUENCE}
LcsStatusIpRouterFilterListEntry ::= SEQUENCE {
    lcsStatusIpRouterFilterListEntryIdx INTEGER,
    lcsStatusIpRouterFilterListEntryProt INTEGER,
    lcsStatusIpRouterFilterListEntrySrcMac DisplayString,
    lcsStatusIpRouterFilterListEntrySrcAddress IpAddress,
    lcsStatusIpRouterFilterListEntrySrcNetmask IpAddress,
    lcsStatusIpRouterFilterListEntrySSt INTEGER,
    lcsStatusIpRouterFilterListEntrySEnd INTEGER,
    lcsStatusIpRouterFilterListEntryDstMac DisplayString,
    lcsStatusIpRouterFilterListEntryDstAddress IpAddress,
    lcsStatusIpRouterFilterListEntryDstNetmask IpAddress,
    lcsStatusIpRouterFilterListEntryDSt INTEGER,
    lcsStatusIpRouterFilterListEntryDEnd INTEGER,
    lcsStatusIpRouterFilterListEntryAction DisplayString,
    lcsStatusIpRouterFilterListEntryLinked INTEGER,
    lcsStatusIpRouterFilterListEntryPrio INTEGER,
    lcsStatusIpRouterFilterListEntrySrcTag INTEGER,
    lcsStatusIpRouterFilterListEntryRtgTag INTEGER
}

-- {COLUMN} 1712.1.10.22.1.1
lcsStatusIpRouterFilterListEntryIdx OBJECT-TYPE
    SYNTAX     INTEGER (0..2147483647)
    MAX-ACCESS read-only
    STATUS     current
    DESCRIPTION
        "-- empty --"
    ::= { lcsStatusIpRouterFilterListEntry 1 }

-- {COLUMN} 1712.1.10.22.1.2
lcsStatusIpRouterFilterListEntryProt OBJECT-TYPE
    SYNTAX     INTEGER (0..255)
    MAX-ACCESS read-only
    STATUS     current
    DESCRIPTION
        "-- empty --"
    ::= { lcsStatusIpRouterFilterListEntry 2 }

-- {COLUMN} 1712.1.10.22.1.13
lcsStatusIpRouterFilterListEntrySrcMac OBJECT-TYPE
    SYNTAX     DisplayString (SIZE(0..255))
    MAX-ACCESS read-only
    STATUS     current
    DESCRIPTION
        "-- empty --"
    ::= { lcsStatusIpRouterFilterListEntry 13 }

-- {COLUMN} 1712.1.10.22.1.3
lcsStatusIpRouterFilterListEntrySrcAddress OBJECT-TYPE
    SYNTAX     IpAddress
    MAX-ACCESS read-only
    STATUS     current
    DESCRIPTION
        "-- empty --"
    ::= { lcsStatusIpRouterFilterListEntry 3 }

-- {COLUMN} 1712.1.10.22.1.4
lcsStatusIpRouterFilterListEntrySrcNetmask OBJECT-TYPE
    SYNTAX     IpAddress
    MAX-ACCESS read-only
    STATUS     current
    DESCRIPTION
        "-- empty --"
    ::= { lcsStatusIpRouterFilterListEntry 4 }

-- {COLUMN} 1712.1.10.22.1.5
lcsStatusIpRouterFilterListEntrySSt OBJECT-TYPE
    SYNTAX     INTEGER (0..65535)
    MAX-ACCESS read-only
    STATUS     current
    DESCRIPTION
        "-- empty --"
    ::= { lcsStatusIpRouterFilterListEntry 5 }

-- {COLUMN} 1712.1.10.22.1.6
lcsStatusIpRouterFilterListEntrySEnd OBJECT-TYPE
    SYNTAX     INTEGER (0..65535)
    MAX-ACCESS read-only
    STATUS     current
    DESCRIPTION
        "-- empty --"
    ::= { lcsStatusIpRouterFilterListEntry 6 }

-- {COLUMN} 1712.1.10.22.1.14
lcsStatusIpRouterFilterListEntryDstMac OBJECT-TYPE
    SYNTAX     DisplayString (SIZE(0..255))
    MAX-ACCESS read-only
    STATUS     current
    DESCRIPTION
        "-- empty --"
    ::= { lcsStatusIpRouterFilterListEntry 14 }

-- {COLUMN} 1712.1.10.22.1.7
lcsStatusIpRouterFilterListEntryDstAddress OBJECT-TYPE
    SYNTAX     IpAddress
    MAX-ACCESS read-only
    STATUS     current
    DESCRIPTION
        "-- empty --"
    ::= { lcsStatusIpRouterFilterListEntry 7 }

-- {COLUMN} 1712.1.10.22.1.8
lcsStatusIpRouterFilterListEntryDstNetmask OBJECT-TYPE
    SYNTAX     IpAddress
    MAX-ACCESS read-only
    STATUS     current
    DESCRIPTION
        "-- empty --"
    ::= { lcsStatusIpRouterFilterListEntry 8 }

-- {COLUMN} 1712.1.10.22.1.9
lcsStatusIpRouterFilterListEntryDSt OBJECT-TYPE
    SYNTAX     INTEGER (0..65535)
    MAX-ACCESS read-only
    STATUS     current
    DESCRIPTION
        "-- empty --"
    ::= { lcsStatusIpRouterFilterListEntry 9 }

-- {COLUMN} 1712.1.10.22.1.10
lcsStatusIpRouterFilterListEntryDEnd OBJECT-TYPE
    SYNTAX     INTEGER (0..65535)
    MAX-ACCESS read-only
    STATUS     current
    DESCRIPTION
        "-- empty --"
    ::= { lcsStatusIpRouterFilterListEntry 10 }

-- {COLUMN} 1712.1.10.22.1.11
lcsStatusIpRouterFilterListEntryAction OBJECT-TYPE
    SYNTAX     DisplayString (SIZE(0..255))
    MAX-ACCESS read-only
    STATUS     current
    DESCRIPTION
        "-- empty --"
    ::= { lcsStatusIpRouterFilterListEntry 11 }

-- {COLUMN} 1712.1.10.22.1.15
lcsStatusIpRouterFilterListEntryLinked OBJECT-TYPE
    SYNTAX     INTEGER
      {
        eNo (0),
        eYes (1)
      }
    MAX-ACCESS read-only
    STATUS     current
    DESCRIPTION
        "-- empty --"
    ::= { lcsStatusIpRouterFilterListEntry 15 }

-- {COLUMN} 1712.1.10.22.1.16
lcsStatusIpRouterFilterListEntryPrio OBJECT-TYPE
    SYNTAX     INTEGER (0..65535)
    MAX-ACCESS read-only
    STATUS     current
    DESCRIPTION
        "-- empty --"
    ::= { lcsStatusIpRouterFilterListEntry 16 }

-- {COLUMN} 1712.1.10.22.1.18
lcsStatusIpRouterFilterListEntrySrcTag OBJECT-TYPE
    SYNTAX     INTEGER (0..65535)
    MAX-ACCESS read-only
    STATUS     current
    DESCRIPTION
        "-- empty --"
    ::= { lcsStatusIpRouterFilterListEntry 18 }

-- {COLUMN} 1712.1.10.22.1.17
lcsStatusIpRouterFilterListEntryRtgTag OBJECT-TYPE
    SYNTAX     INTEGER (0..65535)
    MAX-ACCESS read-only
    STATUS     current
    DESCRIPTION
        "-- empty --"
    ::= { lcsStatusIpRouterFilterListEntry 17 }

-- {TABLE} 1712.1.10.23
lcsStatusIpRouterConnectionListTable OBJECT-TYPE
    SYNTAX     SEQUENCE OF LcsStatusIpRouterConnectionListEntry
    MAX-ACCESS not-accessible
    STATUS     current
    DESCRIPTION
        "-- empty --"
    ::= { lcsStatusIpRouter 23 }

-- {ENTRY} 1712.1.10.23.1
lcsStatusIpRouterConnectionListEntry OBJECT-TYPE
    SYNTAX     LcsStatusIpRouterConnectionListEntry
    MAX-ACCESS not-accessible
    STATUS     current
    DESCRIPTION
        ""
    INDEX {
        lcsStatusIpRouterConnectionListEntrySrcAddress,
        lcsStatusIpRouterConnectionListEntryDstAddress,
        lcsStatusIpRouterConnectionListEntryProt,
        lcsStatusIpRouterConnectionListEntrySrcPort,
        lcsStatusIpRouterConnectionListEntryDstPort
    }
    ::= { lcsStatusIpRouterConnectionListTable 1 }

-- {SEQUENCE}
LcsStatusIpRouterConnectionListEntry ::= SEQUENCE {
    lcsStatusIpRouterConnectionListEntrySrcAddress IpAddress,
    lcsStatusIpRouterConnectionListEntryDstAddress IpAddress,
    lcsStatusIpRouterConnectionListEntryProt INTEGER,
    lcsStatusIpRouterConnectionListEntrySrcPort INTEGER,
    lcsStatusIpRouterConnectionListEntryDstPort INTEGER,
    lcsStatusIpRouterConnectionListEntryRtgTag INTEGER,
    lcsStatusIpRouterConnectionListEntryTimeout INTEGER,
    lcsStatusIpRouterConnectionListEntryFlags INTEGER,
    lcsStatusIpRouterConnectionListEntryFilterRule DisplayString,
    lcsStatusIpRouterConnectionListEntrySrcRoute DisplayString,
    lcsStatusIpRouterConnectionListEntryDestRoute DisplayString
}

-- {COLUMN} 1712.1.10.23.1.1
lcsStatusIpRouterConnectionListEntrySrcAddress OBJECT-TYPE
    SYNTAX     IpAddress
    MAX-ACCESS read-only
    STATUS     current
    DESCRIPTION
        "-- empty --"
    ::= { lcsStatusIpRouterConnectionListEntry 1 }

-- {COLUMN} 1712.1.10.23.1.2
lcsStatusIpRouterConnectionListEntryDstAddress OBJECT-TYPE
    SYNTAX     IpAddress
    MAX-ACCESS read-only
    STATUS     current
    DESCRIPTION
        "-- empty --"
    ::= { lcsStatusIpRouterConnectionListEntry 2 }

-- {COLUMN} 1712.1.10.23.1.3
lcsStatusIpRouterConnectionListEntryProt OBJECT-TYPE
    SYNTAX     INTEGER (0..255)
    MAX-ACCESS read-only
    STATUS     current
    DESCRIPTION
        "-- empty --"
    ::= { lcsStatusIpRouterConnectionListEntry 3 }

-- {COLUMN} 1712.1.10.23.1.4
lcsStatusIpRouterConnectionListEntrySrcPort OBJECT-TYPE
    SYNTAX     INTEGER (0..65535)
    MAX-ACCESS read-only
    STATUS     current
    DESCRIPTION
        "-- empty --"
    ::= { lcsStatusIpRouterConnectionListEntry 4 }

-- {COLUMN} 1712.1.10.23.1.5
lcsStatusIpRouterConnectionListEntryDstPort OBJECT-TYPE
    SYNTAX     INTEGER (0..65535)
    MAX-ACCESS read-only
    STATUS     current
    DESCRIPTION
        "-- empty --"
    ::= { lcsStatusIpRouterConnectionListEntry 5 }

-- {COLUMN} 1712.1.10.23.1.11
lcsStatusIpRouterConnectionListEntryRtgTag OBJECT-TYPE
    SYNTAX     INTEGER (0..65535)
    MAX-ACCESS read-only
    STATUS     current
    DESCRIPTION
        "-- empty --"
    ::= { lcsStatusIpRouterConnectionListEntry 11 }

-- {COLUMN} 1712.1.10.23.1.6
lcsStatusIpRouterConnectionListEntryTimeout OBJECT-TYPE
    SYNTAX     INTEGER (0..65535)
    MAX-ACCESS read-only
    STATUS     current
    DESCRIPTION
        "-- empty --"
    ::= { lcsStatusIpRouterConnectionListEntry 6 }

-- {COLUMN} 1712.1.10.23.1.7
lcsStatusIpRouterConnectionListEntryFlags OBJECT-TYPE
    SYNTAX     INTEGER (0..2147483647)
    MAX-ACCESS read-only
    STATUS     current
    DESCRIPTION
        "-- empty --"
    ::= { lcsStatusIpRouterConnectionListEntry 7 }

-- {COLUMN} 1712.1.10.23.1.8
lcsStatusIpRouterConnectionListEntryFilterRule OBJECT-TYPE
    SYNTAX     DisplayString (SIZE(0..255))
    MAX-ACCESS read-only
    STATUS     current
    DESCRIPTION
        "-- empty --"
    ::= { lcsStatusIpRouterConnectionListEntry 8 }

-- {COLUMN} 1712.1.10.23.1.9
lcsStatusIpRouterConnectionListEntrySrcRoute OBJECT-TYPE
    SYNTAX     DisplayString (SIZE(0..255))
    MAX-ACCESS read-only
    STATUS     current
    DESCRIPTION
        "-- empty --"
    ::= { lcsStatusIpRouterConnectionListEntry 9 }

-- {COLUMN} 1712.1.10.23.1.10
lcsStatusIpRouterConnectionListEntryDestRoute OBJECT-TYPE
    SYNTAX     DisplayString (SIZE(0..255))
    MAX-ACCESS read-only
    STATUS     current
    DESCRIPTION
        "-- empty --"
    ::= { lcsStatusIpRouterConnectionListEntry 10 }

-- {TABLE} 1712.1.10.29
lcsStatusIpRouterOpenPortListTable OBJECT-TYPE
    SYNTAX     SEQUENCE OF LcsStatusIpRouterOpenPortListEntry
    MAX-ACCESS not-accessible
    STATUS     current
    DESCRIPTION
        "-- empty --"
    ::= { lcsStatusIpRouter 29 }

-- {ENTRY} 1712.1.10.29.1
lcsStatusIpRouterOpenPortListEntry OBJECT-TYPE
    SYNTAX     LcsStatusIpRouterOpenPortListEntry
    MAX-ACCESS not-accessible
    STATUS     current
    DESCRIPTION
        ""
    INDEX {
        lcsStatusIpRouterOpenPortListEntrySrcAddress,
        lcsStatusIpRouterOpenPortListEntryDstAddress,
        lcsStatusIpRouterOpenPortListEntryProt,
        lcsStatusIpRouterOpenPortListEntryDstPort
    }
    ::= { lcsStatusIpRouterOpenPortListTable 1 }

-- {SEQUENCE}
LcsStatusIpRouterOpenPortListEntry ::= SEQUENCE {
    lcsStatusIpRouterOpenPortListEntrySrcAddress IpAddress,
    lcsStatusIpRouterOpenPortListEntryDstAddress IpAddress,
    lcsStatusIpRouterOpenPortListEntryProt INTEGER,
    lcsStatusIpRouterOpenPortListEntryDstPort INTEGER,
    lcsStatusIpRouterOpenPortListEntryTimeout INTEGER,
    lcsStatusIpRouterOpenPortListEntryFilterRule DisplayString,
    lcsStatusIpRouterOpenPortListEntrySrcRoute DisplayString
}

-- {COLUMN} 1712.1.10.29.1.1
lcsStatusIpRouterOpenPortListEntrySrcAddress OBJECT-TYPE
    SYNTAX     IpAddress
    MAX-ACCESS read-only
    STATUS     current
    DESCRIPTION
        "-- empty --"
    ::= { lcsStatusIpRouterOpenPortListEntry 1 }

-- {COLUMN} 1712.1.10.29.1.2
lcsStatusIpRouterOpenPortListEntryDstAddress OBJECT-TYPE
    SYNTAX     IpAddress
    MAX-ACCESS read-only
    STATUS     current
    DESCRIPTION
        "-- empty --"
    ::= { lcsStatusIpRouterOpenPortListEntry 2 }

-- {COLUMN} 1712.1.10.29.1.3
lcsStatusIpRouterOpenPortListEntryProt OBJECT-TYPE
    SYNTAX     INTEGER (0..255)
    MAX-ACCESS read-only
    STATUS     current
    DESCRIPTION
        "-- empty --"
    ::= { lcsStatusIpRouterOpenPortListEntry 3 }

-- {COLUMN} 1712.1.10.29.1.5
lcsStatusIpRouterOpenPortListEntryDstPort OBJECT-TYPE
    SYNTAX     INTEGER (0..65535)
    MAX-ACCESS read-only
    STATUS     current
    DESCRIPTION
        "-- empty --"
    ::= { lcsStatusIpRouterOpenPortListEntry 5 }

-- {COLUMN} 1712.1.10.29.1.6
lcsStatusIpRouterOpenPortListEntryTimeout OBJECT-TYPE
    SYNTAX     INTEGER (0..65535)
    MAX-ACCESS read-only
    STATUS     current
    DESCRIPTION
        "-- empty --"
    ::= { lcsStatusIpRouterOpenPortListEntry 6 }

-- {COLUMN} 1712.1.10.29.1.8
lcsStatusIpRouterOpenPortListEntryFilterRule OBJECT-TYPE
    SYNTAX     DisplayString (SIZE(0..255))
    MAX-ACCESS read-only
    STATUS     current
    DESCRIPTION
        "-- empty --"
    ::= { lcsStatusIpRouterOpenPortListEntry 8 }

-- {COLUMN} 1712.1.10.29.1.9
lcsStatusIpRouterOpenPortListEntrySrcRoute OBJECT-TYPE
    SYNTAX     DisplayString (SIZE(0..255))
    MAX-ACCESS read-only
    STATUS     current
    DESCRIPTION
        "-- empty --"
    ::= { lcsStatusIpRouterOpenPortListEntry 9 }

-- {TABLE} 1712.1.10.24
lcsStatusIpRouterHostBlockListTable OBJECT-TYPE
    SYNTAX     SEQUENCE OF LcsStatusIpRouterHostBlockListEntry
    MAX-ACCESS not-accessible
    STATUS     current
    DESCRIPTION
        "-- empty --"
    ::= { lcsStatusIpRouter 24 }

-- {ENTRY} 1712.1.10.24.1
lcsStatusIpRouterHostBlockListEntry OBJECT-TYPE
    SYNTAX     LcsStatusIpRouterHostBlockListEntry
    MAX-ACCESS not-accessible
    STATUS     current
    DESCRIPTION
        ""
    INDEX {
        lcsStatusIpRouterHostBlockListEntrySrcAddress
    }
    ::= { lcsStatusIpRouterHostBlockListTable 1 }

-- {SEQUENCE}
LcsStatusIpRouterHostBlockListEntry ::= SEQUENCE {
    lcsStatusIpRouterHostBlockListEntrySrcAddress IpAddress,
    lcsStatusIpRouterHostBlockListEntryTimeout INTEGER,
    lcsStatusIpRouterHostBlockListEntryFilterRule DisplayString
}

-- {COLUMN} 1712.1.10.24.1.1
lcsStatusIpRouterHostBlockListEntrySrcAddress OBJECT-TYPE
    SYNTAX     IpAddress
    MAX-ACCESS read-only
    STATUS     current
    DESCRIPTION
        "-- empty --"
    ::= { lcsStatusIpRouterHostBlockListEntry 1 }

-- {COLUMN} 1712.1.10.24.1.2
lcsStatusIpRouterHostBlockListEntryTimeout OBJECT-TYPE
    SYNTAX     INTEGER (0..2147483647)
    MAX-ACCESS read-only
    STATUS     current
    DESCRIPTION
        "-- empty --"
    ::= { lcsStatusIpRouterHostBlockListEntry 2 }

-- {COLUMN} 1712.1.10.24.1.3
lcsStatusIpRouterHostBlockListEntryFilterRule OBJECT-TYPE
    SYNTAX     DisplayString (SIZE(0..255))
    MAX-ACCESS read-only
    STATUS     current
    DESCRIPTION
        "-- empty --"
    ::= { lcsStatusIpRouterHostBlockListEntry 3 }

-- {TABLE} 1712.1.10.25
lcsStatusIpRouterPortBlockListTable OBJECT-TYPE
    SYNTAX     SEQUENCE OF LcsStatusIpRouterPortBlockListEntry
    MAX-ACCESS not-accessible
    STATUS     current
    DESCRIPTION
        "-- empty --"
    ::= { lcsStatusIpRouter 25 }

-- {ENTRY} 1712.1.10.25.1
lcsStatusIpRouterPortBlockListEntry OBJECT-TYPE
    SYNTAX     LcsStatusIpRouterPortBlockListEntry
    MAX-ACCESS not-accessible
    STATUS     current
    DESCRIPTION
        ""
    INDEX {
        lcsStatusIpRouterPortBlockListEntryDstAddress
    }
    ::= { lcsStatusIpRouterPortBlockListTable 1 }

-- {SEQUENCE}
LcsStatusIpRouterPortBlockListEntry ::= SEQUENCE {
    lcsStatusIpRouterPortBlockListEntryDstAddress IpAddress,
    lcsStatusIpRouterPortBlockListEntryProt INTEGER,
    lcsStatusIpRouterPortBlockListEntryDstPort INTEGER,
    lcsStatusIpRouterPortBlockListEntryTimeout INTEGER,
    lcsStatusIpRouterPortBlockListEntryFilterRule DisplayString
}

-- {COLUMN} 1712.1.10.25.1.1
lcsStatusIpRouterPortBlockListEntryDstAddress OBJECT-TYPE
    SYNTAX     IpAddress
    MAX-ACCESS read-only
    STATUS     current
    DESCRIPTION
        "-- empty --"
    ::= { lcsStatusIpRouterPortBlockListEntry 1 }

-- {COLUMN} 1712.1.10.25.1.2
lcsStatusIpRouterPortBlockListEntryProt OBJECT-TYPE
    SYNTAX     INTEGER (0..65535)
    MAX-ACCESS read-only
    STATUS     current
    DESCRIPTION
        "-- empty --"
    ::= { lcsStatusIpRouterPortBlockListEntry 2 }

-- {COLUMN} 1712.1.10.25.1.3
lcsStatusIpRouterPortBlockListEntryDstPort OBJECT-TYPE
    SYNTAX     INTEGER (0..65535)
    MAX-ACCESS read-only
    STATUS     current
    DESCRIPTION
        "-- empty --"
    ::= { lcsStatusIpRouterPortBlockListEntry 3 }

-- {COLUMN} 1712.1.10.25.1.4
lcsStatusIpRouterPortBlockListEntryTimeout OBJECT-TYPE
    SYNTAX     INTEGER (0..2147483647)
    MAX-ACCESS read-only
    STATUS     current
    DESCRIPTION
        "-- empty --"
    ::= { lcsStatusIpRouterPortBlockListEntry 4 }

-- {COLUMN} 1712.1.10.25.1.5
lcsStatusIpRouterPortBlockListEntryFilterRule OBJECT-TYPE
    SYNTAX     DisplayString (SIZE(0..255))
    MAX-ACCESS read-only
    STATUS     current
    DESCRIPTION
        "-- empty --"
    ::= { lcsStatusIpRouterPortBlockListEntry 5 }

-- {TABLE} 1712.1.10.26
lcsStatusIpRouterLogTableTable OBJECT-TYPE
    SYNTAX     SEQUENCE OF LcsStatusIpRouterLogTableEntry
    MAX-ACCESS not-accessible
    STATUS     current
    DESCRIPTION
        "-- empty --"
    ::= { lcsStatusIpRouter 26 }

-- {ENTRY} 1712.1.10.26.1
lcsStatusIpRouterLogTableEntry OBJECT-TYPE
    SYNTAX     LcsStatusIpRouterLogTableEntry
    MAX-ACCESS not-accessible
    STATUS     current
    DESCRIPTION
        ""
    INDEX {
        lcsStatusIpRouterLogTableEntryIdx
    }
    ::= { lcsStatusIpRouterLogTableTable 1 }

-- {SEQUENCE}
LcsStatusIpRouterLogTableEntry ::= SEQUENCE {
    lcsStatusIpRouterLogTableEntryIdx INTEGER,
    lcsStatusIpRouterLogTableEntrySystemTime DisplayString,
    lcsStatusIpRouterLogTableEntrySrcAddress IpAddress,
    lcsStatusIpRouterLogTableEntryDstAddress IpAddress,
    lcsStatusIpRouterLogTableEntryProt INTEGER,
    lcsStatusIpRouterLogTableEntrySrcPort INTEGER,
    lcsStatusIpRouterLogTableEntryDstPort INTEGER,
    lcsStatusIpRouterLogTableEntryFilterRule DisplayString,
    lcsStatusIpRouterLogTableEntryLimit INTEGER,
    lcsStatusIpRouterLogTableEntryThreshold INTEGER,
    lcsStatusIpRouterLogTableEntryAction INTEGER
}

-- {COLUMN} 1712.1.10.26.1.1
lcsStatusIpRouterLogTableEntryIdx OBJECT-TYPE
    SYNTAX     INTEGER (0..65535)
    MAX-ACCESS read-only
    STATUS     current
    DESCRIPTION
        "-- empty --"
    ::= { lcsStatusIpRouterLogTableEntry 1 }

-- {COLUMN} 1712.1.10.26.1.2
lcsStatusIpRouterLogTableEntrySystemTime OBJECT-TYPE
    SYNTAX     DisplayString (SIZE(0..19))
    MAX-ACCESS read-only
    STATUS     current
    DESCRIPTION
        "-- empty --"
    ::= { lcsStatusIpRouterLogTableEntry 2 }

-- {COLUMN} 1712.1.10.26.1.3
lcsStatusIpRouterLogTableEntrySrcAddress OBJECT-TYPE
    SYNTAX     IpAddress
    MAX-ACCESS read-only
    STATUS     current
    DESCRIPTION
        "-- empty --"
    ::= { lcsStatusIpRouterLogTableEntry 3 }

-- {COLUMN} 1712.1.10.26.1.4
lcsStatusIpRouterLogTableEntryDstAddress OBJECT-TYPE
    SYNTAX     IpAddress
    MAX-ACCESS read-only
    STATUS     current
    DESCRIPTION
        "-- empty --"
    ::= { lcsStatusIpRouterLogTableEntry 4 }

-- {COLUMN} 1712.1.10.26.1.5
lcsStatusIpRouterLogTableEntryProt OBJECT-TYPE
    SYNTAX     INTEGER (0..255)
    MAX-ACCESS read-only
    STATUS     current
    DESCRIPTION
        "-- empty --"
    ::= { lcsStatusIpRouterLogTableEntry 5 }

-- {COLUMN} 1712.1.10.26.1.6
lcsStatusIpRouterLogTableEntrySrcPort OBJECT-TYPE
    SYNTAX     INTEGER (0..65535)
    MAX-ACCESS read-only
    STATUS     current
    DESCRIPTION
        "-- empty --"
    ::= { lcsStatusIpRouterLogTableEntry 6 }

-- {COLUMN} 1712.1.10.26.1.7
lcsStatusIpRouterLogTableEntryDstPort OBJECT-TYPE
    SYNTAX     INTEGER (0..65535)
    MAX-ACCESS read-only
    STATUS     current
    DESCRIPTION
        "-- empty --"
    ::= { lcsStatusIpRouterLogTableEntry 7 }

-- {COLUMN} 1712.1.10.26.1.8
lcsStatusIpRouterLogTableEntryFilterRule OBJECT-TYPE
    SYNTAX     DisplayString (SIZE(0..32))
    MAX-ACCESS read-only
    STATUS     current
    DESCRIPTION
        "-- empty --"
    ::= { lcsStatusIpRouterLogTableEntry 8 }

-- {COLUMN} 1712.1.10.26.1.9
lcsStatusIpRouterLogTableEntryLimit OBJECT-TYPE
    SYNTAX     INTEGER (0..2147483647)
    MAX-ACCESS read-only
    STATUS     current
    DESCRIPTION
        "-- empty --"
    ::= { lcsStatusIpRouterLogTableEntry 9 }

-- {COLUMN} 1712.1.10.26.1.10
lcsStatusIpRouterLogTableEntryThreshold OBJECT-TYPE
    SYNTAX     INTEGER (0..2147483647)
    MAX-ACCESS read-only
    STATUS     current
    DESCRIPTION
        "-- empty --"
    ::= { lcsStatusIpRouterLogTableEntry 10 }

-- {COLUMN} 1712.1.10.26.1.11
lcsStatusIpRouterLogTableEntryAction OBJECT-TYPE
    SYNTAX     INTEGER (0..2147483647)
    MAX-ACCESS read-only
    STATUS     current
    DESCRIPTION
        "-- empty --"
    ::= { lcsStatusIpRouterLogTableEntry 11 }

-- {TABLE} 1712.1.10.27
lcsStatusIpRouterHoConnListTable OBJECT-TYPE
    SYNTAX     SEQUENCE OF LcsStatusIpRouterHoConnListEntry
    MAX-ACCESS not-accessible
    STATUS     current
    DESCRIPTION
        "-- empty --"
    ::= { lcsStatusIpRouter 27 }

-- {ENTRY} 1712.1.10.27.1
lcsStatusIpRouterHoConnListEntry OBJECT-TYPE
    SYNTAX     LcsStatusIpRouterHoConnListEntry
    MAX-ACCESS not-accessible
    STATUS     current
    DESCRIPTION
        ""
    INDEX {
        lcsStatusIpRouterHoConnListEntryDstAddress
    }
    ::= { lcsStatusIpRouterHoConnListTable 1 }

-- {SEQUENCE}
LcsStatusIpRouterHoConnListEntry ::= SEQUENCE {
    lcsStatusIpRouterHoConnListEntryDstAddress IpAddress,
    lcsStatusIpRouterHoConnListEntryNumHoConn INTEGER,
    lcsStatusIpRouterHoConnListEntryTimeout INTEGER
}

-- {COLUMN} 1712.1.10.27.1.1
lcsStatusIpRouterHoConnListEntryDstAddress OBJECT-TYPE
    SYNTAX     IpAddress
    MAX-ACCESS read-only
    STATUS     current
    DESCRIPTION
        "-- empty --"
    ::= { lcsStatusIpRouterHoConnListEntry 1 }

-- {COLUMN} 1712.1.10.27.1.2
lcsStatusIpRouterHoConnListEntryNumHoConn OBJECT-TYPE
    SYNTAX     INTEGER (0..2147483647)
    MAX-ACCESS read-only
    STATUS     current
    DESCRIPTION
        "-- empty --"
    ::= { lcsStatusIpRouterHoConnListEntry 2 }

-- {COLUMN} 1712.1.10.27.1.3
lcsStatusIpRouterHoConnListEntryTimeout OBJECT-TYPE
    SYNTAX     INTEGER (0..65535)
    MAX-ACCESS read-only
    STATUS     current
    DESCRIPTION
        "-- empty --"
    ::= { lcsStatusIpRouterHoConnListEntry 3 }

-- {TABLE} 1712.1.10.28
lcsStatusIpRouterQosTable OBJECT-TYPE
    SYNTAX     SEQUENCE OF LcsStatusIpRouterQosEntry
    MAX-ACCESS not-accessible
    STATUS     current
    DESCRIPTION
        "-- empty --"
    ::= { lcsStatusIpRouter 28 }

-- {ENTRY} 1712.1.10.28.1
lcsStatusIpRouterQosEntry OBJECT-TYPE
    SYNTAX     LcsStatusIpRouterQosEntry
    MAX-ACCESS not-accessible
    STATUS     current
    DESCRIPTION
        ""
    INDEX {
        lcsStatusIpRouterQosEntryIfc
    }
    ::= { lcsStatusIpRouterQosTable 1 }

-- {SEQUENCE}
LcsStatusIpRouterQosEntry ::= SEQUENCE {
    lcsStatusIpRouterQosEntryIfc INTEGER,
    lcsStatusIpRouterQosEntryPeer DisplayString,
    lcsStatusIpRouterQosEntryUpstreamRate INTEGER,
    lcsStatusIpRouterQosEntryDownstreamRate INTEGER,
    lcsStatusIpRouterQosEntryRxReserved INTEGER,
    lcsStatusIpRouterQosEntryRxRequested INTEGER,
    lcsStatusIpRouterQosEntryRxBlocksPending INTEGER,
    lcsStatusIpRouterQosEntryTxReserved INTEGER,
    lcsStatusIpRouterQosEntryTxRequested INTEGER,
    lcsStatusIpRouterQosEntryTxFavoured INTEGER,
    lcsStatusIpRouterQosEntryTxBlocksPending INTEGER,
    lcsStatusIpRouterQosEntryFragmentSize INTEGER,
    lcsStatusIpRouterQosEntryPmtuSize INTEGER
}

-- {COLUMN} 1712.1.10.28.1.1
lcsStatusIpRouterQosEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusIpRouterQosEntry 1 }

-- {COLUMN} 1712.1.10.28.1.2
lcsStatusIpRouterQosEntryPeer OBJECT-TYPE
    SYNTAX     DisplayString (SIZE(0..16))
    MAX-ACCESS read-only
    STATUS     current
    DESCRIPTION
        "-- empty --"
    ::= { lcsStatusIpRouterQosEntry 2 }

-- {COLUMN} 1712.1.10.28.1.8
lcsStatusIpRouterQosEntryUpstreamRate OBJECT-TYPE
    SYNTAX     INTEGER (0..2147483647)
    MAX-ACCESS read-only
    STATUS     current
    DESCRIPTION
        "-- empty --"
    ::= { lcsStatusIpRouterQosEntry 8 }

-- {COLUMN} 1712.1.10.28.1.3
lcsStatusIpRouterQosEntryDownstreamRate OBJECT-TYPE
    SYNTAX     INTEGER (0..2147483647)
    MAX-ACCESS read-only
    STATUS     current
    DESCRIPTION
        "-- empty --"
    ::= { lcsStatusIpRouterQosEntry 3 }

-- {COLUMN} 1712.1.10.28.1.4
lcsStatusIpRouterQosEntryRxReserved OBJECT-TYPE
    SYNTAX     INTEGER (0..2147483647)
    MAX-ACCESS read-only
    STATUS     current
    DESCRIPTION
        "-- empty --"
    ::= { lcsStatusIpRouterQosEntry 4 }

-- {COLUMN} 1712.1.10.28.1.11
lcsStatusIpRouterQosEntryRxRequested OBJECT-TYPE
    SYNTAX     INTEGER (0..2147483647)
    MAX-ACCESS read-only
    STATUS     current
    DESCRIPTION
        "-- empty --"
    ::= { lcsStatusIpRouterQosEntry 11 }

-- {COLUMN} 1712.1.10.28.1.5
lcsStatusIpRouterQosEntryRxBlocksPending OBJECT-TYPE
    SYNTAX     INTEGER (0..65535)
    MAX-ACCESS read-only
    STATUS     current
    DESCRIPTION
        "-- empty --"
    ::= { lcsStatusIpRouterQosEntry 5 }

-- {COLUMN} 1712.1.10.28.1.9
lcsStatusIpRouterQosEntryTxReserved OBJECT-TYPE
    SYNTAX     INTEGER (0..2147483647)
    MAX-ACCESS read-only
    STATUS     current
    DESCRIPTION
        "-- empty --"
    ::= { lcsStatusIpRouterQosEntry 9 }

-- {COLUMN} 1712.1.10.28.1.12
lcsStatusIpRouterQosEntryTxRequested OBJECT-TYPE
    SYNTAX     INTEGER (0..2147483647)
    MAX-ACCESS read-only
    STATUS     current
    DESCRIPTION
        "-- empty --"
    ::= { lcsStatusIpRouterQosEntry 12 }

-- {COLUMN} 1712.1.10.28.1.13
lcsStatusIpRouterQosEntryTxFavoured OBJECT-TYPE
    SYNTAX     INTEGER (0..2147483647)
    MAX-ACCESS read-only
    STATUS     current
    DESCRIPTION
        "-- empty --"
    ::= { lcsStatusIpRouterQosEntry 13 }

-- {COLUMN} 1712.1.10.28.1.10
lcsStatusIpRouterQosEntryTxBlocksPending OBJECT-TYPE
    SYNTAX     INTEGER (0..65535)
    MAX-ACCESS read-only
    STATUS     current
    DESCRIPTION
        "-- empty --"
    ::= { lcsStatusIpRouterQosEntry 10 }

-- {COLUMN} 1712.1.10.28.1.6
lcsStatusIpRouterQosEntryFragmentSize OBJECT-TYPE
    SYNTAX     INTEGER (0..65535)
    MAX-ACCESS read-only
    STATUS     current
    DESCRIPTION
        "-- empty --"
    ::= { lcsStatusIpRouterQosEntry 6 }

-- {COLUMN} 1712.1.10.28.1.7
lcsStatusIpRouterQosEntryPmtuSize OBJECT-TYPE
    SYNTAX     INTEGER (0..65535)
    MAX-ACCESS read-only
    STATUS     current
    DESCRIPTION
        "-- empty --"
    ::= { lcsStatusIpRouterQosEntry 7 }

-- {SCALAR} 1712.1.10.34
lcsStatusIpRouterRules OBJECT-TYPE
    SYNTAX     INTEGER (0..2147483647)
    MAX-ACCESS read-only
    STATUS     current
    DESCRIPTION
        "-- empty --"
    ::= { lcsStatusIpRouter 34 }

-- {SCALAR} 1712.1.10.35
lcsStatusIpRouterFilter OBJECT-TYPE
    SYNTAX     INTEGER (0..2147483647)
    MAX-ACCESS read-only
    STATUS     current
    DESCRIPTION
        "-- empty --"
    ::= { lcsStatusIpRouter 35 }

-- {SCALAR} 1712.1.10.31
lcsStatusIpRouterL4Errors OBJECT-TYPE
    SYNTAX     Counter32
    MAX-ACCESS read-only
    STATUS     current
    DESCRIPTION
        "-- empty --"
    ::= { lcsStatusIpRouter 31 }

-- {OID} 1712.1.10.32
lcsStatusIpRouterLoadBalancer OBJECT IDENTIFIER ::= { lcsStatusIpRouter 32 }

-- {SCALAR} 1712.1.10.32.1
lcsStatusIpRouterLoadBalancerOperating OBJECT-TYPE
    SYNTAX     INTEGER
      {
        eNo (0),
        eYes (1)
      }
    MAX-ACCESS read-only
    STATUS     current
    DESCRIPTION
        "-- empty --"
    ::= { lcsStatusIpRouterLoadBalancer 1 }

-- {TABLE} 1712.1.10.32.2
lcsStatusIpRouterLoadBalancerConnectionsTable OBJECT-TYPE
    SYNTAX     SEQUENCE OF LcsStatusIpRouterLoadBalancerConnectionsEntry
    MAX-ACCESS not-accessible
    STATUS     current
    DESCRIPTION
        "-- empty --"
    ::= { lcsStatusIpRouterLoadBalancer 2 }

-- {ENTRY} 1712.1.10.32.2.1
lcsStatusIpRouterLoadBalancerConnectionsEntry OBJECT-TYPE
    SYNTAX     LcsStatusIpRouterLoadBalancerConnectionsEntry
    MAX-ACCESS not-accessible
    STATUS     current
    DESCRIPTION
        ""
    INDEX {
        lcsStatusIpRouterLoadBalancerConnectionsEntryPeer,
        lcsStatusIpRouterLoadBalancerConnectionsEntryBundlePeer
    }
    ::= { lcsStatusIpRouterLoadBalancerConnectionsTable 1 }

-- {SEQUENCE}
LcsStatusIpRouterLoadBalancerConnectionsEntry ::= SEQUENCE {
    lcsStatusIpRouterLoadBalancerConnectionsEntryPeer DisplayString,
    lcsStatusIpRouterLoadBalancerConnectionsEntryBundlePeer DisplayString,
    lcsStatusIpRouterLoadBalancerConnectionsEntryState INTEGER,
    lcsStatusIpRouterLoadBalancerConnectionsEntryTcpIpSessions INTEGER,
    lcsStatusIpRouterLoadBalancerConnectionsEntryPptpSessions INTEGER,
    lcsStatusIpRouterLoadBalancerConnectionsEntryVpnSessions INTEGER
}

-- {COLUMN} 1712.1.10.32.2.1.1
lcsStatusIpRouterLoadBalancerConnectionsEntryPeer OBJECT-TYPE
    SYNTAX     DisplayString (SIZE(0..16))
    MAX-ACCESS read-only
    STATUS     current
    DESCRIPTION
        "-- empty --"
    ::= { lcsStatusIpRouterLoadBalancerConnectionsEntry 1 }

-- {COLUMN} 1712.1.10.32.2.1.2
lcsStatusIpRouterLoadBalancerConnectionsEntryBundlePeer OBJECT-TYPE
    SYNTAX     DisplayString (SIZE(0..16))
    MAX-ACCESS read-only
    STATUS     current
    DESCRIPTION
        "-- empty --"
    ::= { lcsStatusIpRouterLoadBalancerConnectionsEntry 2 }

-- {COLUMN} 1712.1.10.32.2.1.3
lcsStatusIpRouterLoadBalancerConnectionsEntryState OBJECT-TYPE
    SYNTAX     INTEGER
      {
        eReady (2),
        eConnection (7),
        eDisconnecting (8)
      }
    MAX-ACCESS read-only
    STATUS     current
    DESCRIPTION
        "-- empty --"
    ::= { lcsStatusIpRouterLoadBalancerConnectionsEntry 3 }

-- {COLUMN} 1712.1.10.32.2.1.4
lcsStatusIpRouterLoadBalancerConnectionsEntryTcpIpSessions OBJECT-TYPE
    SYNTAX     INTEGER (0..2147483647)
    MAX-ACCESS read-only
    STATUS     current
    DESCRIPTION
        "-- empty --"
    ::= { lcsStatusIpRouterLoadBalancerConnectionsEntry 4 }

-- {COLUMN} 1712.1.10.32.2.1.5
lcsStatusIpRouterLoadBalancerConnectionsEntryPptpSessions OBJECT-TYPE
    SYNTAX     INTEGER (0..2147483647)
    MAX-ACCESS read-only
    STATUS     current
    DESCRIPTION
        "-- empty --"
    ::= { lcsStatusIpRouterLoadBalancerConnectionsEntry 5 }

-- {COLUMN} 1712.1.10.32.2.1.6
lcsStatusIpRouterLoadBalancerConnectionsEntryVpnSessions OBJECT-TYPE
    SYNTAX     INTEGER (0..2147483647)
    MAX-ACCESS read-only
    STATUS     current
    DESCRIPTION
        "-- empty --"
    ::= { lcsStatusIpRouterLoadBalancerConnectionsEntry 6 }

-- {OID} 1712.1.10.33
lcsStatusIpRouterVrrp OBJECT IDENTIFIER ::= { lcsStatusIpRouter 33 }

-- {SCALAR} 1712.1.10.33.5
lcsStatusIpRouterVrrpOperating OBJECT-TYPE
    SYNTAX     INTEGER
      {
        eNo (0),
        eYes (1)
      }
    MAX-ACCESS read-only
    STATUS     current
    DESCRIPTION
        "-- empty --"
    ::= { lcsStatusIpRouterVrrp 5 }

-- {SCALAR} 1712.1.10.33.1
lcsStatusIpRouterVrrpRx OBJECT-TYPE
    SYNTAX     Counter32
    MAX-ACCESS read-only
    STATUS     current
    DESCRIPTION
        "-- empty --"
    ::= { lcsStatusIpRouterVrrp 1 }

-- {SCALAR} 1712.1.10.33.2
lcsStatusIpRouterVrrpTx OBJECT-TYPE
    SYNTAX     Counter32
    MAX-ACCESS read-only
    STATUS     current
    DESCRIPTION
        "-- empty --"
    ::= { lcsStatusIpRouterVrrp 2 }

-- {SCALAR} 1712.1.10.33.3
lcsStatusIpRouterVrrpError OBJECT-TYPE
    SYNTAX     Counter32
    MAX-ACCESS read-only
    STATUS     current
    DESCRIPTION
        "-- empty --"
    ::= { lcsStatusIpRouterVrrp 3 }

-- {SCALAR} 1712.1.10.33.4
lcsStatusIpRouterVrrpDrop OBJECT-TYPE
    SYNTAX     Counter32
    MAX-ACCESS read-only
    STATUS     current
    DESCRIPTION
        "-- empty --"
    ::= { lcsStatusIpRouterVrrp 4 }

-- {SCALAR} 1712.1.10.33.7
lcsStatusIpRouterVrrpQueueErrors OBJECT-TYPE
    SYNTAX     Counter32
    MAX-ACCESS read-only
    STATUS     current
    DESCRIPTION
        "-- empty --"
    ::= { lcsStatusIpRouterVrrp 7 }

-- {SCALAR} 1712.1.10.33.6
lcsStatusIpRouterVrrpInternalServices OBJECT-TYPE
    SYNTAX     INTEGER
      {
        eNo (0),
        eYes (1)
      }
    MAX-ACCESS read-only
    STATUS     current
    DESCRIPTION
        "-- empty --"
    ::= { lcsStatusIpRouterVrrp 6 }

-- {TABLE} 1712.1.10.33.10
lcsStatusIpRouterVrrpVirtualRouterTable OBJECT-TYPE
    SYNTAX     SEQUENCE OF LcsStatusIpRouterVrrpVirtualRouterEntry
    MAX-ACCESS not-accessible
    STATUS     current
    DESCRIPTION
        "-- empty --"
    ::= { lcsStatusIpRouterVrrp 10 }

-- {ENTRY} 1712.1.10.33.10.1
lcsStatusIpRouterVrrpVirtualRouterEntry OBJECT-TYPE
    SYNTAX     LcsStatusIpRouterVrrpVirtualRouterEntry
    MAX-ACCESS not-accessible
    STATUS     current
    DESCRIPTION
        ""
    INDEX {
        lcsStatusIpRouterVrrpVirtualRouterEntryRouterId
    }
    ::= { lcsStatusIpRouterVrrpVirtualRouterTable 1 }

-- {SEQUENCE}
LcsStatusIpRouterVrrpVirtualRouterEntry ::= SEQUENCE {
    lcsStatusIpRouterVrrpVirtualRouterEntryRouterId INTEGER,
    lcsStatusIpRouterVrrpVirtualRouterEntryVirtAddress IpAddress,
    lcsStatusIpRouterVrrpVirtualRouterEntryPrio INTEGER,
    lcsStatusIpRouterVrrpVirtualRouterEntryBPrio INTEGER,
    lcsStatusIpRouterVrrpVirtualRouterEntryPeer DisplayString,
    lcsStatusIpRouterVrrpVirtualRouterEntryState INTEGER,
    lcsStatusIpRouterVrrpVirtualRouterEntryBackup INTEGER,
    lcsStatusIpRouterVrrpVirtualRouterEntryMaster IpAddress,
    lcsStatusIpRouterVrrpVirtualRouterEntryPort INTEGER,
    lcsStatusIpRouterVrrpVirtualRouterEntryVlanId INTEGER,
    lcsStatusIpRouterVrrpVirtualRouterEntryNetworkName DisplayString
}

-- {COLUMN} 1712.1.10.33.10.1.1
lcsStatusIpRouterVrrpVirtualRouterEntryRouterId OBJECT-TYPE
    SYNTAX     INTEGER (0..255)
    MAX-ACCESS read-only
    STATUS     current
    DESCRIPTION
        "-- empty --"
    ::= { lcsStatusIpRouterVrrpVirtualRouterEntry 1 }

-- {COLUMN} 1712.1.10.33.10.1.2
lcsStatusIpRouterVrrpVirtualRouterEntryVirtAddress OBJECT-TYPE
    SYNTAX     IpAddress
    MAX-ACCESS read-only
    STATUS     current
    DESCRIPTION
        "-- empty --"
    ::= { lcsStatusIpRouterVrrpVirtualRouterEntry 2 }

-- {COLUMN} 1712.1.10.33.10.1.3
lcsStatusIpRouterVrrpVirtualRouterEntryPrio OBJECT-TYPE
    SYNTAX     INTEGER (0..255)
    MAX-ACCESS read-only
    STATUS     current
    DESCRIPTION
        "-- empty --"
    ::= { lcsStatusIpRouterVrrpVirtualRouterEntry 3 }

-- {COLUMN} 1712.1.10.33.10.1.4
lcsStatusIpRouterVrrpVirtualRouterEntryBPrio OBJECT-TYPE
    SYNTAX     INTEGER (0..255)
    MAX-ACCESS read-only
    STATUS     current
    DESCRIPTION
        "-- empty --"
    ::= { lcsStatusIpRouterVrrpVirtualRouterEntry 4 }

-- {COLUMN} 1712.1.10.33.10.1.5
lcsStatusIpRouterVrrpVirtualRouterEntryPeer OBJECT-TYPE
    SYNTAX     DisplayString (SIZE(0..16))
    MAX-ACCESS read-only
    STATUS     current
    DESCRIPTION
        "-- empty --"
    ::= { lcsStatusIpRouterVrrpVirtualRouterEntry 5 }

-- {COLUMN} 1712.1.10.33.10.1.6
lcsStatusIpRouterVrrpVirtualRouterEntryState OBJECT-TYPE
    SYNTAX     INTEGER
      {
        eInit (0),
        eListen (1),
        eStandby (2),
        eMaster (3),
        eDown (4),
        eReconnect (5)
      }
    MAX-ACCESS read-only
    STATUS     current
    DESCRIPTION
        "-- empty --"
    ::= { lcsStatusIpRouterVrrpVirtualRouterEntry 6 }

-- {COLUMN} 1712.1.10.33.10.1.7
lcsStatusIpRouterVrrpVirtualRouterEntryBackup OBJECT-TYPE
    SYNTAX     INTEGER
      {
        eNo (0),
        eYes (1)
      }
    MAX-ACCESS read-only
    STATUS     current
    DESCRIPTION
        "-- empty --"
    ::= { lcsStatusIpRouterVrrpVirtualRouterEntry 7 }

-- {COLUMN} 1712.1.10.33.10.1.8
lcsStatusIpRouterVrrpVirtualRouterEntryMaster OBJECT-TYPE
    SYNTAX     IpAddress
    MAX-ACCESS read-only
    STATUS     current
    DESCRIPTION
        "-- empty --"
    ::= { lcsStatusIpRouterVrrpVirtualRouterEntry 8 }

-- {COLUMN} 1712.1.10.33.10.1.12
lcsStatusIpRouterVrrpVirtualRouterEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsStatusIpRouterVrrpVirtualRouterEntry 12 }

-- {COLUMN} 1712.1.10.33.10.1.10
lcsStatusIpRouterVrrpVirtualRouterEntryVlanId OBJECT-TYPE
    SYNTAX     INTEGER (0..65535)
    MAX-ACCESS read-only
    STATUS     current
    DESCRIPTION
        "-- empty --"
    ::= { lcsStatusIpRouterVrrpVirtualRouterEntry 10 }

-- {COLUMN} 1712.1.10.33.10.1.11
lcsStatusIpRouterVrrpVirtualRouterEntryNetworkName OBJECT-TYPE
    SYNTAX     DisplayString (SIZE(0..16))
    MAX-ACCESS read-only
    STATUS     current
    DESCRIPTION
        "-- empty --"
    ::= { lcsStatusIpRouterVrrpVirtualRouterEntry 11 }

-- {TABLE} 1712.1.10.33.11
lcsStatusIpRouterVrrpMacListTable OBJECT-TYPE
    SYNTAX     SEQUENCE OF LcsStatusIpRouterVrrpMacListEntry
    MAX-ACCESS not-accessible
    STATUS     current
    DESCRIPTION
        "-- empty --"
    ::= { lcsStatusIpRouterVrrp 11 }

-- {ENTRY} 1712.1.10.33.11.1
lcsStatusIpRouterVrrpMacListEntry OBJECT-TYPE
    SYNTAX     LcsStatusIpRouterVrrpMacListEntry
    MAX-ACCESS not-accessible
    STATUS     current
    DESCRIPTION
        ""
    INDEX {
        lcsStatusIpRouterVrrpMacListEntryVirtAddress
    }
    ::= { lcsStatusIpRouterVrrpMacListTable 1 }

-- {SEQUENCE}
LcsStatusIpRouterVrrpMacListEntry ::= SEQUENCE {
    lcsStatusIpRouterVrrpMacListEntryVirtAddress IpAddress,
    lcsStatusIpRouterVrrpMacListEntryMacAddress MacAddress,
    lcsStatusIpRouterVrrpMacListEntryRouterId INTEGER
}

-- {COLUMN} 1712.1.10.33.11.1.1
lcsStatusIpRouterVrrpMacListEntryVirtAddress OBJECT-TYPE
    SYNTAX     IpAddress
    MAX-ACCESS read-only
    STATUS     current
    DESCRIPTION
        "-- empty --"
    ::= { lcsStatusIpRouterVrrpMacListEntry 1 }

-- {COLUMN} 1712.1.10.33.11.1.2
lcsStatusIpRouterVrrpMacListEntryMacAddress OBJECT-TYPE
    SYNTAX     MacAddress
    MAX-ACCESS read-only
    STATUS     current
    DESCRIPTION
        "-- empty --"
    ::= { lcsStatusIpRouterVrrpMacListEntry 2 }

-- {COLUMN} 1712.1.10.33.11.1.3
lcsStatusIpRouterVrrpMacListEntryRouterId OBJECT-TYPE
    SYNTAX     INTEGER (0..255)
    MAX-ACCESS read-only
    STATUS     current
    DESCRIPTION
        "-- empty --"
    ::= { lcsStatusIpRouterVrrpMacListEntry 3 }

-- {TABLE} 1712.1.10.33.12
lcsStatusIpRouterVrrpEventLogTable OBJECT-TYPE
    SYNTAX     SEQUENCE OF LcsStatusIpRouterVrrpEventLogEntry
    MAX-ACCESS not-accessible
    STATUS     current
    DESCRIPTION
        "-- empty --"
    ::= { lcsStatusIpRouterVrrp 12 }

-- {ENTRY} 1712.1.10.33.12.1
lcsStatusIpRouterVrrpEventLogEntry OBJECT-TYPE
    SYNTAX     LcsStatusIpRouterVrrpEventLogEntry
    MAX-ACCESS not-accessible
    STATUS     current
    DESCRIPTION
        ""
    INDEX {
        lcsStatusIpRouterVrrpEventLogEntryIdx
    }
    ::= { lcsStatusIpRouterVrrpEventLogTable 1 }

-- {SEQUENCE}
LcsStatusIpRouterVrrpEventLogEntry ::= SEQUENCE {
    lcsStatusIpRouterVrrpEventLogEntryIdx INTEGER,
    lcsStatusIpRouterVrrpEventLogEntrySystemTime DisplayString,
    lcsStatusIpRouterVrrpEventLogEntrySrcAddress IpAddress,
    lcsStatusIpRouterVrrpEventLogEntryVrid INTEGER,
    lcsStatusIpRouterVrrpEventLogEntryEvent INTEGER,
    lcsStatusIpRouterVrrpEventLogEntryInfo DisplayString
}

-- {COLUMN} 1712.1.10.33.12.1.1
lcsStatusIpRouterVrrpEventLogEntryIdx OBJECT-TYPE
    SYNTAX     INTEGER (0..65535)
    MAX-ACCESS read-only
    STATUS     current
    DESCRIPTION
        "-- empty --"
    ::= { lcsStatusIpRouterVrrpEventLogEntry 1 }

-- {COLUMN} 1712.1.10.33.12.1.2
lcsStatusIpRouterVrrpEventLogEntrySystemTime OBJECT-TYPE
    SYNTAX     DisplayString (SIZE(0..19))
    MAX-ACCESS read-only
    STATUS     current
    DESCRIPTION
        "-- empty --"
    ::= { lcsStatusIpRouterVrrpEventLogEntry 2 }

-- {COLUMN} 1712.1.10.33.12.1.3
lcsStatusIpRouterVrrpEventLogEntrySrcAddress OBJECT-TYPE
    SYNTAX     IpAddress
    MAX-ACCESS read-only
    STATUS     current
    DESCRIPTION
        "-- empty --"
    ::= { lcsStatusIpRouterVrrpEventLogEntry 3 }

-- {COLUMN} 1712.1.10.33.12.1.4
lcsStatusIpRouterVrrpEventLogEntryVrid OBJECT-TYPE
    SYNTAX     INTEGER (0..255)
    MAX-ACCESS read-only
    STATUS     current
    DESCRIPTION
        "-- empty --"
    ::= { lcsStatusIpRouterVrrpEventLogEntry 4 }

-- {COLUMN} 1712.1.10.33.12.1.5
lcsStatusIpRouterVrrpEventLogEntryEvent OBJECT-TYPE
    SYNTAX     INTEGER
      {
        eInvalidTtl (1),
        eInvalidVersion (2),
        eBadNumberOfVirtualAddresses (3),
        eBadAuthenticationType (4),
        eBadAdvertisementInterval (5),
        eInvalidVrid (6),
        eInvalidRouterAddress (7),
        eInvalidPriority (8),
        eVirtualRouterStopped (9),
        eVirtualRouterStarted (10),
        eLinkUp (11),
        eLinkDown (12),
        eNewMaster (13),
        eBackupStarted (14),
        eBackupEnded (15)
      }
    MAX-ACCESS read-only
    STATUS     current
    DESCRIPTION
        "-- empty --"
    ::= { lcsStatusIpRouterVrrpEventLogEntry 5 }

-- {COLUMN} 1712.1.10.33.12.1.6
lcsStatusIpRouterVrrpEventLogEntryInfo OBJECT-TYPE
    SYNTAX     DisplayString (SIZE(0..255))
    MAX-ACCESS read-only
    STATUS     current
    DESCRIPTION
        "-- empty --"
    ::= { lcsStatusIpRouterVrrpEventLogEntry 6 }

-- {SCALAR} 1712.1.10.33.20
lcsStatusIpRouterVrrpDeleteValues OBJECT-TYPE
    SYNTAX     DisplayString
    MAX-ACCESS read-write
    STATUS     current
    DESCRIPTION
        "-- empty --"
    ::= { lcsStatusIpRouterVrrp 20 }

-- {TABLE} 1712.1.10.30
lcsStatusIpRouterActIpRoutingTabTable OBJECT-TYPE
    SYNTAX     SEQUENCE OF LcsStatusIpRouterActIpRoutingTabEntry
    MAX-ACCESS not-accessible
    STATUS     current
    DESCRIPTION
        "-- empty --"
    ::= { lcsStatusIpRouter 30 }

-- {ENTRY} 1712.1.10.30.1
lcsStatusIpRouterActIpRoutingTabEntry OBJECT-TYPE
    SYNTAX     LcsStatusIpRouterActIpRoutingTabEntry
    MAX-ACCESS not-accessible
    STATUS     current
    DESCRIPTION
        ""
    INDEX {
        lcsStatusIpRouterActIpRoutingTabEntryIpAddress,
        lcsStatusIpRouterActIpRoutingTabEntryIpNetmask,
        lcsStatusIpRouterActIpRoutingTabEntryRtgTag
    }
    ::= { lcsStatusIpRouterActIpRoutingTabTable 1 }

-- {SEQUENCE}
LcsStatusIpRouterActIpRoutingTabEntry ::= SEQUENCE {
    lcsStatusIpRouterActIpRoutingTabEntryIpAddress IpAddress,
    lcsStatusIpRouterActIpRoutingTabEntryIpNetmask IpAddress,
    lcsStatusIpRouterActIpRoutingTabEntryRtgTag INTEGER,
    lcsStatusIpRouterActIpRoutingTabEntryGateway IpAddress,
    lcsStatusIpRouterActIpRoutingTabEntryPeer DisplayString,
    lcsStatusIpRouterActIpRoutingTabEntryDistance INTEGER,
    lcsStatusIpRouterActIpRoutingTabEntryMasquerade INTEGER,
    lcsStatusIpRouterActIpRoutingTabEntryType INTEGER
}

-- {COLUMN} 1712.1.10.30.1.1
lcsStatusIpRouterActIpRoutingTabEntryIpAddress OBJECT-TYPE
    SYNTAX     IpAddress
    MAX-ACCESS read-only
    STATUS     current
    DESCRIPTION
        "-- empty --"
    ::= { lcsStatusIpRouterActIpRoutingTabEntry 1 }

-- {COLUMN} 1712.1.10.30.1.2
lcsStatusIpRouterActIpRoutingTabEntryIpNetmask OBJECT-TYPE
    SYNTAX     IpAddress
    MAX-ACCESS read-only
    STATUS     current
    DESCRIPTION
        "-- empty --"
    ::= { lcsStatusIpRouterActIpRoutingTabEntry 2 }

-- {COLUMN} 1712.1.10.30.1.3
lcsStatusIpRouterActIpRoutingTabEntryRtgTag OBJECT-TYPE
    SYNTAX     INTEGER (0..65535)
    MAX-ACCESS read-only
    STATUS     current
    DESCRIPTION
        "-- empty --"
    ::= { lcsStatusIpRouterActIpRoutingTabEntry 3 }

-- {COLUMN} 1712.1.10.30.1.4
lcsStatusIpRouterActIpRoutingTabEntryGateway OBJECT-TYPE
    SYNTAX     IpAddress
    MAX-ACCESS read-only
    STATUS     current
    DESCRIPTION
        "-- empty --"
    ::= { lcsStatusIpRouterActIpRoutingTabEntry 4 }

-- {COLUMN} 1712.1.10.30.1.5
lcsStatusIpRouterActIpRoutingTabEntryPeer OBJECT-TYPE
    SYNTAX     DisplayString (SIZE(0..255))
    MAX-ACCESS read-only
    STATUS     current
    DESCRIPTION
        "-- empty --"
    ::= { lcsStatusIpRouterActIpRoutingTabEntry 5 }

-- {COLUMN} 1712.1.10.30.1.6
lcsStatusIpRouterActIpRoutingTabEntryDistance OBJECT-TYPE
    SYNTAX     INTEGER (0..255)
    MAX-ACCESS read-only
    STATUS     current
    DESCRIPTION
        "-- empty --"
    ::= { lcsStatusIpRouterActIpRoutingTabEntry 6 }

-- {COLUMN} 1712.1.10.30.1.7
lcsStatusIpRouterActIpRoutingTabEntryMasquerade OBJECT-TYPE
    SYNTAX     INTEGER
      {
        eNo (0),
        eOn (1),
        eIntranet (2),
        eUnknown (255)
      }
    MAX-ACCESS read-only
    STATUS     current
    DESCRIPTION
        "-- empty --"
    ::= { lcsStatusIpRouterActIpRoutingTabEntry 7 }

-- {COLUMN} 1712.1.10.30.1.8
lcsStatusIpRouterActIpRoutingTabEntryType OBJECT-TYPE
    SYNTAX     INTEGER
      {
        eUnknown (0),
        eStatic (1),
        eRip (2),
        eVpn (3),
        eCapwap (4),
        eRas (5),
        eIntranet (6),
        eDmz (7),
        eDisabled (8)
      }
    MAX-ACCESS read-only
    STATUS     current
    DESCRIPTION
        "-- empty --"
    ::= { lcsStatusIpRouterActIpRoutingTabEntry 8 }

-- {OID} 1712.1.11
lcsStatusConfig OBJECT IDENTIFIER ::= { lcsStatus 11 }

-- {SCALAR} 1712.1.11.1
lcsStatusConfigLanActiveConnections OBJECT-TYPE
    SYNTAX     INTEGER (0..65535)
    MAX-ACCESS read-only
    STATUS     current
    DESCRIPTION
        "-- empty --"
    ::= { lcsStatusConfig 1 }

-- {SCALAR} 1712.1.11.2
lcsStatusConfigLanTotalConnections OBJECT-TYPE
    SYNTAX     Counter32
    MAX-ACCESS read-only
    STATUS     current
    DESCRIPTION
        "-- empty --"
    ::= { lcsStatusConfig 2 }

-- {SCALAR} 1712.1.11.3
lcsStatusConfigWanActiveConnections OBJECT-TYPE
    SYNTAX     INTEGER (0..65535)
    MAX-ACCESS read-only
    STATUS     current
    DESCRIPTION
        "-- empty --"
    ::= { lcsStatusConfig 3 }

-- {SCALAR} 1712.1.11.4
lcsStatusConfigWanTotalConnections OBJECT-TYPE
    SYNTAX     Counter32
    MAX-ACCESS read-only
    STATUS     current
    DESCRIPTION
        "-- empty --"
    ::= { lcsStatusConfig 4 }

-- {SCALAR} 1712.1.11.5
lcsStatusConfigOutbandActiveConnections OBJECT-TYPE
    SYNTAX     INTEGER (0..65535)
    MAX-ACCESS read-only
    STATUS     current
    DESCRIPTION
        "-- empty --"
    ::= { lcsStatusConfig 5 }

-- {SCALAR} 1712.1.11.6
lcsStatusConfigOutbandTotalConnections OBJECT-TYPE
    SYNTAX     Counter32
    MAX-ACCESS read-only
    STATUS     current
    DESCRIPTION
        "-- empty --"
    ::= { lcsStatusConfig 6 }

-- {SCALAR} 1712.1.11.7
lcsStatusConfigOutbandBitrate OBJECT-TYPE
    SYNTAX     INTEGER (0..2147483647)
    MAX-ACCESS read-only
    STATUS     current
    DESCRIPTION
        "-- empty --"
    ::= { lcsStatusConfig 7 }

-- {SCALAR} 1712.1.11.8
lcsStatusConfigLoginErrors OBJECT-TYPE
    SYNTAX     Counter32
    MAX-ACCESS read-only
    STATUS     current
    DESCRIPTION
        "-- empty --"
    ::= { lcsStatusConfig 8 }

-- {SCALAR} 1712.1.11.9
lcsStatusConfigLoginLocks OBJECT-TYPE
    SYNTAX     Counter32
    MAX-ACCESS read-only
    STATUS     current
    DESCRIPTION
        "-- empty --"
    ::= { lcsStatusConfig 9 }

-- {SCALAR} 1712.1.11.10
lcsStatusConfigLoginRejects OBJECT-TYPE
    SYNTAX     Counter32
    MAX-ACCESS read-only
    STATUS     current
    DESCRIPTION
        "-- empty --"
    ::= { lcsStatusConfig 10 }

-- {SCALAR} 1712.1.11.13
lcsStatusConfigStartScan OBJECT-TYPE
    SYNTAX     DisplayString
    MAX-ACCESS read-write
    STATUS     current
    DESCRIPTION
        "-- empty --"
    ::= { lcsStatusConfig 13 }

-- {TABLE} 1712.1.11.14
lcsStatusConfigScanResultsTable OBJECT-TYPE
    SYNTAX     SEQUENCE OF LcsStatusConfigScanResultsEntry
    MAX-ACCESS not-accessible
    STATUS     current
    DESCRIPTION
        "-- empty --"
    ::= { lcsStatusConfig 14 }

-- {ENTRY} 1712.1.11.14.1
lcsStatusConfigScanResultsEntry OBJECT-TYPE
    SYNTAX     LcsStatusConfigScanResultsEntry
    MAX-ACCESS not-accessible
    STATUS     current
    DESCRIPTION
        ""
    INDEX {
        lcsStatusConfigScanResultsEntryIpAddress,
        lcsStatusConfigScanResultsEntryRtgTag
    }
    ::= { lcsStatusConfigScanResultsTable 1 }

-- {SEQUENCE}
LcsStatusConfigScanResultsEntry ::= SEQUENCE {
    lcsStatusConfigScanResultsEntryIpAddress IpAddress,
    lcsStatusConfigScanResultsEntryRtgTag INTEGER,
    lcsStatusConfigScanResultsEntryName DisplayString,
    lcsStatusConfigScanResultsEntryDeviceType DisplayString,
    lcsStatusConfigScanResultsEntryVersion DisplayString,
    lcsStatusConfigScanResultsEntryCapiPort INTEGER,
    lcsStatusConfigScanResultsEntryHttpPort INTEGER,
    lcsStatusConfigScanResultsEntryHttpsPort INTEGER,
    lcsStatusConfigScanResultsEntryState INTEGER
}

-- {COLUMN} 1712.1.11.14.1.1
lcsStatusConfigScanResultsEntryIpAddress OBJECT-TYPE
    SYNTAX     IpAddress
    MAX-ACCESS read-only
    STATUS     current
    DESCRIPTION
        "-- empty --"
    ::= { lcsStatusConfigScanResultsEntry 1 }

-- {COLUMN} 1712.1.11.14.1.9
lcsStatusConfigScanResultsEntryRtgTag OBJECT-TYPE
    SYNTAX     INTEGER (0..65535)
    MAX-ACCESS read-only
    STATUS     current
    DESCRIPTION
        "-- empty --"
    ::= { lcsStatusConfigScanResultsEntry 9 }

-- {COLUMN} 1712.1.11.14.1.2
lcsStatusConfigScanResultsEntryName OBJECT-TYPE
    SYNTAX     DisplayString (SIZE(0..17))
    MAX-ACCESS read-only
    STATUS     current
    DESCRIPTION
        "-- empty --"
    ::= { lcsStatusConfigScanResultsEntry 2 }

-- {COLUMN} 1712.1.11.14.1.3
lcsStatusConfigScanResultsEntryDeviceType OBJECT-TYPE
    SYNTAX     DisplayString (SIZE(0..64))
    MAX-ACCESS read-only
    STATUS     current
    DESCRIPTION
        "-- empty --"
    ::= { lcsStatusConfigScanResultsEntry 3 }

-- {COLUMN} 1712.1.11.14.1.4
lcsStatusConfigScanResultsEntryVersion OBJECT-TYPE
    SYNTAX     DisplayString (SIZE(0..30))
    MAX-ACCESS read-only
    STATUS     current
    DESCRIPTION
        "-- empty --"
    ::= { lcsStatusConfigScanResultsEntry 4 }

-- {COLUMN} 1712.1.11.14.1.6
lcsStatusConfigScanResultsEntryCapiPort OBJECT-TYPE
    SYNTAX     INTEGER (0..65535)
    MAX-ACCESS read-only
    STATUS     current
    DESCRIPTION
        "-- empty --"
    ::= { lcsStatusConfigScanResultsEntry 6 }

-- {COLUMN} 1712.1.11.14.1.7
lcsStatusConfigScanResultsEntryHttpPort OBJECT-TYPE
    SYNTAX     INTEGER (0..65535)
    MAX-ACCESS read-only
    STATUS     current
    DESCRIPTION
        "-- empty --"
    ::= { lcsStatusConfigScanResultsEntry 7 }

-- {COLUMN} 1712.1.11.14.1.8
lcsStatusConfigScanResultsEntryHttpsPort OBJECT-TYPE
    SYNTAX     INTEGER (0..65535)
    MAX-ACCESS read-only
    STATUS     current
    DESCRIPTION
        "-- empty --"
    ::= { lcsStatusConfigScanResultsEntry 8 }

-- {COLUMN} 1712.1.11.14.1.5
lcsStatusConfigScanResultsEntryState OBJECT-TYPE
    SYNTAX     INTEGER
      {
        eScanning (0),
        eReady (1),
        eError (2)
      }
    MAX-ACCESS read-only
    STATUS     current
    DESCRIPTION
        "-- empty --"
    ::= { lcsStatusConfigScanResultsEntry 5 }

-- {TABLE} 1712.1.11.16
lcsStatusConfigFeaturesTable OBJECT-TYPE
    SYNTAX     SEQUENCE OF LcsStatusConfigFeaturesEntry
    MAX-ACCESS not-accessible
    STATUS     current
    DESCRIPTION
        "-- empty --"
    ::= { lcsStatusConfig 16 }

-- {ENTRY} 1712.1.11.16.1
lcsStatusConfigFeaturesEntry OBJECT-TYPE
    SYNTAX     LcsStatusConfigFeaturesEntry
    MAX-ACCESS not-accessible
    STATUS     current
    DESCRIPTION
        ""
    INDEX {
        lcsStatusConfigFeaturesEntryFeature,
        lcsStatusConfigFeaturesEntryIndex
    }
    ::= { lcsStatusConfigFeaturesTable 1 }

-- {SEQUENCE}
LcsStatusConfigFeaturesEntry ::= SEQUENCE {
    lcsStatusConfigFeaturesEntryFeature INTEGER,
    lcsStatusConfigFeaturesEntryExpires DisplayString,
    lcsStatusConfigFeaturesEntryExpire Gauge32,
    lcsStatusConfigFeaturesEntryState INTEGER,
    lcsStatusConfigFeaturesEntryIndex INTEGER,
    lcsStatusConfigFeaturesEntryCount INTEGER
}

-- {COLUMN} 1712.1.11.16.1.1
lcsStatusConfigFeaturesEntryFeature OBJECT-TYPE
    SYNTAX     INTEGER
      {
        eLanBridge (2),
        eLancapi (3),
        eLeasedLine (4),
        eSwitchedLine (5),
        eDslInterface (6),
        eFax (7),
        eModem (8),
        eVpn5 (9),
        eVpn25 (10),
        eCommonCriteria (11),
        eProductionOk (12),
        eVpn100 (13),
        eWlc4025100 (14),
        eWlanPointToPoint (15),
        ePublicSpot (16),
        eVpn200 (17),
        eVpn500 (18),
        eVpn1000 (19),
        eHermes1Wpa (20),
        eVpn3 (21),
        eUmts (22),
        eDynamicVpn (23),
        eWlan5ghz (24),
        eWlanNoEncryption (25),
        eVoipAdvanced32 (26),
        eVoipBasic (27),
        eWlanFccRestrictions (28),
        eWlc402550 (29),
        eWlc400612 (30),
        eVoipAdvanced8 (31),
        eContentfilterAdditive (36),
        eWlcPublicSpot (37),
        eWlanMonitorMode (38),
        eWlanNo5ghz (39),
        eWlcApUpgrade (40),
        eWlanDfs3 (41),
        eInProduction (42),
        eNetioServer (43),
        eLanWlanBridge (44),
        eEthernetIp (45),
        eProfinet (46),
        eWlanFilteredAveraging (47),
        eVpn50 (48),
        eWlcApBasic (49),
        ePms (50),
        ePrp (53)
      }
    MAX-ACCESS read-only
    STATUS     current
    DESCRIPTION
        "-- empty --"
    ::= { lcsStatusConfigFeaturesEntry 1 }

-- {COLUMN} 1712.1.11.16.1.2
lcsStatusConfigFeaturesEntryExpires OBJECT-TYPE
    SYNTAX     DisplayString (SIZE(0..255))
    MAX-ACCESS read-only
    STATUS     current
    DESCRIPTION
        "-- empty --"
    ::= { lcsStatusConfigFeaturesEntry 2 }

-- {COLUMN} 1712.1.11.16.1.3
lcsStatusConfigFeaturesEntryExpire OBJECT-TYPE
    SYNTAX     Gauge32
    MAX-ACCESS read-only
    STATUS     current
    DESCRIPTION
        "-- empty --"
    ::= { lcsStatusConfigFeaturesEntry 3 }

-- {COLUMN} 1712.1.11.16.1.4
lcsStatusConfigFeaturesEntryState OBJECT-TYPE
    SYNTAX     INTEGER
      {
        eLocked (0),
        eActive (1),
        eHidden (2),
        eExpired (3),
        eUnused (4)
      }
    MAX-ACCESS read-only
    STATUS     current
    DESCRIPTION
        "-- empty --"
    ::= { lcsStatusConfigFeaturesEntry 4 }

-- {COLUMN} 1712.1.11.16.1.5
lcsStatusConfigFeaturesEntryIndex OBJECT-TYPE
    SYNTAX     INTEGER (0..2147483647)
    MAX-ACCESS read-only
    STATUS     current
    DESCRIPTION
        "-- empty --"
    ::= { lcsStatusConfigFeaturesEntry 5 }

-- {COLUMN} 1712.1.11.16.1.6
lcsStatusConfigFeaturesEntryCount OBJECT-TYPE
    SYNTAX     INTEGER (0..2147483647)
    MAX-ACCESS read-only
    STATUS     current
    DESCRIPTION
        "-- empty --"
    ::= { lcsStatusConfigFeaturesEntry 6 }

-- {OID} 1712.1.11.15
lcsStatusConfigAntiTheftProtection OBJECT IDENTIFIER ::= { lcsStatusConfig 15 }

-- {SCALAR} 1712.1.11.15.1
lcsStatusConfigAntiTheftProtectionState OBJECT-TYPE
    SYNTAX     INTEGER
      {
        eDisabled (0),
        eActive (1),
        eSuccessfull (2),
        eLocked (3)
      }
    MAX-ACCESS read-only
    STATUS     current
    DESCRIPTION
        "-- empty --"
    ::= { lcsStatusConfigAntiTheftProtection 1 }

-- {SCALAR} 1712.1.11.15.2
lcsStatusConfigAntiTheftProtectionSendingCallTo OBJECT-TYPE
    SYNTAX     DisplayString (SIZE(0..14))
    MAX-ACCESS read-only
    STATUS     current
    DESCRIPTION
        "-- empty --"
    ::= { lcsStatusConfigAntiTheftProtection 2 }

-- {SCALAR} 1712.1.11.15.3
lcsStatusConfigAntiTheftProtectionWaitingForCallFrom OBJECT-TYPE
    SYNTAX     DisplayString (SIZE(0..14))
    MAX-ACCESS read-only
    STATUS     current
    DESCRIPTION
        "-- empty --"
    ::= { lcsStatusConfigAntiTheftProtection 3 }

-- {SCALAR} 1712.1.11.15.4
lcsStatusConfigAntiTheftProtectionLastSeenCallFrom OBJECT-TYPE
    SYNTAX     DisplayString (SIZE(0..14))
    MAX-ACCESS read-only
    STATUS     current
    DESCRIPTION
        "-- empty --"
    ::= { lcsStatusConfigAntiTheftProtection 4 }

-- {SCALAR} 1712.1.11.15.5
lcsStatusConfigAntiTheftProtectionCallAccepted OBJECT-TYPE
    SYNTAX     INTEGER
      {
        eNo (0),
        eYes (1)
      }
    MAX-ACCESS read-only
    STATUS     current
    DESCRIPTION
        "-- empty --"
    ::= { lcsStatusConfigAntiTheftProtection 5 }

-- {SCALAR} 1712.1.11.15.7
lcsStatusConfigAntiTheftProtectionIncomingCall OBJECT-TYPE
    SYNTAX     INTEGER
      {
        eNo (0),
        eYes (1)
      }
    MAX-ACCESS read-only
    STATUS     current
    DESCRIPTION
        "-- empty --"
    ::= { lcsStatusConfigAntiTheftProtection 7 }

-- {SCALAR} 1712.1.11.15.6
lcsStatusConfigAntiTheftProtectionLastError OBJECT-TYPE
    SYNTAX     INTEGER
      {
        eNone (0),
        eUnallocatedNumber (1),
        eNoRouteToDestination (3),
        eNormalCallClearing (16),
        eUserBusy (17),
        eNoUserResponding (18),
        eUserAlertingNoAnswer (19),
        eCallRejected (21),
        eNumberChanged (22),
        eNonSelectedUserClearing (26),
        eDestinationOutOfOrder (27),
        eNormalUnspecified (31),
        eNoChannelAvailable (34),
        eSwitchingEquipmentCongestion (42),
        eInvalidCallReferenceNumber (81),
        eIncompatibleDestination (88),
        eTempFailure (41),
        eFacilityNotSubscribed (50),
        eFacilityNotAvailable (63)
      }
    MAX-ACCESS read-only
    STATUS     current
    DESCRIPTION
        "-- empty --"
    ::= { lcsStatusConfigAntiTheftProtection 6 }

-- {SCALAR} 1712.1.11.15.8
lcsStatusConfigAntiTheftProtectionMethod OBJECT-TYPE
    SYNTAX     INTEGER
      {
        eBasicCall (0),
        eFacility (1)
      }
    MAX-ACCESS read-only
    STATUS     current
    DESCRIPTION
        "-- empty --"
    ::= { lcsStatusConfigAntiTheftProtection 8 }

-- {OID} 1712.1.11.65
lcsStatusConfigLl2m OBJECT IDENTIFIER ::= { lcsStatusConfig 65 }

-- {SCALAR} 1712.1.11.65.1
lcsStatusConfigLl2mRxPackets OBJECT-TYPE
    SYNTAX     INTEGER (0..2147483647)
    MAX-ACCESS read-only
    STATUS     current
    DESCRIPTION
        "-- empty --"
    ::= { lcsStatusConfigLl2m 1 }

-- {SCALAR} 1712.1.11.65.2
lcsStatusConfigLl2mRxBroadcastPackets OBJECT-TYPE
    SYNTAX     INTEGER (0..2147483647)
    MAX-ACCESS read-only
    STATUS     current
    DESCRIPTION
        "-- empty --"
    ::= { lcsStatusConfigLl2m 2 }

-- {SCALAR} 1712.1.11.65.3
lcsStatusConfigLl2mRxMulticastPackets OBJECT-TYPE
    SYNTAX     INTEGER (0..2147483647)
    MAX-ACCESS read-only
    STATUS     current
    DESCRIPTION
        "-- empty --"
    ::= { lcsStatusConfigLl2m 3 }

-- {SCALAR} 1712.1.11.65.4
lcsStatusConfigLl2mRxUnicastPackets OBJECT-TYPE
    SYNTAX     INTEGER (0..2147483647)
    MAX-ACCESS read-only
    STATUS     current
    DESCRIPTION
        "-- empty --"
    ::= { lcsStatusConfigLl2m 4 }

-- {SCALAR} 1712.1.11.65.5
lcsStatusConfigLl2mRxDiscard OBJECT-TYPE
    SYNTAX     INTEGER (0..2147483647)
    MAX-ACCESS read-only
    STATUS     current
    DESCRIPTION
        "-- empty --"
    ::= { lcsStatusConfigLl2m 5 }

-- {SCALAR} 1712.1.11.65.6
lcsStatusConfigLl2mRxMalformed OBJECT-TYPE
    SYNTAX     INTEGER (0..2147483647)
    MAX-ACCESS read-only
    STATUS     current
    DESCRIPTION
        "-- empty --"
    ::= { lcsStatusConfigLl2m 6 }

-- {OID} 1712.1.11.65.20
lcsStatusConfigLl2mServer OBJECT IDENTIFIER ::= { lcsStatusConfigLl2m 20 }

-- {SCALAR} 1712.1.11.65.20.1
lcsStatusConfigLl2mServerRxPackets OBJECT-TYPE
    SYNTAX     INTEGER (0..2147483647)
    MAX-ACCESS read-only
    STATUS     current
    DESCRIPTION
        "-- empty --"
    ::= { lcsStatusConfigLl2mServer 1 }

-- {SCALAR} 1712.1.11.65.20.2
lcsStatusConfigLl2mServerRxBroadcastPackets OBJECT-TYPE
    SYNTAX     INTEGER (0..2147483647)
    MAX-ACCESS read-only
    STATUS     current
    DESCRIPTION
        "-- empty --"
    ::= { lcsStatusConfigLl2mServer 2 }

-- {SCALAR} 1712.1.11.65.20.3
lcsStatusConfigLl2mServerRxMulticastPackets OBJECT-TYPE
    SYNTAX     INTEGER (0..2147483647)
    MAX-ACCESS read-only
    STATUS     current
    DESCRIPTION
        "-- empty --"
    ::= { lcsStatusConfigLl2mServer 3 }

-- {SCALAR} 1712.1.11.65.20.4
lcsStatusConfigLl2mServerRxUnicastPackets OBJECT-TYPE
    SYNTAX     INTEGER (0..2147483647)
    MAX-ACCESS read-only
    STATUS     current
    DESCRIPTION
        "-- empty --"
    ::= { lcsStatusConfigLl2mServer 4 }

-- {SCALAR} 1712.1.11.65.20.5
lcsStatusConfigLl2mServerRxDiscard OBJECT-TYPE
    SYNTAX     INTEGER (0..2147483647)
    MAX-ACCESS read-only
    STATUS     current
    DESCRIPTION
        "-- empty --"
    ::= { lcsStatusConfigLl2mServer 5 }

-- {SCALAR} 1712.1.11.65.20.99
lcsStatusConfigLl2mServerDeleteValues OBJECT-TYPE
    SYNTAX     DisplayString
    MAX-ACCESS read-write
    STATUS     current
    DESCRIPTION
        "-- empty --"
    ::= { lcsStatusConfigLl2mServer 99 }

-- {OID} 1712.1.11.65.30
lcsStatusConfigLl2mClient OBJECT IDENTIFIER ::= { lcsStatusConfigLl2m 30 }

-- {SCALAR} 1712.1.11.65.30.1
lcsStatusConfigLl2mClientRxPackets OBJECT-TYPE
    SYNTAX     INTEGER (0..2147483647)
    MAX-ACCESS read-only
    STATUS     current
    DESCRIPTION
        "-- empty --"
    ::= { lcsStatusConfigLl2mClient 1 }

-- {SCALAR} 1712.1.11.65.30.2
lcsStatusConfigLl2mClientRxBroadcastPackets OBJECT-TYPE
    SYNTAX     INTEGER (0..2147483647)
    MAX-ACCESS read-only
    STATUS     current
    DESCRIPTION
        "-- empty --"
    ::= { lcsStatusConfigLl2mClient 2 }

-- {SCALAR} 1712.1.11.65.30.3
lcsStatusConfigLl2mClientRxMulticastPackets OBJECT-TYPE
    SYNTAX     INTEGER (0..2147483647)
    MAX-ACCESS read-only
    STATUS     current
    DESCRIPTION
        "-- empty --"
    ::= { lcsStatusConfigLl2mClient 3 }

-- {SCALAR} 1712.1.11.65.30.4
lcsStatusConfigLl2mClientRxUnicastPackets OBJECT-TYPE
    SYNTAX     INTEGER (0..2147483647)
    MAX-ACCESS read-only
    STATUS     current
    DESCRIPTION
        "-- empty --"
    ::= { lcsStatusConfigLl2mClient 4 }

-- {SCALAR} 1712.1.11.65.30.5
lcsStatusConfigLl2mClientRxDiscard OBJECT-TYPE
    SYNTAX     INTEGER (0..2147483647)
    MAX-ACCESS read-only
    STATUS     current
    DESCRIPTION
        "-- empty --"
    ::= { lcsStatusConfigLl2mClient 5 }

-- {SCALAR} 1712.1.11.65.30.99
lcsStatusConfigLl2mClientDeleteValues OBJECT-TYPE
    SYNTAX     DisplayString
    MAX-ACCESS read-write
    STATUS     current
    DESCRIPTION
        "-- empty --"
    ::= { lcsStatusConfigLl2mClient 99 }

-- {SCALAR} 1712.1.11.65.99
lcsStatusConfigLl2mDeleteValues OBJECT-TYPE
    SYNTAX     DisplayString
    MAX-ACCESS read-write
    STATUS     current
    DESCRIPTION
        "-- empty --"
    ::= { lcsStatusConfigLl2m 99 }

-- {SCALAR} 1712.1.11.11
lcsStatusConfigDeleteValues OBJECT-TYPE
    SYNTAX     DisplayString
    MAX-ACCESS read-write
    STATUS     current
    DESCRIPTION
        "-- empty --"
    ::= { lcsStatusConfig 11 }

-- {TABLE} 1712.1.11.12
lcsStatusConfigEventLogTable OBJECT-TYPE
    SYNTAX     SEQUENCE OF LcsStatusConfigEventLogEntry
    MAX-ACCESS not-accessible
    STATUS     current
    DESCRIPTION
        "-- empty --"
    ::= { lcsStatusConfig 12 }

-- {ENTRY} 1712.1.11.12.1
lcsStatusConfigEventLogEntry OBJECT-TYPE
    SYNTAX     LcsStatusConfigEventLogEntry
    MAX-ACCESS not-accessible
    STATUS     current
    DESCRIPTION
        ""
    INDEX {
        lcsStatusConfigEventLogEntryIdx
    }
    ::= { lcsStatusConfigEventLogTable 1 }

-- {SEQUENCE}
LcsStatusConfigEventLogEntry ::= SEQUENCE {
    lcsStatusConfigEventLogEntryIdx INTEGER,
    lcsStatusConfigEventLogEntrySystemTime DisplayString,
    lcsStatusConfigEventLogEntryEvent INTEGER,
    lcsStatusConfigEventLogEntryAccess INTEGER,
    lcsStatusConfigEventLogEntryIpAddressNew DisplayString,
    lcsStatusConfigEventLogEntryInfo1 DisplayString,
    lcsStatusConfigEventLogEntryInfo2 DisplayString
}

-- {COLUMN} 1712.1.11.12.1.1
lcsStatusConfigEventLogEntryIdx OBJECT-TYPE
    SYNTAX     INTEGER (0..255)
    MAX-ACCESS read-only
    STATUS     current
    DESCRIPTION
        "-- empty --"
    ::= { lcsStatusConfigEventLogEntry 1 }

-- {COLUMN} 1712.1.11.12.1.7
lcsStatusConfigEventLogEntrySystemTime OBJECT-TYPE
    SYNTAX     DisplayString (SIZE(0..19))
    MAX-ACCESS read-only
    STATUS     current
    DESCRIPTION
        "-- empty --"
    ::= { lcsStatusConfigEventLogEntry 7 }

-- {COLUMN} 1712.1.11.12.1.2
lcsStatusConfigEventLogEntryEvent OBJECT-TYPE
    SYNTAX     INTEGER
      {
        eFwUplStart (4), -- Firmware upload was started
        eUplsucc (5), -- Firmware or configuration upload successful
        eUplfailto (6), -- The upload of firmware or configuration failed: maximum time was exceeded
        eUplfailincl (7), -- The upload of firmware or configuration failed: incomplete configuration
        eUplfailbaddev (8), -- The upload of firmware or configuration failed: wrong device
        eUplinvversion (7000), -- The upload of firmware failed: invalid firmware version
        eUplfileexists (7001), -- The upload of file failed: file with this version already exists
        eLogin (9), -- Login to configuration successful
        eLogout (10), -- Logout from configuration was successful
        eCnfuplstart (11), -- Configuration upload was started
        eCnfdnlstart (12), -- Configuration download was started
        eScrptuplstart (79), -- script upload was started
        eScrptdnlstart (80), -- script download was started
        eCnfdnlsucc (13), -- Configuration download successful
        eErrlogin (29) -- Error during login to configuration
      }
    MAX-ACCESS read-only
    STATUS     current
    DESCRIPTION
        "-- empty --"
    ::= { lcsStatusConfigEventLogEntry 2 }

-- {COLUMN} 1712.1.11.12.1.3
lcsStatusConfigEventLogEntryAccess OBJECT-TYPE
    SYNTAX     INTEGER
      {
        eOutband (0),
        eTelnet (1),
        eTftp (2),
        eHttp (3),
        eSnmp (4),
        eHttps (5),
        eTelnetSsl (6),
        eSsh (7),
        eLl2m (8),
        ePpp (254),
        eUnknown (255)
      }
    MAX-ACCESS read-only
    STATUS     current
    DESCRIPTION
        "-- empty --"
    ::= { lcsStatusConfigEventLogEntry 3 }

-- {COLUMN} 1712.1.11.12.1.8
lcsStatusConfigEventLogEntryIpAddressNew OBJECT-TYPE
    SYNTAX     DisplayString (SIZE(0..255))
    MAX-ACCESS read-only
    STATUS     current
    DESCRIPTION
        ""
    ::= { lcsStatusConfigEventLogEntry 8 }

-- {COLUMN} 1712.1.11.12.1.5
lcsStatusConfigEventLogEntryInfo1 OBJECT-TYPE
    SYNTAX     DisplayString (SIZE(0..32))
    MAX-ACCESS read-only
    STATUS     current
    DESCRIPTION
        "-- empty --"
    ::= { lcsStatusConfigEventLogEntry 5 }

-- {COLUMN} 1712.1.11.12.1.6
lcsStatusConfigEventLogEntryInfo2 OBJECT-TYPE
    SYNTAX     DisplayString (SIZE(0..64))
    MAX-ACCESS read-only
    STATUS     current
    DESCRIPTION
        "-- empty --"
    ::= { lcsStatusConfigEventLogEntry 6 }

-- {OID} 1712.1.11.70
lcsStatusConfigDownloadStatus OBJECT IDENTIFIER ::= { lcsStatusConfig 70 }

-- {SCALAR} 1712.1.11.70.1
lcsStatusConfigDownloadStatusFirmwareSuccesses OBJECT-TYPE
    SYNTAX     INTEGER (0..2147483647)
    MAX-ACCESS read-only
    STATUS     current
    DESCRIPTION
        "-- empty --"
    ::= { lcsStatusConfigDownloadStatus 1 }

-- {SCALAR} 1712.1.11.70.2
lcsStatusConfigDownloadStatusFirmwareFailures OBJECT-TYPE
    SYNTAX     INTEGER (0..2147483647)
    MAX-ACCESS read-only
    STATUS     current
    DESCRIPTION
        "-- empty --"
    ::= { lcsStatusConfigDownloadStatus 2 }

-- {SCALAR} 1712.1.11.70.3
lcsStatusConfigDownloadStatusConfigurationSuccesses OBJECT-TYPE
    SYNTAX     INTEGER (0..2147483647)
    MAX-ACCESS read-only
    STATUS     current
    DESCRIPTION
        "-- empty --"
    ::= { lcsStatusConfigDownloadStatus 3 }

-- {SCALAR} 1712.1.11.70.4
lcsStatusConfigDownloadStatusConfigurationFailures OBJECT-TYPE
    SYNTAX     INTEGER (0..2147483647)
    MAX-ACCESS read-only
    STATUS     current
    DESCRIPTION
        "-- empty --"
    ::= { lcsStatusConfigDownloadStatus 4 }

-- {SCALAR} 1712.1.11.70.5
lcsStatusConfigDownloadStatusScriptSuccesses OBJECT-TYPE
    SYNTAX     INTEGER (0..2147483647)
    MAX-ACCESS read-only
    STATUS     current
    DESCRIPTION
        "-- empty --"
    ::= { lcsStatusConfigDownloadStatus 5 }

-- {SCALAR} 1712.1.11.70.6
lcsStatusConfigDownloadStatusScriptFailures OBJECT-TYPE
    SYNTAX     INTEGER (0..2147483647)
    MAX-ACCESS read-only
    STATUS     current
    DESCRIPTION
        "-- empty --"
    ::= { lcsStatusConfigDownloadStatus 6 }

-- {SCALAR} 1712.1.11.70.7
lcsStatusConfigDownloadStatusFileSuccesses OBJECT-TYPE
    SYNTAX     INTEGER (0..2147483647)
    MAX-ACCESS read-only
    STATUS     current
    DESCRIPTION
        "-- empty --"
    ::= { lcsStatusConfigDownloadStatus 7 }

-- {SCALAR} 1712.1.11.70.8
lcsStatusConfigDownloadStatusFileFailures OBJECT-TYPE
    SYNTAX     INTEGER (0..2147483647)
    MAX-ACCESS read-only
    STATUS     current
    DESCRIPTION
        "-- empty --"
    ::= { lcsStatusConfigDownloadStatus 8 }

-- {TABLE} 1712.1.11.70.20
lcsStatusConfigDownloadStatusLastOperationsTable OBJECT-TYPE
    SYNTAX     SEQUENCE OF LcsStatusConfigDownloadStatusLastOperationsEntry
    MAX-ACCESS not-accessible
    STATUS     current
    DESCRIPTION
        "-- empty --"
    ::= { lcsStatusConfigDownloadStatus 20 }

-- {ENTRY} 1712.1.11.70.20.1
lcsStatusConfigDownloadStatusLastOperationsEntry OBJECT-TYPE
    SYNTAX     LcsStatusConfigDownloadStatusLastOperationsEntry
    MAX-ACCESS not-accessible
    STATUS     current
    DESCRIPTION
        ""
    INDEX {
        lcsStatusConfigDownloadStatusLastOperationsEntryIndex
    }
    ::= { lcsStatusConfigDownloadStatusLastOperationsTable 1 }

-- {SEQUENCE}
LcsStatusConfigDownloadStatusLastOperationsEntry ::= SEQUENCE {
    lcsStatusConfigDownloadStatusLastOperationsEntryIndex INTEGER,
    lcsStatusConfigDownloadStatusLastOperationsEntryIdentifier INTEGER,
    lcsStatusConfigDownloadStatusLastOperationsEntryType INTEGER,
    lcsStatusConfigDownloadStatusLastOperationsEntryUrl DisplayString,
    lcsStatusConfigDownloadStatusLastOperationsEntryStatus INTEGER,
    lcsStatusConfigDownloadStatusLastOperationsEntryFailureReason DisplayString
}

-- {COLUMN} 1712.1.11.70.20.1.1
lcsStatusConfigDownloadStatusLastOperationsEntryIndex OBJECT-TYPE
    SYNTAX     INTEGER (0..2147483647)
    MAX-ACCESS read-only
    STATUS     current
    DESCRIPTION
        "-- empty --"
    ::= { lcsStatusConfigDownloadStatusLastOperationsEntry 1 }

-- {COLUMN} 1712.1.11.70.20.1.2
lcsStatusConfigDownloadStatusLastOperationsEntryIdentifier OBJECT-TYPE
    SYNTAX     INTEGER (0..2147483647)
    MAX-ACCESS read-only
    STATUS     current
    DESCRIPTION
        "-- empty --"
    ::= { lcsStatusConfigDownloadStatusLastOperationsEntry 2 }

-- {COLUMN} 1712.1.11.70.20.1.3
lcsStatusConfigDownloadStatusLastOperationsEntryType OBJECT-TYPE
    SYNTAX     INTEGER
      {
        eFirmware (1),
        eConfiguration (0),
        eScript (2),
        eFile (3)
      }
    MAX-ACCESS read-only
    STATUS     current
    DESCRIPTION
        "-- empty --"
    ::= { lcsStatusConfigDownloadStatusLastOperationsEntry 3 }

-- {COLUMN} 1712.1.11.70.20.1.4
lcsStatusConfigDownloadStatusLastOperationsEntryUrl OBJECT-TYPE
    SYNTAX     DisplayString (SIZE(0..252))
    MAX-ACCESS read-only
    STATUS     current
    DESCRIPTION
        "-- empty --"
    ::= { lcsStatusConfigDownloadStatusLastOperationsEntry 4 }

-- {COLUMN} 1712.1.11.70.20.1.5
lcsStatusConfigDownloadStatusLastOperationsEntryStatus OBJECT-TYPE
    SYNTAX     INTEGER
      {
        eIdle (0),
        ePending (1),
        eSuccess (2),
        eFailure (3),
        eUnknown (4)
      }
    MAX-ACCESS read-only
    STATUS     current
    DESCRIPTION
        "-- empty --"
    ::= { lcsStatusConfigDownloadStatusLastOperationsEntry 5 }

-- {COLUMN} 1712.1.11.70.20.1.6
lcsStatusConfigDownloadStatusLastOperationsEntryFailureReason OBJECT-TYPE
    SYNTAX     DisplayString (SIZE(0..100))
    MAX-ACCESS read-only
    STATUS     current
    DESCRIPTION
        "-- empty --"
    ::= { lcsStatusConfigDownloadStatusLastOperationsEntry 6 }

-- {SCALAR} 1712.1.11.70.99
lcsStatusConfigDownloadStatusDeleteValues OBJECT-TYPE
    SYNTAX     DisplayString
    MAX-ACCESS read-write
    STATUS     current
    DESCRIPTION
        "-- empty --"
    ::= { lcsStatusConfigDownloadStatus 99 }

-- {OID} 1712.1.56
lcsStatusAccounting OBJECT IDENTIFIER ::= { lcsStatus 56 }

-- {TABLE} 1712.1.56.1
lcsStatusAccountingCurrentUserTable OBJECT-TYPE
    SYNTAX     SEQUENCE OF LcsStatusAccountingCurrentUserEntry
    MAX-ACCESS not-accessible
    STATUS     current
    DESCRIPTION
        "-- empty --"
    ::= { lcsStatusAccounting 1 }

-- {ENTRY} 1712.1.56.1.1
lcsStatusAccountingCurrentUserEntry OBJECT-TYPE
    SYNTAX     LcsStatusAccountingCurrentUserEntry
    MAX-ACCESS not-accessible
    STATUS     current
    DESCRIPTION
        ""
    INDEX {
        lcsStatusAccountingCurrentUserEntryUsername,
        lcsStatusAccountingCurrentUserEntryMacAddress,
        lcsStatusAccountingCurrentUserEntryPeer,
        lcsStatusAccountingCurrentUserEntryConnType
    }
    ::= { lcsStatusAccountingCurrentUserTable 1 }

-- {SEQUENCE}
LcsStatusAccountingCurrentUserEntry ::= SEQUENCE {
    lcsStatusAccountingCurrentUserEntryUsername DisplayString,
    lcsStatusAccountingCurrentUserEntryMacAddress DisplayString,
    lcsStatusAccountingCurrentUserEntryPeer DisplayString,
    lcsStatusAccountingCurrentUserEntryConnType INTEGER,
    lcsStatusAccountingCurrentUserEntryRxKbytes INTEGER,
    lcsStatusAccountingCurrentUserEntryTxKbytes INTEGER,
    lcsStatusAccountingCurrentUserEntryTotalTime Gauge32,
    lcsStatusAccountingCurrentUserEntryConnections INTEGER
}

-- {COLUMN} 1712.1.56.1.1.1
lcsStatusAccountingCurrentUserEntryUsername OBJECT-TYPE
    SYNTAX     DisplayString (SIZE(0..28))
    MAX-ACCESS read-only
    STATUS     current
    DESCRIPTION
        "-- empty --"
    ::= { lcsStatusAccountingCurrentUserEntry 1 }

-- {COLUMN} 1712.1.56.1.1.2
lcsStatusAccountingCurrentUserEntryMacAddress OBJECT-TYPE
    SYNTAX     DisplayString (SIZE(0..255))
    MAX-ACCESS read-only
    STATUS     current
    DESCRIPTION
        "-- empty --"
    ::= { lcsStatusAccountingCurrentUserEntry 2 }

-- {COLUMN} 1712.1.56.1.1.3
lcsStatusAccountingCurrentUserEntryPeer OBJECT-TYPE
    SYNTAX     DisplayString (SIZE(0..16))
    MAX-ACCESS read-only
    STATUS     current
    DESCRIPTION
        "-- empty --"
    ::= { lcsStatusAccountingCurrentUserEntry 3 }

-- {COLUMN} 1712.1.56.1.1.4
lcsStatusAccountingCurrentUserEntryConnType OBJECT-TYPE
    SYNTAX     INTEGER
      {
        eUnknown (0),
        eDialUp (1),
        eLeasedLine (2),
        eDslLine (4),
        eVpnConn (7),
        ePptpConn (8),
        eL2tpConn (9),
        eDsLiteConn (10)
      }
    MAX-ACCESS read-only
    STATUS     current
    DESCRIPTION
        "-- empty --"
    ::= { lcsStatusAccountingCurrentUserEntry 4 }

-- {COLUMN} 1712.1.56.1.1.5
lcsStatusAccountingCurrentUserEntryRxKbytes OBJECT-TYPE
    SYNTAX     INTEGER (0..2147483647)
    MAX-ACCESS read-only
    STATUS     current
    DESCRIPTION
        "-- empty --"
    ::= { lcsStatusAccountingCurrentUserEntry 5 }

-- {COLUMN} 1712.1.56.1.1.6
lcsStatusAccountingCurrentUserEntryTxKbytes OBJECT-TYPE
    SYNTAX     INTEGER (0..2147483647)
    MAX-ACCESS read-only
    STATUS     current
    DESCRIPTION
        "-- empty --"
    ::= { lcsStatusAccountingCurrentUserEntry 6 }

-- {COLUMN} 1712.1.56.1.1.8
lcsStatusAccountingCurrentUserEntryTotalTime OBJECT-TYPE
    SYNTAX     Gauge32
    MAX-ACCESS read-only
    STATUS     current
    DESCRIPTION
        "-- empty --"
    ::= { lcsStatusAccountingCurrentUserEntry 8 }

-- {COLUMN} 1712.1.56.1.1.9
lcsStatusAccountingCurrentUserEntryConnections OBJECT-TYPE
    SYNTAX     INTEGER (0..2147483647)
    MAX-ACCESS read-only
    STATUS     current
    DESCRIPTION
        "-- empty --"
    ::= { lcsStatusAccountingCurrentUserEntry 9 }

-- {TABLE} 1712.1.56.2
lcsStatusAccountingAccountingListTable OBJECT-TYPE
    SYNTAX     SEQUENCE OF LcsStatusAccountingAccountingListEntry
    MAX-ACCESS not-accessible
    STATUS     current
    DESCRIPTION
        "-- empty --"
    ::= { lcsStatusAccounting 2 }

-- {ENTRY} 1712.1.56.2.1
lcsStatusAccountingAccountingListEntry OBJECT-TYPE
    SYNTAX     LcsStatusAccountingAccountingListEntry
    MAX-ACCESS not-accessible
    STATUS     current
    DESCRIPTION
        ""
    INDEX {
        lcsStatusAccountingAccountingListEntryUsername,
        lcsStatusAccountingAccountingListEntryMacAddress,
        lcsStatusAccountingAccountingListEntryPeer,
        lcsStatusAccountingAccountingListEntryConnType
    }
    ::= { lcsStatusAccountingAccountingListTable 1 }

-- {SEQUENCE}
LcsStatusAccountingAccountingListEntry ::= SEQUENCE {
    lcsStatusAccountingAccountingListEntryUsername DisplayString,
    lcsStatusAccountingAccountingListEntryMacAddress DisplayString,
    lcsStatusAccountingAccountingListEntryPeer DisplayString,
    lcsStatusAccountingAccountingListEntryConnType INTEGER,
    lcsStatusAccountingAccountingListEntryRxKbytes INTEGER,
    lcsStatusAccountingAccountingListEntryTxKbytes INTEGER,
    lcsStatusAccountingAccountingListEntryTotalTime Gauge32,
    lcsStatusAccountingAccountingListEntryConnections INTEGER
}

-- {COLUMN} 1712.1.56.2.1.1
lcsStatusAccountingAccountingListEntryUsername OBJECT-TYPE
    SYNTAX     DisplayString (SIZE(0..28))
    MAX-ACCESS read-only
    STATUS     current
    DESCRIPTION
        "-- empty --"
    ::= { lcsStatusAccountingAccountingListEntry 1 }

-- {COLUMN} 1712.1.56.2.1.2
lcsStatusAccountingAccountingListEntryMacAddress OBJECT-TYPE
    SYNTAX     DisplayString (SIZE(0..255))
    MAX-ACCESS read-only
    STATUS     current
    DESCRIPTION
        "-- empty --"
    ::= { lcsStatusAccountingAccountingListEntry 2 }

-- {COLUMN} 1712.1.56.2.1.3
lcsStatusAccountingAccountingListEntryPeer OBJECT-TYPE
    SYNTAX     DisplayString (SIZE(0..16))
    MAX-ACCESS read-only
    STATUS     current
    DESCRIPTION
        "-- empty --"
    ::= { lcsStatusAccountingAccountingListEntry 3 }

-- {COLUMN} 1712.1.56.2.1.4
lcsStatusAccountingAccountingListEntryConnType OBJECT-TYPE
    SYNTAX     INTEGER
      {
        eUnknown (0),
        eDialUp (1),
        eLeasedLine (2),
        eDslLine (4),
        eVpnConn (7),
        ePptpConn (8),
        eL2tpConn (9),
        eDsLiteConn (10)
      }
    MAX-ACCESS read-only
    STATUS     current
    DESCRIPTION
        "-- empty --"
    ::= { lcsStatusAccountingAccountingListEntry 4 }

-- {COLUMN} 1712.1.56.2.1.5
lcsStatusAccountingAccountingListEntryRxKbytes OBJECT-TYPE
    SYNTAX     INTEGER (0..2147483647)
    MAX-ACCESS read-only
    STATUS     current
    DESCRIPTION
        "-- empty --"
    ::= { lcsStatusAccountingAccountingListEntry 5 }

-- {COLUMN} 1712.1.56.2.1.6
lcsStatusAccountingAccountingListEntryTxKbytes OBJECT-TYPE
    SYNTAX     INTEGER (0..2147483647)
    MAX-ACCESS read-only
    STATUS     current
    DESCRIPTION
        "-- empty --"
    ::= { lcsStatusAccountingAccountingListEntry 6 }

-- {COLUMN} 1712.1.56.2.1.8
lcsStatusAccountingAccountingListEntryTotalTime OBJECT-TYPE
    SYNTAX     Gauge32
    MAX-ACCESS read-only
    STATUS     current
    DESCRIPTION
        "-- empty --"
    ::= { lcsStatusAccountingAccountingListEntry 8 }

-- {COLUMN} 1712.1.56.2.1.9
lcsStatusAccountingAccountingListEntryConnections OBJECT-TYPE
    SYNTAX     INTEGER (0..2147483647)
    MAX-ACCESS read-only
    STATUS     current
    DESCRIPTION
        "-- empty --"
    ::= { lcsStatusAccountingAccountingListEntry 9 }

-- {TABLE} 1712.1.56.3
lcsStatusAccountingLastSnapshotTable OBJECT-TYPE
    SYNTAX     SEQUENCE OF LcsStatusAccountingLastSnapshotEntry
    MAX-ACCESS not-accessible
    STATUS     current
    DESCRIPTION
        "-- empty --"
    ::= { lcsStatusAccounting 3 }

-- {ENTRY} 1712.1.56.3.1
lcsStatusAccountingLastSnapshotEntry OBJECT-TYPE
    SYNTAX     LcsStatusAccountingLastSnapshotEntry
    MAX-ACCESS not-accessible
    STATUS     current
    DESCRIPTION
        ""
    INDEX {
        lcsStatusAccountingLastSnapshotEntryUsername,
        lcsStatusAccountingLastSnapshotEntryMacAddress,
        lcsStatusAccountingLastSnapshotEntryPeer,
        lcsStatusAccountingLastSnapshotEntryConnType
    }
    ::= { lcsStatusAccountingLastSnapshotTable 1 }

-- {SEQUENCE}
LcsStatusAccountingLastSnapshotEntry ::= SEQUENCE {
    lcsStatusAccountingLastSnapshotEntryUsername DisplayString,
    lcsStatusAccountingLastSnapshotEntryMacAddress DisplayString,
    lcsStatusAccountingLastSnapshotEntryPeer DisplayString,
    lcsStatusAccountingLastSnapshotEntryConnType INTEGER,
    lcsStatusAccountingLastSnapshotEntryRxKbytes INTEGER,
    lcsStatusAccountingLastSnapshotEntryTxKbytes INTEGER,
    lcsStatusAccountingLastSnapshotEntryTotalTime Gauge32,
    lcsStatusAccountingLastSnapshotEntryConnections INTEGER
}

-- {COLUMN} 1712.1.56.3.1.1
lcsStatusAccountingLastSnapshotEntryUsername OBJECT-TYPE
    SYNTAX     DisplayString (SIZE(0..28))
    MAX-ACCESS read-only
    STATUS     current
    DESCRIPTION
        "-- empty --"
    ::= { lcsStatusAccountingLastSnapshotEntry 1 }

-- {COLUMN} 1712.1.56.3.1.2
lcsStatusAccountingLastSnapshotEntryMacAddress OBJECT-TYPE
    SYNTAX     DisplayString (SIZE(0..255))
    MAX-ACCESS read-only
    STATUS     current
    DESCRIPTION
        "-- empty --"
    ::= { lcsStatusAccountingLastSnapshotEntry 2 }

-- {COLUMN} 1712.1.56.3.1.3
lcsStatusAccountingLastSnapshotEntryPeer OBJECT-TYPE
    SYNTAX     DisplayString (SIZE(0..16))
    MAX-ACCESS read-only
    STATUS     current
    DESCRIPTION
        "-- empty --"
    ::= { lcsStatusAccountingLastSnapshotEntry 3 }

-- {COLUMN} 1712.1.56.3.1.4
lcsStatusAccountingLastSnapshotEntryConnType OBJECT-TYPE
    SYNTAX     INTEGER
      {
        eUnknown (0),
        eDialUp (1),
        eLeasedLine (2),
        eDslLine (4),
        eVpnConn (7),
        ePptpConn (8),
        eL2tpConn (9),
        eDsLiteConn (10)
      }
    MAX-ACCESS read-only
    STATUS     current
    DESCRIPTION
        "-- empty --"
    ::= { lcsStatusAccountingLastSnapshotEntry 4 }

-- {COLUMN} 1712.1.56.3.1.5
lcsStatusAccountingLastSnapshotEntryRxKbytes OBJECT-TYPE
    SYNTAX     INTEGER (0..2147483647)
    MAX-ACCESS read-only
    STATUS     current
    DESCRIPTION
        "-- empty --"
    ::= { lcsStatusAccountingLastSnapshotEntry 5 }

-- {COLUMN} 1712.1.56.3.1.6
lcsStatusAccountingLastSnapshotEntryTxKbytes OBJECT-TYPE
    SYNTAX     INTEGER (0..2147483647)
    MAX-ACCESS read-only
    STATUS     current
    DESCRIPTION
        "-- empty --"
    ::= { lcsStatusAccountingLastSnapshotEntry 6 }

-- {COLUMN} 1712.1.56.3.1.8
lcsStatusAccountingLastSnapshotEntryTotalTime OBJECT-TYPE
    SYNTAX     Gauge32
    MAX-ACCESS read-only
    STATUS     current
    DESCRIPTION
        "-- empty --"
    ::= { lcsStatusAccountingLastSnapshotEntry 8 }

-- {COLUMN} 1712.1.56.3.1.9
lcsStatusAccountingLastSnapshotEntryConnections OBJECT-TYPE
    SYNTAX     INTEGER (0..2147483647)
    MAX-ACCESS read-only
    STATUS     current
    DESCRIPTION
        "-- empty --"
    ::= { lcsStatusAccountingLastSnapshotEntry 9 }

-- {TABLE} 1712.1.56.5
lcsStatusAccountingTimeLastSnapshotTable OBJECT-TYPE
    SYNTAX     SEQUENCE OF LcsStatusAccountingTimeLastSnapshotEntry
    MAX-ACCESS not-accessible
    STATUS     current
    DESCRIPTION
        "-- empty --"
    ::= { lcsStatusAccounting 5 }

-- {ENTRY} 1712.1.56.5.1
lcsStatusAccountingTimeLastSnapshotEntry OBJECT-TYPE
    SYNTAX     LcsStatusAccountingTimeLastSnapshotEntry
    MAX-ACCESS not-accessible
    STATUS     current
    DESCRIPTION
        ""
    INDEX {
        lcsStatusAccountingTimeLastSnapshotEntrySystemTime
    }
    ::= { lcsStatusAccountingTimeLastSnapshotTable 1 }

-- {SEQUENCE}
LcsStatusAccountingTimeLastSnapshotEntry ::= SEQUENCE {
    lcsStatusAccountingTimeLastSnapshotEntrySystemTime Counter32
}

-- {COLUMN} 1712.1.56.5.1.1
lcsStatusAccountingTimeLastSnapshotEntrySystemTime OBJECT-TYPE
    SYNTAX     Counter32
    MAX-ACCESS read-only
    STATUS     current
    DESCRIPTION
        "-- empty --"
    ::= { lcsStatusAccountingTimeLastSnapshotEntry 1 }

-- {SCALAR} 1712.1.56.4
lcsStatusAccountingDeleteValues OBJECT-TYPE
    SYNTAX     DisplayString
    MAX-ACCESS read-write
    STATUS     current
    DESCRIPTION
        "-- empty --"
    ::= { lcsStatusAccounting 4 }

-- {OID} 1712.1.61
lcsStatusCerts OBJECT IDENTIFIER ::= { lcsStatus 61 }

-- {OID} 1712.1.61.1
lcsStatusCertsScepClnt OBJECT IDENTIFIER ::= { lcsStatusCerts 1 }

-- {TABLE} 1712.1.61.1.4
lcsStatusCertsScepClntCasTable OBJECT-TYPE
    SYNTAX     SEQUENCE OF LcsStatusCertsScepClntCasEntry
    MAX-ACCESS not-accessible
    STATUS     current
    DESCRIPTION
        "-- empty --"
    ::= { lcsStatusCertsScepClnt 4 }

-- {ENTRY} 1712.1.61.1.4.1
lcsStatusCertsScepClntCasEntry OBJECT-TYPE
    SYNTAX     LcsStatusCertsScepClntCasEntry
    MAX-ACCESS not-accessible
    STATUS     current
    DESCRIPTION
        ""
    INDEX {
        lcsStatusCertsScepClntCasEntryIdx
    }
    ::= { lcsStatusCertsScepClntCasTable 1 }

-- {SEQUENCE}
LcsStatusCertsScepClntCasEntry ::= SEQUENCE {
    lcsStatusCertsScepClntCasEntryIdx INTEGER,
    lcsStatusCertsScepClntCasEntryName DisplayString,
    lcsStatusCertsScepClntCasEntryExpires DisplayString,
    lcsStatusCertsScepClntCasEntryIssued DisplayString,
    lcsStatusCertsScepClntCasEntryKeyUsage DisplayString,
    lcsStatusCertsScepClntCasEntryIssuer DisplayString,
    lcsStatusCertsScepClntCasEntrySubject DisplayString,
    lcsStatusCertsScepClntCasEntryStatus DisplayString,
    lcsStatusCertsScepClntCasEntryIkeCertificate DisplayString,
    lcsStatusCertsScepClntCasEntryMd5Fingerprint DisplayString,
    lcsStatusCertsScepClntCasEntrySha1Fingerprint DisplayString,
    lcsStatusCertsScepClntCasEntryExpSnmp Counter32,
    lcsStatusCertsScepClntCasEntryIssSnmp Counter32
}

-- {COLUMN} 1712.1.61.1.4.1.1
lcsStatusCertsScepClntCasEntryIdx OBJECT-TYPE
    SYNTAX     INTEGER (0..2147483647)
    MAX-ACCESS read-only
    STATUS     current
    DESCRIPTION
        "-- empty --"
    ::= { lcsStatusCertsScepClntCasEntry 1 }

-- {COLUMN} 1712.1.61.1.4.1.2
lcsStatusCertsScepClntCasEntryName OBJECT-TYPE
    SYNTAX     DisplayString (SIZE(0..255))
    MAX-ACCESS read-only
    STATUS     current
    DESCRIPTION
        "-- empty --"
    ::= { lcsStatusCertsScepClntCasEntry 2 }

-- {COLUMN} 1712.1.61.1.4.1.3
lcsStatusCertsScepClntCasEntryExpires OBJECT-TYPE
    SYNTAX     DisplayString (SIZE(0..255))
    MAX-ACCESS read-only
    STATUS     current
    DESCRIPTION
        "-- empty --"
    ::= { lcsStatusCertsScepClntCasEntry 3 }

-- {COLUMN} 1712.1.61.1.4.1.4
lcsStatusCertsScepClntCasEntryIssued OBJECT-TYPE
    SYNTAX     DisplayString (SIZE(0..255))
    MAX-ACCESS read-only
    STATUS     current
    DESCRIPTION
        "-- empty --"
    ::= { lcsStatusCertsScepClntCasEntry 4 }

-- {COLUMN} 1712.1.61.1.4.1.5
lcsStatusCertsScepClntCasEntryKeyUsage OBJECT-TYPE
    SYNTAX     DisplayString (SIZE(0..255))
    MAX-ACCESS read-only
    STATUS     current
    DESCRIPTION
        "-- empty --"
    ::= { lcsStatusCertsScepClntCasEntry 5 }

-- {COLUMN} 1712.1.61.1.4.1.6
lcsStatusCertsScepClntCasEntryIssuer OBJECT-TYPE
    SYNTAX     DisplayString (SIZE(0..255))
    MAX-ACCESS read-only
    STATUS     current
    DESCRIPTION
        "-- empty --"
    ::= { lcsStatusCertsScepClntCasEntry 6 }

-- {COLUMN} 1712.1.61.1.4.1.7
lcsStatusCertsScepClntCasEntrySubject OBJECT-TYPE
    SYNTAX     DisplayString (SIZE(0..255))
    MAX-ACCESS read-only
    STATUS     current
    DESCRIPTION
        "-- empty --"
    ::= { lcsStatusCertsScepClntCasEntry 7 }

-- {COLUMN} 1712.1.61.1.4.1.8
lcsStatusCertsScepClntCasEntryStatus OBJECT-TYPE
    SYNTAX     DisplayString (SIZE(0..255))
    MAX-ACCESS read-only
    STATUS     current
    DESCRIPTION
        "-- empty --"
    ::= { lcsStatusCertsScepClntCasEntry 8 }

-- {COLUMN} 1712.1.61.1.4.1.9
lcsStatusCertsScepClntCasEntryIkeCertificate OBJECT-TYPE
    SYNTAX     DisplayString (SIZE(0..255))
    MAX-ACCESS read-only
    STATUS     current
    DESCRIPTION
        "-- empty --"
    ::= { lcsStatusCertsScepClntCasEntry 9 }

-- {COLUMN} 1712.1.61.1.4.1.10
lcsStatusCertsScepClntCasEntryMd5Fingerprint OBJECT-TYPE
    SYNTAX     DisplayString (SIZE(0..255))
    MAX-ACCESS read-only
    STATUS     current
    DESCRIPTION
        "-- empty --"
    ::= { lcsStatusCertsScepClntCasEntry 10 }

-- {COLUMN} 1712.1.61.1.4.1.11
lcsStatusCertsScepClntCasEntrySha1Fingerprint OBJECT-TYPE
    SYNTAX     DisplayString (SIZE(0..255))
    MAX-ACCESS read-only
    STATUS     current
    DESCRIPTION
        "-- empty --"
    ::= { lcsStatusCertsScepClntCasEntry 11 }

-- {COLUMN} 1712.1.61.1.4.1.12
lcsStatusCertsScepClntCasEntryExpSnmp OBJECT-TYPE
    SYNTAX     Counter32
    MAX-ACCESS read-only
    STATUS     current
    DESCRIPTION
        "-- empty --"
    ::= { lcsStatusCertsScepClntCasEntry 12 }

-- {COLUMN} 1712.1.61.1.4.1.13
lcsStatusCertsScepClntCasEntryIssSnmp OBJECT-TYPE
    SYNTAX     Counter32
    MAX-ACCESS read-only
    STATUS     current
    DESCRIPTION
        "-- empty --"
    ::= { lcsStatusCertsScepClntCasEntry 13 }

-- {TABLE} 1712.1.61.1.5
lcsStatusCertsScepClntRasTable OBJECT-TYPE
    SYNTAX     SEQUENCE OF LcsStatusCertsScepClntRasEntry
    MAX-ACCESS not-accessible
    STATUS     current
    DESCRIPTION
        "-- empty --"
    ::= { lcsStatusCertsScepClnt 5 }

-- {ENTRY} 1712.1.61.1.5.1
lcsStatusCertsScepClntRasEntry OBJECT-TYPE
    SYNTAX     LcsStatusCertsScepClntRasEntry
    MAX-ACCESS not-accessible
    STATUS     current
    DESCRIPTION
        ""
    INDEX {
        lcsStatusCertsScepClntRasEntryIdx
    }
    ::= { lcsStatusCertsScepClntRasTable 1 }

-- {SEQUENCE}
LcsStatusCertsScepClntRasEntry ::= SEQUENCE {
    lcsStatusCertsScepClntRasEntryIdx INTEGER,
    lcsStatusCertsScepClntRasEntryName DisplayString,
    lcsStatusCertsScepClntRasEntryExpires DisplayString,
    lcsStatusCertsScepClntRasEntryIssued DisplayString,
    lcsStatusCertsScepClntRasEntryKeyUsage DisplayString,
    lcsStatusCertsScepClntRasEntryIssuer DisplayString,
    lcsStatusCertsScepClntRasEntrySubject DisplayString,
    lcsStatusCertsScepClntRasEntryStatus DisplayString,
    lcsStatusCertsScepClntRasEntryExpSnmp Counter32,
    lcsStatusCertsScepClntRasEntryIssSnmp Counter32
}

-- {COLUMN} 1712.1.61.1.5.1.1
lcsStatusCertsScepClntRasEntryIdx OBJECT-TYPE
    SYNTAX     INTEGER (0..2147483647)
    MAX-ACCESS read-only
    STATUS     current
    DESCRIPTION
        "-- empty --"
    ::= { lcsStatusCertsScepClntRasEntry 1 }

-- {COLUMN} 1712.1.61.1.5.1.2
lcsStatusCertsScepClntRasEntryName OBJECT-TYPE
    SYNTAX     DisplayString (SIZE(0..255))
    MAX-ACCESS read-only
    STATUS     current
    DESCRIPTION
        "-- empty --"
    ::= { lcsStatusCertsScepClntRasEntry 2 }

-- {COLUMN} 1712.1.61.1.5.1.3
lcsStatusCertsScepClntRasEntryExpires OBJECT-TYPE
    SYNTAX     DisplayString (SIZE(0..255))
    MAX-ACCESS read-only
    STATUS     current
    DESCRIPTION
        "-- empty --"
    ::= { lcsStatusCertsScepClntRasEntry 3 }

-- {COLUMN} 1712.1.61.1.5.1.4
lcsStatusCertsScepClntRasEntryIssued OBJECT-TYPE
    SYNTAX     DisplayString (SIZE(0..255))
    MAX-ACCESS read-only
    STATUS     current
    DESCRIPTION
        "-- empty --"
    ::= { lcsStatusCertsScepClntRasEntry 4 }

-- {COLUMN} 1712.1.61.1.5.1.5
lcsStatusCertsScepClntRasEntryKeyUsage OBJECT-TYPE
    SYNTAX     DisplayString (SIZE(0..255))
    MAX-ACCESS read-only
    STATUS     current
    DESCRIPTION
        "-- empty --"
    ::= { lcsStatusCertsScepClntRasEntry 5 }

-- {COLUMN} 1712.1.61.1.5.1.6
lcsStatusCertsScepClntRasEntryIssuer OBJECT-TYPE
    SYNTAX     DisplayString (SIZE(0..255))
    MAX-ACCESS read-only
    STATUS     current
    DESCRIPTION
        "-- empty --"
    ::= { lcsStatusCertsScepClntRasEntry 6 }

-- {COLUMN} 1712.1.61.1.5.1.7
lcsStatusCertsScepClntRasEntrySubject OBJECT-TYPE
    SYNTAX     DisplayString (SIZE(0..255))
    MAX-ACCESS read-only
    STATUS     current
    DESCRIPTION
        "-- empty --"
    ::= { lcsStatusCertsScepClntRasEntry 7 }

-- {COLUMN} 1712.1.61.1.5.1.8
lcsStatusCertsScepClntRasEntryStatus OBJECT-TYPE
    SYNTAX     DisplayString (SIZE(0..255))
    MAX-ACCESS read-only
    STATUS     current
    DESCRIPTION
        "-- empty --"
    ::= { lcsStatusCertsScepClntRasEntry 8 }

-- {COLUMN} 1712.1.61.1.5.1.9
lcsStatusCertsScepClntRasEntryExpSnmp OBJECT-TYPE
    SYNTAX     Counter32
    MAX-ACCESS read-only
    STATUS     current
    DESCRIPTION
        "-- empty --"
    ::= { lcsStatusCertsScepClntRasEntry 9 }

-- {COLUMN} 1712.1.61.1.5.1.10
lcsStatusCertsScepClntRasEntryIssSnmp OBJECT-TYPE
    SYNTAX     Counter32
    MAX-ACCESS read-only
    STATUS     current
    DESCRIPTION
        "-- empty --"
    ::= { lcsStatusCertsScepClntRasEntry 10 }

-- {TABLE} 1712.1.61.1.6
lcsStatusCertsScepClntCertsTable OBJECT-TYPE
    SYNTAX     SEQUENCE OF LcsStatusCertsScepClntCertsEntry
    MAX-ACCESS not-accessible
    STATUS     current
    DESCRIPTION
        "-- empty --"
    ::= { lcsStatusCertsScepClnt 6 }

-- {ENTRY} 1712.1.61.1.6.1
lcsStatusCertsScepClntCertsEntry OBJECT-TYPE
    SYNTAX     LcsStatusCertsScepClntCertsEntry
    MAX-ACCESS not-accessible
    STATUS     current
    DESCRIPTION
        ""
    INDEX {
        lcsStatusCertsScepClntCertsEntryIdx
    }
    ::= { lcsStatusCertsScepClntCertsTable 1 }

-- {SEQUENCE}
LcsStatusCertsScepClntCertsEntry ::= SEQUENCE {
    lcsStatusCertsScepClntCertsEntryIdx INTEGER,
    lcsStatusCertsScepClntCertsEntryName DisplayString,
    lcsStatusCertsScepClntCertsEntryExpires DisplayString,
    lcsStatusCertsScepClntCertsEntryIssued DisplayString,
    lcsStatusCertsScepClntCertsEntryKeyUsage DisplayString,
    lcsStatusCertsScepClntCertsEntryExtendedKeyusage DisplayString,
    lcsStatusCertsScepClntCertsEntrySubjectaltname DisplayString,
    lcsStatusCertsScepClntCertsEntryIssuer DisplayString,
    lcsStatusCertsScepClntCertsEntrySubject DisplayString,
    lcsStatusCertsScepClntCertsEntryStatus DisplayString,
    lcsStatusCertsScepClntCertsEntryExpSnmp Counter32,
    lcsStatusCertsScepClntCertsEntryIssSnmp Counter32,
    lcsStatusCertsScepClntCertsEntryFilename DisplayString
}

-- {COLUMN} 1712.1.61.1.6.1.1
lcsStatusCertsScepClntCertsEntryIdx OBJECT-TYPE
    SYNTAX     INTEGER (0..2147483647)
    MAX-ACCESS read-only
    STATUS     current
    DESCRIPTION
        "-- empty --"
    ::= { lcsStatusCertsScepClntCertsEntry 1 }

-- {COLUMN} 1712.1.61.1.6.1.2
lcsStatusCertsScepClntCertsEntryName OBJECT-TYPE
    SYNTAX     DisplayString (SIZE(0..255))
    MAX-ACCESS read-only
    STATUS     current
    DESCRIPTION
        "-- empty --"
    ::= { lcsStatusCertsScepClntCertsEntry 2 }

-- {COLUMN} 1712.1.61.1.6.1.3
lcsStatusCertsScepClntCertsEntryExpires OBJECT-TYPE
    SYNTAX     DisplayString (SIZE(0..255))
    MAX-ACCESS read-only
    STATUS     current
    DESCRIPTION
        "-- empty --"
    ::= { lcsStatusCertsScepClntCertsEntry 3 }

-- {COLUMN} 1712.1.61.1.6.1.4
lcsStatusCertsScepClntCertsEntryIssued OBJECT-TYPE
    SYNTAX     DisplayString (SIZE(0..255))
    MAX-ACCESS read-only
    STATUS     current
    DESCRIPTION
        "-- empty --"
    ::= { lcsStatusCertsScepClntCertsEntry 4 }

-- {COLUMN} 1712.1.61.1.6.1.5
lcsStatusCertsScepClntCertsEntryKeyUsage OBJECT-TYPE
    SYNTAX     DisplayString (SIZE(0..255))
    MAX-ACCESS read-only
    STATUS     current
    DESCRIPTION
        "-- empty --"
    ::= { lcsStatusCertsScepClntCertsEntry 5 }

-- {COLUMN} 1712.1.61.1.6.1.12
lcsStatusCertsScepClntCertsEntryExtendedKeyusage OBJECT-TYPE
    SYNTAX     DisplayString (SIZE(0..255))
    MAX-ACCESS read-only
    STATUS     current
    DESCRIPTION
        "-- empty --"
    ::= { lcsStatusCertsScepClntCertsEntry 12 }

-- {COLUMN} 1712.1.61.1.6.1.6
lcsStatusCertsScepClntCertsEntrySubjectaltname OBJECT-TYPE
    SYNTAX     DisplayString (SIZE(0..255))
    MAX-ACCESS read-only
    STATUS     current
    DESCRIPTION
        "-- empty --"
    ::= { lcsStatusCertsScepClntCertsEntry 6 }

-- {COLUMN} 1712.1.61.1.6.1.7
lcsStatusCertsScepClntCertsEntryIssuer OBJECT-TYPE
    SYNTAX     DisplayString (SIZE(0..255))
    MAX-ACCESS read-only
    STATUS     current
    DESCRIPTION
        "-- empty --"
    ::= { lcsStatusCertsScepClntCertsEntry 7 }

-- {COLUMN} 1712.1.61.1.6.1.8
lcsStatusCertsScepClntCertsEntrySubject OBJECT-TYPE
    SYNTAX     DisplayString (SIZE(0..255))
    MAX-ACCESS read-only
    STATUS     current
    DESCRIPTION
        "-- empty --"
    ::= { lcsStatusCertsScepClntCertsEntry 8 }

-- {COLUMN} 1712.1.61.1.6.1.9
lcsStatusCertsScepClntCertsEntryStatus OBJECT-TYPE
    SYNTAX     DisplayString (SIZE(0..255))
    MAX-ACCESS read-only
    STATUS     current
    DESCRIPTION
        "-- empty --"
    ::= { lcsStatusCertsScepClntCertsEntry 9 }

-- {COLUMN} 1712.1.61.1.6.1.10
lcsStatusCertsScepClntCertsEntryExpSnmp OBJECT-TYPE
    SYNTAX     Counter32
    MAX-ACCESS read-only
    STATUS     current
    DESCRIPTION
        "-- empty --"
    ::= { lcsStatusCertsScepClntCertsEntry 10 }

-- {COLUMN} 1712.1.61.1.6.1.11
lcsStatusCertsScepClntCertsEntryIssSnmp OBJECT-TYPE
    SYNTAX     Counter32
    MAX-ACCESS read-only
    STATUS     current
    DESCRIPTION
        "-- empty --"
    ::= { lcsStatusCertsScepClntCertsEntry 11 }

-- {COLUMN} 1712.1.61.1.6.1.13
lcsStatusCertsScepClntCertsEntryFilename OBJECT-TYPE
    SYNTAX     DisplayString (SIZE(0..255))
    MAX-ACCESS read-only
    STATUS     current
    DESCRIPTION
        "-- empty --"
    ::= { lcsStatusCertsScepClntCertsEntry 13 }

-- {SCALAR} 1712.1.61.1.8
lcsStatusCertsScepClntScepClientState OBJECT-TYPE
    SYNTAX     DisplayString
    MAX-ACCESS read-only
    STATUS     current
    DESCRIPTION
        "-- empty --"
    ::= { lcsStatusCertsScepClnt 8 }

-- {TABLE} 1712.1.61.4
lcsStatusCertsDeviceCertificatesTable OBJECT-TYPE
    SYNTAX     SEQUENCE OF LcsStatusCertsDeviceCertificatesEntry
    MAX-ACCESS not-accessible
    STATUS     current
    DESCRIPTION
        "-- empty --"
    ::= { lcsStatusCerts 4 }

-- {ENTRY} 1712.1.61.4.1
lcsStatusCertsDeviceCertificatesEntry OBJECT-TYPE
    SYNTAX     LcsStatusCertsDeviceCertificatesEntry
    MAX-ACCESS not-accessible
    STATUS     current
    DESCRIPTION
        ""
    INDEX {
        lcsStatusCertsDeviceCertificatesEntryFilename
    }
    ::= { lcsStatusCertsDeviceCertificatesTable 1 }

-- {SEQUENCE}
LcsStatusCertsDeviceCertificatesEntry ::= SEQUENCE {
    lcsStatusCertsDeviceCertificatesEntryFilename DisplayString,
    lcsStatusCertsDeviceCertificatesEntryApplication DisplayString,
    lcsStatusCertsDeviceCertificatesEntryAvailable INTEGER,
    lcsStatusCertsDeviceCertificatesEntryExpires DisplayString,
    lcsStatusCertsDeviceCertificatesEntryIssued DisplayString,
    lcsStatusCertsDeviceCertificatesEntryKeyUsage DisplayString,
    lcsStatusCertsDeviceCertificatesEntryExtendedKeyusage DisplayString,
    lcsStatusCertsDeviceCertificatesEntrySubjectaltname DisplayString,
    lcsStatusCertsDeviceCertificatesEntryIssuer DisplayString,
    lcsStatusCertsDeviceCertificatesEntrySubject DisplayString
}

-- {COLUMN} 1712.1.61.4.1.1
lcsStatusCertsDeviceCertificatesEntryFilename OBJECT-TYPE
    SYNTAX     DisplayString (SIZE(0..255))
    MAX-ACCESS read-only
    STATUS     current
    DESCRIPTION
        "-- empty --"
    ::= { lcsStatusCertsDeviceCertificatesEntry 1 }

-- {COLUMN} 1712.1.61.4.1.9
lcsStatusCertsDeviceCertificatesEntryApplication OBJECT-TYPE
    SYNTAX     DisplayString (SIZE(0..15))
    MAX-ACCESS read-only
    STATUS     current
    DESCRIPTION
        "-- empty --"
    ::= { lcsStatusCertsDeviceCertificatesEntry 9 }

-- {COLUMN} 1712.1.61.4.1.2
lcsStatusCertsDeviceCertificatesEntryAvailable OBJECT-TYPE
    SYNTAX     INTEGER
      {
        eNo (0),
        eYes (1)
      }
    MAX-ACCESS read-only
    STATUS     current
    DESCRIPTION
        "-- empty --"
    ::= { lcsStatusCertsDeviceCertificatesEntry 2 }

-- {COLUMN} 1712.1.61.4.1.3
lcsStatusCertsDeviceCertificatesEntryExpires OBJECT-TYPE
    SYNTAX     DisplayString (SIZE(0..20))
    MAX-ACCESS read-only
    STATUS     current
    DESCRIPTION
        "-- empty --"
    ::= { lcsStatusCertsDeviceCertificatesEntry 3 }

-- {COLUMN} 1712.1.61.4.1.4
lcsStatusCertsDeviceCertificatesEntryIssued OBJECT-TYPE
    SYNTAX     DisplayString (SIZE(0..20))
    MAX-ACCESS read-only
    STATUS     current
    DESCRIPTION
        "-- empty --"
    ::= { lcsStatusCertsDeviceCertificatesEntry 4 }

-- {COLUMN} 1712.1.61.4.1.5
lcsStatusCertsDeviceCertificatesEntryKeyUsage OBJECT-TYPE
    SYNTAX     DisplayString (SIZE(0..251))
    MAX-ACCESS read-only
    STATUS     current
    DESCRIPTION
        "-- empty --"
    ::= { lcsStatusCertsDeviceCertificatesEntry 5 }

-- {COLUMN} 1712.1.61.4.1.12
lcsStatusCertsDeviceCertificatesEntryExtendedKeyusage OBJECT-TYPE
    SYNTAX     DisplayString (SIZE(0..251))
    MAX-ACCESS read-only
    STATUS     current
    DESCRIPTION
        "-- empty --"
    ::= { lcsStatusCertsDeviceCertificatesEntry 12 }

-- {COLUMN} 1712.1.61.4.1.6
lcsStatusCertsDeviceCertificatesEntrySubjectaltname OBJECT-TYPE
    SYNTAX     DisplayString (SIZE(0..251))
    MAX-ACCESS read-only
    STATUS     current
    DESCRIPTION
        "-- empty --"
    ::= { lcsStatusCertsDeviceCertificatesEntry 6 }

-- {COLUMN} 1712.1.61.4.1.7
lcsStatusCertsDeviceCertificatesEntryIssuer OBJECT-TYPE
    SYNTAX     DisplayString (SIZE(0..251))
    MAX-ACCESS read-only
    STATUS     current
    DESCRIPTION
        "-- empty --"
    ::= { lcsStatusCertsDeviceCertificatesEntry 7 }

-- {COLUMN} 1712.1.61.4.1.8
lcsStatusCertsDeviceCertificatesEntrySubject OBJECT-TYPE
    SYNTAX     DisplayString (SIZE(0..251))
    MAX-ACCESS read-only
    STATUS     current
    DESCRIPTION
        "-- empty --"
    ::= { lcsStatusCertsDeviceCertificatesEntry 8 }

-- {OID} 1712.1.61.3
lcsStatusCertsCrls OBJECT IDENTIFIER ::= { lcsStatusCerts 3 }

-- {SCALAR} 1712.1.61.3.1
lcsStatusCertsCrlsNumcrls OBJECT-TYPE
    SYNTAX     INTEGER (0..2147483647)
    MAX-ACCESS read-only
    STATUS     current
    DESCRIPTION
        "-- empty --"
    ::= { lcsStatusCertsCrls 1 }

-- {TABLE} 1712.1.61.3.2
lcsStatusCertsCrlsCrlsTable OBJECT-TYPE
    SYNTAX     SEQUENCE OF LcsStatusCertsCrlsCrlsEntry
    MAX-ACCESS not-accessible
    STATUS     current
    DESCRIPTION
        "-- empty --"
    ::= { lcsStatusCertsCrls 2 }

-- {ENTRY} 1712.1.61.3.2.1
lcsStatusCertsCrlsCrlsEntry OBJECT-TYPE
    SYNTAX     LcsStatusCertsCrlsCrlsEntry
    MAX-ACCESS not-accessible
    STATUS     current
    DESCRIPTION
        ""
    INDEX {
        lcsStatusCertsCrlsCrlsEntryIdx
    }
    ::= { lcsStatusCertsCrlsCrlsTable 1 }

-- {SEQUENCE}
LcsStatusCertsCrlsCrlsEntry ::= SEQUENCE {
    lcsStatusCertsCrlsCrlsEntryIdx INTEGER,
    lcsStatusCertsCrlsCrlsEntryExpires DisplayString,
    lcsStatusCertsCrlsCrlsEntryIssued DisplayString,
    lcsStatusCertsCrlsCrlsEntryIssuer DisplayString,
    lcsStatusCertsCrlsCrlsEntryDistributionPoint DisplayString,
    lcsStatusCertsCrlsCrlsEntryStatSnmp INTEGER,
    lcsStatusCertsCrlsCrlsEntryExpSnmp Counter32,
    lcsStatusCertsCrlsCrlsEntryIssSnmp Counter32,
    lcsStatusCertsCrlsCrlsEntryStatus DisplayString
}

-- {COLUMN} 1712.1.61.3.2.1.1
lcsStatusCertsCrlsCrlsEntryIdx OBJECT-TYPE
    SYNTAX     INTEGER (0..2147483647)
    MAX-ACCESS read-only
    STATUS     current
    DESCRIPTION
        "-- empty --"
    ::= { lcsStatusCertsCrlsCrlsEntry 1 }

-- {COLUMN} 1712.1.61.3.2.1.2
lcsStatusCertsCrlsCrlsEntryExpires OBJECT-TYPE
    SYNTAX     DisplayString (SIZE(0..255))
    MAX-ACCESS read-only
    STATUS     current
    DESCRIPTION
        "-- empty --"
    ::= { lcsStatusCertsCrlsCrlsEntry 2 }

-- {COLUMN} 1712.1.61.3.2.1.3
lcsStatusCertsCrlsCrlsEntryIssued OBJECT-TYPE
    SYNTAX     DisplayString (SIZE(0..255))
    MAX-ACCESS read-only
    STATUS     current
    DESCRIPTION
        "-- empty --"
    ::= { lcsStatusCertsCrlsCrlsEntry 3 }

-- {COLUMN} 1712.1.61.3.2.1.4
lcsStatusCertsCrlsCrlsEntryIssuer OBJECT-TYPE
    SYNTAX     DisplayString (SIZE(0..255))
    MAX-ACCESS read-only
    STATUS     current
    DESCRIPTION
        "-- empty --"
    ::= { lcsStatusCertsCrlsCrlsEntry 4 }

-- {COLUMN} 1712.1.61.3.2.1.5
lcsStatusCertsCrlsCrlsEntryDistributionPoint OBJECT-TYPE
    SYNTAX     DisplayString (SIZE(0..255))
    MAX-ACCESS read-only
    STATUS     current
    DESCRIPTION
        "-- empty --"
    ::= { lcsStatusCertsCrlsCrlsEntry 5 }

-- {COLUMN} 1712.1.61.3.2.1.6
lcsStatusCertsCrlsCrlsEntryStatSnmp OBJECT-TYPE
    SYNTAX     INTEGER (0..2147483647)
    MAX-ACCESS read-only
    STATUS     current
    DESCRIPTION
        "-- empty --"
    ::= { lcsStatusCertsCrlsCrlsEntry 6 }

-- {COLUMN} 1712.1.61.3.2.1.7
lcsStatusCertsCrlsCrlsEntryExpSnmp OBJECT-TYPE
    SYNTAX     Counter32
    MAX-ACCESS read-only
    STATUS     current
    DESCRIPTION
        "-- empty --"
    ::= { lcsStatusCertsCrlsCrlsEntry 7 }

-- {COLUMN} 1712.1.61.3.2.1.8
lcsStatusCertsCrlsCrlsEntryIssSnmp OBJECT-TYPE
    SYNTAX     Counter32
    MAX-ACCESS read-only
    STATUS     current
    DESCRIPTION
        "-- empty --"
    ::= { lcsStatusCertsCrlsCrlsEntry 8 }

-- {COLUMN} 1712.1.61.3.2.1.9
lcsStatusCertsCrlsCrlsEntryStatus OBJECT-TYPE
    SYNTAX     DisplayString (SIZE(0..255))
    MAX-ACCESS read-only
    STATUS     current
    DESCRIPTION
        "-- empty --"
    ::= { lcsStatusCertsCrlsCrlsEntry 9 }

-- {OID} 1712.1.61.6
lcsStatusCertsOcspClient OBJECT IDENTIFIER ::= { lcsStatusCerts 6 }

-- {TABLE} 1712.1.61.6.1
lcsStatusCertsOcspClientCaStatusTableTable OBJECT-TYPE
    SYNTAX     SEQUENCE OF LcsStatusCertsOcspClientCaStatusTableEntry
    MAX-ACCESS not-accessible
    STATUS     current
    DESCRIPTION
        "-- empty --"
    ::= { lcsStatusCertsOcspClient 1 }

-- {ENTRY} 1712.1.61.6.1.1
lcsStatusCertsOcspClientCaStatusTableEntry OBJECT-TYPE
    SYNTAX     LcsStatusCertsOcspClientCaStatusTableEntry
    MAX-ACCESS not-accessible
    STATUS     current
    DESCRIPTION
        ""
    INDEX {
        lcsStatusCertsOcspClientCaStatusTableEntryProfileName
    }
    ::= { lcsStatusCertsOcspClientCaStatusTableTable 1 }

-- {SEQUENCE}
LcsStatusCertsOcspClientCaStatusTableEntry ::= SEQUENCE {
    lcsStatusCertsOcspClientCaStatusTableEntryProfileName DisplayString,
    lcsStatusCertsOcspClientCaStatusTableEntryRequests INTEGER,
    lcsStatusCertsOcspClientCaStatusTableEntryResponses INTEGER,
    lcsStatusCertsOcspClientCaStatusTableEntryGoodResponses INTEGER,
    lcsStatusCertsOcspClientCaStatusTableEntryRevokeResponses INTEGER,
    lcsStatusCertsOcspClientCaStatusTableEntryUnknownResponses INTEGER,
    lcsStatusCertsOcspClientCaStatusTableEntrySuccessfulResponses INTEGER,
    lcsStatusCertsOcspClientCaStatusTableEntryErrorResponses INTEGER,
    lcsStatusCertsOcspClientCaStatusTableEntryMalformedRequests INTEGER,
    lcsStatusCertsOcspClientCaStatusTableEntryIntErrorResponses INTEGER,
    lcsStatusCertsOcspClientCaStatusTableEntryTryLaterResponses INTEGER,
    lcsStatusCertsOcspClientCaStatusTableEntrySignRequiredResponses INTEGER,
    lcsStatusCertsOcspClientCaStatusTableEntryUnauthorizedResponses INTEGER,
    lcsStatusCertsOcspClientCaStatusTableEntrySignerVerifyFailures INTEGER,
    lcsStatusCertsOcspClientCaStatusTableEntryCertTimedOuts INTEGER,
    lcsStatusCertsOcspClientCaStatusTableEntryGenericErrors INTEGER,
    lcsStatusCertsOcspClientCaStatusTableEntryTransportErrors INTEGER
}

-- {COLUMN} 1712.1.61.6.1.1.1
lcsStatusCertsOcspClientCaStatusTableEntryProfileName OBJECT-TYPE
    SYNTAX     DisplayString (SIZE(0..32))
    MAX-ACCESS read-only
    STATUS     current
    DESCRIPTION
        "-- empty --"
    ::= { lcsStatusCertsOcspClientCaStatusTableEntry 1 }

-- {COLUMN} 1712.1.61.6.1.1.2
lcsStatusCertsOcspClientCaStatusTableEntryRequests OBJECT-TYPE
    SYNTAX     INTEGER (0..2147483647)
    MAX-ACCESS read-only
    STATUS     current
    DESCRIPTION
        "-- empty --"
    ::= { lcsStatusCertsOcspClientCaStatusTableEntry 2 }

-- {COLUMN} 1712.1.61.6.1.1.3
lcsStatusCertsOcspClientCaStatusTableEntryResponses OBJECT-TYPE
    SYNTAX     INTEGER (0..2147483647)
    MAX-ACCESS read-only
    STATUS     current
    DESCRIPTION
        "-- empty --"
    ::= { lcsStatusCertsOcspClientCaStatusTableEntry 3 }

-- {COLUMN} 1712.1.61.6.1.1.4
lcsStatusCertsOcspClientCaStatusTableEntryGoodResponses OBJECT-TYPE
    SYNTAX     INTEGER (0..2147483647)
    MAX-ACCESS read-only
    STATUS     current
    DESCRIPTION
        "-- empty --"
    ::= { lcsStatusCertsOcspClientCaStatusTableEntry 4 }

-- {COLUMN} 1712.1.61.6.1.1.5
lcsStatusCertsOcspClientCaStatusTableEntryRevokeResponses OBJECT-TYPE
    SYNTAX     INTEGER (0..2147483647)
    MAX-ACCESS read-only
    STATUS     current
    DESCRIPTION
        "-- empty --"
    ::= { lcsStatusCertsOcspClientCaStatusTableEntry 5 }

-- {COLUMN} 1712.1.61.6.1.1.6
lcsStatusCertsOcspClientCaStatusTableEntryUnknownResponses OBJECT-TYPE
    SYNTAX     INTEGER (0..2147483647)
    MAX-ACCESS read-only
    STATUS     current
    DESCRIPTION
        "-- empty --"
    ::= { lcsStatusCertsOcspClientCaStatusTableEntry 6 }

-- {COLUMN} 1712.1.61.6.1.1.7
lcsStatusCertsOcspClientCaStatusTableEntrySuccessfulResponses OBJECT-TYPE
    SYNTAX     INTEGER (0..2147483647)
    MAX-ACCESS read-only
    STATUS     current
    DESCRIPTION
        "-- empty --"
    ::= { lcsStatusCertsOcspClientCaStatusTableEntry 7 }

-- {COLUMN} 1712.1.61.6.1.1.8
lcsStatusCertsOcspClientCaStatusTableEntryErrorResponses OBJECT-TYPE
    SYNTAX     INTEGER (0..2147483647)
    MAX-ACCESS read-only
    STATUS     current
    DESCRIPTION
        "-- empty --"
    ::= { lcsStatusCertsOcspClientCaStatusTableEntry 8 }

-- {COLUMN} 1712.1.61.6.1.1.9
lcsStatusCertsOcspClientCaStatusTableEntryMalformedRequests OBJECT-TYPE
    SYNTAX     INTEGER (0..2147483647)
    MAX-ACCESS read-only
    STATUS     current
    DESCRIPTION
        "-- empty --"
    ::= { lcsStatusCertsOcspClientCaStatusTableEntry 9 }

-- {COLUMN} 1712.1.61.6.1.1.10
lcsStatusCertsOcspClientCaStatusTableEntryIntErrorResponses OBJECT-TYPE
    SYNTAX     INTEGER (0..2147483647)
    MAX-ACCESS read-only
    STATUS     current
    DESCRIPTION
        "-- empty --"
    ::= { lcsStatusCertsOcspClientCaStatusTableEntry 10 }

-- {COLUMN} 1712.1.61.6.1.1.11
lcsStatusCertsOcspClientCaStatusTableEntryTryLaterResponses OBJECT-TYPE
    SYNTAX     INTEGER (0..2147483647)
    MAX-ACCESS read-only
    STATUS     current
    DESCRIPTION
        "-- empty --"
    ::= { lcsStatusCertsOcspClientCaStatusTableEntry 11 }

-- {COLUMN} 1712.1.61.6.1.1.12
lcsStatusCertsOcspClientCaStatusTableEntrySignRequiredResponses OBJECT-TYPE
    SYNTAX     INTEGER (0..2147483647)
    MAX-ACCESS read-only
    STATUS     current
    DESCRIPTION
        "-- empty --"
    ::= { lcsStatusCertsOcspClientCaStatusTableEntry 12 }

-- {COLUMN} 1712.1.61.6.1.1.13
lcsStatusCertsOcspClientCaStatusTableEntryUnauthorizedResponses OBJECT-TYPE
    SYNTAX     INTEGER (0..2147483647)
    MAX-ACCESS read-only
    STATUS     current
    DESCRIPTION
        "-- empty --"
    ::= { lcsStatusCertsOcspClientCaStatusTableEntry 13 }

-- {COLUMN} 1712.1.61.6.1.1.14
lcsStatusCertsOcspClientCaStatusTableEntrySignerVerifyFailures OBJECT-TYPE
    SYNTAX     INTEGER (0..2147483647)
    MAX-ACCESS read-only
    STATUS     current
    DESCRIPTION
        "-- empty --"
    ::= { lcsStatusCertsOcspClientCaStatusTableEntry 14 }

-- {COLUMN} 1712.1.61.6.1.1.15
lcsStatusCertsOcspClientCaStatusTableEntryCertTimedOuts OBJECT-TYPE
    SYNTAX     INTEGER (0..2147483647)
    MAX-ACCESS read-only
    STATUS     current
    DESCRIPTION
        "-- empty --"
    ::= { lcsStatusCertsOcspClientCaStatusTableEntry 15 }

-- {COLUMN} 1712.1.61.6.1.1.16
lcsStatusCertsOcspClientCaStatusTableEntryGenericErrors OBJECT-TYPE
    SYNTAX     INTEGER (0..2147483647)
    MAX-ACCESS read-only
    STATUS     current
    DESCRIPTION
        "-- empty --"
    ::= { lcsStatusCertsOcspClientCaStatusTableEntry 16 }

-- {COLUMN} 1712.1.61.6.1.1.17
lcsStatusCertsOcspClientCaStatusTableEntryTransportErrors OBJECT-TYPE
    SYNTAX     INTEGER (0..2147483647)
    MAX-ACCESS read-only
    STATUS     current
    DESCRIPTION
        "-- empty --"
    ::= { lcsStatusCertsOcspClientCaStatusTableEntry 17 }

-- {OID} 1712.1.33
lcsStatusIsdn OBJECT IDENTIFIER ::= { lcsStatus 33 }

-- {OID} 1712.1.33.1
lcsStatusIsdnLine OBJECT IDENTIFIER ::= { lcsStatusIsdn 1 }

-- {TABLE} 1712.1.33.1.1
lcsStatusIsdnLineS0Table OBJECT-TYPE
    SYNTAX     SEQUENCE OF LcsStatusIsdnLineS0Entry
    MAX-ACCESS not-accessible
    STATUS     current
    DESCRIPTION
        "-- empty --"
    ::= { lcsStatusIsdnLine 1 }

-- {ENTRY} 1712.1.33.1.1.1
lcsStatusIsdnLineS0Entry OBJECT-TYPE
    SYNTAX     LcsStatusIsdnLineS0Entry
    MAX-ACCESS not-accessible
    STATUS     current
    DESCRIPTION
        ""
    INDEX {
        lcsStatusIsdnLineS0EntryIfc
    }
    ::= { lcsStatusIsdnLineS0Table 1 }

-- {SEQUENCE}
LcsStatusIsdnLineS0Entry ::= SEQUENCE {
    lcsStatusIsdnLineS0EntryIfc INTEGER,
    lcsStatusIsdnLineS0EntryOperating INTEGER
}

-- {COLUMN} 1712.1.33.1.1.1.1
lcsStatusIsdnLineS0EntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsStatusIsdnLineS0Entry 1 }

-- {COLUMN} 1712.1.33.1.1.1.2
lcsStatusIsdnLineS0EntryOperating OBJECT-TYPE
    SYNTAX     INTEGER
      {
        eNo (0),
        eYes (1)
      }
    MAX-ACCESS read-only
    STATUS     current
    DESCRIPTION
        "-- empty --"
    ::= { lcsStatusIsdnLineS0Entry 2 }

-- {OID} 1712.1.33.2
lcsStatusIsdnFraming OBJECT IDENTIFIER ::= { lcsStatusIsdn 2 }

-- {TABLE} 1712.1.33.2.1
lcsStatusIsdnFramingS0Table OBJECT-TYPE
    SYNTAX     SEQUENCE OF LcsStatusIsdnFramingS0Entry
    MAX-ACCESS not-accessible
    STATUS     current
    DESCRIPTION
        "-- empty --"
    ::= { lcsStatusIsdnFraming 1 }

-- {ENTRY} 1712.1.33.2.1.1
lcsStatusIsdnFramingS0Entry OBJECT-TYPE
    SYNTAX     LcsStatusIsdnFramingS0Entry
    MAX-ACCESS not-accessible
    STATUS     current
    DESCRIPTION
        ""
    INDEX {
        lcsStatusIsdnFramingS0EntryIfc
    }
    ::= { lcsStatusIsdnFramingS0Table 1 }

-- {SEQUENCE}
LcsStatusIsdnFramingS0Entry ::= SEQUENCE {
    lcsStatusIsdnFramingS0EntryIfc INTEGER,
    lcsStatusIsdnFramingS0EntryState DisplayString,
    lcsStatusIsdnFramingS0EntryB1Frame BITS,
    lcsStatusIsdnFramingS0EntryB2Frame BITS
}

-- {COLUMN} 1712.1.33.2.1.1.1
lcsStatusIsdnFramingS0EntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsStatusIsdnFramingS0Entry 1 }

-- {COLUMN} 1712.1.33.2.1.1.2
lcsStatusIsdnFramingS0EntryState OBJECT-TYPE
    SYNTAX     DisplayString (SIZE(0..255))
    MAX-ACCESS read-only
    STATUS     current
    DESCRIPTION
        "-- empty --"
    ::= { lcsStatusIsdnFramingS0Entry 2 }

-- {COLUMN} 1712.1.33.2.1.1.3
lcsStatusIsdnFramingS0EntryB1Frame OBJECT-TYPE
    SYNTAX     BITS
      {
        eLoop (7),
        eRxData (6),
        eTxData (5)
      }
    MAX-ACCESS read-only
    STATUS     current
    DESCRIPTION
        "-- empty --"
    ::= { lcsStatusIsdnFramingS0Entry 3 }

-- {COLUMN} 1712.1.33.2.1.1.4
lcsStatusIsdnFramingS0EntryB2Frame OBJECT-TYPE
    SYNTAX     BITS
      {
        eLoop (7),
        eRxData (6),
        eTxData (5)
      }
    MAX-ACCESS read-only
    STATUS     current
    DESCRIPTION
        "-- empty --"
    ::= { lcsStatusIsdnFramingS0Entry 4 }

-- {OID} 1712.1.33.3
lcsStatusIsdnSignaling OBJECT IDENTIFIER ::= { lcsStatusIsdn 3 }

-- {OID} 1712.1.33.3.1
lcsStatusIsdnSignalingLayer2 OBJECT IDENTIFIER ::= { lcsStatusIsdnSignaling 1 }

-- {TABLE} 1712.1.33.3.1.1
lcsStatusIsdnSignalingLayer2LapdTable OBJECT-TYPE
    SYNTAX     SEQUENCE OF LcsStatusIsdnSignalingLayer2LapdEntry
    MAX-ACCESS not-accessible
    STATUS     current
    DESCRIPTION
        "-- empty --"
    ::= { lcsStatusIsdnSignalingLayer2 1 }

-- {ENTRY} 1712.1.33.3.1.1.1
lcsStatusIsdnSignalingLayer2LapdEntry OBJECT-TYPE
    SYNTAX     LcsStatusIsdnSignalingLayer2LapdEntry
    MAX-ACCESS not-accessible
    STATUS     current
    DESCRIPTION
        ""
    INDEX {
        lcsStatusIsdnSignalingLayer2LapdEntryChannel
    }
    ::= { lcsStatusIsdnSignalingLayer2LapdTable 1 }

-- {SEQUENCE}
LcsStatusIsdnSignalingLayer2LapdEntry ::= SEQUENCE {
    lcsStatusIsdnSignalingLayer2LapdEntryChannel INTEGER,
    lcsStatusIsdnSignalingLayer2LapdEntryTei INTEGER,
    lcsStatusIsdnSignalingLayer2LapdEntryL2Activation INTEGER,
    lcsStatusIsdnSignalingLayer2LapdEntryConnections INTEGER
}

-- {COLUMN} 1712.1.33.3.1.1.1.1
lcsStatusIsdnSignalingLayer2LapdEntryChannel OBJECT-TYPE
    SYNTAX     INTEGER
      {
        e11 (1),
        e12 (2)
      }
    MAX-ACCESS read-only
    STATUS     current
    DESCRIPTION
        "-- empty --"
    ::= { lcsStatusIsdnSignalingLayer2LapdEntry 1 }

-- {COLUMN} 1712.1.33.3.1.1.1.2
lcsStatusIsdnSignalingLayer2LapdEntryTei OBJECT-TYPE
    SYNTAX     INTEGER
      {
        eNone (128)
      }
    MAX-ACCESS read-only
    STATUS     current
    DESCRIPTION
        "-- empty --"
    ::= { lcsStatusIsdnSignalingLayer2LapdEntry 2 }

-- {COLUMN} 1712.1.33.3.1.1.1.3
lcsStatusIsdnSignalingLayer2LapdEntryL2Activation OBJECT-TYPE
    SYNTAX     INTEGER
      {
        eNo (0),
        eYes (1)
      }
    MAX-ACCESS read-only
    STATUS     current
    DESCRIPTION
        "-- empty --"
    ::= { lcsStatusIsdnSignalingLayer2LapdEntry 3 }

-- {COLUMN} 1712.1.33.3.1.1.1.4
lcsStatusIsdnSignalingLayer2LapdEntryConnections OBJECT-TYPE
    SYNTAX     INTEGER (0..255)
    MAX-ACCESS read-only
    STATUS     current
    DESCRIPTION
        "-- empty --"
    ::= { lcsStatusIsdnSignalingLayer2LapdEntry 4 }

-- {OID} 1712.1.33.3.3
lcsStatusIsdnSignalingManagement OBJECT IDENTIFIER ::= { lcsStatusIsdnSignaling 3 }

-- {TABLE} 1712.1.33.3.3.1
lcsStatusIsdnSignalingManagementDInfoTable OBJECT-TYPE
    SYNTAX     SEQUENCE OF LcsStatusIsdnSignalingManagementDInfoEntry
    MAX-ACCESS not-accessible
    STATUS     current
    DESCRIPTION
        "-- empty --"
    ::= { lcsStatusIsdnSignalingManagement 1 }

-- {ENTRY} 1712.1.33.3.3.1.1
lcsStatusIsdnSignalingManagementDInfoEntry OBJECT-TYPE
    SYNTAX     LcsStatusIsdnSignalingManagementDInfoEntry
    MAX-ACCESS not-accessible
    STATUS     current
    DESCRIPTION
        ""
    INDEX {
        lcsStatusIsdnSignalingManagementDInfoEntryChannel
    }
    ::= { lcsStatusIsdnSignalingManagementDInfoTable 1 }

-- {SEQUENCE}
LcsStatusIsdnSignalingManagementDInfoEntry ::= SEQUENCE {
    lcsStatusIsdnSignalingManagementDInfoEntryChannel INTEGER,
    lcsStatusIsdnSignalingManagementDInfoEntryProtocol INTEGER,
    lcsStatusIsdnSignalingManagementDInfoEntryLayer2 INTEGER,
    lcsStatusIsdnSignalingManagementDInfoEntryTei INTEGER,
    lcsStatusIsdnSignalingManagementDInfoEntryS0Activation INTEGER
}

-- {COLUMN} 1712.1.33.3.3.1.1.1
lcsStatusIsdnSignalingManagementDInfoEntryChannel OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsStatusIsdnSignalingManagementDInfoEntry 1 }

-- {COLUMN} 1712.1.33.3.3.1.1.2
lcsStatusIsdnSignalingManagementDInfoEntryProtocol OBJECT-TYPE
    SYNTAX     INTEGER
      {
        eNo (0),
        eDss1 (1),
        e1tr6 (2),
        eP2pDss1 (4),
        eAuto (255)
      }
    MAX-ACCESS read-only
    STATUS     current
    DESCRIPTION
        "-- empty --"
    ::= { lcsStatusIsdnSignalingManagementDInfoEntry 2 }

-- {COLUMN} 1712.1.33.3.3.1.1.3
lcsStatusIsdnSignalingManagementDInfoEntryLayer2 OBJECT-TYPE
    SYNTAX     INTEGER
      {
        eNo (0),
        eYes (1)
      }
    MAX-ACCESS read-only
    STATUS     current
    DESCRIPTION
        "-- empty --"
    ::= { lcsStatusIsdnSignalingManagementDInfoEntry 3 }

-- {COLUMN} 1712.1.33.3.3.1.1.4
lcsStatusIsdnSignalingManagementDInfoEntryTei OBJECT-TYPE
    SYNTAX     INTEGER
      {
        eNo (0),
        eYes (1)
      }
    MAX-ACCESS read-only
    STATUS     current
    DESCRIPTION
        "-- empty --"
    ::= { lcsStatusIsdnSignalingManagementDInfoEntry 4 }

-- {COLUMN} 1712.1.33.3.3.1.1.5
lcsStatusIsdnSignalingManagementDInfoEntryS0Activation OBJECT-TYPE
    SYNTAX     INTEGER
      {
        eNo (0),
        eYes (1)
      }
    MAX-ACCESS read-only
    STATUS     current
    DESCRIPTION
        "-- empty --"
    ::= { lcsStatusIsdnSignalingManagementDInfoEntry 5 }

-- {TABLE} 1712.1.33.3.3.2
lcsStatusIsdnSignalingManagementErrorStatisticTable OBJECT-TYPE
    SYNTAX     SEQUENCE OF LcsStatusIsdnSignalingManagementErrorStatisticEntry
    MAX-ACCESS not-accessible
    STATUS     current
    DESCRIPTION
        "-- empty --"
    ::= { lcsStatusIsdnSignalingManagement 2 }

-- {ENTRY} 1712.1.33.3.3.2.1
lcsStatusIsdnSignalingManagementErrorStatisticEntry OBJECT-TYPE
    SYNTAX     LcsStatusIsdnSignalingManagementErrorStatisticEntry
    MAX-ACCESS not-accessible
    STATUS     current
    DESCRIPTION
        ""
    INDEX {
        lcsStatusIsdnSignalingManagementErrorStatisticEntryIfc
    }
    ::= { lcsStatusIsdnSignalingManagementErrorStatisticTable 1 }

-- {SEQUENCE}
LcsStatusIsdnSignalingManagementErrorStatisticEntry ::= SEQUENCE {
    lcsStatusIsdnSignalingManagementErrorStatisticEntryIfc INTEGER,
    lcsStatusIsdnSignalingManagementErrorStatisticEntryA INTEGER,
    lcsStatusIsdnSignalingManagementErrorStatisticEntryB INTEGER,
    lcsStatusIsdnSignalingManagementErrorStatisticEntryC INTEGER,
    lcsStatusIsdnSignalingManagementErrorStatisticEntryD INTEGER,
    lcsStatusIsdnSignalingManagementErrorStatisticEntryE INTEGER,
    lcsStatusIsdnSignalingManagementErrorStatisticEntryF INTEGER,
    lcsStatusIsdnSignalingManagementErrorStatisticEntryG INTEGER,
    lcsStatusIsdnSignalingManagementErrorStatisticEntryH INTEGER,
    lcsStatusIsdnSignalingManagementErrorStatisticEntryI INTEGER,
    lcsStatusIsdnSignalingManagementErrorStatisticEntryJ INTEGER,
    lcsStatusIsdnSignalingManagementErrorStatisticEntryK INTEGER,
    lcsStatusIsdnSignalingManagementErrorStatisticEntryL INTEGER,
    lcsStatusIsdnSignalingManagementErrorStatisticEntryM INTEGER,
    lcsStatusIsdnSignalingManagementErrorStatisticEntryN INTEGER,
    lcsStatusIsdnSignalingManagementErrorStatisticEntryO INTEGER
}

-- {COLUMN} 1712.1.33.3.3.2.1.1
lcsStatusIsdnSignalingManagementErrorStatisticEntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsStatusIsdnSignalingManagementErrorStatisticEntry 1 }

-- {COLUMN} 1712.1.33.3.3.2.1.2
lcsStatusIsdnSignalingManagementErrorStatisticEntryA OBJECT-TYPE
    SYNTAX     INTEGER (0..65535)
    MAX-ACCESS read-only
    STATUS     current
    DESCRIPTION
        "-- empty --"
    ::= { lcsStatusIsdnSignalingManagementErrorStatisticEntry 2 }

-- {COLUMN} 1712.1.33.3.3.2.1.3
lcsStatusIsdnSignalingManagementErrorStatisticEntryB OBJECT-TYPE
    SYNTAX     INTEGER (0..65535)
    MAX-ACCESS read-only
    STATUS     current
    DESCRIPTION
        "-- empty --"
    ::= { lcsStatusIsdnSignalingManagementErrorStatisticEntry 3 }

-- {COLUMN} 1712.1.33.3.3.2.1.4
lcsStatusIsdnSignalingManagementErrorStatisticEntryC OBJECT-TYPE
    SYNTAX     INTEGER (0..65535)
    MAX-ACCESS read-only
    STATUS     current
    DESCRIPTION
        "-- empty --"
    ::= { lcsStatusIsdnSignalingManagementErrorStatisticEntry 4 }

-- {COLUMN} 1712.1.33.3.3.2.1.5
lcsStatusIsdnSignalingManagementErrorStatisticEntryD OBJECT-TYPE
    SYNTAX     INTEGER (0..65535)
    MAX-ACCESS read-only
    STATUS     current
    DESCRIPTION
        "-- empty --"
    ::= { lcsStatusIsdnSignalingManagementErrorStatisticEntry 5 }

-- {COLUMN} 1712.1.33.3.3.2.1.6
lcsStatusIsdnSignalingManagementErrorStatisticEntryE OBJECT-TYPE
    SYNTAX     INTEGER (0..65535)
    MAX-ACCESS read-only
    STATUS     current
    DESCRIPTION
        "-- empty --"
    ::= { lcsStatusIsdnSignalingManagementErrorStatisticEntry 6 }

-- {COLUMN} 1712.1.33.3.3.2.1.7
lcsStatusIsdnSignalingManagementErrorStatisticEntryF OBJECT-TYPE
    SYNTAX     INTEGER (0..65535)
    MAX-ACCESS read-only
    STATUS     current
    DESCRIPTION
        "-- empty --"
    ::= { lcsStatusIsdnSignalingManagementErrorStatisticEntry 7 }

-- {COLUMN} 1712.1.33.3.3.2.1.8
lcsStatusIsdnSignalingManagementErrorStatisticEntryG OBJECT-TYPE
    SYNTAX     INTEGER (0..65535)
    MAX-ACCESS read-only
    STATUS     current
    DESCRIPTION
        "-- empty --"
    ::= { lcsStatusIsdnSignalingManagementErrorStatisticEntry 8 }

-- {COLUMN} 1712.1.33.3.3.2.1.9
lcsStatusIsdnSignalingManagementErrorStatisticEntryH OBJECT-TYPE
    SYNTAX     INTEGER (0..65535)
    MAX-ACCESS read-only
    STATUS     current
    DESCRIPTION
        "-- empty --"
    ::= { lcsStatusIsdnSignalingManagementErrorStatisticEntry 9 }

-- {COLUMN} 1712.1.33.3.3.2.1.10
lcsStatusIsdnSignalingManagementErrorStatisticEntryI OBJECT-TYPE
    SYNTAX     INTEGER (0..65535)
    MAX-ACCESS read-only
    STATUS     current
    DESCRIPTION
        "-- empty --"
    ::= { lcsStatusIsdnSignalingManagementErrorStatisticEntry 10 }

-- {COLUMN} 1712.1.33.3.3.2.1.11
lcsStatusIsdnSignalingManagementErrorStatisticEntryJ OBJECT-TYPE
    SYNTAX     INTEGER (0..65535)
    MAX-ACCESS read-only
    STATUS     current
    DESCRIPTION
        "-- empty --"
    ::= { lcsStatusIsdnSignalingManagementErrorStatisticEntry 11 }

-- {COLUMN} 1712.1.33.3.3.2.1.12
lcsStatusIsdnSignalingManagementErrorStatisticEntryK OBJECT-TYPE
    SYNTAX     INTEGER (0..65535)
    MAX-ACCESS read-only
    STATUS     current
    DESCRIPTION
        "-- empty --"
    ::= { lcsStatusIsdnSignalingManagementErrorStatisticEntry 12 }

-- {COLUMN} 1712.1.33.3.3.2.1.13
lcsStatusIsdnSignalingManagementErrorStatisticEntryL OBJECT-TYPE
    SYNTAX     INTEGER (0..65535)
    MAX-ACCESS read-only
    STATUS     current
    DESCRIPTION
        "-- empty --"
    ::= { lcsStatusIsdnSignalingManagementErrorStatisticEntry 13 }

-- {COLUMN} 1712.1.33.3.3.2.1.14
lcsStatusIsdnSignalingManagementErrorStatisticEntryM OBJECT-TYPE
    SYNTAX     INTEGER (0..65535)
    MAX-ACCESS read-only
    STATUS     current
    DESCRIPTION
        "-- empty --"
    ::= { lcsStatusIsdnSignalingManagementErrorStatisticEntry 14 }

-- {COLUMN} 1712.1.33.3.3.2.1.15
lcsStatusIsdnSignalingManagementErrorStatisticEntryN OBJECT-TYPE
    SYNTAX     INTEGER (0..65535)
    MAX-ACCESS read-only
    STATUS     current
    DESCRIPTION
        "-- empty --"
    ::= { lcsStatusIsdnSignalingManagementErrorStatisticEntry 15 }

-- {COLUMN} 1712.1.33.3.3.2.1.16
lcsStatusIsdnSignalingManagementErrorStatisticEntryO OBJECT-TYPE
    SYNTAX     INTEGER (0..65535)
    MAX-ACCESS read-only
    STATUS     current
    DESCRIPTION
        "-- empty --"
    ::= { lcsStatusIsdnSignalingManagementErrorStatisticEntry 16 }

-- {SCALAR} 1712.1.33.99
lcsStatusIsdnDeleteValues OBJECT-TYPE
    SYNTAX     DisplayString
    MAX-ACCESS read-write
    STATUS     current
    DESCRIPTION
        "-- empty --"
    ::= { lcsStatusIsdn 99 }

-- {OID} 1712.1.35
lcsStatusSnmp OBJECT IDENTIFIER ::= { lcsStatus 35 }

-- {TABLE} 1712.1.35.1
lcsStatusSnmpEventTable OBJECT-TYPE
    SYNTAX     SEQUENCE OF LcsStatusSnmpEventEntry
    MAX-ACCESS not-accessible
    STATUS     current
    DESCRIPTION
        "-- empty --"
    ::= { lcsStatusSnmp 1 }

-- {ENTRY} 1712.1.35.1.1
lcsStatusSnmpEventEntry OBJECT-TYPE
    SYNTAX     LcsStatusSnmpEventEntry
    MAX-ACCESS not-accessible
    STATUS     current
    DESCRIPTION
        ""
    INDEX {
        lcsStatusSnmpEventEntryTrapName,
        lcsStatusSnmpEventEntryVendorName
    }
    ::= { lcsStatusSnmpEventTable 1 }

-- {SEQUENCE}
LcsStatusSnmpEventEntry ::= SEQUENCE {
    lcsStatusSnmpEventEntryTrapName INTEGER,
    lcsStatusSnmpEventEntryVendorName INTEGER,
    lcsStatusSnmpEventEntryCount INTEGER
}

-- {COLUMN} 1712.1.35.1.1.1
lcsStatusSnmpEventEntryTrapName OBJECT-TYPE
    SYNTAX     INTEGER
      {
        eColdstart (255), -- Device cold-start
        eWarmstart (1), -- Device warm-start
        eLinkdown (2), -- Link down event
        eLinkup (3), -- Link up event
        eAuthfail (4), -- Authentication failed
        eEpgnloss (5), -- EGP neighbor lost
        eEnterprise (6) -- Enterprise specific trap
      }
    MAX-ACCESS read-only
    STATUS     current
    DESCRIPTION
        "-- empty --"
    ::= { lcsStatusSnmpEventEntry 1 }

-- {COLUMN} 1712.1.35.1.1.2
lcsStatusSnmpEventEntryVendorName OBJECT-TYPE
    SYNTAX     INTEGER
      {
        eWwanStates (82),
        eFwUplStart (4), -- Firmware upload was started
        eUplsucc (5), -- Firmware or configuration upload successful
        eUplfailto (6), -- The upload of firmware or configuration failed: maximum time was exceeded
        eUplfailincl (7), -- The upload of firmware or configuration failed: incomplete configuration
        eUplfailbaddev (8), -- The upload of firmware or configuration failed: wrong device
        eLogin (9), -- Login to configuration successful
        eLogout (10), -- Logout from configuration was successful
        eCnfuplstart (11), -- Configuration upload was started
        eCnfdnlstart (12), -- Configuration download was started
        eScrptuplstart (79), -- script upload was started
        eScrptdnlstart (80), -- script download was started
        eCnfdnlsucc (13), -- Configuration download successful
        eErrlogin (29), -- Error during login to configuration
        eUplinvversion (7000), -- The upload of firmware failed: invalid firmware version
        eUplfileexists (7001), -- The upload of file failed: file with this version already exists
        eNone (0), -- End of universe reached
        ePptpconn (28), -- Status of PPTP connection
        ePppoesconn (39), -- PPPoE server connection status
        eVpnconn (27), -- Status of VPN connection
        eIpfwflt (26), -- Information about an IPv4 firewall event
        eLdblconn (38), -- Load balancer connection status
        eVrrp (41), -- Information about a VRRP event
        eLanOvertempThrottle (5002), -- Throttling of LAN Speed due to temperature exceedance active
        eLanOvertempThrottleEnd (5003), -- Throttling of LAN Speed due to temperature exceedance stopped
        eLanOvertempThrottleRecommend (5004), -- Throttling of LAN Speed due to temperature exceedance recommended
        eStatChan (1), -- WAN connection status
        eL2TP-Endpoints (85), -- L2TP tunnel end point status
        eL2TP-Connections (86), -- L2TP connection status
        eDS-Lite (83), -- DS-LITE connection status
        eIpv6fwflt (81), -- Information about an IPv6 firewall event
        eHttpTunnelOpen (2000), -- HTTP tunnel opened successful
        eHttpTunnelClose (2001), -- HTTP tunnel closed successful
        eLicensemgtexpire (77) -- Software option license has expired
      }
    MAX-ACCESS read-only
    STATUS     current
    DESCRIPTION
        "-- empty --"
    ::= { lcsStatusSnmpEventEntry 2 }

-- {COLUMN} 1712.1.35.1.1.3
lcsStatusSnmpEventEntryCount OBJECT-TYPE
    SYNTAX     INTEGER (0..2147483647)
    MAX-ACCESS read-only
    STATUS     current
    DESCRIPTION
        "-- empty --"
    ::= { lcsStatusSnmpEventEntry 3 }

-- {SCALAR} 1712.1.35.2
lcsStatusSnmpRejectedRequests OBJECT-TYPE
    SYNTAX     INTEGER (0..2147483647)
    MAX-ACCESS read-only
    STATUS     current
    DESCRIPTION
        "-- empty --"
    ::= { lcsStatusSnmp 2 }

-- {SCALAR} 1712.1.35.3
lcsStatusSnmpQueueBlockErrors OBJECT-TYPE
    SYNTAX     INTEGER (0..2147483647)
    MAX-ACCESS read-only
    STATUS     current
    DESCRIPTION
        "-- empty --"
    ::= { lcsStatusSnmp 3 }

-- {SCALAR} 1712.1.35.4
lcsStatusSnmpDroppedPackets OBJECT-TYPE
    SYNTAX     INTEGER (0..2147483647)
    MAX-ACCESS read-only
    STATUS     current
    DESCRIPTION
        "-- empty --"
    ::= { lcsStatusSnmp 4 }

-- {OID} 1712.1.43
lcsStatusMail OBJECT IDENTIFIER ::= { lcsStatus 43 }

-- {SCALAR} 1712.1.43.1
lcsStatusMailBufferedMails OBJECT-TYPE
    SYNTAX     INTEGER (0..65535)
    MAX-ACCESS read-only
    STATUS     current
    DESCRIPTION
        "-- empty --"
    ::= { lcsStatusMail 1 }

-- {SCALAR} 1712.1.43.2
lcsStatusMailSentMails OBJECT-TYPE
    SYNTAX     Counter32
    MAX-ACCESS read-only
    STATUS     current
    DESCRIPTION
        "-- empty --"
    ::= { lcsStatusMail 2 }

-- {SCALAR} 1712.1.43.3
lcsStatusMailDiscardedMails OBJECT-TYPE
    SYNTAX     Counter32
    MAX-ACCESS read-only
    STATUS     current
    DESCRIPTION
        "-- empty --"
    ::= { lcsStatusMail 3 }

-- {SCALAR} 1712.1.43.4
lcsStatusMailClearBuffer OBJECT-TYPE
    SYNTAX     DisplayString
    MAX-ACCESS read-write
    STATUS     current
    DESCRIPTION
        "-- empty --"
    ::= { lcsStatusMail 4 }

-- {SCALAR} 1712.1.43.5
lcsStatusMailDeleteStatistics OBJECT-TYPE
    SYNTAX     DisplayString
    MAX-ACCESS read-write
    STATUS     current
    DESCRIPTION
        "-- empty --"
    ::= { lcsStatusMail 5 }

-- {OID} 1712.1.72
lcsStatusDsl OBJECT IDENTIFIER ::= { lcsStatus 72 }

-- {TABLE} 1712.1.72.1
lcsStatusDslInterfacesTable OBJECT-TYPE
    SYNTAX     SEQUENCE OF LcsStatusDslInterfacesEntry
    MAX-ACCESS not-accessible
    STATUS     current
    DESCRIPTION
        "-- empty --"
    ::= { lcsStatusDsl 1 }

-- {ENTRY} 1712.1.72.1.1
lcsStatusDslInterfacesEntry OBJECT-TYPE
    SYNTAX     LcsStatusDslInterfacesEntry
    MAX-ACCESS not-accessible
    STATUS     current
    DESCRIPTION
        ""
    INDEX {
        lcsStatusDslInterfacesEntryIfc
    }
    ::= { lcsStatusDslInterfacesTable 1 }

-- {SEQUENCE}
LcsStatusDslInterfacesEntry ::= SEQUENCE {
    lcsStatusDslInterfacesEntryIfc DisplayString,
    lcsStatusDslInterfacesEntryLinkActive INTEGER
}

-- {COLUMN} 1712.1.72.1.1.1
lcsStatusDslInterfacesEntryIfc OBJECT-TYPE
    SYNTAX     DisplayString (SIZE(0..255))
    MAX-ACCESS read-only
    STATUS     current
    DESCRIPTION
        "-- empty --"
    ::= { lcsStatusDslInterfacesEntry 1 }

-- {COLUMN} 1712.1.72.1.1.3
lcsStatusDslInterfacesEntryLinkActive OBJECT-TYPE
    SYNTAX     INTEGER
      {
        eNo (0),
        eYes (1)
      }
    MAX-ACCESS read-only
    STATUS     current
    DESCRIPTION
        "-- empty --"
    ::= { lcsStatusDslInterfacesEntry 3 }

-- {TABLE} 1712.1.72.2
lcsStatusDslByteTransportTable OBJECT-TYPE
    SYNTAX     SEQUENCE OF LcsStatusDslByteTransportEntry
    MAX-ACCESS not-accessible
    STATUS     current
    DESCRIPTION
        "-- empty --"
    ::= { lcsStatusDsl 2 }

-- {ENTRY} 1712.1.72.2.1
lcsStatusDslByteTransportEntry OBJECT-TYPE
    SYNTAX     LcsStatusDslByteTransportEntry
    MAX-ACCESS not-accessible
    STATUS     current
    DESCRIPTION
        ""
    INDEX {
        lcsStatusDslByteTransportEntryIfc
    }
    ::= { lcsStatusDslByteTransportTable 1 }

-- {SEQUENCE}
LcsStatusDslByteTransportEntry ::= SEQUENCE {
    lcsStatusDslByteTransportEntryIfc DisplayString,
    lcsStatusDslByteTransportEntryTxBytes Counter64,
    lcsStatusDslByteTransportEntryRxBytes Counter64
}

-- {COLUMN} 1712.1.72.2.1.1
lcsStatusDslByteTransportEntryIfc OBJECT-TYPE
    SYNTAX     DisplayString (SIZE(0..255))
    MAX-ACCESS read-only
    STATUS     current
    DESCRIPTION
        "-- empty --"
    ::= { lcsStatusDslByteTransportEntry 1 }

-- {COLUMN} 1712.1.72.2.1.2
lcsStatusDslByteTransportEntryTxBytes OBJECT-TYPE
    SYNTAX     Counter64
    MAX-ACCESS read-only
    STATUS     current
    DESCRIPTION
        "-- empty --"
    ::= { lcsStatusDslByteTransportEntry 2 }

-- {COLUMN} 1712.1.72.2.1.3
lcsStatusDslByteTransportEntryRxBytes OBJECT-TYPE
    SYNTAX     Counter64
    MAX-ACCESS read-only
    STATUS     current
    DESCRIPTION
        "-- empty --"
    ::= { lcsStatusDslByteTransportEntry 3 }

-- {TABLE} 1712.1.72.3
lcsStatusDslPacketTransportTable OBJECT-TYPE
    SYNTAX     SEQUENCE OF LcsStatusDslPacketTransportEntry
    MAX-ACCESS not-accessible
    STATUS     current
    DESCRIPTION
        "-- empty --"
    ::= { lcsStatusDsl 3 }

-- {ENTRY} 1712.1.72.3.1
lcsStatusDslPacketTransportEntry OBJECT-TYPE
    SYNTAX     LcsStatusDslPacketTransportEntry
    MAX-ACCESS not-accessible
    STATUS     current
    DESCRIPTION
        ""
    INDEX {
        lcsStatusDslPacketTransportEntryIfc
    }
    ::= { lcsStatusDslPacketTransportTable 1 }

-- {SEQUENCE}
LcsStatusDslPacketTransportEntry ::= SEQUENCE {
    lcsStatusDslPacketTransportEntryIfc DisplayString,
    lcsStatusDslPacketTransportEntryRxPackets Counter32,
    lcsStatusDslPacketTransportEntryTxPackets Counter32,
    lcsStatusDslPacketTransportEntryRxBroadcasts Counter32,
    lcsStatusDslPacketTransportEntryRxMulticasts Counter32,
    lcsStatusDslPacketTransportEntryRxUnicasts Counter32,
    lcsStatusDslPacketTransportEntryTxBroadcasts Counter32,
    lcsStatusDslPacketTransportEntryTxMulticasts Counter32,
    lcsStatusDslPacketTransportEntryTxUnicasts Counter32
}

-- {COLUMN} 1712.1.72.3.1.1
lcsStatusDslPacketTransportEntryIfc OBJECT-TYPE
    SYNTAX     DisplayString (SIZE(0..255))
    MAX-ACCESS read-only
    STATUS     current
    DESCRIPTION
        "-- empty --"
    ::= { lcsStatusDslPacketTransportEntry 1 }

-- {COLUMN} 1712.1.72.3.1.2
lcsStatusDslPacketTransportEntryRxPackets OBJECT-TYPE
    SYNTAX     Counter32
    MAX-ACCESS read-only
    STATUS     current
    DESCRIPTION
        "-- empty --"
    ::= { lcsStatusDslPacketTransportEntry 2 }

-- {COLUMN} 1712.1.72.3.1.3
lcsStatusDslPacketTransportEntryTxPackets OBJECT-TYPE
    SYNTAX     Counter32
    MAX-ACCESS read-only
    STATUS     current
    DESCRIPTION
        "-- empty --"
    ::= { lcsStatusDslPacketTransportEntry 3 }

-- {COLUMN} 1712.1.72.3.1.4
lcsStatusDslPacketTransportEntryRxBroadcasts OBJECT-TYPE
    SYNTAX     Counter32
    MAX-ACCESS read-only
    STATUS     current
    DESCRIPTION
        "-- empty --"
    ::= { lcsStatusDslPacketTransportEntry 4 }

-- {COLUMN} 1712.1.72.3.1.5
lcsStatusDslPacketTransportEntryRxMulticasts OBJECT-TYPE
    SYNTAX     Counter32
    MAX-ACCESS read-only
    STATUS     current
    DESCRIPTION
        "-- empty --"
    ::= { lcsStatusDslPacketTransportEntry 5 }

-- {COLUMN} 1712.1.72.3.1.6
lcsStatusDslPacketTransportEntryRxUnicasts OBJECT-TYPE
    SYNTAX     Counter32
    MAX-ACCESS read-only
    STATUS     current
    DESCRIPTION
        "-- empty --"
    ::= { lcsStatusDslPacketTransportEntry 6 }

-- {COLUMN} 1712.1.72.3.1.7
lcsStatusDslPacketTransportEntryTxBroadcasts OBJECT-TYPE
    SYNTAX     Counter32
    MAX-ACCESS read-only
    STATUS     current
    DESCRIPTION
        "-- empty --"
    ::= { lcsStatusDslPacketTransportEntry 7 }

-- {COLUMN} 1712.1.72.3.1.8
lcsStatusDslPacketTransportEntryTxMulticasts OBJECT-TYPE
    SYNTAX     Counter32
    MAX-ACCESS read-only
    STATUS     current
    DESCRIPTION
        "-- empty --"
    ::= { lcsStatusDslPacketTransportEntry 8 }

-- {COLUMN} 1712.1.72.3.1.9
lcsStatusDslPacketTransportEntryTxUnicasts OBJECT-TYPE
    SYNTAX     Counter32
    MAX-ACCESS read-only
    STATUS     current
    DESCRIPTION
        "-- empty --"
    ::= { lcsStatusDslPacketTransportEntry 9 }

-- {TABLE} 1712.1.72.4
lcsStatusDslErrorsTable OBJECT-TYPE
    SYNTAX     SEQUENCE OF LcsStatusDslErrorsEntry
    MAX-ACCESS not-accessible
    STATUS     current
    DESCRIPTION
        "-- empty --"
    ::= { lcsStatusDsl 4 }

-- {ENTRY} 1712.1.72.4.1
lcsStatusDslErrorsEntry OBJECT-TYPE
    SYNTAX     LcsStatusDslErrorsEntry
    MAX-ACCESS not-accessible
    STATUS     current
    DESCRIPTION
        ""
    INDEX {
        lcsStatusDslErrorsEntryIfc
    }
    ::= { lcsStatusDslErrorsTable 1 }

-- {SEQUENCE}
LcsStatusDslErrorsEntry ::= SEQUENCE {
    lcsStatusDslErrorsEntryIfc DisplayString,
    lcsStatusDslErrorsEntryRxErrors Counter32,
    lcsStatusDslErrorsEntryTxErrors Counter32,
    lcsStatusDslErrorsEntryStackErrors Counter32,
    lcsStatusDslErrorsEntryNicErrors Counter32,
    lcsStatusDslErrorsEntryQueueErrors Counter32,
    lcsStatusDslErrorsEntryRxCrcErrors Counter32,
    lcsStatusDslErrorsEntryCollisions Counter32,
    lcsStatusDslErrorsEntrySingleCollisions Counter32,
    lcsStatusDslErrorsEntryMultipleCollisions Counter32,
    lcsStatusDslErrorsEntryLateCollisions Counter32,
    lcsStatusDslErrorsEntryExcessiveCollisions Counter32,
    lcsStatusDslErrorsEntryRxAlignErrors Counter32,
    lcsStatusDslErrorsEntryRxTooShort Counter32,
    lcsStatusDslErrorsEntryRxTooLong Counter32,
    lcsStatusDslErrorsEntryTxCarrier Counter32,
    lcsStatusDslErrorsEntryTxDeferred Counter32
}

-- {COLUMN} 1712.1.72.4.1.1
lcsStatusDslErrorsEntryIfc OBJECT-TYPE
    SYNTAX     DisplayString (SIZE(0..255))
    MAX-ACCESS read-only
    STATUS     current
    DESCRIPTION
        "-- empty --"
    ::= { lcsStatusDslErrorsEntry 1 }

-- {COLUMN} 1712.1.72.4.1.2
lcsStatusDslErrorsEntryRxErrors OBJECT-TYPE
    SYNTAX     Counter32
    MAX-ACCESS read-only
    STATUS     current
    DESCRIPTION
        "-- empty --"
    ::= { lcsStatusDslErrorsEntry 2 }

-- {COLUMN} 1712.1.72.4.1.3
lcsStatusDslErrorsEntryTxErrors OBJECT-TYPE
    SYNTAX     Counter32
    MAX-ACCESS read-only
    STATUS     current
    DESCRIPTION
        "-- empty --"
    ::= { lcsStatusDslErrorsEntry 3 }

-- {COLUMN} 1712.1.72.4.1.4
lcsStatusDslErrorsEntryStackErrors OBJECT-TYPE
    SYNTAX     Counter32
    MAX-ACCESS read-only
    STATUS     current
    DESCRIPTION
        "-- empty --"
    ::= { lcsStatusDslErrorsEntry 4 }

-- {COLUMN} 1712.1.72.4.1.5
lcsStatusDslErrorsEntryNicErrors OBJECT-TYPE
    SYNTAX     Counter32
    MAX-ACCESS read-only
    STATUS     current
    DESCRIPTION
        "-- empty --"
    ::= { lcsStatusDslErrorsEntry 5 }

-- {COLUMN} 1712.1.72.4.1.6
lcsStatusDslErrorsEntryQueueErrors OBJECT-TYPE
    SYNTAX     Counter32
    MAX-ACCESS read-only
    STATUS     current
    DESCRIPTION
        "-- empty --"
    ::= { lcsStatusDslErrorsEntry 6 }

-- {COLUMN} 1712.1.72.4.1.7
lcsStatusDslErrorsEntryRxCrcErrors OBJECT-TYPE
    SYNTAX     Counter32
    MAX-ACCESS read-only
    STATUS     current
    DESCRIPTION
        "-- empty --"
    ::= { lcsStatusDslErrorsEntry 7 }

-- {COLUMN} 1712.1.72.4.1.8
lcsStatusDslErrorsEntryCollisions OBJECT-TYPE
    SYNTAX     Counter32
    MAX-ACCESS read-only
    STATUS     current
    DESCRIPTION
        "-- empty --"
    ::= { lcsStatusDslErrorsEntry 8 }

-- {COLUMN} 1712.1.72.4.1.9
lcsStatusDslErrorsEntrySingleCollisions OBJECT-TYPE
    SYNTAX     Counter32
    MAX-ACCESS read-only
    STATUS     current
    DESCRIPTION
        "-- empty --"
    ::= { lcsStatusDslErrorsEntry 9 }

-- {COLUMN} 1712.1.72.4.1.10
lcsStatusDslErrorsEntryMultipleCollisions OBJECT-TYPE
    SYNTAX     Counter32
    MAX-ACCESS read-only
    STATUS     current
    DESCRIPTION
        "-- empty --"
    ::= { lcsStatusDslErrorsEntry 10 }

-- {COLUMN} 1712.1.72.4.1.11
lcsStatusDslErrorsEntryLateCollisions OBJECT-TYPE
    SYNTAX     Counter32
    MAX-ACCESS read-only
    STATUS     current
    DESCRIPTION
        "-- empty --"
    ::= { lcsStatusDslErrorsEntry 11 }

-- {COLUMN} 1712.1.72.4.1.12
lcsStatusDslErrorsEntryExcessiveCollisions OBJECT-TYPE
    SYNTAX     Counter32
    MAX-ACCESS read-only
    STATUS     current
    DESCRIPTION
        "-- empty --"
    ::= { lcsStatusDslErrorsEntry 12 }

-- {COLUMN} 1712.1.72.4.1.13
lcsStatusDslErrorsEntryRxAlignErrors OBJECT-TYPE
    SYNTAX     Counter32
    MAX-ACCESS read-only
    STATUS     current
    DESCRIPTION
        "-- empty --"
    ::= { lcsStatusDslErrorsEntry 13 }

-- {COLUMN} 1712.1.72.4.1.14
lcsStatusDslErrorsEntryRxTooShort OBJECT-TYPE
    SYNTAX     Counter32
    MAX-ACCESS read-only
    STATUS     current
    DESCRIPTION
        "-- empty --"
    ::= { lcsStatusDslErrorsEntry 14 }

-- {COLUMN} 1712.1.72.4.1.15
lcsStatusDslErrorsEntryRxTooLong OBJECT-TYPE
    SYNTAX     Counter32
    MAX-ACCESS read-only
    STATUS     current
    DESCRIPTION
        "-- empty --"
    ::= { lcsStatusDslErrorsEntry 15 }

-- {COLUMN} 1712.1.72.4.1.16
lcsStatusDslErrorsEntryTxCarrier OBJECT-TYPE
    SYNTAX     Counter32
    MAX-ACCESS read-only
    STATUS     current
    DESCRIPTION
        "-- empty --"
    ::= { lcsStatusDslErrorsEntry 16 }

-- {COLUMN} 1712.1.72.4.1.17
lcsStatusDslErrorsEntryTxDeferred OBJECT-TYPE
    SYNTAX     Counter32
    MAX-ACCESS read-only
    STATUS     current
    DESCRIPTION
        "-- empty --"
    ::= { lcsStatusDslErrorsEntry 17 }

-- {SCALAR} 1712.1.72.30
lcsStatusDslDeleteValues OBJECT-TYPE
    SYNTAX     DisplayString
    MAX-ACCESS read-write
    STATUS     current
    DESCRIPTION
        "-- empty --"
    ::= { lcsStatusDsl 30 }

-- {OID} 1712.1.77
lcsStatusIpv6 OBJECT IDENTIFIER ::= { lcsStatus 77 }

-- {TABLE} 1712.1.77.1
lcsStatusIpv6AddressesTable OBJECT-TYPE
    SYNTAX     SEQUENCE OF LcsStatusIpv6AddressesEntry
    MAX-ACCESS not-accessible
    STATUS     current
    DESCRIPTION
        "-- empty --"
    ::= { lcsStatusIpv6 1 }

-- {ENTRY} 1712.1.77.1.1
lcsStatusIpv6AddressesEntry OBJECT-TYPE
    SYNTAX     LcsStatusIpv6AddressesEntry
    MAX-ACCESS not-accessible
    STATUS     current
    DESCRIPTION
        ""
    INDEX {
        lcsStatusIpv6AddressesEntryInterfaceName,
        lcsStatusIpv6AddressesEntryIpv6Address
    }
    ::= { lcsStatusIpv6AddressesTable 1 }

-- {SEQUENCE}
LcsStatusIpv6AddressesEntry ::= SEQUENCE {
    lcsStatusIpv6AddressesEntryInterfaceName DisplayString,
    lcsStatusIpv6AddressesEntryIpv6Address DisplayString,
    lcsStatusIpv6AddressesEntryStatus DisplayString,
    lcsStatusIpv6AddressesEntryProperties DisplayString,
    lcsStatusIpv6AddressesEntryAddressType DisplayString,
    lcsStatusIpv6AddressesEntryInterfaceType INTEGER
}

-- {COLUMN} 1712.1.77.1.1.1
lcsStatusIpv6AddressesEntryInterfaceName OBJECT-TYPE
    SYNTAX     DisplayString (SIZE(0..16))
    MAX-ACCESS read-only
    STATUS     current
    DESCRIPTION
        "-- empty --"
    ::= { lcsStatusIpv6AddressesEntry 1 }

-- {COLUMN} 1712.1.77.1.1.2
lcsStatusIpv6AddressesEntryIpv6Address OBJECT-TYPE
    SYNTAX     DisplayString (SIZE(0..39))
    MAX-ACCESS read-only
    STATUS     current
    DESCRIPTION
        "-- empty --"
    ::= { lcsStatusIpv6AddressesEntry 2 }

-- {COLUMN} 1712.1.77.1.1.3
lcsStatusIpv6AddressesEntryStatus OBJECT-TYPE
    SYNTAX     DisplayString (SIZE(0..10))
    MAX-ACCESS read-only
    STATUS     current
    DESCRIPTION
        "-- empty --"
    ::= { lcsStatusIpv6AddressesEntry 3 }

-- {COLUMN} 1712.1.77.1.1.4
lcsStatusIpv6AddressesEntryProperties OBJECT-TYPE
    SYNTAX     DisplayString (SIZE(0..57))
    MAX-ACCESS read-only
    STATUS     current
    DESCRIPTION
        "-- empty --"
    ::= { lcsStatusIpv6AddressesEntry 4 }

-- {COLUMN} 1712.1.77.1.1.5
lcsStatusIpv6AddressesEntryAddressType OBJECT-TYPE
    SYNTAX     DisplayString (SIZE(0..26))
    MAX-ACCESS read-only
    STATUS     current
    DESCRIPTION
        "-- empty --"
    ::= { lcsStatusIpv6AddressesEntry 5 }

-- {COLUMN} 1712.1.77.1.1.6
lcsStatusIpv6AddressesEntryInterfaceType OBJECT-TYPE
    SYNTAX     INTEGER
      {
        eLan (0),
        eWan (1),
        eLoopback (2)
      }
    MAX-ACCESS read-only
    STATUS     current
    DESCRIPTION
        "-- empty --"
    ::= { lcsStatusIpv6AddressesEntry 6 }

-- {TABLE} 1712.1.77.2
lcsStatusIpv6PrefixTable OBJECT-TYPE
    SYNTAX     SEQUENCE OF LcsStatusIpv6PrefixEntry
    MAX-ACCESS not-accessible
    STATUS     current
    DESCRIPTION
        "-- empty --"
    ::= { lcsStatusIpv6 2 }

-- {ENTRY} 1712.1.77.2.1
lcsStatusIpv6PrefixEntry OBJECT-TYPE
    SYNTAX     LcsStatusIpv6PrefixEntry
    MAX-ACCESS not-accessible
    STATUS     current
    DESCRIPTION
        ""
    INDEX {
        lcsStatusIpv6PrefixEntryInterfaceName,
        lcsStatusIpv6PrefixEntryPrefix
    }
    ::= { lcsStatusIpv6PrefixTable 1 }

-- {SEQUENCE}
LcsStatusIpv6PrefixEntry ::= SEQUENCE {
    lcsStatusIpv6PrefixEntryInterfaceName DisplayString,
    lcsStatusIpv6PrefixEntryPrefix DisplayString,
    lcsStatusIpv6PrefixEntryStatus DisplayString,
    lcsStatusIpv6PrefixEntryType DisplayString
}

-- {COLUMN} 1712.1.77.2.1.1
lcsStatusIpv6PrefixEntryInterfaceName OBJECT-TYPE
    SYNTAX     DisplayString (SIZE(0..16))
    MAX-ACCESS read-only
    STATUS     current
    DESCRIPTION
        "-- empty --"
    ::= { lcsStatusIpv6PrefixEntry 1 }

-- {COLUMN} 1712.1.77.2.1.2
lcsStatusIpv6PrefixEntryPrefix OBJECT-TYPE
    SYNTAX     DisplayString (SIZE(0..43))
    MAX-ACCESS read-only
    STATUS     current
    DESCRIPTION
        "-- empty --"
    ::= { lcsStatusIpv6PrefixEntry 2 }

-- {COLUMN} 1712.1.77.2.1.3
lcsStatusIpv6PrefixEntryStatus OBJECT-TYPE
    SYNTAX     DisplayString (SIZE(0..10))
    MAX-ACCESS read-only
    STATUS     current
    DESCRIPTION
        "-- empty --"
    ::= { lcsStatusIpv6PrefixEntry 3 }

-- {COLUMN} 1712.1.77.2.1.4
lcsStatusIpv6PrefixEntryType OBJECT-TYPE
    SYNTAX     DisplayString (SIZE(0..26))
    MAX-ACCESS read-only
    STATUS     current
    DESCRIPTION
        "-- empty --"
    ::= { lcsStatusIpv6PrefixEntry 4 }

-- {SCALAR} 1712.1.77.4
lcsStatusIpv6Interfaces OBJECT-TYPE
    SYNTAX     INTEGER (0..2147483647)
    MAX-ACCESS read-only
    STATUS     current
    DESCRIPTION
        "-- empty --"
    ::= { lcsStatusIpv6 4 }

-- {SCALAR} 1712.1.77.5
lcsStatusIpv6ActIpRoutingTab OBJECT-TYPE
    SYNTAX     INTEGER (0..2147483647)
    MAX-ACCESS read-only
    STATUS     current
    DESCRIPTION
        "-- empty --"
    ::= { lcsStatusIpv6 5 }

-- {OID} 1712.1.77.6
lcsStatusIpv6Network OBJECT IDENTIFIER ::= { lcsStatusIpv6 6 }

-- {SCALAR} 1712.1.77.6.1
lcsStatusIpv6NetworkAddresses OBJECT-TYPE
    SYNTAX     INTEGER (0..2147483647)
    MAX-ACCESS read-only
    STATUS     current
    DESCRIPTION
        "-- empty --"
    ::= { lcsStatusIpv6Network 1 }

-- {SCALAR} 1712.1.77.6.2
lcsStatusIpv6NetworkParameter OBJECT-TYPE
    SYNTAX     INTEGER (0..2147483647)
    MAX-ACCESS read-only
    STATUS     current
    DESCRIPTION
        "-- empty --"
    ::= { lcsStatusIpv6Network 2 }

-- {OID} 1712.1.77.7
lcsStatusIpv6RouterAdv OBJECT IDENTIFIER ::= { lcsStatusIpv6 7 }

-- {SCALAR} 1712.1.77.7.1
lcsStatusIpv6RouterAdvInterfaceOptions OBJECT-TYPE
    SYNTAX     INTEGER (0..2147483647)
    MAX-ACCESS read-only
    STATUS     current
    DESCRIPTION
        "-- empty --"
    ::= { lcsStatusIpv6RouterAdv 1 }

-- {SCALAR} 1712.1.77.7.2
lcsStatusIpv6RouterAdvPrefixOptions OBJECT-TYPE
    SYNTAX     INTEGER (0..2147483647)
    MAX-ACCESS read-only
    STATUS     current
    DESCRIPTION
        "-- empty --"
    ::= { lcsStatusIpv6RouterAdv 2 }

-- {OID} 1712.1.77.8
lcsStatusIpv6Tunnel OBJECT IDENTIFIER ::= { lcsStatusIpv6 8 }

-- {SCALAR} 1712.1.77.8.1
lcsStatusIpv6Tunnel6in4 OBJECT-TYPE
    SYNTAX     INTEGER (0..2147483647)
    MAX-ACCESS read-only
    STATUS     current
    DESCRIPTION
        "-- empty --"
    ::= { lcsStatusIpv6Tunnel 1 }

-- {SCALAR} 1712.1.77.8.2
lcsStatusIpv6Tunnel6rd OBJECT-TYPE
    SYNTAX     INTEGER (0..2147483647)
    MAX-ACCESS read-only
    STATUS     current
    DESCRIPTION
        "-- empty --"
    ::= { lcsStatusIpv6Tunnel 2 }

-- {SCALAR} 1712.1.77.8.3
lcsStatusIpv6Tunnel6rdBorderRelay OBJECT-TYPE
    SYNTAX     INTEGER (0..2147483647)
    MAX-ACCESS read-only
    STATUS     current
    DESCRIPTION
        "-- empty --"
    ::= { lcsStatusIpv6Tunnel 3 }

-- {SCALAR} 1712.1.77.8.4
lcsStatusIpv6Tunnel6to4 OBJECT-TYPE
    SYNTAX     INTEGER (0..2147483647)
    MAX-ACCESS read-only
    STATUS     current
    DESCRIPTION
        "-- empty --"
    ::= { lcsStatusIpv6Tunnel 4 }

-- {OID} 1712.1.77.3
lcsStatusIpv6Dhcpv6 OBJECT IDENTIFIER ::= { lcsStatusIpv6 3 }

-- {OID} 1712.1.77.3.1
lcsStatusIpv6Dhcpv6Server OBJECT IDENTIFIER ::= { lcsStatusIpv6Dhcpv6 1 }

-- {TABLE} 1712.1.77.3.1.1
lcsStatusIpv6Dhcpv6ServerAddressBindTable OBJECT-TYPE
    SYNTAX     SEQUENCE OF LcsStatusIpv6Dhcpv6ServerAddressBindEntry
    MAX-ACCESS not-accessible
    STATUS     current
    DESCRIPTION
        ""
    ::= { lcsStatusIpv6Dhcpv6Server 1 }

-- {ENTRY} 1712.1.77.3.1.1.1
lcsStatusIpv6Dhcpv6ServerAddressBindEntry OBJECT-TYPE
    SYNTAX     LcsStatusIpv6Dhcpv6ServerAddressBindEntry
    MAX-ACCESS not-accessible
    STATUS     current
    DESCRIPTION
        ""
    INDEX {
        lcsStatusIpv6Dhcpv6ServerAddressBindEntryInterfaceNameOrRelay,
        lcsStatusIpv6Dhcpv6ServerAddressBindEntryAddress
    }
    ::= { lcsStatusIpv6Dhcpv6ServerAddressBindTable 1 }

-- {SEQUENCE}
LcsStatusIpv6Dhcpv6ServerAddressBindEntry ::= SEQUENCE {
    lcsStatusIpv6Dhcpv6ServerAddressBindEntryInterfaceNameOrRelay DisplayString,
    lcsStatusIpv6Dhcpv6ServerAddressBindEntryAddress DisplayString,
    lcsStatusIpv6Dhcpv6ServerAddressBindEntryHostName DisplayString,
    lcsStatusIpv6Dhcpv6ServerAddressBindEntryPreferredUntilNumerical Counter32,
    lcsStatusIpv6Dhcpv6ServerAddressBindEntryPreferredUntil DisplayString,
    lcsStatusIpv6Dhcpv6ServerAddressBindEntryValidUntilNumerical Counter32,
    lcsStatusIpv6Dhcpv6ServerAddressBindEntryValidUntil DisplayString,
    lcsStatusIpv6Dhcpv6ServerAddressBindEntryUpdatedAtNumerical Counter32,
    lcsStatusIpv6Dhcpv6ServerAddressBindEntryUpdatedAt DisplayString,
    lcsStatusIpv6Dhcpv6ServerAddressBindEntryClientId DisplayString,
    lcsStatusIpv6Dhcpv6ServerAddressBindEntryIaId INTEGER
}

-- {COLUMN} 1712.1.77.3.1.1.1.1
lcsStatusIpv6Dhcpv6ServerAddressBindEntryInterfaceNameOrRelay OBJECT-TYPE
    SYNTAX     DisplayString (SIZE(0..255))
    MAX-ACCESS read-only
    STATUS     current
    DESCRIPTION
        "-- empty --"
    ::= { lcsStatusIpv6Dhcpv6ServerAddressBindEntry 1 }

-- {COLUMN} 1712.1.77.3.1.1.1.2
lcsStatusIpv6Dhcpv6ServerAddressBindEntryAddress OBJECT-TYPE
    SYNTAX     DisplayString (SIZE(0..255))
    MAX-ACCESS read-only
    STATUS     current
    DESCRIPTION
        "-- empty --"
    ::= { lcsStatusIpv6Dhcpv6ServerAddressBindEntry 2 }

-- {COLUMN} 1712.1.77.3.1.1.1.9
lcsStatusIpv6Dhcpv6ServerAddressBindEntryHostName OBJECT-TYPE
    SYNTAX     DisplayString (SIZE(0..255))
    MAX-ACCESS read-only
    STATUS     current
    DESCRIPTION
        "-- empty --"
    ::= { lcsStatusIpv6Dhcpv6ServerAddressBindEntry 9 }

-- {COLUMN} 1712.1.77.3.1.1.1.3
lcsStatusIpv6Dhcpv6ServerAddressBindEntryPreferredUntilNumerical OBJECT-TYPE
    SYNTAX     Counter32
    MAX-ACCESS read-only
    STATUS     current
    DESCRIPTION
        "-- empty --"
    ::= { lcsStatusIpv6Dhcpv6ServerAddressBindEntry 3 }

-- {COLUMN} 1712.1.77.3.1.1.1.4
lcsStatusIpv6Dhcpv6ServerAddressBindEntryPreferredUntil OBJECT-TYPE
    SYNTAX     DisplayString (SIZE(0..255))
    MAX-ACCESS read-only
    STATUS     current
    DESCRIPTION
        "-- empty --"
    ::= { lcsStatusIpv6Dhcpv6ServerAddressBindEntry 4 }

-- {COLUMN} 1712.1.77.3.1.1.1.5
lcsStatusIpv6Dhcpv6ServerAddressBindEntryValidUntilNumerical OBJECT-TYPE
    SYNTAX     Counter32
    MAX-ACCESS read-only
    STATUS     current
    DESCRIPTION
        "-- empty --"
    ::= { lcsStatusIpv6Dhcpv6ServerAddressBindEntry 5 }

-- {COLUMN} 1712.1.77.3.1.1.1.6
lcsStatusIpv6Dhcpv6ServerAddressBindEntryValidUntil OBJECT-TYPE
    SYNTAX     DisplayString (SIZE(0..255))
    MAX-ACCESS read-only
    STATUS     current
    DESCRIPTION
        "-- empty --"
    ::= { lcsStatusIpv6Dhcpv6ServerAddressBindEntry 6 }

-- {COLUMN} 1712.1.77.3.1.1.1.10
lcsStatusIpv6Dhcpv6ServerAddressBindEntryUpdatedAtNumerical OBJECT-TYPE
    SYNTAX     Counter32
    MAX-ACCESS read-only
    STATUS     current
    DESCRIPTION
        "-- empty --"
    ::= { lcsStatusIpv6Dhcpv6ServerAddressBindEntry 10 }

-- {COLUMN} 1712.1.77.3.1.1.1.11
lcsStatusIpv6Dhcpv6ServerAddressBindEntryUpdatedAt OBJECT-TYPE
    SYNTAX     DisplayString (SIZE(0..255))
    MAX-ACCESS read-only
    STATUS     current
    DESCRIPTION
        "-- empty --"
    ::= { lcsStatusIpv6Dhcpv6ServerAddressBindEntry 11 }

-- {COLUMN} 1712.1.77.3.1.1.1.7
lcsStatusIpv6Dhcpv6ServerAddressBindEntryClientId OBJECT-TYPE
    SYNTAX     DisplayString (SIZE(0..255))
    MAX-ACCESS read-only
    STATUS     current
    DESCRIPTION
        "-- empty --"
    ::= { lcsStatusIpv6Dhcpv6ServerAddressBindEntry 7 }

-- {COLUMN} 1712.1.77.3.1.1.1.8
lcsStatusIpv6Dhcpv6ServerAddressBindEntryIaId OBJECT-TYPE
    SYNTAX     INTEGER (0..2147483647)
    MAX-ACCESS read-only
    STATUS     current
    DESCRIPTION
        "-- empty --"
    ::= { lcsStatusIpv6Dhcpv6ServerAddressBindEntry 8 }

-- {TABLE} 1712.1.77.3.1.2
lcsStatusIpv6Dhcpv6ServerPdBindingsTable OBJECT-TYPE
    SYNTAX     SEQUENCE OF LcsStatusIpv6Dhcpv6ServerPdBindingsEntry
    MAX-ACCESS not-accessible
    STATUS     current
    DESCRIPTION
        "-- empty --"
    ::= { lcsStatusIpv6Dhcpv6Server 2 }

-- {ENTRY} 1712.1.77.3.1.2.1
lcsStatusIpv6Dhcpv6ServerPdBindingsEntry OBJECT-TYPE
    SYNTAX     LcsStatusIpv6Dhcpv6ServerPdBindingsEntry
    MAX-ACCESS not-accessible
    STATUS     current
    DESCRIPTION
        ""
    INDEX {
        lcsStatusIpv6Dhcpv6ServerPdBindingsEntryInterfaceNameOrRelay,
        lcsStatusIpv6Dhcpv6ServerPdBindingsEntryPdPrefix
    }
    ::= { lcsStatusIpv6Dhcpv6ServerPdBindingsTable 1 }

-- {SEQUENCE}
LcsStatusIpv6Dhcpv6ServerPdBindingsEntry ::= SEQUENCE {
    lcsStatusIpv6Dhcpv6ServerPdBindingsEntryInterfaceNameOrRelay DisplayString,
    lcsStatusIpv6Dhcpv6ServerPdBindingsEntryPdPrefix DisplayString,
    lcsStatusIpv6Dhcpv6ServerPdBindingsEntryHostName DisplayString,
    lcsStatusIpv6Dhcpv6ServerPdBindingsEntryPreferredUntilNumerical Counter32,
    lcsStatusIpv6Dhcpv6ServerPdBindingsEntryPreferredUntil DisplayString,
    lcsStatusIpv6Dhcpv6ServerPdBindingsEntryValidUntilNumerical Counter32,
    lcsStatusIpv6Dhcpv6ServerPdBindingsEntryValidUntil DisplayString,
    lcsStatusIpv6Dhcpv6ServerPdBindingsEntryUpdatedAtNumerical Counter32,
    lcsStatusIpv6Dhcpv6ServerPdBindingsEntryUpdatedAt DisplayString,
    lcsStatusIpv6Dhcpv6ServerPdBindingsEntryClientId DisplayString,
    lcsStatusIpv6Dhcpv6ServerPdBindingsEntryIaId INTEGER
}

-- {COLUMN} 1712.1.77.3.1.2.1.1
lcsStatusIpv6Dhcpv6ServerPdBindingsEntryInterfaceNameOrRelay OBJECT-TYPE
    SYNTAX     DisplayString (SIZE(0..255))
    MAX-ACCESS read-only
    STATUS     current
    DESCRIPTION
        "-- empty --"
    ::= { lcsStatusIpv6Dhcpv6ServerPdBindingsEntry 1 }

-- {COLUMN} 1712.1.77.3.1.2.1.2
lcsStatusIpv6Dhcpv6ServerPdBindingsEntryPdPrefix OBJECT-TYPE
    SYNTAX     DisplayString (SIZE(0..255))
    MAX-ACCESS read-only
    STATUS     current
    DESCRIPTION
        "-- empty --"
    ::= { lcsStatusIpv6Dhcpv6ServerPdBindingsEntry 2 }

-- {COLUMN} 1712.1.77.3.1.2.1.9
lcsStatusIpv6Dhcpv6ServerPdBindingsEntryHostName OBJECT-TYPE
    SYNTAX     DisplayString (SIZE(0..255))
    MAX-ACCESS read-only
    STATUS     current
    DESCRIPTION
        "-- empty --"
    ::= { lcsStatusIpv6Dhcpv6ServerPdBindingsEntry 9 }

-- {COLUMN} 1712.1.77.3.1.2.1.3
lcsStatusIpv6Dhcpv6ServerPdBindingsEntryPreferredUntilNumerical OBJECT-TYPE
    SYNTAX     Counter32
    MAX-ACCESS read-only
    STATUS     current
    DESCRIPTION
        "-- empty --"
    ::= { lcsStatusIpv6Dhcpv6ServerPdBindingsEntry 3 }

-- {COLUMN} 1712.1.77.3.1.2.1.4
lcsStatusIpv6Dhcpv6ServerPdBindingsEntryPreferredUntil OBJECT-TYPE
    SYNTAX     DisplayString (SIZE(0..255))
    MAX-ACCESS read-only
    STATUS     current
    DESCRIPTION
        "-- empty --"
    ::= { lcsStatusIpv6Dhcpv6ServerPdBindingsEntry 4 }

-- {COLUMN} 1712.1.77.3.1.2.1.5
lcsStatusIpv6Dhcpv6ServerPdBindingsEntryValidUntilNumerical OBJECT-TYPE
    SYNTAX     Counter32
    MAX-ACCESS read-only
    STATUS     current
    DESCRIPTION
        "-- empty --"
    ::= { lcsStatusIpv6Dhcpv6ServerPdBindingsEntry 5 }

-- {COLUMN} 1712.1.77.3.1.2.1.6
lcsStatusIpv6Dhcpv6ServerPdBindingsEntryValidUntil OBJECT-TYPE
    SYNTAX     DisplayString (SIZE(0..255))
    MAX-ACCESS read-only
    STATUS     current
    DESCRIPTION
        "-- empty --"
    ::= { lcsStatusIpv6Dhcpv6ServerPdBindingsEntry 6 }

-- {COLUMN} 1712.1.77.3.1.2.1.10
lcsStatusIpv6Dhcpv6ServerPdBindingsEntryUpdatedAtNumerical OBJECT-TYPE
    SYNTAX     Counter32
    MAX-ACCESS read-only
    STATUS     current
    DESCRIPTION
        "-- empty --"
    ::= { lcsStatusIpv6Dhcpv6ServerPdBindingsEntry 10 }

-- {COLUMN} 1712.1.77.3.1.2.1.11
lcsStatusIpv6Dhcpv6ServerPdBindingsEntryUpdatedAt OBJECT-TYPE
    SYNTAX     DisplayString (SIZE(0..255))
    MAX-ACCESS read-only
    STATUS     current
    DESCRIPTION
        "-- empty --"
    ::= { lcsStatusIpv6Dhcpv6ServerPdBindingsEntry 11 }

-- {COLUMN} 1712.1.77.3.1.2.1.7
lcsStatusIpv6Dhcpv6ServerPdBindingsEntryClientId OBJECT-TYPE
    SYNTAX     DisplayString (SIZE(0..255))
    MAX-ACCESS read-only
    STATUS     current
    DESCRIPTION
        "-- empty --"
    ::= { lcsStatusIpv6Dhcpv6ServerPdBindingsEntry 7 }

-- {COLUMN} 1712.1.77.3.1.2.1.8
lcsStatusIpv6Dhcpv6ServerPdBindingsEntryIaId OBJECT-TYPE
    SYNTAX     INTEGER (0..2147483647)
    MAX-ACCESS read-only
    STATUS     current
    DESCRIPTION
        "-- empty --"
    ::= { lcsStatusIpv6Dhcpv6ServerPdBindingsEntry 8 }

-- {TABLE} 1712.1.77.3.1.3
lcsStatusIpv6Dhcpv6ServerDeclinedAddrTable OBJECT-TYPE
    SYNTAX     SEQUENCE OF LcsStatusIpv6Dhcpv6ServerDeclinedAddrEntry
    MAX-ACCESS not-accessible
    STATUS     current
    DESCRIPTION
        ""
    ::= { lcsStatusIpv6Dhcpv6Server 3 }

-- {ENTRY} 1712.1.77.3.1.3.1
lcsStatusIpv6Dhcpv6ServerDeclinedAddrEntry OBJECT-TYPE
    SYNTAX     LcsStatusIpv6Dhcpv6ServerDeclinedAddrEntry
    MAX-ACCESS not-accessible
    STATUS     current
    DESCRIPTION
        ""
    INDEX {
        lcsStatusIpv6Dhcpv6ServerDeclinedAddrEntryInterfaceNameOrRelay,
        lcsStatusIpv6Dhcpv6ServerDeclinedAddrEntryAddress
    }
    ::= { lcsStatusIpv6Dhcpv6ServerDeclinedAddrTable 1 }

-- {SEQUENCE}
LcsStatusIpv6Dhcpv6ServerDeclinedAddrEntry ::= SEQUENCE {
    lcsStatusIpv6Dhcpv6ServerDeclinedAddrEntryInterfaceNameOrRelay DisplayString,
    lcsStatusIpv6Dhcpv6ServerDeclinedAddrEntryAddress DisplayString,
    lcsStatusIpv6Dhcpv6ServerDeclinedAddrEntryHostName DisplayString,
    lcsStatusIpv6Dhcpv6ServerDeclinedAddrEntryDeclinedAtNumerical Counter32,
    lcsStatusIpv6Dhcpv6ServerDeclinedAddrEntryDeclinedAt DisplayString,
    lcsStatusIpv6Dhcpv6ServerDeclinedAddrEntryClientId DisplayString,
    lcsStatusIpv6Dhcpv6ServerDeclinedAddrEntryIaId INTEGER
}

-- {COLUMN} 1712.1.77.3.1.3.1.1
lcsStatusIpv6Dhcpv6ServerDeclinedAddrEntryInterfaceNameOrRelay OBJECT-TYPE
    SYNTAX     DisplayString (SIZE(0..255))
    MAX-ACCESS read-only
    STATUS     current
    DESCRIPTION
        "-- empty --"
    ::= { lcsStatusIpv6Dhcpv6ServerDeclinedAddrEntry 1 }

-- {COLUMN} 1712.1.77.3.1.3.1.2
lcsStatusIpv6Dhcpv6ServerDeclinedAddrEntryAddress OBJECT-TYPE
    SYNTAX     DisplayString (SIZE(0..255))
    MAX-ACCESS read-only
    STATUS     current
    DESCRIPTION
        "-- empty --"
    ::= { lcsStatusIpv6Dhcpv6ServerDeclinedAddrEntry 2 }

-- {COLUMN} 1712.1.77.3.1.3.1.9
lcsStatusIpv6Dhcpv6ServerDeclinedAddrEntryHostName OBJECT-TYPE
    SYNTAX     DisplayString (SIZE(0..255))
    MAX-ACCESS read-only
    STATUS     current
    DESCRIPTION
        "-- empty --"
    ::= { lcsStatusIpv6Dhcpv6ServerDeclinedAddrEntry 9 }

-- {COLUMN} 1712.1.77.3.1.3.1.3
lcsStatusIpv6Dhcpv6ServerDeclinedAddrEntryDeclinedAtNumerical OBJECT-TYPE
    SYNTAX     Counter32
    MAX-ACCESS read-only
    STATUS     current
    DESCRIPTION
        "-- empty --"
    ::= { lcsStatusIpv6Dhcpv6ServerDeclinedAddrEntry 3 }

-- {COLUMN} 1712.1.77.3.1.3.1.4
lcsStatusIpv6Dhcpv6ServerDeclinedAddrEntryDeclinedAt OBJECT-TYPE
    SYNTAX     DisplayString (SIZE(0..255))
    MAX-ACCESS read-only
    STATUS     current
    DESCRIPTION
        "-- empty --"
    ::= { lcsStatusIpv6Dhcpv6ServerDeclinedAddrEntry 4 }

-- {COLUMN} 1712.1.77.3.1.3.1.5
lcsStatusIpv6Dhcpv6ServerDeclinedAddrEntryClientId OBJECT-TYPE
    SYNTAX     DisplayString (SIZE(0..255))
    MAX-ACCESS read-only
    STATUS     current
    DESCRIPTION
        "-- empty --"
    ::= { lcsStatusIpv6Dhcpv6ServerDeclinedAddrEntry 5 }

-- {COLUMN} 1712.1.77.3.1.3.1.6
lcsStatusIpv6Dhcpv6ServerDeclinedAddrEntryIaId OBJECT-TYPE
    SYNTAX     INTEGER (0..2147483647)
    MAX-ACCESS read-only
    STATUS     current
    DESCRIPTION
        "-- empty --"
    ::= { lcsStatusIpv6Dhcpv6ServerDeclinedAddrEntry 6 }

-- {TABLE} 1712.1.77.3.1.6
lcsStatusIpv6Dhcpv6ServerClientsTable OBJECT-TYPE
    SYNTAX     SEQUENCE OF LcsStatusIpv6Dhcpv6ServerClientsEntry
    MAX-ACCESS not-accessible
    STATUS     current
    DESCRIPTION
        "-- empty --"
    ::= { lcsStatusIpv6Dhcpv6Server 6 }

-- {ENTRY} 1712.1.77.3.1.6.1
lcsStatusIpv6Dhcpv6ServerClientsEntry OBJECT-TYPE
    SYNTAX     LcsStatusIpv6Dhcpv6ServerClientsEntry
    MAX-ACCESS not-accessible
    STATUS     current
    DESCRIPTION
        ""
    INDEX {
        lcsStatusIpv6Dhcpv6ServerClientsEntryClientId
    }
    ::= { lcsStatusIpv6Dhcpv6ServerClientsTable 1 }

-- {SEQUENCE}
LcsStatusIpv6Dhcpv6ServerClientsEntry ::= SEQUENCE {
    lcsStatusIpv6Dhcpv6ServerClientsEntryClientId DisplayString,
    lcsStatusIpv6Dhcpv6ServerClientsEntryHostName DisplayString,
    lcsStatusIpv6Dhcpv6ServerClientsEntryReconfNegotiated INTEGER,
    lcsStatusIpv6Dhcpv6ServerClientsEntryReconfNegotiatedAtNumerical Counter32,
    lcsStatusIpv6Dhcpv6ServerClientsEntryReconfNegotiatedAt DisplayString,
    lcsStatusIpv6Dhcpv6ServerClientsEntryReconfigure INTEGER
}

-- {COLUMN} 1712.1.77.3.1.6.1.1
lcsStatusIpv6Dhcpv6ServerClientsEntryClientId OBJECT-TYPE
    SYNTAX     DisplayString (SIZE(0..255))
    MAX-ACCESS read-only
    STATUS     current
    DESCRIPTION
        "-- empty --"
    ::= { lcsStatusIpv6Dhcpv6ServerClientsEntry 1 }

-- {COLUMN} 1712.1.77.3.1.6.1.2
lcsStatusIpv6Dhcpv6ServerClientsEntryHostName OBJECT-TYPE
    SYNTAX     DisplayString (SIZE(0..255))
    MAX-ACCESS read-only
    STATUS     current
    DESCRIPTION
        "-- empty --"
    ::= { lcsStatusIpv6Dhcpv6ServerClientsEntry 2 }

-- {COLUMN} 1712.1.77.3.1.6.1.3
lcsStatusIpv6Dhcpv6ServerClientsEntryReconfNegotiated OBJECT-TYPE
    SYNTAX     INTEGER
      {
        eNo (0),
        eYes (1),
        eNotEnoughRandom (2)
      }
    MAX-ACCESS read-only
    STATUS     current
    DESCRIPTION
        "-- empty --"
    ::= { lcsStatusIpv6Dhcpv6ServerClientsEntry 3 }

-- {COLUMN} 1712.1.77.3.1.6.1.4
lcsStatusIpv6Dhcpv6ServerClientsEntryReconfNegotiatedAtNumerical OBJECT-TYPE
    SYNTAX     Counter32
    MAX-ACCESS read-only
    STATUS     current
    DESCRIPTION
        "-- empty --"
    ::= { lcsStatusIpv6Dhcpv6ServerClientsEntry 4 }

-- {COLUMN} 1712.1.77.3.1.6.1.5
lcsStatusIpv6Dhcpv6ServerClientsEntryReconfNegotiatedAt OBJECT-TYPE
    SYNTAX     DisplayString (SIZE(0..255))
    MAX-ACCESS read-only
    STATUS     current
    DESCRIPTION
        "-- empty --"
    ::= { lcsStatusIpv6Dhcpv6ServerClientsEntry 5 }

-- {COLUMN} 1712.1.77.3.1.6.1.6
lcsStatusIpv6Dhcpv6ServerClientsEntryReconfigure OBJECT-TYPE
    SYNTAX     INTEGER
      {
        eOff (0),
        eRunning (1),
        eSucceeded (2),
        eFailed (3)
      }
    MAX-ACCESS read-only
    STATUS     current
    DESCRIPTION
        "-- empty --"
    ::= { lcsStatusIpv6Dhcpv6ServerClientsEntry 6 }

-- {SCALAR} 1712.1.77.3.1.5
lcsStatusIpv6Dhcpv6ServerServerId OBJECT-TYPE
    SYNTAX     DisplayString (SIZE(0..97))
    MAX-ACCESS read-only
    STATUS     current
    DESCRIPTION
        "-- empty --"
    ::= { lcsStatusIpv6Dhcpv6Server 5 }

-- {SCALAR} 1712.1.77.3.1.7
lcsStatusIpv6Dhcpv6ServerReconfigure OBJECT-TYPE
    SYNTAX     DisplayString
    MAX-ACCESS read-write
    STATUS     current
    DESCRIPTION
        "-- empty --"
    ::= { lcsStatusIpv6Dhcpv6Server 7 }

-- {TABLE} 1712.1.77.3.1.4
lcsStatusIpv6Dhcpv6ServerInterfaceStateTable OBJECT-TYPE
    SYNTAX     SEQUENCE OF LcsStatusIpv6Dhcpv6ServerInterfaceStateEntry
    MAX-ACCESS not-accessible
    STATUS     current
    DESCRIPTION
        "-- empty --"
    ::= { lcsStatusIpv6Dhcpv6Server 4 }

-- {ENTRY} 1712.1.77.3.1.4.1
lcsStatusIpv6Dhcpv6ServerInterfaceStateEntry OBJECT-TYPE
    SYNTAX     LcsStatusIpv6Dhcpv6ServerInterfaceStateEntry
    MAX-ACCESS not-accessible
    STATUS     current
    DESCRIPTION
        ""
    INDEX {
        lcsStatusIpv6Dhcpv6ServerInterfaceStateEntryInterfaceNameOrRelay
    }
    ::= { lcsStatusIpv6Dhcpv6ServerInterfaceStateTable 1 }

-- {SEQUENCE}
LcsStatusIpv6Dhcpv6ServerInterfaceStateEntry ::= SEQUENCE {
    lcsStatusIpv6Dhcpv6ServerInterfaceStateEntryInterfaceNameOrRelay DisplayString,
    lcsStatusIpv6Dhcpv6ServerInterfaceStateEntryOperating INTEGER,
    lcsStatusIpv6Dhcpv6ServerInterfaceStateEntryMode INTEGER,
    lcsStatusIpv6Dhcpv6ServerInterfaceStateEntryAssignPd INTEGER
}

-- {COLUMN} 1712.1.77.3.1.4.1.1
lcsStatusIpv6Dhcpv6ServerInterfaceStateEntryInterfaceNameOrRelay OBJECT-TYPE
    SYNTAX     DisplayString (SIZE(0..255))
    MAX-ACCESS read-only
    STATUS     current
    DESCRIPTION
        "-- empty --"
    ::= { lcsStatusIpv6Dhcpv6ServerInterfaceStateEntry 1 }

-- {COLUMN} 1712.1.77.3.1.4.1.2
lcsStatusIpv6Dhcpv6ServerInterfaceStateEntryOperating OBJECT-TYPE
    SYNTAX     INTEGER
      {
        eNo (0),
        eYes (1)
      }
    MAX-ACCESS read-only
    STATUS     current
    DESCRIPTION
        "-- empty --"
    ::= { lcsStatusIpv6Dhcpv6ServerInterfaceStateEntry 2 }

-- {COLUMN} 1712.1.77.3.1.4.1.3
lcsStatusIpv6Dhcpv6ServerInterfaceStateEntryMode OBJECT-TYPE
    SYNTAX     INTEGER
      {
        eStateless (0),
        eStateful (1),
        eStatic (2)
      }
    MAX-ACCESS read-only
    STATUS     current
    DESCRIPTION
        "-- empty --"
    ::= { lcsStatusIpv6Dhcpv6ServerInterfaceStateEntry 3 }

-- {COLUMN} 1712.1.77.3.1.4.1.4
lcsStatusIpv6Dhcpv6ServerInterfaceStateEntryAssignPd OBJECT-TYPE
    SYNTAX     INTEGER
      {
        eNo (0),
        eYes (1)
      }
    MAX-ACCESS read-only
    STATUS     current
    DESCRIPTION
        "-- empty --"
    ::= { lcsStatusIpv6Dhcpv6ServerInterfaceStateEntry 4 }

-- {SCALAR} 1712.1.77.3.1.8
lcsStatusIpv6Dhcpv6ServerRasInterfaces OBJECT-TYPE
    SYNTAX     INTEGER (0..2147483647)
    MAX-ACCESS read-only
    STATUS     current
    DESCRIPTION
        "-- empty --"
    ::= { lcsStatusIpv6Dhcpv6Server 8 }

-- {OID} 1712.1.77.3.2
lcsStatusIpv6Dhcpv6Client OBJECT IDENTIFIER ::= { lcsStatusIpv6Dhcpv6 2 }

-- {TABLE} 1712.1.77.3.2.1
lcsStatusIpv6Dhcpv6ClientInterfaceListTable OBJECT-TYPE
    SYNTAX     SEQUENCE OF LcsStatusIpv6Dhcpv6ClientInterfaceListEntry
    MAX-ACCESS not-accessible
    STATUS     current
    DESCRIPTION
        "-- empty --"
    ::= { lcsStatusIpv6Dhcpv6Client 1 }

-- {ENTRY} 1712.1.77.3.2.1.1
lcsStatusIpv6Dhcpv6ClientInterfaceListEntry OBJECT-TYPE
    SYNTAX     LcsStatusIpv6Dhcpv6ClientInterfaceListEntry
    MAX-ACCESS not-accessible
    STATUS     current
    DESCRIPTION
        ""
    INDEX {
        lcsStatusIpv6Dhcpv6ClientInterfaceListEntryInterfaceName
    }
    ::= { lcsStatusIpv6Dhcpv6ClientInterfaceListTable 1 }

-- {SEQUENCE}
LcsStatusIpv6Dhcpv6ClientInterfaceListEntry ::= SEQUENCE {
    lcsStatusIpv6Dhcpv6ClientInterfaceListEntryInterfaceName DisplayString,
    lcsStatusIpv6Dhcpv6ClientInterfaceListEntryDnsDefault DisplayString,
    lcsStatusIpv6Dhcpv6ClientInterfaceListEntryDnsBackup DisplayString,
    lcsStatusIpv6Dhcpv6ClientInterfaceListEntryDomainList DisplayString,
    lcsStatusIpv6Dhcpv6ClientInterfaceListEntryAftrNameForDsLite DisplayString
}

-- {COLUMN} 1712.1.77.3.2.1.1.1
lcsStatusIpv6Dhcpv6ClientInterfaceListEntryInterfaceName OBJECT-TYPE
    SYNTAX     DisplayString (SIZE(0..255))
    MAX-ACCESS read-only
    STATUS     current
    DESCRIPTION
        "-- empty --"
    ::= { lcsStatusIpv6Dhcpv6ClientInterfaceListEntry 1 }

-- {COLUMN} 1712.1.77.3.2.1.1.2
lcsStatusIpv6Dhcpv6ClientInterfaceListEntryDnsDefault OBJECT-TYPE
    SYNTAX     DisplayString (SIZE(0..255))
    MAX-ACCESS read-only
    STATUS     current
    DESCRIPTION
        "-- empty --"
    ::= { lcsStatusIpv6Dhcpv6ClientInterfaceListEntry 2 }

-- {COLUMN} 1712.1.77.3.2.1.1.3
lcsStatusIpv6Dhcpv6ClientInterfaceListEntryDnsBackup OBJECT-TYPE
    SYNTAX     DisplayString (SIZE(0..255))
    MAX-ACCESS read-only
    STATUS     current
    DESCRIPTION
        "-- empty --"
    ::= { lcsStatusIpv6Dhcpv6ClientInterfaceListEntry 3 }

-- {COLUMN} 1712.1.77.3.2.1.1.4
lcsStatusIpv6Dhcpv6ClientInterfaceListEntryDomainList OBJECT-TYPE
    SYNTAX     DisplayString (SIZE(0..255))
    MAX-ACCESS read-only
    STATUS     current
    DESCRIPTION
        "-- empty --"
    ::= { lcsStatusIpv6Dhcpv6ClientInterfaceListEntry 4 }

-- {COLUMN} 1712.1.77.3.2.1.1.5
lcsStatusIpv6Dhcpv6ClientInterfaceListEntryAftrNameForDsLite OBJECT-TYPE
    SYNTAX     DisplayString (SIZE(0..255))
    MAX-ACCESS read-only
    STATUS     current
    DESCRIPTION
        "-- empty --"
    ::= { lcsStatusIpv6Dhcpv6ClientInterfaceListEntry 5 }

-- {TABLE} 1712.1.77.3.2.2
lcsStatusIpv6Dhcpv6ClientAddressBindTable OBJECT-TYPE
    SYNTAX     SEQUENCE OF LcsStatusIpv6Dhcpv6ClientAddressBindEntry
    MAX-ACCESS not-accessible
    STATUS     current
    DESCRIPTION
        ""
    ::= { lcsStatusIpv6Dhcpv6Client 2 }

-- {ENTRY} 1712.1.77.3.2.2.1
lcsStatusIpv6Dhcpv6ClientAddressBindEntry OBJECT-TYPE
    SYNTAX     LcsStatusIpv6Dhcpv6ClientAddressBindEntry
    MAX-ACCESS not-accessible
    STATUS     current
    DESCRIPTION
        ""
    INDEX {
        lcsStatusIpv6Dhcpv6ClientAddressBindEntryInterfaceName,
        lcsStatusIpv6Dhcpv6ClientAddressBindEntryAddress
    }
    ::= { lcsStatusIpv6Dhcpv6ClientAddressBindTable 1 }

-- {SEQUENCE}
LcsStatusIpv6Dhcpv6ClientAddressBindEntry ::= SEQUENCE {
    lcsStatusIpv6Dhcpv6ClientAddressBindEntryInterfaceName DisplayString,
    lcsStatusIpv6Dhcpv6ClientAddressBindEntryAddress DisplayString,
    lcsStatusIpv6Dhcpv6ClientAddressBindEntryPreferredUntilNumerical Counter32,
    lcsStatusIpv6Dhcpv6ClientAddressBindEntryPreferredUntil DisplayString,
    lcsStatusIpv6Dhcpv6ClientAddressBindEntryValidUntilNumerical Counter32,
    lcsStatusIpv6Dhcpv6ClientAddressBindEntryValidUntil DisplayString
}

-- {COLUMN} 1712.1.77.3.2.2.1.1
lcsStatusIpv6Dhcpv6ClientAddressBindEntryInterfaceName OBJECT-TYPE
    SYNTAX     DisplayString (SIZE(0..255))
    MAX-ACCESS read-only
    STATUS     current
    DESCRIPTION
        "-- empty --"
    ::= { lcsStatusIpv6Dhcpv6ClientAddressBindEntry 1 }

-- {COLUMN} 1712.1.77.3.2.2.1.2
lcsStatusIpv6Dhcpv6ClientAddressBindEntryAddress OBJECT-TYPE
    SYNTAX     DisplayString (SIZE(0..255))
    MAX-ACCESS read-only
    STATUS     current
    DESCRIPTION
        "-- empty --"
    ::= { lcsStatusIpv6Dhcpv6ClientAddressBindEntry 2 }

-- {COLUMN} 1712.1.77.3.2.2.1.3
lcsStatusIpv6Dhcpv6ClientAddressBindEntryPreferredUntilNumerical OBJECT-TYPE
    SYNTAX     Counter32
    MAX-ACCESS read-only
    STATUS     current
    DESCRIPTION
        "-- empty --"
    ::= { lcsStatusIpv6Dhcpv6ClientAddressBindEntry 3 }

-- {COLUMN} 1712.1.77.3.2.2.1.4
lcsStatusIpv6Dhcpv6ClientAddressBindEntryPreferredUntil OBJECT-TYPE
    SYNTAX     DisplayString (SIZE(0..255))
    MAX-ACCESS read-only
    STATUS     current
    DESCRIPTION
        "-- empty --"
    ::= { lcsStatusIpv6Dhcpv6ClientAddressBindEntry 4 }

-- {COLUMN} 1712.1.77.3.2.2.1.5
lcsStatusIpv6Dhcpv6ClientAddressBindEntryValidUntilNumerical OBJECT-TYPE
    SYNTAX     Counter32
    MAX-ACCESS read-only
    STATUS     current
    DESCRIPTION
        "-- empty --"
    ::= { lcsStatusIpv6Dhcpv6ClientAddressBindEntry 5 }

-- {COLUMN} 1712.1.77.3.2.2.1.6
lcsStatusIpv6Dhcpv6ClientAddressBindEntryValidUntil OBJECT-TYPE
    SYNTAX     DisplayString (SIZE(0..255))
    MAX-ACCESS read-only
    STATUS     current
    DESCRIPTION
        "-- empty --"
    ::= { lcsStatusIpv6Dhcpv6ClientAddressBindEntry 6 }

-- {TABLE} 1712.1.77.3.2.3
lcsStatusIpv6Dhcpv6ClientPdBindingsTable OBJECT-TYPE
    SYNTAX     SEQUENCE OF LcsStatusIpv6Dhcpv6ClientPdBindingsEntry
    MAX-ACCESS not-accessible
    STATUS     current
    DESCRIPTION
        "-- empty --"
    ::= { lcsStatusIpv6Dhcpv6Client 3 }

-- {ENTRY} 1712.1.77.3.2.3.1
lcsStatusIpv6Dhcpv6ClientPdBindingsEntry OBJECT-TYPE
    SYNTAX     LcsStatusIpv6Dhcpv6ClientPdBindingsEntry
    MAX-ACCESS not-accessible
    STATUS     current
    DESCRIPTION
        ""
    INDEX {
        lcsStatusIpv6Dhcpv6ClientPdBindingsEntryInterfaceName,
        lcsStatusIpv6Dhcpv6ClientPdBindingsEntryPdPrefix
    }
    ::= { lcsStatusIpv6Dhcpv6ClientPdBindingsTable 1 }

-- {SEQUENCE}
LcsStatusIpv6Dhcpv6ClientPdBindingsEntry ::= SEQUENCE {
    lcsStatusIpv6Dhcpv6ClientPdBindingsEntryInterfaceName DisplayString,
    lcsStatusIpv6Dhcpv6ClientPdBindingsEntryPdPrefix DisplayString,
    lcsStatusIpv6Dhcpv6ClientPdBindingsEntryPreferredUntilNumerical Counter32,
    lcsStatusIpv6Dhcpv6ClientPdBindingsEntryPreferredUntil DisplayString,
    lcsStatusIpv6Dhcpv6ClientPdBindingsEntryValidUntilNumerical Counter32,
    lcsStatusIpv6Dhcpv6ClientPdBindingsEntryValidUntil DisplayString
}

-- {COLUMN} 1712.1.77.3.2.3.1.1
lcsStatusIpv6Dhcpv6ClientPdBindingsEntryInterfaceName OBJECT-TYPE
    SYNTAX     DisplayString (SIZE(0..255))
    MAX-ACCESS read-only
    STATUS     current
    DESCRIPTION
        "-- empty --"
    ::= { lcsStatusIpv6Dhcpv6ClientPdBindingsEntry 1 }

-- {COLUMN} 1712.1.77.3.2.3.1.2
lcsStatusIpv6Dhcpv6ClientPdBindingsEntryPdPrefix OBJECT-TYPE
    SYNTAX     DisplayString (SIZE(0..255))
    MAX-ACCESS read-only
    STATUS     current
    DESCRIPTION
        "-- empty --"
    ::= { lcsStatusIpv6Dhcpv6ClientPdBindingsEntry 2 }

-- {COLUMN} 1712.1.77.3.2.3.1.3
lcsStatusIpv6Dhcpv6ClientPdBindingsEntryPreferredUntilNumerical OBJECT-TYPE
    SYNTAX     Counter32
    MAX-ACCESS read-only
    STATUS     current
    DESCRIPTION
        "-- empty --"
    ::= { lcsStatusIpv6Dhcpv6ClientPdBindingsEntry 3 }

-- {COLUMN} 1712.1.77.3.2.3.1.4
lcsStatusIpv6Dhcpv6ClientPdBindingsEntryPreferredUntil OBJECT-TYPE
    SYNTAX     DisplayString (SIZE(0..255))
    MAX-ACCESS read-only
    STATUS     current
    DESCRIPTION
        "-- empty --"
    ::= { lcsStatusIpv6Dhcpv6ClientPdBindingsEntry 4 }

-- {COLUMN} 1712.1.77.3.2.3.1.5
lcsStatusIpv6Dhcpv6ClientPdBindingsEntryValidUntilNumerical OBJECT-TYPE
    SYNTAX     Counter32
    MAX-ACCESS read-only
    STATUS     current
    DESCRIPTION
        "-- empty --"
    ::= { lcsStatusIpv6Dhcpv6ClientPdBindingsEntry 5 }

-- {COLUMN} 1712.1.77.3.2.3.1.6
lcsStatusIpv6Dhcpv6ClientPdBindingsEntryValidUntil OBJECT-TYPE
    SYNTAX     DisplayString (SIZE(0..255))
    MAX-ACCESS read-only
    STATUS     current
    DESCRIPTION
        "-- empty --"
    ::= { lcsStatusIpv6Dhcpv6ClientPdBindingsEntry 6 }

-- {TABLE} 1712.1.77.3.2.4
lcsStatusIpv6Dhcpv6ClientInterfaceStateTable OBJECT-TYPE
    SYNTAX     SEQUENCE OF LcsStatusIpv6Dhcpv6ClientInterfaceStateEntry
    MAX-ACCESS not-accessible
    STATUS     current
    DESCRIPTION
        "-- empty --"
    ::= { lcsStatusIpv6Dhcpv6Client 4 }

-- {ENTRY} 1712.1.77.3.2.4.1
lcsStatusIpv6Dhcpv6ClientInterfaceStateEntry OBJECT-TYPE
    SYNTAX     LcsStatusIpv6Dhcpv6ClientInterfaceStateEntry
    MAX-ACCESS not-accessible
    STATUS     current
    DESCRIPTION
        ""
    INDEX {
        lcsStatusIpv6Dhcpv6ClientInterfaceStateEntryInterfaceName
    }
    ::= { lcsStatusIpv6Dhcpv6ClientInterfaceStateTable 1 }

-- {SEQUENCE}
LcsStatusIpv6Dhcpv6ClientInterfaceStateEntry ::= SEQUENCE {
    lcsStatusIpv6Dhcpv6ClientInterfaceStateEntryInterfaceName DisplayString,
    lcsStatusIpv6Dhcpv6ClientInterfaceStateEntryMode INTEGER,
    lcsStatusIpv6Dhcpv6ClientInterfaceStateEntryRequestPd INTEGER,
    lcsStatusIpv6Dhcpv6ClientInterfaceStateEntryReconfNegotiated INTEGER
}

-- {COLUMN} 1712.1.77.3.2.4.1.1
lcsStatusIpv6Dhcpv6ClientInterfaceStateEntryInterfaceName OBJECT-TYPE
    SYNTAX     DisplayString (SIZE(0..255))
    MAX-ACCESS read-only
    STATUS     current
    DESCRIPTION
        "-- empty --"
    ::= { lcsStatusIpv6Dhcpv6ClientInterfaceStateEntry 1 }

-- {COLUMN} 1712.1.77.3.2.4.1.2
lcsStatusIpv6Dhcpv6ClientInterfaceStateEntryMode OBJECT-TYPE
    SYNTAX     INTEGER
      {
        eStateless (0),
        eStateful (1),
        eStatic (2)
      }
    MAX-ACCESS read-only
    STATUS     current
    DESCRIPTION
        "-- empty --"
    ::= { lcsStatusIpv6Dhcpv6ClientInterfaceStateEntry 2 }

-- {COLUMN} 1712.1.77.3.2.4.1.3
lcsStatusIpv6Dhcpv6ClientInterfaceStateEntryRequestPd OBJECT-TYPE
    SYNTAX     INTEGER
      {
        eNo (0),
        eYes (1)
      }
    MAX-ACCESS read-only
    STATUS     current
    DESCRIPTION
        "-- empty --"
    ::= { lcsStatusIpv6Dhcpv6ClientInterfaceStateEntry 3 }

-- {COLUMN} 1712.1.77.3.2.4.1.4
lcsStatusIpv6Dhcpv6ClientInterfaceStateEntryReconfNegotiated OBJECT-TYPE
    SYNTAX     INTEGER
      {
        eNo (0),
        eYes (1)
      }
    MAX-ACCESS read-only
    STATUS     current
    DESCRIPTION
        "-- empty --"
    ::= { lcsStatusIpv6Dhcpv6ClientInterfaceStateEntry 4 }

-- {SCALAR} 1712.1.77.3.2.5
lcsStatusIpv6Dhcpv6ClientRelease OBJECT-TYPE
    SYNTAX     DisplayString
    MAX-ACCESS read-write
    STATUS     current
    DESCRIPTION
        "-- empty --"
    ::= { lcsStatusIpv6Dhcpv6Client 5 }

-- {SCALAR} 1712.1.77.3.2.6
lcsStatusIpv6Dhcpv6ClientClientId OBJECT-TYPE
    SYNTAX     DisplayString (SIZE(0..97))
    MAX-ACCESS read-only
    STATUS     current
    DESCRIPTION
        "-- empty --"
    ::= { lcsStatusIpv6Dhcpv6Client 6 }

-- {OID} 1712.1.77.3.3
lcsStatusIpv6Dhcpv6RelayAgent OBJECT IDENTIFIER ::= { lcsStatusIpv6Dhcpv6 3 }

-- {OID} 1712.1.77.9
lcsStatusIpv6Firewall OBJECT IDENTIFIER ::= { lcsStatusIpv6 9 }

-- {TABLE} 1712.1.77.9.1
lcsStatusIpv6FirewallLogTableTable OBJECT-TYPE
    SYNTAX     SEQUENCE OF LcsStatusIpv6FirewallLogTableEntry
    MAX-ACCESS not-accessible
    STATUS     current
    DESCRIPTION
        "-- empty --"
    ::= { lcsStatusIpv6Firewall 1 }

-- {ENTRY} 1712.1.77.9.1.1
lcsStatusIpv6FirewallLogTableEntry OBJECT-TYPE
    SYNTAX     LcsStatusIpv6FirewallLogTableEntry
    MAX-ACCESS not-accessible
    STATUS     current
    DESCRIPTION
        ""
    INDEX {
        lcsStatusIpv6FirewallLogTableEntryIdx
    }
    ::= { lcsStatusIpv6FirewallLogTableTable 1 }

-- {SEQUENCE}
LcsStatusIpv6FirewallLogTableEntry ::= SEQUENCE {
    lcsStatusIpv6FirewallLogTableEntryIdx INTEGER,
    lcsStatusIpv6FirewallLogTableEntrySystemTime DisplayString,
    lcsStatusIpv6FirewallLogTableEntrySrcAddress DisplayString,
    lcsStatusIpv6FirewallLogTableEntryDstAddress DisplayString,
    lcsStatusIpv6FirewallLogTableEntryProt INTEGER,
    lcsStatusIpv6FirewallLogTableEntrySrcPort INTEGER,
    lcsStatusIpv6FirewallLogTableEntryDstPort INTEGER,
    lcsStatusIpv6FirewallLogTableEntryFilterRule DisplayString,
    lcsStatusIpv6FirewallLogTableEntryLimit INTEGER,
    lcsStatusIpv6FirewallLogTableEntryThreshold INTEGER,
    lcsStatusIpv6FirewallLogTableEntryAction INTEGER
}

-- {COLUMN} 1712.1.77.9.1.1.1
lcsStatusIpv6FirewallLogTableEntryIdx OBJECT-TYPE
    SYNTAX     INTEGER (0..65535)
    MAX-ACCESS read-only
    STATUS     current
    DESCRIPTION
        "-- empty --"
    ::= { lcsStatusIpv6FirewallLogTableEntry 1 }

-- {COLUMN} 1712.1.77.9.1.1.2
lcsStatusIpv6FirewallLogTableEntrySystemTime OBJECT-TYPE
    SYNTAX     DisplayString (SIZE(0..19))
    MAX-ACCESS read-only
    STATUS     current
    DESCRIPTION
        "-- empty --"
    ::= { lcsStatusIpv6FirewallLogTableEntry 2 }

-- {COLUMN} 1712.1.77.9.1.1.3
lcsStatusIpv6FirewallLogTableEntrySrcAddress OBJECT-TYPE
    SYNTAX     DisplayString (SIZE(0..255))
    MAX-ACCESS read-only
    STATUS     current
    DESCRIPTION
        "-- empty --"
    ::= { lcsStatusIpv6FirewallLogTableEntry 3 }

-- {COLUMN} 1712.1.77.9.1.1.4
lcsStatusIpv6FirewallLogTableEntryDstAddress OBJECT-TYPE
    SYNTAX     DisplayString (SIZE(0..255))
    MAX-ACCESS read-only
    STATUS     current
    DESCRIPTION
        "-- empty --"
    ::= { lcsStatusIpv6FirewallLogTableEntry 4 }

-- {COLUMN} 1712.1.77.9.1.1.5
lcsStatusIpv6FirewallLogTableEntryProt OBJECT-TYPE
    SYNTAX     INTEGER (0..255)
    MAX-ACCESS read-only
    STATUS     current
    DESCRIPTION
        "-- empty --"
    ::= { lcsStatusIpv6FirewallLogTableEntry 5 }

-- {COLUMN} 1712.1.77.9.1.1.6
lcsStatusIpv6FirewallLogTableEntrySrcPort OBJECT-TYPE
    SYNTAX     INTEGER (0..65535)
    MAX-ACCESS read-only
    STATUS     current
    DESCRIPTION
        "-- empty --"
    ::= { lcsStatusIpv6FirewallLogTableEntry 6 }

-- {COLUMN} 1712.1.77.9.1.1.7
lcsStatusIpv6FirewallLogTableEntryDstPort OBJECT-TYPE
    SYNTAX     INTEGER (0..65535)
    MAX-ACCESS read-only
    STATUS     current
    DESCRIPTION
        "-- empty --"
    ::= { lcsStatusIpv6FirewallLogTableEntry 7 }

-- {COLUMN} 1712.1.77.9.1.1.8
lcsStatusIpv6FirewallLogTableEntryFilterRule OBJECT-TYPE
    SYNTAX     DisplayString (SIZE(0..69))
    MAX-ACCESS read-only
    STATUS     current
    DESCRIPTION
        "-- empty --"
    ::= { lcsStatusIpv6FirewallLogTableEntry 8 }

-- {COLUMN} 1712.1.77.9.1.1.9
lcsStatusIpv6FirewallLogTableEntryLimit OBJECT-TYPE
    SYNTAX     INTEGER (0..2147483647)
    MAX-ACCESS read-only
    STATUS     current
    DESCRIPTION
        "-- empty --"
    ::= { lcsStatusIpv6FirewallLogTableEntry 9 }

-- {COLUMN} 1712.1.77.9.1.1.10
lcsStatusIpv6FirewallLogTableEntryThreshold OBJECT-TYPE
    SYNTAX     INTEGER (0..2147483647)
    MAX-ACCESS read-only
    STATUS     current
    DESCRIPTION
        "-- empty --"
    ::= { lcsStatusIpv6FirewallLogTableEntry 10 }

-- {COLUMN} 1712.1.77.9.1.1.11
lcsStatusIpv6FirewallLogTableEntryAction OBJECT-TYPE
    SYNTAX     INTEGER (0..2147483647)
    MAX-ACCESS read-only
    STATUS     current
    DESCRIPTION
        "-- empty --"
    ::= { lcsStatusIpv6FirewallLogTableEntry 11 }

-- {SCALAR} 1712.1.77.9.2
lcsStatusIpv6FirewallForwardingFilter OBJECT-TYPE
    SYNTAX     INTEGER (0..2147483647)
    MAX-ACCESS read-only
    STATUS     current
    DESCRIPTION
        "-- empty --"
    ::= { lcsStatusIpv6Firewall 2 }

-- {SCALAR} 1712.1.77.9.3
lcsStatusIpv6FirewallInboundFilter OBJECT-TYPE
    SYNTAX     INTEGER (0..2147483647)
    MAX-ACCESS read-only
    STATUS     current
    DESCRIPTION
        "-- empty --"
    ::= { lcsStatusIpv6Firewall 3 }

-- {SCALAR} 1712.1.77.9.4
lcsStatusIpv6FirewallForwardingSessions OBJECT-TYPE
    SYNTAX     INTEGER (0..2147483647)
    MAX-ACCESS read-only
    STATUS     current
    DESCRIPTION
        "-- empty --"
    ::= { lcsStatusIpv6Firewall 4 }

-- {SCALAR} 1712.1.77.9.5
lcsStatusIpv6FirewallInboundSessions OBJECT-TYPE
    SYNTAX     INTEGER (0..2147483647)
    MAX-ACCESS read-only
    STATUS     current
    DESCRIPTION
        "-- empty --"
    ::= { lcsStatusIpv6Firewall 5 }

-- {SCALAR} 1712.1.77.9.6
lcsStatusIpv6FirewallForwardingOpenPorts OBJECT-TYPE
    SYNTAX     INTEGER (0..2147483647)
    MAX-ACCESS read-only
    STATUS     current
    DESCRIPTION
        "-- empty --"
    ::= { lcsStatusIpv6Firewall 6 }

-- {SCALAR} 1712.1.77.9.7
lcsStatusIpv6FirewallHostBlockList OBJECT-TYPE
    SYNTAX     INTEGER (0..2147483647)
    MAX-ACCESS read-only
    STATUS     current
    DESCRIPTION
        "-- empty --"
    ::= { lcsStatusIpv6Firewall 7 }

-- {SCALAR} 1712.1.77.9.8
lcsStatusIpv6FirewallPortBlockList OBJECT-TYPE
    SYNTAX     INTEGER (0..2147483647)
    MAX-ACCESS read-only
    STATUS     current
    DESCRIPTION
        "-- empty --"
    ::= { lcsStatusIpv6Firewall 8 }

-- {SCALAR} 1712.1.77.9.9
lcsStatusIpv6FirewallHalfOpenConnections OBJECT-TYPE
    SYNTAX     INTEGER (0..2147483647)
    MAX-ACCESS read-only
    STATUS     current
    DESCRIPTION
        "-- empty --"
    ::= { lcsStatusIpv6Firewall 9 }

-- {OID} 1712.1.81
lcsStatusDsLite OBJECT IDENTIFIER ::= { lcsStatus 81 }

-- {SCALAR} 1712.1.81.1
lcsStatusDsLiteRxPackets OBJECT-TYPE
    SYNTAX     INTEGER (0..2147483647)
    MAX-ACCESS read-only
    STATUS     current
    DESCRIPTION
        "-- empty --"
    ::= { lcsStatusDsLite 1 }

-- {SCALAR} 1712.1.81.2
lcsStatusDsLiteTxPackets OBJECT-TYPE
    SYNTAX     INTEGER (0..2147483647)
    MAX-ACCESS read-only
    STATUS     current
    DESCRIPTION
        "-- empty --"
    ::= { lcsStatusDsLite 2 }

-- {SCALAR} 1712.1.81.3
lcsStatusDsLiteQueueErrors OBJECT-TYPE
    SYNTAX     INTEGER (0..2147483647)
    MAX-ACCESS read-only
    STATUS     current
    DESCRIPTION
        "-- empty --"
    ::= { lcsStatusDsLite 3 }

-- {TABLE} 1712.1.81.4
lcsStatusDsLiteConnectionsTable OBJECT-TYPE
    SYNTAX     SEQUENCE OF LcsStatusDsLiteConnectionsEntry
    MAX-ACCESS not-accessible
    STATUS     current
    DESCRIPTION
        "-- empty --"
    ::= { lcsStatusDsLite 4 }

-- {ENTRY} 1712.1.81.4.1
lcsStatusDsLiteConnectionsEntry OBJECT-TYPE
    SYNTAX     LcsStatusDsLiteConnectionsEntry
    MAX-ACCESS not-accessible
    STATUS     current
    DESCRIPTION
        ""
    INDEX {
        lcsStatusDsLiteConnectionsEntryPeer
    }
    ::= { lcsStatusDsLiteConnectionsTable 1 }

-- {SEQUENCE}
LcsStatusDsLiteConnectionsEntry ::= SEQUENCE {
    lcsStatusDsLiteConnectionsEntryPeer DisplayString,
    lcsStatusDsLiteConnectionsEntryState INTEGER,
    lcsStatusDsLiteConnectionsEntryLastError INTEGER,
    lcsStatusDsLiteConnectionsEntryIpv4Address IpAddress,
    lcsStatusDsLiteConnectionsEntryPhysConn DisplayString,
    lcsStatusDsLiteConnectionsEntryAftrName DisplayString,
    lcsStatusDsLiteConnectionsEntryAftrIpv6Address DisplayString,
    lcsStatusDsLiteConnectionsEntryConnTime Gauge32
}

-- {COLUMN} 1712.1.81.4.1.1
lcsStatusDsLiteConnectionsEntryPeer OBJECT-TYPE
    SYNTAX     DisplayString (SIZE(0..16))
    MAX-ACCESS read-only
    STATUS     current
    DESCRIPTION
        "-- empty --"
    ::= { lcsStatusDsLiteConnectionsEntry 1 }

-- {COLUMN} 1712.1.81.4.1.2
lcsStatusDsLiteConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusDsLiteConnectionsEntry 2 }

-- {COLUMN} 1712.1.81.4.1.3
lcsStatusDsLiteConnectionsEntryLastError OBJECT-TYPE
    SYNTAX     INTEGER
      {
        eNone (0),
        eDnsResolutionFailed (20481),
        eNoRouteToGateway (20482),
        eNoGatewayByDhcp (20483),
        eInvalidGatewayAddress (20484),
        eMultipleGatewayUsage (20485),
        eIcmpConnError (275)
      }
    MAX-ACCESS read-write
    STATUS     current
    DESCRIPTION
        "-- empty --"
    ::= { lcsStatusDsLiteConnectionsEntry 3 }

-- {COLUMN} 1712.1.81.4.1.4
lcsStatusDsLiteConnectionsEntryIpv4Address OBJECT-TYPE
    SYNTAX     IpAddress
    MAX-ACCESS read-only
    STATUS     current
    DESCRIPTION
        "-- empty --"
    ::= { lcsStatusDsLiteConnectionsEntry 4 }

-- {COLUMN} 1712.1.81.4.1.5
lcsStatusDsLiteConnectionsEntryPhysConn OBJECT-TYPE
    SYNTAX     DisplayString (SIZE(0..16))
    MAX-ACCESS read-only
    STATUS     current
    DESCRIPTION
        "-- empty --"
    ::= { lcsStatusDsLiteConnectionsEntry 5 }

-- {COLUMN} 1712.1.81.4.1.6
lcsStatusDsLiteConnectionsEntryAftrName OBJECT-TYPE
    SYNTAX     DisplayString (SIZE(0..64))
    MAX-ACCESS read-only
    STATUS     current
    DESCRIPTION
        "-- empty --"
    ::= { lcsStatusDsLiteConnectionsEntry 6 }

-- {COLUMN} 1712.1.81.4.1.7
lcsStatusDsLiteConnectionsEntryAftrIpv6Address OBJECT-TYPE
    SYNTAX     DisplayString (SIZE(0..255))
    MAX-ACCESS read-only
    STATUS     current
    DESCRIPTION
        "-- empty --"
    ::= { lcsStatusDsLiteConnectionsEntry 7 }

-- {COLUMN} 1712.1.81.4.1.8
lcsStatusDsLiteConnectionsEntryConnTime OBJECT-TYPE
    SYNTAX     Gauge32
    MAX-ACCESS read-only
    STATUS     current
    DESCRIPTION
        "-- empty --"
    ::= { lcsStatusDsLiteConnectionsEntry 8 }

-- {SCALAR} 1712.1.81.5
lcsStatusDsLiteTunnel OBJECT-TYPE
    SYNTAX     INTEGER (0..2147483647)
    MAX-ACCESS read-only
    STATUS     current
    DESCRIPTION
        "-- empty --"
    ::= { lcsStatusDsLite 5 }

-- {SCALAR} 1712.1.81.6
lcsStatusDsLiteDeleteValues OBJECT-TYPE
    SYNTAX     DisplayString
    MAX-ACCESS read-write
    STATUS     current
    DESCRIPTION
        "-- empty --"
    ::= { lcsStatusDsLite 6 }

-- {OID} 1712.1.84
lcsStatusL2tp OBJECT IDENTIFIER ::= { lcsStatus 84 }

-- {SCALAR} 1712.1.84.1
lcsStatusL2tpRxPackets OBJECT-TYPE
    SYNTAX     INTEGER (0..2147483647)
    MAX-ACCESS read-only
    STATUS     current
    DESCRIPTION
        "-- empty --"
    ::= { lcsStatusL2tp 1 }

-- {SCALAR} 1712.1.84.2
lcsStatusL2tpTxPackets OBJECT-TYPE
    SYNTAX     INTEGER (0..2147483647)
    MAX-ACCESS read-only
    STATUS     current
    DESCRIPTION
        "-- empty --"
    ::= { lcsStatusL2tp 2 }

-- {SCALAR} 1712.1.84.3
lcsStatusL2tpTxRetries OBJECT-TYPE
    SYNTAX     INTEGER (0..2147483647)
    MAX-ACCESS read-only
    STATUS     current
    DESCRIPTION
        "-- empty --"
    ::= { lcsStatusL2tp 3 }

-- {SCALAR} 1712.1.84.4
lcsStatusL2tpCallErrors OBJECT-TYPE
    SYNTAX     INTEGER (0..2147483647)
    MAX-ACCESS read-only
    STATUS     current
    DESCRIPTION
        "-- empty --"
    ::= { lcsStatusL2tp 4 }

-- {TABLE} 1712.1.84.5
lcsStatusL2tpEndpointsTable OBJECT-TYPE
    SYNTAX     SEQUENCE OF LcsStatusL2tpEndpointsEntry
    MAX-ACCESS not-accessible
    STATUS     current
    DESCRIPTION
        "-- empty --"
    ::= { lcsStatusL2tp 5 }

-- {ENTRY} 1712.1.84.5.1
lcsStatusL2tpEndpointsEntry OBJECT-TYPE
    SYNTAX     LcsStatusL2tpEndpointsEntry
    MAX-ACCESS not-accessible
    STATUS     current
    DESCRIPTION
        ""
    INDEX {
        lcsStatusL2tpEndpointsEntryL2tpEndpoint
    }
    ::= { lcsStatusL2tpEndpointsTable 1 }

-- {SEQUENCE}
LcsStatusL2tpEndpointsEntry ::= SEQUENCE {
    lcsStatusL2tpEndpointsEntryL2tpEndpoint DisplayString,
    lcsStatusL2tpEndpointsEntryState INTEGER,
    lcsStatusL2tpEndpointsEntryLastError INTEGER,
    lcsStatusL2tpEndpointsEntryMode INTEGER,
    lcsStatusL2tpEndpointsEntryPhysConnection DisplayString,
    lcsStatusL2tpEndpointsEntryGateway DisplayString,
    lcsStatusL2tpEndpointsEntrySessions INTEGER,
    lcsStatusL2tpEndpointsEntryConnTime Gauge32,
    lcsStatusL2tpEndpointsEntryEmbeddedErrorMessage DisplayString
}

-- {COLUMN} 1712.1.84.5.1.1
lcsStatusL2tpEndpointsEntryL2tpEndpoint OBJECT-TYPE
    SYNTAX     DisplayString (SIZE(0..16))
    MAX-ACCESS read-only
    STATUS     current
    DESCRIPTION
        "-- empty --"
    ::= { lcsStatusL2tpEndpointsEntry 1 }

-- {COLUMN} 1712.1.84.5.1.2
lcsStatusL2tpEndpointsEntryState OBJECT-TYPE
    SYNTAX     INTEGER
      {
        eInvalid (-1),
        eDestroying (0),
        eIdle (1),
        eWaitCtlReply (2),
        eWaitCtlConn (3),
        eWaitEstablish (4),
        eEstablished (5),
        eAuthenticating (6)
      }
    MAX-ACCESS read-only
    STATUS     current
    DESCRIPTION
        "-- empty --"
    ::= { lcsStatusL2tpEndpointsEntry 2 }

-- {COLUMN} 1712.1.84.5.1.3
lcsStatusL2tpEndpointsEntryLastError OBJECT-TYPE
    SYNTAX     INTEGER
      {
        eNone (0),
        eUnknown (255),
        eDnsResolutionFailed (1),
        eNoRouteToGateway (2),
        eNoResponse (4),
        eMessageTimeout (5),
        eTunnelAlreadyExists (19),
        eAuthorizationFailed (20),
        eBadProtocolVersion (21),
        eShuttingDown (22),
        eStateMachineError (23),
        eNoTunnelExists (33),
        eInvalidLength (34),
        eInvalidValue (35),
        eNoRessources (36),
        eInvalidSessionId (37),
        eVendorSpecificError (38),
        eTryAnother (39),
        eUnknownMandatoryAttribute (40)
      }
    MAX-ACCESS read-write
    STATUS     current
    DESCRIPTION
        "-- empty --"
    ::= { lcsStatusL2tpEndpointsEntry 3 }

-- {COLUMN} 1712.1.84.5.1.4
lcsStatusL2tpEndpointsEntryMode OBJECT-TYPE
    SYNTAX     INTEGER
      {
        eLac (0),
        eLns (1)
      }
    MAX-ACCESS read-only
    STATUS     current
    DESCRIPTION
        "-- empty --"
    ::= { lcsStatusL2tpEndpointsEntry 4 }

-- {COLUMN} 1712.1.84.5.1.5
lcsStatusL2tpEndpointsEntryPhysConnection OBJECT-TYPE
    SYNTAX     DisplayString (SIZE(0..16))
    MAX-ACCESS read-only
    STATUS     current
    DESCRIPTION
        "-- empty --"
    ::= { lcsStatusL2tpEndpointsEntry 5 }

-- {COLUMN} 1712.1.84.5.1.6
lcsStatusL2tpEndpointsEntryGateway OBJECT-TYPE
    SYNTAX     DisplayString (SIZE(0..39))
    MAX-ACCESS read-only
    STATUS     current
    DESCRIPTION
        "-- empty --"
    ::= { lcsStatusL2tpEndpointsEntry 6 }

-- {COLUMN} 1712.1.84.5.1.7
lcsStatusL2tpEndpointsEntrySessions OBJECT-TYPE
    SYNTAX     INTEGER (0..65535)
    MAX-ACCESS read-only
    STATUS     current
    DESCRIPTION
        "-- empty --"
    ::= { lcsStatusL2tpEndpointsEntry 7 }

-- {COLUMN} 1712.1.84.5.1.8
lcsStatusL2tpEndpointsEntryConnTime OBJECT-TYPE
    SYNTAX     Gauge32
    MAX-ACCESS read-only
    STATUS     current
    DESCRIPTION
        "-- empty --"
    ::= { lcsStatusL2tpEndpointsEntry 8 }

-- {COLUMN} 1712.1.84.5.1.9
lcsStatusL2tpEndpointsEntryEmbeddedErrorMessage OBJECT-TYPE
    SYNTAX     DisplayString (SIZE(0..32))
    MAX-ACCESS read-only
    STATUS     current
    DESCRIPTION
        "-- empty --"
    ::= { lcsStatusL2tpEndpointsEntry 9 }

-- {SCALAR} 1712.1.84.6
lcsStatusL2tpNumEndpoints OBJECT-TYPE
    SYNTAX     INTEGER (0..2147483647)
    MAX-ACCESS read-only
    STATUS     current
    DESCRIPTION
        "-- empty --"
    ::= { lcsStatusL2tp 6 }

-- {TABLE} 1712.1.84.7
lcsStatusL2tpConnectionsTable OBJECT-TYPE
    SYNTAX     SEQUENCE OF LcsStatusL2tpConnectionsEntry
    MAX-ACCESS not-accessible
    STATUS     current
    DESCRIPTION
        "-- empty --"
    ::= { lcsStatusL2tp 7 }

-- {ENTRY} 1712.1.84.7.1
lcsStatusL2tpConnectionsEntry OBJECT-TYPE
    SYNTAX     LcsStatusL2tpConnectionsEntry
    MAX-ACCESS not-accessible
    STATUS     current
    DESCRIPTION
        ""
    INDEX {
        lcsStatusL2tpConnectionsEntryPeer
    }
    ::= { lcsStatusL2tpConnectionsTable 1 }

-- {SEQUENCE}
LcsStatusL2tpConnectionsEntry ::= SEQUENCE {
    lcsStatusL2tpConnectionsEntryPeer DisplayString,
    lcsStatusL2tpConnectionsEntryState INTEGER,
    lcsStatusL2tpConnectionsEntryLastError INTEGER,
    lcsStatusL2tpConnectionsEntryMode INTEGER,
    lcsStatusL2tpConnectionsEntryShTime INTEGER,
    lcsStatusL2tpConnectionsEntryL2tpEndpoint DisplayString,
    lcsStatusL2tpConnectionsEntryPeerAddress IpAddress,
    lcsStatusL2tpConnectionsEntryIpAddress IpAddress,
    lcsStatusL2tpConnectionsEntryDnsDefault IpAddress,
    lcsStatusL2tpConnectionsEntryDnsBackup IpAddress,
    lcsStatusL2tpConnectionsEntryNbnsDefault IpAddress,
    lcsStatusL2tpConnectionsEntryNbnsBackup IpAddress,
    lcsStatusL2tpConnectionsEntryConnTime Gauge32
}

-- {COLUMN} 1712.1.84.7.1.1
lcsStatusL2tpConnectionsEntryPeer OBJECT-TYPE
    SYNTAX     DisplayString (SIZE(0..16))
    MAX-ACCESS read-only
    STATUS     current
    DESCRIPTION
        "-- empty --"
    ::= { lcsStatusL2tpConnectionsEntry 1 }

-- {COLUMN} 1712.1.84.7.1.2
lcsStatusL2tpConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusL2tpConnectionsEntry 2 }

-- {COLUMN} 1712.1.84.7.1.3
lcsStatusL2tpConnectionsEntryLastError OBJECT-TYPE
    SYNTAX     INTEGER
      {
        eNone (0),
        eRemoteDisconnected (17153),
        eManualDisconnect (17154),
        eShortholdExpired (17155),
        ePhysicalDisconnected (17156),
        eInvalidPhysicalChannel (17157),
        eDynamicVpnReconnect (17158),
        eConfigurationChanged (17159),
        eRemovedFromConfig (17160),
        eRemoteDoubled (267),
        eIcmpConnError (275),
        eChargeLocked (283),
        eLcpRejected (32768),
        eAuthError (32769),
        eAuthRejected (32770),
        eLcpConnError (32771),
        ePapRejected (32784),
        ePapRxTimeout (32785),
        ePapTxTimeout (32786),
        eWrongPapReq (32787),
        ePapNakReceived (32788),
        eUnknPapPeer (32789),
        eChapRejected (32800),
        eChapRxTimeout (32801),
        eChapTxTimeout (32802),
        eWrongChapResp (32803),
        eChapFailRecvd (32804),
        eUnknChapPeer (32805),
        eIpcpRejected (32832),
        eCcpRejected (32848),
        eNoNcpAvailable (33008)
      }
    MAX-ACCESS read-write
    STATUS     current
    DESCRIPTION
        "-- empty --"
    ::= { lcsStatusL2tpConnectionsEntry 3 }

-- {COLUMN} 1712.1.84.7.1.4
lcsStatusL2tpConnectionsEntryMode OBJECT-TYPE
    SYNTAX     INTEGER
      {
        eActive (128),
        ePassive (0)
      }
    MAX-ACCESS read-only
    STATUS     current
    DESCRIPTION
        "-- empty --"
    ::= { lcsStatusL2tpConnectionsEntry 4 }

-- {COLUMN} 1712.1.84.7.1.5
lcsStatusL2tpConnectionsEntryShTime OBJECT-TYPE
    SYNTAX     INTEGER (0..65535)
    MAX-ACCESS read-only
    STATUS     current
    DESCRIPTION
        "-- empty --"
    ::= { lcsStatusL2tpConnectionsEntry 5 }

-- {COLUMN} 1712.1.84.7.1.6
lcsStatusL2tpConnectionsEntryL2tpEndpoint OBJECT-TYPE
    SYNTAX     DisplayString (SIZE(0..16))
    MAX-ACCESS read-only
    STATUS     current
    DESCRIPTION
        "-- empty --"
    ::= { lcsStatusL2tpConnectionsEntry 6 }

-- {COLUMN} 1712.1.84.7.1.7
lcsStatusL2tpConnectionsEntryPeerAddress OBJECT-TYPE
    SYNTAX     IpAddress
    MAX-ACCESS read-only
    STATUS     current
    DESCRIPTION
        "-- empty --"
    ::= { lcsStatusL2tpConnectionsEntry 7 }

-- {COLUMN} 1712.1.84.7.1.8
lcsStatusL2tpConnectionsEntryIpAddress OBJECT-TYPE
    SYNTAX     IpAddress
    MAX-ACCESS read-only
    STATUS     current
    DESCRIPTION
        "-- empty --"
    ::= { lcsStatusL2tpConnectionsEntry 8 }

-- {COLUMN} 1712.1.84.7.1.9
lcsStatusL2tpConnectionsEntryDnsDefault OBJECT-TYPE
    SYNTAX     IpAddress
    MAX-ACCESS read-only
    STATUS     current
    DESCRIPTION
        "-- empty --"
    ::= { lcsStatusL2tpConnectionsEntry 9 }

-- {COLUMN} 1712.1.84.7.1.10
lcsStatusL2tpConnectionsEntryDnsBackup OBJECT-TYPE
    SYNTAX     IpAddress
    MAX-ACCESS read-only
    STATUS     current
    DESCRIPTION
        "-- empty --"
    ::= { lcsStatusL2tpConnectionsEntry 10 }

-- {COLUMN} 1712.1.84.7.1.11
lcsStatusL2tpConnectionsEntryNbnsDefault OBJECT-TYPE
    SYNTAX     IpAddress
    MAX-ACCESS read-only
    STATUS     current
    DESCRIPTION
        "-- empty --"
    ::= { lcsStatusL2tpConnectionsEntry 11 }

-- {COLUMN} 1712.1.84.7.1.12
lcsStatusL2tpConnectionsEntryNbnsBackup OBJECT-TYPE
    SYNTAX     IpAddress
    MAX-ACCESS read-only
    STATUS     current
    DESCRIPTION
        "-- empty --"
    ::= { lcsStatusL2tpConnectionsEntry 12 }

-- {COLUMN} 1712.1.84.7.1.13
lcsStatusL2tpConnectionsEntryConnTime OBJECT-TYPE
    SYNTAX     Gauge32
    MAX-ACCESS read-only
    STATUS     current
    DESCRIPTION
        "-- empty --"
    ::= { lcsStatusL2tpConnectionsEntry 13 }

-- {SCALAR} 1712.1.84.8
lcsStatusL2tpNumConnections OBJECT-TYPE
    SYNTAX     INTEGER (0..2147483647)
    MAX-ACCESS read-only
    STATUS     current
    DESCRIPTION
        "-- empty --"
    ::= { lcsStatusL2tp 8 }

-- {SCALAR} 1712.1.84.9
lcsStatusL2tpDeleteValues OBJECT-TYPE
    SYNTAX     DisplayString
    MAX-ACCESS read-write
    STATUS     current
    DESCRIPTION
        "-- empty --"
    ::= { lcsStatusL2tp 9 }

-- {OID} 1712.1.12
lcsStatusQueue OBJECT IDENTIFIER ::= { lcsStatus 12 }

-- {SCALAR} 1712.1.12.1
lcsStatusQueueLanHeapPackets OBJECT-TYPE
    SYNTAX     INTEGER (0..2147483647)
    MAX-ACCESS read-only
    STATUS     current
    DESCRIPTION
        "-- empty --"
    ::= { lcsStatusQueue 1 }

-- {SCALAR} 1712.1.12.2
lcsStatusQueueQueuePackets OBJECT-TYPE
    SYNTAX     INTEGER (0..2147483647)
    MAX-ACCESS read-only
    STATUS     current
    DESCRIPTION
        "LAN Queue Packets"
    ::= { lcsStatusQueue 2 }

-- {SCALAR} 1712.1.12.3
lcsStatusQueueWanHeapPackets OBJECT-TYPE
    SYNTAX     INTEGER (0..2147483647)
    MAX-ACCESS read-only
    STATUS     current
    DESCRIPTION
        "-- empty --"
    ::= { lcsStatusQueue 3 }

-- {SCALAR} 1712.1.12.4
lcsStatusQueueWanQueuePackets OBJECT-TYPE
    SYNTAX     INTEGER (0..2147483647)
    MAX-ACCESS read-only
    STATUS     current
    DESCRIPTION
        "-- empty --"
    ::= { lcsStatusQueue 4 }

-- {SCALAR} 1712.1.12.7
lcsStatusQueueArpQueryQueuePackets OBJECT-TYPE
    SYNTAX     INTEGER (0..2147483647)
    MAX-ACCESS read-only
    STATUS     current
    DESCRIPTION
        "-- empty --"
    ::= { lcsStatusQueue 7 }

-- {SCALAR} 1712.1.12.8
lcsStatusQueueArpQueuePackets OBJECT-TYPE
    SYNTAX     INTEGER (0..2147483647)
    MAX-ACCESS read-only
    STATUS     current
    DESCRIPTION
        "-- empty --"
    ::= { lcsStatusQueue 8 }

-- {SCALAR} 1712.1.12.9
lcsStatusQueueIpQueuePackets OBJECT-TYPE
    SYNTAX     INTEGER (0..2147483647)
    MAX-ACCESS read-only
    STATUS     current
    DESCRIPTION
        "-- empty --"
    ::= { lcsStatusQueue 9 }

-- {SCALAR} 1712.1.12.10
lcsStatusQueueIpUrgentQueuePackets OBJECT-TYPE
    SYNTAX     INTEGER (0..2147483647)
    MAX-ACCESS read-only
    STATUS     current
    DESCRIPTION
        "-- empty --"
    ::= { lcsStatusQueue 10 }

-- {SCALAR} 1712.1.12.11
lcsStatusQueueIcmpQueuePackets OBJECT-TYPE
    SYNTAX     INTEGER (0..2147483647)
    MAX-ACCESS read-only
    STATUS     current
    DESCRIPTION
        "-- empty --"
    ::= { lcsStatusQueue 11 }

-- {SCALAR} 1712.1.12.12
lcsStatusQueueTcpQueuePackets OBJECT-TYPE
    SYNTAX     INTEGER (0..2147483647)
    MAX-ACCESS read-only
    STATUS     current
    DESCRIPTION
        "-- empty --"
    ::= { lcsStatusQueue 12 }

-- {SCALAR} 1712.1.12.13
lcsStatusQueueTftpServerQueuePackets OBJECT-TYPE
    SYNTAX     INTEGER (0..2147483647)
    MAX-ACCESS read-only
    STATUS     current
    DESCRIPTION
        "-- empty --"
    ::= { lcsStatusQueue 13 }

-- {SCALAR} 1712.1.12.14
lcsStatusQueueSnmpQueuePackets OBJECT-TYPE
    SYNTAX     INTEGER (0..2147483647)
    MAX-ACCESS read-only
    STATUS     current
    DESCRIPTION
        "-- empty --"
    ::= { lcsStatusQueue 14 }

-- {SCALAR} 1712.1.12.22
lcsStatusQueueProtHeapPackets OBJECT-TYPE
    SYNTAX     INTEGER (0..2147483647)
    MAX-ACCESS read-only
    STATUS     current
    DESCRIPTION
        "-- empty --"
    ::= { lcsStatusQueue 22 }

-- {SCALAR} 1712.1.12.27
lcsStatusQueueDhcpServerQueuePackets OBJECT-TYPE
    SYNTAX     INTEGER (0..2147483647)
    MAX-ACCESS read-only
    STATUS     current
    DESCRIPTION
        "-- empty --"
    ::= { lcsStatusQueue 27 }

-- {SCALAR} 1712.1.12.28
lcsStatusQueueDhcpClientQueuePackets OBJECT-TYPE
    SYNTAX     INTEGER (0..2147483647)
    MAX-ACCESS read-only
    STATUS     current
    DESCRIPTION
        "-- empty --"
    ::= { lcsStatusQueue 28 }

-- {SCALAR} 1712.1.12.29
lcsStatusQueueIprRipQueuePackets OBJECT-TYPE
    SYNTAX     INTEGER (0..2147483647)
    MAX-ACCESS read-only
    STATUS     current
    DESCRIPTION
        "-- empty --"
    ::= { lcsStatusQueue 29 }

-- {TABLE} 1712.1.13
lcsStatusConnectionTable OBJECT-TYPE
    SYNTAX     SEQUENCE OF LcsStatusConnectionEntry
    MAX-ACCESS not-accessible
    STATUS     current
    DESCRIPTION
        "-- empty --"
    ::= { lcsStatus 13 }

-- {ENTRY} 1712.1.13.1
lcsStatusConnectionEntry OBJECT-TYPE
    SYNTAX     LcsStatusConnectionEntry
    MAX-ACCESS not-accessible
    STATUS     current
    DESCRIPTION
        ""
    INDEX {
        lcsStatusConnectionEntryIfc
    }
    ::= { lcsStatusConnectionTable 1 }

-- {SEQUENCE}
LcsStatusConnectionEntry ::= SEQUENCE {
    lcsStatusConnectionEntryIfc INTEGER,
    lcsStatusConnectionEntryConnections INTEGER,
    lcsStatusConnectionEntryActive INTEGER,
    lcsStatusConnectionEntryPassive INTEGER,
    lcsStatusConnectionEntryErrors INTEGER,
    lcsStatusConnectionEntryConTime DisplayString,
    lcsStatusConnectionEntryCharge INTEGER
}

-- {COLUMN} 1712.1.13.1.1
lcsStatusConnectionEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusConnectionEntry 1 }

-- {COLUMN} 1712.1.13.1.2
lcsStatusConnectionEntryConnections OBJECT-TYPE
    SYNTAX     INTEGER (0..2147483647)
    MAX-ACCESS read-only
    STATUS     current
    DESCRIPTION
        "-- empty --"
    ::= { lcsStatusConnectionEntry 2 }

-- {COLUMN} 1712.1.13.1.3
lcsStatusConnectionEntryActive OBJECT-TYPE
    SYNTAX     INTEGER (0..2147483647)
    MAX-ACCESS read-only
    STATUS     current
    DESCRIPTION
        "-- empty --"
    ::= { lcsStatusConnectionEntry 3 }

-- {COLUMN} 1712.1.13.1.4
lcsStatusConnectionEntryPassive OBJECT-TYPE
    SYNTAX     INTEGER (0..2147483647)
    MAX-ACCESS read-only
    STATUS     current
    DESCRIPTION
        "-- empty --"
    ::= { lcsStatusConnectionEntry 4 }

-- {COLUMN} 1712.1.13.1.5
lcsStatusConnectionEntryErrors OBJECT-TYPE
    SYNTAX     INTEGER (0..2147483647)
    MAX-ACCESS read-only
    STATUS     current
    DESCRIPTION
        "-- empty --"
    ::= { lcsStatusConnectionEntry 5 }

-- {COLUMN} 1712.1.13.1.6
lcsStatusConnectionEntryConTime OBJECT-TYPE
    SYNTAX     DisplayString (SIZE(0..255))
    MAX-ACCESS read-only
    STATUS     current
    DESCRIPTION
        "-- empty --"
    ::= { lcsStatusConnectionEntry 6 }

-- {COLUMN} 1712.1.13.1.7
lcsStatusConnectionEntryCharge OBJECT-TYPE
    SYNTAX     INTEGER (0..2147483647)
    MAX-ACCESS read-only
    STATUS     current
    DESCRIPTION
        "-- empty --"
    ::= { lcsStatusConnectionEntry 7 }

-- {TABLE} 1712.1.14
lcsStatusInfoConnectionTable OBJECT-TYPE
    SYNTAX     SEQUENCE OF LcsStatusInfoConnectionEntry
    MAX-ACCESS not-accessible
    STATUS     current
    DESCRIPTION
        "-- empty --"
    ::= { lcsStatus 14 }

-- {ENTRY} 1712.1.14.1
lcsStatusInfoConnectionEntry OBJECT-TYPE
    SYNTAX     LcsStatusInfoConnectionEntry
    MAX-ACCESS not-accessible
    STATUS     current
    DESCRIPTION
        ""
    INDEX {
        lcsStatusInfoConnectionEntryIfc
    }
    ::= { lcsStatusInfoConnectionTable 1 }

-- {SEQUENCE}
LcsStatusInfoConnectionEntry ::= SEQUENCE {
    lcsStatusInfoConnectionEntryIfc INTEGER,
    lcsStatusInfoConnectionEntryStatus DisplayString,
    lcsStatusInfoConnectionEntryMode INTEGER,
    lcsStatusInfoConnectionEntryDialupRemote DisplayString,
    lcsStatusInfoConnectionEntryPeer DisplayString,
    lcsStatusInfoConnectionEntryB1Dt INTEGER,
    lcsStatusInfoConnectionEntryB2Dt INTEGER
}

-- {COLUMN} 1712.1.14.1.1
lcsStatusInfoConnectionEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusInfoConnectionEntry 1 }

-- {COLUMN} 1712.1.14.1.2
lcsStatusInfoConnectionEntryStatus OBJECT-TYPE
    SYNTAX     DisplayString (SIZE(0..16))
    MAX-ACCESS read-only
    STATUS     current
    DESCRIPTION
        "-- empty --"
    ::= { lcsStatusInfoConnectionEntry 2 }

-- {COLUMN} 1712.1.14.1.3
lcsStatusInfoConnectionEntryMode OBJECT-TYPE
    SYNTAX     INTEGER
      {
        eUnknown (0),
        eActive (4),
        ePassive (5),
        eCallback (9)
      }
    MAX-ACCESS read-only
    STATUS     current
    DESCRIPTION
        "-- empty --"
    ::= { lcsStatusInfoConnectionEntry 3 }

-- {COLUMN} 1712.1.14.1.4
lcsStatusInfoConnectionEntryDialupRemote OBJECT-TYPE
    SYNTAX     DisplayString (SIZE(0..20))
    MAX-ACCESS read-only
    STATUS     current
    DESCRIPTION
        "-- empty --"
    ::= { lcsStatusInfoConnectionEntry 4 }

-- {COLUMN} 1712.1.14.1.5
lcsStatusInfoConnectionEntryPeer OBJECT-TYPE
    SYNTAX     DisplayString (SIZE(0..16))
    MAX-ACCESS read-only
    STATUS     current
    DESCRIPTION
        "-- empty --"
    ::= { lcsStatusInfoConnectionEntry 5 }

-- {COLUMN} 1712.1.14.1.6
lcsStatusInfoConnectionEntryB1Dt OBJECT-TYPE
    SYNTAX     INTEGER (0..65535)
    MAX-ACCESS read-only
    STATUS     current
    DESCRIPTION
        "-- empty --"
    ::= { lcsStatusInfoConnectionEntry 6 }

-- {COLUMN} 1712.1.14.1.7
lcsStatusInfoConnectionEntryB2Dt OBJECT-TYPE
    SYNTAX     INTEGER (0..65535)
    MAX-ACCESS read-only
    STATUS     current
    DESCRIPTION
        "-- empty --"
    ::= { lcsStatusInfoConnectionEntry 7 }

-- {TABLE} 1712.1.15
lcsStatusLayerConnectionTable OBJECT-TYPE
    SYNTAX     SEQUENCE OF LcsStatusLayerConnectionEntry
    MAX-ACCESS not-accessible
    STATUS     current
    DESCRIPTION
        "-- empty --"
    ::= { lcsStatus 15 }

-- {ENTRY} 1712.1.15.1
lcsStatusLayerConnectionEntry OBJECT-TYPE
    SYNTAX     LcsStatusLayerConnectionEntry
    MAX-ACCESS not-accessible
    STATUS     current
    DESCRIPTION
        ""
    INDEX {
        lcsStatusLayerConnectionEntryIfc
    }
    ::= { lcsStatusLayerConnectionTable 1 }

-- {SEQUENCE}
LcsStatusLayerConnectionEntry ::= SEQUENCE {
    lcsStatusLayerConnectionEntryIfc INTEGER,
    lcsStatusLayerConnectionEntryWanLayer DisplayString,
    lcsStatusLayerConnectionEntryEncaps INTEGER,
    lcsStatusLayerConnectionEntryLay3 INTEGER,
    lcsStatusLayerConnectionEntryLay2 INTEGER,
    lcsStatusLayerConnectionEntryL2Opt INTEGER,
    lcsStatusLayerConnectionEntryLay1 INTEGER,
    lcsStatusLayerConnectionEntryL1Parameter INTEGER
}

-- {COLUMN} 1712.1.15.1.1
lcsStatusLayerConnectionEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusLayerConnectionEntry 1 }

-- {COLUMN} 1712.1.15.1.2
lcsStatusLayerConnectionEntryWanLayer OBJECT-TYPE
    SYNTAX     DisplayString (SIZE(0..9))
    MAX-ACCESS read-only
    STATUS     current
    DESCRIPTION
        "-- empty --"
    ::= { lcsStatusLayerConnectionEntry 2 }

-- {COLUMN} 1712.1.15.1.3
lcsStatusLayerConnectionEntryEncaps OBJECT-TYPE
    SYNTAX     INTEGER
      {
        eEther (0),
        eTrans (255)
      }
    MAX-ACCESS read-only
    STATUS     current
    DESCRIPTION
        "-- empty --"
    ::= { lcsStatusLayerConnectionEntry 3 }

-- {COLUMN} 1712.1.15.1.4
lcsStatusLayerConnectionEntryLay3 OBJECT-TYPE
    SYNTAX     INTEGER
      {
        ePpp (4),
        eAppp (5),
        eScppp (6),
        eScappp (7),
        eSctrans (8),
        eDhcp (9),
        eTRANS (255)
      }
    MAX-ACCESS read-only
    STATUS     current
    DESCRIPTION
        "-- empty --"
    ::= { lcsStatusLayerConnectionEntry 4 }

-- {COLUMN} 1712.1.15.1.5
lcsStatusLayerConnectionEntryLay2 OBJECT-TYPE
    SYNTAX     INTEGER
      {
        eSscop (6),
        ePppoe (5),
        eX75lapb (0),
        eTrans (1)
      }
    MAX-ACCESS read-only
    STATUS     current
    DESCRIPTION
        "-- empty --"
    ::= { lcsStatusLayerConnectionEntry 5 }

-- {COLUMN} 1712.1.15.1.6
lcsStatusLayerConnectionEntryL2Opt OBJECT-TYPE
    SYNTAX     INTEGER
      {
        eNone (255),
        eCompr (0),
        eBundle (1),
        eBndPlusCmpr (2)
      }
    MAX-ACCESS read-only
    STATUS     current
    DESCRIPTION
        "-- empty --"
    ::= { lcsStatusLayerConnectionEntry 6 }

-- {COLUMN} 1712.1.15.1.7
lcsStatusLayerConnectionEntryLay1 OBJECT-TYPE
    SYNTAX     INTEGER
      {
        eAdsl (2),
        eEth (4),
        eHdlc64k (0),
        eHdlc56k (1),
        eSerial (6),
        eV1109k6 (3),
        eV11019k2 (67),
        eV11038k4 (131),
        eModem (5)
      }
    MAX-ACCESS read-only
    STATUS     current
    DESCRIPTION
        "-- empty --"
    ::= { lcsStatusLayerConnectionEntry 7 }

-- {COLUMN} 1712.1.15.1.8
lcsStatusLayerConnectionEntryL1Parameter OBJECT-TYPE
    SYNTAX     INTEGER
      {
        eNone (0),
        eV21300 (1),
        eV23600 (2),
        eV231200 (3),
        eV221200 (4),
        eV22bis2400 (5),
        eV32qam4800 (6),
        eV32qam9600 (7),
        eV32bis7200 (8),
        eV32tcm9600 (9),
        eV32bis12000 (10),
        eV32bis14400 (11),
        eV342400 (12),
        eV344800 (13),
        eV347200 (14),
        eV349600 (15),
        eV3412000 (16),
        eV3414400 (17),
        eV3416800 (18),
        eV3419200 (19),
        eV3421600 (20),
        eV3424000 (21),
        eV3426400 (22),
        eV3428800 (23),
        eV3431200 (24),
        eV3433600 (25),
        eV9028000 (26),
        eV9029333 (27),
        eV9030667 (28),
        eV9032000 (29),
        eV9033333 (30),
        eV9034667 (31),
        eV9036000 (32),
        eV9037333 (33),
        eV9038667 (34),
        eV9040000 (35),
        eV9041333 (36),
        eV9042667 (37),
        eV9044000 (38),
        eV9045333 (39),
        eV9046667 (40),
        eV9048000 (41),
        eV9049333 (42),
        eV9050667 (43),
        eV9052000 (44),
        eV9053333 (45),
        eV9054667 (46),
        eV9056000 (47)
      }
    MAX-ACCESS read-only
    STATUS     current
    DESCRIPTION
        "-- empty --"
    ::= { lcsStatusLayerConnectionEntry 8 }

-- {TABLE} 1712.1.16
lcsStatusCallInformationTable OBJECT-TYPE
    SYNTAX     SEQUENCE OF LcsStatusCallInformationEntry
    MAX-ACCESS not-accessible
    STATUS     current
    DESCRIPTION
        "-- empty --"
    ::= { lcsStatus 16 }

-- {ENTRY} 1712.1.16.1
lcsStatusCallInformationEntry OBJECT-TYPE
    SYNTAX     LcsStatusCallInformationEntry
    MAX-ACCESS not-accessible
    STATUS     current
    DESCRIPTION
        ""
    INDEX {
        lcsStatusCallInformationEntrySystemTime,
        lcsStatusCallInformationEntryCounter
    }
    ::= { lcsStatusCallInformationTable 1 }

-- {SEQUENCE}
LcsStatusCallInformationEntry ::= SEQUENCE {
    lcsStatusCallInformationEntrySystemTime Gauge32,
    lcsStatusCallInformationEntryIfc INTEGER,
    lcsStatusCallInformationEntryClipCaller DisplayString,
    lcsStatusCallInformationEntryDialCaller DisplayString,
    lcsStatusCallInformationEntryCapab INTEGER,
    lcsStatusCallInformationEntryBChan INTEGER,
    lcsStatusCallInformationEntryCounter INTEGER
}

-- {COLUMN} 1712.1.16.1.1
lcsStatusCallInformationEntrySystemTime OBJECT-TYPE
    SYNTAX     Gauge32
    MAX-ACCESS read-only
    STATUS     current
    DESCRIPTION
        "-- empty --"
    ::= { lcsStatusCallInformationEntry 1 }

-- {COLUMN} 1712.1.16.1.2
lcsStatusCallInformationEntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsStatusCallInformationEntry 2 }

-- {COLUMN} 1712.1.16.1.3
lcsStatusCallInformationEntryClipCaller OBJECT-TYPE
    SYNTAX     DisplayString (SIZE(0..20))
    MAX-ACCESS read-only
    STATUS     current
    DESCRIPTION
        "-- empty --"
    ::= { lcsStatusCallInformationEntry 3 }

-- {COLUMN} 1712.1.16.1.4
lcsStatusCallInformationEntryDialCaller OBJECT-TYPE
    SYNTAX     DisplayString (SIZE(0..20))
    MAX-ACCESS read-only
    STATUS     current
    DESCRIPTION
        "-- empty --"
    ::= { lcsStatusCallInformationEntry 4 }

-- {COLUMN} 1712.1.16.1.5
lcsStatusCallInformationEntryCapab OBJECT-TYPE
    SYNTAX     INTEGER
      {
        eUnknown (255),
        eHdlc64k (0),
        eHdlc56k (1),
        eV1109k6 (3),
        eV11019k2 (67),
        eV11038k4 (131),
        eModem (5),
        eA31khz (13),
        eSpeech (14),
        eFaxG23 (15)
      }
    MAX-ACCESS read-only
    STATUS     current
    DESCRIPTION
        "-- empty --"
    ::= { lcsStatusCallInformationEntry 5 }

-- {COLUMN} 1712.1.16.1.6
lcsStatusCallInformationEntryBChan OBJECT-TYPE
    SYNTAX     INTEGER (0..65535)
    MAX-ACCESS read-only
    STATUS     current
    DESCRIPTION
        "-- empty --"
    ::= { lcsStatusCallInformationEntry 6 }

-- {COLUMN} 1712.1.16.1.7
lcsStatusCallInformationEntryCounter OBJECT-TYPE
    SYNTAX     INTEGER (0..2147483647)
    MAX-ACCESS read-only
    STATUS     current
    DESCRIPTION
        "-- empty --"
    ::= { lcsStatusCallInformationEntry 7 }

-- {TABLE} 1712.1.17
lcsStatusRemoteConnectionsTable OBJECT-TYPE
    SYNTAX     SEQUENCE OF LcsStatusRemoteConnectionsEntry
    MAX-ACCESS not-accessible
    STATUS     current
    DESCRIPTION
        "-- empty --"
    ::= { lcsStatus 17 }

-- {ENTRY} 1712.1.17.1
lcsStatusRemoteConnectionsEntry OBJECT-TYPE
    SYNTAX     LcsStatusRemoteConnectionsEntry
    MAX-ACCESS not-accessible
    STATUS     current
    DESCRIPTION
        ""
    INDEX {
        lcsStatusRemoteConnectionsEntryConnStart,
        lcsStatusRemoteConnectionsEntryCounter
    }
    ::= { lcsStatusRemoteConnectionsTable 1 }

-- {SEQUENCE}
LcsStatusRemoteConnectionsEntry ::= SEQUENCE {
    lcsStatusRemoteConnectionsEntryConnStart DisplayString,
    lcsStatusRemoteConnectionsEntryRemoteId DisplayString,
    lcsStatusRemoteConnectionsEntryMode INTEGER,
    lcsStatusRemoteConnectionsEntryIfc INTEGER,
    lcsStatusRemoteConnectionsEntryConnTime DisplayString,
    lcsStatusRemoteConnectionsEntryCharge INTEGER,
    lcsStatusRemoteConnectionsEntryCounter INTEGER
}

-- {COLUMN} 1712.1.17.1.1
lcsStatusRemoteConnectionsEntryConnStart OBJECT-TYPE
    SYNTAX     DisplayString (SIZE(0..19))
    MAX-ACCESS read-only
    STATUS     current
    DESCRIPTION
        "-- empty --"
    ::= { lcsStatusRemoteConnectionsEntry 1 }

-- {COLUMN} 1712.1.17.1.2
lcsStatusRemoteConnectionsEntryRemoteId OBJECT-TYPE
    SYNTAX     DisplayString (SIZE(0..16))
    MAX-ACCESS read-only
    STATUS     current
    DESCRIPTION
        "-- empty --"
    ::= { lcsStatusRemoteConnectionsEntry 2 }

-- {COLUMN} 1712.1.17.1.3
lcsStatusRemoteConnectionsEntryMode OBJECT-TYPE
    SYNTAX     INTEGER
      {
        eUnknown (0),
        eActive (4),
        ePassive (5),
        eCallback (9)
      }
    MAX-ACCESS read-only
    STATUS     current
    DESCRIPTION
        "-- empty --"
    ::= { lcsStatusRemoteConnectionsEntry 3 }

-- {COLUMN} 1712.1.17.1.4
lcsStatusRemoteConnectionsEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusRemoteConnectionsEntry 4 }

-- {COLUMN} 1712.1.17.1.5
lcsStatusRemoteConnectionsEntryConnTime OBJECT-TYPE
    SYNTAX     DisplayString (SIZE(0..255))
    MAX-ACCESS read-only
    STATUS     current
    DESCRIPTION
        "-- empty --"
    ::= { lcsStatusRemoteConnectionsEntry 5 }

-- {COLUMN} 1712.1.17.1.6
lcsStatusRemoteConnectionsEntryCharge OBJECT-TYPE
    SYNTAX     INTEGER (0..2147483647)
    MAX-ACCESS read-only
    STATUS     current
    DESCRIPTION
        "-- empty --"
    ::= { lcsStatusRemoteConnectionsEntry 6 }

-- {COLUMN} 1712.1.17.1.8
lcsStatusRemoteConnectionsEntryCounter OBJECT-TYPE
    SYNTAX     INTEGER (0..2147483647)
    MAX-ACCESS read-only
    STATUS     current
    DESCRIPTION
        "-- empty --"
    ::= { lcsStatusRemoteConnectionsEntry 8 }

-- {TABLE} 1712.1.48
lcsStatusChannelTable OBJECT-TYPE
    SYNTAX     SEQUENCE OF LcsStatusChannelEntry
    MAX-ACCESS not-accessible
    STATUS     current
    DESCRIPTION
        "-- empty --"
    ::= { lcsStatus 48 }

-- {ENTRY} 1712.1.48.1
lcsStatusChannelEntry OBJECT-TYPE
    SYNTAX     LcsStatusChannelEntry
    MAX-ACCESS not-accessible
    STATUS     current
    DESCRIPTION
        ""
    INDEX {
        lcsStatusChannelEntryChan
    }
    ::= { lcsStatusChannelTable 1 }

-- {SEQUENCE}
LcsStatusChannelEntry ::= SEQUENCE {
    lcsStatusChannelEntryChan INTEGER,
    lcsStatusChannelEntryPhChan INTEGER,
    lcsStatusChannelEntryPlci INTEGER,
    lcsStatusChannelEntryBus INTEGER,
    lcsStatusChannelEntryState INTEGER,
    lcsStatusChannelEntryApp INTEGER,
    lcsStatusChannelEntryConnector INTEGER,
    lcsStatusChannelEntryCause INTEGER,
    lcsStatusChannelEntryNumber DisplayString,
    lcsStatusChannelEntrySubaddress INTEGER,
    lcsStatusChannelEntryCharge INTEGER,
    lcsStatusChannelEntryConnStart INTEGER,
    lcsStatusChannelEntryConnTime INTEGER,
    lcsStatusChannelEntryExtra DisplayString,
    lcsStatusChannelEntryIsdnDisplay DisplayString,
    lcsStatusChannelEntryPptpConns INTEGER,
    lcsStatusChannelEntryVpnConns INTEGER
}

-- {COLUMN} 1712.1.48.1.1
lcsStatusChannelEntryChan OBJECT-TYPE
    SYNTAX     INTEGER
      {
        eDslErr (1),
        eDslCh1 (2),
        eDslCh2 (3),
        eDslCh3 (4),
        eDslCh4 (5),
        eDslCh5 (6),
        eDslCh6 (7),
        eDslCh7 (8),
        eDslCh8 (9),
        eS01Err (10),
        eS01B1 (11),
        eS01B2 (12),
        eExtErr (13),
        eExt (14)
      }
    MAX-ACCESS read-only
    STATUS     current
    DESCRIPTION
        "-- empty --"
    ::= { lcsStatusChannelEntry 1 }

-- {COLUMN} 1712.1.48.1.15
lcsStatusChannelEntryPhChan OBJECT-TYPE
    SYNTAX     INTEGER (0..2147483647)
    MAX-ACCESS read-only
    STATUS     current
    DESCRIPTION
        "-- empty --"
    ::= { lcsStatusChannelEntry 15 }

-- {COLUMN} 1712.1.48.1.2
lcsStatusChannelEntryPlci OBJECT-TYPE
    SYNTAX     INTEGER (0..2147483647)
    MAX-ACCESS read-only
    STATUS     current
    DESCRIPTION
        "-- empty --"
    ::= { lcsStatusChannelEntry 2 }

-- {COLUMN} 1712.1.48.1.3
lcsStatusChannelEntryBus OBJECT-TYPE
    SYNTAX     INTEGER (0..2147483647)
    MAX-ACCESS read-only
    STATUS     current
    DESCRIPTION
        "-- empty --"
    ::= { lcsStatusChannelEntry 3 }

-- {COLUMN} 1712.1.48.1.4
lcsStatusChannelEntryState OBJECT-TYPE
    SYNTAX     INTEGER (0..2147483647)
    MAX-ACCESS read-only
    STATUS     current
    DESCRIPTION
        "-- empty --"
    ::= { lcsStatusChannelEntry 4 }

-- {COLUMN} 1712.1.48.1.5
lcsStatusChannelEntryApp OBJECT-TYPE
    SYNTAX     INTEGER
      {
        eNone (0),
        eRouter (1),
        eCapi (2),
        eAB (3),
        eTimeModule (255)
      }
    MAX-ACCESS read-only
    STATUS     current
    DESCRIPTION
        "-- empty --"
    ::= { lcsStatusChannelEntry 5 }

-- {COLUMN} 1712.1.48.1.6
lcsStatusChannelEntryConnector OBJECT-TYPE
    SYNTAX     INTEGER
      {
        eUnk (0),
        eAct (1),
        ePas (2),
        ePerm (3)
      }
    MAX-ACCESS read-only
    STATUS     current
    DESCRIPTION
        ""
    ::= { lcsStatusChannelEntry 6 }

-- {COLUMN} 1712.1.48.1.7
lcsStatusChannelEntryCause OBJECT-TYPE
    SYNTAX     INTEGER (0..65535)
    MAX-ACCESS read-write
    STATUS     current
    DESCRIPTION
        "-- empty --"
    ::= { lcsStatusChannelEntry 7 }

-- {COLUMN} 1712.1.48.1.8
lcsStatusChannelEntryNumber OBJECT-TYPE
    SYNTAX     DisplayString (SIZE(0..40))
    MAX-ACCESS read-only
    STATUS     current
    DESCRIPTION
        "-- empty --"
    ::= { lcsStatusChannelEntry 8 }

-- {COLUMN} 1712.1.48.1.9
lcsStatusChannelEntrySubaddress OBJECT-TYPE
    SYNTAX     INTEGER (0..2147483647)
    MAX-ACCESS read-only
    STATUS     current
    DESCRIPTION
        "-- empty --"
    ::= { lcsStatusChannelEntry 9 }

-- {COLUMN} 1712.1.48.1.10
lcsStatusChannelEntryCharge OBJECT-TYPE
    SYNTAX     INTEGER (0..2147483647)
    MAX-ACCESS read-only
    STATUS     current
    DESCRIPTION
        "-- empty --"
    ::= { lcsStatusChannelEntry 10 }

-- {COLUMN} 1712.1.48.1.13
lcsStatusChannelEntryConnStart OBJECT-TYPE
    SYNTAX     INTEGER (0..2147483647)
    MAX-ACCESS read-only
    STATUS     current
    DESCRIPTION
        "-- empty --"
    ::= { lcsStatusChannelEntry 13 }

-- {COLUMN} 1712.1.48.1.12
lcsStatusChannelEntryConnTime OBJECT-TYPE
    SYNTAX     INTEGER (0..2147483647)
    MAX-ACCESS read-only
    STATUS     current
    DESCRIPTION
        "-- empty --"
    ::= { lcsStatusChannelEntry 12 }

-- {COLUMN} 1712.1.48.1.11
lcsStatusChannelEntryExtra OBJECT-TYPE
    SYNTAX     DisplayString (SIZE(0..16))
    MAX-ACCESS read-only
    STATUS     current
    DESCRIPTION
        "-- empty --"
    ::= { lcsStatusChannelEntry 11 }

-- {COLUMN} 1712.1.48.1.14
lcsStatusChannelEntryIsdnDisplay OBJECT-TYPE
    SYNTAX     DisplayString (SIZE(0..34))
    MAX-ACCESS read-only
    STATUS     current
    DESCRIPTION
        "-- empty --"
    ::= { lcsStatusChannelEntry 14 }

-- {COLUMN} 1712.1.48.1.16
lcsStatusChannelEntryPptpConns OBJECT-TYPE
    SYNTAX     INTEGER (0..2147483647)
    MAX-ACCESS read-only
    STATUS     current
    DESCRIPTION
        "-- empty --"
    ::= { lcsStatusChannelEntry 16 }

-- {COLUMN} 1712.1.48.1.17
lcsStatusChannelEntryVpnConns OBJECT-TYPE
    SYNTAX     INTEGER (0..2147483647)
    MAX-ACCESS read-only
    STATUS     current
    DESCRIPTION
        "-- empty --"
    ::= { lcsStatusChannelEntry 17 }

-- {OID} 1712.1.21
lcsStatusTime OBJECT IDENTIFIER ::= { lcsStatus 21 }

-- {SCALAR} 1712.1.21.1
lcsStatusTimeCurrentTime OBJECT-TYPE
    SYNTAX     DisplayString
    MAX-ACCESS read-only
    STATUS     current
    DESCRIPTION
        "-- empty --"
    ::= { lcsStatusTime 1 }

-- {SCALAR} 1712.1.21.2
lcsStatusTimeSource OBJECT-TYPE
    SYNTAX     INTEGER
      {
        eManual (1),
        eIsdn (2),
        eLan (3),
        eRam (4),
        eNtp (9),
        eLanconfig (8),
        eNo (0)
      }
    MAX-ACCESS read-only
    STATUS     current
    DESCRIPTION
        "-- empty --"
    ::= { lcsStatusTime 2 }

-- {SCALAR} 1712.1.21.3
lcsStatusTimeSetCount OBJECT-TYPE
    SYNTAX     Counter32
    MAX-ACCESS read-only
    STATUS     current
    DESCRIPTION
        "-- empty --"
    ::= { lcsStatusTime 3 }

-- {OID} 1712.1.21.4
lcsStatusTimeIsdn OBJECT IDENTIFIER ::= { lcsStatusTime 4 }

-- {SCALAR} 1712.1.21.4.1
lcsStatusTimeIsdnConnection OBJECT-TYPE
    SYNTAX     INTEGER (0..255)
    MAX-ACCESS read-only
    STATUS     current
    DESCRIPTION
        "-- empty --"
    ::= { lcsStatusTimeIsdn 1 }

-- {SCALAR} 1712.1.21.4.2
lcsStatusTimeIsdnInformation OBJECT-TYPE
    SYNTAX     INTEGER (0..255)
    MAX-ACCESS read-only
    STATUS     current
    DESCRIPTION
        "-- empty --"
    ::= { lcsStatusTimeIsdn 2 }

-- {SCALAR} 1712.1.21.4.3
lcsStatusTimeIsdnInfoError OBJECT-TYPE
    SYNTAX     INTEGER (0..255)
    MAX-ACCESS read-only
    STATUS     current
    DESCRIPTION
        "-- empty --"
    ::= { lcsStatusTimeIsdn 3 }

-- {SCALAR} 1712.1.21.4.4
lcsStatusTimeIsdnUnits OBJECT-TYPE
    SYNTAX     INTEGER (0..65535)
    MAX-ACCESS read-only
    STATUS     current
    DESCRIPTION
        "-- empty --"
    ::= { lcsStatusTimeIsdn 4 }

-- {SCALAR} 1712.1.21.4.5
lcsStatusTimeIsdnDeleteValues OBJECT-TYPE
    SYNTAX     DisplayString
    MAX-ACCESS read-write
    STATUS     current
    DESCRIPTION
        "-- empty --"
    ::= { lcsStatusTimeIsdn 5 }

-- {SCALAR} 1712.1.21.7
lcsStatusTimeUtcInSeconds OBJECT-TYPE
    SYNTAX     Counter32
    MAX-ACCESS read-only
    STATUS     current
    DESCRIPTION
        "-- empty --"
    ::= { lcsStatusTime 7 }

-- {SCALAR} 1712.1.21.10
lcsStatusTimeTimezone OBJECT-TYPE
    SYNTAX     INTEGER
      {
        e0 (0),
        eplus1 (1), -- plus 1 hour
        eplus2 (2), -- plus 2 hours
        eplus3 (3), -- plus 3 hours
        eplus4 (4), -- plus 4 hours
        eplus5 (5), -- plus 5 hours
        eplus6 (6), -- plus 6 hours
        eplus7 (7), -- plus 7 hours
        eplus8 (8), -- plus 8 hours
        eplus9 (9), -- plus 9 hours
        eplus10 (10), -- plus 10 hours
        eplus11 (11), -- plus 11 hours
        eplus12 (12), -- plus 12 hours
        eplus13 (13), -- plus 13 hours
        eplus14 (14), -- plus 14 hours
        eminus1 (255), -- minus 1 hour
        eminus2 (254), -- minus 2 hours
        eminus3 (253), -- minus 3 hours
        eminus4 (252), -- minus 4 hours
        eminus5 (251), -- minus 5 hours
        eminus6 (250), -- minus 6 hours
        eminus7 (249), -- minus 7 hours
        eminus8 (248), -- minus 8 hours
        eminus9 (247), -- minus 9 hours
        eminus10 (246), -- minus 10 hours
        eminus11 (245), -- minus 11 hours
        eminus12 (244) -- minus 12 hours
      }
    MAX-ACCESS read-only
    STATUS     current
    DESCRIPTION
        "-- empty --"
    ::= { lcsStatusTime 10 }

-- {SCALAR} 1712.1.21.11
lcsStatusTimeDaylightSavingTime OBJECT-TYPE
    SYNTAX     INTEGER
      {
        eNo (0),
        eYes (1),
        eEuropeEu (2),
        eUsa (4),
        eUserDefined (255)
      }
    MAX-ACCESS read-only
    STATUS     current
    DESCRIPTION
        "-- empty --"
    ::= { lcsStatusTime 11 }

-- {TABLE} 1712.1.21.12
lcsStatusTimeDstClockChangesTable OBJECT-TYPE
    SYNTAX     SEQUENCE OF LcsStatusTimeDstClockChangesEntry
    MAX-ACCESS not-accessible
    STATUS     current
    DESCRIPTION
        "-- empty --"
    ::= { lcsStatusTime 12 }

-- {ENTRY} 1712.1.21.12.1
lcsStatusTimeDstClockChangesEntry OBJECT-TYPE
    SYNTAX     LcsStatusTimeDstClockChangesEntry
    MAX-ACCESS not-accessible
    STATUS     current
    DESCRIPTION
        ""
    INDEX {
        lcsStatusTimeDstClockChangesEntryEvent
    }
    ::= { lcsStatusTimeDstClockChangesTable 1 }

-- {SEQUENCE}
LcsStatusTimeDstClockChangesEntry ::= SEQUENCE {
    lcsStatusTimeDstClockChangesEntryEvent INTEGER,
    lcsStatusTimeDstClockChangesEntryIndex INTEGER,
    lcsStatusTimeDstClockChangesEntryDay INTEGER,
    lcsStatusTimeDstClockChangesEntryMonth INTEGER,
    lcsStatusTimeDstClockChangesEntryHour INTEGER,
    lcsStatusTimeDstClockChangesEntryMinute INTEGER,
    lcsStatusTimeDstClockChangesEntryTimeType INTEGER
}

-- {COLUMN} 1712.1.21.12.1.1
lcsStatusTimeDstClockChangesEntryEvent OBJECT-TYPE
    SYNTAX     INTEGER
      {
        eStart (1),
        eEnd (2)
      }
    MAX-ACCESS read-only
    STATUS     current
    DESCRIPTION
        "-- empty --"
    ::= { lcsStatusTimeDstClockChangesEntry 1 }

-- {COLUMN} 1712.1.21.12.1.2
lcsStatusTimeDstClockChangesEntryIndex OBJECT-TYPE
    SYNTAX     INTEGER
      {
        e4Last (252),
        e3Last (253),
        e2Last (254),
        eLast (255),
        eFirst (1),
        eSecond (2),
        eThird (3),
        eFourth (4)
      }
    MAX-ACCESS read-only
    STATUS     current
    DESCRIPTION
        "-- empty --"
    ::= { lcsStatusTimeDstClockChangesEntry 2 }

-- {COLUMN} 1712.1.21.12.1.3
lcsStatusTimeDstClockChangesEntryDay OBJECT-TYPE
    SYNTAX     INTEGER
      {
        eSunday (0),
        eMonday (1),
        eTuesday (2),
        eWednesday (3),
        eThursday (4),
        eFriday (5),
        eSaturday (6)
      }
    MAX-ACCESS read-only
    STATUS     current
    DESCRIPTION
        "-- empty --"
    ::= { lcsStatusTimeDstClockChangesEntry 3 }

-- {COLUMN} 1712.1.21.12.1.4
lcsStatusTimeDstClockChangesEntryMonth OBJECT-TYPE
    SYNTAX     INTEGER
      {
        eJanuary (1),
        eFebruary (2),
        eMarch (3),
        eApril (4),
        eMay (5),
        eJune (6),
        eJuly (7),
        eAugust (8),
        eSeptember (9),
        eOctober (10),
        eNovember (11),
        eDecember (12)
      }
    MAX-ACCESS read-only
    STATUS     current
    DESCRIPTION
        "-- empty --"
    ::= { lcsStatusTimeDstClockChangesEntry 4 }

-- {COLUMN} 1712.1.21.12.1.5
lcsStatusTimeDstClockChangesEntryHour OBJECT-TYPE
    SYNTAX     INTEGER (0..255)
    MAX-ACCESS read-only
    STATUS     current
    DESCRIPTION
        "-- empty --"
    ::= { lcsStatusTimeDstClockChangesEntry 5 }

-- {COLUMN} 1712.1.21.12.1.6
lcsStatusTimeDstClockChangesEntryMinute OBJECT-TYPE
    SYNTAX     INTEGER (0..255)
    MAX-ACCESS read-only
    STATUS     current
    DESCRIPTION
        "-- empty --"
    ::= { lcsStatusTimeDstClockChangesEntry 6 }

-- {COLUMN} 1712.1.21.12.1.7
lcsStatusTimeDstClockChangesEntryTimeType OBJECT-TYPE
    SYNTAX     INTEGER
      {
        eUtc (1),
        eLst (0)
      }
    MAX-ACCESS read-only
    STATUS     current
    DESCRIPTION
        "-- empty --"
    ::= { lcsStatusTimeDstClockChangesEntry 7 }

-- {OID} 1712.1.22
lcsStatusLcr OBJECT IDENTIFIER ::= { lcsStatus 22 }

-- {SCALAR} 1712.1.22.1
lcsStatusLcrTotalCalls OBJECT-TYPE
    SYNTAX     Counter32
    MAX-ACCESS read-only
    STATUS     current
    DESCRIPTION
        "-- empty --"
    ::= { lcsStatusLcr 1 }

-- {SCALAR} 1712.1.22.2
lcsStatusLcrFoundEvents OBJECT-TYPE
    SYNTAX     Counter32
    MAX-ACCESS read-only
    STATUS     current
    DESCRIPTION
        "-- empty --"
    ::= { lcsStatusLcr 2 }

-- {SCALAR} 1712.1.22.3
lcsStatusLcrNotfoundErrors OBJECT-TYPE
    SYNTAX     Counter32
    MAX-ACCESS read-only
    STATUS     current
    DESCRIPTION
        "-- empty --"
    ::= { lcsStatusLcr 3 }

-- {SCALAR} 1712.1.22.4
lcsStatusLcrMissingtimeErrors OBJECT-TYPE
    SYNTAX     Counter32
    MAX-ACCESS read-only
    STATUS     current
    DESCRIPTION
        "-- empty --"
    ::= { lcsStatusLcr 4 }

-- {TABLE} 1712.1.22.6
lcsStatusLcrProviderTable OBJECT-TYPE
    SYNTAX     SEQUENCE OF LcsStatusLcrProviderEntry
    MAX-ACCESS not-accessible
    STATUS     current
    DESCRIPTION
        "-- empty --"
    ::= { lcsStatusLcr 6 }

-- {ENTRY} 1712.1.22.6.1
lcsStatusLcrProviderEntry OBJECT-TYPE
    SYNTAX     LcsStatusLcrProviderEntry
    MAX-ACCESS not-accessible
    STATUS     current
    DESCRIPTION
        ""
    INDEX {
        lcsStatusLcrProviderEntryProvider
    }
    ::= { lcsStatusLcrProviderTable 1 }

-- {SEQUENCE}
LcsStatusLcrProviderEntry ::= SEQUENCE {
    lcsStatusLcrProviderEntryProvider DisplayString,
    lcsStatusLcrProviderEntryFailures INTEGER,
    lcsStatusLcrProviderEntrySuccesses INTEGER
}

-- {COLUMN} 1712.1.22.6.1.1
lcsStatusLcrProviderEntryProvider OBJECT-TYPE
    SYNTAX     DisplayString (SIZE(0..10))
    MAX-ACCESS read-only
    STATUS     current
    DESCRIPTION
        "-- empty --"
    ::= { lcsStatusLcrProviderEntry 1 }

-- {COLUMN} 1712.1.22.6.1.2
lcsStatusLcrProviderEntryFailures OBJECT-TYPE
    SYNTAX     INTEGER (0..2147483647)
    MAX-ACCESS read-only
    STATUS     current
    DESCRIPTION
        "-- empty --"
    ::= { lcsStatusLcrProviderEntry 2 }

-- {COLUMN} 1712.1.22.6.1.3
lcsStatusLcrProviderEntrySuccesses OBJECT-TYPE
    SYNTAX     INTEGER (0..2147483647)
    MAX-ACCESS read-only
    STATUS     current
    DESCRIPTION
        "-- empty --"
    ::= { lcsStatusLcrProviderEntry 3 }

-- {SCALAR} 1712.1.22.7
lcsStatusLcrDeleteValues OBJECT-TYPE
    SYNTAX     DisplayString
    MAX-ACCESS read-write
    STATUS     current
    DESCRIPTION
        "-- empty --"
    ::= { lcsStatusLcr 7 }

-- {OID} 1712.1.24
lcsStatusCharging OBJECT IDENTIFIER ::= { lcsStatus 24 }

-- {SCALAR} 1712.1.24.6
lcsStatusChargingSpareDaysPerPeriod OBJECT-TYPE
    SYNTAX     INTEGER (0..65535)
    MAX-ACCESS read-only
    STATUS     current
    DESCRIPTION
        "-- empty --"
    ::= { lcsStatusCharging 6 }

-- {SCALAR} 1712.1.24.4
lcsStatusChargingSpareUnits OBJECT-TYPE
    SYNTAX     INTEGER (0..65535)
    MAX-ACCESS read-only
    STATUS     current
    DESCRIPTION
        "-- empty --"
    ::= { lcsStatusCharging 4 }

-- {SCALAR} 1712.1.24.7
lcsStatusChargingRouterUnits OBJECT-TYPE
    SYNTAX     INTEGER (0..2147483647)
    MAX-ACCESS read-only
    STATUS     current
    DESCRIPTION
        "-- empty --"
    ::= { lcsStatusCharging 7 }

-- {SCALAR} 1712.1.24.8
lcsStatusChargingTotalUnits OBJECT-TYPE
    SYNTAX     INTEGER (0..2147483647)
    MAX-ACCESS read-only
    STATUS     current
    DESCRIPTION
        "-- empty --"
    ::= { lcsStatusCharging 8 }

-- {TABLE} 1712.1.24.5
lcsStatusChargingTableBudgetTable OBJECT-TYPE
    SYNTAX     SEQUENCE OF LcsStatusChargingTableBudgetEntry
    MAX-ACCESS not-accessible
    STATUS     current
    DESCRIPTION
        "-- empty --"
    ::= { lcsStatusCharging 5 }

-- {ENTRY} 1712.1.24.5.1
lcsStatusChargingTableBudgetEntry OBJECT-TYPE
    SYNTAX     LcsStatusChargingTableBudgetEntry
    MAX-ACCESS not-accessible
    STATUS     current
    DESCRIPTION
        ""
    INDEX {
        lcsStatusChargingTableBudgetEntryIfc
    }
    ::= { lcsStatusChargingTableBudgetTable 1 }

-- {SEQUENCE}
LcsStatusChargingTableBudgetEntry ::= SEQUENCE {
    lcsStatusChargingTableBudgetEntryIfc INTEGER,
    lcsStatusChargingTableBudgetEntryBudgetUnits INTEGER,
    lcsStatusChargingTableBudgetEntrySpareBudget INTEGER,
    lcsStatusChargingTableBudgetEntryTotalUnits INTEGER
}

-- {COLUMN} 1712.1.24.5.1.1
lcsStatusChargingTableBudgetEntryIfc OBJECT-TYPE
    SYNTAX     INTEGER
      {
        eRouterIsdnSerial (1),
        eLancapi (2),
        eAb1 (3),
        eAb2 (4),
        eAb3 (5),
        eAb4 (6),
        eTimeModul (255)
      }
    MAX-ACCESS read-only
    STATUS     current
    DESCRIPTION
        "-- empty --"
    ::= { lcsStatusChargingTableBudgetEntry 1 }

-- {COLUMN} 1712.1.24.5.1.2
lcsStatusChargingTableBudgetEntryBudgetUnits OBJECT-TYPE
    SYNTAX     INTEGER (0..65535)
    MAX-ACCESS read-only
    STATUS     current
    DESCRIPTION
        "-- empty --"
    ::= { lcsStatusChargingTableBudgetEntry 2 }

-- {COLUMN} 1712.1.24.5.1.3
lcsStatusChargingTableBudgetEntrySpareBudget OBJECT-TYPE
    SYNTAX     INTEGER (0..65535)
    MAX-ACCESS read-only
    STATUS     current
    DESCRIPTION
        "-- empty --"
    ::= { lcsStatusChargingTableBudgetEntry 3 }

-- {COLUMN} 1712.1.24.5.1.4
lcsStatusChargingTableBudgetEntryTotalUnits OBJECT-TYPE
    SYNTAX     INTEGER (0..2147483647)
    MAX-ACCESS read-only
    STATUS     current
    DESCRIPTION
        "-- empty --"
    ::= { lcsStatusChargingTableBudgetEntry 4 }

-- {SCALAR} 1712.1.24.10
lcsStatusChargingSpareDialupMinutes OBJECT-TYPE
    SYNTAX     INTEGER (0..2147483647)
    MAX-ACCESS read-only
    STATUS     current
    DESCRIPTION
        "-- empty --"
    ::= { lcsStatusCharging 10 }

-- {SCALAR} 1712.1.24.11
lcsStatusChargingDialupMinutesActive OBJECT-TYPE
    SYNTAX     INTEGER (0..2147483647)
    MAX-ACCESS read-only
    STATUS     current
    DESCRIPTION
        "-- empty --"
    ::= { lcsStatusCharging 11 }

-- {SCALAR} 1712.1.24.1
lcsStatusChargingSpareDslBroadbandMinutes OBJECT-TYPE
    SYNTAX     INTEGER (0..2147483647)
    MAX-ACCESS read-only
    STATUS     current
    DESCRIPTION
        "-- empty --"
    ::= { lcsStatusCharging 1 }

-- {SCALAR} 1712.1.24.9
lcsStatusChargingRouterDslBroadbandMinutesActive OBJECT-TYPE
    SYNTAX     INTEGER (0..2147483647)
    MAX-ACCESS read-only
    STATUS     current
    DESCRIPTION
        "-- empty --"
    ::= { lcsStatusCharging 9 }

-- {TABLE} 1712.1.24.2
lcsStatusChargingTimeTableTable OBJECT-TYPE
    SYNTAX     SEQUENCE OF LcsStatusChargingTimeTableEntry
    MAX-ACCESS not-accessible
    STATUS     current
    DESCRIPTION
        "-- empty --"
    ::= { lcsStatusCharging 2 }

-- {ENTRY} 1712.1.24.2.1
lcsStatusChargingTimeTableEntry OBJECT-TYPE
    SYNTAX     LcsStatusChargingTimeTableEntry
    MAX-ACCESS not-accessible
    STATUS     current
    DESCRIPTION
        ""
    INDEX {
        lcsStatusChargingTimeTableEntryIfc
    }
    ::= { lcsStatusChargingTimeTableTable 1 }

-- {SEQUENCE}
LcsStatusChargingTimeTableEntry ::= SEQUENCE {
    lcsStatusChargingTimeTableEntryIfc INTEGER,
    lcsStatusChargingTimeTableEntryBudgetMinutes INTEGER,
    lcsStatusChargingTimeTableEntrySpareMinutes INTEGER,
    lcsStatusChargingTimeTableEntryMinutesActive INTEGER,
    lcsStatusChargingTimeTableEntryMinutesPassive INTEGER
}

-- {COLUMN} 1712.1.24.2.1.1
lcsStatusChargingTimeTableEntryIfc OBJECT-TYPE
    SYNTAX     INTEGER
      {
        eRouterDslBroadband (1),
        eRouterIsdnSerial (2),
        eLancapi (3),
        eAb1 (4),
        eAb2 (5),
        eAb3 (6),
        eAb4 (7),
        eTimeModul (255)
      }
    MAX-ACCESS read-only
    STATUS     current
    DESCRIPTION
        "-- empty --"
    ::= { lcsStatusChargingTimeTableEntry 1 }

-- {COLUMN} 1712.1.24.2.1.2
lcsStatusChargingTimeTableEntryBudgetMinutes OBJECT-TYPE
    SYNTAX     INTEGER (0..2147483647)
    MAX-ACCESS read-only
    STATUS     current
    DESCRIPTION
        "-- empty --"
    ::= { lcsStatusChargingTimeTableEntry 2 }

-- {COLUMN} 1712.1.24.2.1.3
lcsStatusChargingTimeTableEntrySpareMinutes OBJECT-TYPE
    SYNTAX     INTEGER (0..2147483647)
    MAX-ACCESS read-only
    STATUS     current
    DESCRIPTION
        "-- empty --"
    ::= { lcsStatusChargingTimeTableEntry 3 }

-- {COLUMN} 1712.1.24.2.1.4
lcsStatusChargingTimeTableEntryMinutesActive OBJECT-TYPE
    SYNTAX     INTEGER (0..2147483647)
    MAX-ACCESS read-only
    STATUS     current
    DESCRIPTION
        "-- empty --"
    ::= { lcsStatusChargingTimeTableEntry 4 }

-- {COLUMN} 1712.1.24.2.1.5
lcsStatusChargingTimeTableEntryMinutesPassive OBJECT-TYPE
    SYNTAX     INTEGER (0..2147483647)
    MAX-ACCESS read-only
    STATUS     current
    DESCRIPTION
        "-- empty --"
    ::= { lcsStatusChargingTimeTableEntry 5 }

-- {SCALAR} 1712.1.24.3
lcsStatusChargingDeleteValues OBJECT-TYPE
    SYNTAX     DisplayString
    MAX-ACCESS read-write
    STATUS     current
    DESCRIPTION
        "-- empty --"
    ::= { lcsStatusCharging 3 }

-- {OID} 1712.1.26
lcsStatusVpn OBJECT IDENTIFIER ::= { lcsStatus 26 }

-- {SCALAR} 1712.1.26.1
lcsStatusVpnPeers OBJECT-TYPE
    SYNTAX     INTEGER (0..2147483647)
    MAX-ACCESS read-only
    STATUS     current
    DESCRIPTION
        "-- empty --"
    ::= { lcsStatusVpn 1 }

-- {SCALAR} 1712.1.26.2
lcsStatusVpnRules OBJECT-TYPE
    SYNTAX     INTEGER (0..2147483647)
    MAX-ACCESS read-only
    STATUS     current
    DESCRIPTION
        "-- empty --"
    ::= { lcsStatusVpn 2 }

-- {SCALAR} 1712.1.26.4
lcsStatusVpnTunnel OBJECT-TYPE
    SYNTAX     INTEGER (0..2147483647)
    MAX-ACCESS read-only
    STATUS     current
    DESCRIPTION
        "-- empty --"
    ::= { lcsStatusVpn 4 }

-- {SCALAR} 1712.1.26.5
lcsStatusVpnIkeSas OBJECT-TYPE
    SYNTAX     INTEGER (0..2147483647)
    MAX-ACCESS read-only
    STATUS     current
    DESCRIPTION
        "-- empty --"
    ::= { lcsStatusVpn 5 }

-- {SCALAR} 1712.1.26.6
lcsStatusVpnEspSas OBJECT-TYPE
    SYNTAX     INTEGER (0..2147483647)
    MAX-ACCESS read-only
    STATUS     current
    DESCRIPTION
        "-- empty --"
    ::= { lcsStatusVpn 6 }

-- {SCALAR} 1712.1.26.7
lcsStatusVpnAhSas OBJECT-TYPE
    SYNTAX     INTEGER (0..2147483647)
    MAX-ACCESS read-only
    STATUS     current
    DESCRIPTION
        "-- empty --"
    ::= { lcsStatusVpn 7 }

-- {SCALAR} 1712.1.26.13
lcsStatusVpnIpcompSas OBJECT-TYPE
    SYNTAX     INTEGER (0..2147483647)
    MAX-ACCESS read-only
    STATUS     current
    DESCRIPTION
        "-- empty --"
    ::= { lcsStatusVpn 13 }

-- {TABLE} 1712.1.26.8
lcsStatusVpnIkeTable OBJECT-TYPE
    SYNTAX     SEQUENCE OF LcsStatusVpnIkeEntry
    MAX-ACCESS not-accessible
    STATUS     current
    DESCRIPTION
        "-- empty --"
    ::= { lcsStatusVpn 8 }

-- {ENTRY} 1712.1.26.8.1
lcsStatusVpnIkeEntry OBJECT-TYPE
    SYNTAX     LcsStatusVpnIkeEntry
    MAX-ACCESS not-accessible
    STATUS     current
    DESCRIPTION
        ""
    INDEX {
        lcsStatusVpnIkeEntryIdx
    }
    ::= { lcsStatusVpnIkeTable 1 }

-- {SEQUENCE}
LcsStatusVpnIkeEntry ::= SEQUENCE {
    lcsStatusVpnIkeEntryIdx DisplayString,
    lcsStatusVpnIkeEntryPeer DisplayString,
    lcsStatusVpnIkeEntryDestAddressNew DisplayString,
    lcsStatusVpnIkeEntryDstPort INTEGER,
    lcsStatusVpnIkeEntrySrcAddressNew DisplayString,
    lcsStatusVpnIkeEntrySrcPort INTEGER,
    lcsStatusVpnIkeEntryCryptAlg DisplayString,
    lcsStatusVpnIkeEntryHashAlg DisplayString,
    lcsStatusVpnIkeEntryIkeAuthMode INTEGER,
    lcsStatusVpnIkeEntryInitiator DisplayString,
    lcsStatusVpnIkeEntryAge INTEGER,
    lcsStatusVpnIkeEntrySoftSec INTEGER,
    lcsStatusVpnIkeEntryMaxSec INTEGER,
    lcsStatusVpnIkeEntryKbyte INTEGER,
    lcsStatusVpnIkeEntrySoftKbyte INTEGER,
    lcsStatusVpnIkeEntryMaxKbyte INTEGER
}

-- {COLUMN} 1712.1.26.8.1.1
lcsStatusVpnIkeEntryIdx OBJECT-TYPE
    SYNTAX     DisplayString (SIZE(0..255))
    MAX-ACCESS read-only
    STATUS     current
    DESCRIPTION
        "-- empty --"
    ::= { lcsStatusVpnIkeEntry 1 }

-- {COLUMN} 1712.1.26.8.1.2
lcsStatusVpnIkeEntryPeer OBJECT-TYPE
    SYNTAX     DisplayString (SIZE(0..15))
    MAX-ACCESS read-only
    STATUS     current
    DESCRIPTION
        "-- empty --"
    ::= { lcsStatusVpnIkeEntry 2 }

-- {COLUMN} 1712.1.26.8.1.18
lcsStatusVpnIkeEntryDestAddressNew OBJECT-TYPE
    SYNTAX     DisplayString (SIZE(0..39))
    MAX-ACCESS read-only
    STATUS     current
    DESCRIPTION
        ""
    ::= { lcsStatusVpnIkeEntry 18 }

-- {COLUMN} 1712.1.26.8.1.16
lcsStatusVpnIkeEntryDstPort OBJECT-TYPE
    SYNTAX     INTEGER (0..65535)
    MAX-ACCESS read-only
    STATUS     current
    DESCRIPTION
        "-- empty --"
    ::= { lcsStatusVpnIkeEntry 16 }

-- {COLUMN} 1712.1.26.8.1.19
lcsStatusVpnIkeEntrySrcAddressNew OBJECT-TYPE
    SYNTAX     DisplayString (SIZE(0..39))
    MAX-ACCESS read-only
    STATUS     current
    DESCRIPTION
        ""
    ::= { lcsStatusVpnIkeEntry 19 }

-- {COLUMN} 1712.1.26.8.1.17
lcsStatusVpnIkeEntrySrcPort OBJECT-TYPE
    SYNTAX     INTEGER (0..65535)
    MAX-ACCESS read-only
    STATUS     current
    DESCRIPTION
        "-- empty --"
    ::= { lcsStatusVpnIkeEntry 17 }

-- {COLUMN} 1712.1.26.8.1.5
lcsStatusVpnIkeEntryCryptAlg OBJECT-TYPE
    SYNTAX     DisplayString (SIZE(0..12))
    MAX-ACCESS read-only
    STATUS     current
    DESCRIPTION
        "-- empty --"
    ::= { lcsStatusVpnIkeEntry 5 }

-- {COLUMN} 1712.1.26.8.1.6
lcsStatusVpnIkeEntryHashAlg OBJECT-TYPE
    SYNTAX     DisplayString (SIZE(0..12))
    MAX-ACCESS read-only
    STATUS     current
    DESCRIPTION
        "-- empty --"
    ::= { lcsStatusVpnIkeEntry 6 }

-- {COLUMN} 1712.1.26.8.1.15
lcsStatusVpnIkeEntryIkeAuthMode OBJECT-TYPE
    SYNTAX     INTEGER
      {
        eNo (0),
        ePreShared (1),
        eDss (2),
        eRsaSig (3),
        eRsaEnc (4),
        eRsaEncRev (5),
        eElGamalEnc (6),
        eElGamalEncRev (7),
        eEcdsaSig (8),
        ePreSharedInitXauth (65001),
        ePreSharedRespXauth (65002),
        eDssInitXauth (65003),
        eDssRespXauth (65004),
        eRsaInitXauth (65005),
        eRsaRespXauth (65006)
      }
    MAX-ACCESS read-only
    STATUS     current
    DESCRIPTION
        "-- empty --"
    ::= { lcsStatusVpnIkeEntry 15 }

-- {COLUMN} 1712.1.26.8.1.9
lcsStatusVpnIkeEntryInitiator OBJECT-TYPE
    SYNTAX     DisplayString (SIZE(0..3))
    MAX-ACCESS read-only
    STATUS     current
    DESCRIPTION
        "-- empty --"
    ::= { lcsStatusVpnIkeEntry 9 }

-- {COLUMN} 1712.1.26.8.1.8
lcsStatusVpnIkeEntryAge OBJECT-TYPE
    SYNTAX     INTEGER (0..2147483647)
    MAX-ACCESS read-only
    STATUS     current
    DESCRIPTION
        "-- empty --"
    ::= { lcsStatusVpnIkeEntry 8 }

-- {COLUMN} 1712.1.26.8.1.10
lcsStatusVpnIkeEntrySoftSec OBJECT-TYPE
    SYNTAX     INTEGER (0..2147483647)
    MAX-ACCESS read-only
    STATUS     current
    DESCRIPTION
        "-- empty --"
    ::= { lcsStatusVpnIkeEntry 10 }

-- {COLUMN} 1712.1.26.8.1.11
lcsStatusVpnIkeEntryMaxSec OBJECT-TYPE
    SYNTAX     INTEGER (0..2147483647)
    MAX-ACCESS read-only
    STATUS     current
    DESCRIPTION
        "-- empty --"
    ::= { lcsStatusVpnIkeEntry 11 }

-- {COLUMN} 1712.1.26.8.1.12
lcsStatusVpnIkeEntryKbyte OBJECT-TYPE
    SYNTAX     INTEGER (0..2147483647)
    MAX-ACCESS read-only
    STATUS     current
    DESCRIPTION
        "-- empty --"
    ::= { lcsStatusVpnIkeEntry 12 }

-- {COLUMN} 1712.1.26.8.1.13
lcsStatusVpnIkeEntrySoftKbyte OBJECT-TYPE
    SYNTAX     INTEGER (0..2147483647)
    MAX-ACCESS read-only
    STATUS     current
    DESCRIPTION
        "-- empty --"
    ::= { lcsStatusVpnIkeEntry 13 }

-- {COLUMN} 1712.1.26.8.1.14
lcsStatusVpnIkeEntryMaxKbyte OBJECT-TYPE
    SYNTAX     INTEGER (0..2147483647)
    MAX-ACCESS read-only
    STATUS     current
    DESCRIPTION
        "-- empty --"
    ::= { lcsStatusVpnIkeEntry 14 }

-- {TABLE} 1712.1.26.9
lcsStatusVpnEspTable OBJECT-TYPE
    SYNTAX     SEQUENCE OF LcsStatusVpnEspEntry
    MAX-ACCESS not-accessible
    STATUS     current
    DESCRIPTION
        "-- empty --"
    ::= { lcsStatusVpn 9 }

-- {ENTRY} 1712.1.26.9.1
lcsStatusVpnEspEntry OBJECT-TYPE
    SYNTAX     LcsStatusVpnEspEntry
    MAX-ACCESS not-accessible
    STATUS     current
    DESCRIPTION
        ""
    INDEX {
        lcsStatusVpnEspEntryIdx
    }
    ::= { lcsStatusVpnEspTable 1 }

-- {SEQUENCE}
LcsStatusVpnEspEntry ::= SEQUENCE {
    lcsStatusVpnEspEntryIdx DisplayString,
    lcsStatusVpnEspEntryPeer DisplayString,
    lcsStatusVpnEspEntryDestAddressNew DisplayString,
    lcsStatusVpnEspEntrySrcAddressNew DisplayString,
    lcsStatusVpnEspEntryMode DisplayString,
    lcsStatusVpnEspEntryCryptAlg DisplayString,
    lcsStatusVpnEspEntryHashAlg DisplayString,
    lcsStatusVpnEspEntrySpi DisplayString,
    lcsStatusVpnEspEntryAge INTEGER,
    lcsStatusVpnEspEntrySoftSec INTEGER,
    lcsStatusVpnEspEntryMaxSec INTEGER,
    lcsStatusVpnEspEntryKbyte INTEGER,
    lcsStatusVpnEspEntrySoftKbyte INTEGER,
    lcsStatusVpnEspEntryMaxKbyte INTEGER
}

-- {COLUMN} 1712.1.26.9.1.1
lcsStatusVpnEspEntryIdx OBJECT-TYPE
    SYNTAX     DisplayString (SIZE(0..255))
    MAX-ACCESS read-only
    STATUS     current
    DESCRIPTION
        "-- empty --"
    ::= { lcsStatusVpnEspEntry 1 }

-- {COLUMN} 1712.1.26.9.1.2
lcsStatusVpnEspEntryPeer OBJECT-TYPE
    SYNTAX     DisplayString (SIZE(0..15))
    MAX-ACCESS read-only
    STATUS     current
    DESCRIPTION
        "-- empty --"
    ::= { lcsStatusVpnEspEntry 2 }

-- {COLUMN} 1712.1.26.9.1.16
lcsStatusVpnEspEntryDestAddressNew OBJECT-TYPE
    SYNTAX     DisplayString (SIZE(0..39))
    MAX-ACCESS read-only
    STATUS     current
    DESCRIPTION
        ""
    ::= { lcsStatusVpnEspEntry 16 }

-- {COLUMN} 1712.1.26.9.1.17
lcsStatusVpnEspEntrySrcAddressNew OBJECT-TYPE
    SYNTAX     DisplayString (SIZE(0..39))
    MAX-ACCESS read-only
    STATUS     current
    DESCRIPTION
        ""
    ::= { lcsStatusVpnEspEntry 17 }

-- {COLUMN} 1712.1.26.9.1.5
lcsStatusVpnEspEntryMode OBJECT-TYPE
    SYNTAX     DisplayString (SIZE(0..2))
    MAX-ACCESS read-only
    STATUS     current
    DESCRIPTION
        "-- empty --"
    ::= { lcsStatusVpnEspEntry 5 }

-- {COLUMN} 1712.1.26.9.1.6
lcsStatusVpnEspEntryCryptAlg OBJECT-TYPE
    SYNTAX     DisplayString (SIZE(0..12))
    MAX-ACCESS read-only
    STATUS     current
    DESCRIPTION
        "-- empty --"
    ::= { lcsStatusVpnEspEntry 6 }

-- {COLUMN} 1712.1.26.9.1.7
lcsStatusVpnEspEntryHashAlg OBJECT-TYPE
    SYNTAX     DisplayString (SIZE(0..12))
    MAX-ACCESS read-only
    STATUS     current
    DESCRIPTION
        "-- empty --"
    ::= { lcsStatusVpnEspEntry 7 }

-- {COLUMN} 1712.1.26.9.1.9
lcsStatusVpnEspEntrySpi OBJECT-TYPE
    SYNTAX     DisplayString (SIZE(0..15))
    MAX-ACCESS read-only
    STATUS     current
    DESCRIPTION
        "-- empty --"
    ::= { lcsStatusVpnEspEntry 9 }

-- {COLUMN} 1712.1.26.9.1.10
lcsStatusVpnEspEntryAge OBJECT-TYPE
    SYNTAX     INTEGER (0..2147483647)
    MAX-ACCESS read-only
    STATUS     current
    DESCRIPTION
        "-- empty --"
    ::= { lcsStatusVpnEspEntry 10 }

-- {COLUMN} 1712.1.26.9.1.11
lcsStatusVpnEspEntrySoftSec OBJECT-TYPE
    SYNTAX     INTEGER (0..2147483647)
    MAX-ACCESS read-only
    STATUS     current
    DESCRIPTION
        "-- empty --"
    ::= { lcsStatusVpnEspEntry 11 }

-- {COLUMN} 1712.1.26.9.1.12
lcsStatusVpnEspEntryMaxSec OBJECT-TYPE
    SYNTAX     INTEGER (0..2147483647)
    MAX-ACCESS read-only
    STATUS     current
    DESCRIPTION
        "-- empty --"
    ::= { lcsStatusVpnEspEntry 12 }

-- {COLUMN} 1712.1.26.9.1.13
lcsStatusVpnEspEntryKbyte OBJECT-TYPE
    SYNTAX     INTEGER (0..2147483647)
    MAX-ACCESS read-only
    STATUS     current
    DESCRIPTION
        "-- empty --"
    ::= { lcsStatusVpnEspEntry 13 }

-- {COLUMN} 1712.1.26.9.1.14
lcsStatusVpnEspEntrySoftKbyte OBJECT-TYPE
    SYNTAX     INTEGER (0..2147483647)
    MAX-ACCESS read-only
    STATUS     current
    DESCRIPTION
        "-- empty --"
    ::= { lcsStatusVpnEspEntry 14 }

-- {COLUMN} 1712.1.26.9.1.15
lcsStatusVpnEspEntryMaxKbyte OBJECT-TYPE
    SYNTAX     INTEGER (0..2147483647)
    MAX-ACCESS read-only
    STATUS     current
    DESCRIPTION
        "-- empty --"
    ::= { lcsStatusVpnEspEntry 15 }

-- {TABLE} 1712.1.26.10
lcsStatusVpnAhTable OBJECT-TYPE
    SYNTAX     SEQUENCE OF LcsStatusVpnAhEntry
    MAX-ACCESS not-accessible
    STATUS     current
    DESCRIPTION
        "-- empty --"
    ::= { lcsStatusVpn 10 }

-- {ENTRY} 1712.1.26.10.1
lcsStatusVpnAhEntry OBJECT-TYPE
    SYNTAX     LcsStatusVpnAhEntry
    MAX-ACCESS not-accessible
    STATUS     current
    DESCRIPTION
        ""
    INDEX {
        lcsStatusVpnAhEntryIdx
    }
    ::= { lcsStatusVpnAhTable 1 }

-- {SEQUENCE}
LcsStatusVpnAhEntry ::= SEQUENCE {
    lcsStatusVpnAhEntryIdx DisplayString,
    lcsStatusVpnAhEntryPeer DisplayString,
    lcsStatusVpnAhEntryDestAddressNew DisplayString,
    lcsStatusVpnAhEntrySrcAddressNew DisplayString,
    lcsStatusVpnAhEntryMode DisplayString,
    lcsStatusVpnAhEntryCryptAlg DisplayString,
    lcsStatusVpnAhEntryHashAlg DisplayString,
    lcsStatusVpnAhEntrySpi DisplayString,
    lcsStatusVpnAhEntryAge INTEGER,
    lcsStatusVpnAhEntrySoftSec INTEGER,
    lcsStatusVpnAhEntryMaxSec INTEGER,
    lcsStatusVpnAhEntryKbyte INTEGER,
    lcsStatusVpnAhEntrySoftKbyte INTEGER,
    lcsStatusVpnAhEntryMaxKbyte INTEGER
}

-- {COLUMN} 1712.1.26.10.1.1
lcsStatusVpnAhEntryIdx OBJECT-TYPE
    SYNTAX     DisplayString (SIZE(0..255))
    MAX-ACCESS read-only
    STATUS     current
    DESCRIPTION
        "-- empty --"
    ::= { lcsStatusVpnAhEntry 1 }

-- {COLUMN} 1712.1.26.10.1.2
lcsStatusVpnAhEntryPeer OBJECT-TYPE
    SYNTAX     DisplayString (SIZE(0..15))
    MAX-ACCESS read-only
    STATUS     current
    DESCRIPTION
        "-- empty --"
    ::= { lcsStatusVpnAhEntry 2 }

-- {COLUMN} 1712.1.26.10.1.16
lcsStatusVpnAhEntryDestAddressNew OBJECT-TYPE
    SYNTAX     DisplayString (SIZE(0..39))
    MAX-ACCESS read-only
    STATUS     current
    DESCRIPTION
        ""
    ::= { lcsStatusVpnAhEntry 16 }

-- {COLUMN} 1712.1.26.10.1.17
lcsStatusVpnAhEntrySrcAddressNew OBJECT-TYPE
    SYNTAX     DisplayString (SIZE(0..39))
    MAX-ACCESS read-only
    STATUS     current
    DESCRIPTION
        ""
    ::= { lcsStatusVpnAhEntry 17 }

-- {COLUMN} 1712.1.26.10.1.5
lcsStatusVpnAhEntryMode OBJECT-TYPE
    SYNTAX     DisplayString (SIZE(0..2))
    MAX-ACCESS read-only
    STATUS     current
    DESCRIPTION
        "-- empty --"
    ::= { lcsStatusVpnAhEntry 5 }

-- {COLUMN} 1712.1.26.10.1.6
lcsStatusVpnAhEntryCryptAlg OBJECT-TYPE
    SYNTAX     DisplayString (SIZE(0..12))
    MAX-ACCESS read-only
    STATUS     current
    DESCRIPTION
        "-- empty --"
    ::= { lcsStatusVpnAhEntry 6 }

-- {COLUMN} 1712.1.26.10.1.7
lcsStatusVpnAhEntryHashAlg OBJECT-TYPE
    SYNTAX     DisplayString (SIZE(0..12))
    MAX-ACCESS read-only
    STATUS     current
    DESCRIPTION
        "-- empty --"
    ::= { lcsStatusVpnAhEntry 7 }

-- {COLUMN} 1712.1.26.10.1.9
lcsStatusVpnAhEntrySpi OBJECT-TYPE
    SYNTAX     DisplayString (SIZE(0..15))
    MAX-ACCESS read-only
    STATUS     current
    DESCRIPTION
        "-- empty --"
    ::= { lcsStatusVpnAhEntry 9 }

-- {COLUMN} 1712.1.26.10.1.10
lcsStatusVpnAhEntryAge OBJECT-TYPE
    SYNTAX     INTEGER (0..2147483647)
    MAX-ACCESS read-only
    STATUS     current
    DESCRIPTION
        "-- empty --"
    ::= { lcsStatusVpnAhEntry 10 }

-- {COLUMN} 1712.1.26.10.1.11
lcsStatusVpnAhEntrySoftSec OBJECT-TYPE
    SYNTAX     INTEGER (0..2147483647)
    MAX-ACCESS read-only
    STATUS     current
    DESCRIPTION
        "-- empty --"
    ::= { lcsStatusVpnAhEntry 11 }

-- {COLUMN} 1712.1.26.10.1.12
lcsStatusVpnAhEntryMaxSec OBJECT-TYPE
    SYNTAX     INTEGER (0..2147483647)
    MAX-ACCESS read-only
    STATUS     current
    DESCRIPTION
        "-- empty --"
    ::= { lcsStatusVpnAhEntry 12 }

-- {COLUMN} 1712.1.26.10.1.13
lcsStatusVpnAhEntryKbyte OBJECT-TYPE
    SYNTAX     INTEGER (0..2147483647)
    MAX-ACCESS read-only
    STATUS     current
    DESCRIPTION
        "-- empty --"
    ::= { lcsStatusVpnAhEntry 13 }

-- {COLUMN} 1712.1.26.10.1.14
lcsStatusVpnAhEntrySoftKbyte OBJECT-TYPE
    SYNTAX     INTEGER (0..2147483647)
    MAX-ACCESS read-only
    STATUS     current
    DESCRIPTION
        "-- empty --"
    ::= { lcsStatusVpnAhEntry 14 }

-- {COLUMN} 1712.1.26.10.1.15
lcsStatusVpnAhEntryMaxKbyte OBJECT-TYPE
    SYNTAX     INTEGER (0..2147483647)
    MAX-ACCESS read-only
    STATUS     current
    DESCRIPTION
        "-- empty --"
    ::= { lcsStatusVpnAhEntry 15 }

-- {TABLE} 1712.1.26.14
lcsStatusVpnIpcompTable OBJECT-TYPE
    SYNTAX     SEQUENCE OF LcsStatusVpnIpcompEntry
    MAX-ACCESS not-accessible
    STATUS     current
    DESCRIPTION
        "-- empty --"
    ::= { lcsStatusVpn 14 }

-- {ENTRY} 1712.1.26.14.1
lcsStatusVpnIpcompEntry OBJECT-TYPE
    SYNTAX     LcsStatusVpnIpcompEntry
    MAX-ACCESS not-accessible
    STATUS     current
    DESCRIPTION
        ""
    INDEX {
        lcsStatusVpnIpcompEntryIdx
    }
    ::= { lcsStatusVpnIpcompTable 1 }

-- {SEQUENCE}
LcsStatusVpnIpcompEntry ::= SEQUENCE {
    lcsStatusVpnIpcompEntryIdx DisplayString,
    lcsStatusVpnIpcompEntryPeer DisplayString,
    lcsStatusVpnIpcompEntryDestAddressNew DisplayString,
    lcsStatusVpnIpcompEntrySrcAddressNew DisplayString,
    lcsStatusVpnIpcompEntryMode DisplayString,
    lcsStatusVpnIpcompEntryCryptAlg DisplayString,
    lcsStatusVpnIpcompEntryHashAlg DisplayString,
    lcsStatusVpnIpcompEntrySpi DisplayString,
    lcsStatusVpnIpcompEntryAge INTEGER,
    lcsStatusVpnIpcompEntrySoftSec INTEGER,
    lcsStatusVpnIpcompEntryMaxSec INTEGER,
    lcsStatusVpnIpcompEntryKbyte INTEGER,
    lcsStatusVpnIpcompEntrySoftKbyte INTEGER,
    lcsStatusVpnIpcompEntryMaxKbyte INTEGER
}

-- {COLUMN} 1712.1.26.14.1.1
lcsStatusVpnIpcompEntryIdx OBJECT-TYPE
    SYNTAX     DisplayString (SIZE(0..255))
    MAX-ACCESS read-only
    STATUS     current
    DESCRIPTION
        "-- empty --"
    ::= { lcsStatusVpnIpcompEntry 1 }

-- {COLUMN} 1712.1.26.14.1.2
lcsStatusVpnIpcompEntryPeer OBJECT-TYPE
    SYNTAX     DisplayString (SIZE(0..15))
    MAX-ACCESS read-only
    STATUS     current
    DESCRIPTION
        "-- empty --"
    ::= { lcsStatusVpnIpcompEntry 2 }

-- {COLUMN} 1712.1.26.14.1.16
lcsStatusVpnIpcompEntryDestAddressNew OBJECT-TYPE
    SYNTAX     DisplayString (SIZE(0..39))
    MAX-ACCESS read-only
    STATUS     current
    DESCRIPTION
        ""
    ::= { lcsStatusVpnIpcompEntry 16 }

-- {COLUMN} 1712.1.26.14.1.17
lcsStatusVpnIpcompEntrySrcAddressNew OBJECT-TYPE
    SYNTAX     DisplayString (SIZE(0..39))
    MAX-ACCESS read-only
    STATUS     current
    DESCRIPTION
        ""
    ::= { lcsStatusVpnIpcompEntry 17 }

-- {COLUMN} 1712.1.26.14.1.5
lcsStatusVpnIpcompEntryMode OBJECT-TYPE
    SYNTAX     DisplayString (SIZE(0..2))
    MAX-ACCESS read-only
    STATUS     current
    DESCRIPTION
        "-- empty --"
    ::= { lcsStatusVpnIpcompEntry 5 }

-- {COLUMN} 1712.1.26.14.1.6
lcsStatusVpnIpcompEntryCryptAlg OBJECT-TYPE
    SYNTAX     DisplayString (SIZE(0..12))
    MAX-ACCESS read-only
    STATUS     current
    DESCRIPTION
        "-- empty --"
    ::= { lcsStatusVpnIpcompEntry 6 }

-- {COLUMN} 1712.1.26.14.1.7
lcsStatusVpnIpcompEntryHashAlg OBJECT-TYPE
    SYNTAX     DisplayString (SIZE(0..12))
    MAX-ACCESS read-only
    STATUS     current
    DESCRIPTION
        "-- empty --"
    ::= { lcsStatusVpnIpcompEntry 7 }

-- {COLUMN} 1712.1.26.14.1.9
lcsStatusVpnIpcompEntrySpi OBJECT-TYPE
    SYNTAX     DisplayString (SIZE(0..15))
    MAX-ACCESS read-only
    STATUS     current
    DESCRIPTION
        "-- empty --"
    ::= { lcsStatusVpnIpcompEntry 9 }

-- {COLUMN} 1712.1.26.14.1.10
lcsStatusVpnIpcompEntryAge OBJECT-TYPE
    SYNTAX     INTEGER (0..2147483647)
    MAX-ACCESS read-only
    STATUS     current
    DESCRIPTION
        "-- empty --"
    ::= { lcsStatusVpnIpcompEntry 10 }

-- {COLUMN} 1712.1.26.14.1.11
lcsStatusVpnIpcompEntrySoftSec OBJECT-TYPE
    SYNTAX     INTEGER (0..2147483647)
    MAX-ACCESS read-only
    STATUS     current
    DESCRIPTION
        "-- empty --"
    ::= { lcsStatusVpnIpcompEntry 11 }

-- {COLUMN} 1712.1.26.14.1.12
lcsStatusVpnIpcompEntryMaxSec OBJECT-TYPE
    SYNTAX     INTEGER (0..2147483647)
    MAX-ACCESS read-only
    STATUS     current
    DESCRIPTION
        "-- empty --"
    ::= { lcsStatusVpnIpcompEntry 12 }

-- {COLUMN} 1712.1.26.14.1.13
lcsStatusVpnIpcompEntryKbyte OBJECT-TYPE
    SYNTAX     INTEGER (0..2147483647)
    MAX-ACCESS read-only
    STATUS     current
    DESCRIPTION
        "-- empty --"
    ::= { lcsStatusVpnIpcompEntry 13 }

-- {COLUMN} 1712.1.26.14.1.14
lcsStatusVpnIpcompEntrySoftKbyte OBJECT-TYPE
    SYNTAX     INTEGER (0..2147483647)
    MAX-ACCESS read-only
    STATUS     current
    DESCRIPTION
        "-- empty --"
    ::= { lcsStatusVpnIpcompEntry 14 }

-- {COLUMN} 1712.1.26.14.1.15
lcsStatusVpnIpcompEntryMaxKbyte OBJECT-TYPE
    SYNTAX     INTEGER (0..2147483647)
    MAX-ACCESS read-only
    STATUS     current
    DESCRIPTION
        "-- empty --"
    ::= { lcsStatusVpnIpcompEntry 15 }

-- {TABLE} 1712.1.26.17
lcsStatusVpnConnectionsTable OBJECT-TYPE
    SYNTAX     SEQUENCE OF LcsStatusVpnConnectionsEntry
    MAX-ACCESS not-accessible
    STATUS     current
    DESCRIPTION
        "-- empty --"
    ::= { lcsStatusVpn 17 }

-- {ENTRY} 1712.1.26.17.1
lcsStatusVpnConnectionsEntry OBJECT-TYPE
    SYNTAX     LcsStatusVpnConnectionsEntry
    MAX-ACCESS not-accessible
    STATUS     current
    DESCRIPTION
        ""
    INDEX {
        lcsStatusVpnConnectionsEntryPeer
    }
    ::= { lcsStatusVpnConnectionsTable 1 }

-- {SEQUENCE}
LcsStatusVpnConnectionsEntry ::= SEQUENCE {
    lcsStatusVpnConnectionsEntryPeer DisplayString,
    lcsStatusVpnConnectionsEntryState INTEGER,
    lcsStatusVpnConnectionsEntryLastError INTEGER,
    lcsStatusVpnConnectionsEntryMode INTEGER,
    lcsStatusVpnConnectionsEntryShTime INTEGER,
    lcsStatusVpnConnectionsEntryPhysConn DisplayString,
    lcsStatusVpnConnectionsEntryB1Dt INTEGER,
    lcsStatusVpnConnectionsEntryRemoteGwNew DisplayString,
    lcsStatusVpnConnectionsEntryNatDetection INTEGER,
    lcsStatusVpnConnectionsEntrySslEncaps INTEGER,
    lcsStatusVpnConnectionsEntryCryptAlg DisplayString,
    lcsStatusVpnConnectionsEntryCryptLength INTEGER,
    lcsStatusVpnConnectionsEntryHashAlg DisplayString,
    lcsStatusVpnConnectionsEntryHashLength INTEGER,
    lcsStatusVpnConnectionsEntryHmacAlg DisplayString,
    lcsStatusVpnConnectionsEntryHmacLength INTEGER,
    lcsStatusVpnConnectionsEntryComprAlg DisplayString,
    lcsStatusVpnConnectionsEntryClientSn INTEGER,
    lcsStatusVpnConnectionsEntryConnTime Gauge32
}

-- {COLUMN} 1712.1.26.17.1.1
lcsStatusVpnConnectionsEntryPeer OBJECT-TYPE
    SYNTAX     DisplayString (SIZE(0..16))
    MAX-ACCESS read-only
    STATUS     current
    DESCRIPTION
        "-- empty --"
    ::= { lcsStatusVpnConnectionsEntry 1 }

-- {COLUMN} 1712.1.26.17.1.11
lcsStatusVpnConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusVpnConnectionsEntry 11 }

-- {COLUMN} 1712.1.26.17.1.16
lcsStatusVpnConnectionsEntryLastError OBJECT-TYPE
    SYNTAX     INTEGER
      {
        eNone (0),
        eIcmpConnError (275),
        eIfcILicenseExceeded (4353),
        eIfcRLicenseExceeded (4609),
        eIfcINoChannelAvailable (4354),
        eIfcRNoChannelAvailable (4610),
        eIfcINoRouteToRemoteGateway (4355),
        eIfcRNoRouteToRemoteGateway (4611),
        eIfcINoPppTableEntryMatched (4356),
        eIfcRNoPppTableEntryMatched (4612),
        eIfcIConnectionTimeoutDynamic (4357),
        eIfcRConnectionTimeoutDynamic (4613),
        eIfcIConnectionTimeoutIkeIpsec (4358),
        eIfcRConnectionTimeoutIkeIpsec (4614),
        eIfcXLinePollingFailed (4871),
        eIfcINoPollTableEntryMatched (4360),
        eIfcINameResolutionFailed (4361),
        eIfcINegotiatorChargeLocked (4369),
        eIfcINegotiatorTimeLocked (4370),
        eIfcINegotiatorNoDialNumber (4371),
        eIfcINegotiatorNoRemote (4372),
        eIfcINegotiatorRemoteBlocked (4373),
        eIfcINegotiatorNoMulticonnect (4374),
        eIfcINegotiatorLineError (4375),
        eIfcIPhysicalChargeLocked (4385),
        eIfcIPhysicalTimeLocked (4386),
        eIfcIPhysicalNoDialNumber (4387),
        eIfcIPhysicalNoRemote (4388),
        eIfcIPhysicalNoServerAddress (4389),
        eIfcIPhysicalRemoteLocked (4390),
        eIfcIPhysicalNoMulticonnect (4391),
        eIfcXPhysicalLineError (4904),
        eIkeRLicenseExceeded (8705),
        eIkeRExchangeTypeMismatch (8706),
        eIkeINoProposalMatched (8451),
        eIkeRNoProposalMatched (8707),
        eIkeRIkeGroupMismatch (8708),
        eIkeRLifeTypeUnsupported (8709),
        eIkeRLifeDurationMismatch (8710),
        eIkeRIdTypeUnsupported (8711),
        eIkeRIdTypeMismatch (8712),
        eIkeRNoRuleMatchedId (8713),
        eIkeIIkeKeyMismatch (8458),
        eIkeRIkeKeyMismatch (8714),
        eIkeRLicenseDemosnExceeded (8715),
        eIkeRLicenseSnExceeded (8716),
        eIkeIDpdTimeout (8461),
        eIkeRDpdTimeout (8717),
        eIkeIUnableToGetIssuerCert (8462),
        eIkeRUnableToGetIssuerCert (8718),
        eIkeIUnableToGetCrl (8463),
        eIkeRUnableToGetCrl (8719),
        eIkeIUnableToDecryptCertSignature (8464),
        eIkeRUnableToDecryptCertSignature (8720),
        eIkeIUnableToDecryptCrlSignature (8465),
        eIkeRUnableToDecryptCrlSignature (8721),
        eIkeIUnableToDecodeIssuerPublicKey (8466),
        eIkeRUnableToDecodeIssuerPublicKey (8722),
        eIkeICertSignatureFailure (8467),
        eIkeRCertSignatureFailure (8723),
        eIkeICrlSignatureFailure (8468),
        eIkeRCrlSignatureFailure (8724),
        eIkeICertNotYetValid (8469),
        eIkeRCertNotYetValid (8725),
        eIkeICertHasExpired (8470),
        eIkeRCertHasExpired (8726),
        eIkeICrlNotYetValid (8471),
        eIkeRCrlNotYetValid (8727),
        eIkeICrlHasExpired (8472),
        eIkeRCrlHasExpired (8728),
        eIkeIErrorInCertNotBeforeField (8473),
        eIkeRErrorInCertNotBeforeField (8729),
        eIkeIErrorInCertNotAfterField (8474),
        eIkeRErrorInCertNotAfterField (8730),
        eIkeIErrorInCrlLastUpdateField (8475),
        eIkeRErrorInCrlLastUpdateField (8731),
        eIkeIErrorInCrlNextUpdateField (8476),
        eIkeRErrorInCrlNextUpdateField (8732),
        eIkeIOutOfMem (8477),
        eIkeROutOfMem (8733),
        eIkeIDepthZeroSelfSignedCert (8478),
        eIkeRDepthZeroSelfSignedCert (8734),
        eIkeISelfSignedCertInChain (8479),
        eIkeRSelfSignedCertInChain (8735),
        eIkeIUnableToGetIssuerCertLocally (8480),
        eIkeRUnableToGetIssuerCertLocally (8736),
        eIkeIUnableToVerifyLeafSignature (8481),
        eIkeRUnableToVerifyLeafSignature (8737),
        eIkeICertChainTooLong (8482),
        eIkeRCertChainTooLong (8738),
        eIkeICertRevoked (8483),
        eIkeRCertRevoked (8739),
        eIkeIInvalidCa (8484),
        eIkeRInvalidCa (8740),
        eIkeIPathLengthExceeded (8485),
        eIkeRPathLengthExceeded (8741),
        eIkeIInvalidPurpose (8486),
        eIkeRInvalidPurpose (8742),
        eIkeICertUntrusted (8487),
        eIkeRCertUntrusted (8743),
        eIkeICertRejected (8488),
        eIkeRCertRejected (8744),
        eIkeISubjectIssuerMismatch (8489),
        eIkeRSubjectIssuerMismatch (8745),
        eIkeIAkidSkidMismatch (8490),
        eIkeRAkidSkidMismatch (8746),
        eIkeIAkidIssuerSerialMismatch (8491),
        eIkeRAkidIssuerSerialMismatch (8747),
        eIkeIKeyusageNoCertsign (8492),
        eIkeRKeyusageNoCertsign (8748),
        eIkeIUnableToGetCrlIssuer (8493),
        eIkeRUnableToGetCrlIssuer (8749),
        eIkeIUnhandledCriticalExtension (8494),
        eIkeRUnhandledCriticalExtension (8750),
        eIkeIKeyusageNoCrlSign (8495),
        eIkeRKeyusageNoCrlSign (8751),
        eIkeIUnhandledCriticalCrlExtension (8496),
        eIkeRUnhandledCriticalCrlExtension (8752),
        eIkeICrlHasExceededExceedance (8497),
        eIkeRCrlHasExceededExceedance (8753),
        eIkeIApplicationVerification (8498),
        eIkeRApplicationVerification (8754),
        eIkeICertRevokedUnspecified (8499),
        eIkeRCertRevokedUnspecified (8755),
        eIkeICertRevokedKeyCompromise (8500),
        eIkeRCertRevokedKeyCompromise (8756),
        eIkeICertRevokedCaCompromise (8501),
        eIkeRCertRevokedCaCompromise (8757),
        eIkeICertRevokedAffiliationChanged (8502),
        eIkeRCertRevokedAffiliationChanged (8758),
        eIkeICertRevokedSuperseded (8503),
        eIkeRCertRevokedSuperseded (8759),
        eIkeICertRevokedCessationOfOperation (8504),
        eIkeRCertRevokedCessationOfOperation (8760),
        eIkeICertRevokedCertificateHold (8505),
        eIkeRCertRevokedCertificateHold (8761),
        eIkeICertRevokedRemoveFromCrl (8506),
        eIkeRCertRevokedRemoveFromCrl (8762),
        eIkeICertRevokedPrivilegeWithdrawn (8507),
        eIkeRCertRevokedPrivilegeWithdrawn (8763),
        eIkeICertRevokedAACompromise (8508),
        eIkeRCertRevokedAACompromise (8764),
        eIkeICertRevokedUnknownReason (8509),
        eIkeRCertRevokedUnknownReason (8765),
        eIkeRConnLimitReached (8784),
        eIkeIGeneralFailure (8703),
        eIkeRGeneralFailure (8959),
        eIkeIOutOfMemory (8702),
        eIkeROutOfMemory (8958),
        eIpsecRNoRuleMatchedIds (12801),
        eIpsecINoProposalMatched (12546),
        eIpsecRNoProposalMatched (12802),
        eIpsecRPfsGroupMismatch (12803),
        eRemoteDisconnected (17153),
        eManualDisconnect (17154),
        eShortholdExpired (17155),
        ePhysicalDisconnected (17156),
        eInvalidPhysicalChannel (17157),
        eDynamicVpnReconnect (17158),
        eConfigurationChanged (17159),
        eRemovedFromConfig (17160),
        eIfcIConnectionLimitReached (4393),
        eIfcRConnectionLimitReached (4649)
      }
    MAX-ACCESS read-write
    STATUS     current
    DESCRIPTION
        "-- empty --"
    ::= { lcsStatusVpnConnectionsEntry 16 }

-- {COLUMN} 1712.1.26.17.1.12
lcsStatusVpnConnectionsEntryMode OBJECT-TYPE
    SYNTAX     INTEGER
      {
        eActive (128),
        ePassive (0)
      }
    MAX-ACCESS read-only
    STATUS     current
    DESCRIPTION
        "-- empty --"
    ::= { lcsStatusVpnConnectionsEntry 12 }

-- {COLUMN} 1712.1.26.17.1.13
lcsStatusVpnConnectionsEntryShTime OBJECT-TYPE
    SYNTAX     INTEGER (0..65535)
    MAX-ACCESS read-only
    STATUS     current
    DESCRIPTION
        "-- empty --"
    ::= { lcsStatusVpnConnectionsEntry 13 }

-- {COLUMN} 1712.1.26.17.1.2
lcsStatusVpnConnectionsEntryPhysConn OBJECT-TYPE
    SYNTAX     DisplayString (SIZE(0..16))
    MAX-ACCESS read-only
    STATUS     current
    DESCRIPTION
        "-- empty --"
    ::= { lcsStatusVpnConnectionsEntry 2 }

-- {COLUMN} 1712.1.26.17.1.14
lcsStatusVpnConnectionsEntryB1Dt OBJECT-TYPE
    SYNTAX     INTEGER (0..65535)
    MAX-ACCESS read-only
    STATUS     current
    DESCRIPTION
        "-- empty --"
    ::= { lcsStatusVpnConnectionsEntry 14 }

-- {COLUMN} 1712.1.26.17.1.21
lcsStatusVpnConnectionsEntryRemoteGwNew OBJECT-TYPE
    SYNTAX     DisplayString (SIZE(0..39))
    MAX-ACCESS read-only
    STATUS     current
    DESCRIPTION
        ""
    ::= { lcsStatusVpnConnectionsEntry 21 }

-- {COLUMN} 1712.1.26.17.1.18
lcsStatusVpnConnectionsEntryNatDetection OBJECT-TYPE
    SYNTAX     INTEGER
      {
        eNoNat (0),
        eNatLocal (1),
        eNatRemote (2),
        eNatBoth (3)
      }
    MAX-ACCESS read-only
    STATUS     current
    DESCRIPTION
        "-- empty --"
    ::= { lcsStatusVpnConnectionsEntry 18 }

-- {COLUMN} 1712.1.26.17.1.20
lcsStatusVpnConnectionsEntrySslEncaps OBJECT-TYPE
    SYNTAX     INTEGER
      {
        eNo (0),
        eYes (1)
      }
    MAX-ACCESS read-only
    STATUS     current
    DESCRIPTION
        "-- empty --"
    ::= { lcsStatusVpnConnectionsEntry 20 }

-- {COLUMN} 1712.1.26.17.1.4
lcsStatusVpnConnectionsEntryCryptAlg OBJECT-TYPE
    SYNTAX     DisplayString (SIZE(0..14))
    MAX-ACCESS read-only
    STATUS     current
    DESCRIPTION
        "-- empty --"
    ::= { lcsStatusVpnConnectionsEntry 4 }

-- {COLUMN} 1712.1.26.17.1.5
lcsStatusVpnConnectionsEntryCryptLength OBJECT-TYPE
    SYNTAX     INTEGER (0..65535)
    MAX-ACCESS read-only
    STATUS     current
    DESCRIPTION
        "-- empty --"
    ::= { lcsStatusVpnConnectionsEntry 5 }

-- {COLUMN} 1712.1.26.17.1.6
lcsStatusVpnConnectionsEntryHashAlg OBJECT-TYPE
    SYNTAX     DisplayString (SIZE(0..14))
    MAX-ACCESS read-only
    STATUS     current
    DESCRIPTION
        "-- empty --"
    ::= { lcsStatusVpnConnectionsEntry 6 }

-- {COLUMN} 1712.1.26.17.1.7
lcsStatusVpnConnectionsEntryHashLength OBJECT-TYPE
    SYNTAX     INTEGER (0..65535)
    MAX-ACCESS read-only
    STATUS     current
    DESCRIPTION
        "-- empty --"
    ::= { lcsStatusVpnConnectionsEntry 7 }

-- {COLUMN} 1712.1.26.17.1.8
lcsStatusVpnConnectionsEntryHmacAlg OBJECT-TYPE
    SYNTAX     DisplayString (SIZE(0..14))
    MAX-ACCESS read-only
    STATUS     current
    DESCRIPTION
        "-- empty --"
    ::= { lcsStatusVpnConnectionsEntry 8 }

-- {COLUMN} 1712.1.26.17.1.9
lcsStatusVpnConnectionsEntryHmacLength OBJECT-TYPE
    SYNTAX     INTEGER (0..65535)
    MAX-ACCESS read-only
    STATUS     current
    DESCRIPTION
        "-- empty --"
    ::= { lcsStatusVpnConnectionsEntry 9 }

-- {COLUMN} 1712.1.26.17.1.10
lcsStatusVpnConnectionsEntryComprAlg OBJECT-TYPE
    SYNTAX     DisplayString (SIZE(0..14))
    MAX-ACCESS read-only
    STATUS     current
    DESCRIPTION
        "-- empty --"
    ::= { lcsStatusVpnConnectionsEntry 10 }

-- {COLUMN} 1712.1.26.17.1.17
lcsStatusVpnConnectionsEntryClientSn OBJECT-TYPE
    SYNTAX     INTEGER
      {
        eNotAvailable (-1),
        eDemoVersion (0)
      }
    MAX-ACCESS read-only
    STATUS     current
    DESCRIPTION
        "-- empty --"
    ::= { lcsStatusVpnConnectionsEntry 17 }

-- {COLUMN} 1712.1.26.17.1.19
lcsStatusVpnConnectionsEntryConnTime OBJECT-TYPE
    SYNTAX     Gauge32
    MAX-ACCESS read-only
    STATUS     current
    DESCRIPTION
        "-- empty --"
    ::= { lcsStatusVpnConnectionsEntry 19 }

-- {SCALAR} 1712.1.26.20
lcsStatusVpnRxPackets OBJECT-TYPE
    SYNTAX     Counter32
    MAX-ACCESS read-only
    STATUS     current
    DESCRIPTION
        "-- empty --"
    ::= { lcsStatusVpn 20 }

-- {SCALAR} 1712.1.26.21
lcsStatusVpnTxPackets OBJECT-TYPE
    SYNTAX     Counter32
    MAX-ACCESS read-only
    STATUS     current
    DESCRIPTION
        "-- empty --"
    ::= { lcsStatusVpn 21 }

-- {SCALAR} 1712.1.26.22
lcsStatusVpnTxDropped OBJECT-TYPE
    SYNTAX     Counter32
    MAX-ACCESS read-only
    STATUS     current
    DESCRIPTION
        "-- empty --"
    ::= { lcsStatusVpn 22 }

-- {SCALAR} 1712.1.26.23
lcsStatusVpnRxErrors OBJECT-TYPE
    SYNTAX     Counter32
    MAX-ACCESS read-only
    STATUS     current
    DESCRIPTION
        "-- empty --"
    ::= { lcsStatusVpn 23 }

-- {SCALAR} 1712.1.26.25
lcsStatusVpnTxInvalid OBJECT-TYPE
    SYNTAX     Counter64
    MAX-ACCESS read-only
    STATUS     current
    DESCRIPTION
        "-- empty --"
    ::= { lcsStatusVpn 25 }

-- {SCALAR} 1712.1.26.26
lcsStatusVpnTxNoSa OBJECT-TYPE
    SYNTAX     Counter64
    MAX-ACCESS read-only
    STATUS     current
    DESCRIPTION
        "-- empty --"
    ::= { lcsStatusVpn 26 }

-- {SCALAR} 1712.1.26.27
lcsStatusVpnTxNoPolicy OBJECT-TYPE
    SYNTAX     Counter64
    MAX-ACCESS read-only
    STATUS     current
    DESCRIPTION
        "-- empty --"
    ::= { lcsStatusVpn 27 }

-- {SCALAR} 1712.1.26.28
lcsStatusVpnRxEspAuthFail OBJECT-TYPE
    SYNTAX     Counter64
    MAX-ACCESS read-only
    STATUS     current
    DESCRIPTION
        "-- empty --"
    ::= { lcsStatusVpn 28 }

-- {SCALAR} 1712.1.26.29
lcsStatusVpnRxAhAuthFail OBJECT-TYPE
    SYNTAX     Counter64
    MAX-ACCESS read-only
    STATUS     current
    DESCRIPTION
        "-- empty --"
    ::= { lcsStatusVpn 29 }

-- {SCALAR} 1712.1.26.30
lcsStatusVpnRxIpcompFail OBJECT-TYPE
    SYNTAX     Counter64
    MAX-ACCESS read-only
    STATUS     current
    DESCRIPTION
        "-- empty --"
    ::= { lcsStatusVpn 30 }

-- {SCALAR} 1712.1.26.31
lcsStatusVpnRxEspReplay OBJECT-TYPE
    SYNTAX     Counter64
    MAX-ACCESS read-only
    STATUS     current
    DESCRIPTION
        "-- empty --"
    ::= { lcsStatusVpn 31 }

-- {SCALAR} 1712.1.26.32
lcsStatusVpnRxAhReplay OBJECT-TYPE
    SYNTAX     Counter64
    MAX-ACCESS read-only
    STATUS     current
    DESCRIPTION
        "-- empty --"
    ::= { lcsStatusVpn 32 }

-- {SCALAR} 1712.1.26.33
lcsStatusVpnRxBadSpi OBJECT-TYPE
    SYNTAX     Counter64
    MAX-ACCESS read-only
    STATUS     current
    DESCRIPTION
        "-- empty --"
    ::= { lcsStatusVpn 33 }

-- {SCALAR} 1712.1.26.34
lcsStatusVpnRxInvalid OBJECT-TYPE
    SYNTAX     Counter64
    MAX-ACCESS read-only
    STATUS     current
    DESCRIPTION
        "-- empty --"
    ::= { lcsStatusVpn 34 }

-- {SCALAR} 1712.1.26.35
lcsStatusVpnRxNoSa OBJECT-TYPE
    SYNTAX     Counter64
    MAX-ACCESS read-only
    STATUS     current
    DESCRIPTION
        "-- empty --"
    ::= { lcsStatusVpn 35 }

-- {SCALAR} 1712.1.26.36
lcsStatusVpnQueueError OBJECT-TYPE
    SYNTAX     Counter64
    MAX-ACCESS read-only
    STATUS     current
    DESCRIPTION
        "-- empty --"
    ::= { lcsStatusVpn 36 }

-- {SCALAR} 1712.1.26.12
lcsStatusVpnDeleteValues OBJECT-TYPE
    SYNTAX     DisplayString
    MAX-ACCESS read-write
    STATUS     current
    DESCRIPTION
        "-- empty --"
    ::= { lcsStatusVpn 12 }

-- {SCALAR} 1712.1.26.38
lcsStatusVpnDeleteConnErrors OBJECT-TYPE
    SYNTAX     DisplayString
    MAX-ACCESS read-write
    STATUS     current
    DESCRIPTION
        "-- empty --"
    ::= { lcsStatusVpn 38 }

-- {OID} 1712.1.26.37
lcsStatusVpnDhGroups OBJECT IDENTIFIER ::= { lcsStatusVpn 37 }

-- {TABLE} 1712.1.26.37.5
lcsStatusVpnDhGroupsPrecalculationTable OBJECT-TYPE
    SYNTAX     SEQUENCE OF LcsStatusVpnDhGroupsPrecalculationEntry
    MAX-ACCESS not-accessible
    STATUS     current
    DESCRIPTION
        "-- empty --"
    ::= { lcsStatusVpnDhGroups 5 }

-- {ENTRY} 1712.1.26.37.5.1
lcsStatusVpnDhGroupsPrecalculationEntry OBJECT-TYPE
    SYNTAX     LcsStatusVpnDhGroupsPrecalculationEntry
    MAX-ACCESS not-accessible
    STATUS     current
    DESCRIPTION
        ""
    INDEX {
        lcsStatusVpnDhGroupsPrecalculationEntryDhGroup
    }
    ::= { lcsStatusVpnDhGroupsPrecalculationTable 1 }

-- {SEQUENCE}
LcsStatusVpnDhGroupsPrecalculationEntry ::= SEQUENCE {
    lcsStatusVpnDhGroupsPrecalculationEntryDhGroup INTEGER,
    lcsStatusVpnDhGroupsPrecalculationEntryRuleDependentTarget INTEGER,
    lcsStatusVpnDhGroupsPrecalculationEntryConfiguredTarget INTEGER,
    lcsStatusVpnDhGroupsPrecalculationEntryActualTarget INTEGER,
    lcsStatusVpnDhGroupsPrecalculationEntryCurrentStock INTEGER
}

-- {COLUMN} 1712.1.26.37.5.1.1
lcsStatusVpnDhGroupsPrecalculationEntryDhGroup OBJECT-TYPE
    SYNTAX     INTEGER (0..2147483647)
    MAX-ACCESS read-only
    STATUS     current
    DESCRIPTION
        "-- empty --"
    ::= { lcsStatusVpnDhGroupsPrecalculationEntry 1 }

-- {COLUMN} 1712.1.26.37.5.1.2
lcsStatusVpnDhGroupsPrecalculationEntryRuleDependentTarget OBJECT-TYPE
    SYNTAX     INTEGER (0..2147483647)
    MAX-ACCESS read-only
    STATUS     current
    DESCRIPTION
        "-- empty --"
    ::= { lcsStatusVpnDhGroupsPrecalculationEntry 2 }

-- {COLUMN} 1712.1.26.37.5.1.3
lcsStatusVpnDhGroupsPrecalculationEntryConfiguredTarget OBJECT-TYPE
    SYNTAX     INTEGER (0..2147483647)
    MAX-ACCESS read-only
    STATUS     current
    DESCRIPTION
        "-- empty --"
    ::= { lcsStatusVpnDhGroupsPrecalculationEntry 3 }

-- {COLUMN} 1712.1.26.37.5.1.4
lcsStatusVpnDhGroupsPrecalculationEntryActualTarget OBJECT-TYPE
    SYNTAX     INTEGER (0..2147483647)
    MAX-ACCESS read-only
    STATUS     current
    DESCRIPTION
        "-- empty --"
    ::= { lcsStatusVpnDhGroupsPrecalculationEntry 4 }

-- {COLUMN} 1712.1.26.37.5.1.5
lcsStatusVpnDhGroupsPrecalculationEntryCurrentStock OBJECT-TYPE
    SYNTAX     INTEGER (0..2147483647)
    MAX-ACCESS read-only
    STATUS     current
    DESCRIPTION
        "-- empty --"
    ::= { lcsStatusVpnDhGroupsPrecalculationEntry 5 }

-- {OID} 1712.1.27
lcsStatusPptp OBJECT IDENTIFIER ::= { lcsStatus 27 }

-- {SCALAR} 1712.1.27.1
lcsStatusPptpRxPackets OBJECT-TYPE
    SYNTAX     Counter32
    MAX-ACCESS read-only
    STATUS     current
    DESCRIPTION
        "-- empty --"
    ::= { lcsStatusPptp 1 }

-- {SCALAR} 1712.1.27.2
lcsStatusPptpTxPackets OBJECT-TYPE
    SYNTAX     Counter32
    MAX-ACCESS read-only
    STATUS     current
    DESCRIPTION
        "-- empty --"
    ::= { lcsStatusPptp 2 }

-- {SCALAR} 1712.1.27.3
lcsStatusPptpEchoRetries OBJECT-TYPE
    SYNTAX     Counter32
    MAX-ACCESS read-only
    STATUS     current
    DESCRIPTION
        "-- empty --"
    ::= { lcsStatusPptp 3 }

-- {SCALAR} 1712.1.27.4
lcsStatusPptpAckTimeouts OBJECT-TYPE
    SYNTAX     Counter32
    MAX-ACCESS read-only
    STATUS     current
    DESCRIPTION
        "-- empty --"
    ::= { lcsStatusPptp 4 }

-- {SCALAR} 1712.1.27.5
lcsStatusPptpDroppedPackets OBJECT-TYPE
    SYNTAX     Counter32
    MAX-ACCESS read-only
    STATUS     current
    DESCRIPTION
        "-- empty --"
    ::= { lcsStatusPptp 5 }

-- {SCALAR} 1712.1.27.6
lcsStatusPptpRxErrors OBJECT-TYPE
    SYNTAX     Counter32
    MAX-ACCESS read-only
    STATUS     current
    DESCRIPTION
        "-- empty --"
    ::= { lcsStatusPptp 6 }

-- {SCALAR} 1712.1.27.7
lcsStatusPptpTcpErrors OBJECT-TYPE
    SYNTAX     Counter32
    MAX-ACCESS read-only
    STATUS     current
    DESCRIPTION
        "-- empty --"
    ::= { lcsStatusPptp 7 }

-- {SCALAR} 1712.1.27.8
lcsStatusPptpCallErrors OBJECT-TYPE
    SYNTAX     Counter32
    MAX-ACCESS read-only
    STATUS     current
    DESCRIPTION
        "-- empty --"
    ::= { lcsStatusPptp 8 }

-- {TABLE} 1712.1.27.9
lcsStatusPptpConnectionsTable OBJECT-TYPE
    SYNTAX     SEQUENCE OF LcsStatusPptpConnectionsEntry
    MAX-ACCESS not-accessible
    STATUS     current
    DESCRIPTION
        "-- empty --"
    ::= { lcsStatusPptp 9 }

-- {ENTRY} 1712.1.27.9.1
lcsStatusPptpConnectionsEntry OBJECT-TYPE
    SYNTAX     LcsStatusPptpConnectionsEntry
    MAX-ACCESS not-accessible
    STATUS     current
    DESCRIPTION
        ""
    INDEX {
        lcsStatusPptpConnectionsEntryChannel
    }
    ::= { lcsStatusPptpConnectionsTable 1 }

-- {SEQUENCE}
LcsStatusPptpConnectionsEntry ::= SEQUENCE {
    lcsStatusPptpConnectionsEntryChannel DisplayString,
    lcsStatusPptpConnectionsEntryState INTEGER,
    lcsStatusPptpConnectionsEntryLastError INTEGER,
    lcsStatusPptpConnectionsEntryMode INTEGER,
    lcsStatusPptpConnectionsEntryShTime INTEGER,
    lcsStatusPptpConnectionsEntryPhysConnection DisplayString,
    lcsStatusPptpConnectionsEntryPeerAddress IpAddress,
    lcsStatusPptpConnectionsEntryIpAddress IpAddress,
    lcsStatusPptpConnectionsEntryDnsDefault IpAddress,
    lcsStatusPptpConnectionsEntryDnsBackup IpAddress,
    lcsStatusPptpConnectionsEntryNbnsDefault IpAddress,
    lcsStatusPptpConnectionsEntryNbnsBackup IpAddress,
    lcsStatusPptpConnectionsEntryConnTime Gauge32,
    lcsStatusPptpConnectionsEntryGateway IpAddress,
    lcsStatusPptpConnectionsEntryEncryption INTEGER
}

-- {COLUMN} 1712.1.27.9.1.1
lcsStatusPptpConnectionsEntryChannel OBJECT-TYPE
    SYNTAX     DisplayString (SIZE(0..16))
    MAX-ACCESS read-only
    STATUS     current
    DESCRIPTION
        "-- empty --"
    ::= { lcsStatusPptpConnectionsEntry 1 }

-- {COLUMN} 1712.1.27.9.1.3
lcsStatusPptpConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusPptpConnectionsEntry 3 }

-- {COLUMN} 1712.1.27.9.1.11
lcsStatusPptpConnectionsEntryLastError OBJECT-TYPE
    SYNTAX     INTEGER
      {
        eNone (0),
        eRemoteDisconnected (17153),
        eManualDisconnect (17154),
        eShortholdExpired (17155),
        ePhysicalDisconnected (17156),
        eInvalidPhysicalChannel (17157),
        eDynamicVpnReconnect (17158),
        eConfigurationChanged (17159),
        eRemovedFromConfig (17160),
        eRemoteDoubled (267),
        eIcmpConnError (275),
        eDhcpTimeout (277),
        ePptpNoResponse (278),
        eVpnNoResponse (279),
        eArpNoResponse (280),
        ePptpNoChannel (513),
        ePptpBadFormat (514),
        ePptpBadValue (515),
        ePptpNoRessource (516),
        ePptpBadCallId (517),
        ePptpGenError (518),
        ePptpNoAddress (519),
        ePptpDnsResolvError (520),
        ePptpTcpConnError (521),
        eLcpRejected (32768),
        eAuthError (32769),
        eAuthRejected (32770),
        eLcpConnError (32771),
        ePapRejected (32784),
        ePapRxTimeout (32785),
        ePapTxTimeout (32786),
        eWrongPapReq (32787),
        ePapNakReceived (32788),
        eUnknPapPeer (32789),
        eChapRejected (32800),
        eChapRxTimeout (32801),
        eChapTxTimeout (32802),
        eWrongChapResp (32803),
        eChapFailRecvd (32804),
        eUnknChapPeer (32805),
        eIpcpRejected (32832),
        eCcpRejected (32848),
        eNoNcpAvailable (33008)
      }
    MAX-ACCESS read-write
    STATUS     current
    DESCRIPTION
        "-- empty --"
    ::= { lcsStatusPptpConnectionsEntry 11 }

-- {COLUMN} 1712.1.27.9.1.4
lcsStatusPptpConnectionsEntryMode OBJECT-TYPE
    SYNTAX     INTEGER
      {
        eActive (128),
        ePassive (0)
      }
    MAX-ACCESS read-only
    STATUS     current
    DESCRIPTION
        "-- empty --"
    ::= { lcsStatusPptpConnectionsEntry 4 }

-- {COLUMN} 1712.1.27.9.1.5
lcsStatusPptpConnectionsEntryShTime OBJECT-TYPE
    SYNTAX     INTEGER (0..65535)
    MAX-ACCESS read-only
    STATUS     current
    DESCRIPTION
        "-- empty --"
    ::= { lcsStatusPptpConnectionsEntry 5 }

-- {COLUMN} 1712.1.27.9.1.6
lcsStatusPptpConnectionsEntryPhysConnection OBJECT-TYPE
    SYNTAX     DisplayString (SIZE(0..16))
    MAX-ACCESS read-only
    STATUS     current
    DESCRIPTION
        "-- empty --"
    ::= { lcsStatusPptpConnectionsEntry 6 }

-- {COLUMN} 1712.1.27.9.1.7
lcsStatusPptpConnectionsEntryPeerAddress OBJECT-TYPE
    SYNTAX     IpAddress
    MAX-ACCESS read-only
    STATUS     current
    DESCRIPTION
        "-- empty --"
    ::= { lcsStatusPptpConnectionsEntry 7 }

-- {COLUMN} 1712.1.27.9.1.8
lcsStatusPptpConnectionsEntryIpAddress OBJECT-TYPE
    SYNTAX     IpAddress
    MAX-ACCESS read-only
    STATUS     current
    DESCRIPTION
        "-- empty --"
    ::= { lcsStatusPptpConnectionsEntry 8 }

-- {COLUMN} 1712.1.27.9.1.9
lcsStatusPptpConnectionsEntryDnsDefault OBJECT-TYPE
    SYNTAX     IpAddress
    MAX-ACCESS read-only
    STATUS     current
    DESCRIPTION
        "-- empty --"
    ::= { lcsStatusPptpConnectionsEntry 9 }

-- {COLUMN} 1712.1.27.9.1.12
lcsStatusPptpConnectionsEntryDnsBackup OBJECT-TYPE
    SYNTAX     IpAddress
    MAX-ACCESS read-only
    STATUS     current
    DESCRIPTION
        "-- empty --"
    ::= { lcsStatusPptpConnectionsEntry 12 }

-- {COLUMN} 1712.1.27.9.1.10
lcsStatusPptpConnectionsEntryNbnsDefault OBJECT-TYPE
    SYNTAX     IpAddress
    MAX-ACCESS read-only
    STATUS     current
    DESCRIPTION
        "-- empty --"
    ::= { lcsStatusPptpConnectionsEntry 10 }

-- {COLUMN} 1712.1.27.9.1.13
lcsStatusPptpConnectionsEntryNbnsBackup OBJECT-TYPE
    SYNTAX     IpAddress
    MAX-ACCESS read-only
    STATUS     current
    DESCRIPTION
        "-- empty --"
    ::= { lcsStatusPptpConnectionsEntry 13 }

-- {COLUMN} 1712.1.27.9.1.14
lcsStatusPptpConnectionsEntryConnTime OBJECT-TYPE
    SYNTAX     Gauge32
    MAX-ACCESS read-only
    STATUS     current
    DESCRIPTION
        "-- empty --"
    ::= { lcsStatusPptpConnectionsEntry 14 }

-- {COLUMN} 1712.1.27.9.1.15
lcsStatusPptpConnectionsEntryGateway OBJECT-TYPE
    SYNTAX     IpAddress
    MAX-ACCESS read-only
    STATUS     current
    DESCRIPTION
        "-- empty --"
    ::= { lcsStatusPptpConnectionsEntry 15 }

-- {COLUMN} 1712.1.27.9.1.16
lcsStatusPptpConnectionsEntryEncryption OBJECT-TYPE
    SYNTAX     INTEGER
      {
        eOff (0),
        e40Bits (224),
        e56Bits (192),
        e128Bits (64)
      }
    MAX-ACCESS read-only
    STATUS     current
    DESCRIPTION
        "-- empty --"
    ::= { lcsStatusPptpConnectionsEntry 16 }

-- {SCALAR} 1712.1.27.10
lcsStatusPptpTunnel OBJECT-TYPE
    SYNTAX     INTEGER (0..2147483647)
    MAX-ACCESS read-only
    STATUS     current
    DESCRIPTION
        "-- empty --"
    ::= { lcsStatusPptp 10 }

-- {SCALAR} 1712.1.27.13
lcsStatusPptpEncryptedTunnel OBJECT-TYPE
    SYNTAX     INTEGER (0..2147483647)
    MAX-ACCESS read-only
    STATUS     current
    DESCRIPTION
        "-- empty --"
    ::= { lcsStatusPptp 13 }

-- {SCALAR} 1712.1.27.11
lcsStatusPptpDeleteValues OBJECT-TYPE
    SYNTAX     DisplayString
    MAX-ACCESS read-write
    STATUS     current
    DESCRIPTION
        "-- empty --"
    ::= { lcsStatusPptp 11 }

-- {SCALAR} 1712.1.27.12
lcsStatusPptpFlowControlQueue OBJECT-TYPE
    SYNTAX     INTEGER (0..2147483647)
    MAX-ACCESS read-only
    STATUS     current
    DESCRIPTION
        "-- empty --"
    ::= { lcsStatusPptp 12 }

-- {OID} 1712.1.28
lcsStatusPppoe OBJECT IDENTIFIER ::= { lcsStatus 28 }

-- {SCALAR} 1712.1.28.1
lcsStatusPppoeTxPadi OBJECT-TYPE
    SYNTAX     INTEGER (0..2147483647)
    MAX-ACCESS read-only
    STATUS     current
    DESCRIPTION
        "-- empty --"
    ::= { lcsStatusPppoe 1 }

-- {SCALAR} 1712.1.28.2
lcsStatusPppoeRxPado OBJECT-TYPE
    SYNTAX     INTEGER (0..2147483647)
    MAX-ACCESS read-only
    STATUS     current
    DESCRIPTION
        "-- empty --"
    ::= { lcsStatusPppoe 2 }

-- {SCALAR} 1712.1.28.3
lcsStatusPppoeTxPadr OBJECT-TYPE
    SYNTAX     INTEGER (0..2147483647)
    MAX-ACCESS read-only
    STATUS     current
    DESCRIPTION
        "-- empty --"
    ::= { lcsStatusPppoe 3 }

-- {SCALAR} 1712.1.28.4
lcsStatusPppoeRxPads OBJECT-TYPE
    SYNTAX     INTEGER (0..2147483647)
    MAX-ACCESS read-only
    STATUS     current
    DESCRIPTION
        "-- empty --"
    ::= { lcsStatusPppoe 4 }

-- {SCALAR} 1712.1.28.5
lcsStatusPppoeTxPadt OBJECT-TYPE
    SYNTAX     INTEGER (0..2147483647)
    MAX-ACCESS read-only
    STATUS     current
    DESCRIPTION
        "-- empty --"
    ::= { lcsStatusPppoe 5 }

-- {SCALAR} 1712.1.28.6
lcsStatusPppoeRxPadt OBJECT-TYPE
    SYNTAX     INTEGER (0..2147483647)
    MAX-ACCESS read-only
    STATUS     current
    DESCRIPTION
        "-- empty --"
    ::= { lcsStatusPppoe 6 }

-- {SCALAR} 1712.1.28.7
lcsStatusPppoeTxProtocol OBJECT-TYPE
    SYNTAX     INTEGER (0..2147483647)
    MAX-ACCESS read-only
    STATUS     current
    DESCRIPTION
        "-- empty --"
    ::= { lcsStatusPppoe 7 }

-- {SCALAR} 1712.1.28.8
lcsStatusPppoeRxProtocol OBJECT-TYPE
    SYNTAX     INTEGER (0..2147483647)
    MAX-ACCESS read-only
    STATUS     current
    DESCRIPTION
        "-- empty --"
    ::= { lcsStatusPppoe 8 }

-- {SCALAR} 1712.1.28.9
lcsStatusPppoeTxData OBJECT-TYPE
    SYNTAX     INTEGER (0..2147483647)
    MAX-ACCESS read-only
    STATUS     current
    DESCRIPTION
        "-- empty --"
    ::= { lcsStatusPppoe 9 }

-- {SCALAR} 1712.1.28.10
lcsStatusPppoeRxData OBJECT-TYPE
    SYNTAX     INTEGER (0..2147483647)
    MAX-ACCESS read-only
    STATUS     current
    DESCRIPTION
        "-- empty --"
    ::= { lcsStatusPppoe 10 }

-- {SCALAR} 1712.1.28.11
lcsStatusPppoeRxBad OBJECT-TYPE
    SYNTAX     INTEGER (0..2147483647)
    MAX-ACCESS read-only
    STATUS     current
    DESCRIPTION
        "-- empty --"
    ::= { lcsStatusPppoe 11 }

-- {SCALAR} 1712.1.28.12
lcsStatusPppoeAcName OBJECT-TYPE
    SYNTAX     DisplayString (SIZE(0..63))
    MAX-ACCESS read-only
    STATUS     current
    DESCRIPTION
        "-- empty --"
    ::= { lcsStatusPppoe 12 }

-- {SCALAR} 1712.1.28.13
lcsStatusPppoeService OBJECT-TYPE
    SYNTAX     DisplayString (SIZE(0..63))
    MAX-ACCESS read-only
    STATUS     current
    DESCRIPTION
        "-- empty --"
    ::= { lcsStatusPppoe 13 }

-- {SCALAR} 1712.1.28.30
lcsStatusPppoeDeleteValues OBJECT-TYPE
    SYNTAX     DisplayString
    MAX-ACCESS read-write
    STATUS     current
    DESCRIPTION
        "-- empty --"
    ::= { lcsStatusPppoe 30 }

-- {OID} 1712.1.32
lcsStatusDhcpClient OBJECT IDENTIFIER ::= { lcsStatus 32 }

-- {TABLE} 1712.1.32.20
lcsStatusDhcpClientWanIpListTable OBJECT-TYPE
    SYNTAX     SEQUENCE OF LcsStatusDhcpClientWanIpListEntry
    MAX-ACCESS not-accessible
    STATUS     current
    DESCRIPTION
        "-- empty --"
    ::= { lcsStatusDhcpClient 20 }

-- {ENTRY} 1712.1.32.20.1
lcsStatusDhcpClientWanIpListEntry OBJECT-TYPE
    SYNTAX     LcsStatusDhcpClientWanIpListEntry
    MAX-ACCESS not-accessible
    STATUS     current
    DESCRIPTION
        ""
    INDEX {
        lcsStatusDhcpClientWanIpListEntryIfc
    }
    ::= { lcsStatusDhcpClientWanIpListTable 1 }

-- {SEQUENCE}
LcsStatusDhcpClientWanIpListEntry ::= SEQUENCE {
    lcsStatusDhcpClientWanIpListEntryIfc INTEGER,
    lcsStatusDhcpClientWanIpListEntryIpAddress IpAddress,
    lcsStatusDhcpClientWanIpListEntryIpNetmask IpAddress,
    lcsStatusDhcpClientWanIpListEntryGateway IpAddress,
    lcsStatusDhcpClientWanIpListEntryDnsDefault IpAddress,
    lcsStatusDhcpClientWanIpListEntryDnsBackup IpAddress,
    lcsStatusDhcpClientWanIpListEntryNbnsDefault IpAddress,
    lcsStatusDhcpClientWanIpListEntryNbnsBackup IpAddress,
    lcsStatusDhcpClientWanIpListEntryDomain DisplayString,
    lcsStatusDhcpClientWanIpListEntryDhcpServer IpAddress
}

-- {COLUMN} 1712.1.32.20.1.1
lcsStatusDhcpClientWanIpListEntryIfc OBJECT-TYPE
    SYNTAX     INTEGER
      {
        eDslCh1 (1),
        eDslCh2 (2),
        eDslCh3 (3),
        eDslCh4 (4),
        eDslCh5 (5),
        eDslCh6 (6),
        eDslCh7 (7),
        eDslCh8 (8),
        eCh01 (9),
        eCh02 (10),
        eModem (11)
      }
    MAX-ACCESS read-only
    STATUS     current
    DESCRIPTION
        "-- empty --"
    ::= { lcsStatusDhcpClientWanIpListEntry 1 }

-- {COLUMN} 1712.1.32.20.1.2
lcsStatusDhcpClientWanIpListEntryIpAddress OBJECT-TYPE
    SYNTAX     IpAddress
    MAX-ACCESS read-only
    STATUS     current
    DESCRIPTION
        "-- empty --"
    ::= { lcsStatusDhcpClientWanIpListEntry 2 }

-- {COLUMN} 1712.1.32.20.1.3
lcsStatusDhcpClientWanIpListEntryIpNetmask OBJECT-TYPE
    SYNTAX     IpAddress
    MAX-ACCESS read-only
    STATUS     current
    DESCRIPTION
        "-- empty --"
    ::= { lcsStatusDhcpClientWanIpListEntry 3 }

-- {COLUMN} 1712.1.32.20.1.4
lcsStatusDhcpClientWanIpListEntryGateway OBJECT-TYPE
    SYNTAX     IpAddress
    MAX-ACCESS read-only
    STATUS     current
    DESCRIPTION
        "-- empty --"
    ::= { lcsStatusDhcpClientWanIpListEntry 4 }

-- {COLUMN} 1712.1.32.20.1.5
lcsStatusDhcpClientWanIpListEntryDnsDefault OBJECT-TYPE
    SYNTAX     IpAddress
    MAX-ACCESS read-only
    STATUS     current
    DESCRIPTION
        "-- empty --"
    ::= { lcsStatusDhcpClientWanIpListEntry 5 }

-- {COLUMN} 1712.1.32.20.1.6
lcsStatusDhcpClientWanIpListEntryDnsBackup OBJECT-TYPE
    SYNTAX     IpAddress
    MAX-ACCESS read-only
    STATUS     current
    DESCRIPTION
        "-- empty --"
    ::= { lcsStatusDhcpClientWanIpListEntry 6 }

-- {COLUMN} 1712.1.32.20.1.7
lcsStatusDhcpClientWanIpListEntryNbnsDefault OBJECT-TYPE
    SYNTAX     IpAddress
    MAX-ACCESS read-only
    STATUS     current
    DESCRIPTION
        "-- empty --"
    ::= { lcsStatusDhcpClientWanIpListEntry 7 }

-- {COLUMN} 1712.1.32.20.1.8
lcsStatusDhcpClientWanIpListEntryNbnsBackup OBJECT-TYPE
    SYNTAX     IpAddress
    MAX-ACCESS read-only
    STATUS     current
    DESCRIPTION
        "-- empty --"
    ::= { lcsStatusDhcpClientWanIpListEntry 8 }

-- {COLUMN} 1712.1.32.20.1.10
lcsStatusDhcpClientWanIpListEntryDomain OBJECT-TYPE
    SYNTAX     DisplayString (SIZE(0..255))
    MAX-ACCESS read-only
    STATUS     current
    DESCRIPTION
        "-- empty --"
    ::= { lcsStatusDhcpClientWanIpListEntry 10 }

-- {COLUMN} 1712.1.32.20.1.9
lcsStatusDhcpClientWanIpListEntryDhcpServer OBJECT-TYPE
    SYNTAX     IpAddress
    MAX-ACCESS read-only
    STATUS     current
    DESCRIPTION
        "-- empty --"
    ::= { lcsStatusDhcpClientWanIpListEntry 9 }

-- {TABLE} 1712.1.32.21
lcsStatusDhcpClientLanIpListTable OBJECT-TYPE
    SYNTAX     SEQUENCE OF LcsStatusDhcpClientLanIpListEntry
    MAX-ACCESS not-accessible
    STATUS     current
    DESCRIPTION
        "-- empty --"
    ::= { lcsStatusDhcpClient 21 }

-- {ENTRY} 1712.1.32.21.1
lcsStatusDhcpClientLanIpListEntry OBJECT-TYPE
    SYNTAX     LcsStatusDhcpClientLanIpListEntry
    MAX-ACCESS not-accessible
    STATUS     current
    DESCRIPTION
        ""
    INDEX {
        lcsStatusDhcpClientLanIpListEntryIfc
    }
    ::= { lcsStatusDhcpClientLanIpListTable 1 }

-- {SEQUENCE}
LcsStatusDhcpClientLanIpListEntry ::= SEQUENCE {
    lcsStatusDhcpClientLanIpListEntryIfc DisplayString,
    lcsStatusDhcpClientLanIpListEntryIpAddress IpAddress,
    lcsStatusDhcpClientLanIpListEntryIpNetmask IpAddress,
    lcsStatusDhcpClientLanIpListEntryGateway IpAddress,
    lcsStatusDhcpClientLanIpListEntryDnsDefault IpAddress,
    lcsStatusDhcpClientLanIpListEntryDnsBackup IpAddress,
    lcsStatusDhcpClientLanIpListEntryNbnsDefault IpAddress,
    lcsStatusDhcpClientLanIpListEntryNbnsBackup IpAddress,
    lcsStatusDhcpClientLanIpListEntryDomain DisplayString,
    lcsStatusDhcpClientLanIpListEntryDhcpServer IpAddress
}

-- {COLUMN} 1712.1.32.21.1.1
lcsStatusDhcpClientLanIpListEntryIfc OBJECT-TYPE
    SYNTAX     DisplayString (SIZE(0..16))
    MAX-ACCESS read-only
    STATUS     current
    DESCRIPTION
        "-- empty --"
    ::= { lcsStatusDhcpClientLanIpListEntry 1 }

-- {COLUMN} 1712.1.32.21.1.2
lcsStatusDhcpClientLanIpListEntryIpAddress OBJECT-TYPE
    SYNTAX     IpAddress
    MAX-ACCESS read-only
    STATUS     current
    DESCRIPTION
        "-- empty --"
    ::= { lcsStatusDhcpClientLanIpListEntry 2 }

-- {COLUMN} 1712.1.32.21.1.3
lcsStatusDhcpClientLanIpListEntryIpNetmask OBJECT-TYPE
    SYNTAX     IpAddress
    MAX-ACCESS read-only
    STATUS     current
    DESCRIPTION
        "-- empty --"
    ::= { lcsStatusDhcpClientLanIpListEntry 3 }

-- {COLUMN} 1712.1.32.21.1.4
lcsStatusDhcpClientLanIpListEntryGateway OBJECT-TYPE
    SYNTAX     IpAddress
    MAX-ACCESS read-only
    STATUS     current
    DESCRIPTION
        "-- empty --"
    ::= { lcsStatusDhcpClientLanIpListEntry 4 }

-- {COLUMN} 1712.1.32.21.1.5
lcsStatusDhcpClientLanIpListEntryDnsDefault OBJECT-TYPE
    SYNTAX     IpAddress
    MAX-ACCESS read-only
    STATUS     current
    DESCRIPTION
        "-- empty --"
    ::= { lcsStatusDhcpClientLanIpListEntry 5 }

-- {COLUMN} 1712.1.32.21.1.6
lcsStatusDhcpClientLanIpListEntryDnsBackup OBJECT-TYPE
    SYNTAX     IpAddress
    MAX-ACCESS read-only
    STATUS     current
    DESCRIPTION
        "-- empty --"
    ::= { lcsStatusDhcpClientLanIpListEntry 6 }

-- {COLUMN} 1712.1.32.21.1.7
lcsStatusDhcpClientLanIpListEntryNbnsDefault OBJECT-TYPE
    SYNTAX     IpAddress
    MAX-ACCESS read-only
    STATUS     current
    DESCRIPTION
        "-- empty --"
    ::= { lcsStatusDhcpClientLanIpListEntry 7 }

-- {COLUMN} 1712.1.32.21.1.8
lcsStatusDhcpClientLanIpListEntryNbnsBackup OBJECT-TYPE
    SYNTAX     IpAddress
    MAX-ACCESS read-only
    STATUS     current
    DESCRIPTION
        "-- empty --"
    ::= { lcsStatusDhcpClientLanIpListEntry 8 }

-- {COLUMN} 1712.1.32.21.1.10
lcsStatusDhcpClientLanIpListEntryDomain OBJECT-TYPE
    SYNTAX     DisplayString (SIZE(0..255))
    MAX-ACCESS read-only
    STATUS     current
    DESCRIPTION
        "-- empty --"
    ::= { lcsStatusDhcpClientLanIpListEntry 10 }

-- {COLUMN} 1712.1.32.21.1.9
lcsStatusDhcpClientLanIpListEntryDhcpServer OBJECT-TYPE
    SYNTAX     IpAddress
    MAX-ACCESS read-only
    STATUS     current
    DESCRIPTION
        "-- empty --"
    ::= { lcsStatusDhcpClientLanIpListEntry 9 }

-- {OID} 1712.1.47
lcsStatusHardwareInfo OBJECT IDENTIFIER ::= { lcsStatus 47 }

-- {SCALAR} 1712.1.47.6
lcsStatusHardwareInfoModelNumber OBJECT-TYPE
    SYNTAX     DisplayString (SIZE(0..64))
    MAX-ACCESS read-only
    STATUS     current
    DESCRIPTION
        "-- empty --"
    ::= { lcsStatusHardwareInfo 6 }

-- {SCALAR} 1712.1.47.39
lcsStatusHardwareInfoExtendedName OBJECT-TYPE
    SYNTAX     DisplayString (SIZE(0..127))
    MAX-ACCESS read-only
    STATUS     current
    DESCRIPTION
        "-- empty --"
    ::= { lcsStatusHardwareInfo 39 }

-- {SCALAR} 1712.1.47.7
lcsStatusHardwareInfoSerialNumber OBJECT-TYPE
    SYNTAX     DisplayString (SIZE(0..18))
    MAX-ACCESS read-only
    STATUS     current
    DESCRIPTION
        "-- empty --"
    ::= { lcsStatusHardwareInfo 7 }

-- {SCALAR} 1712.1.47.40
lcsStatusHardwareInfoModLevel OBJECT-TYPE
    SYNTAX     DisplayString (SIZE(0..32))
    MAX-ACCESS read-only
    STATUS     current
    DESCRIPTION
        "-- empty --"
    ::= { lcsStatusHardwareInfo 40 }

-- {SCALAR} 1712.1.47.41
lcsStatusHardwareInfoProductionDate OBJECT-TYPE
    SYNTAX     DisplayString (SIZE(0..10))
    MAX-ACCESS read-only
    STATUS     current
    DESCRIPTION
        "-- empty --"
    ::= { lcsStatusHardwareInfo 41 }

-- {SCALAR} 1712.1.47.44
lcsStatusHardwareInfoPldVersion OBJECT-TYPE
    SYNTAX     DisplayString (SIZE(0..7))
    MAX-ACCESS read-only
    STATUS     current
    DESCRIPTION
        "-- empty --"
    ::= { lcsStatusHardwareInfo 44 }

-- {SCALAR} 1712.1.47.45
lcsStatusHardwareInfoResetButtonState OBJECT-TYPE
    SYNTAX     INTEGER
      {
        eActive (1),
        eInactive (0)
      }
    MAX-ACCESS read-only
    STATUS     current
    DESCRIPTION
        "-- empty --"
    ::= { lcsStatusHardwareInfo 45 }

-- {SCALAR} 1712.1.47.8
lcsStatusHardwareInfoBoardRevision OBJECT-TYPE
    SYNTAX     DisplayString (SIZE(0..1))
    MAX-ACCESS read-only
    STATUS     current
    DESCRIPTION
        "-- empty --"
    ::= { lcsStatusHardwareInfo 8 }

-- {SCALAR} 1712.1.47.1
lcsStatusHardwareInfoCpuType OBJECT-TYPE
    SYNTAX     DisplayString (SIZE(0..39))
    MAX-ACCESS read-only
    STATUS     current
    DESCRIPTION
        "-- empty --"
    ::= { lcsStatusHardwareInfo 1 }

-- {SCALAR} 1712.1.47.2
lcsStatusHardwareInfoCpuClockMhz OBJECT-TYPE
    SYNTAX     INTEGER (0..2147483647)
    MAX-ACCESS read-only
    STATUS     current
    DESCRIPTION
        "-- empty --"
    ::= { lcsStatusHardwareInfo 2 }

-- {SCALAR} 1712.1.47.3
lcsStatusHardwareInfoCpuLoadPercent OBJECT-TYPE
    SYNTAX     INTEGER (0..255)
    MAX-ACCESS read-only
    STATUS     current
    DESCRIPTION
        "-- empty --"
    ::= { lcsStatusHardwareInfo 3 }

-- {SCALAR} 1712.1.47.12
lcsStatusHardwareInfoCpuLoad1sPercent OBJECT-TYPE
    SYNTAX     INTEGER (0..255)
    MAX-ACCESS read-only
    STATUS     current
    DESCRIPTION
        "-- empty --"
    ::= { lcsStatusHardwareInfo 12 }

-- {SCALAR} 1712.1.47.13
lcsStatusHardwareInfoCpuLoad5sPercent OBJECT-TYPE
    SYNTAX     INTEGER (0..255)
    MAX-ACCESS read-only
    STATUS     current
    DESCRIPTION
        "-- empty --"
    ::= { lcsStatusHardwareInfo 13 }

-- {SCALAR} 1712.1.47.14
lcsStatusHardwareInfoCpuLoad60sPercent OBJECT-TYPE
    SYNTAX     INTEGER (0..255)
    MAX-ACCESS read-only
    STATUS     current
    DESCRIPTION
        "-- empty --"
    ::= { lcsStatusHardwareInfo 14 }

-- {SCALAR} 1712.1.47.15
lcsStatusHardwareInfoCpuLoad300sPercent OBJECT-TYPE
    SYNTAX     INTEGER (0..255)
    MAX-ACCESS read-only
    STATUS     current
    DESCRIPTION
        "-- empty --"
    ::= { lcsStatusHardwareInfo 15 }

-- {SCALAR} 1712.1.47.4
lcsStatusHardwareInfoTotalMemoryKbytes OBJECT-TYPE
    SYNTAX     INTEGER (0..2147483647)
    MAX-ACCESS read-only
    STATUS     current
    DESCRIPTION
        "-- empty --"
    ::= { lcsStatusHardwareInfo 4 }

-- {SCALAR} 1712.1.47.5
lcsStatusHardwareInfoFreeMemoryKbytes OBJECT-TYPE
    SYNTAX     INTEGER (0..2147483647)
    MAX-ACCESS read-only
    STATUS     current
    DESCRIPTION
        "-- empty --"
    ::= { lcsStatusHardwareInfo 5 }

-- {SCALAR} 1712.1.47.11
lcsStatusHardwareInfoSecurityEngine OBJECT-TYPE
    SYNTAX     INTEGER
      {
        eNo (0),
        eYes (1)
      }
    MAX-ACCESS read-only
    STATUS     current
    DESCRIPTION
        "-- empty --"
    ::= { lcsStatusHardwareInfo 11 }

-- {SCALAR} 1712.1.47.9
lcsStatusHardwareInfoSwVersion OBJECT-TYPE
    SYNTAX     DisplayString (SIZE(0..39))
    MAX-ACCESS read-only
    STATUS     current
    DESCRIPTION
        "-- empty --"
    ::= { lcsStatusHardwareInfo 9 }

-- {SCALAR} 1712.1.47.10
lcsStatusHardwareInfoEthernetSwitchType OBJECT-TYPE
    SYNTAX     DisplayString (SIZE(0..40))
    MAX-ACCESS read-only
    STATUS     current
    DESCRIPTION
        "-- empty --"
    ::= { lcsStatusHardwareInfo 10 }

-- {OID} 1712.1.50
lcsStatusFileSystem OBJECT IDENTIFIER ::= { lcsStatus 50 }

-- {TABLE} 1712.1.50.1
lcsStatusFileSystemContentsTable OBJECT-TYPE
    SYNTAX     SEQUENCE OF LcsStatusFileSystemContentsEntry
    MAX-ACCESS not-accessible
    STATUS     current
    DESCRIPTION
        "-- empty --"
    ::= { lcsStatusFileSystem 1 }

-- {ENTRY} 1712.1.50.1.1
lcsStatusFileSystemContentsEntry OBJECT-TYPE
    SYNTAX     LcsStatusFileSystemContentsEntry
    MAX-ACCESS not-accessible
    STATUS     current
    DESCRIPTION
        ""
    INDEX {
        lcsStatusFileSystemContentsEntryName
    }
    ::= { lcsStatusFileSystemContentsTable 1 }

-- {SEQUENCE}
LcsStatusFileSystemContentsEntry ::= SEQUENCE {
    lcsStatusFileSystemContentsEntryName DisplayString,
    lcsStatusFileSystemContentsEntrySize INTEGER
}

-- {COLUMN} 1712.1.50.1.1.1
lcsStatusFileSystemContentsEntryName OBJECT-TYPE
    SYNTAX     DisplayString (SIZE(0..255))
    MAX-ACCESS read-only
    STATUS     current
    DESCRIPTION
        "-- empty --"
    ::= { lcsStatusFileSystemContentsEntry 1 }

-- {COLUMN} 1712.1.50.1.1.2
lcsStatusFileSystemContentsEntrySize OBJECT-TYPE
    SYNTAX     INTEGER (0..2147483647)
    MAX-ACCESS read-only
    STATUS     current
    DESCRIPTION
        "-- empty --"
    ::= { lcsStatusFileSystemContentsEntry 2 }

-- {TABLE} 1712.1.50.2
lcsStatusFileSystemVolumesTable OBJECT-TYPE
    SYNTAX     SEQUENCE OF LcsStatusFileSystemVolumesEntry
    MAX-ACCESS not-accessible
    STATUS     current
    DESCRIPTION
        "-- empty --"
    ::= { lcsStatusFileSystem 2 }

-- {ENTRY} 1712.1.50.2.1
lcsStatusFileSystemVolumesEntry OBJECT-TYPE
    SYNTAX     LcsStatusFileSystemVolumesEntry
    MAX-ACCESS not-accessible
    STATUS     current
    DESCRIPTION
        ""
    INDEX {
        lcsStatusFileSystemVolumesEntryId
    }
    ::= { lcsStatusFileSystemVolumesTable 1 }

-- {SEQUENCE}
LcsStatusFileSystemVolumesEntry ::= SEQUENCE {
    lcsStatusFileSystemVolumesEntryId DisplayString,
    lcsStatusFileSystemVolumesEntryMountpoints DisplayString,
    lcsStatusFileSystemVolumesEntryFilesystem DisplayString,
    lcsStatusFileSystemVolumesEntryUnmountable INTEGER,
    lcsStatusFileSystemVolumesEntryFree DisplayString,
    lcsStatusFileSystemVolumesEntrySize DisplayString,
    lcsStatusFileSystemVolumesEntryFb INTEGER,
    lcsStatusFileSystemVolumesEntrySb INTEGER
}

-- {COLUMN} 1712.1.50.2.1.1
lcsStatusFileSystemVolumesEntryId OBJECT-TYPE
    SYNTAX     DisplayString (SIZE(0..255))
    MAX-ACCESS read-only
    STATUS     current
    DESCRIPTION
        "-- empty --"
    ::= { lcsStatusFileSystemVolumesEntry 1 }

-- {COLUMN} 1712.1.50.2.1.2
lcsStatusFileSystemVolumesEntryMountpoints OBJECT-TYPE
    SYNTAX     DisplayString (SIZE(0..255))
    MAX-ACCESS read-only
    STATUS     current
    DESCRIPTION
        "-- empty --"
    ::= { lcsStatusFileSystemVolumesEntry 2 }

-- {COLUMN} 1712.1.50.2.1.3
lcsStatusFileSystemVolumesEntryFilesystem OBJECT-TYPE
    SYNTAX     DisplayString (SIZE(0..255))
    MAX-ACCESS read-only
    STATUS     current
    DESCRIPTION
        "-- empty --"
    ::= { lcsStatusFileSystemVolumesEntry 3 }

-- {COLUMN} 1712.1.50.2.1.4
lcsStatusFileSystemVolumesEntryUnmountable OBJECT-TYPE
    SYNTAX     INTEGER (0..255)
    MAX-ACCESS read-only
    STATUS     current
    DESCRIPTION
        "-- empty --"
    ::= { lcsStatusFileSystemVolumesEntry 4 }

-- {COLUMN} 1712.1.50.2.1.5
lcsStatusFileSystemVolumesEntryFree OBJECT-TYPE
    SYNTAX     DisplayString (SIZE(0..255))
    MAX-ACCESS read-only
    STATUS     current
    DESCRIPTION
        "-- empty --"
    ::= { lcsStatusFileSystemVolumesEntry 5 }

-- {COLUMN} 1712.1.50.2.1.6
lcsStatusFileSystemVolumesEntrySize OBJECT-TYPE
    SYNTAX     DisplayString (SIZE(0..255))
    MAX-ACCESS read-only
    STATUS     current
    DESCRIPTION
        "-- empty --"
    ::= { lcsStatusFileSystemVolumesEntry 6 }

-- {COLUMN} 1712.1.50.2.1.7
lcsStatusFileSystemVolumesEntryFb OBJECT-TYPE
    SYNTAX     INTEGER (0..2147483647)
    MAX-ACCESS read-only
    STATUS     current
    DESCRIPTION
        "-- empty --"
    ::= { lcsStatusFileSystemVolumesEntry 7 }

-- {COLUMN} 1712.1.50.2.1.8
lcsStatusFileSystemVolumesEntrySb OBJECT-TYPE
    SYNTAX     INTEGER (0..2147483647)
    MAX-ACCESS read-only
    STATUS     current
    DESCRIPTION
        "-- empty --"
    ::= { lcsStatusFileSystemVolumesEntry 8 }

-- {SCALAR} 1712.1.50.3
lcsStatusFileSystemUnmount OBJECT-TYPE
    SYNTAX     DisplayString
    MAX-ACCESS read-write
    STATUS     current
    DESCRIPTION
        "-- empty --"
    ::= { lcsStatusFileSystem 3 }

-- {SCALAR} 1712.1.50.4
lcsStatusFileSystemSecureErase OBJECT-TYPE
    SYNTAX     DisplayString
    MAX-ACCESS read-write
    STATUS     current
    DESCRIPTION
        "-- empty --"
    ::= { lcsStatusFileSystem 4 }

-- {OID} 1712.1.52
lcsStatusPppoeServer OBJECT IDENTIFIER ::= { lcsStatus 52 }

-- {SCALAR} 1712.1.52.1
lcsStatusPppoeServerRxPackets OBJECT-TYPE
    SYNTAX     Counter32
    MAX-ACCESS read-only
    STATUS     current
    DESCRIPTION
        "-- empty --"
    ::= { lcsStatusPppoeServer 1 }

-- {SCALAR} 1712.1.52.2
lcsStatusPppoeServerTxPackets OBJECT-TYPE
    SYNTAX     Counter32
    MAX-ACCESS read-only
    STATUS     current
    DESCRIPTION
        "-- empty --"
    ::= { lcsStatusPppoeServer 2 }

-- {SCALAR} 1712.1.52.5
lcsStatusPppoeServerDroppedPackets OBJECT-TYPE
    SYNTAX     Counter32
    MAX-ACCESS read-only
    STATUS     current
    DESCRIPTION
        "-- empty --"
    ::= { lcsStatusPppoeServer 5 }

-- {SCALAR} 1712.1.52.6
lcsStatusPppoeServerRxErrors OBJECT-TYPE
    SYNTAX     Counter32
    MAX-ACCESS read-only
    STATUS     current
    DESCRIPTION
        "-- empty --"
    ::= { lcsStatusPppoeServer 6 }

-- {SCALAR} 1712.1.52.8
lcsStatusPppoeServerSessionErrors OBJECT-TYPE
    SYNTAX     Counter32
    MAX-ACCESS read-only
    STATUS     current
    DESCRIPTION
        "-- empty --"
    ::= { lcsStatusPppoeServer 8 }

-- {TABLE} 1712.1.52.9
lcsStatusPppoeServerConnectionsTable OBJECT-TYPE
    SYNTAX     SEQUENCE OF LcsStatusPppoeServerConnectionsEntry
    MAX-ACCESS not-accessible
    STATUS     current
    DESCRIPTION
        "-- empty --"
    ::= { lcsStatusPppoeServer 9 }

-- {ENTRY} 1712.1.52.9.1
lcsStatusPppoeServerConnectionsEntry OBJECT-TYPE
    SYNTAX     LcsStatusPppoeServerConnectionsEntry
    MAX-ACCESS not-accessible
    STATUS     current
    DESCRIPTION
        ""
    INDEX {
        lcsStatusPppoeServerConnectionsEntryChannel,
        lcsStatusPppoeServerConnectionsEntryMacAddress
    }
    ::= { lcsStatusPppoeServerConnectionsTable 1 }

-- {SEQUENCE}
LcsStatusPppoeServerConnectionsEntry ::= SEQUENCE {
    lcsStatusPppoeServerConnectionsEntryChannel DisplayString,
    lcsStatusPppoeServerConnectionsEntryMacAddress DisplayString,
    lcsStatusPppoeServerConnectionsEntryState INTEGER,
    lcsStatusPppoeServerConnectionsEntryLastError INTEGER,
    lcsStatusPppoeServerConnectionsEntryShTime INTEGER,
    lcsStatusPppoeServerConnectionsEntryPeerAddress IpAddress,
    lcsStatusPppoeServerConnectionsEntryConnTime Gauge32
}

-- {COLUMN} 1712.1.52.9.1.1
lcsStatusPppoeServerConnectionsEntryChannel OBJECT-TYPE
    SYNTAX     DisplayString (SIZE(0..16))
    MAX-ACCESS read-only
    STATUS     current
    DESCRIPTION
        "-- empty --"
    ::= { lcsStatusPppoeServerConnectionsEntry 1 }

-- {COLUMN} 1712.1.52.9.1.2
lcsStatusPppoeServerConnectionsEntryMacAddress OBJECT-TYPE
    SYNTAX     DisplayString (SIZE(0..12))
    MAX-ACCESS read-only
    STATUS     current
    DESCRIPTION
        "-- empty --"
    ::= { lcsStatusPppoeServerConnectionsEntry 2 }

-- {COLUMN} 1712.1.52.9.1.3
lcsStatusPppoeServerConnectionsEntryState OBJECT-TYPE
    SYNTAX     INTEGER
      {
        eInit (0),
        eSetupWan (1),
        eReady (2),
        eWaitForCb (3),
        eDial (4),
        eIncomingCall (5),
        eProtocol (6),
        eConnection (7),
        eDisconnecting (8),
        eCallBack (9),
        eBundleConnect (10),
        eProtocol2 (11),
        eReserved (12),
        eBundle (13)
      }
    MAX-ACCESS read-only
    STATUS     current
    DESCRIPTION
        "-- empty --"
    ::= { lcsStatusPppoeServerConnectionsEntry 3 }

-- {COLUMN} 1712.1.52.9.1.4
lcsStatusPppoeServerConnectionsEntryLastError OBJECT-TYPE
    SYNTAX     INTEGER
      {
        eNone (0),
        eRemoteDisconnected (17153),
        eManualDisconnect (17154),
        eShortholdExpired (17155),
        ePhysicalDisconnected (17156),
        eInvalidPhysicalChannel (17157),
        eDynamicVpnReconnect (17158),
        eConfigurationChanged (17159),
        eRemovedFromConfig (17160),
        eRemoteDoubled (267),
        eIcmpConnError (275),
        eDhcpTimeout (277),
        ePptpNoResponse (278),
        eVpnNoResponse (279),
        eArpNoResponse (280),
        ePptpNoChannel (513),
        ePptpBadFormat (514),
        ePptpBadValue (515),
        ePptpNoRessource (516),
        ePptpBadCallId (517),
        ePptpGenError (518),
        eLcpRejected (32768),
        eAuthError (32769),
        eAuthRejected (32770),
        eLcpConnError (32771),
        ePapRejected (32784),
        ePapRxTimeout (32785),
        ePapTxTimeout (32786),
        eWrongPapReq (32787),
        ePapNakReceived (32788),
        eUnknPapPeer (32789),
        eChapRejected (32800),
        eChapRxTimeout (32801),
        eChapTxTimeout (32802),
        eWrongChapResp (32803),
        eChapFailRecvd (32804),
        eUnknChapPeer (32805),
        eIpcpRejected (32832),
        eCcpRejected (32848),
        eNoNcpAvailable (33008)
      }
    MAX-ACCESS read-write
    STATUS     current
    DESCRIPTION
        "-- empty --"
    ::= { lcsStatusPppoeServerConnectionsEntry 4 }

-- {COLUMN} 1712.1.52.9.1.5
lcsStatusPppoeServerConnectionsEntryShTime OBJECT-TYPE
    SYNTAX     INTEGER (0..65535)
    MAX-ACCESS read-only
    STATUS     current
    DESCRIPTION
        "-- empty --"
    ::= { lcsStatusPppoeServerConnectionsEntry 5 }

-- {COLUMN} 1712.1.52.9.1.6
lcsStatusPppoeServerConnectionsEntryPeerAddress OBJECT-TYPE
    SYNTAX     IpAddress
    MAX-ACCESS read-only
    STATUS     current
    DESCRIPTION
        "-- empty --"
    ::= { lcsStatusPppoeServerConnectionsEntry 6 }

-- {COLUMN} 1712.1.52.9.1.7
lcsStatusPppoeServerConnectionsEntryConnTime OBJECT-TYPE
    SYNTAX     Gauge32
    MAX-ACCESS read-only
    STATUS     current
    DESCRIPTION
        "-- empty --"
    ::= { lcsStatusPppoeServerConnectionsEntry 7 }

-- {SCALAR} 1712.1.52.10
lcsStatusPppoeServerNumConnections OBJECT-TYPE
    SYNTAX     INTEGER (0..2147483647)
    MAX-ACCESS read-only
    STATUS     current
    DESCRIPTION
        "-- empty --"
    ::= { lcsStatusPppoeServer 10 }

-- {SCALAR} 1712.1.52.11
lcsStatusPppoeServerDeleteValues OBJECT-TYPE
    SYNTAX     DisplayString
    MAX-ACCESS read-write
    STATUS     current
    DESCRIPTION
        "-- empty --"
    ::= { lcsStatusPppoeServer 11 }

-- {OID} 1712.1.62
lcsStatusVlan OBJECT IDENTIFIER ::= { lcsStatus 62 }

-- {SCALAR} 1712.1.62.4
lcsStatusVlanOperating OBJECT-TYPE
    SYNTAX     INTEGER
      {
        eNo (0),
        eYes (1)
      }
    MAX-ACCESS read-only
    STATUS     current
    DESCRIPTION
        "-- empty --"
    ::= { lcsStatusVlan 4 }

-- {TABLE} 1712.1.62.1
lcsStatusVlanNetworksTable OBJECT-TYPE
    SYNTAX     SEQUENCE OF LcsStatusVlanNetworksEntry
    MAX-ACCESS not-accessible
    STATUS     current
    DESCRIPTION
        "-- empty --"
    ::= { lcsStatusVlan 1 }

-- {ENTRY} 1712.1.62.1.1
lcsStatusVlanNetworksEntry OBJECT-TYPE
    SYNTAX     LcsStatusVlanNetworksEntry
    MAX-ACCESS not-accessible
    STATUS     current
    DESCRIPTION
        ""
    INDEX {
        lcsStatusVlanNetworksEntryVlanId
    }
    ::= { lcsStatusVlanNetworksTable 1 }

-- {SEQUENCE}
LcsStatusVlanNetworksEntry ::= SEQUENCE {
    lcsStatusVlanNetworksEntryVlanId INTEGER,
    lcsStatusVlanNetworksEntryPorts DisplayString
}

-- {COLUMN} 1712.1.62.1.1.1
lcsStatusVlanNetworksEntryVlanId OBJECT-TYPE
    SYNTAX     INTEGER (0..65535)
    MAX-ACCESS read-only
    STATUS     current
    DESCRIPTION
        "-- empty --"
    ::= { lcsStatusVlanNetworksEntry 1 }

-- {COLUMN} 1712.1.62.1.1.4
lcsStatusVlanNetworksEntryPorts OBJECT-TYPE
    SYNTAX     DisplayString (SIZE(0..255))
    MAX-ACCESS read-only
    STATUS     current
    DESCRIPTION
        "-- empty --"
    ::= { lcsStatusVlanNetworksEntry 4 }

-- {TABLE} 1712.1.62.2
lcsStatusVlanPortTableTable OBJECT-TYPE
    SYNTAX     SEQUENCE OF LcsStatusVlanPortTableEntry
    MAX-ACCESS not-accessible
    STATUS     current
    DESCRIPTION
        "-- empty --"
    ::= { lcsStatusVlan 2 }

-- {ENTRY} 1712.1.62.2.1
lcsStatusVlanPortTableEntry OBJECT-TYPE
    SYNTAX     LcsStatusVlanPortTableEntry
    MAX-ACCESS not-accessible
    STATUS     current
    DESCRIPTION
        ""
    INDEX {
        lcsStatusVlanPortTableEntryPort
    }
    ::= { lcsStatusVlanPortTableTable 1 }

-- {SEQUENCE}
LcsStatusVlanPortTableEntry ::= SEQUENCE {
    lcsStatusVlanPortTableEntryPort DisplayString,
    lcsStatusVlanPortTableEntryTaggingMode INTEGER,
    lcsStatusVlanPortTableEntryAllowAllVlans INTEGER,
    lcsStatusVlanPortTableEntryPortVlanId INTEGER
}

-- {COLUMN} 1712.1.62.2.1.1
lcsStatusVlanPortTableEntryPort OBJECT-TYPE
    SYNTAX     DisplayString (SIZE(0..255))
    MAX-ACCESS read-only
    STATUS     current
    DESCRIPTION
        "-- empty --"
    ::= { lcsStatusVlanPortTableEntry 1 }

-- {COLUMN} 1712.1.62.2.1.6
lcsStatusVlanPortTableEntryTaggingMode OBJECT-TYPE
    SYNTAX     INTEGER
      {
        eIngressMixed (0),
        eNever (1),
        eMixed (2),
        eAlways (3)
      }
    MAX-ACCESS read-only
    STATUS     current
    DESCRIPTION
        "-- empty --"
    ::= { lcsStatusVlanPortTableEntry 6 }

-- {COLUMN} 1712.1.62.2.1.4
lcsStatusVlanPortTableEntryAllowAllVlans OBJECT-TYPE
    SYNTAX     INTEGER
      {
        eNo (0),
        eYes (1)
      }
    MAX-ACCESS read-only
    STATUS     current
    DESCRIPTION
        "-- empty --"
    ::= { lcsStatusVlanPortTableEntry 4 }

-- {COLUMN} 1712.1.62.2.1.5
lcsStatusVlanPortTableEntryPortVlanId OBJECT-TYPE
    SYNTAX     INTEGER (0..65535)
    MAX-ACCESS read-only
    STATUS     current
    DESCRIPTION
        "-- empty --"
    ::= { lcsStatusVlanPortTableEntry 5 }

-- {SCALAR} 1712.1.100
lcsStatusDeleteValues OBJECT-TYPE
    SYNTAX     DisplayString
    MAX-ACCESS read-write
    STATUS     current
    DESCRIPTION
        "-- empty --"
    ::= { lcsStatus 100 }

-- {OID} 1712.1.49
lcsStatusModemMobile OBJECT IDENTIFIER ::= { lcsStatus 49 }

-- {SCALAR} 1712.1.49.4
lcsStatusModemMobileOperating OBJECT-TYPE
    SYNTAX     INTEGER
      {
        eNo (0),
        eModem (1),
        eWwan (2)
      }
    MAX-ACCESS read-only
    STATUS     current
    DESCRIPTION
        "-- empty --"
    ::= { lcsStatusModemMobile 4 }

-- {SCALAR} 1712.1.49.1
lcsStatusModemMobileModemInfo OBJECT-TYPE
    SYNTAX     DisplayString (SIZE(0..255))
    MAX-ACCESS read-only
    STATUS     current
    DESCRIPTION
        "-- empty --"
    ::= { lcsStatusModemMobile 1 }

-- {SCALAR} 1712.1.49.2
lcsStatusModemMobileConnectInfo OBJECT-TYPE
    SYNTAX     DisplayString (SIZE(0..63))
    MAX-ACCESS read-only
    STATUS     current
    DESCRIPTION
        "-- empty --"
    ::= { lcsStatusModemMobile 2 }

-- {SCALAR} 1712.1.49.3
lcsStatusModemMobileState OBJECT-TYPE
    SYNTAX     INTEGER
      {
        eWaitForDevice (15),
        eDeactivated (0),
        eDeviceDetection (1),
        eReset (2),
        eInitializing (3),
        eModemId (4),
        eReady (5),
        eConnecting (6),
        ePassConnecting (7),
        eDataMode (8),
        eNetworkScan (9),
        eSetPin (10),
        ePinInvalid (11),
        ePinMissing (16),
        eUnexpectedResponse (12),
        ePukRequired (13),
        eNetwork (14),
        eHwPoll (18)
      }
    MAX-ACCESS read-only
    STATUS     current
    DESCRIPTION
        "-- empty --"
    ::= { lcsStatusModemMobile 3 }

-- {SCALAR} 1712.1.49.5
lcsStatusModemMobileDataRate OBJECT-TYPE
    SYNTAX     INTEGER (0..2147483647)
    MAX-ACCESS read-only
    STATUS     current
    DESCRIPTION
        "-- empty --"
    ::= { lcsStatusModemMobile 5 }

-- {SCALAR} 1712.1.49.31
lcsStatusModemMobileMaxDownstreamRateKbS OBJECT-TYPE
    SYNTAX     INTEGER (0..2147483647)
    MAX-ACCESS read-only
    STATUS     current
    DESCRIPTION
        "-- empty --"
    ::= { lcsStatusModemMobile 31 }

-- {SCALAR} 1712.1.49.32
lcsStatusModemMobileMaxUpstreamRateKbS OBJECT-TYPE
    SYNTAX     INTEGER (0..2147483647)
    MAX-ACCESS read-only
    STATUS     current
    DESCRIPTION
        "-- empty --"
    ::= { lcsStatusModemMobile 32 }

-- {SCALAR} 1712.1.49.6
lcsStatusModemMobileSignalDbm OBJECT-TYPE
    SYNTAX     INTEGER (-2147483648..2147483647)
    MAX-ACCESS read-only
    STATUS     current
    DESCRIPTION
        "-- empty --"
    ::= { lcsStatusModemMobile 6 }

-- {SCALAR} 1712.1.49.7
lcsStatusModemMobileRegistration OBJECT-TYPE
    SYNTAX     INTEGER
      {
        eNoNetwork (0),
        eHomeNetwork (1),
        eSearching (2),
        eUnknown (4),
        eRoaming (5),
        eNoNetworkDenied (128),
        eSearchingDenied (130),
        eRegistrationDenied (131),
        eUnknownDenied (132)
      }
    MAX-ACCESS read-only
    STATUS     current
    DESCRIPTION
        "-- empty --"
    ::= { lcsStatusModemMobile 7 }

-- {SCALAR} 1712.1.49.8
lcsStatusModemMobileNetwork OBJECT-TYPE
    SYNTAX     DisplayString (SIZE(0..16))
    MAX-ACCESS read-only
    STATUS     current
    DESCRIPTION
        "-- empty --"
    ::= { lcsStatusModemMobile 8 }

-- {SCALAR} 1712.1.49.26
lcsStatusModemMobileMobileCountryCode OBJECT-TYPE
    SYNTAX     INTEGER
      {
        eUnknown (0),
        eDe (262)
      }
    MAX-ACCESS read-only
    STATUS     current
    DESCRIPTION
        "-- empty --"
    ::= { lcsStatusModemMobile 26 }

-- {SCALAR} 1712.1.49.27
lcsStatusModemMobileMobileNetworkCode OBJECT-TYPE
    SYNTAX     INTEGER (0..2147483647)
    MAX-ACCESS read-only
    STATUS     current
    DESCRIPTION
        "-- empty --"
    ::= { lcsStatusModemMobile 27 }

-- {SCALAR} 1712.1.49.28
lcsStatusModemMobileMobileCellId OBJECT-TYPE
    SYNTAX     INTEGER (0..2147483647)
    MAX-ACCESS read-only
    STATUS     current
    DESCRIPTION
        "-- empty --"
    ::= { lcsStatusModemMobile 28 }

-- {SCALAR} 1712.1.49.29
lcsStatusModemMobileMobileLocalAreaCode OBJECT-TYPE
    SYNTAX     INTEGER (0..2147483647)
    MAX-ACCESS read-only
    STATUS     current
    DESCRIPTION
        "-- empty --"
    ::= { lcsStatusModemMobile 29 }

-- {SCALAR} 1712.1.49.12
lcsStatusModemMobileMode OBJECT-TYPE
    SYNTAX     INTEGER
      {
        eUnknown (0),
        eUmts (1),
        eGprs (2),
        eGsm (3),
        eEdge (4),
        eHsdpa (5),
        eHsupa (6),
        eHspaPlus (7),
        eLte (8),
        eHspa (9)
      }
    MAX-ACCESS read-only
    STATUS     current
    DESCRIPTION
        "-- empty --"
    ::= { lcsStatusModemMobile 12 }

-- {SCALAR} 1712.1.49.13
lcsStatusModemMobilePort OBJECT-TYPE
    SYNTAX     INTEGER
      {
        eNone (0),
        eOutband (1),
        eUsb (2)
      }
    MAX-ACCESS read-only
    STATUS     current
    DESCRIPTION
        "-- empty --"
    ::= { lcsStatusModemMobile 13 }

-- {SCALAR} 1712.1.49.21
lcsStatusModemMobilePinStatus OBJECT-TYPE
    SYNTAX     DisplayString (SIZE(0..47))
    MAX-ACCESS read-only
    STATUS     current
    DESCRIPTION
        "-- empty --"
    ::= { lcsStatusModemMobile 21 }

-- {SCALAR} 1712.1.49.15
lcsStatusModemMobileHardwareResets OBJECT-TYPE
    SYNTAX     INTEGER (0..2147483647)
    MAX-ACCESS read-only
    STATUS     current
    DESCRIPTION
        "-- empty --"
    ::= { lcsStatusModemMobile 15 }

-- {SCALAR} 1712.1.49.17
lcsStatusModemMobileTemperatureStatus OBJECT-TYPE
    SYNTAX     INTEGER
      {
        eUnknown (0),
        eNormal (1),
        eLow (2),
        eHigh (3),
        eLowCritical (5),
        eHighCritical (6)
      }
    MAX-ACCESS read-only
    STATUS     current
    DESCRIPTION
        "-- empty --"
    ::= { lcsStatusModemMobile 17 }

-- {SCALAR} 1712.1.49.18
lcsStatusModemMobileTemperatureDegc OBJECT-TYPE
    SYNTAX     INTEGER (0..255)
    MAX-ACCESS read-only
    STATUS     current
    DESCRIPTION
        "-- empty --"
    ::= { lcsStatusModemMobile 18 }

-- {SCALAR} 1712.1.49.19
lcsStatusModemMobileSupplyVoltageStatus OBJECT-TYPE
    SYNTAX     INTEGER
      {
        eUnknown (0),
        eNormal (1),
        eLow (2),
        eHigh (3),
        eLowCritical (5),
        eHighCritical (6)
      }
    MAX-ACCESS read-only
    STATUS     current
    DESCRIPTION
        "-- empty --"
    ::= { lcsStatusModemMobile 19 }

-- {SCALAR} 1712.1.49.20
lcsStatusModemMobileSupplyVoltageMv OBJECT-TYPE
    SYNTAX     INTEGER (0..65535)
    MAX-ACCESS read-only
    STATUS     current
    DESCRIPTION
        "-- empty --"
    ::= { lcsStatusModemMobile 20 }

-- {SCALAR} 1712.1.49.30
lcsStatusModemMobileRelease OBJECT-TYPE
    SYNTAX     INTEGER (0..2147483647)
    MAX-ACCESS read-only
    STATUS     current
    DESCRIPTION
        "-- empty --"
    ::= { lcsStatusModemMobile 30 }

-- {SCALAR} 1712.1.49.23
lcsStatusModemMobileSimIdIccid OBJECT-TYPE
    SYNTAX     DisplayString (SIZE(0..22))
    MAX-ACCESS read-only
    STATUS     current
    DESCRIPTION
        "-- empty --"
    ::= { lcsStatusModemMobile 23 }

-- {SCALAR} 1712.1.49.37
lcsStatusModemMobileImei OBJECT-TYPE
    SYNTAX     DisplayString (SIZE(0..15))
    MAX-ACCESS read-only
    STATUS     current
    DESCRIPTION
        "-- empty --"
    ::= { lcsStatusModemMobile 37 }

-- {SCALAR} 1712.1.49.39
lcsStatusModemMobileImsi OBJECT-TYPE
    SYNTAX     DisplayString (SIZE(0..15))
    MAX-ACCESS read-only
    STATUS     current
    DESCRIPTION
        "-- empty --"
    ::= { lcsStatusModemMobile 39 }

-- {SCALAR} 1712.1.49.40
lcsStatusModemMobilePhoneNumber OBJECT-TYPE
    SYNTAX     DisplayString (SIZE(0..31))
    MAX-ACCESS read-only
    STATUS     current
    DESCRIPTION
        "-- empty --"
    ::= { lcsStatusModemMobile 40 }

-- {SCALAR} 1712.1.49.41
lcsStatusModemMobileSetApn OBJECT-TYPE
    SYNTAX     DisplayString (SIZE(0..63))
    MAX-ACCESS read-only
    STATUS     current
    DESCRIPTION
        "-- empty --"
    ::= { lcsStatusModemMobile 41 }

-- {TABLE} 1712.1.49.9
lcsStatusModemMobileNetworkListTable OBJECT-TYPE
    SYNTAX     SEQUENCE OF LcsStatusModemMobileNetworkListEntry
    MAX-ACCESS not-accessible
    STATUS     current
    DESCRIPTION
        "-- empty --"
    ::= { lcsStatusModemMobile 9 }

-- {ENTRY} 1712.1.49.9.1
lcsStatusModemMobileNetworkListEntry OBJECT-TYPE
    SYNTAX     LcsStatusModemMobileNetworkListEntry
    MAX-ACCESS not-accessible
    STATUS     current
    DESCRIPTION
        ""
    INDEX {
        lcsStatusModemMobileNetworkListEntryNetwork
    }
    ::= { lcsStatusModemMobileNetworkListTable 1 }

-- {SEQUENCE}
LcsStatusModemMobileNetworkListEntry ::= SEQUENCE {
    lcsStatusModemMobileNetworkListEntryNetwork DisplayString,
    lcsStatusModemMobileNetworkListEntryNumeric INTEGER,
    lcsStatusModemMobileNetworkListEntryState INTEGER,
    lcsStatusModemMobileNetworkListEntryMode BITS
}

-- {COLUMN} 1712.1.49.9.1.1
lcsStatusModemMobileNetworkListEntryNetwork OBJECT-TYPE
    SYNTAX     DisplayString (SIZE(0..16))
    MAX-ACCESS read-only
    STATUS     current
    DESCRIPTION
        "-- empty --"
    ::= { lcsStatusModemMobileNetworkListEntry 1 }

-- {COLUMN} 1712.1.49.9.1.4
lcsStatusModemMobileNetworkListEntryNumeric OBJECT-TYPE
    SYNTAX     INTEGER (0..2147483647)
    MAX-ACCESS read-only
    STATUS     current
    DESCRIPTION
        "-- empty --"
    ::= { lcsStatusModemMobileNetworkListEntry 4 }

-- {COLUMN} 1712.1.49.9.1.2
lcsStatusModemMobileNetworkListEntryState OBJECT-TYPE
    SYNTAX     INTEGER
      {
        eUnknown (1),
        eAvailable (2),
        eCurrent (3),
        eForbidden (4)
      }
    MAX-ACCESS read-only
    STATUS     current
    DESCRIPTION
        "-- empty --"
    ::= { lcsStatusModemMobileNetworkListEntry 2 }

-- {COLUMN} 1712.1.49.9.1.3
lcsStatusModemMobileNetworkListEntryMode OBJECT-TYPE
    SYNTAX     BITS
      {
        eUnknown (0),
        eGprs (31),
        eUmts (30),
        eLte (29)
      }
    MAX-ACCESS read-only
    STATUS     current
    DESCRIPTION
        "-- empty --"
    ::= { lcsStatusModemMobileNetworkListEntry 3 }

-- {TABLE} 1712.1.49.16
lcsStatusModemMobileHistoryTable OBJECT-TYPE
    SYNTAX     SEQUENCE OF LcsStatusModemMobileHistoryEntry
    MAX-ACCESS not-accessible
    STATUS     current
    DESCRIPTION
        "-- empty --"
    ::= { lcsStatusModemMobile 16 }

-- {ENTRY} 1712.1.49.16.1
lcsStatusModemMobileHistoryEntry OBJECT-TYPE
    SYNTAX     LcsStatusModemMobileHistoryEntry
    MAX-ACCESS not-accessible
    STATUS     current
    DESCRIPTION
        ""
    INDEX {
        lcsStatusModemMobileHistoryEntryIndex
    }
    ::= { lcsStatusModemMobileHistoryTable 1 }

-- {SEQUENCE}
LcsStatusModemMobileHistoryEntry ::= SEQUENCE {
    lcsStatusModemMobileHistoryEntryIndex INTEGER,
    lcsStatusModemMobileHistoryEntryTimestamp Gauge32,
    lcsStatusModemMobileHistoryEntrySignalDbm INTEGER,
    lcsStatusModemMobileHistoryEntryNetwork DisplayString,
    lcsStatusModemMobileHistoryEntryMode INTEGER,
    lcsStatusModemMobileHistoryEntryRegistration INTEGER
}

-- {COLUMN} 1712.1.49.16.1.1
lcsStatusModemMobileHistoryEntryIndex OBJECT-TYPE
    SYNTAX     INTEGER (0..2147483647)
    MAX-ACCESS read-only
    STATUS     current
    DESCRIPTION
        "-- empty --"
    ::= { lcsStatusModemMobileHistoryEntry 1 }

-- {COLUMN} 1712.1.49.16.1.2
lcsStatusModemMobileHistoryEntryTimestamp OBJECT-TYPE
    SYNTAX     Gauge32
    MAX-ACCESS read-only
    STATUS     current
    DESCRIPTION
        "-- empty --"
    ::= { lcsStatusModemMobileHistoryEntry 2 }

-- {COLUMN} 1712.1.49.16.1.3
lcsStatusModemMobileHistoryEntrySignalDbm OBJECT-TYPE
    SYNTAX     INTEGER (-2147483648..2147483647)
    MAX-ACCESS read-only
    STATUS     current
    DESCRIPTION
        "-- empty --"
    ::= { lcsStatusModemMobileHistoryEntry 3 }

-- {COLUMN} 1712.1.49.16.1.4
lcsStatusModemMobileHistoryEntryNetwork OBJECT-TYPE
    SYNTAX     DisplayString (SIZE(0..1))
    MAX-ACCESS read-only
    STATUS     current
    DESCRIPTION
        "-- empty --"
    ::= { lcsStatusModemMobileHistoryEntry 4 }

-- {COLUMN} 1712.1.49.16.1.5
lcsStatusModemMobileHistoryEntryMode OBJECT-TYPE
    SYNTAX     INTEGER
      {
        eUnknown (0),
        eUmts (1),
        eGprs (2),
        eGsm (3),
        eEdge (4),
        eHsdpa (5),
        eHsupa (6),
        eHspaPlus (7),
        eLte (8),
        eHspa (9)
      }
    MAX-ACCESS read-only
    STATUS     current
    DESCRIPTION
        "-- empty --"
    ::= { lcsStatusModemMobileHistoryEntry 5 }

-- {COLUMN} 1712.1.49.16.1.6
lcsStatusModemMobileHistoryEntryRegistration OBJECT-TYPE
    SYNTAX     INTEGER
      {
        eNoNetwork (0),
        eHomeNetwork (1),
        eSearching (2),
        eUnknown (4),
        eRoaming (5),
        eNoNetworkDenied (128),
        eSearchingDenied (130),
        eRegistrationDenied (131),
        eUnknownDenied (132)
      }
    MAX-ACCESS read-only
    STATUS     current
    DESCRIPTION
        "-- empty --"
    ::= { lcsStatusModemMobileHistoryEntry 6 }

-- {SCALAR} 1712.1.49.10
lcsStatusModemMobileScanNetworks OBJECT-TYPE
    SYNTAX     DisplayString
    MAX-ACCESS read-write
    STATUS     current
    DESCRIPTION
        "-- empty --"
    ::= { lcsStatusModemMobile 10 }

-- {SCALAR} 1712.1.49.11
lcsStatusModemMobileInputPuk OBJECT-TYPE
    SYNTAX     DisplayString
    MAX-ACCESS read-write
    STATUS     current
    DESCRIPTION
        "-- empty --"
    ::= { lcsStatusModemMobile 11 }

-- {SCALAR} 1712.1.49.42
lcsStatusModemMobilePinChange OBJECT-TYPE
    SYNTAX     DisplayString
    MAX-ACCESS read-write
    STATUS     current
    DESCRIPTION
        "-- empty --"
    ::= { lcsStatusModemMobile 42 }

-- {SCALAR} 1712.1.49.25
lcsStatusModemMobileFallbackTo2g OBJECT-TYPE
    SYNTAX     INTEGER
      {
        eNo (0),
        eYes (1)
      }
    MAX-ACCESS read-only
    STATUS     current
    DESCRIPTION
        "-- empty --"
    ::= { lcsStatusModemMobile 25 }

-- {SCALAR} 1712.1.49.33
lcsStatusModemMobileMobileBand OBJECT-TYPE
    SYNTAX     DisplayString (SIZE(0..15))
    MAX-ACCESS read-only
    STATUS     current
    DESCRIPTION
        "-- empty --"
    ::= { lcsStatusModemMobile 33 }

-- {SCALAR} 1712.1.49.34
lcsStatusModemMobileMobileBandwidthMhz OBJECT-TYPE
    SYNTAX     INTEGER (0..2147483647)
    MAX-ACCESS read-only
    STATUS     current
    DESCRIPTION
        "-- empty --"
    ::= { lcsStatusModemMobile 34 }

-- {SCALAR} 1712.1.49.35
lcsStatusModemMobileMobileTxChannel OBJECT-TYPE
    SYNTAX     INTEGER (0..2147483647)
    MAX-ACCESS read-only
    STATUS     current
    DESCRIPTION
        "-- empty --"
    ::= { lcsStatusModemMobile 35 }

-- {SCALAR} 1712.1.49.36
lcsStatusModemMobileMobileRxChannel OBJECT-TYPE
    SYNTAX     INTEGER (0..2147483647)
    MAX-ACCESS read-only
    STATUS     current
    DESCRIPTION
        "-- empty --"
    ::= { lcsStatusModemMobile 36 }

-- {SCALAR} 1712.1.49.14
lcsStatusModemMobileDroppedTxPackets OBJECT-TYPE
    SYNTAX     INTEGER (0..2147483647)
    MAX-ACCESS read-only
    STATUS     current
    DESCRIPTION
        "-- empty --"
    ::= { lcsStatusModemMobile 14 }

-- {SCALAR} 1712.1.49.22
lcsStatusModemMobileRxTimeouts OBJECT-TYPE
    SYNTAX     INTEGER (0..2147483647)
    MAX-ACCESS read-only
    STATUS     current
    DESCRIPTION
        "-- empty --"
    ::= { lcsStatusModemMobile 22 }

-- {OID} 1712.1.67
lcsStatusComPorts OBJECT IDENTIFIER ::= { lcsStatus 67 }

-- {TABLE} 1712.1.67.1
lcsStatusComPortsDevTable OBJECT-TYPE
    SYNTAX     SEQUENCE OF LcsStatusComPortsDevEntry
    MAX-ACCESS not-accessible
    STATUS     current
    DESCRIPTION
        ""
    ::= { lcsStatusComPorts 1 }

-- {ENTRY} 1712.1.67.1.1
lcsStatusComPortsDevEntry OBJECT-TYPE
    SYNTAX     LcsStatusComPortsDevEntry
    MAX-ACCESS not-accessible
    STATUS     current
    DESCRIPTION
        ""
    INDEX {
        lcsStatusComPortsDevEntryIndex
    }
    ::= { lcsStatusComPortsDevTable 1 }

-- {SEQUENCE}
LcsStatusComPortsDevEntry ::= SEQUENCE {
    lcsStatusComPortsDevEntryIndex INTEGER,
    lcsStatusComPortsDevEntryDeviceType INTEGER,
    lcsStatusComPortsDevEntryBus INTEGER,
    lcsStatusComPortsDevEntryDevice INTEGER,
    lcsStatusComPortsDevEntryVendor INTEGER,
    lcsStatusComPortsDevEntryUsbDriver INTEGER,
    lcsStatusComPortsDevEntryState INTEGER,
    lcsStatusComPortsDevEntryFirmwareVersion DisplayString,
    lcsStatusComPortsDevEntryServ INTEGER,
    lcsStatusComPortsDevEntryFullName DisplayString
}

-- {COLUMN} 1712.1.67.1.1.1
lcsStatusComPortsDevEntryIndex OBJECT-TYPE
    SYNTAX     INTEGER (0..2147483647)
    MAX-ACCESS read-only
    STATUS     current
    DESCRIPTION
        "-- empty --"
    ::= { lcsStatusComPortsDevEntry 1 }

-- {COLUMN} 1712.1.67.1.1.2
lcsStatusComPortsDevEntryDeviceType OBJECT-TYPE
    SYNTAX     INTEGER
      {
        eOutbandModem (2),
        eOutband (1),
        eSierraDirectIp (53),
        eOptionIcon (17),
        eNovatelMerlinMc950d (26),
        eSierraCompass885 (39),
        eSierraAircard875u (30),
        eHuaweiE172E220E870 (31),
        eHuaweiE612E630E1750 (21),
        eHuaweiE1750 (57),
        eHuaweiE182 (54),
        eHuaweiK3765 (51),
        eHuaweiK4505 (49),
        e4gSystemsUxs1 (23),
        eBelkinF5u103 (33),
        eProlific2303 (34),
        eFtdi8u232am (35),
        eSierraAircard501 (46),
        eNokiaCs19 (59),
        eHuaweiE398 (60),
        eHuaweiE352 (64),
        eHuaweiE1550 (61)
      }
    MAX-ACCESS read-only
    STATUS     current
    DESCRIPTION
        "-- empty --"
    ::= { lcsStatusComPortsDevEntry 2 }

-- {COLUMN} 1712.1.67.1.1.3
lcsStatusComPortsDevEntryBus OBJECT-TYPE
    SYNTAX     INTEGER
      {
        eOutband (1),
        eCardbus (2),
        eUsb (3),
        eVirtual (4)
      }
    MAX-ACCESS read-only
    STATUS     current
    DESCRIPTION
        "-- empty --"
    ::= { lcsStatusComPortsDevEntry 3 }

-- {COLUMN} 1712.1.67.1.1.4
lcsStatusComPortsDevEntryDevice OBJECT-TYPE
    SYNTAX     INTEGER (0..65535)
    MAX-ACCESS read-only
    STATUS     current
    DESCRIPTION
        "-- empty --"
    ::= { lcsStatusComPortsDevEntry 4 }

-- {COLUMN} 1712.1.67.1.1.5
lcsStatusComPortsDevEntryVendor OBJECT-TYPE
    SYNTAX     INTEGER (0..65535)
    MAX-ACCESS read-only
    STATUS     current
    DESCRIPTION
        "-- empty --"
    ::= { lcsStatusComPortsDevEntry 5 }

-- {COLUMN} 1712.1.67.1.1.11
lcsStatusComPortsDevEntryUsbDriver OBJECT-TYPE
    SYNTAX     INTEGER
      {
        eNone (0),
        eUbsa (1),
        eUchcom (2),
        eUftdi (3),
        eUgensa (4),
        eUhmodem (5),
        eUkyopon (6),
        eUplcom (7),
        eUslsa (8),
        eUcdcacm (10)
      }
    MAX-ACCESS read-only
    STATUS     current
    DESCRIPTION
        "-- empty --"
    ::= { lcsStatusComPortsDevEntry 11 }

-- {COLUMN} 1712.1.67.1.1.13
lcsStatusComPortsDevEntryState OBJECT-TYPE
    SYNTAX     INTEGER
      {
        eUnknown (0),
        eInitialize (1),
        eWaitForFirmware (2),
        eReady (3),
        eInUse (4),
        eExclusive (5),
        eInitialize2 (6),
        eResetting (7)
      }
    MAX-ACCESS read-only
    STATUS     current
    DESCRIPTION
        "-- empty --"
    ::= { lcsStatusComPortsDevEntry 13 }

-- {COLUMN} 1712.1.67.1.1.14
lcsStatusComPortsDevEntryFirmwareVersion OBJECT-TYPE
    SYNTAX     DisplayString (SIZE(0..63))
    MAX-ACCESS read-only
    STATUS     current
    DESCRIPTION
        "-- empty --"
    ::= { lcsStatusComPortsDevEntry 14 }

-- {COLUMN} 1712.1.67.1.1.15
lcsStatusComPortsDevEntryServ OBJECT-TYPE
    SYNTAX     INTEGER
      {
        eWan (1),
        eCOMPortServ (2)
      }
    MAX-ACCESS read-only
    STATUS     current
    DESCRIPTION
        ""
    ::= { lcsStatusComPortsDevEntry 15 }

-- {COLUMN} 1712.1.67.1.1.99
lcsStatusComPortsDevEntryFullName OBJECT-TYPE
    SYNTAX     DisplayString (SIZE(0..31))
    MAX-ACCESS read-only
    STATUS     current
    DESCRIPTION
        "-- empty --"
    ::= { lcsStatusComPortsDevEntry 99 }

-- {OID} 1712.1.67.2
lcsStatusComPortsComPortServer OBJECT IDENTIFIER ::= { lcsStatusComPorts 2 }

-- {TABLE} 1712.1.67.2.1
lcsStatusComPortsComPortServerNetworkStatusTable OBJECT-TYPE
    SYNTAX     SEQUENCE OF LcsStatusComPortsComPortServerNetworkStatusEntry
    MAX-ACCESS not-accessible
    STATUS     current
    DESCRIPTION
        "-- empty --"
    ::= { lcsStatusComPortsComPortServer 1 }

-- {ENTRY} 1712.1.67.2.1.1
lcsStatusComPortsComPortServerNetworkStatusEntry OBJECT-TYPE
    SYNTAX     LcsStatusComPortsComPortServerNetworkStatusEntry
    MAX-ACCESS not-accessible
    STATUS     current
    DESCRIPTION
        ""
    INDEX {
        lcsStatusComPortsComPortServerNetworkStatusEntryDeviceType,
        lcsStatusComPortsComPortServerNetworkStatusEntryPortNumber
    }
    ::= { lcsStatusComPortsComPortServerNetworkStatusTable 1 }

-- {SEQUENCE}
LcsStatusComPortsComPortServerNetworkStatusEntry ::= SEQUENCE {
    lcsStatusComPortsComPortServerNetworkStatusEntryDeviceType INTEGER,
    lcsStatusComPortsComPortServerNetworkStatusEntryPortNumber INTEGER,
    lcsStatusComPortsComPortServerNetworkStatusEntryFullName DisplayString,
    lcsStatusComPortsComPortServerNetworkStatusEntryConnectionStatus INTEGER,
    lcsStatusComPortsComPortServerNetworkStatusEntryLastError INTEGER,
    lcsStatusComPortsComPortServerNetworkStatusEntryRemoteAddress IpAddress,
    lcsStatusComPortsComPortServerNetworkStatusEntryLocalPort INTEGER,
    lcsStatusComPortsComPortServerNetworkStatusEntryRemotePort INTEGER
}

-- {COLUMN} 1712.1.67.2.1.1.1
lcsStatusComPortsComPortServerNetworkStatusEntryDeviceType OBJECT-TYPE
    SYNTAX     INTEGER
      {
        eOutband (1),
        eBelkinF5u103 (33),
        eProlific2303 (34),
        eFtdi8u232am (35)
      }
    MAX-ACCESS read-only
    STATUS     current
    DESCRIPTION
        "-- empty --"
    ::= { lcsStatusComPortsComPortServerNetworkStatusEntry 1 }

-- {COLUMN} 1712.1.67.2.1.1.2
lcsStatusComPortsComPortServerNetworkStatusEntryPortNumber OBJECT-TYPE
    SYNTAX     INTEGER (0..255)
    MAX-ACCESS read-only
    STATUS     current
    DESCRIPTION
        "-- empty --"
    ::= { lcsStatusComPortsComPortServerNetworkStatusEntry 2 }

-- {COLUMN} 1712.1.67.2.1.1.99
lcsStatusComPortsComPortServerNetworkStatusEntryFullName OBJECT-TYPE
    SYNTAX     DisplayString (SIZE(0..255))
    MAX-ACCESS read-only
    STATUS     current
    DESCRIPTION
        "-- empty --"
    ::= { lcsStatusComPortsComPortServerNetworkStatusEntry 99 }

-- {COLUMN} 1712.1.67.2.1.1.4
lcsStatusComPortsComPortServerNetworkStatusEntryConnectionStatus OBJECT-TYPE
    SYNTAX     INTEGER
      {
        eIdle (0),
        eListening (1),
        eConnecting (2),
        eConnected (3),
        eNotListening (4),
        eConErrBackoff (5)
      }
    MAX-ACCESS read-only
    STATUS     current
    DESCRIPTION
        "-- empty --"
    ::= { lcsStatusComPortsComPortServerNetworkStatusEntry 4 }

-- {COLUMN} 1712.1.67.2.1.1.5
lcsStatusComPortsComPortServerNetworkStatusEntryLastError OBJECT-TYPE
    SYNTAX     INTEGER
      {
        eNone (0),
        eDnsError (1),
        eTCPConnErr (2),
        eRemDisc (3)
      }
    MAX-ACCESS read-only
    STATUS     current
    DESCRIPTION
        "-- empty --"
    ::= { lcsStatusComPortsComPortServerNetworkStatusEntry 5 }

-- {COLUMN} 1712.1.67.2.1.1.6
lcsStatusComPortsComPortServerNetworkStatusEntryRemoteAddress OBJECT-TYPE
    SYNTAX     IpAddress
    MAX-ACCESS read-only
    STATUS     current
    DESCRIPTION
        "-- empty --"
    ::= { lcsStatusComPortsComPortServerNetworkStatusEntry 6 }

-- {COLUMN} 1712.1.67.2.1.1.7
lcsStatusComPortsComPortServerNetworkStatusEntryLocalPort OBJECT-TYPE
    SYNTAX     INTEGER (0..65535)
    MAX-ACCESS read-only
    STATUS     current
    DESCRIPTION
        "-- empty --"
    ::= { lcsStatusComPortsComPortServerNetworkStatusEntry 7 }

-- {COLUMN} 1712.1.67.2.1.1.8
lcsStatusComPortsComPortServerNetworkStatusEntryRemotePort OBJECT-TYPE
    SYNTAX     INTEGER (0..65535)
    MAX-ACCESS read-only
    STATUS     current
    DESCRIPTION
        "-- empty --"
    ::= { lcsStatusComPortsComPortServerNetworkStatusEntry 8 }

-- {TABLE} 1712.1.67.2.2
lcsStatusComPortsComPortServerComPortStatusTable OBJECT-TYPE
    SYNTAX     SEQUENCE OF LcsStatusComPortsComPortServerComPortStatusEntry
    MAX-ACCESS not-accessible
    STATUS     current
    DESCRIPTION
        "-- empty --"
    ::= { lcsStatusComPortsComPortServer 2 }

-- {ENTRY} 1712.1.67.2.2.1
lcsStatusComPortsComPortServerComPortStatusEntry OBJECT-TYPE
    SYNTAX     LcsStatusComPortsComPortServerComPortStatusEntry
    MAX-ACCESS not-accessible
    STATUS     current
    DESCRIPTION
        ""
    INDEX {
        lcsStatusComPortsComPortServerComPortStatusEntryDeviceType,
        lcsStatusComPortsComPortServerComPortStatusEntryPortNumber
    }
    ::= { lcsStatusComPortsComPortServerComPortStatusTable 1 }

-- {SEQUENCE}
LcsStatusComPortsComPortServerComPortStatusEntry ::= SEQUENCE {
    lcsStatusComPortsComPortServerComPortStatusEntryDeviceType INTEGER,
    lcsStatusComPortsComPortServerComPortStatusEntryPortNumber INTEGER,
    lcsStatusComPortsComPortServerComPortStatusEntryFullName DisplayString,
    lcsStatusComPortsComPortServerComPortStatusEntryInterfaceStatus INTEGER,
    lcsStatusComPortsComPortServerComPortStatusEntryBitRate INTEGER,
    lcsStatusComPortsComPortServerComPortStatusEntryDataBits INTEGER,
    lcsStatusComPortsComPortServerComPortStatusEntryParity INTEGER,
    lcsStatusComPortsComPortServerComPortStatusEntryStopBits INTEGER,
    lcsStatusComPortsComPortServerComPortStatusEntryHandshake INTEGER
}

-- {COLUMN} 1712.1.67.2.2.1.1
lcsStatusComPortsComPortServerComPortStatusEntryDeviceType OBJECT-TYPE
    SYNTAX     INTEGER
      {
        eOutband (1),
        eBelkinF5u103 (33),
        eProlific2303 (34),
        eFtdi8u232am (35)
      }
    MAX-ACCESS read-only
    STATUS     current
    DESCRIPTION
        "-- empty --"
    ::= { lcsStatusComPortsComPortServerComPortStatusEntry 1 }

-- {COLUMN} 1712.1.67.2.2.1.2
lcsStatusComPortsComPortServerComPortStatusEntryPortNumber OBJECT-TYPE
    SYNTAX     INTEGER (0..255)
    MAX-ACCESS read-only
    STATUS     current
    DESCRIPTION
        "-- empty --"
    ::= { lcsStatusComPortsComPortServerComPortStatusEntry 2 }

-- {COLUMN} 1712.1.67.2.2.1.99
lcsStatusComPortsComPortServerComPortStatusEntryFullName OBJECT-TYPE
    SYNTAX     DisplayString (SIZE(0..255))
    MAX-ACCESS read-only
    STATUS     current
    DESCRIPTION
        "-- empty --"
    ::= { lcsStatusComPortsComPortServerComPortStatusEntry 99 }

-- {COLUMN} 1712.1.67.2.2.1.4
lcsStatusComPortsComPortServerComPortStatusEntryInterfaceStatus OBJECT-TYPE
    SYNTAX     INTEGER
      {
        eNotPresent (0),
        eNotReady (1),
        eReady (2)
      }
    MAX-ACCESS read-only
    STATUS     current
    DESCRIPTION
        "-- empty --"
    ::= { lcsStatusComPortsComPortServerComPortStatusEntry 4 }

-- {COLUMN} 1712.1.67.2.2.1.5
lcsStatusComPortsComPortServerComPortStatusEntryBitRate OBJECT-TYPE
    SYNTAX     INTEGER
      {
        e110 (110),
        e300 (300),
        e600 (600),
        e1200 (1200),
        e2400 (2400),
        e4800 (4800),
        e9600 (9600),
        e19200 (19200),
        e38400 (38400),
        e57600 (57600),
        e115200 (115200),
        e125000 (125000),
        e230400 (230400)
      }
    MAX-ACCESS read-only
    STATUS     current
    DESCRIPTION
        "-- empty --"
    ::= { lcsStatusComPortsComPortServerComPortStatusEntry 5 }

-- {COLUMN} 1712.1.67.2.2.1.6
lcsStatusComPortsComPortServerComPortStatusEntryDataBits OBJECT-TYPE
    SYNTAX     INTEGER
      {
        e7 (7),
        e8 (8)
      }
    MAX-ACCESS read-only
    STATUS     current
    DESCRIPTION
        "-- empty --"
    ::= { lcsStatusComPortsComPortServerComPortStatusEntry 6 }

-- {COLUMN} 1712.1.67.2.2.1.7
lcsStatusComPortsComPortServerComPortStatusEntryParity OBJECT-TYPE
    SYNTAX     INTEGER
      {
        eNone (1),
        eOdd (2),
        eEven (3)
      }
    MAX-ACCESS read-only
    STATUS     current
    DESCRIPTION
        "-- empty --"
    ::= { lcsStatusComPortsComPortServerComPortStatusEntry 7 }

-- {COLUMN} 1712.1.67.2.2.1.8
lcsStatusComPortsComPortServerComPortStatusEntryStopBits OBJECT-TYPE
    SYNTAX     INTEGER
      {
        e1 (1),
        e2 (2)
      }
    MAX-ACCESS read-only
    STATUS     current
    DESCRIPTION
        "-- empty --"
    ::= { lcsStatusComPortsComPortServerComPortStatusEntry 8 }

-- {COLUMN} 1712.1.67.2.2.1.9
lcsStatusComPortsComPortServerComPortStatusEntryHandshake OBJECT-TYPE
    SYNTAX     INTEGER
      {
        eNone (0),
        eRtsCts (1)
      }
    MAX-ACCESS read-only
    STATUS     current
    DESCRIPTION
        "-- empty --"
    ::= { lcsStatusComPortsComPortServerComPortStatusEntry 9 }

-- {TABLE} 1712.1.67.2.3
lcsStatusComPortsComPortServerByteCountersTable OBJECT-TYPE
    SYNTAX     SEQUENCE OF LcsStatusComPortsComPortServerByteCountersEntry
    MAX-ACCESS not-accessible
    STATUS     current
    DESCRIPTION
        "-- empty --"
    ::= { lcsStatusComPortsComPortServer 3 }

-- {ENTRY} 1712.1.67.2.3.1
lcsStatusComPortsComPortServerByteCountersEntry OBJECT-TYPE
    SYNTAX     LcsStatusComPortsComPortServerByteCountersEntry
    MAX-ACCESS not-accessible
    STATUS     current
    DESCRIPTION
        ""
    INDEX {
        lcsStatusComPortsComPortServerByteCountersEntryDeviceType,
        lcsStatusComPortsComPortServerByteCountersEntryPortNumber
    }
    ::= { lcsStatusComPortsComPortServerByteCountersTable 1 }

-- {SEQUENCE}
LcsStatusComPortsComPortServerByteCountersEntry ::= SEQUENCE {
    lcsStatusComPortsComPortServerByteCountersEntryDeviceType INTEGER,
    lcsStatusComPortsComPortServerByteCountersEntryPortNumber INTEGER,
    lcsStatusComPortsComPortServerByteCountersEntryFullName DisplayString,
    lcsStatusComPortsComPortServerByteCountersEntrySerialTx INTEGER,
    lcsStatusComPortsComPortServerByteCountersEntrySerialRx INTEGER,
    lcsStatusComPortsComPortServerByteCountersEntryNetworkTx INTEGER,
    lcsStatusComPortsComPortServerByteCountersEntryNetworkRx INTEGER
}

-- {COLUMN} 1712.1.67.2.3.1.1
lcsStatusComPortsComPortServerByteCountersEntryDeviceType OBJECT-TYPE
    SYNTAX     INTEGER
      {
        eOutband (1),
        eBelkinF5u103 (33),
        eProlific2303 (34),
        eFtdi8u232am (35)
      }
    MAX-ACCESS read-only
    STATUS     current
    DESCRIPTION
        "-- empty --"
    ::= { lcsStatusComPortsComPortServerByteCountersEntry 1 }

-- {COLUMN} 1712.1.67.2.3.1.2
lcsStatusComPortsComPortServerByteCountersEntryPortNumber OBJECT-TYPE
    SYNTAX     INTEGER (0..255)
    MAX-ACCESS read-only
    STATUS     current
    DESCRIPTION
        "-- empty --"
    ::= { lcsStatusComPortsComPortServerByteCountersEntry 2 }

-- {COLUMN} 1712.1.67.2.3.1.99
lcsStatusComPortsComPortServerByteCountersEntryFullName OBJECT-TYPE
    SYNTAX     DisplayString (SIZE(0..255))
    MAX-ACCESS read-only
    STATUS     current
    DESCRIPTION
        "-- empty --"
    ::= { lcsStatusComPortsComPortServerByteCountersEntry 99 }

-- {COLUMN} 1712.1.67.2.3.1.4
lcsStatusComPortsComPortServerByteCountersEntrySerialTx OBJECT-TYPE
    SYNTAX     INTEGER (0..2147483647)
    MAX-ACCESS read-only
    STATUS     current
    DESCRIPTION
        "-- empty --"
    ::= { lcsStatusComPortsComPortServerByteCountersEntry 4 }

-- {COLUMN} 1712.1.67.2.3.1.5
lcsStatusComPortsComPortServerByteCountersEntrySerialRx OBJECT-TYPE
    SYNTAX     INTEGER (0..2147483647)
    MAX-ACCESS read-only
    STATUS     current
    DESCRIPTION
        "-- empty --"
    ::= { lcsStatusComPortsComPortServerByteCountersEntry 5 }

-- {COLUMN} 1712.1.67.2.3.1.6
lcsStatusComPortsComPortServerByteCountersEntryNetworkTx OBJECT-TYPE
    SYNTAX     INTEGER (0..2147483647)
    MAX-ACCESS read-only
    STATUS     current
    DESCRIPTION
        "-- empty --"
    ::= { lcsStatusComPortsComPortServerByteCountersEntry 6 }

-- {COLUMN} 1712.1.67.2.3.1.7
lcsStatusComPortsComPortServerByteCountersEntryNetworkRx OBJECT-TYPE
    SYNTAX     INTEGER (0..2147483647)
    MAX-ACCESS read-only
    STATUS     current
    DESCRIPTION
        "-- empty --"
    ::= { lcsStatusComPortsComPortServerByteCountersEntry 7 }

-- {TABLE} 1712.1.67.2.4
lcsStatusComPortsComPortServerComPortErrorsTable OBJECT-TYPE
    SYNTAX     SEQUENCE OF LcsStatusComPortsComPortServerComPortErrorsEntry
    MAX-ACCESS not-accessible
    STATUS     current
    DESCRIPTION
        "-- empty --"
    ::= { lcsStatusComPortsComPortServer 4 }

-- {ENTRY} 1712.1.67.2.4.1
lcsStatusComPortsComPortServerComPortErrorsEntry OBJECT-TYPE
    SYNTAX     LcsStatusComPortsComPortServerComPortErrorsEntry
    MAX-ACCESS not-accessible
    STATUS     current
    DESCRIPTION
        ""
    INDEX {
        lcsStatusComPortsComPortServerComPortErrorsEntryDeviceType,
        lcsStatusComPortsComPortServerComPortErrorsEntryPortNumber
    }
    ::= { lcsStatusComPortsComPortServerComPortErrorsTable 1 }

-- {SEQUENCE}
LcsStatusComPortsComPortServerComPortErrorsEntry ::= SEQUENCE {
    lcsStatusComPortsComPortServerComPortErrorsEntryDeviceType INTEGER,
    lcsStatusComPortsComPortServerComPortErrorsEntryPortNumber INTEGER,
    lcsStatusComPortsComPortServerComPortErrorsEntryFullName DisplayString,
    lcsStatusComPortsComPortServerComPortErrorsEntryParityErrors INTEGER,
    lcsStatusComPortsComPortServerComPortErrorsEntryFramingErrors INTEGER,
    lcsStatusComPortsComPortServerComPortErrorsEntryRxLostErrors INTEGER
}

-- {COLUMN} 1712.1.67.2.4.1.1
lcsStatusComPortsComPortServerComPortErrorsEntryDeviceType OBJECT-TYPE
    SYNTAX     INTEGER
      {
        eOutband (1),
        eBelkinF5u103 (33),
        eProlific2303 (34),
        eFtdi8u232am (35)
      }
    MAX-ACCESS read-only
    STATUS     current
    DESCRIPTION
        "-- empty --"
    ::= { lcsStatusComPortsComPortServerComPortErrorsEntry 1 }

-- {COLUMN} 1712.1.67.2.4.1.2
lcsStatusComPortsComPortServerComPortErrorsEntryPortNumber OBJECT-TYPE
    SYNTAX     INTEGER (0..255)
    MAX-ACCESS read-only
    STATUS     current
    DESCRIPTION
        "-- empty --"
    ::= { lcsStatusComPortsComPortServerComPortErrorsEntry 2 }

-- {COLUMN} 1712.1.67.2.4.1.99
lcsStatusComPortsComPortServerComPortErrorsEntryFullName OBJECT-TYPE
    SYNTAX     DisplayString (SIZE(0..255))
    MAX-ACCESS read-only
    STATUS     current
    DESCRIPTION
        "-- empty --"
    ::= { lcsStatusComPortsComPortServerComPortErrorsEntry 99 }

-- {COLUMN} 1712.1.67.2.4.1.4
lcsStatusComPortsComPortServerComPortErrorsEntryParityErrors OBJECT-TYPE
    SYNTAX     INTEGER (0..2147483647)
    MAX-ACCESS read-only
    STATUS     current
    DESCRIPTION
        "-- empty --"
    ::= { lcsStatusComPortsComPortServerComPortErrorsEntry 4 }

-- {COLUMN} 1712.1.67.2.4.1.5
lcsStatusComPortsComPortServerComPortErrorsEntryFramingErrors OBJECT-TYPE
    SYNTAX     INTEGER (0..2147483647)
    MAX-ACCESS read-only
    STATUS     current
    DESCRIPTION
        "-- empty --"
    ::= { lcsStatusComPortsComPortServerComPortErrorsEntry 5 }

-- {COLUMN} 1712.1.67.2.4.1.6
lcsStatusComPortsComPortServerComPortErrorsEntryRxLostErrors OBJECT-TYPE
    SYNTAX     INTEGER (0..2147483647)
    MAX-ACCESS read-only
    STATUS     current
    DESCRIPTION
        "-- empty --"
    ::= { lcsStatusComPortsComPortServerComPortErrorsEntry 6 }

-- {TABLE} 1712.1.67.2.5
lcsStatusComPortsComPortServerConnTable OBJECT-TYPE
    SYNTAX     SEQUENCE OF LcsStatusComPortsComPortServerConnEntry
    MAX-ACCESS not-accessible
    STATUS     current
    DESCRIPTION
        ""
    ::= { lcsStatusComPortsComPortServer 5 }

-- {ENTRY} 1712.1.67.2.5.1
lcsStatusComPortsComPortServerConnEntry OBJECT-TYPE
    SYNTAX     LcsStatusComPortsComPortServerConnEntry
    MAX-ACCESS not-accessible
    STATUS     current
    DESCRIPTION
        ""
    INDEX {
        lcsStatusComPortsComPortServerConnEntryDeviceType,
        lcsStatusComPortsComPortServerConnEntryPortNumber
    }
    ::= { lcsStatusComPortsComPortServerConnTable 1 }

-- {SEQUENCE}
LcsStatusComPortsComPortServerConnEntry ::= SEQUENCE {
    lcsStatusComPortsComPortServerConnEntryDeviceType INTEGER,
    lcsStatusComPortsComPortServerConnEntryPortNumber INTEGER,
    lcsStatusComPortsComPortServerConnEntryFullName DisplayString,
    lcsStatusComPortsComPortServerConnEntryServGrant INTEGER,
    lcsStatusComPortsComPortServerConnEntryServRej INTEGER,
    lcsStatusComPortsComPortServerConnEntryClntSucc INTEGER,
    lcsStatusComPortsComPortServerConnEntryClntDnsErr INTEGER,
    lcsStatusComPortsComPortServerConnEntryClntTcpErr INTEGER,
    lcsStatusComPortsComPortServerConnEntryClntRemDisc INTEGER
}

-- {COLUMN} 1712.1.67.2.5.1.1
lcsStatusComPortsComPortServerConnEntryDeviceType OBJECT-TYPE
    SYNTAX     INTEGER
      {
        eOutband (1),
        eBelkinF5u103 (33),
        eProlific2303 (34),
        eFtdi8u232am (35)
      }
    MAX-ACCESS read-only
    STATUS     current
    DESCRIPTION
        "-- empty --"
    ::= { lcsStatusComPortsComPortServerConnEntry 1 }

-- {COLUMN} 1712.1.67.2.5.1.2
lcsStatusComPortsComPortServerConnEntryPortNumber OBJECT-TYPE
    SYNTAX     INTEGER (0..255)
    MAX-ACCESS read-only
    STATUS     current
    DESCRIPTION
        "-- empty --"
    ::= { lcsStatusComPortsComPortServerConnEntry 2 }

-- {COLUMN} 1712.1.67.2.5.1.99
lcsStatusComPortsComPortServerConnEntryFullName OBJECT-TYPE
    SYNTAX     DisplayString (SIZE(0..255))
    MAX-ACCESS read-only
    STATUS     current
    DESCRIPTION
        "-- empty --"
    ::= { lcsStatusComPortsComPortServerConnEntry 99 }

-- {COLUMN} 1712.1.67.2.5.1.4
lcsStatusComPortsComPortServerConnEntryServGrant OBJECT-TYPE
    SYNTAX     INTEGER (0..2147483647)
    MAX-ACCESS read-only
    STATUS     current
    DESCRIPTION
        ""
    ::= { lcsStatusComPortsComPortServerConnEntry 4 }

-- {COLUMN} 1712.1.67.2.5.1.5
lcsStatusComPortsComPortServerConnEntryServRej OBJECT-TYPE
    SYNTAX     INTEGER (0..2147483647)
    MAX-ACCESS read-only
    STATUS     current
    DESCRIPTION
        ""
    ::= { lcsStatusComPortsComPortServerConnEntry 5 }

-- {COLUMN} 1712.1.67.2.5.1.6
lcsStatusComPortsComPortServerConnEntryClntSucc OBJECT-TYPE
    SYNTAX     INTEGER (0..2147483647)
    MAX-ACCESS read-only
    STATUS     current
    DESCRIPTION
        ""
    ::= { lcsStatusComPortsComPortServerConnEntry 6 }

-- {COLUMN} 1712.1.67.2.5.1.7
lcsStatusComPortsComPortServerConnEntryClntDnsErr OBJECT-TYPE
    SYNTAX     INTEGER (0..2147483647)
    MAX-ACCESS read-only
    STATUS     current
    DESCRIPTION
        ""
    ::= { lcsStatusComPortsComPortServerConnEntry 7 }

-- {COLUMN} 1712.1.67.2.5.1.8
lcsStatusComPortsComPortServerConnEntryClntTcpErr OBJECT-TYPE
    SYNTAX     INTEGER (0..2147483647)
    MAX-ACCESS read-only
    STATUS     current
    DESCRIPTION
        ""
    ::= { lcsStatusComPortsComPortServerConnEntry 8 }

-- {COLUMN} 1712.1.67.2.5.1.9
lcsStatusComPortsComPortServerConnEntryClntRemDisc OBJECT-TYPE
    SYNTAX     INTEGER (0..2147483647)
    MAX-ACCESS read-only
    STATUS     current
    DESCRIPTION
        ""
    ::= { lcsStatusComPortsComPortServerConnEntry 9 }

-- {SCALAR} 1712.1.67.2.99
lcsStatusComPortsComPortServerDeleteValues OBJECT-TYPE
    SYNTAX     DisplayString
    MAX-ACCESS read-write
    STATUS     current
    DESCRIPTION
        "-- empty --"
    ::= { lcsStatusComPortsComPortServer 99 }

-- {OID} 1712.1.51
lcsStatusEthernetPorts OBJECT IDENTIFIER ::= { lcsStatus 51 }

-- {TABLE} 1712.1.51.1
lcsStatusEthernetPortsPortsTable OBJECT-TYPE
    SYNTAX     SEQUENCE OF LcsStatusEthernetPortsPortsEntry
    MAX-ACCESS not-accessible
    STATUS     current
    DESCRIPTION
        "-- empty --"
    ::= { lcsStatusEthernetPorts 1 }

-- {ENTRY} 1712.1.51.1.1
lcsStatusEthernetPortsPortsEntry OBJECT-TYPE
    SYNTAX     LcsStatusEthernetPortsPortsEntry
    MAX-ACCESS not-accessible
    STATUS     current
    DESCRIPTION
        ""
    INDEX {
        lcsStatusEthernetPortsPortsEntryPort
    }
    ::= { lcsStatusEthernetPortsPortsTable 1 }

-- {SEQUENCE}
LcsStatusEthernetPortsPortsEntry ::= SEQUENCE {
    lcsStatusEthernetPortsPortsEntryPort INTEGER,
    lcsStatusEthernetPortsPortsEntryAssignment INTEGER,
    lcsStatusEthernetPortsPortsEntryPrivateMode INTEGER,
    lcsStatusEthernetPortsPortsEntryLinkActive INTEGER,
    lcsStatusEthernetPortsPortsEntryConnector INTEGER,
    lcsStatusEthernetPortsPortsEntryAutoNegotiation INTEGER,
    lcsStatusEthernetPortsPortsEntryFlowControl INTEGER,
    lcsStatusEthernetPortsPortsEntryMdiMode INTEGER
}

-- {COLUMN} 1712.1.51.1.1.1
lcsStatusEthernetPortsPortsEntryPort OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsStatusEthernetPortsPortsEntry 1 }

-- {COLUMN} 1712.1.51.1.1.7
lcsStatusEthernetPortsPortsEntryAssignment OBJECT-TYPE
    SYNTAX     INTEGER
      {
        eDsl1 (512),
        eDsl2 (513),
        eDsl3 (514),
        eDsl4 (515),
        eLan1 (0),
        eLan2 (1),
        eLan3 (2),
        eLan4 (3),
        eIdle (65533),
        eMonitor (65534),
        ePowerDown (65535)
      }
    MAX-ACCESS read-only
    STATUS     current
    DESCRIPTION
        "-- empty --"
    ::= { lcsStatusEthernetPortsPortsEntry 7 }

-- {COLUMN} 1712.1.51.1.1.9
lcsStatusEthernetPortsPortsEntryPrivateMode OBJECT-TYPE
    SYNTAX     INTEGER
      {
        eNo (0),
        eYes (1)
      }
    MAX-ACCESS read-only
    STATUS     current
    DESCRIPTION
        "-- empty --"
    ::= { lcsStatusEthernetPortsPortsEntry 9 }

-- {COLUMN} 1712.1.51.1.1.3
lcsStatusEthernetPortsPortsEntryLinkActive OBJECT-TYPE
    SYNTAX     INTEGER
      {
        eNo (0),
        eYes (1)
      }
    MAX-ACCESS read-only
    STATUS     current
    DESCRIPTION
        "-- empty --"
    ::= { lcsStatusEthernetPortsPortsEntry 3 }

-- {COLUMN} 1712.1.51.1.1.4
lcsStatusEthernetPortsPortsEntryConnector OBJECT-TYPE
    SYNTAX     INTEGER
      {
        eNone (0),
        e10bT (1),
        eFd10bTx (2),
        e100bTx (3),
        eFd100bTx (4)
      }
    MAX-ACCESS read-only
    STATUS     current
    DESCRIPTION
        "-- empty --"
    ::= { lcsStatusEthernetPortsPortsEntry 4 }

-- {COLUMN} 1712.1.51.1.1.10
lcsStatusEthernetPortsPortsEntryAutoNegotiation OBJECT-TYPE
    SYNTAX     INTEGER
      {
        ePending (0),
        eCompleted (1),
        eDisabled (2),
        eNotAvailable (3)
      }
    MAX-ACCESS read-only
    STATUS     current
    DESCRIPTION
        "-- empty --"
    ::= { lcsStatusEthernetPortsPortsEntry 10 }

-- {COLUMN} 1712.1.51.1.1.8
lcsStatusEthernetPortsPortsEntryFlowControl OBJECT-TYPE
    SYNTAX     INTEGER
      {
        eNo (0),
        eYes (1),
        eTxOnly (3),
        eRxOnly (4)
      }
    MAX-ACCESS read-only
    STATUS     current
    DESCRIPTION
        "-- empty --"
    ::= { lcsStatusEthernetPortsPortsEntry 8 }

-- {COLUMN} 1712.1.51.1.1.6
lcsStatusEthernetPortsPortsEntryMdiMode OBJECT-TYPE
    SYNTAX     INTEGER
      {
        eMdi (0),
        eMdix (1)
      }
    MAX-ACCESS read-only
    STATUS     current
    DESCRIPTION
        "-- empty --"
    ::= { lcsStatusEthernetPortsPortsEntry 6 }

-- {SCALAR} 1712.1.51.2
lcsStatusEthernetPortsCableTest OBJECT-TYPE
    SYNTAX     DisplayString
    MAX-ACCESS read-write
    STATUS     current
    DESCRIPTION
        "-- empty --"
    ::= { lcsStatusEthernetPorts 2 }

-- {TABLE} 1712.1.51.3
lcsStatusEthernetPortsCableTestResultsTable OBJECT-TYPE
    SYNTAX     SEQUENCE OF LcsStatusEthernetPortsCableTestResultsEntry
    MAX-ACCESS not-accessible
    STATUS     current
    DESCRIPTION
        "-- empty --"
    ::= { lcsStatusEthernetPorts 3 }

-- {ENTRY} 1712.1.51.3.1
lcsStatusEthernetPortsCableTestResultsEntry OBJECT-TYPE
    SYNTAX     LcsStatusEthernetPortsCableTestResultsEntry
    MAX-ACCESS not-accessible
    STATUS     current
    DESCRIPTION
        ""
    INDEX {
        lcsStatusEthernetPortsCableTestResultsEntryIfc
    }
    ::= { lcsStatusEthernetPortsCableTestResultsTable 1 }

-- {SEQUENCE}
LcsStatusEthernetPortsCableTestResultsEntry ::= SEQUENCE {
    lcsStatusEthernetPortsCableTestResultsEntryIfc INTEGER,
    lcsStatusEthernetPortsCableTestResultsEntryTxStatus INTEGER,
    lcsStatusEthernetPortsCableTestResultsEntryTxDistance DisplayString,
    lcsStatusEthernetPortsCableTestResultsEntryRxStatus INTEGER,
    lcsStatusEthernetPortsCableTestResultsEntryRxDistance DisplayString
}

-- {COLUMN} 1712.1.51.3.1.1
lcsStatusEthernetPortsCableTestResultsEntryIfc OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsStatusEthernetPortsCableTestResultsEntry 1 }

-- {COLUMN} 1712.1.51.3.1.4
lcsStatusEthernetPortsCableTestResultsEntryTxStatus OBJECT-TYPE
    SYNTAX     INTEGER
      {
        eUnknown (0),
        eOk (1),
        eOpen (2),
        eShort (3),
        eImpedanceFault (4),
        eFail (5),
        eBusy (6),
        eLinkUp (7)
      }
    MAX-ACCESS read-only
    STATUS     current
    DESCRIPTION
        "-- empty --"
    ::= { lcsStatusEthernetPortsCableTestResultsEntry 4 }

-- {COLUMN} 1712.1.51.3.1.5
lcsStatusEthernetPortsCableTestResultsEntryTxDistance OBJECT-TYPE
    SYNTAX     DisplayString (SIZE(0..10))
    MAX-ACCESS read-only
    STATUS     current
    DESCRIPTION
        "-- empty --"
    ::= { lcsStatusEthernetPortsCableTestResultsEntry 5 }

-- {COLUMN} 1712.1.51.3.1.2
lcsStatusEthernetPortsCableTestResultsEntryRxStatus OBJECT-TYPE
    SYNTAX     INTEGER
      {
        eUnknown (0),
        eOk (1),
        eOpen (2),
        eShort (3),
        eImpedanceFault (4),
        eFail (5),
        eBusy (6),
        eLinkUp (7)
      }
    MAX-ACCESS read-only
    STATUS     current
    DESCRIPTION
        "-- empty --"
    ::= { lcsStatusEthernetPortsCableTestResultsEntry 2 }

-- {COLUMN} 1712.1.51.3.1.3
lcsStatusEthernetPortsCableTestResultsEntryRxDistance OBJECT-TYPE
    SYNTAX     DisplayString (SIZE(0..10))
    MAX-ACCESS read-only
    STATUS     current
    DESCRIPTION
        "-- empty --"
    ::= { lcsStatusEthernetPortsCableTestResultsEntry 3 }

-- {OID} 1712.2
lcsSetup OBJECT IDENTIFIER ::= { lancom-1711-plus 2 }

-- {SCALAR} 1712.2.1
lcsSetupName OBJECT-TYPE
    SYNTAX     DisplayString (SIZE(0..16))
    MAX-ACCESS read-write
    STATUS     current
    DESCRIPTION
        "-- empty --"
    ::= { lcsSetup 1 }

-- {OID} 1712.2.2
lcsSetupWan OBJECT IDENTIFIER ::= { lcsSetup 2 }

-- {TABLE} 1712.2.2.2
lcsSetupWanDialupPeersTable OBJECT-TYPE
    SYNTAX     SEQUENCE OF LcsSetupWanDialupPeersEntry
    MAX-ACCESS not-accessible
    STATUS     current
    DESCRIPTION
        "-- empty --"
    ::= { lcsSetupWan 2 }

-- {ENTRY} 1712.2.2.2.1
lcsSetupWanDialupPeersEntry OBJECT-TYPE
    SYNTAX     LcsSetupWanDialupPeersEntry
    MAX-ACCESS not-accessible
    STATUS     current
    DESCRIPTION
        ""
    INDEX {
        lcsSetupWanDialupPeersEntryPeer
    }
    ::= { lcsSetupWanDialupPeersTable 1 }

-- {SEQUENCE}
LcsSetupWanDialupPeersEntry ::= SEQUENCE {
    lcsSetupWanDialupPeersEntryPeer DisplayString,
    lcsSetupWanDialupPeersEntryDialupRemote DisplayString,
    lcsSetupWanDialupPeersEntryB1Dt INTEGER,
    lcsSetupWanDialupPeersEntryB2Dt INTEGER,
    lcsSetupWanDialupPeersEntryWanLayer DisplayString,
    lcsSetupWanDialupPeersEntryCallback INTEGER
}

-- {COLUMN} 1712.2.2.2.1.1
lcsSetupWanDialupPeersEntryPeer OBJECT-TYPE
    SYNTAX     DisplayString (SIZE(0..16))
    MAX-ACCESS read-write
    STATUS     current
    DESCRIPTION
        "-- empty --"
    ::= { lcsSetupWanDialupPeersEntry 1 }

-- {COLUMN} 1712.2.2.2.1.2
lcsSetupWanDialupPeersEntryDialupRemote OBJECT-TYPE
    SYNTAX     DisplayString (SIZE(0..31))
    MAX-ACCESS read-write
    STATUS     current
    DESCRIPTION
        "-- empty --"
    ::= { lcsSetupWanDialupPeersEntry 2 }

-- {COLUMN} 1712.2.2.2.1.3
lcsSetupWanDialupPeersEntryB1Dt OBJECT-TYPE
    SYNTAX     INTEGER (0..65535)
    MAX-ACCESS read-write
    STATUS     current
    DESCRIPTION
        "-- empty --"
    ::= { lcsSetupWanDialupPeersEntry 3 }

-- {COLUMN} 1712.2.2.2.1.4
lcsSetupWanDialupPeersEntryB2Dt OBJECT-TYPE
    SYNTAX     INTEGER (0..65535)
    MAX-ACCESS read-write
    STATUS     current
    DESCRIPTION
        "-- empty --"
    ::= { lcsSetupWanDialupPeersEntry 4 }

-- {COLUMN} 1712.2.2.2.1.5
lcsSetupWanDialupPeersEntryWanLayer OBJECT-TYPE
    SYNTAX     DisplayString (SIZE(0..9))
    MAX-ACCESS read-write
    STATUS     current
    DESCRIPTION
        "-- empty --"
    ::= { lcsSetupWanDialupPeersEntry 5 }

-- {COLUMN} 1712.2.2.2.1.6
lcsSetupWanDialupPeersEntryCallback OBJECT-TYPE
    SYNTAX     INTEGER
      {
        eNo (0),
        eAuto (1),
        eName (5),
        eFast (9),
        eLooser (2)
      }
    MAX-ACCESS read-write
    STATUS     current
    DESCRIPTION
        "-- empty --"
    ::= { lcsSetupWanDialupPeersEntry 6 }

-- {TABLE} 1712.2.2.3
lcsSetupWanRoundrobinTable OBJECT-TYPE
    SYNTAX     SEQUENCE OF LcsSetupWanRoundrobinEntry
    MAX-ACCESS not-accessible
    STATUS     current
    DESCRIPTION
        "-- empty --"
    ::= { lcsSetupWan 3 }

-- {ENTRY} 1712.2.2.3.1
lcsSetupWanRoundrobinEntry OBJECT-TYPE
    SYNTAX     LcsSetupWanRoundrobinEntry
    MAX-ACCESS not-accessible
    STATUS     current
    DESCRIPTION
        ""
    INDEX {
        lcsSetupWanRoundrobinEntryPeer
    }
    ::= { lcsSetupWanRoundrobinTable 1 }

-- {SEQUENCE}
LcsSetupWanRoundrobinEntry ::= SEQUENCE {
    lcsSetupWanRoundrobinEntryPeer DisplayString,
    lcsSetupWanRoundrobinEntryRoundRobin DisplayString,
    lcsSetupWanRoundrobinEntryHead INTEGER
}

-- {COLUMN} 1712.2.2.3.1.1
lcsSetupWanRoundrobinEntryPeer OBJECT-TYPE
    SYNTAX     DisplayString (SIZE(0..18))
    MAX-ACCESS read-write
    STATUS     current
    DESCRIPTION
        "-- empty --"
    ::= { lcsSetupWanRoundrobinEntry 1 }

-- {COLUMN} 1712.2.2.3.1.2
lcsSetupWanRoundrobinEntryRoundRobin OBJECT-TYPE
    SYNTAX     DisplayString (SIZE(0..53))
    MAX-ACCESS read-write
    STATUS     current
    DESCRIPTION
        "-- empty --"
    ::= { lcsSetupWanRoundrobinEntry 2 }

-- {COLUMN} 1712.2.2.3.1.3
lcsSetupWanRoundrobinEntryHead OBJECT-TYPE
    SYNTAX     INTEGER
      {
        eLast (0),
        eFirst (1)
      }
    MAX-ACCESS read-write
    STATUS     current
    DESCRIPTION
        "-- empty --"
    ::= { lcsSetupWanRoundrobinEntry 3 }

-- {TABLE} 1712.2.2.4
lcsSetupWanLayerTable OBJECT-TYPE
    SYNTAX     SEQUENCE OF LcsSetupWanLayerEntry
    MAX-ACCESS not-accessible
    STATUS     current
    DESCRIPTION
        "-- empty --"
    ::= { lcsSetupWan 4 }

-- {ENTRY} 1712.2.2.4.1
lcsSetupWanLayerEntry OBJECT-TYPE
    SYNTAX     LcsSetupWanLayerEntry
    MAX-ACCESS not-accessible
    STATUS     current
    DESCRIPTION
        ""
    INDEX {
        lcsSetupWanLayerEntryWanLayer
    }
    ::= { lcsSetupWanLayerTable 1 }

-- {SEQUENCE}
LcsSetupWanLayerEntry ::= SEQUENCE {
    lcsSetupWanLayerEntryWanLayer DisplayString,
    lcsSetupWanLayerEntryEncaps INTEGER,
    lcsSetupWanLayerEntryLay3 INTEGER,
    lcsSetupWanLayerEntryLay2 INTEGER,
    lcsSetupWanLayerEntryL2Opt INTEGER,
    lcsSetupWanLayerEntryLay1 INTEGER
}

-- {COLUMN} 1712.2.2.4.1.1
lcsSetupWanLayerEntryWanLayer OBJECT-TYPE
    SYNTAX     DisplayString (SIZE(0..9))
    MAX-ACCESS read-write
    STATUS     current
    DESCRIPTION
        "-- empty --"
    ::= { lcsSetupWanLayerEntry 1 }

-- {COLUMN} 1712.2.2.4.1.2
lcsSetupWanLayerEntryEncaps OBJECT-TYPE
    SYNTAX     INTEGER
      {
        eEther (0),
        eTrans (255)
      }
    MAX-ACCESS read-write
    STATUS     current
    DESCRIPTION
        "-- empty --"
    ::= { lcsSetupWanLayerEntry 2 }

-- {COLUMN} 1712.2.2.4.1.3
lcsSetupWanLayerEntryLay3 OBJECT-TYPE
    SYNTAX     INTEGER
      {
        ePpp (4),
        eAppp (5),
        eScppp (6),
        eScappp (7),
        eSctrans (8),
        eDhcp (9),
        eTRANS (255)
      }
    MAX-ACCESS read-write
    STATUS     current
    DESCRIPTION
        "-- empty --"
    ::= { lcsSetupWanLayerEntry 3 }

-- {COLUMN} 1712.2.2.4.1.4
lcsSetupWanLayerEntryLay2 OBJECT-TYPE
    SYNTAX     INTEGER
      {
        ePppoe (5),
        eX75lapb (0),
        eTrans (1)
      }
    MAX-ACCESS read-write
    STATUS     current
    DESCRIPTION
        "-- empty --"
    ::= { lcsSetupWanLayerEntry 4 }

-- {COLUMN} 1712.2.2.4.1.5
lcsSetupWanLayerEntryL2Opt OBJECT-TYPE
    SYNTAX     INTEGER
      {
        eNone (255),
        eCompr (0),
        eBundle (1),
        eBndPlusCmpr (2)
      }
    MAX-ACCESS read-write
    STATUS     current
    DESCRIPTION
        "-- empty --"
    ::= { lcsSetupWanLayerEntry 5 }

-- {COLUMN} 1712.2.2.4.1.6
lcsSetupWanLayerEntryLay1 OBJECT-TYPE
    SYNTAX     INTEGER
      {
        eEth (4),
        eHdlc64k (0),
        eHdlc56k (1),
        eV1109k6 (3),
        eV11019k2 (67),
        eV11038k4 (131),
        eSerial (6)
      }
    MAX-ACCESS read-write
    STATUS     current
    DESCRIPTION
        "-- empty --"
    ::= { lcsSetupWanLayerEntry 6 }

-- {TABLE} 1712.2.2.5
lcsSetupWanPppTable OBJECT-TYPE
    SYNTAX     SEQUENCE OF LcsSetupWanPppEntry
    MAX-ACCESS not-accessible
    STATUS     current
    DESCRIPTION
        "-- empty --"
    ::= { lcsSetupWan 5 }

-- {ENTRY} 1712.2.2.5.1
lcsSetupWanPppEntry OBJECT-TYPE
    SYNTAX     LcsSetupWanPppEntry
    MAX-ACCESS not-accessible
    STATUS     current
    DESCRIPTION
        ""
    INDEX {
        lcsSetupWanPppEntryPeer
    }
    ::= { lcsSetupWanPppTable 1 }

-- {SEQUENCE}
LcsSetupWanPppEntry ::= SEQUENCE {
    lcsSetupWanPppEntryPeer DisplayString,
    lcsSetupWanPppEntryAuthentRequest BITS,
    lcsSetupWanPppEntryAuthentResponse BITS,
    lcsSetupWanPppEntryKey DisplayString,
    lcsSetupWanPppEntryTime INTEGER,
    lcsSetupWanPppEntryTry INTEGER,
    lcsSetupWanPppEntryConf INTEGER,
    lcsSetupWanPppEntryFail INTEGER,
    lcsSetupWanPppEntryTerm INTEGER,
    lcsSetupWanPppEntryUsername DisplayString,
    lcsSetupWanPppEntryRights BITS
}

-- {COLUMN} 1712.2.2.5.1.1
lcsSetupWanPppEntryPeer OBJECT-TYPE
    SYNTAX     DisplayString (SIZE(0..16))
    MAX-ACCESS read-write
    STATUS     current
    DESCRIPTION
        "-- empty --"
    ::= { lcsSetupWanPppEntry 1 }

-- {COLUMN} 1712.2.2.5.1.2
lcsSetupWanPppEntryAuthentRequest OBJECT-TYPE
    SYNTAX     BITS
      {
        eMsChapv2 (2),
        eMsChap (3),
        eChap (4),
        ePap (5)
      }
    MAX-ACCESS read-write
    STATUS     current
    DESCRIPTION
        "-- empty --"
    ::= { lcsSetupWanPppEntry 2 }

-- {COLUMN} 1712.2.2.5.1.11
lcsSetupWanPppEntryAuthentResponse OBJECT-TYPE
    SYNTAX     BITS
      {
        eMsChapv2 (2),
        eMsChap (3),
        eChap (4),
        ePap (5)
      }
    MAX-ACCESS read-write
    STATUS     current
    DESCRIPTION
        "-- empty --"
    ::= { lcsSetupWanPppEntry 11 }

-- {COLUMN} 1712.2.2.5.1.3
lcsSetupWanPppEntryKey OBJECT-TYPE
    SYNTAX     DisplayString (SIZE(0..32))
    MAX-ACCESS read-write
    STATUS     current
    DESCRIPTION
        "-- empty --"
    ::= { lcsSetupWanPppEntry 3 }

-- {COLUMN} 1712.2.2.5.1.4
lcsSetupWanPppEntryTime OBJECT-TYPE
    SYNTAX     INTEGER (0..255)
    MAX-ACCESS read-write
    STATUS     current
    DESCRIPTION
        "-- empty --"
    ::= { lcsSetupWanPppEntry 4 }

-- {COLUMN} 1712.2.2.5.1.5
lcsSetupWanPppEntryTry OBJECT-TYPE
    SYNTAX     INTEGER (0..255)
    MAX-ACCESS read-write
    STATUS     current
    DESCRIPTION
        "-- empty --"
    ::= { lcsSetupWanPppEntry 5 }

-- {COLUMN} 1712.2.2.5.1.7
lcsSetupWanPppEntryConf OBJECT-TYPE
    SYNTAX     INTEGER (0..255)
    MAX-ACCESS read-write
    STATUS     current
    DESCRIPTION
        "-- empty --"
    ::= { lcsSetupWanPppEntry 7 }

-- {COLUMN} 1712.2.2.5.1.8
lcsSetupWanPppEntryFail OBJECT-TYPE
    SYNTAX     INTEGER (0..255)
    MAX-ACCESS read-write
    STATUS     current
    DESCRIPTION
        "-- empty --"
    ::= { lcsSetupWanPppEntry 8 }

-- {COLUMN} 1712.2.2.5.1.9
lcsSetupWanPppEntryTerm OBJECT-TYPE
    SYNTAX     INTEGER (0..255)
    MAX-ACCESS read-write
    STATUS     current
    DESCRIPTION
        "-- empty --"
    ::= { lcsSetupWanPppEntry 9 }

-- {COLUMN} 1712.2.2.5.1.6
lcsSetupWanPppEntryUsername OBJECT-TYPE
    SYNTAX     DisplayString (SIZE(0..64))
    MAX-ACCESS read-write
    STATUS     current
    DESCRIPTION
        "-- empty --"
    ::= { lcsSetupWanPppEntry 6 }

-- {COLUMN} 1712.2.2.5.1.10
lcsSetupWanPppEntryRights OBJECT-TYPE
    SYNTAX     BITS
      {
        eIp (7),
        eNbt (6),
        eIpv6 (3)
      }
    MAX-ACCESS read-write
    STATUS     current
    DESCRIPTION
        "-- empty --"
    ::= { lcsSetupWanPppEntry 10 }

-- {TABLE} 1712.2.2.19
lcsSetupWanDslBroadbandPeersTable OBJECT-TYPE
    SYNTAX     SEQUENCE OF LcsSetupWanDslBroadbandPeersEntry
    MAX-ACCESS not-accessible
    STATUS     current
    DESCRIPTION
        "-- empty --"
    ::= { lcsSetupWan 19 }

-- {ENTRY} 1712.2.2.19.1
lcsSetupWanDslBroadbandPeersEntry OBJECT-TYPE
    SYNTAX     LcsSetupWanDslBroadbandPeersEntry
    MAX-ACCESS not-accessible
    STATUS     current
    DESCRIPTION
        ""
    INDEX {
        lcsSetupWanDslBroadbandPeersEntryPeer
    }
    ::= { lcsSetupWanDslBroadbandPeersTable 1 }

-- {SEQUENCE}
LcsSetupWanDslBroadbandPeersEntry ::= SEQUENCE {
    lcsSetupWanDslBroadbandPeersEntryPeer DisplayString,
    lcsSetupWanDslBroadbandPeersEntryShTime INTEGER,
    lcsSetupWanDslBroadbandPeersEntryAcName DisplayString,
    lcsSetupWanDslBroadbandPeersEntryServicename DisplayString,
    lcsSetupWanDslBroadbandPeersEntryWanLayer DisplayString,
    lcsSetupWanDslBroadbandPeersEntryMacType INTEGER,
    lcsSetupWanDslBroadbandPeersEntryUserDefMac MacAddress,
    lcsSetupWanDslBroadbandPeersEntryDslIfcS DisplayString,
    lcsSetupWanDslBroadbandPeersEntryVlanId INTEGER
}

-- {COLUMN} 1712.2.2.19.1.1
lcsSetupWanDslBroadbandPeersEntryPeer OBJECT-TYPE
    SYNTAX     DisplayString (SIZE(0..16))
    MAX-ACCESS read-write
    STATUS     current
    DESCRIPTION
        "-- empty --"
    ::= { lcsSetupWanDslBroadbandPeersEntry 1 }

-- {COLUMN} 1712.2.2.19.1.2
lcsSetupWanDslBroadbandPeersEntryShTime OBJECT-TYPE
    SYNTAX     INTEGER (0..65535)
    MAX-ACCESS read-write
    STATUS     current
    DESCRIPTION
        "-- empty --"
    ::= { lcsSetupWanDslBroadbandPeersEntry 2 }

-- {COLUMN} 1712.2.2.19.1.3
lcsSetupWanDslBroadbandPeersEntryAcName OBJECT-TYPE
    SYNTAX     DisplayString (SIZE(0..64))
    MAX-ACCESS read-write
    STATUS     current
    DESCRIPTION
        "-- empty --"
    ::= { lcsSetupWanDslBroadbandPeersEntry 3 }

-- {COLUMN} 1712.2.2.19.1.4
lcsSetupWanDslBroadbandPeersEntryServicename OBJECT-TYPE
    SYNTAX     DisplayString (SIZE(0..32))
    MAX-ACCESS read-write
    STATUS     current
    DESCRIPTION
        "-- empty --"
    ::= { lcsSetupWanDslBroadbandPeersEntry 4 }

-- {COLUMN} 1712.2.2.19.1.5
lcsSetupWanDslBroadbandPeersEntryWanLayer OBJECT-TYPE
    SYNTAX     DisplayString (SIZE(0..9))
    MAX-ACCESS read-write
    STATUS     current
    DESCRIPTION
        "-- empty --"
    ::= { lcsSetupWanDslBroadbandPeersEntry 5 }

-- {COLUMN} 1712.2.2.19.1.15
lcsSetupWanDslBroadbandPeersEntryMacType OBJECT-TYPE
    SYNTAX     INTEGER
      {
        eGlobal (1),
        eLocal (0),
        eUserDef (2)
      }
    MAX-ACCESS read-write
    STATUS     current
    DESCRIPTION
        "-- empty --"
    ::= { lcsSetupWanDslBroadbandPeersEntry 15 }

-- {COLUMN} 1712.2.2.19.1.13
lcsSetupWanDslBroadbandPeersEntryUserDefMac OBJECT-TYPE
    SYNTAX     MacAddress
    MAX-ACCESS read-write
    STATUS     current
    DESCRIPTION
        "-- empty --"
    ::= { lcsSetupWanDslBroadbandPeersEntry 13 }

-- {COLUMN} 1712.2.2.19.1.14
lcsSetupWanDslBroadbandPeersEntryDslIfcS OBJECT-TYPE
    SYNTAX     DisplayString (SIZE(0..8))
    MAX-ACCESS read-write
    STATUS     current
    DESCRIPTION
        "-- empty --"
    ::= { lcsSetupWanDslBroadbandPeersEntry 14 }

-- {COLUMN} 1712.2.2.19.1.16
lcsSetupWanDslBroadbandPeersEntryVlanId OBJECT-TYPE
    SYNTAX     INTEGER (0..65535)
    MAX-ACCESS read-write
    STATUS     current
    DESCRIPTION
        "-- empty --"
    ::= { lcsSetupWanDslBroadbandPeersEntry 16 }

-- {TABLE} 1712.2.2.26
lcsSetupWanMtuListTable OBJECT-TYPE
    SYNTAX     SEQUENCE OF LcsSetupWanMtuListEntry
    MAX-ACCESS not-accessible
    STATUS     current
    DESCRIPTION
        "-- empty --"
    ::= { lcsSetupWan 26 }

-- {ENTRY} 1712.2.2.26.1
lcsSetupWanMtuListEntry OBJECT-TYPE
    SYNTAX     LcsSetupWanMtuListEntry
    MAX-ACCESS not-accessible
    STATUS     current
    DESCRIPTION
        ""
    INDEX {
        lcsSetupWanMtuListEntryPeer
    }
    ::= { lcsSetupWanMtuListTable 1 }

-- {SEQUENCE}
LcsSetupWanMtuListEntry ::= SEQUENCE {
    lcsSetupWanMtuListEntryPeer DisplayString,
    lcsSetupWanMtuListEntryMtu INTEGER
}

-- {COLUMN} 1712.2.2.26.1.1
lcsSetupWanMtuListEntryPeer OBJECT-TYPE
    SYNTAX     DisplayString (SIZE(0..16))
    MAX-ACCESS read-write
    STATUS     current
    DESCRIPTION
        "-- empty --"
    ::= { lcsSetupWanMtuListEntry 1 }

-- {COLUMN} 1712.2.2.26.1.2
lcsSetupWanMtuListEntryMtu OBJECT-TYPE
    SYNTAX     INTEGER (0..65535)
    MAX-ACCESS read-write
    STATUS     current
    DESCRIPTION
        "-- empty --"
    ::= { lcsSetupWanMtuListEntry 2 }

-- {TABLE} 1712.2.2.20
lcsSetupWanIpListTable OBJECT-TYPE
    SYNTAX     SEQUENCE OF LcsSetupWanIpListEntry
    MAX-ACCESS not-accessible
    STATUS     current
    DESCRIPTION
        "-- empty --"
    ::= { lcsSetupWan 20 }

-- {ENTRY} 1712.2.2.20.1
lcsSetupWanIpListEntry OBJECT-TYPE
    SYNTAX     LcsSetupWanIpListEntry
    MAX-ACCESS not-accessible
    STATUS     current
    DESCRIPTION
        ""
    INDEX {
        lcsSetupWanIpListEntryPeer
    }
    ::= { lcsSetupWanIpListTable 1 }

-- {SEQUENCE}
LcsSetupWanIpListEntry ::= SEQUENCE {
    lcsSetupWanIpListEntryPeer DisplayString,
    lcsSetupWanIpListEntryIpAddress IpAddress,
    lcsSetupWanIpListEntryIpNetmask IpAddress,
    lcsSetupWanIpListEntryMasqIpAddr IpAddress,
    lcsSetupWanIpListEntryGateway IpAddress,
    lcsSetupWanIpListEntryDnsDefault IpAddress,
    lcsSetupWanIpListEntryDnsBackup IpAddress,
    lcsSetupWanIpListEntryNbnsDefault IpAddress,
    lcsSetupWanIpListEntryNbnsBackup IpAddress
}

-- {COLUMN} 1712.2.2.20.1.1
lcsSetupWanIpListEntryPeer OBJECT-TYPE
    SYNTAX     DisplayString (SIZE(0..16))
    MAX-ACCESS read-write
    STATUS     current
    DESCRIPTION
        "-- empty --"
    ::= { lcsSetupWanIpListEntry 1 }

-- {COLUMN} 1712.2.2.20.1.2
lcsSetupWanIpListEntryIpAddress OBJECT-TYPE
    SYNTAX     IpAddress
    MAX-ACCESS read-write
    STATUS     current
    DESCRIPTION
        "-- empty --"
    ::= { lcsSetupWanIpListEntry 2 }

-- {COLUMN} 1712.2.2.20.1.3
lcsSetupWanIpListEntryIpNetmask OBJECT-TYPE
    SYNTAX     IpAddress
    MAX-ACCESS read-write
    STATUS     current
    DESCRIPTION
        "-- empty --"
    ::= { lcsSetupWanIpListEntry 3 }

-- {COLUMN} 1712.2.2.20.1.9
lcsSetupWanIpListEntryMasqIpAddr OBJECT-TYPE
    SYNTAX     IpAddress
    MAX-ACCESS read-write
    STATUS     current
    DESCRIPTION
        "-- empty --"
    ::= { lcsSetupWanIpListEntry 9 }

-- {COLUMN} 1712.2.2.20.1.4
lcsSetupWanIpListEntryGateway OBJECT-TYPE
    SYNTAX     IpAddress
    MAX-ACCESS read-write
    STATUS     current
    DESCRIPTION
        "-- empty --"
    ::= { lcsSetupWanIpListEntry 4 }

-- {COLUMN} 1712.2.2.20.1.5
lcsSetupWanIpListEntryDnsDefault OBJECT-TYPE
    SYNTAX     IpAddress
    MAX-ACCESS read-write
    STATUS     current
    DESCRIPTION
        "-- empty --"
    ::= { lcsSetupWanIpListEntry 5 }

-- {COLUMN} 1712.2.2.20.1.6
lcsSetupWanIpListEntryDnsBackup OBJECT-TYPE
    SYNTAX     IpAddress
    MAX-ACCESS read-write
    STATUS     current
    DESCRIPTION
        "-- empty --"
    ::= { lcsSetupWanIpListEntry 6 }

-- {COLUMN} 1712.2.2.20.1.7
lcsSetupWanIpListEntryNbnsDefault OBJECT-TYPE
    SYNTAX     IpAddress
    MAX-ACCESS read-write
    STATUS     current
    DESCRIPTION
        "-- empty --"
    ::= { lcsSetupWanIpListEntry 7 }

-- {COLUMN} 1712.2.2.20.1.8
lcsSetupWanIpListEntryNbnsBackup OBJECT-TYPE
    SYNTAX     IpAddress
    MAX-ACCESS read-write
    STATUS     current
    DESCRIPTION
        "-- empty --"
    ::= { lcsSetupWanIpListEntry 8 }

-- {TABLE} 1712.2.2.21
lcsSetupWanPptpPeersTable OBJECT-TYPE
    SYNTAX     SEQUENCE OF LcsSetupWanPptpPeersEntry
    MAX-ACCESS not-accessible
    STATUS     current
    DESCRIPTION
        "-- empty --"
    ::= { lcsSetupWan 21 }

-- {ENTRY} 1712.2.2.21.1
lcsSetupWanPptpPeersEntry OBJECT-TYPE
    SYNTAX     LcsSetupWanPptpPeersEntry
    MAX-ACCESS not-accessible
    STATUS     current
    DESCRIPTION
        ""
    INDEX {
        lcsSetupWanPptpPeersEntryPeer
    }
    ::= { lcsSetupWanPptpPeersTable 1 }

-- {SEQUENCE}
LcsSetupWanPptpPeersEntry ::= SEQUENCE {
    lcsSetupWanPptpPeersEntryPeer DisplayString,
    lcsSetupWanPptpPeersEntryIpAddress DisplayString,
    lcsSetupWanPptpPeersEntryRtgTag INTEGER,
    lcsSetupWanPptpPeersEntryPort INTEGER,
    lcsSetupWanPptpPeersEntryShTime INTEGER,
    lcsSetupWanPptpPeersEntryEncryption INTEGER
}

-- {COLUMN} 1712.2.2.21.1.1
lcsSetupWanPptpPeersEntryPeer OBJECT-TYPE
    SYNTAX     DisplayString (SIZE(0..16))
    MAX-ACCESS read-write
    STATUS     current
    DESCRIPTION
        "-- empty --"
    ::= { lcsSetupWanPptpPeersEntry 1 }

-- {COLUMN} 1712.2.2.21.1.6
lcsSetupWanPptpPeersEntryIpAddress OBJECT-TYPE
    SYNTAX     DisplayString (SIZE(0..63))
    MAX-ACCESS read-write
    STATUS     current
    DESCRIPTION
        "-- empty --"
    ::= { lcsSetupWanPptpPeersEntry 6 }

-- {COLUMN} 1712.2.2.21.1.5
lcsSetupWanPptpPeersEntryRtgTag OBJECT-TYPE
    SYNTAX     INTEGER (0..65535)
    MAX-ACCESS read-write
    STATUS     current
    DESCRIPTION
        "-- empty --"
    ::= { lcsSetupWanPptpPeersEntry 5 }

-- {COLUMN} 1712.2.2.21.1.3
lcsSetupWanPptpPeersEntryPort OBJECT-TYPE
    SYNTAX     INTEGER (0..65535)
    MAX-ACCESS read-write
    STATUS     current
    DESCRIPTION
        "-- empty --"
    ::= { lcsSetupWanPptpPeersEntry 3 }

-- {COLUMN} 1712.2.2.21.1.4
lcsSetupWanPptpPeersEntryShTime OBJECT-TYPE
    SYNTAX     INTEGER (0..65535)
    MAX-ACCESS read-write
    STATUS     current
    DESCRIPTION
        "-- empty --"
    ::= { lcsSetupWanPptpPeersEntry 4 }

-- {COLUMN} 1712.2.2.21.1.7
lcsSetupWanPptpPeersEntryEncryption OBJECT-TYPE
    SYNTAX     INTEGER
      {
        eOff (0),
        e40Bits (224),
        e56Bits (192),
        e128Bits (64)
      }
    MAX-ACCESS read-write
    STATUS     current
    DESCRIPTION
        "-- empty --"
    ::= { lcsSetupWanPptpPeersEntry 7 }

-- {TABLE} 1712.2.2.30
lcsSetupWanAdditionalPptpGatewaysTable OBJECT-TYPE
    SYNTAX     SEQUENCE OF LcsSetupWanAdditionalPptpGatewaysEntry
    MAX-ACCESS not-accessible
    STATUS     current
    DESCRIPTION
        "-- empty --"
    ::= { lcsSetupWan 30 }

-- {ENTRY} 1712.2.2.30.1
lcsSetupWanAdditionalPptpGatewaysEntry OBJECT-TYPE
    SYNTAX     LcsSetupWanAdditionalPptpGatewaysEntry
    MAX-ACCESS not-accessible
    STATUS     current
    DESCRIPTION
        ""
    INDEX {
        lcsSetupWanAdditionalPptpGatewaysEntryPeer
    }
    ::= { lcsSetupWanAdditionalPptpGatewaysTable 1 }

-- {SEQUENCE}
LcsSetupWanAdditionalPptpGatewaysEntry ::= SEQUENCE {
    lcsSetupWanAdditionalPptpGatewaysEntryPeer DisplayString,
    lcsSetupWanAdditionalPptpGatewaysEntryGateway1 DisplayString,
    lcsSetupWanAdditionalPptpGatewaysEntryRtgTag1 INTEGER,
    lcsSetupWanAdditionalPptpGatewaysEntryGateway2 DisplayString,
    lcsSetupWanAdditionalPptpGatewaysEntryRtgTag2 INTEGER,
    lcsSetupWanAdditionalPptpGatewaysEntryGateway3 DisplayString,
    lcsSetupWanAdditionalPptpGatewaysEntryRtgTag3 INTEGER,
    lcsSetupWanAdditionalPptpGatewaysEntryGateway4 DisplayString,
    lcsSetupWanAdditionalPptpGatewaysEntryRtgTag4 INTEGER,
    lcsSetupWanAdditionalPptpGatewaysEntryGateway5 DisplayString,
    lcsSetupWanAdditionalPptpGatewaysEntryRtgTag5 INTEGER,
    lcsSetupWanAdditionalPptpGatewaysEntryGateway6 DisplayString,
    lcsSetupWanAdditionalPptpGatewaysEntryRtgTag6 INTEGER,
    lcsSetupWanAdditionalPptpGatewaysEntryGateway7 DisplayString,
    lcsSetupWanAdditionalPptpGatewaysEntryRtgTag7 INTEGER,
    lcsSetupWanAdditionalPptpGatewaysEntryGateway8 DisplayString,
    lcsSetupWanAdditionalPptpGatewaysEntryRtgTag8 INTEGER,
    lcsSetupWanAdditionalPptpGatewaysEntryGateway9 DisplayString,
    lcsSetupWanAdditionalPptpGatewaysEntryRtgTag9 INTEGER,
    lcsSetupWanAdditionalPptpGatewaysEntryGateway10 DisplayString,
    lcsSetupWanAdditionalPptpGatewaysEntryRtgTag10 INTEGER,
    lcsSetupWanAdditionalPptpGatewaysEntryGateway11 DisplayString,
    lcsSetupWanAdditionalPptpGatewaysEntryRtgTag11 INTEGER,
    lcsSetupWanAdditionalPptpGatewaysEntryGateway12 DisplayString,
    lcsSetupWanAdditionalPptpGatewaysEntryRtgTag12 INTEGER,
    lcsSetupWanAdditionalPptpGatewaysEntryGateway13 DisplayString,
    lcsSetupWanAdditionalPptpGatewaysEntryRtgTag13 INTEGER,
    lcsSetupWanAdditionalPptpGatewaysEntryGateway14 DisplayString,
    lcsSetupWanAdditionalPptpGatewaysEntryRtgTag14 INTEGER,
    lcsSetupWanAdditionalPptpGatewaysEntryGateway15 DisplayString,
    lcsSetupWanAdditionalPptpGatewaysEntryRtgTag15 INTEGER,
    lcsSetupWanAdditionalPptpGatewaysEntryGateway16 DisplayString,
    lcsSetupWanAdditionalPptpGatewaysEntryRtgTag16 INTEGER,
    lcsSetupWanAdditionalPptpGatewaysEntryGateway17 DisplayString,
    lcsSetupWanAdditionalPptpGatewaysEntryRtgTag17 INTEGER,
    lcsSetupWanAdditionalPptpGatewaysEntryGateway18 DisplayString,
    lcsSetupWanAdditionalPptpGatewaysEntryRtgTag18 INTEGER,
    lcsSetupWanAdditionalPptpGatewaysEntryGateway19 DisplayString,
    lcsSetupWanAdditionalPptpGatewaysEntryRtgTag19 INTEGER,
    lcsSetupWanAdditionalPptpGatewaysEntryGateway20 DisplayString,
    lcsSetupWanAdditionalPptpGatewaysEntryRtgTag20 INTEGER,
    lcsSetupWanAdditionalPptpGatewaysEntryGateway21 DisplayString,
    lcsSetupWanAdditionalPptpGatewaysEntryRtgTag21 INTEGER,
    lcsSetupWanAdditionalPptpGatewaysEntryGateway22 DisplayString,
    lcsSetupWanAdditionalPptpGatewaysEntryRtgTag22 INTEGER,
    lcsSetupWanAdditionalPptpGatewaysEntryGateway23 DisplayString,
    lcsSetupWanAdditionalPptpGatewaysEntryRtgTag23 INTEGER,
    lcsSetupWanAdditionalPptpGatewaysEntryGateway24 DisplayString,
    lcsSetupWanAdditionalPptpGatewaysEntryRtgTag24 INTEGER,
    lcsSetupWanAdditionalPptpGatewaysEntryGateway25 DisplayString,
    lcsSetupWanAdditionalPptpGatewaysEntryRtgTag25 INTEGER,
    lcsSetupWanAdditionalPptpGatewaysEntryGateway26 DisplayString,
    lcsSetupWanAdditionalPptpGatewaysEntryRtgTag26 INTEGER,
    lcsSetupWanAdditionalPptpGatewaysEntryGateway27 DisplayString,
    lcsSetupWanAdditionalPptpGatewaysEntryRtgTag27 INTEGER,
    lcsSetupWanAdditionalPptpGatewaysEntryGateway28 DisplayString,
    lcsSetupWanAdditionalPptpGatewaysEntryRtgTag28 INTEGER,
    lcsSetupWanAdditionalPptpGatewaysEntryGateway29 DisplayString,
    lcsSetupWanAdditionalPptpGatewaysEntryRtgTag29 INTEGER,
    lcsSetupWanAdditionalPptpGatewaysEntryGateway30 DisplayString,
    lcsSetupWanAdditionalPptpGatewaysEntryRtgTag30 INTEGER,
    lcsSetupWanAdditionalPptpGatewaysEntryGateway31 DisplayString,
    lcsSetupWanAdditionalPptpGatewaysEntryRtgTag31 INTEGER,
    lcsSetupWanAdditionalPptpGatewaysEntryGateway32 DisplayString,
    lcsSetupWanAdditionalPptpGatewaysEntryRtgTag32 INTEGER,
    lcsSetupWanAdditionalPptpGatewaysEntryBeginWith INTEGER
}

-- {COLUMN} 1712.2.2.30.1.1
lcsSetupWanAdditionalPptpGatewaysEntryPeer OBJECT-TYPE
    SYNTAX     DisplayString (SIZE(0..16))
    MAX-ACCESS read-write
    STATUS     current
    DESCRIPTION
        "-- empty --"
    ::= { lcsSetupWanAdditionalPptpGatewaysEntry 1 }

-- {COLUMN} 1712.2.2.30.1.3
lcsSetupWanAdditionalPptpGatewaysEntryGateway1 OBJECT-TYPE
    SYNTAX     DisplayString (SIZE(0..64))
    MAX-ACCESS read-write
    STATUS     current
    DESCRIPTION
        "-- empty --"
    ::= { lcsSetupWanAdditionalPptpGatewaysEntry 3 }

-- {COLUMN} 1712.2.2.30.1.4
lcsSetupWanAdditionalPptpGatewaysEntryRtgTag1 OBJECT-TYPE
    SYNTAX     INTEGER (0..65535)
    MAX-ACCESS read-write
    STATUS     current
    DESCRIPTION
        "-- empty --"
    ::= { lcsSetupWanAdditionalPptpGatewaysEntry 4 }

-- {COLUMN} 1712.2.2.30.1.5
lcsSetupWanAdditionalPptpGatewaysEntryGateway2 OBJECT-TYPE
    SYNTAX     DisplayString (SIZE(0..64))
    MAX-ACCESS read-write
    STATUS     current
    DESCRIPTION
        "-- empty --"
    ::= { lcsSetupWanAdditionalPptpGatewaysEntry 5 }

-- {COLUMN} 1712.2.2.30.1.6
lcsSetupWanAdditionalPptpGatewaysEntryRtgTag2 OBJECT-TYPE
    SYNTAX     INTEGER (0..65535)
    MAX-ACCESS read-write
    STATUS     current
    DESCRIPTION
        "-- empty --"
    ::= { lcsSetupWanAdditionalPptpGatewaysEntry 6 }

-- {COLUMN} 1712.2.2.30.1.7
lcsSetupWanAdditionalPptpGatewaysEntryGateway3 OBJECT-TYPE
    SYNTAX     DisplayString (SIZE(0..64))
    MAX-ACCESS read-write
    STATUS     current
    DESCRIPTION
        "-- empty --"
    ::= { lcsSetupWanAdditionalPptpGatewaysEntry 7 }

-- {COLUMN} 1712.2.2.30.1.8
lcsSetupWanAdditionalPptpGatewaysEntryRtgTag3 OBJECT-TYPE
    SYNTAX     INTEGER (0..65535)
    MAX-ACCESS read-write
    STATUS     current
    DESCRIPTION
        "-- empty --"
    ::= { lcsSetupWanAdditionalPptpGatewaysEntry 8 }

-- {COLUMN} 1712.2.2.30.1.9
lcsSetupWanAdditionalPptpGatewaysEntryGateway4 OBJECT-TYPE
    SYNTAX     DisplayString (SIZE(0..64))
    MAX-ACCESS read-write
    STATUS     current
    DESCRIPTION
        "-- empty --"
    ::= { lcsSetupWanAdditionalPptpGatewaysEntry 9 }

-- {COLUMN} 1712.2.2.30.1.10
lcsSetupWanAdditionalPptpGatewaysEntryRtgTag4 OBJECT-TYPE
    SYNTAX     INTEGER (0..65535)
    MAX-ACCESS read-write
    STATUS     current
    DESCRIPTION
        "-- empty --"
    ::= { lcsSetupWanAdditionalPptpGatewaysEntry 10 }

-- {COLUMN} 1712.2.2.30.1.11
lcsSetupWanAdditionalPptpGatewaysEntryGateway5 OBJECT-TYPE
    SYNTAX     DisplayString (SIZE(0..64))
    MAX-ACCESS read-write
    STATUS     current
    DESCRIPTION
        "-- empty --"
    ::= { lcsSetupWanAdditionalPptpGatewaysEntry 11 }

-- {COLUMN} 1712.2.2.30.1.12
lcsSetupWanAdditionalPptpGatewaysEntryRtgTag5 OBJECT-TYPE
    SYNTAX     INTEGER (0..65535)
    MAX-ACCESS read-write
    STATUS     current
    DESCRIPTION
        "-- empty --"
    ::= { lcsSetupWanAdditionalPptpGatewaysEntry 12 }

-- {COLUMN} 1712.2.2.30.1.13
lcsSetupWanAdditionalPptpGatewaysEntryGateway6 OBJECT-TYPE
    SYNTAX     DisplayString (SIZE(0..64))
    MAX-ACCESS read-write
    STATUS     current
    DESCRIPTION
        "-- empty --"
    ::= { lcsSetupWanAdditionalPptpGatewaysEntry 13 }

-- {COLUMN} 1712.2.2.30.1.14
lcsSetupWanAdditionalPptpGatewaysEntryRtgTag6 OBJECT-TYPE
    SYNTAX     INTEGER (0..65535)
    MAX-ACCESS read-write
    STATUS     current
    DESCRIPTION
        "-- empty --"
    ::= { lcsSetupWanAdditionalPptpGatewaysEntry 14 }

-- {COLUMN} 1712.2.2.30.1.15
lcsSetupWanAdditionalPptpGatewaysEntryGateway7 OBJECT-TYPE
    SYNTAX     DisplayString (SIZE(0..64))
    MAX-ACCESS read-write
    STATUS     current
    DESCRIPTION
        "-- empty --"
    ::= { lcsSetupWanAdditionalPptpGatewaysEntry 15 }

-- {COLUMN} 1712.2.2.30.1.16
lcsSetupWanAdditionalPptpGatewaysEntryRtgTag7 OBJECT-TYPE
    SYNTAX     INTEGER (0..65535)
    MAX-ACCESS read-write
    STATUS     current
    DESCRIPTION
        "-- empty --"
    ::= { lcsSetupWanAdditionalPptpGatewaysEntry 16 }

-- {COLUMN} 1712.2.2.30.1.17
lcsSetupWanAdditionalPptpGatewaysEntryGateway8 OBJECT-TYPE
    SYNTAX     DisplayString (SIZE(0..64))
    MAX-ACCESS read-write
    STATUS     current
    DESCRIPTION
        "-- empty --"
    ::= { lcsSetupWanAdditionalPptpGatewaysEntry 17 }

-- {COLUMN} 1712.2.2.30.1.18
lcsSetupWanAdditionalPptpGatewaysEntryRtgTag8 OBJECT-TYPE
    SYNTAX     INTEGER (0..65535)
    MAX-ACCESS read-write
    STATUS     current
    DESCRIPTION
        "-- empty --"
    ::= { lcsSetupWanAdditionalPptpGatewaysEntry 18 }

-- {COLUMN} 1712.2.2.30.1.19
lcsSetupWanAdditionalPptpGatewaysEntryGateway9 OBJECT-TYPE
    SYNTAX     DisplayString (SIZE(0..64))
    MAX-ACCESS read-write
    STATUS     current
    DESCRIPTION
        "-- empty --"
    ::= { lcsSetupWanAdditionalPptpGatewaysEntry 19 }

-- {COLUMN} 1712.2.2.30.1.20
lcsSetupWanAdditionalPptpGatewaysEntryRtgTag9 OBJECT-TYPE
    SYNTAX     INTEGER (0..65535)
    MAX-ACCESS read-write
    STATUS     current
    DESCRIPTION
        "-- empty --"
    ::= { lcsSetupWanAdditionalPptpGatewaysEntry 20 }

-- {COLUMN} 1712.2.2.30.1.21
lcsSetupWanAdditionalPptpGatewaysEntryGateway10 OBJECT-TYPE
    SYNTAX     DisplayString (SIZE(0..64))
    MAX-ACCESS read-write
    STATUS     current
    DESCRIPTION
        "-- empty --"
    ::= { lcsSetupWanAdditionalPptpGatewaysEntry 21 }

-- {COLUMN} 1712.2.2.30.1.22
lcsSetupWanAdditionalPptpGatewaysEntryRtgTag10 OBJECT-TYPE
    SYNTAX     INTEGER (0..65535)
    MAX-ACCESS read-write
    STATUS     current
    DESCRIPTION
        "-- empty --"
    ::= { lcsSetupWanAdditionalPptpGatewaysEntry 22 }

-- {COLUMN} 1712.2.2.30.1.23
lcsSetupWanAdditionalPptpGatewaysEntryGateway11 OBJECT-TYPE
    SYNTAX     DisplayString (SIZE(0..64))
    MAX-ACCESS read-write
    STATUS     current
    DESCRIPTION
        "-- empty --"
    ::= { lcsSetupWanAdditionalPptpGatewaysEntry 23 }

-- {COLUMN} 1712.2.2.30.1.24
lcsSetupWanAdditionalPptpGatewaysEntryRtgTag11 OBJECT-TYPE
    SYNTAX     INTEGER (0..65535)
    MAX-ACCESS read-write
    STATUS     current
    DESCRIPTION
        "-- empty --"
    ::= { lcsSetupWanAdditionalPptpGatewaysEntry 24 }

-- {COLUMN} 1712.2.2.30.1.25
lcsSetupWanAdditionalPptpGatewaysEntryGateway12 OBJECT-TYPE
    SYNTAX     DisplayString (SIZE(0..64))
    MAX-ACCESS read-write
    STATUS     current
    DESCRIPTION
        "-- empty --"
    ::= { lcsSetupWanAdditionalPptpGatewaysEntry 25 }

-- {COLUMN} 1712.2.2.30.1.26
lcsSetupWanAdditionalPptpGatewaysEntryRtgTag12 OBJECT-TYPE
    SYNTAX     INTEGER (0..65535)
    MAX-ACCESS read-write
    STATUS     current
    DESCRIPTION
        "-- empty --"
    ::= { lcsSetupWanAdditionalPptpGatewaysEntry 26 }

-- {COLUMN} 1712.2.2.30.1.27
lcsSetupWanAdditionalPptpGatewaysEntryGateway13 OBJECT-TYPE
    SYNTAX     DisplayString (SIZE(0..64))
    MAX-ACCESS read-write
    STATUS     current
    DESCRIPTION
        "-- empty --"
    ::= { lcsSetupWanAdditionalPptpGatewaysEntry 27 }

-- {COLUMN} 1712.2.2.30.1.28
lcsSetupWanAdditionalPptpGatewaysEntryRtgTag13 OBJECT-TYPE
    SYNTAX     INTEGER (0..65535)
    MAX-ACCESS read-write
    STATUS     current
    DESCRIPTION
        "-- empty --"
    ::= { lcsSetupWanAdditionalPptpGatewaysEntry 28 }

-- {COLUMN} 1712.2.2.30.1.29
lcsSetupWanAdditionalPptpGatewaysEntryGateway14 OBJECT-TYPE
    SYNTAX     DisplayString (SIZE(0..64))
    MAX-ACCESS read-write
    STATUS     current
    DESCRIPTION
        "-- empty --"
    ::= { lcsSetupWanAdditionalPptpGatewaysEntry 29 }

-- {COLUMN} 1712.2.2.30.1.30
lcsSetupWanAdditionalPptpGatewaysEntryRtgTag14 OBJECT-TYPE
    SYNTAX     INTEGER (0..65535)
    MAX-ACCESS read-write
    STATUS     current
    DESCRIPTION
        "-- empty --"
    ::= { lcsSetupWanAdditionalPptpGatewaysEntry 30 }

-- {COLUMN} 1712.2.2.30.1.31
lcsSetupWanAdditionalPptpGatewaysEntryGateway15 OBJECT-TYPE
    SYNTAX     DisplayString (SIZE(0..64))
    MAX-ACCESS read-write
    STATUS     current
    DESCRIPTION
        "-- empty --"
    ::= { lcsSetupWanAdditionalPptpGatewaysEntry 31 }

-- {COLUMN} 1712.2.2.30.1.32
lcsSetupWanAdditionalPptpGatewaysEntryRtgTag15 OBJECT-TYPE
    SYNTAX     INTEGER (0..65535)
    MAX-ACCESS read-write
    STATUS     current
    DESCRIPTION
        "-- empty --"
    ::= { lcsSetupWanAdditionalPptpGatewaysEntry 32 }

-- {COLUMN} 1712.2.2.30.1.33
lcsSetupWanAdditionalPptpGatewaysEntryGateway16 OBJECT-TYPE
    SYNTAX     DisplayString (SIZE(0..64))
    MAX-ACCESS read-write
    STATUS     current
    DESCRIPTION
        "-- empty --"
    ::= { lcsSetupWanAdditionalPptpGatewaysEntry 33 }

-- {COLUMN} 1712.2.2.30.1.34
lcsSetupWanAdditionalPptpGatewaysEntryRtgTag16 OBJECT-TYPE
    SYNTAX     INTEGER (0..65535)
    MAX-ACCESS read-write
    STATUS     current
    DESCRIPTION
        "-- empty --"
    ::= { lcsSetupWanAdditionalPptpGatewaysEntry 34 }

-- {COLUMN} 1712.2.2.30.1.35
lcsSetupWanAdditionalPptpGatewaysEntryGateway17 OBJECT-TYPE
    SYNTAX     DisplayString (SIZE(0..64))
    MAX-ACCESS read-write
    STATUS     current
    DESCRIPTION
        "-- empty --"
    ::= { lcsSetupWanAdditionalPptpGatewaysEntry 35 }

-- {COLUMN} 1712.2.2.30.1.36
lcsSetupWanAdditionalPptpGatewaysEntryRtgTag17 OBJECT-TYPE
    SYNTAX     INTEGER (0..65535)
    MAX-ACCESS read-write
    STATUS     current
    DESCRIPTION
        "-- empty --"
    ::= { lcsSetupWanAdditionalPptpGatewaysEntry 36 }

-- {COLUMN} 1712.2.2.30.1.37
lcsSetupWanAdditionalPptpGatewaysEntryGateway18 OBJECT-TYPE
    SYNTAX     DisplayString (SIZE(0..64))
    MAX-ACCESS read-write
    STATUS     current
    DESCRIPTION
        "-- empty --"
    ::= { lcsSetupWanAdditionalPptpGatewaysEntry 37 }

-- {COLUMN} 1712.2.2.30.1.38
lcsSetupWanAdditionalPptpGatewaysEntryRtgTag18 OBJECT-TYPE
    SYNTAX     INTEGER (0..65535)
    MAX-ACCESS read-write
    STATUS     current
    DESCRIPTION
        "-- empty --"
    ::= { lcsSetupWanAdditionalPptpGatewaysEntry 38 }

-- {COLUMN} 1712.2.2.30.1.39
lcsSetupWanAdditionalPptpGatewaysEntryGateway19 OBJECT-TYPE
    SYNTAX     DisplayString (SIZE(0..64))
    MAX-ACCESS read-write
    STATUS     current
    DESCRIPTION
        "-- empty --"
    ::= { lcsSetupWanAdditionalPptpGatewaysEntry 39 }

-- {COLUMN} 1712.2.2.30.1.40
lcsSetupWanAdditionalPptpGatewaysEntryRtgTag19 OBJECT-TYPE
    SYNTAX     INTEGER (0..65535)
    MAX-ACCESS read-write
    STATUS     current
    DESCRIPTION
        "-- empty --"
    ::= { lcsSetupWanAdditionalPptpGatewaysEntry 40 }

-- {COLUMN} 1712.2.2.30.1.41
lcsSetupWanAdditionalPptpGatewaysEntryGateway20 OBJECT-TYPE
    SYNTAX     DisplayString (SIZE(0..64))
    MAX-ACCESS read-write
    STATUS     current
    DESCRIPTION
        "-- empty --"
    ::= { lcsSetupWanAdditionalPptpGatewaysEntry 41 }

-- {COLUMN} 1712.2.2.30.1.42
lcsSetupWanAdditionalPptpGatewaysEntryRtgTag20 OBJECT-TYPE
    SYNTAX     INTEGER (0..65535)
    MAX-ACCESS read-write
    STATUS     current
    DESCRIPTION
        "-- empty --"
    ::= { lcsSetupWanAdditionalPptpGatewaysEntry 42 }

-- {COLUMN} 1712.2.2.30.1.43
lcsSetupWanAdditionalPptpGatewaysEntryGateway21 OBJECT-TYPE
    SYNTAX     DisplayString (SIZE(0..64))
    MAX-ACCESS read-write
    STATUS     current
    DESCRIPTION
        "-- empty --"
    ::= { lcsSetupWanAdditionalPptpGatewaysEntry 43 }

-- {COLUMN} 1712.2.2.30.1.44
lcsSetupWanAdditionalPptpGatewaysEntryRtgTag21 OBJECT-TYPE
    SYNTAX     INTEGER (0..65535)
    MAX-ACCESS read-write
    STATUS     current
    DESCRIPTION
        "-- empty --"
    ::= { lcsSetupWanAdditionalPptpGatewaysEntry 44 }

-- {COLUMN} 1712.2.2.30.1.45
lcsSetupWanAdditionalPptpGatewaysEntryGateway22 OBJECT-TYPE
    SYNTAX     DisplayString (SIZE(0..64))
    MAX-ACCESS read-write
    STATUS     current
    DESCRIPTION
        "-- empty --"
    ::= { lcsSetupWanAdditionalPptpGatewaysEntry 45 }

-- {COLUMN} 1712.2.2.30.1.46
lcsSetupWanAdditionalPptpGatewaysEntryRtgTag22 OBJECT-TYPE
    SYNTAX     INTEGER (0..65535)
    MAX-ACCESS read-write
    STATUS     current
    DESCRIPTION
        "-- empty --"
    ::= { lcsSetupWanAdditionalPptpGatewaysEntry 46 }

-- {COLUMN} 1712.2.2.30.1.47
lcsSetupWanAdditionalPptpGatewaysEntryGateway23 OBJECT-TYPE
    SYNTAX     DisplayString (SIZE(0..64))
    MAX-ACCESS read-write
    STATUS     current
    DESCRIPTION
        "-- empty --"
    ::= { lcsSetupWanAdditionalPptpGatewaysEntry 47 }

-- {COLUMN} 1712.2.2.30.1.48
lcsSetupWanAdditionalPptpGatewaysEntryRtgTag23 OBJECT-TYPE
    SYNTAX     INTEGER (0..65535)
    MAX-ACCESS read-write
    STATUS     current
    DESCRIPTION
        "-- empty --"
    ::= { lcsSetupWanAdditionalPptpGatewaysEntry 48 }

-- {COLUMN} 1712.2.2.30.1.49
lcsSetupWanAdditionalPptpGatewaysEntryGateway24 OBJECT-TYPE
    SYNTAX     DisplayString (SIZE(0..64))
    MAX-ACCESS read-write
    STATUS     current
    DESCRIPTION
        "-- empty --"
    ::= { lcsSetupWanAdditionalPptpGatewaysEntry 49 }

-- {COLUMN} 1712.2.2.30.1.50
lcsSetupWanAdditionalPptpGatewaysEntryRtgTag24 OBJECT-TYPE
    SYNTAX     INTEGER (0..65535)
    MAX-ACCESS read-write
    STATUS     current
    DESCRIPTION
        "-- empty --"
    ::= { lcsSetupWanAdditionalPptpGatewaysEntry 50 }

-- {COLUMN} 1712.2.2.30.1.51
lcsSetupWanAdditionalPptpGatewaysEntryGateway25 OBJECT-TYPE
    SYNTAX     DisplayString (SIZE(0..64))
    MAX-ACCESS read-write
    STATUS     current
    DESCRIPTION
        "-- empty --"
    ::= { lcsSetupWanAdditionalPptpGatewaysEntry 51 }

-- {COLUMN} 1712.2.2.30.1.52
lcsSetupWanAdditionalPptpGatewaysEntryRtgTag25 OBJECT-TYPE
    SYNTAX     INTEGER (0..65535)
    MAX-ACCESS read-write
    STATUS     current
    DESCRIPTION
        "-- empty --"
    ::= { lcsSetupWanAdditionalPptpGatewaysEntry 52 }

-- {COLUMN} 1712.2.2.30.1.53
lcsSetupWanAdditionalPptpGatewaysEntryGateway26 OBJECT-TYPE
    SYNTAX     DisplayString (SIZE(0..64))
    MAX-ACCESS read-write
    STATUS     current
    DESCRIPTION
        "-- empty --"
    ::= { lcsSetupWanAdditionalPptpGatewaysEntry 53 }

-- {COLUMN} 1712.2.2.30.1.54
lcsSetupWanAdditionalPptpGatewaysEntryRtgTag26 OBJECT-TYPE
    SYNTAX     INTEGER (0..65535)
    MAX-ACCESS read-write
    STATUS     current
    DESCRIPTION
        "-- empty --"
    ::= { lcsSetupWanAdditionalPptpGatewaysEntry 54 }

-- {COLUMN} 1712.2.2.30.1.55
lcsSetupWanAdditionalPptpGatewaysEntryGateway27 OBJECT-TYPE
    SYNTAX     DisplayString (SIZE(0..64))
    MAX-ACCESS read-write
    STATUS     current
    DESCRIPTION
        "-- empty --"
    ::= { lcsSetupWanAdditionalPptpGatewaysEntry 55 }

-- {COLUMN} 1712.2.2.30.1.56
lcsSetupWanAdditionalPptpGatewaysEntryRtgTag27 OBJECT-TYPE
    SYNTAX     INTEGER (0..65535)
    MAX-ACCESS read-write
    STATUS     current
    DESCRIPTION
        "-- empty --"
    ::= { lcsSetupWanAdditionalPptpGatewaysEntry 56 }

-- {COLUMN} 1712.2.2.30.1.57
lcsSetupWanAdditionalPptpGatewaysEntryGateway28 OBJECT-TYPE
    SYNTAX     DisplayString (SIZE(0..64))
    MAX-ACCESS read-write
    STATUS     current
    DESCRIPTION
        "-- empty --"
    ::= { lcsSetupWanAdditionalPptpGatewaysEntry 57 }

-- {COLUMN} 1712.2.2.30.1.58
lcsSetupWanAdditionalPptpGatewaysEntryRtgTag28 OBJECT-TYPE
    SYNTAX     INTEGER (0..65535)
    MAX-ACCESS read-write
    STATUS     current
    DESCRIPTION
        "-- empty --"
    ::= { lcsSetupWanAdditionalPptpGatewaysEntry 58 }

-- {COLUMN} 1712.2.2.30.1.59
lcsSetupWanAdditionalPptpGatewaysEntryGateway29 OBJECT-TYPE
    SYNTAX     DisplayString (SIZE(0..64))
    MAX-ACCESS read-write
    STATUS     current
    DESCRIPTION
        "-- empty --"
    ::= { lcsSetupWanAdditionalPptpGatewaysEntry 59 }

-- {COLUMN} 1712.2.2.30.1.60
lcsSetupWanAdditionalPptpGatewaysEntryRtgTag29 OBJECT-TYPE
    SYNTAX     INTEGER (0..65535)
    MAX-ACCESS read-write
    STATUS     current
    DESCRIPTION
        "-- empty --"
    ::= { lcsSetupWanAdditionalPptpGatewaysEntry 60 }

-- {COLUMN} 1712.2.2.30.1.61
lcsSetupWanAdditionalPptpGatewaysEntryGateway30 OBJECT-TYPE
    SYNTAX     DisplayString (SIZE(0..64))
    MAX-ACCESS read-write
    STATUS     current
    DESCRIPTION
        "-- empty --"
    ::= { lcsSetupWanAdditionalPptpGatewaysEntry 61 }

-- {COLUMN} 1712.2.2.30.1.62
lcsSetupWanAdditionalPptpGatewaysEntryRtgTag30 OBJECT-TYPE
    SYNTAX     INTEGER (0..65535)
    MAX-ACCESS read-write
    STATUS     current
    DESCRIPTION
        "-- empty --"
    ::= { lcsSetupWanAdditionalPptpGatewaysEntry 62 }

-- {COLUMN} 1712.2.2.30.1.63
lcsSetupWanAdditionalPptpGatewaysEntryGateway31 OBJECT-TYPE
    SYNTAX     DisplayString (SIZE(0..64))
    MAX-ACCESS read-write
    STATUS     current
    DESCRIPTION
        "-- empty --"
    ::= { lcsSetupWanAdditionalPptpGatewaysEntry 63 }

-- {COLUMN} 1712.2.2.30.1.64
lcsSetupWanAdditionalPptpGatewaysEntryRtgTag31 OBJECT-TYPE
    SYNTAX     INTEGER (0..65535)
    MAX-ACCESS read-write
    STATUS     current
    DESCRIPTION
        "-- empty --"
    ::= { lcsSetupWanAdditionalPptpGatewaysEntry 64 }

-- {COLUMN} 1712.2.2.30.1.65
lcsSetupWanAdditionalPptpGatewaysEntryGateway32 OBJECT-TYPE
    SYNTAX     DisplayString (SIZE(0..64))
    MAX-ACCESS read-write
    STATUS     current
    DESCRIPTION
        "-- empty --"
    ::= { lcsSetupWanAdditionalPptpGatewaysEntry 65 }

-- {COLUMN} 1712.2.2.30.1.66
lcsSetupWanAdditionalPptpGatewaysEntryRtgTag32 OBJECT-TYPE
    SYNTAX     INTEGER (0..65535)
    MAX-ACCESS read-write
    STATUS     current
    DESCRIPTION
        "-- empty --"
    ::= { lcsSetupWanAdditionalPptpGatewaysEntry 66 }

-- {COLUMN} 1712.2.2.30.1.2
lcsSetupWanAdditionalPptpGatewaysEntryBeginWith OBJECT-TYPE
    SYNTAX     INTEGER
      {
        eLastUsed (0),
        eFirst (1),
        eRandom (2)
      }
    MAX-ACCESS read-write
    STATUS     current
    DESCRIPTION
        "-- empty --"
    ::= { lcsSetupWanAdditionalPptpGatewaysEntry 2 }

-- {SCALAR} 1712.2.2.31
lcsSetupWanPptpSourceCheck OBJECT-TYPE
    SYNTAX     INTEGER
      {
        eAddress (0),
        eTagPlusAddress (1)
      }
    MAX-ACCESS read-write
    STATUS     current
    DESCRIPTION
        "-- empty --"
    ::= { lcsSetupWan 31 }

-- {TABLE} 1712.2.2.35
lcsSetupWanL2tpEndpointsTable OBJECT-TYPE
    SYNTAX     SEQUENCE OF LcsSetupWanL2tpEndpointsEntry
    MAX-ACCESS not-accessible
    STATUS     current
    DESCRIPTION
        "-- empty --"
    ::= { lcsSetupWan 35 }

-- {ENTRY} 1712.2.2.35.1
lcsSetupWanL2tpEndpointsEntry OBJECT-TYPE
    SYNTAX     LcsSetupWanL2tpEndpointsEntry
    MAX-ACCESS not-accessible
    STATUS     current
    DESCRIPTION
        ""
    INDEX {
        lcsSetupWanL2tpEndpointsEntryIdentifier
    }
    ::= { lcsSetupWanL2tpEndpointsTable 1 }

-- {SEQUENCE}
LcsSetupWanL2tpEndpointsEntry ::= SEQUENCE {
    lcsSetupWanL2tpEndpointsEntryIdentifier DisplayString,
    lcsSetupWanL2tpEndpointsEntryIpAddress DisplayString,
    lcsSetupWanL2tpEndpointsEntryRtgTag INTEGER,
    lcsSetupWanL2tpEndpointsEntryPort INTEGER,
    lcsSetupWanL2tpEndpointsEntryPoll INTEGER,
    lcsSetupWanL2tpEndpointsEntryHostname DisplayString,
    lcsSetupWanL2tpEndpointsEntryPassword DisplayString,
    lcsSetupWanL2tpEndpointsEntryAuthPeer INTEGER,
    lcsSetupWanL2tpEndpointsEntryHide INTEGER
}

-- {COLUMN} 1712.2.2.35.1.1
lcsSetupWanL2tpEndpointsEntryIdentifier OBJECT-TYPE
    SYNTAX     DisplayString (SIZE(0..16))
    MAX-ACCESS read-write
    STATUS     current
    DESCRIPTION
        "-- empty --"
    ::= { lcsSetupWanL2tpEndpointsEntry 1 }

-- {COLUMN} 1712.2.2.35.1.2
lcsSetupWanL2tpEndpointsEntryIpAddress OBJECT-TYPE
    SYNTAX     DisplayString (SIZE(0..64))
    MAX-ACCESS read-write
    STATUS     current
    DESCRIPTION
        "-- empty --"
    ::= { lcsSetupWanL2tpEndpointsEntry 2 }

-- {COLUMN} 1712.2.2.35.1.3
lcsSetupWanL2tpEndpointsEntryRtgTag OBJECT-TYPE
    SYNTAX     INTEGER (0..65535)
    MAX-ACCESS read-write
    STATUS     current
    DESCRIPTION
        "-- empty --"
    ::= { lcsSetupWanL2tpEndpointsEntry 3 }

-- {COLUMN} 1712.2.2.35.1.4
lcsSetupWanL2tpEndpointsEntryPort OBJECT-TYPE
    SYNTAX     INTEGER (0..65535)
    MAX-ACCESS read-write
    STATUS     current
    DESCRIPTION
        "-- empty --"
    ::= { lcsSetupWanL2tpEndpointsEntry 4 }

-- {COLUMN} 1712.2.2.35.1.5
lcsSetupWanL2tpEndpointsEntryPoll OBJECT-TYPE
    SYNTAX     INTEGER (0..65535)
    MAX-ACCESS read-write
    STATUS     current
    DESCRIPTION
        "-- empty --"
    ::= { lcsSetupWanL2tpEndpointsEntry 5 }

-- {COLUMN} 1712.2.2.35.1.6
lcsSetupWanL2tpEndpointsEntryHostname OBJECT-TYPE
    SYNTAX     DisplayString (SIZE(0..64))
    MAX-ACCESS read-write
    STATUS     current
    DESCRIPTION
        "-- empty --"
    ::= { lcsSetupWanL2tpEndpointsEntry 6 }

-- {COLUMN} 1712.2.2.35.1.7
lcsSetupWanL2tpEndpointsEntryPassword OBJECT-TYPE
    SYNTAX     DisplayString (SIZE(0..32))
    MAX-ACCESS read-write
    STATUS     current
    DESCRIPTION
        "-- empty --"
    ::= { lcsSetupWanL2tpEndpointsEntry 7 }

-- {COLUMN} 1712.2.2.35.1.8
lcsSetupWanL2tpEndpointsEntryAuthPeer OBJECT-TYPE
    SYNTAX     INTEGER
      {
        eNo (0),
        eYes (1)
      }
    MAX-ACCESS read-write
    STATUS     current
    DESCRIPTION
        "-- empty --"
    ::= { lcsSetupWanL2tpEndpointsEntry 8 }

-- {COLUMN} 1712.2.2.35.1.9
lcsSetupWanL2tpEndpointsEntryHide OBJECT-TYPE
    SYNTAX     INTEGER
      {
        eNo (0),
        eYes (1)
      }
    MAX-ACCESS read-write
    STATUS     current
    DESCRIPTION
        "-- empty --"
    ::= { lcsSetupWanL2tpEndpointsEntry 9 }

-- {TABLE} 1712.2.2.36
lcsSetupWanL2tpAdditionalGatewaysTable OBJECT-TYPE
    SYNTAX     SEQUENCE OF LcsSetupWanL2tpAdditionalGatewaysEntry
    MAX-ACCESS not-accessible
    STATUS     current
    DESCRIPTION
        "-- empty --"
    ::= { lcsSetupWan 36 }

-- {ENTRY} 1712.2.2.36.1
lcsSetupWanL2tpAdditionalGatewaysEntry OBJECT-TYPE
    SYNTAX     LcsSetupWanL2tpAdditionalGatewaysEntry
    MAX-ACCESS not-accessible
    STATUS     current
    DESCRIPTION
        ""
    INDEX {
        lcsSetupWanL2tpAdditionalGatewaysEntryIdentifier
    }
    ::= { lcsSetupWanL2tpAdditionalGatewaysTable 1 }

-- {SEQUENCE}
LcsSetupWanL2tpAdditionalGatewaysEntry ::= SEQUENCE {
    lcsSetupWanL2tpAdditionalGatewaysEntryIdentifier DisplayString,
    lcsSetupWanL2tpAdditionalGatewaysEntryGateway1 DisplayString,
    lcsSetupWanL2tpAdditionalGatewaysEntryRtgTag1 INTEGER,
    lcsSetupWanL2tpAdditionalGatewaysEntryGateway2 DisplayString,
    lcsSetupWanL2tpAdditionalGatewaysEntryRtgTag2 INTEGER,
    lcsSetupWanL2tpAdditionalGatewaysEntryGateway3 DisplayString,
    lcsSetupWanL2tpAdditionalGatewaysEntryRtgTag3 INTEGER,
    lcsSetupWanL2tpAdditionalGatewaysEntryGateway4 DisplayString,
    lcsSetupWanL2tpAdditionalGatewaysEntryRtgTag4 INTEGER,
    lcsSetupWanL2tpAdditionalGatewaysEntryGateway5 DisplayString,
    lcsSetupWanL2tpAdditionalGatewaysEntryRtgTag5 INTEGER,
    lcsSetupWanL2tpAdditionalGatewaysEntryGateway6 DisplayString,
    lcsSetupWanL2tpAdditionalGatewaysEntryRtgTag6 INTEGER,
    lcsSetupWanL2tpAdditionalGatewaysEntryGateway7 DisplayString,
    lcsSetupWanL2tpAdditionalGatewaysEntryRtgTag7 INTEGER,
    lcsSetupWanL2tpAdditionalGatewaysEntryGateway8 DisplayString,
    lcsSetupWanL2tpAdditionalGatewaysEntryRtgTag8 INTEGER,
    lcsSetupWanL2tpAdditionalGatewaysEntryGateway9 DisplayString,
    lcsSetupWanL2tpAdditionalGatewaysEntryRtgTag9 INTEGER,
    lcsSetupWanL2tpAdditionalGatewaysEntryGateway10 DisplayString,
    lcsSetupWanL2tpAdditionalGatewaysEntryRtgTag10 INTEGER,
    lcsSetupWanL2tpAdditionalGatewaysEntryGateway11 DisplayString,
    lcsSetupWanL2tpAdditionalGatewaysEntryRtgTag11 INTEGER,
    lcsSetupWanL2tpAdditionalGatewaysEntryGateway12 DisplayString,
    lcsSetupWanL2tpAdditionalGatewaysEntryRtgTag12 INTEGER,
    lcsSetupWanL2tpAdditionalGatewaysEntryGateway13 DisplayString,
    lcsSetupWanL2tpAdditionalGatewaysEntryRtgTag13 INTEGER,
    lcsSetupWanL2tpAdditionalGatewaysEntryGateway14 DisplayString,
    lcsSetupWanL2tpAdditionalGatewaysEntryRtgTag14 INTEGER,
    lcsSetupWanL2tpAdditionalGatewaysEntryGateway15 DisplayString,
    lcsSetupWanL2tpAdditionalGatewaysEntryRtgTag15 INTEGER,
    lcsSetupWanL2tpAdditionalGatewaysEntryGateway16 DisplayString,
    lcsSetupWanL2tpAdditionalGatewaysEntryRtgTag16 INTEGER,
    lcsSetupWanL2tpAdditionalGatewaysEntryGateway17 DisplayString,
    lcsSetupWanL2tpAdditionalGatewaysEntryRtgTag17 INTEGER,
    lcsSetupWanL2tpAdditionalGatewaysEntryGateway18 DisplayString,
    lcsSetupWanL2tpAdditionalGatewaysEntryRtgTag18 INTEGER,
    lcsSetupWanL2tpAdditionalGatewaysEntryGateway19 DisplayString,
    lcsSetupWanL2tpAdditionalGatewaysEntryRtgTag19 INTEGER,
    lcsSetupWanL2tpAdditionalGatewaysEntryGateway20 DisplayString,
    lcsSetupWanL2tpAdditionalGatewaysEntryRtgTag20 INTEGER,
    lcsSetupWanL2tpAdditionalGatewaysEntryGateway21 DisplayString,
    lcsSetupWanL2tpAdditionalGatewaysEntryRtgTag21 INTEGER,
    lcsSetupWanL2tpAdditionalGatewaysEntryGateway22 DisplayString,
    lcsSetupWanL2tpAdditionalGatewaysEntryRtgTag22 INTEGER,
    lcsSetupWanL2tpAdditionalGatewaysEntryGateway23 DisplayString,
    lcsSetupWanL2tpAdditionalGatewaysEntryRtgTag23 INTEGER,
    lcsSetupWanL2tpAdditionalGatewaysEntryGateway24 DisplayString,
    lcsSetupWanL2tpAdditionalGatewaysEntryRtgTag24 INTEGER,
    lcsSetupWanL2tpAdditionalGatewaysEntryGateway25 DisplayString,
    lcsSetupWanL2tpAdditionalGatewaysEntryRtgTag25 INTEGER,
    lcsSetupWanL2tpAdditionalGatewaysEntryGateway26 DisplayString,
    lcsSetupWanL2tpAdditionalGatewaysEntryRtgTag26 INTEGER,
    lcsSetupWanL2tpAdditionalGatewaysEntryGateway27 DisplayString,
    lcsSetupWanL2tpAdditionalGatewaysEntryRtgTag27 INTEGER,
    lcsSetupWanL2tpAdditionalGatewaysEntryGateway28 DisplayString,
    lcsSetupWanL2tpAdditionalGatewaysEntryRtgTag28 INTEGER,
    lcsSetupWanL2tpAdditionalGatewaysEntryGateway29 DisplayString,
    lcsSetupWanL2tpAdditionalGatewaysEntryRtgTag29 INTEGER,
    lcsSetupWanL2tpAdditionalGatewaysEntryGateway30 DisplayString,
    lcsSetupWanL2tpAdditionalGatewaysEntryRtgTag30 INTEGER,
    lcsSetupWanL2tpAdditionalGatewaysEntryGateway31 DisplayString,
    lcsSetupWanL2tpAdditionalGatewaysEntryRtgTag31 INTEGER,
    lcsSetupWanL2tpAdditionalGatewaysEntryGateway32 DisplayString,
    lcsSetupWanL2tpAdditionalGatewaysEntryRtgTag32 INTEGER,
    lcsSetupWanL2tpAdditionalGatewaysEntryBeginWith INTEGER
}

-- {COLUMN} 1712.2.2.36.1.1
lcsSetupWanL2tpAdditionalGatewaysEntryIdentifier OBJECT-TYPE
    SYNTAX     DisplayString (SIZE(0..16))
    MAX-ACCESS read-write
    STATUS     current
    DESCRIPTION
        "-- empty --"
    ::= { lcsSetupWanL2tpAdditionalGatewaysEntry 1 }

-- {COLUMN} 1712.2.2.36.1.3
lcsSetupWanL2tpAdditionalGatewaysEntryGateway1 OBJECT-TYPE
    SYNTAX     DisplayString (SIZE(0..64))
    MAX-ACCESS read-write
    STATUS     current
    DESCRIPTION
        "-- empty --"
    ::= { lcsSetupWanL2tpAdditionalGatewaysEntry 3 }

-- {COLUMN} 1712.2.2.36.1.4
lcsSetupWanL2tpAdditionalGatewaysEntryRtgTag1 OBJECT-TYPE
    SYNTAX     INTEGER (0..65535)
    MAX-ACCESS read-write
    STATUS     current
    DESCRIPTION
        "-- empty --"
    ::= { lcsSetupWanL2tpAdditionalGatewaysEntry 4 }

-- {COLUMN} 1712.2.2.36.1.5
lcsSetupWanL2tpAdditionalGatewaysEntryGateway2 OBJECT-TYPE
    SYNTAX     DisplayString (SIZE(0..64))
    MAX-ACCESS read-write
    STATUS     current
    DESCRIPTION
        "-- empty --"
    ::= { lcsSetupWanL2tpAdditionalGatewaysEntry 5 }

-- {COLUMN} 1712.2.2.36.1.6
lcsSetupWanL2tpAdditionalGatewaysEntryRtgTag2 OBJECT-TYPE
    SYNTAX     INTEGER (0..65535)
    MAX-ACCESS read-write
    STATUS     current
    DESCRIPTION
        "-- empty --"
    ::= { lcsSetupWanL2tpAdditionalGatewaysEntry 6 }

-- {COLUMN} 1712.2.2.36.1.7
lcsSetupWanL2tpAdditionalGatewaysEntryGateway3 OBJECT-TYPE
    SYNTAX     DisplayString (SIZE(0..64))
    MAX-ACCESS read-write
    STATUS     current
    DESCRIPTION
        "-- empty --"
    ::= { lcsSetupWanL2tpAdditionalGatewaysEntry 7 }

-- {COLUMN} 1712.2.2.36.1.8
lcsSetupWanL2tpAdditionalGatewaysEntryRtgTag3 OBJECT-TYPE
    SYNTAX     INTEGER (0..65535)
    MAX-ACCESS read-write
    STATUS     current
    DESCRIPTION
        "-- empty --"
    ::= { lcsSetupWanL2tpAdditionalGatewaysEntry 8 }

-- {COLUMN} 1712.2.2.36.1.9
lcsSetupWanL2tpAdditionalGatewaysEntryGateway4 OBJECT-TYPE
    SYNTAX     DisplayString (SIZE(0..64))
    MAX-ACCESS read-write
    STATUS     current
    DESCRIPTION
        "-- empty --"
    ::= { lcsSetupWanL2tpAdditionalGatewaysEntry 9 }

-- {COLUMN} 1712.2.2.36.1.10
lcsSetupWanL2tpAdditionalGatewaysEntryRtgTag4 OBJECT-TYPE
    SYNTAX     INTEGER (0..65535)
    MAX-ACCESS read-write
    STATUS     current
    DESCRIPTION
        "-- empty --"
    ::= { lcsSetupWanL2tpAdditionalGatewaysEntry 10 }

-- {COLUMN} 1712.2.2.36.1.11
lcsSetupWanL2tpAdditionalGatewaysEntryGateway5 OBJECT-TYPE
    SYNTAX     DisplayString (SIZE(0..64))
    MAX-ACCESS read-write
    STATUS     current
    DESCRIPTION
        "-- empty --"
    ::= { lcsSetupWanL2tpAdditionalGatewaysEntry 11 }

-- {COLUMN} 1712.2.2.36.1.12
lcsSetupWanL2tpAdditionalGatewaysEntryRtgTag5 OBJECT-TYPE
    SYNTAX     INTEGER (0..65535)
    MAX-ACCESS read-write
    STATUS     current
    DESCRIPTION
        "-- empty --"
    ::= { lcsSetupWanL2tpAdditionalGatewaysEntry 12 }

-- {COLUMN} 1712.2.2.36.1.13
lcsSetupWanL2tpAdditionalGatewaysEntryGateway6 OBJECT-TYPE
    SYNTAX     DisplayString (SIZE(0..64))
    MAX-ACCESS read-write
    STATUS     current
    DESCRIPTION
        "-- empty --"
    ::= { lcsSetupWanL2tpAdditionalGatewaysEntry 13 }

-- {COLUMN} 1712.2.2.36.1.14
lcsSetupWanL2tpAdditionalGatewaysEntryRtgTag6 OBJECT-TYPE
    SYNTAX     INTEGER (0..65535)
    MAX-ACCESS read-write
    STATUS     current
    DESCRIPTION
        "-- empty --"
    ::= { lcsSetupWanL2tpAdditionalGatewaysEntry 14 }

-- {COLUMN} 1712.2.2.36.1.15
lcsSetupWanL2tpAdditionalGatewaysEntryGateway7 OBJECT-TYPE
    SYNTAX     DisplayString (SIZE(0..64))
    MAX-ACCESS read-write
    STATUS     current
    DESCRIPTION
        "-- empty --"
    ::= { lcsSetupWanL2tpAdditionalGatewaysEntry 15 }

-- {COLUMN} 1712.2.2.36.1.16
lcsSetupWanL2tpAdditionalGatewaysEntryRtgTag7 OBJECT-TYPE
    SYNTAX     INTEGER (0..65535)
    MAX-ACCESS read-write
    STATUS     current
    DESCRIPTION
        "-- empty --"
    ::= { lcsSetupWanL2tpAdditionalGatewaysEntry 16 }

-- {COLUMN} 1712.2.2.36.1.17
lcsSetupWanL2tpAdditionalGatewaysEntryGateway8 OBJECT-TYPE
    SYNTAX     DisplayString (SIZE(0..64))
    MAX-ACCESS read-write
    STATUS     current
    DESCRIPTION
        "-- empty --"
    ::= { lcsSetupWanL2tpAdditionalGatewaysEntry 17 }

-- {COLUMN} 1712.2.2.36.1.18
lcsSetupWanL2tpAdditionalGatewaysEntryRtgTag8 OBJECT-TYPE
    SYNTAX     INTEGER (0..65535)
    MAX-ACCESS read-write
    STATUS     current
    DESCRIPTION
        "-- empty --"
    ::= { lcsSetupWanL2tpAdditionalGatewaysEntry 18 }

-- {COLUMN} 1712.2.2.36.1.19
lcsSetupWanL2tpAdditionalGatewaysEntryGateway9 OBJECT-TYPE
    SYNTAX     DisplayString (SIZE(0..64))
    MAX-ACCESS read-write
    STATUS     current
    DESCRIPTION
        "-- empty --"
    ::= { lcsSetupWanL2tpAdditionalGatewaysEntry 19 }

-- {COLUMN} 1712.2.2.36.1.20
lcsSetupWanL2tpAdditionalGatewaysEntryRtgTag9 OBJECT-TYPE
    SYNTAX     INTEGER (0..65535)
    MAX-ACCESS read-write
    STATUS     current
    DESCRIPTION
        "-- empty --"
    ::= { lcsSetupWanL2tpAdditionalGatewaysEntry 20 }

-- {COLUMN} 1712.2.2.36.1.21
lcsSetupWanL2tpAdditionalGatewaysEntryGateway10 OBJECT-TYPE
    SYNTAX     DisplayString (SIZE(0..64))
    MAX-ACCESS read-write
    STATUS     current
    DESCRIPTION
        "-- empty --"
    ::= { lcsSetupWanL2tpAdditionalGatewaysEntry 21 }

-- {COLUMN} 1712.2.2.36.1.22
lcsSetupWanL2tpAdditionalGatewaysEntryRtgTag10 OBJECT-TYPE
    SYNTAX     INTEGER (0..65535)
    MAX-ACCESS read-write
    STATUS     current
    DESCRIPTION
        "-- empty --"
    ::= { lcsSetupWanL2tpAdditionalGatewaysEntry 22 }

-- {COLUMN} 1712.2.2.36.1.23
lcsSetupWanL2tpAdditionalGatewaysEntryGateway11 OBJECT-TYPE
    SYNTAX     DisplayString (SIZE(0..64))
    MAX-ACCESS read-write
    STATUS     current
    DESCRIPTION
        "-- empty --"
    ::= { lcsSetupWanL2tpAdditionalGatewaysEntry 23 }

-- {COLUMN} 1712.2.2.36.1.24
lcsSetupWanL2tpAdditionalGatewaysEntryRtgTag11 OBJECT-TYPE
    SYNTAX     INTEGER (0..65535)
    MAX-ACCESS read-write
    STATUS     current
    DESCRIPTION
        "-- empty --"
    ::= { lcsSetupWanL2tpAdditionalGatewaysEntry 24 }

-- {COLUMN} 1712.2.2.36.1.25
lcsSetupWanL2tpAdditionalGatewaysEntryGateway12 OBJECT-TYPE
    SYNTAX     DisplayString (SIZE(0..64))
    MAX-ACCESS read-write
    STATUS     current
    DESCRIPTION
        "-- empty --"
    ::= { lcsSetupWanL2tpAdditionalGatewaysEntry 25 }

-- {COLUMN} 1712.2.2.36.1.26
lcsSetupWanL2tpAdditionalGatewaysEntryRtgTag12 OBJECT-TYPE
    SYNTAX     INTEGER (0..65535)
    MAX-ACCESS read-write
    STATUS     current
    DESCRIPTION
        "-- empty --"
    ::= { lcsSetupWanL2tpAdditionalGatewaysEntry 26 }

-- {COLUMN} 1712.2.2.36.1.27
lcsSetupWanL2tpAdditionalGatewaysEntryGateway13 OBJECT-TYPE
    SYNTAX     DisplayString (SIZE(0..64))
    MAX-ACCESS read-write
    STATUS     current
    DESCRIPTION
        "-- empty --"
    ::= { lcsSetupWanL2tpAdditionalGatewaysEntry 27 }

-- {COLUMN} 1712.2.2.36.1.28
lcsSetupWanL2tpAdditionalGatewaysEntryRtgTag13 OBJECT-TYPE
    SYNTAX     INTEGER (0..65535)
    MAX-ACCESS read-write
    STATUS     current
    DESCRIPTION
        "-- empty --"
    ::= { lcsSetupWanL2tpAdditionalGatewaysEntry 28 }

-- {COLUMN} 1712.2.2.36.1.29
lcsSetupWanL2tpAdditionalGatewaysEntryGateway14 OBJECT-TYPE
    SYNTAX     DisplayString (SIZE(0..64))
    MAX-ACCESS read-write
    STATUS     current
    DESCRIPTION
        "-- empty --"
    ::= { lcsSetupWanL2tpAdditionalGatewaysEntry 29 }

-- {COLUMN} 1712.2.2.36.1.30
lcsSetupWanL2tpAdditionalGatewaysEntryRtgTag14 OBJECT-TYPE
    SYNTAX     INTEGER (0..65535)
    MAX-ACCESS read-write
    STATUS     current
    DESCRIPTION
        "-- empty --"
    ::= { lcsSetupWanL2tpAdditionalGatewaysEntry 30 }

-- {COLUMN} 1712.2.2.36.1.31
lcsSetupWanL2tpAdditionalGatewaysEntryGateway15 OBJECT-TYPE
    SYNTAX     DisplayString (SIZE(0..64))
    MAX-ACCESS read-write
    STATUS     current
    DESCRIPTION
        "-- empty --"
    ::= { lcsSetupWanL2tpAdditionalGatewaysEntry 31 }

-- {COLUMN} 1712.2.2.36.1.32
lcsSetupWanL2tpAdditionalGatewaysEntryRtgTag15 OBJECT-TYPE
    SYNTAX     INTEGER (0..65535)
    MAX-ACCESS read-write
    STATUS     current
    DESCRIPTION
        "-- empty --"
    ::= { lcsSetupWanL2tpAdditionalGatewaysEntry 32 }

-- {COLUMN} 1712.2.2.36.1.33
lcsSetupWanL2tpAdditionalGatewaysEntryGateway16 OBJECT-TYPE
    SYNTAX     DisplayString (SIZE(0..64))
    MAX-ACCESS read-write
    STATUS     current
    DESCRIPTION
        "-- empty --"
    ::= { lcsSetupWanL2tpAdditionalGatewaysEntry 33 }

-- {COLUMN} 1712.2.2.36.1.34
lcsSetupWanL2tpAdditionalGatewaysEntryRtgTag16 OBJECT-TYPE
    SYNTAX     INTEGER (0..65535)
    MAX-ACCESS read-write
    STATUS     current
    DESCRIPTION
        "-- empty --"
    ::= { lcsSetupWanL2tpAdditionalGatewaysEntry 34 }

-- {COLUMN} 1712.2.2.36.1.35
lcsSetupWanL2tpAdditionalGatewaysEntryGateway17 OBJECT-TYPE
    SYNTAX     DisplayString (SIZE(0..64))
    MAX-ACCESS read-write
    STATUS     current
    DESCRIPTION
        "-- empty --"
    ::= { lcsSetupWanL2tpAdditionalGatewaysEntry 35 }

-- {COLUMN} 1712.2.2.36.1.36
lcsSetupWanL2tpAdditionalGatewaysEntryRtgTag17 OBJECT-TYPE
    SYNTAX     INTEGER (0..65535)
    MAX-ACCESS read-write
    STATUS     current
    DESCRIPTION
        "-- empty --"
    ::= { lcsSetupWanL2tpAdditionalGatewaysEntry 36 }

-- {COLUMN} 1712.2.2.36.1.37
lcsSetupWanL2tpAdditionalGatewaysEntryGateway18 OBJECT-TYPE
    SYNTAX     DisplayString (SIZE(0..64))
    MAX-ACCESS read-write
    STATUS     current
    DESCRIPTION
        "-- empty --"
    ::= { lcsSetupWanL2tpAdditionalGatewaysEntry 37 }

-- {COLUMN} 1712.2.2.36.1.38
lcsSetupWanL2tpAdditionalGatewaysEntryRtgTag18 OBJECT-TYPE
    SYNTAX     INTEGER (0..65535)
    MAX-ACCESS read-write
    STATUS     current
    DESCRIPTION
        "-- empty --"
    ::= { lcsSetupWanL2tpAdditionalGatewaysEntry 38 }

-- {COLUMN} 1712.2.2.36.1.39
lcsSetupWanL2tpAdditionalGatewaysEntryGateway19 OBJECT-TYPE
    SYNTAX     DisplayString (SIZE(0..64))
    MAX-ACCESS read-write
    STATUS     current
    DESCRIPTION
        "-- empty --"
    ::= { lcsSetupWanL2tpAdditionalGatewaysEntry 39 }

-- {COLUMN} 1712.2.2.36.1.40
lcsSetupWanL2tpAdditionalGatewaysEntryRtgTag19 OBJECT-TYPE
    SYNTAX     INTEGER (0..65535)
    MAX-ACCESS read-write
    STATUS     current
    DESCRIPTION
        "-- empty --"
    ::= { lcsSetupWanL2tpAdditionalGatewaysEntry 40 }

-- {COLUMN} 1712.2.2.36.1.41
lcsSetupWanL2tpAdditionalGatewaysEntryGateway20 OBJECT-TYPE
    SYNTAX     DisplayString (SIZE(0..64))
    MAX-ACCESS read-write
    STATUS     current
    DESCRIPTION
        "-- empty --"
    ::= { lcsSetupWanL2tpAdditionalGatewaysEntry 41 }

-- {COLUMN} 1712.2.2.36.1.42
lcsSetupWanL2tpAdditionalGatewaysEntryRtgTag20 OBJECT-TYPE
    SYNTAX     INTEGER (0..65535)
    MAX-ACCESS read-write
    STATUS     current
    DESCRIPTION
        "-- empty --"
    ::= { lcsSetupWanL2tpAdditionalGatewaysEntry 42 }

-- {COLUMN} 1712.2.2.36.1.43
lcsSetupWanL2tpAdditionalGatewaysEntryGateway21 OBJECT-TYPE
    SYNTAX     DisplayString (SIZE(0..64))
    MAX-ACCESS read-write
    STATUS     current
    DESCRIPTION
        "-- empty --"
    ::= { lcsSetupWanL2tpAdditionalGatewaysEntry 43 }

-- {COLUMN} 1712.2.2.36.1.44
lcsSetupWanL2tpAdditionalGatewaysEntryRtgTag21 OBJECT-TYPE
    SYNTAX     INTEGER (0..65535)
    MAX-ACCESS read-write
    STATUS     current
    DESCRIPTION
        "-- empty --"
    ::= { lcsSetupWanL2tpAdditionalGatewaysEntry 44 }

-- {COLUMN} 1712.2.2.36.1.45
lcsSetupWanL2tpAdditionalGatewaysEntryGateway22 OBJECT-TYPE
    SYNTAX     DisplayString (SIZE(0..64))
    MAX-ACCESS read-write
    STATUS     current
    DESCRIPTION
        "-- empty --"
    ::= { lcsSetupWanL2tpAdditionalGatewaysEntry 45 }

-- {COLUMN} 1712.2.2.36.1.46
lcsSetupWanL2tpAdditionalGatewaysEntryRtgTag22 OBJECT-TYPE
    SYNTAX     INTEGER (0..65535)
    MAX-ACCESS read-write
    STATUS     current
    DESCRIPTION
        "-- empty --"
    ::= { lcsSetupWanL2tpAdditionalGatewaysEntry 46 }

-- {COLUMN} 1712.2.2.36.1.47
lcsSetupWanL2tpAdditionalGatewaysEntryGateway23 OBJECT-TYPE
    SYNTAX     DisplayString (SIZE(0..64))
    MAX-ACCESS read-write
    STATUS     current
    DESCRIPTION
        "-- empty --"
    ::= { lcsSetupWanL2tpAdditionalGatewaysEntry 47 }

-- {COLUMN} 1712.2.2.36.1.48
lcsSetupWanL2tpAdditionalGatewaysEntryRtgTag23 OBJECT-TYPE
    SYNTAX     INTEGER (0..65535)
    MAX-ACCESS read-write
    STATUS     current
    DESCRIPTION
        "-- empty --"
    ::= { lcsSetupWanL2tpAdditionalGatewaysEntry 48 }

-- {COLUMN} 1712.2.2.36.1.49
lcsSetupWanL2tpAdditionalGatewaysEntryGateway24 OBJECT-TYPE
    SYNTAX     DisplayString (SIZE(0..64))
    MAX-ACCESS read-write
    STATUS     current
    DESCRIPTION
        "-- empty --"
    ::= { lcsSetupWanL2tpAdditionalGatewaysEntry 49 }

-- {COLUMN} 1712.2.2.36.1.50
lcsSetupWanL2tpAdditionalGatewaysEntryRtgTag24 OBJECT-TYPE
    SYNTAX     INTEGER (0..65535)
    MAX-ACCESS read-write
    STATUS     current
    DESCRIPTION
        "-- empty --"
    ::= { lcsSetupWanL2tpAdditionalGatewaysEntry 50 }

-- {COLUMN} 1712.2.2.36.1.51
lcsSetupWanL2tpAdditionalGatewaysEntryGateway25 OBJECT-TYPE
    SYNTAX     DisplayString (SIZE(0..64))
    MAX-ACCESS read-write
    STATUS     current
    DESCRIPTION
        "-- empty --"
    ::= { lcsSetupWanL2tpAdditionalGatewaysEntry 51 }

-- {COLUMN} 1712.2.2.36.1.52
lcsSetupWanL2tpAdditionalGatewaysEntryRtgTag25 OBJECT-TYPE
    SYNTAX     INTEGER (0..65535)
    MAX-ACCESS read-write
    STATUS     current
    DESCRIPTION
        "-- empty --"
    ::= { lcsSetupWanL2tpAdditionalGatewaysEntry 52 }

-- {COLUMN} 1712.2.2.36.1.53
lcsSetupWanL2tpAdditionalGatewaysEntryGateway26 OBJECT-TYPE
    SYNTAX     DisplayString (SIZE(0..64))
    MAX-ACCESS read-write
    STATUS     current
    DESCRIPTION
        "-- empty --"
    ::= { lcsSetupWanL2tpAdditionalGatewaysEntry 53 }

-- {COLUMN} 1712.2.2.36.1.54
lcsSetupWanL2tpAdditionalGatewaysEntryRtgTag26 OBJECT-TYPE
    SYNTAX     INTEGER (0..65535)
    MAX-ACCESS read-write
    STATUS     current
    DESCRIPTION
        "-- empty --"
    ::= { lcsSetupWanL2tpAdditionalGatewaysEntry 54 }

-- {COLUMN} 1712.2.2.36.1.55
lcsSetupWanL2tpAdditionalGatewaysEntryGateway27 OBJECT-TYPE
    SYNTAX     DisplayString (SIZE(0..64))
    MAX-ACCESS read-write
    STATUS     current
    DESCRIPTION
        "-- empty --"
    ::= { lcsSetupWanL2tpAdditionalGatewaysEntry 55 }

-- {COLUMN} 1712.2.2.36.1.56
lcsSetupWanL2tpAdditionalGatewaysEntryRtgTag27 OBJECT-TYPE
    SYNTAX     INTEGER (0..65535)
    MAX-ACCESS read-write
    STATUS     current
    DESCRIPTION
        "-- empty --"
    ::= { lcsSetupWanL2tpAdditionalGatewaysEntry 56 }

-- {COLUMN} 1712.2.2.36.1.57
lcsSetupWanL2tpAdditionalGatewaysEntryGateway28 OBJECT-TYPE
    SYNTAX     DisplayString (SIZE(0..64))
    MAX-ACCESS read-write
    STATUS     current
    DESCRIPTION
        "-- empty --"
    ::= { lcsSetupWanL2tpAdditionalGatewaysEntry 57 }

-- {COLUMN} 1712.2.2.36.1.58
lcsSetupWanL2tpAdditionalGatewaysEntryRtgTag28 OBJECT-TYPE
    SYNTAX     INTEGER (0..65535)
    MAX-ACCESS read-write
    STATUS     current
    DESCRIPTION
        "-- empty --"
    ::= { lcsSetupWanL2tpAdditionalGatewaysEntry 58 }

-- {COLUMN} 1712.2.2.36.1.59
lcsSetupWanL2tpAdditionalGatewaysEntryGateway29 OBJECT-TYPE
    SYNTAX     DisplayString (SIZE(0..64))
    MAX-ACCESS read-write
    STATUS     current
    DESCRIPTION
        "-- empty --"
    ::= { lcsSetupWanL2tpAdditionalGatewaysEntry 59 }

-- {COLUMN} 1712.2.2.36.1.60
lcsSetupWanL2tpAdditionalGatewaysEntryRtgTag29 OBJECT-TYPE
    SYNTAX     INTEGER (0..65535)
    MAX-ACCESS read-write
    STATUS     current
    DESCRIPTION
        "-- empty --"
    ::= { lcsSetupWanL2tpAdditionalGatewaysEntry 60 }

-- {COLUMN} 1712.2.2.36.1.61
lcsSetupWanL2tpAdditionalGatewaysEntryGateway30 OBJECT-TYPE
    SYNTAX     DisplayString (SIZE(0..64))
    MAX-ACCESS read-write
    STATUS     current
    DESCRIPTION
        "-- empty --"
    ::= { lcsSetupWanL2tpAdditionalGatewaysEntry 61 }

-- {COLUMN} 1712.2.2.36.1.62
lcsSetupWanL2tpAdditionalGatewaysEntryRtgTag30 OBJECT-TYPE
    SYNTAX     INTEGER (0..65535)
    MAX-ACCESS read-write
    STATUS     current
    DESCRIPTION
        "-- empty --"
    ::= { lcsSetupWanL2tpAdditionalGatewaysEntry 62 }

-- {COLUMN} 1712.2.2.36.1.63
lcsSetupWanL2tpAdditionalGatewaysEntryGateway31 OBJECT-TYPE
    SYNTAX     DisplayString (SIZE(0..64))
    MAX-ACCESS read-write
    STATUS     current
    DESCRIPTION
        "-- empty --"
    ::= { lcsSetupWanL2tpAdditionalGatewaysEntry 63 }

-- {COLUMN} 1712.2.2.36.1.64
lcsSetupWanL2tpAdditionalGatewaysEntryRtgTag31 OBJECT-TYPE
    SYNTAX     INTEGER (0..65535)
    MAX-ACCESS read-write
    STATUS     current
    DESCRIPTION
        "-- empty --"
    ::= { lcsSetupWanL2tpAdditionalGatewaysEntry 64 }

-- {COLUMN} 1712.2.2.36.1.65
lcsSetupWanL2tpAdditionalGatewaysEntryGateway32 OBJECT-TYPE
    SYNTAX     DisplayString (SIZE(0..64))
    MAX-ACCESS read-write
    STATUS     current
    DESCRIPTION
        "-- empty --"
    ::= { lcsSetupWanL2tpAdditionalGatewaysEntry 65 }

-- {COLUMN} 1712.2.2.36.1.66
lcsSetupWanL2tpAdditionalGatewaysEntryRtgTag32 OBJECT-TYPE
    SYNTAX     INTEGER (0..65535)
    MAX-ACCESS read-write
    STATUS     current
    DESCRIPTION
        "-- empty --"
    ::= { lcsSetupWanL2tpAdditionalGatewaysEntry 66 }

-- {COLUMN} 1712.2.2.36.1.2
lcsSetupWanL2tpAdditionalGatewaysEntryBeginWith OBJECT-TYPE
    SYNTAX     INTEGER
      {
        eLastUsed (0),
        eFirst (1),
        eRandom (2)
      }
    MAX-ACCESS read-write
    STATUS     current
    DESCRIPTION
        "-- empty --"
    ::= { lcsSetupWanL2tpAdditionalGatewaysEntry 2 }

-- {TABLE} 1712.2.2.37
lcsSetupWanL2tpPeersTable OBJECT-TYPE
    SYNTAX     SEQUENCE OF LcsSetupWanL2tpPeersEntry
    MAX-ACCESS not-accessible
    STATUS     current
    DESCRIPTION
        "-- empty --"
    ::= { lcsSetupWan 37 }

-- {ENTRY} 1712.2.2.37.1
lcsSetupWanL2tpPeersEntry OBJECT-TYPE
    SYNTAX     LcsSetupWanL2tpPeersEntry
    MAX-ACCESS not-accessible
    STATUS     current
    DESCRIPTION
        ""
    INDEX {
        lcsSetupWanL2tpPeersEntryPeer
    }
    ::= { lcsSetupWanL2tpPeersTable 1 }

-- {SEQUENCE}
LcsSetupWanL2tpPeersEntry ::= SEQUENCE {
    lcsSetupWanL2tpPeersEntryPeer DisplayString,
    lcsSetupWanL2tpPeersEntryL2tpEndpoint DisplayString,
    lcsSetupWanL2tpPeersEntryShTime INTEGER
}

-- {COLUMN} 1712.2.2.37.1.1
lcsSetupWanL2tpPeersEntryPeer OBJECT-TYPE
    SYNTAX     DisplayString (SIZE(0..16))
    MAX-ACCESS read-write
    STATUS     current
    DESCRIPTION
        "-- empty --"
    ::= { lcsSetupWanL2tpPeersEntry 1 }

-- {COLUMN} 1712.2.2.37.1.2
lcsSetupWanL2tpPeersEntryL2tpEndpoint OBJECT-TYPE
    SYNTAX     DisplayString (SIZE(0..16))
    MAX-ACCESS read-write
    STATUS     current
    DESCRIPTION
        "-- empty --"
    ::= { lcsSetupWanL2tpPeersEntry 2 }

-- {COLUMN} 1712.2.2.37.1.3
lcsSetupWanL2tpPeersEntryShTime OBJECT-TYPE
    SYNTAX     INTEGER (0..65535)
    MAX-ACCESS read-write
    STATUS     current
    DESCRIPTION
        "-- empty --"
    ::= { lcsSetupWanL2tpPeersEntry 3 }

-- {SCALAR} 1712.2.2.38
lcsSetupWanL2tpSourceCheck OBJECT-TYPE
    SYNTAX     INTEGER
      {
        eAddress (0),
        eTagPlusAddress (1)
      }
    MAX-ACCESS read-write
    STATUS     current
    DESCRIPTION
        "-- empty --"
    ::= { lcsSetupWan 38 }

-- {TABLE} 1712.2.2.40
lcsSetupWanDsLiteTunnelTable OBJECT-TYPE
    SYNTAX     SEQUENCE OF LcsSetupWanDsLiteTunnelEntry
    MAX-ACCESS not-accessible
    STATUS     current
    DESCRIPTION
        "-- empty --"
    ::= { lcsSetupWan 40 }

-- {ENTRY} 1712.2.2.40.1
lcsSetupWanDsLiteTunnelEntry OBJECT-TYPE
    SYNTAX     LcsSetupWanDsLiteTunnelEntry
    MAX-ACCESS not-accessible
    STATUS     current
    DESCRIPTION
        ""
    INDEX {
        lcsSetupWanDsLiteTunnelEntryName
    }
    ::= { lcsSetupWanDsLiteTunnelTable 1 }

-- {SEQUENCE}
LcsSetupWanDsLiteTunnelEntry ::= SEQUENCE {
    lcsSetupWanDsLiteTunnelEntryName DisplayString,
    lcsSetupWanDsLiteTunnelEntryGatewayAddress DisplayString,
    lcsSetupWanDsLiteTunnelEntryRtgTag INTEGER
}

-- {COLUMN} 1712.2.2.40.1.1
lcsSetupWanDsLiteTunnelEntryName OBJECT-TYPE
    SYNTAX     DisplayString (SIZE(0..16))
    MAX-ACCESS read-write
    STATUS     current
    DESCRIPTION
        "-- empty --"
    ::= { lcsSetupWanDsLiteTunnelEntry 1 }

-- {COLUMN} 1712.2.2.40.1.2
lcsSetupWanDsLiteTunnelEntryGatewayAddress OBJECT-TYPE
    SYNTAX     DisplayString (SIZE(0..64))
    MAX-ACCESS read-write
    STATUS     current
    DESCRIPTION
        "-- empty --"
    ::= { lcsSetupWanDsLiteTunnelEntry 2 }

-- {COLUMN} 1712.2.2.40.1.3
lcsSetupWanDsLiteTunnelEntryRtgTag OBJECT-TYPE
    SYNTAX     INTEGER (0..65535)
    MAX-ACCESS read-write
    STATUS     current
    DESCRIPTION
        "-- empty --"
    ::= { lcsSetupWanDsLiteTunnelEntry 3 }

-- {OID} 1712.2.2.22
lcsSetupWanRadius OBJECT IDENTIFIER ::= { lcsSetupWan 22 }

-- {SCALAR} 1712.2.2.22.1
lcsSetupWanRadiusOperating OBJECT-TYPE
    SYNTAX     INTEGER
      {
        eNo (0),
        eYes (1),
        eExclusive (2)
      }
    MAX-ACCESS read-write
    STATUS     current
    DESCRIPTION
        "-- empty --"
    ::= { lcsSetupWanRadius 1 }

-- {SCALAR} 1712.2.2.22.11
lcsSetupWanRadiusServerHostname OBJECT-TYPE
    SYNTAX     DisplayString (SIZE(0..64))
    MAX-ACCESS read-write
    STATUS     current
    DESCRIPTION
        "-- empty --"
    ::= { lcsSetupWanRadius 11 }

-- {SCALAR} 1712.2.2.22.3
lcsSetupWanRadiusAuthPort OBJECT-TYPE
    SYNTAX     INTEGER (0..65535)
    MAX-ACCESS read-write
    STATUS     current
    DESCRIPTION
        "-- empty --"
    ::= { lcsSetupWanRadius 3 }

-- {SCALAR} 1712.2.2.22.8
lcsSetupWanRadiusLoopbackAddr OBJECT-TYPE
    SYNTAX     DisplayString (SIZE(0..16))
    MAX-ACCESS read-write
    STATUS     current
    DESCRIPTION
        "-- empty --"
    ::= { lcsSetupWanRadius 8 }

-- {SCALAR} 1712.2.2.22.9
lcsSetupWanRadiusProtocol OBJECT-TYPE
    SYNTAX     INTEGER
      {
        eRadius (0),
        eRadsec (1)
      }
    MAX-ACCESS read-write
    STATUS     current
    DESCRIPTION
        "-- empty --"
    ::= { lcsSetupWanRadius 9 }

-- {SCALAR} 1712.2.2.22.4
lcsSetupWanRadiusSecret OBJECT-TYPE
    SYNTAX     DisplayString (SIZE(0..64))
    MAX-ACCESS read-write
    STATUS     current
    DESCRIPTION
        "-- empty --"
    ::= { lcsSetupWanRadius 4 }

-- {SCALAR} 1712.2.2.22.5
lcsSetupWanRadiusPppOperation OBJECT-TYPE
    SYNTAX     INTEGER
      {
        eNo (0),
        eYes (1),
        eExclusive (2)
      }
    MAX-ACCESS read-write
    STATUS     current
    DESCRIPTION
        "-- empty --"
    ::= { lcsSetupWanRadius 5 }

-- {SCALAR} 1712.2.2.22.10
lcsSetupWanRadiusAuthProtocols OBJECT-TYPE
    SYNTAX     BITS
      {
        eMsChapv2 (2),
        eMsChap (3),
        eChap (4),
        ePap (5)
      }
    MAX-ACCESS read-write
    STATUS     current
    DESCRIPTION
        "-- empty --"
    ::= { lcsSetupWanRadius 10 }

-- {SCALAR} 1712.2.2.22.6
lcsSetupWanRadiusClipOperation OBJECT-TYPE
    SYNTAX     INTEGER
      {
        eNo (0),
        eYes (1),
        eExclusive (2)
      }
    MAX-ACCESS read-write
    STATUS     current
    DESCRIPTION
        "-- empty --"
    ::= { lcsSetupWanRadius 6 }

-- {SCALAR} 1712.2.2.22.7
lcsSetupWanRadiusClipPassword OBJECT-TYPE
    SYNTAX     DisplayString (SIZE(0..64))
    MAX-ACCESS read-write
    STATUS     current
    DESCRIPTION
        "-- empty --"
    ::= { lcsSetupWanRadius 7 }

-- {SCALAR} 1712.2.2.22.20
lcsSetupWanRadiusL2tpOperating OBJECT-TYPE
    SYNTAX     INTEGER
      {
        eNo (0),
        eYes (1),
        eExclusive (2)
      }
    MAX-ACCESS read-write
    STATUS     current
    DESCRIPTION
        "-- empty --"
    ::= { lcsSetupWanRadius 20 }

-- {SCALAR} 1712.2.2.22.21
lcsSetupWanRadiusL2tpServerHostname OBJECT-TYPE
    SYNTAX     DisplayString (SIZE(0..64))
    MAX-ACCESS read-write
    STATUS     current
    DESCRIPTION
        "-- empty --"
    ::= { lcsSetupWanRadius 21 }

-- {SCALAR} 1712.2.2.22.22
lcsSetupWanRadiusL2tpAuthPort OBJECT-TYPE
    SYNTAX     INTEGER (0..65535)
    MAX-ACCESS read-write
    STATUS     current
    DESCRIPTION
        "-- empty --"
    ::= { lcsSetupWanRadius 22 }

-- {SCALAR} 1712.2.2.22.23
lcsSetupWanRadiusL2tpLoopbackAddress OBJECT-TYPE
    SYNTAX     DisplayString (SIZE(0..16))
    MAX-ACCESS read-write
    STATUS     current
    DESCRIPTION
        "-- empty --"
    ::= { lcsSetupWanRadius 23 }

-- {SCALAR} 1712.2.2.22.24
lcsSetupWanRadiusL2tpProtocol OBJECT-TYPE
    SYNTAX     INTEGER
      {
        eRadius (0),
        eRadsec (1)
      }
    MAX-ACCESS read-write
    STATUS     current
    DESCRIPTION
        "-- empty --"
    ::= { lcsSetupWanRadius 24 }

-- {SCALAR} 1712.2.2.22.25
lcsSetupWanRadiusL2tpSecret OBJECT-TYPE
    SYNTAX     DisplayString (SIZE(0..64))
    MAX-ACCESS read-write
    STATUS     current
    DESCRIPTION
        "-- empty --"
    ::= { lcsSetupWanRadius 25 }

-- {SCALAR} 1712.2.2.22.26
lcsSetupWanRadiusL2tpPassword OBJECT-TYPE
    SYNTAX     DisplayString (SIZE(0..64))
    MAX-ACCESS read-write
    STATUS     current
    DESCRIPTION
        "-- empty --"
    ::= { lcsSetupWanRadius 26 }

-- {TABLE} 1712.2.2.23
lcsSetupWanPollingTableTable OBJECT-TYPE
    SYNTAX     SEQUENCE OF LcsSetupWanPollingTableEntry
    MAX-ACCESS not-accessible
    STATUS     current
    DESCRIPTION
        "-- empty --"
    ::= { lcsSetupWan 23 }

-- {ENTRY} 1712.2.2.23.1
lcsSetupWanPollingTableEntry OBJECT-TYPE
    SYNTAX     LcsSetupWanPollingTableEntry
    MAX-ACCESS not-accessible
    STATUS     current
    DESCRIPTION
        ""
    INDEX {
        lcsSetupWanPollingTableEntryPeer
    }
    ::= { lcsSetupWanPollingTableTable 1 }

-- {SEQUENCE}
LcsSetupWanPollingTableEntry ::= SEQUENCE {
    lcsSetupWanPollingTableEntryPeer DisplayString,
    lcsSetupWanPollingTableEntryIpAddress1 IpAddress,
    lcsSetupWanPollingTableEntryIpAddress2 IpAddress,
    lcsSetupWanPollingTableEntryIpAddress3 IpAddress,
    lcsSetupWanPollingTableEntryIpAddress4 IpAddress,
    lcsSetupWanPollingTableEntryTime INTEGER,
    lcsSetupWanPollingTableEntryTry INTEGER,
    lcsSetupWanPollingTableEntryLoopbackAddr DisplayString,
    lcsSetupWanPollingTableEntryType INTEGER
}

-- {COLUMN} 1712.2.2.23.1.1
lcsSetupWanPollingTableEntryPeer OBJECT-TYPE
    SYNTAX     DisplayString (SIZE(0..16))
    MAX-ACCESS read-write
    STATUS     current
    DESCRIPTION
        "-- empty --"
    ::= { lcsSetupWanPollingTableEntry 1 }

-- {COLUMN} 1712.2.2.23.1.2
lcsSetupWanPollingTableEntryIpAddress1 OBJECT-TYPE
    SYNTAX     IpAddress
    MAX-ACCESS read-write
    STATUS     current
    DESCRIPTION
        "-- empty --"
    ::= { lcsSetupWanPollingTableEntry 2 }

-- {COLUMN} 1712.2.2.23.1.5
lcsSetupWanPollingTableEntryIpAddress2 OBJECT-TYPE
    SYNTAX     IpAddress
    MAX-ACCESS read-write
    STATUS     current
    DESCRIPTION
        "-- empty --"
    ::= { lcsSetupWanPollingTableEntry 5 }

-- {COLUMN} 1712.2.2.23.1.6
lcsSetupWanPollingTableEntryIpAddress3 OBJECT-TYPE
    SYNTAX     IpAddress
    MAX-ACCESS read-write
    STATUS     current
    DESCRIPTION
        "-- empty --"
    ::= { lcsSetupWanPollingTableEntry 6 }

-- {COLUMN} 1712.2.2.23.1.7
lcsSetupWanPollingTableEntryIpAddress4 OBJECT-TYPE
    SYNTAX     IpAddress
    MAX-ACCESS read-write
    STATUS     current
    DESCRIPTION
        "-- empty --"
    ::= { lcsSetupWanPollingTableEntry 7 }

-- {COLUMN} 1712.2.2.23.1.3
lcsSetupWanPollingTableEntryTime OBJECT-TYPE
    SYNTAX     INTEGER (0..65535)
    MAX-ACCESS read-write
    STATUS     current
    DESCRIPTION
        "-- empty --"
    ::= { lcsSetupWanPollingTableEntry 3 }

-- {COLUMN} 1712.2.2.23.1.4
lcsSetupWanPollingTableEntryTry OBJECT-TYPE
    SYNTAX     INTEGER (0..255)
    MAX-ACCESS read-write
    STATUS     current
    DESCRIPTION
        "-- empty --"
    ::= { lcsSetupWanPollingTableEntry 4 }

-- {COLUMN} 1712.2.2.23.1.8
lcsSetupWanPollingTableEntryLoopbackAddr OBJECT-TYPE
    SYNTAX     DisplayString (SIZE(0..16))
    MAX-ACCESS read-write
    STATUS     current
    DESCRIPTION
        "-- empty --"
    ::= { lcsSetupWanPollingTableEntry 8 }

-- {COLUMN} 1712.2.2.23.1.9
lcsSetupWanPollingTableEntryType OBJECT-TYPE
    SYNTAX     INTEGER
      {
        eAuto (1),
        eForced (0)
      }
    MAX-ACCESS read-write
    STATUS     current
    DESCRIPTION
        "-- empty --"
    ::= { lcsSetupWanPollingTableEntry 9 }

-- {TABLE} 1712.2.2.24
lcsSetupWanBackupPeersTable OBJECT-TYPE
    SYNTAX     SEQUENCE OF LcsSetupWanBackupPeersEntry
    MAX-ACCESS not-accessible
    STATUS     current
    DESCRIPTION
        "-- empty --"
    ::= { lcsSetupWan 24 }

-- {ENTRY} 1712.2.2.24.1
lcsSetupWanBackupPeersEntry OBJECT-TYPE
    SYNTAX     LcsSetupWanBackupPeersEntry
    MAX-ACCESS not-accessible
    STATUS     current
    DESCRIPTION
        ""
    INDEX {
        lcsSetupWanBackupPeersEntryPeer
    }
    ::= { lcsSetupWanBackupPeersTable 1 }

-- {SEQUENCE}
LcsSetupWanBackupPeersEntry ::= SEQUENCE {
    lcsSetupWanBackupPeersEntryPeer DisplayString,
    lcsSetupWanBackupPeersEntryAlternativePeers DisplayString,
    lcsSetupWanBackupPeersEntryHead INTEGER
}

-- {COLUMN} 1712.2.2.24.1.1
lcsSetupWanBackupPeersEntryPeer OBJECT-TYPE
    SYNTAX     DisplayString (SIZE(0..18))
    MAX-ACCESS read-write
    STATUS     current
    DESCRIPTION
        "-- empty --"
    ::= { lcsSetupWanBackupPeersEntry 1 }

-- {COLUMN} 1712.2.2.24.1.2
lcsSetupWanBackupPeersEntryAlternativePeers OBJECT-TYPE
    SYNTAX     DisplayString (SIZE(0..53))
    MAX-ACCESS read-write
    STATUS     current
    DESCRIPTION
        "-- empty --"
    ::= { lcsSetupWanBackupPeersEntry 2 }

-- {COLUMN} 1712.2.2.24.1.3
lcsSetupWanBackupPeersEntryHead OBJECT-TYPE
    SYNTAX     INTEGER
      {
        eLast (0),
        eFirst (1)
      }
    MAX-ACCESS read-write
    STATUS     current
    DESCRIPTION
        "-- empty --"
    ::= { lcsSetupWanBackupPeersEntry 3 }

-- {TABLE} 1712.2.2.25
lcsSetupWanActionTableTable OBJECT-TYPE
    SYNTAX     SEQUENCE OF LcsSetupWanActionTableEntry
    MAX-ACCESS not-accessible
    STATUS     current
    DESCRIPTION
        "-- empty --"
    ::= { lcsSetupWan 25 }

-- {ENTRY} 1712.2.2.25.1
lcsSetupWanActionTableEntry OBJECT-TYPE
    SYNTAX     LcsSetupWanActionTableEntry
    MAX-ACCESS not-accessible
    STATUS     current
    DESCRIPTION
        ""
    INDEX {
        lcsSetupWanActionTableEntryIndex
    }
    ::= { lcsSetupWanActionTableTable 1 }

-- {SEQUENCE}
LcsSetupWanActionTableEntry ::= SEQUENCE {
    lcsSetupWanActionTableEntryIndex INTEGER,
    lcsSetupWanActionTableEntryActive INTEGER,
    lcsSetupWanActionTableEntryHostName DisplayString,
    lcsSetupWanActionTableEntryPeer DisplayString,
    lcsSetupWanActionTableEntryLockTime INTEGER,
    lcsSetupWanActionTableEntryCondition INTEGER,
    lcsSetupWanActionTableEntryAction DisplayString,
    lcsSetupWanActionTableEntryCheckFor DisplayString,
    lcsSetupWanActionTableEntryOwner DisplayString,
    lcsSetupWanActionTableEntryRoutingTag INTEGER
}

-- {COLUMN} 1712.2.2.25.1.1
lcsSetupWanActionTableEntryIndex OBJECT-TYPE
    SYNTAX     INTEGER (0..65535)
    MAX-ACCESS read-write
    STATUS     current
    DESCRIPTION
        "-- empty --"
    ::= { lcsSetupWanActionTableEntry 1 }

-- {COLUMN} 1712.2.2.25.1.8
lcsSetupWanActionTableEntryActive OBJECT-TYPE
    SYNTAX     INTEGER
      {
        eYes (0),
        eNo (1)
      }
    MAX-ACCESS read-write
    STATUS     current
    DESCRIPTION
        "-- empty --"
    ::= { lcsSetupWanActionTableEntry 8 }

-- {COLUMN} 1712.2.2.25.1.2
lcsSetupWanActionTableEntryHostName OBJECT-TYPE
    SYNTAX     DisplayString (SIZE(0..64))
    MAX-ACCESS read-write
    STATUS     current
    DESCRIPTION
        "-- empty --"
    ::= { lcsSetupWanActionTableEntry 2 }

-- {COLUMN} 1712.2.2.25.1.3
lcsSetupWanActionTableEntryPeer OBJECT-TYPE
    SYNTAX     DisplayString (SIZE(0..16))
    MAX-ACCESS read-write
    STATUS     current
    DESCRIPTION
        "-- empty --"
    ::= { lcsSetupWanActionTableEntry 3 }

-- {COLUMN} 1712.2.2.25.1.4
lcsSetupWanActionTableEntryLockTime OBJECT-TYPE
    SYNTAX     INTEGER (0..2147483647)
    MAX-ACCESS read-write
    STATUS     current
    DESCRIPTION
        "-- empty --"
    ::= { lcsSetupWanActionTableEntry 4 }

-- {COLUMN} 1712.2.2.25.1.5
lcsSetupWanActionTableEntryCondition OBJECT-TYPE
    SYNTAX     INTEGER
      {
        eEstablish (0),
        eDisconnect (1),
        eEnd (2),
        eFailure (3),
        eEstablishFailure (4),
        eBudgetExhausted (5),
        eBudgetReleased (6)
      }
    MAX-ACCESS read-write
    STATUS     current
    DESCRIPTION
        "-- empty --"
    ::= { lcsSetupWanActionTableEntry 5 }

-- {COLUMN} 1712.2.2.25.1.6
lcsSetupWanActionTableEntryAction OBJECT-TYPE
    SYNTAX     DisplayString (SIZE(0..250))
    MAX-ACCESS read-write
    STATUS     current
    DESCRIPTION
        "-- empty --"
    ::= { lcsSetupWanActionTableEntry 6 }

-- {COLUMN} 1712.2.2.25.1.7
lcsSetupWanActionTableEntryCheckFor OBJECT-TYPE
    SYNTAX     DisplayString (SIZE(0..50))
    MAX-ACCESS read-write
    STATUS     current
    DESCRIPTION
        "-- empty --"
    ::= { lcsSetupWanActionTableEntry 7 }

-- {COLUMN} 1712.2.2.25.1.9
lcsSetupWanActionTableEntryOwner OBJECT-TYPE
    SYNTAX     DisplayString (SIZE(0..16))
    MAX-ACCESS read-write
    STATUS     current
    DESCRIPTION
        "-- empty --"
    ::= { lcsSetupWanActionTableEntry 9 }

-- {COLUMN} 1712.2.2.25.1.10
lcsSetupWanActionTableEntryRoutingTag OBJECT-TYPE
    SYNTAX     INTEGER (0..65535)
    MAX-ACCESS read-write
    STATUS     current
    DESCRIPTION
        "-- empty --"
    ::= { lcsSetupWanActionTableEntry 10 }

-- {SCALAR} 1712.2.2.18
lcsSetupWanBackupDelaySeconds OBJECT-TYPE
    SYNTAX     INTEGER (0..65535)
    MAX-ACCESS read-write
    STATUS     current
    DESCRIPTION
        "-- empty --"
    ::= { lcsSetupWan 18 }

-- {TABLE} 1712.2.2.6
lcsSetupWanIncomingCallingNumbersTable OBJECT-TYPE
    SYNTAX     SEQUENCE OF LcsSetupWanIncomingCallingNumbersEntry
    MAX-ACCESS not-accessible
    STATUS     current
    DESCRIPTION
        "-- empty --"
    ::= { lcsSetupWan 6 }

-- {ENTRY} 1712.2.2.6.1
lcsSetupWanIncomingCallingNumbersEntry OBJECT-TYPE
    SYNTAX     LcsSetupWanIncomingCallingNumbersEntry
    MAX-ACCESS not-accessible
    STATUS     current
    DESCRIPTION
        ""
    INDEX {
        lcsSetupWanIncomingCallingNumbersEntryDialupRemote
    }
    ::= { lcsSetupWanIncomingCallingNumbersTable 1 }

-- {SEQUENCE}
LcsSetupWanIncomingCallingNumbersEntry ::= SEQUENCE {
    lcsSetupWanIncomingCallingNumbersEntryDialupRemote DisplayString,
    lcsSetupWanIncomingCallingNumbersEntryPeer DisplayString
}

-- {COLUMN} 1712.2.2.6.1.1
lcsSetupWanIncomingCallingNumbersEntryDialupRemote OBJECT-TYPE
    SYNTAX     DisplayString (SIZE(0..31))
    MAX-ACCESS read-write
    STATUS     current
    DESCRIPTION
        "-- empty --"
    ::= { lcsSetupWanIncomingCallingNumbersEntry 1 }

-- {COLUMN} 1712.2.2.6.1.2
lcsSetupWanIncomingCallingNumbersEntryPeer OBJECT-TYPE
    SYNTAX     DisplayString (SIZE(0..16))
    MAX-ACCESS read-write
    STATUS     current
    DESCRIPTION
        "-- empty --"
    ::= { lcsSetupWanIncomingCallingNumbersEntry 2 }

-- {TABLE} 1712.2.2.8
lcsSetupWanScriptsTable OBJECT-TYPE
    SYNTAX     SEQUENCE OF LcsSetupWanScriptsEntry
    MAX-ACCESS not-accessible
    STATUS     current
    DESCRIPTION
        "-- empty --"
    ::= { lcsSetupWan 8 }

-- {ENTRY} 1712.2.2.8.1
lcsSetupWanScriptsEntry OBJECT-TYPE
    SYNTAX     LcsSetupWanScriptsEntry
    MAX-ACCESS not-accessible
    STATUS     current
    DESCRIPTION
        ""
    INDEX {
        lcsSetupWanScriptsEntryPeer
    }
    ::= { lcsSetupWanScriptsTable 1 }

-- {SEQUENCE}
LcsSetupWanScriptsEntry ::= SEQUENCE {
    lcsSetupWanScriptsEntryPeer DisplayString,
    lcsSetupWanScriptsEntryScript DisplayString
}

-- {COLUMN} 1712.2.2.8.1.1
lcsSetupWanScriptsEntryPeer OBJECT-TYPE
    SYNTAX     DisplayString (SIZE(0..18))
    MAX-ACCESS read-write
    STATUS     current
    DESCRIPTION
        "-- empty --"
    ::= { lcsSetupWanScriptsEntry 1 }

-- {COLUMN} 1712.2.2.8.1.2
lcsSetupWanScriptsEntryScript OBJECT-TYPE
    SYNTAX     DisplayString (SIZE(0..58))
    MAX-ACCESS read-write
    STATUS     current
    DESCRIPTION
        "-- empty --"
    ::= { lcsSetupWanScriptsEntry 2 }

-- {SCALAR} 1712.2.2.9
lcsSetupWanProtect OBJECT-TYPE
    SYNTAX     INTEGER
      {
        eNone (0),
        eNumber (2),
        eScreened (4)
      }
    MAX-ACCESS read-write
    STATUS     current
    DESCRIPTION
        "-- empty --"
    ::= { lcsSetupWan 9 }

-- {SCALAR} 1712.2.2.10
lcsSetupWanCallbackAttempts OBJECT-TYPE
    SYNTAX     INTEGER (0..255)
    MAX-ACCESS read-write
    STATUS     current
    DESCRIPTION
        "-- empty --"
    ::= { lcsSetupWan 10 }

-- {OID} 1712.2.2.13
lcsSetupWanManualDialing OBJECT IDENTIFIER ::= { lcsSetupWan 13 }

-- {SCALAR} 1712.2.2.13.1
lcsSetupWanManualDialingConnect OBJECT-TYPE
    SYNTAX     DisplayString
    MAX-ACCESS read-write
    STATUS     current
    DESCRIPTION
        "-- empty --"
    ::= { lcsSetupWanManualDialing 1 }

-- {SCALAR} 1712.2.2.13.2
lcsSetupWanManualDialingDisconnect OBJECT-TYPE
    SYNTAX     DisplayString
    MAX-ACCESS read-write
    STATUS     current
    DESCRIPTION
        "-- empty --"
    ::= { lcsSetupWanManualDialing 2 }

-- {TABLE} 1712.2.2.11
lcsSetupWanRouterInterfaceTable OBJECT-TYPE
    SYNTAX     SEQUENCE OF LcsSetupWanRouterInterfaceEntry
    MAX-ACCESS not-accessible
    STATUS     current
    DESCRIPTION
        "-- empty --"
    ::= { lcsSetupWan 11 }

-- {ENTRY} 1712.2.2.11.1
lcsSetupWanRouterInterfaceEntry OBJECT-TYPE
    SYNTAX     LcsSetupWanRouterInterfaceEntry
    MAX-ACCESS not-accessible
    STATUS     current
    DESCRIPTION
        ""
    INDEX {
        lcsSetupWanRouterInterfaceEntryIfc
    }
    ::= { lcsSetupWanRouterInterfaceTable 1 }

-- {SEQUENCE}
LcsSetupWanRouterInterfaceEntry ::= SEQUENCE {
    lcsSetupWanRouterInterfaceEntryIfc INTEGER,
    lcsSetupWanRouterInterfaceEntryMsnEaz DisplayString,
    lcsSetupWanRouterInterfaceEntryYc INTEGER,
    lcsSetupWanRouterInterfaceEntryClip INTEGER,
    lcsSetupWanRouterInterfaceEntryAcceptCalls INTEGER,
    lcsSetupWanRouterInterfaceEntryTypeOfInterface INTEGER
}

-- {COLUMN} 1712.2.2.11.1.1
lcsSetupWanRouterInterfaceEntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsSetupWanRouterInterfaceEntry 1 }

-- {COLUMN} 1712.2.2.11.1.2
lcsSetupWanRouterInterfaceEntryMsnEaz OBJECT-TYPE
    SYNTAX     DisplayString (SIZE(0..30))
    MAX-ACCESS read-write
    STATUS     current
    DESCRIPTION
        "-- empty --"
    ::= { lcsSetupWanRouterInterfaceEntry 2 }

-- {COLUMN} 1712.2.2.11.1.8
lcsSetupWanRouterInterfaceEntryYc OBJECT-TYPE
    SYNTAX     INTEGER
      {
        eYes (0),
        eNo (1)
      }
    MAX-ACCESS read-write
    STATUS     current
    DESCRIPTION
        "-- empty --"
    ::= { lcsSetupWanRouterInterfaceEntry 8 }

-- {COLUMN} 1712.2.2.11.1.3
lcsSetupWanRouterInterfaceEntryClip OBJECT-TYPE
    SYNTAX     INTEGER
      {
        eYes (0),
        eNo (1)
      }
    MAX-ACCESS read-write
    STATUS     current
    DESCRIPTION
        "-- empty --"
    ::= { lcsSetupWanRouterInterfaceEntry 3 }

-- {COLUMN} 1712.2.2.11.1.9
lcsSetupWanRouterInterfaceEntryAcceptCalls OBJECT-TYPE
    SYNTAX     INTEGER
      {
        eAll (0),
        eNone (128)
      }
    MAX-ACCESS read-write
    STATUS     current
    DESCRIPTION
        "-- empty --"
    ::= { lcsSetupWanRouterInterfaceEntry 9 }

-- {COLUMN} 1712.2.2.11.1.10
lcsSetupWanRouterInterfaceEntryTypeOfInterface OBJECT-TYPE
    SYNTAX     INTEGER (0..2147483647)
    MAX-ACCESS read-only
    STATUS     current
    DESCRIPTION
        "-- empty --"
    ::= { lcsSetupWanRouterInterfaceEntry 10 }

-- {SCALAR} 1712.2.2.7
lcsSetupWanDialPrefix OBJECT-TYPE
    SYNTAX     DisplayString (SIZE(0..8))
    MAX-ACCESS read-only
    STATUS     current
    DESCRIPTION
        "-- empty --"
    ::= { lcsSetupWan 7 }

-- {OID} 1712.2.2.45
lcsSetupWanX25Bridge OBJECT IDENTIFIER ::= { lcsSetupWan 45 }

-- {TABLE} 1712.2.2.45.2
lcsSetupWanX25BridgeOutgoingCallsTable OBJECT-TYPE
    SYNTAX     SEQUENCE OF LcsSetupWanX25BridgeOutgoingCallsEntry
    MAX-ACCESS not-accessible
    STATUS     current
    DESCRIPTION
        "-- empty --"
    ::= { lcsSetupWanX25Bridge 2 }

-- {ENTRY} 1712.2.2.45.2.1
lcsSetupWanX25BridgeOutgoingCallsEntry OBJECT-TYPE
    SYNTAX     LcsSetupWanX25BridgeOutgoingCallsEntry
    MAX-ACCESS not-accessible
    STATUS     current
    DESCRIPTION
        ""
    INDEX {
        lcsSetupWanX25BridgeOutgoingCallsEntryName
    }
    ::= { lcsSetupWanX25BridgeOutgoingCallsTable 1 }

-- {SEQUENCE}
LcsSetupWanX25BridgeOutgoingCallsEntry ::= SEQUENCE {
    lcsSetupWanX25BridgeOutgoingCallsEntryName DisplayString,
    lcsSetupWanX25BridgeOutgoingCallsEntryPrio INTEGER,
    lcsSetupWanX25BridgeOutgoingCallsEntryTerminalIp IpAddress,
    lcsSetupWanX25BridgeOutgoingCallsEntryTerminalPort INTEGER,
    lcsSetupWanX25BridgeOutgoingCallsEntryLoopbackAddress DisplayString,
    lcsSetupWanX25BridgeOutgoingCallsEntryLocalPort INTEGER,
    lcsSetupWanX25BridgeOutgoingCallsEntryIsdnRemote DisplayString,
    lcsSetupWanX25BridgeOutgoingCallsEntryIsdnLocal DisplayString,
    lcsSetupWanX25BridgeOutgoingCallsEntryX25Remote DisplayString,
    lcsSetupWanX25BridgeOutgoingCallsEntryX25Local DisplayString,
    lcsSetupWanX25BridgeOutgoingCallsEntryProtocolId INTEGER,
    lcsSetupWanX25BridgeOutgoingCallsEntryUserdata DisplayString,
    lcsSetupWanX25BridgeOutgoingCallsEntryPayloadSize INTEGER
}

-- {COLUMN} 1712.2.2.45.2.1.1
lcsSetupWanX25BridgeOutgoingCallsEntryName OBJECT-TYPE
    SYNTAX     DisplayString (SIZE(0..16))
    MAX-ACCESS read-write
    STATUS     current
    DESCRIPTION
        "-- empty --"
    ::= { lcsSetupWanX25BridgeOutgoingCallsEntry 1 }

-- {COLUMN} 1712.2.2.45.2.1.2
lcsSetupWanX25BridgeOutgoingCallsEntryPrio OBJECT-TYPE
    SYNTAX     INTEGER (0..65535)
    MAX-ACCESS read-write
    STATUS     current
    DESCRIPTION
        "-- empty --"
    ::= { lcsSetupWanX25BridgeOutgoingCallsEntry 2 }

-- {COLUMN} 1712.2.2.45.2.1.3
lcsSetupWanX25BridgeOutgoingCallsEntryTerminalIp OBJECT-TYPE
    SYNTAX     IpAddress
    MAX-ACCESS read-write
    STATUS     current
    DESCRIPTION
        "-- empty --"
    ::= { lcsSetupWanX25BridgeOutgoingCallsEntry 3 }

-- {COLUMN} 1712.2.2.45.2.1.4
lcsSetupWanX25BridgeOutgoingCallsEntryTerminalPort OBJECT-TYPE
    SYNTAX     INTEGER (0..65535)
    MAX-ACCESS read-write
    STATUS     current
    DESCRIPTION
        "-- empty --"
    ::= { lcsSetupWanX25BridgeOutgoingCallsEntry 4 }

-- {COLUMN} 1712.2.2.45.2.1.5
lcsSetupWanX25BridgeOutgoingCallsEntryLoopbackAddress OBJECT-TYPE
    SYNTAX     DisplayString (SIZE(0..39))
    MAX-ACCESS read-write
    STATUS     current
    DESCRIPTION
        "-- empty --"
    ::= { lcsSetupWanX25BridgeOutgoingCallsEntry 5 }

-- {COLUMN} 1712.2.2.45.2.1.6
lcsSetupWanX25BridgeOutgoingCallsEntryLocalPort OBJECT-TYPE
    SYNTAX     INTEGER (0..65535)
    MAX-ACCESS read-write
    STATUS     current
    DESCRIPTION
        "-- empty --"
    ::= { lcsSetupWanX25BridgeOutgoingCallsEntry 6 }

-- {COLUMN} 1712.2.2.45.2.1.7
lcsSetupWanX25BridgeOutgoingCallsEntryIsdnRemote OBJECT-TYPE
    SYNTAX     DisplayString (SIZE(0..21))
    MAX-ACCESS read-write
    STATUS     current
    DESCRIPTION
        "-- empty --"
    ::= { lcsSetupWanX25BridgeOutgoingCallsEntry 7 }

-- {COLUMN} 1712.2.2.45.2.1.8
lcsSetupWanX25BridgeOutgoingCallsEntryIsdnLocal OBJECT-TYPE
    SYNTAX     DisplayString (SIZE(0..21))
    MAX-ACCESS read-write
    STATUS     current
    DESCRIPTION
        "-- empty --"
    ::= { lcsSetupWanX25BridgeOutgoingCallsEntry 8 }

-- {COLUMN} 1712.2.2.45.2.1.9
lcsSetupWanX25BridgeOutgoingCallsEntryX25Remote OBJECT-TYPE
    SYNTAX     DisplayString (SIZE(0..14))
    MAX-ACCESS read-write
    STATUS     current
    DESCRIPTION
        "-- empty --"
    ::= { lcsSetupWanX25BridgeOutgoingCallsEntry 9 }

-- {COLUMN} 1712.2.2.45.2.1.10
lcsSetupWanX25BridgeOutgoingCallsEntryX25Local OBJECT-TYPE
    SYNTAX     DisplayString (SIZE(0..14))
    MAX-ACCESS read-write
    STATUS     current
    DESCRIPTION
        "-- empty --"
    ::= { lcsSetupWanX25BridgeOutgoingCallsEntry 10 }

-- {COLUMN} 1712.2.2.45.2.1.11
lcsSetupWanX25BridgeOutgoingCallsEntryProtocolId OBJECT-TYPE
    SYNTAX     INTEGER (0..2147483647)
    MAX-ACCESS read-write
    STATUS     current
    DESCRIPTION
        "-- empty --"
    ::= { lcsSetupWanX25BridgeOutgoingCallsEntry 11 }

-- {COLUMN} 1712.2.2.45.2.1.12
lcsSetupWanX25BridgeOutgoingCallsEntryUserdata OBJECT-TYPE
    SYNTAX     DisplayString (SIZE(0..8))
    MAX-ACCESS read-write
    STATUS     current
    DESCRIPTION
        "-- empty --"
    ::= { lcsSetupWanX25BridgeOutgoingCallsEntry 12 }

-- {COLUMN} 1712.2.2.45.2.1.13
lcsSetupWanX25BridgeOutgoingCallsEntryPayloadSize OBJECT-TYPE
    SYNTAX     INTEGER (0..2147483647)
    MAX-ACCESS read-write
    STATUS     current
    DESCRIPTION
        "-- empty --"
    ::= { lcsSetupWanX25BridgeOutgoingCallsEntry 13 }

-- {SCALAR} 1712.2.2.45.4
lcsSetupWanX25BridgeDisconnectDelay OBJECT-TYPE
    SYNTAX     INTEGER (0..2147483647)
    MAX-ACCESS read-write
    STATUS     current
    DESCRIPTION
        "-- empty --"
    ::= { lcsSetupWanX25Bridge 4 }

-- {SCALAR} 1712.2.2.45.5
lcsSetupWanX25BridgeDataTrace OBJECT-TYPE
    SYNTAX     INTEGER
      {
        eOff (0),
        eOn (1),
        eExtended (2)
      }
    MAX-ACCESS read-write
    STATUS     current
    DESCRIPTION
        "-- empty --"
    ::= { lcsSetupWanX25Bridge 5 }

-- {OID} 1712.2.18
lcsSetupAccounting OBJECT IDENTIFIER ::= { lcsSetup 18 }

-- {SCALAR} 1712.2.18.1
lcsSetupAccountingOperating OBJECT-TYPE
    SYNTAX     INTEGER
      {
        eNo (0),
        eYes (1)
      }
    MAX-ACCESS read-write
    STATUS     current
    DESCRIPTION
        "-- empty --"
    ::= { lcsSetupAccounting 1 }

-- {SCALAR} 1712.2.18.2
lcsSetupAccountingSaveToFlashrom OBJECT-TYPE
    SYNTAX     INTEGER
      {
        eNo (0),
        eYes (1)
      }
    MAX-ACCESS read-write
    STATUS     current
    DESCRIPTION
        "-- empty --"
    ::= { lcsSetupAccounting 2 }

-- {SCALAR} 1712.2.18.10
lcsSetupAccountingDiscriminator OBJECT-TYPE
    SYNTAX     INTEGER
      {
        eMacAddress (0),
        eIpAddress (1)
      }
    MAX-ACCESS read-write
    STATUS     current
    DESCRIPTION
        "-- empty --"
    ::= { lcsSetupAccounting 10 }

-- {SCALAR} 1712.2.18.3
lcsSetupAccountingSortBy OBJECT-TYPE
    SYNTAX     INTEGER
      {
        eTime (0),
        eData (1)
      }
    MAX-ACCESS read-write
    STATUS     current
    DESCRIPTION
        "-- empty --"
    ::= { lcsSetupAccounting 3 }

-- {TABLE} 1712.2.18.4
lcsSetupAccountingCurrentUserTable OBJECT-TYPE
    SYNTAX     SEQUENCE OF LcsSetupAccountingCurrentUserEntry
    MAX-ACCESS not-accessible
    STATUS     current
    DESCRIPTION
        "-- empty --"
    ::= { lcsSetupAccounting 4 }

-- {ENTRY} 1712.2.18.4.1
lcsSetupAccountingCurrentUserEntry OBJECT-TYPE
    SYNTAX     LcsSetupAccountingCurrentUserEntry
    MAX-ACCESS not-accessible
    STATUS     current
    DESCRIPTION
        ""
    INDEX {
        lcsSetupAccountingCurrentUserEntryUsername,
        lcsSetupAccountingCurrentUserEntryMacAddress,
        lcsSetupAccountingCurrentUserEntryPeer,
        lcsSetupAccountingCurrentUserEntryConnType
    }
    ::= { lcsSetupAccountingCurrentUserTable 1 }

-- {SEQUENCE}
LcsSetupAccountingCurrentUserEntry ::= SEQUENCE {
    lcsSetupAccountingCurrentUserEntryUsername DisplayString,
    lcsSetupAccountingCurrentUserEntryMacAddress DisplayString,
    lcsSetupAccountingCurrentUserEntryPeer DisplayString,
    lcsSetupAccountingCurrentUserEntryConnType INTEGER,
    lcsSetupAccountingCurrentUserEntryRxKbytes INTEGER,
    lcsSetupAccountingCurrentUserEntryTxKbytes INTEGER,
    lcsSetupAccountingCurrentUserEntryTotalTime Gauge32,
    lcsSetupAccountingCurrentUserEntryConnections INTEGER
}

-- {COLUMN} 1712.2.18.4.1.1
lcsSetupAccountingCurrentUserEntryUsername OBJECT-TYPE
    SYNTAX     DisplayString (SIZE(0..28))
    MAX-ACCESS read-only
    STATUS     current
    DESCRIPTION
        "-- empty --"
    ::= { lcsSetupAccountingCurrentUserEntry 1 }

-- {COLUMN} 1712.2.18.4.1.2
lcsSetupAccountingCurrentUserEntryMacAddress OBJECT-TYPE
    SYNTAX     DisplayString (SIZE(0..255))
    MAX-ACCESS read-only
    STATUS     current
    DESCRIPTION
        "-- empty --"
    ::= { lcsSetupAccountingCurrentUserEntry 2 }

-- {COLUMN} 1712.2.18.4.1.3
lcsSetupAccountingCurrentUserEntryPeer OBJECT-TYPE
    SYNTAX     DisplayString (SIZE(0..16))
    MAX-ACCESS read-only
    STATUS     current
    DESCRIPTION
        "-- empty --"
    ::= { lcsSetupAccountingCurrentUserEntry 3 }

-- {COLUMN} 1712.2.18.4.1.4
lcsSetupAccountingCurrentUserEntryConnType OBJECT-TYPE
    SYNTAX     INTEGER
      {
        eUnknown (0),
        eDialUp (1),
        eLeasedLine (2),
        eDslLine (4),
        eVpnConn (7),
        ePptpConn (8),
        eL2tpConn (9),
        eDsLiteConn (10)
      }
    MAX-ACCESS read-only
    STATUS     current
    DESCRIPTION
        "-- empty --"
    ::= { lcsSetupAccountingCurrentUserEntry 4 }

-- {COLUMN} 1712.2.18.4.1.5
lcsSetupAccountingCurrentUserEntryRxKbytes OBJECT-TYPE
    SYNTAX     INTEGER (0..2147483647)
    MAX-ACCESS read-only
    STATUS     current
    DESCRIPTION
        "-- empty --"
    ::= { lcsSetupAccountingCurrentUserEntry 5 }

-- {COLUMN} 1712.2.18.4.1.6
lcsSetupAccountingCurrentUserEntryTxKbytes OBJECT-TYPE
    SYNTAX     INTEGER (0..2147483647)
    MAX-ACCESS read-only
    STATUS     current
    DESCRIPTION
        "-- empty --"
    ::= { lcsSetupAccountingCurrentUserEntry 6 }

-- {COLUMN} 1712.2.18.4.1.8
lcsSetupAccountingCurrentUserEntryTotalTime OBJECT-TYPE
    SYNTAX     Gauge32
    MAX-ACCESS read-only
    STATUS     current
    DESCRIPTION
        "-- empty --"
    ::= { lcsSetupAccountingCurrentUserEntry 8 }

-- {COLUMN} 1712.2.18.4.1.9
lcsSetupAccountingCurrentUserEntryConnections OBJECT-TYPE
    SYNTAX     INTEGER (0..2147483647)
    MAX-ACCESS read-only
    STATUS     current
    DESCRIPTION
        "-- empty --"
    ::= { lcsSetupAccountingCurrentUserEntry 9 }

-- {TABLE} 1712.2.18.5
lcsSetupAccountingAccountingListTable OBJECT-TYPE
    SYNTAX     SEQUENCE OF LcsSetupAccountingAccountingListEntry
    MAX-ACCESS not-accessible
    STATUS     current
    DESCRIPTION
        "-- empty --"
    ::= { lcsSetupAccounting 5 }

-- {ENTRY} 1712.2.18.5.1
lcsSetupAccountingAccountingListEntry OBJECT-TYPE
    SYNTAX     LcsSetupAccountingAccountingListEntry
    MAX-ACCESS not-accessible
    STATUS     current
    DESCRIPTION
        ""
    INDEX {
        lcsSetupAccountingAccountingListEntryUsername,
        lcsSetupAccountingAccountingListEntryMacAddress,
        lcsSetupAccountingAccountingListEntryPeer,
        lcsSetupAccountingAccountingListEntryConnType
    }
    ::= { lcsSetupAccountingAccountingListTable 1 }

-- {SEQUENCE}
LcsSetupAccountingAccountingListEntry ::= SEQUENCE {
    lcsSetupAccountingAccountingListEntryUsername DisplayString,
    lcsSetupAccountingAccountingListEntryMacAddress DisplayString,
    lcsSetupAccountingAccountingListEntryPeer DisplayString,
    lcsSetupAccountingAccountingListEntryConnType INTEGER,
    lcsSetupAccountingAccountingListEntryRxKbytes INTEGER,
    lcsSetupAccountingAccountingListEntryTxKbytes INTEGER,
    lcsSetupAccountingAccountingListEntryTotalTime Gauge32,
    lcsSetupAccountingAccountingListEntryConnections INTEGER
}

-- {COLUMN} 1712.2.18.5.1.1
lcsSetupAccountingAccountingListEntryUsername OBJECT-TYPE
    SYNTAX     DisplayString (SIZE(0..28))
    MAX-ACCESS read-only
    STATUS     current
    DESCRIPTION
        "-- empty --"
    ::= { lcsSetupAccountingAccountingListEntry 1 }

-- {COLUMN} 1712.2.18.5.1.2
lcsSetupAccountingAccountingListEntryMacAddress OBJECT-TYPE
    SYNTAX     DisplayString (SIZE(0..255))
    MAX-ACCESS read-only
    STATUS     current
    DESCRIPTION
        "-- empty --"
    ::= { lcsSetupAccountingAccountingListEntry 2 }

-- {COLUMN} 1712.2.18.5.1.3
lcsSetupAccountingAccountingListEntryPeer OBJECT-TYPE
    SYNTAX     DisplayString (SIZE(0..16))
    MAX-ACCESS read-only
    STATUS     current
    DESCRIPTION
        "-- empty --"
    ::= { lcsSetupAccountingAccountingListEntry 3 }

-- {COLUMN} 1712.2.18.5.1.4
lcsSetupAccountingAccountingListEntryConnType OBJECT-TYPE
    SYNTAX     INTEGER
      {
        eUnknown (0),
        eDialUp (1),
        eLeasedLine (2),
        eDslLine (4),
        eVpnConn (7),
        ePptpConn (8),
        eL2tpConn (9),
        eDsLiteConn (10)
      }
    MAX-ACCESS read-only
    STATUS     current
    DESCRIPTION
        "-- empty --"
    ::= { lcsSetupAccountingAccountingListEntry 4 }

-- {COLUMN} 1712.2.18.5.1.5
lcsSetupAccountingAccountingListEntryRxKbytes OBJECT-TYPE
    SYNTAX     INTEGER (0..2147483647)
    MAX-ACCESS read-only
    STATUS     current
    DESCRIPTION
        "-- empty --"
    ::= { lcsSetupAccountingAccountingListEntry 5 }

-- {COLUMN} 1712.2.18.5.1.6
lcsSetupAccountingAccountingListEntryTxKbytes OBJECT-TYPE
    SYNTAX     INTEGER (0..2147483647)
    MAX-ACCESS read-only
    STATUS     current
    DESCRIPTION
        "-- empty --"
    ::= { lcsSetupAccountingAccountingListEntry 6 }

-- {COLUMN} 1712.2.18.5.1.8
lcsSetupAccountingAccountingListEntryTotalTime OBJECT-TYPE
    SYNTAX     Gauge32
    MAX-ACCESS read-only
    STATUS     current
    DESCRIPTION
        "-- empty --"
    ::= { lcsSetupAccountingAccountingListEntry 8 }

-- {COLUMN} 1712.2.18.5.1.9
lcsSetupAccountingAccountingListEntryConnections OBJECT-TYPE
    SYNTAX     INTEGER (0..2147483647)
    MAX-ACCESS read-only
    STATUS     current
    DESCRIPTION
        "-- empty --"
    ::= { lcsSetupAccountingAccountingListEntry 9 }

-- {SCALAR} 1712.2.18.6
lcsSetupAccountingDeleteAccountingList OBJECT-TYPE
    SYNTAX     DisplayString
    MAX-ACCESS read-write
    STATUS     current
    DESCRIPTION
        "-- empty --"
    ::= { lcsSetupAccounting 6 }

-- {TABLE} 1712.2.18.8
lcsSetupAccountingTimeSnapshotTable OBJECT-TYPE
    SYNTAX     SEQUENCE OF LcsSetupAccountingTimeSnapshotEntry
    MAX-ACCESS not-accessible
    STATUS     current
    DESCRIPTION
        "-- empty --"
    ::= { lcsSetupAccounting 8 }

-- {ENTRY} 1712.2.18.8.1
lcsSetupAccountingTimeSnapshotEntry OBJECT-TYPE
    SYNTAX     LcsSetupAccountingTimeSnapshotEntry
    MAX-ACCESS not-accessible
    STATUS     current
    DESCRIPTION
        ""
    INDEX {
        lcsSetupAccountingTimeSnapshotEntryIndex
    }
    ::= { lcsSetupAccountingTimeSnapshotTable 1 }

-- {SEQUENCE}
LcsSetupAccountingTimeSnapshotEntry ::= SEQUENCE {
    lcsSetupAccountingTimeSnapshotEntryIndex INTEGER,
    lcsSetupAccountingTimeSnapshotEntryActive INTEGER,
    lcsSetupAccountingTimeSnapshotEntryType INTEGER,
    lcsSetupAccountingTimeSnapshotEntryDay INTEGER,
    lcsSetupAccountingTimeSnapshotEntryDayofweek INTEGER,
    lcsSetupAccountingTimeSnapshotEntryHour INTEGER,
    lcsSetupAccountingTimeSnapshotEntryMinute INTEGER
}

-- {COLUMN} 1712.2.18.8.1.1
lcsSetupAccountingTimeSnapshotEntryIndex OBJECT-TYPE
    SYNTAX     INTEGER (0..255)
    MAX-ACCESS read-only
    STATUS     current
    DESCRIPTION
        "-- empty --"
    ::= { lcsSetupAccountingTimeSnapshotEntry 1 }

-- {COLUMN} 1712.2.18.8.1.2
lcsSetupAccountingTimeSnapshotEntryActive OBJECT-TYPE
    SYNTAX     INTEGER
      {
        eYes (1),
        eNo (0)
      }
    MAX-ACCESS read-write
    STATUS     current
    DESCRIPTION
        "-- empty --"
    ::= { lcsSetupAccountingTimeSnapshotEntry 2 }

-- {COLUMN} 1712.2.18.8.1.3
lcsSetupAccountingTimeSnapshotEntryType OBJECT-TYPE
    SYNTAX     INTEGER
      {
        eMonthly (0),
        eWeekly (1),
        eDaily (2)
      }
    MAX-ACCESS read-write
    STATUS     current
    DESCRIPTION
        "-- empty --"
    ::= { lcsSetupAccountingTimeSnapshotEntry 3 }

-- {COLUMN} 1712.2.18.8.1.4
lcsSetupAccountingTimeSnapshotEntryDay OBJECT-TYPE
    SYNTAX     INTEGER (0..255)
    MAX-ACCESS read-write
    STATUS     current
    DESCRIPTION
        "-- empty --"
    ::= { lcsSetupAccountingTimeSnapshotEntry 4 }

-- {COLUMN} 1712.2.18.8.1.5
lcsSetupAccountingTimeSnapshotEntryDayofweek OBJECT-TYPE
    SYNTAX     INTEGER
      {
        eUnknown (0),
        eSunday (1),
        eMonday (2),
        eTuesday (3),
        eWednesday (4),
        eThursday (5),
        eFriday (6),
        eSaturday (7)
      }
    MAX-ACCESS read-write
    STATUS     current
    DESCRIPTION
        "-- empty --"
    ::= { lcsSetupAccountingTimeSnapshotEntry 5 }

-- {COLUMN} 1712.2.18.8.1.6
lcsSetupAccountingTimeSnapshotEntryHour OBJECT-TYPE
    SYNTAX     INTEGER (0..255)
    MAX-ACCESS read-write
    STATUS     current
    DESCRIPTION
        "-- empty --"
    ::= { lcsSetupAccountingTimeSnapshotEntry 6 }

-- {COLUMN} 1712.2.18.8.1.7
lcsSetupAccountingTimeSnapshotEntryMinute OBJECT-TYPE
    SYNTAX     INTEGER (0..255)
    MAX-ACCESS read-write
    STATUS     current
    DESCRIPTION
        "-- empty --"
    ::= { lcsSetupAccountingTimeSnapshotEntry 7 }

-- {TABLE} 1712.2.18.9
lcsSetupAccountingLastSnapshotTable OBJECT-TYPE
    SYNTAX     SEQUENCE OF LcsSetupAccountingLastSnapshotEntry
    MAX-ACCESS not-accessible
    STATUS     current
    DESCRIPTION
        "-- empty --"
    ::= { lcsSetupAccounting 9 }

-- {ENTRY} 1712.2.18.9.1
lcsSetupAccountingLastSnapshotEntry OBJECT-TYPE
    SYNTAX     LcsSetupAccountingLastSnapshotEntry
    MAX-ACCESS not-accessible
    STATUS     current
    DESCRIPTION
        ""
    INDEX {
        lcsSetupAccountingLastSnapshotEntryUsername,
        lcsSetupAccountingLastSnapshotEntryMacAddress,
        lcsSetupAccountingLastSnapshotEntryPeer,
        lcsSetupAccountingLastSnapshotEntryConnType
    }
    ::= { lcsSetupAccountingLastSnapshotTable 1 }

-- {SEQUENCE}
LcsSetupAccountingLastSnapshotEntry ::= SEQUENCE {
    lcsSetupAccountingLastSnapshotEntryUsername DisplayString,
    lcsSetupAccountingLastSnapshotEntryMacAddress DisplayString,
    lcsSetupAccountingLastSnapshotEntryPeer DisplayString,
    lcsSetupAccountingLastSnapshotEntryConnType INTEGER,
    lcsSetupAccountingLastSnapshotEntryRxKbytes INTEGER,
    lcsSetupAccountingLastSnapshotEntryTxKbytes INTEGER,
    lcsSetupAccountingLastSnapshotEntryTotalTime Gauge32,
    lcsSetupAccountingLastSnapshotEntryConnections INTEGER
}

-- {COLUMN} 1712.2.18.9.1.1
lcsSetupAccountingLastSnapshotEntryUsername OBJECT-TYPE
    SYNTAX     DisplayString (SIZE(0..28))
    MAX-ACCESS read-only
    STATUS     current
    DESCRIPTION
        "-- empty --"
    ::= { lcsSetupAccountingLastSnapshotEntry 1 }

-- {COLUMN} 1712.2.18.9.1.2
lcsSetupAccountingLastSnapshotEntryMacAddress OBJECT-TYPE
    SYNTAX     DisplayString (SIZE(0..255))
    MAX-ACCESS read-only
    STATUS     current
    DESCRIPTION
        "-- empty --"
    ::= { lcsSetupAccountingLastSnapshotEntry 2 }

-- {COLUMN} 1712.2.18.9.1.3
lcsSetupAccountingLastSnapshotEntryPeer OBJECT-TYPE
    SYNTAX     DisplayString (SIZE(0..16))
    MAX-ACCESS read-only
    STATUS     current
    DESCRIPTION
        "-- empty --"
    ::= { lcsSetupAccountingLastSnapshotEntry 3 }

-- {COLUMN} 1712.2.18.9.1.4
lcsSetupAccountingLastSnapshotEntryConnType OBJECT-TYPE
    SYNTAX     INTEGER
      {
        eUnknown (0),
        eDialUp (1),
        eLeasedLine (2),
        eDslLine (4),
        eVpnConn (7),
        ePptpConn (8),
        eL2tpConn (9),
        eDsLiteConn (10)
      }
    MAX-ACCESS read-only
    STATUS     current
    DESCRIPTION
        "-- empty --"
    ::= { lcsSetupAccountingLastSnapshotEntry 4 }

-- {COLUMN} 1712.2.18.9.1.5
lcsSetupAccountingLastSnapshotEntryRxKbytes OBJECT-TYPE
    SYNTAX     INTEGER (0..2147483647)
    MAX-ACCESS read-only
    STATUS     current
    DESCRIPTION
        "-- empty --"
    ::= { lcsSetupAccountingLastSnapshotEntry 5 }

-- {COLUMN} 1712.2.18.9.1.6
lcsSetupAccountingLastSnapshotEntryTxKbytes OBJECT-TYPE
    SYNTAX     INTEGER (0..2147483647)
    MAX-ACCESS read-only
    STATUS     current
    DESCRIPTION
        "-- empty --"
    ::= { lcsSetupAccountingLastSnapshotEntry 6 }

-- {COLUMN} 1712.2.18.9.1.8
lcsSetupAccountingLastSnapshotEntryTotalTime OBJECT-TYPE
    SYNTAX     Gauge32
    MAX-ACCESS read-only
    STATUS     current
    DESCRIPTION
        "-- empty --"
    ::= { lcsSetupAccountingLastSnapshotEntry 8 }

-- {COLUMN} 1712.2.18.9.1.9
lcsSetupAccountingLastSnapshotEntryConnections OBJECT-TYPE
    SYNTAX     INTEGER (0..2147483647)
    MAX-ACCESS read-only
    STATUS     current
    DESCRIPTION
        "-- empty --"
    ::= { lcsSetupAccountingLastSnapshotEntry 9 }

-- {OID} 1712.2.3
lcsSetupCharges OBJECT IDENTIFIER ::= { lcsSetup 3 }

-- {SCALAR} 1712.2.3.2
lcsSetupChargesDaysPerPeriod OBJECT-TYPE
    SYNTAX     INTEGER (0..65535)
    MAX-ACCESS read-write
    STATUS     current
    DESCRIPTION
        "-- empty --"
    ::= { lcsSetupCharges 2 }

-- {SCALAR} 1712.2.3.1
lcsSetupChargesBudgetUnits OBJECT-TYPE
    SYNTAX     INTEGER (0..65535)
    MAX-ACCESS read-write
    STATUS     current
    DESCRIPTION
        "-- empty --"
    ::= { lcsSetupCharges 1 }

-- {SCALAR} 1712.2.3.3
lcsSetupChargesSpareUnits OBJECT-TYPE
    SYNTAX     INTEGER (0..65535)
    MAX-ACCESS read-only
    STATUS     current
    DESCRIPTION
        "-- empty --"
    ::= { lcsSetupCharges 3 }

-- {SCALAR} 1712.2.3.4
lcsSetupChargesRouterUnits OBJECT-TYPE
    SYNTAX     INTEGER (0..2147483647)
    MAX-ACCESS read-only
    STATUS     current
    DESCRIPTION
        "-- empty --"
    ::= { lcsSetupCharges 4 }

-- {SCALAR} 1712.2.3.6
lcsSetupChargesTotalUnits OBJECT-TYPE
    SYNTAX     INTEGER (0..2147483647)
    MAX-ACCESS read-only
    STATUS     current
    DESCRIPTION
        "-- empty --"
    ::= { lcsSetupCharges 6 }

-- {TABLE} 1712.2.3.5
lcsSetupChargesTableBudgetTable OBJECT-TYPE
    SYNTAX     SEQUENCE OF LcsSetupChargesTableBudgetEntry
    MAX-ACCESS not-accessible
    STATUS     current
    DESCRIPTION
        "-- empty --"
    ::= { lcsSetupCharges 5 }

-- {ENTRY} 1712.2.3.5.1
lcsSetupChargesTableBudgetEntry OBJECT-TYPE
    SYNTAX     LcsSetupChargesTableBudgetEntry
    MAX-ACCESS not-accessible
    STATUS     current
    DESCRIPTION
        ""
    INDEX {
        lcsSetupChargesTableBudgetEntryIfc
    }
    ::= { lcsSetupChargesTableBudgetTable 1 }

-- {SEQUENCE}
LcsSetupChargesTableBudgetEntry ::= SEQUENCE {
    lcsSetupChargesTableBudgetEntryIfc INTEGER,
    lcsSetupChargesTableBudgetEntryBudgetUnits INTEGER,
    lcsSetupChargesTableBudgetEntrySpareBudget INTEGER,
    lcsSetupChargesTableBudgetEntryTotalUnits INTEGER
}

-- {COLUMN} 1712.2.3.5.1.1
lcsSetupChargesTableBudgetEntryIfc OBJECT-TYPE
    SYNTAX     INTEGER
      {
        eRouterIsdnSerial (1),
        eLancapi (2),
        eAb1 (3),
        eAb2 (4),
        eAb3 (5),
        eAb4 (6),
        eTimeModul (255)
      }
    MAX-ACCESS read-only
    STATUS     current
    DESCRIPTION
        "-- empty --"
    ::= { lcsSetupChargesTableBudgetEntry 1 }

-- {COLUMN} 1712.2.3.5.1.2
lcsSetupChargesTableBudgetEntryBudgetUnits OBJECT-TYPE
    SYNTAX     INTEGER (0..65535)
    MAX-ACCESS read-only
    STATUS     current
    DESCRIPTION
        "-- empty --"
    ::= { lcsSetupChargesTableBudgetEntry 2 }

-- {COLUMN} 1712.2.3.5.1.3
lcsSetupChargesTableBudgetEntrySpareBudget OBJECT-TYPE
    SYNTAX     INTEGER (0..65535)
    MAX-ACCESS read-only
    STATUS     current
    DESCRIPTION
        "-- empty --"
    ::= { lcsSetupChargesTableBudgetEntry 3 }

-- {COLUMN} 1712.2.3.5.1.4
lcsSetupChargesTableBudgetEntryTotalUnits OBJECT-TYPE
    SYNTAX     INTEGER (0..2147483647)
    MAX-ACCESS read-only
    STATUS     current
    DESCRIPTION
        "-- empty --"
    ::= { lcsSetupChargesTableBudgetEntry 4 }

-- {SCALAR} 1712.2.3.13
lcsSetupChargesDialupMinutesBudget OBJECT-TYPE
    SYNTAX     INTEGER (0..2147483647)
    MAX-ACCESS read-write
    STATUS     current
    DESCRIPTION
        "-- empty --"
    ::= { lcsSetupCharges 13 }

-- {SCALAR} 1712.2.3.14
lcsSetupChargesSpareDialupMinutes OBJECT-TYPE
    SYNTAX     INTEGER (0..2147483647)
    MAX-ACCESS read-only
    STATUS     current
    DESCRIPTION
        "-- empty --"
    ::= { lcsSetupCharges 14 }

-- {SCALAR} 1712.2.3.15
lcsSetupChargesDialupMinutesActive OBJECT-TYPE
    SYNTAX     INTEGER (0..2147483647)
    MAX-ACCESS read-only
    STATUS     current
    DESCRIPTION
        "-- empty --"
    ::= { lcsSetupCharges 15 }

-- {TABLE} 1712.2.3.7
lcsSetupChargesTimeTableTable OBJECT-TYPE
    SYNTAX     SEQUENCE OF LcsSetupChargesTimeTableEntry
    MAX-ACCESS not-accessible
    STATUS     current
    DESCRIPTION
        "-- empty --"
    ::= { lcsSetupCharges 7 }

-- {ENTRY} 1712.2.3.7.1
lcsSetupChargesTimeTableEntry OBJECT-TYPE
    SYNTAX     LcsSetupChargesTimeTableEntry
    MAX-ACCESS not-accessible
    STATUS     current
    DESCRIPTION
        ""
    INDEX {
        lcsSetupChargesTimeTableEntryIfc
    }
    ::= { lcsSetupChargesTimeTableTable 1 }

-- {SEQUENCE}
LcsSetupChargesTimeTableEntry ::= SEQUENCE {
    lcsSetupChargesTimeTableEntryIfc INTEGER,
    lcsSetupChargesTimeTableEntryBudgetMinutes INTEGER,
    lcsSetupChargesTimeTableEntrySpareMinutes INTEGER,
    lcsSetupChargesTimeTableEntryMinutesActive INTEGER,
    lcsSetupChargesTimeTableEntryMinutesPassive INTEGER
}

-- {COLUMN} 1712.2.3.7.1.1
lcsSetupChargesTimeTableEntryIfc OBJECT-TYPE
    SYNTAX     INTEGER
      {
        eRouterDslBroadband (1),
        eRouterIsdnSerial (2),
        eLancapi (3),
        eAb1 (4),
        eAb2 (5),
        eAb3 (6),
        eAb4 (7),
        eTimeModul (255)
      }
    MAX-ACCESS read-only
    STATUS     current
    DESCRIPTION
        "-- empty --"
    ::= { lcsSetupChargesTimeTableEntry 1 }

-- {COLUMN} 1712.2.3.7.1.2
lcsSetupChargesTimeTableEntryBudgetMinutes OBJECT-TYPE
    SYNTAX     INTEGER (0..2147483647)
    MAX-ACCESS read-only
    STATUS     current
    DESCRIPTION
        "-- empty --"
    ::= { lcsSetupChargesTimeTableEntry 2 }

-- {COLUMN} 1712.2.3.7.1.3
lcsSetupChargesTimeTableEntrySpareMinutes OBJECT-TYPE
    SYNTAX     INTEGER (0..2147483647)
    MAX-ACCESS read-only
    STATUS     current
    DESCRIPTION
        "-- empty --"
    ::= { lcsSetupChargesTimeTableEntry 3 }

-- {COLUMN} 1712.2.3.7.1.4
lcsSetupChargesTimeTableEntryMinutesActive OBJECT-TYPE
    SYNTAX     INTEGER (0..2147483647)
    MAX-ACCESS read-only
    STATUS     current
    DESCRIPTION
        "-- empty --"
    ::= { lcsSetupChargesTimeTableEntry 4 }

-- {COLUMN} 1712.2.3.7.1.5
lcsSetupChargesTimeTableEntryMinutesPassive OBJECT-TYPE
    SYNTAX     INTEGER (0..2147483647)
    MAX-ACCESS read-only
    STATUS     current
    DESCRIPTION
        "-- empty --"
    ::= { lcsSetupChargesTimeTableEntry 5 }

-- {SCALAR} 1712.2.3.8
lcsSetupChargesDslBroadbandMinutesBudget OBJECT-TYPE
    SYNTAX     INTEGER (0..2147483647)
    MAX-ACCESS read-write
    STATUS     current
    DESCRIPTION
        "-- empty --"
    ::= { lcsSetupCharges 8 }

-- {SCALAR} 1712.2.3.11
lcsSetupChargesAdditionalDslBroadbandBudget OBJECT-TYPE
    SYNTAX     INTEGER (0..2147483647)
    MAX-ACCESS read-write
    STATUS     current
    DESCRIPTION
        "-- empty --"
    ::= { lcsSetupCharges 11 }

-- {SCALAR} 1712.2.3.9
lcsSetupChargesSpareDslBroadbandMinutes OBJECT-TYPE
    SYNTAX     INTEGER (0..2147483647)
    MAX-ACCESS read-only
    STATUS     current
    DESCRIPTION
        "-- empty --"
    ::= { lcsSetupCharges 9 }

-- {SCALAR} 1712.2.3.10
lcsSetupChargesRouterDslBroadbandMinutesActive OBJECT-TYPE
    SYNTAX     INTEGER (0..2147483647)
    MAX-ACCESS read-only
    STATUS     current
    DESCRIPTION
        "-- empty --"
    ::= { lcsSetupCharges 10 }

-- {SCALAR} 1712.2.3.12
lcsSetupChargesActivateAdditionalBudget OBJECT-TYPE
    SYNTAX     DisplayString
    MAX-ACCESS read-write
    STATUS     current
    DESCRIPTION
        "-- empty --"
    ::= { lcsSetupCharges 12 }

-- {SCALAR} 1712.2.3.16
lcsSetupChargesResetBudgets OBJECT-TYPE
    SYNTAX     DisplayString
    MAX-ACCESS read-write
    STATUS     current
    DESCRIPTION
        "-- empty --"
    ::= { lcsSetupCharges 16 }

-- {OID} 1712.2.4
lcsSetupLan OBJECT IDENTIFIER ::= { lcsSetup 4 }

-- {SCALAR} 1712.2.4.2
lcsSetupLanMacAddress OBJECT-TYPE
    SYNTAX     MacAddress
    MAX-ACCESS read-only
    STATUS     current
    DESCRIPTION
        "-- empty --"
    ::= { lcsSetupLan 2 }

-- {SCALAR} 1712.2.4.3
lcsSetupLanSpareHeap OBJECT-TYPE
    SYNTAX     INTEGER (0..65535)
    MAX-ACCESS read-write
    STATUS     current
    DESCRIPTION
        "-- empty --"
    ::= { lcsSetupLan 3 }

-- {SCALAR} 1712.2.4.8
lcsSetupLanTraceMac OBJECT-TYPE
    SYNTAX     MacAddress
    MAX-ACCESS read-write
    STATUS     current
    DESCRIPTION
        "-- empty --"
    ::= { lcsSetupLan 8 }

-- {SCALAR} 1712.2.4.9
lcsSetupLanTraceLevel OBJECT-TYPE
    SYNTAX     INTEGER (0..255)
    MAX-ACCESS read-write
    STATUS     current
    DESCRIPTION
        "-- empty --"
    ::= { lcsSetupLan 9 }

-- {OID} 1712.2.4.10
lcsSetupLanIeee8021x OBJECT IDENTIFIER ::= { lcsSetupLan 10 }

-- {TABLE} 1712.2.4.10.1
lcsSetupLanIeee8021xSupplicantIfcSetupTable OBJECT-TYPE
    SYNTAX     SEQUENCE OF LcsSetupLanIeee8021xSupplicantIfcSetupEntry
    MAX-ACCESS not-accessible
    STATUS     current
    DESCRIPTION
        "-- empty --"
    ::= { lcsSetupLanIeee8021x 1 }

-- {ENTRY} 1712.2.4.10.1.1
lcsSetupLanIeee8021xSupplicantIfcSetupEntry OBJECT-TYPE
    SYNTAX     LcsSetupLanIeee8021xSupplicantIfcSetupEntry
    MAX-ACCESS not-accessible
    STATUS     current
    DESCRIPTION
        ""
    INDEX {
        lcsSetupLanIeee8021xSupplicantIfcSetupEntryIfc
    }
    ::= { lcsSetupLanIeee8021xSupplicantIfcSetupTable 1 }

-- {SEQUENCE}
LcsSetupLanIeee8021xSupplicantIfcSetupEntry ::= SEQUENCE {
    lcsSetupLanIeee8021xSupplicantIfcSetupEntryIfc INTEGER,
    lcsSetupLanIeee8021xSupplicantIfcSetupEntryMethod INTEGER,
    lcsSetupLanIeee8021xSupplicantIfcSetupEntryCredentials DisplayString
}

-- {COLUMN} 1712.2.4.10.1.1.1
lcsSetupLanIeee8021xSupplicantIfcSetupEntryIfc OBJECT-TYPE
    SYNTAX     INTEGER
      {
        eLan1 (1),
        eLan2 (2),
        eLan3 (3),
        eLan4 (4)
      }
    MAX-ACCESS read-only
    STATUS     current
    DESCRIPTION
        "-- empty --"
    ::= { lcsSetupLanIeee8021xSupplicantIfcSetupEntry 1 }

-- {COLUMN} 1712.2.4.10.1.1.2
lcsSetupLanIeee8021xSupplicantIfcSetupEntryMethod OBJECT-TYPE
    SYNTAX     INTEGER
      {
        eNone (0),
        eMd5 (1024),
        eTls (3328),
        eTtlsPap (5383),
        eTtlsChap (5384),
        eTtlsMschap (5567),
        eTtlsMschapv2 (5402),
        eTtlsMd5 (5380),
        ePeapMschapv2 (6426),
        ePeapGtc (6406)
      }
    MAX-ACCESS read-write
    STATUS     current
    DESCRIPTION
        "-- empty --"
    ::= { lcsSetupLanIeee8021xSupplicantIfcSetupEntry 2 }

-- {COLUMN} 1712.2.4.10.1.1.3
lcsSetupLanIeee8021xSupplicantIfcSetupEntryCredentials OBJECT-TYPE
    SYNTAX     DisplayString (SIZE(0..64))
    MAX-ACCESS read-write
    STATUS     current
    DESCRIPTION
        "-- empty --"
    ::= { lcsSetupLanIeee8021xSupplicantIfcSetupEntry 3 }

-- {SCALAR} 1712.2.4.11
lcsSetupLanLinkupReportDelayMs OBJECT-TYPE
    SYNTAX     INTEGER (0..2147483647)
    MAX-ACCESS read-write
    STATUS     current
    DESCRIPTION
        "-- empty --"
    ::= { lcsSetupLan 11 }

-- {OID} 1712.2.7
lcsSetupTcpIp OBJECT IDENTIFIER ::= { lcsSetup 7 }

-- {SCALAR} 1712.2.7.1
lcsSetupTcpIpOperating OBJECT-TYPE
    SYNTAX     INTEGER
      {
        eNo (0),
        eYes (1)
      }
    MAX-ACCESS read-write
    STATUS     current
    DESCRIPTION
        "-- empty --"
    ::= { lcsSetupTcpIp 1 }

-- {TABLE} 1712.2.7.30
lcsSetupTcpIpNetworkListTable OBJECT-TYPE
    SYNTAX     SEQUENCE OF LcsSetupTcpIpNetworkListEntry
    MAX-ACCESS not-accessible
    STATUS     current
    DESCRIPTION
        "-- empty --"
    ::= { lcsSetupTcpIp 30 }

-- {ENTRY} 1712.2.7.30.1
lcsSetupTcpIpNetworkListEntry OBJECT-TYPE
    SYNTAX     LcsSetupTcpIpNetworkListEntry
    MAX-ACCESS not-accessible
    STATUS     current
    DESCRIPTION
        ""
    INDEX {
        lcsSetupTcpIpNetworkListEntryNetworkName
    }
    ::= { lcsSetupTcpIpNetworkListTable 1 }

-- {SEQUENCE}
LcsSetupTcpIpNetworkListEntry ::= SEQUENCE {
    lcsSetupTcpIpNetworkListEntryNetworkName DisplayString,
    lcsSetupTcpIpNetworkListEntryIpAddress IpAddress,
    lcsSetupTcpIpNetworkListEntryIpNetmask IpAddress,
    lcsSetupTcpIpNetworkListEntryVlanId INTEGER,
    lcsSetupTcpIpNetworkListEntryInterface INTEGER,
    lcsSetupTcpIpNetworkListEntrySrcCheck INTEGER,
    lcsSetupTcpIpNetworkListEntryType INTEGER,
    lcsSetupTcpIpNetworkListEntryRtgTag INTEGER,
    lcsSetupTcpIpNetworkListEntryComment DisplayString
}

-- {COLUMN} 1712.2.7.30.1.1
lcsSetupTcpIpNetworkListEntryNetworkName OBJECT-TYPE
    SYNTAX     DisplayString (SIZE(0..17))
    MAX-ACCESS read-write
    STATUS     current
    DESCRIPTION
        "-- empty --"
    ::= { lcsSetupTcpIpNetworkListEntry 1 }

-- {COLUMN} 1712.2.7.30.1.2
lcsSetupTcpIpNetworkListEntryIpAddress OBJECT-TYPE
    SYNTAX     IpAddress
    MAX-ACCESS read-write
    STATUS     current
    DESCRIPTION
        "-- empty --"
    ::= { lcsSetupTcpIpNetworkListEntry 2 }

-- {COLUMN} 1712.2.7.30.1.3
lcsSetupTcpIpNetworkListEntryIpNetmask OBJECT-TYPE
    SYNTAX     IpAddress
    MAX-ACCESS read-write
    STATUS     current
    DESCRIPTION
        "-- empty --"
    ::= { lcsSetupTcpIpNetworkListEntry 3 }

-- {COLUMN} 1712.2.7.30.1.4
lcsSetupTcpIpNetworkListEntryVlanId OBJECT-TYPE
    SYNTAX     INTEGER (0..65535)
    MAX-ACCESS read-write
    STATUS     current
    DESCRIPTION
        "-- empty --"
    ::= { lcsSetupTcpIpNetworkListEntry 4 }

-- {COLUMN} 1712.2.7.30.1.5
lcsSetupTcpIpNetworkListEntryInterface OBJECT-TYPE
    SYNTAX     INTEGER
      {
        eLan1 (256),
        eLan2 (257),
        eLan3 (258),
        eLan4 (259),
        eAny (65535)
      }
    MAX-ACCESS read-write
    STATUS     current
    DESCRIPTION
        "-- empty --"
    ::= { lcsSetupTcpIpNetworkListEntry 5 }

-- {COLUMN} 1712.2.7.30.1.6
lcsSetupTcpIpNetworkListEntrySrcCheck OBJECT-TYPE
    SYNTAX     INTEGER
      {
        eStrict (1),
        eLoose (0)
      }
    MAX-ACCESS read-write
    STATUS     current
    DESCRIPTION
        "-- empty --"
    ::= { lcsSetupTcpIpNetworkListEntry 6 }

-- {COLUMN} 1712.2.7.30.1.7
lcsSetupTcpIpNetworkListEntryType OBJECT-TYPE
    SYNTAX     INTEGER
      {
        eDisabled (0),
        eIntranet (1),
        eDmz (2)
      }
    MAX-ACCESS read-write
    STATUS     current
    DESCRIPTION
        "-- empty --"
    ::= { lcsSetupTcpIpNetworkListEntry 7 }

-- {COLUMN} 1712.2.7.30.1.8
lcsSetupTcpIpNetworkListEntryRtgTag OBJECT-TYPE
    SYNTAX     INTEGER (0..65535)
    MAX-ACCESS read-write
    STATUS     current
    DESCRIPTION
        "-- empty --"
    ::= { lcsSetupTcpIpNetworkListEntry 8 }

-- {COLUMN} 1712.2.7.30.1.9
lcsSetupTcpIpNetworkListEntryComment OBJECT-TYPE
    SYNTAX     DisplayString (SIZE(0..64))
    MAX-ACCESS read-write
    STATUS     current
    DESCRIPTION
        "-- empty --"
    ::= { lcsSetupTcpIpNetworkListEntry 9 }

-- {TABLE} 1712.2.7.17
lcsSetupTcpIpLoopbackListTable OBJECT-TYPE
    SYNTAX     SEQUENCE OF LcsSetupTcpIpLoopbackListEntry
    MAX-ACCESS not-accessible
    STATUS     current
    DESCRIPTION
        "-- empty --"
    ::= { lcsSetupTcpIp 17 }

-- {ENTRY} 1712.2.7.17.1
lcsSetupTcpIpLoopbackListEntry OBJECT-TYPE
    SYNTAX     LcsSetupTcpIpLoopbackListEntry
    MAX-ACCESS not-accessible
    STATUS     current
    DESCRIPTION
        ""
    INDEX {
        lcsSetupTcpIpLoopbackListEntryName
    }
    ::= { lcsSetupTcpIpLoopbackListTable 1 }

-- {SEQUENCE}
LcsSetupTcpIpLoopbackListEntry ::= SEQUENCE {
    lcsSetupTcpIpLoopbackListEntryName DisplayString,
    lcsSetupTcpIpLoopbackListEntryLoopbackAddr IpAddress,
    lcsSetupTcpIpLoopbackListEntryRtgTag INTEGER
}

-- {COLUMN} 1712.2.7.17.1.2
lcsSetupTcpIpLoopbackListEntryName OBJECT-TYPE
    SYNTAX     DisplayString (SIZE(0..16))
    MAX-ACCESS read-write
    STATUS     current
    DESCRIPTION
        "-- empty --"
    ::= { lcsSetupTcpIpLoopbackListEntry 2 }

-- {COLUMN} 1712.2.7.17.1.1
lcsSetupTcpIpLoopbackListEntryLoopbackAddr OBJECT-TYPE
    SYNTAX     IpAddress
    MAX-ACCESS read-write
    STATUS     current
    DESCRIPTION
        "-- empty --"
    ::= { lcsSetupTcpIpLoopbackListEntry 1 }

-- {COLUMN} 1712.2.7.17.1.3
lcsSetupTcpIpLoopbackListEntryRtgTag OBJECT-TYPE
    SYNTAX     INTEGER (0..65535)
    MAX-ACCESS read-write
    STATUS     current
    DESCRIPTION
        "-- empty --"
    ::= { lcsSetupTcpIpLoopbackListEntry 3 }

-- {TABLE} 1712.2.7.6
lcsSetupTcpIpAccessListTable OBJECT-TYPE
    SYNTAX     SEQUENCE OF LcsSetupTcpIpAccessListEntry
    MAX-ACCESS not-accessible
    STATUS     current
    DESCRIPTION
        "-- empty --"
    ::= { lcsSetupTcpIp 6 }

-- {ENTRY} 1712.2.7.6.1
lcsSetupTcpIpAccessListEntry OBJECT-TYPE
    SYNTAX     LcsSetupTcpIpAccessListEntry
    MAX-ACCESS not-accessible
    STATUS     current
    DESCRIPTION
        ""
    INDEX {
        lcsSetupTcpIpAccessListEntryIpAddress,
        lcsSetupTcpIpAccessListEntryIpNetmask,
        lcsSetupTcpIpAccessListEntryRtgTag
    }
    ::= { lcsSetupTcpIpAccessListTable 1 }

-- {SEQUENCE}
LcsSetupTcpIpAccessListEntry ::= SEQUENCE {
    lcsSetupTcpIpAccessListEntryIpAddress IpAddress,
    lcsSetupTcpIpAccessListEntryIpNetmask IpAddress,
    lcsSetupTcpIpAccessListEntryRtgTag INTEGER,
    lcsSetupTcpIpAccessListEntryComment DisplayString
}

-- {COLUMN} 1712.2.7.6.1.1
lcsSetupTcpIpAccessListEntryIpAddress OBJECT-TYPE
    SYNTAX     IpAddress
    MAX-ACCESS read-write
    STATUS     current
    DESCRIPTION
        "-- empty --"
    ::= { lcsSetupTcpIpAccessListEntry 1 }

-- {COLUMN} 1712.2.7.6.1.2
lcsSetupTcpIpAccessListEntryIpNetmask OBJECT-TYPE
    SYNTAX     IpAddress
    MAX-ACCESS read-write
    STATUS     current
    DESCRIPTION
        "-- empty --"
    ::= { lcsSetupTcpIpAccessListEntry 2 }

-- {COLUMN} 1712.2.7.6.1.3
lcsSetupTcpIpAccessListEntryRtgTag OBJECT-TYPE
    SYNTAX     INTEGER (0..65535)
    MAX-ACCESS read-write
    STATUS     current
    DESCRIPTION
        "-- empty --"
    ::= { lcsSetupTcpIpAccessListEntry 3 }

-- {COLUMN} 1712.2.7.6.1.4
lcsSetupTcpIpAccessListEntryComment OBJECT-TYPE
    SYNTAX     DisplayString (SIZE(0..63))
    MAX-ACCESS read-write
    STATUS     current
    DESCRIPTION
        "-- empty --"
    ::= { lcsSetupTcpIpAccessListEntry 4 }

-- {SCALAR} 1712.2.7.7
lcsSetupTcpIpDnsDefault OBJECT-TYPE
    SYNTAX     IpAddress
    MAX-ACCESS read-write
    STATUS     current
    DESCRIPTION
        "-- empty --"
    ::= { lcsSetupTcpIp 7 }

-- {SCALAR} 1712.2.7.8
lcsSetupTcpIpDnsBackup OBJECT-TYPE
    SYNTAX     IpAddress
    MAX-ACCESS read-write
    STATUS     current
    DESCRIPTION
        "-- empty --"
    ::= { lcsSetupTcpIp 8 }

-- {SCALAR} 1712.2.7.9
lcsSetupTcpIpNbnsDefault OBJECT-TYPE
    SYNTAX     IpAddress
    MAX-ACCESS read-write
    STATUS     current
    DESCRIPTION
        "-- empty --"
    ::= { lcsSetupTcpIp 9 }

-- {SCALAR} 1712.2.7.10
lcsSetupTcpIpNbnsBackup OBJECT-TYPE
    SYNTAX     IpAddress
    MAX-ACCESS read-write
    STATUS     current
    DESCRIPTION
        "-- empty --"
    ::= { lcsSetupTcpIp 10 }

-- {TABLE} 1712.2.7.16
lcsSetupTcpIpArpTableTable OBJECT-TYPE
    SYNTAX     SEQUENCE OF LcsSetupTcpIpArpTableEntry
    MAX-ACCESS not-accessible
    STATUS     current
    DESCRIPTION
        "-- empty --"
    ::= { lcsSetupTcpIp 16 }

-- {ENTRY} 1712.2.7.16.1
lcsSetupTcpIpArpTableEntry OBJECT-TYPE
    SYNTAX     LcsSetupTcpIpArpTableEntry
    MAX-ACCESS not-accessible
    STATUS     current
    DESCRIPTION
        ""
    INDEX {
        lcsSetupTcpIpArpTableEntryIpAddress
    }
    ::= { lcsSetupTcpIpArpTableTable 1 }

-- {SEQUENCE}
LcsSetupTcpIpArpTableEntry ::= SEQUENCE {
    lcsSetupTcpIpArpTableEntryIpAddress IpAddress,
    lcsSetupTcpIpArpTableEntryMacAddress MacAddress,
    lcsSetupTcpIpArpTableEntryLastAccess INTEGER,
    lcsSetupTcpIpArpTableEntryConnect INTEGER,
    lcsSetupTcpIpArpTableEntryEthernetPort INTEGER,
    lcsSetupTcpIpArpTableEntryVlanId INTEGER,
    lcsSetupTcpIpArpTableEntryPeer DisplayString
}

-- {COLUMN} 1712.2.7.16.1.1
lcsSetupTcpIpArpTableEntryIpAddress OBJECT-TYPE
    SYNTAX     IpAddress
    MAX-ACCESS read-only
    STATUS     current
    DESCRIPTION
        "-- empty --"
    ::= { lcsSetupTcpIpArpTableEntry 1 }

-- {COLUMN} 1712.2.7.16.1.2
lcsSetupTcpIpArpTableEntryMacAddress OBJECT-TYPE
    SYNTAX     MacAddress
    MAX-ACCESS read-only
    STATUS     current
    DESCRIPTION
        "-- empty --"
    ::= { lcsSetupTcpIpArpTableEntry 2 }

-- {COLUMN} 1712.2.7.16.1.3
lcsSetupTcpIpArpTableEntryLastAccess OBJECT-TYPE
    SYNTAX     INTEGER (0..2147483647)
    MAX-ACCESS read-only
    STATUS     current
    DESCRIPTION
        "-- empty --"
    ::= { lcsSetupTcpIpArpTableEntry 3 }

-- {COLUMN} 1712.2.7.16.1.8
lcsSetupTcpIpArpTableEntryConnect OBJECT-TYPE
    SYNTAX     INTEGER
      {
        eLan1 (256),
        eLan2 (257),
        eLan3 (258),
        eLan4 (259),
        eWan (32768)
      }
    MAX-ACCESS read-only
    STATUS     current
    DESCRIPTION
        "-- empty --"
    ::= { lcsSetupTcpIpArpTableEntry 8 }

-- {COLUMN} 1712.2.7.16.1.5
lcsSetupTcpIpArpTableEntryEthernetPort OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsSetupTcpIpArpTableEntry 5 }

-- {COLUMN} 1712.2.7.16.1.7
lcsSetupTcpIpArpTableEntryVlanId OBJECT-TYPE
    SYNTAX     INTEGER (0..65535)
    MAX-ACCESS read-only
    STATUS     current
    DESCRIPTION
        "-- empty --"
    ::= { lcsSetupTcpIpArpTableEntry 7 }

-- {COLUMN} 1712.2.7.16.1.6
lcsSetupTcpIpArpTableEntryPeer OBJECT-TYPE
    SYNTAX     DisplayString (SIZE(0..255))
    MAX-ACCESS read-only
    STATUS     current
    DESCRIPTION
        "-- empty --"
    ::= { lcsSetupTcpIpArpTableEntry 6 }

-- {SCALAR} 1712.2.7.20
lcsSetupTcpIpNonLocArpReplies OBJECT-TYPE
    SYNTAX     INTEGER
      {
        eNo (0),
        eYes (1)
      }
    MAX-ACCESS read-write
    STATUS     current
    DESCRIPTION
        "-- empty --"
    ::= { lcsSetupTcpIp 20 }

-- {SCALAR} 1712.2.7.22
lcsSetupTcpIpIcmpOnArpTimeout OBJECT-TYPE
    SYNTAX     INTEGER
      {
        eNo (0),
        eYes (1)
      }
    MAX-ACCESS read-write
    STATUS     current
    DESCRIPTION
        "-- empty --"
    ::= { lcsSetupTcpIp 22 }

-- {SCALAR} 1712.2.7.11
lcsSetupTcpIpArpAgingMinutes OBJECT-TYPE
    SYNTAX     INTEGER (0..255)
    MAX-ACCESS read-write
    STATUS     current
    DESCRIPTION
        "-- empty --"
    ::= { lcsSetupTcpIp 11 }

-- {OID} 1712.2.7.21
lcsSetupTcpIpAliveTest OBJECT IDENTIFIER ::= { lcsSetupTcpIp 21 }

-- {SCALAR} 1712.2.7.21.1
lcsSetupTcpIpAliveTestTargetAddress OBJECT-TYPE
    SYNTAX     IpAddress
    MAX-ACCESS read-write
    STATUS     current
    DESCRIPTION
        "-- empty --"
    ::= { lcsSetupTcpIpAliveTest 1 }

-- {SCALAR} 1712.2.7.21.2
lcsSetupTcpIpAliveTestTestInterval OBJECT-TYPE
    SYNTAX     INTEGER (0..2147483647)
    MAX-ACCESS read-write
    STATUS     current
    DESCRIPTION
        "-- empty --"
    ::= { lcsSetupTcpIpAliveTest 2 }

-- {SCALAR} 1712.2.7.21.3
lcsSetupTcpIpAliveTestRetryCount OBJECT-TYPE
    SYNTAX     INTEGER (0..2147483647)
    MAX-ACCESS read-write
    STATUS     current
    DESCRIPTION
        "-- empty --"
    ::= { lcsSetupTcpIpAliveTest 3 }

-- {SCALAR} 1712.2.7.21.4
lcsSetupTcpIpAliveTestRetryInterval OBJECT-TYPE
    SYNTAX     INTEGER (0..2147483647)
    MAX-ACCESS read-write
    STATUS     current
    DESCRIPTION
        "-- empty --"
    ::= { lcsSetupTcpIpAliveTest 4 }

-- {SCALAR} 1712.2.7.21.5
lcsSetupTcpIpAliveTestFailLimit OBJECT-TYPE
    SYNTAX     INTEGER (0..2147483647)
    MAX-ACCESS read-write
    STATUS     current
    DESCRIPTION
        "-- empty --"
    ::= { lcsSetupTcpIpAliveTest 5 }

-- {SCALAR} 1712.2.7.21.6
lcsSetupTcpIpAliveTestBootType OBJECT-TYPE
    SYNTAX     INTEGER
      {
        eWarmBoot (0),
        eColdBoot (1),
        eAction (2)
      }
    MAX-ACCESS read-write
    STATUS     current
    DESCRIPTION
        "-- empty --"
    ::= { lcsSetupTcpIpAliveTest 6 }

-- {SCALAR} 1712.2.7.21.7
lcsSetupTcpIpAliveTestAction OBJECT-TYPE
    SYNTAX     DisplayString (SIZE(0..251))
    MAX-ACCESS read-write
    STATUS     current
    DESCRIPTION
        "-- empty --"
    ::= { lcsSetupTcpIpAliveTest 7 }

-- {OID} 1712.2.8
lcsSetupIpRouter OBJECT IDENTIFIER ::= { lcsSetup 8 }

-- {SCALAR} 1712.2.8.1
lcsSetupIpRouterOperating OBJECT-TYPE
    SYNTAX     INTEGER
      {
        eNo (0),
        eYes (1)
      }
    MAX-ACCESS read-write
    STATUS     current
    DESCRIPTION
        "-- empty --"
    ::= { lcsSetupIpRouter 1 }

-- {TABLE} 1712.2.8.2
lcsSetupIpRouterIpRoutingTableTable OBJECT-TYPE
    SYNTAX     SEQUENCE OF LcsSetupIpRouterIpRoutingTableEntry
    MAX-ACCESS not-accessible
    STATUS     current
    DESCRIPTION
        "-- empty --"
    ::= { lcsSetupIpRouter 2 }

-- {ENTRY} 1712.2.8.2.1
lcsSetupIpRouterIpRoutingTableEntry OBJECT-TYPE
    SYNTAX     LcsSetupIpRouterIpRoutingTableEntry
    MAX-ACCESS not-accessible
    STATUS     current
    DESCRIPTION
        ""
    INDEX {
        lcsSetupIpRouterIpRoutingTableEntryIpAddress,
        lcsSetupIpRouterIpRoutingTableEntryIpNetmask,
        lcsSetupIpRouterIpRoutingTableEntryRtgTag
    }
    ::= { lcsSetupIpRouterIpRoutingTableTable 1 }

-- {SEQUENCE}
LcsSetupIpRouterIpRoutingTableEntry ::= SEQUENCE {
    lcsSetupIpRouterIpRoutingTableEntryIpAddress IpAddress,
    lcsSetupIpRouterIpRoutingTableEntryIpNetmask IpAddress,
    lcsSetupIpRouterIpRoutingTableEntryRtgTag INTEGER,
    lcsSetupIpRouterIpRoutingTableEntryPeerOrIp DisplayString,
    lcsSetupIpRouterIpRoutingTableEntryDistance INTEGER,
    lcsSetupIpRouterIpRoutingTableEntryMasquerade INTEGER,
    lcsSetupIpRouterIpRoutingTableEntryActive INTEGER,
    lcsSetupIpRouterIpRoutingTableEntryComment DisplayString
}

-- {COLUMN} 1712.2.8.2.1.1
lcsSetupIpRouterIpRoutingTableEntryIpAddress OBJECT-TYPE
    SYNTAX     IpAddress
    MAX-ACCESS read-write
    STATUS     current
    DESCRIPTION
        "-- empty --"
    ::= { lcsSetupIpRouterIpRoutingTableEntry 1 }

-- {COLUMN} 1712.2.8.2.1.2
lcsSetupIpRouterIpRoutingTableEntryIpNetmask OBJECT-TYPE
    SYNTAX     IpAddress
    MAX-ACCESS read-write
    STATUS     current
    DESCRIPTION
        "-- empty --"
    ::= { lcsSetupIpRouterIpRoutingTableEntry 2 }

-- {COLUMN} 1712.2.8.2.1.8
lcsSetupIpRouterIpRoutingTableEntryRtgTag OBJECT-TYPE
    SYNTAX     INTEGER (0..65535)
    MAX-ACCESS read-write
    STATUS     current
    DESCRIPTION
        "-- empty --"
    ::= { lcsSetupIpRouterIpRoutingTableEntry 8 }

-- {COLUMN} 1712.2.8.2.1.3
lcsSetupIpRouterIpRoutingTableEntryPeerOrIp OBJECT-TYPE
    SYNTAX     DisplayString (SIZE(0..16))
    MAX-ACCESS read-write
    STATUS     current
    DESCRIPTION
        "-- empty --"
    ::= { lcsSetupIpRouterIpRoutingTableEntry 3 }

-- {COLUMN} 1712.2.8.2.1.4
lcsSetupIpRouterIpRoutingTableEntryDistance OBJECT-TYPE
    SYNTAX     INTEGER (0..255)
    MAX-ACCESS read-write
    STATUS     current
    DESCRIPTION
        "-- empty --"
    ::= { lcsSetupIpRouterIpRoutingTableEntry 4 }

-- {COLUMN} 1712.2.8.2.1.5
lcsSetupIpRouterIpRoutingTableEntryMasquerade OBJECT-TYPE
    SYNTAX     INTEGER
      {
        eNo (0),
        eOn (1),
        eIntranet (2)
      }
    MAX-ACCESS read-write
    STATUS     current
    DESCRIPTION
        "-- empty --"
    ::= { lcsSetupIpRouterIpRoutingTableEntry 5 }

-- {COLUMN} 1712.2.8.2.1.6
lcsSetupIpRouterIpRoutingTableEntryActive OBJECT-TYPE
    SYNTAX     INTEGER
      {
        eNo (1),
        eYes (0),
        eSemi (2)
      }
    MAX-ACCESS read-write
    STATUS     current
    DESCRIPTION
        "-- empty --"
    ::= { lcsSetupIpRouterIpRoutingTableEntry 6 }

-- {COLUMN} 1712.2.8.2.1.7
lcsSetupIpRouterIpRoutingTableEntryComment OBJECT-TYPE
    SYNTAX     DisplayString (SIZE(0..64))
    MAX-ACCESS read-write
    STATUS     current
    DESCRIPTION
        "-- empty --"
    ::= { lcsSetupIpRouterIpRoutingTableEntry 7 }

-- {TABLE} 1712.2.8.13
lcsSetupIpRouterDefaultTimeListTable OBJECT-TYPE
    SYNTAX     SEQUENCE OF LcsSetupIpRouterDefaultTimeListEntry
    MAX-ACCESS not-accessible
    STATUS     current
    DESCRIPTION
        "-- empty --"
    ::= { lcsSetupIpRouter 13 }

-- {ENTRY} 1712.2.8.13.1
lcsSetupIpRouterDefaultTimeListEntry OBJECT-TYPE
    SYNTAX     LcsSetupIpRouterDefaultTimeListEntry
    MAX-ACCESS not-accessible
    STATUS     current
    DESCRIPTION
        ""
    INDEX {
        lcsSetupIpRouterDefaultTimeListEntryIndex
    }
    ::= { lcsSetupIpRouterDefaultTimeListTable 1 }

-- {SEQUENCE}
LcsSetupIpRouterDefaultTimeListEntry ::= SEQUENCE {
    lcsSetupIpRouterDefaultTimeListEntryIndex INTEGER,
    lcsSetupIpRouterDefaultTimeListEntryDays BITS,
    lcsSetupIpRouterDefaultTimeListEntryStart DisplayString,
    lcsSetupIpRouterDefaultTimeListEntryStop DisplayString,
    lcsSetupIpRouterDefaultTimeListEntryPeer DisplayString
}

-- {COLUMN} 1712.2.8.13.1.1
lcsSetupIpRouterDefaultTimeListEntryIndex OBJECT-TYPE
    SYNTAX     INTEGER (0..65535)
    MAX-ACCESS read-write
    STATUS     current
    DESCRIPTION
        "-- empty --"
    ::= { lcsSetupIpRouterDefaultTimeListEntry 1 }

-- {COLUMN} 1712.2.8.13.1.2
lcsSetupIpRouterDefaultTimeListEntryDays OBJECT-TYPE
    SYNTAX     BITS
      {
        eMonday (7),
        eTuesday (6),
        eWednesday (5),
        eThursday (4),
        eFriday (3),
        eSaturday (2),
        eSunday (1),
        eHoliday (0)
      }
    MAX-ACCESS read-write
    STATUS     current
    DESCRIPTION
        "-- empty --"
    ::= { lcsSetupIpRouterDefaultTimeListEntry 2 }

-- {COLUMN} 1712.2.8.13.1.3
lcsSetupIpRouterDefaultTimeListEntryStart OBJECT-TYPE
    SYNTAX     DisplayString (SIZE(0..5))
    MAX-ACCESS read-write
    STATUS     current
    DESCRIPTION
        "-- empty --"
    ::= { lcsSetupIpRouterDefaultTimeListEntry 3 }

-- {COLUMN} 1712.2.8.13.1.4
lcsSetupIpRouterDefaultTimeListEntryStop OBJECT-TYPE
    SYNTAX     DisplayString (SIZE(0..5))
    MAX-ACCESS read-write
    STATUS     current
    DESCRIPTION
        "-- empty --"
    ::= { lcsSetupIpRouterDefaultTimeListEntry 4 }

-- {COLUMN} 1712.2.8.13.1.5
lcsSetupIpRouterDefaultTimeListEntryPeer OBJECT-TYPE
    SYNTAX     DisplayString (SIZE(0..16))
    MAX-ACCESS read-write
    STATUS     current
    DESCRIPTION
        "-- empty --"
    ::= { lcsSetupIpRouterDefaultTimeListEntry 5 }

-- {SCALAR} 1712.2.8.14
lcsSetupIpRouterUsageDefaultTimetable OBJECT-TYPE
    SYNTAX     INTEGER
      {
        eNo (0),
        eYes (1)
      }
    MAX-ACCESS read-write
    STATUS     current
    DESCRIPTION
        "-- empty --"
    ::= { lcsSetupIpRouter 14 }

-- {SCALAR} 1712.2.8.5
lcsSetupIpRouterProxyArp OBJECT-TYPE
    SYNTAX     INTEGER
      {
        eNo (0),
        eYes (1)
      }
    MAX-ACCESS read-write
    STATUS     current
    DESCRIPTION
        "-- empty --"
    ::= { lcsSetupIpRouter 5 }

-- {SCALAR} 1712.2.8.6
lcsSetupIpRouterSendIcmpRedirect OBJECT-TYPE
    SYNTAX     INTEGER
      {
        eNo (1),
        eYes (0)
      }
    MAX-ACCESS read-write
    STATUS     current
    DESCRIPTION
        "-- empty --"
    ::= { lcsSetupIpRouter 6 }

-- {SCALAR} 1712.2.8.11
lcsSetupIpRouterStartWanPool OBJECT-TYPE
    SYNTAX     IpAddress
    MAX-ACCESS read-write
    STATUS     current
    DESCRIPTION
        "-- empty --"
    ::= { lcsSetupIpRouter 11 }

-- {SCALAR} 1712.2.8.12
lcsSetupIpRouterEndWanPool OBJECT-TYPE
    SYNTAX     IpAddress
    MAX-ACCESS read-write
    STATUS     current
    DESCRIPTION
        "-- empty --"
    ::= { lcsSetupIpRouter 12 }

-- {OID} 1712.2.8.20
lcsSetupIpRouterLoadBalancer OBJECT IDENTIFIER ::= { lcsSetupIpRouter 20 }

-- {SCALAR} 1712.2.8.20.1
lcsSetupIpRouterLoadBalancerOperating OBJECT-TYPE
    SYNTAX     INTEGER
      {
        eNo (0),
        eYes (1)
      }
    MAX-ACCESS read-write
    STATUS     current
    DESCRIPTION
        "-- empty --"
    ::= { lcsSetupIpRouterLoadBalancer 1 }

-- {TABLE} 1712.2.8.20.2
lcsSetupIpRouterLoadBalancerBundlePeersTable OBJECT-TYPE
    SYNTAX     SEQUENCE OF LcsSetupIpRouterLoadBalancerBundlePeersEntry
    MAX-ACCESS not-accessible
    STATUS     current
    DESCRIPTION
        "-- empty --"
    ::= { lcsSetupIpRouterLoadBalancer 2 }

-- {ENTRY} 1712.2.8.20.2.1
lcsSetupIpRouterLoadBalancerBundlePeersEntry OBJECT-TYPE
    SYNTAX     LcsSetupIpRouterLoadBalancerBundlePeersEntry
    MAX-ACCESS not-accessible
    STATUS     current
    DESCRIPTION
        ""
    INDEX {
        lcsSetupIpRouterLoadBalancerBundlePeersEntryPeer
    }
    ::= { lcsSetupIpRouterLoadBalancerBundlePeersTable 1 }

-- {SEQUENCE}
LcsSetupIpRouterLoadBalancerBundlePeersEntry ::= SEQUENCE {
    lcsSetupIpRouterLoadBalancerBundlePeersEntryPeer DisplayString,
    lcsSetupIpRouterLoadBalancerBundlePeersEntryBundlePeer1 DisplayString,
    lcsSetupIpRouterLoadBalancerBundlePeersEntryBundlePeer2 DisplayString,
    lcsSetupIpRouterLoadBalancerBundlePeersEntryBundlePeer3 DisplayString,
    lcsSetupIpRouterLoadBalancerBundlePeersEntryBundlePeer4 DisplayString
}

-- {COLUMN} 1712.2.8.20.2.1.1
lcsSetupIpRouterLoadBalancerBundlePeersEntryPeer OBJECT-TYPE
    SYNTAX     DisplayString (SIZE(0..16))
    MAX-ACCESS read-write
    STATUS     current
    DESCRIPTION
        "-- empty --"
    ::= { lcsSetupIpRouterLoadBalancerBundlePeersEntry 1 }

-- {COLUMN} 1712.2.8.20.2.1.2
lcsSetupIpRouterLoadBalancerBundlePeersEntryBundlePeer1 OBJECT-TYPE
    SYNTAX     DisplayString (SIZE(0..16))
    MAX-ACCESS read-write
    STATUS     current
    DESCRIPTION
        "-- empty --"
    ::= { lcsSetupIpRouterLoadBalancerBundlePeersEntry 2 }

-- {COLUMN} 1712.2.8.20.2.1.3
lcsSetupIpRouterLoadBalancerBundlePeersEntryBundlePeer2 OBJECT-TYPE
    SYNTAX     DisplayString (SIZE(0..16))
    MAX-ACCESS read-write
    STATUS     current
    DESCRIPTION
        "-- empty --"
    ::= { lcsSetupIpRouterLoadBalancerBundlePeersEntry 3 }

-- {COLUMN} 1712.2.8.20.2.1.4
lcsSetupIpRouterLoadBalancerBundlePeersEntryBundlePeer3 OBJECT-TYPE
    SYNTAX     DisplayString (SIZE(0..16))
    MAX-ACCESS read-write
    STATUS     current
    DESCRIPTION
        "-- empty --"
    ::= { lcsSetupIpRouterLoadBalancerBundlePeersEntry 4 }

-- {COLUMN} 1712.2.8.20.2.1.5
lcsSetupIpRouterLoadBalancerBundlePeersEntryBundlePeer4 OBJECT-TYPE
    SYNTAX     DisplayString (SIZE(0..16))
    MAX-ACCESS read-write
    STATUS     current
    DESCRIPTION
        "-- empty --"
    ::= { lcsSetupIpRouterLoadBalancerBundlePeersEntry 5 }

-- {OID} 1712.2.8.21
lcsSetupIpRouterVrrp OBJECT IDENTIFIER ::= { lcsSetupIpRouter 21 }

-- {SCALAR} 1712.2.8.21.1
lcsSetupIpRouterVrrpOperating OBJECT-TYPE
    SYNTAX     INTEGER
      {
        eNo (0),
        eYes (1)
      }
    MAX-ACCESS read-write
    STATUS     current
    DESCRIPTION
        "-- empty --"
    ::= { lcsSetupIpRouterVrrp 1 }

-- {TABLE} 1712.2.8.21.2
lcsSetupIpRouterVrrpVrrpListTable OBJECT-TYPE
    SYNTAX     SEQUENCE OF LcsSetupIpRouterVrrpVrrpListEntry
    MAX-ACCESS not-accessible
    STATUS     current
    DESCRIPTION
        "-- empty --"
    ::= { lcsSetupIpRouterVrrp 2 }

-- {ENTRY} 1712.2.8.21.2.1
lcsSetupIpRouterVrrpVrrpListEntry OBJECT-TYPE
    SYNTAX     LcsSetupIpRouterVrrpVrrpListEntry
    MAX-ACCESS not-accessible
    STATUS     current
    DESCRIPTION
        ""
    INDEX {
        lcsSetupIpRouterVrrpVrrpListEntryRouterId
    }
    ::= { lcsSetupIpRouterVrrpVrrpListTable 1 }

-- {SEQUENCE}
LcsSetupIpRouterVrrpVrrpListEntry ::= SEQUENCE {
    lcsSetupIpRouterVrrpVrrpListEntryRouterId INTEGER,
    lcsSetupIpRouterVrrpVrrpListEntryVirtAddress IpAddress,
    lcsSetupIpRouterVrrpVrrpListEntryPrio INTEGER,
    lcsSetupIpRouterVrrpVrrpListEntryBPrio INTEGER,
    lcsSetupIpRouterVrrpVrrpListEntryPeer DisplayString,
    lcsSetupIpRouterVrrpVrrpListEntryComment DisplayString
}

-- {COLUMN} 1712.2.8.21.2.1.1
lcsSetupIpRouterVrrpVrrpListEntryRouterId OBJECT-TYPE
    SYNTAX     INTEGER (0..255)
    MAX-ACCESS read-write
    STATUS     current
    DESCRIPTION
        "-- empty --"
    ::= { lcsSetupIpRouterVrrpVrrpListEntry 1 }

-- {COLUMN} 1712.2.8.21.2.1.2
lcsSetupIpRouterVrrpVrrpListEntryVirtAddress OBJECT-TYPE
    SYNTAX     IpAddress
    MAX-ACCESS read-write
    STATUS     current
    DESCRIPTION
        "-- empty --"
    ::= { lcsSetupIpRouterVrrpVrrpListEntry 2 }

-- {COLUMN} 1712.2.8.21.2.1.3
lcsSetupIpRouterVrrpVrrpListEntryPrio OBJECT-TYPE
    SYNTAX     INTEGER (0..255)
    MAX-ACCESS read-write
    STATUS     current
    DESCRIPTION
        "-- empty --"
    ::= { lcsSetupIpRouterVrrpVrrpListEntry 3 }

-- {COLUMN} 1712.2.8.21.2.1.4
lcsSetupIpRouterVrrpVrrpListEntryBPrio OBJECT-TYPE
    SYNTAX     INTEGER (0..255)
    MAX-ACCESS read-write
    STATUS     current
    DESCRIPTION
        "-- empty --"
    ::= { lcsSetupIpRouterVrrpVrrpListEntry 4 }

-- {COLUMN} 1712.2.8.21.2.1.5
lcsSetupIpRouterVrrpVrrpListEntryPeer OBJECT-TYPE
    SYNTAX     DisplayString (SIZE(0..16))
    MAX-ACCESS read-write
    STATUS     current
    DESCRIPTION
        "-- empty --"
    ::= { lcsSetupIpRouterVrrpVrrpListEntry 5 }

-- {COLUMN} 1712.2.8.21.2.1.6
lcsSetupIpRouterVrrpVrrpListEntryComment OBJECT-TYPE
    SYNTAX     DisplayString (SIZE(0..64))
    MAX-ACCESS read-write
    STATUS     current
    DESCRIPTION
        "-- empty --"
    ::= { lcsSetupIpRouterVrrpVrrpListEntry 6 }

-- {SCALAR} 1712.2.8.21.3
lcsSetupIpRouterVrrpReconnectDelay OBJECT-TYPE
    SYNTAX     INTEGER (0..65535)
    MAX-ACCESS read-write
    STATUS     current
    DESCRIPTION
        "-- empty --"
    ::= { lcsSetupIpRouterVrrp 3 }

-- {SCALAR} 1712.2.8.21.4
lcsSetupIpRouterVrrpAdvertIntervall OBJECT-TYPE
    SYNTAX     INTEGER (0..255)
    MAX-ACCESS read-write
    STATUS     current
    DESCRIPTION
        "-- empty --"
    ::= { lcsSetupIpRouterVrrp 4 }

-- {SCALAR} 1712.2.8.21.5
lcsSetupIpRouterVrrpInternalServices OBJECT-TYPE
    SYNTAX     INTEGER
      {
        eNo (0),
        eYes (1)
      }
    MAX-ACCESS read-write
    STATUS     current
    DESCRIPTION
        "-- empty --"
    ::= { lcsSetupIpRouterVrrp 5 }

-- {OID} 1712.2.8.7
lcsSetupIpRouterRoutingMethod OBJECT IDENTIFIER ::= { lcsSetupIpRouter 7 }

-- {SCALAR} 1712.2.8.7.1
lcsSetupIpRouterRoutingMethodRoutingMethod OBJECT-TYPE
    SYNTAX     INTEGER
      {
        eNormal (0),
        eTypeOfService (1),
        eDiffserv (2)
      }
    MAX-ACCESS read-write
    STATUS     current
    DESCRIPTION
        "-- empty --"
    ::= { lcsSetupIpRouterRoutingMethod 1 }

-- {SCALAR} 1712.2.8.7.2
lcsSetupIpRouterRoutingMethodIcmpRoutingMethod OBJECT-TYPE
    SYNTAX     INTEGER
      {
        eNormal (0),
        eReliable (1)
      }
    MAX-ACCESS read-write
    STATUS     current
    DESCRIPTION
        "-- empty --"
    ::= { lcsSetupIpRouterRoutingMethod 2 }

-- {SCALAR} 1712.2.8.7.3
lcsSetupIpRouterRoutingMethodSynAckSpeedup OBJECT-TYPE
    SYNTAX     INTEGER
      {
        eNo (0),
        eYes (1)
      }
    MAX-ACCESS read-write
    STATUS     current
    DESCRIPTION
        "-- empty --"
    ::= { lcsSetupIpRouterRoutingMethod 3 }

-- {SCALAR} 1712.2.8.7.4
lcsSetupIpRouterRoutingMethodL2L3Tagging OBJECT-TYPE
    SYNTAX     INTEGER
      {
        eNo (0),
        eYes (1),
        eAuto (2)
      }
    MAX-ACCESS read-write
    STATUS     current
    DESCRIPTION
        "-- empty --"
    ::= { lcsSetupIpRouterRoutingMethod 4 }

-- {SCALAR} 1712.2.8.7.5
lcsSetupIpRouterRoutingMethodL3L2Tagging OBJECT-TYPE
    SYNTAX     INTEGER
      {
        eNo (0),
        eYes (1)
      }
    MAX-ACCESS read-write
    STATUS     current
    DESCRIPTION
        "-- empty --"
    ::= { lcsSetupIpRouterRoutingMethod 5 }

-- {SCALAR} 1712.2.8.7.6
lcsSetupIpRouterRoutingMethodRouteInternalServices OBJECT-TYPE
    SYNTAX     INTEGER
      {
        eNo (0),
        eYes (1)
      }
    MAX-ACCESS read-write
    STATUS     current
    DESCRIPTION
        "-- empty --"
    ::= { lcsSetupIpRouterRoutingMethod 6 }

-- {OID} 1712.2.8.8
lcsSetupIpRouterRip OBJECT IDENTIFIER ::= { lcsSetupIpRouter 8 }

-- {TABLE} 1712.2.8.8.5
lcsSetupIpRouterRipLanSitesTable OBJECT-TYPE
    SYNTAX     SEQUENCE OF LcsSetupIpRouterRipLanSitesEntry
    MAX-ACCESS not-accessible
    STATUS     current
    DESCRIPTION
        "-- empty --"
    ::= { lcsSetupIpRouterRip 5 }

-- {ENTRY} 1712.2.8.8.5.1
lcsSetupIpRouterRipLanSitesEntry OBJECT-TYPE
    SYNTAX     LcsSetupIpRouterRipLanSitesEntry
    MAX-ACCESS not-accessible
    STATUS     current
    DESCRIPTION
        ""
    INDEX {
        lcsSetupIpRouterRipLanSitesEntryNetworkName
    }
    ::= { lcsSetupIpRouterRipLanSitesTable 1 }

-- {SEQUENCE}
LcsSetupIpRouterRipLanSitesEntry ::= SEQUENCE {
    lcsSetupIpRouterRipLanSitesEntryNetworkName DisplayString,
    lcsSetupIpRouterRipLanSitesEntryRipType INTEGER,
    lcsSetupIpRouterRipLanSitesEntryRipSend INTEGER,
    lcsSetupIpRouterRipLanSitesEntryRipAccept INTEGER,
    lcsSetupIpRouterRipLanSitesEntryPropagate INTEGER,
    lcsSetupIpRouterRipLanSitesEntryPoisonedReverse INTEGER,
    lcsSetupIpRouterRipLanSitesEntryDftRtgTag INTEGER,
    lcsSetupIpRouterRipLanSitesEntryRtgTagList DisplayString,
    lcsSetupIpRouterRipLanSitesEntryRxFilter DisplayString,
    lcsSetupIpRouterRipLanSitesEntryTxFilter DisplayString
}

-- {COLUMN} 1712.2.8.8.5.1.1
lcsSetupIpRouterRipLanSitesEntryNetworkName OBJECT-TYPE
    SYNTAX     DisplayString (SIZE(0..16))
    MAX-ACCESS read-write
    STATUS     current
    DESCRIPTION
        "-- empty --"
    ::= { lcsSetupIpRouterRipLanSitesEntry 1 }

-- {COLUMN} 1712.2.8.8.5.1.2
lcsSetupIpRouterRipLanSitesEntryRipType OBJECT-TYPE
    SYNTAX     INTEGER
      {
        eOff (0),
        eRip1 (1),
        eR1Comp (2),
        eRip2 (3)
      }
    MAX-ACCESS read-write
    STATUS     current
    DESCRIPTION
        "-- empty --"
    ::= { lcsSetupIpRouterRipLanSitesEntry 2 }

-- {COLUMN} 1712.2.8.8.5.1.12
lcsSetupIpRouterRipLanSitesEntryRipSend OBJECT-TYPE
    SYNTAX     INTEGER
      {
        eNo (0),
        eYes (1)
      }
    MAX-ACCESS read-write
    STATUS     current
    DESCRIPTION
        "-- empty --"
    ::= { lcsSetupIpRouterRipLanSitesEntry 12 }

-- {COLUMN} 1712.2.8.8.5.1.3
lcsSetupIpRouterRipLanSitesEntryRipAccept OBJECT-TYPE
    SYNTAX     INTEGER
      {
        eNo (0),
        eYes (1)
      }
    MAX-ACCESS read-write
    STATUS     current
    DESCRIPTION
        "-- empty --"
    ::= { lcsSetupIpRouterRipLanSitesEntry 3 }

-- {COLUMN} 1712.2.8.8.5.1.4
lcsSetupIpRouterRipLanSitesEntryPropagate OBJECT-TYPE
    SYNTAX     INTEGER
      {
        eNo (0),
        eYes (1)
      }
    MAX-ACCESS read-write
    STATUS     current
    DESCRIPTION
        "-- empty --"
    ::= { lcsSetupIpRouterRipLanSitesEntry 4 }

-- {COLUMN} 1712.2.8.8.5.1.7
lcsSetupIpRouterRipLanSitesEntryPoisonedReverse OBJECT-TYPE
    SYNTAX     INTEGER
      {
        eNo (0),
        eYes (1)
      }
    MAX-ACCESS read-write
    STATUS     current
    DESCRIPTION
        "-- empty --"
    ::= { lcsSetupIpRouterRipLanSitesEntry 7 }

-- {COLUMN} 1712.2.8.8.5.1.5
lcsSetupIpRouterRipLanSitesEntryDftRtgTag OBJECT-TYPE
    SYNTAX     INTEGER (0..65535)
    MAX-ACCESS read-write
    STATUS     current
    DESCRIPTION
        "-- empty --"
    ::= { lcsSetupIpRouterRipLanSitesEntry 5 }

-- {COLUMN} 1712.2.8.8.5.1.6
lcsSetupIpRouterRipLanSitesEntryRtgTagList OBJECT-TYPE
    SYNTAX     DisplayString (SIZE(0..33))
    MAX-ACCESS read-write
    STATUS     current
    DESCRIPTION
        "-- empty --"
    ::= { lcsSetupIpRouterRipLanSitesEntry 6 }

-- {COLUMN} 1712.2.8.8.5.1.10
lcsSetupIpRouterRipLanSitesEntryRxFilter OBJECT-TYPE
    SYNTAX     DisplayString (SIZE(0..16))
    MAX-ACCESS read-write
    STATUS     current
    DESCRIPTION
        "-- empty --"
    ::= { lcsSetupIpRouterRipLanSitesEntry 10 }

-- {COLUMN} 1712.2.8.8.5.1.11
lcsSetupIpRouterRipLanSitesEntryTxFilter OBJECT-TYPE
    SYNTAX     DisplayString (SIZE(0..16))
    MAX-ACCESS read-write
    STATUS     current
    DESCRIPTION
        "-- empty --"
    ::= { lcsSetupIpRouterRipLanSitesEntry 11 }

-- {TABLE} 1712.2.8.8.4
lcsSetupIpRouterRipWanSitesTable OBJECT-TYPE
    SYNTAX     SEQUENCE OF LcsSetupIpRouterRipWanSitesEntry
    MAX-ACCESS not-accessible
    STATUS     current
    DESCRIPTION
        "-- empty --"
    ::= { lcsSetupIpRouterRip 4 }

-- {ENTRY} 1712.2.8.8.4.1
lcsSetupIpRouterRipWanSitesEntry OBJECT-TYPE
    SYNTAX     LcsSetupIpRouterRipWanSitesEntry
    MAX-ACCESS not-accessible
    STATUS     current
    DESCRIPTION
        ""
    INDEX {
        lcsSetupIpRouterRipWanSitesEntryPeer
    }
    ::= { lcsSetupIpRouterRipWanSitesTable 1 }

-- {SEQUENCE}
LcsSetupIpRouterRipWanSitesEntry ::= SEQUENCE {
    lcsSetupIpRouterRipWanSitesEntryPeer DisplayString,
    lcsSetupIpRouterRipWanSitesEntryRipType INTEGER,
    lcsSetupIpRouterRipWanSitesEntryRipSend INTEGER,
    lcsSetupIpRouterRipWanSitesEntryRipAccept INTEGER,
    lcsSetupIpRouterRipWanSitesEntryMasquerade INTEGER,
    lcsSetupIpRouterRipWanSitesEntryPoisonedReverse INTEGER,
    lcsSetupIpRouterRipWanSitesEntryRfc2091 INTEGER,
    lcsSetupIpRouterRipWanSitesEntryGateway IpAddress,
    lcsSetupIpRouterRipWanSitesEntryDftRtgTag INTEGER,
    lcsSetupIpRouterRipWanSitesEntryRtgTagList DisplayString,
    lcsSetupIpRouterRipWanSitesEntryRxFilter DisplayString,
    lcsSetupIpRouterRipWanSitesEntryTxFilter DisplayString
}

-- {COLUMN} 1712.2.8.8.4.1.1
lcsSetupIpRouterRipWanSitesEntryPeer OBJECT-TYPE
    SYNTAX     DisplayString (SIZE(0..16))
    MAX-ACCESS read-write
    STATUS     current
    DESCRIPTION
        "-- empty --"
    ::= { lcsSetupIpRouterRipWanSitesEntry 1 }

-- {COLUMN} 1712.2.8.8.4.1.2
lcsSetupIpRouterRipWanSitesEntryRipType OBJECT-TYPE
    SYNTAX     INTEGER
      {
        eOff (0),
        eRip1 (1),
        eR1Comp (2),
        eRip2 (3)
      }
    MAX-ACCESS read-write
    STATUS     current
    DESCRIPTION
        "-- empty --"
    ::= { lcsSetupIpRouterRipWanSitesEntry 2 }

-- {COLUMN} 1712.2.8.8.4.1.12
lcsSetupIpRouterRipWanSitesEntryRipSend OBJECT-TYPE
    SYNTAX     INTEGER
      {
        eNo (0),
        eYes (1)
      }
    MAX-ACCESS read-write
    STATUS     current
    DESCRIPTION
        "-- empty --"
    ::= { lcsSetupIpRouterRipWanSitesEntry 12 }

-- {COLUMN} 1712.2.8.8.4.1.3
lcsSetupIpRouterRipWanSitesEntryRipAccept OBJECT-TYPE
    SYNTAX     INTEGER
      {
        eNo (0),
        eYes (1)
      }
    MAX-ACCESS read-write
    STATUS     current
    DESCRIPTION
        "-- empty --"
    ::= { lcsSetupIpRouterRipWanSitesEntry 3 }

-- {COLUMN} 1712.2.8.8.4.1.4
lcsSetupIpRouterRipWanSitesEntryMasquerade OBJECT-TYPE
    SYNTAX     INTEGER
      {
        eAuto (0),
        eOn (1),
        eIntranet (2)
      }
    MAX-ACCESS read-write
    STATUS     current
    DESCRIPTION
        "-- empty --"
    ::= { lcsSetupIpRouterRipWanSitesEntry 4 }

-- {COLUMN} 1712.2.8.8.4.1.7
lcsSetupIpRouterRipWanSitesEntryPoisonedReverse OBJECT-TYPE
    SYNTAX     INTEGER
      {
        eNo (0),
        eYes (1)
      }
    MAX-ACCESS read-write
    STATUS     current
    DESCRIPTION
        "-- empty --"
    ::= { lcsSetupIpRouterRipWanSitesEntry 7 }

-- {COLUMN} 1712.2.8.8.4.1.8
lcsSetupIpRouterRipWanSitesEntryRfc2091 OBJECT-TYPE
    SYNTAX     INTEGER
      {
        eNo (0),
        eYes (1)
      }
    MAX-ACCESS read-write
    STATUS     current
    DESCRIPTION
        "-- empty --"
    ::= { lcsSetupIpRouterRipWanSitesEntry 8 }

-- {COLUMN} 1712.2.8.8.4.1.9
lcsSetupIpRouterRipWanSitesEntryGateway OBJECT-TYPE
    SYNTAX     IpAddress
    MAX-ACCESS read-write
    STATUS     current
    DESCRIPTION
        "-- empty --"
    ::= { lcsSetupIpRouterRipWanSitesEntry 9 }

-- {COLUMN} 1712.2.8.8.4.1.5
lcsSetupIpRouterRipWanSitesEntryDftRtgTag OBJECT-TYPE
    SYNTAX     INTEGER (0..65535)
    MAX-ACCESS read-write
    STATUS     current
    DESCRIPTION
        "-- empty --"
    ::= { lcsSetupIpRouterRipWanSitesEntry 5 }

-- {COLUMN} 1712.2.8.8.4.1.6
lcsSetupIpRouterRipWanSitesEntryRtgTagList OBJECT-TYPE
    SYNTAX     DisplayString (SIZE(0..33))
    MAX-ACCESS read-write
    STATUS     current
    DESCRIPTION
        "-- empty --"
    ::= { lcsSetupIpRouterRipWanSitesEntry 6 }

-- {COLUMN} 1712.2.8.8.4.1.10
lcsSetupIpRouterRipWanSitesEntryRxFilter OBJECT-TYPE
    SYNTAX     DisplayString (SIZE(0..16))
    MAX-ACCESS read-write
    STATUS     current
    DESCRIPTION
        "-- empty --"
    ::= { lcsSetupIpRouterRipWanSitesEntry 10 }

-- {COLUMN} 1712.2.8.8.4.1.11
lcsSetupIpRouterRipWanSitesEntryTxFilter OBJECT-TYPE
    SYNTAX     DisplayString (SIZE(0..16))
    MAX-ACCESS read-write
    STATUS     current
    DESCRIPTION
        "-- empty --"
    ::= { lcsSetupIpRouterRipWanSitesEntry 11 }

-- {SCALAR} 1712.2.8.8.2
lcsSetupIpRouterRipR1Mask OBJECT-TYPE
    SYNTAX     INTEGER
      {
        eClass (0),
        eAddress (1),
        eClPlusAddr (2)
      }
    MAX-ACCESS read-write
    STATUS     current
    DESCRIPTION
        "-- empty --"
    ::= { lcsSetupIpRouterRip 2 }

-- {TABLE} 1712.2.8.8.7
lcsSetupIpRouterRipFilterTable OBJECT-TYPE
    SYNTAX     SEQUENCE OF LcsSetupIpRouterRipFilterEntry
    MAX-ACCESS not-accessible
    STATUS     current
    DESCRIPTION
        "-- empty --"
    ::= { lcsSetupIpRouterRip 7 }

-- {ENTRY} 1712.2.8.8.7.1
lcsSetupIpRouterRipFilterEntry OBJECT-TYPE
    SYNTAX     LcsSetupIpRouterRipFilterEntry
    MAX-ACCESS not-accessible
    STATUS     current
    DESCRIPTION
        ""
    INDEX {
        lcsSetupIpRouterRipFilterEntryName
    }
    ::= { lcsSetupIpRouterRipFilterTable 1 }

-- {SEQUENCE}
LcsSetupIpRouterRipFilterEntry ::= SEQUENCE {
    lcsSetupIpRouterRipFilterEntryName DisplayString,
    lcsSetupIpRouterRipFilterEntryFilter DisplayString
}

-- {COLUMN} 1712.2.8.8.7.1.1
lcsSetupIpRouterRipFilterEntryName OBJECT-TYPE
    SYNTAX     DisplayString (SIZE(0..18))
    MAX-ACCESS read-write
    STATUS     current
    DESCRIPTION
        "-- empty --"
    ::= { lcsSetupIpRouterRipFilterEntry 1 }

-- {COLUMN} 1712.2.8.8.7.1.2
lcsSetupIpRouterRipFilterEntryFilter OBJECT-TYPE
    SYNTAX     DisplayString (SIZE(0..64))
    MAX-ACCESS read-write
    STATUS     current
    DESCRIPTION
        "-- empty --"
    ::= { lcsSetupIpRouterRipFilterEntry 2 }

-- {OID} 1712.2.8.8.6
lcsSetupIpRouterRipParameter OBJECT IDENTIFIER ::= { lcsSetupIpRouterRip 6 }

-- {SCALAR} 1712.2.8.8.6.1
lcsSetupIpRouterRipParameterUpdate OBJECT-TYPE
    SYNTAX     INTEGER (0..255)
    MAX-ACCESS read-write
    STATUS     current
    DESCRIPTION
        "-- empty --"
    ::= { lcsSetupIpRouterRipParameter 1 }

-- {SCALAR} 1712.2.8.8.6.2
lcsSetupIpRouterRipParameterHolddown OBJECT-TYPE
    SYNTAX     INTEGER (0..255)
    MAX-ACCESS read-write
    STATUS     current
    DESCRIPTION
        "-- empty --"
    ::= { lcsSetupIpRouterRipParameter 2 }

-- {SCALAR} 1712.2.8.8.6.3
lcsSetupIpRouterRipParameterInvalidate OBJECT-TYPE
    SYNTAX     INTEGER (0..255)
    MAX-ACCESS read-write
    STATUS     current
    DESCRIPTION
        "-- empty --"
    ::= { lcsSetupIpRouterRipParameter 3 }

-- {SCALAR} 1712.2.8.8.6.4
lcsSetupIpRouterRipParameterFlush OBJECT-TYPE
    SYNTAX     INTEGER (0..255)
    MAX-ACCESS read-write
    STATUS     current
    DESCRIPTION
        "-- empty --"
    ::= { lcsSetupIpRouterRipParameter 4 }

-- {SCALAR} 1712.2.8.8.6.5
lcsSetupIpRouterRipParameterUpdDelay OBJECT-TYPE
    SYNTAX     INTEGER (0..255)
    MAX-ACCESS read-write
    STATUS     current
    DESCRIPTION
        "-- empty --"
    ::= { lcsSetupIpRouterRipParameter 5 }

-- {SCALAR} 1712.2.8.8.6.6
lcsSetupIpRouterRipParameterMaxHopcount OBJECT-TYPE
    SYNTAX     INTEGER (0..255)
    MAX-ACCESS read-write
    STATUS     current
    DESCRIPTION
        "-- empty --"
    ::= { lcsSetupIpRouterRipParameter 6 }

-- {SCALAR} 1712.2.8.8.6.7
lcsSetupIpRouterRipParameterRoutesPerFrame OBJECT-TYPE
    SYNTAX     INTEGER (0..255)
    MAX-ACCESS read-write
    STATUS     current
    DESCRIPTION
        "-- empty --"
    ::= { lcsSetupIpRouterRipParameter 7 }

-- {SCALAR} 1712.2.8.8.6.8
lcsSetupIpRouterRipParameterInterPacketDelay OBJECT-TYPE
    SYNTAX     INTEGER (0..255)
    MAX-ACCESS read-write
    STATUS     current
    DESCRIPTION
        "-- empty --"
    ::= { lcsSetupIpRouterRipParameter 8 }

-- {TABLE} 1712.2.8.8.8
lcsSetupIpRouterRipBestRoutesTable OBJECT-TYPE
    SYNTAX     SEQUENCE OF LcsSetupIpRouterRipBestRoutesEntry
    MAX-ACCESS not-accessible
    STATUS     current
    DESCRIPTION
        "-- empty --"
    ::= { lcsSetupIpRouterRip 8 }

-- {ENTRY} 1712.2.8.8.8.1
lcsSetupIpRouterRipBestRoutesEntry OBJECT-TYPE
    SYNTAX     LcsSetupIpRouterRipBestRoutesEntry
    MAX-ACCESS not-accessible
    STATUS     current
    DESCRIPTION
        ""
    INDEX {
        lcsSetupIpRouterRipBestRoutesEntryIpAddress,
        lcsSetupIpRouterRipBestRoutesEntryIpNetmask,
        lcsSetupIpRouterRipBestRoutesEntryRtgTag,
        lcsSetupIpRouterRipBestRoutesEntryGateway
    }
    ::= { lcsSetupIpRouterRipBestRoutesTable 1 }

-- {SEQUENCE}
LcsSetupIpRouterRipBestRoutesEntry ::= SEQUENCE {
    lcsSetupIpRouterRipBestRoutesEntryIpAddress IpAddress,
    lcsSetupIpRouterRipBestRoutesEntryIpNetmask IpAddress,
    lcsSetupIpRouterRipBestRoutesEntryRtgTag INTEGER,
    lcsSetupIpRouterRipBestRoutesEntryGateway IpAddress,
    lcsSetupIpRouterRipBestRoutesEntryDistance INTEGER,
    lcsSetupIpRouterRipBestRoutesEntryTime INTEGER,
    lcsSetupIpRouterRipBestRoutesEntryPeer DisplayString,
    lcsSetupIpRouterRipBestRoutesEntryPort INTEGER,
    lcsSetupIpRouterRipBestRoutesEntryVlanId INTEGER,
    lcsSetupIpRouterRipBestRoutesEntryNetworkName DisplayString
}

-- {COLUMN} 1712.2.8.8.8.1.1
lcsSetupIpRouterRipBestRoutesEntryIpAddress OBJECT-TYPE
    SYNTAX     IpAddress
    MAX-ACCESS read-only
    STATUS     current
    DESCRIPTION
        "-- empty --"
    ::= { lcsSetupIpRouterRipBestRoutesEntry 1 }

-- {COLUMN} 1712.2.8.8.8.1.2
lcsSetupIpRouterRipBestRoutesEntryIpNetmask OBJECT-TYPE
    SYNTAX     IpAddress
    MAX-ACCESS read-only
    STATUS     current
    DESCRIPTION
        "-- empty --"
    ::= { lcsSetupIpRouterRipBestRoutesEntry 2 }

-- {COLUMN} 1712.2.8.8.8.1.6
lcsSetupIpRouterRipBestRoutesEntryRtgTag OBJECT-TYPE
    SYNTAX     INTEGER (0..65535)
    MAX-ACCESS read-only
    STATUS     current
    DESCRIPTION
        "-- empty --"
    ::= { lcsSetupIpRouterRipBestRoutesEntry 6 }

-- {COLUMN} 1712.2.8.8.8.1.5
lcsSetupIpRouterRipBestRoutesEntryGateway OBJECT-TYPE
    SYNTAX     IpAddress
    MAX-ACCESS read-only
    STATUS     current
    DESCRIPTION
        "-- empty --"
    ::= { lcsSetupIpRouterRipBestRoutesEntry 5 }

-- {COLUMN} 1712.2.8.8.8.1.4
lcsSetupIpRouterRipBestRoutesEntryDistance OBJECT-TYPE
    SYNTAX     INTEGER (0..65535)
    MAX-ACCESS read-only
    STATUS     current
    DESCRIPTION
        "-- empty --"
    ::= { lcsSetupIpRouterRipBestRoutesEntry 4 }

-- {COLUMN} 1712.2.8.8.8.1.3
lcsSetupIpRouterRipBestRoutesEntryTime OBJECT-TYPE
    SYNTAX     INTEGER (0..65535)
    MAX-ACCESS read-only
    STATUS     current
    DESCRIPTION
        "-- empty --"
    ::= { lcsSetupIpRouterRipBestRoutesEntry 3 }

-- {COLUMN} 1712.2.8.8.8.1.8
lcsSetupIpRouterRipBestRoutesEntryPeer OBJECT-TYPE
    SYNTAX     DisplayString (SIZE(0..255))
    MAX-ACCESS read-only
    STATUS     current
    DESCRIPTION
        "-- empty --"
    ::= { lcsSetupIpRouterRipBestRoutesEntry 8 }

-- {COLUMN} 1712.2.8.8.8.1.12
lcsSetupIpRouterRipBestRoutesEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsSetupIpRouterRipBestRoutesEntry 12 }

-- {COLUMN} 1712.2.8.8.8.1.10
lcsSetupIpRouterRipBestRoutesEntryVlanId OBJECT-TYPE
    SYNTAX     INTEGER (0..65535)
    MAX-ACCESS read-only
    STATUS     current
    DESCRIPTION
        "-- empty --"
    ::= { lcsSetupIpRouterRipBestRoutesEntry 10 }

-- {COLUMN} 1712.2.8.8.8.1.11
lcsSetupIpRouterRipBestRoutesEntryNetworkName OBJECT-TYPE
    SYNTAX     DisplayString (SIZE(0..255))
    MAX-ACCESS read-only
    STATUS     current
    DESCRIPTION
        "-- empty --"
    ::= { lcsSetupIpRouterRipBestRoutesEntry 11 }

-- {TABLE} 1712.2.8.8.9
lcsSetupIpRouterRipAllRoutesTable OBJECT-TYPE
    SYNTAX     SEQUENCE OF LcsSetupIpRouterRipAllRoutesEntry
    MAX-ACCESS not-accessible
    STATUS     current
    DESCRIPTION
        "-- empty --"
    ::= { lcsSetupIpRouterRip 9 }

-- {ENTRY} 1712.2.8.8.9.1
lcsSetupIpRouterRipAllRoutesEntry OBJECT-TYPE
    SYNTAX     LcsSetupIpRouterRipAllRoutesEntry
    MAX-ACCESS not-accessible
    STATUS     current
    DESCRIPTION
        ""
    INDEX {
        lcsSetupIpRouterRipAllRoutesEntryIpAddress,
        lcsSetupIpRouterRipAllRoutesEntryIpNetmask,
        lcsSetupIpRouterRipAllRoutesEntryRtgTag,
        lcsSetupIpRouterRipAllRoutesEntryGateway
    }
    ::= { lcsSetupIpRouterRipAllRoutesTable 1 }

-- {SEQUENCE}
LcsSetupIpRouterRipAllRoutesEntry ::= SEQUENCE {
    lcsSetupIpRouterRipAllRoutesEntryIpAddress IpAddress,
    lcsSetupIpRouterRipAllRoutesEntryIpNetmask IpAddress,
    lcsSetupIpRouterRipAllRoutesEntryRtgTag INTEGER,
    lcsSetupIpRouterRipAllRoutesEntryGateway IpAddress,
    lcsSetupIpRouterRipAllRoutesEntryDistance INTEGER,
    lcsSetupIpRouterRipAllRoutesEntryTime INTEGER,
    lcsSetupIpRouterRipAllRoutesEntryPeer DisplayString,
    lcsSetupIpRouterRipAllRoutesEntryPort INTEGER,
    lcsSetupIpRouterRipAllRoutesEntryVlanId INTEGER,
    lcsSetupIpRouterRipAllRoutesEntryNetworkName DisplayString
}

-- {COLUMN} 1712.2.8.8.9.1.1
lcsSetupIpRouterRipAllRoutesEntryIpAddress OBJECT-TYPE
    SYNTAX     IpAddress
    MAX-ACCESS read-only
    STATUS     current
    DESCRIPTION
        "-- empty --"
    ::= { lcsSetupIpRouterRipAllRoutesEntry 1 }

-- {COLUMN} 1712.2.8.8.9.1.2
lcsSetupIpRouterRipAllRoutesEntryIpNetmask OBJECT-TYPE
    SYNTAX     IpAddress
    MAX-ACCESS read-only
    STATUS     current
    DESCRIPTION
        "-- empty --"
    ::= { lcsSetupIpRouterRipAllRoutesEntry 2 }

-- {COLUMN} 1712.2.8.8.9.1.6
lcsSetupIpRouterRipAllRoutesEntryRtgTag OBJECT-TYPE
    SYNTAX     INTEGER (0..65535)
    MAX-ACCESS read-only
    STATUS     current
    DESCRIPTION
        "-- empty --"
    ::= { lcsSetupIpRouterRipAllRoutesEntry 6 }

-- {COLUMN} 1712.2.8.8.9.1.5
lcsSetupIpRouterRipAllRoutesEntryGateway OBJECT-TYPE
    SYNTAX     IpAddress
    MAX-ACCESS read-only
    STATUS     current
    DESCRIPTION
        "-- empty --"
    ::= { lcsSetupIpRouterRipAllRoutesEntry 5 }

-- {COLUMN} 1712.2.8.8.9.1.4
lcsSetupIpRouterRipAllRoutesEntryDistance OBJECT-TYPE
    SYNTAX     INTEGER (0..65535)
    MAX-ACCESS read-only
    STATUS     current
    DESCRIPTION
        "-- empty --"
    ::= { lcsSetupIpRouterRipAllRoutesEntry 4 }

-- {COLUMN} 1712.2.8.8.9.1.3
lcsSetupIpRouterRipAllRoutesEntryTime OBJECT-TYPE
    SYNTAX     INTEGER (0..65535)
    MAX-ACCESS read-only
    STATUS     current
    DESCRIPTION
        "-- empty --"
    ::= { lcsSetupIpRouterRipAllRoutesEntry 3 }

-- {COLUMN} 1712.2.8.8.9.1.8
lcsSetupIpRouterRipAllRoutesEntryPeer OBJECT-TYPE
    SYNTAX     DisplayString (SIZE(0..255))
    MAX-ACCESS read-only
    STATUS     current
    DESCRIPTION
        "-- empty --"
    ::= { lcsSetupIpRouterRipAllRoutesEntry 8 }

-- {COLUMN} 1712.2.8.8.9.1.12
lcsSetupIpRouterRipAllRoutesEntryPort OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsSetupIpRouterRipAllRoutesEntry 12 }

-- {COLUMN} 1712.2.8.8.9.1.10
lcsSetupIpRouterRipAllRoutesEntryVlanId OBJECT-TYPE
    SYNTAX     INTEGER (0..65535)
    MAX-ACCESS read-only
    STATUS     current
    DESCRIPTION
        "-- empty --"
    ::= { lcsSetupIpRouterRipAllRoutesEntry 10 }

-- {COLUMN} 1712.2.8.8.9.1.11
lcsSetupIpRouterRipAllRoutesEntryNetworkName OBJECT-TYPE
    SYNTAX     DisplayString (SIZE(0..255))
    MAX-ACCESS read-only
    STATUS     current
    DESCRIPTION
        "-- empty --"
    ::= { lcsSetupIpRouterRipAllRoutesEntry 11 }

-- {OID} 1712.2.8.9
lcsSetupIpRouter1NNat OBJECT IDENTIFIER ::= { lcsSetupIpRouter 9 }

-- {SCALAR} 1712.2.8.9.1
lcsSetupIpRouter1NNatTcpAgingSeconds OBJECT-TYPE
    SYNTAX     INTEGER (0..65535)
    MAX-ACCESS read-write
    STATUS     current
    DESCRIPTION
        "-- empty --"
    ::= { lcsSetupIpRouter1NNat 1 }

-- {SCALAR} 1712.2.8.9.2
lcsSetupIpRouter1NNatUdpAgingSeconds OBJECT-TYPE
    SYNTAX     INTEGER (0..65535)
    MAX-ACCESS read-write
    STATUS     current
    DESCRIPTION
        "-- empty --"
    ::= { lcsSetupIpRouter1NNat 2 }

-- {SCALAR} 1712.2.8.9.3
lcsSetupIpRouter1NNatIcmpAgingSeconds OBJECT-TYPE
    SYNTAX     INTEGER (0..65535)
    MAX-ACCESS read-write
    STATUS     current
    DESCRIPTION
        "-- empty --"
    ::= { lcsSetupIpRouter1NNat 3 }

-- {TABLE} 1712.2.8.9.4
lcsSetupIpRouter1NNatServiceTableTable OBJECT-TYPE
    SYNTAX     SEQUENCE OF LcsSetupIpRouter1NNatServiceTableEntry
    MAX-ACCESS not-accessible
    STATUS     current
    DESCRIPTION
        "-- empty --"
    ::= { lcsSetupIpRouter1NNat 4 }

-- {ENTRY} 1712.2.8.9.4.1
lcsSetupIpRouter1NNatServiceTableEntry OBJECT-TYPE
    SYNTAX     LcsSetupIpRouter1NNatServiceTableEntry
    MAX-ACCESS not-accessible
    STATUS     current
    DESCRIPTION
        ""
    INDEX {
        lcsSetupIpRouter1NNatServiceTableEntryDPortFrom,
        lcsSetupIpRouter1NNatServiceTableEntryDPortTo,
        lcsSetupIpRouter1NNatServiceTableEntryProtocol,
        lcsSetupIpRouter1NNatServiceTableEntryPeer,
        lcsSetupIpRouter1NNatServiceTableEntryWanAddress
    }
    ::= { lcsSetupIpRouter1NNatServiceTableTable 1 }

-- {SEQUENCE}
LcsSetupIpRouter1NNatServiceTableEntry ::= SEQUENCE {
    lcsSetupIpRouter1NNatServiceTableEntryDPortFrom INTEGER,
    lcsSetupIpRouter1NNatServiceTableEntryDPortTo INTEGER,
    lcsSetupIpRouter1NNatServiceTableEntryProtocol INTEGER,
    lcsSetupIpRouter1NNatServiceTableEntryPeer DisplayString,
    lcsSetupIpRouter1NNatServiceTableEntryWanAddress IpAddress,
    lcsSetupIpRouter1NNatServiceTableEntryIntranetAddress IpAddress,
    lcsSetupIpRouter1NNatServiceTableEntryMapPort INTEGER,
    lcsSetupIpRouter1NNatServiceTableEntryActive INTEGER,
    lcsSetupIpRouter1NNatServiceTableEntryComment DisplayString
}

-- {COLUMN} 1712.2.8.9.4.1.1
lcsSetupIpRouter1NNatServiceTableEntryDPortFrom OBJECT-TYPE
    SYNTAX     INTEGER (0..65535)
    MAX-ACCESS read-write
    STATUS     current
    DESCRIPTION
        "-- empty --"
    ::= { lcsSetupIpRouter1NNatServiceTableEntry 1 }

-- {COLUMN} 1712.2.8.9.4.1.3
lcsSetupIpRouter1NNatServiceTableEntryDPortTo OBJECT-TYPE
    SYNTAX     INTEGER (0..65535)
    MAX-ACCESS read-write
    STATUS     current
    DESCRIPTION
        "-- empty --"
    ::= { lcsSetupIpRouter1NNatServiceTableEntry 3 }

-- {COLUMN} 1712.2.8.9.4.1.8
lcsSetupIpRouter1NNatServiceTableEntryProtocol OBJECT-TYPE
    SYNTAX     INTEGER
      {
        eTcp (1),
        eUdp (2),
        eTcpPlusUdp (0)
      }
    MAX-ACCESS read-write
    STATUS     current
    DESCRIPTION
        "-- empty --"
    ::= { lcsSetupIpRouter1NNatServiceTableEntry 8 }

-- {COLUMN} 1712.2.8.9.4.1.7
lcsSetupIpRouter1NNatServiceTableEntryPeer OBJECT-TYPE
    SYNTAX     DisplayString (SIZE(0..16))
    MAX-ACCESS read-write
    STATUS     current
    DESCRIPTION
        "-- empty --"
    ::= { lcsSetupIpRouter1NNatServiceTableEntry 7 }

-- {COLUMN} 1712.2.8.9.4.1.9
lcsSetupIpRouter1NNatServiceTableEntryWanAddress OBJECT-TYPE
    SYNTAX     IpAddress
    MAX-ACCESS read-write
    STATUS     current
    DESCRIPTION
        "-- empty --"
    ::= { lcsSetupIpRouter1NNatServiceTableEntry 9 }

-- {COLUMN} 1712.2.8.9.4.1.2
lcsSetupIpRouter1NNatServiceTableEntryIntranetAddress OBJECT-TYPE
    SYNTAX     IpAddress
    MAX-ACCESS read-write
    STATUS     current
    DESCRIPTION
        "-- empty --"
    ::= { lcsSetupIpRouter1NNatServiceTableEntry 2 }

-- {COLUMN} 1712.2.8.9.4.1.4
lcsSetupIpRouter1NNatServiceTableEntryMapPort OBJECT-TYPE
    SYNTAX     INTEGER (0..65535)
    MAX-ACCESS read-write
    STATUS     current
    DESCRIPTION
        "-- empty --"
    ::= { lcsSetupIpRouter1NNatServiceTableEntry 4 }

-- {COLUMN} 1712.2.8.9.4.1.5
lcsSetupIpRouter1NNatServiceTableEntryActive OBJECT-TYPE
    SYNTAX     INTEGER
      {
        eNo (1),
        eYes (0)
      }
    MAX-ACCESS read-write
    STATUS     current
    DESCRIPTION
        "-- empty --"
    ::= { lcsSetupIpRouter1NNatServiceTableEntry 5 }

-- {COLUMN} 1712.2.8.9.4.1.6
lcsSetupIpRouter1NNatServiceTableEntryComment OBJECT-TYPE
    SYNTAX     DisplayString (SIZE(0..64))
    MAX-ACCESS read-write
    STATUS     current
    DESCRIPTION
        "-- empty --"
    ::= { lcsSetupIpRouter1NNatServiceTableEntry 6 }

-- {TABLE} 1712.2.8.9.5
lcsSetupIpRouter1NNatTable1NNatTable OBJECT-TYPE
    SYNTAX     SEQUENCE OF LcsSetupIpRouter1NNatTable1NNatEntry
    MAX-ACCESS not-accessible
    STATUS     current
    DESCRIPTION
        "-- empty --"
    ::= { lcsSetupIpRouter1NNat 5 }

-- {ENTRY} 1712.2.8.9.5.1
lcsSetupIpRouter1NNatTable1NNatEntry OBJECT-TYPE
    SYNTAX     LcsSetupIpRouter1NNatTable1NNatEntry
    MAX-ACCESS not-accessible
    STATUS     current
    DESCRIPTION
        ""
    INDEX {
        lcsSetupIpRouter1NNatTable1NNatEntryIntranetAddress
    }
    ::= { lcsSetupIpRouter1NNatTable1NNatTable 1 }

-- {SEQUENCE}
LcsSetupIpRouter1NNatTable1NNatEntry ::= SEQUENCE {
    lcsSetupIpRouter1NNatTable1NNatEntryIntranetAddress IpAddress,
    lcsSetupIpRouter1NNatTable1NNatEntrySourcePort INTEGER,
    lcsSetupIpRouter1NNatTable1NNatEntryProtocol INTEGER,
    lcsSetupIpRouter1NNatTable1NNatEntryTimeout INTEGER,
    lcsSetupIpRouter1NNatTable1NNatEntryHandler DisplayString,
    lcsSetupIpRouter1NNatTable1NNatEntryRemoteAddress IpAddress
}

-- {COLUMN} 1712.2.8.9.5.1.1
lcsSetupIpRouter1NNatTable1NNatEntryIntranetAddress OBJECT-TYPE
    SYNTAX     IpAddress
    MAX-ACCESS read-only
    STATUS     current
    DESCRIPTION
        "-- empty --"
    ::= { lcsSetupIpRouter1NNatTable1NNatEntry 1 }

-- {COLUMN} 1712.2.8.9.5.1.2
lcsSetupIpRouter1NNatTable1NNatEntrySourcePort OBJECT-TYPE
    SYNTAX     INTEGER (0..65535)
    MAX-ACCESS read-only
    STATUS     current
    DESCRIPTION
        "-- empty --"
    ::= { lcsSetupIpRouter1NNatTable1NNatEntry 2 }

-- {COLUMN} 1712.2.8.9.5.1.3
lcsSetupIpRouter1NNatTable1NNatEntryProtocol OBJECT-TYPE
    SYNTAX     INTEGER
      {
        eTcp (6),
        eUdp (17),
        eIcmp (1)
      }
    MAX-ACCESS read-only
    STATUS     current
    DESCRIPTION
        "-- empty --"
    ::= { lcsSetupIpRouter1NNatTable1NNatEntry 3 }

-- {COLUMN} 1712.2.8.9.5.1.4
lcsSetupIpRouter1NNatTable1NNatEntryTimeout OBJECT-TYPE
    SYNTAX     INTEGER (0..65535)
    MAX-ACCESS read-only
    STATUS     current
    DESCRIPTION
        "-- empty --"
    ::= { lcsSetupIpRouter1NNatTable1NNatEntry 4 }

-- {COLUMN} 1712.2.8.9.5.1.5
lcsSetupIpRouter1NNatTable1NNatEntryHandler OBJECT-TYPE
    SYNTAX     DisplayString (SIZE(0..255))
    MAX-ACCESS read-only
    STATUS     current
    DESCRIPTION
        "-- empty --"
    ::= { lcsSetupIpRouter1NNatTable1NNatEntry 5 }

-- {COLUMN} 1712.2.8.9.5.1.6
lcsSetupIpRouter1NNatTable1NNatEntryRemoteAddress OBJECT-TYPE
    SYNTAX     IpAddress
    MAX-ACCESS read-only
    STATUS     current
    DESCRIPTION
        "-- empty --"
    ::= { lcsSetupIpRouter1NNatTable1NNatEntry 6 }

-- {SCALAR} 1712.2.8.9.6
lcsSetupIpRouter1NNatFragments OBJECT-TYPE
    SYNTAX     INTEGER
      {
        eFilter (0),
        eRoute (1),
        eReassemble (2)
      }
    MAX-ACCESS read-write
    STATUS     current
    DESCRIPTION
        "-- empty --"
    ::= { lcsSetupIpRouter1NNat 6 }

-- {SCALAR} 1712.2.8.9.7
lcsSetupIpRouter1NNatFragmentAgingSeconds OBJECT-TYPE
    SYNTAX     INTEGER (0..255)
    MAX-ACCESS read-write
    STATUS     current
    DESCRIPTION
        "-- empty --"
    ::= { lcsSetupIpRouter1NNat 7 }

-- {SCALAR} 1712.2.8.9.8
lcsSetupIpRouter1NNatIpsecAgingSeconds OBJECT-TYPE
    SYNTAX     INTEGER (0..65535)
    MAX-ACCESS read-write
    STATUS     current
    DESCRIPTION
        "-- empty --"
    ::= { lcsSetupIpRouter1NNat 8 }

-- {TABLE} 1712.2.8.9.9
lcsSetupIpRouter1NNatIpsecTableTable OBJECT-TYPE
    SYNTAX     SEQUENCE OF LcsSetupIpRouter1NNatIpsecTableEntry
    MAX-ACCESS not-accessible
    STATUS     current
    DESCRIPTION
        "-- empty --"
    ::= { lcsSetupIpRouter1NNat 9 }

-- {ENTRY} 1712.2.8.9.9.1
lcsSetupIpRouter1NNatIpsecTableEntry OBJECT-TYPE
    SYNTAX     LcsSetupIpRouter1NNatIpsecTableEntry
    MAX-ACCESS not-accessible
    STATUS     current
    DESCRIPTION
        ""
    INDEX {
        lcsSetupIpRouter1NNatIpsecTableEntryRemoteAddress
    }
    ::= { lcsSetupIpRouter1NNatIpsecTableTable 1 }

-- {SEQUENCE}
LcsSetupIpRouter1NNatIpsecTableEntry ::= SEQUENCE {
    lcsSetupIpRouter1NNatIpsecTableEntryRemoteAddress IpAddress,
    lcsSetupIpRouter1NNatIpsecTableEntryLocalAddress IpAddress,
    lcsSetupIpRouter1NNatIpsecTableEntryRcHi DisplayString,
    lcsSetupIpRouter1NNatIpsecTableEntryRcLo DisplayString,
    lcsSetupIpRouter1NNatIpsecTableEntryLcHi DisplayString,
    lcsSetupIpRouter1NNatIpsecTableEntryLcLo DisplayString,
    lcsSetupIpRouter1NNatIpsecTableEntryRemoteSpi DisplayString,
    lcsSetupIpRouter1NNatIpsecTableEntryLocalSpi DisplayString,
    lcsSetupIpRouter1NNatIpsecTableEntryTimeout INTEGER,
    lcsSetupIpRouter1NNatIpsecTableEntryCo INTEGER,
    lcsSetupIpRouter1NNatIpsecTableEntryNl INTEGER,
    lcsSetupIpRouter1NNatIpsecTableEntryNr INTEGER,
    lcsSetupIpRouter1NNatIpsecTableEntryDp INTEGER,
    lcsSetupIpRouter1NNatIpsecTableEntryFlags DisplayString
}

-- {COLUMN} 1712.2.8.9.9.1.1
lcsSetupIpRouter1NNatIpsecTableEntryRemoteAddress OBJECT-TYPE
    SYNTAX     IpAddress
    MAX-ACCESS read-only
    STATUS     current
    DESCRIPTION
        "-- empty --"
    ::= { lcsSetupIpRouter1NNatIpsecTableEntry 1 }

-- {COLUMN} 1712.2.8.9.9.1.2
lcsSetupIpRouter1NNatIpsecTableEntryLocalAddress OBJECT-TYPE
    SYNTAX     IpAddress
    MAX-ACCESS read-only
    STATUS     current
    DESCRIPTION
        "-- empty --"
    ::= { lcsSetupIpRouter1NNatIpsecTableEntry 2 }

-- {COLUMN} 1712.2.8.9.9.1.3
lcsSetupIpRouter1NNatIpsecTableEntryRcHi OBJECT-TYPE
    SYNTAX     DisplayString (SIZE(0..8))
    MAX-ACCESS read-only
    STATUS     current
    DESCRIPTION
        "-- empty --"
    ::= { lcsSetupIpRouter1NNatIpsecTableEntry 3 }

-- {COLUMN} 1712.2.8.9.9.1.4
lcsSetupIpRouter1NNatIpsecTableEntryRcLo OBJECT-TYPE
    SYNTAX     DisplayString (SIZE(0..8))
    MAX-ACCESS read-only
    STATUS     current
    DESCRIPTION
        "-- empty --"
    ::= { lcsSetupIpRouter1NNatIpsecTableEntry 4 }

-- {COLUMN} 1712.2.8.9.9.1.5
lcsSetupIpRouter1NNatIpsecTableEntryLcHi OBJECT-TYPE
    SYNTAX     DisplayString (SIZE(0..8))
    MAX-ACCESS read-only
    STATUS     current
    DESCRIPTION
        "-- empty --"
    ::= { lcsSetupIpRouter1NNatIpsecTableEntry 5 }

-- {COLUMN} 1712.2.8.9.9.1.6
lcsSetupIpRouter1NNatIpsecTableEntryLcLo OBJECT-TYPE
    SYNTAX     DisplayString (SIZE(0..8))
    MAX-ACCESS read-only
    STATUS     current
    DESCRIPTION
        "-- empty --"
    ::= { lcsSetupIpRouter1NNatIpsecTableEntry 6 }

-- {COLUMN} 1712.2.8.9.9.1.7
lcsSetupIpRouter1NNatIpsecTableEntryRemoteSpi OBJECT-TYPE
    SYNTAX     DisplayString (SIZE(0..8))
    MAX-ACCESS read-only
    STATUS     current
    DESCRIPTION
        "-- empty --"
    ::= { lcsSetupIpRouter1NNatIpsecTableEntry 7 }

-- {COLUMN} 1712.2.8.9.9.1.8
lcsSetupIpRouter1NNatIpsecTableEntryLocalSpi OBJECT-TYPE
    SYNTAX     DisplayString (SIZE(0..8))
    MAX-ACCESS read-only
    STATUS     current
    DESCRIPTION
        "-- empty --"
    ::= { lcsSetupIpRouter1NNatIpsecTableEntry 8 }

-- {COLUMN} 1712.2.8.9.9.1.9
lcsSetupIpRouter1NNatIpsecTableEntryTimeout OBJECT-TYPE
    SYNTAX     INTEGER (0..2147483647)
    MAX-ACCESS read-only
    STATUS     current
    DESCRIPTION
        "-- empty --"
    ::= { lcsSetupIpRouter1NNatIpsecTableEntry 9 }

-- {COLUMN} 1712.2.8.9.9.1.11
lcsSetupIpRouter1NNatIpsecTableEntryCo OBJECT-TYPE
    SYNTAX     INTEGER (0..255)
    MAX-ACCESS read-only
    STATUS     current
    DESCRIPTION
        "-- empty --"
    ::= { lcsSetupIpRouter1NNatIpsecTableEntry 11 }

-- {COLUMN} 1712.2.8.9.9.1.12
lcsSetupIpRouter1NNatIpsecTableEntryNl OBJECT-TYPE
    SYNTAX     INTEGER (0..255)
    MAX-ACCESS read-only
    STATUS     current
    DESCRIPTION
        "-- empty --"
    ::= { lcsSetupIpRouter1NNatIpsecTableEntry 12 }

-- {COLUMN} 1712.2.8.9.9.1.13
lcsSetupIpRouter1NNatIpsecTableEntryNr OBJECT-TYPE
    SYNTAX     INTEGER (0..255)
    MAX-ACCESS read-only
    STATUS     current
    DESCRIPTION
        "-- empty --"
    ::= { lcsSetupIpRouter1NNatIpsecTableEntry 13 }

-- {COLUMN} 1712.2.8.9.9.1.14
lcsSetupIpRouter1NNatIpsecTableEntryDp OBJECT-TYPE
    SYNTAX     INTEGER (0..255)
    MAX-ACCESS read-only
    STATUS     current
    DESCRIPTION
        "-- empty --"
    ::= { lcsSetupIpRouter1NNatIpsecTableEntry 14 }

-- {COLUMN} 1712.2.8.9.9.1.10
lcsSetupIpRouter1NNatIpsecTableEntryFlags OBJECT-TYPE
    SYNTAX     DisplayString (SIZE(0..4))
    MAX-ACCESS read-only
    STATUS     current
    DESCRIPTION
        "-- empty --"
    ::= { lcsSetupIpRouter1NNatIpsecTableEntry 10 }

-- {SCALAR} 1712.2.8.9.10
lcsSetupIpRouter1NNatIdSpoofing OBJECT-TYPE
    SYNTAX     INTEGER
      {
        eNo (0),
        eYes (1)
      }
    MAX-ACCESS read-write
    STATUS     current
    DESCRIPTION
        "-- empty --"
    ::= { lcsSetupIpRouter1NNat 10 }

-- {OID} 1712.2.8.10
lcsSetupIpRouterFirewall OBJECT IDENTIFIER ::= { lcsSetupIpRouter 10 }

-- {SCALAR} 1712.2.8.10.11
lcsSetupIpRouterFirewallOperating OBJECT-TYPE
    SYNTAX     INTEGER
      {
        eNo (0),
        eYes (1)
      }
    MAX-ACCESS read-write
    STATUS     current
    DESCRIPTION
        "-- empty --"
    ::= { lcsSetupIpRouterFirewall 11 }

-- {TABLE} 1712.2.8.10.4
lcsSetupIpRouterFirewallActionsTable OBJECT-TYPE
    SYNTAX     SEQUENCE OF LcsSetupIpRouterFirewallActionsEntry
    MAX-ACCESS not-accessible
    STATUS     current
    DESCRIPTION
        "-- empty --"
    ::= { lcsSetupIpRouterFirewall 4 }

-- {ENTRY} 1712.2.8.10.4.1
lcsSetupIpRouterFirewallActionsEntry OBJECT-TYPE
    SYNTAX     LcsSetupIpRouterFirewallActionsEntry
    MAX-ACCESS not-accessible
    STATUS     current
    DESCRIPTION
        ""
    INDEX {
        lcsSetupIpRouterFirewallActionsEntryName
    }
    ::= { lcsSetupIpRouterFirewallActionsTable 1 }

-- {SEQUENCE}
LcsSetupIpRouterFirewallActionsEntry ::= SEQUENCE {
    lcsSetupIpRouterFirewallActionsEntryName DisplayString,
    lcsSetupIpRouterFirewallActionsEntryDescription DisplayString
}

-- {COLUMN} 1712.2.8.10.4.1.1
lcsSetupIpRouterFirewallActionsEntryName OBJECT-TYPE
    SYNTAX     DisplayString (SIZE(0..32))
    MAX-ACCESS read-write
    STATUS     current
    DESCRIPTION
        "-- empty --"
    ::= { lcsSetupIpRouterFirewallActionsEntry 1 }

-- {COLUMN} 1712.2.8.10.4.1.2
lcsSetupIpRouterFirewallActionsEntryDescription OBJECT-TYPE
    SYNTAX     DisplayString (SIZE(0..64))
    MAX-ACCESS read-write
    STATUS     current
    DESCRIPTION
        "-- empty --"
    ::= { lcsSetupIpRouterFirewallActionsEntry 2 }

-- {TABLE} 1712.2.8.10.1
lcsSetupIpRouterFirewallObjectsTable OBJECT-TYPE
    SYNTAX     SEQUENCE OF LcsSetupIpRouterFirewallObjectsEntry
    MAX-ACCESS not-accessible
    STATUS     current
    DESCRIPTION
        "-- empty --"
    ::= { lcsSetupIpRouterFirewall 1 }

-- {ENTRY} 1712.2.8.10.1.1
lcsSetupIpRouterFirewallObjectsEntry OBJECT-TYPE
    SYNTAX     LcsSetupIpRouterFirewallObjectsEntry
    MAX-ACCESS not-accessible
    STATUS     current
    DESCRIPTION
        ""
    INDEX {
        lcsSetupIpRouterFirewallObjectsEntryName
    }
    ::= { lcsSetupIpRouterFirewallObjectsTable 1 }

-- {SEQUENCE}
LcsSetupIpRouterFirewallObjectsEntry ::= SEQUENCE {
    lcsSetupIpRouterFirewallObjectsEntryName DisplayString,
    lcsSetupIpRouterFirewallObjectsEntryDescription DisplayString
}

-- {COLUMN} 1712.2.8.10.1.1.1
lcsSetupIpRouterFirewallObjectsEntryName OBJECT-TYPE
    SYNTAX     DisplayString (SIZE(0..32))
    MAX-ACCESS read-write
    STATUS     current
    DESCRIPTION
        "-- empty --"
    ::= { lcsSetupIpRouterFirewallObjectsEntry 1 }

-- {COLUMN} 1712.2.8.10.1.1.2
lcsSetupIpRouterFirewallObjectsEntryDescription OBJECT-TYPE
    SYNTAX     DisplayString (SIZE(0..64))
    MAX-ACCESS read-write
    STATUS     current
    DESCRIPTION
        "-- empty --"
    ::= { lcsSetupIpRouterFirewallObjectsEntry 2 }

-- {TABLE} 1712.2.8.10.2
lcsSetupIpRouterFirewallRulesTable OBJECT-TYPE
    SYNTAX     SEQUENCE OF LcsSetupIpRouterFirewallRulesEntry
    MAX-ACCESS not-accessible
    STATUS     current
    DESCRIPTION
        "-- empty --"
    ::= { lcsSetupIpRouterFirewall 2 }

-- {ENTRY} 1712.2.8.10.2.1
lcsSetupIpRouterFirewallRulesEntry OBJECT-TYPE
    SYNTAX     LcsSetupIpRouterFirewallRulesEntry
    MAX-ACCESS not-accessible
    STATUS     current
    DESCRIPTION
        ""
    INDEX {
        lcsSetupIpRouterFirewallRulesEntryName
    }
    ::= { lcsSetupIpRouterFirewallRulesTable 1 }

-- {SEQUENCE}
LcsSetupIpRouterFirewallRulesEntry ::= SEQUENCE {
    lcsSetupIpRouterFirewallRulesEntryName DisplayString,
    lcsSetupIpRouterFirewallRulesEntryProt DisplayString,
    lcsSetupIpRouterFirewallRulesEntrySource DisplayString,
    lcsSetupIpRouterFirewallRulesEntryDestination DisplayString,
    lcsSetupIpRouterFirewallRulesEntryAction DisplayString,
    lcsSetupIpRouterFirewallRulesEntryLinked INTEGER,
    lcsSetupIpRouterFirewallRulesEntryPrio INTEGER,
    lcsSetupIpRouterFirewallRulesEntryFirewallRule INTEGER,
    lcsSetupIpRouterFirewallRulesEntryVpnRule INTEGER,
    lcsSetupIpRouterFirewallRulesEntryStateful INTEGER,
    lcsSetupIpRouterFirewallRulesEntrySrcTag INTEGER,
    lcsSetupIpRouterFirewallRulesEntryRtgTag INTEGER,
    lcsSetupIpRouterFirewallRulesEntryComment DisplayString
}

-- {COLUMN} 1712.2.8.10.2.1.1
lcsSetupIpRouterFirewallRulesEntryName OBJECT-TYPE
    SYNTAX     DisplayString (SIZE(0..32))
    MAX-ACCESS read-write
    STATUS     current
    DESCRIPTION
        "-- empty --"
    ::= { lcsSetupIpRouterFirewallRulesEntry 1 }

-- {COLUMN} 1712.2.8.10.2.1.2
lcsSetupIpRouterFirewallRulesEntryProt OBJECT-TYPE
    SYNTAX     DisplayString (SIZE(0..10))
    MAX-ACCESS read-write
    STATUS     current
    DESCRIPTION
        "-- empty --"
    ::= { lcsSetupIpRouterFirewallRulesEntry 2 }

-- {COLUMN} 1712.2.8.10.2.1.3
lcsSetupIpRouterFirewallRulesEntrySource OBJECT-TYPE
    SYNTAX     DisplayString (SIZE(0..40))
    MAX-ACCESS read-write
    STATUS     current
    DESCRIPTION
        "-- empty --"
    ::= { lcsSetupIpRouterFirewallRulesEntry 3 }

-- {COLUMN} 1712.2.8.10.2.1.4
lcsSetupIpRouterFirewallRulesEntryDestination OBJECT-TYPE
    SYNTAX     DisplayString (SIZE(0..40))
    MAX-ACCESS read-write
    STATUS     current
    DESCRIPTION
        "-- empty --"
    ::= { lcsSetupIpRouterFirewallRulesEntry 4 }

-- {COLUMN} 1712.2.8.10.2.1.7
lcsSetupIpRouterFirewallRulesEntryAction OBJECT-TYPE
    SYNTAX     DisplayString (SIZE(0..40))
    MAX-ACCESS read-write
    STATUS     current
    DESCRIPTION
        "-- empty --"
    ::= { lcsSetupIpRouterFirewallRulesEntry 7 }

-- {COLUMN} 1712.2.8.10.2.1.8
lcsSetupIpRouterFirewallRulesEntryLinked OBJECT-TYPE
    SYNTAX     INTEGER
      {
        eNo (0),
        eYes (1)
      }
    MAX-ACCESS read-write
    STATUS     current
    DESCRIPTION
        "-- empty --"
    ::= { lcsSetupIpRouterFirewallRulesEntry 8 }

-- {COLUMN} 1712.2.8.10.2.1.9
lcsSetupIpRouterFirewallRulesEntryPrio OBJECT-TYPE
    SYNTAX     INTEGER (0..65535)
    MAX-ACCESS read-write
    STATUS     current
    DESCRIPTION
        "-- empty --"
    ::= { lcsSetupIpRouterFirewallRulesEntry 9 }

-- {COLUMN} 1712.2.8.10.2.1.10
lcsSetupIpRouterFirewallRulesEntryFirewallRule OBJECT-TYPE
    SYNTAX     INTEGER
      {
        eNo (1),
        eYes (0)
      }
    MAX-ACCESS read-write
    STATUS     current
    DESCRIPTION
        "-- empty --"
    ::= { lcsSetupIpRouterFirewallRulesEntry 10 }

-- {COLUMN} 1712.2.8.10.2.1.11
lcsSetupIpRouterFirewallRulesEntryVpnRule OBJECT-TYPE
    SYNTAX     INTEGER
      {
        eNo (0),
        eYes (1)
      }
    MAX-ACCESS read-write
    STATUS     current
    DESCRIPTION
        "-- empty --"
    ::= { lcsSetupIpRouterFirewallRulesEntry 11 }

-- {COLUMN} 1712.2.8.10.2.1.12
lcsSetupIpRouterFirewallRulesEntryStateful OBJECT-TYPE
    SYNTAX     INTEGER
      {
        eNo (1),
        eYes (0)
      }
    MAX-ACCESS read-write
    STATUS     current
    DESCRIPTION
        "-- empty --"
    ::= { lcsSetupIpRouterFirewallRulesEntry 12 }

-- {COLUMN} 1712.2.8.10.2.1.15
lcsSetupIpRouterFirewallRulesEntrySrcTag OBJECT-TYPE
    SYNTAX     INTEGER (0..65535)
    MAX-ACCESS read-write
    STATUS     current
    DESCRIPTION
        "-- empty --"
    ::= { lcsSetupIpRouterFirewallRulesEntry 15 }

-- {COLUMN} 1712.2.8.10.2.1.14
lcsSetupIpRouterFirewallRulesEntryRtgTag OBJECT-TYPE
    SYNTAX     INTEGER (0..65535)
    MAX-ACCESS read-write
    STATUS     current
    DESCRIPTION
        "-- empty --"
    ::= { lcsSetupIpRouterFirewallRulesEntry 14 }

-- {COLUMN} 1712.2.8.10.2.1.13
lcsSetupIpRouterFirewallRulesEntryComment OBJECT-TYPE
    SYNTAX     DisplayString (SIZE(0..64))
    MAX-ACCESS read-write
    STATUS     current
    DESCRIPTION
        "-- empty --"
    ::= { lcsSetupIpRouterFirewallRulesEntry 13 }

-- {TABLE} 1712.2.8.10.3
lcsSetupIpRouterFirewallFilterListTable OBJECT-TYPE
    SYNTAX     SEQUENCE OF LcsSetupIpRouterFirewallFilterListEntry
    MAX-ACCESS not-accessible
    STATUS     current
    DESCRIPTION
        "-- empty --"
    ::= { lcsSetupIpRouterFirewall 3 }

-- {ENTRY} 1712.2.8.10.3.1
lcsSetupIpRouterFirewallFilterListEntry OBJECT-TYPE
    SYNTAX     LcsSetupIpRouterFirewallFilterListEntry
    MAX-ACCESS not-accessible
    STATUS     current
    DESCRIPTION
        ""
    INDEX {
        lcsSetupIpRouterFirewallFilterListEntryIdx
    }
    ::= { lcsSetupIpRouterFirewallFilterListTable 1 }

-- {SEQUENCE}
LcsSetupIpRouterFirewallFilterListEntry ::= SEQUENCE {
    lcsSetupIpRouterFirewallFilterListEntryIdx INTEGER,
    lcsSetupIpRouterFirewallFilterListEntryProt INTEGER,
    lcsSetupIpRouterFirewallFilterListEntrySrcMac DisplayString,
    lcsSetupIpRouterFirewallFilterListEntrySrcAddress IpAddress,
    lcsSetupIpRouterFirewallFilterListEntrySrcNetmask IpAddress,
    lcsSetupIpRouterFirewallFilterListEntrySSt INTEGER,
    lcsSetupIpRouterFirewallFilterListEntrySEnd INTEGER,
    lcsSetupIpRouterFirewallFilterListEntryDstMac DisplayString,
    lcsSetupIpRouterFirewallFilterListEntryDstAddress IpAddress,
    lcsSetupIpRouterFirewallFilterListEntryDstNetmask IpAddress,
    lcsSetupIpRouterFirewallFilterListEntryDSt INTEGER,
    lcsSetupIpRouterFirewallFilterListEntryDEnd INTEGER,
    lcsSetupIpRouterFirewallFilterListEntryAction DisplayString,
    lcsSetupIpRouterFirewallFilterListEntryLinked INTEGER,
    lcsSetupIpRouterFirewallFilterListEntryPrio INTEGER,
    lcsSetupIpRouterFirewallFilterListEntrySrcTag INTEGER,
    lcsSetupIpRouterFirewallFilterListEntryRtgTag INTEGER
}

-- {COLUMN} 1712.2.8.10.3.1.1
lcsSetupIpRouterFirewallFilterListEntryIdx OBJECT-TYPE
    SYNTAX     INTEGER (0..2147483647)
    MAX-ACCESS read-only
    STATUS     current
    DESCRIPTION
        "-- empty --"
    ::= { lcsSetupIpRouterFirewallFilterListEntry 1 }

-- {COLUMN} 1712.2.8.10.3.1.2
lcsSetupIpRouterFirewallFilterListEntryProt OBJECT-TYPE
    SYNTAX     INTEGER (0..255)
    MAX-ACCESS read-only
    STATUS     current
    DESCRIPTION
        "-- empty --"
    ::= { lcsSetupIpRouterFirewallFilterListEntry 2 }

-- {COLUMN} 1712.2.8.10.3.1.13
lcsSetupIpRouterFirewallFilterListEntrySrcMac OBJECT-TYPE
    SYNTAX     DisplayString (SIZE(0..255))
    MAX-ACCESS read-only
    STATUS     current
    DESCRIPTION
        "-- empty --"
    ::= { lcsSetupIpRouterFirewallFilterListEntry 13 }

-- {COLUMN} 1712.2.8.10.3.1.3
lcsSetupIpRouterFirewallFilterListEntrySrcAddress OBJECT-TYPE
    SYNTAX     IpAddress
    MAX-ACCESS read-only
    STATUS     current
    DESCRIPTION
        "-- empty --"
    ::= { lcsSetupIpRouterFirewallFilterListEntry 3 }

-- {COLUMN} 1712.2.8.10.3.1.4
lcsSetupIpRouterFirewallFilterListEntrySrcNetmask OBJECT-TYPE
    SYNTAX     IpAddress
    MAX-ACCESS read-only
    STATUS     current
    DESCRIPTION
        "-- empty --"
    ::= { lcsSetupIpRouterFirewallFilterListEntry 4 }

-- {COLUMN} 1712.2.8.10.3.1.5
lcsSetupIpRouterFirewallFilterListEntrySSt OBJECT-TYPE
    SYNTAX     INTEGER (0..65535)
    MAX-ACCESS read-only
    STATUS     current
    DESCRIPTION
        "-- empty --"
    ::= { lcsSetupIpRouterFirewallFilterListEntry 5 }

-- {COLUMN} 1712.2.8.10.3.1.6
lcsSetupIpRouterFirewallFilterListEntrySEnd OBJECT-TYPE
    SYNTAX     INTEGER (0..65535)
    MAX-ACCESS read-only
    STATUS     current
    DESCRIPTION
        "-- empty --"
    ::= { lcsSetupIpRouterFirewallFilterListEntry 6 }

-- {COLUMN} 1712.2.8.10.3.1.14
lcsSetupIpRouterFirewallFilterListEntryDstMac OBJECT-TYPE
    SYNTAX     DisplayString (SIZE(0..255))
    MAX-ACCESS read-only
    STATUS     current
    DESCRIPTION
        "-- empty --"
    ::= { lcsSetupIpRouterFirewallFilterListEntry 14 }

-- {COLUMN} 1712.2.8.10.3.1.7
lcsSetupIpRouterFirewallFilterListEntryDstAddress OBJECT-TYPE
    SYNTAX     IpAddress
    MAX-ACCESS read-only
    STATUS     current
    DESCRIPTION
        "-- empty --"
    ::= { lcsSetupIpRouterFirewallFilterListEntry 7 }

-- {COLUMN} 1712.2.8.10.3.1.8
lcsSetupIpRouterFirewallFilterListEntryDstNetmask OBJECT-TYPE
    SYNTAX     IpAddress
    MAX-ACCESS read-only
    STATUS     current
    DESCRIPTION
        "-- empty --"
    ::= { lcsSetupIpRouterFirewallFilterListEntry 8 }

-- {COLUMN} 1712.2.8.10.3.1.9
lcsSetupIpRouterFirewallFilterListEntryDSt OBJECT-TYPE
    SYNTAX     INTEGER (0..65535)
    MAX-ACCESS read-only
    STATUS     current
    DESCRIPTION
        "-- empty --"
    ::= { lcsSetupIpRouterFirewallFilterListEntry 9 }

-- {COLUMN} 1712.2.8.10.3.1.10
lcsSetupIpRouterFirewallFilterListEntryDEnd OBJECT-TYPE
    SYNTAX     INTEGER (0..65535)
    MAX-ACCESS read-only
    STATUS     current
    DESCRIPTION
        "-- empty --"
    ::= { lcsSetupIpRouterFirewallFilterListEntry 10 }

-- {COLUMN} 1712.2.8.10.3.1.11
lcsSetupIpRouterFirewallFilterListEntryAction OBJECT-TYPE
    SYNTAX     DisplayString (SIZE(0..255))
    MAX-ACCESS read-only
    STATUS     current
    DESCRIPTION
        "-- empty --"
    ::= { lcsSetupIpRouterFirewallFilterListEntry 11 }

-- {COLUMN} 1712.2.8.10.3.1.15
lcsSetupIpRouterFirewallFilterListEntryLinked OBJECT-TYPE
    SYNTAX     INTEGER
      {
        eNo (0),
        eYes (1)
      }
    MAX-ACCESS read-only
    STATUS     current
    DESCRIPTION
        "-- empty --"
    ::= { lcsSetupIpRouterFirewallFilterListEntry 15 }

-- {COLUMN} 1712.2.8.10.3.1.16
lcsSetupIpRouterFirewallFilterListEntryPrio OBJECT-TYPE
    SYNTAX     INTEGER (0..65535)
    MAX-ACCESS read-only
    STATUS     current
    DESCRIPTION
        "-- empty --"
    ::= { lcsSetupIpRouterFirewallFilterListEntry 16 }

-- {COLUMN} 1712.2.8.10.3.1.18
lcsSetupIpRouterFirewallFilterListEntrySrcTag OBJECT-TYPE
    SYNTAX     INTEGER (0..65535)
    MAX-ACCESS read-only
    STATUS     current
    DESCRIPTION
        "-- empty --"
    ::= { lcsSetupIpRouterFirewallFilterListEntry 18 }

-- {COLUMN} 1712.2.8.10.3.1.17
lcsSetupIpRouterFirewallFilterListEntryRtgTag OBJECT-TYPE
    SYNTAX     INTEGER (0..65535)
    MAX-ACCESS read-only
    STATUS     current
    DESCRIPTION
        "-- empty --"
    ::= { lcsSetupIpRouterFirewallFilterListEntry 17 }

-- {TABLE} 1712.2.8.10.5
lcsSetupIpRouterFirewallConnectionListTable OBJECT-TYPE
    SYNTAX     SEQUENCE OF LcsSetupIpRouterFirewallConnectionListEntry
    MAX-ACCESS not-accessible
    STATUS     current
    DESCRIPTION
        "-- empty --"
    ::= { lcsSetupIpRouterFirewall 5 }

-- {ENTRY} 1712.2.8.10.5.1
lcsSetupIpRouterFirewallConnectionListEntry OBJECT-TYPE
    SYNTAX     LcsSetupIpRouterFirewallConnectionListEntry
    MAX-ACCESS not-accessible
    STATUS     current
    DESCRIPTION
        ""
    INDEX {
        lcsSetupIpRouterFirewallConnectionListEntrySrcAddress,
        lcsSetupIpRouterFirewallConnectionListEntryDstAddress,
        lcsSetupIpRouterFirewallConnectionListEntryProt,
        lcsSetupIpRouterFirewallConnectionListEntrySrcPort,
        lcsSetupIpRouterFirewallConnectionListEntryDstPort
    }
    ::= { lcsSetupIpRouterFirewallConnectionListTable 1 }

-- {SEQUENCE}
LcsSetupIpRouterFirewallConnectionListEntry ::= SEQUENCE {
    lcsSetupIpRouterFirewallConnectionListEntrySrcAddress IpAddress,
    lcsSetupIpRouterFirewallConnectionListEntryDstAddress IpAddress,
    lcsSetupIpRouterFirewallConnectionListEntryProt INTEGER,
    lcsSetupIpRouterFirewallConnectionListEntrySrcPort INTEGER,
    lcsSetupIpRouterFirewallConnectionListEntryDstPort INTEGER,
    lcsSetupIpRouterFirewallConnectionListEntryRtgTag INTEGER,
    lcsSetupIpRouterFirewallConnectionListEntryTimeout INTEGER,
    lcsSetupIpRouterFirewallConnectionListEntryFlags INTEGER,
    lcsSetupIpRouterFirewallConnectionListEntryFilterRule DisplayString,
    lcsSetupIpRouterFirewallConnectionListEntrySrcRoute DisplayString,
    lcsSetupIpRouterFirewallConnectionListEntryDestRoute DisplayString
}

-- {COLUMN} 1712.2.8.10.5.1.1
lcsSetupIpRouterFirewallConnectionListEntrySrcAddress OBJECT-TYPE
    SYNTAX     IpAddress
    MAX-ACCESS read-only
    STATUS     current
    DESCRIPTION
        "-- empty --"
    ::= { lcsSetupIpRouterFirewallConnectionListEntry 1 }

-- {COLUMN} 1712.2.8.10.5.1.2
lcsSetupIpRouterFirewallConnectionListEntryDstAddress OBJECT-TYPE
    SYNTAX     IpAddress
    MAX-ACCESS read-only
    STATUS     current
    DESCRIPTION
        "-- empty --"
    ::= { lcsSetupIpRouterFirewallConnectionListEntry 2 }

-- {COLUMN} 1712.2.8.10.5.1.3
lcsSetupIpRouterFirewallConnectionListEntryProt OBJECT-TYPE
    SYNTAX     INTEGER (0..255)
    MAX-ACCESS read-only
    STATUS     current
    DESCRIPTION
        "-- empty --"
    ::= { lcsSetupIpRouterFirewallConnectionListEntry 3 }

-- {COLUMN} 1712.2.8.10.5.1.4
lcsSetupIpRouterFirewallConnectionListEntrySrcPort OBJECT-TYPE
    SYNTAX     INTEGER (0..65535)
    MAX-ACCESS read-only
    STATUS     current
    DESCRIPTION
        "-- empty --"
    ::= { lcsSetupIpRouterFirewallConnectionListEntry 4 }

-- {COLUMN} 1712.2.8.10.5.1.5
lcsSetupIpRouterFirewallConnectionListEntryDstPort OBJECT-TYPE
    SYNTAX     INTEGER (0..65535)
    MAX-ACCESS read-only
    STATUS     current
    DESCRIPTION
        "-- empty --"
    ::= { lcsSetupIpRouterFirewallConnectionListEntry 5 }

-- {COLUMN} 1712.2.8.10.5.1.11
lcsSetupIpRouterFirewallConnectionListEntryRtgTag OBJECT-TYPE
    SYNTAX     INTEGER (0..65535)
    MAX-ACCESS read-only
    STATUS     current
    DESCRIPTION
        "-- empty --"
    ::= { lcsSetupIpRouterFirewallConnectionListEntry 11 }

-- {COLUMN} 1712.2.8.10.5.1.6
lcsSetupIpRouterFirewallConnectionListEntryTimeout OBJECT-TYPE
    SYNTAX     INTEGER (0..65535)
    MAX-ACCESS read-only
    STATUS     current
    DESCRIPTION
        "-- empty --"
    ::= { lcsSetupIpRouterFirewallConnectionListEntry 6 }

-- {COLUMN} 1712.2.8.10.5.1.7
lcsSetupIpRouterFirewallConnectionListEntryFlags OBJECT-TYPE
    SYNTAX     INTEGER (0..2147483647)
    MAX-ACCESS read-only
    STATUS     current
    DESCRIPTION
        "-- empty --"
    ::= { lcsSetupIpRouterFirewallConnectionListEntry 7 }

-- {COLUMN} 1712.2.8.10.5.1.8
lcsSetupIpRouterFirewallConnectionListEntryFilterRule OBJECT-TYPE
    SYNTAX     DisplayString (SIZE(0..255))
    MAX-ACCESS read-only
    STATUS     current
    DESCRIPTION
        "-- empty --"
    ::= { lcsSetupIpRouterFirewallConnectionListEntry 8 }

-- {COLUMN} 1712.2.8.10.5.1.9
lcsSetupIpRouterFirewallConnectionListEntrySrcRoute OBJECT-TYPE
    SYNTAX     DisplayString (SIZE(0..255))
    MAX-ACCESS read-only
    STATUS     current
    DESCRIPTION
        "-- empty --"
    ::= { lcsSetupIpRouterFirewallConnectionListEntry 9 }

-- {COLUMN} 1712.2.8.10.5.1.10
lcsSetupIpRouterFirewallConnectionListEntryDestRoute OBJECT-TYPE
    SYNTAX     DisplayString (SIZE(0..255))
    MAX-ACCESS read-only
    STATUS     current
    DESCRIPTION
        "-- empty --"
    ::= { lcsSetupIpRouterFirewallConnectionListEntry 10 }

-- {TABLE} 1712.2.8.10.19
lcsSetupIpRouterFirewallOpenPortListTable OBJECT-TYPE
    SYNTAX     SEQUENCE OF LcsSetupIpRouterFirewallOpenPortListEntry
    MAX-ACCESS not-accessible
    STATUS     current
    DESCRIPTION
        "-- empty --"
    ::= { lcsSetupIpRouterFirewall 19 }

-- {ENTRY} 1712.2.8.10.19.1
lcsSetupIpRouterFirewallOpenPortListEntry OBJECT-TYPE
    SYNTAX     LcsSetupIpRouterFirewallOpenPortListEntry
    MAX-ACCESS not-accessible
    STATUS     current
    DESCRIPTION
        ""
    INDEX {
        lcsSetupIpRouterFirewallOpenPortListEntrySrcAddress,
        lcsSetupIpRouterFirewallOpenPortListEntryDstAddress,
        lcsSetupIpRouterFirewallOpenPortListEntryProt,
        lcsSetupIpRouterFirewallOpenPortListEntryDstPort
    }
    ::= { lcsSetupIpRouterFirewallOpenPortListTable 1 }

-- {SEQUENCE}
LcsSetupIpRouterFirewallOpenPortListEntry ::= SEQUENCE {
    lcsSetupIpRouterFirewallOpenPortListEntrySrcAddress IpAddress,
    lcsSetupIpRouterFirewallOpenPortListEntryDstAddress IpAddress,
    lcsSetupIpRouterFirewallOpenPortListEntryProt INTEGER,
    lcsSetupIpRouterFirewallOpenPortListEntryDstPort INTEGER,
    lcsSetupIpRouterFirewallOpenPortListEntryTimeout INTEGER,
    lcsSetupIpRouterFirewallOpenPortListEntryFilterRule DisplayString,
    lcsSetupIpRouterFirewallOpenPortListEntrySrcRoute DisplayString
}

-- {COLUMN} 1712.2.8.10.19.1.1
lcsSetupIpRouterFirewallOpenPortListEntrySrcAddress OBJECT-TYPE
    SYNTAX     IpAddress
    MAX-ACCESS read-only
    STATUS     current
    DESCRIPTION
        "-- empty --"
    ::= { lcsSetupIpRouterFirewallOpenPortListEntry 1 }

-- {COLUMN} 1712.2.8.10.19.1.2
lcsSetupIpRouterFirewallOpenPortListEntryDstAddress OBJECT-TYPE
    SYNTAX     IpAddress
    MAX-ACCESS read-only
    STATUS     current
    DESCRIPTION
        "-- empty --"
    ::= { lcsSetupIpRouterFirewallOpenPortListEntry 2 }

-- {COLUMN} 1712.2.8.10.19.1.3
lcsSetupIpRouterFirewallOpenPortListEntryProt OBJECT-TYPE
    SYNTAX     INTEGER (0..255)
    MAX-ACCESS read-only
    STATUS     current
    DESCRIPTION
        "-- empty --"
    ::= { lcsSetupIpRouterFirewallOpenPortListEntry 3 }

-- {COLUMN} 1712.2.8.10.19.1.5
lcsSetupIpRouterFirewallOpenPortListEntryDstPort OBJECT-TYPE
    SYNTAX     INTEGER (0..65535)
    MAX-ACCESS read-only
    STATUS     current
    DESCRIPTION
        "-- empty --"
    ::= { lcsSetupIpRouterFirewallOpenPortListEntry 5 }

-- {COLUMN} 1712.2.8.10.19.1.6
lcsSetupIpRouterFirewallOpenPortListEntryTimeout OBJECT-TYPE
    SYNTAX     INTEGER (0..65535)
    MAX-ACCESS read-only
    STATUS     current
    DESCRIPTION
        "-- empty --"
    ::= { lcsSetupIpRouterFirewallOpenPortListEntry 6 }

-- {COLUMN} 1712.2.8.10.19.1.8
lcsSetupIpRouterFirewallOpenPortListEntryFilterRule OBJECT-TYPE
    SYNTAX     DisplayString (SIZE(0..255))
    MAX-ACCESS read-only
    STATUS     current
    DESCRIPTION
        "-- empty --"
    ::= { lcsSetupIpRouterFirewallOpenPortListEntry 8 }

-- {COLUMN} 1712.2.8.10.19.1.9
lcsSetupIpRouterFirewallOpenPortListEntrySrcRoute OBJECT-TYPE
    SYNTAX     DisplayString (SIZE(0..255))
    MAX-ACCESS read-only
    STATUS     current
    DESCRIPTION
        "-- empty --"
    ::= { lcsSetupIpRouterFirewallOpenPortListEntry 9 }

-- {TABLE} 1712.2.8.10.6
lcsSetupIpRouterFirewallHostBlockListTable OBJECT-TYPE
    SYNTAX     SEQUENCE OF LcsSetupIpRouterFirewallHostBlockListEntry
    MAX-ACCESS not-accessible
    STATUS     current
    DESCRIPTION
        "-- empty --"
    ::= { lcsSetupIpRouterFirewall 6 }

-- {ENTRY} 1712.2.8.10.6.1
lcsSetupIpRouterFirewallHostBlockListEntry OBJECT-TYPE
    SYNTAX     LcsSetupIpRouterFirewallHostBlockListEntry
    MAX-ACCESS not-accessible
    STATUS     current
    DESCRIPTION
        ""
    INDEX {
        lcsSetupIpRouterFirewallHostBlockListEntrySrcAddress
    }
    ::= { lcsSetupIpRouterFirewallHostBlockListTable 1 }

-- {SEQUENCE}
LcsSetupIpRouterFirewallHostBlockListEntry ::= SEQUENCE {
    lcsSetupIpRouterFirewallHostBlockListEntrySrcAddress IpAddress,
    lcsSetupIpRouterFirewallHostBlockListEntryTimeout INTEGER,
    lcsSetupIpRouterFirewallHostBlockListEntryFilterRule DisplayString
}

-- {COLUMN} 1712.2.8.10.6.1.1
lcsSetupIpRouterFirewallHostBlockListEntrySrcAddress OBJECT-TYPE
    SYNTAX     IpAddress
    MAX-ACCESS read-only
    STATUS     current
    DESCRIPTION
        "-- empty --"
    ::= { lcsSetupIpRouterFirewallHostBlockListEntry 1 }

-- {COLUMN} 1712.2.8.10.6.1.2
lcsSetupIpRouterFirewallHostBlockListEntryTimeout OBJECT-TYPE
    SYNTAX     INTEGER (0..2147483647)
    MAX-ACCESS read-only
    STATUS     current
    DESCRIPTION
        "-- empty --"
    ::= { lcsSetupIpRouterFirewallHostBlockListEntry 2 }

-- {COLUMN} 1712.2.8.10.6.1.3
lcsSetupIpRouterFirewallHostBlockListEntryFilterRule OBJECT-TYPE
    SYNTAX     DisplayString (SIZE(0..255))
    MAX-ACCESS read-only
    STATUS     current
    DESCRIPTION
        "-- empty --"
    ::= { lcsSetupIpRouterFirewallHostBlockListEntry 3 }

-- {TABLE} 1712.2.8.10.7
lcsSetupIpRouterFirewallPortBlockListTable OBJECT-TYPE
    SYNTAX     SEQUENCE OF LcsSetupIpRouterFirewallPortBlockListEntry
    MAX-ACCESS not-accessible
    STATUS     current
    DESCRIPTION
        "-- empty --"
    ::= { lcsSetupIpRouterFirewall 7 }

-- {ENTRY} 1712.2.8.10.7.1
lcsSetupIpRouterFirewallPortBlockListEntry OBJECT-TYPE
    SYNTAX     LcsSetupIpRouterFirewallPortBlockListEntry
    MAX-ACCESS not-accessible
    STATUS     current
    DESCRIPTION
        ""
    INDEX {
        lcsSetupIpRouterFirewallPortBlockListEntryDstAddress
    }
    ::= { lcsSetupIpRouterFirewallPortBlockListTable 1 }

-- {SEQUENCE}
LcsSetupIpRouterFirewallPortBlockListEntry ::= SEQUENCE {
    lcsSetupIpRouterFirewallPortBlockListEntryDstAddress IpAddress,
    lcsSetupIpRouterFirewallPortBlockListEntryProt INTEGER,
    lcsSetupIpRouterFirewallPortBlockListEntryDstPort INTEGER,
    lcsSetupIpRouterFirewallPortBlockListEntryTimeout INTEGER,
    lcsSetupIpRouterFirewallPortBlockListEntryFilterRule DisplayString
}

-- {COLUMN} 1712.2.8.10.7.1.1
lcsSetupIpRouterFirewallPortBlockListEntryDstAddress OBJECT-TYPE
    SYNTAX     IpAddress
    MAX-ACCESS read-only
    STATUS     current
    DESCRIPTION
        "-- empty --"
    ::= { lcsSetupIpRouterFirewallPortBlockListEntry 1 }

-- {COLUMN} 1712.2.8.10.7.1.2
lcsSetupIpRouterFirewallPortBlockListEntryProt OBJECT-TYPE
    SYNTAX     INTEGER (0..65535)
    MAX-ACCESS read-only
    STATUS     current
    DESCRIPTION
        "-- empty --"
    ::= { lcsSetupIpRouterFirewallPortBlockListEntry 2 }

-- {COLUMN} 1712.2.8.10.7.1.3
lcsSetupIpRouterFirewallPortBlockListEntryDstPort OBJECT-TYPE
    SYNTAX     INTEGER (0..65535)
    MAX-ACCESS read-only
    STATUS     current
    DESCRIPTION
        "-- empty --"
    ::= { lcsSetupIpRouterFirewallPortBlockListEntry 3 }

-- {COLUMN} 1712.2.8.10.7.1.4
lcsSetupIpRouterFirewallPortBlockListEntryTimeout OBJECT-TYPE
    SYNTAX     INTEGER (0..2147483647)
    MAX-ACCESS read-only
    STATUS     current
    DESCRIPTION
        "-- empty --"
    ::= { lcsSetupIpRouterFirewallPortBlockListEntry 4 }

-- {COLUMN} 1712.2.8.10.7.1.5
lcsSetupIpRouterFirewallPortBlockListEntryFilterRule OBJECT-TYPE
    SYNTAX     DisplayString (SIZE(0..255))
    MAX-ACCESS read-only
    STATUS     current
    DESCRIPTION
        "-- empty --"
    ::= { lcsSetupIpRouterFirewallPortBlockListEntry 5 }

-- {SCALAR} 1712.2.8.10.8
lcsSetupIpRouterFirewallMaxHalfOpenConns OBJECT-TYPE
    SYNTAX     INTEGER (0..2147483647)
    MAX-ACCESS read-write
    STATUS     current
    DESCRIPTION
        "-- empty --"
    ::= { lcsSetupIpRouterFirewall 8 }

-- {SCALAR} 1712.2.8.10.9
lcsSetupIpRouterFirewallDosAction OBJECT-TYPE
    SYNTAX     DisplayString (SIZE(0..29))
    MAX-ACCESS read-write
    STATUS     current
    DESCRIPTION
        "-- empty --"
    ::= { lcsSetupIpRouterFirewall 9 }

-- {SCALAR} 1712.2.8.10.12
lcsSetupIpRouterFirewallPortScanThreshold OBJECT-TYPE
    SYNTAX     INTEGER (0..2147483647)
    MAX-ACCESS read-write
    STATUS     current
    DESCRIPTION
        "-- empty --"
    ::= { lcsSetupIpRouterFirewall 12 }

-- {SCALAR} 1712.2.8.10.13
lcsSetupIpRouterFirewallIdsAction OBJECT-TYPE
    SYNTAX     DisplayString (SIZE(0..29))
    MAX-ACCESS read-write
    STATUS     current
    DESCRIPTION
        "-- empty --"
    ::= { lcsSetupIpRouterFirewall 13 }

-- {SCALAR} 1712.2.8.10.10
lcsSetupIpRouterFirewallAdminEmail OBJECT-TYPE
    SYNTAX     DisplayString (SIZE(0..255))
    MAX-ACCESS read-write
    STATUS     current
    DESCRIPTION
        "-- empty --"
    ::= { lcsSetupIpRouterFirewall 10 }

-- {SCALAR} 1712.2.8.10.14
lcsSetupIpRouterFirewallPingBlock OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewall 14 }

-- {SCALAR} 1712.2.8.10.15
lcsSetupIpRouterFirewallStealthMode OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewall 15 }

-- {SCALAR} 1712.2.8.10.16
lcsSetupIpRouterFirewallAuthPort OBJECT-TYPE
    SYNTAX     INTEGER
      {
        eClosed (0),
        eStealth (1)
      }
    MAX-ACCESS read-write
    STATUS     current
    DESCRIPTION
        "-- empty --"
    ::= { lcsSetupIpRouterFirewall 16 }

-- {SCALAR} 1712.2.8.10.17
lcsSetupIpRouterFirewallDenySessionRecover OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewall 17 }

-- {OID} 1712.2.8.10.20
lcsSetupIpRouterFirewallApplications OBJECT IDENTIFIER ::= { lcsSetupIpRouterFirewall 20 }

-- {OID} 1712.2.8.10.20.1
lcsSetupIpRouterFirewallApplicationsFtp OBJECT IDENTIFIER ::= { lcsSetupIpRouterFirewallApplications 1 }

-- {SCALAR} 1712.2.8.10.20.1.1
lcsSetupIpRouterFirewallApplicationsFtpFtpBlock OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsFtp 1 }

-- {SCALAR} 1712.2.8.10.20.1.2
lcsSetupIpRouterFirewallApplicationsFtpActiveFtpBlock OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsFtp 2 }

-- {SCALAR} 1712.2.8.10.20.1.3
lcsSetupIpRouterFirewallApplicationsFtpMinPort OBJECT-TYPE
    SYNTAX     INTEGER (0..65535)
    MAX-ACCESS read-write
    STATUS     current
    DESCRIPTION
        "-- empty --"
    ::= { lcsSetupIpRouterFirewallApplicationsFtp 3 }

-- {SCALAR} 1712.2.8.10.20.1.4
lcsSetupIpRouterFirewallApplicationsFtpCheckHostIp OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsFtp 4 }

-- {SCALAR} 1712.2.8.10.20.1.5
lcsSetupIpRouterFirewallApplicationsFtpFxpBlock OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsFtp 5 }

-- {OID} 1712.2.8.10.20.2
lcsSetupIpRouterFirewallApplicationsIrc OBJECT IDENTIFIER ::= { lcsSetupIpRouterFirewallApplications 2 }

-- {SCALAR} 1712.2.8.10.20.2.1
lcsSetupIpRouterFirewallApplicationsIrcIrcBlock OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsIrc 1 }

-- {SCALAR} 1712.2.8.10.20.2.2
lcsSetupIpRouterFirewallApplicationsIrcDdcBlock OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsIrc 2 }

-- {SCALAR} 1712.2.8.10.20.2.3
lcsSetupIpRouterFirewallApplicationsIrcMinPort OBJECT-TYPE
    SYNTAX     INTEGER (0..65535)
    MAX-ACCESS read-write
    STATUS     current
    DESCRIPTION
        "-- empty --"
    ::= { lcsSetupIpRouterFirewallApplicationsIrc 3 }

-- {SCALAR} 1712.2.8.10.20.2.4
lcsSetupIpRouterFirewallApplicationsIrcCheckHostIp OBJECT-TYPE
    SYNTAX     INTEGER
      {
        eOff (0),
        eAlways (1),
        eWan (2),
        eDefaultRoute (3)
      }
    MAX-ACCESS read-write
    STATUS     current
    DESCRIPTION
        "-- empty --"
    ::= { lcsSetupIpRouterFirewallApplicationsIrc 4 }

-- {SCALAR} 1712.2.8.10.20.10
lcsSetupIpRouterFirewallApplicationsApplAction OBJECT-TYPE
    SYNTAX     DisplayString (SIZE(0..29))
    MAX-ACCESS read-write
    STATUS     current
    DESCRIPTION
        "-- empty --"
    ::= { lcsSetupIpRouterFirewallApplications 10 }

-- {TABLE} 1712.2.8.19
lcsSetupIpRouterNNNatTable OBJECT-TYPE
    SYNTAX     SEQUENCE OF LcsSetupIpRouterNNNatEntry
    MAX-ACCESS not-accessible
    STATUS     current
    DESCRIPTION
        "-- empty --"
    ::= { lcsSetupIpRouter 19 }

-- {ENTRY} 1712.2.8.19.1
lcsSetupIpRouterNNNatEntry OBJECT-TYPE
    SYNTAX     LcsSetupIpRouterNNNatEntry
    MAX-ACCESS not-accessible
    STATUS     current
    DESCRIPTION
        ""
    INDEX {
        lcsSetupIpRouterNNNatEntryIdx
    }
    ::= { lcsSetupIpRouterNNNatTable 1 }

-- {SEQUENCE}
LcsSetupIpRouterNNNatEntry ::= SEQUENCE {
    lcsSetupIpRouterNNNatEntryIdx DisplayString,
    lcsSetupIpRouterNNNatEntrySrcAddress IpAddress,
    lcsSetupIpRouterNNNatEntrySrcMask IpAddress,
    lcsSetupIpRouterNNNatEntryDstStation DisplayString,
    lcsSetupIpRouterNNNatEntryMappedNetwork IpAddress
}

-- {COLUMN} 1712.2.8.19.1.1
lcsSetupIpRouterNNNatEntryIdx OBJECT-TYPE
    SYNTAX     DisplayString (SIZE(0..4))
    MAX-ACCESS read-write
    STATUS     current
    DESCRIPTION
        "-- empty --"
    ::= { lcsSetupIpRouterNNNatEntry 1 }

-- {COLUMN} 1712.2.8.19.1.2
lcsSetupIpRouterNNNatEntrySrcAddress OBJECT-TYPE
    SYNTAX     IpAddress
    MAX-ACCESS read-write
    STATUS     current
    DESCRIPTION
        "-- empty --"
    ::= { lcsSetupIpRouterNNNatEntry 2 }

-- {COLUMN} 1712.2.8.19.1.3
lcsSetupIpRouterNNNatEntrySrcMask OBJECT-TYPE
    SYNTAX     IpAddress
    MAX-ACCESS read-write
    STATUS     current
    DESCRIPTION
        "-- empty --"
    ::= { lcsSetupIpRouterNNNatEntry 3 }

-- {COLUMN} 1712.2.8.19.1.4
lcsSetupIpRouterNNNatEntryDstStation OBJECT-TYPE
    SYNTAX     DisplayString (SIZE(0..16))
    MAX-ACCESS read-write
    STATUS     current
    DESCRIPTION
        "-- empty --"
    ::= { lcsSetupIpRouterNNNatEntry 4 }

-- {COLUMN} 1712.2.8.19.1.5
lcsSetupIpRouterNNNatEntryMappedNetwork OBJECT-TYPE
    SYNTAX     IpAddress
    MAX-ACCESS read-write
    STATUS     current
    DESCRIPTION
        "-- empty --"
    ::= { lcsSetupIpRouterNNNatEntry 5 }

-- {SCALAR} 1712.2.8.22
lcsSetupIpRouterWanTagCreation OBJECT-TYPE
    SYNTAX     INTEGER
      {
        eManual (0),
        eAuto (1)
      }
    MAX-ACCESS read-write
    STATUS     current
    DESCRIPTION
        "-- empty --"
    ::= { lcsSetupIpRouter 22 }

-- {TABLE} 1712.2.8.23
lcsSetupIpRouterTagTableTable OBJECT-TYPE
    SYNTAX     SEQUENCE OF LcsSetupIpRouterTagTableEntry
    MAX-ACCESS not-accessible
    STATUS     current
    DESCRIPTION
        "-- empty --"
    ::= { lcsSetupIpRouter 23 }

-- {ENTRY} 1712.2.8.23.1
lcsSetupIpRouterTagTableEntry OBJECT-TYPE
    SYNTAX     LcsSetupIpRouterTagTableEntry
    MAX-ACCESS not-accessible
    STATUS     current
    DESCRIPTION
        ""
    INDEX {
        lcsSetupIpRouterTagTableEntryPeer
    }
    ::= { lcsSetupIpRouterTagTableTable 1 }

-- {SEQUENCE}
LcsSetupIpRouterTagTableEntry ::= SEQUENCE {
    lcsSetupIpRouterTagTableEntryPeer DisplayString,
    lcsSetupIpRouterTagTableEntryRtgTag INTEGER,
    lcsSetupIpRouterTagTableEntryStartWanPool IpAddress,
    lcsSetupIpRouterTagTableEntryEndWanPool IpAddress,
    lcsSetupIpRouterTagTableEntryDnsDefault IpAddress,
    lcsSetupIpRouterTagTableEntryDnsBackup IpAddress,
    lcsSetupIpRouterTagTableEntryNbnsDefault IpAddress,
    lcsSetupIpRouterTagTableEntryNbnsBackup IpAddress
}

-- {COLUMN} 1712.2.8.23.1.1
lcsSetupIpRouterTagTableEntryPeer OBJECT-TYPE
    SYNTAX     DisplayString (SIZE(0..16))
    MAX-ACCESS read-write
    STATUS     current
    DESCRIPTION
        "-- empty --"
    ::= { lcsSetupIpRouterTagTableEntry 1 }

-- {COLUMN} 1712.2.8.23.1.2
lcsSetupIpRouterTagTableEntryRtgTag OBJECT-TYPE
    SYNTAX     INTEGER (0..65535)
    MAX-ACCESS read-write
    STATUS     current
    DESCRIPTION
        "-- empty --"
    ::= { lcsSetupIpRouterTagTableEntry 2 }

-- {COLUMN} 1712.2.8.23.1.3
lcsSetupIpRouterTagTableEntryStartWanPool OBJECT-TYPE
    SYNTAX     IpAddress
    MAX-ACCESS read-write
    STATUS     current
    DESCRIPTION
        "-- empty --"
    ::= { lcsSetupIpRouterTagTableEntry 3 }

-- {COLUMN} 1712.2.8.23.1.4
lcsSetupIpRouterTagTableEntryEndWanPool OBJECT-TYPE
    SYNTAX     IpAddress
    MAX-ACCESS read-write
    STATUS     current
    DESCRIPTION
        "-- empty --"
    ::= { lcsSetupIpRouterTagTableEntry 4 }

-- {COLUMN} 1712.2.8.23.1.5
lcsSetupIpRouterTagTableEntryDnsDefault OBJECT-TYPE
    SYNTAX     IpAddress
    MAX-ACCESS read-write
    STATUS     current
    DESCRIPTION
        "-- empty --"
    ::= { lcsSetupIpRouterTagTableEntry 5 }

-- {COLUMN} 1712.2.8.23.1.6
lcsSetupIpRouterTagTableEntryDnsBackup OBJECT-TYPE
    SYNTAX     IpAddress
    MAX-ACCESS read-write
    STATUS     current
    DESCRIPTION
        "-- empty --"
    ::= { lcsSetupIpRouterTagTableEntry 6 }

-- {COLUMN} 1712.2.8.23.1.7
lcsSetupIpRouterTagTableEntryNbnsDefault OBJECT-TYPE
    SYNTAX     IpAddress
    MAX-ACCESS read-write
    STATUS     current
    DESCRIPTION
        "-- empty --"
    ::= { lcsSetupIpRouterTagTableEntry 7 }

-- {COLUMN} 1712.2.8.23.1.8
lcsSetupIpRouterTagTableEntryNbnsBackup OBJECT-TYPE
    SYNTAX     IpAddress
    MAX-ACCESS read-write
    STATUS     current
    DESCRIPTION
        "-- empty --"
    ::= { lcsSetupIpRouterTagTableEntry 8 }

-- {OID} 1712.2.9
lcsSetupSnmp OBJECT IDENTIFIER ::= { lcsSetup 9 }

-- {SCALAR} 1712.2.9.1
lcsSetupSnmpSendTraps OBJECT-TYPE
    SYNTAX     INTEGER
      {
        eNo (0),
        eYes (1)
      }
    MAX-ACCESS read-write
    STATUS     current
    DESCRIPTION
        "-- empty --"
    ::= { lcsSetupSnmp 1 }

-- {TABLE} 1712.2.9.2
lcsSetupSnmpIpTrapsTable OBJECT-TYPE
    SYNTAX     SEQUENCE OF LcsSetupSnmpIpTrapsEntry
    MAX-ACCESS not-accessible
    STATUS     current
    DESCRIPTION
        "-- empty --"
    ::= { lcsSetupSnmp 2 }

-- {ENTRY} 1712.2.9.2.1
lcsSetupSnmpIpTrapsEntry OBJECT-TYPE
    SYNTAX     LcsSetupSnmpIpTrapsEntry
    MAX-ACCESS not-accessible
    STATUS     current
    DESCRIPTION
        ""
    INDEX {
        lcsSetupSnmpIpTrapsEntryTrapIp
    }
    ::= { lcsSetupSnmpIpTrapsTable 1 }

-- {SEQUENCE}
LcsSetupSnmpIpTrapsEntry ::= SEQUENCE {
    lcsSetupSnmpIpTrapsEntryTrapIp IpAddress,
    lcsSetupSnmpIpTrapsEntryLoopbackAddr DisplayString,
    lcsSetupSnmpIpTrapsEntryVersion INTEGER,
    lcsSetupSnmpIpTrapsEntryPort INTEGER
}

-- {COLUMN} 1712.2.9.2.1.1
lcsSetupSnmpIpTrapsEntryTrapIp OBJECT-TYPE
    SYNTAX     IpAddress
    MAX-ACCESS read-write
    STATUS     current
    DESCRIPTION
        "-- empty --"
    ::= { lcsSetupSnmpIpTrapsEntry 1 }

-- {COLUMN} 1712.2.9.2.1.3
lcsSetupSnmpIpTrapsEntryLoopbackAddr OBJECT-TYPE
    SYNTAX     DisplayString (SIZE(0..16))
    MAX-ACCESS read-write
    STATUS     current
    DESCRIPTION
        "-- empty --"
    ::= { lcsSetupSnmpIpTrapsEntry 3 }

-- {COLUMN} 1712.2.9.2.1.4
lcsSetupSnmpIpTrapsEntryVersion OBJECT-TYPE
    SYNTAX     INTEGER
      {
        eSnmpv1 (1),
        eSnmpv2 (0)
      }
    MAX-ACCESS read-write
    STATUS     current
    DESCRIPTION
        "-- empty --"
    ::= { lcsSetupSnmpIpTrapsEntry 4 }

-- {COLUMN} 1712.2.9.2.1.5
lcsSetupSnmpIpTrapsEntryPort OBJECT-TYPE
    SYNTAX     INTEGER (0..65535)
    MAX-ACCESS read-write
    STATUS     current
    DESCRIPTION
        "-- empty --"
    ::= { lcsSetupSnmpIpTrapsEntry 5 }

-- {SCALAR} 1712.2.9.3
lcsSetupSnmpAdministrator OBJECT-TYPE
    SYNTAX     DisplayString (SIZE(0..255))
    MAX-ACCESS read-write
    STATUS     current
    DESCRIPTION
        "-- empty --"
    ::= { lcsSetupSnmp 3 }

-- {SCALAR} 1712.2.9.4
lcsSetupSnmpLocation OBJECT-TYPE
    SYNTAX     DisplayString (SIZE(0..255))
    MAX-ACCESS read-write
    STATUS     current
    DESCRIPTION
        "-- empty --"
    ::= { lcsSetupSnmp 4 }

-- {SCALAR} 1712.2.9.5
lcsSetupSnmpRegisterMonitor OBJECT-TYPE
    SYNTAX     DisplayString
    MAX-ACCESS read-write
    STATUS     current
    DESCRIPTION
        "-- empty --"
    ::= { lcsSetupSnmp 5 }

-- {SCALAR} 1712.2.9.6
lcsSetupSnmpDeleteMonitor OBJECT-TYPE
    SYNTAX     DisplayString
    MAX-ACCESS read-write
    STATUS     current
    DESCRIPTION
        "-- empty --"
    ::= { lcsSetupSnmp 6 }

-- {TABLE} 1712.2.9.7
lcsSetupSnmpMonitorTableTable OBJECT-TYPE
    SYNTAX     SEQUENCE OF LcsSetupSnmpMonitorTableEntry
    MAX-ACCESS not-accessible
    STATUS     current
    DESCRIPTION
        "-- empty --"
    ::= { lcsSetupSnmp 7 }

-- {ENTRY} 1712.2.9.7.1
lcsSetupSnmpMonitorTableEntry OBJECT-TYPE
    SYNTAX     LcsSetupSnmpMonitorTableEntry
    MAX-ACCESS not-accessible
    STATUS     current
    DESCRIPTION
        ""
    INDEX {
        lcsSetupSnmpMonitorTableEntryIpAddress,
        lcsSetupSnmpMonitorTableEntryPort
    }
    ::= { lcsSetupSnmpMonitorTableTable 1 }

-- {SEQUENCE}
LcsSetupSnmpMonitorTableEntry ::= SEQUENCE {
    lcsSetupSnmpMonitorTableEntryIpAddress IpAddress,
    lcsSetupSnmpMonitorTableEntryPort INTEGER,
    lcsSetupSnmpMonitorTableEntryMacAddress DisplayString,
    lcsSetupSnmpMonitorTableEntryVlanId INTEGER,
    lcsSetupSnmpMonitorTableEntryTimeout INTEGER,
    lcsSetupSnmpMonitorTableEntryPeer DisplayString,
    lcsSetupSnmpMonitorTableEntryLoopbackAddr IpAddress,
    lcsSetupSnmpMonitorTableEntryLanIfc DisplayString,
    lcsSetupSnmpMonitorTableEntryEthernetPort INTEGER
}

-- {COLUMN} 1712.2.9.7.1.1
lcsSetupSnmpMonitorTableEntryIpAddress OBJECT-TYPE
    SYNTAX     IpAddress
    MAX-ACCESS read-only
    STATUS     current
    DESCRIPTION
        "-- empty --"
    ::= { lcsSetupSnmpMonitorTableEntry 1 }

-- {COLUMN} 1712.2.9.7.1.2
lcsSetupSnmpMonitorTableEntryPort OBJECT-TYPE
    SYNTAX     INTEGER (0..65535)
    MAX-ACCESS read-only
    STATUS     current
    DESCRIPTION
        "-- empty --"
    ::= { lcsSetupSnmpMonitorTableEntry 2 }

-- {COLUMN} 1712.2.9.7.1.4
lcsSetupSnmpMonitorTableEntryMacAddress OBJECT-TYPE
    SYNTAX     DisplayString (SIZE(0..12))
    MAX-ACCESS read-only
    STATUS     current
    DESCRIPTION
        "-- empty --"
    ::= { lcsSetupSnmpMonitorTableEntry 4 }

-- {COLUMN} 1712.2.9.7.1.7
lcsSetupSnmpMonitorTableEntryVlanId OBJECT-TYPE
    SYNTAX     INTEGER (0..65535)
    MAX-ACCESS read-only
    STATUS     current
    DESCRIPTION
        "-- empty --"
    ::= { lcsSetupSnmpMonitorTableEntry 7 }

-- {COLUMN} 1712.2.9.7.1.3
lcsSetupSnmpMonitorTableEntryTimeout OBJECT-TYPE
    SYNTAX     INTEGER (0..65535)
    MAX-ACCESS read-only
    STATUS     current
    DESCRIPTION
        "-- empty --"
    ::= { lcsSetupSnmpMonitorTableEntry 3 }

-- {COLUMN} 1712.2.9.7.1.5
lcsSetupSnmpMonitorTableEntryPeer OBJECT-TYPE
    SYNTAX     DisplayString (SIZE(0..16))
    MAX-ACCESS read-only
    STATUS     current
    DESCRIPTION
        "-- empty --"
    ::= { lcsSetupSnmpMonitorTableEntry 5 }

-- {COLUMN} 1712.2.9.7.1.6
lcsSetupSnmpMonitorTableEntryLoopbackAddr OBJECT-TYPE
    SYNTAX     IpAddress
    MAX-ACCESS read-only
    STATUS     current
    DESCRIPTION
        "-- empty --"
    ::= { lcsSetupSnmpMonitorTableEntry 6 }

-- {COLUMN} 1712.2.9.7.1.8
lcsSetupSnmpMonitorTableEntryLanIfc OBJECT-TYPE
    SYNTAX     DisplayString (SIZE(0..255))
    MAX-ACCESS read-only
    STATUS     current
    DESCRIPTION
        "-- empty --"
    ::= { lcsSetupSnmpMonitorTableEntry 8 }

-- {COLUMN} 1712.2.9.7.1.9
lcsSetupSnmpMonitorTableEntryEthernetPort OBJECT-TYPE
    SYNTAX     INTEGER (0..255)
    MAX-ACCESS read-only
    STATUS     current
    DESCRIPTION
        "-- empty --"
    ::= { lcsSetupSnmpMonitorTableEntry 9 }

-- {SCALAR} 1712.2.9.10
lcsSetupSnmpPasswordRequiredForSnmpReadAccess OBJECT-TYPE
    SYNTAX     INTEGER
      {
        eNo (0),
        eYes (1)
      }
    MAX-ACCESS read-write
    STATUS     current
    DESCRIPTION
        "-- empty --"
    ::= { lcsSetupSnmp 10 }

-- {SCALAR} 1712.2.9.15
lcsSetupSnmpReadOnlyCommunity OBJECT-TYPE
    SYNTAX     DisplayString (SIZE(0..31))
    MAX-ACCESS read-write
    STATUS     current
    DESCRIPTION
        "-- empty --"
    ::= { lcsSetupSnmp 15 }

-- {SCALAR} 1712.2.9.20
lcsSetupSnmpFullHostMib OBJECT-TYPE
    SYNTAX     INTEGER
      {
        eNo (0),
        eYes (1)
      }
    MAX-ACCESS read-write
    STATUS     current
    DESCRIPTION
        "-- empty --"
    ::= { lcsSetupSnmp 20 }

-- {SCALAR} 1712.2.9.21
lcsSetupSnmpPort OBJECT-TYPE
    SYNTAX     INTEGER (0..65535)
    MAX-ACCESS read-write
    STATUS     current
    DESCRIPTION
        "-- empty --"
    ::= { lcsSetupSnmp 21 }

-- {TABLE} 1712.2.9.22
lcsSetupSnmpReadOnlyCommunitiesTable OBJECT-TYPE
    SYNTAX     SEQUENCE OF LcsSetupSnmpReadOnlyCommunitiesEntry
    MAX-ACCESS not-accessible
    STATUS     current
    DESCRIPTION
        "-- empty --"
    ::= { lcsSetupSnmp 22 }

-- {ENTRY} 1712.2.9.22.1
lcsSetupSnmpReadOnlyCommunitiesEntry OBJECT-TYPE
    SYNTAX     LcsSetupSnmpReadOnlyCommunitiesEntry
    MAX-ACCESS not-accessible
    STATUS     current
    DESCRIPTION
        ""
    INDEX {
        lcsSetupSnmpReadOnlyCommunitiesEntryReadOnlyCommunity
    }
    ::= { lcsSetupSnmpReadOnlyCommunitiesTable 1 }

-- {SEQUENCE}
LcsSetupSnmpReadOnlyCommunitiesEntry ::= SEQUENCE {
    lcsSetupSnmpReadOnlyCommunitiesEntryReadOnlyCommunity DisplayString
}

-- {COLUMN} 1712.2.9.22.1.1
lcsSetupSnmpReadOnlyCommunitiesEntryReadOnlyCommunity OBJECT-TYPE
    SYNTAX     DisplayString (SIZE(0..31))
    MAX-ACCESS read-write
    STATUS     current
    DESCRIPTION
        "-- empty --"
    ::= { lcsSetupSnmpReadOnlyCommunitiesEntry 1 }

-- {SCALAR} 1712.2.9.11
lcsSetupSnmpComment1 OBJECT-TYPE
    SYNTAX     DisplayString (SIZE(0..255))
    MAX-ACCESS read-write
    STATUS     current
    DESCRIPTION
        "-- empty --"
    ::= { lcsSetupSnmp 11 }

-- {SCALAR} 1712.2.9.12
lcsSetupSnmpComment2 OBJECT-TYPE
    SYNTAX     DisplayString (SIZE(0..255))
    MAX-ACCESS read-write
    STATUS     current
    DESCRIPTION
        "-- empty --"
    ::= { lcsSetupSnmp 12 }

-- {SCALAR} 1712.2.9.13
lcsSetupSnmpComment3 OBJECT-TYPE
    SYNTAX     DisplayString (SIZE(0..255))
    MAX-ACCESS read-write
    STATUS     current
    DESCRIPTION
        "-- empty --"
    ::= { lcsSetupSnmp 13 }

-- {SCALAR} 1712.2.9.14
lcsSetupSnmpComment4 OBJECT-TYPE
    SYNTAX     DisplayString (SIZE(0..255))
    MAX-ACCESS read-write
    STATUS     current
    DESCRIPTION
        "-- empty --"
    ::= { lcsSetupSnmp 14 }

-- {SCALAR} 1712.2.9.16
lcsSetupSnmpComment5 OBJECT-TYPE
    SYNTAX     DisplayString (SIZE(0..255))
    MAX-ACCESS read-write
    STATUS     current
    DESCRIPTION
        "-- empty --"
    ::= { lcsSetupSnmp 16 }

-- {SCALAR} 1712.2.9.17
lcsSetupSnmpComment6 OBJECT-TYPE
    SYNTAX     DisplayString (SIZE(0..255))
    MAX-ACCESS read-write
    STATUS     current
    DESCRIPTION
        "-- empty --"
    ::= { lcsSetupSnmp 17 }

-- {SCALAR} 1712.2.9.18
lcsSetupSnmpComment7 OBJECT-TYPE
    SYNTAX     DisplayString (SIZE(0..255))
    MAX-ACCESS read-write
    STATUS     current
    DESCRIPTION
        "-- empty --"
    ::= { lcsSetupSnmp 18 }

-- {SCALAR} 1712.2.9.19
lcsSetupSnmpComment8 OBJECT-TYPE
    SYNTAX     DisplayString (SIZE(0..255))
    MAX-ACCESS read-write
    STATUS     current
    DESCRIPTION
        "-- empty --"
    ::= { lcsSetupSnmp 19 }

-- {OID} 1712.2.10
lcsSetupDhcp OBJECT IDENTIFIER ::= { lcsSetup 10 }

-- {TABLE} 1712.2.10.20
lcsSetupDhcpNetworkListTable OBJECT-TYPE
    SYNTAX     SEQUENCE OF LcsSetupDhcpNetworkListEntry
    MAX-ACCESS not-accessible
    STATUS     current
    DESCRIPTION
        "-- empty --"
    ::= { lcsSetupDhcp 20 }

-- {ENTRY} 1712.2.10.20.1
lcsSetupDhcpNetworkListEntry OBJECT-TYPE
    SYNTAX     LcsSetupDhcpNetworkListEntry
    MAX-ACCESS not-accessible
    STATUS     current
    DESCRIPTION
        ""
    INDEX {
        lcsSetupDhcpNetworkListEntryNetworkName
    }
    ::= { lcsSetupDhcpNetworkListTable 1 }

-- {SEQUENCE}
LcsSetupDhcpNetworkListEntry ::= SEQUENCE {
    lcsSetupDhcpNetworkListEntryNetworkName DisplayString,
    lcsSetupDhcpNetworkListEntryStartAddressPool IpAddress,
    lcsSetupDhcpNetworkListEntryEndAddressPool IpAddress,
    lcsSetupDhcpNetworkListEntryNetmask IpAddress,
    lcsSetupDhcpNetworkListEntryBroadcastAddress IpAddress,
    lcsSetupDhcpNetworkListEntryGatewayAddress IpAddress,
    lcsSetupDhcpNetworkListEntryDnsDefault IpAddress,
    lcsSetupDhcpNetworkListEntryDnsBackup IpAddress,
    lcsSetupDhcpNetworkListEntryNbnsDefault IpAddress,
    lcsSetupDhcpNetworkListEntryNbnsBackup IpAddress,
    lcsSetupDhcpNetworkListEntryOperating INTEGER,
    lcsSetupDhcpNetworkListEntryBroadcastBit INTEGER,
    lcsSetupDhcpNetworkListEntryMasterServer IpAddress,
    lcsSetupDhcpNetworkListEntry2ndMasterServer IpAddress,
    lcsSetupDhcpNetworkListEntry3rdMasterServer IpAddress,
    lcsSetupDhcpNetworkListEntry4thMasterServer IpAddress,
    lcsSetupDhcpNetworkListEntryCache INTEGER,
    lcsSetupDhcpNetworkListEntryAdaption INTEGER,
    lcsSetupDhcpNetworkListEntryCluster INTEGER
}

-- {COLUMN} 1712.2.10.20.1.1
lcsSetupDhcpNetworkListEntryNetworkName OBJECT-TYPE
    SYNTAX     DisplayString (SIZE(0..16))
    MAX-ACCESS read-write
    STATUS     current
    DESCRIPTION
        "-- empty --"
    ::= { lcsSetupDhcpNetworkListEntry 1 }

-- {COLUMN} 1712.2.10.20.1.2
lcsSetupDhcpNetworkListEntryStartAddressPool OBJECT-TYPE
    SYNTAX     IpAddress
    MAX-ACCESS read-write
    STATUS     current
    DESCRIPTION
        "-- empty --"
    ::= { lcsSetupDhcpNetworkListEntry 2 }

-- {COLUMN} 1712.2.10.20.1.3
lcsSetupDhcpNetworkListEntryEndAddressPool OBJECT-TYPE
    SYNTAX     IpAddress
    MAX-ACCESS read-write
    STATUS     current
    DESCRIPTION
        "-- empty --"
    ::= { lcsSetupDhcpNetworkListEntry 3 }

-- {COLUMN} 1712.2.10.20.1.4
lcsSetupDhcpNetworkListEntryNetmask OBJECT-TYPE
    SYNTAX     IpAddress
    MAX-ACCESS read-write
    STATUS     current
    DESCRIPTION
        "-- empty --"
    ::= { lcsSetupDhcpNetworkListEntry 4 }

-- {COLUMN} 1712.2.10.20.1.5
lcsSetupDhcpNetworkListEntryBroadcastAddress OBJECT-TYPE
    SYNTAX     IpAddress
    MAX-ACCESS read-write
    STATUS     current
    DESCRIPTION
        "-- empty --"
    ::= { lcsSetupDhcpNetworkListEntry 5 }

-- {COLUMN} 1712.2.10.20.1.6
lcsSetupDhcpNetworkListEntryGatewayAddress OBJECT-TYPE
    SYNTAX     IpAddress
    MAX-ACCESS read-write
    STATUS     current
    DESCRIPTION
        "-- empty --"
    ::= { lcsSetupDhcpNetworkListEntry 6 }

-- {COLUMN} 1712.2.10.20.1.7
lcsSetupDhcpNetworkListEntryDnsDefault OBJECT-TYPE
    SYNTAX     IpAddress
    MAX-ACCESS read-write
    STATUS     current
    DESCRIPTION
        "-- empty --"
    ::= { lcsSetupDhcpNetworkListEntry 7 }

-- {COLUMN} 1712.2.10.20.1.8
lcsSetupDhcpNetworkListEntryDnsBackup OBJECT-TYPE
    SYNTAX     IpAddress
    MAX-ACCESS read-write
    STATUS     current
    DESCRIPTION
        "-- empty --"
    ::= { lcsSetupDhcpNetworkListEntry 8 }

-- {COLUMN} 1712.2.10.20.1.9
lcsSetupDhcpNetworkListEntryNbnsDefault OBJECT-TYPE
    SYNTAX     IpAddress
    MAX-ACCESS read-write
    STATUS     current
    DESCRIPTION
        "-- empty --"
    ::= { lcsSetupDhcpNetworkListEntry 9 }

-- {COLUMN} 1712.2.10.20.1.10
lcsSetupDhcpNetworkListEntryNbnsBackup OBJECT-TYPE
    SYNTAX     IpAddress
    MAX-ACCESS read-write
    STATUS     current
    DESCRIPTION
        "-- empty --"
    ::= { lcsSetupDhcpNetworkListEntry 10 }

-- {COLUMN} 1712.2.10.20.1.11
lcsSetupDhcpNetworkListEntryOperating OBJECT-TYPE
    SYNTAX     INTEGER
      {
        eNo (0),
        eYes (1),
        eAuto (2),
        eRelay (16),
        eClient (4)
      }
    MAX-ACCESS read-write
    STATUS     current
    DESCRIPTION
        "-- empty --"
    ::= { lcsSetupDhcpNetworkListEntry 11 }

-- {COLUMN} 1712.2.10.20.1.12
lcsSetupDhcpNetworkListEntryBroadcastBit OBJECT-TYPE
    SYNTAX     INTEGER
      {
        eNo (0),
        eYes (1)
      }
    MAX-ACCESS read-write
    STATUS     current
    DESCRIPTION
        "-- empty --"
    ::= { lcsSetupDhcpNetworkListEntry 12 }

-- {COLUMN} 1712.2.10.20.1.13
lcsSetupDhcpNetworkListEntryMasterServer OBJECT-TYPE
    SYNTAX     IpAddress
    MAX-ACCESS read-write
    STATUS     current
    DESCRIPTION
        "-- empty --"
    ::= { lcsSetupDhcpNetworkListEntry 13 }

-- {COLUMN} 1712.2.10.20.1.17
lcsSetupDhcpNetworkListEntry2ndMasterServer OBJECT-TYPE
    SYNTAX     IpAddress
    MAX-ACCESS read-write
    STATUS     current
    DESCRIPTION
        "-- empty --"
    ::= { lcsSetupDhcpNetworkListEntry 17 }

-- {COLUMN} 1712.2.10.20.1.18
lcsSetupDhcpNetworkListEntry3rdMasterServer OBJECT-TYPE
    SYNTAX     IpAddress
    MAX-ACCESS read-write
    STATUS     current
    DESCRIPTION
        "-- empty --"
    ::= { lcsSetupDhcpNetworkListEntry 18 }

-- {COLUMN} 1712.2.10.20.1.19
lcsSetupDhcpNetworkListEntry4thMasterServer OBJECT-TYPE
    SYNTAX     IpAddress
    MAX-ACCESS read-write
    STATUS     current
    DESCRIPTION
        "-- empty --"
    ::= { lcsSetupDhcpNetworkListEntry 19 }

-- {COLUMN} 1712.2.10.20.1.14
lcsSetupDhcpNetworkListEntryCache OBJECT-TYPE
    SYNTAX     INTEGER
      {
        eNo (0),
        eYes (1)
      }
    MAX-ACCESS read-write
    STATUS     current
    DESCRIPTION
        "-- empty --"
    ::= { lcsSetupDhcpNetworkListEntry 14 }

-- {COLUMN} 1712.2.10.20.1.15
lcsSetupDhcpNetworkListEntryAdaption OBJECT-TYPE
    SYNTAX     INTEGER
      {
        eNo (0),
        eYes (1)
      }
    MAX-ACCESS read-write
    STATUS     current
    DESCRIPTION
        "-- empty --"
    ::= { lcsSetupDhcpNetworkListEntry 15 }

-- {COLUMN} 1712.2.10.20.1.16
lcsSetupDhcpNetworkListEntryCluster OBJECT-TYPE
    SYNTAX     INTEGER
      {
        eNo (0),
        eYes (1)
      }
    MAX-ACCESS read-write
    STATUS     current
    DESCRIPTION
        "-- empty --"
    ::= { lcsSetupDhcpNetworkListEntry 16 }

-- {TABLE} 1712.2.10.18
lcsSetupDhcpPortsTable OBJECT-TYPE
    SYNTAX     SEQUENCE OF LcsSetupDhcpPortsEntry
    MAX-ACCESS not-accessible
    STATUS     current
    DESCRIPTION
        "-- empty --"
    ::= { lcsSetupDhcp 18 }

-- {ENTRY} 1712.2.10.18.1
lcsSetupDhcpPortsEntry OBJECT-TYPE
    SYNTAX     LcsSetupDhcpPortsEntry
    MAX-ACCESS not-accessible
    STATUS     current
    DESCRIPTION
        ""
    INDEX {
        lcsSetupDhcpPortsEntryPort
    }
    ::= { lcsSetupDhcpPortsTable 1 }

-- {SEQUENCE}
LcsSetupDhcpPortsEntry ::= SEQUENCE {
    lcsSetupDhcpPortsEntryPort DisplayString,
    lcsSetupDhcpPortsEntryEnableDhcp INTEGER
}

-- {COLUMN} 1712.2.10.18.1.2
lcsSetupDhcpPortsEntryPort OBJECT-TYPE
    SYNTAX     DisplayString (SIZE(0..18))
    MAX-ACCESS read-only
    STATUS     current
    DESCRIPTION
        "-- empty --"
    ::= { lcsSetupDhcpPortsEntry 2 }

-- {COLUMN} 1712.2.10.18.1.3
lcsSetupDhcpPortsEntryEnableDhcp OBJECT-TYPE
    SYNTAX     INTEGER
      {
        eNo (0),
        eYes (1)
      }
    MAX-ACCESS read-write
    STATUS     current
    DESCRIPTION
        "-- empty --"
    ::= { lcsSetupDhcpPortsEntry 3 }

-- {SCALAR} 1712.2.10.6
lcsSetupDhcpMaxLeaseTimeMinutes OBJECT-TYPE
    SYNTAX     INTEGER (0..2147483647)
    MAX-ACCESS read-write
    STATUS     current
    DESCRIPTION
        "-- empty --"
    ::= { lcsSetupDhcp 6 }

-- {SCALAR} 1712.2.10.7
lcsSetupDhcpDefaultLeaseTimeMinutes OBJECT-TYPE
    SYNTAX     INTEGER (0..2147483647)
    MAX-ACCESS read-write
    STATUS     current
    DESCRIPTION
        "-- empty --"
    ::= { lcsSetupDhcp 7 }

-- {TABLE} 1712.2.10.8
lcsSetupDhcpDhcpTableTable OBJECT-TYPE
    SYNTAX     SEQUENCE OF LcsSetupDhcpDhcpTableEntry
    MAX-ACCESS not-accessible
    STATUS     current
    DESCRIPTION
        "-- empty --"
    ::= { lcsSetupDhcp 8 }

-- {ENTRY} 1712.2.10.8.1
lcsSetupDhcpDhcpTableEntry OBJECT-TYPE
    SYNTAX     LcsSetupDhcpDhcpTableEntry
    MAX-ACCESS not-accessible
    STATUS     current
    DESCRIPTION
        ""
    INDEX {
        lcsSetupDhcpDhcpTableEntryIpAddress,
        lcsSetupDhcpDhcpTableEntryNetworkName
    }
    ::= { lcsSetupDhcpDhcpTableTable 1 }

-- {SEQUENCE}
LcsSetupDhcpDhcpTableEntry ::= SEQUENCE {
    lcsSetupDhcpDhcpTableEntryIpAddress IpAddress,
    lcsSetupDhcpDhcpTableEntryMacAddress DisplayString,
    lcsSetupDhcpDhcpTableEntryTimeout INTEGER,
    lcsSetupDhcpDhcpTableEntryHostname DisplayString,
    lcsSetupDhcpDhcpTableEntryType BITS,
    lcsSetupDhcpDhcpTableEntryLanIfc INTEGER,
    lcsSetupDhcpDhcpTableEntryEthernetPort INTEGER,
    lcsSetupDhcpDhcpTableEntryVlanId INTEGER,
    lcsSetupDhcpDhcpTableEntryNetworkName DisplayString,
    lcsSetupDhcpDhcpTableEntryAssignment DisplayString,
    lcsSetupDhcpDhcpTableEntryAssignmentNumeric Gauge32
}

-- {COLUMN} 1712.2.10.8.1.1
lcsSetupDhcpDhcpTableEntryIpAddress OBJECT-TYPE
    SYNTAX     IpAddress
    MAX-ACCESS read-only
    STATUS     current
    DESCRIPTION
        "-- empty --"
    ::= { lcsSetupDhcpDhcpTableEntry 1 }

-- {COLUMN} 1712.2.10.8.1.2
lcsSetupDhcpDhcpTableEntryMacAddress OBJECT-TYPE
    SYNTAX     DisplayString (SIZE(0..12))
    MAX-ACCESS read-only
    STATUS     current
    DESCRIPTION
        "-- empty --"
    ::= { lcsSetupDhcpDhcpTableEntry 2 }

-- {COLUMN} 1712.2.10.8.1.3
lcsSetupDhcpDhcpTableEntryTimeout OBJECT-TYPE
    SYNTAX     INTEGER (0..2147483647)
    MAX-ACCESS read-only
    STATUS     current
    DESCRIPTION
        "-- empty --"
    ::= { lcsSetupDhcpDhcpTableEntry 3 }

-- {COLUMN} 1712.2.10.8.1.4
lcsSetupDhcpDhcpTableEntryHostname OBJECT-TYPE
    SYNTAX     DisplayString (SIZE(0..65))
    MAX-ACCESS read-only
    STATUS     current
    DESCRIPTION
        "-- empty --"
    ::= { lcsSetupDhcpDhcpTableEntry 4 }

-- {COLUMN} 1712.2.10.8.1.5
lcsSetupDhcpDhcpTableEntryType OBJECT-TYPE
    SYNTAX     BITS
      {
        enew (15),
        enewreq (14),
        eDyn (11),
        eUnkn (13),
        eStat (12),
        eBootp (10),
        eRelay (4),
        eCache (8)
      }
    MAX-ACCESS read-only
    STATUS     current
    DESCRIPTION
        "-- empty --"
    ::= { lcsSetupDhcpDhcpTableEntry 5 }

-- {COLUMN} 1712.2.10.8.1.10
lcsSetupDhcpDhcpTableEntryLanIfc OBJECT-TYPE
    SYNTAX     INTEGER
      {
        eLan1 (256),
        eLan2 (257),
        eLan3 (258),
        eLan4 (259),
        eAny (65535)
      }
    MAX-ACCESS read-only
    STATUS     current
    DESCRIPTION
        "-- empty --"
    ::= { lcsSetupDhcpDhcpTableEntry 10 }

-- {COLUMN} 1712.2.10.8.1.7
lcsSetupDhcpDhcpTableEntryEthernetPort OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsSetupDhcpDhcpTableEntry 7 }

-- {COLUMN} 1712.2.10.8.1.8
lcsSetupDhcpDhcpTableEntryVlanId OBJECT-TYPE
    SYNTAX     INTEGER (0..65535)
    MAX-ACCESS read-only
    STATUS     current
    DESCRIPTION
        "-- empty --"
    ::= { lcsSetupDhcpDhcpTableEntry 8 }

-- {COLUMN} 1712.2.10.8.1.9
lcsSetupDhcpDhcpTableEntryNetworkName OBJECT-TYPE
    SYNTAX     DisplayString (SIZE(0..17))
    MAX-ACCESS read-only
    STATUS     current
    DESCRIPTION
        "-- empty --"
    ::= { lcsSetupDhcpDhcpTableEntry 9 }

-- {COLUMN} 1712.2.10.8.1.11
lcsSetupDhcpDhcpTableEntryAssignment OBJECT-TYPE
    SYNTAX     DisplayString (SIZE(0..21))
    MAX-ACCESS read-only
    STATUS     current
    DESCRIPTION
        "-- empty --"
    ::= { lcsSetupDhcpDhcpTableEntry 11 }

-- {COLUMN} 1712.2.10.8.1.12
lcsSetupDhcpDhcpTableEntryAssignmentNumeric OBJECT-TYPE
    SYNTAX     Gauge32
    MAX-ACCESS read-only
    STATUS     current
    DESCRIPTION
        "-- empty --"
    ::= { lcsSetupDhcpDhcpTableEntry 12 }

-- {TABLE} 1712.2.10.9
lcsSetupDhcpHostsTable OBJECT-TYPE
    SYNTAX     SEQUENCE OF LcsSetupDhcpHostsEntry
    MAX-ACCESS not-accessible
    STATUS     current
    DESCRIPTION
        "-- empty --"
    ::= { lcsSetupDhcp 9 }

-- {ENTRY} 1712.2.10.9.1
lcsSetupDhcpHostsEntry OBJECT-TYPE
    SYNTAX     LcsSetupDhcpHostsEntry
    MAX-ACCESS not-accessible
    STATUS     current
    DESCRIPTION
        ""
    INDEX {
        lcsSetupDhcpHostsEntryMacAddress,
        lcsSetupDhcpHostsEntryNetworkName
    }
    ::= { lcsSetupDhcpHostsTable 1 }

-- {SEQUENCE}
LcsSetupDhcpHostsEntry ::= SEQUENCE {
    lcsSetupDhcpHostsEntryMacAddress DisplayString,
    lcsSetupDhcpHostsEntryNetworkName DisplayString,
    lcsSetupDhcpHostsEntryIpAddress IpAddress,
    lcsSetupDhcpHostsEntryHostname DisplayString,
    lcsSetupDhcpHostsEntryImageAlias DisplayString
}

-- {COLUMN} 1712.2.10.9.1.1
lcsSetupDhcpHostsEntryMacAddress OBJECT-TYPE
    SYNTAX     DisplayString (SIZE(0..12))
    MAX-ACCESS read-write
    STATUS     current
    DESCRIPTION
        "-- empty --"
    ::= { lcsSetupDhcpHostsEntry 1 }

-- {COLUMN} 1712.2.10.9.1.5
lcsSetupDhcpHostsEntryNetworkName OBJECT-TYPE
    SYNTAX     DisplayString (SIZE(0..16))
    MAX-ACCESS read-write
    STATUS     current
    DESCRIPTION
        "-- empty --"
    ::= { lcsSetupDhcpHostsEntry 5 }

-- {COLUMN} 1712.2.10.9.1.2
lcsSetupDhcpHostsEntryIpAddress OBJECT-TYPE
    SYNTAX     IpAddress
    MAX-ACCESS read-write
    STATUS     current
    DESCRIPTION
        "-- empty --"
    ::= { lcsSetupDhcpHostsEntry 2 }

-- {COLUMN} 1712.2.10.9.1.3
lcsSetupDhcpHostsEntryHostname OBJECT-TYPE
    SYNTAX     DisplayString (SIZE(0..30))
    MAX-ACCESS read-write
    STATUS     current
    DESCRIPTION
        "-- empty --"
    ::= { lcsSetupDhcpHostsEntry 3 }

-- {COLUMN} 1712.2.10.9.1.4
lcsSetupDhcpHostsEntryImageAlias OBJECT-TYPE
    SYNTAX     DisplayString (SIZE(0..16))
    MAX-ACCESS read-write
    STATUS     current
    DESCRIPTION
        "-- empty --"
    ::= { lcsSetupDhcpHostsEntry 4 }

-- {TABLE} 1712.2.10.10
lcsSetupDhcpAliasListTable OBJECT-TYPE
    SYNTAX     SEQUENCE OF LcsSetupDhcpAliasListEntry
    MAX-ACCESS not-accessible
    STATUS     current
    DESCRIPTION
        "-- empty --"
    ::= { lcsSetupDhcp 10 }

-- {ENTRY} 1712.2.10.10.1
lcsSetupDhcpAliasListEntry OBJECT-TYPE
    SYNTAX     LcsSetupDhcpAliasListEntry
    MAX-ACCESS not-accessible
    STATUS     current
    DESCRIPTION
        ""
    INDEX {
        lcsSetupDhcpAliasListEntryImageAlias
    }
    ::= { lcsSetupDhcpAliasListTable 1 }

-- {SEQUENCE}
LcsSetupDhcpAliasListEntry ::= SEQUENCE {
    lcsSetupDhcpAliasListEntryImageAlias DisplayString,
    lcsSetupDhcpAliasListEntryImageServer IpAddress,
    lcsSetupDhcpAliasListEntryImageFile DisplayString
}

-- {COLUMN} 1712.2.10.10.1.1
lcsSetupDhcpAliasListEntryImageAlias OBJECT-TYPE
    SYNTAX     DisplayString (SIZE(0..16))
    MAX-ACCESS read-write
    STATUS     current
    DESCRIPTION
        "-- empty --"
    ::= { lcsSetupDhcpAliasListEntry 1 }

-- {COLUMN} 1712.2.10.10.1.3
lcsSetupDhcpAliasListEntryImageServer OBJECT-TYPE
    SYNTAX     IpAddress
    MAX-ACCESS read-write
    STATUS     current
    DESCRIPTION
        "-- empty --"
    ::= { lcsSetupDhcpAliasListEntry 3 }

-- {COLUMN} 1712.2.10.10.1.2
lcsSetupDhcpAliasListEntryImageFile OBJECT-TYPE
    SYNTAX     DisplayString (SIZE(0..60))
    MAX-ACCESS read-write
    STATUS     current
    DESCRIPTION
        "-- empty --"
    ::= { lcsSetupDhcpAliasListEntry 2 }

-- {TABLE} 1712.2.10.21
lcsSetupDhcpAdditionalOptionsTable OBJECT-TYPE
    SYNTAX     SEQUENCE OF LcsSetupDhcpAdditionalOptionsEntry
    MAX-ACCESS not-accessible
    STATUS     current
    DESCRIPTION
        "-- empty --"
    ::= { lcsSetupDhcp 21 }

-- {ENTRY} 1712.2.10.21.1
lcsSetupDhcpAdditionalOptionsEntry OBJECT-TYPE
    SYNTAX     LcsSetupDhcpAdditionalOptionsEntry
    MAX-ACCESS not-accessible
    STATUS     current
    DESCRIPTION
        ""
    INDEX {
        lcsSetupDhcpAdditionalOptionsEntryOptionNumber,
        lcsSetupDhcpAdditionalOptionsEntryNetworkName
    }
    ::= { lcsSetupDhcpAdditionalOptionsTable 1 }

-- {SEQUENCE}
LcsSetupDhcpAdditionalOptionsEntry ::= SEQUENCE {
    lcsSetupDhcpAdditionalOptionsEntryOptionNumber INTEGER,
    lcsSetupDhcpAdditionalOptionsEntryNetworkName DisplayString,
    lcsSetupDhcpAdditionalOptionsEntryOptionType INTEGER,
    lcsSetupDhcpAdditionalOptionsEntryOptionValue DisplayString
}

-- {COLUMN} 1712.2.10.21.1.1
lcsSetupDhcpAdditionalOptionsEntryOptionNumber OBJECT-TYPE
    SYNTAX     INTEGER (0..255)
    MAX-ACCESS read-write
    STATUS     current
    DESCRIPTION
        "-- empty --"
    ::= { lcsSetupDhcpAdditionalOptionsEntry 1 }

-- {COLUMN} 1712.2.10.21.1.2
lcsSetupDhcpAdditionalOptionsEntryNetworkName OBJECT-TYPE
    SYNTAX     DisplayString (SIZE(0..16))
    MAX-ACCESS read-write
    STATUS     current
    DESCRIPTION
        "-- empty --"
    ::= { lcsSetupDhcpAdditionalOptionsEntry 2 }

-- {COLUMN} 1712.2.10.21.1.4
lcsSetupDhcpAdditionalOptionsEntryOptionType OBJECT-TYPE
    SYNTAX     INTEGER
      {
        eString (0),
        eInteger32 (1),
        eInteger16 (3),
        eInteger8 (4),
        eIpAddress (2)
      }
    MAX-ACCESS read-write
    STATUS     current
    DESCRIPTION
        "-- empty --"
    ::= { lcsSetupDhcpAdditionalOptionsEntry 4 }

-- {COLUMN} 1712.2.10.21.1.3
lcsSetupDhcpAdditionalOptionsEntryOptionValue OBJECT-TYPE
    SYNTAX     DisplayString (SIZE(0..128))
    MAX-ACCESS read-write
    STATUS     current
    DESCRIPTION
        "-- empty --"
    ::= { lcsSetupDhcpAdditionalOptionsEntry 3 }

-- {SCALAR} 1712.2.10.19
lcsSetupDhcpUserClassIdentifer OBJECT-TYPE
    SYNTAX     DisplayString (SIZE(0..63))
    MAX-ACCESS read-write
    STATUS     current
    DESCRIPTION
        "-- empty --"
    ::= { lcsSetupDhcp 19 }

-- {SCALAR} 1712.2.10.22
lcsSetupDhcpVendorClassIdentifer OBJECT-TYPE
    SYNTAX     DisplayString (SIZE(0..63))
    MAX-ACCESS read-write
    STATUS     current
    DESCRIPTION
        "-- empty --"
    ::= { lcsSetupDhcp 22 }

-- {OID} 1712.2.17
lcsSetupDns OBJECT IDENTIFIER ::= { lcsSetup 17 }

-- {SCALAR} 1712.2.17.1
lcsSetupDnsOperating OBJECT-TYPE
    SYNTAX     INTEGER
      {
        eNo (0),
        eYes (1)
      }
    MAX-ACCESS read-write
    STATUS     current
    DESCRIPTION
        "-- empty --"
    ::= { lcsSetupDns 1 }

-- {SCALAR} 1712.2.17.14
lcsSetupDnsForwarder OBJECT-TYPE
    SYNTAX     INTEGER
      {
        eNo (0),
        eYes (1)
      }
    MAX-ACCESS read-write
    STATUS     current
    DESCRIPTION
        "-- empty --"
    ::= { lcsSetupDns 14 }

-- {SCALAR} 1712.2.17.3
lcsSetupDnsDhcpUsage OBJECT-TYPE
    SYNTAX     INTEGER
      {
        eNo (0),
        eYes (1)
      }
    MAX-ACCESS read-write
    STATUS     current
    DESCRIPTION
        "-- empty --"
    ::= { lcsSetupDns 3 }

-- {SCALAR} 1712.2.17.4
lcsSetupDnsNetbiosUsage OBJECT-TYPE
    SYNTAX     INTEGER
      {
        eNo (0),
        eYes (1)
      }
    MAX-ACCESS read-write
    STATUS     current
    DESCRIPTION
        "-- empty --"
    ::= { lcsSetupDns 4 }

-- {SCALAR} 1712.2.17.12
lcsSetupDnsResolveDomain OBJECT-TYPE
    SYNTAX     INTEGER
      {
        eNo (0),
        eYes (1)
      }
    MAX-ACCESS read-write
    STATUS     current
    DESCRIPTION
        "-- empty --"
    ::= { lcsSetupDns 12 }

-- {SCALAR} 1712.2.17.7
lcsSetupDnsLeasetime OBJECT-TYPE
    SYNTAX     INTEGER (0..65535)
    MAX-ACCESS read-write
    STATUS     current
    DESCRIPTION
        "-- empty --"
    ::= { lcsSetupDns 7 }

-- {TABLE} 1712.2.17.15
lcsSetupDnsTagConfigurationTable OBJECT-TYPE
    SYNTAX     SEQUENCE OF LcsSetupDnsTagConfigurationEntry
    MAX-ACCESS not-accessible
    STATUS     current
    DESCRIPTION
        "-- empty --"
    ::= { lcsSetupDns 15 }

-- {ENTRY} 1712.2.17.15.1
lcsSetupDnsTagConfigurationEntry OBJECT-TYPE
    SYNTAX     LcsSetupDnsTagConfigurationEntry
    MAX-ACCESS not-accessible
    STATUS     current
    DESCRIPTION
        ""
    INDEX {
        lcsSetupDnsTagConfigurationEntryRtgTag
    }
    ::= { lcsSetupDnsTagConfigurationTable 1 }

-- {SEQUENCE}
LcsSetupDnsTagConfigurationEntry ::= SEQUENCE {
    lcsSetupDnsTagConfigurationEntryRtgTag INTEGER,
    lcsSetupDnsTagConfigurationEntryOperating INTEGER,
    lcsSetupDnsTagConfigurationEntryForwarder INTEGER,
    lcsSetupDnsTagConfigurationEntryDhcpUsage INTEGER,
    lcsSetupDnsTagConfigurationEntryNetbiosUsage INTEGER,
    lcsSetupDnsTagConfigurationEntryResolveDomain INTEGER
}

-- {COLUMN} 1712.2.17.15.1.1
lcsSetupDnsTagConfigurationEntryRtgTag OBJECT-TYPE
    SYNTAX     INTEGER (0..65535)
    MAX-ACCESS read-write
    STATUS     current
    DESCRIPTION
        "-- empty --"
    ::= { lcsSetupDnsTagConfigurationEntry 1 }

-- {COLUMN} 1712.2.17.15.1.2
lcsSetupDnsTagConfigurationEntryOperating OBJECT-TYPE
    SYNTAX     INTEGER
      {
        eNo (0),
        eYes (1)
      }
    MAX-ACCESS read-write
    STATUS     current
    DESCRIPTION
        "-- empty --"
    ::= { lcsSetupDnsTagConfigurationEntry 2 }

-- {COLUMN} 1712.2.17.15.1.3
lcsSetupDnsTagConfigurationEntryForwarder OBJECT-TYPE
    SYNTAX     INTEGER
      {
        eNo (0),
        eYes (1)
      }
    MAX-ACCESS read-write
    STATUS     current
    DESCRIPTION
        "-- empty --"
    ::= { lcsSetupDnsTagConfigurationEntry 3 }

-- {COLUMN} 1712.2.17.15.1.4
lcsSetupDnsTagConfigurationEntryDhcpUsage OBJECT-TYPE
    SYNTAX     INTEGER
      {
        eNo (0),
        eYes (1)
      }
    MAX-ACCESS read-write
    STATUS     current
    DESCRIPTION
        "-- empty --"
    ::= { lcsSetupDnsTagConfigurationEntry 4 }

-- {COLUMN} 1712.2.17.15.1.5
lcsSetupDnsTagConfigurationEntryNetbiosUsage OBJECT-TYPE
    SYNTAX     INTEGER
      {
        eNo (0),
        eYes (1)
      }
    MAX-ACCESS read-write
    STATUS     current
    DESCRIPTION
        "-- empty --"
    ::= { lcsSetupDnsTagConfigurationEntry 5 }

-- {COLUMN} 1712.2.17.15.1.6
lcsSetupDnsTagConfigurationEntryResolveDomain OBJECT-TYPE
    SYNTAX     INTEGER
      {
        eNo (0),
        eYes (1)
      }
    MAX-ACCESS read-write
    STATUS     current
    DESCRIPTION
        "-- empty --"
    ::= { lcsSetupDnsTagConfigurationEntry 6 }

-- {SCALAR} 1712.2.17.2
lcsSetupDnsDomain OBJECT-TYPE
    SYNTAX     DisplayString (SIZE(0..64))
    MAX-ACCESS read-write
    STATUS     current
    DESCRIPTION
        "-- empty --"
    ::= { lcsSetupDns 2 }

-- {TABLE} 1712.2.17.13
lcsSetupDnsSubDomainsTable OBJECT-TYPE
    SYNTAX     SEQUENCE OF LcsSetupDnsSubDomainsEntry
    MAX-ACCESS not-accessible
    STATUS     current
    DESCRIPTION
        "-- empty --"
    ::= { lcsSetupDns 13 }

-- {ENTRY} 1712.2.17.13.1
lcsSetupDnsSubDomainsEntry OBJECT-TYPE
    SYNTAX     LcsSetupDnsSubDomainsEntry
    MAX-ACCESS not-accessible
    STATUS     current
    DESCRIPTION
        ""
    INDEX {
        lcsSetupDnsSubDomainsEntryNetworkName
    }
    ::= { lcsSetupDnsSubDomainsTable 1 }

-- {SEQUENCE}
LcsSetupDnsSubDomainsEntry ::= SEQUENCE {
    lcsSetupDnsSubDomainsEntryNetworkName DisplayString,
    lcsSetupDnsSubDomainsEntrySubDomain DisplayString
}

-- {COLUMN} 1712.2.17.13.1.1
lcsSetupDnsSubDomainsEntryNetworkName OBJECT-TYPE
    SYNTAX     DisplayString (SIZE(0..16))
    MAX-ACCESS read-write
    STATUS     current
    DESCRIPTION
        "-- empty --"
    ::= { lcsSetupDnsSubDomainsEntry 1 }

-- {COLUMN} 1712.2.17.13.1.2
lcsSetupDnsSubDomainsEntrySubDomain OBJECT-TYPE
    SYNTAX     DisplayString (SIZE(0..64))
    MAX-ACCESS read-write
    STATUS     current
    DESCRIPTION
        "-- empty --"
    ::= { lcsSetupDnsSubDomainsEntry 2 }

-- {TABLE} 1712.2.17.5
lcsSetupDnsDnsListTable OBJECT-TYPE
    SYNTAX     SEQUENCE OF LcsSetupDnsDnsListEntry
    MAX-ACCESS not-accessible
    STATUS     current
    DESCRIPTION
        "-- empty --"
    ::= { lcsSetupDns 5 }

-- {ENTRY} 1712.2.17.5.1
lcsSetupDnsDnsListEntry OBJECT-TYPE
    SYNTAX     LcsSetupDnsDnsListEntry
    MAX-ACCESS not-accessible
    STATUS     current
    DESCRIPTION
        ""
    INDEX {
        lcsSetupDnsDnsListEntryHostName,
        lcsSetupDnsDnsListEntryRtgTag
    }
    ::= { lcsSetupDnsDnsListTable 1 }

-- {SEQUENCE}
LcsSetupDnsDnsListEntry ::= SEQUENCE {
    lcsSetupDnsDnsListEntryHostName DisplayString,
    lcsSetupDnsDnsListEntryRtgTag INTEGER,
    lcsSetupDnsDnsListEntryIpAddress IpAddress,
    lcsSetupDnsDnsListEntryIpv6Address DisplayString
}

-- {COLUMN} 1712.2.17.5.1.1
lcsSetupDnsDnsListEntryHostName OBJECT-TYPE
    SYNTAX     DisplayString (SIZE(0..64))
    MAX-ACCESS read-write
    STATUS     current
    DESCRIPTION
        "-- empty --"
    ::= { lcsSetupDnsDnsListEntry 1 }

-- {COLUMN} 1712.2.17.5.1.4
lcsSetupDnsDnsListEntryRtgTag OBJECT-TYPE
    SYNTAX     INTEGER (0..65535)
    MAX-ACCESS read-write
    STATUS     current
    DESCRIPTION
        "-- empty --"
    ::= { lcsSetupDnsDnsListEntry 4 }

-- {COLUMN} 1712.2.17.5.1.2
lcsSetupDnsDnsListEntryIpAddress OBJECT-TYPE
    SYNTAX     IpAddress
    MAX-ACCESS read-write
    STATUS     current
    DESCRIPTION
        "-- empty --"
    ::= { lcsSetupDnsDnsListEntry 2 }

-- {COLUMN} 1712.2.17.5.1.3
lcsSetupDnsDnsListEntryIpv6Address OBJECT-TYPE
    SYNTAX     DisplayString (SIZE(0..39))
    MAX-ACCESS read-write
    STATUS     current
    DESCRIPTION
        "-- empty --"
    ::= { lcsSetupDnsDnsListEntry 3 }

-- {TABLE} 1712.2.17.6
lcsSetupDnsFilterListTable OBJECT-TYPE
    SYNTAX     SEQUENCE OF LcsSetupDnsFilterListEntry
    MAX-ACCESS not-accessible
    STATUS     current
    DESCRIPTION
        "-- empty --"
    ::= { lcsSetupDns 6 }

-- {ENTRY} 1712.2.17.6.1
lcsSetupDnsFilterListEntry OBJECT-TYPE
    SYNTAX     LcsSetupDnsFilterListEntry
    MAX-ACCESS not-accessible
    STATUS     current
    DESCRIPTION
        ""
    INDEX {
        lcsSetupDnsFilterListEntryIdx
    }
    ::= { lcsSetupDnsFilterListTable 1 }

-- {SEQUENCE}
LcsSetupDnsFilterListEntry ::= SEQUENCE {
    lcsSetupDnsFilterListEntryIdx DisplayString,
    lcsSetupDnsFilterListEntryDomain DisplayString,
    lcsSetupDnsFilterListEntryRtgTag INTEGER,
    lcsSetupDnsFilterListEntryIpAddress IpAddress,
    lcsSetupDnsFilterListEntryNetmask IpAddress,
    lcsSetupDnsFilterListEntryIpv6Prefix DisplayString
}

-- {COLUMN} 1712.2.17.6.1.1
lcsSetupDnsFilterListEntryIdx OBJECT-TYPE
    SYNTAX     DisplayString (SIZE(0..4))
    MAX-ACCESS read-write
    STATUS     current
    DESCRIPTION
        "-- empty --"
    ::= { lcsSetupDnsFilterListEntry 1 }

-- {COLUMN} 1712.2.17.6.1.2
lcsSetupDnsFilterListEntryDomain OBJECT-TYPE
    SYNTAX     DisplayString (SIZE(0..64))
    MAX-ACCESS read-write
    STATUS     current
    DESCRIPTION
        "-- empty --"
    ::= { lcsSetupDnsFilterListEntry 2 }

-- {COLUMN} 1712.2.17.6.1.6
lcsSetupDnsFilterListEntryRtgTag OBJECT-TYPE
    SYNTAX     INTEGER (0..65535)
    MAX-ACCESS read-write
    STATUS     current
    DESCRIPTION
        "-- empty --"
    ::= { lcsSetupDnsFilterListEntry 6 }

-- {COLUMN} 1712.2.17.6.1.3
lcsSetupDnsFilterListEntryIpAddress OBJECT-TYPE
    SYNTAX     IpAddress
    MAX-ACCESS read-write
    STATUS     current
    DESCRIPTION
        "-- empty --"
    ::= { lcsSetupDnsFilterListEntry 3 }

-- {COLUMN} 1712.2.17.6.1.4
lcsSetupDnsFilterListEntryNetmask OBJECT-TYPE
    SYNTAX     IpAddress
    MAX-ACCESS read-write
    STATUS     current
    DESCRIPTION
        "-- empty --"
    ::= { lcsSetupDnsFilterListEntry 4 }

-- {COLUMN} 1712.2.17.6.1.5
lcsSetupDnsFilterListEntryIpv6Prefix OBJECT-TYPE
    SYNTAX     DisplayString (SIZE(0..43))
    MAX-ACCESS read-write
    STATUS     current
    DESCRIPTION
        "-- empty --"
    ::= { lcsSetupDnsFilterListEntry 5 }

-- {TABLE} 1712.2.17.9
lcsSetupDnsDnsDestinationsTable OBJECT-TYPE
    SYNTAX     SEQUENCE OF LcsSetupDnsDnsDestinationsEntry
    MAX-ACCESS not-accessible
    STATUS     current
    DESCRIPTION
        "-- empty --"
    ::= { lcsSetupDns 9 }

-- {ENTRY} 1712.2.17.9.1
lcsSetupDnsDnsDestinationsEntry OBJECT-TYPE
    SYNTAX     LcsSetupDnsDnsDestinationsEntry
    MAX-ACCESS not-accessible
    STATUS     current
    DESCRIPTION
        ""
    INDEX {
        lcsSetupDnsDnsDestinationsEntryDomainName,
        lcsSetupDnsDnsDestinationsEntryRtgTag
    }
    ::= { lcsSetupDnsDnsDestinationsTable 1 }

-- {SEQUENCE}
LcsSetupDnsDnsDestinationsEntry ::= SEQUENCE {
    lcsSetupDnsDnsDestinationsEntryDomainName DisplayString,
    lcsSetupDnsDnsDestinationsEntryRtgTag INTEGER,
    lcsSetupDnsDnsDestinationsEntryDestination DisplayString
}

-- {COLUMN} 1712.2.17.9.1.1
lcsSetupDnsDnsDestinationsEntryDomainName OBJECT-TYPE
    SYNTAX     DisplayString (SIZE(0..64))
    MAX-ACCESS read-write
    STATUS     current
    DESCRIPTION
        "-- empty --"
    ::= { lcsSetupDnsDnsDestinationsEntry 1 }

-- {COLUMN} 1712.2.17.9.1.3
lcsSetupDnsDnsDestinationsEntryRtgTag OBJECT-TYPE
    SYNTAX     INTEGER (0..65535)
    MAX-ACCESS read-write
    STATUS     current
    DESCRIPTION
        "-- empty --"
    ::= { lcsSetupDnsDnsDestinationsEntry 3 }

-- {COLUMN} 1712.2.17.9.1.2
lcsSetupDnsDnsDestinationsEntryDestination OBJECT-TYPE
    SYNTAX     DisplayString (SIZE(0..80))
    MAX-ACCESS read-write
    STATUS     current
    DESCRIPTION
        "-- empty --"
    ::= { lcsSetupDnsDnsDestinationsEntry 2 }

-- {TABLE} 1712.2.17.10
lcsSetupDnsServiceLocationListTable OBJECT-TYPE
    SYNTAX     SEQUENCE OF LcsSetupDnsServiceLocationListEntry
    MAX-ACCESS not-accessible
    STATUS     current
    DESCRIPTION
        "-- empty --"
    ::= { lcsSetupDns 10 }

-- {ENTRY} 1712.2.17.10.1
lcsSetupDnsServiceLocationListEntry OBJECT-TYPE
    SYNTAX     LcsSetupDnsServiceLocationListEntry
    MAX-ACCESS not-accessible
    STATUS     current
    DESCRIPTION
        ""
    INDEX {
        lcsSetupDnsServiceLocationListEntryServiceName,
        lcsSetupDnsServiceLocationListEntryRtgTag
    }
    ::= { lcsSetupDnsServiceLocationListTable 1 }

-- {SEQUENCE}
LcsSetupDnsServiceLocationListEntry ::= SEQUENCE {
    lcsSetupDnsServiceLocationListEntryServiceName DisplayString,
    lcsSetupDnsServiceLocationListEntryRtgTag INTEGER,
    lcsSetupDnsServiceLocationListEntryHostName DisplayString,
    lcsSetupDnsServiceLocationListEntryPort INTEGER
}

-- {COLUMN} 1712.2.17.10.1.1
lcsSetupDnsServiceLocationListEntryServiceName OBJECT-TYPE
    SYNTAX     DisplayString (SIZE(0..64))
    MAX-ACCESS read-write
    STATUS     current
    DESCRIPTION
        "-- empty --"
    ::= { lcsSetupDnsServiceLocationListEntry 1 }

-- {COLUMN} 1712.2.17.10.1.4
lcsSetupDnsServiceLocationListEntryRtgTag OBJECT-TYPE
    SYNTAX     INTEGER (0..65535)
    MAX-ACCESS read-write
    STATUS     current
    DESCRIPTION
        "-- empty --"
    ::= { lcsSetupDnsServiceLocationListEntry 4 }

-- {COLUMN} 1712.2.17.10.1.2
lcsSetupDnsServiceLocationListEntryHostName OBJECT-TYPE
    SYNTAX     DisplayString (SIZE(0..64))
    MAX-ACCESS read-write
    STATUS     current
    DESCRIPTION
        "-- empty --"
    ::= { lcsSetupDnsServiceLocationListEntry 2 }

-- {COLUMN} 1712.2.17.10.1.3
lcsSetupDnsServiceLocationListEntryPort OBJECT-TYPE
    SYNTAX     INTEGER (0..65535)
    MAX-ACCESS read-write
    STATUS     current
    DESCRIPTION
        "-- empty --"
    ::= { lcsSetupDnsServiceLocationListEntry 3 }

-- {TABLE} 1712.2.17.8
lcsSetupDnsDynDnsListTable OBJECT-TYPE
    SYNTAX     SEQUENCE OF LcsSetupDnsDynDnsListEntry
    MAX-ACCESS not-accessible
    STATUS     current
    DESCRIPTION
        "-- empty --"
    ::= { lcsSetupDns 8 }

-- {ENTRY} 1712.2.17.8.1
lcsSetupDnsDynDnsListEntry OBJECT-TYPE
    SYNTAX     LcsSetupDnsDynDnsListEntry
    MAX-ACCESS not-accessible
    STATUS     current
    DESCRIPTION
        ""
    INDEX {
        lcsSetupDnsDynDnsListEntryHostName,
        lcsSetupDnsDynDnsListEntryNetworkName
    }
    ::= { lcsSetupDnsDynDnsListTable 1 }

-- {SEQUENCE}
LcsSetupDnsDynDnsListEntry ::= SEQUENCE {
    lcsSetupDnsDynDnsListEntryHostName DisplayString,
    lcsSetupDnsDynDnsListEntryIpAddress IpAddress,
    lcsSetupDnsDynDnsListEntryIpv6Address DisplayString,
    lcsSetupDnsDynDnsListEntryTimeout INTEGER,
    lcsSetupDnsDynDnsListEntryNetworkName DisplayString
}

-- {COLUMN} 1712.2.17.8.1.1
lcsSetupDnsDynDnsListEntryHostName OBJECT-TYPE
    SYNTAX     DisplayString (SIZE(0..64))
    MAX-ACCESS read-only
    STATUS     current
    DESCRIPTION
        "-- empty --"
    ::= { lcsSetupDnsDynDnsListEntry 1 }

-- {COLUMN} 1712.2.17.8.1.2
lcsSetupDnsDynDnsListEntryIpAddress OBJECT-TYPE
    SYNTAX     IpAddress
    MAX-ACCESS read-only
    STATUS     current
    DESCRIPTION
        "-- empty --"
    ::= { lcsSetupDnsDynDnsListEntry 2 }

-- {COLUMN} 1712.2.17.8.1.4
lcsSetupDnsDynDnsListEntryIpv6Address OBJECT-TYPE
    SYNTAX     DisplayString (SIZE(0..255))
    MAX-ACCESS read-only
    STATUS     current
    DESCRIPTION
        "-- empty --"
    ::= { lcsSetupDnsDynDnsListEntry 4 }

-- {COLUMN} 1712.2.17.8.1.3
lcsSetupDnsDynDnsListEntryTimeout OBJECT-TYPE
    SYNTAX     INTEGER (0..2147483647)
    MAX-ACCESS read-only
    STATUS     current
    DESCRIPTION
        "-- empty --"
    ::= { lcsSetupDnsDynDnsListEntry 3 }

-- {COLUMN} 1712.2.17.8.1.5
lcsSetupDnsDynDnsListEntryNetworkName OBJECT-TYPE
    SYNTAX     DisplayString (SIZE(0..16))
    MAX-ACCESS read-only
    STATUS     current
    DESCRIPTION
        "-- empty --"
    ::= { lcsSetupDnsDynDnsListEntry 5 }

-- {TABLE} 1712.2.17.11
lcsSetupDnsDynamicSrvListTable OBJECT-TYPE
    SYNTAX     SEQUENCE OF LcsSetupDnsDynamicSrvListEntry
    MAX-ACCESS not-accessible
    STATUS     current
    DESCRIPTION
        "-- empty --"
    ::= { lcsSetupDns 11 }

-- {ENTRY} 1712.2.17.11.1
lcsSetupDnsDynamicSrvListEntry OBJECT-TYPE
    SYNTAX     LcsSetupDnsDynamicSrvListEntry
    MAX-ACCESS not-accessible
    STATUS     current
    DESCRIPTION
        ""
    INDEX {
        lcsSetupDnsDynamicSrvListEntryServiceName
    }
    ::= { lcsSetupDnsDynamicSrvListTable 1 }

-- {SEQUENCE}
LcsSetupDnsDynamicSrvListEntry ::= SEQUENCE {
    lcsSetupDnsDynamicSrvListEntryServiceName DisplayString,
    lcsSetupDnsDynamicSrvListEntryHostName DisplayString,
    lcsSetupDnsDynamicSrvListEntryPort INTEGER
}

-- {COLUMN} 1712.2.17.11.1.1
lcsSetupDnsDynamicSrvListEntryServiceName OBJECT-TYPE
    SYNTAX     DisplayString (SIZE(0..64))
    MAX-ACCESS read-only
    STATUS     current
    DESCRIPTION
        "-- empty --"
    ::= { lcsSetupDnsDynamicSrvListEntry 1 }

-- {COLUMN} 1712.2.17.11.1.2
lcsSetupDnsDynamicSrvListEntryHostName OBJECT-TYPE
    SYNTAX     DisplayString (SIZE(0..64))
    MAX-ACCESS read-only
    STATUS     current
    DESCRIPTION
        "-- empty --"
    ::= { lcsSetupDnsDynamicSrvListEntry 2 }

-- {COLUMN} 1712.2.17.11.1.3
lcsSetupDnsDynamicSrvListEntryPort OBJECT-TYPE
    SYNTAX     INTEGER (0..65535)
    MAX-ACCESS read-only
    STATUS     current
    DESCRIPTION
        "-- empty --"
    ::= { lcsSetupDnsDynamicSrvListEntry 3 }

-- {OID} 1712.2.16
lcsSetupNetbios OBJECT IDENTIFIER ::= { lcsSetup 16 }

-- {SCALAR} 1712.2.16.1
lcsSetupNetbiosOperating OBJECT-TYPE
    SYNTAX     INTEGER
      {
        eNo (0),
        eYes (1)
      }
    MAX-ACCESS read-write
    STATUS     current
    DESCRIPTION
        "-- empty --"
    ::= { lcsSetupNetbios 1 }

-- {TABLE} 1712.2.16.12
lcsSetupNetbiosNetworksTable OBJECT-TYPE
    SYNTAX     SEQUENCE OF LcsSetupNetbiosNetworksEntry
    MAX-ACCESS not-accessible
    STATUS     current
    DESCRIPTION
        "-- empty --"
    ::= { lcsSetupNetbios 12 }

-- {ENTRY} 1712.2.16.12.1
lcsSetupNetbiosNetworksEntry OBJECT-TYPE
    SYNTAX     LcsSetupNetbiosNetworksEntry
    MAX-ACCESS not-accessible
    STATUS     current
    DESCRIPTION
        ""
    INDEX {
        lcsSetupNetbiosNetworksEntryNetworkName
    }
    ::= { lcsSetupNetbiosNetworksTable 1 }

-- {SEQUENCE}
LcsSetupNetbiosNetworksEntry ::= SEQUENCE {
    lcsSetupNetbiosNetworksEntryNetworkName DisplayString,
    lcsSetupNetbiosNetworksEntryOperating INTEGER,
    lcsSetupNetbiosNetworksEntryNtDomain DisplayString
}

-- {COLUMN} 1712.2.16.12.1.1
lcsSetupNetbiosNetworksEntryNetworkName OBJECT-TYPE
    SYNTAX     DisplayString (SIZE(0..16))
    MAX-ACCESS read-write
    STATUS     current
    DESCRIPTION
        "-- empty --"
    ::= { lcsSetupNetbiosNetworksEntry 1 }

-- {COLUMN} 1712.2.16.12.1.2
lcsSetupNetbiosNetworksEntryOperating OBJECT-TYPE
    SYNTAX     INTEGER
      {
        eNo (0),
        eYes (1)
      }
    MAX-ACCESS read-write
    STATUS     current
    DESCRIPTION
        "-- empty --"
    ::= { lcsSetupNetbiosNetworksEntry 2 }

-- {COLUMN} 1712.2.16.12.1.3
lcsSetupNetbiosNetworksEntryNtDomain OBJECT-TYPE
    SYNTAX     DisplayString (SIZE(0..15))
    MAX-ACCESS read-write
    STATUS     current
    DESCRIPTION
        "-- empty --"
    ::= { lcsSetupNetbiosNetworksEntry 3 }

-- {SCALAR} 1712.2.16.2
lcsSetupNetbiosScopeId OBJECT-TYPE
    SYNTAX     DisplayString (SIZE(0..64))
    MAX-ACCESS read-write
    STATUS     current
    DESCRIPTION
        "-- empty --"
    ::= { lcsSetupNetbios 2 }

-- {TABLE} 1712.2.16.4
lcsSetupNetbiosPeersTable OBJECT-TYPE
    SYNTAX     SEQUENCE OF LcsSetupNetbiosPeersEntry
    MAX-ACCESS not-accessible
    STATUS     current
    DESCRIPTION
        "-- empty --"
    ::= { lcsSetupNetbios 4 }

-- {ENTRY} 1712.2.16.4.1
lcsSetupNetbiosPeersEntry OBJECT-TYPE
    SYNTAX     LcsSetupNetbiosPeersEntry
    MAX-ACCESS not-accessible
    STATUS     current
    DESCRIPTION
        ""
    INDEX {
        lcsSetupNetbiosPeersEntryName
    }
    ::= { lcsSetupNetbiosPeersTable 1 }

-- {SEQUENCE}
LcsSetupNetbiosPeersEntry ::= SEQUENCE {
    lcsSetupNetbiosPeersEntryName DisplayString,
    lcsSetupNetbiosPeersEntryType INTEGER
}

-- {COLUMN} 1712.2.16.4.1.1
lcsSetupNetbiosPeersEntryName OBJECT-TYPE
    SYNTAX     DisplayString (SIZE(0..16))
    MAX-ACCESS read-write
    STATUS     current
    DESCRIPTION
        "-- empty --"
    ::= { lcsSetupNetbiosPeersEntry 1 }

-- {COLUMN} 1712.2.16.4.1.3
lcsSetupNetbiosPeersEntryType OBJECT-TYPE
    SYNTAX     INTEGER
      {
        eWorkstation (1),
        eRouter (0)
      }
    MAX-ACCESS read-write
    STATUS     current
    DESCRIPTION
        "-- empty --"
    ::= { lcsSetupNetbiosPeersEntry 3 }

-- {TABLE} 1712.2.16.5
lcsSetupNetbiosGroupListTable OBJECT-TYPE
    SYNTAX     SEQUENCE OF LcsSetupNetbiosGroupListEntry
    MAX-ACCESS not-accessible
    STATUS     current
    DESCRIPTION
        "-- empty --"
    ::= { lcsSetupNetbios 5 }

-- {ENTRY} 1712.2.16.5.1
lcsSetupNetbiosGroupListEntry OBJECT-TYPE
    SYNTAX     LcsSetupNetbiosGroupListEntry
    MAX-ACCESS not-accessible
    STATUS     current
    DESCRIPTION
        ""
    INDEX {
        lcsSetupNetbiosGroupListEntryGroupDomain,
        lcsSetupNetbiosGroupListEntryType,
        lcsSetupNetbiosGroupListEntryIpAddress,
        lcsSetupNetbiosGroupListEntryRtgTag
    }
    ::= { lcsSetupNetbiosGroupListTable 1 }

-- {SEQUENCE}
LcsSetupNetbiosGroupListEntry ::= SEQUENCE {
    lcsSetupNetbiosGroupListEntryGroupDomain DisplayString,
    lcsSetupNetbiosGroupListEntryType DisplayString,
    lcsSetupNetbiosGroupListEntryIpAddress IpAddress,
    lcsSetupNetbiosGroupListEntryRtgTag INTEGER,
    lcsSetupNetbiosGroupListEntryPeer DisplayString,
    lcsSetupNetbiosGroupListEntryNetworkName DisplayString,
    lcsSetupNetbiosGroupListEntryTimeout INTEGER,
    lcsSetupNetbiosGroupListEntryFlags DisplayString
}

-- {COLUMN} 1712.2.16.5.1.1
lcsSetupNetbiosGroupListEntryGroupDomain OBJECT-TYPE
    SYNTAX     DisplayString (SIZE(0..15))
    MAX-ACCESS read-only
    STATUS     current
    DESCRIPTION
        "-- empty --"
    ::= { lcsSetupNetbiosGroupListEntry 1 }

-- {COLUMN} 1712.2.16.5.1.2
lcsSetupNetbiosGroupListEntryType OBJECT-TYPE
    SYNTAX     DisplayString (SIZE(0..1))
    MAX-ACCESS read-only
    STATUS     current
    DESCRIPTION
        "-- empty --"
    ::= { lcsSetupNetbiosGroupListEntry 2 }

-- {COLUMN} 1712.2.16.5.1.3
lcsSetupNetbiosGroupListEntryIpAddress OBJECT-TYPE
    SYNTAX     IpAddress
    MAX-ACCESS read-only
    STATUS     current
    DESCRIPTION
        "-- empty --"
    ::= { lcsSetupNetbiosGroupListEntry 3 }

-- {COLUMN} 1712.2.16.5.1.8
lcsSetupNetbiosGroupListEntryRtgTag OBJECT-TYPE
    SYNTAX     INTEGER (0..65535)
    MAX-ACCESS read-only
    STATUS     current
    DESCRIPTION
        "-- empty --"
    ::= { lcsSetupNetbiosGroupListEntry 8 }

-- {COLUMN} 1712.2.16.5.1.4
lcsSetupNetbiosGroupListEntryPeer OBJECT-TYPE
    SYNTAX     DisplayString (SIZE(0..16))
    MAX-ACCESS read-only
    STATUS     current
    DESCRIPTION
        "-- empty --"
    ::= { lcsSetupNetbiosGroupListEntry 4 }

-- {COLUMN} 1712.2.16.5.1.7
lcsSetupNetbiosGroupListEntryNetworkName OBJECT-TYPE
    SYNTAX     DisplayString (SIZE(0..16))
    MAX-ACCESS read-only
    STATUS     current
    DESCRIPTION
        "-- empty --"
    ::= { lcsSetupNetbiosGroupListEntry 7 }

-- {COLUMN} 1712.2.16.5.1.5
lcsSetupNetbiosGroupListEntryTimeout OBJECT-TYPE
    SYNTAX     INTEGER (0..2147483647)
    MAX-ACCESS read-only
    STATUS     current
    DESCRIPTION
        "-- empty --"
    ::= { lcsSetupNetbiosGroupListEntry 5 }

-- {COLUMN} 1712.2.16.5.1.6
lcsSetupNetbiosGroupListEntryFlags OBJECT-TYPE
    SYNTAX     DisplayString (SIZE(0..2))
    MAX-ACCESS read-only
    STATUS     current
    DESCRIPTION
        "-- empty --"
    ::= { lcsSetupNetbiosGroupListEntry 6 }

-- {TABLE} 1712.2.16.6
lcsSetupNetbiosHostListTable OBJECT-TYPE
    SYNTAX     SEQUENCE OF LcsSetupNetbiosHostListEntry
    MAX-ACCESS not-accessible
    STATUS     current
    DESCRIPTION
        "-- empty --"
    ::= { lcsSetupNetbios 6 }

-- {ENTRY} 1712.2.16.6.1
lcsSetupNetbiosHostListEntry OBJECT-TYPE
    SYNTAX     LcsSetupNetbiosHostListEntry
    MAX-ACCESS not-accessible
    STATUS     current
    DESCRIPTION
        ""
    INDEX {
        lcsSetupNetbiosHostListEntryName,
        lcsSetupNetbiosHostListEntryType,
        lcsSetupNetbiosHostListEntryIpAddress,
        lcsSetupNetbiosHostListEntryRtgTag
    }
    ::= { lcsSetupNetbiosHostListTable 1 }

-- {SEQUENCE}
LcsSetupNetbiosHostListEntry ::= SEQUENCE {
    lcsSetupNetbiosHostListEntryName DisplayString,
    lcsSetupNetbiosHostListEntryType DisplayString,
    lcsSetupNetbiosHostListEntryIpAddress IpAddress,
    lcsSetupNetbiosHostListEntryRtgTag INTEGER,
    lcsSetupNetbiosHostListEntryPeer DisplayString,
    lcsSetupNetbiosHostListEntryNetworkName DisplayString,
    lcsSetupNetbiosHostListEntryTimeout INTEGER,
    lcsSetupNetbiosHostListEntryFlags DisplayString
}

-- {COLUMN} 1712.2.16.6.1.1
lcsSetupNetbiosHostListEntryName OBJECT-TYPE
    SYNTAX     DisplayString (SIZE(0..15))
    MAX-ACCESS read-only
    STATUS     current
    DESCRIPTION
        "-- empty --"
    ::= { lcsSetupNetbiosHostListEntry 1 }

-- {COLUMN} 1712.2.16.6.1.2
lcsSetupNetbiosHostListEntryType OBJECT-TYPE
    SYNTAX     DisplayString (SIZE(0..1))
    MAX-ACCESS read-only
    STATUS     current
    DESCRIPTION
        "-- empty --"
    ::= { lcsSetupNetbiosHostListEntry 2 }

-- {COLUMN} 1712.2.16.6.1.3
lcsSetupNetbiosHostListEntryIpAddress OBJECT-TYPE
    SYNTAX     IpAddress
    MAX-ACCESS read-only
    STATUS     current
    DESCRIPTION
        "-- empty --"
    ::= { lcsSetupNetbiosHostListEntry 3 }

-- {COLUMN} 1712.2.16.6.1.8
lcsSetupNetbiosHostListEntryRtgTag OBJECT-TYPE
    SYNTAX     INTEGER (0..65535)
    MAX-ACCESS read-only
    STATUS     current
    DESCRIPTION
        "-- empty --"
    ::= { lcsSetupNetbiosHostListEntry 8 }

-- {COLUMN} 1712.2.16.6.1.4
lcsSetupNetbiosHostListEntryPeer OBJECT-TYPE
    SYNTAX     DisplayString (SIZE(0..16))
    MAX-ACCESS read-only
    STATUS     current
    DESCRIPTION
        "-- empty --"
    ::= { lcsSetupNetbiosHostListEntry 4 }

-- {COLUMN} 1712.2.16.6.1.7
lcsSetupNetbiosHostListEntryNetworkName OBJECT-TYPE
    SYNTAX     DisplayString (SIZE(0..16))
    MAX-ACCESS read-only
    STATUS     current
    DESCRIPTION
        "-- empty --"
    ::= { lcsSetupNetbiosHostListEntry 7 }

-- {COLUMN} 1712.2.16.6.1.5
lcsSetupNetbiosHostListEntryTimeout OBJECT-TYPE
    SYNTAX     INTEGER (0..2147483647)
    MAX-ACCESS read-only
    STATUS     current
    DESCRIPTION
        "-- empty --"
    ::= { lcsSetupNetbiosHostListEntry 5 }

-- {COLUMN} 1712.2.16.6.1.6
lcsSetupNetbiosHostListEntryFlags OBJECT-TYPE
    SYNTAX     DisplayString (SIZE(0..2))
    MAX-ACCESS read-only
    STATUS     current
    DESCRIPTION
        "-- empty --"
    ::= { lcsSetupNetbiosHostListEntry 6 }

-- {TABLE} 1712.2.16.7
lcsSetupNetbiosServerListTable OBJECT-TYPE
    SYNTAX     SEQUENCE OF LcsSetupNetbiosServerListEntry
    MAX-ACCESS not-accessible
    STATUS     current
    DESCRIPTION
        "-- empty --"
    ::= { lcsSetupNetbios 7 }

-- {ENTRY} 1712.2.16.7.1
lcsSetupNetbiosServerListEntry OBJECT-TYPE
    SYNTAX     LcsSetupNetbiosServerListEntry
    MAX-ACCESS not-accessible
    STATUS     current
    DESCRIPTION
        ""
    INDEX {
        lcsSetupNetbiosServerListEntryHost,
        lcsSetupNetbiosServerListEntryGroupDomain,
        lcsSetupNetbiosServerListEntryIpAddress,
        lcsSetupNetbiosServerListEntryRtgTag
    }
    ::= { lcsSetupNetbiosServerListTable 1 }

-- {SEQUENCE}
LcsSetupNetbiosServerListEntry ::= SEQUENCE {
    lcsSetupNetbiosServerListEntryHost DisplayString,
    lcsSetupNetbiosServerListEntryGroupDomain DisplayString,
    lcsSetupNetbiosServerListEntryIpAddress DisplayString,
    lcsSetupNetbiosServerListEntryRtgTag INTEGER,
    lcsSetupNetbiosServerListEntryOsVer DisplayString,
    lcsSetupNetbiosServerListEntrySmbVer DisplayString,
    lcsSetupNetbiosServerListEntryServerTyp DisplayString,
    lcsSetupNetbiosServerListEntryPeer DisplayString,
    lcsSetupNetbiosServerListEntryNetworkName DisplayString,
    lcsSetupNetbiosServerListEntryTimeout INTEGER,
    lcsSetupNetbiosServerListEntryFlags DisplayString
}

-- {COLUMN} 1712.2.16.7.1.1
lcsSetupNetbiosServerListEntryHost OBJECT-TYPE
    SYNTAX     DisplayString (SIZE(0..15))
    MAX-ACCESS read-only
    STATUS     current
    DESCRIPTION
        "-- empty --"
    ::= { lcsSetupNetbiosServerListEntry 1 }

-- {COLUMN} 1712.2.16.7.1.2
lcsSetupNetbiosServerListEntryGroupDomain OBJECT-TYPE
    SYNTAX     DisplayString (SIZE(0..16))
    MAX-ACCESS read-only
    STATUS     current
    DESCRIPTION
        "-- empty --"
    ::= { lcsSetupNetbiosServerListEntry 2 }

-- {COLUMN} 1712.2.16.7.1.4
lcsSetupNetbiosServerListEntryIpAddress OBJECT-TYPE
    SYNTAX     DisplayString (SIZE(0..15))
    MAX-ACCESS read-only
    STATUS     current
    DESCRIPTION
        "-- empty --"
    ::= { lcsSetupNetbiosServerListEntry 4 }

-- {COLUMN} 1712.2.16.7.1.12
lcsSetupNetbiosServerListEntryRtgTag OBJECT-TYPE
    SYNTAX     INTEGER (0..65535)
    MAX-ACCESS read-only
    STATUS     current
    DESCRIPTION
        "-- empty --"
    ::= { lcsSetupNetbiosServerListEntry 12 }

-- {COLUMN} 1712.2.16.7.1.5
lcsSetupNetbiosServerListEntryOsVer OBJECT-TYPE
    SYNTAX     DisplayString (SIZE(0..2))
    MAX-ACCESS read-only
    STATUS     current
    DESCRIPTION
        "-- empty --"
    ::= { lcsSetupNetbiosServerListEntry 5 }

-- {COLUMN} 1712.2.16.7.1.6
lcsSetupNetbiosServerListEntrySmbVer OBJECT-TYPE
    SYNTAX     DisplayString (SIZE(0..2))
    MAX-ACCESS read-only
    STATUS     current
    DESCRIPTION
        "-- empty --"
    ::= { lcsSetupNetbiosServerListEntry 6 }

-- {COLUMN} 1712.2.16.7.1.7
lcsSetupNetbiosServerListEntryServerTyp OBJECT-TYPE
    SYNTAX     DisplayString (SIZE(0..4))
    MAX-ACCESS read-only
    STATUS     current
    DESCRIPTION
        "-- empty --"
    ::= { lcsSetupNetbiosServerListEntry 7 }

-- {COLUMN} 1712.2.16.7.1.8
lcsSetupNetbiosServerListEntryPeer OBJECT-TYPE
    SYNTAX     DisplayString (SIZE(0..16))
    MAX-ACCESS read-only
    STATUS     current
    DESCRIPTION
        "-- empty --"
    ::= { lcsSetupNetbiosServerListEntry 8 }

-- {COLUMN} 1712.2.16.7.1.11
lcsSetupNetbiosServerListEntryNetworkName OBJECT-TYPE
    SYNTAX     DisplayString (SIZE(0..16))
    MAX-ACCESS read-only
    STATUS     current
    DESCRIPTION
        "-- empty --"
    ::= { lcsSetupNetbiosServerListEntry 11 }

-- {COLUMN} 1712.2.16.7.1.9
lcsSetupNetbiosServerListEntryTimeout OBJECT-TYPE
    SYNTAX     INTEGER (0..2147483647)
    MAX-ACCESS read-only
    STATUS     current
    DESCRIPTION
        "-- empty --"
    ::= { lcsSetupNetbiosServerListEntry 9 }

-- {COLUMN} 1712.2.16.7.1.10
lcsSetupNetbiosServerListEntryFlags OBJECT-TYPE
    SYNTAX     DisplayString (SIZE(0..2))
    MAX-ACCESS read-only
    STATUS     current
    DESCRIPTION
        "-- empty --"
    ::= { lcsSetupNetbiosServerListEntry 10 }

-- {TABLE} 1712.2.16.13
lcsSetupNetbiosBrowserListTable OBJECT-TYPE
    SYNTAX     SEQUENCE OF LcsSetupNetbiosBrowserListEntry
    MAX-ACCESS not-accessible
    STATUS     current
    DESCRIPTION
        "-- empty --"
    ::= { lcsSetupNetbios 13 }

-- {ENTRY} 1712.2.16.13.1
lcsSetupNetbiosBrowserListEntry OBJECT-TYPE
    SYNTAX     LcsSetupNetbiosBrowserListEntry
    MAX-ACCESS not-accessible
    STATUS     current
    DESCRIPTION
        ""
    INDEX {
        lcsSetupNetbiosBrowserListEntryBrowser,
        lcsSetupNetbiosBrowserListEntryGroupDomain,
        lcsSetupNetbiosBrowserListEntryIpAddress,
        lcsSetupNetbiosBrowserListEntryRtgTag
    }
    ::= { lcsSetupNetbiosBrowserListTable 1 }

-- {SEQUENCE}
LcsSetupNetbiosBrowserListEntry ::= SEQUENCE {
    lcsSetupNetbiosBrowserListEntryBrowser DisplayString,
    lcsSetupNetbiosBrowserListEntryGroupDomain DisplayString,
    lcsSetupNetbiosBrowserListEntryIpAddress DisplayString,
    lcsSetupNetbiosBrowserListEntryRtgTag INTEGER,
    lcsSetupNetbiosBrowserListEntryOsVer DisplayString,
    lcsSetupNetbiosBrowserListEntryServerTyp DisplayString,
    lcsSetupNetbiosBrowserListEntryPeer DisplayString,
    lcsSetupNetbiosBrowserListEntryNetworkName DisplayString,
    lcsSetupNetbiosBrowserListEntryTimeout INTEGER,
    lcsSetupNetbiosBrowserListEntryFlags DisplayString
}

-- {COLUMN} 1712.2.16.13.1.1
lcsSetupNetbiosBrowserListEntryBrowser OBJECT-TYPE
    SYNTAX     DisplayString (SIZE(0..15))
    MAX-ACCESS read-only
    STATUS     current
    DESCRIPTION
        "-- empty --"
    ::= { lcsSetupNetbiosBrowserListEntry 1 }

-- {COLUMN} 1712.2.16.13.1.2
lcsSetupNetbiosBrowserListEntryGroupDomain OBJECT-TYPE
    SYNTAX     DisplayString (SIZE(0..16))
    MAX-ACCESS read-only
    STATUS     current
    DESCRIPTION
        "-- empty --"
    ::= { lcsSetupNetbiosBrowserListEntry 2 }

-- {COLUMN} 1712.2.16.13.1.4
lcsSetupNetbiosBrowserListEntryIpAddress OBJECT-TYPE
    SYNTAX     DisplayString (SIZE(0..15))
    MAX-ACCESS read-only
    STATUS     current
    DESCRIPTION
        "-- empty --"
    ::= { lcsSetupNetbiosBrowserListEntry 4 }

-- {COLUMN} 1712.2.16.13.1.12
lcsSetupNetbiosBrowserListEntryRtgTag OBJECT-TYPE
    SYNTAX     INTEGER (0..65535)
    MAX-ACCESS read-only
    STATUS     current
    DESCRIPTION
        "-- empty --"
    ::= { lcsSetupNetbiosBrowserListEntry 12 }

-- {COLUMN} 1712.2.16.13.1.5
lcsSetupNetbiosBrowserListEntryOsVer OBJECT-TYPE
    SYNTAX     DisplayString (SIZE(0..2))
    MAX-ACCESS read-only
    STATUS     current
    DESCRIPTION
        "-- empty --"
    ::= { lcsSetupNetbiosBrowserListEntry 5 }

-- {COLUMN} 1712.2.16.13.1.7
lcsSetupNetbiosBrowserListEntryServerTyp OBJECT-TYPE
    SYNTAX     DisplayString (SIZE(0..4))
    MAX-ACCESS read-only
    STATUS     current
    DESCRIPTION
        "-- empty --"
    ::= { lcsSetupNetbiosBrowserListEntry 7 }

-- {COLUMN} 1712.2.16.13.1.8
lcsSetupNetbiosBrowserListEntryPeer OBJECT-TYPE
    SYNTAX     DisplayString (SIZE(0..16))
    MAX-ACCESS read-only
    STATUS     current
    DESCRIPTION
        "-- empty --"
    ::= { lcsSetupNetbiosBrowserListEntry 8 }

-- {COLUMN} 1712.2.16.13.1.11
lcsSetupNetbiosBrowserListEntryNetworkName OBJECT-TYPE
    SYNTAX     DisplayString (SIZE(0..16))
    MAX-ACCESS read-only
    STATUS     current
    DESCRIPTION
        "-- empty --"
    ::= { lcsSetupNetbiosBrowserListEntry 11 }

-- {COLUMN} 1712.2.16.13.1.9
lcsSetupNetbiosBrowserListEntryTimeout OBJECT-TYPE
    SYNTAX     INTEGER (0..2147483647)
    MAX-ACCESS read-only
    STATUS     current
    DESCRIPTION
        "-- empty --"
    ::= { lcsSetupNetbiosBrowserListEntry 9 }

-- {COLUMN} 1712.2.16.13.1.10
lcsSetupNetbiosBrowserListEntryFlags OBJECT-TYPE
    SYNTAX     DisplayString (SIZE(0..2))
    MAX-ACCESS read-only
    STATUS     current
    DESCRIPTION
        "-- empty --"
    ::= { lcsSetupNetbiosBrowserListEntry 10 }

-- {SCALAR} 1712.2.16.14
lcsSetupNetbiosSupportBrowsing OBJECT-TYPE
    SYNTAX     INTEGER
      {
        eNo (0),
        eYes (1)
      }
    MAX-ACCESS read-write
    STATUS     current
    DESCRIPTION
        "-- empty --"
    ::= { lcsSetupNetbios 14 }

-- {SCALAR} 1712.2.16.8
lcsSetupNetbiosWatchdogs OBJECT-TYPE
    SYNTAX     INTEGER
      {
        eSpoof (1),
        eRoute (0)
      }
    MAX-ACCESS read-write
    STATUS     current
    DESCRIPTION
        "-- empty --"
    ::= { lcsSetupNetbios 8 }

-- {SCALAR} 1712.2.16.9
lcsSetupNetbiosUpdate OBJECT-TYPE
    SYNTAX     INTEGER
      {
        ePback (0),
        eTrig (1),
        eTime (2)
      }
    MAX-ACCESS read-write
    STATUS     current
    DESCRIPTION
        "-- empty --"
    ::= { lcsSetupNetbios 9 }

-- {SCALAR} 1712.2.16.10
lcsSetupNetbiosWanUpdateMinutes OBJECT-TYPE
    SYNTAX     INTEGER (0..65535)
    MAX-ACCESS read-write
    STATUS     current
    DESCRIPTION
        "-- empty --"
    ::= { lcsSetupNetbios 10 }

-- {SCALAR} 1712.2.16.11
lcsSetupNetbiosLeasetime OBJECT-TYPE
    SYNTAX     INTEGER (0..65535)
    MAX-ACCESS read-write
    STATUS     current
    DESCRIPTION
        "-- empty --"
    ::= { lcsSetupNetbios 11 }

-- {OID} 1712.2.11
lcsSetupConfig OBJECT IDENTIFIER ::= { lcsSetup 11 }

-- {SCALAR} 1712.2.11.3
lcsSetupConfigPasswordRequiredForSnmpReadAccess OBJECT-TYPE
    SYNTAX     INTEGER
      {
        eNo (0),
        eYes (1)
      }
    MAX-ACCESS read-write
    STATUS     current
    DESCRIPTION
        "-- empty --"
    ::= { lcsSetupConfig 3 }

-- {SCALAR} 1712.2.11.60
lcsSetupConfigCpuLoadInterval OBJECT-TYPE
    SYNTAX     INTEGER
      {
        eT1s (1),
        eT5s (5),
        eT60s (60),
        eT300s (300)
      }
    MAX-ACCESS read-write
    STATUS     current
    DESCRIPTION
        "-- empty --"
    ::= { lcsSetupConfig 60 }

-- {SCALAR} 1712.2.11.9
lcsSetupConfigAdminEazMsn OBJECT-TYPE
    SYNTAX     DisplayString (SIZE(0..31))
    MAX-ACCESS read-write
    STATUS     current
    DESCRIPTION
        "-- empty --"
    ::= { lcsSetupConfig 9 }

-- {SCALAR} 1712.2.11.4
lcsSetupConfigMaximumConnections OBJECT-TYPE
    SYNTAX     INTEGER (0..255)
    MAX-ACCESS read-write
    STATUS     current
    DESCRIPTION
        "-- empty --"
    ::= { lcsSetupConfig 4 }

-- {SCALAR} 1712.2.11.5
lcsSetupConfigConfigAgingMinutes OBJECT-TYPE
    SYNTAX     INTEGER (0..255)
    MAX-ACCESS read-write
    STATUS     current
    DESCRIPTION
        "-- empty --"
    ::= { lcsSetupConfig 5 }

-- {SCALAR} 1712.2.11.33
lcsSetupConfigOutbandAgingMinutes OBJECT-TYPE
    SYNTAX     INTEGER (0..255)
    MAX-ACCESS read-write
    STATUS     current
    DESCRIPTION
        "-- empty --"
    ::= { lcsSetupConfig 33 }

-- {SCALAR} 1712.2.11.7
lcsSetupConfigLoginErrors OBJECT-TYPE
    SYNTAX     INTEGER (0..255)
    MAX-ACCESS read-write
    STATUS     current
    DESCRIPTION
        "-- empty --"
    ::= { lcsSetupConfig 7 }

-- {SCALAR} 1712.2.11.8
lcsSetupConfigLockMinutes OBJECT-TYPE
    SYNTAX     INTEGER (0..255)
    MAX-ACCESS read-write
    STATUS     current
    DESCRIPTION
        "-- empty --"
    ::= { lcsSetupConfig 8 }

-- {SCALAR} 1712.2.11.6
lcsSetupConfigLanguage OBJECT-TYPE
    SYNTAX     INTEGER
      {
        eEnglish (1),
        eDeutsch (2)
      }
    MAX-ACCESS read-write
    STATUS     current
    DESCRIPTION
        "-- empty --"
    ::= { lcsSetupConfig 6 }

-- {TABLE} 1712.2.11.15
lcsSetupConfigAccessTableTable OBJECT-TYPE
    SYNTAX     SEQUENCE OF LcsSetupConfigAccessTableEntry
    MAX-ACCESS not-accessible
    STATUS     current
    DESCRIPTION
        "-- empty --"
    ::= { lcsSetupConfig 15 }

-- {ENTRY} 1712.2.11.15.1
lcsSetupConfigAccessTableEntry OBJECT-TYPE
    SYNTAX     LcsSetupConfigAccessTableEntry
    MAX-ACCESS not-accessible
    STATUS     current
    DESCRIPTION
        ""
    INDEX {
        lcsSetupConfigAccessTableEntryIfc
    }
    ::= { lcsSetupConfigAccessTableTable 1 }

-- {SEQUENCE}
LcsSetupConfigAccessTableEntry ::= SEQUENCE {
    lcsSetupConfigAccessTableEntryIfc INTEGER,
    lcsSetupConfigAccessTableEntryTelnet INTEGER,
    lcsSetupConfigAccessTableEntryTftp INTEGER,
    lcsSetupConfigAccessTableEntryHttp INTEGER,
    lcsSetupConfigAccessTableEntrySnmp INTEGER,
    lcsSetupConfigAccessTableEntryHttps INTEGER,
    lcsSetupConfigAccessTableEntryTelnetSsl INTEGER,
    lcsSetupConfigAccessTableEntrySsh INTEGER
}

-- {COLUMN} 1712.2.11.15.1.1
lcsSetupConfigAccessTableEntryIfc OBJECT-TYPE
    SYNTAX     INTEGER
      {
        eLan (1),
        eWan (2)
      }
    MAX-ACCESS read-only
    STATUS     current
    DESCRIPTION
        "-- empty --"
    ::= { lcsSetupConfigAccessTableEntry 1 }

-- {COLUMN} 1712.2.11.15.1.2
lcsSetupConfigAccessTableEntryTelnet OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 2 }

-- {COLUMN} 1712.2.11.15.1.3
lcsSetupConfigAccessTableEntryTftp OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 3 }

-- {COLUMN} 1712.2.11.15.1.4
lcsSetupConfigAccessTableEntryHttp OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 4 }

-- {COLUMN} 1712.2.11.15.1.5
lcsSetupConfigAccessTableEntrySnmp OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 5 }

-- {COLUMN} 1712.2.11.15.1.6
lcsSetupConfigAccessTableEntryHttps OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 6 }

-- {COLUMN} 1712.2.11.15.1.7
lcsSetupConfigAccessTableEntryTelnetSsl OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 7 }

-- {COLUMN} 1712.2.11.15.1.8
lcsSetupConfigAccessTableEntrySsh OBJECT-TYPE
    SYNTAX     INTEGER
      {
        eVpn (16),
        eYes (1),
        eRead (4),
        eNo (0)
      }
    MAX-ACCESS read-write
    STATUS     current
    DESCRIPTION
        "-- empty --"
    ::= { lcsSetupConfigAccessTableEntry 8 }

-- {SCALAR} 1712.2.11.16
lcsSetupConfigScreenHeight OBJECT-TYPE
    SYNTAX     INTEGER (0..65535)
    MAX-ACCESS read-write
    STATUS     current
    DESCRIPTION
        "-- empty --"
    ::= { lcsSetupConfig 16 }

-- {TABLE} 1712.2.11.43
lcsSetupConfigFunctionKeysTable OBJECT-TYPE
    SYNTAX     SEQUENCE OF LcsSetupConfigFunctionKeysEntry
    MAX-ACCESS not-accessible
    STATUS     current
    DESCRIPTION
        "-- empty --"
    ::= { lcsSetupConfig 43 }

-- {ENTRY} 1712.2.11.43.1
lcsSetupConfigFunctionKeysEntry OBJECT-TYPE
    SYNTAX     LcsSetupConfigFunctionKeysEntry
    MAX-ACCESS not-accessible
    STATUS     current
    DESCRIPTION
        ""
    INDEX {
        lcsSetupConfigFunctionKeysEntryKey
    }
    ::= { lcsSetupConfigFunctionKeysTable 1 }

-- {SEQUENCE}
LcsSetupConfigFunctionKeysEntry ::= SEQUENCE {
    lcsSetupConfigFunctionKeysEntryKey INTEGER,
    lcsSetupConfigFunctionKeysEntryMapping DisplayString
}

-- {COLUMN} 1712.2.11.43.1.1
lcsSetupConfigFunctionKeysEntryKey OBJECT-TYPE
    SYNTAX     INTEGER
      {
        eF1 (1),
        eF2 (2),
        eF3 (3),
        eF4 (4),
        eF5 (5),
        eF6 (6),
        eF7 (7),
        eF8 (8),
        eF9 (9),
        eF10 (10),
        eF11 (11),
        eF12 (12)
      }
    MAX-ACCESS read-write
    STATUS     current
    DESCRIPTION
        "-- empty --"
    ::= { lcsSetupConfigFunctionKeysEntry 1 }

-- {COLUMN} 1712.2.11.43.1.2
lcsSetupConfigFunctionKeysEntryMapping OBJECT-TYPE
    SYNTAX     DisplayString (SIZE(0..99))
    MAX-ACCESS read-write
    STATUS     current
    DESCRIPTION
        "-- empty --"
    ::= { lcsSetupConfigFunctionKeysEntry 2 }

-- {OID} 1712.2.11.50
lcsSetupConfigLl2m OBJECT IDENTIFIER ::= { lcsSetupConfig 50 }

-- {SCALAR} 1712.2.11.50.1
lcsSetupConfigLl2mOperating OBJECT-TYPE
    SYNTAX     INTEGER
      {
        eNo (0),
        eYes (1)
      }
    MAX-ACCESS read-write
    STATUS     current
    DESCRIPTION
        "-- empty --"
    ::= { lcsSetupConfigLl2m 1 }

-- {SCALAR} 1712.2.11.50.2
lcsSetupConfigLl2mTimeLimit OBJECT-TYPE
    SYNTAX     INTEGER (0..2147483647)
    MAX-ACCESS read-write
    STATUS     current
    DESCRIPTION
        "-- empty --"
    ::= { lcsSetupConfigLl2m 2 }

-- {SCALAR} 1712.2.11.40
lcsSetupConfigCrashMessage OBJECT-TYPE
    SYNTAX     DisplayString (SIZE(0..32))
    MAX-ACCESS read-write
    STATUS     current
    DESCRIPTION
        "-- empty --"
    ::= { lcsSetupConfig 40 }

-- {SCALAR} 1712.2.11.41
lcsSetupConfigAdminGender OBJECT-TYPE
    SYNTAX     INTEGER
      {
        eUnknown (0),
        eMale (1),
        eFemale (2),
        eGeek (3)
      }
    MAX-ACCESS read-write
    STATUS     current
    DESCRIPTION
        "-- empty --"
    ::= { lcsSetupConfig 41 }

-- {SCALAR} 1712.2.11.42
lcsSetupConfigAssertAction OBJECT-TYPE
    SYNTAX     INTEGER
      {
        eLogOnly (0),
        eReboot (1)
      }
    MAX-ACCESS read-write
    STATUS     current
    DESCRIPTION
        "-- empty --"
    ::= { lcsSetupConfig 42 }

-- {SCALAR} 1712.2.11.17
lcsSetupConfigPrompt OBJECT-TYPE
    SYNTAX     DisplayString (SIZE(0..31))
    MAX-ACCESS read-write
    STATUS     current
    DESCRIPTION
        "-- empty --"
    ::= { lcsSetupConfig 17 }

-- {SCALAR} 1712.2.11.45
lcsSetupConfigConfigDateNew OBJECT-TYPE
    SYNTAX     Counter32
    MAX-ACCESS read-write
    STATUS     current
    DESCRIPTION
        ""
    ::= { lcsSetupConfig 45 }

-- {SCALAR} 1712.2.11.1
lcsSetupConfigLan OBJECT-TYPE
    SYNTAX     INTEGER (0..255)
    MAX-ACCESS read-only
    STATUS     current
    DESCRIPTION
        "-- empty --"
    ::= { lcsSetupConfig 1 }

-- {SCALAR} 1712.2.11.2
lcsSetupConfigWan OBJECT-TYPE
    SYNTAX     INTEGER (0..255)
    MAX-ACCESS read-only
    STATUS     current
    DESCRIPTION
        "-- empty --"
    ::= { lcsSetupConfig 2 }

-- {SCALAR} 1712.2.11.23
lcsSetupConfigTelnetPort OBJECT-TYPE
    SYNTAX     INTEGER (0..65535)
    MAX-ACCESS read-write
    STATUS     current
    DESCRIPTION
        "-- empty --"
    ::= { lcsSetupConfig 23 }

-- {OID} 1712.2.11.29
lcsSetupConfigTelnetSsl OBJECT IDENTIFIER ::= { lcsSetupConfig 29 }

-- {SCALAR} 1712.2.11.29.10
lcsSetupConfigTelnetSslPortNew OBJECT-TYPE
    SYNTAX     INTEGER (0..65535)
    MAX-ACCESS read-write
    STATUS     current
    DESCRIPTION
        "TCP port device is listening on for Telnet/SSL"
    ::= { lcsSetupConfigTelnetSsl 10 }

-- {SCALAR} 1712.2.11.29.2
lcsSetupConfigTelnetSslVersions OBJECT-TYPE
    SYNTAX     BITS
      {
        eSslv3 (31),
        eTlsv1 (30),
        eTlsv11 (29),
        eTlsv12 (28)
      }
    MAX-ACCESS read-write
    STATUS     current
    DESCRIPTION
        "-- empty --"
    ::= { lcsSetupConfigTelnetSsl 2 }

-- {SCALAR} 1712.2.11.29.3
lcsSetupConfigTelnetSslKeyexAlgorithms OBJECT-TYPE
    SYNTAX     BITS
      {
        eRsa (31),
        eDhe (29),
        eEcdhe (27)
      }
    MAX-ACCESS read-write
    STATUS     current
    DESCRIPTION
        "-- empty --"
    ::= { lcsSetupConfigTelnetSsl 3 }

-- {SCALAR} 1712.2.11.29.4
lcsSetupConfigTelnetSslCryptoAlgorithms OBJECT-TYPE
    SYNTAX     BITS
      {
        eRc440 (29),
        eRc456 (28),
        eRc4128 (27),
        eDes40 (26),
        eDes (25),
        e3des (24),
        eAes128 (23),
        eAes256 (22),
        eAesgcm128 (21),
        eAesgcm256 (20)
      }
    MAX-ACCESS read-write
    STATUS     current
    DESCRIPTION
        "-- empty --"
    ::= { lcsSetupConfigTelnetSsl 4 }

-- {SCALAR} 1712.2.11.29.5
lcsSetupConfigTelnetSslHashAlgorithms OBJECT-TYPE
    SYNTAX     BITS
      {
        eMd5 (30),
        eSha1 (29),
        eSha2256 (27),
        eSha2384 (26)
      }
    MAX-ACCESS read-write
    STATUS     current
    DESCRIPTION
        "-- empty --"
    ::= { lcsSetupConfigTelnetSsl 5 }

-- {OID} 1712.2.11.31
lcsSetupConfigAntiTheftProtection OBJECT IDENTIFIER ::= { lcsSetupConfig 31 }

-- {SCALAR} 1712.2.11.31.1
lcsSetupConfigAntiTheftProtectionEnabled OBJECT-TYPE
    SYNTAX     INTEGER
      {
        eNo (0),
        eYes (1)
      }
    MAX-ACCESS read-write
    STATUS     current
    DESCRIPTION
        "-- empty --"
    ::= { lcsSetupConfigAntiTheftProtection 1 }

-- {SCALAR} 1712.2.11.31.6
lcsSetupConfigAntiTheftProtectionMethod OBJECT-TYPE
    SYNTAX     INTEGER
      {
        eBasicCall (0),
        eFacility (1)
      }
    MAX-ACCESS read-write
    STATUS     current
    DESCRIPTION
        "-- empty --"
    ::= { lcsSetupConfigAntiTheftProtection 6 }

-- {SCALAR} 1712.2.11.31.7
lcsSetupConfigAntiTheftProtectionIsdnIfc OBJECT-TYPE
    SYNTAX     INTEGER
      {
        eS01 (1)
      }
    MAX-ACCESS read-write
    STATUS     current
    DESCRIPTION
        "-- empty --"
    ::= { lcsSetupConfigAntiTheftProtection 7 }

-- {SCALAR} 1712.2.11.31.2
lcsSetupConfigAntiTheftProtectionCalledNumber OBJECT-TYPE
    SYNTAX     DisplayString (SIZE(0..14))
    MAX-ACCESS read-write
    STATUS     current
    DESCRIPTION
        "-- empty --"
    ::= { lcsSetupConfigAntiTheftProtection 2 }

-- {SCALAR} 1712.2.11.31.3
lcsSetupConfigAntiTheftProtectionOutgoingCallingNumber OBJECT-TYPE
    SYNTAX     DisplayString (SIZE(0..14))
    MAX-ACCESS read-write
    STATUS     current
    DESCRIPTION
        "-- empty --"
    ::= { lcsSetupConfigAntiTheftProtection 3 }

-- {SCALAR} 1712.2.11.31.4
lcsSetupConfigAntiTheftProtectionCheckedCallingNumber OBJECT-TYPE
    SYNTAX     DisplayString (SIZE(0..14))
    MAX-ACCESS read-write
    STATUS     current
    DESCRIPTION
        "-- empty --"
    ::= { lcsSetupConfigAntiTheftProtection 4 }

-- {SCALAR} 1712.2.11.32
lcsSetupConfigResetButton OBJECT-TYPE
    SYNTAX     INTEGER
      {
        eIgnore (0),
        eBootOnly (1),
        eResetOrBoot (2)
      }
    MAX-ACCESS read-write
    STATUS     current
    DESCRIPTION
        "-- empty --"
    ::= { lcsSetupConfig 32 }

-- {OID} 1712.2.11.35
lcsSetupConfigMonitortrace OBJECT IDENTIFIER ::= { lcsSetupConfig 35 }

-- {SCALAR} 1712.2.11.35.1
lcsSetupConfigMonitortraceTracemask1 OBJECT-TYPE
    SYNTAX     INTEGER (0..2147483647)
    MAX-ACCESS read-only
    STATUS     current
    DESCRIPTION
        "-- empty --"
    ::= { lcsSetupConfigMonitortrace 1 }

-- {SCALAR} 1712.2.11.35.2
lcsSetupConfigMonitortraceTracemask2 OBJECT-TYPE
    SYNTAX     INTEGER (0..2147483647)
    MAX-ACCESS read-only
    STATUS     current
    DESCRIPTION
        "-- empty --"
    ::= { lcsSetupConfigMonitortrace 2 }

-- {SCALAR} 1712.2.11.39
lcsSetupConfigLicenseExpiryEmail OBJECT-TYPE
    SYNTAX     DisplayString (SIZE(0..63))
    MAX-ACCESS read-write
    STATUS     current
    DESCRIPTION
        "-- empty --"
    ::= { lcsSetupConfig 39 }

-- {SCALAR} 1712.2.11.73
lcsSetupConfigSortMenu OBJECT-TYPE
    SYNTAX     INTEGER
      {
        eNo (0),
        eYes (1)
      }
    MAX-ACCESS read-write
    STATUS     current
    DESCRIPTION
        "-- empty --"
    ::= { lcsSetupConfig 73 }

-- {SCALAR} 1712.2.11.80
lcsSetupConfigAuthentication OBJECT-TYPE
    SYNTAX     INTEGER
      {
        eIntern (0),
        eRadius (1),
        eTacacsPlus (2)
      }
    MAX-ACCESS read-write
    STATUS     current
    DESCRIPTION
        "-- empty --"
    ::= { lcsSetupConfig 80 }

-- {OID} 1712.2.11.81
lcsSetupConfigRadius OBJECT IDENTIFIER ::= { lcsSetupConfig 81 }

-- {TABLE} 1712.2.11.81.1
lcsSetupConfigRadiusServerTable OBJECT-TYPE
    SYNTAX     SEQUENCE OF LcsSetupConfigRadiusServerEntry
    MAX-ACCESS not-accessible
    STATUS     current
    DESCRIPTION
        "-- empty --"
    ::= { lcsSetupConfigRadius 1 }

-- {ENTRY} 1712.2.11.81.1.1
lcsSetupConfigRadiusServerEntry OBJECT-TYPE
    SYNTAX     LcsSetupConfigRadiusServerEntry
    MAX-ACCESS not-accessible
    STATUS     current
    DESCRIPTION
        ""
    INDEX {
        lcsSetupConfigRadiusServerEntryName
    }
    ::= { lcsSetupConfigRadiusServerTable 1 }

-- {SEQUENCE}
LcsSetupConfigRadiusServerEntry ::= SEQUENCE {
    lcsSetupConfigRadiusServerEntryName DisplayString,
    lcsSetupConfigRadiusServerEntryServer DisplayString,
    lcsSetupConfigRadiusServerEntryPort INTEGER,
    lcsSetupConfigRadiusServerEntryProtocol INTEGER,
    lcsSetupConfigRadiusServerEntryLoopbackAddress DisplayString,
    lcsSetupConfigRadiusServerEntrySecret DisplayString,
    lcsSetupConfigRadiusServerEntryBackup DisplayString,
    lcsSetupConfigRadiusServerEntryCategory BITS
}

-- {COLUMN} 1712.2.11.81.1.1.1
lcsSetupConfigRadiusServerEntryName OBJECT-TYPE
    SYNTAX     DisplayString (SIZE(0..16))
    MAX-ACCESS read-write
    STATUS     current
    DESCRIPTION
        "-- empty --"
    ::= { lcsSetupConfigRadiusServerEntry 1 }

-- {COLUMN} 1712.2.11.81.1.1.2
lcsSetupConfigRadiusServerEntryServer OBJECT-TYPE
    SYNTAX     DisplayString (SIZE(0..64))
    MAX-ACCESS read-write
    STATUS     current
    DESCRIPTION
        "-- empty --"
    ::= { lcsSetupConfigRadiusServerEntry 2 }

-- {COLUMN} 1712.2.11.81.1.1.3
lcsSetupConfigRadiusServerEntryPort OBJECT-TYPE
    SYNTAX     INTEGER (0..65535)
    MAX-ACCESS read-write
    STATUS     current
    DESCRIPTION
        "-- empty --"
    ::= { lcsSetupConfigRadiusServerEntry 3 }

-- {COLUMN} 1712.2.11.81.1.1.4
lcsSetupConfigRadiusServerEntryProtocol OBJECT-TYPE
    SYNTAX     INTEGER
      {
        eRadius (0),
        eRadsec (1)
      }
    MAX-ACCESS read-write
    STATUS     current
    DESCRIPTION
        "-- empty --"
    ::= { lcsSetupConfigRadiusServerEntry 4 }

-- {COLUMN} 1712.2.11.81.1.1.5
lcsSetupConfigRadiusServerEntryLoopbackAddress OBJECT-TYPE
    SYNTAX     DisplayString (SIZE(0..16))
    MAX-ACCESS read-write
    STATUS     current
    DESCRIPTION
        "-- empty --"
    ::= { lcsSetupConfigRadiusServerEntry 5 }

-- {COLUMN} 1712.2.11.81.1.1.6
lcsSetupConfigRadiusServerEntrySecret OBJECT-TYPE
    SYNTAX     DisplayString (SIZE(0..64))
    MAX-ACCESS read-write
    STATUS     current
    DESCRIPTION
        "-- empty --"
    ::= { lcsSetupConfigRadiusServerEntry 6 }

-- {COLUMN} 1712.2.11.81.1.1.7
lcsSetupConfigRadiusServerEntryBackup OBJECT-TYPE
    SYNTAX     DisplayString (SIZE(0..16))
    MAX-ACCESS read-write
    STATUS     current
    DESCRIPTION
        "-- empty --"
    ::= { lcsSetupConfigRadiusServerEntry 7 }

-- {COLUMN} 1712.2.11.81.1.1.8
lcsSetupConfigRadiusServerEntryCategory OBJECT-TYPE
    SYNTAX     BITS
      {
        eAuthentication (7),
        eAccounting (6)
      }
    MAX-ACCESS read-write
    STATUS     current
    DESCRIPTION
        "-- empty --"
    ::= { lcsSetupConfigRadiusServerEntry 8 }

-- {SCALAR} 1712.2.11.81.2
lcsSetupConfigRadiusAccessRightsTransfer OBJECT-TYPE
    SYNTAX     INTEGER
      {
        eVendorSpecific (0),
        eMapped (1),
        eShellPrivilege (2)
      }
    MAX-ACCESS read-write
    STATUS     current
    DESCRIPTION
        "-- empty --"
    ::= { lcsSetupConfigRadius 2 }

-- {SCALAR} 1712.2.11.81.3
lcsSetupConfigRadiusAccounting OBJECT-TYPE
    SYNTAX     INTEGER
      {
        eNo (0),
        eYes (1)
      }
    MAX-ACCESS read-write
    STATUS     current
    DESCRIPTION
        "-- empty --"
    ::= { lcsSetupConfigRadius 3 }

-- {SCALAR} 1712.2.11.18
lcsSetupConfigLedTest OBJECT-TYPE
    SYNTAX     INTEGER
      {
        eOff (0),
        eGreen (2),
        eRed (1),
        eNoTest (255)
      }
    MAX-ACCESS read-write
    STATUS     current
    DESCRIPTION
        "-- empty --"
    ::= { lcsSetupConfig 18 }

-- {TABLE} 1712.2.11.20
lcsSetupConfigCronTableTable OBJECT-TYPE
    SYNTAX     SEQUENCE OF LcsSetupConfigCronTableEntry
    MAX-ACCESS not-accessible
    STATUS     current
    DESCRIPTION
        "-- empty --"
    ::= { lcsSetupConfig 20 }

-- {ENTRY} 1712.2.11.20.1
lcsSetupConfigCronTableEntry OBJECT-TYPE
    SYNTAX     LcsSetupConfigCronTableEntry
    MAX-ACCESS not-accessible
    STATUS     current
    DESCRIPTION
        ""
    INDEX {
        lcsSetupConfigCronTableEntryIndex
    }
    ::= { lcsSetupConfigCronTableTable 1 }

-- {SEQUENCE}
LcsSetupConfigCronTableEntry ::= SEQUENCE {
    lcsSetupConfigCronTableEntryIndex INTEGER,
    lcsSetupConfigCronTableEntryActive INTEGER,
    lcsSetupConfigCronTableEntryBase INTEGER,
    lcsSetupConfigCronTableEntryVariation INTEGER,
    lcsSetupConfigCronTableEntryMinute DisplayString,
    lcsSetupConfigCronTableEntryHour DisplayString,
    lcsSetupConfigCronTableEntryDayofweek DisplayString,
    lcsSetupConfigCronTableEntryDay DisplayString,
    lcsSetupConfigCronTableEntryMonth DisplayString,
    lcsSetupConfigCronTableEntryCommand DisplayString,
    lcsSetupConfigCronTableEntryOwner DisplayString,
    lcsSetupConfigCronTableEntryComment DisplayString
}

-- {COLUMN} 1712.2.11.20.1.1
lcsSetupConfigCronTableEntryIndex OBJECT-TYPE
    SYNTAX     INTEGER (0..65535)
    MAX-ACCESS read-write
    STATUS     current
    DESCRIPTION
        "-- empty --"
    ::= { lcsSetupConfigCronTableEntry 1 }

-- {COLUMN} 1712.2.11.20.1.9
lcsSetupConfigCronTableEntryActive OBJECT-TYPE
    SYNTAX     INTEGER
      {
        eYes (0),
        eNo (1)
      }
    MAX-ACCESS read-write
    STATUS     current
    DESCRIPTION
        "-- empty --"
    ::= { lcsSetupConfigCronTableEntry 9 }

-- {COLUMN} 1712.2.11.20.1.8
lcsSetupConfigCronTableEntryBase OBJECT-TYPE
    SYNTAX     INTEGER
      {
        eRealTime (0),
        eOperationTime (1)
      }
    MAX-ACCESS read-write
    STATUS     current
    DESCRIPTION
        "-- empty --"
    ::= { lcsSetupConfigCronTableEntry 8 }

-- {COLUMN} 1712.2.11.20.1.11
lcsSetupConfigCronTableEntryVariation OBJECT-TYPE
    SYNTAX     INTEGER (0..65535)
    MAX-ACCESS read-write
    STATUS     current
    DESCRIPTION
        "-- empty --"
    ::= { lcsSetupConfigCronTableEntry 11 }

-- {COLUMN} 1712.2.11.20.1.2
lcsSetupConfigCronTableEntryMinute OBJECT-TYPE
    SYNTAX     DisplayString (SIZE(0..50))
    MAX-ACCESS read-write
    STATUS     current
    DESCRIPTION
        "-- empty --"
    ::= { lcsSetupConfigCronTableEntry 2 }

-- {COLUMN} 1712.2.11.20.1.3
lcsSetupConfigCronTableEntryHour OBJECT-TYPE
    SYNTAX     DisplayString (SIZE(0..50))
    MAX-ACCESS read-write
    STATUS     current
    DESCRIPTION
        "-- empty --"
    ::= { lcsSetupConfigCronTableEntry 3 }

-- {COLUMN} 1712.2.11.20.1.4
lcsSetupConfigCronTableEntryDayofweek OBJECT-TYPE
    SYNTAX     DisplayString (SIZE(0..50))
    MAX-ACCESS read-write
    STATUS     current
    DESCRIPTION
        "-- empty --"
    ::= { lcsSetupConfigCronTableEntry 4 }

-- {COLUMN} 1712.2.11.20.1.5
lcsSetupConfigCronTableEntryDay OBJECT-TYPE
    SYNTAX     DisplayString (SIZE(0..50))
    MAX-ACCESS read-write
    STATUS     current
    DESCRIPTION
        "-- empty --"
    ::= { lcsSetupConfigCronTableEntry 5 }

-- {COLUMN} 1712.2.11.20.1.6
lcsSetupConfigCronTableEntryMonth OBJECT-TYPE
    SYNTAX     DisplayString (SIZE(0..50))
    MAX-ACCESS read-write
    STATUS     current
    DESCRIPTION
        "-- empty --"
    ::= { lcsSetupConfigCronTableEntry 6 }

-- {COLUMN} 1712.2.11.20.1.7
lcsSetupConfigCronTableEntryCommand OBJECT-TYPE
    SYNTAX     DisplayString (SIZE(0..252))
    MAX-ACCESS read-write
    STATUS     current
    DESCRIPTION
        "-- empty --"
    ::= { lcsSetupConfigCronTableEntry 7 }

-- {COLUMN} 1712.2.11.20.1.10
lcsSetupConfigCronTableEntryOwner OBJECT-TYPE
    SYNTAX     DisplayString (SIZE(0..16))
    MAX-ACCESS read-write
    STATUS     current
    DESCRIPTION
        "-- empty --"
    ::= { lcsSetupConfigCronTableEntry 10 }

-- {COLUMN} 1712.2.11.20.1.12
lcsSetupConfigCronTableEntryComment OBJECT-TYPE
    SYNTAX     DisplayString (SIZE(0..63))
    MAX-ACCESS read-write
    STATUS     current
    DESCRIPTION
        "-- empty --"
    ::= { lcsSetupConfigCronTableEntry 12 }

-- {TABLE} 1712.2.11.21
lcsSetupConfigAdminsTable OBJECT-TYPE
    SYNTAX     SEQUENCE OF LcsSetupConfigAdminsEntry
    MAX-ACCESS not-accessible
    STATUS     current
    DESCRIPTION
        "-- empty --"
    ::= { lcsSetupConfig 21 }

-- {ENTRY} 1712.2.11.21.1
lcsSetupConfigAdminsEntry OBJECT-TYPE
    SYNTAX     LcsSetupConfigAdminsEntry
    MAX-ACCESS not-accessible
    STATUS     current
    DESCRIPTION
        ""
    INDEX {
        lcsSetupConfigAdminsEntryAdministrator
    }
    ::= { lcsSetupConfigAdminsTable 1 }

-- {SEQUENCE}
LcsSetupConfigAdminsEntry ::= SEQUENCE {
    lcsSetupConfigAdminsEntryAdministrator DisplayString,
    lcsSetupConfigAdminsEntryPassword DisplayString,
    lcsSetupConfigAdminsEntryActive INTEGER,
    lcsSetupConfigAdminsEntryAccessRights INTEGER,
    lcsSetupConfigAdminsEntryFunctionRights BITS
}

-- {COLUMN} 1712.2.11.21.1.1
lcsSetupConfigAdminsEntryAdministrator OBJECT-TYPE
    SYNTAX     DisplayString (SIZE(0..16))
    MAX-ACCESS read-write
    STATUS     current
    DESCRIPTION
        "-- empty --"
    ::= { lcsSetupConfigAdminsEntry 1 }

-- {COLUMN} 1712.2.11.21.1.2
lcsSetupConfigAdminsEntryPassword OBJECT-TYPE
    SYNTAX     DisplayString (SIZE(0..16))
    MAX-ACCESS read-write
    STATUS     current
    DESCRIPTION
        "-- empty --"
    ::= { lcsSetupConfigAdminsEntry 2 }

-- {COLUMN} 1712.2.11.21.1.4
lcsSetupConfigAdminsEntryActive OBJECT-TYPE
    SYNTAX     INTEGER
      {
        eNo (1),
        eYes (0)
      }
    MAX-ACCESS read-write
    STATUS     current
    DESCRIPTION
        "-- empty --"
    ::= { lcsSetupConfigAdminsEntry 4 }

-- {COLUMN} 1712.2.11.21.1.5
lcsSetupConfigAdminsEntryAccessRights OBJECT-TYPE
    SYNTAX     INTEGER
      {
        eNone (0),
        eAdminRoLimit (8388608),
        eAdminRwLimit (8388864),
        eAdminRo (16777216),
        eAdminRw (16777472),
        eSupervisor (-1)
      }
    MAX-ACCESS read-write
    STATUS     current
    DESCRIPTION
        "-- empty --"
    ::= { lcsSetupConfigAdminsEntry 5 }

-- {COLUMN} 1712.2.11.21.1.3
lcsSetupConfigAdminsEntryFunctionRights OBJECT-TYPE
    SYNTAX     BITS
      {
        eBasicWizard (31),
        eSecurityWizard (30),
        eInternetWizard (29),
        eRasWizard (27),
        eProviderSelection (28),
        eLanlanWizard (26),
        eTimeSetting (25),
        eDeviceSearch (24),
        eRolloutWizard (18),
        eDynamicDnsWizard (17),
        eSshCommand (14),
        eCfProfileWizard (13),
        ePublicSpotXmlInterface (12),
        ePublicSpotUserManagementWizard (11),
        ePublicSpotConfigurationWizard (10),
        ePrepareVoipProviderAccess (8)
      }
    MAX-ACCESS read-write
    STATUS     current
    DESCRIPTION
        "-- empty --"
    ::= { lcsSetupConfigAdminsEntry 3 }

-- {TABLE} 1712.2.11.27
lcsSetupConfigPredefAdminsTable OBJECT-TYPE
    SYNTAX     SEQUENCE OF LcsSetupConfigPredefAdminsEntry
    MAX-ACCESS not-accessible
    STATUS     current
    DESCRIPTION
        "-- empty --"
    ::= { lcsSetupConfig 27 }

-- {ENTRY} 1712.2.11.27.1
lcsSetupConfigPredefAdminsEntry OBJECT-TYPE
    SYNTAX     LcsSetupConfigPredefAdminsEntry
    MAX-ACCESS not-accessible
    STATUS     current
    DESCRIPTION
        ""
    INDEX {
        lcsSetupConfigPredefAdminsEntryName
    }
    ::= { lcsSetupConfigPredefAdminsTable 1 }

-- {SEQUENCE}
LcsSetupConfigPredefAdminsEntry ::= SEQUENCE {
    lcsSetupConfigPredefAdminsEntryName DisplayString
}

-- {COLUMN} 1712.2.11.27.1.1
lcsSetupConfigPredefAdminsEntryName OBJECT-TYPE
    SYNTAX     DisplayString (SIZE(0..15))
    MAX-ACCESS read-only
    STATUS     current
    DESCRIPTION
        "-- empty --"
    ::= { lcsSetupConfigPredefAdminsEntry 1 }

-- {SCALAR} 1712.2.11.90
lcsSetupConfigLedMode OBJECT-TYPE
    SYNTAX     INTEGER
      {
        eOn (0),
        eOff (1),
        eTimedOff (2)
      }
    MAX-ACCESS read-write
    STATUS     current
    DESCRIPTION
        "-- empty --"
    ::= { lcsSetupConfig 90 }

-- {SCALAR} 1712.2.11.91
lcsSetupConfigLedOffSeconds OBJECT-TYPE
    SYNTAX     INTEGER (0..2147483647)
    MAX-ACCESS read-write
    STATUS     current
    DESCRIPTION
        "-- empty --"
    ::= { lcsSetupConfig 91 }

-- {OID} 1712.2.11.13
lcsSetupConfigTftpClient OBJECT IDENTIFIER ::= { lcsSetupConfig 13 }

-- {SCALAR} 1712.2.11.13.1
lcsSetupConfigTftpClientConfigAddress OBJECT-TYPE
    SYNTAX     DisplayString (SIZE(0..31))
    MAX-ACCESS read-only
    STATUS     current
    DESCRIPTION
        "-- empty --"
    ::= { lcsSetupConfigTftpClient 1 }

-- {SCALAR} 1712.2.11.13.2
lcsSetupConfigTftpClientConfigFilename OBJECT-TYPE
    SYNTAX     DisplayString (SIZE(0..63))
    MAX-ACCESS read-only
    STATUS     current
    DESCRIPTION
        "-- empty --"
    ::= { lcsSetupConfigTftpClient 2 }

-- {SCALAR} 1712.2.11.13.3
lcsSetupConfigTftpClientFirmwareAddress OBJECT-TYPE
    SYNTAX     DisplayString (SIZE(0..31))
    MAX-ACCESS read-only
    STATUS     current
    DESCRIPTION
        "-- empty --"
    ::= { lcsSetupConfigTftpClient 3 }

-- {SCALAR} 1712.2.11.13.4
lcsSetupConfigTftpClientFirmwareFilename OBJECT-TYPE
    SYNTAX     DisplayString (SIZE(0..63))
    MAX-ACCESS read-only
    STATUS     current
    DESCRIPTION
        "-- empty --"
    ::= { lcsSetupConfigTftpClient 4 }

-- {SCALAR} 1712.2.11.13.6
lcsSetupConfigTftpClientScriptAddress OBJECT-TYPE
    SYNTAX     DisplayString (SIZE(0..31))
    MAX-ACCESS read-only
    STATUS     current
    DESCRIPTION
        "-- empty --"
    ::= { lcsSetupConfigTftpClient 6 }

-- {SCALAR} 1712.2.11.13.7
lcsSetupConfigTftpClientScriptFilename OBJECT-TYPE
    SYNTAX     DisplayString (SIZE(0..63))
    MAX-ACCESS read-only
    STATUS     current
    DESCRIPTION
        "-- empty --"
    ::= { lcsSetupConfigTftpClient 7 }

-- {SCALAR} 1712.2.11.13.5
lcsSetupConfigTftpClientBytesPerHashmark OBJECT-TYPE
    SYNTAX     INTEGER (0..2147483647)
    MAX-ACCESS read-only
    STATUS     current
    DESCRIPTION
        "-- empty --"
    ::= { lcsSetupConfigTftpClient 5 }

-- {SCALAR} 1712.2.11.25
lcsSetupConfigSshPort OBJECT-TYPE
    SYNTAX     INTEGER (0..65535)
    MAX-ACCESS read-write
    STATUS     current
    DESCRIPTION
        "-- empty --"
    ::= { lcsSetupConfig 25 }

-- {TABLE} 1712.2.11.26
lcsSetupConfigSshAuthenticationMethodsTable OBJECT-TYPE
    SYNTAX     SEQUENCE OF LcsSetupConfigSshAuthenticationMethodsEntry
    MAX-ACCESS not-accessible
    STATUS     current
    DESCRIPTION
        "-- empty --"
    ::= { lcsSetupConfig 26 }

-- {ENTRY} 1712.2.11.26.1
lcsSetupConfigSshAuthenticationMethodsEntry OBJECT-TYPE
    SYNTAX     LcsSetupConfigSshAuthenticationMethodsEntry
    MAX-ACCESS not-accessible
    STATUS     current
    DESCRIPTION
        ""
    INDEX {
        lcsSetupConfigSshAuthenticationMethodsEntryIfc
    }
    ::= { lcsSetupConfigSshAuthenticationMethodsTable 1 }

-- {SEQUENCE}
LcsSetupConfigSshAuthenticationMethodsEntry ::= SEQUENCE {
    lcsSetupConfigSshAuthenticationMethodsEntryIfc INTEGER,
    lcsSetupConfigSshAuthenticationMethodsEntryMethods INTEGER
}

-- {COLUMN} 1712.2.11.26.1.1
lcsSetupConfigSshAuthenticationMethodsEntryIfc OBJECT-TYPE
    SYNTAX     INTEGER
      {
        eLan (1),
        eWan (2)
      }
    MAX-ACCESS read-only
    STATUS     current
    DESCRIPTION
        "-- empty --"
    ::= { lcsSetupConfigSshAuthenticationMethodsEntry 1 }

-- {COLUMN} 1712.2.11.26.1.2
lcsSetupConfigSshAuthenticationMethodsEntryMethods OBJECT-TYPE
    SYNTAX     INTEGER
      {
        ePublicKey (1),
        eKeyboardInteractive (4),
        ePassword (2),
        ePasswordPlusKeyboardInteractive (6),
        ePasswordPlusPublicKey (3),
        eKeyboardInteractivePlusPublicKey (5),
        eAll (255)
      }
    MAX-ACCESS read-write
    STATUS     current
    DESCRIPTION
        "-- empty --"
    ::= { lcsSetupConfigSshAuthenticationMethodsEntry 2 }

-- {OID} 1712.2.11.28
lcsSetupConfigSsh OBJECT IDENTIFIER ::= { lcsSetupConfig 28 }

-- {SCALAR} 1712.2.11.28.1
lcsSetupConfigSshCipherAlgorithms OBJECT-TYPE
    SYNTAX     BITS
      {
        e3desCbc (31),
        e3desCtr (30),
        eArcfour (29),
        eArcfour128 (28),
        eArcfour256 (27),
        eBlowfishCbc (26),
        eBlowfishCtr (25),
        eAes128Cbc (24),
        eAes192Cbc (23),
        eAes256Cbc (22),
        eAes128Ctr (21),
        eAes192Ctr (20),
        eAes256Ctr (19)
      }
    MAX-ACCESS read-write
    STATUS     current
    DESCRIPTION
        "-- empty --"
    ::= { lcsSetupConfigSsh 1 }

-- {SCALAR} 1712.2.11.28.2
lcsSetupConfigSshMacAlgorithms OBJECT-TYPE
    SYNTAX     BITS
      {
        eHmacMd596 (31),
        eHmacMd5 (30),
        eHmacSha196 (29),
        eHmacSha1 (28),
        eHmacSha225696 (27),
        eHmacSha2256 (26),
        eHmacSha251296 (25),
        eHmacSha2512 (24)
      }
    MAX-ACCESS read-write
    STATUS     current
    DESCRIPTION
        "-- empty --"
    ::= { lcsSetupConfigSsh 2 }

-- {SCALAR} 1712.2.11.28.3
lcsSetupConfigSshKeyExchangeAlgorithms OBJECT-TYPE
    SYNTAX     BITS
      {
        eDiffieHellmanGroup1Sha1 (31),
        eDiffieHellmanGroup14Sha1 (30),
        eDiffieHellmanGroupExchangeSha1 (29),
        eDiffieHellmanGroupExchangeSha256 (28),
        eEcdhSha2 (27),
        eCurve25519Sha256 (26)
      }
    MAX-ACCESS read-write
    STATUS     current
    DESCRIPTION
        "-- empty --"
    ::= { lcsSetupConfigSsh 3 }

-- {SCALAR} 1712.2.11.28.7
lcsSetupConfigSshDhGroups OBJECT-TYPE
    SYNTAX     BITS
      {
        eGroup1 (31),
        eGroup5 (30),
        eGroup14 (29),
        eGroup15 (28),
        eGroup16 (27)
      }
    MAX-ACCESS read-write
    STATUS     current
    DESCRIPTION
        "-- empty --"
    ::= { lcsSetupConfigSsh 7 }

-- {SCALAR} 1712.2.11.28.9
lcsSetupConfigSshEllipticCurves OBJECT-TYPE
    SYNTAX     BITS
      {
        eNistp256 (31),
        eNistp384 (30),
        eNistp521 (29)
      }
    MAX-ACCESS read-write
    STATUS     current
    DESCRIPTION
        "-- empty --"
    ::= { lcsSetupConfigSsh 9 }

-- {SCALAR} 1712.2.11.28.4
lcsSetupConfigSshHostkeyAlgorithms OBJECT-TYPE
    SYNTAX     BITS
      {
        eSshRsa (31),
        eSshDss (30),
        eEcdsaSha2 (29),
        eSshEd25519 (28)
      }
    MAX-ACCESS read-write
    STATUS     current
    DESCRIPTION
        "-- empty --"
    ::= { lcsSetupConfigSsh 4 }

-- {SCALAR} 1712.2.11.28.5
lcsSetupConfigSshMinHostkeyLength OBJECT-TYPE
    SYNTAX     INTEGER (0..65535)
    MAX-ACCESS read-write
    STATUS     current
    DESCRIPTION
        "-- empty --"
    ::= { lcsSetupConfigSsh 5 }

-- {SCALAR} 1712.2.11.28.6
lcsSetupConfigSshMaxHostkeyLength OBJECT-TYPE
    SYNTAX     INTEGER (0..65535)
    MAX-ACCESS read-write
    STATUS     current
    DESCRIPTION
        "-- empty --"
    ::= { lcsSetupConfigSsh 6 }

-- {SCALAR} 1712.2.11.28.8
lcsSetupConfigSshCompression OBJECT-TYPE
    SYNTAX     INTEGER
      {
        eNo (0),
        eYes (1)
      }
    MAX-ACCESS read-write
    STATUS     current
    DESCRIPTION
        "-- empty --"
    ::= { lcsSetupConfigSsh 8 }

-- {SCALAR} 1712.2.11.28.11
lcsSetupConfigSshKeepaliveInterval OBJECT-TYPE
    SYNTAX     INTEGER (0..2147483647)
    MAX-ACCESS read-write
    STATUS     current
    DESCRIPTION
        "-- empty --"
    ::= { lcsSetupConfigSsh 11 }

-- {OID} 1712.2.11.28.10
lcsSetupConfigSshSftpServer OBJECT IDENTIFIER ::= { lcsSetupConfigSsh 10 }

-- {SCALAR} 1712.2.11.28.10.1
lcsSetupConfigSshSftpServerOperating OBJECT-TYPE
    SYNTAX     INTEGER
      {
        eNo (0),
        eYes (1)
      }
    MAX-ACCESS read-write
    STATUS     current
    DESCRIPTION
        "-- empty --"
    ::= { lcsSetupConfigSshSftpServer 1 }

-- {OID} 1712.2.13
lcsSetupLancapi OBJECT IDENTIFIER ::= { lcsSetup 13 }

-- {TABLE} 1712.2.13.1
lcsSetupLancapiAccessListTable OBJECT-TYPE
    SYNTAX     SEQUENCE OF LcsSetupLancapiAccessListEntry
    MAX-ACCESS not-accessible
    STATUS     current
    DESCRIPTION
        "-- empty --"
    ::= { lcsSetupLancapi 1 }

-- {ENTRY} 1712.2.13.1.1
lcsSetupLancapiAccessListEntry OBJECT-TYPE
    SYNTAX     LcsSetupLancapiAccessListEntry
    MAX-ACCESS not-accessible
    STATUS     current
    DESCRIPTION
        ""
    INDEX {
        lcsSetupLancapiAccessListEntryIpAddress,
        lcsSetupLancapiAccessListEntryIpNetmask,
        lcsSetupLancapiAccessListEntryRtgTag
    }
    ::= { lcsSetupLancapiAccessListTable 1 }

-- {SEQUENCE}
LcsSetupLancapiAccessListEntry ::= SEQUENCE {
    lcsSetupLancapiAccessListEntryIpAddress IpAddress,
    lcsSetupLancapiAccessListEntryIpNetmask IpAddress,
    lcsSetupLancapiAccessListEntryRtgTag INTEGER
}

-- {COLUMN} 1712.2.13.1.1.1
lcsSetupLancapiAccessListEntryIpAddress OBJECT-TYPE
    SYNTAX     IpAddress
    MAX-ACCESS read-write
    STATUS     current
    DESCRIPTION
        "-- empty --"
    ::= { lcsSetupLancapiAccessListEntry 1 }

-- {COLUMN} 1712.2.13.1.1.2
lcsSetupLancapiAccessListEntryIpNetmask OBJECT-TYPE
    SYNTAX     IpAddress
    MAX-ACCESS read-write
    STATUS     current
    DESCRIPTION
        "-- empty --"
    ::= { lcsSetupLancapiAccessListEntry 2 }

-- {COLUMN} 1712.2.13.1.1.3
lcsSetupLancapiAccessListEntryRtgTag OBJECT-TYPE
    SYNTAX     INTEGER (0..65535)
    MAX-ACCESS read-write
    STATUS     current
    DESCRIPTION
        "-- empty --"
    ::= { lcsSetupLancapiAccessListEntry 3 }

-- {SCALAR} 1712.2.13.3
lcsSetupLancapiUdpPort OBJECT-TYPE
    SYNTAX     INTEGER (0..65535)
    MAX-ACCESS read-write
    STATUS     current
    DESCRIPTION
        "-- empty --"
    ::= { lcsSetupLancapi 3 }

-- {TABLE} 1712.2.13.6
lcsSetupLancapiInterfaceListTable OBJECT-TYPE
    SYNTAX     SEQUENCE OF LcsSetupLancapiInterfaceListEntry
    MAX-ACCESS not-accessible
    STATUS     current
    DESCRIPTION
        "-- empty --"
    ::= { lcsSetupLancapi 6 }

-- {ENTRY} 1712.2.13.6.1
lcsSetupLancapiInterfaceListEntry OBJECT-TYPE
    SYNTAX     LcsSetupLancapiInterfaceListEntry
    MAX-ACCESS not-accessible
    STATUS     current
    DESCRIPTION
        ""
    INDEX {
        lcsSetupLancapiInterfaceListEntryIfc
    }
    ::= { lcsSetupLancapiInterfaceListTable 1 }

-- {SEQUENCE}
LcsSetupLancapiInterfaceListEntry ::= SEQUENCE {
    lcsSetupLancapiInterfaceListEntryIfc INTEGER,
    lcsSetupLancapiInterfaceListEntryOperating INTEGER,
    lcsSetupLancapiInterfaceListEntryMaxConnections INTEGER,
    lcsSetupLancapiInterfaceListEntryEazMsnS DisplayString,
    lcsSetupLancapiInterfaceListEntryForceOutMsn INTEGER
}

-- {COLUMN} 1712.2.13.6.1.1
lcsSetupLancapiInterfaceListEntryIfc OBJECT-TYPE
    SYNTAX     INTEGER
      {
        eS01 (1)
      }
    MAX-ACCESS read-only
    STATUS     current
    DESCRIPTION
        "-- empty --"
    ::= { lcsSetupLancapiInterfaceListEntry 1 }

-- {COLUMN} 1712.2.13.6.1.2
lcsSetupLancapiInterfaceListEntryOperating OBJECT-TYPE
    SYNTAX     INTEGER
      {
        eNo (0),
        eYes (1),
        eDialOnly (2),
        eDialInOnly (3)
      }
    MAX-ACCESS read-write
    STATUS     current
    DESCRIPTION
        "-- empty --"
    ::= { lcsSetupLancapiInterfaceListEntry 2 }

-- {COLUMN} 1712.2.13.6.1.6
lcsSetupLancapiInterfaceListEntryMaxConnections OBJECT-TYPE
    SYNTAX     INTEGER (0..255)
    MAX-ACCESS read-write
    STATUS     current
    DESCRIPTION
        "-- empty --"
    ::= { lcsSetupLancapiInterfaceListEntry 6 }

-- {COLUMN} 1712.2.13.6.1.3
lcsSetupLancapiInterfaceListEntryEazMsnS OBJECT-TYPE
    SYNTAX     DisplayString (SIZE(0..30))
    MAX-ACCESS read-write
    STATUS     current
    DESCRIPTION
        "-- empty --"
    ::= { lcsSetupLancapiInterfaceListEntry 3 }

-- {COLUMN} 1712.2.13.6.1.5
lcsSetupLancapiInterfaceListEntryForceOutMsn OBJECT-TYPE
    SYNTAX     INTEGER
      {
        eNo (0),
        eYes (1)
      }
    MAX-ACCESS read-write
    STATUS     current
    DESCRIPTION
        "-- empty --"
    ::= { lcsSetupLancapiInterfaceListEntry 5 }

-- {TABLE} 1712.2.13.7
lcsSetupLancapiPriorityListTable OBJECT-TYPE
    SYNTAX     SEQUENCE OF LcsSetupLancapiPriorityListEntry
    MAX-ACCESS not-accessible
    STATUS     current
    DESCRIPTION
        "-- empty --"
    ::= { lcsSetupLancapi 7 }

-- {ENTRY} 1712.2.13.7.1
lcsSetupLancapiPriorityListEntry OBJECT-TYPE
    SYNTAX     LcsSetupLancapiPriorityListEntry
    MAX-ACCESS not-accessible
    STATUS     current
    DESCRIPTION
        ""
    INDEX {
        lcsSetupLancapiPriorityListEntryIfc
    }
    ::= { lcsSetupLancapiPriorityListTable 1 }

-- {SEQUENCE}
LcsSetupLancapiPriorityListEntry ::= SEQUENCE {
    lcsSetupLancapiPriorityListEntryIfc INTEGER,
    lcsSetupLancapiPriorityListEntryPrioOut INTEGER
}

-- {COLUMN} 1712.2.13.7.1.1
lcsSetupLancapiPriorityListEntryIfc OBJECT-TYPE
    SYNTAX     INTEGER
      {
        eS01 (1)
      }
    MAX-ACCESS read-only
    STATUS     current
    DESCRIPTION
        "-- empty --"
    ::= { lcsSetupLancapiPriorityListEntry 1 }

-- {COLUMN} 1712.2.13.7.1.2
lcsSetupLancapiPriorityListEntryPrioOut OBJECT-TYPE
    SYNTAX     INTEGER
      {
        eP1 (0),
        eP2 (1),
        eP3 (2)
      }
    MAX-ACCESS read-write
    STATUS     current
    DESCRIPTION
        "-- empty --"
    ::= { lcsSetupLancapiPriorityListEntry 2 }

-- {OID} 1712.2.15
lcsSetupLcr OBJECT IDENTIFIER ::= { lcsSetup 15 }

-- {SCALAR} 1712.2.15.1
lcsSetupLcrRouterUsage OBJECT-TYPE
    SYNTAX     INTEGER
      {
        eNo (0),
        eYes (1)
      }
    MAX-ACCESS read-write
    STATUS     current
    DESCRIPTION
        "-- empty --"
    ::= { lcsSetupLcr 1 }

-- {SCALAR} 1712.2.15.2
lcsSetupLcrLancapiUsage OBJECT-TYPE
    SYNTAX     INTEGER
      {
        eNo (0),
        eYes (1)
      }
    MAX-ACCESS read-write
    STATUS     current
    DESCRIPTION
        "-- empty --"
    ::= { lcsSetupLcr 2 }

-- {TABLE} 1712.2.15.4
lcsSetupLcrTimeListTable OBJECT-TYPE
    SYNTAX     SEQUENCE OF LcsSetupLcrTimeListEntry
    MAX-ACCESS not-accessible
    STATUS     current
    DESCRIPTION
        "-- empty --"
    ::= { lcsSetupLcr 4 }

-- {ENTRY} 1712.2.15.4.1
lcsSetupLcrTimeListEntry OBJECT-TYPE
    SYNTAX     LcsSetupLcrTimeListEntry
    MAX-ACCESS not-accessible
    STATUS     current
    DESCRIPTION
        ""
    INDEX {
        lcsSetupLcrTimeListEntryIndex
    }
    ::= { lcsSetupLcrTimeListTable 1 }

-- {SEQUENCE}
LcsSetupLcrTimeListEntry ::= SEQUENCE {
    lcsSetupLcrTimeListEntryIndex INTEGER,
    lcsSetupLcrTimeListEntryPrefix DisplayString,
    lcsSetupLcrTimeListEntryDays BITS,
    lcsSetupLcrTimeListEntryStart DisplayString,
    lcsSetupLcrTimeListEntryStop DisplayString,
    lcsSetupLcrTimeListEntryNumberList DisplayString,
    lcsSetupLcrTimeListEntryFallback INTEGER
}

-- {COLUMN} 1712.2.15.4.1.1
lcsSetupLcrTimeListEntryIndex OBJECT-TYPE
    SYNTAX     INTEGER (0..65535)
    MAX-ACCESS read-write
    STATUS     current
    DESCRIPTION
        "-- empty --"
    ::= { lcsSetupLcrTimeListEntry 1 }

-- {COLUMN} 1712.2.15.4.1.2
lcsSetupLcrTimeListEntryPrefix OBJECT-TYPE
    SYNTAX     DisplayString (SIZE(0..10))
    MAX-ACCESS read-write
    STATUS     current
    DESCRIPTION
        "-- empty --"
    ::= { lcsSetupLcrTimeListEntry 2 }

-- {COLUMN} 1712.2.15.4.1.3
lcsSetupLcrTimeListEntryDays OBJECT-TYPE
    SYNTAX     BITS
      {
        eMonday (7),
        eTuesday (6),
        eWednesday (5),
        eThursday (4),
        eFriday (3),
        eSaturday (2),
        eSunday (1),
        eHoliday (0)
      }
    MAX-ACCESS read-write
    STATUS     current
    DESCRIPTION
        "-- empty --"
    ::= { lcsSetupLcrTimeListEntry 3 }

-- {COLUMN} 1712.2.15.4.1.4
lcsSetupLcrTimeListEntryStart OBJECT-TYPE
    SYNTAX     DisplayString (SIZE(0..5))
    MAX-ACCESS read-write
    STATUS     current
    DESCRIPTION
        "-- empty --"
    ::= { lcsSetupLcrTimeListEntry 4 }

-- {COLUMN} 1712.2.15.4.1.5
lcsSetupLcrTimeListEntryStop OBJECT-TYPE
    SYNTAX     DisplayString (SIZE(0..5))
    MAX-ACCESS read-write
    STATUS     current
    DESCRIPTION
        "-- empty --"
    ::= { lcsSetupLcrTimeListEntry 5 }

-- {COLUMN} 1712.2.15.4.1.6
lcsSetupLcrTimeListEntryNumberList OBJECT-TYPE
    SYNTAX     DisplayString (SIZE(0..29))
    MAX-ACCESS read-write
    STATUS     current
    DESCRIPTION
        "-- empty --"
    ::= { lcsSetupLcrTimeListEntry 6 }

-- {COLUMN} 1712.2.15.4.1.7
lcsSetupLcrTimeListEntryFallback OBJECT-TYPE
    SYNTAX     INTEGER
      {
        eNo (0),
        eYes (1)
      }
    MAX-ACCESS read-write
    STATUS     current
    DESCRIPTION
        "-- empty --"
    ::= { lcsSetupLcrTimeListEntry 7 }

-- {OID} 1712.2.14
lcsSetupTime OBJECT IDENTIFIER ::= { lcsSetup 14 }

-- {SCALAR} 1712.2.14.1
lcsSetupTimeFetchMethod OBJECT-TYPE
    SYNTAX     INTEGER
      {
        eNone (0),
        eIsdn (1),
        eNtp (2)
      }
    MAX-ACCESS read-write
    STATUS     current
    DESCRIPTION
        "-- empty --"
    ::= { lcsSetupTime 1 }

-- {SCALAR} 1712.2.14.2
lcsSetupTimeCurrentTime OBJECT-TYPE
    SYNTAX     DisplayString
    MAX-ACCESS read-only
    STATUS     current
    DESCRIPTION
        "-- empty --"
    ::= { lcsSetupTime 2 }

-- {SCALAR} 1712.2.14.3
lcsSetupTimeTimeCallNumber OBJECT-TYPE
    SYNTAX     DisplayString (SIZE(0..39))
    MAX-ACCESS read-write
    STATUS     current
    DESCRIPTION
        "-- empty --"
    ::= { lcsSetupTime 3 }

-- {SCALAR} 1712.2.14.5
lcsSetupTimeCallAttempts OBJECT-TYPE
    SYNTAX     INTEGER (0..255)
    MAX-ACCESS read-write
    STATUS     current
    DESCRIPTION
        "-- empty --"
    ::= { lcsSetupTime 5 }

-- {SCALAR} 1712.2.14.7
lcsSetupTimeUtcInSeconds OBJECT-TYPE
    SYNTAX     Counter32
    MAX-ACCESS read-only
    STATUS     current
    DESCRIPTION
        "-- empty --"
    ::= { lcsSetupTime 7 }

-- {SCALAR} 1712.2.14.10
lcsSetupTimeTimezone OBJECT-TYPE
    SYNTAX     INTEGER
      {
        e0 (0),
        eplus1 (1), -- plus 1 hour
        eplus2 (2), -- plus 2 hours
        eplus3 (3), -- plus 3 hours
        eplus4 (4), -- plus 4 hours
        eplus5 (5), -- plus 5 hours
        eplus6 (6), -- plus 6 hours
        eplus7 (7), -- plus 7 hours
        eplus8 (8), -- plus 8 hours
        eplus9 (9), -- plus 9 hours
        eplus10 (10), -- plus 10 hours
        eplus11 (11), -- plus 11 hours
        eplus12 (12), -- plus 12 hours
        eplus13 (13), -- plus 13 hours
        eplus14 (14), -- plus 14 hours
        eminus1 (255), -- minus 1 hour
        eminus2 (254), -- minus 2 hours
        eminus3 (253), -- minus 3 hours
        eminus4 (252), -- minus 4 hours
        eminus5 (251), -- minus 5 hours
        eminus6 (250), -- minus 6 hours
        eminus7 (249), -- minus 7 hours
        eminus8 (248), -- minus 8 hours
        eminus9 (247), -- minus 9 hours
        eminus10 (246), -- minus 10 hours
        eminus11 (245), -- minus 11 hours
        eminus12 (244) -- minus 12 hours
      }
    MAX-ACCESS read-write
    STATUS     current
    DESCRIPTION
        "-- empty --"
    ::= { lcsSetupTime 10 }

-- {SCALAR} 1712.2.14.11
lcsSetupTimeDaylightSavingTime OBJECT-TYPE
    SYNTAX     INTEGER
      {
        eNo (0),
        eYes (1),
        eEuropeEu (2),
        eUsa (4),
        eUserDefined (255)
      }
    MAX-ACCESS read-write
    STATUS     current
    DESCRIPTION
        "-- empty --"
    ::= { lcsSetupTime 11 }

-- {TABLE} 1712.2.14.12
lcsSetupTimeDstClockChangesTable OBJECT-TYPE
    SYNTAX     SEQUENCE OF LcsSetupTimeDstClockChangesEntry
    MAX-ACCESS not-accessible
    STATUS     current
    DESCRIPTION
        "-- empty --"
    ::= { lcsSetupTime 12 }

-- {ENTRY} 1712.2.14.12.1
lcsSetupTimeDstClockChangesEntry OBJECT-TYPE
    SYNTAX     LcsSetupTimeDstClockChangesEntry
    MAX-ACCESS not-accessible
    STATUS     current
    DESCRIPTION
        ""
    INDEX {
        lcsSetupTimeDstClockChangesEntryEvent
    }
    ::= { lcsSetupTimeDstClockChangesTable 1 }

-- {SEQUENCE}
LcsSetupTimeDstClockChangesEntry ::= SEQUENCE {
    lcsSetupTimeDstClockChangesEntryEvent INTEGER,
    lcsSetupTimeDstClockChangesEntryIndex INTEGER,
    lcsSetupTimeDstClockChangesEntryDay INTEGER,
    lcsSetupTimeDstClockChangesEntryMonth INTEGER,
    lcsSetupTimeDstClockChangesEntryHour INTEGER,
    lcsSetupTimeDstClockChangesEntryMinute INTEGER,
    lcsSetupTimeDstClockChangesEntryTimeType INTEGER
}

-- {COLUMN} 1712.2.14.12.1.1
lcsSetupTimeDstClockChangesEntryEvent OBJECT-TYPE
    SYNTAX     INTEGER
      {
        eStart (1),
        eEnd (2)
      }
    MAX-ACCESS read-only
    STATUS     current
    DESCRIPTION
        "-- empty --"
    ::= { lcsSetupTimeDstClockChangesEntry 1 }

-- {COLUMN} 1712.2.14.12.1.2
lcsSetupTimeDstClockChangesEntryIndex OBJECT-TYPE
    SYNTAX     INTEGER
      {
        e4Last (252),
        e3Last (253),
        e2Last (254),
        eLast (255),
        eFirst (1),
        eSecond (2),
        eThird (3),
        eFourth (4)
      }
    MAX-ACCESS read-write
    STATUS     current
    DESCRIPTION
        "-- empty --"
    ::= { lcsSetupTimeDstClockChangesEntry 2 }

-- {COLUMN} 1712.2.14.12.1.3
lcsSetupTimeDstClockChangesEntryDay OBJECT-TYPE
    SYNTAX     INTEGER
      {
        eSunday (0),
        eMonday (1),
        eTuesday (2),
        eWednesday (3),
        eThursday (4),
        eFriday (5),
        eSaturday (6)
      }
    MAX-ACCESS read-write
    STATUS     current
    DESCRIPTION
        "-- empty --"
    ::= { lcsSetupTimeDstClockChangesEntry 3 }

-- {COLUMN} 1712.2.14.12.1.4
lcsSetupTimeDstClockChangesEntryMonth OBJECT-TYPE
    SYNTAX     INTEGER
      {
        eJanuary (1),
        eFebruary (2),
        eMarch (3),
        eApril (4),
        eMay (5),
        eJune (6),
        eJuly (7),
        eAugust (8),
        eSeptember (9),
        eOctober (10),
        eNovember (11),
        eDecember (12)
      }
    MAX-ACCESS read-write
    STATUS     current
    DESCRIPTION
        "-- empty --"
    ::= { lcsSetupTimeDstClockChangesEntry 4 }

-- {COLUMN} 1712.2.14.12.1.5
lcsSetupTimeDstClockChangesEntryHour OBJECT-TYPE
    SYNTAX     INTEGER (0..255)
    MAX-ACCESS read-write
    STATUS     current
    DESCRIPTION
        "-- empty --"
    ::= { lcsSetupTimeDstClockChangesEntry 5 }

-- {COLUMN} 1712.2.14.12.1.6
lcsSetupTimeDstClockChangesEntryMinute OBJECT-TYPE
    SYNTAX     INTEGER (0..255)
    MAX-ACCESS read-write
    STATUS     current
    DESCRIPTION
        "-- empty --"
    ::= { lcsSetupTimeDstClockChangesEntry 6 }

-- {COLUMN} 1712.2.14.12.1.7
lcsSetupTimeDstClockChangesEntryTimeType OBJECT-TYPE
    SYNTAX     INTEGER
      {
        eUtc (1),
        eLst (0)
      }
    MAX-ACCESS read-write
    STATUS     current
    DESCRIPTION
        "-- empty --"
    ::= { lcsSetupTimeDstClockChangesEntry 7 }

-- {TABLE} 1712.2.14.15
lcsSetupTimeHolidaysTable OBJECT-TYPE
    SYNTAX     SEQUENCE OF LcsSetupTimeHolidaysEntry
    MAX-ACCESS not-accessible
    STATUS     current
    DESCRIPTION
        "-- empty --"
    ::= { lcsSetupTime 15 }

-- {ENTRY} 1712.2.14.15.1
lcsSetupTimeHolidaysEntry OBJECT-TYPE
    SYNTAX     LcsSetupTimeHolidaysEntry
    MAX-ACCESS not-accessible
    STATUS     current
    DESCRIPTION
        ""
    INDEX {
        lcsSetupTimeHolidaysEntryIndex
    }
    ::= { lcsSetupTimeHolidaysTable 1 }

-- {SEQUENCE}
LcsSetupTimeHolidaysEntry ::= SEQUENCE {
    lcsSetupTimeHolidaysEntryIndex INTEGER,
    lcsSetupTimeHolidaysEntryDate DisplayString
}

-- {COLUMN} 1712.2.14.15.1.1
lcsSetupTimeHolidaysEntryIndex OBJECT-TYPE
    SYNTAX     INTEGER (0..65535)
    MAX-ACCESS read-write
    STATUS     current
    DESCRIPTION
        "-- empty --"
    ::= { lcsSetupTimeHolidaysEntry 1 }

-- {COLUMN} 1712.2.14.15.1.2
lcsSetupTimeHolidaysEntryDate OBJECT-TYPE
    SYNTAX     DisplayString (SIZE(0..13))
    MAX-ACCESS read-write
    STATUS     current
    DESCRIPTION
        "-- empty --"
    ::= { lcsSetupTimeHolidaysEntry 2 }

-- {TABLE} 1712.2.14.16
lcsSetupTimeTimeframeTable OBJECT-TYPE
    SYNTAX     SEQUENCE OF LcsSetupTimeTimeframeEntry
    MAX-ACCESS not-accessible
    STATUS     current
    DESCRIPTION
        "-- empty --"
    ::= { lcsSetupTime 16 }

-- {ENTRY} 1712.2.14.16.1
lcsSetupTimeTimeframeEntry OBJECT-TYPE
    SYNTAX     LcsSetupTimeTimeframeEntry
    MAX-ACCESS not-accessible
    STATUS     current
    DESCRIPTION
        ""
    INDEX {
        lcsSetupTimeTimeframeEntryName,
        lcsSetupTimeTimeframeEntryStart,
        lcsSetupTimeTimeframeEntryStop,
        lcsSetupTimeTimeframeEntryWeekdays
    }
    ::= { lcsSetupTimeTimeframeTable 1 }

-- {SEQUENCE}
LcsSetupTimeTimeframeEntry ::= SEQUENCE {
    lcsSetupTimeTimeframeEntryName DisplayString,
    lcsSetupTimeTimeframeEntryStart DisplayString,
    lcsSetupTimeTimeframeEntryStop DisplayString,
    lcsSetupTimeTimeframeEntryWeekdays BITS
}

-- {COLUMN} 1712.2.14.16.1.1
lcsSetupTimeTimeframeEntryName OBJECT-TYPE
    SYNTAX     DisplayString (SIZE(0..31))
    MAX-ACCESS read-write
    STATUS     current
    DESCRIPTION
        "-- empty --"
    ::= { lcsSetupTimeTimeframeEntry 1 }

-- {COLUMN} 1712.2.14.16.1.2
lcsSetupTimeTimeframeEntryStart OBJECT-TYPE
    SYNTAX     DisplayString (SIZE(0..5))
    MAX-ACCESS read-write
    STATUS     current
    DESCRIPTION
        "-- empty --"
    ::= { lcsSetupTimeTimeframeEntry 2 }

-- {COLUMN} 1712.2.14.16.1.3
lcsSetupTimeTimeframeEntryStop OBJECT-TYPE
    SYNTAX     DisplayString (SIZE(0..5))
    MAX-ACCESS read-write
    STATUS     current
    DESCRIPTION
        "-- empty --"
    ::= { lcsSetupTimeTimeframeEntry 3 }

-- {COLUMN} 1712.2.14.16.1.4
lcsSetupTimeTimeframeEntryWeekdays OBJECT-TYPE
    SYNTAX     BITS
      {
        eSunday (7),
        eMonday (6),
        eTuesday (5),
        eWednesday (4),
        eThursday (3),
        eFriday (2),
        eSaturday (1),
        eHoliday (0)
      }
    MAX-ACCESS read-write
    STATUS     current
    DESCRIPTION
        "-- empty --"
    ::= { lcsSetupTimeTimeframeEntry 4 }

-- {SCALAR} 1712.2.14.13
lcsSetupTimeGetTime OBJECT-TYPE
    SYNTAX     DisplayString
    MAX-ACCESS read-write
    STATUS     current
    DESCRIPTION
        "-- empty --"
    ::= { lcsSetupTime 13 }

-- {OID} 1712.2.19
lcsSetupVpn OBJECT IDENTIFIER ::= { lcsSetup 19 }

-- {SCALAR} 1712.2.19.8
lcsSetupVpnOperating OBJECT-TYPE
    SYNTAX     INTEGER
      {
        eNo (0),
        eYes (1),
        eExclusive (3)
      }
    MAX-ACCESS read-write
    STATUS     current
    DESCRIPTION
        "-- empty --"
    ::= { lcsSetupVpn 8 }

-- {OID} 1712.2.19.64
lcsSetupVpnOcspClient OBJECT IDENTIFIER ::= { lcsSetupVpn 64 }

-- {SCALAR} 1712.2.19.64.1
lcsSetupVpnOcspClientActive OBJECT-TYPE
    SYNTAX     INTEGER
      {
        eNo (0),
        eYes (1)
      }
    MAX-ACCESS read-write
    STATUS     current
    DESCRIPTION
        "-- empty --"
    ::= { lcsSetupVpnOcspClient 1 }

-- {SCALAR} 1712.2.19.16
lcsSetupVpnNatTOperating OBJECT-TYPE
    SYNTAX     INTEGER
      {
        eNo (0),
        eYes (1)
      }
    MAX-ACCESS read-write
    STATUS     current
    DESCRIPTION
        "-- empty --"
    ::= { lcsSetupVpn 16 }

-- {SCALAR} 1712.2.19.17
lcsSetupVpnSimpleCertRasOperating OBJECT-TYPE
    SYNTAX     INTEGER
      {
        eNo (0),
        eYes (1)
      }
    MAX-ACCESS read-write
    STATUS     current
    DESCRIPTION
        "-- empty --"
    ::= { lcsSetupVpn 17 }

-- {SCALAR} 1712.2.19.22
lcsSetupVpnAllowRemoteNetworkSelection OBJECT-TYPE
    SYNTAX     INTEGER
      {
        eNo (0),
        eYes (1)
      }
    MAX-ACCESS read-write
    STATUS     current
    DESCRIPTION
        "-- empty --"
    ::= { lcsSetupVpn 22 }

-- {SCALAR} 1712.2.19.23
lcsSetupVpnEstablishSasCollectively OBJECT-TYPE
    SYNTAX     INTEGER
      {
        eNo (0),
        eYes (1),
        eOnlyWithKeepalive (2)
      }
    MAX-ACCESS read-write
    STATUS     current
    DESCRIPTION
        "-- empty --"
    ::= { lcsSetupVpn 23 }

-- {TABLE} 1712.2.19.9
lcsSetupVpnVpnPeersTable OBJECT-TYPE
    SYNTAX     SEQUENCE OF LcsSetupVpnVpnPeersEntry
    MAX-ACCESS not-accessible
    STATUS     current
    DESCRIPTION
        "-- empty --"
    ::= { lcsSetupVpn 9 }

-- {ENTRY} 1712.2.19.9.1
lcsSetupVpnVpnPeersEntry OBJECT-TYPE
    SYNTAX     LcsSetupVpnVpnPeersEntry
    MAX-ACCESS not-accessible
    STATUS     current
    DESCRIPTION
        ""
    INDEX {
        lcsSetupVpnVpnPeersEntryPeer
    }
    ::= { lcsSetupVpnVpnPeersTable 1 }

-- {SEQUENCE}
LcsSetupVpnVpnPeersEntry ::= SEQUENCE {
    lcsSetupVpnVpnPeersEntryPeer DisplayString,
    lcsSetupVpnVpnPeersEntryShTime INTEGER,
    lcsSetupVpnVpnPeersEntryExtranetAddress IpAddress,
    lcsSetupVpnVpnPeersEntryRemoteGw DisplayString,
    lcsSetupVpnVpnPeersEntryRtgTag INTEGER,
    lcsSetupVpnVpnPeersEntryLayer DisplayString,
    lcsSetupVpnVpnPeersEntryDynamic INTEGER,
    lcsSetupVpnVpnPeersEntryIkeExchange INTEGER,
    lcsSetupVpnVpnPeersEntryRuleCreation INTEGER,
    lcsSetupVpnVpnPeersEntryDpdInactTimeout INTEGER,
    lcsSetupVpnVpnPeersEntryIkeCfg INTEGER,
    lcsSetupVpnVpnPeersEntryXauth INTEGER,
    lcsSetupVpnVpnPeersEntrySslEncaps INTEGER,
    lcsSetupVpnVpnPeersEntryOcspCheck INTEGER
}

-- {COLUMN} 1712.2.19.9.1.1
lcsSetupVpnVpnPeersEntryPeer OBJECT-TYPE
    SYNTAX     DisplayString (SIZE(0..16))
    MAX-ACCESS read-write
    STATUS     current
    DESCRIPTION
        "-- empty --"
    ::= { lcsSetupVpnVpnPeersEntry 1 }

-- {COLUMN} 1712.2.19.9.1.6
lcsSetupVpnVpnPeersEntryShTime OBJECT-TYPE
    SYNTAX     INTEGER (0..65535)
    MAX-ACCESS read-write
    STATUS     current
    DESCRIPTION
        "-- empty --"
    ::= { lcsSetupVpnVpnPeersEntry 6 }

-- {COLUMN} 1712.2.19.9.1.2
lcsSetupVpnVpnPeersEntryExtranetAddress OBJECT-TYPE
    SYNTAX     IpAddress
    MAX-ACCESS read-write
    STATUS     current
    DESCRIPTION
        "-- empty --"
    ::= { lcsSetupVpnVpnPeersEntry 2 }

-- {COLUMN} 1712.2.19.9.1.8
lcsSetupVpnVpnPeersEntryRemoteGw OBJECT-TYPE
    SYNTAX     DisplayString (SIZE(0..63))
    MAX-ACCESS read-write
    STATUS     current
    DESCRIPTION
        "-- empty --"
    ::= { lcsSetupVpnVpnPeersEntry 8 }

-- {COLUMN} 1712.2.19.9.1.15
lcsSetupVpnVpnPeersEntryRtgTag OBJECT-TYPE
    SYNTAX     INTEGER (0..65535)
    MAX-ACCESS read-write
    STATUS     current
    DESCRIPTION
        "-- empty --"
    ::= { lcsSetupVpnVpnPeersEntry 15 }

-- {COLUMN} 1712.2.19.9.1.4
lcsSetupVpnVpnPeersEntryLayer OBJECT-TYPE
    SYNTAX     DisplayString (SIZE(0..16))
    MAX-ACCESS read-write
    STATUS     current
    DESCRIPTION
        "-- empty --"
    ::= { lcsSetupVpnVpnPeersEntry 4 }

-- {COLUMN} 1712.2.19.9.1.5
lcsSetupVpnVpnPeersEntryDynamic OBJECT-TYPE
    SYNTAX     INTEGER
      {
        eNo (0),
        eIcmp (4),
        eUdp (8),
        eBChannel (1),
        eDChannel (2)
      }
    MAX-ACCESS read-write
    STATUS     current
    DESCRIPTION
        "-- empty --"
    ::= { lcsSetupVpnVpnPeersEntry 5 }

-- {COLUMN} 1712.2.19.9.1.7
lcsSetupVpnVpnPeersEntryIkeExchange OBJECT-TYPE
    SYNTAX     INTEGER
      {
        eMainMode (0),
        eAggressiveMode (1)
      }
    MAX-ACCESS read-write
    STATUS     current
    DESCRIPTION
        "-- empty --"
    ::= { lcsSetupVpnVpnPeersEntry 7 }

-- {COLUMN} 1712.2.19.9.1.9
lcsSetupVpnVpnPeersEntryRuleCreation OBJECT-TYPE
    SYNTAX     INTEGER
      {
        eAuto (0),
        eManually (1),
        eOff (2)
      }
    MAX-ACCESS read-write
    STATUS     current
    DESCRIPTION
        "-- empty --"
    ::= { lcsSetupVpnVpnPeersEntry 9 }

-- {COLUMN} 1712.2.19.9.1.10
lcsSetupVpnVpnPeersEntryDpdInactTimeout OBJECT-TYPE
    SYNTAX     INTEGER (0..2147483647)
    MAX-ACCESS read-write
    STATUS     current
    DESCRIPTION
        "-- empty --"
    ::= { lcsSetupVpnVpnPeersEntry 10 }

-- {COLUMN} 1712.2.19.9.1.11
lcsSetupVpnVpnPeersEntryIkeCfg OBJECT-TYPE
    SYNTAX     INTEGER
      {
        eOff (0),
        eClient (1),
        eServer (2)
      }
    MAX-ACCESS read-write
    STATUS     current
    DESCRIPTION
        "-- empty --"
    ::= { lcsSetupVpnVpnPeersEntry 11 }

-- {COLUMN} 1712.2.19.9.1.12
lcsSetupVpnVpnPeersEntryXauth OBJECT-TYPE
    SYNTAX     INTEGER
      {
        eOff (0),
        eClient (1),
        eServer (2)
      }
    MAX-ACCESS read-write
    STATUS     current
    DESCRIPTION
        "-- empty --"
    ::= { lcsSetupVpnVpnPeersEntry 12 }

-- {COLUMN} 1712.2.19.9.1.13
lcsSetupVpnVpnPeersEntrySslEncaps OBJECT-TYPE
    SYNTAX     INTEGER
      {
        eNo (0),
        eYes (1)
      }
    MAX-ACCESS read-write
    STATUS     current
    DESCRIPTION
        "-- empty --"
    ::= { lcsSetupVpnVpnPeersEntry 13 }

-- {COLUMN} 1712.2.19.9.1.16
lcsSetupVpnVpnPeersEntryOcspCheck OBJECT-TYPE
    SYNTAX     INTEGER
      {
        eNo (0),
        eYes (1)
      }
    MAX-ACCESS read-write
    STATUS     current
    DESCRIPTION
        "-- empty --"
    ::= { lcsSetupVpnVpnPeersEntry 16 }

-- {TABLE} 1712.2.19.12
lcsSetupVpnAdditionalGatewaysTable OBJECT-TYPE
    SYNTAX     SEQUENCE OF LcsSetupVpnAdditionalGatewaysEntry
    MAX-ACCESS not-accessible
    STATUS     current
    DESCRIPTION
        "-- empty --"
    ::= { lcsSetupVpn 12 }

-- {ENTRY} 1712.2.19.12.1
lcsSetupVpnAdditionalGatewaysEntry OBJECT-TYPE
    SYNTAX     LcsSetupVpnAdditionalGatewaysEntry
    MAX-ACCESS not-accessible
    STATUS     current
    DESCRIPTION
        ""
    INDEX {
        lcsSetupVpnAdditionalGatewaysEntryPeer
    }
    ::= { lcsSetupVpnAdditionalGatewaysTable 1 }

-- {SEQUENCE}
LcsSetupVpnAdditionalGatewaysEntry ::= SEQUENCE {
    lcsSetupVpnAdditionalGatewaysEntryPeer DisplayString,
    lcsSetupVpnAdditionalGatewaysEntryGateway1 DisplayString,
    lcsSetupVpnAdditionalGatewaysEntryRtgTag1 INTEGER,
    lcsSetupVpnAdditionalGatewaysEntryGateway2 DisplayString,
    lcsSetupVpnAdditionalGatewaysEntryRtgTag2 INTEGER,
    lcsSetupVpnAdditionalGatewaysEntryGateway3 DisplayString,
    lcsSetupVpnAdditionalGatewaysEntryRtgTag3 INTEGER,
    lcsSetupVpnAdditionalGatewaysEntryGateway4 DisplayString,
    lcsSetupVpnAdditionalGatewaysEntryRtgTag4 INTEGER,
    lcsSetupVpnAdditionalGatewaysEntryGateway5 DisplayString,
    lcsSetupVpnAdditionalGatewaysEntryRtgTag5 INTEGER,
    lcsSetupVpnAdditionalGatewaysEntryGateway6 DisplayString,
    lcsSetupVpnAdditionalGatewaysEntryRtgTag6 INTEGER,
    lcsSetupVpnAdditionalGatewaysEntryGateway7 DisplayString,
    lcsSetupVpnAdditionalGatewaysEntryRtgTag7 INTEGER,
    lcsSetupVpnAdditionalGatewaysEntryGateway8 DisplayString,
    lcsSetupVpnAdditionalGatewaysEntryRtgTag8 INTEGER,
    lcsSetupVpnAdditionalGatewaysEntryGateway9 DisplayString,
    lcsSetupVpnAdditionalGatewaysEntryRtgTag9 INTEGER,
    lcsSetupVpnAdditionalGatewaysEntryGateway10 DisplayString,
    lcsSetupVpnAdditionalGatewaysEntryRtgTag10 INTEGER,
    lcsSetupVpnAdditionalGatewaysEntryGateway11 DisplayString,
    lcsSetupVpnAdditionalGatewaysEntryRtgTag11 INTEGER,
    lcsSetupVpnAdditionalGatewaysEntryGateway12 DisplayString,
    lcsSetupVpnAdditionalGatewaysEntryRtgTag12 INTEGER,
    lcsSetupVpnAdditionalGatewaysEntryGateway13 DisplayString,
    lcsSetupVpnAdditionalGatewaysEntryRtgTag13 INTEGER,
    lcsSetupVpnAdditionalGatewaysEntryGateway14 DisplayString,
    lcsSetupVpnAdditionalGatewaysEntryRtgTag14 INTEGER,
    lcsSetupVpnAdditionalGatewaysEntryGateway15 DisplayString,
    lcsSetupVpnAdditionalGatewaysEntryRtgTag15 INTEGER,
    lcsSetupVpnAdditionalGatewaysEntryGateway16 DisplayString,
    lcsSetupVpnAdditionalGatewaysEntryRtgTag16 INTEGER,
    lcsSetupVpnAdditionalGatewaysEntryGateway17 DisplayString,
    lcsSetupVpnAdditionalGatewaysEntryRtgTag17 INTEGER,
    lcsSetupVpnAdditionalGatewaysEntryGateway18 DisplayString,
    lcsSetupVpnAdditionalGatewaysEntryRtgTag18 INTEGER,
    lcsSetupVpnAdditionalGatewaysEntryGateway19 DisplayString,
    lcsSetupVpnAdditionalGatewaysEntryRtgTag19 INTEGER,
    lcsSetupVpnAdditionalGatewaysEntryGateway20 DisplayString,
    lcsSetupVpnAdditionalGatewaysEntryRtgTag20 INTEGER,
    lcsSetupVpnAdditionalGatewaysEntryGateway21 DisplayString,
    lcsSetupVpnAdditionalGatewaysEntryRtgTag21 INTEGER,
    lcsSetupVpnAdditionalGatewaysEntryGateway22 DisplayString,
    lcsSetupVpnAdditionalGatewaysEntryRtgTag22 INTEGER,
    lcsSetupVpnAdditionalGatewaysEntryGateway23 DisplayString,
    lcsSetupVpnAdditionalGatewaysEntryRtgTag23 INTEGER,
    lcsSetupVpnAdditionalGatewaysEntryGateway24 DisplayString,
    lcsSetupVpnAdditionalGatewaysEntryRtgTag24 INTEGER,
    lcsSetupVpnAdditionalGatewaysEntryGateway25 DisplayString,
    lcsSetupVpnAdditionalGatewaysEntryRtgTag25 INTEGER,
    lcsSetupVpnAdditionalGatewaysEntryGateway26 DisplayString,
    lcsSetupVpnAdditionalGatewaysEntryRtgTag26 INTEGER,
    lcsSetupVpnAdditionalGatewaysEntryGateway27 DisplayString,
    lcsSetupVpnAdditionalGatewaysEntryRtgTag27 INTEGER,
    lcsSetupVpnAdditionalGatewaysEntryGateway28 DisplayString,
    lcsSetupVpnAdditionalGatewaysEntryRtgTag28 INTEGER,
    lcsSetupVpnAdditionalGatewaysEntryGateway29 DisplayString,
    lcsSetupVpnAdditionalGatewaysEntryRtgTag29 INTEGER,
    lcsSetupVpnAdditionalGatewaysEntryGateway30 DisplayString,
    lcsSetupVpnAdditionalGatewaysEntryRtgTag30 INTEGER,
    lcsSetupVpnAdditionalGatewaysEntryGateway31 DisplayString,
    lcsSetupVpnAdditionalGatewaysEntryRtgTag31 INTEGER,
    lcsSetupVpnAdditionalGatewaysEntryGateway32 DisplayString,
    lcsSetupVpnAdditionalGatewaysEntryRtgTag32 INTEGER,
    lcsSetupVpnAdditionalGatewaysEntryBeginWith INTEGER
}

-- {COLUMN} 1712.2.19.12.1.1
lcsSetupVpnAdditionalGatewaysEntryPeer OBJECT-TYPE
    SYNTAX     DisplayString (SIZE(0..16))
    MAX-ACCESS read-write
    STATUS     current
    DESCRIPTION
        "-- empty --"
    ::= { lcsSetupVpnAdditionalGatewaysEntry 1 }

-- {COLUMN} 1712.2.19.12.1.2
lcsSetupVpnAdditionalGatewaysEntryGateway1 OBJECT-TYPE
    SYNTAX     DisplayString (SIZE(0..64))
    MAX-ACCESS read-write
    STATUS     current
    DESCRIPTION
        "-- empty --"
    ::= { lcsSetupVpnAdditionalGatewaysEntry 2 }

-- {COLUMN} 1712.2.19.12.1.11
lcsSetupVpnAdditionalGatewaysEntryRtgTag1 OBJECT-TYPE
    SYNTAX     INTEGER (0..65535)
    MAX-ACCESS read-write
    STATUS     current
    DESCRIPTION
        "-- empty --"
    ::= { lcsSetupVpnAdditionalGatewaysEntry 11 }

-- {COLUMN} 1712.2.19.12.1.3
lcsSetupVpnAdditionalGatewaysEntryGateway2 OBJECT-TYPE
    SYNTAX     DisplayString (SIZE(0..64))
    MAX-ACCESS read-write
    STATUS     current
    DESCRIPTION
        "-- empty --"
    ::= { lcsSetupVpnAdditionalGatewaysEntry 3 }

-- {COLUMN} 1712.2.19.12.1.12
lcsSetupVpnAdditionalGatewaysEntryRtgTag2 OBJECT-TYPE
    SYNTAX     INTEGER (0..65535)
    MAX-ACCESS read-write
    STATUS     current
    DESCRIPTION
        "-- empty --"
    ::= { lcsSetupVpnAdditionalGatewaysEntry 12 }

-- {COLUMN} 1712.2.19.12.1.4
lcsSetupVpnAdditionalGatewaysEntryGateway3 OBJECT-TYPE
    SYNTAX     DisplayString (SIZE(0..64))
    MAX-ACCESS read-write
    STATUS     current
    DESCRIPTION
        "-- empty --"
    ::= { lcsSetupVpnAdditionalGatewaysEntry 4 }

-- {COLUMN} 1712.2.19.12.1.13
lcsSetupVpnAdditionalGatewaysEntryRtgTag3 OBJECT-TYPE
    SYNTAX     INTEGER (0..65535)
    MAX-ACCESS read-write
    STATUS     current
    DESCRIPTION
        "-- empty --"
    ::= { lcsSetupVpnAdditionalGatewaysEntry 13 }

-- {COLUMN} 1712.2.19.12.1.5
lcsSetupVpnAdditionalGatewaysEntryGateway4 OBJECT-TYPE
    SYNTAX     DisplayString (SIZE(0..64))
    MAX-ACCESS read-write
    STATUS     current
    DESCRIPTION
        "-- empty --"
    ::= { lcsSetupVpnAdditionalGatewaysEntry 5 }

-- {COLUMN} 1712.2.19.12.1.14
lcsSetupVpnAdditionalGatewaysEntryRtgTag4 OBJECT-TYPE
    SYNTAX     INTEGER (0..65535)
    MAX-ACCESS read-write
    STATUS     current
    DESCRIPTION
        "-- empty --"
    ::= { lcsSetupVpnAdditionalGatewaysEntry 14 }

-- {COLUMN} 1712.2.19.12.1.6
lcsSetupVpnAdditionalGatewaysEntryGateway5 OBJECT-TYPE
    SYNTAX     DisplayString (SIZE(0..64))
    MAX-ACCESS read-write
    STATUS     current
    DESCRIPTION
        "-- empty --"
    ::= { lcsSetupVpnAdditionalGatewaysEntry 6 }

-- {COLUMN} 1712.2.19.12.1.15
lcsSetupVpnAdditionalGatewaysEntryRtgTag5 OBJECT-TYPE
    SYNTAX     INTEGER (0..65535)
    MAX-ACCESS read-write
    STATUS     current
    DESCRIPTION
        "-- empty --"
    ::= { lcsSetupVpnAdditionalGatewaysEntry 15 }

-- {COLUMN} 1712.2.19.12.1.7
lcsSetupVpnAdditionalGatewaysEntryGateway6 OBJECT-TYPE
    SYNTAX     DisplayString (SIZE(0..64))
    MAX-ACCESS read-write
    STATUS     current
    DESCRIPTION
        "-- empty --"
    ::= { lcsSetupVpnAdditionalGatewaysEntry 7 }

-- {COLUMN} 1712.2.19.12.1.16
lcsSetupVpnAdditionalGatewaysEntryRtgTag6 OBJECT-TYPE
    SYNTAX     INTEGER (0..65535)
    MAX-ACCESS read-write
    STATUS     current
    DESCRIPTION
        "-- empty --"
    ::= { lcsSetupVpnAdditionalGatewaysEntry 16 }

-- {COLUMN} 1712.2.19.12.1.8
lcsSetupVpnAdditionalGatewaysEntryGateway7 OBJECT-TYPE
    SYNTAX     DisplayString (SIZE(0..64))
    MAX-ACCESS read-write
    STATUS     current
    DESCRIPTION
        "-- empty --"
    ::= { lcsSetupVpnAdditionalGatewaysEntry 8 }

-- {COLUMN} 1712.2.19.12.1.17
lcsSetupVpnAdditionalGatewaysEntryRtgTag7 OBJECT-TYPE
    SYNTAX     INTEGER (0..65535)
    MAX-ACCESS read-write
    STATUS     current
    DESCRIPTION
        "-- empty --"
    ::= { lcsSetupVpnAdditionalGatewaysEntry 17 }

-- {COLUMN} 1712.2.19.12.1.9
lcsSetupVpnAdditionalGatewaysEntryGateway8 OBJECT-TYPE
    SYNTAX     DisplayString (SIZE(0..64))
    MAX-ACCESS read-write
    STATUS     current
    DESCRIPTION
        "-- empty --"
    ::= { lcsSetupVpnAdditionalGatewaysEntry 9 }

-- {COLUMN} 1712.2.19.12.1.18
lcsSetupVpnAdditionalGatewaysEntryRtgTag8 OBJECT-TYPE
    SYNTAX     INTEGER (0..65535)
    MAX-ACCESS read-write
    STATUS     current
    DESCRIPTION
        "-- empty --"
    ::= { lcsSetupVpnAdditionalGatewaysEntry 18 }

-- {COLUMN} 1712.2.19.12.1.19
lcsSetupVpnAdditionalGatewaysEntryGateway9 OBJECT-TYPE
    SYNTAX     DisplayString (SIZE(0..64))
    MAX-ACCESS read-write
    STATUS     current
    DESCRIPTION
        "-- empty --"
    ::= { lcsSetupVpnAdditionalGatewaysEntry 19 }

-- {COLUMN} 1712.2.19.12.1.27
lcsSetupVpnAdditionalGatewaysEntryRtgTag9 OBJECT-TYPE
    SYNTAX     INTEGER (0..65535)
    MAX-ACCESS read-write
    STATUS     current
    DESCRIPTION
        "-- empty --"
    ::= { lcsSetupVpnAdditionalGatewaysEntry 27 }

-- {COLUMN} 1712.2.19.12.1.20
lcsSetupVpnAdditionalGatewaysEntryGateway10 OBJECT-TYPE
    SYNTAX     DisplayString (SIZE(0..64))
    MAX-ACCESS read-write
    STATUS     current
    DESCRIPTION
        "-- empty --"
    ::= { lcsSetupVpnAdditionalGatewaysEntry 20 }

-- {COLUMN} 1712.2.19.12.1.28
lcsSetupVpnAdditionalGatewaysEntryRtgTag10 OBJECT-TYPE
    SYNTAX     INTEGER (0..65535)
    MAX-ACCESS read-write
    STATUS     current
    DESCRIPTION
        "-- empty --"
    ::= { lcsSetupVpnAdditionalGatewaysEntry 28 }

-- {COLUMN} 1712.2.19.12.1.21
lcsSetupVpnAdditionalGatewaysEntryGateway11 OBJECT-TYPE
    SYNTAX     DisplayString (SIZE(0..64))
    MAX-ACCESS read-write
    STATUS     current
    DESCRIPTION
        "-- empty --"
    ::= { lcsSetupVpnAdditionalGatewaysEntry 21 }

-- {COLUMN} 1712.2.19.12.1.29
lcsSetupVpnAdditionalGatewaysEntryRtgTag11 OBJECT-TYPE
    SYNTAX     INTEGER (0..65535)
    MAX-ACCESS read-write
    STATUS     current
    DESCRIPTION
        "-- empty --"
    ::= { lcsSetupVpnAdditionalGatewaysEntry 29 }

-- {COLUMN} 1712.2.19.12.1.22
lcsSetupVpnAdditionalGatewaysEntryGateway12 OBJECT-TYPE
    SYNTAX     DisplayString (SIZE(0..64))
    MAX-ACCESS read-write
    STATUS     current
    DESCRIPTION
        "-- empty --"
    ::= { lcsSetupVpnAdditionalGatewaysEntry 22 }

-- {COLUMN} 1712.2.19.12.1.30
lcsSetupVpnAdditionalGatewaysEntryRtgTag12 OBJECT-TYPE
    SYNTAX     INTEGER (0..65535)
    MAX-ACCESS read-write
    STATUS     current
    DESCRIPTION
        "-- empty --"
    ::= { lcsSetupVpnAdditionalGatewaysEntry 30 }

-- {COLUMN} 1712.2.19.12.1.23
lcsSetupVpnAdditionalGatewaysEntryGateway13 OBJECT-TYPE
    SYNTAX     DisplayString (SIZE(0..64))
    MAX-ACCESS read-write
    STATUS     current
    DESCRIPTION
        "-- empty --"
    ::= { lcsSetupVpnAdditionalGatewaysEntry 23 }

-- {COLUMN} 1712.2.19.12.1.31
lcsSetupVpnAdditionalGatewaysEntryRtgTag13 OBJECT-TYPE
    SYNTAX     INTEGER (0..65535)
    MAX-ACCESS read-write
    STATUS     current
    DESCRIPTION
        "-- empty --"
    ::= { lcsSetupVpnAdditionalGatewaysEntry 31 }

-- {COLUMN} 1712.2.19.12.1.24
lcsSetupVpnAdditionalGatewaysEntryGateway14 OBJECT-TYPE
    SYNTAX     DisplayString (SIZE(0..64))
    MAX-ACCESS read-write
    STATUS     current
    DESCRIPTION
        "-- empty --"
    ::= { lcsSetupVpnAdditionalGatewaysEntry 24 }

-- {COLUMN} 1712.2.19.12.1.32
lcsSetupVpnAdditionalGatewaysEntryRtgTag14 OBJECT-TYPE
    SYNTAX     INTEGER (0..65535)
    MAX-ACCESS read-write
    STATUS     current
    DESCRIPTION
        "-- empty --"
    ::= { lcsSetupVpnAdditionalGatewaysEntry 32 }

-- {COLUMN} 1712.2.19.12.1.25
lcsSetupVpnAdditionalGatewaysEntryGateway15 OBJECT-TYPE
    SYNTAX     DisplayString (SIZE(0..64))
    MAX-ACCESS read-write
    STATUS     current
    DESCRIPTION
        "-- empty --"
    ::= { lcsSetupVpnAdditionalGatewaysEntry 25 }

-- {COLUMN} 1712.2.19.12.1.33
lcsSetupVpnAdditionalGatewaysEntryRtgTag15 OBJECT-TYPE
    SYNTAX     INTEGER (0..65535)
    MAX-ACCESS read-write
    STATUS     current
    DESCRIPTION
        "-- empty --"
    ::= { lcsSetupVpnAdditionalGatewaysEntry 33 }

-- {COLUMN} 1712.2.19.12.1.26
lcsSetupVpnAdditionalGatewaysEntryGateway16 OBJECT-TYPE
    SYNTAX     DisplayString (SIZE(0..64))
    MAX-ACCESS read-write
    STATUS     current
    DESCRIPTION
        "-- empty --"
    ::= { lcsSetupVpnAdditionalGatewaysEntry 26 }

-- {COLUMN} 1712.2.19.12.1.34
lcsSetupVpnAdditionalGatewaysEntryRtgTag16 OBJECT-TYPE
    SYNTAX     INTEGER (0..65535)
    MAX-ACCESS read-write
    STATUS     current
    DESCRIPTION
        "-- empty --"
    ::= { lcsSetupVpnAdditionalGatewaysEntry 34 }

-- {COLUMN} 1712.2.19.12.1.35
lcsSetupVpnAdditionalGatewaysEntryGateway17 OBJECT-TYPE
    SYNTAX     DisplayString (SIZE(0..64))
    MAX-ACCESS read-write
    STATUS     current
    DESCRIPTION
        "-- empty --"
    ::= { lcsSetupVpnAdditionalGatewaysEntry 35 }

-- {COLUMN} 1712.2.19.12.1.36
lcsSetupVpnAdditionalGatewaysEntryRtgTag17 OBJECT-TYPE
    SYNTAX     INTEGER (0..65535)
    MAX-ACCESS read-write
    STATUS     current
    DESCRIPTION
        "-- empty --"
    ::= { lcsSetupVpnAdditionalGatewaysEntry 36 }

-- {COLUMN} 1712.2.19.12.1.37
lcsSetupVpnAdditionalGatewaysEntryGateway18 OBJECT-TYPE
    SYNTAX     DisplayString (SIZE(0..64))
    MAX-ACCESS read-write
    STATUS     current
    DESCRIPTION
        "-- empty --"
    ::= { lcsSetupVpnAdditionalGatewaysEntry 37 }

-- {COLUMN} 1712.2.19.12.1.38
lcsSetupVpnAdditionalGatewaysEntryRtgTag18 OBJECT-TYPE
    SYNTAX     INTEGER (0..65535)
    MAX-ACCESS read-write
    STATUS     current
    DESCRIPTION
        "-- empty --"
    ::= { lcsSetupVpnAdditionalGatewaysEntry 38 }

-- {COLUMN} 1712.2.19.12.1.39
lcsSetupVpnAdditionalGatewaysEntryGateway19 OBJECT-TYPE
    SYNTAX     DisplayString (SIZE(0..64))
    MAX-ACCESS read-write
    STATUS     current
    DESCRIPTION
        "-- empty --"
    ::= { lcsSetupVpnAdditionalGatewaysEntry 39 }

-- {COLUMN} 1712.2.19.12.1.40
lcsSetupVpnAdditionalGatewaysEntryRtgTag19 OBJECT-TYPE
    SYNTAX     INTEGER (0..65535)
    MAX-ACCESS read-write
    STATUS     current
    DESCRIPTION
        "-- empty --"
    ::= { lcsSetupVpnAdditionalGatewaysEntry 40 }

-- {COLUMN} 1712.2.19.12.1.41
lcsSetupVpnAdditionalGatewaysEntryGateway20 OBJECT-TYPE
    SYNTAX     DisplayString (SIZE(0..64))
    MAX-ACCESS read-write
    STATUS     current
    DESCRIPTION
        "-- empty --"
    ::= { lcsSetupVpnAdditionalGatewaysEntry 41 }

-- {COLUMN} 1712.2.19.12.1.42
lcsSetupVpnAdditionalGatewaysEntryRtgTag20 OBJECT-TYPE
    SYNTAX     INTEGER (0..65535)
    MAX-ACCESS read-write
    STATUS     current
    DESCRIPTION
        "-- empty --"
    ::= { lcsSetupVpnAdditionalGatewaysEntry 42 }

-- {COLUMN} 1712.2.19.12.1.43
lcsSetupVpnAdditionalGatewaysEntryGateway21 OBJECT-TYPE
    SYNTAX     DisplayString (SIZE(0..64))
    MAX-ACCESS read-write
    STATUS     current
    DESCRIPTION
        "-- empty --"
    ::= { lcsSetupVpnAdditionalGatewaysEntry 43 }

-- {COLUMN} 1712.2.19.12.1.44
lcsSetupVpnAdditionalGatewaysEntryRtgTag21 OBJECT-TYPE
    SYNTAX     INTEGER (0..65535)
    MAX-ACCESS read-write
    STATUS     current
    DESCRIPTION
        "-- empty --"
    ::= { lcsSetupVpnAdditionalGatewaysEntry 44 }

-- {COLUMN} 1712.2.19.12.1.45
lcsSetupVpnAdditionalGatewaysEntryGateway22 OBJECT-TYPE
    SYNTAX     DisplayString (SIZE(0..64))
    MAX-ACCESS read-write
    STATUS     current
    DESCRIPTION
        "-- empty --"
    ::= { lcsSetupVpnAdditionalGatewaysEntry 45 }

-- {COLUMN} 1712.2.19.12.1.46
lcsSetupVpnAdditionalGatewaysEntryRtgTag22 OBJECT-TYPE
    SYNTAX     INTEGER (0..65535)
    MAX-ACCESS read-write
    STATUS     current
    DESCRIPTION
        "-- empty --"
    ::= { lcsSetupVpnAdditionalGatewaysEntry 46 }

-- {COLUMN} 1712.2.19.12.1.47
lcsSetupVpnAdditionalGatewaysEntryGateway23 OBJECT-TYPE
    SYNTAX     DisplayString (SIZE(0..64))
    MAX-ACCESS read-write
    STATUS     current
    DESCRIPTION
        "-- empty --"
    ::= { lcsSetupVpnAdditionalGatewaysEntry 47 }

-- {COLUMN} 1712.2.19.12.1.48
lcsSetupVpnAdditionalGatewaysEntryRtgTag23 OBJECT-TYPE
    SYNTAX     INTEGER (0..65535)
    MAX-ACCESS read-write
    STATUS     current
    DESCRIPTION
        "-- empty --"
    ::= { lcsSetupVpnAdditionalGatewaysEntry 48 }

-- {COLUMN} 1712.2.19.12.1.49
lcsSetupVpnAdditionalGatewaysEntryGateway24 OBJECT-TYPE
    SYNTAX     DisplayString (SIZE(0..64))
    MAX-ACCESS read-write
    STATUS     current
    DESCRIPTION
        "-- empty --"
    ::= { lcsSetupVpnAdditionalGatewaysEntry 49 }

-- {COLUMN} 1712.2.19.12.1.50
lcsSetupVpnAdditionalGatewaysEntryRtgTag24 OBJECT-TYPE
    SYNTAX     INTEGER (0..65535)
    MAX-ACCESS read-write
    STATUS     current
    DESCRIPTION
        "-- empty --"
    ::= { lcsSetupVpnAdditionalGatewaysEntry 50 }

-- {COLUMN} 1712.2.19.12.1.51
lcsSetupVpnAdditionalGatewaysEntryGateway25 OBJECT-TYPE
    SYNTAX     DisplayString (SIZE(0..64))
    MAX-ACCESS read-write
    STATUS     current
    DESCRIPTION
        "-- empty --"
    ::= { lcsSetupVpnAdditionalGatewaysEntry 51 }

-- {COLUMN} 1712.2.19.12.1.52
lcsSetupVpnAdditionalGatewaysEntryRtgTag25 OBJECT-TYPE
    SYNTAX     INTEGER (0..65535)
    MAX-ACCESS read-write
    STATUS     current
    DESCRIPTION
        "-- empty --"
    ::= { lcsSetupVpnAdditionalGatewaysEntry 52 }

-- {COLUMN} 1712.2.19.12.1.53
lcsSetupVpnAdditionalGatewaysEntryGateway26 OBJECT-TYPE
    SYNTAX     DisplayString (SIZE(0..64))
    MAX-ACCESS read-write
    STATUS     current
    DESCRIPTION
        "-- empty --"
    ::= { lcsSetupVpnAdditionalGatewaysEntry 53 }

-- {COLUMN} 1712.2.19.12.1.54
lcsSetupVpnAdditionalGatewaysEntryRtgTag26 OBJECT-TYPE
    SYNTAX     INTEGER (0..65535)
    MAX-ACCESS read-write
    STATUS     current
    DESCRIPTION
        "-- empty --"
    ::= { lcsSetupVpnAdditionalGatewaysEntry 54 }

-- {COLUMN} 1712.2.19.12.1.55
lcsSetupVpnAdditionalGatewaysEntryGateway27 OBJECT-TYPE
    SYNTAX     DisplayString (SIZE(0..64))
    MAX-ACCESS read-write
    STATUS     current
    DESCRIPTION
        "-- empty --"
    ::= { lcsSetupVpnAdditionalGatewaysEntry 55 }

-- {COLUMN} 1712.2.19.12.1.56
lcsSetupVpnAdditionalGatewaysEntryRtgTag27 OBJECT-TYPE
    SYNTAX     INTEGER (0..65535)
    MAX-ACCESS read-write
    STATUS     current
    DESCRIPTION
        "-- empty --"
    ::= { lcsSetupVpnAdditionalGatewaysEntry 56 }

-- {COLUMN} 1712.2.19.12.1.57
lcsSetupVpnAdditionalGatewaysEntryGateway28 OBJECT-TYPE
    SYNTAX     DisplayString (SIZE(0..64))
    MAX-ACCESS read-write
    STATUS     current
    DESCRIPTION
        "-- empty --"
    ::= { lcsSetupVpnAdditionalGatewaysEntry 57 }

-- {COLUMN} 1712.2.19.12.1.58
lcsSetupVpnAdditionalGatewaysEntryRtgTag28 OBJECT-TYPE
    SYNTAX     INTEGER (0..65535)
    MAX-ACCESS read-write
    STATUS     current
    DESCRIPTION
        "-- empty --"
    ::= { lcsSetupVpnAdditionalGatewaysEntry 58 }

-- {COLUMN} 1712.2.19.12.1.59
lcsSetupVpnAdditionalGatewaysEntryGateway29 OBJECT-TYPE
    SYNTAX     DisplayString (SIZE(0..64))
    MAX-ACCESS read-write
    STATUS     current
    DESCRIPTION
        "-- empty --"
    ::= { lcsSetupVpnAdditionalGatewaysEntry 59 }

-- {COLUMN} 1712.2.19.12.1.60
lcsSetupVpnAdditionalGatewaysEntryRtgTag29 OBJECT-TYPE
    SYNTAX     INTEGER (0..65535)
    MAX-ACCESS read-write
    STATUS     current
    DESCRIPTION
        "-- empty --"
    ::= { lcsSetupVpnAdditionalGatewaysEntry 60 }

-- {COLUMN} 1712.2.19.12.1.61
lcsSetupVpnAdditionalGatewaysEntryGateway30 OBJECT-TYPE
    SYNTAX     DisplayString (SIZE(0..64))
    MAX-ACCESS read-write
    STATUS     current
    DESCRIPTION
        "-- empty --"
    ::= { lcsSetupVpnAdditionalGatewaysEntry 61 }

-- {COLUMN} 1712.2.19.12.1.62
lcsSetupVpnAdditionalGatewaysEntryRtgTag30 OBJECT-TYPE
    SYNTAX     INTEGER (0..65535)
    MAX-ACCESS read-write
    STATUS     current
    DESCRIPTION
        "-- empty --"
    ::= { lcsSetupVpnAdditionalGatewaysEntry 62 }

-- {COLUMN} 1712.2.19.12.1.63
lcsSetupVpnAdditionalGatewaysEntryGateway31 OBJECT-TYPE
    SYNTAX     DisplayString (SIZE(0..64))
    MAX-ACCESS read-write
    STATUS     current
    DESCRIPTION
        "-- empty --"
    ::= { lcsSetupVpnAdditionalGatewaysEntry 63 }

-- {COLUMN} 1712.2.19.12.1.64
lcsSetupVpnAdditionalGatewaysEntryRtgTag31 OBJECT-TYPE
    SYNTAX     INTEGER (0..65535)
    MAX-ACCESS read-write
    STATUS     current
    DESCRIPTION
        "-- empty --"
    ::= { lcsSetupVpnAdditionalGatewaysEntry 64 }

-- {COLUMN} 1712.2.19.12.1.65
lcsSetupVpnAdditionalGatewaysEntryGateway32 OBJECT-TYPE
    SYNTAX     DisplayString (SIZE(0..64))
    MAX-ACCESS read-write
    STATUS     current
    DESCRIPTION
        "-- empty --"
    ::= { lcsSetupVpnAdditionalGatewaysEntry 65 }

-- {COLUMN} 1712.2.19.12.1.66
lcsSetupVpnAdditionalGatewaysEntryRtgTag32 OBJECT-TYPE
    SYNTAX     INTEGER (0..65535)
    MAX-ACCESS read-write
    STATUS     current
    DESCRIPTION
        "-- empty --"
    ::= { lcsSetupVpnAdditionalGatewaysEntry 66 }

-- {COLUMN} 1712.2.19.12.1.10
lcsSetupVpnAdditionalGatewaysEntryBeginWith OBJECT-TYPE
    SYNTAX     INTEGER
      {
        eLastUsed (0),
        eFirst (1),
        eRandom (2)
      }
    MAX-ACCESS read-write
    STATUS     current
    DESCRIPTION
        "-- empty --"
    ::= { lcsSetupVpnAdditionalGatewaysEntry 10 }

-- {TABLE} 1712.2.19.7
lcsSetupVpnLayerTable OBJECT-TYPE
    SYNTAX     SEQUENCE OF LcsSetupVpnLayerEntry
    MAX-ACCESS not-accessible
    STATUS     current
    DESCRIPTION
        "-- empty --"
    ::= { lcsSetupVpn 7 }

-- {ENTRY} 1712.2.19.7.1
lcsSetupVpnLayerEntry OBJECT-TYPE
    SYNTAX     LcsSetupVpnLayerEntry
    MAX-ACCESS not-accessible
    STATUS     current
    DESCRIPTION
        ""
    INDEX {
        lcsSetupVpnLayerEntryName
    }
    ::= { lcsSetupVpnLayerTable 1 }

-- {SEQUENCE}
LcsSetupVpnLayerEntry ::= SEQUENCE {
    lcsSetupVpnLayerEntryName DisplayString,
    lcsSetupVpnLayerEntryPfsGrp INTEGER,
    lcsSetupVpnLayerEntryIkeGrp INTEGER,
    lcsSetupVpnLayerEntryIkePropList DisplayString,
    lcsSetupVpnLayerEntryIpsecPropList DisplayString,
    lcsSetupVpnLayerEntryIkeKey DisplayString
}

-- {COLUMN} 1712.2.19.7.1.1
lcsSetupVpnLayerEntryName OBJECT-TYPE
    SYNTAX     DisplayString (SIZE(0..16))
    MAX-ACCESS read-write
    STATUS     current
    DESCRIPTION
        "-- empty --"
    ::= { lcsSetupVpnLayerEntry 1 }

-- {COLUMN} 1712.2.19.7.1.3
lcsSetupVpnLayerEntryPfsGrp OBJECT-TYPE
    SYNTAX     INTEGER
      {
        e1 (1),
        e2 (2),
        e5 (5),
        e14 (14),
        e0 (0)
      }
    MAX-ACCESS read-write
    STATUS     current
    DESCRIPTION
        "-- empty --"
    ::= { lcsSetupVpnLayerEntry 3 }

-- {COLUMN} 1712.2.19.7.1.4
lcsSetupVpnLayerEntryIkeGrp OBJECT-TYPE
    SYNTAX     INTEGER
      {
        e1 (1),
        e2 (2),
        e5 (5),
        e14 (14)
      }
    MAX-ACCESS read-write
    STATUS     current
    DESCRIPTION
        "-- empty --"
    ::= { lcsSetupVpnLayerEntry 4 }

-- {COLUMN} 1712.2.19.7.1.5
lcsSetupVpnLayerEntryIkePropList OBJECT-TYPE
    SYNTAX     DisplayString (SIZE(0..17))
    MAX-ACCESS read-write
    STATUS     current
    DESCRIPTION
        "-- empty --"
    ::= { lcsSetupVpnLayerEntry 5 }

-- {COLUMN} 1712.2.19.7.1.6
lcsSetupVpnLayerEntryIpsecPropList OBJECT-TYPE
    SYNTAX     DisplayString (SIZE(0..17))
    MAX-ACCESS read-write
    STATUS     current
    DESCRIPTION
        "-- empty --"
    ::= { lcsSetupVpnLayerEntry 6 }

-- {COLUMN} 1712.2.19.7.1.7
lcsSetupVpnLayerEntryIkeKey OBJECT-TYPE
    SYNTAX     DisplayString (SIZE(0..16))
    MAX-ACCESS read-write
    STATUS     current
    DESCRIPTION
        "-- empty --"
    ::= { lcsSetupVpnLayerEntry 7 }

-- {OID} 1712.2.19.4
lcsSetupVpnProposals OBJECT IDENTIFIER ::= { lcsSetupVpn 4 }

-- {TABLE} 1712.2.19.4.11
lcsSetupVpnProposalsIkeTable OBJECT-TYPE
    SYNTAX     SEQUENCE OF LcsSetupVpnProposalsIkeEntry
    MAX-ACCESS not-accessible
    STATUS     current
    DESCRIPTION
        "-- empty --"
    ::= { lcsSetupVpnProposals 11 }

-- {ENTRY} 1712.2.19.4.11.1
lcsSetupVpnProposalsIkeEntry OBJECT-TYPE
    SYNTAX     LcsSetupVpnProposalsIkeEntry
    MAX-ACCESS not-accessible
    STATUS     current
    DESCRIPTION
        ""
    INDEX {
        lcsSetupVpnProposalsIkeEntryName
    }
    ::= { lcsSetupVpnProposalsIkeTable 1 }

-- {SEQUENCE}
LcsSetupVpnProposalsIkeEntry ::= SEQUENCE {
    lcsSetupVpnProposalsIkeEntryName DisplayString,
    lcsSetupVpnProposalsIkeEntryIkeCryptAlg INTEGER,
    lcsSetupVpnProposalsIkeEntryIkeCryptKeylen INTEGER,
    lcsSetupVpnProposalsIkeEntryIkeAuthAlg INTEGER,
    lcsSetupVpnProposalsIkeEntryIkeAuthMode INTEGER,
    lcsSetupVpnProposalsIkeEntryLifetimeSec INTEGER,
    lcsSetupVpnProposalsIkeEntryLifetimeKb INTEGER
}

-- {COLUMN} 1712.2.19.4.11.1.1
lcsSetupVpnProposalsIkeEntryName OBJECT-TYPE
    SYNTAX     DisplayString (SIZE(0..17))
    MAX-ACCESS read-write
    STATUS     current
    DESCRIPTION
        "-- empty --"
    ::= { lcsSetupVpnProposalsIkeEntry 1 }

-- {COLUMN} 1712.2.19.4.11.1.2
lcsSetupVpnProposalsIkeEntryIkeCryptAlg OBJECT-TYPE
    SYNTAX     INTEGER
      {
        eAesCbc (7),
        eBlowfishCbc (3),
        eCast128Cbc (6),
        e3desCbc (5),
        eDesCbc (1),
        eNull (42)
      }
    MAX-ACCESS read-write
    STATUS     current
    DESCRIPTION
        "-- empty --"
    ::= { lcsSetupVpnProposalsIkeEntry 2 }

-- {COLUMN} 1712.2.19.4.11.1.3
lcsSetupVpnProposalsIkeEntryIkeCryptKeylen OBJECT-TYPE
    SYNTAX     INTEGER (0..65535)
    MAX-ACCESS read-write
    STATUS     current
    DESCRIPTION
        "-- empty --"
    ::= { lcsSetupVpnProposalsIkeEntry 3 }

-- {COLUMN} 1712.2.19.4.11.1.4
lcsSetupVpnProposalsIkeEntryIkeAuthAlg OBJECT-TYPE
    SYNTAX     INTEGER
      {
        eMd5 (1),
        eSha1 (2)
      }
    MAX-ACCESS read-write
    STATUS     current
    DESCRIPTION
        "-- empty --"
    ::= { lcsSetupVpnProposalsIkeEntry 4 }

-- {COLUMN} 1712.2.19.4.11.1.5
lcsSetupVpnProposalsIkeEntryIkeAuthMode OBJECT-TYPE
    SYNTAX     INTEGER
      {
        ePresharedKey (1),
        eRsaSignature (3)
      }
    MAX-ACCESS read-write
    STATUS     current
    DESCRIPTION
        "-- empty --"
    ::= { lcsSetupVpnProposalsIkeEntry 5 }

-- {COLUMN} 1712.2.19.4.11.1.6
lcsSetupVpnProposalsIkeEntryLifetimeSec OBJECT-TYPE
    SYNTAX     INTEGER (0..2147483647)
    MAX-ACCESS read-write
    STATUS     current
    DESCRIPTION
        "-- empty --"
    ::= { lcsSetupVpnProposalsIkeEntry 6 }

-- {COLUMN} 1712.2.19.4.11.1.7
lcsSetupVpnProposalsIkeEntryLifetimeKb OBJECT-TYPE
    SYNTAX     INTEGER (0..2147483647)
    MAX-ACCESS read-write
    STATUS     current
    DESCRIPTION
        "-- empty --"
    ::= { lcsSetupVpnProposalsIkeEntry 7 }

-- {TABLE} 1712.2.19.4.12
lcsSetupVpnProposalsIpsecTable OBJECT-TYPE
    SYNTAX     SEQUENCE OF LcsSetupVpnProposalsIpsecEntry
    MAX-ACCESS not-accessible
    STATUS     current
    DESCRIPTION
        "-- empty --"
    ::= { lcsSetupVpnProposals 12 }

-- {ENTRY} 1712.2.19.4.12.1
lcsSetupVpnProposalsIpsecEntry OBJECT-TYPE
    SYNTAX     LcsSetupVpnProposalsIpsecEntry
    MAX-ACCESS not-accessible
    STATUS     current
    DESCRIPTION
        ""
    INDEX {
        lcsSetupVpnProposalsIpsecEntryName
    }
    ::= { lcsSetupVpnProposalsIpsecTable 1 }

-- {SEQUENCE}
LcsSetupVpnProposalsIpsecEntry ::= SEQUENCE {
    lcsSetupVpnProposalsIpsecEntryName DisplayString,
    lcsSetupVpnProposalsIpsecEntryEncapsMode INTEGER,
    lcsSetupVpnProposalsIpsecEntryEspCryptAlg INTEGER,
    lcsSetupVpnProposalsIpsecEntryEspCryptKeylen INTEGER,
    lcsSetupVpnProposalsIpsecEntryEspAuthAlg INTEGER,
    lcsSetupVpnProposalsIpsecEntryAhAuthAlg INTEGER,
    lcsSetupVpnProposalsIpsecEntryIpcompAlg INTEGER,
    lcsSetupVpnProposalsIpsecEntryLifetimeSec INTEGER,
    lcsSetupVpnProposalsIpsecEntryLifetimeKb INTEGER
}

-- {COLUMN} 1712.2.19.4.12.1.1
lcsSetupVpnProposalsIpsecEntryName OBJECT-TYPE
    SYNTAX     DisplayString (SIZE(0..17))
    MAX-ACCESS read-write
    STATUS     current
    DESCRIPTION
        "-- empty --"
    ::= { lcsSetupVpnProposalsIpsecEntry 1 }

-- {COLUMN} 1712.2.19.4.12.1.2
lcsSetupVpnProposalsIpsecEntryEncapsMode OBJECT-TYPE
    SYNTAX     INTEGER
      {
        eTunnel (1),
        eTransport (2),
        eMixedLcos4 (65001)
      }
    MAX-ACCESS read-write
    STATUS     current
    DESCRIPTION
        "-- empty --"
    ::= { lcsSetupVpnProposalsIpsecEntry 2 }

-- {COLUMN} 1712.2.19.4.12.1.3
lcsSetupVpnProposalsIpsecEntryEspCryptAlg OBJECT-TYPE
    SYNTAX     INTEGER
      {
        eNone (0),
        eAesCbc (12),
        eBlowfishCbc (7),
        eCast128Cbc (6),
        e3desCbc (3),
        eDesCbc (2),
        eNull (11)
      }
    MAX-ACCESS read-write
    STATUS     current
    DESCRIPTION
        "-- empty --"
    ::= { lcsSetupVpnProposalsIpsecEntry 3 }

-- {COLUMN} 1712.2.19.4.12.1.4
lcsSetupVpnProposalsIpsecEntryEspCryptKeylen OBJECT-TYPE
    SYNTAX     INTEGER (0..65535)
    MAX-ACCESS read-write
    STATUS     current
    DESCRIPTION
        "-- empty --"
    ::= { lcsSetupVpnProposalsIpsecEntry 4 }

-- {COLUMN} 1712.2.19.4.12.1.5
lcsSetupVpnProposalsIpsecEntryEspAuthAlg OBJECT-TYPE
    SYNTAX     INTEGER
      {
        eNone (0),
        eHmacMd5 (1),
        eHmacSha1 (2)
      }
    MAX-ACCESS read-write
    STATUS     current
    DESCRIPTION
        "-- empty --"
    ::= { lcsSetupVpnProposalsIpsecEntry 5 }

-- {COLUMN} 1712.2.19.4.12.1.6
lcsSetupVpnProposalsIpsecEntryAhAuthAlg OBJECT-TYPE
    SYNTAX     INTEGER
      {
        eNone (0),
        eHmacMd5 (1),
        eHmacSha1 (2)
      }
    MAX-ACCESS read-write
    STATUS     current
    DESCRIPTION
        "-- empty --"
    ::= { lcsSetupVpnProposalsIpsecEntry 6 }

-- {COLUMN} 1712.2.19.4.12.1.7
lcsSetupVpnProposalsIpsecEntryIpcompAlg OBJECT-TYPE
    SYNTAX     INTEGER
      {
        eNone (0),
        eDeflate (2),
        eLzs (3)
      }
    MAX-ACCESS read-write
    STATUS     current
    DESCRIPTION
        "-- empty --"
    ::= { lcsSetupVpnProposalsIpsecEntry 7 }

-- {COLUMN} 1712.2.19.4.12.1.8
lcsSetupVpnProposalsIpsecEntryLifetimeSec OBJECT-TYPE
    SYNTAX     INTEGER (0..2147483647)
    MAX-ACCESS read-write
    STATUS     current
    DESCRIPTION
        "-- empty --"
    ::= { lcsSetupVpnProposalsIpsecEntry 8 }

-- {COLUMN} 1712.2.19.4.12.1.9
lcsSetupVpnProposalsIpsecEntryLifetimeKb OBJECT-TYPE
    SYNTAX     INTEGER (0..2147483647)
    MAX-ACCESS read-write
    STATUS     current
    DESCRIPTION
        "-- empty --"
    ::= { lcsSetupVpnProposalsIpsecEntry 9 }

-- {TABLE} 1712.2.19.4.9
lcsSetupVpnProposalsIkeProposalListsTable OBJECT-TYPE
    SYNTAX     SEQUENCE OF LcsSetupVpnProposalsIkeProposalListsEntry
    MAX-ACCESS not-accessible
    STATUS     current
    DESCRIPTION
        "-- empty --"
    ::= { lcsSetupVpnProposals 9 }

-- {ENTRY} 1712.2.19.4.9.1
lcsSetupVpnProposalsIkeProposalListsEntry OBJECT-TYPE
    SYNTAX     LcsSetupVpnProposalsIkeProposalListsEntry
    MAX-ACCESS not-accessible
    STATUS     current
    DESCRIPTION
        ""
    INDEX {
        lcsSetupVpnProposalsIkeProposalListsEntryIkeProposalLists
    }
    ::= { lcsSetupVpnProposalsIkeProposalListsTable 1 }

-- {SEQUENCE}
LcsSetupVpnProposalsIkeProposalListsEntry ::= SEQUENCE {
    lcsSetupVpnProposalsIkeProposalListsEntryIkeProposalLists DisplayString,
    lcsSetupVpnProposalsIkeProposalListsEntryIkeProposal1 DisplayString,
    lcsSetupVpnProposalsIkeProposalListsEntryIkeProposal2 DisplayString,
    lcsSetupVpnProposalsIkeProposalListsEntryIkeProposal3 DisplayString,
    lcsSetupVpnProposalsIkeProposalListsEntryIkeProposal4 DisplayString,
    lcsSetupVpnProposalsIkeProposalListsEntryIkeProposal5 DisplayString,
    lcsSetupVpnProposalsIkeProposalListsEntryIkeProposal6 DisplayString,
    lcsSetupVpnProposalsIkeProposalListsEntryIkeProposal7 DisplayString,
    lcsSetupVpnProposalsIkeProposalListsEntryIkeProposal8 DisplayString
}

-- {COLUMN} 1712.2.19.4.9.1.1
lcsSetupVpnProposalsIkeProposalListsEntryIkeProposalLists OBJECT-TYPE
    SYNTAX     DisplayString (SIZE(0..17))
    MAX-ACCESS read-write
    STATUS     current
    DESCRIPTION
        "-- empty --"
    ::= { lcsSetupVpnProposalsIkeProposalListsEntry 1 }

-- {COLUMN} 1712.2.19.4.9.1.2
lcsSetupVpnProposalsIkeProposalListsEntryIkeProposal1 OBJECT-TYPE
    SYNTAX     DisplayString (SIZE(0..17))
    MAX-ACCESS read-write
    STATUS     current
    DESCRIPTION
        "-- empty --"
    ::= { lcsSetupVpnProposalsIkeProposalListsEntry 2 }

-- {COLUMN} 1712.2.19.4.9.1.3
lcsSetupVpnProposalsIkeProposalListsEntryIkeProposal2 OBJECT-TYPE
    SYNTAX     DisplayString (SIZE(0..17))
    MAX-ACCESS read-write
    STATUS     current
    DESCRIPTION
        "-- empty --"
    ::= { lcsSetupVpnProposalsIkeProposalListsEntry 3 }

-- {COLUMN} 1712.2.19.4.9.1.4
lcsSetupVpnProposalsIkeProposalListsEntryIkeProposal3 OBJECT-TYPE
    SYNTAX     DisplayString (SIZE(0..17))
    MAX-ACCESS read-write
    STATUS     current
    DESCRIPTION
        "-- empty --"
    ::= { lcsSetupVpnProposalsIkeProposalListsEntry 4 }

-- {COLUMN} 1712.2.19.4.9.1.5
lcsSetupVpnProposalsIkeProposalListsEntryIkeProposal4 OBJECT-TYPE
    SYNTAX     DisplayString (SIZE(0..17))
    MAX-ACCESS read-write
    STATUS     current
    DESCRIPTION
        "-- empty --"
    ::= { lcsSetupVpnProposalsIkeProposalListsEntry 5 }

-- {COLUMN} 1712.2.19.4.9.1.6
lcsSetupVpnProposalsIkeProposalListsEntryIkeProposal5 OBJECT-TYPE
    SYNTAX     DisplayString (SIZE(0..17))
    MAX-ACCESS read-write
    STATUS     current
    DESCRIPTION
        "-- empty --"
    ::= { lcsSetupVpnProposalsIkeProposalListsEntry 6 }

-- {COLUMN} 1712.2.19.4.9.1.7
lcsSetupVpnProposalsIkeProposalListsEntryIkeProposal6 OBJECT-TYPE
    SYNTAX     DisplayString (SIZE(0..17))
    MAX-ACCESS read-write
    STATUS     current
    DESCRIPTION
        "-- empty --"
    ::= { lcsSetupVpnProposalsIkeProposalListsEntry 7 }

-- {COLUMN} 1712.2.19.4.9.1.8
lcsSetupVpnProposalsIkeProposalListsEntryIkeProposal7 OBJECT-TYPE
    SYNTAX     DisplayString (SIZE(0..17))
    MAX-ACCESS read-write
    STATUS     current
    DESCRIPTION
        "-- empty --"
    ::= { lcsSetupVpnProposalsIkeProposalListsEntry 8 }

-- {COLUMN} 1712.2.19.4.9.1.9
lcsSetupVpnProposalsIkeProposalListsEntryIkeProposal8 OBJECT-TYPE
    SYNTAX     DisplayString (SIZE(0..17))
    MAX-ACCESS read-write
    STATUS     current
    DESCRIPTION
        "-- empty --"
    ::= { lcsSetupVpnProposalsIkeProposalListsEntry 9 }

-- {TABLE} 1712.2.19.4.10
lcsSetupVpnProposalsIpsecProposalListsTable OBJECT-TYPE
    SYNTAX     SEQUENCE OF LcsSetupVpnProposalsIpsecProposalListsEntry
    MAX-ACCESS not-accessible
    STATUS     current
    DESCRIPTION
        "-- empty --"
    ::= { lcsSetupVpnProposals 10 }

-- {ENTRY} 1712.2.19.4.10.1
lcsSetupVpnProposalsIpsecProposalListsEntry OBJECT-TYPE
    SYNTAX     LcsSetupVpnProposalsIpsecProposalListsEntry
    MAX-ACCESS not-accessible
    STATUS     current
    DESCRIPTION
        ""
    INDEX {
        lcsSetupVpnProposalsIpsecProposalListsEntryIpsecProposalLists
    }
    ::= { lcsSetupVpnProposalsIpsecProposalListsTable 1 }

-- {SEQUENCE}
LcsSetupVpnProposalsIpsecProposalListsEntry ::= SEQUENCE {
    lcsSetupVpnProposalsIpsecProposalListsEntryIpsecProposalLists DisplayString,
    lcsSetupVpnProposalsIpsecProposalListsEntryIpsecProposal1 DisplayString,
    lcsSetupVpnProposalsIpsecProposalListsEntryIpsecProposal2 DisplayString,
    lcsSetupVpnProposalsIpsecProposalListsEntryIpsecProposal3 DisplayString,
    lcsSetupVpnProposalsIpsecProposalListsEntryIpsecProposal4 DisplayString,
    lcsSetupVpnProposalsIpsecProposalListsEntryIpsecProposal5 DisplayString,
    lcsSetupVpnProposalsIpsecProposalListsEntryIpsecProposal6 DisplayString,
    lcsSetupVpnProposalsIpsecProposalListsEntryIpsecProposal7 DisplayString,
    lcsSetupVpnProposalsIpsecProposalListsEntryIpsecProposal8 DisplayString
}

-- {COLUMN} 1712.2.19.4.10.1.1
lcsSetupVpnProposalsIpsecProposalListsEntryIpsecProposalLists OBJECT-TYPE
    SYNTAX     DisplayString (SIZE(0..17))
    MAX-ACCESS read-write
    STATUS     current
    DESCRIPTION
        "-- empty --"
    ::= { lcsSetupVpnProposalsIpsecProposalListsEntry 1 }

-- {COLUMN} 1712.2.19.4.10.1.2
lcsSetupVpnProposalsIpsecProposalListsEntryIpsecProposal1 OBJECT-TYPE
    SYNTAX     DisplayString (SIZE(0..17))
    MAX-ACCESS read-write
    STATUS     current
    DESCRIPTION
        "-- empty --"
    ::= { lcsSetupVpnProposalsIpsecProposalListsEntry 2 }

-- {COLUMN} 1712.2.19.4.10.1.3
lcsSetupVpnProposalsIpsecProposalListsEntryIpsecProposal2 OBJECT-TYPE
    SYNTAX     DisplayString (SIZE(0..17))
    MAX-ACCESS read-write
    STATUS     current
    DESCRIPTION
        "-- empty --"
    ::= { lcsSetupVpnProposalsIpsecProposalListsEntry 3 }

-- {COLUMN} 1712.2.19.4.10.1.4
lcsSetupVpnProposalsIpsecProposalListsEntryIpsecProposal3 OBJECT-TYPE
    SYNTAX     DisplayString (SIZE(0..17))
    MAX-ACCESS read-write
    STATUS     current
    DESCRIPTION
        "-- empty --"
    ::= { lcsSetupVpnProposalsIpsecProposalListsEntry 4 }

-- {COLUMN} 1712.2.19.4.10.1.5
lcsSetupVpnProposalsIpsecProposalListsEntryIpsecProposal4 OBJECT-TYPE
    SYNTAX     DisplayString (SIZE(0..17))
    MAX-ACCESS read-write
    STATUS     current
    DESCRIPTION
        "-- empty --"
    ::= { lcsSetupVpnProposalsIpsecProposalListsEntry 5 }

-- {COLUMN} 1712.2.19.4.10.1.6
lcsSetupVpnProposalsIpsecProposalListsEntryIpsecProposal5 OBJECT-TYPE
    SYNTAX     DisplayString (SIZE(0..17))
    MAX-ACCESS read-write
    STATUS     current
    DESCRIPTION
        "-- empty --"
    ::= { lcsSetupVpnProposalsIpsecProposalListsEntry 6 }

-- {COLUMN} 1712.2.19.4.10.1.7
lcsSetupVpnProposalsIpsecProposalListsEntryIpsecProposal6 OBJECT-TYPE
    SYNTAX     DisplayString (SIZE(0..17))
    MAX-ACCESS read-write
    STATUS     current
    DESCRIPTION
        "-- empty --"
    ::= { lcsSetupVpnProposalsIpsecProposalListsEntry 7 }

-- {COLUMN} 1712.2.19.4.10.1.8
lcsSetupVpnProposalsIpsecProposalListsEntryIpsecProposal7 OBJECT-TYPE
    SYNTAX     DisplayString (SIZE(0..17))
    MAX-ACCESS read-write
    STATUS     current
    DESCRIPTION
        "-- empty --"
    ::= { lcsSetupVpnProposalsIpsecProposalListsEntry 8 }

-- {COLUMN} 1712.2.19.4.10.1.9
lcsSetupVpnProposalsIpsecProposalListsEntryIpsecProposal8 OBJECT-TYPE
    SYNTAX     DisplayString (SIZE(0..17))
    MAX-ACCESS read-write
    STATUS     current
    DESCRIPTION
        "-- empty --"
    ::= { lcsSetupVpnProposalsIpsecProposalListsEntry 9 }

-- {OID} 1712.2.19.5
lcsSetupVpnCertificatesAndKeys OBJECT IDENTIFIER ::= { lcsSetupVpn 5 }

-- {TABLE} 1712.2.19.5.3
lcsSetupVpnCertificatesAndKeysIkeKeysTable OBJECT-TYPE
    SYNTAX     SEQUENCE OF LcsSetupVpnCertificatesAndKeysIkeKeysEntry
    MAX-ACCESS not-accessible
    STATUS     current
    DESCRIPTION
        "-- empty --"
    ::= { lcsSetupVpnCertificatesAndKeys 3 }

-- {ENTRY} 1712.2.19.5.3.1
lcsSetupVpnCertificatesAndKeysIkeKeysEntry OBJECT-TYPE
    SYNTAX     LcsSetupVpnCertificatesAndKeysIkeKeysEntry
    MAX-ACCESS not-accessible
    STATUS     current
    DESCRIPTION
        ""
    INDEX {
        lcsSetupVpnCertificatesAndKeysIkeKeysEntryName
    }
    ::= { lcsSetupVpnCertificatesAndKeysIkeKeysTable 1 }

-- {SEQUENCE}
LcsSetupVpnCertificatesAndKeysIkeKeysEntry ::= SEQUENCE {
    lcsSetupVpnCertificatesAndKeysIkeKeysEntryName DisplayString,
    lcsSetupVpnCertificatesAndKeysIkeKeysEntryLocalIdType INTEGER,
    lcsSetupVpnCertificatesAndKeysIkeKeysEntryLocalIdentity DisplayString,
    lcsSetupVpnCertificatesAndKeysIkeKeysEntryRemoteIdType INTEGER,
    lcsSetupVpnCertificatesAndKeysIkeKeysEntryRemoteIdentity DisplayString,
    lcsSetupVpnCertificatesAndKeysIkeKeysEntrySharedSec DisplayString,
    lcsSetupVpnCertificatesAndKeysIkeKeysEntrySharedSecFile DisplayString
}

-- {COLUMN} 1712.2.19.5.3.1.1
lcsSetupVpnCertificatesAndKeysIkeKeysEntryName OBJECT-TYPE
    SYNTAX     DisplayString (SIZE(0..16))
    MAX-ACCESS read-write
    STATUS     current
    DESCRIPTION
        "-- empty --"
    ::= { lcsSetupVpnCertificatesAndKeysIkeKeysEntry 1 }

-- {COLUMN} 1712.2.19.5.3.1.6
lcsSetupVpnCertificatesAndKeysIkeKeysEntryLocalIdType OBJECT-TYPE
    SYNTAX     INTEGER
      {
        eNoIdentity (0),
        eIpAddress (1),
        eIpv6Address (5),
        eDomainName (2),
        eEmailAddress (3),
        eDistinguishedName (9),
        eKeyId (11)
      }
    MAX-ACCESS read-write
    STATUS     current
    DESCRIPTION
        "-- empty --"
    ::= { lcsSetupVpnCertificatesAndKeysIkeKeysEntry 6 }

-- {COLUMN} 1712.2.19.5.3.1.7
lcsSetupVpnCertificatesAndKeysIkeKeysEntryLocalIdentity OBJECT-TYPE
    SYNTAX     DisplayString (SIZE(0..254))
    MAX-ACCESS read-write
    STATUS     current
    DESCRIPTION
        "-- empty --"
    ::= { lcsSetupVpnCertificatesAndKeysIkeKeysEntry 7 }

-- {COLUMN} 1712.2.19.5.3.1.5
lcsSetupVpnCertificatesAndKeysIkeKeysEntryRemoteIdType OBJECT-TYPE
    SYNTAX     INTEGER
      {
        eNoIdentity (0),
        eIpAddress (1),
        eIpv6Address (5),
        eDomainName (2),
        eEmailAddress (3),
        eDistinguishedName (9),
        eKeyId (11)
      }
    MAX-ACCESS read-write
    STATUS     current
    DESCRIPTION
        "-- empty --"
    ::= { lcsSetupVpnCertificatesAndKeysIkeKeysEntry 5 }

-- {COLUMN} 1712.2.19.5.3.1.2
lcsSetupVpnCertificatesAndKeysIkeKeysEntryRemoteIdentity OBJECT-TYPE
    SYNTAX     DisplayString (SIZE(0..254))
    MAX-ACCESS read-write
    STATUS     current
    DESCRIPTION
        "-- empty --"
    ::= { lcsSetupVpnCertificatesAndKeysIkeKeysEntry 2 }

-- {COLUMN} 1712.2.19.5.3.1.3
lcsSetupVpnCertificatesAndKeysIkeKeysEntrySharedSec OBJECT-TYPE
    SYNTAX     DisplayString (SIZE(0..64))
    MAX-ACCESS read-write
    STATUS     current
    DESCRIPTION
        "-- empty --"
    ::= { lcsSetupVpnCertificatesAndKeysIkeKeysEntry 3 }

-- {COLUMN} 1712.2.19.5.3.1.4
lcsSetupVpnCertificatesAndKeysIkeKeysEntrySharedSecFile OBJECT-TYPE
    SYNTAX     DisplayString (SIZE(0..20))
    MAX-ACCESS read-write
    STATUS     current
    DESCRIPTION
        "-- empty --"
    ::= { lcsSetupVpnCertificatesAndKeysIkeKeysEntry 4 }

-- {OID} 1712.2.19.3
lcsSetupVpnIsakmp OBJECT IDENTIFIER ::= { lcsSetupVpn 3 }

-- {TABLE} 1712.2.19.3.4
lcsSetupVpnIsakmpTimerTable OBJECT-TYPE
    SYNTAX     SEQUENCE OF LcsSetupVpnIsakmpTimerEntry
    MAX-ACCESS not-accessible
    STATUS     current
    DESCRIPTION
        "-- empty --"
    ::= { lcsSetupVpnIsakmp 4 }

-- {ENTRY} 1712.2.19.3.4.1
lcsSetupVpnIsakmpTimerEntry OBJECT-TYPE
    SYNTAX     LcsSetupVpnIsakmpTimerEntry
    MAX-ACCESS not-accessible
    STATUS     current
    DESCRIPTION
        ""
    INDEX {
        lcsSetupVpnIsakmpTimerEntryIdx
    }
    ::= { lcsSetupVpnIsakmpTimerTable 1 }

-- {SEQUENCE}
LcsSetupVpnIsakmpTimerEntry ::= SEQUENCE {
    lcsSetupVpnIsakmpTimerEntryIdx INTEGER,
    lcsSetupVpnIsakmpTimerEntryRetrLim INTEGER,
    lcsSetupVpnIsakmpTimerEntryRetrTim INTEGER,
    lcsSetupVpnIsakmpTimerEntryRetrTimUsec INTEGER,
    lcsSetupVpnIsakmpTimerEntryRetrTimMax INTEGER,
    lcsSetupVpnIsakmpTimerEntryExpTim INTEGER
}

-- {COLUMN} 1712.2.19.3.4.1.6
lcsSetupVpnIsakmpTimerEntryIdx OBJECT-TYPE
    SYNTAX     INTEGER (0..255)
    MAX-ACCESS read-only
    STATUS     current
    DESCRIPTION
        "-- empty --"
    ::= { lcsSetupVpnIsakmpTimerEntry 6 }

-- {COLUMN} 1712.2.19.3.4.1.1
lcsSetupVpnIsakmpTimerEntryRetrLim OBJECT-TYPE
    SYNTAX     INTEGER (0..65535)
    MAX-ACCESS read-write
    STATUS     current
    DESCRIPTION
        "-- empty --"
    ::= { lcsSetupVpnIsakmpTimerEntry 1 }

-- {COLUMN} 1712.2.19.3.4.1.2
lcsSetupVpnIsakmpTimerEntryRetrTim OBJECT-TYPE
    SYNTAX     INTEGER (0..65535)
    MAX-ACCESS read-write
    STATUS     current
    DESCRIPTION
        "-- empty --"
    ::= { lcsSetupVpnIsakmpTimerEntry 2 }

-- {COLUMN} 1712.2.19.3.4.1.3
lcsSetupVpnIsakmpTimerEntryRetrTimUsec OBJECT-TYPE
    SYNTAX     INTEGER (0..2147483647)
    MAX-ACCESS read-write
    STATUS     current
    DESCRIPTION
        "-- empty --"
    ::= { lcsSetupVpnIsakmpTimerEntry 3 }

-- {COLUMN} 1712.2.19.3.4.1.4
lcsSetupVpnIsakmpTimerEntryRetrTimMax OBJECT-TYPE
    SYNTAX     INTEGER (0..65535)
    MAX-ACCESS read-write
    STATUS     current
    DESCRIPTION
        "-- empty --"
    ::= { lcsSetupVpnIsakmpTimerEntry 4 }

-- {COLUMN} 1712.2.19.3.4.1.5
lcsSetupVpnIsakmpTimerEntryExpTim OBJECT-TYPE
    SYNTAX     INTEGER (0..65535)
    MAX-ACCESS read-write
    STATUS     current
    DESCRIPTION
        "-- empty --"
    ::= { lcsSetupVpnIsakmpTimerEntry 5 }

-- {OID} 1712.2.19.3.29
lcsSetupVpnIsakmpDhGroups OBJECT IDENTIFIER ::= { lcsSetupVpnIsakmp 29 }

-- {SCALAR} 1712.2.19.3.29.1
lcsSetupVpnIsakmpDhGroupsPrecalculation OBJECT-TYPE
    SYNTAX     INTEGER
      {
        eNo (0),
        eYes (1)
      }
    MAX-ACCESS read-write
    STATUS     current
    DESCRIPTION
        "-- empty --"
    ::= { lcsSetupVpnIsakmpDhGroups 1 }

-- {TABLE} 1712.2.19.3.29.2
lcsSetupVpnIsakmpDhGroupsGroupConfigTable OBJECT-TYPE
    SYNTAX     SEQUENCE OF LcsSetupVpnIsakmpDhGroupsGroupConfigEntry
    MAX-ACCESS not-accessible
    STATUS     current
    DESCRIPTION
        "-- empty --"
    ::= { lcsSetupVpnIsakmpDhGroups 2 }

-- {ENTRY} 1712.2.19.3.29.2.1
lcsSetupVpnIsakmpDhGroupsGroupConfigEntry OBJECT-TYPE
    SYNTAX     LcsSetupVpnIsakmpDhGroupsGroupConfigEntry
    MAX-ACCESS not-accessible
    STATUS     current
    DESCRIPTION
        ""
    INDEX {
        lcsSetupVpnIsakmpDhGroupsGroupConfigEntryDhGroup
    }
    ::= { lcsSetupVpnIsakmpDhGroupsGroupConfigTable 1 }

-- {SEQUENCE}
LcsSetupVpnIsakmpDhGroupsGroupConfigEntry ::= SEQUENCE {
    lcsSetupVpnIsakmpDhGroupsGroupConfigEntryDhGroup INTEGER,
    lcsSetupVpnIsakmpDhGroupsGroupConfigEntryPrecalcTarget INTEGER
}

-- {COLUMN} 1712.2.19.3.29.2.1.1
lcsSetupVpnIsakmpDhGroupsGroupConfigEntryDhGroup OBJECT-TYPE
    SYNTAX     INTEGER (0..255)
    MAX-ACCESS read-only
    STATUS     current
    DESCRIPTION
        "-- empty --"
    ::= { lcsSetupVpnIsakmpDhGroupsGroupConfigEntry 1 }

-- {COLUMN} 1712.2.19.3.29.2.1.2
lcsSetupVpnIsakmpDhGroupsGroupConfigEntryPrecalcTarget OBJECT-TYPE
    SYNTAX     INTEGER (0..2147483647)
    MAX-ACCESS read-write
    STATUS     current
    DESCRIPTION
        "-- empty --"
    ::= { lcsSetupVpnIsakmpDhGroupsGroupConfigEntry 2 }

-- {SCALAR} 1712.2.19.13
lcsSetupVpnMainmodeProposalListDefault OBJECT-TYPE
    SYNTAX     DisplayString (SIZE(0..17))
    MAX-ACCESS read-write
    STATUS     current
    DESCRIPTION
        "-- empty --"
    ::= { lcsSetupVpn 13 }

-- {SCALAR} 1712.2.19.14
lcsSetupVpnMainmodeIkeGroupDefault OBJECT-TYPE
    SYNTAX     INTEGER
      {
        e1 (1),
        e2 (2),
        e5 (5),
        e14 (14)
      }
    MAX-ACCESS read-write
    STATUS     current
    DESCRIPTION
        "-- empty --"
    ::= { lcsSetupVpn 14 }

-- {SCALAR} 1712.2.19.10
lcsSetupVpnAggrmodeProposalListDefault OBJECT-TYPE
    SYNTAX     DisplayString (SIZE(0..17))
    MAX-ACCESS read-write
    STATUS     current
    DESCRIPTION
        "-- empty --"
    ::= { lcsSetupVpn 10 }

-- {SCALAR} 1712.2.19.11
lcsSetupVpnAggrmodeIkeGroupDefault OBJECT-TYPE
    SYNTAX     INTEGER
      {
        e1 (1),
        e2 (2),
        e5 (5),
        e14 (14)
      }
    MAX-ACCESS read-write
    STATUS     current
    DESCRIPTION
        "-- empty --"
    ::= { lcsSetupVpn 11 }

-- {SCALAR} 1712.2.19.19
lcsSetupVpnQuickmodeProposalListDefault OBJECT-TYPE
    SYNTAX     DisplayString (SIZE(0..17))
    MAX-ACCESS read-write
    STATUS     current
    DESCRIPTION
        "-- empty --"
    ::= { lcsSetupVpn 19 }

-- {SCALAR} 1712.2.19.20
lcsSetupVpnQuickmodePfsGroupDefault OBJECT-TYPE
    SYNTAX     INTEGER
      {
        e1 (1),
        e2 (2),
        e5 (5),
        e14 (14),
        e0 (0)
      }
    MAX-ACCESS read-write
    STATUS     current
    DESCRIPTION
        "-- empty --"
    ::= { lcsSetupVpn 20 }

-- {SCALAR} 1712.2.19.21
lcsSetupVpnQuickmodeShortholdTimeDefault OBJECT-TYPE
    SYNTAX     INTEGER (0..65535)
    MAX-ACCESS read-write
    STATUS     current
    DESCRIPTION
        "-- empty --"
    ::= { lcsSetupVpn 21 }

-- {SCALAR} 1712.2.19.24
lcsSetupVpnMaxConcurrentConnections OBJECT-TYPE
    SYNTAX     INTEGER (0..2147483647)
    MAX-ACCESS read-write
    STATUS     current
    DESCRIPTION
        "-- empty --"
    ::= { lcsSetupVpn 24 }

-- {SCALAR} 1712.2.19.25
lcsSetupVpnFlexibleIdComparison OBJECT-TYPE
    SYNTAX     INTEGER
      {
        eNo (0),
        eYes (1)
      }
    MAX-ACCESS read-write
    STATUS     current
    DESCRIPTION
        "-- empty --"
    ::= { lcsSetupVpn 25 }

-- {SCALAR} 1712.2.19.26
lcsSetupVpnNatTPortForRekeying OBJECT-TYPE
    SYNTAX     INTEGER
      {
        eNo (0),
        eYes (1)
      }
    MAX-ACCESS read-write
    STATUS     current
    DESCRIPTION
        "-- empty --"
    ::= { lcsSetupVpn 26 }

-- {SCALAR} 1712.2.19.27
lcsSetupVpnSslEncapsAllowed OBJECT-TYPE
    SYNTAX     INTEGER
      {
        eNo (0),
        eYes (1)
      }
    MAX-ACCESS read-write
    STATUS     current
    DESCRIPTION
        "-- empty --"
    ::= { lcsSetupVpn 27 }

-- {OID} 1712.2.19.28
lcsSetupVpnMyvpn OBJECT IDENTIFIER ::= { lcsSetupVpn 28 }

-- {SCALAR} 1712.2.19.28.1
lcsSetupVpnMyvpnOperating OBJECT-TYPE
    SYNTAX     INTEGER
      {
        eNo (0),
        eYes (1)
      }
    MAX-ACCESS read-write
    STATUS     current
    DESCRIPTION
        "-- empty --"
    ::= { lcsSetupVpnMyvpn 1 }

-- {SCALAR} 1712.2.19.28.2
lcsSetupVpnMyvpnPinLength OBJECT-TYPE
    SYNTAX     INTEGER (0..255)
    MAX-ACCESS read-write
    STATUS     current
    DESCRIPTION
        "-- empty --"
    ::= { lcsSetupVpnMyvpn 2 }

-- {SCALAR} 1712.2.19.28.3
lcsSetupVpnMyvpnDeviceHostname OBJECT-TYPE
    SYNTAX     DisplayString (SIZE(0..31))
    MAX-ACCESS read-write
    STATUS     current
    DESCRIPTION
        "-- empty --"
    ::= { lcsSetupVpnMyvpn 3 }

-- {TABLE} 1712.2.19.28.4
lcsSetupVpnMyvpnMappingTable OBJECT-TYPE
    SYNTAX     SEQUENCE OF LcsSetupVpnMyvpnMappingEntry
    MAX-ACCESS not-accessible
    STATUS     current
    DESCRIPTION
        "-- empty --"
    ::= { lcsSetupVpnMyvpn 4 }

-- {ENTRY} 1712.2.19.28.4.1
lcsSetupVpnMyvpnMappingEntry OBJECT-TYPE
    SYNTAX     LcsSetupVpnMyvpnMappingEntry
    MAX-ACCESS not-accessible
    STATUS     current
    DESCRIPTION
        ""
    INDEX {
        lcsSetupVpnMyvpnMappingEntryPin
    }
    ::= { lcsSetupVpnMyvpnMappingTable 1 }

-- {SEQUENCE}
LcsSetupVpnMyvpnMappingEntry ::= SEQUENCE {
    lcsSetupVpnMyvpnMappingEntryPin DisplayString,
    lcsSetupVpnMyvpnMappingEntryVpnProfile DisplayString,
    lcsSetupVpnMyvpnMappingEntryActive INTEGER
}

-- {COLUMN} 1712.2.19.28.4.1.1
lcsSetupVpnMyvpnMappingEntryPin OBJECT-TYPE
    SYNTAX     DisplayString (SIZE(0..12))
    MAX-ACCESS read-write
    STATUS     current
    DESCRIPTION
        "-- empty --"
    ::= { lcsSetupVpnMyvpnMappingEntry 1 }

-- {COLUMN} 1712.2.19.28.4.1.2
lcsSetupVpnMyvpnMappingEntryVpnProfile OBJECT-TYPE
    SYNTAX     DisplayString (SIZE(0..16))
    MAX-ACCESS read-write
    STATUS     current
    DESCRIPTION
        "-- empty --"
    ::= { lcsSetupVpnMyvpnMappingEntry 2 }

-- {COLUMN} 1712.2.19.28.4.1.3
lcsSetupVpnMyvpnMappingEntryActive OBJECT-TYPE
    SYNTAX     INTEGER
      {
        eNo (0),
        eYes (1)
      }
    MAX-ACCESS read-write
    STATUS     current
    DESCRIPTION
        "-- empty --"
    ::= { lcsSetupVpnMyvpnMappingEntry 3 }

-- {SCALAR} 1712.2.19.28.5
lcsSetupVpnMyvpnReEnableLogin OBJECT-TYPE
    SYNTAX     DisplayString
    MAX-ACCESS read-write
    STATUS     current
    DESCRIPTION
        "-- empty --"
    ::= { lcsSetupVpnMyvpn 5 }

-- {SCALAR} 1712.2.19.28.6
lcsSetupVpnMyvpnEMailNotification OBJECT-TYPE
    SYNTAX     INTEGER
      {
        eNo (0),
        eYes (1)
      }
    MAX-ACCESS read-write
    STATUS     current
    DESCRIPTION
        "-- empty --"
    ::= { lcsSetupVpnMyvpn 6 }

-- {SCALAR} 1712.2.19.28.7
lcsSetupVpnMyvpnEMailAddress OBJECT-TYPE
    SYNTAX     DisplayString (SIZE(0..63))
    MAX-ACCESS read-write
    STATUS     current
    DESCRIPTION
        "-- empty --"
    ::= { lcsSetupVpnMyvpn 7 }

-- {SCALAR} 1712.2.19.28.8
lcsSetupVpnMyvpnSyslog OBJECT-TYPE
    SYNTAX     INTEGER
      {
        eNo (0),
        eYes (1)
      }
    MAX-ACCESS read-write
    STATUS     current
    DESCRIPTION
        "-- empty --"
    ::= { lcsSetupVpnMyvpn 8 }

-- {SCALAR} 1712.2.19.28.9
lcsSetupVpnMyvpnRemoteGateway OBJECT-TYPE
    SYNTAX     DisplayString (SIZE(0..63))
    MAX-ACCESS read-write
    STATUS     current
    DESCRIPTION
        "-- empty --"
    ::= { lcsSetupVpnMyvpn 9 }

-- {SCALAR} 1712.2.19.28.10
lcsSetupVpnMyvpnErrorCountForLoginBlock OBJECT-TYPE
    SYNTAX     INTEGER (0..2147483647)
    MAX-ACCESS read-write
    STATUS     current
    DESCRIPTION
        "-- empty --"
    ::= { lcsSetupVpnMyvpn 10 }

-- {SCALAR} 1712.2.19.28.11
lcsSetupVpnMyvpnAllowAccessFromWan OBJECT-TYPE
    SYNTAX     INTEGER
      {
        eNo (0),
        eYes (1)
      }
    MAX-ACCESS read-write
    STATUS     current
    DESCRIPTION
        "-- empty --"
    ::= { lcsSetupVpnMyvpn 11 }

-- {SCALAR} 1712.2.19.30
lcsSetupVpnAntiReplayWindowSize OBJECT-TYPE
    SYNTAX     INTEGER (0..65535)
    MAX-ACCESS read-write
    STATUS     current
    DESCRIPTION
        "-- empty --"
    ::= { lcsSetupVpn 30 }

-- {OID} 1712.2.21
lcsSetupHttp OBJECT IDENTIFIER ::= { lcsSetup 21 }

-- {SCALAR} 1712.2.21.1
lcsSetupHttpDocumentRoot OBJECT-TYPE
    SYNTAX     DisplayString (SIZE(0..99))
    MAX-ACCESS read-write
    STATUS     current
    DESCRIPTION
        "-- empty --"
    ::= { lcsSetupHttp 1 }

-- {SCALAR} 1712.2.21.2
lcsSetupHttpUseCss OBJECT-TYPE
    SYNTAX     INTEGER
      {
        eNo (0),
        eYes (1)
      }
    MAX-ACCESS read-write
    STATUS     current
    DESCRIPTION
        "-- empty --"
    ::= { lcsSetupHttp 2 }

-- {SCALAR} 1712.2.21.3
lcsSetupHttpFontFamily OBJECT-TYPE
    SYNTAX     DisplayString (SIZE(0..39))
    MAX-ACCESS read-write
    STATUS     current
    DESCRIPTION
        "-- empty --"
    ::= { lcsSetupHttp 3 }

-- {SCALAR} 1712.2.21.5
lcsSetupHttpPageHeaders OBJECT-TYPE
    SYNTAX     INTEGER
      {
        eImages (0),
        eTexts (1)
      }
    MAX-ACCESS read-write
    STATUS     current
    DESCRIPTION
        "-- empty --"
    ::= { lcsSetupHttp 5 }

-- {SCALAR} 1712.2.21.6
lcsSetupHttpErrorPageStyle OBJECT-TYPE
    SYNTAX     INTEGER
      {
        eStandard (0),
        eNifty (1)
      }
    MAX-ACCESS read-write
    STATUS     current
    DESCRIPTION
        "-- empty --"
    ::= { lcsSetupHttp 6 }

-- {SCALAR} 1712.2.21.7
lcsSetupHttpPort OBJECT-TYPE
    SYNTAX     INTEGER (0..65535)
    MAX-ACCESS read-write
    STATUS     current
    DESCRIPTION
        "-- empty --"
    ::= { lcsSetupHttp 7 }

-- {OID} 1712.2.21.40
lcsSetupHttpSslNew OBJECT IDENTIFIER ::= { lcsSetupHttp 40 }

-- {SCALAR} 1712.2.21.40.10
lcsSetupHttpSslNewPortNew OBJECT-TYPE
    SYNTAX     INTEGER (0..65535)
    MAX-ACCESS read-write
    STATUS     current
    DESCRIPTION
        "TCP port device is listening on for HTTPS"
    ::= { lcsSetupHttpSslNew 10 }

-- {SCALAR} 1712.2.21.40.11
lcsSetupHttpSslNewUseUserDefCert OBJECT-TYPE
    SYNTAX     INTEGER
      {
        eNo (0),
        eYes (1)
      }
    MAX-ACCESS read-write
    STATUS     current
    DESCRIPTION
        "use uploaded SSL certificate for HTTPS server"
    ::= { lcsSetupHttpSslNew 11 }

-- {SCALAR} 1712.2.21.40.3
lcsSetupHttpSslNewVersions OBJECT-TYPE
    SYNTAX     BITS
      {
        eSslv3 (31),
        eTlsv1 (30),
        eTlsv11 (29),
        eTlsv12 (28)
      }
    MAX-ACCESS read-write
    STATUS     current
    DESCRIPTION
        "-- empty --"
    ::= { lcsSetupHttpSslNew 3 }

-- {SCALAR} 1712.2.21.40.4
lcsSetupHttpSslNewKeyexAlgorithms OBJECT-TYPE
    SYNTAX     BITS
      {
        eRsa (31),
        eDhe (29),
        eEcdhe (27)
      }
    MAX-ACCESS read-write
    STATUS     current
    DESCRIPTION
        "-- empty --"
    ::= { lcsSetupHttpSslNew 4 }

-- {SCALAR} 1712.2.21.40.5
lcsSetupHttpSslNewCryptoAlgorithms OBJECT-TYPE
    SYNTAX     BITS
      {
        eRc440 (29),
        eRc456 (28),
        eRc4128 (27),
        eDes40 (26),
        eDes (25),
        e3des (24),
        eAes128 (23),
        eAes256 (22),
        eAesgcm128 (21),
        eAesgcm256 (20)
      }
    MAX-ACCESS read-write
    STATUS     current
    DESCRIPTION
        "-- empty --"
    ::= { lcsSetupHttpSslNew 5 }

-- {SCALAR} 1712.2.21.40.6
lcsSetupHttpSslNewHashAlgorithms OBJECT-TYPE
    SYNTAX     BITS
      {
        eMd5 (30),
        eSha1 (29),
        eSha2256 (27),
        eSha2384 (26)
      }
    MAX-ACCESS read-write
    STATUS     current
    DESCRIPTION
        "-- empty --"
    ::= { lcsSetupHttpSslNew 6 }

-- {SCALAR} 1712.2.21.11
lcsSetupHttpSessionTimeout OBJECT-TYPE
    SYNTAX     INTEGER (0..2147483647)
    MAX-ACCESS read-write
    STATUS     current
    DESCRIPTION
        "-- empty --"
    ::= { lcsSetupHttp 11 }

-- {SCALAR} 1712.2.21.13
lcsSetupHttpStandardDesign OBJECT-TYPE
    SYNTAX     INTEGER
      {
        eNormalDesign (0),
        eDesignForSmallResolutions (1),
        eDesignWithHighContrast (2)
      }
    MAX-ACCESS read-write
    STATUS     current
    DESCRIPTION
        "-- empty --"
    ::= { lcsSetupHttp 13 }

-- {TABLE} 1712.2.21.14
lcsSetupHttpShowDeviceInformationTable OBJECT-TYPE
    SYNTAX     SEQUENCE OF LcsSetupHttpShowDeviceInformationEntry
    MAX-ACCESS not-accessible
    STATUS     current
    DESCRIPTION
        "-- empty --"
    ::= { lcsSetupHttp 14 }

-- {ENTRY} 1712.2.21.14.1
lcsSetupHttpShowDeviceInformationEntry OBJECT-TYPE
    SYNTAX     LcsSetupHttpShowDeviceInformationEntry
    MAX-ACCESS not-accessible
    STATUS     current
    DESCRIPTION
        ""
    INDEX {
        lcsSetupHttpShowDeviceInformationEntryDeviceInformation
    }
    ::= { lcsSetupHttpShowDeviceInformationTable 1 }

-- {SEQUENCE}
LcsSetupHttpShowDeviceInformationEntry ::= SEQUENCE {
    lcsSetupHttpShowDeviceInformationEntryDeviceInformation INTEGER,
    lcsSetupHttpShowDeviceInformationEntryPosition INTEGER
}

-- {COLUMN} 1712.2.21.14.1.1
lcsSetupHttpShowDeviceInformationEntryDeviceInformation OBJECT-TYPE
    SYNTAX     INTEGER
      {
        eCpu (1),
        eMemory (2),
        eEthernetPorts (5),
        eTroughputEthernet (6),
        eUmtsModemInterface (7),
        eRouter (8),
        eFirewall (9),
        eDhcp (10),
        eDns (11),
        eVpn (12),
        eIsdn (14),
        eDSLDSLoL (15), -- deprecated value
        eTime (18),
        eIpv4Addresses (19),
        eOperatingTime (20),
        eConnections (22),
        eIpv6Addresses (23),
        eIpv6Prefixes (24),
        eDhcpv6Client (25),
        eDhcpv6Server (26)
      }
    MAX-ACCESS read-write
    STATUS     current
    DESCRIPTION
        "-- empty --"
    ::= { lcsSetupHttpShowDeviceInformationEntry 1 }

-- {COLUMN} 1712.2.21.14.1.2
lcsSetupHttpShowDeviceInformationEntryPosition OBJECT-TYPE
    SYNTAX     INTEGER (0..2147483647)
    MAX-ACCESS read-write
    STATUS     current
    DESCRIPTION
        "-- empty --"
    ::= { lcsSetupHttpShowDeviceInformationEntry 2 }

-- {SCALAR} 1712.2.21.15
lcsSetupHttpHttpCompression OBJECT-TYPE
    SYNTAX     INTEGER
      {
        eActivated (0),
        eOnlyForWan (1),
        eDeactivated (2)
      }
    MAX-ACCESS read-write
    STATUS     current
    DESCRIPTION
        "-- empty --"
    ::= { lcsSetupHttp 15 }

-- {TABLE} 1712.2.21.16
lcsSetupHttpKeepServerPortsOpenTable OBJECT-TYPE
    SYNTAX     SEQUENCE OF LcsSetupHttpKeepServerPortsOpenEntry
    MAX-ACCESS not-accessible
    STATUS     current
    DESCRIPTION
        "-- empty --"
    ::= { lcsSetupHttp 16 }

-- {ENTRY} 1712.2.21.16.1
lcsSetupHttpKeepServerPortsOpenEntry OBJECT-TYPE
    SYNTAX     LcsSetupHttpKeepServerPortsOpenEntry
    MAX-ACCESS not-accessible
    STATUS     current
    DESCRIPTION
        ""
    INDEX {
        lcsSetupHttpKeepServerPortsOpenEntryIfc
    }
    ::= { lcsSetupHttpKeepServerPortsOpenTable 1 }

-- {SEQUENCE}
LcsSetupHttpKeepServerPortsOpenEntry ::= SEQUENCE {
    lcsSetupHttpKeepServerPortsOpenEntryIfc INTEGER,
    lcsSetupHttpKeepServerPortsOpenEntryKeepServerPortsOpen INTEGER
}

-- {COLUMN} 1712.2.21.16.1.1
lcsSetupHttpKeepServerPortsOpenEntryIfc OBJECT-TYPE
    SYNTAX     INTEGER
      {
        eLan (1),
        eWan (2)
      }
    MAX-ACCESS read-only
    STATUS     current
    DESCRIPTION
        "-- empty --"
    ::= { lcsSetupHttpKeepServerPortsOpenEntry 1 }

-- {COLUMN} 1712.2.21.16.1.2
lcsSetupHttpKeepServerPortsOpenEntryKeepServerPortsOpen OBJECT-TYPE
    SYNTAX     INTEGER
      {
        eAutomatic (0),
        eEnabled (1),
        eDisabled (2)
      }
    MAX-ACCESS read-write
    STATUS     current
    DESCRIPTION
        "-- empty --"
    ::= { lcsSetupHttpKeepServerPortsOpenEntry 2 }

-- {SCALAR} 1712.2.21.21
lcsSetupHttpMaxHttpJobCount OBJECT-TYPE
    SYNTAX     INTEGER (0..2147483647)
    MAX-ACCESS read-write
    STATUS     current
    DESCRIPTION
        "-- empty --"
    ::= { lcsSetupHttp 21 }

-- {SCALAR} 1712.2.21.9
lcsSetupHttpMaxTunnelConnections OBJECT-TYPE
    SYNTAX     INTEGER (0..255)
    MAX-ACCESS read-write
    STATUS     current
    DESCRIPTION
        "-- empty --"
    ::= { lcsSetupHttp 9 }

-- {SCALAR} 1712.2.21.10
lcsSetupHttpTunnelIdleTimeout OBJECT-TYPE
    SYNTAX     INTEGER (0..2147483647)
    MAX-ACCESS read-write
    STATUS     current
    DESCRIPTION
        "-- empty --"
    ::= { lcsSetupHttp 10 }

-- {OID} 1712.2.21.30
lcsSetupHttpFileServer OBJECT IDENTIFIER ::= { lcsSetupHttp 30 }

-- {SCALAR} 1712.2.21.30.2
lcsSetupHttpFileServerOperating OBJECT-TYPE
    SYNTAX     INTEGER
      {
        eNo (0),
        eYes (1)
      }
    MAX-ACCESS read-write
    STATUS     current
    DESCRIPTION
        "-- empty --"
    ::= { lcsSetupHttpFileServer 2 }

-- {SCALAR} 1712.2.21.30.1
lcsSetupHttpFileServerPublicSubdir OBJECT-TYPE
    SYNTAX     DisplayString (SIZE(0..64))
    MAX-ACCESS read-write
    STATUS     current
    DESCRIPTION
        "-- empty --"
    ::= { lcsSetupHttpFileServer 1 }

-- {OID} 1712.2.21.20
lcsSetupHttpRolloutWizard OBJECT IDENTIFIER ::= { lcsSetupHttp 20 }

-- {SCALAR} 1712.2.21.20.1
lcsSetupHttpRolloutWizardOperating OBJECT-TYPE
    SYNTAX     INTEGER
      {
        eNo (0),
        eYes (1)
      }
    MAX-ACCESS read-write
    STATUS     current
    DESCRIPTION
        "-- empty --"
    ::= { lcsSetupHttpRolloutWizard 1 }

-- {SCALAR} 1712.2.21.20.2
lcsSetupHttpRolloutWizardTitle OBJECT-TYPE
    SYNTAX     DisplayString (SIZE(0..50))
    MAX-ACCESS read-write
    STATUS     current
    DESCRIPTION
        "-- empty --"
    ::= { lcsSetupHttpRolloutWizard 2 }

-- {SCALAR} 1712.2.21.20.8
lcsSetupHttpRolloutWizardUseExtraChecks OBJECT-TYPE
    SYNTAX     INTEGER
      {
        eNo (0),
        eYes (1)
      }
    MAX-ACCESS read-write
    STATUS     current
    DESCRIPTION
        "-- empty --"
    ::= { lcsSetupHttpRolloutWizard 8 }

-- {TABLE} 1712.2.21.20.9
lcsSetupHttpRolloutWizardPresetsTable OBJECT-TYPE
    SYNTAX     SEQUENCE OF LcsSetupHttpRolloutWizardPresetsEntry
    MAX-ACCESS not-accessible
    STATUS     current
    DESCRIPTION
        "-- empty --"
    ::= { lcsSetupHttpRolloutWizard 9 }

-- {ENTRY} 1712.2.21.20.9.1
lcsSetupHttpRolloutWizardPresetsEntry OBJECT-TYPE
    SYNTAX     LcsSetupHttpRolloutWizardPresetsEntry
    MAX-ACCESS not-accessible
    STATUS     current
    DESCRIPTION
        ""
    INDEX {
        lcsSetupHttpRolloutWizardPresetsEntryName
    }
    ::= { lcsSetupHttpRolloutWizardPresetsTable 1 }

-- {SEQUENCE}
LcsSetupHttpRolloutWizardPresetsEntry ::= SEQUENCE {
    lcsSetupHttpRolloutWizardPresetsEntryName INTEGER,
    lcsSetupHttpRolloutWizardPresetsEntryPreset DisplayString,
    lcsSetupHttpRolloutWizardPresetsEntryUsePreset INTEGER
}

-- {COLUMN} 1712.2.21.20.9.1.1
lcsSetupHttpRolloutWizardPresetsEntryName OBJECT-TYPE
    SYNTAX     INTEGER
      {
        eRolloutHost (1),
        eProtocol (2),
        eUsername (3),
        ePassword (4),
        eProject (5),
        eDeviceId (6),
        eTan (8),
        eSourceLoopbackAddress (10),
        ePort (11)
      }
    MAX-ACCESS read-only
    STATUS     current
    DESCRIPTION
        "-- empty --"
    ::= { lcsSetupHttpRolloutWizardPresetsEntry 1 }

-- {COLUMN} 1712.2.21.20.9.1.2
lcsSetupHttpRolloutWizardPresetsEntryPreset OBJECT-TYPE
    SYNTAX     DisplayString (SIZE(0..127))
    MAX-ACCESS read-write
    STATUS     current
    DESCRIPTION
        "-- empty --"
    ::= { lcsSetupHttpRolloutWizardPresetsEntry 2 }

-- {COLUMN} 1712.2.21.20.9.1.3
lcsSetupHttpRolloutWizardPresetsEntryUsePreset OBJECT-TYPE
    SYNTAX     INTEGER
      {
        eNo (0),
        eYes (1)
      }
    MAX-ACCESS read-write
    STATUS     current
    DESCRIPTION
        "-- empty --"
    ::= { lcsSetupHttpRolloutWizardPresetsEntry 3 }

-- {SCALAR} 1712.2.21.20.10
lcsSetupHttpRolloutWizardDeleteWizard OBJECT-TYPE
    SYNTAX     DisplayString
    MAX-ACCESS read-write
    STATUS     current
    DESCRIPTION
        "-- empty --"
    ::= { lcsSetupHttpRolloutWizard 10 }

-- {OID} 1712.2.22
lcsSetupSyslog OBJECT IDENTIFIER ::= { lcsSetup 22 }

-- {SCALAR} 1712.2.22.1
lcsSetupSyslogOperating OBJECT-TYPE
    SYNTAX     INTEGER
      {
        eNo (0),
        eYes (1)
      }
    MAX-ACCESS read-write
    STATUS     current
    DESCRIPTION
        "-- empty --"
    ::= { lcsSetupSyslog 1 }

-- {TABLE} 1712.2.22.2
lcsSetupSyslogServerTable OBJECT-TYPE
    SYNTAX     SEQUENCE OF LcsSetupSyslogServerEntry
    MAX-ACCESS not-accessible
    STATUS     current
    DESCRIPTION
        "-- empty --"
    ::= { lcsSetupSyslog 2 }

-- {ENTRY} 1712.2.22.2.1
lcsSetupSyslogServerEntry OBJECT-TYPE
    SYNTAX     LcsSetupSyslogServerEntry
    MAX-ACCESS not-accessible
    STATUS     current
    DESCRIPTION
        ""
    INDEX {
        lcsSetupSyslogServerEntryIdx
    }
    ::= { lcsSetupSyslogServerTable 1 }

-- {SEQUENCE}
LcsSetupSyslogServerEntry ::= SEQUENCE {
    lcsSetupSyslogServerEntryIdx DisplayString,
    lcsSetupSyslogServerEntryIpAddress IpAddress,
    lcsSetupSyslogServerEntrySource INTEGER,
    lcsSetupSyslogServerEntryLevel INTEGER,
    lcsSetupSyslogServerEntryLoopbackAddr DisplayString
}

-- {COLUMN} 1712.2.22.2.1.1
lcsSetupSyslogServerEntryIdx OBJECT-TYPE
    SYNTAX     DisplayString (SIZE(0..4))
    MAX-ACCESS read-write
    STATUS     current
    DESCRIPTION
        "-- empty --"
    ::= { lcsSetupSyslogServerEntry 1 }

-- {COLUMN} 1712.2.22.2.1.2
lcsSetupSyslogServerEntryIpAddress OBJECT-TYPE
    SYNTAX     IpAddress
    MAX-ACCESS read-write
    STATUS     current
    DESCRIPTION
        "-- empty --"
    ::= { lcsSetupSyslogServerEntry 2 }

-- {COLUMN} 1712.2.22.2.1.3
lcsSetupSyslogServerEntrySource OBJECT-TYPE
    SYNTAX     INTEGER (0..255)
    MAX-ACCESS read-write
    STATUS     current
    DESCRIPTION
        "-- empty --"
    ::= { lcsSetupSyslogServerEntry 3 }

-- {COLUMN} 1712.2.22.2.1.4
lcsSetupSyslogServerEntryLevel OBJECT-TYPE
    SYNTAX     INTEGER (0..255)
    MAX-ACCESS read-write
    STATUS     current
    DESCRIPTION
        "-- empty --"
    ::= { lcsSetupSyslogServerEntry 4 }

-- {COLUMN} 1712.2.22.2.1.6
lcsSetupSyslogServerEntryLoopbackAddr OBJECT-TYPE
    SYNTAX     DisplayString (SIZE(0..16))
    MAX-ACCESS read-write
    STATUS     current
    DESCRIPTION
        "-- empty --"
    ::= { lcsSetupSyslogServerEntry 6 }

-- {TABLE} 1712.2.22.3
lcsSetupSyslogFacilityMapperTable OBJECT-TYPE
    SYNTAX     SEQUENCE OF LcsSetupSyslogFacilityMapperEntry
    MAX-ACCESS not-accessible
    STATUS     current
    DESCRIPTION
        "-- empty --"
    ::= { lcsSetupSyslog 3 }

-- {ENTRY} 1712.2.22.3.1
lcsSetupSyslogFacilityMapperEntry OBJECT-TYPE
    SYNTAX     LcsSetupSyslogFacilityMapperEntry
    MAX-ACCESS not-accessible
    STATUS     current
    DESCRIPTION
        ""
    INDEX {
        lcsSetupSyslogFacilityMapperEntrySource
    }
    ::= { lcsSetupSyslogFacilityMapperTable 1 }

-- {SEQUENCE}
LcsSetupSyslogFacilityMapperEntry ::= SEQUENCE {
    lcsSetupSyslogFacilityMapperEntrySource INTEGER,
    lcsSetupSyslogFacilityMapperEntryFacility INTEGER
}

-- {COLUMN} 1712.2.22.3.1.1
lcsSetupSyslogFacilityMapperEntrySource OBJECT-TYPE
    SYNTAX     INTEGER
      {
        eSystem (1),
        eLogin (2),
        eSystemtime (4),
        eConsoleLogin (8),
        eConnections (16),
        eAccounting (32),
        eAdministration (64),
        eRouter (128)
      }
    MAX-ACCESS read-only
    STATUS     current
    DESCRIPTION
        "-- empty --"
    ::= { lcsSetupSyslogFacilityMapperEntry 1 }

-- {COLUMN} 1712.2.22.3.1.2
lcsSetupSyslogFacilityMapperEntryFacility OBJECT-TYPE
    SYNTAX     INTEGER
      {
        eKern (0),
        eUser (1),
        eMail (2),
        eDaemon (3),
        eAuth (4),
        eSyslog (5),
        eLpr (6),
        eNews (7),
        eUucp (8),
        eCron (9),
        eAuthpriv (10),
        eLocal0 (16),
        eLocal1 (17),
        eLocal2 (18),
        eLocal3 (19),
        eLocal4 (20),
        eLocal5 (21),
        eLocal6 (22),
        eLocal7 (23)
      }
    MAX-ACCESS read-write
    STATUS     current
    DESCRIPTION
        "-- empty --"
    ::= { lcsSetupSyslogFacilityMapperEntry 2 }

-- {SCALAR} 1712.2.22.4
lcsSetupSyslogPort OBJECT-TYPE
    SYNTAX     INTEGER (0..65535)
    MAX-ACCESS read-write
    STATUS     current
    DESCRIPTION
        "-- empty --"
    ::= { lcsSetupSyslog 4 }

-- {SCALAR} 1712.2.22.5
lcsSetupSyslogMessagesTableOrder OBJECT-TYPE
    SYNTAX     INTEGER
      {
        eOldestOnTop (0),
        eNewestOnTop (1)
      }
    MAX-ACCESS read-write
    STATUS     current
    DESCRIPTION
        "-- empty --"
    ::= { lcsSetupSyslog 5 }

-- {SCALAR} 1712.2.22.8
lcsSetupSyslogLogCliChanges OBJECT-TYPE
    SYNTAX     INTEGER
      {
        eNo (0),
        eYes (1)
      }
    MAX-ACCESS read-write
    STATUS     current
    DESCRIPTION
        "-- empty --"
    ::= { lcsSetupSyslog 8 }

-- {SCALAR} 1712.2.22.9
lcsSetupSyslogMaxMessageAgeHours OBJECT-TYPE
    SYNTAX     INTEGER (0..2147483647)
    MAX-ACCESS read-write
    STATUS     current
    DESCRIPTION
        ""
    ::= { lcsSetupSyslog 9 }

-- {SCALAR} 1712.2.22.10
lcsSetupSyslogRemoveOldMessages OBJECT-TYPE
    SYNTAX     INTEGER
      {
        eNo (0),
        eYes (1)
      }
    MAX-ACCESS read-write
    STATUS     current
    DESCRIPTION
        "-- empty --"
    ::= { lcsSetupSyslog 10 }

-- {SCALAR} 1712.2.22.11
lcsSetupSyslogMaxAgeUnit OBJECT-TYPE
    SYNTAX     INTEGER
      {
        eHour (0),
        eDay (1),
        eMonth (2)
      }
    MAX-ACCESS read-write
    STATUS     current
    DESCRIPTION
        "-- empty --"
    ::= { lcsSetupSyslog 11 }

-- {OID} 1712.2.23
lcsSetupInterfaces OBJECT IDENTIFIER ::= { lcsSetup 23 }

-- {OID} 1712.2.23.40
lcsSetupInterfacesModem OBJECT IDENTIFIER ::= { lcsSetupInterfaces 40 }

-- {SCALAR} 1712.2.23.40.1
lcsSetupInterfacesModemRingCount OBJECT-TYPE
    SYNTAX     INTEGER (0..255)
    MAX-ACCESS read-write
    STATUS     current
    DESCRIPTION
        "-- empty --"
    ::= { lcsSetupInterfacesModem 1 }

-- {SCALAR} 1712.2.23.40.2
lcsSetupInterfacesModemEchoOffCommand OBJECT-TYPE
    SYNTAX     DisplayString (SIZE(0..9))
    MAX-ACCESS read-write
    STATUS     current
    DESCRIPTION
        "-- empty --"
    ::= { lcsSetupInterfacesModem 2 }

-- {SCALAR} 1712.2.23.40.3
lcsSetupInterfacesModemResetCommand OBJECT-TYPE
    SYNTAX     DisplayString (SIZE(0..9))
    MAX-ACCESS read-write
    STATUS     current
    DESCRIPTION
        "-- empty --"
    ::= { lcsSetupInterfacesModem 3 }

-- {SCALAR} 1712.2.23.40.4
lcsSetupInterfacesModemInitCommand OBJECT-TYPE
    SYNTAX     DisplayString (SIZE(0..63))
    MAX-ACCESS read-write
    STATUS     current
    DESCRIPTION
        "-- empty --"
    ::= { lcsSetupInterfacesModem 4 }

-- {SCALAR} 1712.2.23.40.6
lcsSetupInterfacesModemRequestId OBJECT-TYPE
    SYNTAX     DisplayString (SIZE(0..9))
    MAX-ACCESS read-write
    STATUS     current
    DESCRIPTION
        "-- empty --"
    ::= { lcsSetupInterfacesModem 6 }

-- {SCALAR} 1712.2.23.40.11
lcsSetupInterfacesModemInitDial OBJECT-TYPE
    SYNTAX     DisplayString (SIZE(0..63))
    MAX-ACCESS read-write
    STATUS     current
    DESCRIPTION
        "-- empty --"
    ::= { lcsSetupInterfacesModem 11 }

-- {SCALAR} 1712.2.23.40.5
lcsSetupInterfacesModemDialCommand OBJECT-TYPE
    SYNTAX     DisplayString (SIZE(0..31))
    MAX-ACCESS read-write
    STATUS     current
    DESCRIPTION
        "-- empty --"
    ::= { lcsSetupInterfacesModem 5 }

-- {SCALAR} 1712.2.23.40.12
lcsSetupInterfacesModemInitAnswer OBJECT-TYPE
    SYNTAX     DisplayString (SIZE(0..63))
    MAX-ACCESS read-write
    STATUS     current
    DESCRIPTION
        "-- empty --"
    ::= { lcsSetupInterfacesModem 12 }

-- {SCALAR} 1712.2.23.40.7
lcsSetupInterfacesModemAnswerCommand OBJECT-TYPE
    SYNTAX     DisplayString (SIZE(0..9))
    MAX-ACCESS read-write
    STATUS     current
    DESCRIPTION
        "-- empty --"
    ::= { lcsSetupInterfacesModem 7 }

-- {SCALAR} 1712.2.23.40.8
lcsSetupInterfacesModemDisconnectCommand OBJECT-TYPE
    SYNTAX     DisplayString (SIZE(0..9))
    MAX-ACCESS read-write
    STATUS     current
    DESCRIPTION
        "-- empty --"
    ::= { lcsSetupInterfacesModem 8 }

-- {SCALAR} 1712.2.23.40.9
lcsSetupInterfacesModemEscapeSequence OBJECT-TYPE
    SYNTAX     DisplayString (SIZE(0..9))
    MAX-ACCESS read-write
    STATUS     current
    DESCRIPTION
        "-- empty --"
    ::= { lcsSetupInterfacesModem 9 }

-- {SCALAR} 1712.2.23.40.10
lcsSetupInterfacesModemEscapePromtDelayMs OBJECT-TYPE
    SYNTAX     INTEGER (0..65535)
    MAX-ACCESS read-write
    STATUS     current
    DESCRIPTION
        "-- empty --"
    ::= { lcsSetupInterfacesModem 10 }

-- {SCALAR} 1712.2.23.40.13
lcsSetupInterfacesModemCycletimeAtPollS OBJECT-TYPE
    SYNTAX     INTEGER (0..255)
    MAX-ACCESS read-write
    STATUS     current
    DESCRIPTION
        "-- empty --"
    ::= { lcsSetupInterfacesModem 13 }

-- {SCALAR} 1712.2.23.40.14
lcsSetupInterfacesModemAtPollCount OBJECT-TYPE
    SYNTAX     INTEGER (0..255)
    MAX-ACCESS read-write
    STATUS     current
    DESCRIPTION
        "-- empty --"
    ::= { lcsSetupInterfacesModem 14 }

-- {OID} 1712.2.23.41
lcsSetupInterfacesMobile OBJECT IDENTIFIER ::= { lcsSetupInterfaces 41 }

-- {TABLE} 1712.2.23.41.1
lcsSetupInterfacesMobileProfilesTable OBJECT-TYPE
    SYNTAX     SEQUENCE OF LcsSetupInterfacesMobileProfilesEntry
    MAX-ACCESS not-accessible
    STATUS     current
    DESCRIPTION
        "-- empty --"
    ::= { lcsSetupInterfacesMobile 1 }

-- {ENTRY} 1712.2.23.41.1.1
lcsSetupInterfacesMobileProfilesEntry OBJECT-TYPE
    SYNTAX     LcsSetupInterfacesMobileProfilesEntry
    MAX-ACCESS not-accessible
    STATUS     current
    DESCRIPTION
        ""
    INDEX {
        lcsSetupInterfacesMobileProfilesEntryProfile
    }
    ::= { lcsSetupInterfacesMobileProfilesTable 1 }

-- {SEQUENCE}
LcsSetupInterfacesMobileProfilesEntry ::= SEQUENCE {
    lcsSetupInterfacesMobileProfilesEntryProfile DisplayString,
    lcsSetupInterfacesMobileProfilesEntryPin DisplayString,
    lcsSetupInterfacesMobileProfilesEntryApn DisplayString,
    lcsSetupInterfacesMobileProfilesEntryNetwork DisplayString,
    lcsSetupInterfacesMobileProfilesEntrySelect INTEGER,
    lcsSetupInterfacesMobileProfilesEntryMode INTEGER,
    lcsSetupInterfacesMobileProfilesEntryQosDownstreamDataRate INTEGER,
    lcsSetupInterfacesMobileProfilesEntryQosUpstreamDataRate INTEGER,
    lcsSetupInterfacesMobileProfilesEntryPdpType INTEGER,
    lcsSetupInterfacesMobileProfilesEntryLteBands BITS,
    lcsSetupInterfacesMobileProfilesEntryLteAttach INTEGER
}

-- {COLUMN} 1712.2.23.41.1.1.1
lcsSetupInterfacesMobileProfilesEntryProfile OBJECT-TYPE
    SYNTAX     DisplayString (SIZE(0..16))
    MAX-ACCESS read-write
    STATUS     current
    DESCRIPTION
        "-- empty --"
    ::= { lcsSetupInterfacesMobileProfilesEntry 1 }

-- {COLUMN} 1712.2.23.41.1.1.2
lcsSetupInterfacesMobileProfilesEntryPin OBJECT-TYPE
    SYNTAX     DisplayString (SIZE(0..6))
    MAX-ACCESS read-write
    STATUS     current
    DESCRIPTION
        "-- empty --"
    ::= { lcsSetupInterfacesMobileProfilesEntry 2 }

-- {COLUMN} 1712.2.23.41.1.1.3
lcsSetupInterfacesMobileProfilesEntryApn OBJECT-TYPE
    SYNTAX     DisplayString (SIZE(0..47))
    MAX-ACCESS read-write
    STATUS     current
    DESCRIPTION
        "-- empty --"
    ::= { lcsSetupInterfacesMobileProfilesEntry 3 }

-- {COLUMN} 1712.2.23.41.1.1.4
lcsSetupInterfacesMobileProfilesEntryNetwork OBJECT-TYPE
    SYNTAX     DisplayString (SIZE(0..16))
    MAX-ACCESS read-write
    STATUS     current
    DESCRIPTION
        "-- empty --"
    ::= { lcsSetupInterfacesMobileProfilesEntry 4 }

-- {COLUMN} 1712.2.23.41.1.1.5
lcsSetupInterfacesMobileProfilesEntrySelect OBJECT-TYPE
    SYNTAX     INTEGER
      {
        eAuto (0),
        eManual (1)
      }
    MAX-ACCESS read-write
    STATUS     current
    DESCRIPTION
        "-- empty --"
    ::= { lcsSetupInterfacesMobileProfilesEntry 5 }

-- {COLUMN} 1712.2.23.41.1.1.6
lcsSetupInterfacesMobileProfilesEntryMode OBJECT-TYPE
    SYNTAX     INTEGER
      {
        eAuto (0),
        eUmts (1),
        eGprs (2),
        eUmtsGprs (11),
        eLte (8)
      }
    MAX-ACCESS read-write
    STATUS     current
    DESCRIPTION
        "-- empty --"
    ::= { lcsSetupInterfacesMobileProfilesEntry 6 }

-- {COLUMN} 1712.2.23.41.1.1.7
lcsSetupInterfacesMobileProfilesEntryQosDownstreamDataRate OBJECT-TYPE
    SYNTAX     INTEGER (0..2147483647)
    MAX-ACCESS read-write
    STATUS     current
    DESCRIPTION
        "-- empty --"
    ::= { lcsSetupInterfacesMobileProfilesEntry 7 }

-- {COLUMN} 1712.2.23.41.1.1.8
lcsSetupInterfacesMobileProfilesEntryQosUpstreamDataRate OBJECT-TYPE
    SYNTAX     INTEGER (0..2147483647)
    MAX-ACCESS read-write
    STATUS     current
    DESCRIPTION
        "-- empty --"
    ::= { lcsSetupInterfacesMobileProfilesEntry 8 }

-- {COLUMN} 1712.2.23.41.1.1.9
lcsSetupInterfacesMobileProfilesEntryPdpType OBJECT-TYPE
    SYNTAX     INTEGER
      {
        eIpv4 (0),
        eIpv6 (2),
        eIpv4v6 (3)
      }
    MAX-ACCESS read-write
    STATUS     current
    DESCRIPTION
        "-- empty --"
    ::= { lcsSetupInterfacesMobileProfilesEntry 9 }

-- {COLUMN} 1712.2.23.41.1.1.10
lcsSetupInterfacesMobileProfilesEntryLteBands OBJECT-TYPE
    SYNTAX     BITS
      {
        eAll (31),
        eB12100 (30),
        eB31800 (29),
        eB72600 (28),
        eB8900 (27),
        eB20800 (26)
      }
    MAX-ACCESS read-write
    STATUS     current
    DESCRIPTION
        "-- empty --"
    ::= { lcsSetupInterfacesMobileProfilesEntry 10 }

-- {COLUMN} 1712.2.23.41.1.1.11
lcsSetupInterfacesMobileProfilesEntryLteAttach OBJECT-TYPE
    SYNTAX     INTEGER
      {
        eImmediate (0),
        eDelayed (1)
      }
    MAX-ACCESS read-write
    STATUS     current
    DESCRIPTION
        "-- empty --"
    ::= { lcsSetupInterfacesMobileProfilesEntry 11 }

-- {SCALAR} 1712.2.23.41.6
lcsSetupInterfacesMobileHistoryIntervalSec OBJECT-TYPE
    SYNTAX     INTEGER (0..2147483647)
    MAX-ACCESS read-write
    STATUS     current
    DESCRIPTION
        "-- empty --"
    ::= { lcsSetupInterfacesMobile 6 }

-- {SCALAR} 1712.2.23.41.7
lcsSetupInterfacesMobileSyslogEnabled OBJECT-TYPE
    SYNTAX     INTEGER
      {
        eNo (0),
        eYes (1)
      }
    MAX-ACCESS read-write
    STATUS     current
    DESCRIPTION
        "-- empty --"
    ::= { lcsSetupInterfacesMobile 7 }

-- {SCALAR} 1712.2.23.41.9
lcsSetupInterfacesMobileSignalCheckIntervallMin OBJECT-TYPE
    SYNTAX     INTEGER (0..2147483647)
    MAX-ACCESS read-write
    STATUS     current
    DESCRIPTION
        "-- empty --"
    ::= { lcsSetupInterfacesMobile 9 }

-- {SCALAR} 1712.2.23.41.10
lcsSetupInterfacesMobileTreshold3gTo2gDb OBJECT-TYPE
    SYNTAX     INTEGER (-2147483648..2147483647)
    MAX-ACCESS read-write
    STATUS     current
    DESCRIPTION
        "-- empty --"
    ::= { lcsSetupInterfacesMobile 10 }

-- {SCALAR} 1712.2.23.41.11
lcsSetupInterfacesMobileCheckWhileConnected OBJECT-TYPE
    SYNTAX     INTEGER
      {
        eNo (0),
        eYes (1)
      }
    MAX-ACCESS read-write
    STATUS     current
    DESCRIPTION
        "-- empty --"
    ::= { lcsSetupInterfacesMobile 11 }

-- {SCALAR} 1712.2.23.41.2
lcsSetupInterfacesMobileScanNetworks OBJECT-TYPE
    SYNTAX     DisplayString
    MAX-ACCESS read-write
    STATUS     current
    DESCRIPTION
        "-- empty --"
    ::= { lcsSetupInterfacesMobile 2 }

-- {SCALAR} 1712.2.23.41.3
lcsSetupInterfacesMobileInputPuk OBJECT-TYPE
    SYNTAX     DisplayString
    MAX-ACCESS read-write
    STATUS     current
    DESCRIPTION
        "-- empty --"
    ::= { lcsSetupInterfacesMobile 3 }

-- {SCALAR} 1712.2.23.41.12
lcsSetupInterfacesMobilePinChange OBJECT-TYPE
    SYNTAX     DisplayString
    MAX-ACCESS read-write
    STATUS     current
    DESCRIPTION
        "-- empty --"
    ::= { lcsSetupInterfacesMobile 12 }

-- {TABLE} 1712.2.23.21
lcsSetupInterfacesLanInterfacesTable OBJECT-TYPE
    SYNTAX     SEQUENCE OF LcsSetupInterfacesLanInterfacesEntry
    MAX-ACCESS not-accessible
    STATUS     current
    DESCRIPTION
        "-- empty --"
    ::= { lcsSetupInterfaces 21 }

-- {ENTRY} 1712.2.23.21.1
lcsSetupInterfacesLanInterfacesEntry OBJECT-TYPE
    SYNTAX     LcsSetupInterfacesLanInterfacesEntry
    MAX-ACCESS not-accessible
    STATUS     current
    DESCRIPTION
        ""
    INDEX {
        lcsSetupInterfacesLanInterfacesEntryIfc
    }
    ::= { lcsSetupInterfacesLanInterfacesTable 1 }

-- {SEQUENCE}
LcsSetupInterfacesLanInterfacesEntry ::= SEQUENCE {
    lcsSetupInterfacesLanInterfacesEntryIfc INTEGER,
    lcsSetupInterfacesLanInterfacesEntryOperating INTEGER
}

-- {COLUMN} 1712.2.23.21.1.1
lcsSetupInterfacesLanInterfacesEntryIfc OBJECT-TYPE
    SYNTAX     INTEGER
      {
        eLan1 (1),
        eLan2 (2),
        eLan3 (3),
        eLan4 (4)
      }
    MAX-ACCESS read-only
    STATUS     current
    DESCRIPTION
        "-- empty --"
    ::= { lcsSetupInterfacesLanInterfacesEntry 1 }

-- {COLUMN} 1712.2.23.21.1.7
lcsSetupInterfacesLanInterfacesEntryOperating OBJECT-TYPE
    SYNTAX     INTEGER
      {
        eYes (0),
        eNo (1)
      }
    MAX-ACCESS read-write
    STATUS     current
    DESCRIPTION
        "-- empty --"
    ::= { lcsSetupInterfacesLanInterfacesEntry 7 }

-- {TABLE} 1712.2.23.30
lcsSetupInterfacesEthernetPortsTable OBJECT-TYPE
    SYNTAX     SEQUENCE OF LcsSetupInterfacesEthernetPortsEntry
    MAX-ACCESS not-accessible
    STATUS     current
    DESCRIPTION
        "-- empty --"
    ::= { lcsSetupInterfaces 30 }

-- {ENTRY} 1712.2.23.30.1
lcsSetupInterfacesEthernetPortsEntry OBJECT-TYPE
    SYNTAX     LcsSetupInterfacesEthernetPortsEntry
    MAX-ACCESS not-accessible
    STATUS     current
    DESCRIPTION
        ""
    INDEX {
        lcsSetupInterfacesEthernetPortsEntryPort
    }
    ::= { lcsSetupInterfacesEthernetPortsTable 1 }

-- {SEQUENCE}
LcsSetupInterfacesEthernetPortsEntry ::= SEQUENCE {
    lcsSetupInterfacesEthernetPortsEntryPort INTEGER,
    lcsSetupInterfacesEthernetPortsEntryAssignment INTEGER,
    lcsSetupInterfacesEthernetPortsEntryConnector INTEGER,
    lcsSetupInterfacesEthernetPortsEntryMdiMode INTEGER,
    lcsSetupInterfacesEthernetPortsEntryPrivateMode INTEGER,
    lcsSetupInterfacesEthernetPortsEntryFlowControl INTEGER
}

-- {COLUMN} 1712.2.23.30.1.1
lcsSetupInterfacesEthernetPortsEntryPort OBJECT-TYPE
    SYNTAX     INTEGER
      {
        eWan (1),
        eEth1 (2),
        eEth2 (3),
        eEth3 (4),
        eEth4 (5),
        eUnknown (0)
      }
    MAX-ACCESS read-only
    STATUS     current
    DESCRIPTION
        "-- empty --"
    ::= { lcsSetupInterfacesEthernetPortsEntry 1 }

-- {COLUMN} 1712.2.23.30.1.4
lcsSetupInterfacesEthernetPortsEntryAssignment OBJECT-TYPE
    SYNTAX     INTEGER
      {
        eDsl1 (512),
        eDsl2 (513),
        eDsl3 (514),
        eDsl4 (515),
        eLan1 (0),
        eLan2 (1),
        eLan3 (2),
        eLan4 (3),
        eIdle (65533),
        eMonitor (65534),
        ePowerDown (65535)
      }
    MAX-ACCESS read-write
    STATUS     current
    DESCRIPTION
        "-- empty --"
    ::= { lcsSetupInterfacesEthernetPortsEntry 4 }

-- {COLUMN} 1712.2.23.30.1.2
lcsSetupInterfacesEthernetPortsEntryConnector OBJECT-TYPE
    SYNTAX     INTEGER
      {
        eAuto (0),
        e10bT (1),
        eFd10bTx (2),
        e100bTx (3),
        eFd100bTx (4)
      }
    MAX-ACCESS read-write
    STATUS     current
    DESCRIPTION
        "-- empty --"
    ::= { lcsSetupInterfacesEthernetPortsEntry 2 }

-- {COLUMN} 1712.2.23.30.1.5
lcsSetupInterfacesEthernetPortsEntryMdiMode OBJECT-TYPE
    SYNTAX     INTEGER
      {
        eAuto (0),
        eMdi (1),
        eMdix (2)
      }
    MAX-ACCESS read-write
    STATUS     current
    DESCRIPTION
        "-- empty --"
    ::= { lcsSetupInterfacesEthernetPortsEntry 5 }

-- {COLUMN} 1712.2.23.30.1.3
lcsSetupInterfacesEthernetPortsEntryPrivateMode OBJECT-TYPE
    SYNTAX     INTEGER
      {
        eNo (0),
        eYes (1)
      }
    MAX-ACCESS read-write
    STATUS     current
    DESCRIPTION
        "-- empty --"
    ::= { lcsSetupInterfacesEthernetPortsEntry 3 }

-- {COLUMN} 1712.2.23.30.1.9
lcsSetupInterfacesEthernetPortsEntryFlowControl OBJECT-TYPE
    SYNTAX     INTEGER
      {
        eAuto (0),
        eOn (1),
        eOff (2)
      }
    MAX-ACCESS read-write
    STATUS     current
    DESCRIPTION
        "-- empty --"
    ::= { lcsSetupInterfacesEthernetPortsEntry 9 }

-- {TABLE} 1712.2.23.4
lcsSetupInterfacesDslTable OBJECT-TYPE
    SYNTAX     SEQUENCE OF LcsSetupInterfacesDslEntry
    MAX-ACCESS not-accessible
    STATUS     current
    DESCRIPTION
        "-- empty --"
    ::= { lcsSetupInterfaces 4 }

-- {ENTRY} 1712.2.23.4.1
lcsSetupInterfacesDslEntry OBJECT-TYPE
    SYNTAX     LcsSetupInterfacesDslEntry
    MAX-ACCESS not-accessible
    STATUS     current
    DESCRIPTION
        ""
    INDEX {
        lcsSetupInterfacesDslEntryIfc
    }
    ::= { lcsSetupInterfacesDslTable 1 }

-- {SEQUENCE}
LcsSetupInterfacesDslEntry ::= SEQUENCE {
    lcsSetupInterfacesDslEntryIfc INTEGER,
    lcsSetupInterfacesDslEntryOperating INTEGER,
    lcsSetupInterfacesDslEntryUpstreamRate INTEGER,
    lcsSetupInterfacesDslEntryExtOverhead INTEGER,
    lcsSetupInterfacesDslEntryDownstreamRate INTEGER,
    lcsSetupInterfacesDslEntryTypeOfInterface INTEGER
}

-- {COLUMN} 1712.2.23.4.1.1
lcsSetupInterfacesDslEntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsSetupInterfacesDslEntry 1 }

-- {COLUMN} 1712.2.23.4.1.2
lcsSetupInterfacesDslEntryOperating OBJECT-TYPE
    SYNTAX     INTEGER
      {
        eNo (0),
        eYes (16)
      }
    MAX-ACCESS read-write
    STATUS     current
    DESCRIPTION
        "-- empty --"
    ::= { lcsSetupInterfacesDslEntry 2 }

-- {COLUMN} 1712.2.23.4.1.16
lcsSetupInterfacesDslEntryUpstreamRate OBJECT-TYPE
    SYNTAX     INTEGER (0..2147483647)
    MAX-ACCESS read-write
    STATUS     current
    DESCRIPTION
        "-- empty --"
    ::= { lcsSetupInterfacesDslEntry 16 }

-- {COLUMN} 1712.2.23.4.1.17
lcsSetupInterfacesDslEntryExtOverhead OBJECT-TYPE
    SYNTAX     INTEGER (0..2147483647)
    MAX-ACCESS read-write
    STATUS     current
    DESCRIPTION
        "-- empty --"
    ::= { lcsSetupInterfacesDslEntry 17 }

-- {COLUMN} 1712.2.23.4.1.18
lcsSetupInterfacesDslEntryDownstreamRate OBJECT-TYPE
    SYNTAX     INTEGER (0..2147483647)
    MAX-ACCESS read-write
    STATUS     current
    DESCRIPTION
        "-- empty --"
    ::= { lcsSetupInterfacesDslEntry 18 }

-- {COLUMN} 1712.2.23.4.1.15
lcsSetupInterfacesDslEntryTypeOfInterface OBJECT-TYPE
    SYNTAX     INTEGER (0..2147483647)
    MAX-ACCESS read-only
    STATUS     current
    DESCRIPTION
        "-- empty --"
    ::= { lcsSetupInterfacesDslEntry 15 }

-- {TABLE} 1712.2.23.1
lcsSetupInterfacesS0Table OBJECT-TYPE
    SYNTAX     SEQUENCE OF LcsSetupInterfacesS0Entry
    MAX-ACCESS not-accessible
    STATUS     current
    DESCRIPTION
        "-- empty --"
    ::= { lcsSetupInterfaces 1 }

-- {ENTRY} 1712.2.23.1.1
lcsSetupInterfacesS0Entry OBJECT-TYPE
    SYNTAX     LcsSetupInterfacesS0Entry
    MAX-ACCESS not-accessible
    STATUS     current
    DESCRIPTION
        ""
    INDEX {
        lcsSetupInterfacesS0EntryIfc
    }
    ::= { lcsSetupInterfacesS0Table 1 }

-- {SEQUENCE}
LcsSetupInterfacesS0Entry ::= SEQUENCE {
    lcsSetupInterfacesS0EntryIfc INTEGER,
    lcsSetupInterfacesS0EntryProtocol INTEGER,
    lcsSetupInterfacesS0EntryLlBChan INTEGER,
    lcsSetupInterfacesS0EntryDialPrefix DisplayString,
    lcsSetupInterfacesS0EntryMaxInCalls INTEGER,
    lcsSetupInterfacesS0EntryMaxOutCalls INTEGER,
    lcsSetupInterfacesS0EntryTypeOfInterface INTEGER
}

-- {COLUMN} 1712.2.23.1.1.1
lcsSetupInterfacesS0EntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsSetupInterfacesS0Entry 1 }

-- {COLUMN} 1712.2.23.1.1.2
lcsSetupInterfacesS0EntryProtocol OBJECT-TYPE
    SYNTAX     INTEGER
      {
        eNo (0),
        eDss1 (1),
        e1tr6 (2),
        eP2pDss1 (4),
        eGrp0 (16),
        eAuto (255)
      }
    MAX-ACCESS read-write
    STATUS     current
    DESCRIPTION
        "-- empty --"
    ::= { lcsSetupInterfacesS0Entry 2 }

-- {COLUMN} 1712.2.23.1.1.7
lcsSetupInterfacesS0EntryLlBChan OBJECT-TYPE
    SYNTAX     INTEGER
      {
        eNone (0),
        eB1 (1),
        eB2 (2)
      }
    MAX-ACCESS read-write
    STATUS     current
    DESCRIPTION
        "-- empty --"
    ::= { lcsSetupInterfacesS0Entry 7 }

-- {COLUMN} 1712.2.23.1.1.9
lcsSetupInterfacesS0EntryDialPrefix OBJECT-TYPE
    SYNTAX     DisplayString (SIZE(0..8))
    MAX-ACCESS read-write
    STATUS     current
    DESCRIPTION
        "-- empty --"
    ::= { lcsSetupInterfacesS0Entry 9 }

-- {COLUMN} 1712.2.23.1.1.13
lcsSetupInterfacesS0EntryMaxInCalls OBJECT-TYPE
    SYNTAX     INTEGER
      {
        eZero (2),
        eOne (1),
        eTwo (0)
      }
    MAX-ACCESS read-write
    STATUS     current
    DESCRIPTION
        "-- empty --"
    ::= { lcsSetupInterfacesS0Entry 13 }

-- {COLUMN} 1712.2.23.1.1.14
lcsSetupInterfacesS0EntryMaxOutCalls OBJECT-TYPE
    SYNTAX     INTEGER
      {
        eZero (2),
        eOne (1),
        eTwo (0)
      }
    MAX-ACCESS read-write
    STATUS     current
    DESCRIPTION
        "-- empty --"
    ::= { lcsSetupInterfacesS0Entry 14 }

-- {COLUMN} 1712.2.23.1.1.15
lcsSetupInterfacesS0EntryTypeOfInterface OBJECT-TYPE
    SYNTAX     INTEGER (0..2147483647)
    MAX-ACCESS read-only
    STATUS     current
    DESCRIPTION
        "-- empty --"
    ::= { lcsSetupInterfacesS0Entry 15 }

-- {TABLE} 1712.2.23.7
lcsSetupInterfacesModemMobileTable OBJECT-TYPE
    SYNTAX     SEQUENCE OF LcsSetupInterfacesModemMobileEntry
    MAX-ACCESS not-accessible
    STATUS     current
    DESCRIPTION
        "-- empty --"
    ::= { lcsSetupInterfaces 7 }

-- {ENTRY} 1712.2.23.7.1
lcsSetupInterfacesModemMobileEntry OBJECT-TYPE
    SYNTAX     LcsSetupInterfacesModemMobileEntry
    MAX-ACCESS not-accessible
    STATUS     current
    DESCRIPTION
        ""
    INDEX {
        lcsSetupInterfacesModemMobileEntryIfc
    }
    ::= { lcsSetupInterfacesModemMobileTable 1 }

-- {SEQUENCE}
LcsSetupInterfacesModemMobileEntry ::= SEQUENCE {
    lcsSetupInterfacesModemMobileEntryIfc INTEGER,
    lcsSetupInterfacesModemMobileEntryOperating INTEGER,
    lcsSetupInterfacesModemMobileEntryTypeOfInterface INTEGER,
    lcsSetupInterfacesModemMobileEntryDataRate INTEGER,
    lcsSetupInterfacesModemMobileEntryProfile DisplayString
}

-- {COLUMN} 1712.2.23.7.1.1
lcsSetupInterfacesModemMobileEntryIfc OBJECT-TYPE
    SYNTAX     INTEGER
      {
        eDsl1 (1),
        eDsl2 (2),
        eDsl3 (3),
        eDsl4 (4),
        eS01 (5),
        eModem (6)
      }
    MAX-ACCESS read-only
    STATUS     current
    DESCRIPTION
        "-- empty --"
    ::= { lcsSetupInterfacesModemMobileEntry 1 }

-- {COLUMN} 1712.2.23.7.1.2
lcsSetupInterfacesModemMobileEntryOperating OBJECT-TYPE
    SYNTAX     INTEGER
      {
        eNo (0),
        eModem (1),
        eWwan (2)
      }
    MAX-ACCESS read-write
    STATUS     current
    DESCRIPTION
        "-- empty --"
    ::= { lcsSetupInterfacesModemMobileEntry 2 }

-- {COLUMN} 1712.2.23.7.1.15
lcsSetupInterfacesModemMobileEntryTypeOfInterface OBJECT-TYPE
    SYNTAX     INTEGER (0..2147483647)
    MAX-ACCESS read-only
    STATUS     current
    DESCRIPTION
        "-- empty --"
    ::= { lcsSetupInterfacesModemMobileEntry 15 }

-- {COLUMN} 1712.2.23.7.1.21
lcsSetupInterfacesModemMobileEntryDataRate OBJECT-TYPE
    SYNTAX     INTEGER
      {
        e19200 (19200),
        e38400 (38400),
        e57600 (57600),
        e115200 (115200)
      }
    MAX-ACCESS read-write
    STATUS     current
    DESCRIPTION
        "-- empty --"
    ::= { lcsSetupInterfacesModemMobileEntry 21 }

-- {COLUMN} 1712.2.23.7.1.22
lcsSetupInterfacesModemMobileEntryProfile OBJECT-TYPE
    SYNTAX     DisplayString (SIZE(0..16))
    MAX-ACCESS read-write
    STATUS     current
    DESCRIPTION
        "-- empty --"
    ::= { lcsSetupInterfacesModemMobileEntry 22 }

-- {OID} 1712.2.25
lcsSetupRadius OBJECT IDENTIFIER ::= { lcsSetup 25 }

-- {SCALAR} 1712.2.25.4
lcsSetupRadiusAuthTimeout OBJECT-TYPE
    SYNTAX     INTEGER (0..65535)
    MAX-ACCESS read-write
    STATUS     current
    DESCRIPTION
        "-- empty --"
    ::= { lcsSetupRadius 4 }

-- {SCALAR} 1712.2.25.5
lcsSetupRadiusAuthRetry OBJECT-TYPE
    SYNTAX     INTEGER (0..255)
    MAX-ACCESS read-write
    STATUS     current
    DESCRIPTION
        "-- empty --"
    ::= { lcsSetupRadius 5 }

-- {SCALAR} 1712.2.25.9
lcsSetupRadiusBackupQueryStrategy OBJECT-TYPE
    SYNTAX     INTEGER
      {
        eBlock (0),
        eCyclic (1)
      }
    MAX-ACCESS read-write
    STATUS     current
    DESCRIPTION
        "-- empty --"
    ::= { lcsSetupRadius 9 }

-- {OID} 1712.2.25.10
lcsSetupRadiusServer OBJECT IDENTIFIER ::= { lcsSetupRadius 10 }

-- {SCALAR} 1712.2.25.10.1
lcsSetupRadiusServerAuthentificationPort OBJECT-TYPE
    SYNTAX     INTEGER (0..65535)
    MAX-ACCESS read-write
    STATUS     current
    DESCRIPTION
        "-- empty --"
    ::= { lcsSetupRadiusServer 1 }

-- {SCALAR} 1712.2.25.10.11
lcsSetupRadiusServerAccountingPort OBJECT-TYPE
    SYNTAX     INTEGER (0..65535)
    MAX-ACCESS read-write
    STATUS     current
    DESCRIPTION
        "-- empty --"
    ::= { lcsSetupRadiusServer 11 }

-- {SCALAR} 1712.2.25.10.13
lcsSetupRadiusServerRadsecPort OBJECT-TYPE
    SYNTAX     INTEGER (0..65535)
    MAX-ACCESS read-write
    STATUS     current
    DESCRIPTION
        "-- empty --"
    ::= { lcsSetupRadiusServer 13 }

-- {SCALAR} 1712.2.25.10.15
lcsSetupRadiusServerAllowStatusRequests OBJECT-TYPE
    SYNTAX     INTEGER
      {
        eNo (0),
        eYes (1)
      }
    MAX-ACCESS read-write
    STATUS     current
    DESCRIPTION
        "-- empty --"
    ::= { lcsSetupRadiusServer 15 }

-- {TABLE} 1712.2.25.10.2
lcsSetupRadiusServerClientsTable OBJECT-TYPE
    SYNTAX     SEQUENCE OF LcsSetupRadiusServerClientsEntry
    MAX-ACCESS not-accessible
    STATUS     current
    DESCRIPTION
        "-- empty --"
    ::= { lcsSetupRadiusServer 2 }

-- {ENTRY} 1712.2.25.10.2.1
lcsSetupRadiusServerClientsEntry OBJECT-TYPE
    SYNTAX     LcsSetupRadiusServerClientsEntry
    MAX-ACCESS not-accessible
    STATUS     current
    DESCRIPTION
        ""
    INDEX {
        lcsSetupRadiusServerClientsEntryIpNetwork,
        lcsSetupRadiusServerClientsEntryIpNetmask
    }
    ::= { lcsSetupRadiusServerClientsTable 1 }

-- {SEQUENCE}
LcsSetupRadiusServerClientsEntry ::= SEQUENCE {
    lcsSetupRadiusServerClientsEntryIpNetwork IpAddress,
    lcsSetupRadiusServerClientsEntryIpNetmask IpAddress,
    lcsSetupRadiusServerClientsEntryProtocols INTEGER,
    lcsSetupRadiusServerClientsEntrySecret DisplayString
}

-- {COLUMN} 1712.2.25.10.2.1.1
lcsSetupRadiusServerClientsEntryIpNetwork OBJECT-TYPE
    SYNTAX     IpAddress
    MAX-ACCESS read-write
    STATUS     current
    DESCRIPTION
        "-- empty --"
    ::= { lcsSetupRadiusServerClientsEntry 1 }

-- {COLUMN} 1712.2.25.10.2.1.3
lcsSetupRadiusServerClientsEntryIpNetmask OBJECT-TYPE
    SYNTAX     IpAddress
    MAX-ACCESS read-write
    STATUS     current
    DESCRIPTION
        "-- empty --"
    ::= { lcsSetupRadiusServerClientsEntry 3 }

-- {COLUMN} 1712.2.25.10.2.1.4
lcsSetupRadiusServerClientsEntryProtocols OBJECT-TYPE
    SYNTAX     INTEGER
      {
        eRadius (0),
        eRadsec (1),
        eAll (255)
      }
    MAX-ACCESS read-write
    STATUS     current
    DESCRIPTION
        "-- empty --"
    ::= { lcsSetupRadiusServerClientsEntry 4 }

-- {COLUMN} 1712.2.25.10.2.1.2
lcsSetupRadiusServerClientsEntrySecret OBJECT-TYPE
    SYNTAX     DisplayString (SIZE(0..64))
    MAX-ACCESS read-write
    STATUS     current
    DESCRIPTION
        "-- empty --"
    ::= { lcsSetupRadiusServerClientsEntry 2 }

-- {TABLE} 1712.2.25.10.16
lcsSetupRadiusServerIpv6ClientsTable OBJECT-TYPE
    SYNTAX     SEQUENCE OF LcsSetupRadiusServerIpv6ClientsEntry
    MAX-ACCESS not-accessible
    STATUS     current
    DESCRIPTION
        "-- empty --"
    ::= { lcsSetupRadiusServer 16 }

-- {ENTRY} 1712.2.25.10.16.1
lcsSetupRadiusServerIpv6ClientsEntry OBJECT-TYPE
    SYNTAX     LcsSetupRadiusServerIpv6ClientsEntry
    MAX-ACCESS not-accessible
    STATUS     current
    DESCRIPTION
        ""
    INDEX {
        lcsSetupRadiusServerIpv6ClientsEntryAddressPrefixlength
    }
    ::= { lcsSetupRadiusServerIpv6ClientsTable 1 }

-- {SEQUENCE}
LcsSetupRadiusServerIpv6ClientsEntry ::= SEQUENCE {
    lcsSetupRadiusServerIpv6ClientsEntryAddressPrefixlength DisplayString,
    lcsSetupRadiusServerIpv6ClientsEntryProtocols INTEGER,
    lcsSetupRadiusServerIpv6ClientsEntrySecret DisplayString
}

-- {COLUMN} 1712.2.25.10.16.1.1
lcsSetupRadiusServerIpv6ClientsEntryAddressPrefixlength OBJECT-TYPE
    SYNTAX     DisplayString (SIZE(0..43))
    MAX-ACCESS read-write
    STATUS     current
    DESCRIPTION
        "-- empty --"
    ::= { lcsSetupRadiusServerIpv6ClientsEntry 1 }

-- {COLUMN} 1712.2.25.10.16.1.4
lcsSetupRadiusServerIpv6ClientsEntryProtocols OBJECT-TYPE
    SYNTAX     INTEGER
      {
        eRadius (0),
        eRadsec (1),
        eAll (255)
      }
    MAX-ACCESS read-write
    STATUS     current
    DESCRIPTION
        "-- empty --"
    ::= { lcsSetupRadiusServerIpv6ClientsEntry 4 }

-- {COLUMN} 1712.2.25.10.16.1.2
lcsSetupRadiusServerIpv6ClientsEntrySecret OBJECT-TYPE
    SYNTAX     DisplayString (SIZE(0..64))
    MAX-ACCESS read-write
    STATUS     current
    DESCRIPTION
        "-- empty --"
    ::= { lcsSetupRadiusServerIpv6ClientsEntry 2 }

-- {TABLE} 1712.2.25.10.7
lcsSetupRadiusServerUsersTable OBJECT-TYPE
    SYNTAX     SEQUENCE OF LcsSetupRadiusServerUsersEntry
    MAX-ACCESS not-accessible
    STATUS     current
    DESCRIPTION
        "-- empty --"
    ::= { lcsSetupRadiusServer 7 }

-- {ENTRY} 1712.2.25.10.7.1
lcsSetupRadiusServerUsersEntry OBJECT-TYPE
    SYNTAX     LcsSetupRadiusServerUsersEntry
    MAX-ACCESS not-accessible
    STATUS     current
    DESCRIPTION
        ""
    INDEX {
        lcsSetupRadiusServerUsersEntryUserName,
        lcsSetupRadiusServerUsersEntryCallingStationIdMask,
        lcsSetupRadiusServerUsersEntryCalledStationIdMask
    }
    ::= { lcsSetupRadiusServerUsersTable 1 }

-- {SEQUENCE}
LcsSetupRadiusServerUsersEntry ::= SEQUENCE {
    lcsSetupRadiusServerUsersEntryUserName DisplayString,
    lcsSetupRadiusServerUsersEntryCallingStationIdMask DisplayString,
    lcsSetupRadiusServerUsersEntryCalledStationIdMask DisplayString,
    lcsSetupRadiusServerUsersEntryActive INTEGER,
    lcsSetupRadiusServerUsersEntryCaseSensitive INTEGER,
    lcsSetupRadiusServerUsersEntryPassword DisplayString,
    lcsSetupRadiusServerUsersEntryMultipleLogin INTEGER,
    lcsSetupRadiusServerUsersEntryMaxConcurrentLogins INTEGER,
    lcsSetupRadiusServerUsersEntryExpiryType BITS,
    lcsSetupRadiusServerUsersEntryAbsExpiry DisplayString,
    lcsSetupRadiusServerUsersEntryRelExpiry INTEGER,
    lcsSetupRadiusServerUsersEntryTimeBudget INTEGER,
    lcsSetupRadiusServerUsersEntryVolumeBudget INTEGER,
    lcsSetupRadiusServerUsersEntryComment DisplayString,
    lcsSetupRadiusServerUsersEntryServiceType INTEGER,
    lcsSetupRadiusServerUsersEntryLimitAuthMethods BITS,
    lcsSetupRadiusServerUsersEntryVlanId INTEGER,
    lcsSetupRadiusServerUsersEntryTxLimit INTEGER,
    lcsSetupRadiusServerUsersEntryRxLimit INTEGER,
    lcsSetupRadiusServerUsersEntryWpaPassphrase DisplayString,
    lcsSetupRadiusServerUsersEntryShellPrivLevel INTEGER
}

-- {COLUMN} 1712.2.25.10.7.1.1
lcsSetupRadiusServerUsersEntryUserName OBJECT-TYPE
    SYNTAX     DisplayString (SIZE(0..48))
    MAX-ACCESS read-write
    STATUS     current
    DESCRIPTION
        "-- empty --"
    ::= { lcsSetupRadiusServerUsersEntry 1 }

-- {COLUMN} 1712.2.25.10.7.1.5
lcsSetupRadiusServerUsersEntryCallingStationIdMask OBJECT-TYPE
    SYNTAX     DisplayString (SIZE(0..64))
    MAX-ACCESS read-write
    STATUS     current
    DESCRIPTION
        "-- empty --"
    ::= { lcsSetupRadiusServerUsersEntry 5 }

-- {COLUMN} 1712.2.25.10.7.1.6
lcsSetupRadiusServerUsersEntryCalledStationIdMask OBJECT-TYPE
    SYNTAX     DisplayString (SIZE(0..64))
    MAX-ACCESS read-write
    STATUS     current
    DESCRIPTION
        "-- empty --"
    ::= { lcsSetupRadiusServerUsersEntry 6 }

-- {COLUMN} 1712.2.25.10.7.1.20
lcsSetupRadiusServerUsersEntryActive OBJECT-TYPE
    SYNTAX     INTEGER
      {
        eNo (0),
        eYes (1)
      }
    MAX-ACCESS read-write
    STATUS     current
    DESCRIPTION
        "-- empty --"
    ::= { lcsSetupRadiusServerUsersEntry 20 }

-- {COLUMN} 1712.2.25.10.7.1.17
lcsSetupRadiusServerUsersEntryCaseSensitive OBJECT-TYPE
    SYNTAX     INTEGER
      {
        eYes (0),
        eNo (1)
      }
    MAX-ACCESS read-write
    STATUS     current
    DESCRIPTION
        "-- empty --"
    ::= { lcsSetupRadiusServerUsersEntry 17 }

-- {COLUMN} 1712.2.25.10.7.1.2
lcsSetupRadiusServerUsersEntryPassword OBJECT-TYPE
    SYNTAX     DisplayString (SIZE(0..32))
    MAX-ACCESS read-write
    STATUS     current
    DESCRIPTION
        "-- empty --"
    ::= { lcsSetupRadiusServerUsersEntry 2 }

-- {COLUMN} 1712.2.25.10.7.1.9
lcsSetupRadiusServerUsersEntryMultipleLogin OBJECT-TYPE
    SYNTAX     INTEGER
      {
        eYes (0),
        eNo (1)
      }
    MAX-ACCESS read-write
    STATUS     current
    DESCRIPTION
        "-- empty --"
    ::= { lcsSetupRadiusServerUsersEntry 9 }

-- {COLUMN} 1712.2.25.10.7.1.19
lcsSetupRadiusServerUsersEntryMaxConcurrentLogins OBJECT-TYPE
    SYNTAX     INTEGER (0..2147483647)
    MAX-ACCESS read-write
    STATUS     current
    DESCRIPTION
        "-- empty --"
    ::= { lcsSetupRadiusServerUsersEntry 19 }

-- {COLUMN} 1712.2.25.10.7.1.13
lcsSetupRadiusServerUsersEntryExpiryType OBJECT-TYPE
    SYNTAX     BITS
      {
        eAbsolute (7),
        eRelative (6)
      }
    MAX-ACCESS read-write
    STATUS     current
    DESCRIPTION
        "-- empty --"
    ::= { lcsSetupRadiusServerUsersEntry 13 }

-- {COLUMN} 1712.2.25.10.7.1.10
lcsSetupRadiusServerUsersEntryAbsExpiry OBJECT-TYPE
    SYNTAX     DisplayString (SIZE(0..21))
    MAX-ACCESS read-write
    STATUS     current
    DESCRIPTION
        "-- empty --"
    ::= { lcsSetupRadiusServerUsersEntry 10 }

-- {COLUMN} 1712.2.25.10.7.1.14
lcsSetupRadiusServerUsersEntryRelExpiry OBJECT-TYPE
    SYNTAX     INTEGER (0..2147483647)
    MAX-ACCESS read-write
    STATUS     current
    DESCRIPTION
        "-- empty --"
    ::= { lcsSetupRadiusServerUsersEntry 14 }

-- {COLUMN} 1712.2.25.10.7.1.11
lcsSetupRadiusServerUsersEntryTimeBudget OBJECT-TYPE
    SYNTAX     INTEGER (0..2147483647)
    MAX-ACCESS read-write
    STATUS     current
    DESCRIPTION
        "-- empty --"
    ::= { lcsSetupRadiusServerUsersEntry 11 }

-- {COLUMN} 1712.2.25.10.7.1.12
lcsSetupRadiusServerUsersEntryVolumeBudget OBJECT-TYPE
    SYNTAX     INTEGER (0..2147483647)
    MAX-ACCESS read-write
    STATUS     current
    DESCRIPTION
        "-- empty --"
    ::= { lcsSetupRadiusServerUsersEntry 12 }

-- {COLUMN} 1712.2.25.10.7.1.15
lcsSetupRadiusServerUsersEntryComment OBJECT-TYPE
    SYNTAX     DisplayString (SIZE(0..251))
    MAX-ACCESS read-write
    STATUS     current
    DESCRIPTION
        "-- empty --"
    ::= { lcsSetupRadiusServerUsersEntry 15 }

-- {COLUMN} 1712.2.25.10.7.1.16
lcsSetupRadiusServerUsersEntryServiceType OBJECT-TYPE
    SYNTAX     INTEGER
      {
        eAny (0),
        eLogin (1),
        eFramed (2),
        eCallbackLogin (3),
        eCallbackFramed (4),
        eOutbound (5),
        eAdministrative (6),
        eNasPrompt (7),
        eAuthOnly (8),
        eCallbackNasPrompt (9),
        eCallCheck (10),
        eCallbackAdministrative (11),
        eVoice (12),
        eFax (13),
        eModemRelay (14),
        eAuthorizeOnly (17),
        eFramedManagement (18)
      }
    MAX-ACCESS read-write
    STATUS     current
    DESCRIPTION
        "-- empty --"
    ::= { lcsSetupRadiusServerUsersEntry 16 }

-- {COLUMN} 1712.2.25.10.7.1.3
lcsSetupRadiusServerUsersEntryLimitAuthMethods OBJECT-TYPE
    SYNTAX     BITS
      {
        ePap (15),
        eChap (14),
        eMschap (13),
        eMschapv2 (12),
        eEap (11),
        eAll (0)
      }
    MAX-ACCESS read-write
    STATUS     current
    DESCRIPTION
        "-- empty --"
    ::= { lcsSetupRadiusServerUsersEntry 3 }

-- {COLUMN} 1712.2.25.10.7.1.4
lcsSetupRadiusServerUsersEntryVlanId OBJECT-TYPE
    SYNTAX     INTEGER (0..65535)
    MAX-ACCESS read-write
    STATUS     current
    DESCRIPTION
        "-- empty --"
    ::= { lcsSetupRadiusServerUsersEntry 4 }

-- {COLUMN} 1712.2.25.10.7.1.7
lcsSetupRadiusServerUsersEntryTxLimit OBJECT-TYPE
    SYNTAX     INTEGER (0..2147483647)
    MAX-ACCESS read-write
    STATUS     current
    DESCRIPTION
        "-- empty --"
    ::= { lcsSetupRadiusServerUsersEntry 7 }

-- {COLUMN} 1712.2.25.10.7.1.8
lcsSetupRadiusServerUsersEntryRxLimit OBJECT-TYPE
    SYNTAX     INTEGER (0..2147483647)
    MAX-ACCESS read-write
    STATUS     current
    DESCRIPTION
        "-- empty --"
    ::= { lcsSetupRadiusServerUsersEntry 8 }

-- {COLUMN} 1712.2.25.10.7.1.18
lcsSetupRadiusServerUsersEntryWpaPassphrase OBJECT-TYPE
    SYNTAX     DisplayString (SIZE(0..63))
    MAX-ACCESS read-write
    STATUS     current
    DESCRIPTION
        "-- empty --"
    ::= { lcsSetupRadiusServerUsersEntry 18 }

-- {COLUMN} 1712.2.25.10.7.1.21
lcsSetupRadiusServerUsersEntryShellPrivLevel OBJECT-TYPE
    SYNTAX     INTEGER (0..2147483647)
    MAX-ACCESS read-write
    STATUS     current
    DESCRIPTION
        "-- empty --"
    ::= { lcsSetupRadiusServerUsersEntry 21 }

-- {TABLE} 1712.2.25.10.3
lcsSetupRadiusServerForwardServersTable OBJECT-TYPE
    SYNTAX     SEQUENCE OF LcsSetupRadiusServerForwardServersEntry
    MAX-ACCESS not-accessible
    STATUS     current
    DESCRIPTION
        "-- empty --"
    ::= { lcsSetupRadiusServer 3 }

-- {ENTRY} 1712.2.25.10.3.1
lcsSetupRadiusServerForwardServersEntry OBJECT-TYPE
    SYNTAX     LcsSetupRadiusServerForwardServersEntry
    MAX-ACCESS not-accessible
    STATUS     current
    DESCRIPTION
        ""
    INDEX {
        lcsSetupRadiusServerForwardServersEntryRealm
    }
    ::= { lcsSetupRadiusServerForwardServersTable 1 }

-- {SEQUENCE}
LcsSetupRadiusServerForwardServersEntry ::= SEQUENCE {
    lcsSetupRadiusServerForwardServersEntryRealm DisplayString,
    lcsSetupRadiusServerForwardServersEntryHostname DisplayString,
    lcsSetupRadiusServerForwardServersEntryPort INTEGER,
    lcsSetupRadiusServerForwardServersEntrySecret DisplayString,
    lcsSetupRadiusServerForwardServersEntryLoopbackAddr DisplayString,
    lcsSetupRadiusServerForwardServersEntryProtocol INTEGER,
    lcsSetupRadiusServerForwardServersEntryAccntHostname DisplayString,
    lcsSetupRadiusServerForwardServersEntryAccntPort INTEGER,
    lcsSetupRadiusServerForwardServersEntryAccntSecret DisplayString,
    lcsSetupRadiusServerForwardServersEntryAccntLoopbackAddr DisplayString,
    lcsSetupRadiusServerForwardServersEntryAccntProtocol INTEGER,
    lcsSetupRadiusServerForwardServersEntryBackup DisplayString
}

-- {COLUMN} 1712.2.25.10.3.1.1
lcsSetupRadiusServerForwardServersEntryRealm OBJECT-TYPE
    SYNTAX     DisplayString (SIZE(0..64))
    MAX-ACCESS read-write
    STATUS     current
    DESCRIPTION
        "-- empty --"
    ::= { lcsSetupRadiusServerForwardServersEntry 1 }

-- {COLUMN} 1712.2.25.10.3.1.13
lcsSetupRadiusServerForwardServersEntryHostname OBJECT-TYPE
    SYNTAX     DisplayString (SIZE(0..64))
    MAX-ACCESS read-write
    STATUS     current
    DESCRIPTION
        "-- empty --"
    ::= { lcsSetupRadiusServerForwardServersEntry 13 }

-- {COLUMN} 1712.2.25.10.3.1.3
lcsSetupRadiusServerForwardServersEntryPort OBJECT-TYPE
    SYNTAX     INTEGER (0..65535)
    MAX-ACCESS read-write
    STATUS     current
    DESCRIPTION
        "-- empty --"
    ::= { lcsSetupRadiusServerForwardServersEntry 3 }

-- {COLUMN} 1712.2.25.10.3.1.4
lcsSetupRadiusServerForwardServersEntrySecret OBJECT-TYPE
    SYNTAX     DisplayString (SIZE(0..64))
    MAX-ACCESS read-write
    STATUS     current
    DESCRIPTION
        "-- empty --"
    ::= { lcsSetupRadiusServerForwardServersEntry 4 }

-- {COLUMN} 1712.2.25.10.3.1.6
lcsSetupRadiusServerForwardServersEntryLoopbackAddr OBJECT-TYPE
    SYNTAX     DisplayString (SIZE(0..16))
    MAX-ACCESS read-write
    STATUS     current
    DESCRIPTION
        "-- empty --"
    ::= { lcsSetupRadiusServerForwardServersEntry 6 }

-- {COLUMN} 1712.2.25.10.3.1.7
lcsSetupRadiusServerForwardServersEntryProtocol OBJECT-TYPE
    SYNTAX     INTEGER
      {
        eRadius (0),
        eRadsec (1)
      }
    MAX-ACCESS read-write
    STATUS     current
    DESCRIPTION
        "-- empty --"
    ::= { lcsSetupRadiusServerForwardServersEntry 7 }

-- {COLUMN} 1712.2.25.10.3.1.14
lcsSetupRadiusServerForwardServersEntryAccntHostname OBJECT-TYPE
    SYNTAX     DisplayString (SIZE(0..64))
    MAX-ACCESS read-write
    STATUS     current
    DESCRIPTION
        "-- empty --"
    ::= { lcsSetupRadiusServerForwardServersEntry 14 }

-- {COLUMN} 1712.2.25.10.3.1.9
lcsSetupRadiusServerForwardServersEntryAccntPort OBJECT-TYPE
    SYNTAX     INTEGER (0..65535)
    MAX-ACCESS read-write
    STATUS     current
    DESCRIPTION
        "-- empty --"
    ::= { lcsSetupRadiusServerForwardServersEntry 9 }

-- {COLUMN} 1712.2.25.10.3.1.10
lcsSetupRadiusServerForwardServersEntryAccntSecret OBJECT-TYPE
    SYNTAX     DisplayString (SIZE(0..64))
    MAX-ACCESS read-write
    STATUS     current
    DESCRIPTION
        "-- empty --"
    ::= { lcsSetupRadiusServerForwardServersEntry 10 }

-- {COLUMN} 1712.2.25.10.3.1.11
lcsSetupRadiusServerForwardServersEntryAccntLoopbackAddr OBJECT-TYPE
    SYNTAX     DisplayString (SIZE(0..16))
    MAX-ACCESS read-write
    STATUS     current
    DESCRIPTION
        "-- empty --"
    ::= { lcsSetupRadiusServerForwardServersEntry 11 }

-- {COLUMN} 1712.2.25.10.3.1.12
lcsSetupRadiusServerForwardServersEntryAccntProtocol OBJECT-TYPE
    SYNTAX     INTEGER
      {
        eRadius (0),
        eRadsec (1)
      }
    MAX-ACCESS read-write
    STATUS     current
    DESCRIPTION
        "-- empty --"
    ::= { lcsSetupRadiusServerForwardServersEntry 12 }

-- {COLUMN} 1712.2.25.10.3.1.5
lcsSetupRadiusServerForwardServersEntryBackup OBJECT-TYPE
    SYNTAX     DisplayString (SIZE(0..64))
    MAX-ACCESS read-write
    STATUS     current
    DESCRIPTION
        "-- empty --"
    ::= { lcsSetupRadiusServerForwardServersEntry 5 }

-- {SCALAR} 1712.2.25.10.5
lcsSetupRadiusServerDefaultRealm OBJECT-TYPE
    SYNTAX     DisplayString (SIZE(0..64))
    MAX-ACCESS read-write
    STATUS     current
    DESCRIPTION
        "-- empty --"
    ::= { lcsSetupRadiusServer 5 }

-- {SCALAR} 1712.2.25.10.6
lcsSetupRadiusServerEmptyRealm OBJECT-TYPE
    SYNTAX     DisplayString (SIZE(0..64))
    MAX-ACCESS read-write
    STATUS     current
    DESCRIPTION
        "-- empty --"
    ::= { lcsSetupRadiusServer 6 }

-- {SCALAR} 1712.2.25.10.12
lcsSetupRadiusServerAccountingInterimInterval OBJECT-TYPE
    SYNTAX     INTEGER (0..2147483647)
    MAX-ACCESS read-write
    STATUS     current
    DESCRIPTION
        "-- empty --"
    ::= { lcsSetupRadiusServer 12 }

-- {SCALAR} 1712.2.25.10.14
lcsSetupRadiusServerAutoCleanupUserTable OBJECT-TYPE
    SYNTAX     INTEGER
      {
        eNo (0),
        eYes (1)
      }
    MAX-ACCESS read-write
    STATUS     current
    DESCRIPTION
        "-- empty --"
    ::= { lcsSetupRadiusServer 14 }

-- {OID} 1712.2.25.10.10
lcsSetupRadiusServerEap OBJECT IDENTIFIER ::= { lcsSetupRadiusServer 10 }

-- {SCALAR} 1712.2.25.10.10.7
lcsSetupRadiusServerEapDefaultMethod OBJECT-TYPE
    SYNTAX     INTEGER
      {
        eMd5 (4),
        eGtc (6),
        eMschapv2 (26),
        eTls (13),
        eTtls (21),
        ePeap (25),
        eSim (18)
      }
    MAX-ACCESS read-write
    STATUS     current
    DESCRIPTION
        "-- empty --"
    ::= { lcsSetupRadiusServerEap 7 }

-- {SCALAR} 1712.2.25.10.10.10
lcsSetupRadiusServerEapMschapv2BackendServer OBJECT-TYPE
    SYNTAX     DisplayString (SIZE(0..64))
    MAX-ACCESS read-write
    STATUS     current
    DESCRIPTION
        "-- empty --"
    ::= { lcsSetupRadiusServerEap 10 }

-- {SCALAR} 1712.2.25.10.10.1
lcsSetupRadiusServerEapTunnelServer OBJECT-TYPE
    SYNTAX     DisplayString (SIZE(0..64))
    MAX-ACCESS read-write
    STATUS     current
    DESCRIPTION
        "-- empty --"
    ::= { lcsSetupRadiusServerEap 1 }

-- {SCALAR} 1712.2.25.10.10.5
lcsSetupRadiusServerEapTtlsDefaultTunnelMethod OBJECT-TYPE
    SYNTAX     INTEGER
      {
        eNone (0),
        eMd5 (4),
        eGtc (6),
        eMschapv2 (26)
      }
    MAX-ACCESS read-write
    STATUS     current
    DESCRIPTION
        "-- empty --"
    ::= { lcsSetupRadiusServerEap 5 }

-- {SCALAR} 1712.2.25.10.10.6
lcsSetupRadiusServerEapPeapDefaultTunnelMethod OBJECT-TYPE
    SYNTAX     INTEGER
      {
        eNone (0),
        eMd5 (4),
        eGtc (6),
        eMschapv2 (26)
      }
    MAX-ACCESS read-write
    STATUS     current
    DESCRIPTION
        "-- empty --"
    ::= { lcsSetupRadiusServerEap 6 }

-- {OID} 1712.2.25.10.10.19
lcsSetupRadiusServerEapEapTls OBJECT IDENTIFIER ::= { lcsSetupRadiusServerEap 19 }

-- {SCALAR} 1712.2.25.10.10.19.10
lcsSetupRadiusServerEapEapTlsCheckUsername OBJECT-TYPE
    SYNTAX     INTEGER
      {
        eNo (0),
        eYes (1)
      }
    MAX-ACCESS read-write
    STATUS     current
    DESCRIPTION
        "-- empty --"
    ::= { lcsSetupRadiusServerEapEapTls 10 }

-- {SCALAR} 1712.2.25.10.10.19.3
lcsSetupRadiusServerEapEapTlsKeyexAlgorithms OBJECT-TYPE
    SYNTAX     BITS
      {
        eRsa (31),
        eDhe (29),
        eEcdhe (27)
      }
    MAX-ACCESS read-write
    STATUS     current
    DESCRIPTION
        "-- empty --"
    ::= { lcsSetupRadiusServerEapEapTls 3 }

-- {SCALAR} 1712.2.25.10.10.19.4
lcsSetupRadiusServerEapEapTlsCryptoAlgorithms OBJECT-TYPE
    SYNTAX     BITS
      {
        eRc440 (29),
        eRc456 (28),
        eRc4128 (27),
        eDes40 (26),
        eDes (25),
        e3des (24),
        eAes128 (23),
        eAes256 (22),
        eAesgcm128 (21),
        eAesgcm256 (20)
      }
    MAX-ACCESS read-write
    STATUS     current
    DESCRIPTION
        "-- empty --"
    ::= { lcsSetupRadiusServerEapEapTls 4 }

-- {SCALAR} 1712.2.25.10.10.19.5
lcsSetupRadiusServerEapEapTlsHashAlgorithms OBJECT-TYPE
    SYNTAX     BITS
      {
        eMd5 (30),
        eSha1 (29),
        eSha2256 (27),
        eSha2384 (26)
      }
    MAX-ACCESS read-write
    STATUS     current
    DESCRIPTION
        "-- empty --"
    ::= { lcsSetupRadiusServerEapEapTls 5 }

-- {SCALAR} 1712.2.25.10.10.3
lcsSetupRadiusServerEapReauthPeriod OBJECT-TYPE
    SYNTAX     INTEGER (0..2147483647)
    MAX-ACCESS read-write
    STATUS     current
    DESCRIPTION
        "-- empty --"
    ::= { lcsSetupRadiusServerEap 3 }

-- {SCALAR} 1712.2.25.10.10.4
lcsSetupRadiusServerEapRetransmitTimeout OBJECT-TYPE
    SYNTAX     INTEGER (0..2147483647)
    MAX-ACCESS read-write
    STATUS     current
    DESCRIPTION
        "-- empty --"
    ::= { lcsSetupRadiusServerEap 4 }

-- {SCALAR} 1712.2.25.10.10.8
lcsSetupRadiusServerEapDefaultMtu OBJECT-TYPE
    SYNTAX     INTEGER (0..65535)
    MAX-ACCESS read-write
    STATUS     current
    DESCRIPTION
        "-- empty --"
    ::= { lcsSetupRadiusServerEap 8 }

-- {TABLE} 1712.2.25.10.10.9
lcsSetupRadiusServerEapAllowMethodsTable OBJECT-TYPE
    SYNTAX     SEQUENCE OF LcsSetupRadiusServerEapAllowMethodsEntry
    MAX-ACCESS not-accessible
    STATUS     current
    DESCRIPTION
        "-- empty --"
    ::= { lcsSetupRadiusServerEap 9 }

-- {ENTRY} 1712.2.25.10.10.9.1
lcsSetupRadiusServerEapAllowMethodsEntry OBJECT-TYPE
    SYNTAX     LcsSetupRadiusServerEapAllowMethodsEntry
    MAX-ACCESS not-accessible
    STATUS     current
    DESCRIPTION
        ""
    INDEX {
        lcsSetupRadiusServerEapAllowMethodsEntryMethod
    }
    ::= { lcsSetupRadiusServerEapAllowMethodsTable 1 }

-- {SEQUENCE}
LcsSetupRadiusServerEapAllowMethodsEntry ::= SEQUENCE {
    lcsSetupRadiusServerEapAllowMethodsEntryMethod INTEGER,
    lcsSetupRadiusServerEapAllowMethodsEntryAllow INTEGER
}

-- {COLUMN} 1712.2.25.10.10.9.1.1
lcsSetupRadiusServerEapAllowMethodsEntryMethod OBJECT-TYPE
    SYNTAX     INTEGER
      {
        eMd5 (4),
        eGtc (6),
        eMschapv2 (26),
        eTls (13),
        eTtls (21),
        ePeap (25),
        eSim (18)
      }
    MAX-ACCESS read-write
    STATUS     current
    DESCRIPTION
        "-- empty --"
    ::= { lcsSetupRadiusServerEapAllowMethodsEntry 1 }

-- {COLUMN} 1712.2.25.10.10.9.1.2
lcsSetupRadiusServerEapAllowMethodsEntryAllow OBJECT-TYPE
    SYNTAX     INTEGER
      {
        eOff (0),
        eOn (1),
        eInternalOnly (2)
      }
    MAX-ACCESS read-write
    STATUS     current
    DESCRIPTION
        "-- empty --"
    ::= { lcsSetupRadiusServerEapAllowMethodsEntry 2 }

-- {OID} 1712.2.25.10.10.18
lcsSetupRadiusServerEapEapSim OBJECT IDENTIFIER ::= { lcsSetupRadiusServerEap 18 }

-- {TABLE} 1712.2.25.10.10.18.1
lcsSetupRadiusServerEapEapSimCardKeysTable OBJECT-TYPE
    SYNTAX     SEQUENCE OF LcsSetupRadiusServerEapEapSimCardKeysEntry
    MAX-ACCESS not-accessible
    STATUS     current
    DESCRIPTION
        "-- empty --"
    ::= { lcsSetupRadiusServerEapEapSim 1 }

-- {ENTRY} 1712.2.25.10.10.18.1.1
lcsSetupRadiusServerEapEapSimCardKeysEntry OBJECT-TYPE
    SYNTAX     LcsSetupRadiusServerEapEapSimCardKeysEntry
    MAX-ACCESS not-accessible
    STATUS     current
    DESCRIPTION
        ""
    INDEX {
        lcsSetupRadiusServerEapEapSimCardKeysEntryUserName,
        lcsSetupRadiusServerEapEapSimCardKeysEntryCallingStationIdMask,
        lcsSetupRadiusServerEapEapSimCardKeysEntryCalledStationIdMask
    }
    ::= { lcsSetupRadiusServerEapEapSimCardKeysTable 1 }

-- {SEQUENCE}
LcsSetupRadiusServerEapEapSimCardKeysEntry ::= SEQUENCE {
    lcsSetupRadiusServerEapEapSimCardKeysEntryUserName DisplayString,
    lcsSetupRadiusServerEapEapSimCardKeysEntryCallingStationIdMask DisplayString,
    lcsSetupRadiusServerEapEapSimCardKeysEntryCalledStationIdMask DisplayString,
    lcsSetupRadiusServerEapEapSimCardKeysEntryRand1 OCTET STRING,
    lcsSetupRadiusServerEapEapSimCardKeysEntrySres1 OCTET STRING,
    lcsSetupRadiusServerEapEapSimCardKeysEntryKc1 OCTET STRING,
    lcsSetupRadiusServerEapEapSimCardKeysEntryRand2 OCTET STRING,
    lcsSetupRadiusServerEapEapSimCardKeysEntrySres2 OCTET STRING,
    lcsSetupRadiusServerEapEapSimCardKeysEntryKc2 OCTET STRING,
    lcsSetupRadiusServerEapEapSimCardKeysEntryRand3 OCTET STRING,
    lcsSetupRadiusServerEapEapSimCardKeysEntrySres3 OCTET STRING,
    lcsSetupRadiusServerEapEapSimCardKeysEntryKc3 OCTET STRING
}

-- {COLUMN} 1712.2.25.10.10.18.1.1.1
lcsSetupRadiusServerEapEapSimCardKeysEntryUserName OBJECT-TYPE
    SYNTAX     DisplayString (SIZE(0..48))
    MAX-ACCESS read-write
    STATUS     current
    DESCRIPTION
        "-- empty --"
    ::= { lcsSetupRadiusServerEapEapSimCardKeysEntry 1 }

-- {COLUMN} 1712.2.25.10.10.18.1.1.5
lcsSetupRadiusServerEapEapSimCardKeysEntryCallingStationIdMask OBJECT-TYPE
    SYNTAX     DisplayString (SIZE(0..64))
    MAX-ACCESS read-write
    STATUS     current
    DESCRIPTION
        "-- empty --"
    ::= { lcsSetupRadiusServerEapEapSimCardKeysEntry 5 }

-- {COLUMN} 1712.2.25.10.10.18.1.1.6
lcsSetupRadiusServerEapEapSimCardKeysEntryCalledStationIdMask OBJECT-TYPE
    SYNTAX     DisplayString (SIZE(0..64))
    MAX-ACCESS read-write
    STATUS     current
    DESCRIPTION
        "-- empty --"
    ::= { lcsSetupRadiusServerEapEapSimCardKeysEntry 6 }

-- {COLUMN} 1712.2.25.10.10.18.1.1.7
lcsSetupRadiusServerEapEapSimCardKeysEntryRand1 OBJECT-TYPE
    SYNTAX     OCTET STRING
    MAX-ACCESS read-write
    STATUS     current
    DESCRIPTION
        "-- empty --"
    ::= { lcsSetupRadiusServerEapEapSimCardKeysEntry 7 }

-- {COLUMN} 1712.2.25.10.10.18.1.1.8
lcsSetupRadiusServerEapEapSimCardKeysEntrySres1 OBJECT-TYPE
    SYNTAX     OCTET STRING
    MAX-ACCESS read-write
    STATUS     current
    DESCRIPTION
        "-- empty --"
    ::= { lcsSetupRadiusServerEapEapSimCardKeysEntry 8 }

-- {COLUMN} 1712.2.25.10.10.18.1.1.9
lcsSetupRadiusServerEapEapSimCardKeysEntryKc1 OBJECT-TYPE
    SYNTAX     OCTET STRING
    MAX-ACCESS read-write
    STATUS     current
    DESCRIPTION
        "-- empty --"
    ::= { lcsSetupRadiusServerEapEapSimCardKeysEntry 9 }

-- {COLUMN} 1712.2.25.10.10.18.1.1.10
lcsSetupRadiusServerEapEapSimCardKeysEntryRand2 OBJECT-TYPE
    SYNTAX     OCTET STRING
    MAX-ACCESS read-write
    STATUS     current
    DESCRIPTION
        "-- empty --"
    ::= { lcsSetupRadiusServerEapEapSimCardKeysEntry 10 }

-- {COLUMN} 1712.2.25.10.10.18.1.1.11
lcsSetupRadiusServerEapEapSimCardKeysEntrySres2 OBJECT-TYPE
    SYNTAX     OCTET STRING
    MAX-ACCESS read-write
    STATUS     current
    DESCRIPTION
        "-- empty --"
    ::= { lcsSetupRadiusServerEapEapSimCardKeysEntry 11 }

-- {COLUMN} 1712.2.25.10.10.18.1.1.12
lcsSetupRadiusServerEapEapSimCardKeysEntryKc2 OBJECT-TYPE
    SYNTAX     OCTET STRING
    MAX-ACCESS read-write
    STATUS     current
    DESCRIPTION
        "-- empty --"
    ::= { lcsSetupRadiusServerEapEapSimCardKeysEntry 12 }

-- {COLUMN} 1712.2.25.10.10.18.1.1.13
lcsSetupRadiusServerEapEapSimCardKeysEntryRand3 OBJECT-TYPE
    SYNTAX     OCTET STRING
    MAX-ACCESS read-write
    STATUS     current
    DESCRIPTION
        "-- empty --"
    ::= { lcsSetupRadiusServerEapEapSimCardKeysEntry 13 }

-- {COLUMN} 1712.2.25.10.10.18.1.1.14
lcsSetupRadiusServerEapEapSimCardKeysEntrySres3 OBJECT-TYPE
    SYNTAX     OCTET STRING
    MAX-ACCESS read-write
    STATUS     current
    DESCRIPTION
        "-- empty --"
    ::= { lcsSetupRadiusServerEapEapSimCardKeysEntry 14 }

-- {COLUMN} 1712.2.25.10.10.18.1.1.15
lcsSetupRadiusServerEapEapSimCardKeysEntryKc3 OBJECT-TYPE
    SYNTAX     OCTET STRING
    MAX-ACCESS read-write
    STATUS     current
    DESCRIPTION
        "-- empty --"
    ::= { lcsSetupRadiusServerEapEapSimCardKeysEntry 15 }

-- {OID} 1712.2.25.20
lcsSetupRadiusRadsec OBJECT IDENTIFIER ::= { lcsSetupRadius 20 }

-- {SCALAR} 1712.2.25.20.1
lcsSetupRadiusRadsecVersions OBJECT-TYPE
    SYNTAX     BITS
      {
        eSslv3 (31),
        eTlsv1 (30),
        eTlsv11 (29),
        eTlsv12 (28)
      }
    MAX-ACCESS read-write
    STATUS     current
    DESCRIPTION
        "-- empty --"
    ::= { lcsSetupRadiusRadsec 1 }

-- {SCALAR} 1712.2.25.20.2
lcsSetupRadiusRadsecKeyexAlgorithms OBJECT-TYPE
    SYNTAX     BITS
      {
        eRsa (31),
        eDhe (29),
        eEcdhe (27)
      }
    MAX-ACCESS read-write
    STATUS     current
    DESCRIPTION
        "-- empty --"
    ::= { lcsSetupRadiusRadsec 2 }

-- {SCALAR} 1712.2.25.20.3
lcsSetupRadiusRadsecCryptoAlgorithms OBJECT-TYPE
    SYNTAX     BITS
      {
        eRc440 (29),
        eRc456 (28),
        eRc4128 (27),
        eDes40 (26),
        eDes (25),
        e3des (24),
        eAes128 (23),
        eAes256 (22),
        eAesgcm128 (21),
        eAesgcm256 (20)
      }
    MAX-ACCESS read-write
    STATUS     current
    DESCRIPTION
        "-- empty --"
    ::= { lcsSetupRadiusRadsec 3 }

-- {SCALAR} 1712.2.25.20.4
lcsSetupRadiusRadsecHashAlgorithms OBJECT-TYPE
    SYNTAX     BITS
      {
        eMd5 (30),
        eSha1 (29),
        eSha2256 (27),
        eSha2384 (26)
      }
    MAX-ACCESS read-write
    STATUS     current
    DESCRIPTION
        "-- empty --"
    ::= { lcsSetupRadiusRadsec 4 }

-- {OID} 1712.2.26
lcsSetupNtp OBJECT IDENTIFIER ::= { lcsSetup 26 }

-- {SCALAR} 1712.2.26.2
lcsSetupNtpServerOperating OBJECT-TYPE
    SYNTAX     INTEGER
      {
        eNo (0),
        eYes (1)
      }
    MAX-ACCESS read-write
    STATUS     current
    DESCRIPTION
        "-- empty --"
    ::= { lcsSetupNtp 2 }

-- {SCALAR} 1712.2.26.3
lcsSetupNtpBcMode OBJECT-TYPE
    SYNTAX     INTEGER
      {
        eNo (0),
        eYes (1)
      }
    MAX-ACCESS read-write
    STATUS     current
    DESCRIPTION
        "-- empty --"
    ::= { lcsSetupNtp 3 }

-- {SCALAR} 1712.2.26.4
lcsSetupNtpBcInterval OBJECT-TYPE
    SYNTAX     INTEGER (0..65535)
    MAX-ACCESS read-write
    STATUS     current
    DESCRIPTION
        "-- empty --"
    ::= { lcsSetupNtp 4 }

-- {SCALAR} 1712.2.26.7
lcsSetupNtpRqInterval OBJECT-TYPE
    SYNTAX     INTEGER (0..2147483647)
    MAX-ACCESS read-write
    STATUS     current
    DESCRIPTION
        "-- empty --"
    ::= { lcsSetupNtp 7 }

-- {SCALAR} 1712.2.26.12
lcsSetupNtpRqTries OBJECT-TYPE
    SYNTAX     INTEGER (0..2147483647)
    MAX-ACCESS read-write
    STATUS     current
    DESCRIPTION
        "-- empty --"
    ::= { lcsSetupNtp 12 }

-- {TABLE} 1712.2.26.11
lcsSetupNtpRqAddressTable OBJECT-TYPE
    SYNTAX     SEQUENCE OF LcsSetupNtpRqAddressEntry
    MAX-ACCESS not-accessible
    STATUS     current
    DESCRIPTION
        "-- empty --"
    ::= { lcsSetupNtp 11 }

-- {ENTRY} 1712.2.26.11.1
lcsSetupNtpRqAddressEntry OBJECT-TYPE
    SYNTAX     LcsSetupNtpRqAddressEntry
    MAX-ACCESS not-accessible
    STATUS     current
    DESCRIPTION
        ""
    INDEX {
        lcsSetupNtpRqAddressEntryRqAddress
    }
    ::= { lcsSetupNtpRqAddressTable 1 }

-- {SEQUENCE}
LcsSetupNtpRqAddressEntry ::= SEQUENCE {
    lcsSetupNtpRqAddressEntryRqAddress DisplayString,
    lcsSetupNtpRqAddressEntryLoopbackAddr DisplayString
}

-- {COLUMN} 1712.2.26.11.1.1
lcsSetupNtpRqAddressEntryRqAddress OBJECT-TYPE
    SYNTAX     DisplayString (SIZE(0..31))
    MAX-ACCESS read-write
    STATUS     current
    DESCRIPTION
        "-- empty --"
    ::= { lcsSetupNtpRqAddressEntry 1 }

-- {COLUMN} 1712.2.26.11.1.2
lcsSetupNtpRqAddressEntryLoopbackAddr OBJECT-TYPE
    SYNTAX     DisplayString (SIZE(0..16))
    MAX-ACCESS read-write
    STATUS     current
    DESCRIPTION
        "-- empty --"
    ::= { lcsSetupNtpRqAddressEntry 2 }

-- {OID} 1712.2.27
lcsSetupMail OBJECT IDENTIFIER ::= { lcsSetup 27 }

-- {SCALAR} 1712.2.27.1
lcsSetupMailSmtpServer OBJECT-TYPE
    SYNTAX     DisplayString (SIZE(0..31))
    MAX-ACCESS read-write
    STATUS     current
    DESCRIPTION
        "-- empty --"
    ::= { lcsSetupMail 1 }

-- {SCALAR} 1712.2.27.2
lcsSetupMailSmtpPort OBJECT-TYPE
    SYNTAX     INTEGER (0..65535)
    MAX-ACCESS read-write
    STATUS     current
    DESCRIPTION
        "-- empty --"
    ::= { lcsSetupMail 2 }

-- {SCALAR} 1712.2.27.12
lcsSetupMailSmtpUseTls OBJECT-TYPE
    SYNTAX     INTEGER
      {
        eYes (1),
        eNo (0),
        ePreferred (2),
        eRequired (3)
      }
    MAX-ACCESS read-write
    STATUS     current
    DESCRIPTION
        "-- empty --"
    ::= { lcsSetupMail 12 }

-- {SCALAR} 1712.2.27.13
lcsSetupMailSmtpAuthentication OBJECT-TYPE
    SYNTAX     INTEGER
      {
        eNone (0),
        ePlainTextPreferred (1),
        eEncrypted (2),
        ePreferredEncrypted (3)
      }
    MAX-ACCESS read-write
    STATUS     current
    DESCRIPTION
        "-- empty --"
    ::= { lcsSetupMail 13 }

-- {SCALAR} 1712.2.27.3
lcsSetupMailPop3Server OBJECT-TYPE
    SYNTAX     DisplayString (SIZE(0..31))
    MAX-ACCESS read-write
    STATUS     current
    DESCRIPTION
        "-- empty --"
    ::= { lcsSetupMail 3 }

-- {SCALAR} 1712.2.27.4
lcsSetupMailPop3Port OBJECT-TYPE
    SYNTAX     INTEGER (0..65535)
    MAX-ACCESS read-write
    STATUS     current
    DESCRIPTION
        "-- empty --"
    ::= { lcsSetupMail 4 }

-- {SCALAR} 1712.2.27.11
lcsSetupMailLoopbackAddr OBJECT-TYPE
    SYNTAX     DisplayString (SIZE(0..16))
    MAX-ACCESS read-write
    STATUS     current
    DESCRIPTION
        "-- empty --"
    ::= { lcsSetupMail 11 }

-- {SCALAR} 1712.2.27.5
lcsSetupMailUserName OBJECT-TYPE
    SYNTAX     DisplayString (SIZE(0..63))
    MAX-ACCESS read-write
    STATUS     current
    DESCRIPTION
        "-- empty --"
    ::= { lcsSetupMail 5 }

-- {SCALAR} 1712.2.27.6
lcsSetupMailPassword OBJECT-TYPE
    SYNTAX     DisplayString (SIZE(0..31))
    MAX-ACCESS read-write
    STATUS     current
    DESCRIPTION
        "-- empty --"
    ::= { lcsSetupMail 6 }

-- {SCALAR} 1712.2.27.7
lcsSetupMailEMailSender OBJECT-TYPE
    SYNTAX     DisplayString (SIZE(0..63))
    MAX-ACCESS read-write
    STATUS     current
    DESCRIPTION
        "-- empty --"
    ::= { lcsSetupMail 7 }

-- {SCALAR} 1712.2.27.8
lcsSetupMailSendAgainMin OBJECT-TYPE
    SYNTAX     INTEGER (0..65535)
    MAX-ACCESS read-write
    STATUS     current
    DESCRIPTION
        "-- empty --"
    ::= { lcsSetupMail 8 }

-- {SCALAR} 1712.2.27.9
lcsSetupMailHoldTimeHrs OBJECT-TYPE
    SYNTAX     INTEGER (0..65535)
    MAX-ACCESS read-write
    STATUS     current
    DESCRIPTION
        "-- empty --"
    ::= { lcsSetupMail 9 }

-- {SCALAR} 1712.2.27.10
lcsSetupMailBuffers OBJECT-TYPE
    SYNTAX     INTEGER (0..65535)
    MAX-ACCESS read-write
    STATUS     current
    DESCRIPTION
        "-- empty --"
    ::= { lcsSetupMail 10 }

-- {OID} 1712.2.31
lcsSetupPppoeServer OBJECT IDENTIFIER ::= { lcsSetup 31 }

-- {SCALAR} 1712.2.31.1
lcsSetupPppoeServerOperating OBJECT-TYPE
    SYNTAX     INTEGER
      {
        eNo (0),
        eYes (1)
      }
    MAX-ACCESS read-write
    STATUS     current
    DESCRIPTION
        "-- empty --"
    ::= { lcsSetupPppoeServer 1 }

-- {TABLE} 1712.2.31.2
lcsSetupPppoeServerNameListTable OBJECT-TYPE
    SYNTAX     SEQUENCE OF LcsSetupPppoeServerNameListEntry
    MAX-ACCESS not-accessible
    STATUS     current
    DESCRIPTION
        "-- empty --"
    ::= { lcsSetupPppoeServer 2 }

-- {ENTRY} 1712.2.31.2.1
lcsSetupPppoeServerNameListEntry OBJECT-TYPE
    SYNTAX     LcsSetupPppoeServerNameListEntry
    MAX-ACCESS not-accessible
    STATUS     current
    DESCRIPTION
        ""
    INDEX {
        lcsSetupPppoeServerNameListEntryPeer
    }
    ::= { lcsSetupPppoeServerNameListTable 1 }

-- {SEQUENCE}
LcsSetupPppoeServerNameListEntry ::= SEQUENCE {
    lcsSetupPppoeServerNameListEntryPeer DisplayString,
    lcsSetupPppoeServerNameListEntryShTime INTEGER,
    lcsSetupPppoeServerNameListEntryMacAddress DisplayString
}

-- {COLUMN} 1712.2.31.2.1.1
lcsSetupPppoeServerNameListEntryPeer OBJECT-TYPE
    SYNTAX     DisplayString (SIZE(0..16))
    MAX-ACCESS read-write
    STATUS     current
    DESCRIPTION
        "-- empty --"
    ::= { lcsSetupPppoeServerNameListEntry 1 }

-- {COLUMN} 1712.2.31.2.1.2
lcsSetupPppoeServerNameListEntryShTime OBJECT-TYPE
    SYNTAX     INTEGER (0..65535)
    MAX-ACCESS read-write
    STATUS     current
    DESCRIPTION
        "-- empty --"
    ::= { lcsSetupPppoeServerNameListEntry 2 }

-- {COLUMN} 1712.2.31.2.1.3
lcsSetupPppoeServerNameListEntryMacAddress OBJECT-TYPE
    SYNTAX     DisplayString (SIZE(0..12))
    MAX-ACCESS read-write
    STATUS     current
    DESCRIPTION
        "-- empty --"
    ::= { lcsSetupPppoeServerNameListEntry 3 }

-- {SCALAR} 1712.2.31.6
lcsSetupPppoeServerAcName OBJECT-TYPE
    SYNTAX     DisplayString (SIZE(0..32))
    MAX-ACCESS read-write
    STATUS     current
    DESCRIPTION
        "-- empty --"
    ::= { lcsSetupPppoeServer 6 }

-- {SCALAR} 1712.2.31.3
lcsSetupPppoeServerService OBJECT-TYPE
    SYNTAX     DisplayString (SIZE(0..32))
    MAX-ACCESS read-write
    STATUS     current
    DESCRIPTION
        "-- empty --"
    ::= { lcsSetupPppoeServer 3 }

-- {SCALAR} 1712.2.31.4
lcsSetupPppoeServerSessionLimit OBJECT-TYPE
    SYNTAX     INTEGER (0..2147483647)
    MAX-ACCESS read-write
    STATUS     current
    DESCRIPTION
        "-- empty --"
    ::= { lcsSetupPppoeServer 4 }

-- {TABLE} 1712.2.31.5
lcsSetupPppoeServerPortsTable OBJECT-TYPE
    SYNTAX     SEQUENCE OF LcsSetupPppoeServerPortsEntry
    MAX-ACCESS not-accessible
    STATUS     current
    DESCRIPTION
        "-- empty --"
    ::= { lcsSetupPppoeServer 5 }

-- {ENTRY} 1712.2.31.5.1
lcsSetupPppoeServerPortsEntry OBJECT-TYPE
    SYNTAX     LcsSetupPppoeServerPortsEntry
    MAX-ACCESS not-accessible
    STATUS     current
    DESCRIPTION
        ""
    INDEX {
        lcsSetupPppoeServerPortsEntryPort
    }
    ::= { lcsSetupPppoeServerPortsTable 1 }

-- {SEQUENCE}
LcsSetupPppoeServerPortsEntry ::= SEQUENCE {
    lcsSetupPppoeServerPortsEntryPort DisplayString,
    lcsSetupPppoeServerPortsEntryEnablePppoe INTEGER
}

-- {COLUMN} 1712.2.31.5.1.2
lcsSetupPppoeServerPortsEntryPort OBJECT-TYPE
    SYNTAX     DisplayString (SIZE(0..18))
    MAX-ACCESS read-only
    STATUS     current
    DESCRIPTION
        "-- empty --"
    ::= { lcsSetupPppoeServerPortsEntry 2 }

-- {COLUMN} 1712.2.31.5.1.3
lcsSetupPppoeServerPortsEntryEnablePppoe OBJECT-TYPE
    SYNTAX     INTEGER
      {
        eNo (0),
        eYes (1)
      }
    MAX-ACCESS read-write
    STATUS     current
    DESCRIPTION
        "-- empty --"
    ::= { lcsSetupPppoeServerPortsEntry 3 }

-- {OID} 1712.2.32
lcsSetupVlan OBJECT IDENTIFIER ::= { lcsSetup 32 }

-- {SCALAR} 1712.2.32.4
lcsSetupVlanOperating OBJECT-TYPE
    SYNTAX     INTEGER
      {
        eNo (0),
        eYes (1)
      }
    MAX-ACCESS read-write
    STATUS     current
    DESCRIPTION
        "-- empty --"
    ::= { lcsSetupVlan 4 }

-- {TABLE} 1712.2.32.1
lcsSetupVlanNetworksTable OBJECT-TYPE
    SYNTAX     SEQUENCE OF LcsSetupVlanNetworksEntry
    MAX-ACCESS not-accessible
    STATUS     current
    DESCRIPTION
        "-- empty --"
    ::= { lcsSetupVlan 1 }

-- {ENTRY} 1712.2.32.1.1
lcsSetupVlanNetworksEntry OBJECT-TYPE
    SYNTAX     LcsSetupVlanNetworksEntry
    MAX-ACCESS not-accessible
    STATUS     current
    DESCRIPTION
        ""
    INDEX {
        lcsSetupVlanNetworksEntryName
    }
    ::= { lcsSetupVlanNetworksTable 1 }

-- {SEQUENCE}
LcsSetupVlanNetworksEntry ::= SEQUENCE {
    lcsSetupVlanNetworksEntryName DisplayString,
    lcsSetupVlanNetworksEntryVlanId INTEGER,
    lcsSetupVlanNetworksEntryPorts DisplayString
}

-- {COLUMN} 1712.2.32.1.1.1
lcsSetupVlanNetworksEntryName OBJECT-TYPE
    SYNTAX     DisplayString (SIZE(0..16))
    MAX-ACCESS read-write
    STATUS     current
    DESCRIPTION
        "-- empty --"
    ::= { lcsSetupVlanNetworksEntry 1 }

-- {COLUMN} 1712.2.32.1.1.2
lcsSetupVlanNetworksEntryVlanId OBJECT-TYPE
    SYNTAX     INTEGER (0..65535)
    MAX-ACCESS read-write
    STATUS     current
    DESCRIPTION
        "-- empty --"
    ::= { lcsSetupVlanNetworksEntry 2 }

-- {COLUMN} 1712.2.32.1.1.4
lcsSetupVlanNetworksEntryPorts OBJECT-TYPE
    SYNTAX     DisplayString (SIZE(0..251))
    MAX-ACCESS read-write
    STATUS     current
    DESCRIPTION
        "-- empty --"
    ::= { lcsSetupVlanNetworksEntry 4 }

-- {SCALAR} 1712.2.32.5
lcsSetupVlanTagValue OBJECT-TYPE
    SYNTAX     DisplayString (SIZE(0..4))
    MAX-ACCESS read-write
    STATUS     current
    DESCRIPTION
        "-- empty --"
    ::= { lcsSetupVlan 5 }

-- {TABLE} 1712.2.32.2
lcsSetupVlanPortTableTable OBJECT-TYPE
    SYNTAX     SEQUENCE OF LcsSetupVlanPortTableEntry
    MAX-ACCESS not-accessible
    STATUS     current
    DESCRIPTION
        "-- empty --"
    ::= { lcsSetupVlan 2 }

-- {ENTRY} 1712.2.32.2.1
lcsSetupVlanPortTableEntry OBJECT-TYPE
    SYNTAX     LcsSetupVlanPortTableEntry
    MAX-ACCESS not-accessible
    STATUS     current
    DESCRIPTION
        ""
    INDEX {
        lcsSetupVlanPortTableEntryPort
    }
    ::= { lcsSetupVlanPortTableTable 1 }

-- {SEQUENCE}
LcsSetupVlanPortTableEntry ::= SEQUENCE {
    lcsSetupVlanPortTableEntryPort DisplayString,
    lcsSetupVlanPortTableEntryTaggingMode INTEGER,
    lcsSetupVlanPortTableEntryAllowAllVlans INTEGER,
    lcsSetupVlanPortTableEntryPortVlanId INTEGER
}

-- {COLUMN} 1712.2.32.2.1.1
lcsSetupVlanPortTableEntryPort OBJECT-TYPE
    SYNTAX     DisplayString (SIZE(0..18))
    MAX-ACCESS read-only
    STATUS     current
    DESCRIPTION
        "-- empty --"
    ::= { lcsSetupVlanPortTableEntry 1 }

-- {COLUMN} 1712.2.32.2.1.6
lcsSetupVlanPortTableEntryTaggingMode OBJECT-TYPE
    SYNTAX     INTEGER
      {
        eIngressMixed (0),
        eNever (1),
        eMixed (2),
        eAlways (3)
      }
    MAX-ACCESS read-write
    STATUS     current
    DESCRIPTION
        "-- empty --"
    ::= { lcsSetupVlanPortTableEntry 6 }

-- {COLUMN} 1712.2.32.2.1.4
lcsSetupVlanPortTableEntryAllowAllVlans OBJECT-TYPE
    SYNTAX     INTEGER
      {
        eNo (0),
        eYes (1)
      }
    MAX-ACCESS read-write
    STATUS     current
    DESCRIPTION
        "-- empty --"
    ::= { lcsSetupVlanPortTableEntry 4 }

-- {COLUMN} 1712.2.32.2.1.5
lcsSetupVlanPortTableEntryPortVlanId OBJECT-TYPE
    SYNTAX     INTEGER (0..65535)
    MAX-ACCESS read-write
    STATUS     current
    DESCRIPTION
        "-- empty --"
    ::= { lcsSetupVlanPortTableEntry 5 }

-- {OID} 1712.2.34
lcsSetupPrinter OBJECT IDENTIFIER ::= { lcsSetup 34 }

-- {TABLE} 1712.2.34.1
lcsSetupPrinterPrinterTable OBJECT-TYPE
    SYNTAX     SEQUENCE OF LcsSetupPrinterPrinterEntry
    MAX-ACCESS not-accessible
    STATUS     current
    DESCRIPTION
        "-- empty --"
    ::= { lcsSetupPrinter 1 }

-- {ENTRY} 1712.2.34.1.1
lcsSetupPrinterPrinterEntry OBJECT-TYPE
    SYNTAX     LcsSetupPrinterPrinterEntry
    MAX-ACCESS not-accessible
    STATUS     current
    DESCRIPTION
        ""
    INDEX {
        lcsSetupPrinterPrinterEntryPrinter
    }
    ::= { lcsSetupPrinterPrinterTable 1 }

-- {SEQUENCE}
LcsSetupPrinterPrinterEntry ::= SEQUENCE {
    lcsSetupPrinterPrinterEntryPrinter DisplayString,
    lcsSetupPrinterPrinterEntryRawipPort INTEGER,
    lcsSetupPrinterPrinterEntryLpdPort INTEGER,
    lcsSetupPrinterPrinterEntryActiv INTEGER,
    lcsSetupPrinterPrinterEntryBidirectional INTEGER,
    lcsSetupPrinterPrinterEntryResetOnOpen INTEGER
}

-- {COLUMN} 1712.2.34.1.1.1
lcsSetupPrinterPrinterEntryPrinter OBJECT-TYPE
    SYNTAX     DisplayString (SIZE(0..15))
    MAX-ACCESS read-write
    STATUS     current
    DESCRIPTION
        "-- empty --"
    ::= { lcsSetupPrinterPrinterEntry 1 }

-- {COLUMN} 1712.2.34.1.1.2
lcsSetupPrinterPrinterEntryRawipPort OBJECT-TYPE
    SYNTAX     INTEGER (0..2147483647)
    MAX-ACCESS read-write
    STATUS     current
    DESCRIPTION
        "-- empty --"
    ::= { lcsSetupPrinterPrinterEntry 2 }

-- {COLUMN} 1712.2.34.1.1.3
lcsSetupPrinterPrinterEntryLpdPort OBJECT-TYPE
    SYNTAX     INTEGER (0..2147483647)
    MAX-ACCESS read-write
    STATUS     current
    DESCRIPTION
        "-- empty --"
    ::= { lcsSetupPrinterPrinterEntry 3 }

-- {COLUMN} 1712.2.34.1.1.4
lcsSetupPrinterPrinterEntryActiv OBJECT-TYPE
    SYNTAX     INTEGER
      {
        eNo (0),
        eYes (1)
      }
    MAX-ACCESS read-write
    STATUS     current
    DESCRIPTION
        "-- empty --"
    ::= { lcsSetupPrinterPrinterEntry 4 }

-- {COLUMN} 1712.2.34.1.1.5
lcsSetupPrinterPrinterEntryBidirectional OBJECT-TYPE
    SYNTAX     INTEGER
      {
        eNo (0),
        eYes (1)
      }
    MAX-ACCESS read-write
    STATUS     current
    DESCRIPTION
        "-- empty --"
    ::= { lcsSetupPrinterPrinterEntry 5 }

-- {COLUMN} 1712.2.34.1.1.6
lcsSetupPrinterPrinterEntryResetOnOpen OBJECT-TYPE
    SYNTAX     INTEGER
      {
        eNo (0),
        eYes (1)
      }
    MAX-ACCESS read-write
    STATUS     current
    DESCRIPTION
        "-- empty --"
    ::= { lcsSetupPrinterPrinterEntry 6 }

-- {TABLE} 1712.2.34.2
lcsSetupPrinterAccessListTable OBJECT-TYPE
    SYNTAX     SEQUENCE OF LcsSetupPrinterAccessListEntry
    MAX-ACCESS not-accessible
    STATUS     current
    DESCRIPTION
        "-- empty --"
    ::= { lcsSetupPrinter 2 }

-- {ENTRY} 1712.2.34.2.1
lcsSetupPrinterAccessListEntry OBJECT-TYPE
    SYNTAX     LcsSetupPrinterAccessListEntry
    MAX-ACCESS not-accessible
    STATUS     current
    DESCRIPTION
        ""
    INDEX {
        lcsSetupPrinterAccessListEntryIpAddress,
        lcsSetupPrinterAccessListEntryIpNetmask,
        lcsSetupPrinterAccessListEntryRtgTag
    }
    ::= { lcsSetupPrinterAccessListTable 1 }

-- {SEQUENCE}
LcsSetupPrinterAccessListEntry ::= SEQUENCE {
    lcsSetupPrinterAccessListEntryIpAddress IpAddress,
    lcsSetupPrinterAccessListEntryIpNetmask IpAddress,
    lcsSetupPrinterAccessListEntryRtgTag INTEGER
}

-- {COLUMN} 1712.2.34.2.1.1
lcsSetupPrinterAccessListEntryIpAddress OBJECT-TYPE
    SYNTAX     IpAddress
    MAX-ACCESS read-write
    STATUS     current
    DESCRIPTION
        "-- empty --"
    ::= { lcsSetupPrinterAccessListEntry 1 }

-- {COLUMN} 1712.2.34.2.1.2
lcsSetupPrinterAccessListEntryIpNetmask OBJECT-TYPE
    SYNTAX     IpAddress
    MAX-ACCESS read-write
    STATUS     current
    DESCRIPTION
        "-- empty --"
    ::= { lcsSetupPrinterAccessListEntry 2 }

-- {COLUMN} 1712.2.34.2.1.3
lcsSetupPrinterAccessListEntryRtgTag OBJECT-TYPE
    SYNTAX     INTEGER (0..65535)
    MAX-ACCESS read-write
    STATUS     current
    DESCRIPTION
        "-- empty --"
    ::= { lcsSetupPrinterAccessListEntry 3 }

-- {OID} 1712.2.39
lcsSetupCerts OBJECT IDENTIFIER ::= { lcsSetup 39 }

-- {OID} 1712.2.39.1
lcsSetupCertsScepClnt OBJECT IDENTIFIER ::= { lcsSetupCerts 1 }

-- {SCALAR} 1712.2.39.1.1
lcsSetupCertsScepClntScepOperating OBJECT-TYPE
    SYNTAX     INTEGER
      {
        eNo (0),
        eYes (1)
      }
    MAX-ACCESS read-write
    STATUS     current
    DESCRIPTION
        "-- empty --"
    ::= { lcsSetupCertsScepClnt 1 }

-- {SCALAR} 1712.2.39.1.11
lcsSetupCertsScepClntRetryAfterErrorInterval OBJECT-TYPE
    SYNTAX     INTEGER (0..2147483647)
    MAX-ACCESS read-write
    STATUS     current
    DESCRIPTION
        "-- empty --"
    ::= { lcsSetupCertsScepClnt 11 }

-- {SCALAR} 1712.2.39.1.12
lcsSetupCertsScepClntCheckPendingRequestsInterval OBJECT-TYPE
    SYNTAX     INTEGER (0..2147483647)
    MAX-ACCESS read-write
    STATUS     current
    DESCRIPTION
        "-- empty --"
    ::= { lcsSetupCertsScepClnt 12 }

-- {SCALAR} 1712.2.39.1.2
lcsSetupCertsScepClntDeviceCertificateUpdateBefore OBJECT-TYPE
    SYNTAX     INTEGER (0..2147483647)
    MAX-ACCESS read-write
    STATUS     current
    DESCRIPTION
        "-- empty --"
    ::= { lcsSetupCertsScepClnt 2 }

-- {SCALAR} 1712.2.39.1.3
lcsSetupCertsScepClntCaCertificateUpdateBefore OBJECT-TYPE
    SYNTAX     INTEGER (0..2147483647)
    MAX-ACCESS read-write
    STATUS     current
    DESCRIPTION
        "-- empty --"
    ::= { lcsSetupCertsScepClnt 3 }

-- {TABLE} 1712.2.39.1.14
lcsSetupCertsScepClntCasTable OBJECT-TYPE
    SYNTAX     SEQUENCE OF LcsSetupCertsScepClntCasEntry
    MAX-ACCESS not-accessible
    STATUS     current
    DESCRIPTION
        "-- empty --"
    ::= { lcsSetupCertsScepClnt 14 }

-- {ENTRY} 1712.2.39.1.14.1
lcsSetupCertsScepClntCasEntry OBJECT-TYPE
    SYNTAX     LcsSetupCertsScepClntCasEntry
    MAX-ACCESS not-accessible
    STATUS     current
    DESCRIPTION
        ""
    INDEX {
        lcsSetupCertsScepClntCasEntryName
    }
    ::= { lcsSetupCertsScepClntCasTable 1 }

-- {SEQUENCE}
LcsSetupCertsScepClntCasEntry ::= SEQUENCE {
    lcsSetupCertsScepClntCasEntryName DisplayString,
    lcsSetupCertsScepClntCasEntryUrl DisplayString,
    lcsSetupCertsScepClntCasEntryDn DisplayString,
    lcsSetupCertsScepClntCasEntryEncAlg INTEGER,
    lcsSetupCertsScepClntCasEntryIdentifier DisplayString,
    lcsSetupCertsScepClntCasEntryRaAutoapprove INTEGER,
    lcsSetupCertsScepClntCasEntryCaSignatureAlgorithm INTEGER,
    lcsSetupCertsScepClntCasEntryCaFingerprintAlgorithm INTEGER,
    lcsSetupCertsScepClntCasEntryCaFingerprint DisplayString,
    lcsSetupCertsScepClntCasEntryLoopbackAddr DisplayString
}

-- {COLUMN} 1712.2.39.1.14.1.1
lcsSetupCertsScepClntCasEntryName OBJECT-TYPE
    SYNTAX     DisplayString (SIZE(0..16))
    MAX-ACCESS read-write
    STATUS     current
    DESCRIPTION
        "-- empty --"
    ::= { lcsSetupCertsScepClntCasEntry 1 }

-- {COLUMN} 1712.2.39.1.14.1.2
lcsSetupCertsScepClntCasEntryUrl OBJECT-TYPE
    SYNTAX     DisplayString (SIZE(0..251))
    MAX-ACCESS read-write
    STATUS     current
    DESCRIPTION
        "-- empty --"
    ::= { lcsSetupCertsScepClntCasEntry 2 }

-- {COLUMN} 1712.2.39.1.14.1.3
lcsSetupCertsScepClntCasEntryDn OBJECT-TYPE
    SYNTAX     DisplayString (SIZE(0..251))
    MAX-ACCESS read-write
    STATUS     current
    DESCRIPTION
        "-- empty --"
    ::= { lcsSetupCertsScepClntCasEntry 3 }

-- {COLUMN} 1712.2.39.1.14.1.4
lcsSetupCertsScepClntCasEntryEncAlg OBJECT-TYPE
    SYNTAX     INTEGER
      {
        eDes (0),
        e3des (1),
        eBlowfish (2),
        eAes128 (3)
      }
    MAX-ACCESS read-write
    STATUS     current
    DESCRIPTION
        "-- empty --"
    ::= { lcsSetupCertsScepClntCasEntry 4 }

-- {COLUMN} 1712.2.39.1.14.1.5
lcsSetupCertsScepClntCasEntryIdentifier OBJECT-TYPE
    SYNTAX     DisplayString (SIZE(0..251))
    MAX-ACCESS read-write
    STATUS     current
    DESCRIPTION
        "-- empty --"
    ::= { lcsSetupCertsScepClntCasEntry 5 }

-- {COLUMN} 1712.2.39.1.14.1.7
lcsSetupCertsScepClntCasEntryRaAutoapprove OBJECT-TYPE
    SYNTAX     INTEGER
      {
        eNo (0),
        eYes (1)
      }
    MAX-ACCESS read-write
    STATUS     current
    DESCRIPTION
        "-- empty --"
    ::= { lcsSetupCertsScepClntCasEntry 7 }

-- {COLUMN} 1712.2.39.1.14.1.6
lcsSetupCertsScepClntCasEntryCaSignatureAlgorithm OBJECT-TYPE
    SYNTAX     INTEGER
      {
        eMd5 (0),
        eSha1 (1)
      }
    MAX-ACCESS read-write
    STATUS     current
    DESCRIPTION
        "-- empty --"
    ::= { lcsSetupCertsScepClntCasEntry 6 }

-- {COLUMN} 1712.2.39.1.14.1.8
lcsSetupCertsScepClntCasEntryCaFingerprintAlgorithm OBJECT-TYPE
    SYNTAX     INTEGER
      {
        eOff (0),
        eSha1 (1),
        eMd5 (2)
      }
    MAX-ACCESS read-write
    STATUS     current
    DESCRIPTION
        "-- empty --"
    ::= { lcsSetupCertsScepClntCasEntry 8 }

-- {COLUMN} 1712.2.39.1.14.1.9
lcsSetupCertsScepClntCasEntryCaFingerprint OBJECT-TYPE
    SYNTAX     DisplayString (SIZE(0..59))
    MAX-ACCESS read-write
    STATUS     current
    DESCRIPTION
        "-- empty --"
    ::= { lcsSetupCertsScepClntCasEntry 9 }

-- {COLUMN} 1712.2.39.1.14.1.11
lcsSetupCertsScepClntCasEntryLoopbackAddr OBJECT-TYPE
    SYNTAX     DisplayString (SIZE(0..16))
    MAX-ACCESS read-write
    STATUS     current
    DESCRIPTION
        "-- empty --"
    ::= { lcsSetupCertsScepClntCasEntry 11 }

-- {TABLE} 1712.2.39.1.7
lcsSetupCertsScepClntCertsTable OBJECT-TYPE
    SYNTAX     SEQUENCE OF LcsSetupCertsScepClntCertsEntry
    MAX-ACCESS not-accessible
    STATUS     current
    DESCRIPTION
        ""
    ::= { lcsSetupCertsScepClnt 7 }

-- {ENTRY} 1712.2.39.1.7.1
lcsSetupCertsScepClntCertsEntry OBJECT-TYPE
    SYNTAX     LcsSetupCertsScepClntCertsEntry
    MAX-ACCESS not-accessible
    STATUS     current
    DESCRIPTION
        ""
    INDEX {
        lcsSetupCertsScepClntCertsEntryName
    }
    ::= { lcsSetupCertsScepClntCertsTable 1 }

-- {SEQUENCE}
LcsSetupCertsScepClntCertsEntry ::= SEQUENCE {
    lcsSetupCertsScepClntCertsEntryName DisplayString,
    lcsSetupCertsScepClntCertsEntryCadn DisplayString,
    lcsSetupCertsScepClntCertsEntrySubject DisplayString,
    lcsSetupCertsScepClntCertsEntryChallengepwd DisplayString,
    lcsSetupCertsScepClntCertsEntrySubjectaltname DisplayString,
    lcsSetupCertsScepClntCertsEntryKeyusage DisplayString,
    lcsSetupCertsScepClntCertsEntryExtendedKeyusage DisplayString,
    lcsSetupCertsScepClntCertsEntryDevCertKeyl INTEGER,
    lcsSetupCertsScepClntCertsEntryApplication INTEGER
}

-- {COLUMN} 1712.2.39.1.7.1.1
lcsSetupCertsScepClntCertsEntryName OBJECT-TYPE
    SYNTAX     DisplayString (SIZE(0..16))
    MAX-ACCESS read-write
    STATUS     current
    DESCRIPTION
        "-- empty --"
    ::= { lcsSetupCertsScepClntCertsEntry 1 }

-- {COLUMN} 1712.2.39.1.7.1.2
lcsSetupCertsScepClntCertsEntryCadn OBJECT-TYPE
    SYNTAX     DisplayString (SIZE(0..251))
    MAX-ACCESS read-write
    STATUS     current
    DESCRIPTION
        "-- empty --"
    ::= { lcsSetupCertsScepClntCertsEntry 2 }

-- {COLUMN} 1712.2.39.1.7.1.3
lcsSetupCertsScepClntCertsEntrySubject OBJECT-TYPE
    SYNTAX     DisplayString (SIZE(0..251))
    MAX-ACCESS read-write
    STATUS     current
    DESCRIPTION
        "-- empty --"
    ::= { lcsSetupCertsScepClntCertsEntry 3 }

-- {COLUMN} 1712.2.39.1.7.1.4
lcsSetupCertsScepClntCertsEntryChallengepwd OBJECT-TYPE
    SYNTAX     DisplayString (SIZE(0..251))
    MAX-ACCESS read-write
    STATUS     current
    DESCRIPTION
        "-- empty --"
    ::= { lcsSetupCertsScepClntCertsEntry 4 }

-- {COLUMN} 1712.2.39.1.7.1.5
lcsSetupCertsScepClntCertsEntrySubjectaltname OBJECT-TYPE
    SYNTAX     DisplayString (SIZE(0..251))
    MAX-ACCESS read-write
    STATUS     current
    DESCRIPTION
        "-- empty --"
    ::= { lcsSetupCertsScepClntCertsEntry 5 }

-- {COLUMN} 1712.2.39.1.7.1.6
lcsSetupCertsScepClntCertsEntryKeyusage OBJECT-TYPE
    SYNTAX     DisplayString (SIZE(0..251))
    MAX-ACCESS read-write
    STATUS     current
    DESCRIPTION
        "-- empty --"
    ::= { lcsSetupCertsScepClntCertsEntry 6 }

-- {COLUMN} 1712.2.39.1.7.1.9
lcsSetupCertsScepClntCertsEntryExtendedKeyusage OBJECT-TYPE
    SYNTAX     DisplayString (SIZE(0..251))
    MAX-ACCESS read-write
    STATUS     current
    DESCRIPTION
        "-- empty --"
    ::= { lcsSetupCertsScepClntCertsEntry 9 }

-- {COLUMN} 1712.2.39.1.7.1.7
lcsSetupCertsScepClntCertsEntryDevCertKeyl OBJECT-TYPE
    SYNTAX     INTEGER (0..2147483647)
    MAX-ACCESS read-write
    STATUS     current
    DESCRIPTION
        ""
    ::= { lcsSetupCertsScepClntCertsEntry 7 }

-- {COLUMN} 1712.2.39.1.7.1.8
lcsSetupCertsScepClntCertsEntryApplication OBJECT-TYPE
    SYNTAX     INTEGER
      {
        eVpn1 (0),
        eVpn2 (5),
        eVpn3 (6),
        eVpn4 (7),
        eVpn5 (8),
        eVpn6 (9),
        eVpn7 (10),
        eVpn8 (11),
        eVpn9 (12),
        eEapTls (3),
        eDefault (13),
        eCa (14),
        eUnconfigured (-1)
      }
    MAX-ACCESS read-write
    STATUS     current
    DESCRIPTION
        "-- empty --"
    ::= { lcsSetupCertsScepClntCertsEntry 8 }

-- {SCALAR} 1712.2.39.1.8
lcsSetupCertsScepClntReinit OBJECT-TYPE
    SYNTAX     DisplayString
    MAX-ACCESS read-write
    STATUS     current
    DESCRIPTION
        "-- empty --"
    ::= { lcsSetupCertsScepClnt 8 }

-- {SCALAR} 1712.2.39.1.9
lcsSetupCertsScepClntUpdate OBJECT-TYPE
    SYNTAX     DisplayString
    MAX-ACCESS read-write
    STATUS     current
    DESCRIPTION
        "-- empty --"
    ::= { lcsSetupCertsScepClnt 9 }

-- {SCALAR} 1712.2.39.1.10
lcsSetupCertsScepClntClearScepFilesystem OBJECT-TYPE
    SYNTAX     DisplayString
    MAX-ACCESS read-write
    STATUS     current
    DESCRIPTION
        "-- empty --"
    ::= { lcsSetupCertsScepClnt 10 }

-- {SCALAR} 1712.2.39.1.13
lcsSetupCertsScepClntTraceLevel OBJECT-TYPE
    SYNTAX     INTEGER
      {
        eAll (7),
        eReduced (6),
        eOnlyErrors (3)
      }
    MAX-ACCESS read-write
    STATUS     current
    DESCRIPTION
        "-- empty --"
    ::= { lcsSetupCertsScepClnt 13 }

-- {OID} 1712.2.39.3
lcsSetupCertsCrls OBJECT IDENTIFIER ::= { lcsSetupCerts 3 }

-- {SCALAR} 1712.2.39.3.1
lcsSetupCertsCrlsCrlOperating OBJECT-TYPE
    SYNTAX     INTEGER
      {
        eNo (0),
        eYes (1)
      }
    MAX-ACCESS read-write
    STATUS     current
    DESCRIPTION
        "-- empty --"
    ::= { lcsSetupCertsCrls 1 }

-- {SCALAR} 1712.2.39.3.4
lcsSetupCertsCrlsUpdateBefore OBJECT-TYPE
    SYNTAX     INTEGER (0..2147483647)
    MAX-ACCESS read-write
    STATUS     current
    DESCRIPTION
        "-- empty --"
    ::= { lcsSetupCertsCrls 4 }

-- {SCALAR} 1712.2.39.3.5
lcsSetupCertsCrlsPrefetchPeriod OBJECT-TYPE
    SYNTAX     INTEGER (0..2147483647)
    MAX-ACCESS read-write
    STATUS     current
    DESCRIPTION
        "-- empty --"
    ::= { lcsSetupCertsCrls 5 }

-- {SCALAR} 1712.2.39.3.6
lcsSetupCertsCrlsValidityExceedance OBJECT-TYPE
    SYNTAX     INTEGER (0..2147483647)
    MAX-ACCESS read-write
    STATUS     current
    DESCRIPTION
        "-- empty --"
    ::= { lcsSetupCertsCrls 6 }

-- {SCALAR} 1712.2.39.3.9
lcsSetupCertsCrlsLoopbackAddress OBJECT-TYPE
    SYNTAX     DisplayString (SIZE(0..16))
    MAX-ACCESS read-write
    STATUS     current
    DESCRIPTION
        "-- empty --"
    ::= { lcsSetupCertsCrls 9 }

-- {SCALAR} 1712.2.39.3.7
lcsSetupCertsCrlsRefreshCrlNow OBJECT-TYPE
    SYNTAX     DisplayString
    MAX-ACCESS read-write
    STATUS     current
    DESCRIPTION
        "-- empty --"
    ::= { lcsSetupCertsCrls 7 }

-- {TABLE} 1712.2.39.3.8
lcsSetupCertsCrlsAlternativeUrlTableTable OBJECT-TYPE
    SYNTAX     SEQUENCE OF LcsSetupCertsCrlsAlternativeUrlTableEntry
    MAX-ACCESS not-accessible
    STATUS     current
    DESCRIPTION
        "-- empty --"
    ::= { lcsSetupCertsCrls 8 }

-- {ENTRY} 1712.2.39.3.8.1
lcsSetupCertsCrlsAlternativeUrlTableEntry OBJECT-TYPE
    SYNTAX     LcsSetupCertsCrlsAlternativeUrlTableEntry
    MAX-ACCESS not-accessible
    STATUS     current
    DESCRIPTION
        ""
    INDEX {
        lcsSetupCertsCrlsAlternativeUrlTableEntryAlternativeUrl
    }
    ::= { lcsSetupCertsCrlsAlternativeUrlTableTable 1 }

-- {SEQUENCE}
LcsSetupCertsCrlsAlternativeUrlTableEntry ::= SEQUENCE {
    lcsSetupCertsCrlsAlternativeUrlTableEntryAlternativeUrl DisplayString
}

-- {COLUMN} 1712.2.39.3.8.1.1
lcsSetupCertsCrlsAlternativeUrlTableEntryAlternativeUrl OBJECT-TYPE
    SYNTAX     DisplayString (SIZE(0..251))
    MAX-ACCESS read-write
    STATUS     current
    DESCRIPTION
        "-- empty --"
    ::= { lcsSetupCertsCrlsAlternativeUrlTableEntry 1 }

-- {OID} 1712.2.39.6
lcsSetupCertsOcspClient OBJECT IDENTIFIER ::= { lcsSetupCerts 6 }

-- {TABLE} 1712.2.39.6.1
lcsSetupCertsOcspClientCaProfileTableTable OBJECT-TYPE
    SYNTAX     SEQUENCE OF LcsSetupCertsOcspClientCaProfileTableEntry
    MAX-ACCESS not-accessible
    STATUS     current
    DESCRIPTION
        "-- empty --"
    ::= { lcsSetupCertsOcspClient 1 }

-- {ENTRY} 1712.2.39.6.1.1
lcsSetupCertsOcspClientCaProfileTableEntry OBJECT-TYPE
    SYNTAX     LcsSetupCertsOcspClientCaProfileTableEntry
    MAX-ACCESS not-accessible
    STATUS     current
    DESCRIPTION
        ""
    INDEX {
        lcsSetupCertsOcspClientCaProfileTableEntryProfileName
    }
    ::= { lcsSetupCertsOcspClientCaProfileTableTable 1 }

-- {SEQUENCE}
LcsSetupCertsOcspClientCaProfileTableEntry ::= SEQUENCE {
    lcsSetupCertsOcspClientCaProfileTableEntryProfileName DisplayString,
    lcsSetupCertsOcspClientCaProfileTableEntryCaDistinguishedName DisplayString,
    lcsSetupCertsOcspClientCaProfileTableEntryPreferAia INTEGER,
    lcsSetupCertsOcspClientCaProfileTableEntryResponderProfileName DisplayString,
    lcsSetupCertsOcspClientCaProfileTableEntrySourceInterface DisplayString,
    lcsSetupCertsOcspClientCaProfileTableEntryCertEvaluationMode INTEGER,
    lcsSetupCertsOcspClientCaProfileTableEntrySyslogEvents INTEGER
}

-- {COLUMN} 1712.2.39.6.1.1.1
lcsSetupCertsOcspClientCaProfileTableEntryProfileName OBJECT-TYPE
    SYNTAX     DisplayString (SIZE(0..32))
    MAX-ACCESS read-write
    STATUS     current
    DESCRIPTION
        "-- empty --"
    ::= { lcsSetupCertsOcspClientCaProfileTableEntry 1 }

-- {COLUMN} 1712.2.39.6.1.1.2
lcsSetupCertsOcspClientCaProfileTableEntryCaDistinguishedName OBJECT-TYPE
    SYNTAX     DisplayString (SIZE(0..251))
    MAX-ACCESS read-write
    STATUS     current
    DESCRIPTION
        "-- empty --"
    ::= { lcsSetupCertsOcspClientCaProfileTableEntry 2 }

-- {COLUMN} 1712.2.39.6.1.1.3
lcsSetupCertsOcspClientCaProfileTableEntryPreferAia OBJECT-TYPE
    SYNTAX     INTEGER
      {
        eNo (0),
        eYes (1)
      }
    MAX-ACCESS read-write
    STATUS     current
    DESCRIPTION
        "-- empty --"
    ::= { lcsSetupCertsOcspClientCaProfileTableEntry 3 }

-- {COLUMN} 1712.2.39.6.1.1.4
lcsSetupCertsOcspClientCaProfileTableEntryResponderProfileName OBJECT-TYPE
    SYNTAX     DisplayString (SIZE(0..32))
    MAX-ACCESS read-write
    STATUS     current
    DESCRIPTION
        "-- empty --"
    ::= { lcsSetupCertsOcspClientCaProfileTableEntry 4 }

-- {COLUMN} 1712.2.39.6.1.1.5
lcsSetupCertsOcspClientCaProfileTableEntrySourceInterface OBJECT-TYPE
    SYNTAX     DisplayString (SIZE(0..16))
    MAX-ACCESS read-write
    STATUS     current
    DESCRIPTION
        "-- empty --"
    ::= { lcsSetupCertsOcspClientCaProfileTableEntry 5 }

-- {COLUMN} 1712.2.39.6.1.1.6
lcsSetupCertsOcspClientCaProfileTableEntryCertEvaluationMode OBJECT-TYPE
    SYNTAX     INTEGER
      {
        eStrict (0),
        eLoose (1)
      }
    MAX-ACCESS read-write
    STATUS     current
    DESCRIPTION
        "-- empty --"
    ::= { lcsSetupCertsOcspClientCaProfileTableEntry 6 }

-- {COLUMN} 1712.2.39.6.1.1.7
lcsSetupCertsOcspClientCaProfileTableEntrySyslogEvents OBJECT-TYPE
    SYNTAX     INTEGER
      {
        eNo (0),
        eYes (1)
      }
    MAX-ACCESS read-write
    STATUS     current
    DESCRIPTION
        "-- empty --"
    ::= { lcsSetupCertsOcspClientCaProfileTableEntry 7 }

-- {TABLE} 1712.2.39.6.2
lcsSetupCertsOcspClientResponderProfileTableTable OBJECT-TYPE
    SYNTAX     SEQUENCE OF LcsSetupCertsOcspClientResponderProfileTableEntry
    MAX-ACCESS not-accessible
    STATUS     current
    DESCRIPTION
        "-- empty --"
    ::= { lcsSetupCertsOcspClient 2 }

-- {ENTRY} 1712.2.39.6.2.1
lcsSetupCertsOcspClientResponderProfileTableEntry OBJECT-TYPE
    SYNTAX     LcsSetupCertsOcspClientResponderProfileTableEntry
    MAX-ACCESS not-accessible
    STATUS     current
    DESCRIPTION
        ""
    INDEX {
        lcsSetupCertsOcspClientResponderProfileTableEntryProfileName
    }
    ::= { lcsSetupCertsOcspClientResponderProfileTableTable 1 }

-- {SEQUENCE}
LcsSetupCertsOcspClientResponderProfileTableEntry ::= SEQUENCE {
    lcsSetupCertsOcspClientResponderProfileTableEntryProfileName DisplayString,
    lcsSetupCertsOcspClientResponderProfileTableEntryUrl DisplayString
}

-- {COLUMN} 1712.2.39.6.2.1.1
lcsSetupCertsOcspClientResponderProfileTableEntryProfileName OBJECT-TYPE
    SYNTAX     DisplayString (SIZE(0..32))
    MAX-ACCESS read-write
    STATUS     current
    DESCRIPTION
        "-- empty --"
    ::= { lcsSetupCertsOcspClientResponderProfileTableEntry 1 }

-- {COLUMN} 1712.2.39.6.2.1.2
lcsSetupCertsOcspClientResponderProfileTableEntryUrl OBJECT-TYPE
    SYNTAX     DisplayString (SIZE(0..251))
    MAX-ACCESS read-write
    STATUS     current
    DESCRIPTION
        "-- empty --"
    ::= { lcsSetupCertsOcspClientResponderProfileTableEntry 2 }

-- {OID} 1712.2.63
lcsSetupPacketCapture OBJECT IDENTIFIER ::= { lcsSetup 63 }

-- {SCALAR} 1712.2.63.1
lcsSetupPacketCaptureLcoscapOperating OBJECT-TYPE
    SYNTAX     INTEGER
      {
        eNo (0),
        eYes (1)
      }
    MAX-ACCESS read-write
    STATUS     current
    DESCRIPTION
        "-- empty --"
    ::= { lcsSetupPacketCapture 1 }

-- {SCALAR} 1712.2.63.2
lcsSetupPacketCaptureLcoscapPort OBJECT-TYPE
    SYNTAX     INTEGER (0..65535)
    MAX-ACCESS read-write
    STATUS     current
    DESCRIPTION
        "-- empty --"
    ::= { lcsSetupPacketCapture 2 }

-- {SCALAR} 1712.2.63.11
lcsSetupPacketCaptureRpcapOperating OBJECT-TYPE
    SYNTAX     INTEGER
      {
        eNo (0),
        eYes (1)
      }
    MAX-ACCESS read-write
    STATUS     current
    DESCRIPTION
        "-- empty --"
    ::= { lcsSetupPacketCapture 11 }

-- {SCALAR} 1712.2.63.12
lcsSetupPacketCaptureRpcapPort OBJECT-TYPE
    SYNTAX     INTEGER (0..65535)
    MAX-ACCESS read-write
    STATUS     current
    DESCRIPTION
        "-- empty --"
    ::= { lcsSetupPacketCapture 12 }

-- {OID} 1712.2.70
lcsSetupIpv6 OBJECT IDENTIFIER ::= { lcsSetup 70 }

-- {OID} 1712.2.70.1
lcsSetupIpv6Tunnel OBJECT IDENTIFIER ::= { lcsSetupIpv6 1 }

-- {TABLE} 1712.2.70.1.1
lcsSetupIpv6Tunnel6in4Table OBJECT-TYPE
    SYNTAX     SEQUENCE OF LcsSetupIpv6Tunnel6in4Entry
    MAX-ACCESS not-accessible
    STATUS     current
    DESCRIPTION
        "-- empty --"
    ::= { lcsSetupIpv6Tunnel 1 }

-- {ENTRY} 1712.2.70.1.1.1
lcsSetupIpv6Tunnel6in4Entry OBJECT-TYPE
    SYNTAX     LcsSetupIpv6Tunnel6in4Entry
    MAX-ACCESS not-accessible
    STATUS     current
    DESCRIPTION
        ""
    INDEX {
        lcsSetupIpv6Tunnel6in4EntryPeerName
    }
    ::= { lcsSetupIpv6Tunnel6in4Table 1 }

-- {SEQUENCE}
LcsSetupIpv6Tunnel6in4Entry ::= SEQUENCE {
    lcsSetupIpv6Tunnel6in4EntryPeerName DisplayString,
    lcsSetupIpv6Tunnel6in4EntryRtgTag INTEGER,
    lcsSetupIpv6Tunnel6in4EntryGatewayAddress DisplayString,
    lcsSetupIpv6Tunnel6in4EntryIpv4RtgTag INTEGER,
    lcsSetupIpv6Tunnel6in4EntryGatewayIpv6Address DisplayString,
    lcsSetupIpv6Tunnel6in4EntryLocalIpv6Address DisplayString,
    lcsSetupIpv6Tunnel6in4EntryRoutedIpv6Prefix DisplayString,
    lcsSetupIpv6Tunnel6in4EntryFirewall INTEGER
}

-- {COLUMN} 1712.2.70.1.1.1.1
lcsSetupIpv6Tunnel6in4EntryPeerName OBJECT-TYPE
    SYNTAX     DisplayString (SIZE(0..16))
    MAX-ACCESS read-write
    STATUS     current
    DESCRIPTION
        "-- empty --"
    ::= { lcsSetupIpv6Tunnel6in4Entry 1 }

-- {COLUMN} 1712.2.70.1.1.1.2
lcsSetupIpv6Tunnel6in4EntryRtgTag OBJECT-TYPE
    SYNTAX     INTEGER (0..65535)
    MAX-ACCESS read-write
    STATUS     current
    DESCRIPTION
        "-- empty --"
    ::= { lcsSetupIpv6Tunnel6in4Entry 2 }

-- {COLUMN} 1712.2.70.1.1.1.3
lcsSetupIpv6Tunnel6in4EntryGatewayAddress OBJECT-TYPE
    SYNTAX     DisplayString (SIZE(0..64))
    MAX-ACCESS read-write
    STATUS     current
    DESCRIPTION
        "-- empty --"
    ::= { lcsSetupIpv6Tunnel6in4Entry 3 }

-- {COLUMN} 1712.2.70.1.1.1.4
lcsSetupIpv6Tunnel6in4EntryIpv4RtgTag OBJECT-TYPE
    SYNTAX     INTEGER (0..65535)
    MAX-ACCESS read-write
    STATUS     current
    DESCRIPTION
        "-- empty --"
    ::= { lcsSetupIpv6Tunnel6in4Entry 4 }

-- {COLUMN} 1712.2.70.1.1.1.5
lcsSetupIpv6Tunnel6in4EntryGatewayIpv6Address OBJECT-TYPE
    SYNTAX     DisplayString (SIZE(0..43))
    MAX-ACCESS read-write
    STATUS     current
    DESCRIPTION
        "-- empty --"
    ::= { lcsSetupIpv6Tunnel6in4Entry 5 }

-- {COLUMN} 1712.2.70.1.1.1.6
lcsSetupIpv6Tunnel6in4EntryLocalIpv6Address OBJECT-TYPE
    SYNTAX     DisplayString (SIZE(0..43))
    MAX-ACCESS read-write
    STATUS     current
    DESCRIPTION
        "-- empty --"
    ::= { lcsSetupIpv6Tunnel6in4Entry 6 }

-- {COLUMN} 1712.2.70.1.1.1.7
lcsSetupIpv6Tunnel6in4EntryRoutedIpv6Prefix OBJECT-TYPE
    SYNTAX     DisplayString (SIZE(0..43))
    MAX-ACCESS read-write
    STATUS     current
    DESCRIPTION
        "-- empty --"
    ::= { lcsSetupIpv6Tunnel6in4Entry 7 }

-- {COLUMN} 1712.2.70.1.1.1.8
lcsSetupIpv6Tunnel6in4EntryFirewall OBJECT-TYPE
    SYNTAX     INTEGER
      {
        eYes (0),
        eNo (1)
      }
    MAX-ACCESS read-write
    STATUS     current
    DESCRIPTION
        "-- empty --"
    ::= { lcsSetupIpv6Tunnel6in4Entry 8 }

-- {TABLE} 1712.2.70.1.2
lcsSetupIpv6Tunnel6rdBorderRelayTable OBJECT-TYPE
    SYNTAX     SEQUENCE OF LcsSetupIpv6Tunnel6rdBorderRelayEntry
    MAX-ACCESS not-accessible
    STATUS     current
    DESCRIPTION
        "-- empty --"
    ::= { lcsSetupIpv6Tunnel 2 }

-- {ENTRY} 1712.2.70.1.2.1
lcsSetupIpv6Tunnel6rdBorderRelayEntry OBJECT-TYPE
    SYNTAX     LcsSetupIpv6Tunnel6rdBorderRelayEntry
    MAX-ACCESS not-accessible
    STATUS     current
    DESCRIPTION
        ""
    INDEX {
        lcsSetupIpv6Tunnel6rdBorderRelayEntryPeerName
    }
    ::= { lcsSetupIpv6Tunnel6rdBorderRelayTable 1 }

-- {SEQUENCE}
LcsSetupIpv6Tunnel6rdBorderRelayEntry ::= SEQUENCE {
    lcsSetupIpv6Tunnel6rdBorderRelayEntryPeerName DisplayString,
    lcsSetupIpv6Tunnel6rdBorderRelayEntryRtgTag INTEGER,
    lcsSetupIpv6Tunnel6rdBorderRelayEntryIpv4LoopbackAddress DisplayString,
    lcsSetupIpv6Tunnel6rdBorderRelayEntry6rdPrefix DisplayString,
    lcsSetupIpv6Tunnel6rdBorderRelayEntryIpv4MaskLength INTEGER,
    lcsSetupIpv6Tunnel6rdBorderRelayEntryDhcpv4Propagate INTEGER,
    lcsSetupIpv6Tunnel6rdBorderRelayEntryFirewall INTEGER
}

-- {COLUMN} 1712.2.70.1.2.1.1
lcsSetupIpv6Tunnel6rdBorderRelayEntryPeerName OBJECT-TYPE
    SYNTAX     DisplayString (SIZE(0..16))
    MAX-ACCESS read-write
    STATUS     current
    DESCRIPTION
        "-- empty --"
    ::= { lcsSetupIpv6Tunnel6rdBorderRelayEntry 1 }

-- {COLUMN} 1712.2.70.1.2.1.2
lcsSetupIpv6Tunnel6rdBorderRelayEntryRtgTag OBJECT-TYPE
    SYNTAX     INTEGER (0..65535)
    MAX-ACCESS read-write
    STATUS     current
    DESCRIPTION
        "-- empty --"
    ::= { lcsSetupIpv6Tunnel6rdBorderRelayEntry 2 }

-- {COLUMN} 1712.2.70.1.2.1.3
lcsSetupIpv6Tunnel6rdBorderRelayEntryIpv4LoopbackAddress OBJECT-TYPE
    SYNTAX     DisplayString (SIZE(0..21))
    MAX-ACCESS read-write
    STATUS     current
    DESCRIPTION
        "-- empty --"
    ::= { lcsSetupIpv6Tunnel6rdBorderRelayEntry 3 }

-- {COLUMN} 1712.2.70.1.2.1.4
lcsSetupIpv6Tunnel6rdBorderRelayEntry6rdPrefix OBJECT-TYPE
    SYNTAX     DisplayString (SIZE(0..24))
    MAX-ACCESS read-write
    STATUS     current
    DESCRIPTION
        "-- empty --"
    ::= { lcsSetupIpv6Tunnel6rdBorderRelayEntry 4 }

-- {COLUMN} 1712.2.70.1.2.1.5
lcsSetupIpv6Tunnel6rdBorderRelayEntryIpv4MaskLength OBJECT-TYPE
    SYNTAX     INTEGER (0..65535)
    MAX-ACCESS read-write
    STATUS     current
    DESCRIPTION
        "-- empty --"
    ::= { lcsSetupIpv6Tunnel6rdBorderRelayEntry 5 }

-- {COLUMN} 1712.2.70.1.2.1.6
lcsSetupIpv6Tunnel6rdBorderRelayEntryDhcpv4Propagate OBJECT-TYPE
    SYNTAX     INTEGER
      {
        eNo (0),
        eYes (1)
      }
    MAX-ACCESS read-write
    STATUS     current
    DESCRIPTION
        "-- empty --"
    ::= { lcsSetupIpv6Tunnel6rdBorderRelayEntry 6 }

-- {COLUMN} 1712.2.70.1.2.1.7
lcsSetupIpv6Tunnel6rdBorderRelayEntryFirewall OBJECT-TYPE
    SYNTAX     INTEGER
      {
        eYes (0),
        eNo (1)
      }
    MAX-ACCESS read-write
    STATUS     current
    DESCRIPTION
        "-- empty --"
    ::= { lcsSetupIpv6Tunnel6rdBorderRelayEntry 7 }

-- {TABLE} 1712.2.70.1.3
lcsSetupIpv6Tunnel6rdTable OBJECT-TYPE
    SYNTAX     SEQUENCE OF LcsSetupIpv6Tunnel6rdEntry
    MAX-ACCESS not-accessible
    STATUS     current
    DESCRIPTION
        "-- empty --"
    ::= { lcsSetupIpv6Tunnel 3 }

-- {ENTRY} 1712.2.70.1.3.1
lcsSetupIpv6Tunnel6rdEntry OBJECT-TYPE
    SYNTAX     LcsSetupIpv6Tunnel6rdEntry
    MAX-ACCESS not-accessible
    STATUS     current
    DESCRIPTION
        ""
    INDEX {
        lcsSetupIpv6Tunnel6rdEntryPeerName
    }
    ::= { lcsSetupIpv6Tunnel6rdTable 1 }

-- {SEQUENCE}
LcsSetupIpv6Tunnel6rdEntry ::= SEQUENCE {
    lcsSetupIpv6Tunnel6rdEntryPeerName DisplayString,
    lcsSetupIpv6Tunnel6rdEntryRtgTag INTEGER,
    lcsSetupIpv6Tunnel6rdEntryBorderRelayAddress DisplayString,
    lcsSetupIpv6Tunnel6rdEntryIpv4RtgTag INTEGER,
    lcsSetupIpv6Tunnel6rdEntry6rdPrefix DisplayString,
    lcsSetupIpv6Tunnel6rdEntryIpv4MaskLength INTEGER,
    lcsSetupIpv6Tunnel6rdEntryFirewall INTEGER
}

-- {COLUMN} 1712.2.70.1.3.1.1
lcsSetupIpv6Tunnel6rdEntryPeerName OBJECT-TYPE
    SYNTAX     DisplayString (SIZE(0..16))
    MAX-ACCESS read-write
    STATUS     current
    DESCRIPTION
        "-- empty --"
    ::= { lcsSetupIpv6Tunnel6rdEntry 1 }

-- {COLUMN} 1712.2.70.1.3.1.2
lcsSetupIpv6Tunnel6rdEntryRtgTag OBJECT-TYPE
    SYNTAX     INTEGER (0..65535)
    MAX-ACCESS read-write
    STATUS     current
    DESCRIPTION
        "-- empty --"
    ::= { lcsSetupIpv6Tunnel6rdEntry 2 }

-- {COLUMN} 1712.2.70.1.3.1.3
lcsSetupIpv6Tunnel6rdEntryBorderRelayAddress OBJECT-TYPE
    SYNTAX     DisplayString (SIZE(0..64))
    MAX-ACCESS read-write
    STATUS     current
    DESCRIPTION
        "-- empty --"
    ::= { lcsSetupIpv6Tunnel6rdEntry 3 }

-- {COLUMN} 1712.2.70.1.3.1.4
lcsSetupIpv6Tunnel6rdEntryIpv4RtgTag OBJECT-TYPE
    SYNTAX     INTEGER (0..65535)
    MAX-ACCESS read-write
    STATUS     current
    DESCRIPTION
        "-- empty --"
    ::= { lcsSetupIpv6Tunnel6rdEntry 4 }

-- {COLUMN} 1712.2.70.1.3.1.5
lcsSetupIpv6Tunnel6rdEntry6rdPrefix OBJECT-TYPE
    SYNTAX     DisplayString (SIZE(0..24))
    MAX-ACCESS read-write
    STATUS     current
    DESCRIPTION
        "-- empty --"
    ::= { lcsSetupIpv6Tunnel6rdEntry 5 }

-- {COLUMN} 1712.2.70.1.3.1.6
lcsSetupIpv6Tunnel6rdEntryIpv4MaskLength OBJECT-TYPE
    SYNTAX     INTEGER (0..65535)
    MAX-ACCESS read-write
    STATUS     current
    DESCRIPTION
        "-- empty --"
    ::= { lcsSetupIpv6Tunnel6rdEntry 6 }

-- {COLUMN} 1712.2.70.1.3.1.7
lcsSetupIpv6Tunnel6rdEntryFirewall OBJECT-TYPE
    SYNTAX     INTEGER
      {
        eYes (0),
        eNo (1)
      }
    MAX-ACCESS read-write
    STATUS     current
    DESCRIPTION
        "-- empty --"
    ::= { lcsSetupIpv6Tunnel6rdEntry 7 }

-- {TABLE} 1712.2.70.1.4
lcsSetupIpv6Tunnel6to4Table OBJECT-TYPE
    SYNTAX     SEQUENCE OF LcsSetupIpv6Tunnel6to4Entry
    MAX-ACCESS not-accessible
    STATUS     current
    DESCRIPTION
        "-- empty --"
    ::= { lcsSetupIpv6Tunnel 4 }

-- {ENTRY} 1712.2.70.1.4.1
lcsSetupIpv6Tunnel6to4Entry OBJECT-TYPE
    SYNTAX     LcsSetupIpv6Tunnel6to4Entry
    MAX-ACCESS not-accessible
    STATUS     current
    DESCRIPTION
        ""
    INDEX {
        lcsSetupIpv6Tunnel6to4EntryPeerName
    }
    ::= { lcsSetupIpv6Tunnel6to4Table 1 }

-- {SEQUENCE}
LcsSetupIpv6Tunnel6to4Entry ::= SEQUENCE {
    lcsSetupIpv6Tunnel6to4EntryPeerName DisplayString,
    lcsSetupIpv6Tunnel6to4EntryRtgTag INTEGER,
    lcsSetupIpv6Tunnel6to4EntryGatewayAddress DisplayString,
    lcsSetupIpv6Tunnel6to4EntryIpv4RtgTag INTEGER,
    lcsSetupIpv6Tunnel6to4EntryFirewall INTEGER
}

-- {COLUMN} 1712.2.70.1.4.1.1
lcsSetupIpv6Tunnel6to4EntryPeerName OBJECT-TYPE
    SYNTAX     DisplayString (SIZE(0..16))
    MAX-ACCESS read-write
    STATUS     current
    DESCRIPTION
        "-- empty --"
    ::= { lcsSetupIpv6Tunnel6to4Entry 1 }

-- {COLUMN} 1712.2.70.1.4.1.2
lcsSetupIpv6Tunnel6to4EntryRtgTag OBJECT-TYPE
    SYNTAX     INTEGER (0..65535)
    MAX-ACCESS read-write
    STATUS     current
    DESCRIPTION
        "-- empty --"
    ::= { lcsSetupIpv6Tunnel6to4Entry 2 }

-- {COLUMN} 1712.2.70.1.4.1.3
lcsSetupIpv6Tunnel6to4EntryGatewayAddress OBJECT-TYPE
    SYNTAX     DisplayString (SIZE(0..64))
    MAX-ACCESS read-write
    STATUS     current
    DESCRIPTION
        "-- empty --"
    ::= { lcsSetupIpv6Tunnel6to4Entry 3 }

-- {COLUMN} 1712.2.70.1.4.1.4
lcsSetupIpv6Tunnel6to4EntryIpv4RtgTag OBJECT-TYPE
    SYNTAX     INTEGER (0..65535)
    MAX-ACCESS read-write
    STATUS     current
    DESCRIPTION
        "-- empty --"
    ::= { lcsSetupIpv6Tunnel6to4Entry 4 }

-- {COLUMN} 1712.2.70.1.4.1.5
lcsSetupIpv6Tunnel6to4EntryFirewall OBJECT-TYPE
    SYNTAX     INTEGER
      {
        eYes (0),
        eNo (1)
      }
    MAX-ACCESS read-write
    STATUS     current
    DESCRIPTION
        "-- empty --"
    ::= { lcsSetupIpv6Tunnel6to4Entry 5 }

-- {OID} 1712.2.70.2
lcsSetupIpv6RouterAdv OBJECT IDENTIFIER ::= { lcsSetupIpv6 2 }

-- {TABLE} 1712.2.70.2.1
lcsSetupIpv6RouterAdvPrefixOptionsTable OBJECT-TYPE
    SYNTAX     SEQUENCE OF LcsSetupIpv6RouterAdvPrefixOptionsEntry
    MAX-ACCESS not-accessible
    STATUS     current
    DESCRIPTION
        "-- empty --"
    ::= { lcsSetupIpv6RouterAdv 1 }

-- {ENTRY} 1712.2.70.2.1.1
lcsSetupIpv6RouterAdvPrefixOptionsEntry OBJECT-TYPE
    SYNTAX     LcsSetupIpv6RouterAdvPrefixOptionsEntry
    MAX-ACCESS not-accessible
    STATUS     current
    DESCRIPTION
        ""
    INDEX {
        lcsSetupIpv6RouterAdvPrefixOptionsEntryInterfaceName,
        lcsSetupIpv6RouterAdvPrefixOptionsEntryPrefix
    }
    ::= { lcsSetupIpv6RouterAdvPrefixOptionsTable 1 }

-- {SEQUENCE}
LcsSetupIpv6RouterAdvPrefixOptionsEntry ::= SEQUENCE {
    lcsSetupIpv6RouterAdvPrefixOptionsEntryInterfaceName DisplayString,
    lcsSetupIpv6RouterAdvPrefixOptionsEntryPrefix DisplayString,
    lcsSetupIpv6RouterAdvPrefixOptionsEntrySubnetId DisplayString,
    lcsSetupIpv6RouterAdvPrefixOptionsEntryAdvOnlink INTEGER,
    lcsSetupIpv6RouterAdvPrefixOptionsEntryAdvAutonomous INTEGER,
    lcsSetupIpv6RouterAdvPrefixOptionsEntryPdSource DisplayString,
    lcsSetupIpv6RouterAdvPrefixOptionsEntryAdvPrefLifetime INTEGER,
    lcsSetupIpv6RouterAdvPrefixOptionsEntryAdvValidLifetime INTEGER,
    lcsSetupIpv6RouterAdvPrefixOptionsEntryDecrementlifetimes INTEGER
}

-- {COLUMN} 1712.2.70.2.1.1.1
lcsSetupIpv6RouterAdvPrefixOptionsEntryInterfaceName OBJECT-TYPE
    SYNTAX     DisplayString (SIZE(0..16))
    MAX-ACCESS read-write
    STATUS     current
    DESCRIPTION
        "-- empty --"
    ::= { lcsSetupIpv6RouterAdvPrefixOptionsEntry 1 }

-- {COLUMN} 1712.2.70.2.1.1.2
lcsSetupIpv6RouterAdvPrefixOptionsEntryPrefix OBJECT-TYPE
    SYNTAX     DisplayString (SIZE(0..43))
    MAX-ACCESS read-write
    STATUS     current
    DESCRIPTION
        "-- empty --"
    ::= { lcsSetupIpv6RouterAdvPrefixOptionsEntry 2 }

-- {COLUMN} 1712.2.70.2.1.1.3
lcsSetupIpv6RouterAdvPrefixOptionsEntrySubnetId OBJECT-TYPE
    SYNTAX     DisplayString (SIZE(0..19))
    MAX-ACCESS read-write
    STATUS     current
    DESCRIPTION
        "-- empty --"
    ::= { lcsSetupIpv6RouterAdvPrefixOptionsEntry 3 }

-- {COLUMN} 1712.2.70.2.1.1.4
lcsSetupIpv6RouterAdvPrefixOptionsEntryAdvOnlink OBJECT-TYPE
    SYNTAX     INTEGER
      {
        eYes (0),
        eNo (1)
      }
    MAX-ACCESS read-write
    STATUS     current
    DESCRIPTION
        "-- empty --"
    ::= { lcsSetupIpv6RouterAdvPrefixOptionsEntry 4 }

-- {COLUMN} 1712.2.70.2.1.1.5
lcsSetupIpv6RouterAdvPrefixOptionsEntryAdvAutonomous OBJECT-TYPE
    SYNTAX     INTEGER
      {
        eYes (0),
        eNo (1)
      }
    MAX-ACCESS read-write
    STATUS     current
    DESCRIPTION
        "-- empty --"
    ::= { lcsSetupIpv6RouterAdvPrefixOptionsEntry 5 }

-- {COLUMN} 1712.2.70.2.1.1.6
lcsSetupIpv6RouterAdvPrefixOptionsEntryPdSource OBJECT-TYPE
    SYNTAX     DisplayString (SIZE(0..16))
    MAX-ACCESS read-write
    STATUS     current
    DESCRIPTION
        "-- empty --"
    ::= { lcsSetupIpv6RouterAdvPrefixOptionsEntry 6 }

-- {COLUMN} 1712.2.70.2.1.1.7
lcsSetupIpv6RouterAdvPrefixOptionsEntryAdvPrefLifetime OBJECT-TYPE
    SYNTAX     INTEGER (0..2147483647)
    MAX-ACCESS read-write
    STATUS     current
    DESCRIPTION
        "-- empty --"
    ::= { lcsSetupIpv6RouterAdvPrefixOptionsEntry 7 }

-- {COLUMN} 1712.2.70.2.1.1.8
lcsSetupIpv6RouterAdvPrefixOptionsEntryAdvValidLifetime OBJECT-TYPE
    SYNTAX     INTEGER (0..2147483647)
    MAX-ACCESS read-write
    STATUS     current
    DESCRIPTION
        "-- empty --"
    ::= { lcsSetupIpv6RouterAdvPrefixOptionsEntry 8 }

-- {COLUMN} 1712.2.70.2.1.1.9
lcsSetupIpv6RouterAdvPrefixOptionsEntryDecrementlifetimes OBJECT-TYPE
    SYNTAX     INTEGER
      {
        eYes (0),
        eNo (1)
      }
    MAX-ACCESS read-write
    STATUS     current
    DESCRIPTION
        "-- empty --"
    ::= { lcsSetupIpv6RouterAdvPrefixOptionsEntry 9 }

-- {TABLE} 1712.2.70.2.2
lcsSetupIpv6RouterAdvInterfaceOptionsTable OBJECT-TYPE
    SYNTAX     SEQUENCE OF LcsSetupIpv6RouterAdvInterfaceOptionsEntry
    MAX-ACCESS not-accessible
    STATUS     current
    DESCRIPTION
        "-- empty --"
    ::= { lcsSetupIpv6RouterAdv 2 }

-- {ENTRY} 1712.2.70.2.2.1
lcsSetupIpv6RouterAdvInterfaceOptionsEntry OBJECT-TYPE
    SYNTAX     LcsSetupIpv6RouterAdvInterfaceOptionsEntry
    MAX-ACCESS not-accessible
    STATUS     current
    DESCRIPTION
        ""
    INDEX {
        lcsSetupIpv6RouterAdvInterfaceOptionsEntryInterfaceName
    }
    ::= { lcsSetupIpv6RouterAdvInterfaceOptionsTable 1 }

-- {SEQUENCE}
LcsSetupIpv6RouterAdvInterfaceOptionsEntry ::= SEQUENCE {
    lcsSetupIpv6RouterAdvInterfaceOptionsEntryInterfaceName DisplayString,
    lcsSetupIpv6RouterAdvInterfaceOptionsEntrySendAdverts INTEGER,
    lcsSetupIpv6RouterAdvInterfaceOptionsEntryMinRtrInterval INTEGER,
    lcsSetupIpv6RouterAdvInterfaceOptionsEntryMaxRtrInterval INTEGER,
    lcsSetupIpv6RouterAdvInterfaceOptionsEntryManagedFlag INTEGER,
    lcsSetupIpv6RouterAdvInterfaceOptionsEntryOtherConfigFlag INTEGER,
    lcsSetupIpv6RouterAdvInterfaceOptionsEntryLinkMtu INTEGER,
    lcsSetupIpv6RouterAdvInterfaceOptionsEntryReachableTime INTEGER,
    lcsSetupIpv6RouterAdvInterfaceOptionsEntryRtrTime INTEGER,
    lcsSetupIpv6RouterAdvInterfaceOptionsEntryCrtHopLimit INTEGER,
    lcsSetupIpv6RouterAdvInterfaceOptionsEntryDefaultLifetime INTEGER,
    lcsSetupIpv6RouterAdvInterfaceOptionsEntryDefaultRouterMode INTEGER,
    lcsSetupIpv6RouterAdvInterfaceOptionsEntryRouterPreference INTEGER
}

-- {COLUMN} 1712.2.70.2.2.1.1
lcsSetupIpv6RouterAdvInterfaceOptionsEntryInterfaceName OBJECT-TYPE
    SYNTAX     DisplayString (SIZE(0..16))
    MAX-ACCESS read-write
    STATUS     current
    DESCRIPTION
        "-- empty --"
    ::= { lcsSetupIpv6RouterAdvInterfaceOptionsEntry 1 }

-- {COLUMN} 1712.2.70.2.2.1.2
lcsSetupIpv6RouterAdvInterfaceOptionsEntrySendAdverts OBJECT-TYPE
    SYNTAX     INTEGER
      {
        eYes (0),
        eNo (1)
      }
    MAX-ACCESS read-write
    STATUS     current
    DESCRIPTION
        "-- empty --"
    ::= { lcsSetupIpv6RouterAdvInterfaceOptionsEntry 2 }

-- {COLUMN} 1712.2.70.2.2.1.3
lcsSetupIpv6RouterAdvInterfaceOptionsEntryMinRtrInterval OBJECT-TYPE
    SYNTAX     INTEGER (0..2147483647)
    MAX-ACCESS read-write
    STATUS     current
    DESCRIPTION
        "-- empty --"
    ::= { lcsSetupIpv6RouterAdvInterfaceOptionsEntry 3 }

-- {COLUMN} 1712.2.70.2.2.1.4
lcsSetupIpv6RouterAdvInterfaceOptionsEntryMaxRtrInterval OBJECT-TYPE
    SYNTAX     INTEGER (0..2147483647)
    MAX-ACCESS read-write
    STATUS     current
    DESCRIPTION
        "-- empty --"
    ::= { lcsSetupIpv6RouterAdvInterfaceOptionsEntry 4 }

-- {COLUMN} 1712.2.70.2.2.1.5
lcsSetupIpv6RouterAdvInterfaceOptionsEntryManagedFlag OBJECT-TYPE
    SYNTAX     INTEGER
      {
        eYes (0),
        eNo (1)
      }
    MAX-ACCESS read-write
    STATUS     current
    DESCRIPTION
        "-- empty --"
    ::= { lcsSetupIpv6RouterAdvInterfaceOptionsEntry 5 }

-- {COLUMN} 1712.2.70.2.2.1.6
lcsSetupIpv6RouterAdvInterfaceOptionsEntryOtherConfigFlag OBJECT-TYPE
    SYNTAX     INTEGER
      {
        eYes (0),
        eNo (1)
      }
    MAX-ACCESS read-write
    STATUS     current
    DESCRIPTION
        "-- empty --"
    ::= { lcsSetupIpv6RouterAdvInterfaceOptionsEntry 6 }

-- {COLUMN} 1712.2.70.2.2.1.7
lcsSetupIpv6RouterAdvInterfaceOptionsEntryLinkMtu OBJECT-TYPE
    SYNTAX     INTEGER (0..2147483647)
    MAX-ACCESS read-write
    STATUS     current
    DESCRIPTION
        "-- empty --"
    ::= { lcsSetupIpv6RouterAdvInterfaceOptionsEntry 7 }

-- {COLUMN} 1712.2.70.2.2.1.8
lcsSetupIpv6RouterAdvInterfaceOptionsEntryReachableTime OBJECT-TYPE
    SYNTAX     INTEGER (0..2147483647)
    MAX-ACCESS read-write
    STATUS     current
    DESCRIPTION
        "-- empty --"
    ::= { lcsSetupIpv6RouterAdvInterfaceOptionsEntry 8 }

-- {COLUMN} 1712.2.70.2.2.1.14
lcsSetupIpv6RouterAdvInterfaceOptionsEntryRtrTime OBJECT-TYPE
    SYNTAX     INTEGER (0..2147483647)
    MAX-ACCESS read-write
    STATUS     current
    DESCRIPTION
        "-- empty --"
    ::= { lcsSetupIpv6RouterAdvInterfaceOptionsEntry 14 }

-- {COLUMN} 1712.2.70.2.2.1.10
lcsSetupIpv6RouterAdvInterfaceOptionsEntryCrtHopLimit OBJECT-TYPE
    SYNTAX     INTEGER (0..2147483647)
    MAX-ACCESS read-write
    STATUS     current
    DESCRIPTION
        "-- empty --"
    ::= { lcsSetupIpv6RouterAdvInterfaceOptionsEntry 10 }

-- {COLUMN} 1712.2.70.2.2.1.11
lcsSetupIpv6RouterAdvInterfaceOptionsEntryDefaultLifetime OBJECT-TYPE
    SYNTAX     INTEGER (0..2147483647)
    MAX-ACCESS read-write
    STATUS     current
    DESCRIPTION
        "-- empty --"
    ::= { lcsSetupIpv6RouterAdvInterfaceOptionsEntry 11 }

-- {COLUMN} 1712.2.70.2.2.1.12
lcsSetupIpv6RouterAdvInterfaceOptionsEntryDefaultRouterMode OBJECT-TYPE
    SYNTAX     INTEGER
      {
        eAuto (0),
        eAlways (1),
        eNever (2)
      }
    MAX-ACCESS read-write
    STATUS     current
    DESCRIPTION
        "-- empty --"
    ::= { lcsSetupIpv6RouterAdvInterfaceOptionsEntry 12 }

-- {COLUMN} 1712.2.70.2.2.1.13
lcsSetupIpv6RouterAdvInterfaceOptionsEntryRouterPreference OBJECT-TYPE
    SYNTAX     INTEGER
      {
        eLow (2),
        eMedium (0),
        eHigh (1)
      }
    MAX-ACCESS read-write
    STATUS     current
    DESCRIPTION
        "-- empty --"
    ::= { lcsSetupIpv6RouterAdvInterfaceOptionsEntry 13 }

-- {TABLE} 1712.2.70.2.3
lcsSetupIpv6RouterAdvRouteOptionsTable OBJECT-TYPE
    SYNTAX     SEQUENCE OF LcsSetupIpv6RouterAdvRouteOptionsEntry
    MAX-ACCESS not-accessible
    STATUS     current
    DESCRIPTION
        "-- empty --"
    ::= { lcsSetupIpv6RouterAdv 3 }

-- {ENTRY} 1712.2.70.2.3.1
lcsSetupIpv6RouterAdvRouteOptionsEntry OBJECT-TYPE
    SYNTAX     LcsSetupIpv6RouterAdvRouteOptionsEntry
    MAX-ACCESS not-accessible
    STATUS     current
    DESCRIPTION
        ""
    INDEX {
        lcsSetupIpv6RouterAdvRouteOptionsEntryInterfaceName,
        lcsSetupIpv6RouterAdvRouteOptionsEntryPrefix
    }
    ::= { lcsSetupIpv6RouterAdvRouteOptionsTable 1 }

-- {SEQUENCE}
LcsSetupIpv6RouterAdvRouteOptionsEntry ::= SEQUENCE {
    lcsSetupIpv6RouterAdvRouteOptionsEntryInterfaceName DisplayString,
    lcsSetupIpv6RouterAdvRouteOptionsEntryPrefix DisplayString,
    lcsSetupIpv6RouterAdvRouteOptionsEntryRouteLifetime INTEGER,
    lcsSetupIpv6RouterAdvRouteOptionsEntryRoutePreference INTEGER
}

-- {COLUMN} 1712.2.70.2.3.1.1
lcsSetupIpv6RouterAdvRouteOptionsEntryInterfaceName OBJECT-TYPE
    SYNTAX     DisplayString (SIZE(0..16))
    MAX-ACCESS read-write
    STATUS     current
    DESCRIPTION
        "-- empty --"
    ::= { lcsSetupIpv6RouterAdvRouteOptionsEntry 1 }

-- {COLUMN} 1712.2.70.2.3.1.2
lcsSetupIpv6RouterAdvRouteOptionsEntryPrefix OBJECT-TYPE
    SYNTAX     DisplayString (SIZE(0..43))
    MAX-ACCESS read-write
    STATUS     current
    DESCRIPTION
        "-- empty --"
    ::= { lcsSetupIpv6RouterAdvRouteOptionsEntry 2 }

-- {COLUMN} 1712.2.70.2.3.1.3
lcsSetupIpv6RouterAdvRouteOptionsEntryRouteLifetime OBJECT-TYPE
    SYNTAX     INTEGER (0..2147483647)
    MAX-ACCESS read-write
    STATUS     current
    DESCRIPTION
        "-- empty --"
    ::= { lcsSetupIpv6RouterAdvRouteOptionsEntry 3 }

-- {COLUMN} 1712.2.70.2.3.1.4
lcsSetupIpv6RouterAdvRouteOptionsEntryRoutePreference OBJECT-TYPE
    SYNTAX     INTEGER
      {
        eLow (2),
        eMedium (0),
        eHigh (1)
      }
    MAX-ACCESS read-write
    STATUS     current
    DESCRIPTION
        "-- empty --"
    ::= { lcsSetupIpv6RouterAdvRouteOptionsEntry 4 }

-- {TABLE} 1712.2.70.2.5
lcsSetupIpv6RouterAdvRdnssOptionsTable OBJECT-TYPE
    SYNTAX     SEQUENCE OF LcsSetupIpv6RouterAdvRdnssOptionsEntry
    MAX-ACCESS not-accessible
    STATUS     current
    DESCRIPTION
        "-- empty --"
    ::= { lcsSetupIpv6RouterAdv 5 }

-- {ENTRY} 1712.2.70.2.5.1
lcsSetupIpv6RouterAdvRdnssOptionsEntry OBJECT-TYPE
    SYNTAX     LcsSetupIpv6RouterAdvRdnssOptionsEntry
    MAX-ACCESS not-accessible
    STATUS     current
    DESCRIPTION
        ""
    INDEX {
        lcsSetupIpv6RouterAdvRdnssOptionsEntryInterfaceName
    }
    ::= { lcsSetupIpv6RouterAdvRdnssOptionsTable 1 }

-- {SEQUENCE}
LcsSetupIpv6RouterAdvRdnssOptionsEntry ::= SEQUENCE {
    lcsSetupIpv6RouterAdvRdnssOptionsEntryInterfaceName DisplayString,
    lcsSetupIpv6RouterAdvRdnssOptionsEntryPrimaryDns DisplayString,
    lcsSetupIpv6RouterAdvRdnssOptionsEntrySecondaryDns DisplayString,
    lcsSetupIpv6RouterAdvRdnssOptionsEntryDnsSearchList BITS,
    lcsSetupIpv6RouterAdvRdnssOptionsEntryLifetime INTEGER
}

-- {COLUMN} 1712.2.70.2.5.1.1
lcsSetupIpv6RouterAdvRdnssOptionsEntryInterfaceName OBJECT-TYPE
    SYNTAX     DisplayString (SIZE(0..16))
    MAX-ACCESS read-write
    STATUS     current
    DESCRIPTION
        "-- empty --"
    ::= { lcsSetupIpv6RouterAdvRdnssOptionsEntry 1 }

-- {COLUMN} 1712.2.70.2.5.1.2
lcsSetupIpv6RouterAdvRdnssOptionsEntryPrimaryDns OBJECT-TYPE
    SYNTAX     DisplayString (SIZE(0..39))
    MAX-ACCESS read-write
    STATUS     current
    DESCRIPTION
        "-- empty --"
    ::= { lcsSetupIpv6RouterAdvRdnssOptionsEntry 2 }

-- {COLUMN} 1712.2.70.2.5.1.3
lcsSetupIpv6RouterAdvRdnssOptionsEntrySecondaryDns OBJECT-TYPE
    SYNTAX     DisplayString (SIZE(0..39))
    MAX-ACCESS read-write
    STATUS     current
    DESCRIPTION
        "-- empty --"
    ::= { lcsSetupIpv6RouterAdvRdnssOptionsEntry 3 }

-- {COLUMN} 1712.2.70.2.5.1.4
lcsSetupIpv6RouterAdvRdnssOptionsEntryDnsSearchList OBJECT-TYPE
    SYNTAX     BITS
      {
        eInternal (7),
        eWan (6)
      }
    MAX-ACCESS read-write
    STATUS     current
    DESCRIPTION
        "-- empty --"
    ::= { lcsSetupIpv6RouterAdvRdnssOptionsEntry 4 }

-- {COLUMN} 1712.2.70.2.5.1.5
lcsSetupIpv6RouterAdvRdnssOptionsEntryLifetime OBJECT-TYPE
    SYNTAX     INTEGER (0..2147483647)
    MAX-ACCESS read-write
    STATUS     current
    DESCRIPTION
        "-- empty --"
    ::= { lcsSetupIpv6RouterAdvRdnssOptionsEntry 5 }

-- {TABLE} 1712.2.70.2.6
lcsSetupIpv6RouterAdvPrefixPoolsTable OBJECT-TYPE
    SYNTAX     SEQUENCE OF LcsSetupIpv6RouterAdvPrefixPoolsEntry
    MAX-ACCESS not-accessible
    STATUS     current
    DESCRIPTION
        "-- empty --"
    ::= { lcsSetupIpv6RouterAdv 6 }

-- {ENTRY} 1712.2.70.2.6.1
lcsSetupIpv6RouterAdvPrefixPoolsEntry OBJECT-TYPE
    SYNTAX     LcsSetupIpv6RouterAdvPrefixPoolsEntry
    MAX-ACCESS not-accessible
    STATUS     current
    DESCRIPTION
        ""
    INDEX {
        lcsSetupIpv6RouterAdvPrefixPoolsEntryInterfaceName,
        lcsSetupIpv6RouterAdvPrefixPoolsEntryStartPrefixPool
    }
    ::= { lcsSetupIpv6RouterAdvPrefixPoolsTable 1 }

-- {SEQUENCE}
LcsSetupIpv6RouterAdvPrefixPoolsEntry ::= SEQUENCE {
    lcsSetupIpv6RouterAdvPrefixPoolsEntryInterfaceName DisplayString,
    lcsSetupIpv6RouterAdvPrefixPoolsEntryStartPrefixPool DisplayString,
    lcsSetupIpv6RouterAdvPrefixPoolsEntryEndPrefixPool DisplayString,
    lcsSetupIpv6RouterAdvPrefixPoolsEntryPrefixLength INTEGER,
    lcsSetupIpv6RouterAdvPrefixPoolsEntryAdvOnlink INTEGER,
    lcsSetupIpv6RouterAdvPrefixPoolsEntryAdvAutonomous INTEGER,
    lcsSetupIpv6RouterAdvPrefixPoolsEntryAdvPrefLifetime INTEGER,
    lcsSetupIpv6RouterAdvPrefixPoolsEntryAdvValidLifetime INTEGER
}

-- {COLUMN} 1712.2.70.2.6.1.1
lcsSetupIpv6RouterAdvPrefixPoolsEntryInterfaceName OBJECT-TYPE
    SYNTAX     DisplayString (SIZE(0..16))
    MAX-ACCESS read-write
    STATUS     current
    DESCRIPTION
        "-- empty --"
    ::= { lcsSetupIpv6RouterAdvPrefixPoolsEntry 1 }

-- {COLUMN} 1712.2.70.2.6.1.2
lcsSetupIpv6RouterAdvPrefixPoolsEntryStartPrefixPool OBJECT-TYPE
    SYNTAX     DisplayString (SIZE(0..43))
    MAX-ACCESS read-write
    STATUS     current
    DESCRIPTION
        "-- empty --"
    ::= { lcsSetupIpv6RouterAdvPrefixPoolsEntry 2 }

-- {COLUMN} 1712.2.70.2.6.1.3
lcsSetupIpv6RouterAdvPrefixPoolsEntryEndPrefixPool OBJECT-TYPE
    SYNTAX     DisplayString (SIZE(0..43))
    MAX-ACCESS read-write
    STATUS     current
    DESCRIPTION
        "-- empty --"
    ::= { lcsSetupIpv6RouterAdvPrefixPoolsEntry 3 }

-- {COLUMN} 1712.2.70.2.6.1.4
lcsSetupIpv6RouterAdvPrefixPoolsEntryPrefixLength OBJECT-TYPE
    SYNTAX     INTEGER (0..255)
    MAX-ACCESS read-write
    STATUS     current
    DESCRIPTION
        "-- empty --"
    ::= { lcsSetupIpv6RouterAdvPrefixPoolsEntry 4 }

-- {COLUMN} 1712.2.70.2.6.1.5
lcsSetupIpv6RouterAdvPrefixPoolsEntryAdvOnlink OBJECT-TYPE
    SYNTAX     INTEGER
      {
        eYes (0),
        eNo (1)
      }
    MAX-ACCESS read-write
    STATUS     current
    DESCRIPTION
        "-- empty --"
    ::= { lcsSetupIpv6RouterAdvPrefixPoolsEntry 5 }

-- {COLUMN} 1712.2.70.2.6.1.6
lcsSetupIpv6RouterAdvPrefixPoolsEntryAdvAutonomous OBJECT-TYPE
    SYNTAX     INTEGER
      {
        eYes (0),
        eNo (1)
      }
    MAX-ACCESS read-write
    STATUS     current
    DESCRIPTION
        "-- empty --"
    ::= { lcsSetupIpv6RouterAdvPrefixPoolsEntry 6 }

-- {COLUMN} 1712.2.70.2.6.1.7
lcsSetupIpv6RouterAdvPrefixPoolsEntryAdvPrefLifetime OBJECT-TYPE
    SYNTAX     INTEGER (0..2147483647)
    MAX-ACCESS read-write
    STATUS     current
    DESCRIPTION
        "-- empty --"
    ::= { lcsSetupIpv6RouterAdvPrefixPoolsEntry 7 }

-- {COLUMN} 1712.2.70.2.6.1.8
lcsSetupIpv6RouterAdvPrefixPoolsEntryAdvValidLifetime OBJECT-TYPE
    SYNTAX     INTEGER (0..2147483647)
    MAX-ACCESS read-write
    STATUS     current
    DESCRIPTION
        "-- empty --"
    ::= { lcsSetupIpv6RouterAdvPrefixPoolsEntry 8 }

-- {OID} 1712.2.70.3
lcsSetupIpv6Dhcpv6 OBJECT IDENTIFIER ::= { lcsSetupIpv6 3 }

-- {OID} 1712.2.70.3.1
lcsSetupIpv6Dhcpv6Server OBJECT IDENTIFIER ::= { lcsSetupIpv6Dhcpv6 1 }

-- {TABLE} 1712.2.70.3.1.4
lcsSetupIpv6Dhcpv6ServerIfcListTable OBJECT-TYPE
    SYNTAX     SEQUENCE OF LcsSetupIpv6Dhcpv6ServerIfcListEntry
    MAX-ACCESS not-accessible
    STATUS     current
    DESCRIPTION
        ""
    ::= { lcsSetupIpv6Dhcpv6Server 4 }

-- {ENTRY} 1712.2.70.3.1.4.1
lcsSetupIpv6Dhcpv6ServerIfcListEntry OBJECT-TYPE
    SYNTAX     LcsSetupIpv6Dhcpv6ServerIfcListEntry
    MAX-ACCESS not-accessible
    STATUS     current
    DESCRIPTION
        ""
    INDEX {
        lcsSetupIpv6Dhcpv6ServerIfcListEntryInterfaceNameOrRelay
    }
    ::= { lcsSetupIpv6Dhcpv6ServerIfcListTable 1 }

-- {SEQUENCE}
LcsSetupIpv6Dhcpv6ServerIfcListEntry ::= SEQUENCE {
    lcsSetupIpv6Dhcpv6ServerIfcListEntryInterfaceNameOrRelay DisplayString,
    lcsSetupIpv6Dhcpv6ServerIfcListEntryOperating INTEGER,
    lcsSetupIpv6Dhcpv6ServerIfcListEntryPrimaryDns DisplayString,
    lcsSetupIpv6Dhcpv6ServerIfcListEntrySecondaryDns DisplayString,
    lcsSetupIpv6Dhcpv6ServerIfcListEntryDnsSearchList BITS,
    lcsSetupIpv6Dhcpv6ServerIfcListEntryAddressPoolName DisplayString,
    lcsSetupIpv6Dhcpv6ServerIfcListEntryPdPoolName DisplayString,
    lcsSetupIpv6Dhcpv6ServerIfcListEntryRapidCommit INTEGER,
    lcsSetupIpv6Dhcpv6ServerIfcListEntryPreference INTEGER,
    lcsSetupIpv6Dhcpv6ServerIfcListEntryRenewTime INTEGER,
    lcsSetupIpv6Dhcpv6ServerIfcListEntryRebindTime INTEGER,
    lcsSetupIpv6Dhcpv6ServerIfcListEntryUnicastAddress DisplayString,
    lcsSetupIpv6Dhcpv6ServerIfcListEntryReconfigure INTEGER
}

-- {COLUMN} 1712.2.70.3.1.4.1.1
lcsSetupIpv6Dhcpv6ServerIfcListEntryInterfaceNameOrRelay OBJECT-TYPE
    SYNTAX     DisplayString (SIZE(0..39))
    MAX-ACCESS read-write
    STATUS     current
    DESCRIPTION
        "-- empty --"
    ::= { lcsSetupIpv6Dhcpv6ServerIfcListEntry 1 }

-- {COLUMN} 1712.2.70.3.1.4.1.2
lcsSetupIpv6Dhcpv6ServerIfcListEntryOperating OBJECT-TYPE
    SYNTAX     INTEGER
      {
        eNo (0),
        eYes (1)
      }
    MAX-ACCESS read-write
    STATUS     current
    DESCRIPTION
        "-- empty --"
    ::= { lcsSetupIpv6Dhcpv6ServerIfcListEntry 2 }

-- {COLUMN} 1712.2.70.3.1.4.1.3
lcsSetupIpv6Dhcpv6ServerIfcListEntryPrimaryDns OBJECT-TYPE
    SYNTAX     DisplayString (SIZE(0..39))
    MAX-ACCESS read-write
    STATUS     current
    DESCRIPTION
        "-- empty --"
    ::= { lcsSetupIpv6Dhcpv6ServerIfcListEntry 3 }

-- {COLUMN} 1712.2.70.3.1.4.1.4
lcsSetupIpv6Dhcpv6ServerIfcListEntrySecondaryDns OBJECT-TYPE
    SYNTAX     DisplayString (SIZE(0..39))
    MAX-ACCESS read-write
    STATUS     current
    DESCRIPTION
        "-- empty --"
    ::= { lcsSetupIpv6Dhcpv6ServerIfcListEntry 4 }

-- {COLUMN} 1712.2.70.3.1.4.1.12
lcsSetupIpv6Dhcpv6ServerIfcListEntryDnsSearchList OBJECT-TYPE
    SYNTAX     BITS
      {
        eInternal (7),
        eWan (6)
      }
    MAX-ACCESS read-write
    STATUS     current
    DESCRIPTION
        "-- empty --"
    ::= { lcsSetupIpv6Dhcpv6ServerIfcListEntry 12 }

-- {COLUMN} 1712.2.70.3.1.4.1.5
lcsSetupIpv6Dhcpv6ServerIfcListEntryAddressPoolName OBJECT-TYPE
    SYNTAX     DisplayString (SIZE(0..31))
    MAX-ACCESS read-write
    STATUS     current
    DESCRIPTION
        "-- empty --"
    ::= { lcsSetupIpv6Dhcpv6ServerIfcListEntry 5 }

-- {COLUMN} 1712.2.70.3.1.4.1.6
lcsSetupIpv6Dhcpv6ServerIfcListEntryPdPoolName OBJECT-TYPE
    SYNTAX     DisplayString (SIZE(0..31))
    MAX-ACCESS read-write
    STATUS     current
    DESCRIPTION
        "-- empty --"
    ::= { lcsSetupIpv6Dhcpv6ServerIfcListEntry 6 }

-- {COLUMN} 1712.2.70.3.1.4.1.7
lcsSetupIpv6Dhcpv6ServerIfcListEntryRapidCommit OBJECT-TYPE
    SYNTAX     INTEGER
      {
        eNo (0),
        eYes (1)
      }
    MAX-ACCESS read-write
    STATUS     current
    DESCRIPTION
        "-- empty --"
    ::= { lcsSetupIpv6Dhcpv6ServerIfcListEntry 7 }

-- {COLUMN} 1712.2.70.3.1.4.1.8
lcsSetupIpv6Dhcpv6ServerIfcListEntryPreference OBJECT-TYPE
    SYNTAX     INTEGER (0..255)
    MAX-ACCESS read-write
    STATUS     current
    DESCRIPTION
        "-- empty --"
    ::= { lcsSetupIpv6Dhcpv6ServerIfcListEntry 8 }

-- {COLUMN} 1712.2.70.3.1.4.1.9
lcsSetupIpv6Dhcpv6ServerIfcListEntryRenewTime OBJECT-TYPE
    SYNTAX     INTEGER (0..2147483647)
    MAX-ACCESS read-write
    STATUS     current
    DESCRIPTION
        "-- empty --"
    ::= { lcsSetupIpv6Dhcpv6ServerIfcListEntry 9 }

-- {COLUMN} 1712.2.70.3.1.4.1.10
lcsSetupIpv6Dhcpv6ServerIfcListEntryRebindTime OBJECT-TYPE
    SYNTAX     INTEGER (0..2147483647)
    MAX-ACCESS read-write
    STATUS     current
    DESCRIPTION
        "-- empty --"
    ::= { lcsSetupIpv6Dhcpv6ServerIfcListEntry 10 }

-- {COLUMN} 1712.2.70.3.1.4.1.11
lcsSetupIpv6Dhcpv6ServerIfcListEntryUnicastAddress OBJECT-TYPE
    SYNTAX     DisplayString (SIZE(0..39))
    MAX-ACCESS read-write
    STATUS     current
    DESCRIPTION
        "-- empty --"
    ::= { lcsSetupIpv6Dhcpv6ServerIfcListEntry 11 }

-- {COLUMN} 1712.2.70.3.1.4.1.13
lcsSetupIpv6Dhcpv6ServerIfcListEntryReconfigure OBJECT-TYPE
    SYNTAX     INTEGER
      {
        eOff (0),
        eReject (1),
        eAllow (2),
        eRequire (3)
      }
    MAX-ACCESS read-write
    STATUS     current
    DESCRIPTION
        "-- empty --"
    ::= { lcsSetupIpv6Dhcpv6ServerIfcListEntry 13 }

-- {TABLE} 1712.2.70.3.1.2
lcsSetupIpv6Dhcpv6ServerAddressPoolsTable OBJECT-TYPE
    SYNTAX     SEQUENCE OF LcsSetupIpv6Dhcpv6ServerAddressPoolsEntry
    MAX-ACCESS not-accessible
    STATUS     current
    DESCRIPTION
        "-- empty --"
    ::= { lcsSetupIpv6Dhcpv6Server 2 }

-- {ENTRY} 1712.2.70.3.1.2.1
lcsSetupIpv6Dhcpv6ServerAddressPoolsEntry OBJECT-TYPE
    SYNTAX     LcsSetupIpv6Dhcpv6ServerAddressPoolsEntry
    MAX-ACCESS not-accessible
    STATUS     current
    DESCRIPTION
        ""
    INDEX {
        lcsSetupIpv6Dhcpv6ServerAddressPoolsEntryAddressPoolName,
        lcsSetupIpv6Dhcpv6ServerAddressPoolsEntryStartAddressPool,
        lcsSetupIpv6Dhcpv6ServerAddressPoolsEntryPdSource
    }
    ::= { lcsSetupIpv6Dhcpv6ServerAddressPoolsTable 1 }

-- {SEQUENCE}
LcsSetupIpv6Dhcpv6ServerAddressPoolsEntry ::= SEQUENCE {
    lcsSetupIpv6Dhcpv6ServerAddressPoolsEntryAddressPoolName DisplayString,
    lcsSetupIpv6Dhcpv6ServerAddressPoolsEntryStartAddressPool DisplayString,
    lcsSetupIpv6Dhcpv6ServerAddressPoolsEntryPdSource DisplayString,
    lcsSetupIpv6Dhcpv6ServerAddressPoolsEntryEndAddressPool DisplayString,
    lcsSetupIpv6Dhcpv6ServerAddressPoolsEntryPrefLifetime INTEGER,
    lcsSetupIpv6Dhcpv6ServerAddressPoolsEntryValidLifetime INTEGER
}

-- {COLUMN} 1712.2.70.3.1.2.1.1
lcsSetupIpv6Dhcpv6ServerAddressPoolsEntryAddressPoolName OBJECT-TYPE
    SYNTAX     DisplayString (SIZE(0..31))
    MAX-ACCESS read-write
    STATUS     current
    DESCRIPTION
        "-- empty --"
    ::= { lcsSetupIpv6Dhcpv6ServerAddressPoolsEntry 1 }

-- {COLUMN} 1712.2.70.3.1.2.1.2
lcsSetupIpv6Dhcpv6ServerAddressPoolsEntryStartAddressPool OBJECT-TYPE
    SYNTAX     DisplayString (SIZE(0..39))
    MAX-ACCESS read-write
    STATUS     current
    DESCRIPTION
        "-- empty --"
    ::= { lcsSetupIpv6Dhcpv6ServerAddressPoolsEntry 2 }

-- {COLUMN} 1712.2.70.3.1.2.1.7
lcsSetupIpv6Dhcpv6ServerAddressPoolsEntryPdSource OBJECT-TYPE
    SYNTAX     DisplayString (SIZE(0..16))
    MAX-ACCESS read-write
    STATUS     current
    DESCRIPTION
        "-- empty --"
    ::= { lcsSetupIpv6Dhcpv6ServerAddressPoolsEntry 7 }

-- {COLUMN} 1712.2.70.3.1.2.1.3
lcsSetupIpv6Dhcpv6ServerAddressPoolsEntryEndAddressPool OBJECT-TYPE
    SYNTAX     DisplayString (SIZE(0..39))
    MAX-ACCESS read-write
    STATUS     current
    DESCRIPTION
        "-- empty --"
    ::= { lcsSetupIpv6Dhcpv6ServerAddressPoolsEntry 3 }

-- {COLUMN} 1712.2.70.3.1.2.1.5
lcsSetupIpv6Dhcpv6ServerAddressPoolsEntryPrefLifetime OBJECT-TYPE
    SYNTAX     INTEGER (0..2147483647)
    MAX-ACCESS read-write
    STATUS     current
    DESCRIPTION
        "-- empty --"
    ::= { lcsSetupIpv6Dhcpv6ServerAddressPoolsEntry 5 }

-- {COLUMN} 1712.2.70.3.1.2.1.6
lcsSetupIpv6Dhcpv6ServerAddressPoolsEntryValidLifetime OBJECT-TYPE
    SYNTAX     INTEGER (0..2147483647)
    MAX-ACCESS read-write
    STATUS     current
    DESCRIPTION
        "-- empty --"
    ::= { lcsSetupIpv6Dhcpv6ServerAddressPoolsEntry 6 }

-- {TABLE} 1712.2.70.3.1.3
lcsSetupIpv6Dhcpv6ServerPdPoolsTable OBJECT-TYPE
    SYNTAX     SEQUENCE OF LcsSetupIpv6Dhcpv6ServerPdPoolsEntry
    MAX-ACCESS not-accessible
    STATUS     current
    DESCRIPTION
        "-- empty --"
    ::= { lcsSetupIpv6Dhcpv6Server 3 }

-- {ENTRY} 1712.2.70.3.1.3.1
lcsSetupIpv6Dhcpv6ServerPdPoolsEntry OBJECT-TYPE
    SYNTAX     LcsSetupIpv6Dhcpv6ServerPdPoolsEntry
    MAX-ACCESS not-accessible
    STATUS     current
    DESCRIPTION
        ""
    INDEX {
        lcsSetupIpv6Dhcpv6ServerPdPoolsEntryPdPoolName,
        lcsSetupIpv6Dhcpv6ServerPdPoolsEntryStartPdPool,
        lcsSetupIpv6Dhcpv6ServerPdPoolsEntryPdSource
    }
    ::= { lcsSetupIpv6Dhcpv6ServerPdPoolsTable 1 }

-- {SEQUENCE}
LcsSetupIpv6Dhcpv6ServerPdPoolsEntry ::= SEQUENCE {
    lcsSetupIpv6Dhcpv6ServerPdPoolsEntryPdPoolName DisplayString,
    lcsSetupIpv6Dhcpv6ServerPdPoolsEntryStartPdPool DisplayString,
    lcsSetupIpv6Dhcpv6ServerPdPoolsEntryPdSource DisplayString,
    lcsSetupIpv6Dhcpv6ServerPdPoolsEntryEndPdPool DisplayString,
    lcsSetupIpv6Dhcpv6ServerPdPoolsEntryPrefixLength INTEGER,
    lcsSetupIpv6Dhcpv6ServerPdPoolsEntryPrefLifetime INTEGER,
    lcsSetupIpv6Dhcpv6ServerPdPoolsEntryValidLifetime INTEGER
}

-- {COLUMN} 1712.2.70.3.1.3.1.1
lcsSetupIpv6Dhcpv6ServerPdPoolsEntryPdPoolName OBJECT-TYPE
    SYNTAX     DisplayString (SIZE(0..31))
    MAX-ACCESS read-write
    STATUS     current
    DESCRIPTION
        "-- empty --"
    ::= { lcsSetupIpv6Dhcpv6ServerPdPoolsEntry 1 }

-- {COLUMN} 1712.2.70.3.1.3.1.2
lcsSetupIpv6Dhcpv6ServerPdPoolsEntryStartPdPool OBJECT-TYPE
    SYNTAX     DisplayString (SIZE(0..39))
    MAX-ACCESS read-write
    STATUS     current
    DESCRIPTION
        "-- empty --"
    ::= { lcsSetupIpv6Dhcpv6ServerPdPoolsEntry 2 }

-- {COLUMN} 1712.2.70.3.1.3.1.7
lcsSetupIpv6Dhcpv6ServerPdPoolsEntryPdSource OBJECT-TYPE
    SYNTAX     DisplayString (SIZE(0..16))
    MAX-ACCESS read-write
    STATUS     current
    DESCRIPTION
        "-- empty --"
    ::= { lcsSetupIpv6Dhcpv6ServerPdPoolsEntry 7 }

-- {COLUMN} 1712.2.70.3.1.3.1.3
lcsSetupIpv6Dhcpv6ServerPdPoolsEntryEndPdPool OBJECT-TYPE
    SYNTAX     DisplayString (SIZE(0..39))
    MAX-ACCESS read-write
    STATUS     current
    DESCRIPTION
        "-- empty --"
    ::= { lcsSetupIpv6Dhcpv6ServerPdPoolsEntry 3 }

-- {COLUMN} 1712.2.70.3.1.3.1.4
lcsSetupIpv6Dhcpv6ServerPdPoolsEntryPrefixLength OBJECT-TYPE
    SYNTAX     INTEGER (0..255)
    MAX-ACCESS read-write
    STATUS     current
    DESCRIPTION
        "-- empty --"
    ::= { lcsSetupIpv6Dhcpv6ServerPdPoolsEntry 4 }

-- {COLUMN} 1712.2.70.3.1.3.1.5
lcsSetupIpv6Dhcpv6ServerPdPoolsEntryPrefLifetime OBJECT-TYPE
    SYNTAX     INTEGER (0..2147483647)
    MAX-ACCESS read-write
    STATUS     current
    DESCRIPTION
        "-- empty --"
    ::= { lcsSetupIpv6Dhcpv6ServerPdPoolsEntry 5 }

-- {COLUMN} 1712.2.70.3.1.3.1.6
lcsSetupIpv6Dhcpv6ServerPdPoolsEntryValidLifetime OBJECT-TYPE
    SYNTAX     INTEGER (0..2147483647)
    MAX-ACCESS read-write
    STATUS     current
    DESCRIPTION
        "-- empty --"
    ::= { lcsSetupIpv6Dhcpv6ServerPdPoolsEntry 6 }

-- {TABLE} 1712.2.70.3.1.6
lcsSetupIpv6Dhcpv6ServerReservationsTable OBJECT-TYPE
    SYNTAX     SEQUENCE OF LcsSetupIpv6Dhcpv6ServerReservationsEntry
    MAX-ACCESS not-accessible
    STATUS     current
    DESCRIPTION
        "-- empty --"
    ::= { lcsSetupIpv6Dhcpv6Server 6 }

-- {ENTRY} 1712.2.70.3.1.6.1
lcsSetupIpv6Dhcpv6ServerReservationsEntry OBJECT-TYPE
    SYNTAX     LcsSetupIpv6Dhcpv6ServerReservationsEntry
    MAX-ACCESS not-accessible
    STATUS     current
    DESCRIPTION
        ""
    INDEX {
        lcsSetupIpv6Dhcpv6ServerReservationsEntryInterfaceNameOrRelay,
        lcsSetupIpv6Dhcpv6ServerReservationsEntryAddressOrPdPrefix,
        lcsSetupIpv6Dhcpv6ServerReservationsEntryPdSource
    }
    ::= { lcsSetupIpv6Dhcpv6ServerReservationsTable 1 }

-- {SEQUENCE}
LcsSetupIpv6Dhcpv6ServerReservationsEntry ::= SEQUENCE {
    lcsSetupIpv6Dhcpv6ServerReservationsEntryInterfaceNameOrRelay DisplayString,
    lcsSetupIpv6Dhcpv6ServerReservationsEntryAddressOrPdPrefix DisplayString,
    lcsSetupIpv6Dhcpv6ServerReservationsEntryPdSource DisplayString,
    lcsSetupIpv6Dhcpv6ServerReservationsEntryClientId DisplayString,
    lcsSetupIpv6Dhcpv6ServerReservationsEntryPrefLifetime INTEGER,
    lcsSetupIpv6Dhcpv6ServerReservationsEntryValidLifetime INTEGER
}

-- {COLUMN} 1712.2.70.3.1.6.1.1
lcsSetupIpv6Dhcpv6ServerReservationsEntryInterfaceNameOrRelay OBJECT-TYPE
    SYNTAX     DisplayString (SIZE(0..39))
    MAX-ACCESS read-write
    STATUS     current
    DESCRIPTION
        "-- empty --"
    ::= { lcsSetupIpv6Dhcpv6ServerReservationsEntry 1 }

-- {COLUMN} 1712.2.70.3.1.6.1.2
lcsSetupIpv6Dhcpv6ServerReservationsEntryAddressOrPdPrefix OBJECT-TYPE
    SYNTAX     DisplayString (SIZE(0..43))
    MAX-ACCESS read-write
    STATUS     current
    DESCRIPTION
        "-- empty --"
    ::= { lcsSetupIpv6Dhcpv6ServerReservationsEntry 2 }

-- {COLUMN} 1712.2.70.3.1.6.1.7
lcsSetupIpv6Dhcpv6ServerReservationsEntryPdSource OBJECT-TYPE
    SYNTAX     DisplayString (SIZE(0..16))
    MAX-ACCESS read-write
    STATUS     current
    DESCRIPTION
        "-- empty --"
    ::= { lcsSetupIpv6Dhcpv6ServerReservationsEntry 7 }

-- {COLUMN} 1712.2.70.3.1.6.1.3
lcsSetupIpv6Dhcpv6ServerReservationsEntryClientId OBJECT-TYPE
    SYNTAX     DisplayString (SIZE(0..96))
    MAX-ACCESS read-write
    STATUS     current
    DESCRIPTION
        "-- empty --"
    ::= { lcsSetupIpv6Dhcpv6ServerReservationsEntry 3 }

-- {COLUMN} 1712.2.70.3.1.6.1.5
lcsSetupIpv6Dhcpv6ServerReservationsEntryPrefLifetime OBJECT-TYPE
    SYNTAX     INTEGER (0..2147483647)
    MAX-ACCESS read-write
    STATUS     current
    DESCRIPTION
        "-- empty --"
    ::= { lcsSetupIpv6Dhcpv6ServerReservationsEntry 5 }

-- {COLUMN} 1712.2.70.3.1.6.1.6
lcsSetupIpv6Dhcpv6ServerReservationsEntryValidLifetime OBJECT-TYPE
    SYNTAX     INTEGER (0..2147483647)
    MAX-ACCESS read-write
    STATUS     current
    DESCRIPTION
        "-- empty --"
    ::= { lcsSetupIpv6Dhcpv6ServerReservationsEntry 6 }

-- {SCALAR} 1712.2.70.3.1.5
lcsSetupIpv6Dhcpv6ServerLimitConfirmToClientsWithAddresses OBJECT-TYPE
    SYNTAX     INTEGER
      {
        eNo (0),
        eYes (1)
      }
    MAX-ACCESS read-write
    STATUS     current
    DESCRIPTION
        "-- empty --"
    ::= { lcsSetupIpv6Dhcpv6Server 5 }

-- {SCALAR} 1712.2.70.3.1.7
lcsSetupIpv6Dhcpv6ServerCreateAddressRoutes OBJECT-TYPE
    SYNTAX     INTEGER
      {
        eNo (0),
        eYes (1)
      }
    MAX-ACCESS read-write
    STATUS     current
    DESCRIPTION
        "-- empty --"
    ::= { lcsSetupIpv6Dhcpv6Server 7 }

-- {OID} 1712.2.70.3.2
lcsSetupIpv6Dhcpv6Client OBJECT IDENTIFIER ::= { lcsSetupIpv6Dhcpv6 2 }

-- {TABLE} 1712.2.70.3.2.1
lcsSetupIpv6Dhcpv6ClientInterfaceListTable OBJECT-TYPE
    SYNTAX     SEQUENCE OF LcsSetupIpv6Dhcpv6ClientInterfaceListEntry
    MAX-ACCESS not-accessible
    STATUS     current
    DESCRIPTION
        "-- empty --"
    ::= { lcsSetupIpv6Dhcpv6Client 1 }

-- {ENTRY} 1712.2.70.3.2.1.1
lcsSetupIpv6Dhcpv6ClientInterfaceListEntry OBJECT-TYPE
    SYNTAX     LcsSetupIpv6Dhcpv6ClientInterfaceListEntry
    MAX-ACCESS not-accessible
    STATUS     current
    DESCRIPTION
        ""
    INDEX {
        lcsSetupIpv6Dhcpv6ClientInterfaceListEntryInterfaceName
    }
    ::= { lcsSetupIpv6Dhcpv6ClientInterfaceListTable 1 }

-- {SEQUENCE}
LcsSetupIpv6Dhcpv6ClientInterfaceListEntry ::= SEQUENCE {
    lcsSetupIpv6Dhcpv6ClientInterfaceListEntryInterfaceName DisplayString,
    lcsSetupIpv6Dhcpv6ClientInterfaceListEntryOperating INTEGER,
    lcsSetupIpv6Dhcpv6ClientInterfaceListEntryRequestDns INTEGER,
    lcsSetupIpv6Dhcpv6ClientInterfaceListEntryRequestDomainList INTEGER,
    lcsSetupIpv6Dhcpv6ClientInterfaceListEntryRequestAddress INTEGER,
    lcsSetupIpv6Dhcpv6ClientInterfaceListEntryRequestPd INTEGER,
    lcsSetupIpv6Dhcpv6ClientInterfaceListEntryRapidCommit INTEGER,
    lcsSetupIpv6Dhcpv6ClientInterfaceListEntrySendFqdn INTEGER,
    lcsSetupIpv6Dhcpv6ClientInterfaceListEntryAcceptReconf INTEGER
}

-- {COLUMN} 1712.2.70.3.2.1.1.1
lcsSetupIpv6Dhcpv6ClientInterfaceListEntryInterfaceName OBJECT-TYPE
    SYNTAX     DisplayString (SIZE(0..16))
    MAX-ACCESS read-write
    STATUS     current
    DESCRIPTION
        "-- empty --"
    ::= { lcsSetupIpv6Dhcpv6ClientInterfaceListEntry 1 }

-- {COLUMN} 1712.2.70.3.2.1.1.2
lcsSetupIpv6Dhcpv6ClientInterfaceListEntryOperating OBJECT-TYPE
    SYNTAX     INTEGER
      {
        eNo (0),
        eAutoconf (1),
        eYes (2)
      }
    MAX-ACCESS read-write
    STATUS     current
    DESCRIPTION
        "-- empty --"
    ::= { lcsSetupIpv6Dhcpv6ClientInterfaceListEntry 2 }

-- {COLUMN} 1712.2.70.3.2.1.1.3
lcsSetupIpv6Dhcpv6ClientInterfaceListEntryRequestDns OBJECT-TYPE
    SYNTAX     INTEGER
      {
        eNo (0),
        eYes (1)
      }
    MAX-ACCESS read-write
    STATUS     current
    DESCRIPTION
        "-- empty --"
    ::= { lcsSetupIpv6Dhcpv6ClientInterfaceListEntry 3 }

-- {COLUMN} 1712.2.70.3.2.1.1.9
lcsSetupIpv6Dhcpv6ClientInterfaceListEntryRequestDomainList OBJECT-TYPE
    SYNTAX     INTEGER
      {
        eNo (0),
        eYes (1)
      }
    MAX-ACCESS read-write
    STATUS     current
    DESCRIPTION
        "-- empty --"
    ::= { lcsSetupIpv6Dhcpv6ClientInterfaceListEntry 9 }

-- {COLUMN} 1712.2.70.3.2.1.1.4
lcsSetupIpv6Dhcpv6ClientInterfaceListEntryRequestAddress OBJECT-TYPE
    SYNTAX     INTEGER
      {
        eNo (0),
        eYes (1)
      }
    MAX-ACCESS read-write
    STATUS     current
    DESCRIPTION
        "-- empty --"
    ::= { lcsSetupIpv6Dhcpv6ClientInterfaceListEntry 4 }

-- {COLUMN} 1712.2.70.3.2.1.1.5
lcsSetupIpv6Dhcpv6ClientInterfaceListEntryRequestPd OBJECT-TYPE
    SYNTAX     INTEGER
      {
        eNo (0),
        eYes (1)
      }
    MAX-ACCESS read-write
    STATUS     current
    DESCRIPTION
        "-- empty --"
    ::= { lcsSetupIpv6Dhcpv6ClientInterfaceListEntry 5 }

-- {COLUMN} 1712.2.70.3.2.1.1.6
lcsSetupIpv6Dhcpv6ClientInterfaceListEntryRapidCommit OBJECT-TYPE
    SYNTAX     INTEGER
      {
        eNo (0),
        eYes (1)
      }
    MAX-ACCESS read-write
    STATUS     current
    DESCRIPTION
        "-- empty --"
    ::= { lcsSetupIpv6Dhcpv6ClientInterfaceListEntry 6 }

-- {COLUMN} 1712.2.70.3.2.1.1.7
lcsSetupIpv6Dhcpv6ClientInterfaceListEntrySendFqdn OBJECT-TYPE
    SYNTAX     INTEGER
      {
        eNo (0),
        eYes (1)
      }
    MAX-ACCESS read-write
    STATUS     current
    DESCRIPTION
        "-- empty --"
    ::= { lcsSetupIpv6Dhcpv6ClientInterfaceListEntry 7 }

-- {COLUMN} 1712.2.70.3.2.1.1.8
lcsSetupIpv6Dhcpv6ClientInterfaceListEntryAcceptReconf OBJECT-TYPE
    SYNTAX     INTEGER
      {
        eNo (0),
        eYes (1)
      }
    MAX-ACCESS read-write
    STATUS     current
    DESCRIPTION
        "-- empty --"
    ::= { lcsSetupIpv6Dhcpv6ClientInterfaceListEntry 8 }

-- {SCALAR} 1712.2.70.3.2.2
lcsSetupIpv6Dhcpv6ClientUserClassIdentifer OBJECT-TYPE
    SYNTAX     DisplayString (SIZE(0..253))
    MAX-ACCESS read-write
    STATUS     current
    DESCRIPTION
        "-- empty --"
    ::= { lcsSetupIpv6Dhcpv6Client 2 }

-- {SCALAR} 1712.2.70.3.2.3
lcsSetupIpv6Dhcpv6ClientVendorClassIdentifer OBJECT-TYPE
    SYNTAX     DisplayString (SIZE(0..253))
    MAX-ACCESS read-write
    STATUS     current
    DESCRIPTION
        "-- empty --"
    ::= { lcsSetupIpv6Dhcpv6Client 3 }

-- {SCALAR} 1712.2.70.3.2.4
lcsSetupIpv6Dhcpv6ClientVendorClassNumber OBJECT-TYPE
    SYNTAX     INTEGER (0..2147483647)
    MAX-ACCESS read-write
    STATUS     current
    DESCRIPTION
        "-- empty --"
    ::= { lcsSetupIpv6Dhcpv6Client 4 }

-- {OID} 1712.2.70.3.3
lcsSetupIpv6Dhcpv6RelayAgent OBJECT IDENTIFIER ::= { lcsSetupIpv6Dhcpv6 3 }

-- {TABLE} 1712.2.70.3.3.1
lcsSetupIpv6Dhcpv6RelayAgentInterfaceListTable OBJECT-TYPE
    SYNTAX     SEQUENCE OF LcsSetupIpv6Dhcpv6RelayAgentInterfaceListEntry
    MAX-ACCESS not-accessible
    STATUS     current
    DESCRIPTION
        "-- empty --"
    ::= { lcsSetupIpv6Dhcpv6RelayAgent 1 }

-- {ENTRY} 1712.2.70.3.3.1.1
lcsSetupIpv6Dhcpv6RelayAgentInterfaceListEntry OBJECT-TYPE
    SYNTAX     LcsSetupIpv6Dhcpv6RelayAgentInterfaceListEntry
    MAX-ACCESS not-accessible
    STATUS     current
    DESCRIPTION
        ""
    INDEX {
        lcsSetupIpv6Dhcpv6RelayAgentInterfaceListEntryInterfaceName
    }
    ::= { lcsSetupIpv6Dhcpv6RelayAgentInterfaceListTable 1 }

-- {SEQUENCE}
LcsSetupIpv6Dhcpv6RelayAgentInterfaceListEntry ::= SEQUENCE {
    lcsSetupIpv6Dhcpv6RelayAgentInterfaceListEntryInterfaceName DisplayString,
    lcsSetupIpv6Dhcpv6RelayAgentInterfaceListEntryOperating INTEGER,
    lcsSetupIpv6Dhcpv6RelayAgentInterfaceListEntryInterfaceAddress DisplayString,
    lcsSetupIpv6Dhcpv6RelayAgentInterfaceListEntryDestAddress DisplayString,
    lcsSetupIpv6Dhcpv6RelayAgentInterfaceListEntryDestInterface DisplayString
}

-- {COLUMN} 1712.2.70.3.3.1.1.1
lcsSetupIpv6Dhcpv6RelayAgentInterfaceListEntryInterfaceName OBJECT-TYPE
    SYNTAX     DisplayString (SIZE(0..16))
    MAX-ACCESS read-write
    STATUS     current
    DESCRIPTION
        "-- empty --"
    ::= { lcsSetupIpv6Dhcpv6RelayAgentInterfaceListEntry 1 }

-- {COLUMN} 1712.2.70.3.3.1.1.2
lcsSetupIpv6Dhcpv6RelayAgentInterfaceListEntryOperating OBJECT-TYPE
    SYNTAX     INTEGER
      {
        eNo (0),
        eYes (1)
      }
    MAX-ACCESS read-write
    STATUS     current
    DESCRIPTION
        "-- empty --"
    ::= { lcsSetupIpv6Dhcpv6RelayAgentInterfaceListEntry 2 }

-- {COLUMN} 1712.2.70.3.3.1.1.3
lcsSetupIpv6Dhcpv6RelayAgentInterfaceListEntryInterfaceAddress OBJECT-TYPE
    SYNTAX     DisplayString (SIZE(0..39))
    MAX-ACCESS read-write
    STATUS     current
    DESCRIPTION
        "-- empty --"
    ::= { lcsSetupIpv6Dhcpv6RelayAgentInterfaceListEntry 3 }

-- {COLUMN} 1712.2.70.3.3.1.1.4
lcsSetupIpv6Dhcpv6RelayAgentInterfaceListEntryDestAddress OBJECT-TYPE
    SYNTAX     DisplayString (SIZE(0..39))
    MAX-ACCESS read-write
    STATUS     current
    DESCRIPTION
        "-- empty --"
    ::= { lcsSetupIpv6Dhcpv6RelayAgentInterfaceListEntry 4 }

-- {COLUMN} 1712.2.70.3.3.1.1.5
lcsSetupIpv6Dhcpv6RelayAgentInterfaceListEntryDestInterface OBJECT-TYPE
    SYNTAX     DisplayString (SIZE(0..16))
    MAX-ACCESS read-write
    STATUS     current
    DESCRIPTION
        "-- empty --"
    ::= { lcsSetupIpv6Dhcpv6RelayAgentInterfaceListEntry 5 }

-- {SCALAR} 1712.2.70.3.3.2
lcsSetupIpv6Dhcpv6RelayAgentCreateAddressRoutes OBJECT-TYPE
    SYNTAX     INTEGER
      {
        eNo (0),
        eYes (1)
      }
    MAX-ACCESS read-write
    STATUS     current
    DESCRIPTION
        "-- empty --"
    ::= { lcsSetupIpv6Dhcpv6RelayAgent 2 }

-- {OID} 1712.2.70.4
lcsSetupIpv6Network OBJECT IDENTIFIER ::= { lcsSetupIpv6 4 }

-- {TABLE} 1712.2.70.4.1
lcsSetupIpv6NetworkAddressesTable OBJECT-TYPE
    SYNTAX     SEQUENCE OF LcsSetupIpv6NetworkAddressesEntry
    MAX-ACCESS not-accessible
    STATUS     current
    DESCRIPTION
        "-- empty --"
    ::= { lcsSetupIpv6Network 1 }

-- {ENTRY} 1712.2.70.4.1.1
lcsSetupIpv6NetworkAddressesEntry OBJECT-TYPE
    SYNTAX     LcsSetupIpv6NetworkAddressesEntry
    MAX-ACCESS not-accessible
    STATUS     current
    DESCRIPTION
        ""
    INDEX {
        lcsSetupIpv6NetworkAddressesEntryInterfaceName,
        lcsSetupIpv6NetworkAddressesEntryIpv6AddressPrefixlength
    }
    ::= { lcsSetupIpv6NetworkAddressesTable 1 }

-- {SEQUENCE}
LcsSetupIpv6NetworkAddressesEntry ::= SEQUENCE {
    lcsSetupIpv6NetworkAddressesEntryInterfaceName DisplayString,
    lcsSetupIpv6NetworkAddressesEntryIpv6AddressPrefixlength DisplayString,
    lcsSetupIpv6NetworkAddressesEntryAddressType INTEGER,
    lcsSetupIpv6NetworkAddressesEntryNetworkGroup DisplayString,
    lcsSetupIpv6NetworkAddressesEntryComment DisplayString
}

-- {COLUMN} 1712.2.70.4.1.1.1
lcsSetupIpv6NetworkAddressesEntryInterfaceName OBJECT-TYPE
    SYNTAX     DisplayString (SIZE(0..16))
    MAX-ACCESS read-write
    STATUS     current
    DESCRIPTION
        "-- empty --"
    ::= { lcsSetupIpv6NetworkAddressesEntry 1 }

-- {COLUMN} 1712.2.70.4.1.1.2
lcsSetupIpv6NetworkAddressesEntryIpv6AddressPrefixlength OBJECT-TYPE
    SYNTAX     DisplayString (SIZE(0..43))
    MAX-ACCESS read-write
    STATUS     current
    DESCRIPTION
        "-- empty --"
    ::= { lcsSetupIpv6NetworkAddressesEntry 2 }

-- {COLUMN} 1712.2.70.4.1.1.3
lcsSetupIpv6NetworkAddressesEntryAddressType OBJECT-TYPE
    SYNTAX     INTEGER
      {
        eUnicast (0),
        eAnycast (1),
        eEui64 (2)
      }
    MAX-ACCESS read-write
    STATUS     current
    DESCRIPTION
        "-- empty --"
    ::= { lcsSetupIpv6NetworkAddressesEntry 3 }

-- {COLUMN} 1712.2.70.4.1.1.4
lcsSetupIpv6NetworkAddressesEntryNetworkGroup OBJECT-TYPE
    SYNTAX     DisplayString (SIZE(0..16))
    MAX-ACCESS read-write
    STATUS     current
    DESCRIPTION
        "-- empty --"
    ::= { lcsSetupIpv6NetworkAddressesEntry 4 }

-- {COLUMN} 1712.2.70.4.1.1.5
lcsSetupIpv6NetworkAddressesEntryComment OBJECT-TYPE
    SYNTAX     DisplayString (SIZE(0..64))
    MAX-ACCESS read-write
    STATUS     current
    DESCRIPTION
        "-- empty --"
    ::= { lcsSetupIpv6NetworkAddressesEntry 5 }

-- {TABLE} 1712.2.70.4.2
lcsSetupIpv6NetworkParameterTable OBJECT-TYPE
    SYNTAX     SEQUENCE OF LcsSetupIpv6NetworkParameterEntry
    MAX-ACCESS not-accessible
    STATUS     current
    DESCRIPTION
        "-- empty --"
    ::= { lcsSetupIpv6Network 2 }

-- {ENTRY} 1712.2.70.4.2.1
lcsSetupIpv6NetworkParameterEntry OBJECT-TYPE
    SYNTAX     LcsSetupIpv6NetworkParameterEntry
    MAX-ACCESS not-accessible
    STATUS     current
    DESCRIPTION
        ""
    INDEX {
        lcsSetupIpv6NetworkParameterEntryInterfaceName
    }
    ::= { lcsSetupIpv6NetworkParameterTable 1 }

-- {SEQUENCE}
LcsSetupIpv6NetworkParameterEntry ::= SEQUENCE {
    lcsSetupIpv6NetworkParameterEntryInterfaceName DisplayString,
    lcsSetupIpv6NetworkParameterEntryIpv6Gateway DisplayString,
    lcsSetupIpv6NetworkParameterEntryPrimaryDns DisplayString,
    lcsSetupIpv6NetworkParameterEntrySecondaryDns DisplayString
}

-- {COLUMN} 1712.2.70.4.2.1.1
lcsSetupIpv6NetworkParameterEntryInterfaceName OBJECT-TYPE
    SYNTAX     DisplayString (SIZE(0..16))
    MAX-ACCESS read-write
    STATUS     current
    DESCRIPTION
        "-- empty --"
    ::= { lcsSetupIpv6NetworkParameterEntry 1 }

-- {COLUMN} 1712.2.70.4.2.1.2
lcsSetupIpv6NetworkParameterEntryIpv6Gateway OBJECT-TYPE
    SYNTAX     DisplayString (SIZE(0..39))
    MAX-ACCESS read-write
    STATUS     current
    DESCRIPTION
        "-- empty --"
    ::= { lcsSetupIpv6NetworkParameterEntry 2 }

-- {COLUMN} 1712.2.70.4.2.1.3
lcsSetupIpv6NetworkParameterEntryPrimaryDns OBJECT-TYPE
    SYNTAX     DisplayString (SIZE(0..39))
    MAX-ACCESS read-write
    STATUS     current
    DESCRIPTION
        "-- empty --"
    ::= { lcsSetupIpv6NetworkParameterEntry 3 }

-- {COLUMN} 1712.2.70.4.2.1.4
lcsSetupIpv6NetworkParameterEntrySecondaryDns OBJECT-TYPE
    SYNTAX     DisplayString (SIZE(0..39))
    MAX-ACCESS read-write
    STATUS     current
    DESCRIPTION
        "-- empty --"
    ::= { lcsSetupIpv6NetworkParameterEntry 4 }

-- {TABLE} 1712.2.70.4.3
lcsSetupIpv6NetworkLoopbackTable OBJECT-TYPE
    SYNTAX     SEQUENCE OF LcsSetupIpv6NetworkLoopbackEntry
    MAX-ACCESS not-accessible
    STATUS     current
    DESCRIPTION
        "-- empty --"
    ::= { lcsSetupIpv6Network 3 }

-- {ENTRY} 1712.2.70.4.3.1
lcsSetupIpv6NetworkLoopbackEntry OBJECT-TYPE
    SYNTAX     LcsSetupIpv6NetworkLoopbackEntry
    MAX-ACCESS not-accessible
    STATUS     current
    DESCRIPTION
        ""
    INDEX {
        lcsSetupIpv6NetworkLoopbackEntryName
    }
    ::= { lcsSetupIpv6NetworkLoopbackTable 1 }

-- {SEQUENCE}
LcsSetupIpv6NetworkLoopbackEntry ::= SEQUENCE {
    lcsSetupIpv6NetworkLoopbackEntryName DisplayString,
    lcsSetupIpv6NetworkLoopbackEntryIpv6LoopbackAddr DisplayString,
    lcsSetupIpv6NetworkLoopbackEntryRtgTag INTEGER,
    lcsSetupIpv6NetworkLoopbackEntryComment DisplayString
}

-- {COLUMN} 1712.2.70.4.3.1.1
lcsSetupIpv6NetworkLoopbackEntryName OBJECT-TYPE
    SYNTAX     DisplayString (SIZE(0..16))
    MAX-ACCESS read-write
    STATUS     current
    DESCRIPTION
        "-- empty --"
    ::= { lcsSetupIpv6NetworkLoopbackEntry 1 }

-- {COLUMN} 1712.2.70.4.3.1.2
lcsSetupIpv6NetworkLoopbackEntryIpv6LoopbackAddr OBJECT-TYPE
    SYNTAX     DisplayString (SIZE(0..39))
    MAX-ACCESS read-write
    STATUS     current
    DESCRIPTION
        "-- empty --"
    ::= { lcsSetupIpv6NetworkLoopbackEntry 2 }

-- {COLUMN} 1712.2.70.4.3.1.3
lcsSetupIpv6NetworkLoopbackEntryRtgTag OBJECT-TYPE
    SYNTAX     INTEGER (0..65535)
    MAX-ACCESS read-write
    STATUS     current
    DESCRIPTION
        "-- empty --"
    ::= { lcsSetupIpv6NetworkLoopbackEntry 3 }

-- {COLUMN} 1712.2.70.4.3.1.4
lcsSetupIpv6NetworkLoopbackEntryComment OBJECT-TYPE
    SYNTAX     DisplayString (SIZE(0..64))
    MAX-ACCESS read-write
    STATUS     current
    DESCRIPTION
        "-- empty --"
    ::= { lcsSetupIpv6NetworkLoopbackEntry 4 }

-- {OID} 1712.2.70.12
lcsSetupIpv6Router OBJECT IDENTIFIER ::= { lcsSetupIpv6 12 }

-- {TABLE} 1712.2.70.12.1
lcsSetupIpv6RouterRoutingTableTable OBJECT-TYPE
    SYNTAX     SEQUENCE OF LcsSetupIpv6RouterRoutingTableEntry
    MAX-ACCESS not-accessible
    STATUS     current
    DESCRIPTION
        "-- empty --"
    ::= { lcsSetupIpv6Router 1 }

-- {ENTRY} 1712.2.70.12.1.1
lcsSetupIpv6RouterRoutingTableEntry OBJECT-TYPE
    SYNTAX     LcsSetupIpv6RouterRoutingTableEntry
    MAX-ACCESS not-accessible
    STATUS     current
    DESCRIPTION
        ""
    INDEX {
        lcsSetupIpv6RouterRoutingTableEntryPrefix,
        lcsSetupIpv6RouterRoutingTableEntryRtgTag
    }
    ::= { lcsSetupIpv6RouterRoutingTableTable 1 }

-- {SEQUENCE}
LcsSetupIpv6RouterRoutingTableEntry ::= SEQUENCE {
    lcsSetupIpv6RouterRoutingTableEntryPrefix DisplayString,
    lcsSetupIpv6RouterRoutingTableEntryRtgTag INTEGER,
    lcsSetupIpv6RouterRoutingTableEntryPeerOrIpv6 DisplayString,
    lcsSetupIpv6RouterRoutingTableEntryComment DisplayString
}

-- {COLUMN} 1712.2.70.12.1.1.1
lcsSetupIpv6RouterRoutingTableEntryPrefix OBJECT-TYPE
    SYNTAX     DisplayString (SIZE(0..43))
    MAX-ACCESS read-write
    STATUS     current
    DESCRIPTION
        "-- empty --"
    ::= { lcsSetupIpv6RouterRoutingTableEntry 1 }

-- {COLUMN} 1712.2.70.12.1.1.2
lcsSetupIpv6RouterRoutingTableEntryRtgTag OBJECT-TYPE
    SYNTAX     INTEGER (0..65535)
    MAX-ACCESS read-write
    STATUS     current
    DESCRIPTION
        "-- empty --"
    ::= { lcsSetupIpv6RouterRoutingTableEntry 2 }

-- {COLUMN} 1712.2.70.12.1.1.3
lcsSetupIpv6RouterRoutingTableEntryPeerOrIpv6 OBJECT-TYPE
    SYNTAX     DisplayString (SIZE(0..56))
    MAX-ACCESS read-write
    STATUS     current
    DESCRIPTION
        "-- empty --"
    ::= { lcsSetupIpv6RouterRoutingTableEntry 3 }

-- {COLUMN} 1712.2.70.12.1.1.4
lcsSetupIpv6RouterRoutingTableEntryComment OBJECT-TYPE
    SYNTAX     DisplayString (SIZE(0..64))
    MAX-ACCESS read-write
    STATUS     current
    DESCRIPTION
        "-- empty --"
    ::= { lcsSetupIpv6RouterRoutingTableEntry 4 }

-- {SCALAR} 1712.2.70.12.2
lcsSetupIpv6RouterDestCacheTimeout OBJECT-TYPE
    SYNTAX     INTEGER (0..65535)
    MAX-ACCESS read-write
    STATUS     current
    DESCRIPTION
        "-- empty --"
    ::= { lcsSetupIpv6Router 2 }

-- {TABLE} 1712.2.70.6
lcsSetupIpv6LanInterfacesTable OBJECT-TYPE
    SYNTAX     SEQUENCE OF LcsSetupIpv6LanInterfacesEntry
    MAX-ACCESS not-accessible
    STATUS     current
    DESCRIPTION
        "-- empty --"
    ::= { lcsSetupIpv6 6 }

-- {ENTRY} 1712.2.70.6.1
lcsSetupIpv6LanInterfacesEntry OBJECT-TYPE
    SYNTAX     LcsSetupIpv6LanInterfacesEntry
    MAX-ACCESS not-accessible
    STATUS     current
    DESCRIPTION
        ""
    INDEX {
        lcsSetupIpv6LanInterfacesEntryInterfaceName
    }
    ::= { lcsSetupIpv6LanInterfacesTable 1 }

-- {SEQUENCE}
LcsSetupIpv6LanInterfacesEntry ::= SEQUENCE {
    lcsSetupIpv6LanInterfacesEntryInterfaceName DisplayString,
    lcsSetupIpv6LanInterfacesEntryInterfaceId INTEGER,
    lcsSetupIpv6LanInterfacesEntryVlanId INTEGER,
    lcsSetupIpv6LanInterfacesEntryRtgTag INTEGER,
    lcsSetupIpv6LanInterfacesEntryAutoconf INTEGER,
    lcsSetupIpv6LanInterfacesEntryAcceptRa INTEGER,
    lcsSetupIpv6LanInterfacesEntryInterfaceStatus INTEGER,
    lcsSetupIpv6LanInterfacesEntryForwarding INTEGER,
    lcsSetupIpv6LanInterfacesEntryMtu INTEGER,
    lcsSetupIpv6LanInterfacesEntryFirewall INTEGER,
    lcsSetupIpv6LanInterfacesEntryDadAttempts INTEGER,
    lcsSetupIpv6LanInterfacesEntryComment DisplayString
}

-- {COLUMN} 1712.2.70.6.1.1
lcsSetupIpv6LanInterfacesEntryInterfaceName OBJECT-TYPE
    SYNTAX     DisplayString (SIZE(0..16))
    MAX-ACCESS read-write
    STATUS     current
    DESCRIPTION
        "-- empty --"
    ::= { lcsSetupIpv6LanInterfacesEntry 1 }

-- {COLUMN} 1712.2.70.6.1.2
lcsSetupIpv6LanInterfacesEntryInterfaceId OBJECT-TYPE
    SYNTAX     INTEGER
      {
        eLan1 (256),
        eLan2 (257),
        eLan3 (258),
        eLan4 (259)
      }
    MAX-ACCESS read-write
    STATUS     current
    DESCRIPTION
        "-- empty --"
    ::= { lcsSetupIpv6LanInterfacesEntry 2 }

-- {COLUMN} 1712.2.70.6.1.3
lcsSetupIpv6LanInterfacesEntryVlanId OBJECT-TYPE
    SYNTAX     INTEGER (0..65535)
    MAX-ACCESS read-write
    STATUS     current
    DESCRIPTION
        "-- empty --"
    ::= { lcsSetupIpv6LanInterfacesEntry 3 }

-- {COLUMN} 1712.2.70.6.1.4
lcsSetupIpv6LanInterfacesEntryRtgTag OBJECT-TYPE
    SYNTAX     INTEGER (0..65535)
    MAX-ACCESS read-write
    STATUS     current
    DESCRIPTION
        "-- empty --"
    ::= { lcsSetupIpv6LanInterfacesEntry 4 }

-- {COLUMN} 1712.2.70.6.1.5
lcsSetupIpv6LanInterfacesEntryAutoconf OBJECT-TYPE
    SYNTAX     INTEGER
      {
        eYes (0),
        eNo (1)
      }
    MAX-ACCESS read-write
    STATUS     current
    DESCRIPTION
        "-- empty --"
    ::= { lcsSetupIpv6LanInterfacesEntry 5 }

-- {COLUMN} 1712.2.70.6.1.6
lcsSetupIpv6LanInterfacesEntryAcceptRa OBJECT-TYPE
    SYNTAX     INTEGER
      {
        eYes (0),
        eNo (1)
      }
    MAX-ACCESS read-write
    STATUS     current
    DESCRIPTION
        "-- empty --"
    ::= { lcsSetupIpv6LanInterfacesEntry 6 }

-- {COLUMN} 1712.2.70.6.1.7
lcsSetupIpv6LanInterfacesEntryInterfaceStatus OBJECT-TYPE
    SYNTAX     INTEGER
      {
        eUp (1),
        eDown (2)
      }
    MAX-ACCESS read-write
    STATUS     current
    DESCRIPTION
        "-- empty --"
    ::= { lcsSetupIpv6LanInterfacesEntry 7 }

-- {COLUMN} 1712.2.70.6.1.8
lcsSetupIpv6LanInterfacesEntryForwarding OBJECT-TYPE
    SYNTAX     INTEGER
      {
        eYes (0),
        eNo (1)
      }
    MAX-ACCESS read-write
    STATUS     current
    DESCRIPTION
        "-- empty --"
    ::= { lcsSetupIpv6LanInterfacesEntry 8 }

-- {COLUMN} 1712.2.70.6.1.9
lcsSetupIpv6LanInterfacesEntryMtu OBJECT-TYPE
    SYNTAX     INTEGER (0..65535)
    MAX-ACCESS read-write
    STATUS     current
    DESCRIPTION
        "-- empty --"
    ::= { lcsSetupIpv6LanInterfacesEntry 9 }

-- {COLUMN} 1712.2.70.6.1.10
lcsSetupIpv6LanInterfacesEntryFirewall OBJECT-TYPE
    SYNTAX     INTEGER
      {
        eYes (0),
        eNo (1)
      }
    MAX-ACCESS read-write
    STATUS     current
    DESCRIPTION
        "-- empty --"
    ::= { lcsSetupIpv6LanInterfacesEntry 10 }

-- {COLUMN} 1712.2.70.6.1.12
lcsSetupIpv6LanInterfacesEntryDadAttempts OBJECT-TYPE
    SYNTAX     INTEGER (0..255)
    MAX-ACCESS read-write
    STATUS     current
    DESCRIPTION
        "-- empty --"
    ::= { lcsSetupIpv6LanInterfacesEntry 12 }

-- {COLUMN} 1712.2.70.6.1.11
lcsSetupIpv6LanInterfacesEntryComment OBJECT-TYPE
    SYNTAX     DisplayString (SIZE(0..64))
    MAX-ACCESS read-write
    STATUS     current
    DESCRIPTION
        "-- empty --"
    ::= { lcsSetupIpv6LanInterfacesEntry 11 }

-- {TABLE} 1712.2.70.7
lcsSetupIpv6WanInterfacesTable OBJECT-TYPE
    SYNTAX     SEQUENCE OF LcsSetupIpv6WanInterfacesEntry
    MAX-ACCESS not-accessible
    STATUS     current
    DESCRIPTION
        "-- empty --"
    ::= { lcsSetupIpv6 7 }

-- {ENTRY} 1712.2.70.7.1
lcsSetupIpv6WanInterfacesEntry OBJECT-TYPE
    SYNTAX     LcsSetupIpv6WanInterfacesEntry
    MAX-ACCESS not-accessible
    STATUS     current
    DESCRIPTION
        ""
    INDEX {
        lcsSetupIpv6WanInterfacesEntryInterfaceName
    }
    ::= { lcsSetupIpv6WanInterfacesTable 1 }

-- {SEQUENCE}
LcsSetupIpv6WanInterfacesEntry ::= SEQUENCE {
    lcsSetupIpv6WanInterfacesEntryInterfaceName DisplayString,
    lcsSetupIpv6WanInterfacesEntryRtgTag INTEGER,
    lcsSetupIpv6WanInterfacesEntryAutoconf INTEGER,
    lcsSetupIpv6WanInterfacesEntryAcceptRa INTEGER,
    lcsSetupIpv6WanInterfacesEntryInterfaceStatus INTEGER,
    lcsSetupIpv6WanInterfacesEntryForwarding INTEGER,
    lcsSetupIpv6WanInterfacesEntryFirewall INTEGER,
    lcsSetupIpv6WanInterfacesEntryDadAttempts INTEGER,
    lcsSetupIpv6WanInterfacesEntryPdMode INTEGER,
    lcsSetupIpv6WanInterfacesEntryComment DisplayString
}

-- {COLUMN} 1712.2.70.7.1.1
lcsSetupIpv6WanInterfacesEntryInterfaceName OBJECT-TYPE
    SYNTAX     DisplayString (SIZE(0..16))
    MAX-ACCESS read-write
    STATUS     current
    DESCRIPTION
        "-- empty --"
    ::= { lcsSetupIpv6WanInterfacesEntry 1 }

-- {COLUMN} 1712.2.70.7.1.2
lcsSetupIpv6WanInterfacesEntryRtgTag OBJECT-TYPE
    SYNTAX     INTEGER (0..65535)
    MAX-ACCESS read-write
    STATUS     current
    DESCRIPTION
        "-- empty --"
    ::= { lcsSetupIpv6WanInterfacesEntry 2 }

-- {COLUMN} 1712.2.70.7.1.3
lcsSetupIpv6WanInterfacesEntryAutoconf OBJECT-TYPE
    SYNTAX     INTEGER
      {
        eYes (0),
        eNo (1)
      }
    MAX-ACCESS read-write
    STATUS     current
    DESCRIPTION
        "-- empty --"
    ::= { lcsSetupIpv6WanInterfacesEntry 3 }

-- {COLUMN} 1712.2.70.7.1.4
lcsSetupIpv6WanInterfacesEntryAcceptRa OBJECT-TYPE
    SYNTAX     INTEGER
      {
        eYes (0),
        eNo (1)
      }
    MAX-ACCESS read-write
    STATUS     current
    DESCRIPTION
        "-- empty --"
    ::= { lcsSetupIpv6WanInterfacesEntry 4 }

-- {COLUMN} 1712.2.70.7.1.5
lcsSetupIpv6WanInterfacesEntryInterfaceStatus OBJECT-TYPE
    SYNTAX     INTEGER
      {
        eUp (1),
        eDown (2)
      }
    MAX-ACCESS read-write
    STATUS     current
    DESCRIPTION
        "-- empty --"
    ::= { lcsSetupIpv6WanInterfacesEntry 5 }

-- {COLUMN} 1712.2.70.7.1.6
lcsSetupIpv6WanInterfacesEntryForwarding OBJECT-TYPE
    SYNTAX     INTEGER
      {
        eYes (0),
        eNo (1)
      }
    MAX-ACCESS read-write
    STATUS     current
    DESCRIPTION
        "-- empty --"
    ::= { lcsSetupIpv6WanInterfacesEntry 6 }

-- {COLUMN} 1712.2.70.7.1.7
lcsSetupIpv6WanInterfacesEntryFirewall OBJECT-TYPE
    SYNTAX     INTEGER
      {
        eYes (0),
        eNo (1)
      }
    MAX-ACCESS read-write
    STATUS     current
    DESCRIPTION
        "-- empty --"
    ::= { lcsSetupIpv6WanInterfacesEntry 7 }

-- {COLUMN} 1712.2.70.7.1.9
lcsSetupIpv6WanInterfacesEntryDadAttempts OBJECT-TYPE
    SYNTAX     INTEGER (0..255)
    MAX-ACCESS read-write
    STATUS     current
    DESCRIPTION
        "-- empty --"
    ::= { lcsSetupIpv6WanInterfacesEntry 9 }

-- {COLUMN} 1712.2.70.7.1.10
lcsSetupIpv6WanInterfacesEntryPdMode OBJECT-TYPE
    SYNTAX     INTEGER
      {
        eDhcpv6 (0),
        eRouterAdv (1)
      }
    MAX-ACCESS read-write
    STATUS     current
    DESCRIPTION
        "-- empty --"
    ::= { lcsSetupIpv6WanInterfacesEntry 10 }

-- {COLUMN} 1712.2.70.7.1.8
lcsSetupIpv6WanInterfacesEntryComment OBJECT-TYPE
    SYNTAX     DisplayString (SIZE(0..64))
    MAX-ACCESS read-write
    STATUS     current
    DESCRIPTION
        "-- empty --"
    ::= { lcsSetupIpv6WanInterfacesEntry 8 }

-- {TABLE} 1712.2.70.14
lcsSetupIpv6RasInterfacesTable OBJECT-TYPE
    SYNTAX     SEQUENCE OF LcsSetupIpv6RasInterfacesEntry
    MAX-ACCESS not-accessible
    STATUS     current
    DESCRIPTION
        "-- empty --"
    ::= { lcsSetupIpv6 14 }

-- {ENTRY} 1712.2.70.14.1
lcsSetupIpv6RasInterfacesEntry OBJECT-TYPE
    SYNTAX     LcsSetupIpv6RasInterfacesEntry
    MAX-ACCESS not-accessible
    STATUS     current
    DESCRIPTION
        ""
    INDEX {
        lcsSetupIpv6RasInterfacesEntryInterfaceName
    }
    ::= { lcsSetupIpv6RasInterfacesTable 1 }

-- {SEQUENCE}
LcsSetupIpv6RasInterfacesEntry ::= SEQUENCE {
    lcsSetupIpv6RasInterfacesEntryInterfaceName DisplayString,
    lcsSetupIpv6RasInterfacesEntryRtgTag INTEGER,
    lcsSetupIpv6RasInterfacesEntryInterfaceStatus INTEGER,
    lcsSetupIpv6RasInterfacesEntryForwarding INTEGER,
    lcsSetupIpv6RasInterfacesEntryFirewall INTEGER,
    lcsSetupIpv6RasInterfacesEntryDadAttempts INTEGER,
    lcsSetupIpv6RasInterfacesEntryPeerName DisplayString,
    lcsSetupIpv6RasInterfacesEntryComment DisplayString
}

-- {COLUMN} 1712.2.70.14.1.1
lcsSetupIpv6RasInterfacesEntryInterfaceName OBJECT-TYPE
    SYNTAX     DisplayString (SIZE(0..16))
    MAX-ACCESS read-write
    STATUS     current
    DESCRIPTION
        "-- empty --"
    ::= { lcsSetupIpv6RasInterfacesEntry 1 }

-- {COLUMN} 1712.2.70.14.1.2
lcsSetupIpv6RasInterfacesEntryRtgTag OBJECT-TYPE
    SYNTAX     INTEGER (0..65535)
    MAX-ACCESS read-write
    STATUS     current
    DESCRIPTION
        "-- empty --"
    ::= { lcsSetupIpv6RasInterfacesEntry 2 }

-- {COLUMN} 1712.2.70.14.1.3
lcsSetupIpv6RasInterfacesEntryInterfaceStatus OBJECT-TYPE
    SYNTAX     INTEGER
      {
        eUp (1),
        eDown (2)
      }
    MAX-ACCESS read-write
    STATUS     current
    DESCRIPTION
        "-- empty --"
    ::= { lcsSetupIpv6RasInterfacesEntry 3 }

-- {COLUMN} 1712.2.70.14.1.4
lcsSetupIpv6RasInterfacesEntryForwarding OBJECT-TYPE
    SYNTAX     INTEGER
      {
        eYes (0),
        eNo (1)
      }
    MAX-ACCESS read-write
    STATUS     current
    DESCRIPTION
        "-- empty --"
    ::= { lcsSetupIpv6RasInterfacesEntry 4 }

-- {COLUMN} 1712.2.70.14.1.5
lcsSetupIpv6RasInterfacesEntryFirewall OBJECT-TYPE
    SYNTAX     INTEGER
      {
        eYes (0),
        eNo (1)
      }
    MAX-ACCESS read-write
    STATUS     current
    DESCRIPTION
        "-- empty --"
    ::= { lcsSetupIpv6RasInterfacesEntry 5 }

-- {COLUMN} 1712.2.70.14.1.6
lcsSetupIpv6RasInterfacesEntryDadAttempts OBJECT-TYPE
    SYNTAX     INTEGER (0..255)
    MAX-ACCESS read-write
    STATUS     current
    DESCRIPTION
        "-- empty --"
    ::= { lcsSetupIpv6RasInterfacesEntry 6 }

-- {COLUMN} 1712.2.70.14.1.7
lcsSetupIpv6RasInterfacesEntryPeerName OBJECT-TYPE
    SYNTAX     DisplayString (SIZE(0..16))
    MAX-ACCESS read-write
    STATUS     current
    DESCRIPTION
        "-- empty --"
    ::= { lcsSetupIpv6RasInterfacesEntry 7 }

-- {COLUMN} 1712.2.70.14.1.8
lcsSetupIpv6RasInterfacesEntryComment OBJECT-TYPE
    SYNTAX     DisplayString (SIZE(0..64))
    MAX-ACCESS read-write
    STATUS     current
    DESCRIPTION
        "-- empty --"
    ::= { lcsSetupIpv6RasInterfacesEntry 8 }

-- {TABLE} 1712.2.70.13
lcsSetupIpv6Icmpv6Table OBJECT-TYPE
    SYNTAX     SEQUENCE OF LcsSetupIpv6Icmpv6Entry
    MAX-ACCESS not-accessible
    STATUS     current
    DESCRIPTION
        "-- empty --"
    ::= { lcsSetupIpv6 13 }

-- {ENTRY} 1712.2.70.13.1
lcsSetupIpv6Icmpv6Entry OBJECT-TYPE
    SYNTAX     LcsSetupIpv6Icmpv6Entry
    MAX-ACCESS not-accessible
    STATUS     current
    DESCRIPTION
        ""
    INDEX {
        lcsSetupIpv6Icmpv6EntryInterfaceName
    }
    ::= { lcsSetupIpv6Icmpv6Table 1 }

-- {SEQUENCE}
LcsSetupIpv6Icmpv6Entry ::= SEQUENCE {
    lcsSetupIpv6Icmpv6EntryInterfaceName DisplayString,
    lcsSetupIpv6Icmpv6EntryErrorBandwidth INTEGER,
    lcsSetupIpv6Icmpv6EntryRedirects INTEGER
}

-- {COLUMN} 1712.2.70.13.1.1
lcsSetupIpv6Icmpv6EntryInterfaceName OBJECT-TYPE
    SYNTAX     DisplayString (SIZE(0..16))
    MAX-ACCESS read-write
    STATUS     current
    DESCRIPTION
        "-- empty --"
    ::= { lcsSetupIpv6Icmpv6Entry 1 }

-- {COLUMN} 1712.2.70.13.1.2
lcsSetupIpv6Icmpv6EntryErrorBandwidth OBJECT-TYPE
    SYNTAX     INTEGER (0..2147483647)
    MAX-ACCESS read-write
    STATUS     current
    DESCRIPTION
        "-- empty --"
    ::= { lcsSetupIpv6Icmpv6Entry 2 }

-- {COLUMN} 1712.2.70.13.1.3
lcsSetupIpv6Icmpv6EntryRedirects OBJECT-TYPE
    SYNTAX     INTEGER
      {
        eEnable (1),
        eDisable (0)
      }
    MAX-ACCESS read-write
    STATUS     current
    DESCRIPTION
        "-- empty --"
    ::= { lcsSetupIpv6Icmpv6Entry 3 }

-- {SCALAR} 1712.2.70.10
lcsSetupIpv6Operating OBJECT-TYPE
    SYNTAX     INTEGER
      {
        eNo (0),
        eYes (1)
      }
    MAX-ACCESS read-write
    STATUS     current
    DESCRIPTION
        "-- empty --"
    ::= { lcsSetupIpv6 10 }

-- {SCALAR} 1712.2.70.11
lcsSetupIpv6Forwarding OBJECT-TYPE
    SYNTAX     INTEGER
      {
        eNo (0),
        eYes (1)
      }
    MAX-ACCESS read-write
    STATUS     current
    DESCRIPTION
        "-- empty --"
    ::= { lcsSetupIpv6 11 }

-- {OID} 1712.2.70.5
lcsSetupIpv6Firewall OBJECT IDENTIFIER ::= { lcsSetupIpv6 5 }

-- {SCALAR} 1712.2.70.5.1
lcsSetupIpv6FirewallOperating OBJECT-TYPE
    SYNTAX     INTEGER
      {
        eNo (0),
        eYes (1)
      }
    MAX-ACCESS read-write
    STATUS     current
    DESCRIPTION
        "-- empty --"
    ::= { lcsSetupIpv6Firewall 1 }

-- {TABLE} 1712.2.70.5.12
lcsSetupIpv6FirewallConditionsTable OBJECT-TYPE
    SYNTAX     SEQUENCE OF LcsSetupIpv6FirewallConditionsEntry
    MAX-ACCESS not-accessible
    STATUS     current
    DESCRIPTION
        "-- empty --"
    ::= { lcsSetupIpv6Firewall 12 }

-- {ENTRY} 1712.2.70.5.12.1
lcsSetupIpv6FirewallConditionsEntry OBJECT-TYPE
    SYNTAX     LcsSetupIpv6FirewallConditionsEntry
    MAX-ACCESS not-accessible
    STATUS     current
    DESCRIPTION
        ""
    INDEX {
        lcsSetupIpv6FirewallConditionsEntryName
    }
    ::= { lcsSetupIpv6FirewallConditionsTable 1 }

-- {SEQUENCE}
LcsSetupIpv6FirewallConditionsEntry ::= SEQUENCE {
    lcsSetupIpv6FirewallConditionsEntryName DisplayString,
    lcsSetupIpv6FirewallConditionsEntryConditions BITS,
    lcsSetupIpv6FirewallConditionsEntryTransportDirection INTEGER,
    lcsSetupIpv6FirewallConditionsEntryDiffserv INTEGER,
    lcsSetupIpv6FirewallConditionsEntryDscpValue INTEGER
}

-- {COLUMN} 1712.2.70.5.12.1.1
lcsSetupIpv6FirewallConditionsEntryName OBJECT-TYPE
    SYNTAX     DisplayString (SIZE(0..32))
    MAX-ACCESS read-write
    STATUS     current
    DESCRIPTION
        "-- empty --"
    ::= { lcsSetupIpv6FirewallConditionsEntry 1 }

-- {COLUMN} 1712.2.70.5.12.1.2
lcsSetupIpv6FirewallConditionsEntryConditions OBJECT-TYPE
    SYNTAX     BITS
      {
        eNotConnected (7),
        eDefaultRoute (6),
        eBackupConnection (5),
        eVpnRoute (4),
        eSent (3),
        eReceived (2)
      }
    MAX-ACCESS read-write
    STATUS     current
    DESCRIPTION
        "-- empty --"
    ::= { lcsSetupIpv6FirewallConditionsEntry 2 }

-- {COLUMN} 1712.2.70.5.12.1.3
lcsSetupIpv6FirewallConditionsEntryTransportDirection OBJECT-TYPE
    SYNTAX     INTEGER
      {
        ePhysical (0),
        eLogical (1)
      }
    MAX-ACCESS read-write
    STATUS     current
    DESCRIPTION
        "-- empty --"
    ::= { lcsSetupIpv6FirewallConditionsEntry 3 }

-- {COLUMN} 1712.2.70.5.12.1.4
lcsSetupIpv6FirewallConditionsEntryDiffserv OBJECT-TYPE
    SYNTAX     INTEGER
      {
        eBe (0),
        eEf (184),
        eCs0 (249),
        eCs1 (32),
        eCs2 (64),
        eCs3 (96),
        eCs4 (128),
        eCs5 (160),
        eCs6 (192),
        eCs7 (224),
        eCsx (240),
        eAf11 (40),
        eAf12 (48),
        eAf13 (56),
        eAf21 (72),
        eAf22 (80),
        eAf23 (88),
        eAf31 (104),
        eAf32 (112),
        eAf33 (120),
        eAf41 (136),
        eAf42 (144),
        eAf43 (152),
        eAf1x (241),
        eAf2x (242),
        eAf3x (243),
        eAf4x (244),
        eAfx1 (245),
        eAfx2 (246),
        eAfx3 (247),
        eAfxx (248),
        eIgnore (254),
        eValue (255)
      }
    MAX-ACCESS read-write
    STATUS     current
    DESCRIPTION
        "-- empty --"
    ::= { lcsSetupIpv6FirewallConditionsEntry 4 }

-- {COLUMN} 1712.2.70.5.12.1.5
lcsSetupIpv6FirewallConditionsEntryDscpValue OBJECT-TYPE
    SYNTAX     INTEGER (0..255)
    MAX-ACCESS read-write
    STATUS     current
    DESCRIPTION
        "-- empty --"
    ::= { lcsSetupIpv6FirewallConditionsEntry 5 }

-- {TABLE} 1712.2.70.5.13
lcsSetupIpv6FirewallTriggerActionsTable OBJECT-TYPE
    SYNTAX     SEQUENCE OF LcsSetupIpv6FirewallTriggerActionsEntry
    MAX-ACCESS not-accessible
    STATUS     current
    DESCRIPTION
        "-- empty --"
    ::= { lcsSetupIpv6Firewall 13 }

-- {ENTRY} 1712.2.70.5.13.1
lcsSetupIpv6FirewallTriggerActionsEntry OBJECT-TYPE
    SYNTAX     LcsSetupIpv6FirewallTriggerActionsEntry
    MAX-ACCESS not-accessible
    STATUS     current
    DESCRIPTION
        ""
    INDEX {
        lcsSetupIpv6FirewallTriggerActionsEntryName
    }
    ::= { lcsSetupIpv6FirewallTriggerActionsTable 1 }

-- {SEQUENCE}
LcsSetupIpv6FirewallTriggerActionsEntry ::= SEQUENCE {
    lcsSetupIpv6FirewallTriggerActionsEntryName DisplayString,
    lcsSetupIpv6FirewallTriggerActionsEntryNotifications BITS,
    lcsSetupIpv6FirewallTriggerActionsEntryDisconnect INTEGER,
    lcsSetupIpv6FirewallTriggerActionsEntryBlockSource INTEGER,
    lcsSetupIpv6FirewallTriggerActionsEntryBlockTime INTEGER,
    lcsSetupIpv6FirewallTriggerActionsEntryCloseDestination INTEGER,
    lcsSetupIpv6FirewallTriggerActionsEntryCloseTime INTEGER
}

-- {COLUMN} 1712.2.70.5.13.1.1
lcsSetupIpv6FirewallTriggerActionsEntryName OBJECT-TYPE
    SYNTAX     DisplayString (SIZE(0..32))
    MAX-ACCESS read-write
    STATUS     current
    DESCRIPTION
        "-- empty --"
    ::= { lcsSetupIpv6FirewallTriggerActionsEntry 1 }

-- {COLUMN} 1712.2.70.5.13.1.2
lcsSetupIpv6FirewallTriggerActionsEntryNotifications OBJECT-TYPE
    SYNTAX     BITS
      {
        eSnmp (7),
        eSyslog (6),
        eEmail (5)
      }
    MAX-ACCESS read-write
    STATUS     current
    DESCRIPTION
        "-- empty --"
    ::= { lcsSetupIpv6FirewallTriggerActionsEntry 2 }

-- {COLUMN} 1712.2.70.5.13.1.3
lcsSetupIpv6FirewallTriggerActionsEntryDisconnect OBJECT-TYPE
    SYNTAX     INTEGER
      {
        eNo (0),
        eYes (1)
      }
    MAX-ACCESS read-write
    STATUS     current
    DESCRIPTION
        "-- empty --"
    ::= { lcsSetupIpv6FirewallTriggerActionsEntry 3 }

-- {COLUMN} 1712.2.70.5.13.1.4
lcsSetupIpv6FirewallTriggerActionsEntryBlockSource OBJECT-TYPE
    SYNTAX     INTEGER
      {
        eNo (0),
        eYes (1)
      }
    MAX-ACCESS read-write
    STATUS     current
    DESCRIPTION
        "-- empty --"
    ::= { lcsSetupIpv6FirewallTriggerActionsEntry 4 }

-- {COLUMN} 1712.2.70.5.13.1.5
lcsSetupIpv6FirewallTriggerActionsEntryBlockTime OBJECT-TYPE
    SYNTAX     INTEGER (0..2147483647)
    MAX-ACCESS read-write
    STATUS     current
    DESCRIPTION
        "-- empty --"
    ::= { lcsSetupIpv6FirewallTriggerActionsEntry 5 }

-- {COLUMN} 1712.2.70.5.13.1.6
lcsSetupIpv6FirewallTriggerActionsEntryCloseDestination OBJECT-TYPE
    SYNTAX     INTEGER
      {
        eNo (0),
        eYes (1)
      }
    MAX-ACCESS read-write
    STATUS     current
    DESCRIPTION
        "-- empty --"
    ::= { lcsSetupIpv6FirewallTriggerActionsEntry 6 }

-- {COLUMN} 1712.2.70.5.13.1.7
lcsSetupIpv6FirewallTriggerActionsEntryCloseTime OBJECT-TYPE
    SYNTAX     INTEGER (0..2147483647)
    MAX-ACCESS read-write
    STATUS     current
    DESCRIPTION
        "-- empty --"
    ::= { lcsSetupIpv6FirewallTriggerActionsEntry 7 }

-- {TABLE} 1712.2.70.5.7
lcsSetupIpv6FirewallActionsTable OBJECT-TYPE
    SYNTAX     SEQUENCE OF LcsSetupIpv6FirewallActionsEntry
    MAX-ACCESS not-accessible
    STATUS     current
    DESCRIPTION
        "-- empty --"
    ::= { lcsSetupIpv6Firewall 7 }

-- {ENTRY} 1712.2.70.5.7.1
lcsSetupIpv6FirewallActionsEntry OBJECT-TYPE
    SYNTAX     LcsSetupIpv6FirewallActionsEntry
    MAX-ACCESS not-accessible
    STATUS     current
    DESCRIPTION
        ""
    INDEX {
        lcsSetupIpv6FirewallActionsEntryName
    }
    ::= { lcsSetupIpv6FirewallActionsTable 1 }

-- {SEQUENCE}
LcsSetupIpv6FirewallActionsEntry ::= SEQUENCE {
    lcsSetupIpv6FirewallActionsEntryName DisplayString,
    lcsSetupIpv6FirewallActionsEntryLimit INTEGER,
    lcsSetupIpv6FirewallActionsEntryUnit INTEGER,
    lcsSetupIpv6FirewallActionsEntryTime INTEGER,
    lcsSetupIpv6FirewallActionsEntryContext INTEGER,
    lcsSetupIpv6FirewallActionsEntryFlags BITS,
    lcsSetupIpv6FirewallActionsEntryAction INTEGER,
    lcsSetupIpv6FirewallActionsEntryDiffserv INTEGER,
    lcsSetupIpv6FirewallActionsEntryDscpValue INTEGER,
    lcsSetupIpv6FirewallActionsEntryConditions DisplayString,
    lcsSetupIpv6FirewallActionsEntryTriggerActions DisplayString
}

-- {COLUMN} 1712.2.70.5.7.1.1
lcsSetupIpv6FirewallActionsEntryName OBJECT-TYPE
    SYNTAX     DisplayString (SIZE(0..32))
    MAX-ACCESS read-write
    STATUS     current
    DESCRIPTION
        "-- empty --"
    ::= { lcsSetupIpv6FirewallActionsEntry 1 }

-- {COLUMN} 1712.2.70.5.7.1.2
lcsSetupIpv6FirewallActionsEntryLimit OBJECT-TYPE
    SYNTAX     INTEGER (0..2147483647)
    MAX-ACCESS read-write
    STATUS     current
    DESCRIPTION
        "-- empty --"
    ::= { lcsSetupIpv6FirewallActionsEntry 2 }

-- {COLUMN} 1712.2.70.5.7.1.3
lcsSetupIpv6FirewallActionsEntryUnit OBJECT-TYPE
    SYNTAX     INTEGER
      {
        eKbit (0),
        eKbytes (1),
        ePackets (2),
        eSessions (3),
        eBandwidth (4)
      }
    MAX-ACCESS read-write
    STATUS     current
    DESCRIPTION
        "-- empty --"
    ::= { lcsSetupIpv6FirewallActionsEntry 3 }

-- {COLUMN} 1712.2.70.5.7.1.4
lcsSetupIpv6FirewallActionsEntryTime OBJECT-TYPE
    SYNTAX     INTEGER
      {
        eSecond (0),
        eMinute (1),
        eHoute (2),
        eAbsolute (3)
      }
    MAX-ACCESS read-write
    STATUS     current
    DESCRIPTION
        "-- empty --"
    ::= { lcsSetupIpv6FirewallActionsEntry 4 }

-- {COLUMN} 1712.2.70.5.7.1.5
lcsSetupIpv6FirewallActionsEntryContext OBJECT-TYPE
    SYNTAX     INTEGER
      {
        eSession (0),
        eStation (1),
        eGlobal (2)
      }
    MAX-ACCESS read-write
    STATUS     current
    DESCRIPTION
        "-- empty --"
    ::= { lcsSetupIpv6FirewallActionsEntry 5 }

-- {COLUMN} 1712.2.70.5.7.1.6
lcsSetupIpv6FirewallActionsEntryFlags OBJECT-TYPE
    SYNTAX     BITS
      {
        eReset (7),
        eShared (6)
      }
    MAX-ACCESS read-write
    STATUS     current
    DESCRIPTION
        "-- empty --"
    ::= { lcsSetupIpv6FirewallActionsEntry 6 }

-- {COLUMN} 1712.2.70.5.7.1.7
lcsSetupIpv6FirewallActionsEntryAction OBJECT-TYPE
    SYNTAX     INTEGER
      {
        eReject (0),
        eDrop (1),
        eAccept (2),
        eCheck (4)
      }
    MAX-ACCESS read-write
    STATUS     current
    DESCRIPTION
        "-- empty --"
    ::= { lcsSetupIpv6FirewallActionsEntry 7 }

-- {COLUMN} 1712.2.70.5.7.1.11
lcsSetupIpv6FirewallActionsEntryDiffserv OBJECT-TYPE
    SYNTAX     INTEGER
      {
        eBe (0),
        eEf (184),
        eCs0 (249),
        eCs1 (32),
        eCs2 (64),
        eCs3 (96),
        eCs4 (128),
        eCs5 (160),
        eCs6 (192),
        eCs7 (224),
        eAf11 (40),
        eAf12 (48),
        eAf13 (56),
        eAf21 (72),
        eAf22 (80),
        eAf23 (88),
        eAf31 (104),
        eAf32 (112),
        eAf33 (120),
        eAf41 (136),
        eAf42 (144),
        eAf43 (152),
        eNo (254),
        eValue (255)
      }
    MAX-ACCESS read-write
    STATUS     current
    DESCRIPTION
        "-- empty --"
    ::= { lcsSetupIpv6FirewallActionsEntry 11 }

-- {COLUMN} 1712.2.70.5.7.1.12
lcsSetupIpv6FirewallActionsEntryDscpValue OBJECT-TYPE
    SYNTAX     INTEGER (0..255)
    MAX-ACCESS read-write
    STATUS     current
    DESCRIPTION
        "-- empty --"
    ::= { lcsSetupIpv6FirewallActionsEntry 12 }

-- {COLUMN} 1712.2.70.5.7.1.13
lcsSetupIpv6FirewallActionsEntryConditions OBJECT-TYPE
    SYNTAX     DisplayString (SIZE(0..32))
    MAX-ACCESS read-write
    STATUS     current
    DESCRIPTION
        "-- empty --"
    ::= { lcsSetupIpv6FirewallActionsEntry 13 }

-- {COLUMN} 1712.2.70.5.7.1.14
lcsSetupIpv6FirewallActionsEntryTriggerActions OBJECT-TYPE
    SYNTAX     DisplayString (SIZE(0..32))
    MAX-ACCESS read-write
    STATUS     current
    DESCRIPTION
        "-- empty --"
    ::= { lcsSetupIpv6FirewallActionsEntry 14 }

-- {TABLE} 1712.2.70.5.3
lcsSetupIpv6FirewallActionListTable OBJECT-TYPE
    SYNTAX     SEQUENCE OF LcsSetupIpv6FirewallActionListEntry
    MAX-ACCESS not-accessible
    STATUS     current
    DESCRIPTION
        "-- empty --"
    ::= { lcsSetupIpv6Firewall 3 }

-- {ENTRY} 1712.2.70.5.3.1
lcsSetupIpv6FirewallActionListEntry OBJECT-TYPE
    SYNTAX     LcsSetupIpv6FirewallActionListEntry
    MAX-ACCESS not-accessible
    STATUS     current
    DESCRIPTION
        ""
    INDEX {
        lcsSetupIpv6FirewallActionListEntryName
    }
    ::= { lcsSetupIpv6FirewallActionListTable 1 }

-- {SEQUENCE}
LcsSetupIpv6FirewallActionListEntry ::= SEQUENCE {
    lcsSetupIpv6FirewallActionListEntryName DisplayString,
    lcsSetupIpv6FirewallActionListEntryDescription DisplayString
}

-- {COLUMN} 1712.2.70.5.3.1.1
lcsSetupIpv6FirewallActionListEntryName OBJECT-TYPE
    SYNTAX     DisplayString (SIZE(0..36))
    MAX-ACCESS read-write
    STATUS     current
    DESCRIPTION
        "-- empty --"
    ::= { lcsSetupIpv6FirewallActionListEntry 1 }

-- {COLUMN} 1712.2.70.5.3.1.2
lcsSetupIpv6FirewallActionListEntryDescription OBJECT-TYPE
    SYNTAX     DisplayString (SIZE(0..252))
    MAX-ACCESS read-write
    STATUS     current
    DESCRIPTION
        "-- empty --"
    ::= { lcsSetupIpv6FirewallActionListEntry 2 }

-- {TABLE} 1712.2.70.5.11
lcsSetupIpv6FirewallProtocolsTable OBJECT-TYPE
    SYNTAX     SEQUENCE OF LcsSetupIpv6FirewallProtocolsEntry
    MAX-ACCESS not-accessible
    STATUS     current
    DESCRIPTION
        "-- empty --"
    ::= { lcsSetupIpv6Firewall 11 }

-- {ENTRY} 1712.2.70.5.11.1
lcsSetupIpv6FirewallProtocolsEntry OBJECT-TYPE
    SYNTAX     LcsSetupIpv6FirewallProtocolsEntry
    MAX-ACCESS not-accessible
    STATUS     current
    DESCRIPTION
        ""
    INDEX {
        lcsSetupIpv6FirewallProtocolsEntryName
    }
    ::= { lcsSetupIpv6FirewallProtocolsTable 1 }

-- {SEQUENCE}
LcsSetupIpv6FirewallProtocolsEntry ::= SEQUENCE {
    lcsSetupIpv6FirewallProtocolsEntryName DisplayString,
    lcsSetupIpv6FirewallProtocolsEntryProtocol INTEGER
}

-- {COLUMN} 1712.2.70.5.11.1.1
lcsSetupIpv6FirewallProtocolsEntryName OBJECT-TYPE
    SYNTAX     DisplayString (SIZE(0..32))
    MAX-ACCESS read-write
    STATUS     current
    DESCRIPTION
        "-- empty --"
    ::= { lcsSetupIpv6FirewallProtocolsEntry 1 }

-- {COLUMN} 1712.2.70.5.11.1.2
lcsSetupIpv6FirewallProtocolsEntryProtocol OBJECT-TYPE
    SYNTAX     INTEGER (0..2147483647)
    MAX-ACCESS read-write
    STATUS     current
    DESCRIPTION
        "-- empty --"
    ::= { lcsSetupIpv6FirewallProtocolsEntry 2 }

-- {TABLE} 1712.2.70.5.14
lcsSetupIpv6FirewallIcmpServicesTable OBJECT-TYPE
    SYNTAX     SEQUENCE OF LcsSetupIpv6FirewallIcmpServicesEntry
    MAX-ACCESS not-accessible
    STATUS     current
    DESCRIPTION
        "-- empty --"
    ::= { lcsSetupIpv6Firewall 14 }

-- {ENTRY} 1712.2.70.5.14.1
lcsSetupIpv6FirewallIcmpServicesEntry OBJECT-TYPE
    SYNTAX     LcsSetupIpv6FirewallIcmpServicesEntry
    MAX-ACCESS not-accessible
    STATUS     current
    DESCRIPTION
        ""
    INDEX {
        lcsSetupIpv6FirewallIcmpServicesEntryName
    }
    ::= { lcsSetupIpv6FirewallIcmpServicesTable 1 }

-- {SEQUENCE}
LcsSetupIpv6FirewallIcmpServicesEntry ::= SEQUENCE {
    lcsSetupIpv6FirewallIcmpServicesEntryName DisplayString,
    lcsSetupIpv6FirewallIcmpServicesEntryType INTEGER,
    lcsSetupIpv6FirewallIcmpServicesEntryCode INTEGER
}

-- {COLUMN} 1712.2.70.5.14.1.1
lcsSetupIpv6FirewallIcmpServicesEntryName OBJECT-TYPE
    SYNTAX     DisplayString (SIZE(0..32))
    MAX-ACCESS read-write
    STATUS     current
    DESCRIPTION
        "-- empty --"
    ::= { lcsSetupIpv6FirewallIcmpServicesEntry 1 }

-- {COLUMN} 1712.2.70.5.14.1.2
lcsSetupIpv6FirewallIcmpServicesEntryType OBJECT-TYPE
    SYNTAX     INTEGER (0..2147483647)
    MAX-ACCESS read-write
    STATUS     current
    DESCRIPTION
        "-- empty --"
    ::= { lcsSetupIpv6FirewallIcmpServicesEntry 2 }

-- {COLUMN} 1712.2.70.5.14.1.3
lcsSetupIpv6FirewallIcmpServicesEntryCode OBJECT-TYPE
    SYNTAX     INTEGER (0..2147483647)
    MAX-ACCESS read-write
    STATUS     current
    DESCRIPTION
        "-- empty --"
    ::= { lcsSetupIpv6FirewallIcmpServicesEntry 3 }

-- {TABLE} 1712.2.70.5.10
lcsSetupIpv6FirewallServicesTable OBJECT-TYPE
    SYNTAX     SEQUENCE OF LcsSetupIpv6FirewallServicesEntry
    MAX-ACCESS not-accessible
    STATUS     current
    DESCRIPTION
        "-- empty --"
    ::= { lcsSetupIpv6Firewall 10 }

-- {ENTRY} 1712.2.70.5.10.1
lcsSetupIpv6FirewallServicesEntry OBJECT-TYPE
    SYNTAX     LcsSetupIpv6FirewallServicesEntry
    MAX-ACCESS not-accessible
    STATUS     current
    DESCRIPTION
        ""
    INDEX {
        lcsSetupIpv6FirewallServicesEntryName
    }
    ::= { lcsSetupIpv6FirewallServicesTable 1 }

-- {SEQUENCE}
LcsSetupIpv6FirewallServicesEntry ::= SEQUENCE {
    lcsSetupIpv6FirewallServicesEntryName DisplayString,
    lcsSetupIpv6FirewallServicesEntryProtocol INTEGER,
    lcsSetupIpv6FirewallServicesEntryPorts DisplayString,
    lcsSetupIpv6FirewallServicesEntrySrcPorts INTEGER
}

-- {COLUMN} 1712.2.70.5.10.1.1
lcsSetupIpv6FirewallServicesEntryName OBJECT-TYPE
    SYNTAX     DisplayString (SIZE(0..32))
    MAX-ACCESS read-write
    STATUS     current
    DESCRIPTION
        "-- empty --"
    ::= { lcsSetupIpv6FirewallServicesEntry 1 }

-- {COLUMN} 1712.2.70.5.10.1.2
lcsSetupIpv6FirewallServicesEntryProtocol OBJECT-TYPE
    SYNTAX     INTEGER
      {
        eTcpPlusUdp (6),
        eTcp (2),
        eUdp (4)
      }
    MAX-ACCESS read-write
    STATUS     current
    DESCRIPTION
        "-- empty --"
    ::= { lcsSetupIpv6FirewallServicesEntry 2 }

-- {COLUMN} 1712.2.70.5.10.1.3
lcsSetupIpv6FirewallServicesEntryPorts OBJECT-TYPE
    SYNTAX     DisplayString (SIZE(0..64))
    MAX-ACCESS read-write
    STATUS     current
    DESCRIPTION
        "-- empty --"
    ::= { lcsSetupIpv6FirewallServicesEntry 3 }

-- {COLUMN} 1712.2.70.5.10.1.4
lcsSetupIpv6FirewallServicesEntrySrcPorts OBJECT-TYPE
    SYNTAX     INTEGER
      {
        eNo (0),
        eYes (1)
      }
    MAX-ACCESS read-write
    STATUS     current
    DESCRIPTION
        "-- empty --"
    ::= { lcsSetupIpv6FirewallServicesEntry 4 }

-- {TABLE} 1712.2.70.5.6
lcsSetupIpv6FirewallServiceListTable OBJECT-TYPE
    SYNTAX     SEQUENCE OF LcsSetupIpv6FirewallServiceListEntry
    MAX-ACCESS not-accessible
    STATUS     current
    DESCRIPTION
        "-- empty --"
    ::= { lcsSetupIpv6Firewall 6 }

-- {ENTRY} 1712.2.70.5.6.1
lcsSetupIpv6FirewallServiceListEntry OBJECT-TYPE
    SYNTAX     LcsSetupIpv6FirewallServiceListEntry
    MAX-ACCESS not-accessible
    STATUS     current
    DESCRIPTION
        ""
    INDEX {
        lcsSetupIpv6FirewallServiceListEntryName
    }
    ::= { lcsSetupIpv6FirewallServiceListTable 1 }

-- {SEQUENCE}
LcsSetupIpv6FirewallServiceListEntry ::= SEQUENCE {
    lcsSetupIpv6FirewallServiceListEntryName DisplayString,
    lcsSetupIpv6FirewallServiceListEntryDescription DisplayString
}

-- {COLUMN} 1712.2.70.5.6.1.1
lcsSetupIpv6FirewallServiceListEntryName OBJECT-TYPE
    SYNTAX     DisplayString (SIZE(0..36))
    MAX-ACCESS read-write
    STATUS     current
    DESCRIPTION
        "-- empty --"
    ::= { lcsSetupIpv6FirewallServiceListEntry 1 }

-- {COLUMN} 1712.2.70.5.6.1.2
lcsSetupIpv6FirewallServiceListEntryDescription OBJECT-TYPE
    SYNTAX     DisplayString (SIZE(0..252))
    MAX-ACCESS read-write
    STATUS     current
    DESCRIPTION
        "-- empty --"
    ::= { lcsSetupIpv6FirewallServiceListEntry 2 }

-- {TABLE} 1712.2.70.5.9
lcsSetupIpv6FirewallStationsTable OBJECT-TYPE
    SYNTAX     SEQUENCE OF LcsSetupIpv6FirewallStationsEntry
    MAX-ACCESS not-accessible
    STATUS     current
    DESCRIPTION
        "-- empty --"
    ::= { lcsSetupIpv6Firewall 9 }

-- {ENTRY} 1712.2.70.5.9.1
lcsSetupIpv6FirewallStationsEntry OBJECT-TYPE
    SYNTAX     LcsSetupIpv6FirewallStationsEntry
    MAX-ACCESS not-accessible
    STATUS     current
    DESCRIPTION
        ""
    INDEX {
        lcsSetupIpv6FirewallStationsEntryName
    }
    ::= { lcsSetupIpv6FirewallStationsTable 1 }

-- {SEQUENCE}
LcsSetupIpv6FirewallStationsEntry ::= SEQUENCE {
    lcsSetupIpv6FirewallStationsEntryName DisplayString,
    lcsSetupIpv6FirewallStationsEntryType INTEGER,
    lcsSetupIpv6FirewallStationsEntryLocalNetwork DisplayString,
    lcsSetupIpv6FirewallStationsEntryRemotePeerLocalHost DisplayString,
    lcsSetupIpv6FirewallStationsEntryAddressPrefix DisplayString
}

-- {COLUMN} 1712.2.70.5.9.1.1
lcsSetupIpv6FirewallStationsEntryName OBJECT-TYPE
    SYNTAX     DisplayString (SIZE(0..32))
    MAX-ACCESS read-write
    STATUS     current
    DESCRIPTION
        "-- empty --"
    ::= { lcsSetupIpv6FirewallStationsEntry 1 }

-- {COLUMN} 1712.2.70.5.9.1.2
lcsSetupIpv6FirewallStationsEntryType OBJECT-TYPE
    SYNTAX     INTEGER
      {
        eLocalNetwork (0),
        eRemotePeer (1),
        ePrefix (2),
        eIdentifier (3),
        eIpAddress (4),
        eNamedHost (5)
      }
    MAX-ACCESS read-write
    STATUS     current
    DESCRIPTION
        "-- empty --"
    ::= { lcsSetupIpv6FirewallStationsEntry 2 }

-- {COLUMN} 1712.2.70.5.9.1.3
lcsSetupIpv6FirewallStationsEntryLocalNetwork OBJECT-TYPE
    SYNTAX     DisplayString (SIZE(0..16))
    MAX-ACCESS read-write
    STATUS     current
    DESCRIPTION
        "-- empty --"
    ::= { lcsSetupIpv6FirewallStationsEntry 3 }

-- {COLUMN} 1712.2.70.5.9.1.6
lcsSetupIpv6FirewallStationsEntryRemotePeerLocalHost OBJECT-TYPE
    SYNTAX     DisplayString (SIZE(0..64))
    MAX-ACCESS read-write
    STATUS     current
    DESCRIPTION
        "-- empty --"
    ::= { lcsSetupIpv6FirewallStationsEntry 6 }

-- {COLUMN} 1712.2.70.5.9.1.7
lcsSetupIpv6FirewallStationsEntryAddressPrefix OBJECT-TYPE
    SYNTAX     DisplayString (SIZE(0..43))
    MAX-ACCESS read-write
    STATUS     current
    DESCRIPTION
        "-- empty --"
    ::= { lcsSetupIpv6FirewallStationsEntry 7 }

-- {TABLE} 1712.2.70.5.5
lcsSetupIpv6FirewallStationListTable OBJECT-TYPE
    SYNTAX     SEQUENCE OF LcsSetupIpv6FirewallStationListEntry
    MAX-ACCESS not-accessible
    STATUS     current
    DESCRIPTION
        "-- empty --"
    ::= { lcsSetupIpv6Firewall 5 }

-- {ENTRY} 1712.2.70.5.5.1
lcsSetupIpv6FirewallStationListEntry OBJECT-TYPE
    SYNTAX     LcsSetupIpv6FirewallStationListEntry
    MAX-ACCESS not-accessible
    STATUS     current
    DESCRIPTION
        ""
    INDEX {
        lcsSetupIpv6FirewallStationListEntryName
    }
    ::= { lcsSetupIpv6FirewallStationListTable 1 }

-- {SEQUENCE}
LcsSetupIpv6FirewallStationListEntry ::= SEQUENCE {
    lcsSetupIpv6FirewallStationListEntryName DisplayString,
    lcsSetupIpv6FirewallStationListEntryDescription DisplayString
}

-- {COLUMN} 1712.2.70.5.5.1.1
lcsSetupIpv6FirewallStationListEntryName OBJECT-TYPE
    SYNTAX     DisplayString (SIZE(0..36))
    MAX-ACCESS read-write
    STATUS     current
    DESCRIPTION
        "-- empty --"
    ::= { lcsSetupIpv6FirewallStationListEntry 1 }

-- {COLUMN} 1712.2.70.5.5.1.2
lcsSetupIpv6FirewallStationListEntryDescription OBJECT-TYPE
    SYNTAX     DisplayString (SIZE(0..252))
    MAX-ACCESS read-write
    STATUS     current
    DESCRIPTION
        "-- empty --"
    ::= { lcsSetupIpv6FirewallStationListEntry 2 }

-- {TABLE} 1712.2.70.5.2
lcsSetupIpv6FirewallForwardingRulesTable OBJECT-TYPE
    SYNTAX     SEQUENCE OF LcsSetupIpv6FirewallForwardingRulesEntry
    MAX-ACCESS not-accessible
    STATUS     current
    DESCRIPTION
        "-- empty --"
    ::= { lcsSetupIpv6Firewall 2 }

-- {ENTRY} 1712.2.70.5.2.1
lcsSetupIpv6FirewallForwardingRulesEntry OBJECT-TYPE
    SYNTAX     LcsSetupIpv6FirewallForwardingRulesEntry
    MAX-ACCESS not-accessible
    STATUS     current
    DESCRIPTION
        ""
    INDEX {
        lcsSetupIpv6FirewallForwardingRulesEntryName
    }
    ::= { lcsSetupIpv6FirewallForwardingRulesTable 1 }

-- {SEQUENCE}
LcsSetupIpv6FirewallForwardingRulesEntry ::= SEQUENCE {
    lcsSetupIpv6FirewallForwardingRulesEntryName DisplayString,
    lcsSetupIpv6FirewallForwardingRulesEntryAction DisplayString,
    lcsSetupIpv6FirewallForwardingRulesEntryServices DisplayString,
    lcsSetupIpv6FirewallForwardingRulesEntrySourceStations DisplayString,
    lcsSetupIpv6FirewallForwardingRulesEntryDestinationStations DisplayString,
    lcsSetupIpv6FirewallForwardingRulesEntryFlags BITS,
    lcsSetupIpv6FirewallForwardingRulesEntryPrio INTEGER,
    lcsSetupIpv6FirewallForwardingRulesEntrySrcTag INTEGER,
    lcsSetupIpv6FirewallForwardingRulesEntryRtgTag INTEGER,
    lcsSetupIpv6FirewallForwardingRulesEntryComment DisplayString
}

-- {COLUMN} 1712.2.70.5.2.1.1
lcsSetupIpv6FirewallForwardingRulesEntryName OBJECT-TYPE
    SYNTAX     DisplayString (SIZE(0..36))
    MAX-ACCESS read-write
    STATUS     current
    DESCRIPTION
        "-- empty --"
    ::= { lcsSetupIpv6FirewallForwardingRulesEntry 1 }

-- {COLUMN} 1712.2.70.5.2.1.5
lcsSetupIpv6FirewallForwardingRulesEntryAction OBJECT-TYPE
    SYNTAX     DisplayString (SIZE(0..64))
    MAX-ACCESS read-write
    STATUS     current
    DESCRIPTION
        "-- empty --"
    ::= { lcsSetupIpv6FirewallForwardingRulesEntry 5 }

-- {COLUMN} 1712.2.70.5.2.1.7
lcsSetupIpv6FirewallForwardingRulesEntryServices OBJECT-TYPE
    SYNTAX     DisplayString (SIZE(0..64))
    MAX-ACCESS read-write
    STATUS     current
    DESCRIPTION
        "-- empty --"
    ::= { lcsSetupIpv6FirewallForwardingRulesEntry 7 }

-- {COLUMN} 1712.2.70.5.2.1.8
lcsSetupIpv6FirewallForwardingRulesEntrySourceStations OBJECT-TYPE
    SYNTAX     DisplayString (SIZE(0..64))
    MAX-ACCESS read-write
    STATUS     current
    DESCRIPTION
        "-- empty --"
    ::= { lcsSetupIpv6FirewallForwardingRulesEntry 8 }

-- {COLUMN} 1712.2.70.5.2.1.9
lcsSetupIpv6FirewallForwardingRulesEntryDestinationStations OBJECT-TYPE
    SYNTAX     DisplayString (SIZE(0..64))
    MAX-ACCESS read-write
    STATUS     current
    DESCRIPTION
        "-- empty --"
    ::= { lcsSetupIpv6FirewallForwardingRulesEntry 9 }

-- {COLUMN} 1712.2.70.5.2.1.2
lcsSetupIpv6FirewallForwardingRulesEntryFlags OBJECT-TYPE
    SYNTAX     BITS
      {
        eDeactivated (7),
        eLinked (5),
        eStateless (4)
      }
    MAX-ACCESS read-write
    STATUS     current
    DESCRIPTION
        "-- empty --"
    ::= { lcsSetupIpv6FirewallForwardingRulesEntry 2 }

-- {COLUMN} 1712.2.70.5.2.1.3
lcsSetupIpv6FirewallForwardingRulesEntryPrio OBJECT-TYPE
    SYNTAX     INTEGER (0..65535)
    MAX-ACCESS read-write
    STATUS     current
    DESCRIPTION
        "-- empty --"
    ::= { lcsSetupIpv6FirewallForwardingRulesEntry 3 }

-- {COLUMN} 1712.2.70.5.2.1.11
lcsSetupIpv6FirewallForwardingRulesEntrySrcTag OBJECT-TYPE
    SYNTAX     INTEGER (0..65535)
    MAX-ACCESS read-write
    STATUS     current
    DESCRIPTION
        "-- empty --"
    ::= { lcsSetupIpv6FirewallForwardingRulesEntry 11 }

-- {COLUMN} 1712.2.70.5.2.1.4
lcsSetupIpv6FirewallForwardingRulesEntryRtgTag OBJECT-TYPE
    SYNTAX     INTEGER (0..65535)
    MAX-ACCESS read-write
    STATUS     current
    DESCRIPTION
        "-- empty --"
    ::= { lcsSetupIpv6FirewallForwardingRulesEntry 4 }

-- {COLUMN} 1712.2.70.5.2.1.10
lcsSetupIpv6FirewallForwardingRulesEntryComment OBJECT-TYPE
    SYNTAX     DisplayString (SIZE(0..64))
    MAX-ACCESS read-write
    STATUS     current
    DESCRIPTION
        "-- empty --"
    ::= { lcsSetupIpv6FirewallForwardingRulesEntry 10 }

-- {TABLE} 1712.2.70.5.15
lcsSetupIpv6FirewallInboundRulesTable OBJECT-TYPE
    SYNTAX     SEQUENCE OF LcsSetupIpv6FirewallInboundRulesEntry
    MAX-ACCESS not-accessible
    STATUS     current
    DESCRIPTION
        "-- empty --"
    ::= { lcsSetupIpv6Firewall 15 }

-- {ENTRY} 1712.2.70.5.15.1
lcsSetupIpv6FirewallInboundRulesEntry OBJECT-TYPE
    SYNTAX     LcsSetupIpv6FirewallInboundRulesEntry
    MAX-ACCESS not-accessible
    STATUS     current
    DESCRIPTION
        ""
    INDEX {
        lcsSetupIpv6FirewallInboundRulesEntryName
    }
    ::= { lcsSetupIpv6FirewallInboundRulesTable 1 }

-- {SEQUENCE}
LcsSetupIpv6FirewallInboundRulesEntry ::= SEQUENCE {
    lcsSetupIpv6FirewallInboundRulesEntryName DisplayString,
    lcsSetupIpv6FirewallInboundRulesEntryAction DisplayString,
    lcsSetupIpv6FirewallInboundRulesEntryServices DisplayString,
    lcsSetupIpv6FirewallInboundRulesEntrySourceStations DisplayString,
    lcsSetupIpv6FirewallInboundRulesEntryActive INTEGER,
    lcsSetupIpv6FirewallInboundRulesEntryPrio INTEGER,
    lcsSetupIpv6FirewallInboundRulesEntrySrcTag INTEGER,
    lcsSetupIpv6FirewallInboundRulesEntryComment DisplayString
}

-- {COLUMN} 1712.2.70.5.15.1.1
lcsSetupIpv6FirewallInboundRulesEntryName OBJECT-TYPE
    SYNTAX     DisplayString (SIZE(0..36))
    MAX-ACCESS read-write
    STATUS     current
    DESCRIPTION
        "-- empty --"
    ::= { lcsSetupIpv6FirewallInboundRulesEntry 1 }

-- {COLUMN} 1712.2.70.5.15.1.5
lcsSetupIpv6FirewallInboundRulesEntryAction OBJECT-TYPE
    SYNTAX     DisplayString (SIZE(0..64))
    MAX-ACCESS read-write
    STATUS     current
    DESCRIPTION
        "-- empty --"
    ::= { lcsSetupIpv6FirewallInboundRulesEntry 5 }

-- {COLUMN} 1712.2.70.5.15.1.7
lcsSetupIpv6FirewallInboundRulesEntryServices OBJECT-TYPE
    SYNTAX     DisplayString (SIZE(0..64))
    MAX-ACCESS read-write
    STATUS     current
    DESCRIPTION
        "-- empty --"
    ::= { lcsSetupIpv6FirewallInboundRulesEntry 7 }

-- {COLUMN} 1712.2.70.5.15.1.8
lcsSetupIpv6FirewallInboundRulesEntrySourceStations OBJECT-TYPE
    SYNTAX     DisplayString (SIZE(0..64))
    MAX-ACCESS read-write
    STATUS     current
    DESCRIPTION
        "-- empty --"
    ::= { lcsSetupIpv6FirewallInboundRulesEntry 8 }

-- {COLUMN} 1712.2.70.5.15.1.2
lcsSetupIpv6FirewallInboundRulesEntryActive OBJECT-TYPE
    SYNTAX     INTEGER
      {
        eYes (0),
        eNo (1)
      }
    MAX-ACCESS read-write
    STATUS     current
    DESCRIPTION
        "-- empty --"
    ::= { lcsSetupIpv6FirewallInboundRulesEntry 2 }

-- {COLUMN} 1712.2.70.5.15.1.3
lcsSetupIpv6FirewallInboundRulesEntryPrio OBJECT-TYPE
    SYNTAX     INTEGER (0..65535)
    MAX-ACCESS read-write
    STATUS     current
    DESCRIPTION
        "-- empty --"
    ::= { lcsSetupIpv6FirewallInboundRulesEntry 3 }

-- {COLUMN} 1712.2.70.5.15.1.11
lcsSetupIpv6FirewallInboundRulesEntrySrcTag OBJECT-TYPE
    SYNTAX     INTEGER (0..65535)
    MAX-ACCESS read-write
    STATUS     current
    DESCRIPTION
        "-- empty --"
    ::= { lcsSetupIpv6FirewallInboundRulesEntry 11 }

-- {COLUMN} 1712.2.70.5.15.1.10
lcsSetupIpv6FirewallInboundRulesEntryComment OBJECT-TYPE
    SYNTAX     DisplayString (SIZE(0..64))
    MAX-ACCESS read-write
    STATUS     current
    DESCRIPTION
        "-- empty --"
    ::= { lcsSetupIpv6FirewallInboundRulesEntry 10 }

-- {SCALAR} 1712.2.70.5.20
lcsSetupIpv6FirewallAllowRouteOptions OBJECT-TYPE
    SYNTAX     INTEGER
      {
        eNo (0),
        eYes (1)
      }
    MAX-ACCESS read-write
    STATUS     current
    DESCRIPTION
        "-- empty --"
    ::= { lcsSetupIpv6Firewall 20 }

-- {SCALAR} 1712.2.70.5.21
lcsSetupIpv6FirewallDestinationCacheLimit OBJECT-TYPE
    SYNTAX     INTEGER (0..2147483647)
    MAX-ACCESS read-write
    STATUS     current
    DESCRIPTION
        "-- empty --"
    ::= { lcsSetupIpv6Firewall 21 }

-- {OID} 1712.2.52
lcsSetupComPorts OBJECT IDENTIFIER ::= { lcsSetup 52 }

-- {TABLE} 1712.2.52.1
lcsSetupComPortsDevTable OBJECT-TYPE
    SYNTAX     SEQUENCE OF LcsSetupComPortsDevEntry
    MAX-ACCESS not-accessible
    STATUS     current
    DESCRIPTION
        ""
    ::= { lcsSetupComPorts 1 }

-- {ENTRY} 1712.2.52.1.1
lcsSetupComPortsDevEntry OBJECT-TYPE
    SYNTAX     LcsSetupComPortsDevEntry
    MAX-ACCESS not-accessible
    STATUS     current
    DESCRIPTION
        ""
    INDEX {
        lcsSetupComPortsDevEntryDeviceType
    }
    ::= { lcsSetupComPortsDevTable 1 }

-- {SEQUENCE}
LcsSetupComPortsDevEntry ::= SEQUENCE {
    lcsSetupComPortsDevEntryDeviceType INTEGER,
    lcsSetupComPortsDevEntryServ INTEGER
}

-- {COLUMN} 1712.2.52.1.1.1
lcsSetupComPortsDevEntryDeviceType OBJECT-TYPE
    SYNTAX     INTEGER
      {
        eOutband (1),
        eSierraDirectIp (53),
        eOptionIcon (17),
        eNovatelMerlinMc950d (26),
        eSierraCompass885 (39),
        eSierraAircard875u (30),
        eHuaweiE172E220E870 (31),
        eHuaweiE612E630E1750 (21),
        eHuaweiE1750 (57),
        eHuaweiE182 (54),
        eHuaweiK3765 (51),
        eHuaweiK4505 (49),
        e4gSystemsUxs1 (23),
        eBelkinF5u103 (33),
        eProlific2303 (34),
        eFtdi8u232am (35),
        eSierraAircard501 (46),
        eNokiaCs19 (59),
        eHuaweiE398 (60),
        eHuaweiE352 (64),
        eHuaweiE1550 (61)
      }
    MAX-ACCESS read-write
    STATUS     current
    DESCRIPTION
        "-- empty --"
    ::= { lcsSetupComPortsDevEntry 1 }

-- {COLUMN} 1712.2.52.1.1.4
lcsSetupComPortsDevEntryServ OBJECT-TYPE
    SYNTAX     INTEGER
      {
        eWan (1),
        eCOMPortServ (2)
      }
    MAX-ACCESS read-write
    STATUS     current
    DESCRIPTION
        ""
    ::= { lcsSetupComPortsDevEntry 4 }

-- {OID} 1712.2.52.3
lcsSetupComPortsWan OBJECT IDENTIFIER ::= { lcsSetupComPorts 3 }

-- {TABLE} 1712.2.52.3.1
lcsSetupComPortsWanDevTable OBJECT-TYPE
    SYNTAX     SEQUENCE OF LcsSetupComPortsWanDevEntry
    MAX-ACCESS not-accessible
    STATUS     current
    DESCRIPTION
        ""
    ::= { lcsSetupComPortsWan 1 }

-- {ENTRY} 1712.2.52.3.1.1
lcsSetupComPortsWanDevEntry OBJECT-TYPE
    SYNTAX     LcsSetupComPortsWanDevEntry
    MAX-ACCESS not-accessible
    STATUS     current
    DESCRIPTION
        ""
    INDEX {
        lcsSetupComPortsWanDevEntryDeviceType
    }
    ::= { lcsSetupComPortsWanDevTable 1 }

-- {SEQUENCE}
LcsSetupComPortsWanDevEntry ::= SEQUENCE {
    lcsSetupComPortsWanDevEntryDeviceType INTEGER,
    lcsSetupComPortsWanDevEntryOperating INTEGER
}

-- {COLUMN} 1712.2.52.3.1.1.1
lcsSetupComPortsWanDevEntryDeviceType OBJECT-TYPE
    SYNTAX     INTEGER
      {
        eOutbandModem (2),
        eSierraDirectIp (53),
        eOptionIcon (17),
        eNovatelMerlinMc950d (26),
        eSierraCompass885 (39),
        eSierraAircard875u (30),
        eHuaweiE172E220E870 (31),
        eHuaweiE612E630E1750 (21),
        eHuaweiE1750 (57),
        eHuaweiE182 (54),
        eHuaweiK3765 (51),
        eHuaweiK4505 (49),
        e4gSystemsUxs1 (23),
        eBelkinF5u103 (33),
        eProlific2303 (34),
        eFtdi8u232am (35),
        eSierraAircard501 (46),
        eNokiaCs19 (59),
        eHuaweiE398 (60),
        eHuaweiE352 (64),
        eHuaweiE1550 (61)
      }
    MAX-ACCESS read-write
    STATUS     current
    DESCRIPTION
        "-- empty --"
    ::= { lcsSetupComPortsWanDevEntry 1 }

-- {COLUMN} 1712.2.52.3.1.1.3
lcsSetupComPortsWanDevEntryOperating OBJECT-TYPE
    SYNTAX     INTEGER
      {
        eNo (0),
        eYes (1)
      }
    MAX-ACCESS read-write
    STATUS     current
    DESCRIPTION
        "-- empty --"
    ::= { lcsSetupComPortsWanDevEntry 3 }

-- {OID} 1712.2.52.2
lcsSetupComPortsCOMPortServ OBJECT IDENTIFIER ::= { lcsSetupComPorts 2 }

-- {TABLE} 1712.2.52.2.1
lcsSetupComPortsCOMPortServOperTable OBJECT-TYPE
    SYNTAX     SEQUENCE OF LcsSetupComPortsCOMPortServOperEntry
    MAX-ACCESS not-accessible
    STATUS     current
    DESCRIPTION
        ""
    ::= { lcsSetupComPortsCOMPortServ 1 }

-- {ENTRY} 1712.2.52.2.1.1
lcsSetupComPortsCOMPortServOperEntry OBJECT-TYPE
    SYNTAX     LcsSetupComPortsCOMPortServOperEntry
    MAX-ACCESS not-accessible
    STATUS     current
    DESCRIPTION
        ""
    INDEX {
        lcsSetupComPortsCOMPortServOperEntryDeviceType,
        lcsSetupComPortsCOMPortServOperEntryPortNumber
    }
    ::= { lcsSetupComPortsCOMPortServOperTable 1 }

-- {SEQUENCE}
LcsSetupComPortsCOMPortServOperEntry ::= SEQUENCE {
    lcsSetupComPortsCOMPortServOperEntryDeviceType INTEGER,
    lcsSetupComPortsCOMPortServOperEntryPortNumber INTEGER,
    lcsSetupComPortsCOMPortServOperEntryOperating INTEGER
}

-- {COLUMN} 1712.2.52.2.1.1.1
lcsSetupComPortsCOMPortServOperEntryDeviceType OBJECT-TYPE
    SYNTAX     INTEGER
      {
        eOutband (1),
        eBelkinF5u103 (33),
        eProlific2303 (34),
        eFtdi8u232am (35)
      }
    MAX-ACCESS read-write
    STATUS     current
    DESCRIPTION
        "-- empty --"
    ::= { lcsSetupComPortsCOMPortServOperEntry 1 }

-- {COLUMN} 1712.2.52.2.1.1.2
lcsSetupComPortsCOMPortServOperEntryPortNumber OBJECT-TYPE
    SYNTAX     INTEGER (0..255)
    MAX-ACCESS read-write
    STATUS     current
    DESCRIPTION
        "-- empty --"
    ::= { lcsSetupComPortsCOMPortServOperEntry 2 }

-- {COLUMN} 1712.2.52.2.1.1.4
lcsSetupComPortsCOMPortServOperEntryOperating OBJECT-TYPE
    SYNTAX     INTEGER
      {
        eNo (0),
        eYes (1)
      }
    MAX-ACCESS read-write
    STATUS     current
    DESCRIPTION
        "-- empty --"
    ::= { lcsSetupComPortsCOMPortServOperEntry 4 }

-- {TABLE} 1712.2.52.2.2
lcsSetupComPortsCOMPortServCOMPortSetTable OBJECT-TYPE
    SYNTAX     SEQUENCE OF LcsSetupComPortsCOMPortServCOMPortSetEntry
    MAX-ACCESS not-accessible
    STATUS     current
    DESCRIPTION
        ""
    ::= { lcsSetupComPortsCOMPortServ 2 }

-- {ENTRY} 1712.2.52.2.2.1
lcsSetupComPortsCOMPortServCOMPortSetEntry OBJECT-TYPE
    SYNTAX     LcsSetupComPortsCOMPortServCOMPortSetEntry
    MAX-ACCESS not-accessible
    STATUS     current
    DESCRIPTION
        ""
    INDEX {
        lcsSetupComPortsCOMPortServCOMPortSetEntryDeviceType,
        lcsSetupComPortsCOMPortServCOMPortSetEntryPortNumber
    }
    ::= { lcsSetupComPortsCOMPortServCOMPortSetTable 1 }

-- {SEQUENCE}
LcsSetupComPortsCOMPortServCOMPortSetEntry ::= SEQUENCE {
    lcsSetupComPortsCOMPortServCOMPortSetEntryDeviceType INTEGER,
    lcsSetupComPortsCOMPortServCOMPortSetEntryPortNumber INTEGER,
    lcsSetupComPortsCOMPortServCOMPortSetEntryBitRate INTEGER,
    lcsSetupComPortsCOMPortServCOMPortSetEntryDataBits INTEGER,
    lcsSetupComPortsCOMPortServCOMPortSetEntryParity INTEGER,
    lcsSetupComPortsCOMPortServCOMPortSetEntryStopBits INTEGER,
    lcsSetupComPortsCOMPortServCOMPortSetEntryHandshake INTEGER,
    lcsSetupComPortsCOMPortServCOMPortSetEntryReadyCondition INTEGER,
    lcsSetupComPortsCOMPortServCOMPortSetEntryReadyDataTimeout INTEGER
}

-- {COLUMN} 1712.2.52.2.2.1.1
lcsSetupComPortsCOMPortServCOMPortSetEntryDeviceType OBJECT-TYPE
    SYNTAX     INTEGER
      {
        eOutband (1),
        eBelkinF5u103 (33),
        eProlific2303 (34),
        eFtdi8u232am (35)
      }
    MAX-ACCESS read-write
    STATUS     current
    DESCRIPTION
        "-- empty --"
    ::= { lcsSetupComPortsCOMPortServCOMPortSetEntry 1 }

-- {COLUMN} 1712.2.52.2.2.1.2
lcsSetupComPortsCOMPortServCOMPortSetEntryPortNumber OBJECT-TYPE
    SYNTAX     INTEGER (0..255)
    MAX-ACCESS read-write
    STATUS     current
    DESCRIPTION
        "-- empty --"
    ::= { lcsSetupComPortsCOMPortServCOMPortSetEntry 2 }

-- {COLUMN} 1712.2.52.2.2.1.4
lcsSetupComPortsCOMPortServCOMPortSetEntryBitRate OBJECT-TYPE
    SYNTAX     INTEGER
      {
        e110 (110),
        e300 (300),
        e600 (600),
        e1200 (1200),
        e2400 (2400),
        e4800 (4800),
        e9600 (9600),
        e19200 (19200),
        e38400 (38400),
        e57600 (57600),
        e115200 (115200),
        e125000 (125000),
        e230400 (230400)
      }
    MAX-ACCESS read-write
    STATUS     current
    DESCRIPTION
        "-- empty --"
    ::= { lcsSetupComPortsCOMPortServCOMPortSetEntry 4 }

-- {COLUMN} 1712.2.52.2.2.1.5
lcsSetupComPortsCOMPortServCOMPortSetEntryDataBits OBJECT-TYPE
    SYNTAX     INTEGER
      {
        e7 (7),
        e8 (8)
      }
    MAX-ACCESS read-write
    STATUS     current
    DESCRIPTION
        "-- empty --"
    ::= { lcsSetupComPortsCOMPortServCOMPortSetEntry 5 }

-- {COLUMN} 1712.2.52.2.2.1.6
lcsSetupComPortsCOMPortServCOMPortSetEntryParity OBJECT-TYPE
    SYNTAX     INTEGER
      {
        eNone (1),
        eOdd (2),
        eEven (3)
      }
    MAX-ACCESS read-write
    STATUS     current
    DESCRIPTION
        "-- empty --"
    ::= { lcsSetupComPortsCOMPortServCOMPortSetEntry 6 }

-- {COLUMN} 1712.2.52.2.2.1.7
lcsSetupComPortsCOMPortServCOMPortSetEntryStopBits OBJECT-TYPE
    SYNTAX     INTEGER
      {
        e1 (1),
        e2 (2)
      }
    MAX-ACCESS read-write
    STATUS     current
    DESCRIPTION
        "-- empty --"
    ::= { lcsSetupComPortsCOMPortServCOMPortSetEntry 7 }

-- {COLUMN} 1712.2.52.2.2.1.8
lcsSetupComPortsCOMPortServCOMPortSetEntryHandshake OBJECT-TYPE
    SYNTAX     INTEGER
      {
        eNone (0),
        eRtsCts (1)
      }
    MAX-ACCESS read-write
    STATUS     current
    DESCRIPTION
        "-- empty --"
    ::= { lcsSetupComPortsCOMPortServCOMPortSetEntry 8 }

-- {COLUMN} 1712.2.52.2.2.1.9
lcsSetupComPortsCOMPortServCOMPortSetEntryReadyCondition OBJECT-TYPE
    SYNTAX     INTEGER
      {
        eDtr (0),
        eData (1)
      }
    MAX-ACCESS read-write
    STATUS     current
    DESCRIPTION
        "-- empty --"
    ::= { lcsSetupComPortsCOMPortServCOMPortSetEntry 9 }

-- {COLUMN} 1712.2.52.2.2.1.10
lcsSetupComPortsCOMPortServCOMPortSetEntryReadyDataTimeout OBJECT-TYPE
    SYNTAX     INTEGER (0..2147483647)
    MAX-ACCESS read-write
    STATUS     current
    DESCRIPTION
        "-- empty --"
    ::= { lcsSetupComPortsCOMPortServCOMPortSetEntry 10 }

-- {TABLE} 1712.2.52.2.3
lcsSetupComPortsCOMPortServNetwSetTable OBJECT-TYPE
    SYNTAX     SEQUENCE OF LcsSetupComPortsCOMPortServNetwSetEntry
    MAX-ACCESS not-accessible
    STATUS     current
    DESCRIPTION
        ""
    ::= { lcsSetupComPortsCOMPortServ 3 }

-- {ENTRY} 1712.2.52.2.3.1
lcsSetupComPortsCOMPortServNetwSetEntry OBJECT-TYPE
    SYNTAX     LcsSetupComPortsCOMPortServNetwSetEntry
    MAX-ACCESS not-accessible
    STATUS     current
    DESCRIPTION
        ""
    INDEX {
        lcsSetupComPortsCOMPortServNetwSetEntryDeviceType,
        lcsSetupComPortsCOMPortServNetwSetEntryPortNumber
    }
    ::= { lcsSetupComPortsCOMPortServNetwSetTable 1 }

-- {SEQUENCE}
LcsSetupComPortsCOMPortServNetwSetEntry ::= SEQUENCE {
    lcsSetupComPortsCOMPortServNetwSetEntryDeviceType INTEGER,
    lcsSetupComPortsCOMPortServNetwSetEntryPortNumber INTEGER,
    lcsSetupComPortsCOMPortServNetwSetEntryTcpMode INTEGER,
    lcsSetupComPortsCOMPortServNetwSetEntryListenPort INTEGER,
    lcsSetupComPortsCOMPortServNetwSetEntryConnectHostname DisplayString,
    lcsSetupComPortsCOMPortServNetwSetEntryConnectPort INTEGER,
    lcsSetupComPortsCOMPortServNetwSetEntryLoopbackAddr DisplayString,
    lcsSetupComPortsCOMPortServNetwSetEntryRfc2217Extensions INTEGER,
    lcsSetupComPortsCOMPortServNetwSetEntryBinaryMode INTEGER,
    lcsSetupComPortsCOMPortServNetwSetEntryNewlineConversion INTEGER,
    lcsSetupComPortsCOMPortServNetwSetEntryTcpKeepalive INTEGER,
    lcsSetupComPortsCOMPortServNetwSetEntryTcpKeepaliveInterval INTEGER,
    lcsSetupComPortsCOMPortServNetwSetEntryTcpRetransmitTimeout INTEGER,
    lcsSetupComPortsCOMPortServNetwSetEntryTcpRetryCount INTEGER
}

-- {COLUMN} 1712.2.52.2.3.1.1
lcsSetupComPortsCOMPortServNetwSetEntryDeviceType OBJECT-TYPE
    SYNTAX     INTEGER
      {
        eOutband (1),
        eBelkinF5u103 (33),
        eProlific2303 (34),
        eFtdi8u232am (35)
      }
    MAX-ACCESS read-write
    STATUS     current
    DESCRIPTION
        "-- empty --"
    ::= { lcsSetupComPortsCOMPortServNetwSetEntry 1 }

-- {COLUMN} 1712.2.52.2.3.1.2
lcsSetupComPortsCOMPortServNetwSetEntryPortNumber OBJECT-TYPE
    SYNTAX     INTEGER (0..255)
    MAX-ACCESS read-write
    STATUS     current
    DESCRIPTION
        "-- empty --"
    ::= { lcsSetupComPortsCOMPortServNetwSetEntry 2 }

-- {COLUMN} 1712.2.52.2.3.1.4
lcsSetupComPortsCOMPortServNetwSetEntryTcpMode OBJECT-TYPE
    SYNTAX     INTEGER
      {
        eServer (0),
        eClient (1)
      }
    MAX-ACCESS read-write
    STATUS     current
    DESCRIPTION
        "-- empty --"
    ::= { lcsSetupComPortsCOMPortServNetwSetEntry 4 }

-- {COLUMN} 1712.2.52.2.3.1.5
lcsSetupComPortsCOMPortServNetwSetEntryListenPort OBJECT-TYPE
    SYNTAX     INTEGER (0..65535)
    MAX-ACCESS read-write
    STATUS     current
    DESCRIPTION
        "-- empty --"
    ::= { lcsSetupComPortsCOMPortServNetwSetEntry 5 }

-- {COLUMN} 1712.2.52.2.3.1.6
lcsSetupComPortsCOMPortServNetwSetEntryConnectHostname OBJECT-TYPE
    SYNTAX     DisplayString (SIZE(0..48))
    MAX-ACCESS read-write
    STATUS     current
    DESCRIPTION
        "-- empty --"
    ::= { lcsSetupComPortsCOMPortServNetwSetEntry 6 }

-- {COLUMN} 1712.2.52.2.3.1.7
lcsSetupComPortsCOMPortServNetwSetEntryConnectPort OBJECT-TYPE
    SYNTAX     INTEGER (0..65535)
    MAX-ACCESS read-write
    STATUS     current
    DESCRIPTION
        "-- empty --"
    ::= { lcsSetupComPortsCOMPortServNetwSetEntry 7 }

-- {COLUMN} 1712.2.52.2.3.1.8
lcsSetupComPortsCOMPortServNetwSetEntryLoopbackAddr OBJECT-TYPE
    SYNTAX     DisplayString (SIZE(0..16))
    MAX-ACCESS read-write
    STATUS     current
    DESCRIPTION
        "-- empty --"
    ::= { lcsSetupComPortsCOMPortServNetwSetEntry 8 }

-- {COLUMN} 1712.2.52.2.3.1.9
lcsSetupComPortsCOMPortServNetwSetEntryRfc2217Extensions OBJECT-TYPE
    SYNTAX     INTEGER
      {
        eNo (0),
        eYes (1)
      }
    MAX-ACCESS read-write
    STATUS     current
    DESCRIPTION
        "-- empty --"
    ::= { lcsSetupComPortsCOMPortServNetwSetEntry 9 }

-- {COLUMN} 1712.2.52.2.3.1.16
lcsSetupComPortsCOMPortServNetwSetEntryBinaryMode OBJECT-TYPE
    SYNTAX     INTEGER
      {
        eAuto (0),
        eYes (1),
        eNo (2)
      }
    MAX-ACCESS read-write
    STATUS     current
    DESCRIPTION
        "-- empty --"
    ::= { lcsSetupComPortsCOMPortServNetwSetEntry 16 }

-- {COLUMN} 1712.2.52.2.3.1.10
lcsSetupComPortsCOMPortServNetwSetEntryNewlineConversion OBJECT-TYPE
    SYNTAX     INTEGER
      {
        eCrlf (0),
        eCr (1),
        eLf (2)
      }
    MAX-ACCESS read-write
    STATUS     current
    DESCRIPTION
        "-- empty --"
    ::= { lcsSetupComPortsCOMPortServNetwSetEntry 10 }

-- {COLUMN} 1712.2.52.2.3.1.14
lcsSetupComPortsCOMPortServNetwSetEntryTcpKeepalive OBJECT-TYPE
    SYNTAX     INTEGER
      {
        eInactive (0),
        eActive (1),
        eProactive (2)
      }
    MAX-ACCESS read-write
    STATUS     current
    DESCRIPTION
        "-- empty --"
    ::= { lcsSetupComPortsCOMPortServNetwSetEntry 14 }

-- {COLUMN} 1712.2.52.2.3.1.15
lcsSetupComPortsCOMPortServNetwSetEntryTcpKeepaliveInterval OBJECT-TYPE
    SYNTAX     INTEGER (0..2147483647)
    MAX-ACCESS read-write
    STATUS     current
    DESCRIPTION
        "-- empty --"
    ::= { lcsSetupComPortsCOMPortServNetwSetEntry 15 }

-- {COLUMN} 1712.2.52.2.3.1.12
lcsSetupComPortsCOMPortServNetwSetEntryTcpRetransmitTimeout OBJECT-TYPE
    SYNTAX     INTEGER (0..255)
    MAX-ACCESS read-write
    STATUS     current
    DESCRIPTION
        "-- empty --"
    ::= { lcsSetupComPortsCOMPortServNetwSetEntry 12 }

-- {COLUMN} 1712.2.52.2.3.1.13
lcsSetupComPortsCOMPortServNetwSetEntryTcpRetryCount OBJECT-TYPE
    SYNTAX     INTEGER (0..255)
    MAX-ACCESS read-write
    STATUS     current
    DESCRIPTION
        "-- empty --"
    ::= { lcsSetupComPortsCOMPortServNetwSetEntry 13 }

-- {OID} 1712.2.54
lcsSetupTacacsPlus OBJECT IDENTIFIER ::= { lcsSetup 54 }

-- {SCALAR} 1712.2.54.2
lcsSetupTacacsPlusAuthorisation OBJECT-TYPE
    SYNTAX     INTEGER
      {
        eDeactivated (0),
        eActivated (1)
      }
    MAX-ACCESS read-write
    STATUS     current
    DESCRIPTION
        "-- empty --"
    ::= { lcsSetupTacacsPlus 2 }

-- {SCALAR} 1712.2.54.3
lcsSetupTacacsPlusAccounting OBJECT-TYPE
    SYNTAX     INTEGER
      {
        eDeactivated (0),
        eActivated (1)
      }
    MAX-ACCESS read-write
    STATUS     current
    DESCRIPTION
        "-- empty --"
    ::= { lcsSetupTacacsPlus 3 }

-- {TABLE} 1712.2.54.9
lcsSetupTacacsPlusServerTable OBJECT-TYPE
    SYNTAX     SEQUENCE OF LcsSetupTacacsPlusServerEntry
    MAX-ACCESS not-accessible
    STATUS     current
    DESCRIPTION
        "-- empty --"
    ::= { lcsSetupTacacsPlus 9 }

-- {ENTRY} 1712.2.54.9.1
lcsSetupTacacsPlusServerEntry OBJECT-TYPE
    SYNTAX     LcsSetupTacacsPlusServerEntry
    MAX-ACCESS not-accessible
    STATUS     current
    DESCRIPTION
        ""
    INDEX {
        lcsSetupTacacsPlusServerEntryServerAddress
    }
    ::= { lcsSetupTacacsPlusServerTable 1 }

-- {SEQUENCE}
LcsSetupTacacsPlusServerEntry ::= SEQUENCE {
    lcsSetupTacacsPlusServerEntryServerAddress DisplayString,
    lcsSetupTacacsPlusServerEntryLoopbackAddress DisplayString,
    lcsSetupTacacsPlusServerEntryCompatibilityMode INTEGER
}

-- {COLUMN} 1712.2.54.9.1.1
lcsSetupTacacsPlusServerEntryServerAddress OBJECT-TYPE
    SYNTAX     DisplayString (SIZE(0..31))
    MAX-ACCESS read-write
    STATUS     current
    DESCRIPTION
        "-- empty --"
    ::= { lcsSetupTacacsPlusServerEntry 1 }

-- {COLUMN} 1712.2.54.9.1.2
lcsSetupTacacsPlusServerEntryLoopbackAddress OBJECT-TYPE
    SYNTAX     DisplayString (SIZE(0..16))
    MAX-ACCESS read-write
    STATUS     current
    DESCRIPTION
        "-- empty --"
    ::= { lcsSetupTacacsPlusServerEntry 2 }

-- {COLUMN} 1712.2.54.9.1.3
lcsSetupTacacsPlusServerEntryCompatibilityMode OBJECT-TYPE
    SYNTAX     INTEGER
      {
        eDeactivated (0),
        eActivated (1)
      }
    MAX-ACCESS read-write
    STATUS     current
    DESCRIPTION
        "-- empty --"
    ::= { lcsSetupTacacsPlusServerEntry 3 }

-- {SCALAR} 1712.2.54.6
lcsSetupTacacsPlusSharedSecret OBJECT-TYPE
    SYNTAX     DisplayString (SIZE(0..31))
    MAX-ACCESS read-write
    STATUS     current
    DESCRIPTION
        "-- empty --"
    ::= { lcsSetupTacacsPlus 6 }

-- {SCALAR} 1712.2.54.7
lcsSetupTacacsPlusEncryption OBJECT-TYPE
    SYNTAX     INTEGER
      {
        eDeactivated (0),
        eActivated (1)
      }
    MAX-ACCESS read-write
    STATUS     current
    DESCRIPTION
        "-- empty --"
    ::= { lcsSetupTacacsPlus 7 }

-- {SCALAR} 1712.2.54.10
lcsSetupTacacsPlusFallbackToLocalUsers OBJECT-TYPE
    SYNTAX     INTEGER
      {
        eAllowed (0),
        eProhibited (1)
      }
    MAX-ACCESS read-write
    STATUS     current
    DESCRIPTION
        "-- empty --"
    ::= { lcsSetupTacacsPlus 10 }

-- {SCALAR} 1712.2.54.11
lcsSetupTacacsPlusSnmpGetRequestsAuthorisation OBJECT-TYPE
    SYNTAX     INTEGER
      {
        eOnlyForSetupTree (0),
        eAll (1),
        eNone (2)
      }
    MAX-ACCESS read-write
    STATUS     current
    DESCRIPTION
        "-- empty --"
    ::= { lcsSetupTacacsPlus 11 }

-- {SCALAR} 1712.2.54.12
lcsSetupTacacsPlusSnmpGetRequestsAccounting OBJECT-TYPE
    SYNTAX     INTEGER
      {
        eOnlyForSetupTree (0),
        eAll (1),
        eNone (2)
      }
    MAX-ACCESS read-write
    STATUS     current
    DESCRIPTION
        "-- empty --"
    ::= { lcsSetupTacacsPlus 12 }

-- {SCALAR} 1712.2.54.13
lcsSetupTacacsPlusBypassTacacsForCronScriptsActionTable OBJECT-TYPE
    SYNTAX     INTEGER
      {
        eDeactivated (0),
        eActivated (1)
      }
    MAX-ACCESS read-write
    STATUS     current
    DESCRIPTION
        "-- empty --"
    ::= { lcsSetupTacacsPlus 13 }

-- {SCALAR} 1712.2.54.14
lcsSetupTacacsPlusIncludeValueIntoAuthorisationRequest OBJECT-TYPE
    SYNTAX     INTEGER
      {
        eDeactivated (0),
        eActivated (1)
      }
    MAX-ACCESS read-write
    STATUS     current
    DESCRIPTION
        "-- empty --"
    ::= { lcsSetupTacacsPlus 14 }

-- {OID} 1712.2.60
lcsSetupAutold OBJECT IDENTIFIER ::= { lcsSetup 60 }

-- {OID} 1712.2.60.1
lcsSetupAutoldNetwork OBJECT IDENTIFIER ::= { lcsSetupAutold 1 }

-- {OID} 1712.2.60.1.1
lcsSetupAutoldNetworkFirmware OBJECT IDENTIFIER ::= { lcsSetupAutoldNetwork 1 }

-- {SCALAR} 1712.2.60.1.1.1
lcsSetupAutoldNetworkFirmwareCondition OBJECT-TYPE
    SYNTAX     INTEGER
      {
        eUnconditionally (0),
        eIfDifferent (1),
        eIfNewer (2)
      }
    MAX-ACCESS read-write
    STATUS     current
    DESCRIPTION
        "-- empty --"
    ::= { lcsSetupAutoldNetworkFirmware 1 }

-- {SCALAR} 1712.2.60.1.1.2
lcsSetupAutoldNetworkFirmwareUrl OBJECT-TYPE
    SYNTAX     DisplayString (SIZE(0..127))
    MAX-ACCESS read-write
    STATUS     current
    DESCRIPTION
        "-- empty --"
    ::= { lcsSetupAutoldNetworkFirmware 2 }

-- {SCALAR} 1712.2.60.1.1.3
lcsSetupAutoldNetworkFirmwareMinimumVersion OBJECT-TYPE
    SYNTAX     DisplayString (SIZE(0..14))
    MAX-ACCESS read-write
    STATUS     current
    DESCRIPTION
        "-- empty --"
    ::= { lcsSetupAutoldNetworkFirmware 3 }

-- {OID} 1712.2.60.1.2
lcsSetupAutoldNetworkConfig OBJECT IDENTIFIER ::= { lcsSetupAutoldNetwork 2 }

-- {SCALAR} 1712.2.60.1.2.1
lcsSetupAutoldNetworkConfigCondition OBJECT-TYPE
    SYNTAX     INTEGER
      {
        eUnconditionally (0),
        eIfDifferent (1)
      }
    MAX-ACCESS read-write
    STATUS     current
    DESCRIPTION
        "-- empty --"
    ::= { lcsSetupAutoldNetworkConfig 1 }

-- {SCALAR} 1712.2.60.1.2.2
lcsSetupAutoldNetworkConfigUrl OBJECT-TYPE
    SYNTAX     DisplayString (SIZE(0..127))
    MAX-ACCESS read-write
    STATUS     current
    DESCRIPTION
        "-- empty --"
    ::= { lcsSetupAutoldNetworkConfig 2 }

-- {OID} 1712.2.60.1.3
lcsSetupAutoldNetworkScript OBJECT IDENTIFIER ::= { lcsSetupAutoldNetwork 3 }

-- {SCALAR} 1712.2.60.1.3.1
lcsSetupAutoldNetworkScriptCondition OBJECT-TYPE
    SYNTAX     INTEGER
      {
        eUnconditionally (0),
        eIfDifferent (1)
      }
    MAX-ACCESS read-write
    STATUS     current
    DESCRIPTION
        "-- empty --"
    ::= { lcsSetupAutoldNetworkScript 1 }

-- {SCALAR} 1712.2.60.1.3.2
lcsSetupAutoldNetworkScriptUrl OBJECT-TYPE
    SYNTAX     DisplayString (SIZE(0..127))
    MAX-ACCESS read-write
    STATUS     current
    DESCRIPTION
        "-- empty --"
    ::= { lcsSetupAutoldNetworkScript 2 }

-- {OID} 1712.2.60.1.4
lcsSetupAutoldNetworkTftpClient OBJECT IDENTIFIER ::= { lcsSetupAutoldNetwork 4 }

-- {SCALAR} 1712.2.60.1.4.1
lcsSetupAutoldNetworkTftpClientBytesPerHashmark OBJECT-TYPE
    SYNTAX     INTEGER (0..2147483647)
    MAX-ACCESS read-write
    STATUS     current
    DESCRIPTION
        "-- empty --"
    ::= { lcsSetupAutoldNetworkTftpClient 1 }

-- {OID} 1712.2.60.56
lcsSetupAutoldUsb OBJECT IDENTIFIER ::= { lcsSetupAutold 56 }

-- {SCALAR} 1712.2.60.56.1
lcsSetupAutoldUsbFirmwareAndLoader OBJECT-TYPE
    SYNTAX     INTEGER
      {
        eInactive (1),
        eIfUnconfigured (2),
        eActive (3)
      }
    MAX-ACCESS read-write
    STATUS     current
    DESCRIPTION
        "-- empty --"
    ::= { lcsSetupAutoldUsb 1 }

-- {SCALAR} 1712.2.60.56.2
lcsSetupAutoldUsbConfigAndScript OBJECT-TYPE
    SYNTAX     INTEGER
      {
        eInactive (1),
        eIfUnconfigured (2),
        eActive (3)
      }
    MAX-ACCESS read-write
    STATUS     current
    DESCRIPTION
        "-- empty --"
    ::= { lcsSetupAutoldUsb 2 }

-- {OID} 1712.2.60.3
lcsSetupAutoldLicense OBJECT IDENTIFIER ::= { lcsSetupAutold 3 }

-- {SCALAR} 1712.2.60.3.1
lcsSetupAutoldLicenseUrl OBJECT-TYPE
    SYNTAX     DisplayString (SIZE(0..127))
    MAX-ACCESS read-write
    STATUS     current
    DESCRIPTION
        "-- empty --"
    ::= { lcsSetupAutoldLicense 1 }

-- {SCALAR} 1712.2.60.3.2
lcsSetupAutoldLicenseLoopbackAddress OBJECT-TYPE
    SYNTAX     DisplayString (SIZE(0..16))
    MAX-ACCESS read-write
    STATUS     current
    DESCRIPTION
        "-- empty --"
    ::= { lcsSetupAutoldLicense 2 }

-- {SCALAR} 1712.2.60.3.10
lcsSetupAutoldLicenseCompany OBJECT-TYPE
    SYNTAX     DisplayString (SIZE(0..127))
    MAX-ACCESS read-write
    STATUS     current
    DESCRIPTION
        "-- empty --"
    ::= { lcsSetupAutoldLicense 10 }

-- {SCALAR} 1712.2.60.3.11
lcsSetupAutoldLicenseLastName OBJECT-TYPE
    SYNTAX     DisplayString (SIZE(0..31))
    MAX-ACCESS read-write
    STATUS     current
    DESCRIPTION
        "-- empty --"
    ::= { lcsSetupAutoldLicense 11 }

-- {SCALAR} 1712.2.60.3.12
lcsSetupAutoldLicenseFirstName OBJECT-TYPE
    SYNTAX     DisplayString (SIZE(0..31))
    MAX-ACCESS read-write
    STATUS     current
    DESCRIPTION
        "-- empty --"
    ::= { lcsSetupAutoldLicense 12 }

-- {SCALAR} 1712.2.60.3.13
lcsSetupAutoldLicenseStreetAndNumber OBJECT-TYPE
    SYNTAX     DisplayString (SIZE(0..127))
    MAX-ACCESS read-write
    STATUS     current
    DESCRIPTION
        "-- empty --"
    ::= { lcsSetupAutoldLicense 13 }

-- {SCALAR} 1712.2.60.3.14
lcsSetupAutoldLicensePostCode OBJECT-TYPE
    SYNTAX     DisplayString (SIZE(0..10))
    MAX-ACCESS read-write
    STATUS     current
    DESCRIPTION
        "-- empty --"
    ::= { lcsSetupAutoldLicense 14 }

-- {SCALAR} 1712.2.60.3.15
lcsSetupAutoldLicenseCity OBJECT-TYPE
    SYNTAX     DisplayString (SIZE(0..63))
    MAX-ACCESS read-write
    STATUS     current
    DESCRIPTION
        "-- empty --"
    ::= { lcsSetupAutoldLicense 15 }

-- {SCALAR} 1712.2.60.3.16
lcsSetupAutoldLicenseCountry OBJECT-TYPE
    SYNTAX     DisplayString (SIZE(0..63))
    MAX-ACCESS read-write
    STATUS     current
    DESCRIPTION
        "-- empty --"
    ::= { lcsSetupAutoldLicense 16 }

-- {SCALAR} 1712.2.60.3.17
lcsSetupAutoldLicenseEmailAddress OBJECT-TYPE
    SYNTAX     DisplayString (SIZE(0..63))
    MAX-ACCESS read-write
    STATUS     current
    DESCRIPTION
        "-- empty --"
    ::= { lcsSetupAutoldLicense 17 }

-- {OID} 1712.2.56
lcsSetupUsb OBJECT IDENTIFIER ::= { lcsSetup 56 }

-- {SCALAR} 1712.2.56.1
lcsSetupUsbFirmwareAndLoader OBJECT-TYPE
    SYNTAX     INTEGER
      {
        eInactive (1),
        eIfUnconfigured (2),
        eActive (3)
      }
    MAX-ACCESS read-only
    STATUS     current
    DESCRIPTION
        "-- empty --"
    ::= { lcsSetupUsb 1 }

-- {SCALAR} 1712.2.56.2
lcsSetupUsbConfigAndScript OBJECT-TYPE
    SYNTAX     INTEGER
      {
        eInactive (1),
        eIfUnconfigured (2),
        eActive (3)
      }
    MAX-ACCESS read-only
    STATUS     current
    DESCRIPTION
        "-- empty --"
    ::= { lcsSetupUsb 2 }

-- {OID} 1712.2.36
lcsSetupPerfmon OBJECT IDENTIFIER ::= { lcsSetup 36 }

-- {TABLE} 1712.2.36.2
lcsSetupPerfmonRttmonadminTable OBJECT-TYPE
    SYNTAX     SEQUENCE OF LcsSetupPerfmonRttmonadminEntry
    MAX-ACCESS not-accessible
    STATUS     current
    DESCRIPTION
        "-- empty --"
    ::= { lcsSetupPerfmon 2 }

-- {ENTRY} 1712.2.36.2.1
lcsSetupPerfmonRttmonadminEntry OBJECT-TYPE
    SYNTAX     LcsSetupPerfmonRttmonadminEntry
    MAX-ACCESS not-accessible
    STATUS     current
    DESCRIPTION
        ""
    INDEX {
        lcsSetupPerfmonRttmonadminEntryIndex
    }
    ::= { lcsSetupPerfmonRttmonadminTable 1 }

-- {SEQUENCE}
LcsSetupPerfmonRttmonadminEntry ::= SEQUENCE {
    lcsSetupPerfmonRttmonadminEntryIndex INTEGER,
    lcsSetupPerfmonRttmonadminEntryType INTEGER,
    lcsSetupPerfmonRttmonadminEntryFrequency INTEGER,
    lcsSetupPerfmonRttmonadminEntryTimeout INTEGER,
    lcsSetupPerfmonRttmonadminEntryStatus INTEGER
}

-- {COLUMN} 1712.2.36.2.1.1
lcsSetupPerfmonRttmonadminEntryIndex OBJECT-TYPE
    SYNTAX     INTEGER (0..2147483647)
    MAX-ACCESS read-write
    STATUS     current
    DESCRIPTION
        "-- empty --"
    ::= { lcsSetupPerfmonRttmonadminEntry 1 }

-- {COLUMN} 1712.2.36.2.1.4
lcsSetupPerfmonRttmonadminEntryType OBJECT-TYPE
    SYNTAX     INTEGER
      {
        eJitter (9)
      }
    MAX-ACCESS read-write
    STATUS     current
    DESCRIPTION
        "-- empty --"
    ::= { lcsSetupPerfmonRttmonadminEntry 4 }

-- {COLUMN} 1712.2.36.2.1.6
lcsSetupPerfmonRttmonadminEntryFrequency OBJECT-TYPE
    SYNTAX     INTEGER (0..2147483647)
    MAX-ACCESS read-write
    STATUS     current
    DESCRIPTION
        "-- empty --"
    ::= { lcsSetupPerfmonRttmonadminEntry 6 }

-- {COLUMN} 1712.2.36.2.1.7
lcsSetupPerfmonRttmonadminEntryTimeout OBJECT-TYPE
    SYNTAX     INTEGER (0..2147483647)
    MAX-ACCESS read-write
    STATUS     current
    DESCRIPTION
        "-- empty --"
    ::= { lcsSetupPerfmonRttmonadminEntry 7 }

-- {COLUMN} 1712.2.36.2.1.9
lcsSetupPerfmonRttmonadminEntryStatus OBJECT-TYPE
    SYNTAX     INTEGER
      {
        eActive (1),
        eNotInService (2),
        eNotReady (3),
        eCreate (5),
        eDestroy (6)
      }
    MAX-ACCESS read-write
    STATUS     current
    DESCRIPTION
        "-- empty --"
    ::= { lcsSetupPerfmonRttmonadminEntry 9 }

-- {TABLE} 1712.2.36.3
lcsSetupPerfmonRttmonechoadminTable OBJECT-TYPE
    SYNTAX     SEQUENCE OF LcsSetupPerfmonRttmonechoadminEntry
    MAX-ACCESS not-accessible
    STATUS     current
    DESCRIPTION
        "-- empty --"
    ::= { lcsSetupPerfmon 3 }

-- {ENTRY} 1712.2.36.3.1
lcsSetupPerfmonRttmonechoadminEntry OBJECT-TYPE
    SYNTAX     LcsSetupPerfmonRttmonechoadminEntry
    MAX-ACCESS not-accessible
    STATUS     current
    DESCRIPTION
        ""
    INDEX {
        lcsSetupPerfmonRttmonechoadminEntryIndex
    }
    ::= { lcsSetupPerfmonRttmonechoadminTable 1 }

-- {SEQUENCE}
LcsSetupPerfmonRttmonechoadminEntry ::= SEQUENCE {
    lcsSetupPerfmonRttmonechoadminEntryIndex INTEGER,
    lcsSetupPerfmonRttmonechoadminEntryProtocol INTEGER,
    lcsSetupPerfmonRttmonechoadminEntryDestinationAddress IpAddress,
    lcsSetupPerfmonRttmonechoadminEntryPacketSize INTEGER,
    lcsSetupPerfmonRttmonechoadminEntryDestinationPort INTEGER,
    lcsSetupPerfmonRttmonechoadminEntryInterval INTEGER,
    lcsSetupPerfmonRttmonechoadminEntryPacketCount INTEGER
}

-- {COLUMN} 1712.2.36.3.1.255
lcsSetupPerfmonRttmonechoadminEntryIndex OBJECT-TYPE
    SYNTAX     INTEGER (0..2147483647)
    MAX-ACCESS read-only
    STATUS     current
    DESCRIPTION
        "-- empty --"
    ::= { lcsSetupPerfmonRttmonechoadminEntry 255 }

-- {COLUMN} 1712.2.36.3.1.1
lcsSetupPerfmonRttmonechoadminEntryProtocol OBJECT-TYPE
    SYNTAX     INTEGER
      {
        eEcho (3)
      }
    MAX-ACCESS read-write
    STATUS     current
    DESCRIPTION
        "-- empty --"
    ::= { lcsSetupPerfmonRttmonechoadminEntry 1 }

-- {COLUMN} 1712.2.36.3.1.2
lcsSetupPerfmonRttmonechoadminEntryDestinationAddress OBJECT-TYPE
    SYNTAX     IpAddress
    MAX-ACCESS read-write
    STATUS     current
    DESCRIPTION
        "-- empty --"
    ::= { lcsSetupPerfmonRttmonechoadminEntry 2 }

-- {COLUMN} 1712.2.36.3.1.3
lcsSetupPerfmonRttmonechoadminEntryPacketSize OBJECT-TYPE
    SYNTAX     INTEGER (0..65535)
    MAX-ACCESS read-write
    STATUS     current
    DESCRIPTION
        "-- empty --"
    ::= { lcsSetupPerfmonRttmonechoadminEntry 3 }

-- {COLUMN} 1712.2.36.3.1.5
lcsSetupPerfmonRttmonechoadminEntryDestinationPort OBJECT-TYPE
    SYNTAX     INTEGER (0..65535)
    MAX-ACCESS read-write
    STATUS     current
    DESCRIPTION
        "-- empty --"
    ::= { lcsSetupPerfmonRttmonechoadminEntry 5 }

-- {COLUMN} 1712.2.36.3.1.17
lcsSetupPerfmonRttmonechoadminEntryInterval OBJECT-TYPE
    SYNTAX     INTEGER (0..2147483647)
    MAX-ACCESS read-write
    STATUS     current
    DESCRIPTION
        "-- empty --"
    ::= { lcsSetupPerfmonRttmonechoadminEntry 17 }

-- {COLUMN} 1712.2.36.3.1.18
lcsSetupPerfmonRttmonechoadminEntryPacketCount OBJECT-TYPE
    SYNTAX     INTEGER (0..2147483647)
    MAX-ACCESS read-write
    STATUS     current
    DESCRIPTION
        "-- empty --"
    ::= { lcsSetupPerfmonRttmonechoadminEntry 18 }

-- {TABLE} 1712.2.36.4
lcsSetupPerfmonRttmonstatisticsTable OBJECT-TYPE
    SYNTAX     SEQUENCE OF LcsSetupPerfmonRttmonstatisticsEntry
    MAX-ACCESS not-accessible
    STATUS     current
    DESCRIPTION
        "-- empty --"
    ::= { lcsSetupPerfmon 4 }

-- {ENTRY} 1712.2.36.4.1
lcsSetupPerfmonRttmonstatisticsEntry OBJECT-TYPE
    SYNTAX     LcsSetupPerfmonRttmonstatisticsEntry
    MAX-ACCESS not-accessible
    STATUS     current
    DESCRIPTION
        ""
    INDEX {
        lcsSetupPerfmonRttmonstatisticsEntryIndex
    }
    ::= { lcsSetupPerfmonRttmonstatisticsTable 1 }

-- {SEQUENCE}
LcsSetupPerfmonRttmonstatisticsEntry ::= SEQUENCE {
    lcsSetupPerfmonRttmonstatisticsEntryIndex INTEGER,
    lcsSetupPerfmonRttmonstatisticsEntryCompletions INTEGER,
    lcsSetupPerfmonRttmonstatisticsEntryRttCount INTEGER,
    lcsSetupPerfmonRttmonstatisticsEntryRttSum INTEGER,
    lcsSetupPerfmonRttmonstatisticsEntryRttMin INTEGER,
    lcsSetupPerfmonRttmonstatisticsEntryRttMax INTEGER,
    lcsSetupPerfmonRttmonstatisticsEntryJitterMinPosSd INTEGER,
    lcsSetupPerfmonRttmonstatisticsEntryJitterMaxPosSd INTEGER,
    lcsSetupPerfmonRttmonstatisticsEntryJitterCountPosSd INTEGER,
    lcsSetupPerfmonRttmonstatisticsEntryJitterSumPosSd INTEGER,
    lcsSetupPerfmonRttmonstatisticsEntryJitterMinPosDs INTEGER,
    lcsSetupPerfmonRttmonstatisticsEntryJitterMaxPosDs INTEGER,
    lcsSetupPerfmonRttmonstatisticsEntryJitterCountPosDs INTEGER,
    lcsSetupPerfmonRttmonstatisticsEntryJitterSumPosDs INTEGER,
    lcsSetupPerfmonRttmonstatisticsEntryJitterMinNegSd INTEGER,
    lcsSetupPerfmonRttmonstatisticsEntryJitterMaxNegSd INTEGER,
    lcsSetupPerfmonRttmonstatisticsEntryJitterCountNegSd INTEGER,
    lcsSetupPerfmonRttmonstatisticsEntryJitterSumNegSd INTEGER,
    lcsSetupPerfmonRttmonstatisticsEntryJitterMinNegDs INTEGER,
    lcsSetupPerfmonRttmonstatisticsEntryJitterMaxNegDs INTEGER,
    lcsSetupPerfmonRttmonstatisticsEntryJitterCountNegDs INTEGER,
    lcsSetupPerfmonRttmonstatisticsEntryJitterSumNegDs INTEGER,
    lcsSetupPerfmonRttmonstatisticsEntryPacketLossSd INTEGER,
    lcsSetupPerfmonRttmonstatisticsEntryPacketLossDs INTEGER,
    lcsSetupPerfmonRttmonstatisticsEntryAverageJitter INTEGER,
    lcsSetupPerfmonRttmonstatisticsEntryAverageJitterSd INTEGER,
    lcsSetupPerfmonRttmonstatisticsEntryAverageJitterDs INTEGER
}

-- {COLUMN} 1712.2.36.4.1.255
lcsSetupPerfmonRttmonstatisticsEntryIndex OBJECT-TYPE
    SYNTAX     INTEGER (0..2147483647)
    MAX-ACCESS read-only
    STATUS     current
    DESCRIPTION
        "-- empty --"
    ::= { lcsSetupPerfmonRttmonstatisticsEntry 255 }

-- {COLUMN} 1712.2.36.4.1.2
lcsSetupPerfmonRttmonstatisticsEntryCompletions OBJECT-TYPE
    SYNTAX     INTEGER (0..2147483647)
    MAX-ACCESS read-only
    STATUS     current
    DESCRIPTION
        "-- empty --"
    ::= { lcsSetupPerfmonRttmonstatisticsEntry 2 }

-- {COLUMN} 1712.2.36.4.1.4
lcsSetupPerfmonRttmonstatisticsEntryRttCount OBJECT-TYPE
    SYNTAX     INTEGER (0..2147483647)
    MAX-ACCESS read-only
    STATUS     current
    DESCRIPTION
        "-- empty --"
    ::= { lcsSetupPerfmonRttmonstatisticsEntry 4 }

-- {COLUMN} 1712.2.36.4.1.5
lcsSetupPerfmonRttmonstatisticsEntryRttSum OBJECT-TYPE
    SYNTAX     INTEGER (0..2147483647)
    MAX-ACCESS read-only
    STATUS     current
    DESCRIPTION
        "-- empty --"
    ::= { lcsSetupPerfmonRttmonstatisticsEntry 5 }

-- {COLUMN} 1712.2.36.4.1.8
lcsSetupPerfmonRttmonstatisticsEntryRttMin OBJECT-TYPE
    SYNTAX     INTEGER (0..2147483647)
    MAX-ACCESS read-only
    STATUS     current
    DESCRIPTION
        "-- empty --"
    ::= { lcsSetupPerfmonRttmonstatisticsEntry 8 }

-- {COLUMN} 1712.2.36.4.1.9
lcsSetupPerfmonRttmonstatisticsEntryRttMax OBJECT-TYPE
    SYNTAX     INTEGER (0..2147483647)
    MAX-ACCESS read-only
    STATUS     current
    DESCRIPTION
        "-- empty --"
    ::= { lcsSetupPerfmonRttmonstatisticsEntry 9 }

-- {COLUMN} 1712.2.36.4.1.10
lcsSetupPerfmonRttmonstatisticsEntryJitterMinPosSd OBJECT-TYPE
    SYNTAX     INTEGER (0..2147483647)
    MAX-ACCESS read-only
    STATUS     current
    DESCRIPTION
        "-- empty --"
    ::= { lcsSetupPerfmonRttmonstatisticsEntry 10 }

-- {COLUMN} 1712.2.36.4.1.11
lcsSetupPerfmonRttmonstatisticsEntryJitterMaxPosSd OBJECT-TYPE
    SYNTAX     INTEGER (0..2147483647)
    MAX-ACCESS read-only
    STATUS     current
    DESCRIPTION
        "-- empty --"
    ::= { lcsSetupPerfmonRttmonstatisticsEntry 11 }

-- {COLUMN} 1712.2.36.4.1.12
lcsSetupPerfmonRttmonstatisticsEntryJitterCountPosSd OBJECT-TYPE
    SYNTAX     INTEGER (0..2147483647)
    MAX-ACCESS read-only
    STATUS     current
    DESCRIPTION
        "-- empty --"
    ::= { lcsSetupPerfmonRttmonstatisticsEntry 12 }

-- {COLUMN} 1712.2.36.4.1.13
lcsSetupPerfmonRttmonstatisticsEntryJitterSumPosSd OBJECT-TYPE
    SYNTAX     INTEGER (0..2147483647)
    MAX-ACCESS read-only
    STATUS     current
    DESCRIPTION
        "-- empty --"
    ::= { lcsSetupPerfmonRttmonstatisticsEntry 13 }

-- {COLUMN} 1712.2.36.4.1.16
lcsSetupPerfmonRttmonstatisticsEntryJitterMinPosDs OBJECT-TYPE
    SYNTAX     INTEGER (0..2147483647)
    MAX-ACCESS read-only
    STATUS     current
    DESCRIPTION
        "-- empty --"
    ::= { lcsSetupPerfmonRttmonstatisticsEntry 16 }

-- {COLUMN} 1712.2.36.4.1.17
lcsSetupPerfmonRttmonstatisticsEntryJitterMaxPosDs OBJECT-TYPE
    SYNTAX     INTEGER (0..2147483647)
    MAX-ACCESS read-only
    STATUS     current
    DESCRIPTION
        "-- empty --"
    ::= { lcsSetupPerfmonRttmonstatisticsEntry 17 }

-- {COLUMN} 1712.2.36.4.1.18
lcsSetupPerfmonRttmonstatisticsEntryJitterCountPosDs OBJECT-TYPE
    SYNTAX     INTEGER (0..2147483647)
    MAX-ACCESS read-only
    STATUS     current
    DESCRIPTION
        "-- empty --"
    ::= { lcsSetupPerfmonRttmonstatisticsEntry 18 }

-- {COLUMN} 1712.2.36.4.1.19
lcsSetupPerfmonRttmonstatisticsEntryJitterSumPosDs OBJECT-TYPE
    SYNTAX     INTEGER (0..2147483647)
    MAX-ACCESS read-only
    STATUS     current
    DESCRIPTION
        "-- empty --"
    ::= { lcsSetupPerfmonRttmonstatisticsEntry 19 }

-- {COLUMN} 1712.2.36.4.1.22
lcsSetupPerfmonRttmonstatisticsEntryJitterMinNegSd OBJECT-TYPE
    SYNTAX     INTEGER (0..2147483647)
    MAX-ACCESS read-only
    STATUS     current
    DESCRIPTION
        "-- empty --"
    ::= { lcsSetupPerfmonRttmonstatisticsEntry 22 }

-- {COLUMN} 1712.2.36.4.1.23
lcsSetupPerfmonRttmonstatisticsEntryJitterMaxNegSd OBJECT-TYPE
    SYNTAX     INTEGER (0..2147483647)
    MAX-ACCESS read-only
    STATUS     current
    DESCRIPTION
        "-- empty --"
    ::= { lcsSetupPerfmonRttmonstatisticsEntry 23 }

-- {COLUMN} 1712.2.36.4.1.24
lcsSetupPerfmonRttmonstatisticsEntryJitterCountNegSd OBJECT-TYPE
    SYNTAX     INTEGER (0..2147483647)
    MAX-ACCESS read-only
    STATUS     current
    DESCRIPTION
        "-- empty --"
    ::= { lcsSetupPerfmonRttmonstatisticsEntry 24 }

-- {COLUMN} 1712.2.36.4.1.25
lcsSetupPerfmonRttmonstatisticsEntryJitterSumNegSd OBJECT-TYPE
    SYNTAX     INTEGER (0..2147483647)
    MAX-ACCESS read-only
    STATUS     current
    DESCRIPTION
        "-- empty --"
    ::= { lcsSetupPerfmonRttmonstatisticsEntry 25 }

-- {COLUMN} 1712.2.36.4.1.28
lcsSetupPerfmonRttmonstatisticsEntryJitterMinNegDs OBJECT-TYPE
    SYNTAX     INTEGER (0..2147483647)
    MAX-ACCESS read-only
    STATUS     current
    DESCRIPTION
        "-- empty --"
    ::= { lcsSetupPerfmonRttmonstatisticsEntry 28 }

-- {COLUMN} 1712.2.36.4.1.29
lcsSetupPerfmonRttmonstatisticsEntryJitterMaxNegDs OBJECT-TYPE
    SYNTAX     INTEGER (0..2147483647)
    MAX-ACCESS read-only
    STATUS     current
    DESCRIPTION
        "-- empty --"
    ::= { lcsSetupPerfmonRttmonstatisticsEntry 29 }

-- {COLUMN} 1712.2.36.4.1.30
lcsSetupPerfmonRttmonstatisticsEntryJitterCountNegDs OBJECT-TYPE
    SYNTAX     INTEGER (0..2147483647)
    MAX-ACCESS read-only
    STATUS     current
    DESCRIPTION
        "-- empty --"
    ::= { lcsSetupPerfmonRttmonstatisticsEntry 30 }

-- {COLUMN} 1712.2.36.4.1.31
lcsSetupPerfmonRttmonstatisticsEntryJitterSumNegDs OBJECT-TYPE
    SYNTAX     INTEGER (0..2147483647)
    MAX-ACCESS read-only
    STATUS     current
    DESCRIPTION
        "-- empty --"
    ::= { lcsSetupPerfmonRttmonstatisticsEntry 31 }

-- {COLUMN} 1712.2.36.4.1.34
lcsSetupPerfmonRttmonstatisticsEntryPacketLossSd OBJECT-TYPE
    SYNTAX     INTEGER (0..2147483647)
    MAX-ACCESS read-only
    STATUS     current
    DESCRIPTION
        "-- empty --"
    ::= { lcsSetupPerfmonRttmonstatisticsEntry 34 }

-- {COLUMN} 1712.2.36.4.1.35
lcsSetupPerfmonRttmonstatisticsEntryPacketLossDs OBJECT-TYPE
    SYNTAX     INTEGER (0..2147483647)
    MAX-ACCESS read-only
    STATUS     current
    DESCRIPTION
        "-- empty --"
    ::= { lcsSetupPerfmonRttmonstatisticsEntry 35 }

-- {COLUMN} 1712.2.36.4.1.62
lcsSetupPerfmonRttmonstatisticsEntryAverageJitter OBJECT-TYPE
    SYNTAX     INTEGER (0..2147483647)
    MAX-ACCESS read-only
    STATUS     current
    DESCRIPTION
        "-- empty --"
    ::= { lcsSetupPerfmonRttmonstatisticsEntry 62 }

-- {COLUMN} 1712.2.36.4.1.63
lcsSetupPerfmonRttmonstatisticsEntryAverageJitterSd OBJECT-TYPE
    SYNTAX     INTEGER (0..2147483647)
    MAX-ACCESS read-only
    STATUS     current
    DESCRIPTION
        "-- empty --"
    ::= { lcsSetupPerfmonRttmonstatisticsEntry 63 }

-- {COLUMN} 1712.2.36.4.1.64
lcsSetupPerfmonRttmonstatisticsEntryAverageJitterDs OBJECT-TYPE
    SYNTAX     INTEGER (0..2147483647)
    MAX-ACCESS read-only
    STATUS     current
    DESCRIPTION
        "-- empty --"
    ::= { lcsSetupPerfmonRttmonstatisticsEntry 64 }

-- {OID} 1712.2.35
lcsSetupEchoServer OBJECT IDENTIFIER ::= { lcsSetup 35 }

-- {SCALAR} 1712.2.35.1
lcsSetupEchoServerOperating OBJECT-TYPE
    SYNTAX     INTEGER
      {
        eNo (0),
        eYes (1)
      }
    MAX-ACCESS read-write
    STATUS     current
    DESCRIPTION
        "-- empty --"
    ::= { lcsSetupEchoServer 1 }

-- {TABLE} 1712.2.35.2
lcsSetupEchoServerAccessTableTable OBJECT-TYPE
    SYNTAX     SEQUENCE OF LcsSetupEchoServerAccessTableEntry
    MAX-ACCESS not-accessible
    STATUS     current
    DESCRIPTION
        "-- empty --"
    ::= { lcsSetupEchoServer 2 }

-- {ENTRY} 1712.2.35.2.1
lcsSetupEchoServerAccessTableEntry OBJECT-TYPE
    SYNTAX     LcsSetupEchoServerAccessTableEntry
    MAX-ACCESS not-accessible
    STATUS     current
    DESCRIPTION
        ""
    INDEX {
        lcsSetupEchoServerAccessTableEntryIpAddress,
        lcsSetupEchoServerAccessTableEntryNetmask
    }
    ::= { lcsSetupEchoServerAccessTableTable 1 }

-- {SEQUENCE}
LcsSetupEchoServerAccessTableEntry ::= SEQUENCE {
    lcsSetupEchoServerAccessTableEntryIpAddress IpAddress,
    lcsSetupEchoServerAccessTableEntryNetmask IpAddress,
    lcsSetupEchoServerAccessTableEntryProtokoll INTEGER,
    lcsSetupEchoServerAccessTableEntryActive INTEGER,
    lcsSetupEchoServerAccessTableEntryComment DisplayString
}

-- {COLUMN} 1712.2.35.2.1.1
lcsSetupEchoServerAccessTableEntryIpAddress OBJECT-TYPE
    SYNTAX     IpAddress
    MAX-ACCESS read-write
    STATUS     current
    DESCRIPTION
        "-- empty --"
    ::= { lcsSetupEchoServerAccessTableEntry 1 }

-- {COLUMN} 1712.2.35.2.1.2
lcsSetupEchoServerAccessTableEntryNetmask OBJECT-TYPE
    SYNTAX     IpAddress
    MAX-ACCESS read-write
    STATUS     current
    DESCRIPTION
        "-- empty --"
    ::= { lcsSetupEchoServerAccessTableEntry 2 }

-- {COLUMN} 1712.2.35.2.1.3
lcsSetupEchoServerAccessTableEntryProtokoll OBJECT-TYPE
    SYNTAX     INTEGER
      {
        eNone (0),
        eTcp (1),
        eUdp (2),
        eTcpPlusUdp (3)
      }
    MAX-ACCESS read-write
    STATUS     current
    DESCRIPTION
        "-- empty --"
    ::= { lcsSetupEchoServerAccessTableEntry 3 }

-- {COLUMN} 1712.2.35.2.1.4
lcsSetupEchoServerAccessTableEntryActive OBJECT-TYPE
    SYNTAX     INTEGER
      {
        eYes (0),
        eNo (1)
      }
    MAX-ACCESS read-write
    STATUS     current
    DESCRIPTION
        "-- empty --"
    ::= { lcsSetupEchoServerAccessTableEntry 4 }

-- {COLUMN} 1712.2.35.2.1.5
lcsSetupEchoServerAccessTableEntryComment OBJECT-TYPE
    SYNTAX     DisplayString (SIZE(0..31))
    MAX-ACCESS read-write
    STATUS     current
    DESCRIPTION
        "-- empty --"
    ::= { lcsSetupEchoServerAccessTableEntry 5 }

-- {SCALAR} 1712.2.35.3
lcsSetupEchoServerTcpTimeout OBJECT-TYPE
    SYNTAX     INTEGER (0..2147483647)
    MAX-ACCESS read-write
    STATUS     current
    DESCRIPTION
        "-- empty --"
    ::= { lcsSetupEchoServer 3 }

-- {OID} 1712.3
lcsFirmware OBJECT IDENTIFIER ::= { lancom-1711-plus 3 }

-- {TABLE} 1712.3.1
lcsFirmwareVersionTableTable OBJECT-TYPE
    SYNTAX     SEQUENCE OF LcsFirmwareVersionTableEntry
    MAX-ACCESS not-accessible
    STATUS     current
    DESCRIPTION
        "-- empty --"
    ::= { lcsFirmware 1 }

-- {ENTRY} 1712.3.1.1
lcsFirmwareVersionTableEntry OBJECT-TYPE
    SYNTAX     LcsFirmwareVersionTableEntry
    MAX-ACCESS not-accessible
    STATUS     current
    DESCRIPTION
        ""
    INDEX {
        lcsFirmwareVersionTableEntryIfc
    }
    ::= { lcsFirmwareVersionTableTable 1 }

-- {SEQUENCE}
LcsFirmwareVersionTableEntry ::= SEQUENCE {
    lcsFirmwareVersionTableEntryIfc INTEGER,
    lcsFirmwareVersionTableEntryModule DisplayString,
    lcsFirmwareVersionTableEntryVersion DisplayString,
    lcsFirmwareVersionTableEntrySerialNumber DisplayString
}

-- {COLUMN} 1712.3.1.1.1
lcsFirmwareVersionTableEntryIfc OBJECT-TYPE
    SYNTAX     INTEGER
      {
        eIfc (1)
      }
    MAX-ACCESS read-only
    STATUS     current
    DESCRIPTION
        "-- empty --"
    ::= { lcsFirmwareVersionTableEntry 1 }

-- {COLUMN} 1712.3.1.1.2
lcsFirmwareVersionTableEntryModule OBJECT-TYPE
    SYNTAX     DisplayString (SIZE(0..64))
    MAX-ACCESS read-only
    STATUS     current
    DESCRIPTION
        "-- empty --"
    ::= { lcsFirmwareVersionTableEntry 2 }

-- {COLUMN} 1712.3.1.1.3
lcsFirmwareVersionTableEntryVersion OBJECT-TYPE
    SYNTAX     DisplayString (SIZE(0..30))
    MAX-ACCESS read-only
    STATUS     current
    DESCRIPTION
        "-- empty --"
    ::= { lcsFirmwareVersionTableEntry 3 }

-- {COLUMN} 1712.3.1.1.4
lcsFirmwareVersionTableEntrySerialNumber OBJECT-TYPE
    SYNTAX     DisplayString (SIZE(0..19))
    MAX-ACCESS read-only
    STATUS     current
    DESCRIPTION
        "-- empty --"
    ::= { lcsFirmwareVersionTableEntry 4 }

-- {TABLE} 1712.3.2
lcsFirmwareTableFirmsafeTable OBJECT-TYPE
    SYNTAX     SEQUENCE OF LcsFirmwareTableFirmsafeEntry
    MAX-ACCESS not-accessible
    STATUS     current
    DESCRIPTION
        "-- empty --"
    ::= { lcsFirmware 2 }

-- {ENTRY} 1712.3.2.1
lcsFirmwareTableFirmsafeEntry OBJECT-TYPE
    SYNTAX     LcsFirmwareTableFirmsafeEntry
    MAX-ACCESS not-accessible
    STATUS     current
    DESCRIPTION
        ""
    INDEX {
        lcsFirmwareTableFirmsafeEntryPosition
    }
    ::= { lcsFirmwareTableFirmsafeTable 1 }

-- {SEQUENCE}
LcsFirmwareTableFirmsafeEntry ::= SEQUENCE {
    lcsFirmwareTableFirmsafeEntryPosition INTEGER,
    lcsFirmwareTableFirmsafeEntryStatus INTEGER,
    lcsFirmwareTableFirmsafeEntryVersion DisplayString,
    lcsFirmwareTableFirmsafeEntryDate DisplayString,
    lcsFirmwareTableFirmsafeEntrySize INTEGER,
    lcsFirmwareTableFirmsafeEntryIndex INTEGER
}

-- {COLUMN} 1712.3.2.1.1
lcsFirmwareTableFirmsafeEntryPosition OBJECT-TYPE
    SYNTAX     INTEGER (0..255)
    MAX-ACCESS read-only
    STATUS     current
    DESCRIPTION
        "-- empty --"
    ::= { lcsFirmwareTableFirmsafeEntry 1 }

-- {COLUMN} 1712.3.2.1.2
lcsFirmwareTableFirmsafeEntryStatus OBJECT-TYPE
    SYNTAX     INTEGER
      {
        eLoader (2),
        eActive (1),
        eInactive (0),
        eMinimalPlusActive (5),
        eMinimalPlusInactive (4)
      }
    MAX-ACCESS read-write
    STATUS     current
    DESCRIPTION
        "-- empty --"
    ::= { lcsFirmwareTableFirmsafeEntry 2 }

-- {COLUMN} 1712.3.2.1.3
lcsFirmwareTableFirmsafeEntryVersion OBJECT-TYPE
    SYNTAX     DisplayString (SIZE(0..17))
    MAX-ACCESS read-only
    STATUS     current
    DESCRIPTION
        "-- empty --"
    ::= { lcsFirmwareTableFirmsafeEntry 3 }

-- {COLUMN} 1712.3.2.1.4
lcsFirmwareTableFirmsafeEntryDate OBJECT-TYPE
    SYNTAX     DisplayString (SIZE(0..9))
    MAX-ACCESS read-only
    STATUS     current
    DESCRIPTION
        "-- empty --"
    ::= { lcsFirmwareTableFirmsafeEntry 4 }

-- {COLUMN} 1712.3.2.1.5
lcsFirmwareTableFirmsafeEntrySize OBJECT-TYPE
    SYNTAX     INTEGER (0..2147483647)
    MAX-ACCESS read-only
    STATUS     current
    DESCRIPTION
        "-- empty --"
    ::= { lcsFirmwareTableFirmsafeEntry 5 }

-- {COLUMN} 1712.3.2.1.6
lcsFirmwareTableFirmsafeEntryIndex OBJECT-TYPE
    SYNTAX     INTEGER (0..2147483647)
    MAX-ACCESS read-only
    STATUS     current
    DESCRIPTION
        "-- empty --"
    ::= { lcsFirmwareTableFirmsafeEntry 6 }

-- {SCALAR} 1712.3.3
lcsFirmwareModeFirmsafe OBJECT-TYPE
    SYNTAX     INTEGER
      {
        eImmediate (0),
        eLogin (1),
        eManual (2)
      }
    MAX-ACCESS read-write
    STATUS     current
    DESCRIPTION
        "-- empty --"
    ::= { lcsFirmware 3 }

-- {SCALAR} 1712.3.4
lcsFirmwareTimeoutFirmsafe OBJECT-TYPE
    SYNTAX     INTEGER (0..65535)
    MAX-ACCESS read-write
    STATUS     current
    DESCRIPTION
        "-- empty --"
    ::= { lcsFirmware 4 }

-- {SCALAR} 1712.3.7
lcsFirmwareFeatureWord OBJECT-TYPE
    SYNTAX     DisplayString (SIZE(0..34))
    MAX-ACCESS read-only
    STATUS     current
    DESCRIPTION
        "-- empty --"
    ::= { lcsFirmware 7 }

-- {OID} 1712.4
lcsOther OBJECT IDENTIFIER ::= { lancom-1711-plus 4 }

-- {OID} 1712.4.1
lcsOtherManualDialing OBJECT IDENTIFIER ::= { lcsOther 1 }

-- {SCALAR} 1712.4.1.1
lcsOtherManualDialingConnect OBJECT-TYPE
    SYNTAX     DisplayString
    MAX-ACCESS read-write
    STATUS     current
    DESCRIPTION
        "-- empty --"
    ::= { lcsOtherManualDialing 1 }

-- {SCALAR} 1712.4.1.2
lcsOtherManualDialingDisconnect OBJECT-TYPE
    SYNTAX     DisplayString
    MAX-ACCESS read-write
    STATUS     current
    DESCRIPTION
        "-- empty --"
    ::= { lcsOtherManualDialing 2 }

-- {SCALAR} 1712.4.2
lcsOtherBootSystem OBJECT-TYPE
    SYNTAX     DisplayString
    MAX-ACCESS read-write
    STATUS     current
    DESCRIPTION
        "-- empty --"
    ::= { lcsOther 2 }

-- {SCALAR} 1712.4.5
lcsOtherColdBoot OBJECT-TYPE
    SYNTAX     DisplayString
    MAX-ACCESS read-write
    STATUS     current
    DESCRIPTION
        "-- empty --"
    ::= { lcsOther 5 }

-- notifications
-- {OID} 1712.0
lcsTrapGrp OBJECT IDENTIFIER ::= { lancom-1711-plus 0 }

-- {OID} 1712.0.0
lcsTraps OBJECT IDENTIFIER ::= { lcsTrapGrp 0 }

-- {NOTIFICATION} 1712.0.0.1
lcsTrapsStatChan NOTIFICATION-TYPE
    OBJECTS {
        sysDescr,
        sysName,
        lcsStatusSnmpEventEntryCount,
        lcsStatusWanConnections,
        lcsStatusChannelEntryState,
        lcsStatusChannelEntryApp,
        lcsStatusChannelEntryConnector,
        lcsStatusChannelEntryCause,
        lcsStatusChannelEntryNumber,
        lcsStatusChannelEntrySubaddress,
        lcsStatusChannelEntryCharge,
        lcsStatusChannelEntryExtra,
        lcsStatusChannelEntryConnTime,
        lcsStatusChannelEntryConnStart,
        lcsStatusChannelEntryIsdnDisplay,
        lcsStatusChannelEntryPhChan,
        lcsStatusChannelEntryPptpConns,
        lcsStatusChannelEntryVpnConns
    }
    STATUS     current
    DESCRIPTION
        "WAN connection status"
    ::= { lcsTraps 1 }

-- {NOTIFICATION} 1712.0.0.4
lcsTrapsFwUplStart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Firmware upload was started"
    ::= { lcsTraps 4 }

-- {NOTIFICATION} 1712.0.0.5
lcsTrapsUplsucc NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "Firmware or configuration upload successful"
    ::= { lcsTraps 5 }

-- {NOTIFICATION} 1712.0.0.6
lcsTrapsUplfailto NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload of firmware or configuration failed: maximum time was exceeded"
    ::= { lcsTraps 6 }

-- {NOTIFICATION} 1712.0.0.7
lcsTrapsUplfailincl NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload of firmware or configuration failed: incomplete configuration"
    ::= { lcsTraps 7 }

-- {NOTIFICATION} 1712.0.0.8
lcsTrapsUplfailbaddev NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload of firmware or configuration failed: wrong device"
    ::= { lcsTraps 8 }

-- {NOTIFICATION} 1712.0.0.9
lcsTrapsLogin NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Login to configuration successful"
    ::= { lcsTraps 9 }

-- {NOTIFICATION} 1712.0.0.10
lcsTrapsLogout NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Logout from configuration was successful"
    ::= { lcsTraps 10 }

-- {NOTIFICATION} 1712.0.0.11
lcsTrapsCnfuplstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Configuration upload was started"
    ::= { lcsTraps 11 }

-- {NOTIFICATION} 1712.0.0.12
lcsTrapsCnfdnlstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Configuration download was started"
    ::= { lcsTraps 12 }

-- {NOTIFICATION} 1712.0.0.13
lcsTrapsCnfdnlsucc NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "Configuration download successful"
    ::= { lcsTraps 13 }

-- {NOTIFICATION} 1712.0.0.26
lcsTrapsIpfwflt NOTIFICATION-TYPE
    OBJECTS {
        sysDescr,
        sysName,
        lcsStatusSnmpEventEntryCount,
        lcsStatusIpRouterLogTableEntrySystemTime,
        lcsStatusIpRouterLogTableEntrySrcAddress,
        lcsStatusIpRouterLogTableEntryDstAddress,
        lcsStatusIpRouterLogTableEntryProt,
        lcsStatusIpRouterLogTableEntrySrcPort,
        lcsStatusIpRouterLogTableEntryDstPort,
        lcsStatusIpRouterLogTableEntryFilterRule,
        lcsStatusIpRouterLogTableEntryLimit,
        lcsStatusIpRouterLogTableEntryThreshold,
        lcsStatusIpRouterLogTableEntryAction
    }
    STATUS     current
    DESCRIPTION
        "Information about an IPv4 firewall event"
    ::= { lcsTraps 26 }

-- {NOTIFICATION} 1712.0.0.27
lcsTrapsVpnconn NOTIFICATION-TYPE
    OBJECTS {
        sysDescr,
        sysName,
        lcsStatusSnmpEventEntryCount,
        lcsStatusVpnTunnel,
        lcsStatusVpnConnectionsEntryPeer,
        lcsStatusVpnConnectionsEntryState,
        lcsStatusVpnConnectionsEntryLastError,
        lcsStatusVpnConnectionsEntryMode,
        lcsStatusVpnConnectionsEntryShTime,
        lcsStatusVpnConnectionsEntryPhysConn,
        lcsStatusVpnConnectionsEntryB1Dt,
        lcsStatusVpnConnectionsEntryRemoteGwNew,
        lcsStatusVpnConnectionsEntryNatDetection,
        lcsStatusVpnConnectionsEntrySslEncaps,
        lcsStatusVpnConnectionsEntryCryptAlg,
        lcsStatusVpnConnectionsEntryCryptLength,
        lcsStatusVpnConnectionsEntryHashAlg,
        lcsStatusVpnConnectionsEntryHashLength,
        lcsStatusVpnConnectionsEntryHmacAlg,
        lcsStatusVpnConnectionsEntryHmacLength,
        lcsStatusVpnConnectionsEntryComprAlg,
        lcsStatusVpnConnectionsEntryClientSn
    }
    STATUS     current
    DESCRIPTION
        "Status of VPN connection"
    ::= { lcsTraps 27 }

-- {NOTIFICATION} 1712.0.0.28
lcsTrapsPptpconn NOTIFICATION-TYPE
    OBJECTS {
        sysDescr,
        sysName,
        lcsStatusSnmpEventEntryCount,
        lcsStatusPptpTunnel,
        lcsStatusPptpConnectionsEntryChannel,
        lcsStatusPptpConnectionsEntryState,
        lcsStatusPptpConnectionsEntryMode,
        lcsStatusPptpConnectionsEntryShTime,
        lcsStatusPptpConnectionsEntryPhysConnection,
        lcsStatusPptpConnectionsEntryPeerAddress,
        lcsStatusPptpConnectionsEntryIpAddress,
        lcsStatusPptpConnectionsEntryDnsDefault,
        lcsStatusPptpConnectionsEntryNbnsDefault,
        lcsStatusPptpConnectionsEntryLastError,
        lcsStatusPptpConnectionsEntryDnsBackup,
        lcsStatusPptpConnectionsEntryNbnsBackup
    }
    STATUS     current
    DESCRIPTION
        "Status of PPTP connection"
    ::= { lcsTraps 28 }

-- {NOTIFICATION} 1712.0.0.29
lcsTrapsErrlogin NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "Error during login to configuration"
    ::= { lcsTraps 29 }

-- {NOTIFICATION} 1712.0.0.38
lcsTrapsLdblconn NOTIFICATION-TYPE
    OBJECTS {
        sysDescr,
        sysName,
        lcsStatusSnmpEventEntryCount,
        lcsStatusIpRouterLoadBalancerConnectionsEntryPeer,
        lcsStatusIpRouterLoadBalancerConnectionsEntryBundlePeer,
        lcsStatusIpRouterLoadBalancerConnectionsEntryState
    }
    STATUS     current
    DESCRIPTION
        "Load balancer connection status"
    ::= { lcsTraps 38 }

-- {NOTIFICATION} 1712.0.0.39
lcsTrapsPppoesconn NOTIFICATION-TYPE
    OBJECTS {
        sysDescr,
        sysName,
        lcsStatusSnmpEventEntryCount,
        lcsStatusPppoeServerNumConnections,
        lcsStatusPppoeServerConnectionsEntryChannel,
        lcsStatusPppoeServerConnectionsEntryMacAddress,
        lcsStatusPppoeServerConnectionsEntryState,
        lcsStatusPppoeServerConnectionsEntryLastError,
        lcsStatusPppoeServerConnectionsEntryShTime,
        lcsStatusPppoeServerConnectionsEntryPeerAddress
    }
    STATUS     current
    DESCRIPTION
        "PPPoE server connection status"
    ::= { lcsTraps 39 }

-- {NOTIFICATION} 1712.0.0.41
lcsTrapsVrrp NOTIFICATION-TYPE
    OBJECTS {
        sysDescr,
        sysName,
        lcsStatusSnmpEventEntryCount,
        lcsStatusIpRouterVrrpEventLogEntrySystemTime,
        lcsStatusIpRouterVrrpEventLogEntrySrcAddress,
        lcsStatusIpRouterVrrpEventLogEntryVrid,
        lcsStatusIpRouterVrrpEventLogEntryEvent,
        lcsStatusIpRouterVrrpEventLogEntryInfo
    }
    STATUS     current
    DESCRIPTION
        "Information about a VRRP event"
    ::= { lcsTraps 41 }

-- {NOTIFICATION} 1712.0.0.77
lcsTrapsLicensemgtexpire NOTIFICATION-TYPE
    OBJECTS {
        sysDescr,
        sysName,
        lcsStatusSnmpEventEntryCount,
        lcsStatusConfigFeaturesEntryFeature,
        lcsStatusConfigFeaturesEntryExpires,
        lcsStatusConfigFeaturesEntryExpire,
        lcsStatusConfigFeaturesEntryState,
        lcsStatusConfigFeaturesEntryIndex,
        lcsStatusConfigFeaturesEntryCount
    }
    STATUS     current
    DESCRIPTION
        "Software option license has expired"
    ::= { lcsTraps 77 }

-- {NOTIFICATION} 1712.0.0.79
lcsTrapsScrptuplstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "script upload was started"
    ::= { lcsTraps 79 }

-- {NOTIFICATION} 1712.0.0.80
lcsTrapsScrptdnlstart NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew
    }
    STATUS     current
    DESCRIPTION
        "script download was started"
    ::= { lcsTraps 80 }

-- {NOTIFICATION} 1712.0.0.81
lcsTrapsIpv6fwflt NOTIFICATION-TYPE
    OBJECTS {
        sysDescr,
        sysName,
        lcsStatusSnmpEventEntryCount,
        lcsStatusIpv6FirewallLogTableEntrySystemTime,
        lcsStatusIpv6FirewallLogTableEntrySrcAddress,
        lcsStatusIpv6FirewallLogTableEntryDstAddress,
        lcsStatusIpv6FirewallLogTableEntryProt,
        lcsStatusIpv6FirewallLogTableEntrySrcPort,
        lcsStatusIpv6FirewallLogTableEntryDstPort,
        lcsStatusIpv6FirewallLogTableEntryFilterRule,
        lcsStatusIpv6FirewallLogTableEntryLimit,
        lcsStatusIpv6FirewallLogTableEntryThreshold,
        lcsStatusIpv6FirewallLogTableEntryAction
    }
    STATUS     current
    DESCRIPTION
        "Information about an IPv6 firewall event"
    ::= { lcsTraps 81 }

-- {NOTIFICATION} 1712.0.0.82
lcsTrapsWwanStates NOTIFICATION-TYPE
    OBJECTS {
        sysDescr,
        sysName,
        lcsStatusSnmpEventEntryCount,
        lcsStatusModemMobileState,
        lcsStatusModemMobileRegistration
    }
    STATUS     current
    DESCRIPTION
        "-- empty --"
    ::= { lcsTraps 82 }

-- {NOTIFICATION} 1712.0.0.83
lcsTrapsDS-Lite NOTIFICATION-TYPE
    OBJECTS {
        sysDescr,
        sysName,
        lcsStatusSnmpEventEntryCount,
        lcsStatusDsLiteConnectionsEntryPeer,
        lcsStatusDsLiteConnectionsEntryState,
        lcsStatusDsLiteConnectionsEntryLastError,
        lcsStatusDsLiteConnectionsEntryIpv4Address,
        lcsStatusDsLiteConnectionsEntryPhysConn,
        lcsStatusDsLiteConnectionsEntryAftrName,
        lcsStatusDsLiteConnectionsEntryAftrIpv6Address,
        lcsStatusDsLiteConnectionsEntryConnTime
    }
    STATUS     current
    DESCRIPTION
        "DS-LITE connection status"
    ::= { lcsTraps 83 }

-- {NOTIFICATION} 1712.0.0.85
lcsTrapsL2TP-Endpoints NOTIFICATION-TYPE
    OBJECTS {
        sysDescr,
        sysName,
        lcsStatusSnmpEventEntryCount,
        lcsStatusL2tpNumEndpoints,
        lcsStatusL2tpEndpointsEntryL2tpEndpoint,
        lcsStatusL2tpEndpointsEntryState,
        lcsStatusL2tpEndpointsEntryLastError,
        lcsStatusL2tpEndpointsEntryMode,
        lcsStatusL2tpEndpointsEntryPhysConnection,
        lcsStatusL2tpEndpointsEntryGateway,
        lcsStatusL2tpEndpointsEntrySessions,
        lcsStatusL2tpEndpointsEntryConnTime,
        lcsStatusL2tpEndpointsEntryEmbeddedErrorMessage
    }
    STATUS     current
    DESCRIPTION
        "L2TP tunnel end point status"
    ::= { lcsTraps 85 }

-- {NOTIFICATION} 1712.0.0.86
lcsTrapsL2TP-Connections NOTIFICATION-TYPE
    OBJECTS {
        sysDescr,
        sysName,
        lcsStatusSnmpEventEntryCount,
        lcsStatusL2tpNumConnections,
        lcsStatusL2tpConnectionsEntryPeer,
        lcsStatusL2tpConnectionsEntryState,
        lcsStatusL2tpConnectionsEntryLastError,
        lcsStatusL2tpConnectionsEntryMode,
        lcsStatusL2tpConnectionsEntryShTime,
        lcsStatusL2tpConnectionsEntryL2tpEndpoint,
        lcsStatusL2tpConnectionsEntryPeerAddress,
        lcsStatusL2tpConnectionsEntryIpAddress,
        lcsStatusL2tpConnectionsEntryDnsDefault,
        lcsStatusL2tpConnectionsEntryDnsBackup,
        lcsStatusL2tpConnectionsEntryNbnsDefault,
        lcsStatusL2tpConnectionsEntryNbnsBackup,
        lcsStatusL2tpConnectionsEntryConnTime
    }
    STATUS     current
    DESCRIPTION
        "L2TP connection status"
    ::= { lcsTraps 86 }

-- {NOTIFICATION} 1712.0.0.2000
lcsTrapsHttpTunnelOpen NOTIFICATION-TYPE
    OBJECTS {
        sysDescr,
        sysName,
        lcsStatusSnmpEventEntryCount,
        lcsStatusTcpIpHttpActiveTunnelsEntryIndex,
        lcsStatusTcpIpHttpActiveTunnelsEntryRemoteAddress,
        lcsStatusTcpIpHttpActiveTunnelsEntryRemotePort,
        lcsStatusTcpIpHttpActiveTunnelsEntryLocalHost,
        lcsStatusTcpIpHttpActiveTunnelsEntryLocalPort,
        lcsStatusTcpIpHttpActiveTunnelsEntryIdleTime,
        lcsStatusTcpIpHttpActiveTunnelsEntryLocalRtgTag
    }
    STATUS     current
    DESCRIPTION
        "HTTP tunnel opened successful"
    ::= { lcsTraps 2000 }

-- {NOTIFICATION} 1712.0.0.2001
lcsTrapsHttpTunnelClose NOTIFICATION-TYPE
    OBJECTS {
        sysDescr,
        sysName,
        lcsStatusSnmpEventEntryCount,
        lcsStatusTcpIpHttpActiveTunnelsEntryIndex
    }
    STATUS     current
    DESCRIPTION
        "HTTP tunnel closed successful"
    ::= { lcsTraps 2001 }

-- {NOTIFICATION} 1712.0.0.5002
lcsTrapsLanOvertempThrottle NOTIFICATION-TYPE
    OBJECTS {
        sysDescr,
        sysName,
        lcsStatusSnmpEventEntryCount
    }
    STATUS     current
    DESCRIPTION
        "Throttling of LAN Speed due to temperature exceedance active"
    ::= { lcsTraps 5002 }

-- {NOTIFICATION} 1712.0.0.5003
lcsTrapsLanOvertempThrottleEnd NOTIFICATION-TYPE
    OBJECTS {
        sysDescr,
        sysName,
        lcsStatusSnmpEventEntryCount
    }
    STATUS     current
    DESCRIPTION
        "Throttling of LAN Speed due to temperature exceedance stopped"
    ::= { lcsTraps 5003 }

-- {NOTIFICATION} 1712.0.0.5004
lcsTrapsLanOvertempThrottleRecommend NOTIFICATION-TYPE
    OBJECTS {
        sysDescr,
        sysName,
        lcsStatusSnmpEventEntryCount
    }
    STATUS     current
    DESCRIPTION
        "Throttling of LAN Speed due to temperature exceedance recommended"
    ::= { lcsTraps 5004 }

-- {NOTIFICATION} 1712.0.0.7000
lcsTrapsUplinvversion NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload of firmware failed: invalid firmware version"
    ::= { lcsTraps 7000 }

-- {NOTIFICATION} 1712.0.0.7001
lcsTrapsUplfileexists NOTIFICATION-TYPE
    OBJECTS {
        sysDescr,
        sysName,
        lcsStatusSnmpEventEntryCount,
        lcsStatusConfigEventLogEntrySystemTime,
        lcsStatusConfigEventLogEntryEvent,
        lcsStatusConfigEventLogEntryAccess,
        lcsStatusConfigEventLogEntryIpAddressNew,
        lcsStatusConfigEventLogEntryInfo1,
        lcsStatusConfigEventLogEntryInfo2
    }
    STATUS     current
    DESCRIPTION
        "The upload of file failed: file with this version already exists"
    ::= { lcsTraps 7001 }
END
