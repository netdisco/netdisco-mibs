-- ********************************************************************
-- * Wireless LAN Access Point Management Base
-- ********************************************************************

WG302-MIB DEFINITIONS ::= BEGIN

    IMPORTS
	MODULE-IDENTITY,	OBJECT-TYPE,
	NOTIFICATION-TYPE,	enterprises,
	Integer32,		Counter32,
	IpAddress,		Unsigned32,
	TimeTicks,					FROM SNMPv2-SMI
	MODULE-COMPLIANCE,	NOTIFICATION-GROUP,
	OBJECT-GROUP					FROM SNMPv2-CONF

	TEXTUAL-CONVENTION,	DisplayString,
	MacAddress,		TruthValue		FROM SNMPv2-TC
	ifIndex	    					FROM RFC1213-MIB;

-- The Enterprises Number
netgear	OBJECT IDENTIFIER ::= { enterprises 4526 }
wireless OBJECT IDENTIFIER ::= { netgear 4 }


-- ********************************************************************
-- *  MODULE IDENTITY
-- ********************************************************************
    accesspoint MODULE-IDENTITY
    LAST-UPDATED	"200311180000Z"
    ORGANIZATION	"NETGEAR Inc."
    CONTACT-INFO
		"4500 Great America Parkway
		Santa Clara, California 95054
		Phone: (408) 907-8000
		Fax: (408) 907-8097
		Web Site: http://www.netgear.com "
    DESCRIPTION
        "The MIB module for 802.11g ProSafe Wireless Access Point entities.
        iso(1).org(3).dod(6).internet(1).private(4).
        enterprises(1).netgear(4526).wireless(4).accesspoint(2)"
          ::= { wireless 2 }

-- Wireless LAN Access Point Identifier

-- **********************************************************************
-- *  MIB attribute OBJECT-TYPE definitions follow
-- **********************************************************************
-- **********************************************************************
-- *  IP Setting  Table
-- **********************************************************************
lanSettings OBJECT IDENTIFIER ::=  { accesspoint 1 }

apName OBJECT-TYPE
	   SYNTAX DisplayString ( SIZE(1..32) )
	   MAX-ACCESS read-write
	   STATUS current
	   DESCRIPTION
            "The field indicates the name of AP."
        ::= { lanSettings 1 }

dhcpStatus OBJECT-TYPE
        SYNTAX INTEGER { static(0), dhcpclient(1) }
        MAX-ACCESS read-write
        STATUS current
        DESCRIPTION
            "This attribute shall indicate whether dhcp client status."
    	::= { lanSettings 4 }

ipAddr       	OBJECT-TYPE
                SYNTAX IpAddress
                MAX-ACCESS read-write
                STATUS current
                DESCRIPTION
                "The field indicates the IP address of AP on the wireless
                interface,when worked in router or router/bridge mode.
                Ethernet and wireless interface share the same IP address,
                when worked in bridge mode. "
        ::= {  lanSettings 5 }

netmaskAddr  	OBJECT-TYPE
                SYNTAX IpAddress
                MAX-ACCESS read-write
                STATUS current
                DESCRIPTION
                "The field indicates the netmask of AP on the wireless
                interface,when worked in router or router/bridge mode.
                Ethernet and wireless interface share the same netmask
                address,when worked in bridge mode. "
        ::= {  lanSettings 6 }


gatewayAddr  	OBJECT-TYPE
                SYNTAX IpAddress
                MAX-ACCESS read-write
                STATUS current
                DESCRIPTION
                "The field indicates the gateway of AP on the wireless
                interface,when worked in router or router/bridge mode.
                Ethernet and wireless interface share the same gateway
                address,when worked in bridge mode. "
        ::= {  lanSettings 7 }

spantree OBJECT-TYPE
        SYNTAX TruthValue
        MAX-ACCESS read-write
        STATUS current
        DESCRIPTION
            "This attribute shall indicate spanning tree."
    ::= { lanSettings 8 }

-- **********************************************************************
-- *  Wireless Settings Table
-- **********************************************************************
wlanSettingTable OBJECT-TYPE
        SYNTAX SEQUENCE OF wlanSettingEntry
        MAX-ACCESS not-accessible
        STATUS current
        DESCRIPTION
            "wlanSettingsallow for multiple instances on an agent."
    ::= {  accesspoint 2 }

wlanSettingEntry OBJECT-TYPE
        SYNTAX wlanSettingEntry
        MAX-ACCESS not-accessible
        STATUS current
        DESCRIPTION
            "An entry in the wlanSettingTable.  It is possible for
            there to be multiple AP interfaces on one agent,
            each with its unique MAC address. The relationship
            between an AP interface and an interface in the context
            of the Internet-standard MIB is one-to-one.
            As such, the value of an ifIndex object instance can be
            directly used to identify corresponding instances of the
            objects defined herein. "
        INDEX {ifIndex}
    ::= {  wlanSettingTable 1 }

wlanSettingEntry ::=
        SEQUENCE {
         	operatemode				INTEGER,
         	countrycode				INTEGER,
         	ssid					DisplayString,
         	channel					INTEGER,
         	datarate				DisplayString,
         	beaconinterval				INTEGER,
         	rtsthreshold				INTEGER,
         	fraglength				INTEGER,
         	dtiminterval				INTEGER,
         	preambletype				INTEGER,
         	hidenetworkname				TruthValue,
         	txpower					INTEGER,
         	superG					TruthValue,
         	antenna					INTEGER
       	  }

operatemode OBJECT-TYPE
        SYNTAX INTEGER { auto(0), dot11b(2), dot11g(3) }
        MAX-ACCESS read-write
        STATUS current
        DESCRIPTION
            "This attribute shall indicate the desired wireless operating mode.
            The option are:
            Auto -  Both 802.11g and 802.11b wireless stations can be used.
            dot11b - All 802.11b wireless stations can be used.
                     802.11g wireless stations can still be used
                     if they can operate in 802.11b mode.
            dot11g - Only 802.11g wireless stations can be used."
     ::= { wlanSettingEntry 1 }

ssid OBJECT-TYPE
		SYNTAX DisplayString (SIZE(0..32))
		MAX-ACCESS read-write
		STATUS current
		DESCRIPTION
            "This attribute shall indicate SSID.Its length can't be large than 33 ."
    ::= { wlanSettingEntry 2 }

countrycode OBJECT-TYPE
        SYNTAX INTEGER  {Asia(410), Australia(36), Canada(124), Denmark(208),
        Europe(40), Finland(246), France(250), Germany(276), Ireland(372),
        Italy(380),Japan(392), Mexico(484), Netherlands(528), Newzealand(554),Norway(578),
        PuertoRico(630), SouthAmerica(344), Spain(724), Sweden(752),
        Switzerland(756), UnitedKingdom(826), UnitedStates(840) }
        MAX-ACCESS read-write
        STATUS current
        DESCRIPTION
            "This attribute shall indicate the region of operation
            for which which the wireless interface is inted.
                  =410: Asia
                  =36:  Australia
                  =124: Canada
                  =208: Denmark
                  =40:  Europe
                  =246: Finland
                  =250: France
                  =276: Germany
                  =372: Ireland
                  =380: Italy
                  =392: Japan
                  =484: Mexico
                  =528: Netherlands
                  =554:	New zealand
                  =578: Norway
                  =630: Puerto rico
                  =756: Switzerland
                  =344:  South America
                  =724: Spain
                  =752: Sweden
                  =826: UnitedKingdom
                  =840: USA"
    ::= { wlanSettingEntry 3 }

channel OBJECT-TYPE
        SYNTAX INTEGER (1..14)
        MAX-ACCESS read-write
        STATUS current
        DESCRIPTION
            "This attribute shall indicate the channel number to use on your Wireless LAN.
            		1:	CH01 2412MHz
			2:	CH02 2417MHz
			3:	CH03 2422MHz
			4:	CH04 2427MHz
			5:	CH05 2432MHz
			6:	CH06 2437MHz
			7:	CH07 2442MHz
			8:	CH08 2447MHz
			9:	CH09 2452MHz
			10:	CH10 2457MHz
			11:	CH11 2462MHz
			12:	CH12 2467MHz
			13:	CH13 2472MHz
			14:	CH14 2484MHz
		The default value is 11."
    ::= { wlanSettingEntry 4 }

datarate OBJECT-TYPE
        SYNTAX DisplayString (SIZE(0..3))
        MAX-ACCESS read-write
        STATUS current
        DESCRIPTION
            "This attribute shall indicate the transmite rate.
	         When operatemode is auto(0) can set to
	         			0:best,1:1Mb/s,2:2Mb/s, 5.5:5.5Mb/s,11:11 Mb/s,
	         			6:6Mb/s,9:   9Mb/s,12:12Mb/s,18:8Mb/s,24:24Mb/s
	              36:36Mb/s,48:48Mb/s,54:54Mb/s .
            When operatemode is dot11b(2) can set to
						 0:best,1:1Mb/s,2:2Mb/s,5.5:5.5Mb/s,11:11 Mb/s.
			 When operatemode is dot11g(3) can set to
			 			 0:best,6:6Mb/s,9:9Mb/s,12:12Mb/s,18:18Mb/s,24:24Mb/s
	           36:36Mb/s,48:48Mb/s,54:54Mb/s,108:108Mb/s. "

    ::= { wlanSettingEntry 5 }

beaconinterval OBJECT-TYPE
		SYNTAX INTEGER (20..1000)
        MAX-ACCESS read-write
        STATUS current
        DESCRIPTION
            "This attribute shall indicate the Beacon Interval."
    ::= { wlanSettingEntry 6 }

rtsthreshold OBJECT-TYPE
        SYNTAX INTEGER (0..2346)
        MAX-ACCESS read-write
        STATUS current
        DESCRIPTION
            "This attribute shall indicate the RTS threshold."
    ::= { wlanSettingEntry 7 }

fraglength OBJECT-TYPE
        SYNTAX INTEGER (256..2346)
        MAX-ACCESS read-write
        STATUS current
        DESCRIPTION
            "This attribute shall indicate the fragmentation threshold."
    ::= { wlanSettingEntry 8 }

dtiminterval OBJECT-TYPE
		SYNTAX INTEGER (1..255)
        MAX-ACCESS read-write
        STATUS current
        DESCRIPTION
            "This attribute shall indicate the DTIM period."
    ::= { wlanSettingEntry 9 }

preambletype OBJECT-TYPE
        SYNTAX INTEGER { long(0), auto(1) }
        MAX-ACCESS read-write
        STATUS current
        DESCRIPTION
            "This attribute shall indicate the preamble setting."
    ::= { wlanSettingEntry 10 }

hidenetworkname OBJECT-TYPE
        SYNTAX TruthValue
        MAX-ACCESS read-write
        STATUS current
        DESCRIPTION
            "This attribute shall indicate whether broadcast wireless
            network Name (SSID)."
    ::= { wlanSettingEntry 11 }

txpower OBJECT-TYPE
        SYNTAX INTEGER { full(0), half(1), quarter(2), eighth(3), min(4) }
        MAX-ACCESS read-write
        STATUS current
        DESCRIPTION
            "This attribute shall indicate the tranmiste power."
     ::= { wlanSettingEntry 12 }

superG OBJECT-TYPE
        SYNTAX TruthValue
        MAX-ACCESS read-write
        STATUS current
        DESCRIPTION
            "This attribute shall indicate whether super-G."
    ::= { wlanSettingEntry 13 }

antenna OBJECT-TYPE
        SYNTAX INTEGER { Auto(0), primary(1), secondary(2) }
        MAX-ACCESS read-write
        STATUS current
        DESCRIPTION
            "This attribute shall indicate the tranmiste power."
     ::= { wlanSettingEntry 14 }


-- **********************************************************************
-- *  Security  SettingsTable
-- **********************************************************************
securityTable OBJECT-TYPE
        SYNTAX SEQUENCE OF SecurityEntry
        MAX-ACCESS not-accessible
        STATUS current
        DESCRIPTION
            "Security attributes.  In tablular form to
            allow for multiple instances on an agent."
    ::= {  accesspoint 3 }

securityEntry OBJECT-TYPE
        SYNTAX SecurityEntry
        MAX-ACCESS not-accessible
        STATUS current
        DESCRIPTION
            "An entry in the securityTable.  It is possible for
            there to be multiple AP interfaces on one agent,
            each with its unique MAC address. The relationship
            between an AP interface and an interface in the context
            of the Internet-standard MIB is one-to-one.
            As such, the value of an ifIndex object instance can be
            directly used to identify corresponding instances of the
            objects defined herein. "
        INDEX {ifIndex}
    ::= {  securityTable 1 }

SecurityEntry ::=
        SEQUENCE {
                authenticationtype			INTEGER,
                encryptionstrength		 	INTEGER,
                keyno						INTEGER,
                key1					DisplayString,
                key2					DisplayString,
                key3					DisplayString,
                key4					DisplayString,
         	wlanseparator				TruthValue,
         	presharekey				DisplayString
         	   }

authenticationtype OBJECT-TYPE
        SYNTAX INTEGER { open(0), shared(1),Legacy802dot1x(100),WPA(101),WPAPSK(102) }
        MAX-ACCESS read-write
        STATUS current
        DESCRIPTION
            "The field indicates how to authenticate the station"
    ::= { securityEntry 1 }

encryptionstrength OBJECT-TYPE
        SYNTAX INTEGER {none(0),wep64(40), wep128(104), wep152(128),TKIP(255) }
        MAX-ACCESS read-write
        STATUS current
        DESCRIPTION
            "The field indicates the key length of default keys."
    ::= { securityEntry 2 }

keyno OBJECT-TYPE
         SYNTAX INTEGER (1..4)
         MAX-ACCESS read-write
         STATUS current
         DESCRIPTION
             "The field indicates the number of default wep key."
    ::= { securityEntry 3 }

key1 OBJECT-TYPE
         SYNTAX DisplayString (SIZE(0..40))
         MAX-ACCESS read-write
         STATUS current
         DESCRIPTION
             "The field indicates the key value of the first default wep key."
    ::= { securityEntry 4 }

key2 OBJECT-TYPE
         SYNTAX DisplayString (SIZE(0..40))
         MAX-ACCESS read-write
         STATUS current
         DESCRIPTION
             "The field indicates the key value of the second default wep key."
    ::= { securityEntry 5 }

key3 OBJECT-TYPE
         SYNTAX DisplayString (SIZE(0..40))
         MAX-ACCESS read-write
         STATUS current
         DESCRIPTION
             "The field indicates the key value of the third default wep key."
    ::= { securityEntry 6 }

key4 OBJECT-TYPE
         SYNTAX DisplayString (SIZE(0..40))
         MAX-ACCESS read-write
         STATUS current
         DESCRIPTION
             "The field indicates the key value of the fourth default wep key."
    ::= { securityEntry 7 }

wlanseparator OBJECT-TYPE
        SYNTAX TruthValue
        MAX-ACCESS read-write
        STATUS current
        DESCRIPTION
            "This attribute shall indicate whether enable No see."
    ::= { securityEntry 8 }

presharekey OBJECT-TYPE
        SYNTAX DisplayString (SIZE(0..63))
        MAX-ACCESS read-write
        STATUS current
        DESCRIPTION
            "This attribute shall indicate preshare key."
    ::= { securityEntry 9 }


--*********************************************************
-- Remote Settings Information
--*********************************************************
remoteSettings OBJECT IDENTIFIER ::=  { accesspoint 4}

sshd 	OBJECT-TYPE
        SYNTAX TruthValue
        MAX-ACCESS read-write
        STATUS current
        DESCRIPTION
            "This attribute shall indicate whether enable sshd."
        ::= {  remoteSettings 1 }

snmpenable 	OBJECT-TYPE
	        SYNTAX TruthValue
	        MAX-ACCESS read-write
	        STATUS current
	        DESCRIPTION
	            "This attribute shall indicate whether enable snmp."
	        ::= {  remoteSettings 2 }

trapServerIP  OBJECT-TYPE
	    SYNTAX IpAddress
	    MAX-ACCESS read-write
	    STATUS current
	    DESCRIPTION
            "The field indicates the trap server IP address.
            ***The value can only be set to a IP address in dot format."
        ::= {  remoteSettings 3 }

readOnlyCommunity  OBJECT-TYPE
	    SYNTAX DisplayString (SIZE(1..31))
	    MAX-ACCESS read-write
	    STATUS current
	    DESCRIPTION
            "The field indicates the read only community name.
            ***The value can only be set to 1 to 32 readable string."
        ::= {  remoteSettings 4 }

readWriteCommunity  OBJECT-TYPE
	    SYNTAX DisplayString (SIZE(1..31))
	    MAX-ACCESS read-write
	    STATUS current
	    DESCRIPTION
            "The field indicates the read write community name.
            ***The value can only be set to 1 to 32 readable string."
        ::= {  remoteSettings 5 }

--***********************************************************************
--*Statistic
--***********************************************************************
statistic OBJECT IDENTIFIER ::=  { accesspoint 5 }

wiredethernetstat OBJECT IDENTIFIER ::= { statistic 1 }

lanrecvpacket  OBJECT-TYPE
        SYNTAX Unsigned32
        MAX-ACCESS read-only
        STATUS current
        DESCRIPTION
	"the field indicates the sum of received packets."
	::= { wiredethernetstat 1 }

lantranspacket  OBJECT-TYPE
        SYNTAX Unsigned32
        MAX-ACCESS read-only
        STATUS current
        DESCRIPTION
	"the field indicates the sum of transmitted packets."
	::= { wiredethernetstat 2 }

lanrecvbytes  OBJECT-TYPE
        SYNTAX Unsigned32
        MAX-ACCESS read-only
        STATUS current
        DESCRIPTION
	"the field indicates the sum of received bytes."
	::= { wiredethernetstat 3 }

lantransbytes  OBJECT-TYPE
        SYNTAX Unsigned32
        MAX-ACCESS read-only
        STATUS current
        DESCRIPTION
	"the field indicates the sum of transmitted bytes."
	::= { wiredethernetstat 4 }

wirelessstat OBJECT IDENTIFIER ::= { statistic 2 }

wlanrecvunicastpacket  OBJECT-TYPE
        SYNTAX Unsigned32
        MAX-ACCESS read-only
        STATUS current
        DESCRIPTION
	"the field indicates the sum of received unicast packets."
	::= { wirelessstat 1 }

wlantransunicastpacket  OBJECT-TYPE
        SYNTAX Unsigned32
        MAX-ACCESS read-only
        STATUS current
        DESCRIPTION
	"the field indicates the sum of transmitted unicast packets."
	::= { wirelessstat 2 }

wlanrecvbroadcastpacket  OBJECT-TYPE
        SYNTAX Unsigned32
        MAX-ACCESS read-only
        STATUS current
        DESCRIPTION
	"the field indicates the sum of received broadcast packets."
	::= { wirelessstat 3 }

wlantransbroadcastpacket  OBJECT-TYPE
        SYNTAX Unsigned32
        MAX-ACCESS read-only
        STATUS current
        DESCRIPTION
	"the field indicates the sum of transmitted broadcast packets."
	::= { wirelessstat 4 }

wlanrecvmulticastpacket  OBJECT-TYPE
        SYNTAX Unsigned32
        MAX-ACCESS read-only
        STATUS current
        DESCRIPTION
	"the field indicates the sum of received multicast packets."
	::= { wirelessstat 5 }

wlantransmulticastpacket  OBJECT-TYPE
        SYNTAX Unsigned32
        MAX-ACCESS read-only
        STATUS current
        DESCRIPTION
	"the field indicates the sum of transmitted multicast packets."
	::= { wirelessstat 6 }

wlanrecvpacket  OBJECT-TYPE
        SYNTAX Unsigned32
        MAX-ACCESS read-only
        STATUS current
        DESCRIPTION
	"the field indicates the sum of received packets."
	::= { wirelessstat 7 }

wlantranspacket  OBJECT-TYPE
        SYNTAX Unsigned32
        MAX-ACCESS read-only
        STATUS current
        DESCRIPTION
	"the field indicates the sum of transmitted packets."
	::= { wirelessstat 8 }

wlanrecvbytes  OBJECT-TYPE
        SYNTAX Unsigned32
        MAX-ACCESS read-only
        STATUS current
        DESCRIPTION
	"the field indicates the sum of received bytes."
	::= { wirelessstat 9 }

wlantransbytes  OBJECT-TYPE
        SYNTAX Unsigned32
        MAX-ACCESS read-only
        STATUS current
        DESCRIPTION
	"the field indicates the sum of transmitted bytes."
	::= { wirelessstat 10 }

stationnumber OBJECT-TYPE
		SYNTAX Unsigned32
		MAX-ACCESS read-only
		STATUS current
		DESCRIPTION
            "This attribute shall indicate the stations count."
    ::= { wirelessstat 11 }

-- **********************************************************************
-- *  Station List Table
-- **********************************************************************
stationListTable OBJECT-TYPE
        SYNTAX SEQUENCE OF StationListEntry
        MAX-ACCESS not-accessible
        STATUS current
        DESCRIPTION
            "stationList Table show multiple instances on an agent."
    ::= { accesspoint 6 }

stationListEntry OBJECT-TYPE
        SYNTAX StationListEntry
        MAX-ACCESS not-accessible
        STATUS current
        DESCRIPTION
            "stationlist Entry show the connected station status "
        INDEX {ifIndex}
    ::= { stationListTable 1 }



StationListEntry ::=
        SEQUENCE {
                macaddress					MacAddress,
                stationstatus				INTEGER }

macaddress OBJECT-TYPE
		SYNTAX MacAddress
		MAX-ACCESS read-only
		STATUS current
		DESCRIPTION
            "This attribute shall indicate the stationID."
    ::= { stationListEntry 1 }

stationstatus OBJECT-TYPE
		SYNTAX INTEGER { none(0), authenticating(1), authenticated(2), associating(3), associated(4) }
		MAX-ACCESS read-only
		STATUS current
		DESCRIPTION
            "This attribute shall indicate the status of station."
    ::= { stationListEntry 2 }

--*********************************************************
-- AP Operation Mode
--*********************************************************
--ap mode
	apmode OBJECT IDENTIFIER ::=  {accesspoint 7}

apmode  OBJECT-TYPE
		        SYNTAX INTEGER { AP(0), PTP(2), PXP(3), Repeater(4) }
		        MAX-ACCESS read-write
		        STATUS current
		        DESCRIPTION
		        "This a command field for conntrol AP operation mode. "

		        ::= {  apmode 1  }

ptpmode OBJECT IDENTIFIER ::=  {apmode 2}

enableptpwlanclientasoc    OBJECT-TYPE
		        SYNTAX TruthValue
		        MAX-ACCESS read-write
		        STATUS current
		        DESCRIPTION
		        "This a command field for conntrol AP operation mode. "

		        ::= {  ptpmode 1  }

ptpremotemacaddress OBJECT-TYPE
		SYNTAX MacAddress
		MAX-ACCESS read-write
		STATUS current
		DESCRIPTION
	    "This attribute shall indicate the stationID."
    ::= { ptpmode 2 }

pxpmode OBJECT IDENTIFIER ::=  {apmode 3}

enablepxpwlanclientasoc    OBJECT-TYPE
		        SYNTAX TruthValue
		        MAX-ACCESS read-write
		        STATUS current
		        DESCRIPTION
		        "This a command field for conntrol AP operation mode. "

		        ::= {  pxpmode 1  }

pxpremotemacaddress1 OBJECT-TYPE
		SYNTAX MacAddress
		MAX-ACCESS read-write
		STATUS current
		DESCRIPTION
	    "This attribute shall indicate the stationID."
    ::= { pxpmode 2 }

pxpremotemacaddress2 OBJECT-TYPE
		SYNTAX MacAddress
		MAX-ACCESS read-write
		STATUS current
		DESCRIPTION
	    "This attribute shall indicate the stationID."
    ::= { pxpmode 3 }

pxpremotemacaddress3 OBJECT-TYPE
		SYNTAX MacAddress
		MAX-ACCESS read-write
		STATUS current
		DESCRIPTION
	    "This attribute shall indicate the stationID."
    ::= { pxpmode 4 }

pxpremotemacaddress4 OBJECT-TYPE
		SYNTAX MacAddress
		MAX-ACCESS read-write
		STATUS current
		DESCRIPTION
	    "This attribute shall indicate the stationID."
    ::= { pxpmode 5 }

repeatermode OBJECT IDENTIFIER ::=  {apmode 4}

repremotemacaddress1 OBJECT-TYPE
		SYNTAX MacAddress
		MAX-ACCESS read-write
		STATUS current
		DESCRIPTION
	    "This attribute shall indicate the stationID."
    ::= { repeatermode 1 }

repremotemacaddress2 OBJECT-TYPE
		SYNTAX MacAddress
		MAX-ACCESS read-write
		STATUS current
		DESCRIPTION
	    "This attribute shall indicate the stationID."
    ::= { repeatermode 2 }

repremotemacaddress3 OBJECT-TYPE
		SYNTAX MacAddress
		MAX-ACCESS read-write
		STATUS current
		DESCRIPTION
	    "This attribute shall indicate the stationID."
    ::= { repeatermode 3 }

repremotemacaddress4 OBJECT-TYPE
		SYNTAX MacAddress
		MAX-ACCESS read-write
		STATUS current
		DESCRIPTION
	    "This attribute shall indicate the stationID."
    ::= { repeatermode 4 }

--*********************************************************
-- 802.1x Information
--*********************************************************
	info802dot1x OBJECT IDENTIFIER ::=  {accesspoint 8}
	authinfo OBJECT IDENTIFIER ::=  {info802dot1x 1}

PriRadIpAddr OBJECT-TYPE
		SYNTAX IpAddress
		MAX-ACCESS read-write
		STATUS current
		DESCRIPTION
	    "Internet address of the Primary Radius Server."
    ::= { authinfo 1 }

PriRadPort	OBJECT-TYPE
	        SYNTAX INTEGER
	        MAX-ACCESS read-write
	        STATUS current
	        DESCRIPTION
	        "Port number used for authentication at the
	        Primary Radius Server."
	        ::= {  authinfo 2  }

PriRadSharedSecret	OBJECT-TYPE
			SYNTAX DisplayString (SIZE(0..32))
			MAX-ACCESS read-write
			STATUS current
			DESCRIPTION
	            	"Secret shared between NAS and the
	            	Primary Radius Server."
	    		::= { authinfo 3 }

SndRadIpAddr OBJECT-TYPE
		SYNTAX IpAddress
		MAX-ACCESS read-write
		STATUS current
		DESCRIPTION
	    "Internet address of the Second Radius Server."
    		::= { authinfo 4 }

SndRadPort	OBJECT-TYPE
	        SYNTAX INTEGER
	        MAX-ACCESS read-write
	        STATUS current
	        DESCRIPTION
	        "Port number used for authentication at
	        the Second Radius Server."
	        ::= {  authinfo 5  }

SndRadSharedSecret	OBJECT-TYPE
			SYNTAX DisplayString (SIZE(0..32))
			MAX-ACCESS read-write
			STATUS current
			DESCRIPTION
	            	"Secret shared between NAS and the
	            	Second Radius Server."
	    		::= { authinfo 6 }

reauthtime 		OBJECT-TYPE
		        SYNTAX INTEGER
		        MAX-ACCESS read-write
		        STATUS current
		        DESCRIPTION
		            "Current Login Status."
		    ::= { authinfo 7 }


	accntinfo OBJECT IDENTIFIER ::=  {info802dot1x 2}

PriAcntIpAddr OBJECT-TYPE
		SYNTAX IpAddress
		MAX-ACCESS read-write
		STATUS current
		DESCRIPTION
	    "IP address of the Primary radius account server."
    ::= { accntinfo 1 }

PriAcntPort	OBJECT-TYPE
	        SYNTAX INTEGER
	        MAX-ACCESS read-write
	        STATUS current
	        DESCRIPTION
	        "port number of the Primary radius account server."
	        ::= {  accntinfo 2  }

PriAcntSharedSecret	OBJECT-TYPE
			SYNTAX DisplayString (SIZE(0..32))
			MAX-ACCESS read-write
			STATUS current
			DESCRIPTION
	            	"password used by the ap to connect to
	            	the Primary radius account serve."
	    		::= { accntinfo 3 }

SndAcntIpAddr OBJECT-TYPE
		SYNTAX IpAddress
		MAX-ACCESS read-write
		STATUS current
		DESCRIPTION
	    "IP address of the Second radius account server."
    		::= { accntinfo 4 }

SndAcntPort	OBJECT-TYPE
	        SYNTAX INTEGER
	        MAX-ACCESS read-write
	        STATUS current
	        DESCRIPTION
	        "port number of the Second radius account server."
	        ::= {  accntinfo 5  }

SndAcntSharedSecret	OBJECT-TYPE
			SYNTAX DisplayString (SIZE(0..32))
			MAX-ACCESS read-write
			STATUS current
			DESCRIPTION
	            	"password used by the ap to connect to
	            	the Second radius account server."
	    		::= { accntinfo 6 }

--AcntCurLoginStat 	OBJECT-TYPE
--		        SYNTAX TruthValue
--		        MAX-ACCESS read-write
--		        STATUS current
--		        DESCRIPTION
--		            "Current Login Status."
--		    ::= { accntinfo 7 }

--*********************************************************
-- Command Information
--*********************************************************
--  Command information
	userCommand OBJECT IDENTIFIER ::=  {accesspoint 9}

resetAP	OBJECT-TYPE
        SYNTAX INTEGER
        MAX-ACCESS read-write
        STATUS current
        DESCRIPTION
            "This a command field for conntrol AP action.
            Write any value to reset the AP."
        ::= {  userCommand 1  }

setWirelessstatus OBJECT-TYPE
        SYNTAX TruthValue
        MAX-ACCESS read-write
        STATUS current
        DESCRIPTION
            "This a command field for conntrol AP's wireless card action.
            0: enable wireless card
            1: disable wireless card"
        ::= {  userCommand 2  }


END
