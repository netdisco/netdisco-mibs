-- ********************************************************************
-- * Wireless LAN Access Point Management Base
-- ********************************************************************

	WAG302 DEFINITIONS ::= BEGIN
 
		IMPORTS
			ifIndex			
				FROM RFC1213-MIB			
			OBJECT-GROUP			
				FROM SNMPv2-CONF			
			enterprises, IpAddress,Unsigned32, OBJECT-TYPE, MODULE-IDENTITY			
				FROM SNMPv2-SMI			
			DisplayString, RowStatus, TruthValue, MacAddress			
				FROM SNMPv2-TC;

--
-- Node definitions
--

-- The Enterprises Number
		-- 1.3.6.1.4.1.4526	
		netgear OBJECT IDENTIFIER ::= { enterprises 4526 }


		-- 1.3.6.1.4.1.4526.4
		wireless OBJECT IDENTIFIER ::= { netgear 4 }

-- ********************************************************************
-- *  MODULE IDENTITY
-- ********************************************************************
		wag302 MODULE-IDENTITY 
			LAST-UPDATED "200512131300Z"		-- 12 13, 2005 at 13:00 GMT
			ORGANIZATION 
				"NETGEAR Inc."
			CONTACT-INFO 
				"4500 Great America Parkway
				Santa Clara, California 95054
				Phone: (408) 907-8000
				Fax: (408) 907-8097
				Web Site: http://www.netgear.com"
			DESCRIPTION 
				"The MIB module for 802.11a/b/g ProSafe Wireless Access Point entities.
				iso(1).org(3).dod(6).internet(1).private(4).
				enterprises(1).netgear(4526).wireless(4).wag302(7)"
			::= { wireless 7 }

--   Wireless LAN Access Point Identifier
-- 
-- **********************************************************************
-- *  MIB attribute OBJECT-TYPE definitions follow
-- **********************************************************************
-- **********************************************************************
-- *  IP Setting  Table
-- **********************************************************************
		lanSettings OBJECT IDENTIFIER ::= { wag302 1 }


		apName OBJECT-TYPE
			SYNTAX DisplayString (SIZE (1..32))
			MAX-ACCESS read-write
			STATUS current
			DESCRIPTION
				"The field indicates the name of AP. The name is also the NETBIOS name of the AP."
			::= { lanSettings 1 }
               
		sysMacAddress OBJECT-TYPE
			SYNTAX MacAddress
			MAX-ACCESS read-only
			STATUS current
			DESCRIPTION
				"This field indicates the system MAC Address."
			::= { lanSettings 2 }

		sysVersion OBJECT-TYPE
			SYNTAX DisplayString
			MAX-ACCESS read-only
			STATUS current
			DESCRIPTION
				"This field indicates the system firmware version."
			::= { lanSettings 3 }			
		
		sysCountryRegion OBJECT-TYPE
			SYNTAX INTEGER
				{
                                unitedArabEmirates(784),
                                albania(8),
                                armenia(51),
                                argentina(32),                 
                                austria(40),         
				australia(36),
                                azerbaijan(31),
                                belgium(56),
                                bulgaria(100),
                                bahrain(48),
                                brunei(96),   
                                bolivia(68),
                                brazil(76),                   
                                belarus(112),
                                belize(84),              
                                canada(124),
                                switzerland(756),             
                                chile(152),         
                                china(156),        
                                colombia(170),
                                costaRica(188),
                                cyprus(196),                             
                                czechRepublic(203),
                                germany(276),
                                denmark(208),          
                                dominicanRepublic(214),
                                algeria(12),
                                ecuador(218),
                                estonia(233),
                                egypt(818),
                                spain(724),              
                                finland(246),
                                france(250),
                                unitedKingdom(826),
                                georgia(268),     
                                greece(300),
                                guatemala(320),  
                                hongkong(344),
                                honduras(340),
                                croatia(191),    
                                hungary(348),  
                                indonesia(360),    
                                ireland(372),
                                israel(376),             
                                india(356), 
                                iran(364),             
                                iceland(352),
                                italy(380),        
                                jordan(400), 
                                japan(392),
                                northKorea(408),           
                                koreaRepublic(410),
                                kuwait(414),
                                kazakhstan(398),    
                                lebanon(422),
                                liechtenstein(438), 
                                lithuania(440), 
                                luxembourg(442),
                                latvia(428),                  
                                marocco(504),        
                                monaco(492),
                                macedonia(807),
                                macau(446),
                                malta(470),            
                                mexico(484),    
                                malaysia(458),
                                netherlands(528),      
                                norway(578),
                                newZealand(554),
                                oman(512),
                                panama(591),             
                                peru(604), 
                                philippines(608),
                                pakistan(586),
                                poland(616),    
                                puertoRico(630),    
                                portugal(620),
                                qatar(634),  
                                romania(642),    
                                russia(643),
                                saudiArabia(682),   
                                sweden(752),           
                                singapore(702),
                                slovakRepublic(703),       
                                slovenia(705),
                                elSalvador(222),               
                                syria(760),           
                                thailand(764),       
                                tunisia(788),    
                                turkey(792),    
                                trinidadandTobago(780),
				taiwan(158),
                                ukraine(804), 
                                unitedStates(840),
                                uruguay(858),                       
                                uzbekistan(860),
                                venezuela(862),     
                                vietnam(704),            
                                yemen(887),
                                southAfrica(710),               
                                zimbabwe(716)               
				}
			MAX-ACCESS read-write
			STATUS current
			DESCRIPTION
				"This attribute shall indicate the region of operation
				for which which the wireless interface is intended."
			::= { lanSettings 4 }


		adminName OBJECT-TYPE
			SYNTAX DisplayString (SIZE (0..32))
			MAX-ACCESS not-accessible
			STATUS obsolete
			DESCRIPTION
				"The field indicates the administrator name."
			::= { lanSettings 5 }


		adminPasswd OBJECT-TYPE
			SYNTAX DisplayString (SIZE (0..32))
			MAX-ACCESS not-accessible
			STATUS obsolete
			DESCRIPTION
				"The field indicates the administrator password.
				The AP can be managed in such way as utility,telnet
				and so on."
			::= { lanSettings 6 }
 

		dhcpStatus OBJECT-TYPE
			SYNTAX INTEGER
				{
				static(0),
				dhcpclient(1)
				}
			MAX-ACCESS read-write
			STATUS current
			DESCRIPTION
				"This attribute shall indicate whether dhcp client status."
			::= { lanSettings 7 }


		ipAddr OBJECT-TYPE
			SYNTAX IpAddress
			MAX-ACCESS read-write
			STATUS current
			DESCRIPTION
				"The field indicates the IP address of AP on the wireless
				interface,when worked in router or router/bridge mode.
				Ethernet and wireless interface share the same IP address,
				when worked in bridge mode. "
			::= { lanSettings 8 }

		
		netmaskAddr OBJECT-TYPE
			SYNTAX IpAddress
			MAX-ACCESS read-write
			STATUS current
			DESCRIPTION
				"The field indicates the netmask of AP on the wireless
				interface,when worked in router or router/bridge mode.
				Ethernet and wireless interface share the same netmask
				address,when worked in bridge mode. "
			::= { lanSettings 9 }


		gatewayAddr OBJECT-TYPE
			SYNTAX IpAddress
			MAX-ACCESS read-write
			STATUS current
			DESCRIPTION
				"The field indicates the gateway of AP on the wireless
				interface,when worked in router or router/bridge mode.
				Ethernet and wireless interface share the same gateway
				address,when worked in bridge mode. "
			::= { lanSettings 10 }
        

            pridnsipAddr OBJECT-TYPE
			SYNTAX IpAddress
			MAX-ACCESS read-write
			STATUS current
			DESCRIPTION
				"This attributes shall indicates the IP address of the primary DNS server.
				***The value can only be set to an IP address in dot format."
			::= { lanSettings 11 }


		snddnsipAddr OBJECT-TYPE
			SYNTAX IpAddress
			MAX-ACCESS read-write
			STATUS current
			DESCRIPTION
				"This attributes shall indicates the IP address of the secondary DNS server.
				***The value can only be set to an IP address in dot format."
			::= { lanSettings 12 }
		
         
		spantree OBJECT-TYPE
			SYNTAX TruthValue
			MAX-ACCESS read-write
			STATUS current
			DESCRIPTION
				"This attribute shall indicate spanning tree."
			::= { lanSettings 13 }

 
		vlanEnable OBJECT-TYPE
			SYNTAX TruthValue
			MAX-ACCESS read-only
			STATUS current
			DESCRIPTION
				"This attribute shall indicate whether enable VLAN(802.1Q)."
			::= { lanSettings 14 }


		managementVlanID OBJECT-TYPE
			SYNTAX INTEGER (0..4094)
			MAX-ACCESS read-only
			STATUS current
			DESCRIPTION
				"This attribute shall indicate the Management VLAN ID.  "
			::= { lanSettings 15 }

               untaggedVlanID OBJECT-TYPE
                        SYNTAX INTEGER (0..4094)
                        MAX-ACCESS read-only
                        STATUS current
                        DESCRIPTION
                                "This attribute shall indicate the Untagged VLAN ID.  "
                        ::= { lanSettings 16}

		
		
-- **********************************************************************
-- *  Wireless Settings Table
-- **********************************************************************
		wlanSettingTable OBJECT-TYPE
			SYNTAX SEQUENCE OF WlanSettingEntry
			MAX-ACCESS not-accessible
			STATUS current
			DESCRIPTION
				"wlanSettingsallow for multiple instances on an agent."
			::= { wag302 2 }


		wlanSettingEntry OBJECT-TYPE
			SYNTAX WlanSettingEntry
			MAX-ACCESS not-accessible
			STATUS current
			DESCRIPTION
				"An entry in the wlanSettingTable.  It is possible for
				there to be multiple AP interfaces on one agent,
				each with its unique MAC address. The relationship
				between an AP interface and an interface in the context
				of the Internet-standard MIB is one-to-one.
				As such, the value of an ifIndex object instance can be
				directly used to identify corresponding instances of the
				objects defined herein. "
			INDEX { ifIndex }
			::= { wlanSettingTable 1 }

		
		WlanSettingEntry ::=
			SEQUENCE {
				operatemode
					INTEGER, 
				radioEnable
					TruthValue,
				channel
					INTEGER,
				datarate
					INTEGER, 
				wmmSupport
					TruthValue,					
				beaconinterval
					INTEGER, 
				rtsthreshold
					INTEGER,
				fraglength
					INTEGER,		
				dtiminterval
					INTEGER,					
				preambletype
					INTEGER, 
				txpower
					INTEGER,	
				superG
					TruthValue,
				accessControlMode
					INTEGER,
                                antenna
					INTEGER
			 }
        
        operatemode OBJECT-TYPE
			SYNTAX INTEGER
				{
				auto(0),
				dot11a(1),
				dot11b(2),
				dot11g(3)
				}
			MAX-ACCESS read-only
			STATUS current
			DESCRIPTION
				"This attribute shall indicate the desired wireless operating mode.				
				The option are:
				  auto - Both 802.11g and 802.11b wireless stations can be used.
				dot11a - Only 802.11a wireless stations can be used.
				dot11b - All 802.11b wireless stations can be used.
					 802.11g wireless stations can still be used
					 if they can operate in 802.11b mode.
				dot11g - Only 802.11g wireless stations can be used."
			::= { wlanSettingEntry 1 }
	
		
		radioEnable OBJECT-TYPE
			SYNTAX TruthValue
			MAX-ACCESS read-write
			STATUS current
			DESCRIPTION
				"This attribute shall indicate whether the radio is enabled."
			::= { wlanSettingEntry 2 }					
		

		channel OBJECT-TYPE
			SYNTAX INTEGER (1..165)
			MAX-ACCESS read-write
			STATUS current
			DESCRIPTION
				"This attribute shall indicate the channel number to be
				used."
			::= { wlanSettingEntry 3 }

		
		datarate OBJECT-TYPE
			SYNTAX INTEGER
				{
				best(0),
				rate1Mbps(1000),
				rate2Mbps(2000),
				rate5dot5Mbps(5500),
				rate6Mbps(6000),
				rate9Mbps(9000),
				rate11Mbps(11000),
				rate12Mbps(12000),
				rate18Mbps(18000),
				rate24Mbps(24000),
				rate36Mbps(36000),
				rate48Mbps(48000),
				rate54Mbps(54000)
				}
			MAX-ACCESS read-only
			STATUS current
			DESCRIPTION
				"This attribute shall indicate the transmite rate. When
				the operatemode is:
				
				   auto(0) - can set to 0:best, 1:1Mb/s, 2:2Mb/s,
				             5.5:5.5Mb/s, 11:11 Mb/s, 6:6Mb/s, 9:9Mb/s,
				             12:12Mb/s, 18:18Mb/s, 24:24Mb/s, 36:36Mb/s,
				             48:48Mb/s, and 54:54Mb/s.
				
				 dot11a(1) - can set to 0:best, 6:6Mb/s, 9:9Mb/s,
				             12:12Mb/s, 18:18Mb/s, 24:24Mb/s,
				             36:36Mb/s, 48:48Mb/s and 54:54Mb/s.
				
				 dot11b(2) - can set to 0:best, 1:1Mb/s, 2:2Mb/s,
				             5.5:5.5Mb/s, and 11:11 Mb/s.
				
				 dot11g(3) - can set to 0:best, 6:6Mb/s, 9:9Mb/s,
				             12:12Mb/s, 18:18Mb/s, 24:24Mb/s,
				             36:36Mb/s, 48:48Mb/s and 54:54Mb/s."
			::= { wlanSettingEntry 4 }  
		

		wmmSupport OBJECT-TYPE
			SYNTAX TruthValue
			MAX-ACCESS read-write
			STATUS current
			DESCRIPTION
				"This field indicates whether support WMM(Wireless Multimedia)."
			::= { wlanSettingEntry 5 }			
			  

		beaconinterval OBJECT-TYPE
			SYNTAX INTEGER (20..1000)
			UNITS "1024 microsecond"
			MAX-ACCESS read-write
			STATUS current
			DESCRIPTION
				"This attribute shall indicate the Beacon Interval."
			::= { wlanSettingEntry 6 }	   
			

		rtsthreshold OBJECT-TYPE
			SYNTAX INTEGER (0..2346)
			MAX-ACCESS read-write
			STATUS current
			DESCRIPTION
				"This attribute shall indicate the RTS threshold."
			::= { wlanSettingEntry 7}
				

		fraglength OBJECT-TYPE
			SYNTAX INTEGER (256..2346)
			MAX-ACCESS read-write
			STATUS current
			DESCRIPTION
				"This attribute shall indicate the fragmentation threshold."
			::= { wlanSettingEntry 8 }			
		

		dtiminterval OBJECT-TYPE
			SYNTAX INTEGER (1..255)
			MAX-ACCESS read-write
			STATUS current
			DESCRIPTION
				"This attribute shall indicate the DTIM period."
			::= { wlanSettingEntry 9 }				
		

		preambletype OBJECT-TYPE
			SYNTAX INTEGER
				{
				long(0),
				auto(1)
				}
			MAX-ACCESS read-only
			STATUS current
			DESCRIPTION
				"This attribute shall indicate the preamble setting.
				This setting is only applicable to 802.11b mode."
			::= { wlanSettingEntry 10 }


		txpower OBJECT-TYPE
			SYNTAX INTEGER
				{
				full(0),
				half(1),
				quarter(2),
				eighth(3),
				min(4)
				}
			MAX-ACCESS read-write
			STATUS current
			DESCRIPTION
				"This attribute shall indicate the tranmiste power."
			::= { wlanSettingEntry 11 }


		superG OBJECT-TYPE
			SYNTAX TruthValue
			MAX-ACCESS read-write
			STATUS current
			DESCRIPTION
				"This attribute shall indicate whether super mode (super-A
				for 11a radio, Super-G for 11g radio) is enabled."
			::= { wlanSettingEntry 12 }

		accessControlMode OBJECT-TYPE
			SYNTAX INTEGER
				{
				disabled(0),
				local(2),
				server(3)
				}
			MAX-ACCESS read-only
			STATUS current
			DESCRIPTION
				"The field indicates whether the access control list is
				enabled and the source of the database of the access
				control list."
			::= { wlanSettingEntry 13 }   

                   antenna OBJECT-TYPE
			SYNTAX INTEGER
				{
				auto(0),
				primary(1),
				secondary(2)
				}
			MAX-ACCESS read-write
			STATUS obsolete
			DESCRIPTION
				"This attribute shall indicate the tranmistted power."
			::= { wlanSettingEntry 14 }  	
			
						
		vapSetting OBJECT IDENTIFIER ::= { wag302 3 }		
		

		vapWepAndGlobalSettingTable OBJECT-TYPE
			SYNTAX SEQUENCE OF VapWepAndGlobalSettingEntry
			MAX-ACCESS not-accessible
			STATUS current
			DESCRIPTION
				"VAP attributes setting table."
			::= { vapSetting 1 }


		vapWepAndGlobalSettingEntry OBJECT-TYPE
			SYNTAX VapWepAndGlobalSettingEntry
			MAX-ACCESS not-accessible
			STATUS current
			DESCRIPTION
				" VAP attributes setting table."
			INDEX { ifIndex ,vapIndex }
			::= { vapWepAndGlobalSettingTable 1 }

		
		VapWepAndGlobalSettingEntry ::=
			SEQUENCE { 
			        wepKeyType
					INTEGER,
				key1
					DisplayString,
				key2
					DisplayString,
				key3
					DisplayString,
				key4
					DisplayString,
				wepPassPhrase
					DisplayString
			 }
			 
		
		wepKeyType OBJECT-TYPE
			SYNTAX INTEGER
				{
				hex64(40),
				hex128(104),
				hex152(128),
				}
			MAX-ACCESS read-write
			STATUS current
			DESCRIPTION
				"The field shall indicate the type of WEP key."
			::= { vapWepAndGlobalSettingEntry 1 }

		
		key1 OBJECT-TYPE
			SYNTAX DisplayString (SIZE (0..40))
			MAX-ACCESS read-write
			STATUS current
			DESCRIPTION
				"The field indicates the key value of the first default wep key."
			::= { vapWepAndGlobalSettingEntry 2 }

		
		key2 OBJECT-TYPE
			SYNTAX DisplayString (SIZE (0..40))
			MAX-ACCESS read-write
			STATUS current
			DESCRIPTION
				"The field indicates the key value of the second default wep key."
			::= { vapWepAndGlobalSettingEntry 3 }

	
		key3 OBJECT-TYPE
			SYNTAX DisplayString (SIZE (0..40))
			MAX-ACCESS read-write
			STATUS current
			DESCRIPTION
				"The field indicates the key value of the third default wep key."
			::= { vapWepAndGlobalSettingEntry 4 }


		key4 OBJECT-TYPE
			SYNTAX DisplayString (SIZE (0..40))
			MAX-ACCESS read-write
			STATUS current
			DESCRIPTION
				"The field indicates the key value of the fourth default wep key."
			::= { vapWepAndGlobalSettingEntry 5 }

		
		wepPassPhrase OBJECT-TYPE
			SYNTAX DisplayString (SIZE (0..39))
			MAX-ACCESS read-write
			STATUS current
			DESCRIPTION
				"This attribute shall indicate WEP pass phrase, used to
				generate four WEP keys."
			::= { vapWepAndGlobalSettingEntry 6 }

		
		
		vapSettingTable OBJECT-TYPE
			SYNTAX SEQUENCE OF VapSettingEntry
			MAX-ACCESS not-accessible
			STATUS current
			DESCRIPTION
				"VAP attributes setting table."
			::= { vapSetting 2 }

		
		vapSettingEntry OBJECT-TYPE
			SYNTAX VapSettingEntry
			MAX-ACCESS not-accessible
			STATUS current
			DESCRIPTION
				"VAP attributes setting table."
			INDEX { ifIndex, vapIndex }
			::= { vapSettingTable 1 }

		
		VapSettingEntry ::=
			SEQUENCE { 
				vapIndex
					INTEGER,
				vapEnable
					TruthValue,
				ssid
					DisplayString,
				hidenetworkname
					TruthValue,
				vlanID
					INTEGER,
				securityProfileName
					DisplayString,
				presharekey
					DisplayString,
				authenticationtype
					INTEGER,
				encryption
					INTEGER,
				keyno
					INTEGER,
				wlanseparator
					TruthValue
			 }

		vapIndex OBJECT-TYPE
			SYNTAX INTEGER (1..16)
			MAX-ACCESS read-only
			STATUS current
			DESCRIPTION
				"Description."
			::= { vapSettingEntry 1 }

		
		vapEnable OBJECT-TYPE
			SYNTAX TruthValue
			MAX-ACCESS read-write
			STATUS current
			DESCRIPTION
				"This attribute shall indicate whether enable VAP.
				"
			::= { vapSettingEntry 2 }

		
		ssid OBJECT-TYPE
			SYNTAX DisplayString (SIZE (0..32))
			MAX-ACCESS read-write
			STATUS current
			DESCRIPTION
				"This attribute shall indicate SSID.Its length can't be large than 33 ."
			::= { vapSettingEntry 3 }

		
		hidenetworkname OBJECT-TYPE
			SYNTAX TruthValue
			MAX-ACCESS read-write
			STATUS current
			DESCRIPTION
				"This attribute shall indicate whether broadcast wireless network Name (SSID)."
			::= { vapSettingEntry 4 }

		
		vlanID OBJECT-TYPE
			SYNTAX INTEGER (1..4094)
			MAX-ACCESS read-write
			STATUS current
			DESCRIPTION
				"This attribute shall indicate the VLAN ID. "
			::= { vapSettingEntry 5 }

		
		securityProfileName OBJECT-TYPE
			SYNTAX DisplayString (SIZE (1..32))
			MAX-ACCESS read-write
			STATUS current
			DESCRIPTION
				"Description."
			::= { vapSettingEntry 6 }

		
		presharekey OBJECT-TYPE
			SYNTAX DisplayString (SIZE (0..63))
			MAX-ACCESS read-write
			STATUS current
			DESCRIPTION
				"This attribute shall indicate preshare key."
			::= { vapSettingEntry 7 }

		
		authenticationtype OBJECT-TYPE
			SYNTAX INTEGER
				{
				open(0),
				shared(1),
				legacy802dot1x(2),
				wpa(4),
				wpa2(8),
				wpaORwpa2(12),
				wpapsk(16),
				wpa2psk(32),
				wpapskORwpa2psk(48)
				}
			MAX-ACCESS read-write
			STATUS current
			DESCRIPTION
				"The field indicates how to authenticate the station."
			::= { vapSettingEntry 8 }

		
		encryption OBJECT-TYPE
			SYNTAX INTEGER
				{
				none(0),
				wep(1),
				tkip(2),
				aes(4),
				tkipORaes(6)
				}
			MAX-ACCESS read-write
			STATUS current
			DESCRIPTION
				"The field indicates how to encryption the station."
			::= { vapSettingEntry 9 }

		
		keyno OBJECT-TYPE
			SYNTAX INTEGER (1..4)
			MAX-ACCESS read-write
			STATUS current
			DESCRIPTION
				"The field indicates the number of default wep key."
			::= { vapSettingEntry 10 }

		
		wlanseparator OBJECT-TYPE
			SYNTAX TruthValue
			MAX-ACCESS read-write
			STATUS current
			DESCRIPTION
				"This attribute shall indicate whether enable No see."
			::= { vapSettingEntry 11 }      

			
--  *********************************************************
-- Remote Settings Information
-- *********************************************************
		remoteSettings OBJECT IDENTIFIER ::= { wag302 4 }

		
		sshd OBJECT-TYPE
			SYNTAX TruthValue
			MAX-ACCESS read-write
			STATUS current
			DESCRIPTION
				"This attribute shall indicate whether the SSH is enabled."
			::= { remoteSettings 1 }

		
		snmpenable OBJECT-TYPE
			SYNTAX TruthValue
			MAX-ACCESS read-only
			STATUS current
			DESCRIPTION
				"This attribute shall indicate whether the SNMP agent is
				enabled."
			::= { remoteSettings 2 }

		
		trapServerIP OBJECT-TYPE
			SYNTAX IpAddress
			MAX-ACCESS read-write
			STATUS current
			DESCRIPTION
				"The field indicates the  trap server IP address.
				***The value can only be set to an IP address in dot
				format."
			::= { remoteSettings 3 }
 
               trapServerCommunity OBJECT-TYPE
                        SYNTAX DisplayString (SIZE (1..31))
                        MAX-ACCESS read-write
                        STATUS current
                        DESCRIPTION
                                "The field indicates the community name for traps."
                        ::= { remoteSettings 4 }


		
		readOnlyCommunity OBJECT-TYPE
			SYNTAX DisplayString (SIZE (1..31))
			MAX-ACCESS read-write
			STATUS current
			DESCRIPTION
				"The field indicates the  read only community name.
				***The value can only be set to 1 to 32 readable string."
			::= { remoteSettings 5 }

		
		readWriteCommunity OBJECT-TYPE
			SYNTAX DisplayString (SIZE (1..31))
			MAX-ACCESS read-write
			STATUS current
			DESCRIPTION
				"The field indicates the  read write community name.
				***The value can only be set to 1 to 32 readable string."
			::= { remoteSettings 6 }

	
--  ***********************************************************************
-- *Statistic
-- ***********************************************************************
		statistic OBJECT IDENTIFIER ::= { wag302 5 }

		
		wiredethernetstat OBJECT IDENTIFIER ::= { statistic 1 }

		
		lanrecvpacket OBJECT-TYPE
			SYNTAX Unsigned32
			MAX-ACCESS read-only
			STATUS current
			DESCRIPTION
				"the field indicates the sum of received packets."
			::= { wiredethernetstat 1 }

		
		lantranspacket OBJECT-TYPE
			SYNTAX Unsigned32
			MAX-ACCESS read-only
			STATUS current
			DESCRIPTION
				"the field indicates the sum of transmitted packets."
			::= { wiredethernetstat 2 }

		
		lanrecvbytes OBJECT-TYPE
			SYNTAX Unsigned32
			MAX-ACCESS read-only
			STATUS current
			DESCRIPTION
				"the field indicates the sum of received bytes."
			::= { wiredethernetstat 3 }

		
		lantransbytes OBJECT-TYPE
			SYNTAX Unsigned32
			MAX-ACCESS read-only
			STATUS current
			DESCRIPTION
				"the field indicates the sum of transmitted bytes."
			::= { wiredethernetstat 4 }

		
		wirelessStatTable OBJECT-TYPE
			SYNTAX SEQUENCE OF WirelessStatEntry
			MAX-ACCESS not-accessible
			STATUS current
			DESCRIPTION
				"Description."
			::= { statistic 2 }

		
		wirelessStatEntry OBJECT-TYPE
			SYNTAX WirelessStatEntry
			MAX-ACCESS not-accessible
			STATUS current
			DESCRIPTION
				"Description."
			INDEX { ifIndex }
			::= { wirelessStatTable 1 }

		
		WirelessStatEntry ::=
			SEQUENCE { 
				wlanrecvunicastpacket
					Unsigned32,
				wlantransunicastpacket
					Unsigned32,
				wlanrecvbroadcastpacket
					Unsigned32,
				wlantransbroadcastpacket
					Unsigned32,
				wlanrecvmulticastpacket
					Unsigned32,
				wlantransmulticastpacket
					Unsigned32,
				wlanrecvpacket
					Unsigned32,
				wlantranspacket
					Unsigned32,
				wlanrecvbytes
					Unsigned32,
				wlantransbytes
					Unsigned32
			 }

		wlanrecvunicastpacket OBJECT-TYPE
			SYNTAX Unsigned32
			MAX-ACCESS read-only
			STATUS current
			DESCRIPTION
				"the field indicates the sum of received unicast packets."
			::= { wirelessStatEntry 1 }

		
		wlantransunicastpacket OBJECT-TYPE
			SYNTAX Unsigned32
			MAX-ACCESS read-only
			STATUS current
			DESCRIPTION
				"the field indicates the sum of transmitted unicast packets."
			::= { wirelessStatEntry 2 }

		
		wlanrecvbroadcastpacket OBJECT-TYPE
			SYNTAX Unsigned32
			MAX-ACCESS read-only
			STATUS current
			DESCRIPTION
				"the field indicates the sum of received broadcast packets."
			::= { wirelessStatEntry 3 }

		
		wlantransbroadcastpacket OBJECT-TYPE
			SYNTAX Unsigned32
			MAX-ACCESS read-only
			STATUS current
			DESCRIPTION
				"the field indicates the sum of transmitted broadcast packets."
			::= { wirelessStatEntry 4 }

		
		wlanrecvmulticastpacket OBJECT-TYPE
			SYNTAX Unsigned32
			MAX-ACCESS read-only
			STATUS current
			DESCRIPTION
				"the field indicates the sum of received multicast packets."
			::= { wirelessStatEntry 5 }

		
		wlantransmulticastpacket OBJECT-TYPE
			SYNTAX Unsigned32
			MAX-ACCESS read-only
			STATUS current
			DESCRIPTION
				"the field indicates the sum of transmitted multicast packets."
			::= { wirelessStatEntry 6 }

		
		wlanrecvpacket OBJECT-TYPE
			SYNTAX Unsigned32
			MAX-ACCESS read-only
			STATUS current
			DESCRIPTION
				"the field indicates the sum of received packets."
			::= { wirelessStatEntry 7 }

		
		wlantranspacket OBJECT-TYPE
			SYNTAX Unsigned32
			MAX-ACCESS read-only
			STATUS current
			DESCRIPTION
				"the field indicates the sum of transmitted packets."
			::= { wirelessStatEntry 8 }

		
		wlanrecvbytes OBJECT-TYPE
			SYNTAX Unsigned32
			MAX-ACCESS read-only
			STATUS current
			DESCRIPTION
				"the field indicates the sum of received bytes."
			::= { wirelessStatEntry 9 }

		
		wlantransbytes OBJECT-TYPE
			SYNTAX Unsigned32
			MAX-ACCESS read-only
			STATUS current
			DESCRIPTION
				"the field indicates the sum of transmitted bytes."
			::= { wirelessStatEntry 10 }
	
	
--   **********************************************************************
-- *  Station List Table
-- **********************************************************************
			stationListTable OBJECT-TYPE
			SYNTAX SEQUENCE OF StationListEntry
			MAX-ACCESS not-accessible
			STATUS current
			DESCRIPTION
				"stationList Table show multiple instances on an agent."
			::= { wag302  6 }

		
		stationListEntry OBJECT-TYPE
			SYNTAX StationListEntry
			MAX-ACCESS not-accessible
			STATUS current
			DESCRIPTION
				"An entry in the wlanClientsTable. It is possible for there
				to be multiple AP interfaces on one agent, each with its
				unique MAC address. The relationship between an AP
				interface and an interface in the context of the Internet-
				standard MIB is one-to-one. As such, the value of an
				ifIndex object instance can be directly used to identify
				corresponding instances of the objects defined herein. "
			INDEX { ifIndex, macaddress }
			::= { stationListTable 1 }

		
		StationListEntry ::=
			SEQUENCE { 
				macaddress
					MacAddress,
				clientIpaddr
					IpAddress,
				clientWirelessMode
					INTEGER,
				stationstatus
					INTEGER
			 }

		
		macaddress OBJECT-TYPE
			SYNTAX MacAddress
			MAX-ACCESS read-only
			STATUS current
			DESCRIPTION
				"This attribute shall indicate MAC address of the
				associated stationID."
			::= { stationListEntry 1 }

		
		clientIpaddr OBJECT-TYPE
			SYNTAX IpAddress
			MAX-ACCESS read-only
			STATUS current
			DESCRIPTION
				"This attribute shall indicate Ip address of the associated stationID."
			::= { stationListEntry 2 }

		
		clientWirelessMode OBJECT-TYPE
			SYNTAX INTEGER
				{
				dot11a(1),
				dot11b(2),
				dot11g(3)
				}
			MAX-ACCESS read-only
			STATUS current
			DESCRIPTION
				"This attribute shall indicate the wireless mode of the
				associated stationID."
			::= { stationListEntry 3 }

		
		stationstatus OBJECT-TYPE
			SYNTAX INTEGER
				{
				none(0),
				authenticating(1),
				authenticated(2),
				associating(3),
				associated(4)
				}
			MAX-ACCESS read-only
			STATUS current
			DESCRIPTION
				"This attribute shall indicate the status of station."
			::= { stationListEntry 4 }


--  *********************************************************
-- AP Operation Mode
-- *********************************************************
-- ap mode
               wlanWdsTable OBJECT-TYPE
			SYNTAX SEQUENCE OF WlanWdsEntry
			MAX-ACCESS not-accessible
			STATUS current
			DESCRIPTION
				"WDS attributes in tablular form to allow for multiple
				instances on an agent."
			::= { wag302 7}

		
		wlanWdsEntry OBJECT-TYPE
			SYNTAX WlanWdsEntry
			MAX-ACCESS not-accessible
			STATUS current
			DESCRIPTION
				"An entry in the wlanWdsTable. It is possible for there to
				be multiple AP interfaces on one agent, each with its
				unique MAC address. The relationship between an AP
				interface and an interface in the context of the Internet-
				standard MIB is one-to-one. As such, the value of an
				ifIndex object instance can be directly used to identify
				corresponding instances of the objects defined herein. "
			INDEX { ifIndex }
			::= { wlanWdsTable 1 }

		
		WlanWdsEntry ::=
			SEQUENCE { 
				apmode
					INTEGER,
				ptpremotemacaddress
					MacAddress,
				pxpremotemacaddress1
					MacAddress,
				pxpremotemacaddress2
					MacAddress,
				pxpremotemacaddress3
					MacAddress,
				pxpremotemacaddress4
					MacAddress,
				repremotemacaddress1
					MacAddress,
				repremotemacaddress2
					MacAddress,
				repremotemacaddress3
					MacAddress,
				repremotemacaddress4
					MacAddress,
			        localMacAddress
					MacAddress   
        }


		apmode OBJECT-TYPE
			SYNTAX INTEGER
				{
				ap(0),
				ptp(2),
				ptp-ap(3),
				pxp(4),
				pxp-ap(5),
				repeater(6)
				}
			MAX-ACCESS read-only
			STATUS current
			DESCRIPTION
				"This a command field for conntrol AP operation mode. "
			::= { wlanWdsEntry 1 }

		
		ptpremotemacaddress OBJECT-TYPE
			SYNTAX MacAddress
			MAX-ACCESS read-write
			STATUS current
			DESCRIPTION
				"This attribute shall indicate the stationID."
			::= { wlanWdsEntry 2 }

		
		pxpremotemacaddress1 OBJECT-TYPE
			SYNTAX MacAddress
			MAX-ACCESS read-write
			STATUS current
			DESCRIPTION
				"This attribute shall indicate the stationID."
			::= { wlanWdsEntry 3 }

		
		pxpremotemacaddress2 OBJECT-TYPE
			SYNTAX MacAddress
			MAX-ACCESS read-write
			STATUS current
			DESCRIPTION
				"This attribute shall indicate the stationID."
			::= { wlanWdsEntry 4 }

		
		pxpremotemacaddress3 OBJECT-TYPE
			SYNTAX MacAddress
			MAX-ACCESS read-write
			STATUS current
			DESCRIPTION
				"This attribute shall indicate the stationID."
			::= { wlanWdsEntry 5 }

		
		pxpremotemacaddress4 OBJECT-TYPE
			SYNTAX MacAddress
			MAX-ACCESS read-write
			STATUS current
			DESCRIPTION
				"This attribute shall indicate the stationID."
			::= { wlanWdsEntry 6 }

		
		repremotemacaddress1 OBJECT-TYPE
			SYNTAX MacAddress
			MAX-ACCESS read-write
			STATUS current
			DESCRIPTION
				"This attribute shall indicate the stationID."
			::= { wlanWdsEntry 7 }

		
		repremotemacaddress2 OBJECT-TYPE
			SYNTAX MacAddress
			MAX-ACCESS read-write
			STATUS current
			DESCRIPTION
				"This attribute shall indicate the stationID."
			::= { wlanWdsEntry 8 }

		
		repremotemacaddress3 OBJECT-TYPE
			SYNTAX MacAddress
			MAX-ACCESS read-write
			STATUS current
			DESCRIPTION
				"This attribute shall indicate the stationID."
			::= { wlanWdsEntry 9 }

		
		repremotemacaddress4 OBJECT-TYPE
			SYNTAX MacAddress
			MAX-ACCESS read-write
			STATUS current
			DESCRIPTION
				"This attribute shall indicate the stationID."
			::= { wlanWdsEntry 10 }

                 localMacAddress OBJECT-TYPE
			SYNTAX MacAddress
			MAX-ACCESS read-only
			STATUS current
			DESCRIPTION
				"This attribute shall indicate the local MAC Address."
			::= { wlanWdsEntry 11 }

--  *********************************************************
-- 802.1x Information
-- *********************************************************
	info802dot1x OBJECT IDENTIFIER ::= { wag302 8 }

		
		authinfo OBJECT IDENTIFIER ::= { info802dot1x 1 }

		
		priradipaddr OBJECT-TYPE
			SYNTAX IpAddress
			MAX-ACCESS read-write
			STATUS current
			DESCRIPTION
				"Internet address of the Primary Radius Server."
			::= { authinfo 1 }

		
		priradport OBJECT-TYPE
			SYNTAX INTEGER (0..65535)
			MAX-ACCESS read-write
			STATUS current
			DESCRIPTION
				"Port number used for authentication at the
				Primary Radius Server."
			::= { authinfo 2 }

		
		priradsharedsecret OBJECT-TYPE
			SYNTAX DisplayString (SIZE (0..127))
			MAX-ACCESS read-write
			STATUS current
			DESCRIPTION
				"Secret shared between NAS and the Primary Radius Server."
			::= { authinfo 3 }		
		
		sndradipaddr OBJECT-TYPE
			SYNTAX IpAddress
			MAX-ACCESS read-write
			STATUS current
			DESCRIPTION
				"Internet address of the Second Radius Server."
			::= { authinfo 4 }

		sndradport OBJECT-TYPE
			SYNTAX INTEGER (0..65535)
			MAX-ACCESS read-write
			STATUS current
			DESCRIPTION
			"Port number used for authentication at
				the Second Radius Server."
			::= { authinfo 5 }

		
		sndradsharedsecret OBJECT-TYPE
			SYNTAX DisplayString (SIZE (0..127))
			MAX-ACCESS read-write
			STATUS current
			DESCRIPTION
				"Secret shared between NAS and the Second Radius Server."
			::= { authinfo 6 }

		
                --    The primary account RADIUS server setting.
		accntinfo OBJECT IDENTIFIER ::= { info802dot1x 2 }

		
		priacntipaddr OBJECT-TYPE
			SYNTAX IpAddress
			MAX-ACCESS read-write
			STATUS current
			DESCRIPTION
				"IP address of the Primary radius account server."
			::= { accntinfo 1 }

		
		priacntport OBJECT-TYPE
			SYNTAX INTEGER (0..65535)
			MAX-ACCESS read-write
			STATUS current
			DESCRIPTION
				"port number of the Primary radius account server."
			::= { accntinfo 2 }

		
		priacntsharedsecret OBJECT-TYPE
			SYNTAX DisplayString (SIZE (0..127))
			MAX-ACCESS read-write
			STATUS current
			DESCRIPTION
				"password used by the ap to connect to the Primary radius account serve."
			::= { accntinfo 3 }
		
		sndacntipaddr OBJECT-TYPE
			SYNTAX IpAddress
			MAX-ACCESS read-write
			STATUS current
			DESCRIPTION
				"IP address of the Second radius account server."
			::= { accntinfo 4 }

		
		sndacntport OBJECT-TYPE
			SYNTAX INTEGER (0..65535)
			MAX-ACCESS read-write
			STATUS current
			DESCRIPTION
				"port number of the Second radius account server."
			::= { accntinfo 5 }

		
		sndacntsharedsecret OBJECT-TYPE
			SYNTAX DisplayString (SIZE (0..127))
			MAX-ACCESS read-write
			STATUS current
			DESCRIPTION
				"password used by the ap to connect to the Second radius account server."
			::= { accntinfo 6 }


--  acntcurloginstat 	OBJECT-TYPE
-- SYNTAX TruthValue
-- MAX-ACCESS read-write
-- STATUS current
-- DESCRIPTION
-- 	"Current Login Status."
-- ::= { accntinfo 7 }
-- *********************************************************
-- Command Information
-- *********************************************************
-- Command information
          userCommand OBJECT IDENTIFIER ::= { wag302 9 }

		
		resetAP OBJECT-TYPE
			SYNTAX INTEGER
			MAX-ACCESS read-write
			STATUS current
			DESCRIPTION
				"This a command field for conntrol AP action. Write value 1
				 to reset the AP."
			::= { userCommand 1 }


--   **********************************************************************
-- *  System Basic Setting  Table 2005/12/22
-- ********************************************************************
         timeSettings OBJECT IDENTIFIER ::= { wag302 10 }

		
		currenttime OBJECT-TYPE
			SYNTAX DisplayString (SIZE (1..20))
			MAX-ACCESS read-only
			STATUS current
			DESCRIPTION
				"This field indicates the current system time in a format:
				YYYY/MM/DD hh:mm:ss."
			::= { timeSettings 1 }

		
		timezone OBJECT-TYPE
			SYNTAX INTEGER
			{
			afghanistan(0),  
			albania(1),  
			algeria(2),  
			american-samoa(3),
			andorra(4),  
			angola(5),  
			anguilla(6),  
			antigua-and-barbuda(7),
			argentina(8),  
			armenia(9),  
			aruba(10),
			australia-lordHoweIsland(11),
			australia-new-south-wales-capitol-territory-victoria(12),
			australia-northern-territory(13),
			australia-queensland(14),
			australia-south-australia-and-broken-hill(15),
			australia-tasmania(16),
			australia-western(17),
			austria(18),  
			azerbaijan(19),  
			bahamas(20),  
			bahrain(21),  
			bangladesh(22),  
			barbados(23),  
			belarus(24),  
			belgium(25),
			belize(26),  
			benin(27),  
			bermuda(28),  
			bhutan(29),  
			bolivia(30),  
			bonaire(31),  
			bosnia-herzegovina(32),
			botswana(33),  
			brazil-east-including-all-coast-and-brasilia(34),
			brazil-fernando-de-noronha(35),  
			brazil-trinity-of-acre(36),  
			brazil-west(37),
			british-virgin-islands(38),  
			brunei(39),  
			bulgaria(40),  
			burkina-faso(41),
			burma(42),  
			burundi(43),  
			cambodia(44),  
			cameroon(45),  
			canada-atlantic(46),
			canada-central(47),
			canada-eastern(48),
			canada-mountain(49),
			canada-newfoundland(50),
			canada-pacific-and-yukon(51),
			canada-saskatchewan(52),
			cape-verde(53),
			cayman-islands(54),
			central-african-republic(55),
			chad(56),  
			chile(57),  
			chile-easter-island(58),
			china(59),  
			christmas-islands(60),
			cocos-keeling-islands(61),
			colombia(62),  
			congo(63),  
			cook-islands(64),
			costa-rica(65),
			cote-d-ivoire(66),  
			croatia(67),
			cuba(68),  
			curacao(69),  
			cyprus(70),  
			czech-republic(71),
			denmark(72),  
			djibouti(73),  
			dominica(74),  
			the-dominican-republic(75),
			ecuador(76),  
			ecuador-galapagos-islands(77),
			egypt(78),  
			el-salvador(79),
			equatorial-guinea(80),
			eritrea(81),  
			estonia(82),  
			ethiopia(83),  
			faroe-islands(84),
			fiji(85),  
			finland(86),  
			france(87),  
			french-guiana(88),
			french-polynesia(89),
			gabon(90),  
			the-gambia(91),
			georgia(92),  
			germany(93),  
			ghana(94),  
			gibraltar(95),  
			greece(96),  
			greenland-scorsbysund(97),
			greenland-thule(98),
			grenada(99),  
			guadeloupe(100),  
			guam(101),  
			guatemala(102),  
			guinea-bissau(103),
			guyana(104),  
			haiti(105),  
			hawaii(106),  
			honduras(107),  
			hong-kong(108),
			hungary(109),  
			iceland(110),  
			india(111),  
			indonesia-central(112),
			indonesia-east(113),
			indonesia-west(114),
			iran(115),  
			iraq(116),  
			ireland(117),  
			israel(118),  
			italy(119),  
			jamaica(120),  
			japan(121),  
			johnston-islands(122),
			jordan(123),  
			juan-fernandez-islands(124),
			kazakhstan(125),  
			kenya(126),  
			kiribati(127),  
			kuwait(128),  
			kyrgyzstan(129),  
			laos(130),  
			latvia(131),  
			lebanon(132)  
			leeward-islands(133),
			lesotho(134),  
			liberia(135),  
			libya(136),  
			liechtenstein(137),  
			lithuania(138),  
			luxembourg(139),  
			macao(140),  
			macedonia(141),
			madagascar(142),  
			malawi(143),  
			malaysia(144),  
			maldives(145),  
			mali(146),  
			malta(147),  
			mariana-Islands(148),
			martinique(149),  
			mauritania(150),  
			mauritius(151),  
			mayotte(152),  
			mexico(153),  
			mexico-baj-n(154),
			mexico-baj-s(155),
			midway-islands(156),
			moldova(157),  
			monaco(158),  
			mongolia(159),  
			montenegro(160),  
			montserrat(161),  
			morocco(162),  
			mozambique(163),  
			namibia(164),  
			nauru(165),  
			nepal(166),  
			the-netherlands-antilles(167),
			the-netherlands(168),
			new-caledonia(169),
			new-hebrides(170),
			new-zealand9(171),
			new-zealand-chatham-island(172),
			nicaragua(173),  
			niger(174),  
			nigeria(175),  
			niue-islands(176),
			norfolk-island(177),
			north-korea(178),
			norway(179),  
			oman(180),  
			pakistan(181),  
			palau(182),  
			panama(183),  
			papua-new-guinea(184),
			paraguay(185),  
			peru(186),  
			philippines(187),  
			pitcairn-island(188),
			poland(189),  
			portugal-azores(190),
			portugal-madeira(191),
			puerto-rico(192),
			qatar(193),  
			reunion(194),  
			romania(195),  
			russia-moscow(196),
			russian-fed-zone-1-kaliningrad(197),
			russian-fed-zone-10-magadan(198),
			russian-fed-zone-11-petropavlovsk-kamchatsky(199),
			russian-fed-zone-2-st-petersburg(200),
			russian-fed-zone-3-izhevsk(201),
			russian-fed-zone-4-ekaterinburg(202),
			russian-fed-zone-5-novosibirsk(203),
			russian-fed-zone-6-krasnojarsk(204),
			russian-fed-zone-7-irkutsk(205),
			russian-fed-zone-8-yakatsk(206),
			russian-fed-zone-9-vladivostok(207),
			rwanda(208),  
			saint-pierre-and-miquelon(209),
			san-marino(210),
			sao-tome-and-principe(211),
			saudi-arabia(212),
			senegal(213),  
			serbia(214),
			the-seychelles(215),
			sierra-leone(216),
			singapore(217),  
			slovakia(218),  
			slovenia(219),  
			solomon-islands(220),
			somalia(221),  
			south-africa(222),
			south-georgia(223),
			south-korea(224),
			spain(225),  
			spain-canary-islands(226),
			sri-lanka(227),
			st-helena(228),
			st-kitts-nevis(229),
			st-lucia(230),
			st-vincent-and-the-grenadines(231),
			sudan(232),  
			suriname(233),  
			swaziland(234),  
			sweden(235),  
			switzerland(236), 
			syria(237),  
			tahiti(238),  
			taiwan(239),  
			tajikistan(240),
			tanzania(241),  
			thailand(242),  
			togo(243),  
			tonga(244),  
			trinidad-and-tobago(245),
			tunisia(246),
			turkey(247),  
			turkmenistan(248),  
			turks-and-caicos-islands(249),
			tuvalu(250),  
			uganda(251),  
			ukraine(252),  
			ukraine-simferopol(253),
			united-arab-emirates(254),
			united-kingdom(255),
			uruguay(256),  
			us-virgin-islands(257),
			usa-alaska(258),
			usa-aleutian-islands(259)
			usa-arizona(260),
			usa-central(261),
			usa-eastern(262),
			usa-indiana(263),
			usa-mountain(264),
			usa-pacific(265),
			uzbekistan(266),  
			vanuatu(267),  
			vatican-city(268),
			venezuela(269),  
			vietnam(270),  
			wake-islands(271),
			wallis-and-futana-islands(272),
			western-samoa(273),
			windward-islands(274),
			yemen(275),  
			zaire-kasai(276),
			zaire-kinshasa(277),
			zambia(278),
			zimbabwe(279)   			
			}
			MAX-ACCESS read-write
			STATUS current
			DESCRIPTION
				"This field indicates the timezone of the system."
			::= { timeSettings 2 }

		
		daylightsaving OBJECT-TYPE
			SYNTAX TruthValue
			MAX-ACCESS read-write
			STATUS current
			DESCRIPTION
				"This attribute shall indicate the Daylight Saving time."
			::= { timeSettings 3 }


--   **********************************************************************
-- *  DHCP Server Setting  Table 2004/6/17
-- **********************************************************************
         dhcpsSettings OBJECT IDENTIFIER ::= { wag302 11 }

		
		dhcpserver OBJECT-TYPE
			SYNTAX TruthValue
			MAX-ACCESS read-write
			STATUS current
			DESCRIPTION
				"This attribute shall indicate whether DHCP server is enable
				or disable."
			::= { dhcpsSettings 1 }

		
		dhcpsipstart OBJECT-TYPE
			SYNTAX IpAddress
			MAX-ACCESS read-write
			STATUS current
			DESCRIPTION
				"This attribute indicates the starting IP address of DHCP server will give.
				***The value can only be set to a IP address in dot format."
			::= { dhcpsSettings 2 }

		
		dhcpsipend OBJECT-TYPE
			SYNTAX IpAddress
			MAX-ACCESS read-write
			STATUS current
			DESCRIPTION
				"This attribute indicates the ending IP address of DHCP server will give.
				***The value can only be set to a IP address in dot format."
			::= { dhcpsSettings 3 }

		
		dhcpnetmask OBJECT-TYPE
			SYNTAX IpAddress
			MAX-ACCESS read-write
			STATUS current
			DESCRIPTION
					"This attribute indicates the net mask of DHCP server will give.
				***The value can only be set to the net mask address in dot format."
			::= { dhcpsSettings 4 }

		
		dhcpsgateway OBJECT-TYPE
			SYNTAX IpAddress
			MAX-ACCESS read-write
			STATUS current
			DESCRIPTION
				"This attribute indicates the gateway IP address of DHCP server will give.
				***The value can only be set to a IP address in dot format."
			::= { dhcpsSettings 5 }

		
		dhcpspridns OBJECT-TYPE
			SYNTAX IpAddress
			MAX-ACCESS read-write
			STATUS current
			DESCRIPTION
				"This attribute indicates the primary DNS IP address of DHCP server will give.
				***The value can only be set to a IP address in dot format."
			::= { dhcpsSettings 6 }

		dhcpspsnddns OBJECT-TYPE
			SYNTAX IpAddress
			MAX-ACCESS read-write
			STATUS current
			DESCRIPTION
				"This attribute indicates the secondary DNS IP address of DHCP server will give.
				***The value can only be set to a IP address in dot format."
			::= { dhcpsSettings 7 }

		
        	dhcpspriwins OBJECT-TYPE
			SYNTAX IpAddress
			MAX-ACCESS read-write
			STATUS current
			DESCRIPTION
				"This attribute indicates the primary WINS IP address of DHCP server will give.
				***The value can only be set to a IP address in dot format."
			::= { dhcpsSettings 8 }

		
		dhcpspsndwins OBJECT-TYPE
			SYNTAX IpAddress
			MAX-ACCESS read-write
			STATUS current
			DESCRIPTION
				"This attribute indicates the secondary WINS IP address of DHCP server will give.
				***The value can only be set to a IP address in dot format."
			::= { dhcpsSettings 9 }

		
		dhcpsleasetime OBJECT-TYPE
			SYNTAX INTEGER (15..44640)
			MAX-ACCESS read-write
			STATUS current
			DESCRIPTION
				"This attribute shall indicate the IP lease time of DHCP server will give
				to DHCP clients in minutes"
			::= { dhcpsSettings 10 }




--   **********************************************************************
-- *  SYSLOG Server Setting  Table 2004/8/2
-- **********************************************************************
		logSettings OBJECT IDENTIFIER ::= { wag302 12 }

		
		syslog OBJECT-TYPE
			SYNTAX TruthValue
			MAX-ACCESS read-write
			STATUS current
			DESCRIPTION
				"This attribute shall indicate whether syslog is enable 
				or disable."
			::= { logSettings 1 }

		
		syslogsrvip OBJECT-TYPE
			SYNTAX IpAddress
			MAX-ACCESS read-write
			STATUS current
			DESCRIPTION
				"This attributes shall indicates the IP address of the syslog server.
				***The value can only be set to a IP address in dot format."
			::= { logSettings 2 }

		
		syslogsrvport OBJECT-TYPE
			SYNTAX INTEGER (0..65535)
			MAX-ACCESS read-write
			STATUS current
			DESCRIPTION
				"This attributes shall indicates the Port of the Syslog server.
				*** The value can only be set to a port in dot format."
			::= { logSettings 3 }      

--   **********************************************************************
-- *  HTTP Redirect Settings Table
-- **********************************************************************

			
    
       httpRedirectSettings OBJECT IDENTIFIER ::= { wag302 13 }

		
		httpRedirectEnable OBJECT-TYPE
			SYNTAX TruthValue
			MAX-ACCESS read-write
			STATUS current
			DESCRIPTION
				"Description."
			::= { httpRedirectSettings 1 }

		
		httpRedirectURL OBJECT-TYPE
			SYNTAX DisplayString (SIZE (0..119))
			MAX-ACCESS read-write
			STATUS current
			DESCRIPTION
				"Description."
			::= { httpRedirectSettings 2 }			 	
						
		

--   **********************************************************************
-- *  Detected AP Table
-- **********************************************************************
		detectedApTable OBJECT-TYPE
			SYNTAX SEQUENCE OF DetectedApEntry
			MAX-ACCESS not-accessible
			STATUS current
			DESCRIPTION
				"detectedAp Table shows list of detected neighbouring APs."
			::= { wag302 14 }


	        detectedApEntry OBJECT-TYPE
			SYNTAX DetectedApEntry
			MAX-ACCESS not-accessible
			STATUS current
			DESCRIPTION
				"An entry in the detectedApTable."
			INDEX { apmac }
			::= { detectedApTable 1 }

		
		DetectedApEntry ::=
			SEQUENCE { 
				apmac
					MacAddress,
				apssid
					DisplayString,
				apprivacy
					TruthValue,
				apband
					DisplayString,
				apchannel
					INTEGER,
				aprate
					INTEGER,
				apbeaconInterval
					INTEGER,
				apnumBeacons
					INTEGER,
				aplastBeacon
					INTEGER
			 }

		
		apmac OBJECT-TYPE
			SYNTAX MacAddress
			MAX-ACCESS read-only
			STATUS current
			DESCRIPTION
				"This attribute shall indicate MAC address of the
				detected AP."
			::= { detectedApEntry 1 }

		
		apssid  OBJECT-TYPE
			SYNTAX DisplayString
			MAX-ACCESS read-only
			STATUS current
			DESCRIPTION
				"This attribute shall indicate ssid of the detected AP."
			::= { detectedApEntry 2 }

		
		apprivacy OBJECT-TYPE
			SYNTAX TruthValue
			MAX-ACCESS read-only
			STATUS current
			DESCRIPTION
				"This attribute shall indicate whether privacy is enabled."
			::= { detectedApEntry 3 }

		
		apband    OBJECT-TYPE
			SYNTAX DisplayString
			MAX-ACCESS read-only
			STATUS current
			DESCRIPTION
				"This attribute shall indicate the operating band of detected AP."
			::= { detectedApEntry 4 }


		apchannel OBJECT-TYPE
			SYNTAX INTEGER
			MAX-ACCESS read-only
			STATUS current
			DESCRIPTION
				"This attribute shall indicate the channel number used."
			::= { detectedApEntry 5 }

		
		aprate    OBJECT-TYPE
			SYNTAX INTEGER
			MAX-ACCESS read-only
			STATUS current
			DESCRIPTION
				"This attribute shall indicate the rate."
			::= { detectedApEntry 6 }

		
		apbeaconInterval OBJECT-TYPE
			SYNTAX INTEGER
			MAX-ACCESS read-only
			STATUS current
			DESCRIPTION
				"This attribute shall indicate the beacon interval in kus (1.024 ms)."
			::= { detectedApEntry 7 }

		
		apnumBeacons    OBJECT-TYPE
			SYNTAX INTEGER
			MAX-ACCESS read-only
			STATUS current
			DESCRIPTION
				"This attribute shall indicate the number of beacons received."
			::= { detectedApEntry 8 }


		aplastBeacon    OBJECT-TYPE
			SYNTAX INTEGER
			MAX-ACCESS read-only
			STATUS current
			DESCRIPTION
				"This attribute shall indicate the time of the last beacon." 
			::= { detectedApEntry 9 }


		
--   **********************************************************************
-- *  Known AP Table
-- **********************************************************************
		knownApTable OBJECT-TYPE
			SYNTAX SEQUENCE OF KnownApEntry
			MAX-ACCESS not-accessible
			STATUS current
			DESCRIPTION
				"knownAp Table shows list of known APs."
			::= { wag302 15 }


	        knownApEntry OBJECT-TYPE
			SYNTAX KnownApEntry
			MAX-ACCESS not-accessible
			STATUS current
			DESCRIPTION
				"An entry in the knownApTable."
			INDEX { knownapmac }
			::= { knownApTable 1 }

		
		KnownApEntry ::=
			SEQUENCE { 
				knownapmac
					MacAddress,
				knownapssid
					DisplayString,
				knownapprivacy
					TruthValue,
				knownapband
					DisplayString,
				knownapchannel
					INTEGER,
				knownaprate
					INTEGER,
				knownapbeaconInterval
					INTEGER,
				knownapnumBeacons
					INTEGER,
				knownaplastBeacon
					INTEGER,
                knownapEntryStatus
                    RowStatus               
			 }

		
		knownapmac OBJECT-TYPE
			SYNTAX MacAddress
			MAX-ACCESS read-only
			STATUS current
			DESCRIPTION
				"This attribute shall indicate MAC address of the
				known AP."
			::= { knownApEntry 1 }

		
		knownapssid  OBJECT-TYPE
			SYNTAX DisplayString
			MAX-ACCESS read-only
			STATUS current
			DESCRIPTION
				"This attribute shall indicate ssid of the known AP."
			::= { knownApEntry 2 }

		
		knownapprivacy OBJECT-TYPE
			SYNTAX TruthValue
			MAX-ACCESS read-only
			STATUS current
			DESCRIPTION
				"This attribute shall indicate whether privacy is enabled."
			::= { knownApEntry 3 }

		
		knownapband OBJECT-TYPE
			SYNTAX DisplayString
			MAX-ACCESS read-only
			STATUS current
			DESCRIPTION
				"This attribute shall indicate the operating band of known AP."
			::= { knownApEntry 4 }


		knownapchannel OBJECT-TYPE
			SYNTAX INTEGER
			MAX-ACCESS read-only
			STATUS current
			DESCRIPTION
				"This attribute shall indicate the channel number used."
			::= { knownApEntry 5 }

		
		knownaprate OBJECT-TYPE
			SYNTAX INTEGER
			MAX-ACCESS read-only
			STATUS current
			DESCRIPTION
				"This attribute shall indicate the rate."
			::= { knownApEntry 6 }

		
		knownapbeaconInterval OBJECT-TYPE
			SYNTAX INTEGER
			MAX-ACCESS read-only
			STATUS current
			DESCRIPTION
				"This attribute shall indicate the beacon interval in kus (1.024 ms)."
			::= { knownApEntry 7 }

		
		knownapnumBeacons OBJECT-TYPE
			SYNTAX INTEGER
			MAX-ACCESS read-only
			STATUS current
			DESCRIPTION
				"This attribute shall indicate the number of beacons received."
			::= { knownApEntry 8 }


		knownaplastBeacon OBJECT-TYPE
			SYNTAX INTEGER
			MAX-ACCESS read-only
			STATUS current
			DESCRIPTION
				"This attribute shall indicate the time of the last beacon." 
                        ::= { knownApEntry 9 }        

              
                 
		knownapEntryStatus OBJECT-TYPE
			SYNTAX INTEGER
			MAX-ACCESS read-create
			STATUS current
			DESCRIPTION
				"The Known AP Entry status.

                                Supported values:
                                active(1)      - valid entry
                                createAndGo(4) - used to create a new entry
                                destroy(6)     - removes the entry"
                        ::= { knownApEntry 10 }        


--   **********************************************************************
-- *  Unknown AP Table
-- **********************************************************************
		unknownApTable OBJECT-TYPE
			SYNTAX SEQUENCE OF UnknownApEntry
			MAX-ACCESS not-accessible
			STATUS current
			DESCRIPTION
				"unknownAp Table shows list of unknown APs."
			::= { wag302 16 }


	        unknownApEntry OBJECT-TYPE
			SYNTAX UnknownApEntry
			MAX-ACCESS not-accessible
			STATUS current
			DESCRIPTION
				"An entry in the unknownApTable."
			INDEX { unknownapmac }
			::= { unknownApTable 1 }

		
		UnknownApEntry ::=
			SEQUENCE { 
				unknownapmac
					MacAddress,
				unknownapssid
					DisplayString,
				unknownapprivacy
					TruthValue,
				unknownapband
					DisplayString,
				unknownapchannel
					INTEGER,
				unknownaprate
					INTEGER,
				unknownapbeaconInterval
					INTEGER,
				unknownapnumBeacons
					INTEGER,
				unknownaplastBeacon
					INTEGER
			 }

		
		unknownapmac OBJECT-TYPE
			SYNTAX MacAddress
			MAX-ACCESS read-only
			STATUS current
			DESCRIPTION
				"This attribute shall indicate MAC address of the
				unknown AP."
			::= { unknownApEntry 1 }

		
		unknownapssid  OBJECT-TYPE
			SYNTAX DisplayString
			MAX-ACCESS read-only
			STATUS current
			DESCRIPTION
				"This attribute shall indicate ssid of the unknown AP."
			::= { unknownApEntry 2 }

		
		unknownapprivacy OBJECT-TYPE
			SYNTAX TruthValue
			MAX-ACCESS read-only
			STATUS current
			DESCRIPTION
				"This attribute shall indicate whether privacy is enabled."
			::= { unknownApEntry 3 }

		
		unknownapband    OBJECT-TYPE
			SYNTAX DisplayString
			MAX-ACCESS read-only
			STATUS current
			DESCRIPTION
				"This attribute shall indicate the operating band of unknown AP."
			::= { unknownApEntry 4 }


		unknownapchannel OBJECT-TYPE
			SYNTAX INTEGER
			MAX-ACCESS read-only
			STATUS current
			DESCRIPTION
				"This attribute shall indicate the channel number used."
			::= { unknownApEntry 5 }

		
		unknownaprate    OBJECT-TYPE
			SYNTAX INTEGER
			MAX-ACCESS read-only
			STATUS current
			DESCRIPTION
				"This attribute shall indicate the rate."
			::= { unknownApEntry 6 }

		
		unknownapbeaconInterval OBJECT-TYPE
			SYNTAX INTEGER
			MAX-ACCESS read-only
			STATUS current
			DESCRIPTION
				"This attribute shall indicate the beacon interval in kus (1.024 ms)."
			::= { unknownApEntry 7 }

		
		unknownapnumBeacons    OBJECT-TYPE
			SYNTAX INTEGER
			MAX-ACCESS read-only
			STATUS current
			DESCRIPTION
				"This attribute shall indicate the number of beacons received."
			::= { unknownApEntry 8 }


		unknownaplastBeacon    OBJECT-TYPE
			SYNTAX INTEGER
			MAX-ACCESS read-only
			STATUS current
			DESCRIPTION
				"This attribute shall indicate the time of the last beacon." 
                        ::= { unknownApEntry 9 }
	
	wlanAccessControlLocalTable OBJECT-TYPE
			SYNTAX SEQUENCE OF WlanAccessControlLocalEntry
			MAX-ACCESS not-accessible
			STATUS current
			DESCRIPTION
				"ACL attributes in tablular form to allow for multiple
				instances on an agent."
			::= { wag302 17 }

		
		wlanAccessControlLocalEntry OBJECT-TYPE
			SYNTAX WlanAccessControlLocalEntry
			MAX-ACCESS not-accessible
			STATUS current
			DESCRIPTION
				"An entry in the wlanAccessControlListTable. It is possible
				for there to be multiple AP interfaces on one agent, each
				with its unique MAC address. The relationship between an
				AP interface and an interface in the context of the
				Internet-standard MIB is one-to-one. As such, the value of
				an ifIndex object instance can be directly used to identify
				corresponding instances of the objects defined herein. "
			INDEX { aclMAC }
			::= { wlanAccessControlLocalTable 1 }

		
		WlanAccessControlLocalEntry ::=
			SEQUENCE { 
				aclMAC
					MacAddress,
                                aclMacStatus
                                        RowStatus 
			 }


		
		aclMAC OBJECT-TYPE
			SYNTAX MacAddress
			MAX-ACCESS read-only
			STATUS current
			DESCRIPTION
				"This field should indicate an MAC address entry in the
				access control local database. When write this field
				aclMAC=000000000000, shall remove current MAC address from
				local database. Otherwise, shall update the MAC address."
			::= { wlanAccessControlLocalEntry 1 }					
				
	
                aclMacStatus    OBJECT-TYPE
                        SYNTAX INTEGER
                        MAX-ACCESS read-create
                        STATUS current
                        DESCRIPTION
                                "The ACL Mac status.

                                Supported values:
                                active(1)      - valid entry
                                createAndGo(4) - used to create a new entry
                                destroy(6)     - removes the entry"
                        ::= { wlanAccessControlLocalEntry 2 }
END
