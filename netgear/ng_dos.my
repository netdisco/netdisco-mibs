NETGEAR-DENIALOFSERVICE-PRIVATE-MIB DEFINITIONS ::= BEGIN

-- NETGEAR FASTPATH Denial of Service MIB

-- This SNMP Management Information Specification
-- embodies Broadcom Corporation's confidential and proprietary
-- intellectual property.  Broadcom Corporation retains all title
-- and ownership in the Specification including any revisions.

-- This Specification is supplied "AS IS", Broadcom Corporation
-- makes no warranty, either expressed or implied,
-- as to the use, operation, condition, or performance of the
-- Specification.



IMPORTS
    MODULE-IDENTITY, OBJECT-TYPE, NOTIFICATION-TYPE,
    Unsigned32                          FROM SNMPv2-SMI
    TEXTUAL-CONVENTION,RowStatus,
    MacAddress                          FROM SNMPv2-TC
    ifIndex                             FROM IF-MIB

    DisplayString		        FROM RFC1213-MIB
    ng700smartswitch                    FROM NETGEAR-REF-MIB;

    agentDenialOfService MODULE-IDENTITY
           LAST-UPDATED "200803170000Z" -- 17 Mar 2008 12:00:00 GMT
           ORGANIZATION "Netgear"
           CONTACT-INFO
            ""
           DESCRIPTION
            "The Netgear Private MIB for Denial of Service."

     -- Revision history.
     REVISION
          "200803170000Z" -- 17 Mar 2008 12:00:00 GMT
     DESCRIPTION
          "Initial version"

      ::= { ng700smartswitch 31 }


    --**************************************************************************************
    -- agentSwitchDenialOfServiceGroup
    --
    --**************************************************************************************
    
    agentSwitchDenialOfServiceGroup          OBJECT IDENTIFIER ::= { agentDenialOfService 1 }


    agentSwitchDenialOfServiceSIPDIPMode OBJECT-TYPE
         SYNTAX      INTEGER {
                     enable(1),
                     disable(2)
                  }
         MAX-ACCESS  read-write
         STATUS      current
         DESCRIPTION
                     "Enables or Disables the SIP=DIP Denial of Service 
                     protection feature."                
         DEFVAL { disable }
         ::= { agentSwitchDenialOfServiceGroup 1 }
         
    agentSwitchDenialOfServiceFirstFragMode OBJECT-TYPE
         SYNTAX      INTEGER {
                     enable(1),
                     disable(2)
                  }
         MAX-ACCESS  read-write
         STATUS      current
         DESCRIPTION
                     "Enables or Disables the First Fragment Denial of Service 
                     protection feature."
         DEFVAL { disable }
         ::= { agentSwitchDenialOfServiceGroup 2 }
         
    agentSwitchDenialOfServiceTCPHdrSize OBJECT-TYPE
         SYNTAX      Integer32 (0..255) 
         MAX-ACCESS  read-write
         STATUS      current
         DESCRIPTION
                     "Configures the Minimum allowed TCP Header size.
                     This is active if the First Fragment Denial of Service
                     protection feature is enabled."                    
         DEFVAL { 20 }
         ::= { agentSwitchDenialOfServiceGroup 3 }

    agentSwitchDenialOfServiceTCPFragMode OBJECT-TYPE
         SYNTAX      INTEGER {
                     enable(1),
                     disable(2)
                  }
         MAX-ACCESS  read-write
         STATUS      current
         DESCRIPTION
                     "Enables or Disables the TCP Fragment Denial of Service 
                     protection feature."
         DEFVAL { disable }
         ::= { agentSwitchDenialOfServiceGroup 4 }
         
    agentSwitchDenialOfServiceTCPFlagMode OBJECT-TYPE
         SYNTAX      INTEGER {
                     enable(1),
                     disable(2)
                  }
         MAX-ACCESS  read-write
         STATUS      current
         DESCRIPTION
                     "Enables or Disables the TCP Flag Denial of Service 
                     protection feature."
         DEFVAL { disable }
         ::= { agentSwitchDenialOfServiceGroup 5 }
         
    agentSwitchDenialOfServiceL4PortMode OBJECT-TYPE
         SYNTAX      INTEGER {
                     enable(1),
                     disable(2)
                  }
         MAX-ACCESS  read-write
         STATUS      current
         DESCRIPTION
                     "Enables or Disables the L4 Port Denial of Service 
                     protection feature."
         DEFVAL { disable }
         ::= { agentSwitchDenialOfServiceGroup 6 }
         
    agentSwitchDenialOfServiceICMPMode OBJECT-TYPE
         SYNTAX      INTEGER {
                     enable(1),
                     disable(2)
                  }
         MAX-ACCESS  read-write
         STATUS      current
         DESCRIPTION
                     "Enables or Disables the ICMP Denial of Service 
                     protection feature."
         DEFVAL { disable }
         ::= { agentSwitchDenialOfServiceGroup 7 }
         
    agentSwitchDenialOfServiceICMPSize OBJECT-TYPE
         SYNTAX      Integer32 (0..1023) 
         MAX-ACCESS  read-write
         STATUS      current
         DESCRIPTION
                     "Configures the Maximum allowed ICMP data size.
                     This is active if the ICMP Denial of Service
                     protection feature is enabled."
         DEFVAL { 1023 }
         ::= { agentSwitchDenialOfServiceGroup 8 }
                                                  

END
