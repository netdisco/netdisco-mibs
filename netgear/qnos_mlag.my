QNOS-MLAG-MIB DEFINITIONS ::= BEGIN

IMPORTS
    MODULE-IDENTITY, OBJECT-TYPE,
    Integer32, Unsigned32, IpAddress     FROM SNMPv2-SMI
    TruthValue, RowStatus, MacAddress    FROM SNMPv2-TC
    InterfaceIndex                       FROM IF-MIB
    m4500-48xf8c, AgentPortMask          FROM NETGEAR-REF-MIB;

    qNosMlag MODULE-IDENTITY
        LAST-UPDATED "201401200000Z" -- 20 January 2014 12:00:00 GMT
        ORGANIZATION "Netgear Inc"
        CONTACT-INFO ""
        DESCRIPTION
          "The MIB definitions Mlag Feature."

      -- Revision history.
    REVISION
        "201401200000Z"  -- 20 January 2014 12:00:00 GMT
    DESCRIPTION
        "Initial version."

    ::= { m4500-48xf8c 200 }

--**************************************************************************************
-- agentMlagConfigGroup
--
--**************************************************************************************

agentMlagConfigGroup 			 OBJECT IDENTIFIER ::= { qNosMlag 1 }

    agentMlagMode OBJECT-TYPE
         SYNTAX      INTEGER {
                     enable(1),
                     disable(0)
                  }
         MAX-ACCESS  read-write
         STATUS      current
         DESCRIPTION
                     "To enable Mlag globally. The Mlag role election happens if both
                      the Mlag feature is enabled and if the keepalive state machine is
                      enabled.
                      The following options are supported:

                      enable  - Enable Mlag globally
                      disable - Disable Mlag globally"

          ::= { agentMlagConfigGroup 1 }

    agentKeepalivePriority OBJECT-TYPE
         SYNTAX      Unsigned32(1..255)
         MAX-ACCESS  read-write
         STATUS      obsolete
         DESCRIPTION
                     "To configure the priority of the Mlag switch. This value is used
                      for the Mlag role election.
                      Configurable range is 1 to 255. The default value is 100.
                      Note: The Mlag switch with lower priority becomes the Primary. If
                            both the Mlag peer switches have the same role priority, the
                            device with lower system MAC address becomes the Primary.
                            "

          ::= { agentMlagConfigGroup 2 }

    agentKeepaliveTimeout OBJECT-TYPE
         SYNTAX      Unsigned32(2..15)
         MAX-ACCESS  read-write
         STATUS      obsolete
         DESCRIPTION
                     "To configure the peer keepalive timeout value (in seconds). If
                      an Mlag switch does not receive keepalive messages from the peer
                      for this timeout value, it takes the decision to transition its
                      role (if required).
                      Configurable rang is 2 to 15 seconds. Default value is 5 seconds.
                      Note: The keepalive state machine is not restarted if keepalive
                      priority is modified post election."

          ::= { agentMlagConfigGroup 3 }

      agentKeepaliveMode OBJECT-TYPE
         SYNTAX      INTEGER {
                     enable(1),
                     disable(0)
                  }
         MAX-ACCESS  read-write
         STATUS      obsolete
         DESCRIPTION
                     "To start/stop the keepalive state machine on the Mlag device, if
                      Mlag is globally enabled.
                      The following options are supported:

                      enable  - Enable keepalive
                      disable - Disable keepalive"

          ::= { agentMlagConfigGroup 4 }

    agentPeerLink OBJECT-TYPE
         SYNTAX      InterfaceIndex
         MAX-ACCESS  read-write
         STATUS      current
         DESCRIPTION
                     "To configures a port channel as the Mlag peer link.
                      The configurable range is a valid port channel interface index."

          ::= { agentMlagConfigGroup 5 }

     agentPeerDetectionMode OBJECT-TYPE
         SYNTAX      INTEGER {
                     enable(1),
                     disable(0)
                  }
         MAX-ACCESS  read-write
         STATUS      obsolete
         DESCRIPTION
                     "To start/stop the dual control plane detection protocol (DCPDP) on the
                      Mlag switch.
                      The following options are supported:

                      enable  - Enable the DCPDP on Mlag switch
                      disable - Disable the DCPDP on Mlag switch

                      Note: The peer Mlag switch's IP address has to be configured for
                            the DCPDP to start on an Mlag switch."

          ::= { agentMlagConfigGroup 6 }

     agentMlagConfigTable        OBJECT-TYPE
         SYNTAX        SEQUENCE OF AgentMlagConfigEntry
         MAX-ACCESS    not-accessible
         STATUS        obsolete
         DESCRIPTION
                       "Mlag config table."
         ::= { agentMlagConfigGroup 7 }

     agentMlagConfigEntry       OBJECT-TYPE
         SYNTAX        AgentMlagConfigEntry
         MAX-ACCESS    not-accessible
         STATUS        obsolete
         DESCRIPTION
                       "Mlag config entry."
         INDEX         { agentMlagConfigId }
         ::= { agentMlagConfigTable 1 }

     AgentMlagConfigEntry ::= SEQUENCE {
         agentMlagConfigId
             Unsigned32,
         agentMlagTrackPortMask
             AgentPortMask
         }

     agentMlagConfigId          OBJECT-TYPE
         SYNTAX        Unsigned32 (1..63)
         MAX-ACCESS    read-only
         STATUS        obsolete
         DESCRIPTION
                       "Mlag Id. This object is obselete. Refer to agentMlagDomainIndex for configuring Mlag Id."
         ::= {agentMlagConfigEntry 1}

     agentMlagTrackPortMask    OBJECT-TYPE
         SYNTAX        AgentPortMask
         MAX-ACCESS    read-write
         STATUS        obsolete
         DESCRIPTION
                       "Tracking of non-mlag links."
         ::= {agentMlagConfigEntry 2}

     agentPeerConfigTable        OBJECT-TYPE
         SYNTAX        SEQUENCE OF AgentPeerConfigEntry
         MAX-ACCESS    not-accessible
         STATUS        obsolete
         DESCRIPTION
                       "Mlag config table."
         ::= { agentMlagConfigGroup 8 }

     agentPeerConfigEntry       OBJECT-TYPE
         SYNTAX        AgentPeerConfigEntry
         MAX-ACCESS    not-accessible
         STATUS        obsolete
         DESCRIPTION
                       "Mlag config entry."
         INDEX         { agentPeerConfigRowIndex }
         ::= { agentPeerConfigTable 1 }

     AgentPeerConfigEntry ::= SEQUENCE {
         agentPeerConfigRowIndex
             Unsigned32,
         agentPeerIpAddr
             IpAddress,
         agentSourceIpAddr
             IpAddress,
         agentDcpdpUdpPort
             Unsigned32,
         agentPeerRowStatus
             RowStatus
         }

    agentPeerConfigRowIndex   OBJECT-TYPE
         SYNTAX      Unsigned32(1..1)
         MAX-ACCESS  not-accessible
         STATUS      obsolete
         DESCRIPTION
                     "Index."
         ::= { agentPeerConfigEntry 1 }

     agentPeerIpAddr OBJECT-TYPE
         SYNTAX      IpAddress
         MAX-ACCESS  read-write
         STATUS      obsolete
         DESCRIPTION
                     "To configure IP address of the peer Mlag switch. This
                      configuration is used by the dual control plane detection
                      protocol (DCPDP) on the Mlag switches.

                      NOTE: In order to set value for the object, need to set values for agentPeerIpAddr,
                      agentSourceIpAddr, agentPeerRowStatus objects simultaneously.
                      To reset the object to the default state, the agentPeerRowStatus object should be used."
          ::= { agentPeerConfigEntry 2 }

     agentSourceIpAddr OBJECT-TYPE
         SYNTAX      IpAddress
         MAX-ACCESS  read-write
         STATUS      obsolete
         DESCRIPTION
                     "To configure Self IP address of the Mlag switch that is used as
                      the source IP by the dual control plane detection protocol (DCPDP)
                      on the Mlag switches.

                      NOTE: In order to set value for the object, need to set values for agentPeerIpAddr,
                      agentSourceIpAddr, agentPeerRowStatus objects simultaneously.
                      To reset the object to the default state, the agentPeerRowStatus object should be used."
          ::= { agentPeerConfigEntry 3 }

     agentDcpdpUdpPort OBJECT-TYPE
         SYNTAX      Unsigned32(1..65535)
         MAX-ACCESS  read-write
         STATUS      obsolete
         DESCRIPTION
                     "To configure the UDP port on which the Mlag switch listens to
                      the DCPDP messages.
                      Configurable range is 1 to 65535. Default value is 50000.

                      NOTE: In order to set value for the object, need to set values for agentPeerIpAddr,
                      agentSourceIpAddr, agentPeerRowStatus, agentDcpdpUdpPort objects simultaneously.
                      To reset the object to the default state, the agentPeerRowStatus object should be used."
		  ::= { agentPeerConfigEntry 4 }

     agentPeerRowStatus OBJECT-TYPE
         SYNTAX      RowStatus
         MAX-ACCESS  read-create
         STATUS      obsolete
         DESCRIPTION
                     "Peer config status.

                     Supported values:
                     active(1)      - valid instance.
                     createAndGo(4) - used to configure peer configuration.
                     destroy(6)     - reset peer configuration."
         ::= { agentPeerConfigEntry 5 }

--**************************************************************************************
-- agentMlagDomainConfigTable
--
--**************************************************************************************

     agentMlagDomainConfigTable        OBJECT-TYPE
         SYNTAX        SEQUENCE OF AgentMlagDomainConfigEntry
         MAX-ACCESS    not-accessible
         STATUS        current
         DESCRIPTION
                       "Mlag domain config table."
          ::= { agentMlagConfigGroup 9 }

     agentMlagDomainConfigEntry       OBJECT-TYPE
         SYNTAX        AgentMlagDomainConfigEntry
         MAX-ACCESS    not-accessible
         STATUS        current
         DESCRIPTION
                       "Mlag domain config entry."
         INDEX         { agentMlagDomainIndex }
          ::= { agentMlagDomainConfigTable 1 }

     AgentMlagDomainConfigEntry ::= SEQUENCE {
         agentMlagDomainIndex
             Unsigned32,
         agentMlagDomainKeepalivePriority
             Unsigned32,
         agentMlagDomainKeepaliveTimeout
             Unsigned32,
         agentMlagDomainKeepaliveMode
             INTEGER,
         agentMlagDomainPeerDetectionMode
             INTEGER,
         agentMlagDomainSystemMac
             MacAddress,
         agentMlagDomainSystemPriority
             Unsigned32,
         agentMlagDomainPeerDetectionInterval
             Unsigned32,
         agentMlagDomainPeerDetectionTimeout
             Unsigned32,
         agentMlagDomainPeerIpAddr
             IpAddress,
         agentMlagDomainSourceIpAddr
             IpAddress,
         agentMlagDomainDcpdpUdpPort
             Unsigned32,
         agentMlagDomainStatus
             RowStatus
         }

    agentMlagDomainIndex   OBJECT-TYPE
         SYNTAX      Unsigned32(1..255)
         MAX-ACCESS  read-write
         STATUS      current
         DESCRIPTION
                     "Mlag Domain ID."
          ::= { agentMlagDomainConfigEntry 1 }

    agentMlagDomainKeepalivePriority OBJECT-TYPE
         SYNTAX      Unsigned32(1..255)
         MAX-ACCESS  read-write
         STATUS      current
         DESCRIPTION
                     "To configure the priority of the Mlag switch. This value is used
                      for the Mlag role election.
                      Configurable range is 1 to 255. The default value is 100.
                      Note: The Mlag switch with lower priority becomes the Primary. If
                            both the Mlag peer switches have the same role priority, the
                            device with lower system MAC address becomes the Primary.
                            "

          ::= { agentMlagDomainConfigEntry 2 }

    agentMlagDomainKeepaliveTimeout OBJECT-TYPE
         SYNTAX      Unsigned32(2..15)
         MAX-ACCESS  read-write
         STATUS      current
         DESCRIPTION
                     "To configure the peer keepalive timeout value (in seconds). If
                      an Mlag switch does not receive keepalive messages from the peer
                      for this timeout value, it takes the decision to transition its
                      role (if required).
                      Configurable range is 2 to 15 seconds. Default value is 5 seconds.
                      Note: The keepalive state machine is not restarted if keepalive
                      priority is modified post election."

          ::= { agentMlagDomainConfigEntry 3 }
      agentMlagDomainKeepaliveMode OBJECT-TYPE
         SYNTAX      INTEGER {
                     enable(1),
                     disable(0)
                  }
         MAX-ACCESS  read-write
         STATUS      current
         DESCRIPTION
                     "To start/stop the keepalive state machine on the Mlag device, if
                      Mlag is globally enabled.
                      The following options are supported:

                      enable  - Enable keepalive
                      disable - Disable keepalive"

          ::= { agentMlagDomainConfigEntry 4 }

     agentMlagDomainPeerDetectionMode OBJECT-TYPE
         SYNTAX      INTEGER {
                     enable(1),
                     disable(0)
                  }
         MAX-ACCESS  read-write
         STATUS      current
         DESCRIPTION
                     "To start/stop the dual control plane detection protocol (DCPDP) on the
                      Mlag switch.
                      The following options are supported:

                      enable  - Enable the DCPDP on Mlag switch
                      disable - Disable the DCPDP on Mlag switch

                      Note: The peer Mlag switch's IP address has to be configured for
                            the DCPDP to start on an Mlag switch."

          ::= { agentMlagDomainConfigEntry 5 }

     agentMlagDomainSystemMac OBJECT-TYPE
         SYNTAX      MacAddress
         MAX-ACCESS  read-write
         STATUS      current
         DESCRIPTION
                     "To configure the MAC address for the Mlag domain. This mac-address
                     is used in the LACP PDUs and STP BPDUs
                     that are sent out on Mlag member ports. For the Mlag domain to use
                     the manually configured Mlag MAC address, it should be manually
                     configured on both the Mlag peers and should be the same. If Mlag
                     is configured on only one of the Mlag peers or is configured
                     different on Mlag peers, auto-generated MAC address is used.
                     The specified MAC address should be a unicast MAC address in
                     <aa:bb:cc:dd:ee:ff> format and should not be equal to the
                     MAC address of either primary Mlag or secondary Mlag device.
                     The manually configured Mlag MAC address is used instead of
                     auto-generated Mlag MAC address only if the Mlag feature is
                     re-enabled after configuring the Mlag MAC address.
                     "

          ::= { agentMlagDomainConfigEntry 6 }


     agentMlagDomainSystemPriority OBJECT-TYPE
         SYNTAX      Unsigned32(1..65535)
         MAX-ACCESS  read-write
         STATUS      current
         DESCRIPTION
                     "To configure the system priority for the Mlag domain. This is used
                      in the LACP PDUs sent out on Mlag member ports. System-priority
                      should be configured same on both the Mlag peers. If the configured
                      Mlag system priority is different on Mlag peers, then Mlag will not
                      come up. The default priority value is 32767.
                      "
          ::= { agentMlagDomainConfigEntry 7 }

     agentMlagDomainPeerDetectionInterval OBJECT-TYPE
         SYNTAX      Unsigned32(200..4000)
         MAX-ACCESS  read-write
         STATUS      current
         DESCRIPTION
                     "To configure the DCPDP transmission interval.
                      NOTE: In order to set value for the object, need to set values for DCPDP
                      transmission interval and reception timeout simultaneously."
          ::= { agentMlagDomainConfigEntry 8 }

     agentMlagDomainPeerDetectionTimeout OBJECT-TYPE
         SYNTAX      Unsigned32(700..14000)
         MAX-ACCESS  read-write
         STATUS      current
         DESCRIPTION
                     "To configure the DCPDP reception timeout.
                      NOTE: In order to set value for the object, need to set values for DCPDP
                      transmission interval and reception timeout simultaneously."
          ::= { agentMlagDomainConfigEntry 9 }

     agentMlagDomainPeerIpAddr OBJECT-TYPE
         SYNTAX      IpAddress
         MAX-ACCESS  read-write
         STATUS      current
         DESCRIPTION
                     "To configure IP address of the peer Mlag switch. This
                      configuration is used by the dual control plane detection
                      protocol (DCPDP) on the Mlag switches.

                      NOTE: In order to set value for the object, need to set values for
                      IP address of the peer MLAG switch and destination IP of the DCPDP
                      message simultaneously."
          ::= { agentMlagDomainConfigEntry 10 }

     agentMlagDomainSourceIpAddr OBJECT-TYPE
         SYNTAX      IpAddress
         MAX-ACCESS  read-write
         STATUS      current
         DESCRIPTION
                     "To configure Self IP address of the Mlag switch that is used as
                      the source IP by the dual control plane detection protocol (DCPDP)
                      on the Mlag switches.

                      NOTE: In order to set value for the object, need to set values for
                      IP address of the peer MLAG switch and destination IP of the DCPDP
                      message simultaneously."
          ::= { agentMlagDomainConfigEntry 11 }

     agentMlagDomainDcpdpUdpPort OBJECT-TYPE
         SYNTAX      Unsigned32(1..65535)
         MAX-ACCESS  read-write
         STATUS      current
         DESCRIPTION
                     "To configure the UDP port on which the Mlag switch listens to
                      the DCPDP messages.
                      Configurable range is 1 to 65535. Default value is 50000.

                      NOTE: In order to set value for the object, need to set values for
                      IP address of the peer MLAG switch, destination IP of the DCPDP
                      message and UDP port on which the MLAG switch listens to the
                      DCPDP messages simultaneously."
          ::= { agentMlagDomainConfigEntry 12 }

     agentMlagDomainStatus OBJECT-TYPE
         SYNTAX      RowStatus
         MAX-ACCESS  read-create
         STATUS      current
         DESCRIPTION
                       "Status of Mlag Domain."
          ::= { agentMlagDomainConfigEntry 13 }

--**************************************************************************************
-- agentMlagPeerKeepAliveStatsGroup
--
--**************************************************************************************

agentMlagPeerKeepAliveStatsGroup                      OBJECT IDENTIFIER ::= { qNosMlag 2 }

    agentMlagPeerKeepAliveTotalTx OBJECT-TYPE
         SYNTAX      Unsigned32
         MAX-ACCESS  read-only
         STATUS      current
         DESCRIPTION
                     "Total Packets transmitted"

          ::= { agentMlagPeerKeepAliveStatsGroup 1 }

    agentMlagPeerKeepAliveSuccessTx OBJECT-TYPE
         SYNTAX      Unsigned32
         MAX-ACCESS  read-only
         STATUS      current
         DESCRIPTION
                     "Successfully Transmitted Packets."

          ::= { agentMlagPeerKeepAliveStatsGroup 2 }

    agentMlagPeerKeepAliveTxErrors OBJECT-TYPE
         SYNTAX      Unsigned32
         MAX-ACCESS  read-only
         STATUS      current
         DESCRIPTION
                     "Transmit Failed Packets."

          ::= { agentMlagPeerKeepAliveStatsGroup 3 }

     agentMlagPeerKeepAliveTotalRx OBJECT-TYPE
         SYNTAX      Unsigned32
         MAX-ACCESS  read-only
         STATUS      current
         DESCRIPTION
                     "Total Packets Received."
          ::= { agentMlagPeerKeepAliveStatsGroup 4 }

     agentMlagPeerKeepAliveSuccessRx OBJECT-TYPE
         SYNTAX      Unsigned32
         MAX-ACCESS  read-only
         STATUS      current
         DESCRIPTION
                     "Successfully Received Packets."
          ::= { agentMlagPeerKeepAliveStatsGroup 5 }

      agentMlagPeerKeepAliveRxErrors OBJECT-TYPE
         SYNTAX      Unsigned32
         MAX-ACCESS  read-only
         STATUS      current
         DESCRIPTION
                     "Number of packets received with errors."
          ::= { agentMlagPeerKeepAliveStatsGroup 6 }

      agentMlagPeerKeepAliveTimeoutCount OBJECT-TYPE
         SYNTAX      Unsigned32
         MAX-ACCESS  read-only
         STATUS      current
         DESCRIPTION
                     "Timeout counter."
          ::= { agentMlagPeerKeepAliveStatsGroup 7 }


--**************************************************************************************
-- agentMlagPeerKeepAliveStatsGroup
--
--**************************************************************************************

agentMlagPeerLinkStatsGroup                      OBJECT IDENTIFIER ::= { qNosMlag 3 }
     agentMlagPeerLinkControlMsgTx    OBJECT-TYPE
         SYNTAX      Unsigned32
         MAX-ACCESS  read-only
         STATUS      current
         DESCRIPTION
                     "Peer link control messages transmitted."

          ::= { agentMlagPeerLinkStatsGroup 1 }
     agentMlagPeerLinkTxErrors OBJECT-TYPE
         SYNTAX      Unsigned32
         MAX-ACCESS  read-only
         STATUS      current
         DESCRIPTION
                     "Peer link control messages Tx errors."

          ::= { agentMlagPeerLinkStatsGroup 2 }
     agentMlagPeerLinkTxTimeout OBJECT-TYPE
         SYNTAX      Unsigned32
         MAX-ACCESS  read-only
         STATUS      current
         DESCRIPTION
                     "Peer link control messages Tx timeout."

          ::= { agentMlagPeerLinkStatsGroup 3 }
     agentMlagPeerLinkControlMsgAckTx    OBJECT-TYPE
         SYNTAX      Unsigned32
         MAX-ACCESS  read-only
         STATUS      current
         DESCRIPTION
                     "Peer link control messages ACK transmitted."

          ::= { agentMlagPeerLinkStatsGroup 4 }
     agentMlagPeerLinkControlMsgAckErrors OBJECT-TYPE
         SYNTAX      Unsigned32
         MAX-ACCESS  read-only
         STATUS      current
         DESCRIPTION
                     "Peer link control messages ACK Tx errors."

          ::= { agentMlagPeerLinkStatsGroup 5 }
     agentMlagPeerLinkControlMsgRx  OBJECT-TYPE
         SYNTAX      Unsigned32
         MAX-ACCESS  read-only
         STATUS      current
         DESCRIPTION
                     "Peer link control messages received."

          ::= { agentMlagPeerLinkStatsGroup 6 }
     agentMlagPeerLinkDataMsgTx    OBJECT-TYPE
         SYNTAX      Unsigned32
         MAX-ACCESS  read-only
         STATUS      current
         DESCRIPTION
                     "Peer link data messages transmitted."

          ::= { agentMlagPeerLinkStatsGroup 7 }
     agentMlagPeerLinkDataMsgTxErrors OBJECT-TYPE
         SYNTAX      Unsigned32
         MAX-ACCESS  read-only
         STATUS      current
         DESCRIPTION
                     "Peer link data messages Tx errors."

          ::= { agentMlagPeerLinkStatsGroup 8 }
     agentMlagPeerLinkDataMsgTxTimeout OBJECT-TYPE
         SYNTAX      Unsigned32
         MAX-ACCESS  read-only
         STATUS      current
         DESCRIPTION
                     "Peer link data messages Tx timeout."

          ::= { agentMlagPeerLinkStatsGroup 9 }

     agentMlagPeerLinkDataMsgRx OBJECT-TYPE
         SYNTAX      Unsigned32
         MAX-ACCESS  read-only
         STATUS      current
         DESCRIPTION
                     "Peer link data messages received."
          ::= { agentMlagPeerLinkStatsGroup 10 }
     agentMlagPeerLinkBPDUTx OBJECT-TYPE
         SYNTAX      Unsigned32
         MAX-ACCESS  read-only
         STATUS      current
         DESCRIPTION
                     "Peer link BPDU's transmitted to peer."

          ::= { agentMlagPeerLinkStatsGroup 11 }
     agentMlagPeerLinkBPDUTxErrors OBJECT-TYPE
         SYNTAX      Unsigned32
         MAX-ACCESS  read-only
         STATUS      current
         DESCRIPTION
                     "Peer link BPDU's Tx errors."
          ::= { agentMlagPeerLinkStatsGroup 12 }
     agentMlagPeerLinkBPDUrx OBJECT-TYPE
         SYNTAX      Unsigned32
         MAX-ACCESS  read-only
         STATUS      current
         DESCRIPTION
                     "Peer link BPDU's received from peer."

          ::= { agentMlagPeerLinkStatsGroup 13 }
     agentMlagPeerLinkBPDURxErrors OBJECT-TYPE
         SYNTAX      Unsigned32
         MAX-ACCESS  read-only
         STATUS      current
         DESCRIPTION
                     "Peer link BPDU's Rx errors."
          ::= { agentMlagPeerLinkStatsGroup 14 }
     agentMlagPeerLinkLACPDUTx OBJECT-TYPE
         SYNTAX      Unsigned32
         MAX-ACCESS  read-only
         STATUS      current
         DESCRIPTION
                     "Peer link LACPDU's tranmsitted to peer."

          ::= { agentMlagPeerLinkStatsGroup 15 }
     agentMlagPeerLinkLACPDUTxErrors OBJECT-TYPE
         SYNTAX      Unsigned32
         MAX-ACCESS  read-only
         STATUS      current
         DESCRIPTION
                     "Peer link LACPDU's Tx errors."
          ::= { agentMlagPeerLinkStatsGroup 16 }
     agentMlagPeerLinkLACPDUrx OBJECT-TYPE
         SYNTAX      Unsigned32
         MAX-ACCESS  read-only
         STATUS      current
         DESCRIPTION
                     "Peer link LACPDU's received from peer."

          ::= { agentMlagPeerLinkStatsGroup 17 }
     agentMlagPeerLinkLACPDURxErrors OBJECT-TYPE
         SYNTAX      Unsigned32
         MAX-ACCESS  read-only
         STATUS      current
         DESCRIPTION
                     "Peer link LACPDU's Rx errors."
          ::= { agentMlagPeerLinkStatsGroup 18 }

--**************************************************************************************
-- agentMlagStatusGroup
--
--**************************************************************************************

agentMlagStatusGroup           OBJECT IDENTIFIER ::= { qNosMlag 4 }
     agentMlagPeerLinkStatus    OBJECT-TYPE
         SYNTAX      TruthValue
         MAX-ACCESS  read-only
         STATUS      current
         DESCRIPTION
                     "Peer link operational status."

          ::= { agentMlagStatusGroup 1 }
     agentMlagTotalMlagConfigured   OBJECT-TYPE
         SYNTAX      Unsigned32
         MAX-ACCESS  read-only
         STATUS      current
         DESCRIPTION
                     "Number of Mlag's configured."
          ::= { agentMlagStatusGroup 2 }
     agentMlagTotalMlagOperational    OBJECT-TYPE
         SYNTAX      Unsigned32
         MAX-ACCESS  read-only
         STATUS      current
         DESCRIPTION
                     "Number of Mlag's operational."
          ::= { agentMlagStatusGroup 3 }
     agentMlagSelfRole              OBJECT-TYPE
         SYNTAX      INTEGER {
                       none (1),
                       primary (2),
                       secondary (3)
                     }
         MAX-ACCESS  read-only
         STATUS      current
         DESCRIPTION
                     "Mlag role."
          ::= { agentMlagStatusGroup 4 }

     agentMlagOperationMode    OBJECT-TYPE
          SYNTAX        INTEGER {
                          enable  (1),
                          disable (2)
                        }
          MAX-ACCESS    read-only
          STATUS        current
          DESCRIPTION
                        "Mlag operational mode."
             ::= { agentMlagStatusGroup 5 }

     agentMlagPeerRole         OBJECT-TYPE
          SYNTAX        INTEGER {
                          none      (1),
                          primary   (2),
                          secondary (3)
                        }
         MAX-ACCESS     read-only
         STATUS         current
         DESCRIPTION
                        "Mlag peer role."
             ::= { agentMlagStatusGroup 6 }

     agentMlagKeepaliveOperationalMode    OBJECT-TYPE
          SYNTAX        INTEGER {
                          enable  (1),
                          disable (2)
                        }
          MAX-ACCESS    read-only
          STATUS        current
          DESCRIPTION
                        "Mlag keepalive operational mode."
             ::= { agentMlagStatusGroup 7 }

     agentMlagSystemMac        OBJECT-TYPE
          SYNTAX        MacAddress
          MAX-ACCESS    read-only
          STATUS        current
          DESCRIPTION
                        "System MAC address."
             ::= { agentMlagStatusGroup 8 }

     agentMlagState            OBJECT-TYPE
          SYNTAX        INTEGER {
                          disable   (1),
                          listen    (2),
                          ready     (3),
                          primary   (4),
                          secondary (5)
                        }
          MAX-ACCESS    read-only
          STATUS        current
          DESCRIPTION
                        "The following states of a Mlag mean:
                        DISABLE:   In this state, the Mlag interfaces, if any are shut down.
                        LISTEN:    The keepalive does not advertise any packets.
                        READY:     The keepalive component starts sending keepalive messages periodically with the state as READY.
                        PRIMARY:   Traffic over Mlag interfaces is allowed to be forwarded.
                                   The keepalive protocol continues to advertise keepalive messages with the state as PRIMARY.
                        SECONDARY: Traffic over Mlag interfaces is allowed to be forwarded.
                                   The keepalive protocol continues to advertise keepalive messages with the state as SECONDARY."
             ::= { agentMlagStatusGroup 9 }

     agentMlagPeerPriority     OBJECT-TYPE
          SYNTAX        Unsigned32
          MAX-ACCESS    read-only
          STATUS        current
          DESCRIPTION
                        "Mlag peer priority."
             ::= { agentMlagStatusGroup 10 }

     agentMlagPeerMac    OBJECT-TYPE
          SYNTAX        MacAddress
          MAX-ACCESS    read-only
          STATUS        current
          DESCRIPTION
                        "Mlag peer MAC address."
             ::= { agentMlagStatusGroup 11 }

     agentMlagPeerDetectionStatus    OBJECT-TYPE
          SYNTAX        TruthValue
          MAX-ACCESS    read-only
          STATUS        current
          DESCRIPTION
                        "Mlag peer detection status."
             ::= { agentMlagStatusGroup 12 }

     agentMlagIsPeerDetected   OBJECT-TYPE
          SYNTAX        TruthValue
          MAX-ACCESS    read-only
          STATUS        current
          DESCRIPTION
                        "Indicates if the Mlag peer is detected."
             ::= { agentMlagStatusGroup 13 }

    agentMlagSelfMemberStatusTable      OBJECT-TYPE
          SYNTAX        SEQUENCE OF AgentMlagSelfMemberStatusEntry
          MAX-ACCESS    not-accessible
          STATUS        current
          DESCRIPTION
                        "Mlag self member ports status table."
             ::= { agentMlagStatusGroup 14 }

    agentMlagSelfMemberStatusEntry      OBJECT-TYPE
          SYNTAX        AgentMlagSelfMemberStatusEntry
          MAX-ACCESS    not-accessible
          STATUS        current
          DESCRIPTION
                        "Mlag self member port status entry."
          INDEX         { agentMlagSelfMemberStatusMlagId,
                          agentMlagSelfMemberStatusIntfId }
             ::= { agentMlagSelfMemberStatusTable 1 }

    AgentMlagSelfMemberStatusEntry ::= SEQUENCE {
          agentMlagSelfMemberStatusMlagId
               Unsigned32,
          agentMlagSelfMemberStatusIntfId
               InterfaceIndex,
          agentMlagSelfMemberStatusIntfState
               INTEGER
          }

    agentMlagSelfMemberStatusMlagId      OBJECT-TYPE
          SYNTAX        Unsigned32 (1..63)
          MAX-ACCESS    read-only
          STATUS        current
          DESCRIPTION
                        "Mlag Id."
             ::= { agentMlagSelfMemberStatusEntry 1 }

    agentMlagSelfMemberStatusIntfId     OBJECT-TYPE
          SYNTAX        InterfaceIndex
          MAX-ACCESS    read-only
          STATUS        current
          DESCRIPTION
                        "Interface Id."
             ::= { agentMlagSelfMemberStatusEntry 2 }

    agentMlagSelfMemberStatusIntfState  OBJECT-TYPE
          SYNTAX        INTEGER {
                          up   (1),
                          down (2)
                        }
          MAX-ACCESS    read-only
          STATUS        current
          DESCRIPTION
                        "Mlag self member interface status."
             ::= { agentMlagSelfMemberStatusEntry 3 }

    agentMlagPeerMemberStatusTable       OBJECT-TYPE
         SYNTAX      SEQUENCE OF AgentMlagPeerMemberStatusEntry
         MAX-ACCESS  not-accessible
         STATUS      current
         DESCRIPTION
                     "Mlag peer member ports status table."
             ::= { agentMlagStatusGroup 15 }

    agentMlagPeerMemberStatusEntry      OBJECT-TYPE
         SYNTAX      AgentMlagPeerMemberStatusEntry
         MAX-ACCESS  not-accessible
         STATUS      current
         DESCRIPTION
                     "Mlag peer member port status entry."
         INDEX       { agentMlagPeerMemberStatusMlagId,
                       agentMlagPeerMemberStatusIntfId }
             ::= { agentMlagPeerMemberStatusTable 1 }

    AgentMlagPeerMemberStatusEntry ::= SEQUENCE {
          agentMlagPeerMemberStatusMlagId
               Unsigned32,
          agentMlagPeerMemberStatusIntfId
               InterfaceIndex,
          agentMlagPeerMemberStatusIntfState
               INTEGER
          }

    agentMlagPeerMemberStatusMlagId      OBJECT-TYPE
          SYNTAX        Unsigned32 (1..63)
          MAX-ACCESS    read-only
          STATUS        current
          DESCRIPTION
                        "Mlag Id."
             ::= { agentMlagPeerMemberStatusEntry 1 }

    agentMlagPeerMemberStatusIntfId     OBJECT-TYPE
          SYNTAX        InterfaceIndex
          MAX-ACCESS    read-only
          STATUS        current
          DESCRIPTION
                        "Interface Id."
             ::= { agentMlagPeerMemberStatusEntry 2 }

    agentMlagPeerMemberStatusIntfState  OBJECT-TYPE
          SYNTAX        INTEGER {
                          up   (1),
                          down (2)
                        }
          MAX-ACCESS    read-only
          STATUS        current
          DESCRIPTION
                        "Mlag peer member interface status."
             ::= { agentMlagPeerMemberStatusEntry 3 }

     agentMlagStatusTable        OBJECT-TYPE
         SYNTAX      SEQUENCE OF AgentMlagStatusEntry
         MAX-ACCESS  not-accessible
         STATUS      current
         DESCRIPTION
                     "Mlag status table."
          ::= { agentMlagStatusGroup 16 }

     agentMlagStatusEntry       OBJECT-TYPE
         SYNTAX         AgentMlagStatusEntry
         MAX-ACCESS     not-accessible
         STATUS         current
         DESCRIPTION
                      "Mlag status entry."
          INDEX    {agentMlagStatusId}
          ::= {  agentMlagStatusTable 1 }

     AgentMlagStatusEntry  ::= SEQUENCE {
          agentMlagStatusId
              Unsigned32,
          agentMlagOperationalStatus
              INTEGER,
          agentPortChannelId
              InterfaceIndex,
          agentMlagInterfaceState
              INTEGER
          }

     agentMlagStatusId      OBJECT-TYPE
          SYNTAX        Unsigned32 (1..63)
          MAX-ACCESS    read-only
          STATUS        current
          DESCRIPTION
                        "Mlag Id."
             ::= {agentMlagStatusEntry 1}

     agentMlagOperationalStatus    OBJECT-TYPE
          SYNTAX        INTEGER {
                          enable (1),
                          disable (2)
                        }
          MAX-ACCESS    read-only
          STATUS        current
          DESCRIPTION
                        "Mlag operational status."
             ::= {agentMlagStatusEntry 2}

     agentPortChannelId      OBJECT-TYPE
          SYNTAX        InterfaceIndex
          MAX-ACCESS    read-only
          STATUS        current
          DESCRIPTION
                        "Port-channel ID."
             ::= {agentMlagStatusEntry 3}

     agentMlagInterfaceState   OBJECT-TYPE
          SYNTAX        INTEGER {
                          disable  (1),
                          wait     (2),
                          error    (3),
                          active   (4),
                          inactive (5)
                        }
          MAX-ACCESS    read-only
          STATUS        current
          DESCRIPTION
                        "The following states of a Mlag port-channel interface mean:
                         DISABLE:  The state of a port-channel before Mlag functionality is enabled on it.
                         WAIT:     The Mlag port-channel 'waits' for the Mlag functionality
                                   to be enabled on a port-channel of the peer switch.
                         ERROR:    After Mlag is enabled on a port-channel of both peer switches,
                                   the DOT3AD component checks to see if all entry criteria are met
                                   for the port-channel to be operational.
                         ACTIVE:   If the entry criteria are satisfied, then the Mlag interface is set
                                   to ACTIVE and is operationally enabled.
                                   Traffic is now allowed to flow through the Mlag member ports.
                         INACTIVE: If links connected to the Mlag member ports are down,
                                   then the Mlag interface is set to INACTIVE on the switch.
                                   The Mlag will remain ACTIVE on the peer switch."
             ::= {agentMlagStatusEntry 4}
END
