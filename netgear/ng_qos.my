NETGEAR-QOS-MIB DEFINITIONS ::= BEGIN

-- This SNMP Management Information Specification
-- embodies  Broadcom Corporation confidential and proprietary
-- intellectual property. Broadcom Corporation retains all title
-- and ownership in the Specification including any revisions.

-- This Specification is supplied "AS IS", Broadcom Corporation
-- makes no warranty, either expressed or implied,
-- as to the use, operation, condition, or performance of the
-- Specification.


IMPORTS
    MODULE-IDENTITY, OBJECT-TYPE, NOTIFICATION-TYPE, Integer32, Gauge32        
                                        FROM SNMPv2-SMI
    RowStatus                           FROM SNMPv2-TC
    ng700smartswitch                    FROM NETGEAR-REF-MIB
    DisplayString                       FROM RFC1213-MIB;
                
    agentQOS MODULE-IDENTITY
        LAST-UPDATED "200803170000Z" -- 17 Mar 2008 12:00:00 GMT
        ORGANIZATION "Netgear"
        CONTACT-INFO
          ""
        DESCRIPTION
          "The MIB definitaions for Quality of Service Flex package."
          
        -- Revision history.	  
        REVISION
          "200803170000Z" -- 17 Mar 2008 12:00:00 GMT
        DESCRIPTION
          "Initial revision."
          
    ::= { ng700smartswitch 3 }
      
END
