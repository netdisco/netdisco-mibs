SWITCHING-EXTENSION-MIB DEFINITIONS ::= BEGIN

IMPORTS
    MODULE-IDENTITY, OBJECT-TYPE, NOTIFICATION-TYPE, IpAddress,
    Integer32, Unsigned32, TimeTicks
                                        FROM SNMPv2-SMI
	RowStatus, TruthValue, MacAddress, DateAndTime, TEXTUAL-CONVENTION
                                        FROM SNMPv2-TC
    m4500-48xf8c,AgentPortMask          FROM NETGEAR-REF-MIB
    DisplayString,PhysAddress           FROM RFC1213-MIB
    VlanId,VlanIndex,dot1qVlanIndex,dot1qFdbId
                                        FROM Q-BRIDGE-MIB
    IANAifType                          FROM IANAifType-MIB
    InterfaceIndex, ifIndex, InterfaceIndexOrZero
                                        FROM IF-MIB
    InetAddressType, InetAddress        FROM INET-ADDRESS-MIB
    AgentLogSeverity                    FROM QNOS-LOGGING-MIB;

    switchingExtension MODULE-IDENTITY
        LAST-UPDATED "201404090000Z" -- 09 Apr 2014 12:00:00 GMT
        ORGANIZATION "Netgear Inc"
        CONTACT-INFO ""
        DESCRIPTION
          "The Netgear Private MIB for dataCenter Switching"


    ::= { m4500-48xf8c 101 }

    --**************************************************************************************
    --    agentPortBackupConfigGroup
    --**************************************************************************************

    agentPortBackupConfigGroup                      OBJECT IDENTIFIER ::= { switchingExtension 16 }

    agentPortBackupConfigAdminMode OBJECT-TYPE
         SYNTAX      INTEGER {
                     enable(1),
                     disable(2)
                  }
         MAX-ACCESS  read-write
         STATUS      current
         DESCRIPTION
                     "The administration mode of the Port-backup."
         ::= { agentPortBackupConfigGroup 1 }

    -- *****************************************************************
    --      agentPortBackupGroupTable
    -- *****************************************************************

    agentPortBackupGroupTable OBJECT-TYPE
         SYNTAX      SEQUENCE OF AgentPortBackupGroupEntry
         MAX-ACCESS  not-accessible
         STATUS      current
         DESCRIPTION
                     "This table includes entries for the status of
                      all currently configured Port-backup group."
         ::= { agentPortBackupConfigGroup 2 }

    agentPortBackupGroupEntry OBJECT-TYPE
         SYNTAX      AgentPortBackupGroupEntry
         MAX-ACCESS  not-accessible
         STATUS      current
         DESCRIPTION
                     "This table includes entries for the status of
                      all currently configured Port-backup group."
         INDEX       { agentPortBackupGroupId }
         ::= { agentPortBackupGroupTable 1 }

    AgentPortBackupGroupEntry ::= SEQUENCE {
         agentPortBackupGroupId
              Integer32,
         agentPortBackupGroupMode
              INTEGER,
         agentPortBackupGroupActivePort
              DisplayString,
         agentPortBackupGroupBackupPort
              DisplayString,
         agentMacMoveUpdatetMode
              INTEGER,
         agentPortBackupGroupStatus
              RowStatus,
         agentPortBackupGroupFailBackTime
              Integer32
         }

    agentPortBackupGroupId OBJECT-TYPE
         SYNTAX      Integer32 (1..6)
         MAX-ACCESS  read-only
         STATUS      current
         DESCRIPTION
                     "The id of the Port-backup group."
         ::= { agentPortBackupGroupEntry 1 }

    agentPortBackupGroupMode OBJECT-TYPE
         SYNTAX      INTEGER {
                     enable(1),
                     disable(2)
                  }
         MAX-ACCESS  read-write
         STATUS      current
         DESCRIPTION
                     "The mode of this Port-backup group."
         ::= { agentPortBackupGroupEntry 2 }

    agentPortBackupGroupActivePort OBJECT-TYPE
         SYNTAX      DisplayString
         MAX-ACCESS  read-write
         STATUS      current
         DESCRIPTION
                     "The active port of the Port-backup group."
         ::= { agentPortBackupGroupEntry 3 }

    agentPortBackupGroupBackupPort OBJECT-TYPE
         SYNTAX      DisplayString
         MAX-ACCESS  read-write
         STATUS      current
         DESCRIPTION
                     "The backup port of the Port-backup group."
         ::= { agentPortBackupGroupEntry 4 }

    agentMacMoveUpdatetMode OBJECT-TYPE
         SYNTAX      INTEGER {
                     enable(1),
                     disable(2)
                  }
         MAX-ACCESS  read-write
         STATUS      current
         DESCRIPTION
                     "The mode of MAC Address-Table Move Update."
         ::= { agentPortBackupGroupEntry 5 }

    agentPortBackupGroupStatus OBJECT-TYPE
         SYNTAX      RowStatus
         MAX-ACCESS  read-create
         STATUS      current
         DESCRIPTION
                     "The status of Port-backup group.
                     active(1)  - This group setting is active.
                     createAndGo(4) -  Set to this value to create a new group.
                     destroy(6) - Set to this value to remove this group."
         ::= { agentPortBackupGroupEntry 6 }

    agentPortBackupGroupFailBackTime OBJECT-TYPE
         SYNTAX      Integer32 (0..60)
         MAX-ACCESS  read-write
         STATUS      current
         DESCRIPTION
                     "The value of the Port-backup fail back time."
         ::= { agentPortBackupGroupEntry 7 }

    --**************************************************************************************
    --    DOM Group
    --**************************************************************************************
    agentDOMGroup                             OBJECT IDENTIFIER ::= { switchingExtension 100 }

	agentDOMTable OBJECT-TYPE
         SYNTAX      SEQUENCE OF AgentDOMEntry
         MAX-ACCESS  not-accessible
         STATUS      current
         DESCRIPTION
                     "The switch's dom information table."
         ::= { agentDOMGroup 1 }

    agentDOMEntry OBJECT-TYPE
         SYNTAX      AgentDOMEntry
         MAX-ACCESS  not-accessible
         STATUS      current
         DESCRIPTION
                     "Entry of dom information table."
         INDEX       { agentDOMtransceiverIndex }
         ::= { agentDOMTable 1 }

    AgentDOMEntry ::=
         SEQUENCE {
         agentDOMtransceiverIndex
                 Integer32,
         agentDOMtemperatureHighAlarm
                 DisplayString,
         agentDOMtemperatureHighWarning
                 DisplayString,
         agentDOMtemperatureLowWarning
                 DisplayString,
         agentDOMtemperatureLowAlarm
                 DisplayString,
         agentDOMvotageHighAlarm
                 DisplayString,
         agentDOMvotageHighWarning
                 DisplayString,
         agentDOMvotageLowWarning
                 DisplayString,
         agentDOMvotageLowAlarm
                 DisplayString,
         agentDOMbiasHighAlarm
                 DisplayString,
         agentDOMbiasHighWarning
                 DisplayString,
         agentDOMbiasLowWarning
                 DisplayString,
         agentDOMbiasLowAlarm
                 DisplayString,
         agentDOMtxpowerHighAlarm
                 DisplayString,
         agentDOMtxpowerHighWarning
                 DisplayString,
         agentDOMtxpowerLowWarning
                 DisplayString,
         agentDOMtxpowerLowAlarm
                 DisplayString,
         agentDOMrxpowerHighAlarm
                 DisplayString,
         agentDOMrxpowerHighWarning
                 DisplayString,
         agentDOMrxpowerLowWarning
                 DisplayString,
         agentDOMrxpowerLowAlarm
                 DisplayString
	     }

    agentDOMtransceiverIndex OBJECT-TYPE
         SYNTAX      Integer32 (0..2147483647)
         MAX-ACCESS  read-only
         STATUS      current
         DESCRIPTION
                     "Unique index of dom Information entry."
         ::= { agentDOMEntry 1 }

	agentDOMtemperatureHighAlarm OBJECT-TYPE
         SYNTAX      DisplayString
         MAX-ACCESS  read-only
         STATUS      current
         DESCRIPTION
                     "Temperature high alarm of the transceiver module."
         ::= { agentDOMEntry 2 }

    agentDOMtemperatureHighWarning OBJECT-TYPE
         SYNTAX      DisplayString
         MAX-ACCESS  read-only
         STATUS      current
         DESCRIPTION
                     "Temperature high warning of the transceiver module."
         ::= { agentDOMEntry 3 }

    agentDOMtemperatureLowWarning OBJECT-TYPE
         SYNTAX      DisplayString
         MAX-ACCESS  read-only
         STATUS      current
         DESCRIPTION
                     "Temperature low warning of the transceiver module."
         ::= { agentDOMEntry 4 }

    agentDOMtemperatureLowAlarm OBJECT-TYPE
         SYNTAX      DisplayString
         MAX-ACCESS  read-only
         STATUS      current
         DESCRIPTION
                     "Temperature low alarm of the transceiver module."
         ::= { agentDOMEntry 5 }

    agentDOMvotageHighAlarm OBJECT-TYPE
         SYNTAX      DisplayString
         MAX-ACCESS  read-only
         STATUS      current
         DESCRIPTION
                     "Votage high alarm of the transceiver module."
         ::= { agentDOMEntry 6 }

    agentDOMvotageHighWarning OBJECT-TYPE
         SYNTAX      DisplayString
         MAX-ACCESS  read-only
         STATUS      current
         DESCRIPTION
                     "Votage high warning of the transceiver module."
         ::= { agentDOMEntry 7 }

    agentDOMvotageLowWarning OBJECT-TYPE
         SYNTAX      DisplayString
         MAX-ACCESS  read-only
         STATUS      current
         DESCRIPTION
                     "Votage low warning of the transceiver module."
         ::= { agentDOMEntry 8 }

    agentDOMvotageLowAlarm OBJECT-TYPE
         SYNTAX      DisplayString
         MAX-ACCESS  read-only
         STATUS      current
         DESCRIPTION
                     "Votage low alarm of the transceiver module."
         ::= { agentDOMEntry 9 }

    agentDOMbiasHighAlarm OBJECT-TYPE
         SYNTAX      DisplayString
         MAX-ACCESS  read-only
         STATUS      current
         DESCRIPTION
                     "Bias high alarm of the transceiver module."
         ::= { agentDOMEntry 10 }

    agentDOMbiasHighWarning OBJECT-TYPE
         SYNTAX      DisplayString
         MAX-ACCESS  read-only
         STATUS      current
         DESCRIPTION
                     "Bias high warning of the transceiver module."
         ::= { agentDOMEntry 11 }

    agentDOMbiasLowWarning OBJECT-TYPE
         SYNTAX      DisplayString
         MAX-ACCESS  read-only
         STATUS      current
         DESCRIPTION
                     "Bias low warning of the transceiver module."
         ::= { agentDOMEntry 12 }

    agentDOMbiasLowAlarm OBJECT-TYPE
         SYNTAX      DisplayString
         MAX-ACCESS  read-only
         STATUS      current
         DESCRIPTION
                     "Bias low alarm of the transceiver module."
         ::= { agentDOMEntry 13 }

    agentDOMtxpowerHighAlarm OBJECT-TYPE
         SYNTAX      DisplayString
         MAX-ACCESS  read-only
         STATUS      current
         DESCRIPTION
                     "Tx Power high alarm of the transceiver module."
         ::= { agentDOMEntry 14 }

    agentDOMtxpowerHighWarning OBJECT-TYPE
         SYNTAX      DisplayString
         MAX-ACCESS  read-only
         STATUS      current
         DESCRIPTION
                     "Tx Power high warning of the transceiver module."
         ::= { agentDOMEntry 15 }

    agentDOMtxpowerLowWarning OBJECT-TYPE
         SYNTAX      DisplayString
         MAX-ACCESS  read-only
         STATUS      current
         DESCRIPTION
                     "Tx Power low warning of the transceiver module."
         ::= { agentDOMEntry 16 }

    agentDOMtxpowerLowAlarm OBJECT-TYPE
         SYNTAX      DisplayString
         MAX-ACCESS  read-only
         STATUS      current
         DESCRIPTION
                     "Tx Power low alarm of the transceiver module."
         ::= { agentDOMEntry 17 }

    agentDOMrxpowerHighAlarm OBJECT-TYPE
         SYNTAX      DisplayString
         MAX-ACCESS  read-only
         STATUS      current
         DESCRIPTION
                     "Rx Power high alarm of the transceiver module."
         ::= { agentDOMEntry 18 }

    agentDOMrxpowerHighWarning OBJECT-TYPE
         SYNTAX      DisplayString
         MAX-ACCESS  read-only
         STATUS      current
         DESCRIPTION
                     "Rx Power high warning of the transceiver module."
         ::= { agentDOMEntry 19 }

    agentDOMrxpowerLowWarning OBJECT-TYPE
         SYNTAX      DisplayString
         MAX-ACCESS  read-only
         STATUS      current
         DESCRIPTION
                     "Rx Power low warning of the transceiver module."
         ::= { agentDOMEntry 20 }

    agentDOMrxpowerLowAlarm OBJECT-TYPE
         SYNTAX      DisplayString
         MAX-ACCESS  read-only
         STATUS      current
         DESCRIPTION
                     "Rx Power low alarm of the transceiver module."
         ::= { agentDOMEntry 21 }

    agentDOMTraps                            OBJECT IDENTIFIER ::= { agentDOMGroup 2 }

    transceiverAlarmWarningTrap NOTIFICATION-TYPE
	    STATUS      current
        DESCRIPTION
                    "transceiverAlarmWarningTrap"
        ::= { agentDOMTraps 1 }

END
