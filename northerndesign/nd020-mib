ND020-MIB DEFINITIONS ::= BEGIN

IMPORTS
    MODULE-IDENTITY, OBJECT-TYPE,
    Integer32, enterprises
        FROM SNMPv2-SMI;

NDMeter MODULE-IDENTITY
	LAST-UPDATED "201104200000Z"
	ORGANIZATION "Northern Design (Electronics) Ltd."
	CONTACT-INFO
		"	Northern Design (Electronics) Ltd.

		Postal: 228 Bolton Road.
			Bradford
			BD3 0QW
			UK 

		   Tel: +44 1274 729533

		E-mail: support@ndmeter.co.uk"
	DESCRIPTION
		"The Structure of Management Information for
		Northern Design Energy Meters"
	REVISION      "201104200000Z"
	DESCRIPTION
		"Initial version of this MIB module."
	::= { enterprises 37778 }	-- assigned by IANA
	
meterkWhH OBJECT-TYPE
     SYNTAX UInteger32
     UNITS      "kWh"
     MAX-ACCESS read-only
     STATUS current
     DESCRIPTION
        "kWh High."
    ::= { NDMeter 7680 }


meterkWhL OBJECT-TYPE
     SYNTAX UInteger32
     UNITS      "kWh"
     MAX-ACCESS read-only
     STATUS current
     DESCRIPTION
        "kWh Low."
    ::= { NDMeter 7681 }


meterkVAhH OBJECT-TYPE
     SYNTAX UInteger32
     UNITS      "kVAh"
     MAX-ACCESS read-only
     STATUS current
     DESCRIPTION
        "kVAh High."
    ::= { NDMeter 7682 }


meterkVAhL OBJECT-TYPE
     SYNTAX UInteger32
     UNITS      "kVAh"
     MAX-ACCESS read-only
     STATUS current
     DESCRIPTION
        "kVAh Low."
    ::= { NDMeter 7683 }


meterkvarhH OBJECT-TYPE
     SYNTAX UInteger32
     UNITS      "kvarh"
     MAX-ACCESS read-only
     STATUS current
     DESCRIPTION
        "kvarh High."
    ::= { NDMeter 7684 }


meterkvarhL OBJECT-TYPE
     SYNTAX UInteger32
     UNITS      "kvarh"
     MAX-ACCESS read-only
     STATUS current
     DESCRIPTION
        "kvarh Low."
    ::= { NDMeter 7685 }


meterEkWhH OBJECT-TYPE
     SYNTAX UInteger32
     UNITS      "kvarh"
     MAX-ACCESS read-only
     STATUS current
     DESCRIPTION
        "Export kWh High."
    ::= { NDMeter 7686 }


meterEkWhL OBJECT-TYPE
     SYNTAX UInteger32
     UNITS      "kvarh"
     MAX-ACCESS read-only
     STATUS current
     DESCRIPTION
        "Export kWh Low."
    ::= { NDMeter 7687 }


meterP1Amps OBJECT-TYPE
     SYNTAX UInteger32
     UNITS      "Amps"
     MAX-ACCESS read-only
     STATUS current
     DESCRIPTION
        "Phase 1 current scaled by Ki."
    ::= { NDMeter 7688 }

meterP2Amps OBJECT-TYPE
     SYNTAX UInteger32
     UNITS      "Amps"
     MAX-ACCESS read-only
     STATUS current
     DESCRIPTION
        "Phase 2 current scaled by Ki."
    ::= { NDMeter 7689 }

meterP3Amps OBJECT-TYPE
     SYNTAX UInteger32
     UNITS      "Amps"
     MAX-ACCESS read-only
     STATUS current
     DESCRIPTION
        "Phase 3 current scaled by Ki."
    ::= { NDMeter 7690 }


meterP1Volts OBJECT-TYPE
     SYNTAX UInteger32
     UNITS      "Voltsx10"
     MAX-ACCESS read-only
     STATUS current
     DESCRIPTION
        "Phase 1 voltage scaled by Kvp."
    ::= { NDMeter 7691 }


meterP2Volts OBJECT-TYPE
     SYNTAX UInteger32
     UNITS      "Voltsx10"
     MAX-ACCESS read-only
     STATUS current
     DESCRIPTION
        "Phase 2 voltage scaled by Kvp."
    ::= { NDMeter 7692 }


meterP3Volts OBJECT-TYPE
     SYNTAX UInteger32
     UNITS      "Voltsx10"
     MAX-ACCESS read-only
     STATUS current
     DESCRIPTION
        "Phase 3 voltage scaled by Kvp."
    ::= { NDMeter 7693 }


meterP1P2Volts OBJECT-TYPE
     SYNTAX UInteger32
     UNITS      "Voltsx10"
     MAX-ACCESS read-only
     STATUS current
     DESCRIPTION
        "Phase1 Phase2 voltage scaled by Kvl."
    ::= { NDMeter 7694 }


meterP2P3Volts OBJECT-TYPE
     SYNTAX UInteger32
     UNITS      "Voltsx10"
     MAX-ACCESS read-only
     STATUS current
     DESCRIPTION
        "Phase2 Phase3 voltage scaled by Kvl."
    ::= { NDMeter 7695 }


meterP3P1Volts OBJECT-TYPE
     SYNTAX UInteger32
     UNITS      "Voltsx10"
     MAX-ACCESS read-only
     STATUS current
     DESCRIPTION
        "Phase3 Phase1 voltage scaled by Kvl."
    ::= { NDMeter 7696 }


meterFreq OBJECT-TYPE
     SYNTAX UInteger32
     UNITS      "Hz x 10"
     MAX-ACCESS read-only
     STATUS current
     DESCRIPTION
        "Frequency x 10."
    ::= { NDMeter 7697 }


meterPh1PF OBJECT-TYPE
     SYNTAX Integer32
     UNITS      "PF x 100"
     MAX-ACCESS read-only
     STATUS current
     DESCRIPTION
        "Phase1 PF x 100."
    ::= { NDMeter 7698 }


meterPh2PF OBJECT-TYPE
     SYNTAX Integer32
     UNITS      "PF x 100"
     MAX-ACCESS read-only
     STATUS current
     DESCRIPTION
        "Phase2 PF x 100."
    ::= { NDMeter 7699 }


meterPh3PF OBJECT-TYPE
     SYNTAX Integer32
     UNITS      "PF x 100"
     MAX-ACCESS read-only
     STATUS current
     DESCRIPTION
        "Phase3 PF x 100."
    ::= { NDMeter 7700 }


meterSysPh1PF OBJECT-TYPE
     SYNTAX Integer32
     UNITS      "PF x 100"
     MAX-ACCESS read-only
     STATUS current
     DESCRIPTION
        "System PF x 100."
    ::= { NDMeter 7701 }

meterP1kW OBJECT-TYPE
     SYNTAX Integer32
     UNITS      "kW"
     MAX-ACCESS read-only
     STATUS current
     DESCRIPTION
        "Phase 1 kW scaled by Kp."
    ::= { NDMeter 7702 }


meterP2kW OBJECT-TYPE
     SYNTAX Integer32
     UNITS      "kW"
     MAX-ACCESS read-only
     STATUS current
     DESCRIPTION
        "Phase 2 kW scaled by Kp."
    ::= { NDMeter 7703 }


meterP3kW OBJECT-TYPE
     SYNTAX Integer32
     UNITS      "kW"
     MAX-ACCESS read-only
     STATUS current
     DESCRIPTION
        "Phase 3 kW scaled by Kp."
    ::= { NDMeter 7704 }


meterSyskW OBJECT-TYPE
     SYNTAX Integer32
     UNITS      "kW"
     MAX-ACCESS read-only
     STATUS current
     DESCRIPTION
        "System kW scaled by Kp."
    ::= { NDMeter 7705 }


meterP1kVA OBJECT-TYPE
     SYNTAX UInteger32
     UNITS      "kVA"
     MAX-ACCESS read-only
     STATUS current
     DESCRIPTION
        "Phase 1 kVA scaled by Kp."
    ::= { NDMeter 7706 }


meterP2kVA OBJECT-TYPE
     SYNTAX UInteger32
     UNITS      "kVA"
     MAX-ACCESS read-only
     STATUS current
     DESCRIPTION
        "Phase 2 kVA scaled by Kp."
    ::= { NDMeter 7707 }


meterP3kVA OBJECT-TYPE
     SYNTAX UInteger32
     UNITS      "kVA"
     MAX-ACCESS read-only
     STATUS current
     DESCRIPTION
        "Phase 3 kVA scaled by Kp."
    ::= { NDMeter 7708 }


meterSyskVA OBJECT-TYPE
     SYNTAX UInteger32
     UNITS      "kVA"
     MAX-ACCESS read-only
     STATUS current
     DESCRIPTION
        "System kVA scaled by Kp."
    ::= { NDMeter 7709 }

meterP1kvar OBJECT-TYPE
     SYNTAX Integer32
     UNITS      "kvar"
     MAX-ACCESS read-only
     STATUS current
     DESCRIPTION
        "Phase 1 kvar scaled by Kp."
    ::= { NDMeter 7710 }


meterP2kvar OBJECT-TYPE
     SYNTAX Integer32
     UNITS      "kvar"
     MAX-ACCESS read-only
     STATUS current
     DESCRIPTION
        "Phase 2 kvar scaled by Kp."
    ::= { NDMeter 7711 }


meterP3kvar OBJECT-TYPE
     SYNTAX Integer32
     UNITS      "kvar"
     MAX-ACCESS read-only
     STATUS current
     DESCRIPTION
        "Phase 3 kvar scaled by Kp."
    ::= { NDMeter 7712 }


meterSyskvar OBJECT-TYPE
     SYNTAX Integer32
     UNITS      "kvar"
     MAX-ACCESS read-only
     STATUS current
     DESCRIPTION
        "System kvar scaled by Kp."
    ::= { NDMeter 7713 }


meterP1AmpsDem OBJECT-TYPE
     SYNTAX UInteger32
     UNITS      "Amps"
     MAX-ACCESS read-only
     STATUS current
     DESCRIPTION
        "Phase 1 current demand scaled by Ki."
    ::= { NDMeter 7714 }

meterP2AmpsDem OBJECT-TYPE
     SYNTAX UInteger32
     UNITS      "Amps"
     MAX-ACCESS read-only
     STATUS current
     DESCRIPTION
        "Phase 2 current demand scaled by Ki."
    ::= { NDMeter 7715 }

meterP3AmpsDem OBJECT-TYPE
     SYNTAX UInteger32
     UNITS      "Amps"
     MAX-ACCESS read-only
     STATUS current
     DESCRIPTION
        "Phase 3 current demand scaled by Ki."
    ::= { NDMeter 7716 }


meterP1VoltsDem OBJECT-TYPE
     SYNTAX UInteger32
     UNITS      "Voltsx10"
     MAX-ACCESS read-only
     STATUS current
     DESCRIPTION
        "Phase 1 voltage demand scaled by Kvp."
    ::= { NDMeter 7717 }


meterP2VoltsDem OBJECT-TYPE
     SYNTAX UInteger32
     UNITS      "Voltsx10"
     MAX-ACCESS read-only
     STATUS current
     DESCRIPTION
        "Phase 2 voltage demand scaled by Kvp."
    ::= { NDMeter 7718 }


meterP3VoltsDem OBJECT-TYPE
     SYNTAX UInteger32
     UNITS      "Voltsx10"
     MAX-ACCESS read-only
     STATUS current
     DESCRIPTION
        "Phase 3 voltage demand scaled by Kvp."
    ::= { NDMeter 7719 }


meterPkP1Amps OBJECT-TYPE
     SYNTAX UInteger32
     UNITS      "Amps"
     MAX-ACCESS read-only
     STATUS current
     DESCRIPTION
        "Peak Phase 1 current scaled by Ki."
    ::= { NDMeter 7720 }

meterPkP2Amps OBJECT-TYPE
     SYNTAX UInteger32
     UNITS      "Amps"
     MAX-ACCESS read-only
     STATUS current
     DESCRIPTION
        "Peak Phase 2 current scaled by Ki."
    ::= { NDMeter 7721 }

meterPkP3Amps OBJECT-TYPE
     SYNTAX UInteger32
     UNITS      "Amps"
     MAX-ACCESS read-only
     STATUS current
     DESCRIPTION
        "Peak Phase 3 current scaled by Ki."
    ::= { NDMeter 7722 }


meterPkP1Volts OBJECT-TYPE
     SYNTAX UInteger32
     UNITS      "Voltsx10"
     MAX-ACCESS read-only
     STATUS current
     DESCRIPTION
        "Peak Phase 1 voltage scaled by Kvp."
    ::= { NDMeter 7723 }


meterPkP2Volts OBJECT-TYPE
     SYNTAX UInteger32
     UNITS      "Voltsx10"
     MAX-ACCESS read-only
     STATUS current
     DESCRIPTION
        "Peak Phase 2 voltage scaled by Kvp."
    ::= { NDMeter 7724 }


meterPkP3Volts OBJECT-TYPE
     SYNTAX UInteger32
     UNITS      "Voltsx10"
     MAX-ACCESS read-only
     STATUS current
     DESCRIPTION
        "Peak Phase 3 voltage scaled by Kvp."
    ::= { NDMeter 7725 }



meterkWDem OBJECT-TYPE
     SYNTAX Integer32
     UNITS      "kW"
     MAX-ACCESS read-only
     STATUS current
     DESCRIPTION
        "kW Demand scaled with Kp."
    ::= { NDMeter 7726 }


meterkVADem OBJECT-TYPE
     SYNTAX UInteger32
     UNITS      "kVA"
     MAX-ACCESS read-only
     STATUS current
     DESCRIPTION
        "kVA Demand scaled with Kp."
    ::= { NDMeter 7727 }


meterkvarDem OBJECT-TYPE
     SYNTAX Integer32
     UNITS      "kvar"
     MAX-ACCESS read-only
     STATUS current
     DESCRIPTION
        "kvar Demand scaled with Kp."
    ::= { NDMeter 7728 }



meterPkkWDem OBJECT-TYPE
     SYNTAX Integer32
     UNITS      "kW"
     MAX-ACCESS read-only
     STATUS current
     DESCRIPTION
        "Peak kW Demand scaled with Kp."
    ::= { NDMeter 7729 }


meterPkkVADem OBJECT-TYPE
     SYNTAX UInteger32
     UNITS      "kVA"
     MAX-ACCESS read-only
     STATUS current
     DESCRIPTION
        "Peak kVA Demand scaled with Kp."
    ::= { NDMeter 7730 }


meterPkkvarDem OBJECT-TYPE
     SYNTAX Integer32
     UNITS      "kvar"
     MAX-ACCESS read-only
     STATUS current
     DESCRIPTION
        "Peak kvar Demand scaled with Kp."
    ::= { NDMeter 7731 }


meterNeuAmps OBJECT-TYPE
     SYNTAX UInteger32
     UNITS      "Amps"
     MAX-ACCESS read-only
     STATUS current
     DESCRIPTION
        "Neutral current x 10."
    ::= { NDMeter 7732 }


meterAmpsScal OBJECT-TYPE
     SYNTAX UInteger32
     UNITS      "Ki"
     MAX-ACCESS read-only
     STATUS current
     DESCRIPTION
        "Amps scale."
    ::= { NDMeter 7733 }


meterPhVoltScal OBJECT-TYPE
     SYNTAX UInteger32
     UNITS      "Kvp"
     MAX-ACCESS read-only
     STATUS current
     DESCRIPTION
        "Phase Volts scale."
    ::= { NDMeter 7734 }


meterLLVoltScal OBJECT-TYPE
     SYNTAX UInteger32
     UNITS      "Kvl"
     MAX-ACCESS read-only
     STATUS current
     DESCRIPTION
        "Line Volts scale."
    ::= { NDMeter 7735 }


meterPowerScal OBJECT-TYPE
     SYNTAX UInteger32
     UNITS      "Kp"
     MAX-ACCESS read-only
     STATUS current
     DESCRIPTION
        "Power scale."
    ::= { NDMeter 7736 }


meterEnergyScal OBJECT-TYPE
     SYNTAX UInteger32
     UNITS      "Ke"
     MAX-ACCESS read-only
     STATUS current
     DESCRIPTION
        "Energy scale."
    ::= { NDMeter 7737 }


END
