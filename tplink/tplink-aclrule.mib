TPLINK-ACL-RULE-MIB DEFINITIONS ::= BEGIN

	 IMPORTS
		TPRowStatus
				FROM TPLINK-TC-MIB 							
		OBJECT-TYPE,MODULE-IDENTITY,IpAddress
				FROM SNMPv2-SMI
		tplinkMgmt
				FROM TPLINK-MIB
		tplinkAclMIBObjects
				FROM TPLINK-ACL-MIB;
				
	tpAclRuleConfigure				OBJECT IDENTIFIER ::= {tplinkAclMIBObjects 1}			
	
	--MAC RULE LIST
	
	tpMacRuleTable OBJECT-TYPE
	SYNTAX  SEQUENCE OF TPMACRULEENTRY
	MAX-ACCESS  not-accessible
	STATUS  current
	DESCRIPTION
		"A list of L2 MAC ACL rule entries.
		 Here you can add MAC ACL rules for further ACL configuration."
	::= { tpAclRuleConfigure 1 }

	tpMacRuleEntry OBJECT-TYPE
	SYNTAX  TPMACRULEENTRY
	MAX-ACCESS  not-accessible
	STATUS  current
	DESCRIPTION
		"An entry contains of the information of MAC ACL."
	INDEX   { tpMacAclId,tpMacRuleId }
	::= { tpMacRuleTable 1 }

	TPMACRULEENTRY ::=
	SEQUENCE {
		tpMacAclId
			INTEGER,
		tpMacRuleId
			INTEGER,
		tpMacSecOperation
			INTEGER,
		tpMacSmacAddress
			OCTET STRING,
		tpMacSmacMask
			OCTET STRING,
		tpMacDmacAddress
			OCTET STRING,
		tpMacDmacMask
			OCTET STRING,
		tpMacVlanId
			INTEGER,
		tpMacEtherType
			INTEGER,
		tpMacPri
			INTEGER,
		tpMacTimeSegment
			OCTET STRING,
		tpMacRuleStatus
			TPRowStatus
	}	

	tpMacAclId OBJECT-TYPE
		SYNTAX  INTEGER  
		MAX-ACCESS  read-only
		STATUS  current
		DESCRIPTION
			"MAC ACL ID."
		::= { tpMacRuleEntry 1 }

	tpMacRuleId OBJECT-TYPE
		SYNTAX  INTEGER
		MAX-ACCESS  read-only
		STATUS  current
		DESCRIPTION
			"MAC ACL rule ID."
		::= { tpMacRuleEntry 2 }

	tpMacSecOperation OBJECT-TYPE
		SYNTAX  INTEGER
		{permit(0),deny(1)}
		MAX-ACCESS  read-create
		STATUS  current
		DESCRIPTION
			"MAC ACL Security Operation."
		::= {tpMacRuleEntry 3}
		
	tpMacSmacAddress OBJECT-TYPE
		SYNTAX OCTET STRING
		MAX-ACCESS read-create
		STATUS current
		DESCRIPTION
			"Source MAC address, string length setting to zero means that the source MAC address is disabled."
		::= {tpMacRuleEntry 4}
	
	tpMacSmacMask OBJECT-TYPE
		SYNTAX OCTET STRING
		MAX-ACCESS read-create
		STATUS current
		DESCRIPTION
			"Source Mac Mask, string length setting to zero means that every bit of the mask is 1."
		::= {tpMacRuleEntry 5}
	
	tpMacDmacAddress OBJECT-TYPE
		SYNTAX OCTET STRING
		MAX-ACCESS read-create
		STATUS current
		DESCRIPTION
			"Destination MAC address, string length setting to zero means that the destination MAC address is disabled."
		::= {tpMacRuleEntry 6}

	tpMacDmacMask OBJECT-TYPE
		SYNTAX OCTET STRING
		MAX-ACCESS read-create
		STATUS current
		DESCRIPTION
			"Destination Mac Mask, string length setting to zero means that every bit of the mask is 1."
		::= {tpMacRuleEntry 7}

	tpMacVlanId OBJECT-TYPE
		SYNTAX INTEGER
		MAX-ACCESS read-create
		STATUS current
		DESCRIPTION
			"VLAN ID, 0-4094, value '0' means that the vid field is disabled."
		::= {tpMacRuleEntry 8}	

	tpMacEtherType OBJECT-TYPE
		SYNTAX INTEGER
		MAX-ACCESS read-create
		STATUS current
		DESCRIPTION
			"Ethernet protocol type, 0x0-0x10000.
			Value '65536' or '0x10000' means that the EtherType field is disabled."
		::= {tpMacRuleEntry 9}		

	tpMacPri OBJECT-TYPE
		SYNTAX INTEGER
		MAX-ACCESS read-create
		STATUS current
		DESCRIPTION
			"802.1P priority, 0-8, value '8' means that the priority field is disabled."
		::= {tpMacRuleEntry 10}		

	tpMacTimeSegment OBJECT-TYPE
		SYNTAX OCTET STRING
		MAX-ACCESS read-create
		STATUS current
		DESCRIPTION
			"MAC ACL time segment name(max length: 16), the time segment name must be configured previously and string length setting to zero means that this field is disabled."
		::= {tpMacRuleEntry 11}

	tpMacRuleStatus OBJECT-TYPE
		SYNTAX  TPRowStatus
		MAX-ACCESS  read-create
		STATUS  current
		DESCRIPTION
			"the following two values are states:
			these values may be read or written
			active(1),
			notInService(2),

			the following value is a state:
			this value may be read, but not written
			notReady(3),

			the following three values are
			actions: these values may be written,
			but are never read
			createAndGo(4),
			createAndWait(5),
			destroy(6)"
		::= {tpMacRuleEntry 12}    		

	--STDIP RULE LIST	
		
	tpStdipRuleTable OBJECT-TYPE
	SYNTAX  SEQUENCE OF TPSTDIPRULEENTRY
	MAX-ACCESS  not-accessible
	STATUS  current
	DESCRIPTION
		"A list of standard IP rule entries.
		 Here you can add standard IP ACL rules for further ACL configuration."
	::= {tpAclRuleConfigure 2}

	tpStdipRuleEntry OBJECT-TYPE
	SYNTAX  TPSTDIPRULEENTRY
	MAX-ACCESS  not-accessible
	STATUS  current
	DESCRIPTION
		"An entry contains of the information of STDIP ACL."
	INDEX   {tpStdipAclId,tpStdipRuleId}
	::= {tpStdipRuleTable 1}
	
	TPSTDIPRULEENTRY ::=
	SEQUENCE {	
		tpStdipAclId
			INTEGER,
		tpStdipRuleId
			INTEGER,
		tpStdipSecOperation
			INTEGER,
		tpStdipSipAddress
			IpAddress,
		tpStdipSipMask
			IpAddress,
		tpStdipDipAddress
			IpAddress,
		tpStdipDipMask
			IpAddress,
		tpStdipTimeSegment
			OCTET STRING,
		tpStdipRuleStatus
			TPRowStatus
	}
	
	tpStdipAclId OBJECT-TYPE
		SYNTAX  INTEGER 
		MAX-ACCESS  read-only
		STATUS  current
		DESCRIPTION
			"Standard IP ACL ID."
		::= {tpStdipRuleEntry 1}

	tpStdipRuleId OBJECT-TYPE
		SYNTAX  INTEGER
		MAX-ACCESS  read-only
		STATUS  current
		DESCRIPTION
			"Standard IP ACL rule ID."
		::= {tpStdipRuleEntry 2}

	tpStdipSecOperation OBJECT-TYPE
		SYNTAX  INTEGER
		{permit(0),deny(1)}
		MAX-ACCESS  read-create
		STATUS  current
		DESCRIPTION
			"Standard IP ACL Security Operation."
		::= {tpStdipRuleEntry 3}	
	
	tpStdipSipAddress OBJECT-TYPE
		SYNTAX  IpAddress 
		MAX-ACCESS  read-create
		STATUS  current
		DESCRIPTION
			"Source IP address, value '0.0.0.0' means that the source IP address is disabled."
		::= {tpStdipRuleEntry 4}

	tpStdipSipMask OBJECT-TYPE
		SYNTAX  IpAddress 
		MAX-ACCESS  read-create
		STATUS  current
		DESCRIPTION
			"Source IP Mask, value '0.0.0.0' or zero length means that the mask is 255.255.255.255."
		::= {tpStdipRuleEntry 5}		
	
	tpStdipDipAddress OBJECT-TYPE
		SYNTAX  IpAddress 
		MAX-ACCESS  read-create
		STATUS  current
		DESCRIPTION
			"Destination IP address, value '0.0.0.0' means that the destination IP address is disabled."
		::= {tpStdipRuleEntry 6}

	tpStdipDipMask OBJECT-TYPE
		SYNTAX  IpAddress 
		MAX-ACCESS  read-create
		STATUS  current
		DESCRIPTION
			"Destination IP Mask, value '0.0.0.0' or zero length means that the mask is 255.255.255.255."
		::= {tpStdipRuleEntry 7}

	tpStdipTimeSegment OBJECT-TYPE
		SYNTAX  OCTET STRING 
		MAX-ACCESS  read-create
		STATUS  current
		DESCRIPTION
			"STDIP ACL time segment name(max length: 16), the time segment name must be configured previously and string length setting to zero means that this field is disabled."
		::= {tpStdipRuleEntry 8}
		
	tpStdipRuleStatus OBJECT-TYPE
		SYNTAX  TPRowStatus
		MAX-ACCESS  read-create
		STATUS  current
		DESCRIPTION
			"the following two values are states:
			these values may be read or written
			active(1),
			notInService(2),

			the following value is a state:
			this value may be read, but not written
			notReady(3),

			the following three values are
			actions: these values may be written,
			but are never read
			createAndGo(4),
			createAndWait(5),
			destroy(6)"
		::= {tpStdipRuleEntry 9}

	--EXTIP RULE LIST
	
	tpExtipRuleTable OBJECT-TYPE
	SYNTAX  SEQUENCE OF TPEXTIPRULEENTRY
	MAX-ACCESS  not-accessible
	STATUS  current
	DESCRIPTION
		"A list of extended IP rule entries.
		 Here you can add extended IP ACL rules for further ACL configuration."
	::= {tpAclRuleConfigure 3}

	tpExtipRuleEntry OBJECT-TYPE
	SYNTAX  TPEXTIPRULEENTRY
	MAX-ACCESS  not-accessible
	STATUS  current
	DESCRIPTION
		"An entry contains of the information of EXTIP ACL."
	INDEX   {tpExtipAclId,tpExtipRuleId}
	::= {tpExtipRuleTable 1}	

	TPEXTIPRULEENTRY ::=
	SEQUENCE {				
		tpExtipAclId
			INTEGER,
		tpExtipRuleId
			INTEGER,
		tpExtipSecOperation
			INTEGER,
		tpExtipFragment
			INTEGER,
		tpExtipSipAddress
			IpAddress,
		tpExtipSipMask
			IpAddress,
		tpExtipDipAddress
			IpAddress,
		tpExtipDipMask
			IpAddress,
		tpExtipProtocol
			INTEGER,
		tpExtipTcpFlag
			INTEGER,
		tpExtipSourcePort
			INTEGER,
		tpExtipDestPort
			INTEGER,
		tpExtipDscp
			INTEGER,
		tpExtipTos
			INTEGER,
		tpExtipPre
			INTEGER,
		tpExtipTimeSegment
			OCTET STRING,
		tpExtipRuleStatus
			TPRowStatus
	}
		
	tpExtipAclId OBJECT-TYPE
		SYNTAX  INTEGER 
		MAX-ACCESS  read-only
		STATUS  current
		DESCRIPTION
			"Extended IP ACL ID."
		::= {tpExtipRuleEntry 1}

	tpExtipRuleId OBJECT-TYPE
		SYNTAX  INTEGER
		MAX-ACCESS  read-only
		STATUS  current
		DESCRIPTION
			"Extended IP ACL rule ID."
		::= {tpExtipRuleEntry 2}

	tpExtipSecOperation OBJECT-TYPE
		SYNTAX  INTEGER
		{permit(0),deny(1)}
		MAX-ACCESS  read-create
		STATUS  current
		DESCRIPTION
			"Extended IP ACL Security Operation."
		::= {tpExtipRuleEntry 3}		
		
	tpExtipFragment OBJECT-TYPE
		SYNTAX  INTEGER
		{disable(0),enable(1)}
		MAX-ACCESS  read-create
		STATUS  current
		DESCRIPTION
			"Extended IP fragment, conflicts with all the L4 feature."
		::= {tpExtipRuleEntry 4}		
	
	tpExtipSipAddress OBJECT-TYPE
		SYNTAX  IpAddress
		MAX-ACCESS  read-create
		STATUS  current
		DESCRIPTION
			"Source IP address, value '0.0.0.0' means that the source IP address is disabled."
		::= {tpExtipRuleEntry 5}		

	tpExtipSipMask OBJECT-TYPE
		SYNTAX  IpAddress
		MAX-ACCESS  read-create
		STATUS  current
		DESCRIPTION
			"Source IP Mask, value '0.0.0.0' or zero length means that the mask is 255.255.255.255."
		::= {tpExtipRuleEntry 6}		

	tpExtipDipAddress OBJECT-TYPE
		SYNTAX  IpAddress
		MAX-ACCESS  read-create
		STATUS  current
		DESCRIPTION
			"Destination IP address, value '0.0.0.0' means that the Destination IP address is disabled."
		::= {tpExtipRuleEntry 7}		

	tpExtipDipMask OBJECT-TYPE
		SYNTAX  IpAddress
		MAX-ACCESS  read-create
		STATUS  current
		DESCRIPTION
			"Destination IP Mask, value '0.0.0.0' or zero length means that the mask is 255.255.255.255."
		::= {tpExtipRuleEntry 8}

	tpExtipProtocol OBJECT-TYPE
		SYNTAX INTEGER
		MAX-ACCESS read-create
		STATUS current
		DESCRIPTION
			"L4 protocol type, 0-255, value '0' means this field is disabled.
			This field conflicts with the TCP Flags or the source/destination port numbers 
			when it is not the value '6'(TCP), or '17'(UDP)."
		::= {tpExtipRuleEntry 9}
		
	tpExtipTcpFlag OBJECT-TYPE
		SYNTAX INTEGER
		MAX-ACCESS read-create
		STATUS current
		DESCRIPTION
			"Extended IP TCP flag, this field is described as a bit-map structure:
			There are 12 bits of this field, the higher 6 bits show us whether these TCP flags are enabled(1) or disabled(0).
			The lower 6 bits show us the 6 kind of TCP flags' value (0-1).
			From the highest bit(bit11) to the lowest bit(0), each bit stands for a TCP flag:
			bit11 & bit5 -- URG flag		bit10 & bit4 -- ACK flag
			bit9  & bit3 -- PSH flag		bit8  & bit2 -- RST flag
			bit7  & bit1 -- SYN flag		bit6  & bit0 -- FIN flag"
		::= {tpExtipRuleEntry 10}

	tpExtipSourcePort OBJECT-TYPE
		SYNTAX INTEGER
		MAX-ACCESS read-create
		STATUS current
		DESCRIPTION
			"Extended IP TCP/UDP source port, 0-65536, value '65536' means that this field is disabled."
		::= {tpExtipRuleEntry 11}
			
	tpExtipDestPort OBJECT-TYPE
		SYNTAX INTEGER
		MAX-ACCESS read-create
		STATUS current
		DESCRIPTION
			"Extended IP TCP/UDP destination port, 0-65536, value '65536' means that this field is disabled."			
		::= {tpExtipRuleEntry 12}

	tpExtipDscp OBJECT-TYPE
		SYNTAX INTEGER
		MAX-ACCESS read-create
		STATUS current
		DESCRIPTION
			"Extended IP DSCP, 0-64, value '64' means this field is disabled.
			conflicts with the Tos and Pre."			
		::= {tpExtipRuleEntry 13}

	tpExtipTos OBJECT-TYPE
		SYNTAX INTEGER
		MAX-ACCESS read-create
		STATUS current
		DESCRIPTION
			"Extended IP type of service(ToS), 0-16, value '16' means this field is disabled."			
		::= {tpExtipRuleEntry 14}		
		
	tpExtipPre OBJECT-TYPE
		SYNTAX INTEGER
		MAX-ACCESS read-create
		STATUS current
		DESCRIPTION
			"Extended IP pre, 0-8, value '8' means this field is disabled."			
		::= {tpExtipRuleEntry 15}

	tpExtipTimeSegment OBJECT-TYPE
		SYNTAX  OCTET STRING 
		MAX-ACCESS  read-create
		STATUS  current
		DESCRIPTION
			"EXTIP ACL time segment name(max length: 16), the time segment name must be configured previously and string length setting to zero means that this field is disabled."
		::= {tpExtipRuleEntry 16}
		
	tpExtipRuleStatus OBJECT-TYPE
		SYNTAX  TPRowStatus
		MAX-ACCESS  read-create
		STATUS  current
		DESCRIPTION
			"the following two values are states:
			these values may be read or written
			active(1),
			notInService(2),

			the following value is a state:
			this value may be read, but not written
			notReady(3),

			the following three values are
			actions: these values may be written,
			but are never read
			createAndGo(4),
			createAndWait(5),
			destroy(6)"
		::= {tpExtipRuleEntry 17}

	--CombRuleList
	tpCombRuleTable OBJECT-TYPE
	SYNTAX  SEQUENCE OF TPCOMBRULEENTRY
	MAX-ACCESS  not-accessible
	STATUS  current
	DESCRIPTION
		"A list of combined MAC+IP rule entries.
		 Here you can add combined ACL rules for further ACL configuration."
	::= {tpAclRuleConfigure 4}

	tpCombRuleEntry OBJECT-TYPE
	SYNTAX  TPCOMBRULEENTRY
	MAX-ACCESS  not-accessible
	STATUS  current
	DESCRIPTION
		"An entry contains of the information of Combined ACL."
	INDEX   {tpCombAclId,tpCombRuleId}
	::= {tpCombRuleTable 1}	
	
	TPCOMBRULEENTRY ::=
	SEQUENCE {	
		tpCombAclId
			INTEGER,
		tpCombRuleId
			INTEGER,
		tpCombSecOperation
			INTEGER,
		tpCombSmacAddress
			OCTET STRING,
		tpCombSmacMask
			OCTET STRING,
		tpCombDmacAddress
			OCTET STRING,
		tpCombDmacMask
			OCTET STRING,
		tpCombVlanId
			INTEGER,
		tpCombEtherType
			INTEGER,
		tpCombPri
			INTEGER,
		tpCombSipAddress
			IpAddress,
		tpCombSipMask
			IpAddress,
		tpCombDipAddress
			IpAddress,
		tpCombDipMask
			IpAddress,
		tpCombTimeSegment
			OCTET STRING,
		tpCombRuleStatus
			TPRowStatus
	}

	tpCombAclId OBJECT-TYPE
		SYNTAX  INTEGER 
		MAX-ACCESS  read-only
		STATUS  current
		DESCRIPTION
			"Combined MAC+IP ACL ID."
		::= {tpCombRuleEntry 1}

	tpCombRuleId OBJECT-TYPE
		SYNTAX  INTEGER
		MAX-ACCESS  read-only
		STATUS  current
		DESCRIPTION
			"Combined ACL rule ID."
		::= {tpCombRuleEntry 2}

	tpCombSecOperation OBJECT-TYPE
		SYNTAX  INTEGER
		{permit(0),deny(1)}
		MAX-ACCESS  read-create
		STATUS  current
		DESCRIPTION
			"Combined ACL Security Operation."
		::= {tpCombRuleEntry 3}		
	
	tpCombSmacAddress OBJECT-TYPE
		SYNTAX OCTET STRING
		MAX-ACCESS read-create
		STATUS current
		DESCRIPTION
			"Source MAC address, string length setting to zero means that the source MAC address is disabled."
		::= {tpCombRuleEntry 4}
		
	tpCombSmacMask OBJECT-TYPE
		SYNTAX OCTET STRING
		MAX-ACCESS read-create
		STATUS current
		DESCRIPTION
			"Source MAC Mask, string length setting to zero means that every bit of the mask is 1."
		::= {tpCombRuleEntry 5}	
		
	tpCombDmacAddress OBJECT-TYPE
		SYNTAX OCTET STRING
		MAX-ACCESS read-create
		STATUS current
		DESCRIPTION
			"Destination MAC address, string length setting to zero means that the destination MAC address is disabled."
		::= {tpCombRuleEntry 6}
		
	tpCombDmacMask OBJECT-TYPE
		SYNTAX OCTET STRING
		MAX-ACCESS read-create
		STATUS current
		DESCRIPTION
			"Destination MAC Mask, string length setting to zero means that every bit of the mask is 1."
		::= {tpCombRuleEntry 7}	
		
	tpCombVlanId OBJECT-TYPE
		SYNTAX INTEGER
		MAX-ACCESS read-create
		STATUS current
		DESCRIPTION
			"VLAN ID, 0-4094, value '0' means that the vid field is disabled."
		::= {tpCombRuleEntry 8}	
		
	tpCombEtherType OBJECT-TYPE
		SYNTAX INTEGER
		MAX-ACCESS read-create
		STATUS current
		DESCRIPTION
			"Ethernet protocol type, 0x0-0x10000.
			Value '65536' or '0x10000' means that the EtherType field is disabled."
		::= {tpCombRuleEntry 9}

	tpCombPri OBJECT-TYPE
		SYNTAX INTEGER
		MAX-ACCESS read-create
		STATUS current
		DESCRIPTION
			"802.1P priority, 0-8, value '8' means that the priority field is disabled."
		::= {tpCombRuleEntry 10}

	tpCombSipAddress OBJECT-TYPE
		SYNTAX IpAddress
		MAX-ACCESS read-create
		STATUS current
		DESCRIPTION
			"Source IP address, value '0.0.0.0' means that the source IP address is disabled."
		::= {tpCombRuleEntry 11}
	
	tpCombSipMask OBJECT-TYPE
		SYNTAX IpAddress
		MAX-ACCESS read-create
		STATUS current
		DESCRIPTION
			"Source IP mask, value '0.0.0.0' or zero length means that the mask is 255.255.255.255."
		::= {tpCombRuleEntry 12}

	tpCombDipAddress OBJECT-TYPE
		SYNTAX IpAddress
		MAX-ACCESS read-create
		STATUS current
		DESCRIPTION
			"Destination IP address, value '0.0.0.0' means that the destination IP address is disabled."
		::= {tpCombRuleEntry 13}
	
	tpCombDipMask OBJECT-TYPE
		SYNTAX IpAddress
		MAX-ACCESS read-create
		STATUS current
		DESCRIPTION
			"Destination IP mask, value '0.0.0.0' or zero length means that the mask is 255.255.255.255."
		::= {tpCombRuleEntry 14}	

	tpCombTimeSegment OBJECT-TYPE
		SYNTAX OCTET STRING
		MAX-ACCESS read-create
		STATUS current
		DESCRIPTION
			"Combined ACL time segment name(max length: 16), the time segment name must be configured previously and string length setting to zero means that this field is disabled."
		::= {tpCombRuleEntry 15}
		
	tpCombRuleStatus OBJECT-TYPE
		SYNTAX  TPRowStatus
		MAX-ACCESS  read-create
		STATUS  current
		DESCRIPTION
			"the following two values are states:
			these values may be read or written
			active(1),
			notInService(2),

			the following value is a state:
			this value may be read, but not written
			notReady(3),

			the following three values are
			actions: these values may be written,
			but are never read
			createAndGo(4),
			createAndWait(5),
			destroy(6)"
		::= {tpCombRuleEntry 16}
		
	--IPv6 Rule List
	
	tpIPv6RuleTable OBJECT-TYPE
	SYNTAX  SEQUENCE OF TPIPV6RULEENTRY
	MAX-ACCESS  not-accessible
	STATUS  current
	DESCRIPTION
		"A list of IPv6 rule entries.
		 Here you can add IPv6 ACL rules for further ACL configuration."
	::= {tpAclRuleConfigure 5}

	tpIPv6RuleEntry OBJECT-TYPE
	SYNTAX  TPIPV6RULEENTRY
	MAX-ACCESS  not-accessible
	STATUS  current
	DESCRIPTION
		"An entry contains of the information of IPv6 ACL."
	INDEX   {tpIPv6AclId,tpIPv6RuleId}
	::= {tpIPv6RuleTable 1}	
	
	TPIPV6RULEENTRY ::=
	SEQUENCE {	
		tpIPv6AclId
			INTEGER,
		tpIPv6RuleId
			INTEGER,
		tpIPv6SecOperation
			INTEGER,
		tpIPv6TrafficClass
			INTEGER,
		tpIPv6FlowLabel
			INTEGER,
		tpIPv6SipAddress
			OCTET STRING,
		tpIPv6SipMask
			OCTET STRING,
		tpIPv6DipAddress
			OCTET STRING,
		tpIPv6DipMask
			OCTET STRING,
		tpIPv6SourcePort
			INTEGER,
		tpIPv6DestPort
			INTEGER,
		tpIPv6TimeSegment
			OCTET STRING,
		tpIPv6RuleStatus
			TPRowStatus
	}	
	
	tpIPv6AclId OBJECT-TYPE
		SYNTAX  INTEGER 
		MAX-ACCESS  read-only
		STATUS  current
		DESCRIPTION
			"IPv6 ACL ID."
		::= {tpIPv6RuleEntry 1}

	tpIPv6RuleId OBJECT-TYPE
		SYNTAX  INTEGER
		MAX-ACCESS  read-only
		STATUS  current
		DESCRIPTION
			"IPv6 ACL rule ID."
		::= {tpIPv6RuleEntry 2}

	tpIPv6SecOperation OBJECT-TYPE
		SYNTAX  INTEGER
		{permit(0),deny(1)}
		MAX-ACCESS  read-create
		STATUS  current
		DESCRIPTION
			"IPv6 ACL Security Operation."
		::= {tpIPv6RuleEntry 3}		
		
	tpIPv6TrafficClass OBJECT-TYPE
		SYNTAX  INTEGER
		MAX-ACCESS  read-create
		STATUS  current
		DESCRIPTION
			"Traffic Class DSCP, 0-64, value '64' means that this field is disabled."
		::= {tpIPv6RuleEntry 4}	

	tpIPv6FlowLabel OBJECT-TYPE
		SYNTAX INTEGER
		MAX-ACCESS read-create
		STATUS current
		DESCRIPTION
			"IPv6 Flow Label, 0x0-0x100000, value '0x100000' or '1048576' means that this field is disabled."
		::= {tpIPv6RuleEntry 5}
		
	tpIPv6SipAddress OBJECT-TYPE
		SYNTAX OCTET STRING
		MAX-ACCESS read-create
		STATUS current
		DESCRIPTION
			"IPv6 source IP address, only upper 64 bits supported; the all-zero address means that the source IPv6 address is disabled."
		::= {tpIPv6RuleEntry 6}
	
	tpIPv6SipMask OBJECT-TYPE
		SYNTAX OCTET STRING
		MAX-ACCESS read-create
		STATUS current
		DESCRIPTION
			"IPv6 source IP mask, 64 bits, format: ffff:ffff:ffff:ffff; zero length means that every bit of the mask is 1."
		::= {tpIPv6RuleEntry 7}
		
	tpIPv6DipAddress OBJECT-TYPE
		SYNTAX OCTET STRING
		MAX-ACCESS read-create
		STATUS current
		DESCRIPTION
			"IPv6 destination IP address, only upper 64 bits supported; the all-zero address means that the destination IPv6 address is disabled."
		::= {tpIPv6RuleEntry 8}
	
	tpIPv6DipMask OBJECT-TYPE
		SYNTAX OCTET STRING
		MAX-ACCESS read-create
		STATUS current
		DESCRIPTION
			"IPv6 destination IP mask, 64 bits, format: ffff:ffff:ffff:ffff; zero length means that every bit of the mask is 1."
		::= {tpIPv6RuleEntry 9}
		
	tpIPv6SourcePort OBJECT-TYPE
		SYNTAX INTEGER
		MAX-ACCESS read-create
		STATUS current
		DESCRIPTION
			"IPv6 L4 source port, 0-65536, value '65536' means that this field is disabled."
		::= {tpIPv6RuleEntry 10}		
			
	tpIPv6DestPort OBJECT-TYPE
		SYNTAX INTEGER
		MAX-ACCESS read-create
		STATUS current
		DESCRIPTION
			"IPv6 L4 destination port, 0-65536, value '65536' means that this field is disabled."
		::= {tpIPv6RuleEntry 11}
		
	tpIPv6TimeSegment OBJECT-TYPE
		SYNTAX OCTET STRING
		MAX-ACCESS read-create
		STATUS current
		DESCRIPTION
			"IPv6 ACL time segment name(max length: 16), the time segment name must be configured previously and string length setting to zero means that this field is disabled."
		::= {tpIPv6RuleEntry 12}
		
	tpIPv6RuleStatus OBJECT-TYPE
		SYNTAX  TPRowStatus
		MAX-ACCESS  read-create
		STATUS  current
		DESCRIPTION
			"the following two values are states:
			these values may be read or written
			active(1),
			notInService(2),

			the following value is a state:
			this value may be read, but not written
			notReady(3),

			the following three values are
			actions: these values may be written,
			but are never read
			createAndGo(4),
			createAndWait(5),
			destroy(6)"
		::= {tpIPv6RuleEntry 13}
		
END
