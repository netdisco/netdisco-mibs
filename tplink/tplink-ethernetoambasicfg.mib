TPLINK-ETHERNETOAMBASICCFG-MIB DEFINITIONS ::= BEGIN
		IMPORTS
			OBJECT-TYPE				FROM SNMPv2-SMI
			ethernetOamBasicConfig	FROM TPLINK-ETHERNETOAM-MIB
			DisplayString
							FROM SNMPv2-TC
			ifIndex
							FROM RFC1213-MIB;

		ethernetOamBasicCfgTable OBJECT-TYPE
			SYNTAX SEQUENCE OF EthernetOamBasicCfgEntry
			MAX-ACCESS	not-accessible
			STATUS	current
			DESCRIPTION
			"A table that contains the basic configuration of each port.
			Operations, Administration and Maintenance (OAM) is a Layer 2 protocol, used to monitor and solve network problems.
			OAM can report the network state at the data link layer so that a network administrator can manage the network effectively.
			Ethernet OAM is used to solve OAM problems on Ethernet equipment in the last mile."
			::= {ethernetOamBasicConfig 1}

		ethernetOamBasicCfgEntry OBJECT-TYPE
			SYNTAX EthernetOamBasicCfgEntry      
			MAX-ACCESS	not-accessible
			STATUS	current
			DESCRIPTION
			"An entry that contains the basic configuration of each port."
			INDEX {ifIndex}
			::= {ethernetOamBasicCfgTable 1}

		EthernetOamBasicCfgEntry ::=
		SEQUENCE
		{
			ethernetOamBasicCfgPort			DisplayString,
			ethernetOamBasicCfgMode			INTEGER,
			ethernetOamBasicCfgState		INTEGER,
			ethernetOamBasicCfgLAG			OCTET STRING(SIZE(0..10))
		}

		ethernetOamBasicCfgPort OBJECT-TYPE
			SYNTAX DisplayString
			MAX-ACCESS	read-only
			STATUS	current
			DESCRIPTION
			"Displays the port number."
			::= {ethernetOamBasicCfgEntry 1}

		ethernetOamBasicCfgMode OBJECT-TYPE
			SYNTAX INTEGER {passive(0),active(1)}
			MAX-ACCESS	read-write
			STATUS	current
			DESCRIPTION
			"Select mode of Ethernet OAM client."
			::= {ethernetOamBasicCfgEntry 2}

		ethernetOamBasicCfgState OBJECT-TYPE
			SYNTAX INTEGER {disable(0),enable(1)}
			MAX-ACCESS	read-write
			STATUS	current
			DESCRIPTION
			"Select state of Ethernet OAM function."
			::= {ethernetOamBasicCfgEntry 3}

		ethernetOamBasicCfgLAG OBJECT-TYPE
			SYNTAX OCTET STRING(SIZE(0..10))
			MAX-ACCESS	read-only
			STATUS	current
			DESCRIPTION
			"Displays the LAG number of the port."
			::= {ethernetOamBasicCfgEntry 4}

END
