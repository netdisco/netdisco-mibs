TPLINK-NDP-MIB DEFINITIONS ::= BEGIN
		IMPORTS
		  OBJECT-TYPE
			  	         	FROM SNMPv2-SMI
		  ifIndex						
						    FROM RFC1213-MIB
							        	  	         	
		  ndpManage
							FROM TPLINK-CLUSTER-MIB;
																
	    ndpGlobalConfig OBJECT IDENTIFIER ::= {ndpManage 1}
	    
	    ndpStatus	OBJECT-TYPE
	    	SYNTAX
	    		INTEGER
	    		{
	    			disable(0),
	    			enable(1)
	    		}
	    	MAX-ACCESS 	read-write
	    	STATUS			current
	    	DESCRIPTION	
	    	"This object indicates the global status of the ndp."
	    	::= {ndpGlobalConfig 1}
	    	
	    ndpAgingTime	OBJECT-TYPE
	    	SYNTAX 			INTEGER(5..255)
	    	MAX-ACCESS	read-write
	    	STATUS			current
	    	DESCRIPTION	
	    	"This object indicates the period for the switch to keep the NDP
	    	packets from the neighbor switch. The minimum value is 5, maximum
	    	value is 255."
	    	::= {ndpGlobalConfig 2}
	    	
	    ndpHelloTime	OBJECT-TYPE
	    	SYNTAX			INTEGER(5..254)
	    	MAX-ACCESS	read-write
	    	STATUS			current
	    	DESCRIPTION	
	    	"This object indicates the interval time of the switch in second
	    	to periodical send out ndp packet. The minimum valus is 5, maximum
	    	value is 254."
	    	::= {ndpGlobalConfig 3}
	    	
	   	ndpPortTable OBJECT-TYPE
	   		SYNTAX			SEQUENCE OF NdpPortEntry
	   		MAX-ACCESS	not-accessible
	   		STATUS			current
	   		DESCRIPTION	
	   		"A table that contains information about the ndp status of every port."
	   		::=	{ndpManage 2}
	   		
	   	ndpPortEntry 	OBJECT-TYPE
	   		SYNTAX			NdpPortEntry
	   		MAX-ACCESS	not-accessible
	   		STATUS			current
	   		DESCRIPTION	
	   		"A list of information about the ndp status."
	   		INDEX{ifIndex}
	   		::= {ndpPortTable 1}
	   	
	   	NdpPortEntry ::=
	   	SEQUENCE
	   	{
	   		ndpPortStatus
	   			INTEGER,
	   		ndpPortRecvPkt
	   			INTEGER,
	   		ndpPortSendPkt
	   			INTEGER,
	   		ndpPortErrPkt
	   			INTEGER,
	   		ndpPortNeighborNum
	   			INTEGER
	   	}
	   	
	   		
	   	ndpPortStatus	OBJECT-TYPE
	   		SYNTAX			
	   			INTEGER
	   			{
	   				disable(0),
	   				enable(1)
	   			}
	   		MAX-ACCESS	read-write
	   		STATUS			current
	   		DESCRIPTION	
	   		"This object indicates the ndp status of the port."
	   		::=	{ndpPortEntry 2}
	   		
	   	ndpPortRecvPkt OBJECT-TYPE
	   		SYNTAX			INTEGER
	   		MAX-ACCESS	read-only
	   		STATUS			current
	   		DESCRIPTION	
	   		"This object indicates the ndp packet that the port have receive."
	   		::=	{ndpPortEntry 3}
	   		
	   	ndpPortSendPkt	OBJECT-TYPE
	   		SYNTAX			INTEGER
	   		MAX-ACCESS	read-only
	   		STATUS			current
	   		DESCRIPTION	
	   		"This object indicates the ndp packet that the port have send."
	   		::=	{ndpPortEntry 4}
	   		
	   	ndpPortErrPkt		OBJECT-TYPE
	   		SYNTAX			INTEGER
	   		MAX-ACCESS	read-only
	   		STATUS			current
	   		DESCRIPTION	
	   		"This objcet indicates the error ndp packet that the port have receive."
	   		::=	{ndpPortEntry 5}
	   		
	   	ndpPortNeighborNum	OBJECT-TYPE
	   		SYNTAX			INTEGER
	   		MAX-ACCESS	read-only
	   		STATUS			current
	   		DESCRIPTION	
	   		"This object indicates the number of the neighbor."
	   		::= {ndpPortEntry 6}          
END
