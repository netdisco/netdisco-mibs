TPLINK-ARP-INSPECTION-MIB DEFINITIONS ::= BEGIN

       IMPORTS
       		MODULE-IDENTITY
        	  	         	FROM SNMPv2-SMI
            tplinkMgmt
					FROM TPLINK-MIB;
         

		tplinkArpInspectionMIB MODULE-IDENTITY
		LAST-UPDATED    "201212130930Z"
		ORGANIZATION    "TPLINK"
		CONTACT-INFO    "www.tplink.com.cn"
		DESCRIPTION	    "Private MIB for Arp Inspection configuration."
		REVISION        "201212130930Z"
		DESCRIPTION
				"Initial version of this MIB module."
		::= { tplinkMgmt 28 }	
		
		tplinkArpInspectionMIBObjects 		OBJECT IDENTIFIER ::= {tplinkArpInspectionMIB 1}
		tplinkArpInspectionNotifications 	OBJECT IDENTIFIER ::= {tplinkArpInspectionMIB 2}
 END
