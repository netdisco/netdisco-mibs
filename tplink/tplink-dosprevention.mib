TPLINK-DOS-PREVENTION-MIB DEFINITIONS ::= BEGIN

         IMPORTS
            OBJECT-TYPE
          	  	         	FROM SNMPv2-SMI          	 
           tplinkMgmt
					FROM TPLINK-MIB;
         
		tplinkDosPreventionMIB MODULE-IDENTITY
		LAST-UPDATED    "201212130930Z"
		ORGANIZATION    "TPLINK"
		CONTACT-INFO    "www.tplink.com.cn"
		DESCRIPTION	    "Private MIB for DoS Defend configuration."
		REVISION        "201212130930Z"
		DESCRIPTION
				"Initial version of this MIB module."
		::= { tplinkMgmt 30 }
		
		tplinkDosPreventionMIBObjects	OBJECT IDENTIFIER	::= { tplinkDosPreventionMIB 1 }
		tplinkDosPreventionNotifications	OBJECT IDENTIFIER	::= { tplinkDosPreventionMIB 2 }
		
		tpDosDefendGlobalConfig		OBJECT IDENTIFIER ::= {tplinkDosPreventionMIBObjects 1}
        tpDosDefendList 			OBJECT IDENTIFIER ::= {tplinkDosPreventionMIBObjects 2}
  			
			tpDosDefendGlobalEnable OBJECT-TYPE
	        SYNTAX  INTEGER{
	      		disable(0), 						
	      		enable(1)						
	      		}
	            MAX-ACCESS  read-write
	            STATUS  current
	            DESCRIPTION
	                    "0. disable 
	                     1. enable
	                     Allows you to Enable/Disable DoS Defend function."
	            ::= { tpDosDefendGlobalConfig 1 }
           
       
       -- the dos defend index config
        
       tpDosDefendListTable OBJECT-TYPE
          SYNTAX  SEQUENCE OF TPDOSDEFENDLISTENTRY
          MAX-ACCESS  not-accessible
          STATUS  current
          DESCRIPTION
                  "A list of dos defend config entries.
                   Here you can view and select the Defend Type for the switch."
          ::= { tpDosDefendList 1 }

      tpDosDefendListEntry OBJECT-TYPE
          SYNTAX  TPDOSDEFENDLISTENTRY
          MAX-ACCESS  not-accessible
          STATUS  current
          DESCRIPTION
                  "An entry contains of the information of dos defend index config."
          INDEX   { tpDosDefendListIndex }
          ::= { tpDosDefendListTable 1 }
  
      TPDOSDEFENDLISTENTRY ::=
          SEQUENCE {
							tpDosDefendListIndex
									INTEGER, 
							tpDosDefendListType
									OCTET STRING, 
							tpDosDefendListEntryEnable
									INTEGER
          }
          
      tpDosDefendListIndex OBJECT-TYPE
          SYNTAX  INTEGER  
          MAX-ACCESS  read-only
          STATUS  current
          DESCRIPTION
                  "dos defend entry index"
          ::= { tpDosDefendListEntry 1 }
      
      tpDosDefendListType OBJECT-TYPE
          SYNTAX  OCTET STRING
          MAX-ACCESS  read-only
          STATUS  current
          DESCRIPTION
                  "dos defend entry name"
          ::= { tpDosDefendListEntry 2 }
          
      tpDosDefendListEntryEnable OBJECT-TYPE
          SYNTAX  INTEGER{
      		disable(0), 						
      		enable(1)			
      		}
          MAX-ACCESS  read-write
          STATUS  current
          DESCRIPTION
                  "0. disable
                   1. enable"
          ::= { tpDosDefendListEntry 3 }
     
END
