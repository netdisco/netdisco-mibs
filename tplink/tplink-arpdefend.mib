TPLINK-ARP-DEFEND-MIB DEFINITIONS ::= BEGIN

         IMPORTS
            OBJECT-TYPE
          	  	        FROM SNMPv2-SMI
			ifIndex
						FROM  RFC1213-MIB
			tplinkArpInspectionMIBObjects	          
          	  	          FROM TPLINK-ARP-INSPECTION-MIB; 
          	
			tpArpDefend OBJECT IDENTIFIER ::= {tplinkArpInspectionMIBObjects 2}	
			
			tpArpDefendConfig  	OBJECT IDENTIFIER ::= {tpArpDefend 1}
             
        -- the arp defend  config
         tpArpDefendConfigTable OBJECT-TYPE
            SYNTAX  SEQUENCE OF TPARPDEFENDCONFIGENTRY
            MAX-ACCESS  not-accessible
            STATUS  current
            DESCRIPTION
                    "A list of arp defend config entries.
                     Here you can configure the ARP Defend feature."
            ::= { tpArpDefendConfig 1 }
         
        tpArpDefendConfigEntry OBJECT-TYPE
            SYNTAX  TPARPDEFENDCONFIGENTRY
            MAX-ACCESS  not-accessible
            STATUS  current
            DESCRIPTION
                    "An entry contains of the information of arp defend attack config."
            INDEX   { ifIndex }
            ::= { tpArpDefendConfigTable 1 }
    
        TPARPDEFENDCONFIGENTRY ::=
            SEQUENCE {
								tpArpDefendConfigPort
										OCTET STRING,
								tpArpDefendConfigEnable
										INTEGER,
								tpArpDefendConfigRate
										INTEGER,
								tpArpDefendConfigState
										OCTET STRING,
								tpArpDefendConfigPortLag
										OCTET STRING
            }
            
        tpArpDefendConfigPort OBJECT-TYPE
            SYNTAX  OCTET STRING
            MAX-ACCESS  read-only
            STATUS  current
            DESCRIPTION
                    "port number"
            ::= { tpArpDefendConfigEntry 1 }
        
        tpArpDefendConfigEnable OBJECT-TYPE
            SYNTAX  INTEGER{
	      		enable(1),
	      		disable(0)					
	      		}
            MAX-ACCESS  read-write
            STATUS  current
            DESCRIPTION
                    "0. disable
                     1. enable
                     Select Enable/Disable the ARP Defend feature for the port. "
            ::= { tpArpDefendConfigEntry 2 }
       
       tpArpDefendConfigRate OBJECT-TYPE
            SYNTAX  INTEGER  
            MAX-ACCESS  read-write
            STATUS  current
            DESCRIPTION
                    "specify the maximum amount of the received ARP packets per second.(10-100pps)"
            ::= { tpArpDefendConfigEntry 3 }
            
       tpArpDefendConfigState OBJECT-TYPE
           	SYNTAX  OCTET STRING
            MAX-ACCESS  read-only
            STATUS  current
            DESCRIPTION
                    "the state of port, when the rate exceed, the port will discard the arp pkt."
            ::= { tpArpDefendConfigEntry 4 }
            
      tpArpDefendConfigPortLag OBJECT-TYPE
            SYNTAX  OCTET STRING  
            MAX-ACCESS  read-only
            STATUS  current
            DESCRIPTION
                    "the lag the port belong to"
            ::= { tpArpDefendConfigEntry 5 }
END
