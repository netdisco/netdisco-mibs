TPLINK-STATICARP-MIB	DEFINITIONS ::= BEGIN	
    IMPORTS
	    TPRowStatus       	 
  			FROM TPLINK-TC-MIB
		tplinkMgmt
			FROM TPLINK-MIB			
        OBJECT-TYPE,IpAddress
          	FROM SNMPv2-SMI;
          	  	          
    MacAddress ::= OCTET STRING (SIZE (6))
	
	tplinkStaticARPMIB MODULE-IDENTITY
		LAST-UPDATED    "201411241442Z"
		ORGANIZATION    "TPLINK"
		CONTACT-INFO    "www.tplink.com.cn"
		DESCRIPTION	    "Private MIB for static ARP configuration."
		REVISION        "201411241442Z"
		DESCRIPTION
				"Initial version of this MIB module."
		::= { tplinkMgmt 54 }
		
	tplinkStaticARPMIBObjects		OBJECT IDENTIFIER	::= { tplinkStaticARPMIB 1 }
	tplinkStaticARPNotifications	OBJECT IDENTIFIER	::= { tplinkStaticARPMIB 2 }
	
	--**************
	--Set static ARP
	--**************
		
    tpStaticARPConfig 		OBJECT IDENTIFIER ::= {tplinkStaticARPMIBObjects 1}
    
	tpStaticARPConfigTable OBJECT-TYPE
        SYNTAX  SEQUENCE OF STATICITEMCTRLENTRY
        MAX-ACCESS  not-accessible
        STATUS  current
        DESCRIPTION
            "A list of static ARP entries.ARP Presented here is a protocol that allows dynamic
			distribution of the information needed to build tables to
			translate an address A in protocol P's address space into a
			48.bit Ethernet address."
        ::= { tpStaticARPConfig 1 }
        
    tpStaticARPConfigEntry OBJECT-TYPE
        SYNTAX  STATICITEMCTRLENTRY
        MAX-ACCESS  not-accessible
        STATUS  current
        DESCRIPTION
            "The item can be added or removed ."
        INDEX   { tpStaticARPItemIp }
        ::= { tpStaticARPConfigTable 1 }
              
              
    STATICITEMCTRLENTRY ::=
        SEQUENCE {
            tpStaticARPItemIp
                IpAddress, 
            tpStaticARPItemMac
                OCTET STRING (SIZE (0..20)),  
            tpStaticArpItemInterfaceName
                OCTET STRING (SIZE (0..255)),
            tpStaticARPItemStatus
                TPRowStatus
        }
              
    tpStaticARPItemIp OBJECT-TYPE
        SYNTAX  IpAddress  
        MAX-ACCESS  read-only
        STATUS  current
        DESCRIPTION
            "The ip Address of the ARP entry."
        ::= { tpStaticARPConfigEntry 1 }
            
    tpStaticARPItemMac  OBJECT-TYPE
        SYNTAX  OCTET STRING (SIZE (0..20))  
        MAX-ACCESS  read-create
        STATUS  current
        DESCRIPTION
            "The Mac (hardware) address of the ARP entry."
        ::= { tpStaticARPConfigEntry 2 }         
        
    tpStaticArpItemInterfaceName  OBJECT-TYPE
		SYNTAX  OCTET STRING (SIZE (0..255))  
		MAX-ACCESS  read-only
		STATUS  current
		DESCRIPTION
			"The name of the interface."
		::= { tpStaticARPConfigEntry 3 }
		      			      
	tpStaticARPItemStatus OBJECT-TYPE
        SYNTAX  TPRowStatus
        MAX-ACCESS  read-create
        STATUS  current
        DESCRIPTION
            " The following values are states:
             these values may be used as follow:
             active(1),if the entry is being used.
             notInService(2),destory the entry.
             notReady(3),destory the entry.
             createAndGo(4),not being used
             createAndWait(5),creat a new entry
             destroy(6),destory the entry."
        ::={tpStaticARPConfigEntry 4}        	
     
END
