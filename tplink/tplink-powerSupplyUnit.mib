TPLINK-POWERSUPPLYUNIT-MIB DEFINITIONS ::= BEGIN

         IMPORTS
            MODULE-IDENTITY, OBJECT-TYPE, NOTIFICATION-TYPE
          	  	        FROM SNMPv2-SMI			
            tplinkMgmt
						FROM TPLINK-MIB; 
				
			tplinkPowerSupplyUnitMIB MODULE-IDENTITY
				LAST-UPDATED    "201212171014Z"
				ORGANIZATION    "TPLINK"
				CONTACT-INFO    "www.tplink.com"
				DESCRIPTION	    "Private MIB for Power Supply Unit configuration."
				REVISION        "201212171014Z"
				DESCRIPTION
				"Initial version of this MIB module."
			::= { tplinkMgmt 88 }
		
			tplinkPowerSupplyUnitMIBObjects		OBJECT IDENTIFIER	::= { tplinkPowerSupplyUnitMIB 1 }
			tplinkPowerSupplyUnitNotifications		OBJECT IDENTIFIER	::= { tplinkPowerSupplyUnitMIB 2 }
                
  			powerSupplyUnitGlobalConfig		OBJECT IDENTIFIER	::= { tplinkPowerSupplyUnitMIBObjects 1 }
				
				powerSupplyUnitCapacity OBJECT-TYPE
	          		SYNTAX  INTEGER
	            MAX-ACCESS  read-write
	            STATUS  current
	            DESCRIPTION
	                    "Configure power supply unit maximum battery capacity."
	            ::= { powerSupplyUnitGlobalConfig 1 }
				
				powerSupplyUnitRemainingTime OBJECT-TYPE
	          		SYNTAX  INTEGER
	            MAX-ACCESS  read-only
	            STATUS  current
	            DESCRIPTION
	                    "Display device remaining time in miniute."
	            ::= { powerSupplyUnitGlobalConfig 2 }
				
				powerSupplyUnitInternalPower OBJECT-TYPE
	          		SYNTAX  OCTET STRING
	            MAX-ACCESS  read-only
	            STATUS  current
	            DESCRIPTION
	                    "Display device internal(main) power status."
	            ::= { powerSupplyUnitGlobalConfig 3}
				
				powerSupplyUnitExternalPower OBJECT-TYPE
	          		SYNTAX  OCTET STRING
	            MAX-ACCESS  read-only
	            STATUS  current
	            DESCRIPTION
	                    "Display device external(backup) power status."
	            ::= { powerSupplyUnitGlobalConfig 4}
				
		   powerSupplyUnitStatusChangeTrap NOTIFICATION-TYPE	   
				STATUS          current
				DESCRIPTION 
					"A notification is sent when power supply unit status change."
				::= { tplinkPowerSupplyUnitNotifications 1}
END
