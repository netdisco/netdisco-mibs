TPLINK-ETHERNETOAMPDUSTAT-MIB DEFINITIONS ::= BEGIN
		IMPORTS
			OBJECT-TYPE					FROM SNMPv2-SMI
			Counter						FROM RFC1155-SMI
			ethernetOamStatistics		FROM TPLINK-ETHERNETOAM-MIB
			DisplayString
							FROM SNMPv2-TC
			ifIndex
							FROM RFC1213-MIB;

		ethernetOamPduStatTable OBJECT-TYPE
			SYNTAX SEQUENCE OF EthernetOamPduStatEntry
			MAX-ACCESS	not-accessible
			STATUS	current
			DESCRIPTION
			"A table that contains the Ethernet OAM traffic information of each port."
			::= {ethernetOamStatistics 1}

		ethernetOamPduStatEntry OBJECT-TYPE
			SYNTAX EthernetOamPduStatEntry      
			MAX-ACCESS	not-accessible
			STATUS	current
			DESCRIPTION
			"An entry that contains the Ethernet OAM traffic information of each port."
			INDEX {ifIndex}
			::= {ethernetOamPduStatTable 1}

		EthernetOamPduStatEntry ::=
		SEQUENCE
		{
			ethernetOamPduStatPort					DisplayString,
			ethernetOamPduStatClear					INTEGER,
			ethernetOamPduStatInfoTx				Counter,
			ethernetOamPduStatInfoRx				Counter,
			ethernetOamPduStatUniEventTx			Counter,
			ethernetOamPduStatUniEventRx			Counter,
			ethernetOamPduStatDupEventTx			Counter,
			ethernetOamPduStatDupEventRx			Counter,
            ethernetOamPduStatVarReqTx				Counter,
			ethernetOamPduStatVarReqRx				Counter,
			ethernetOamPduStatVarRespTx				Counter,
			ethernetOamPduStatVarRespRx				Counter,
			ethernetOamPduStatLoopbackCtrlTx		Counter,
			ethernetOamPduStatLoopbackCtrlRx		Counter,
			ethernetOamPduStatOrgSpecTx				Counter,
			ethernetOamPduStatOrgSpecRx				Counter,
			ethernetOamPduStatUnsupportedTx			Counter,
			ethernetOamPduStatUnsupportedRx			Counter,
			ethernetOamPduStatFrmLostDueToOam		Counter
		}

		ethernetOamPduStatPort OBJECT-TYPE
			SYNTAX DisplayString
			MAX-ACCESS	read-only
			STATUS	current
			DESCRIPTION
			"Displays the port number."
			::= {ethernetOamPduStatEntry 1}

		ethernetOamPduStatClear OBJECT-TYPE
			SYNTAX INTEGER {unchanged(0),clear(1)}
			MAX-ACCESS	read-write
			STATUS	current
			DESCRIPTION
			"Clear the statistics of OAMPDUs."
			::= {ethernetOamPduStatEntry 2}

		ethernetOamPduStatInfoTx OBJECT-TYPE
			SYNTAX Counter
			MAX-ACCESS	read-only
			STATUS	current
			DESCRIPTION
			"Displays the number of information OAMPDUs transmitted on the port."
			::= {ethernetOamPduStatEntry 3}

		ethernetOamPduStatInfoRx OBJECT-TYPE
			SYNTAX Counter
			MAX-ACCESS	read-only
			STATUS	current
			DESCRIPTION
			"Displays the number of information OAMPDUs received on the port."
			::= {ethernetOamPduStatEntry 4}

		ethernetOamPduStatUniEventTx OBJECT-TYPE
			SYNTAX Counter
			MAX-ACCESS	read-only
			STATUS	current
			DESCRIPTION
			"Displays the number of unique event notification OAMPDUs transmitted on the port."
			::= {ethernetOamPduStatEntry 5}

		ethernetOamPduStatUniEventRx OBJECT-TYPE
			SYNTAX Counter
			MAX-ACCESS	read-only
			STATUS	current
			DESCRIPTION
			"Displays the number of unique event notification OAMPDUs received on the port."
			::= {ethernetOamPduStatEntry 6}

		ethernetOamPduStatDupEventTx OBJECT-TYPE
			SYNTAX Counter
			MAX-ACCESS	read-only
			STATUS	current
			DESCRIPTION
			"Displays the number of duplicate event notification OAMPDUs transmitted on the port."
			::= {ethernetOamPduStatEntry 7}

		ethernetOamPduStatDupEventRx OBJECT-TYPE
			SYNTAX Counter
			MAX-ACCESS	read-only
			STATUS	current
			DESCRIPTION
			"Displays the number of duplicate event notification OAMPDUs received on the port."
			::= {ethernetOamPduStatEntry 8}

		ethernetOamPduStatVarReqTx OBJECT-TYPE
			SYNTAX Counter
			MAX-ACCESS	read-only
			STATUS	current
			DESCRIPTION
			"Displays the number of variable request OAMPDUs transmitted on the port."
			::= {ethernetOamPduStatEntry 9}

		ethernetOamPduStatVarReqRx OBJECT-TYPE
			SYNTAX Counter
			MAX-ACCESS	read-only
			STATUS	current
			DESCRIPTION
			"Displays the number of variable request OAMPDUs received on the port."
			::= {ethernetOamPduStatEntry 10}

		ethernetOamPduStatVarRespTx OBJECT-TYPE
			SYNTAX Counter
			MAX-ACCESS	read-only
			STATUS	current
			DESCRIPTION
			"Displays the number of variable response OAMPDUs transmitted on the port."
			::= {ethernetOamPduStatEntry 11}

		ethernetOamPduStatVarRespRx OBJECT-TYPE
			SYNTAX Counter
			MAX-ACCESS	read-only
			STATUS	current
			DESCRIPTION
			"Displays the number of variable response OAMPDUs received on the port."
			::= {ethernetOamPduStatEntry 12}

		ethernetOamPduStatLoopbackCtrlTx OBJECT-TYPE
			SYNTAX Counter
			MAX-ACCESS	read-only
			STATUS	current
			DESCRIPTION
			"Displays the number of loopback control OAMPDUs transmitted on the port."
			::= {ethernetOamPduStatEntry 13}

		ethernetOamPduStatLoopbackCtrlRx OBJECT-TYPE
			SYNTAX Counter
			MAX-ACCESS	read-only
			STATUS	current
			DESCRIPTION
			"Displays the number of loopback control OAMPDUs received on the port."
			::= {ethernetOamPduStatEntry 14}

		ethernetOamPduStatOrgSpecTx OBJECT-TYPE
			SYNTAX Counter
			MAX-ACCESS	read-only
			STATUS	current
			DESCRIPTION
			"Displays the number of organization specific OAMPDUs transmitted on the port."
			::= {ethernetOamPduStatEntry 15}

		ethernetOamPduStatOrgSpecRx OBJECT-TYPE
			SYNTAX Counter
			MAX-ACCESS	read-only
			STATUS	current
			DESCRIPTION
			"Displays the number of organization specific OAMPDUs received on the port."
			::= {ethernetOamPduStatEntry 16}

		ethernetOamPduStatUnsupportedTx OBJECT-TYPE
			SYNTAX Counter
			MAX-ACCESS	read-only
			STATUS	current
			DESCRIPTION
			"Displays the number of unsupported OAMPDUs transmitted on the port."
			::= {ethernetOamPduStatEntry 17}

		ethernetOamPduStatUnsupportedRx OBJECT-TYPE
			SYNTAX Counter
			MAX-ACCESS	read-only
			STATUS	current
			DESCRIPTION
			"Displays the number of unsupported OAMPDUs received on the port."
			::= {ethernetOamPduStatEntry 18}

		ethernetOamPduStatFrmLostDueToOam OBJECT-TYPE
			SYNTAX Counter
			MAX-ACCESS	read-only
			STATUS	current
			DESCRIPTION
			"Displays the number of frames that would otherwise be transmitted by the OAM sublayer, but could not be due to an internal OAM sublayer transmit error."
			::= {ethernetOamPduStatEntry 19}

END
