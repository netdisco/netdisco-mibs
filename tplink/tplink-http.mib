TPLINK-HTTP-MIB DEFINITIONS ::= BEGIN

		IMPORTS
			OBJECT-TYPE,MODULE-IDENTITY
				FROM SNMPv2-SMI
			tplinkMgmt
				FROM TPLINK-MIB;

		tplinkHttp MODULE-IDENTITY  
			LAST-UPDATED	"201501211030Z"
			ORGANIZATION	"TPLINK"
			CONTACT-INFO	"www.tplink.com.cn"
			DESCRIPTION		"Private MIB for HTTP configuration."
			REVISION		"201501211030Z"
			DESCRIPTION		"Initial version of this MIB module."
			::= { tplinkMgmt 51 }

		tplinkHttpMIBObjects		OBJECT IDENTIFIER ::= {tplinkHttp 1}
		tplinkHttpMIBNotifications	OBJECT IDENTIFIER ::= {tplinkHttp 2}

		httpEnable	OBJECT-TYPE
			SYNTAX  INTEGER{
					disable(0),
					enable(1)
					}
			MAX-ACCESS  read-write
			STATUS  current
			DESCRIPTION
					"0. disable
					1. enable"
			::= { tplinkHttpMIBObjects 1 }

        httpSessionTimeOut	OBJECT-TYPE
			SYNTAX		INTEGER (5..30)
			MAX-ACCESS	read-write
			STATUS		current
			DESCRIPTION	"HTTP session timeout in minutes."
			::= { tplinkHttpMIBObjects 2 }

		httpUserLimitEnable	OBJECT-TYPE
			SYNTAX  INTEGER{
					disable(0),
					enable(1)
					}
			MAX-ACCESS	read-write
			STATUS		current
			DESCRIPTION
						"0. disable
						1.enable"
			::= { tplinkHttpMIBObjects 3 }

		httpUserLimitMaxAdminNum	OBJECT-TYPE
			SYNTAX  INTEGER
			MAX-ACCESS	read-write
			STATUS		current
			DESCRIPTION	"The max num of admin users. You should enable HTTP user number limiting before setting this object."
			::= { tplinkHttpMIBObjects 4 }

		httpUserLimitMaxGuestNum	OBJECT-TYPE
			SYNTAX  INTEGER
			MAX-ACCESS	read-write
			STATUS		current
			DESCRIPTION "The max num of guest users. You should enable HTTP user number limiting before setting this object."
			::= { tplinkHttpMIBObjects 5 }

		END
