TPLINK-IPV6-SOURCE-GUARD-MIB DEFINITIONS ::= BEGIN

         IMPORTS
            OBJECT-TYPE,MODULE-IDENTITY
          	  	         	FROM SNMPv2-SMI
			ifIndex
						FROM  RFC1213-MIB
            tplinkMgmt
					FROM TPLINK-MIB;
        
		tplinkIpv6SourceGuardMIB MODULE-IDENTITY
		LAST-UPDATED    "201212130930Z"
		ORGANIZATION    "TPLINK"
		CONTACT-INFO    "www.tplink.com.cn"
		DESCRIPTION	    "Private MIB for IPv6 source guard configuration."
		REVISION        "201212130930Z"
		DESCRIPTION
				"Initial version of this MIB module."
		::= { tplinkMgmt 94 }	
		
		tplinkIpv6SourceGuardMIBObjects 		OBJECT IDENTIFIER ::= {tplinkIpv6SourceGuardMIB 1}
		tplinkIpv6SourceGuardNotifications 	OBJECT IDENTIFIER ::= {tplinkIpv6SourceGuardMIB 2}
		
		tpIpv6SourceGuardConfig  	OBJECT IDENTIFIER ::= {tplinkIpv6SourceGuardMIBObjects 1}
 
        -- the IPv6 filter config       
        
         tpIpv6SourceGuardConfigTable OBJECT-TYPE
            SYNTAX  SEQUENCE OF TPIPV6SOURCEUARDCONFIGENTRY
            MAX-ACCESS  not-accessible
            STATUS  current
            DESCRIPTION
                    "A list of IPv6 source guard config entries.
                     Here you can configure the IPv6 Source Guard feature."
            ::= { tpIpv6SourceGuardConfig 1 }

        tpIpv6SourceGuardConfigEntry OBJECT-TYPE
            SYNTAX  TPIPV6SOURCEUARDCONFIGENTRY
            MAX-ACCESS  not-accessible
            STATUS  current
            DESCRIPTION
                    "An entry contains of the information of IPv6 source guard config."
            INDEX   { ifIndex }
            ::= { tpIpv6SourceGuardConfigTable 1 }
    
        TPIPV6SOURCEUARDCONFIGENTRY ::=
            SEQUENCE {
								tpIpv6SourceGuardConfigPort
										OCTET STRING,
								tpIpv6SourceGuardConfigType
										INTEGER,
								tpIpv6SourceGuardConfigPortLag
										OCTET STRING 
            }
            
        tpIpv6SourceGuardConfigPort OBJECT-TYPE
            SYNTAX  OCTET STRING (SIZE (1..255)) 
            MAX-ACCESS  read-only
            STATUS  current
            DESCRIPTION
                    "port number"
            ::= { tpIpv6SourceGuardConfigEntry 1 }
        
        tpIpv6SourceGuardConfigType OBJECT-TYPE
            SYNTAX  INTEGER{
	      		disable(0), 						
	      		sipv6-mac(2)		
	      		}
            MAX-ACCESS  read-write
            STATUS  current
            DESCRIPTION
                    "Select Security Type for the port.
                     0. disable: Select this option to disable the IPv6 Source Guard feature for the port.
                     1. SIPv6: Only the packets with its source IPv6 address and port number matched 
                            to the IPv6-MAC binding rules can be processed. 
                     2. SIPv6+MAC: Only the packets with its source IPv6 address, 
                                source MAC address and port number matched to the IPv6-MAC binding rules can be processed."
            ::= { tpIpv6SourceGuardConfigEntry 2 }    
            
        tpIpv6SourceGuardConfigPortLag OBJECT-TYPE
            SYNTAX  OCTET STRING (SIZE (1..255))  
            MAX-ACCESS  read-only
            STATUS  current
            DESCRIPTION
                    "the lag the port belong to"
            ::= { tpIpv6SourceGuardConfigEntry 3 }     
  			
END
