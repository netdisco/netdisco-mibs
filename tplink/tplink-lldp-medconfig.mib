TPLINK-LLDPMEDCONFIG-MIB DEFINITIONS ::= BEGIN
       
       IMPORTS
			TPRowStatus       	 
					FROM TPLINK-TC-MIB
			OBJECT-TYPE,IpAddress
					FROM SNMPv2-SMI
			tplinkLldpMIBObjects
					FROM TPLINK-LLDP-MIB
			ifIndex
					FROM RFC1213-MIB;
          			
			lldpMed OBJECT IDENTIFIER ::= {tplinkLldpMIBObjects 4} 
			
			lldpMedGlobalConfig	  	OBJECT IDENTIFIER ::= {lldpMed 1}
              
            lldpMedGlobalConfigFastStartRepeatCount OBJECT-TYPE
         			SYNTAX  INTEGER(1..10)
              MAX-ACCESS  read-write
              STATUS  current
              DESCRIPTION
                      "When entering LLDP-MED fast start mechanism, multiple LLDP-MED frames will be transmitted based on this parameter."
              ::= { lldpMedGlobalConfig 1 }

	
			lldpMedPortConfigTable OBJECT-TYPE
              SYNTAX  SEQUENCE OF LLDPMEDPORTCONFIGENTRY
              MAX-ACCESS  not-accessible
              STATUS  current
              DESCRIPTION
                      "A table that contains LLDP-MED information of every port."
              ::= { lldpMed 2 }

          lldpMedPortConfigEntry OBJECT-TYPE
              SYNTAX  LLDPMEDPORTCONFIGENTRY
              MAX-ACCESS  not-accessible
              STATUS  current
              DESCRIPTION
                      "A list of LLDP-MED information for every port of the device."
              INDEX   { ifIndex }
              ::= { lldpMedPortConfigTable 1 }
      
          LLDPMEDPORTCONFIGENTRY ::=
              SEQUENCE {
					lldpMedConfigPortId
              				OCTET STRING,
                  lldpMedConfigPortStatus
                  		INTEGER,
                  lldpMedConfigPortTlvNetworkPolicy
                      INTEGER,
                  lldpMedConfigPortTlvLocationId
                      INTEGER,
                  lldpMedConfigPortTlvExtendedPower
                      INTEGER,
                  lldpMedConfigPortTlvInventory
                      INTEGER
              	}
              	
          lldpMedConfigPortId OBJECT-TYPE
              SYNTAX OCTET STRING (SIZE (0..255))
              MAX-ACCESS  read-only
              STATUS  current
              DESCRIPTION
                      "The port id of the switch."
              ::= { lldpMedPortConfigEntry 1 }
                  
          lldpMedConfigPortStatus OBJECT-TYPE
               SYNTAX  INTEGER{
	      										disable(0), 					--Disable
	      										enable(1)						--Enable
	      											}
              MAX-ACCESS  read-write
              STATUS  current
              DESCRIPTION
                      "Select Enable/Disable LLDP-MED for the Port. 
                      0. Disable
                      1. Enable"
              ::= { lldpMedPortConfigEntry 2 }
              
          lldpMedConfigPortTlvNetworkPolicy OBJECT-TYPE
               SYNTAX  INTEGER{
	      										disable(0), 					--Disable
	      										enable(1)						--Enable
	      											}
              MAX-ACCESS  read-write
              STATUS  current
              DESCRIPTION
                      "Select Enable/Disable Network Policy TLV for the Port. 
                      0. Disable
                      1. Enable"
              ::= { lldpMedPortConfigEntry 3 }
              
          lldpMedConfigPortTlvLocationId OBJECT-TYPE
               SYNTAX  INTEGER{
	      										disable(0), 					--Disable
	      										enable(1)						--Enable
	      											}
              MAX-ACCESS  read-write
              STATUS  current
              DESCRIPTION
                      "Select Enable/Disable Location Identification TLV for the Port. 
                      0. Disable
                      1. Enable"
              ::= { lldpMedPortConfigEntry 4 }
              
          lldpMedConfigPortTlvExtendedPower OBJECT-TYPE
               SYNTAX  INTEGER{
	      										disable(0), 					--Disable
	      										enable(1)						--Enable
	      											}
              MAX-ACCESS  read-write
              STATUS  current
              DESCRIPTION
                      "Select Enable/Disable Extended Power-Via-MDI TLV for the Port. 
                      0. Disable
                      1. Enable"
              ::= { lldpMedPortConfigEntry 5 }
              
          lldpMedConfigPortTlvInventory OBJECT-TYPE
               SYNTAX  INTEGER{
	      										disable(0), 					--Disable
	      										enable(1)						--Enable
	      											}
              MAX-ACCESS  read-write
              STATUS  current
              DESCRIPTION
                      "Select Enable/Disable Inventory TLV for the Port. 
                      0. Disable
                      1. Enable"
              ::= { lldpMedPortConfigEntry 6 }

			lldpMedPortConfigTlvLocationTable OBJECT-TYPE
              SYNTAX  SEQUENCE OF LLDPMEDPORTCONFIGTLVLOCATIONENTRY
              MAX-ACCESS  not-accessible
              STATUS  current
              DESCRIPTION
                      "A table that contains LLDP-MED Location Identification TLV information of every port."
              ::= { lldpMed 3 }		
			  
            lldpMedPortConfigTlvLocationEntry OBJECT-TYPE
              SYNTAX  LLDPMEDPORTCONFIGTLVLOCATIONENTRY
              MAX-ACCESS  not-accessible
              STATUS  current
              DESCRIPTION
                      "A list of LLDP-MED Location Identification TLV information for every port of the device."
              INDEX   { ifIndex }
              ::= { lldpMedPortConfigTlvLocationTable 1 }

          LLDPMEDPORTCONFIGTLVLOCATIONENTRY ::=
              SEQUENCE {
					lldpMedConfigLocationPortId
              			OCTET STRING,
					lldpMedConfigPortLocationEmergencyNumber
                  		OCTET STRING,
					lldpMedConfigPortLocationCivicAddressWhat
						INTEGER,
					lldpMedConfigPortLocationCivicAddressCountryCode
						OCTET STRING,
					lldpMedConfigPortLocationCivicAddressLanguage
						OCTET STRING,
					lldpMedConfigPortLocationCivicAddressProvince
						OCTET STRING,
					lldpMedConfigPortLocationCivicAddressCounty
						OCTET STRING,
					lldpMedConfigPortLocationCivicAddressCity
						OCTET STRING,
					lldpMedConfigPortLocationCivicAddressStreet
						OCTET STRING,
					lldpMedConfigPortLocationCivicAddressHouseNumber
						OCTET STRING,
					lldpMedConfigPortLocationCivicAddressName
						OCTET STRING,
					lldpMedConfigPortLocationCivicAddressPostalZipCode
						OCTET STRING,
					lldpMedConfigPortLocationCivicAddressRoomNumber
						OCTET STRING,
					lldpMedConfigPortLocationCivicAddressPostOfficeBox
						OCTET STRING,
					lldpMedConfigPortLocationCivicAddressAdditional
						OCTET STRING						
              	}
				
          lldpMedConfigLocationPortId OBJECT-TYPE
               SYNTAX  OCTET STRING (SIZE (0..255))
              MAX-ACCESS  read-only
              STATUS  current
              DESCRIPTION
                      "The port id of the switch."
              ::= { lldpMedPortConfigTlvLocationEntry 1 }		

          lldpMedConfigPortLocationEmergencyNumber OBJECT-TYPE
               SYNTAX  OCTET STRING (SIZE (10..25))
              MAX-ACCESS  read-write
              STATUS  current
              DESCRIPTION
                      "Emergency number is Emergency Call Service ELIN identifier, which is used during emergency 
					  call setup to a traditional CAMA or ISDN trunk-based PSAP."
              ::= { lldpMedPortConfigTlvLocationEntry 2 }	

          lldpMedConfigPortLocationCivicAddressWhat OBJECT-TYPE
               SYNTAX  INTEGER {
					dhcp-server(0),				-- the location of the DHCP server
					switch(1),					-- the location of the network element believed to be closest to the client 
					lldp-med-endpoint(2)		-- the location of the client
				}
              MAX-ACCESS  read-write
              STATUS  current
              DESCRIPTION
                      "This element describes which location the DHCP entry refers to. Currently, three options are 
					  defined: the location of the DHCP server (0: DHCP server), the location of the network element 
					  believed to be closest to the client (1: Switch) or the location of the client (2: LLDP-MED 
					  Endpoint). Option (2) should be used, but may not be known. Options (0) and (1) should not be 
					  used unless it is known that the DHCP client is in close physical proximity to the server 
					  or network element."
              ::= { lldpMedPortConfigTlvLocationEntry 3 }	

          lldpMedConfigPortLocationCivicAddressCountryCode OBJECT-TYPE
               SYNTAX  OCTET STRING (SIZE (2))
              MAX-ACCESS  read-write
              STATUS  current
              DESCRIPTION
                      "The two-letters ISO 3166 country code in capital ASCII letters, e.g., CN or US."
              ::= { lldpMedPortConfigTlvLocationEntry 4 }	

          lldpMedConfigPortLocationCivicAddressLanguage OBJECT-TYPE
               SYNTAX  OCTET STRING (SIZE (0..256))
              MAX-ACCESS  read-write
              STATUS  current
              DESCRIPTION
                      "Language."
              ::= { lldpMedPortConfigTlvLocationEntry 5 }

          lldpMedConfigPortLocationCivicAddressProvince OBJECT-TYPE
               SYNTAX  OCTET STRING (SIZE (0..256))
              MAX-ACCESS  read-write
              STATUS  current
              DESCRIPTION
                      "Province or State."
              ::= { lldpMedPortConfigTlvLocationEntry 6 }	

          lldpMedConfigPortLocationCivicAddressCounty OBJECT-TYPE
               SYNTAX  OCTET STRING (SIZE (0..256))
              MAX-ACCESS  read-write
              STATUS  current
              DESCRIPTION
                      "County."
              ::= { lldpMedPortConfigTlvLocationEntry 7 }	

          lldpMedConfigPortLocationCivicAddressCity OBJECT-TYPE
               SYNTAX  OCTET STRING (SIZE (0..256))
              MAX-ACCESS  read-write
              STATUS  current
              DESCRIPTION
                      "City."
              ::= { lldpMedPortConfigTlvLocationEntry 8 }	

          lldpMedConfigPortLocationCivicAddressStreet OBJECT-TYPE
               SYNTAX  OCTET STRING (SIZE (0..256))
              MAX-ACCESS  read-write
              STATUS  current
              DESCRIPTION
                      "Street."
              ::= { lldpMedPortConfigTlvLocationEntry 9 }	

          lldpMedConfigPortLocationCivicAddressHouseNumber OBJECT-TYPE
               SYNTAX  OCTET STRING (SIZE (0..256))
              MAX-ACCESS  read-write
              STATUS  current
              DESCRIPTION
                      "House number."
              ::= { lldpMedPortConfigTlvLocationEntry 10 }	

          lldpMedConfigPortLocationCivicAddressName OBJECT-TYPE
               SYNTAX  OCTET STRING (SIZE (0..256))
              MAX-ACCESS  read-write
              STATUS  current
              DESCRIPTION
                      "Residence and office occupant name."
              ::= { lldpMedPortConfigTlvLocationEntry 11 }	

          lldpMedConfigPortLocationCivicAddressPostalZipCode OBJECT-TYPE
               SYNTAX  OCTET STRING (SIZE (0..256))
              MAX-ACCESS  read-write
              STATUS  current
              DESCRIPTION
                      "Postal/zip code."
              ::= { lldpMedPortConfigTlvLocationEntry 12 }	

          lldpMedConfigPortLocationCivicAddressRoomNumber OBJECT-TYPE
               SYNTAX  OCTET STRING (SIZE (0..256))
              MAX-ACCESS  read-write
              STATUS  current
              DESCRIPTION
                      "Room number."
              ::= { lldpMedPortConfigTlvLocationEntry 13 }	

          lldpMedConfigPortLocationCivicAddressPostOfficeBox OBJECT-TYPE
               SYNTAX  OCTET STRING (SIZE (0..256))
              MAX-ACCESS  read-write
              STATUS  current
              DESCRIPTION
                      "Post office box."
              ::= { lldpMedPortConfigTlvLocationEntry 14 }	

          lldpMedConfigPortLocationCivicAddressAdditional OBJECT-TYPE
               SYNTAX  OCTET STRING (SIZE (0..256))
              MAX-ACCESS  read-write
              STATUS  current
              DESCRIPTION
                      "Additional information."
              ::= { lldpMedPortConfigTlvLocationEntry 15 }	
			
			lldpMedLocalInfoTable OBJECT-TYPE
              SYNTAX  SEQUENCE OF LLDPMEDLOCALINFOENTRY
              MAX-ACCESS  not-accessible
              STATUS  current
              DESCRIPTION
                      "Local port LLDP-MED information entries."
              ::= { lldpMed 4 }

          lldpMedLocalInfoEntry OBJECT-TYPE
              SYNTAX  LLDPMEDLOCALINFOENTRY
              MAX-ACCESS  not-accessible
              STATUS  current
              DESCRIPTION
                      "An entry contains of the LLDP-MED information of local port of the switch."
              INDEX   { ifIndex }
              ::= { lldpMedLocalInfoTable 1 }
      
          LLDPMEDLOCALINFOENTRY ::=
              SEQUENCE {
              		lldpMedLocalPortId
              				OCTET STRING,
                  lldpMEDLocalCapabilities
                  		OCTET STRING ,
                  lldpMedLocalDeviceType
                      OCTET STRING,
                  lldpMedLocalApplicationType
                      OCTET STRING,
                  lldpMedLocalUnknownPolicy
                      OCTET STRING,
                  lldpMedLocalAppTagged
                      OCTET STRING,
                  lldpMedLocalAppVLANID
                      INTEGER,
                  lldpMedLocalAppLayer2Priority
                      INTEGER,
                  lldpMedLocalAppDSCP
                      INTEGER,
                  lldpMedLocalLocationDataFormat
                      OCTET STRING,
                  lldpMedLocalLocationID
                      OCTET STRING,
                  lldpMedLocalPowerType
                      OCTET STRING,
                  lldpMedLocalPowerSource
                      OCTET STRING,
                  lldpMedLocalPowerPriority
                      OCTET STRING,
                  lldpMedLocalPowerValue
                      OCTET STRING,
                  lldpMedLocalInventoryHardwareRevision
                      OCTET STRING,
                  lldpMedLocalInventoryFirmwareRevision
                      OCTET STRING,
                  lldpMedLocalInventorySoftwareRevision
                      OCTET STRING,
                  lldpMedLocalInventorySerialNumber
                      OCTET STRING,
                  lldpMedLocalInventoryManufacturerName
                      OCTET STRING,
                  lldpMedLocalInventoryModelName
                      OCTET STRING,
                  lldpMedLocalInventoryAssetID
                      OCTET STRING  
              	}
              	
              
          lldpMedLocalPortId OBJECT-TYPE
            	SYNTAX  OCTET STRING (SIZE (0..255))  
              MAX-ACCESS  read-only
              STATUS  current
              DESCRIPTION
                      "Display the port index."
              ::= { lldpMedLocalInfoEntry 1 }
              
          lldpMEDLocalCapabilities OBJECT-TYPE
            	SYNTAX  OCTET STRING (SIZE (0..200))  
              MAX-ACCESS  read-only
              STATUS  current
              DESCRIPTION
                      "Display the LLDP-MED capabilities the switch supports."
              ::= { lldpMedLocalInfoEntry 2 }
                      
          lldpMedLocalDeviceType OBJECT-TYPE
            	SYNTAX  OCTET STRING (SIZE (0..30))  
              MAX-ACCESS  read-only
              STATUS  current
              DESCRIPTION
                      "LLDP-MED devices are comprised of two primary device types: Network Connectivity Devices 
					  and Endpoint Devices. In turn, Endpoint Devices are composed of three defined Classes: 
					  Class I, Class II and Class III. Switch is a Network Connectivity Device."
              ::= { lldpMedLocalInfoEntry 3 }
            
          lldpMedLocalApplicationType OBJECT-TYPE
            	SYNTAX  OCTET STRING (SIZE (0..30))  
              MAX-ACCESS  read-only
              STATUS  current
              DESCRIPTION
                      "Display the primary function of the applications defined for the network policy."
              ::= { lldpMedLocalInfoEntry 4 }
           
          lldpMedLocalUnknownPolicy OBJECT-TYPE
            	SYNTAX  OCTET STRING (SIZE (0..10))  
              MAX-ACCESS  read-only
              STATUS  current
              DESCRIPTION
                      "A value of 'Yes' indicates that the network policy for the specified application type is currently
					  unknown. In this case, the VLAN ID, the Layer 2 Priority and the DSCP value fields are ignored. A
					  value of 'No' indicates that this network policy is defined."
              ::= { lldpMedLocalInfoEntry 5 }
              
          lldpMedLocalAppTagged OBJECT-TYPE
            	SYNTAX  OCTET STRING (SIZE (0..10))  
              MAX-ACCESS  read-only
              STATUS  current
              DESCRIPTION
                      "Indicate whether the specified application type is using a 'tagged' or an 'untagged' VLAN."
              ::= { lldpMedLocalInfoEntry 6 }
 
          lldpMedLocalAppVLANID OBJECT-TYPE
            	SYNTAX  INTEGER 
              MAX-ACCESS  read-only
              STATUS  current
              DESCRIPTION
                      "An extension of the VLAN Identifier for the port, as defined in IEEE 802.1P-1998."
              ::= { lldpMedLocalInfoEntry 7 }

          lldpMedLocalAppLayer2Priority OBJECT-TYPE
            	SYNTAX  INTEGER 
              MAX-ACCESS  read-only
              STATUS  current
              DESCRIPTION
                      "Contain the value of the 802.1p priority which is associated with the given port on the 
					  local system. "
              ::= { lldpMedLocalInfoEntry 8 }	
			  
          lldpMedLocalAppDSCP OBJECT-TYPE
            	SYNTAX  INTEGER 
              MAX-ACCESS  read-only
              STATUS  current
              DESCRIPTION
                      "Contain the value of the Differentiated Service Code Point (DSCP) as defined in IETF RFC 2474
					  and RFC 2475 which is associated with the given port on the local system."
              ::= { lldpMedLocalInfoEntry 9 }	
  			  
          lldpMedLocalLocationDataFormat OBJECT-TYPE
            	SYNTAX  OCTET STRING (SIZE (0..30))  
              MAX-ACCESS  read-only
              STATUS  current
              DESCRIPTION
                      "The location subtype advertised by the local system."
              ::= { lldpMedLocalInfoEntry 10 }
              
          lldpMedLocalLocationID OBJECT-TYPE
            	SYNTAX  OCTET STRING (SIZE (0..512))  
              MAX-ACCESS  read-only
              STATUS  current
              DESCRIPTION
                      "The location information. Parsing of this information is depedent upon the location subtype."
              ::= { lldpMedLocalInfoEntry 11 }
              
          lldpMedLocalPowerType OBJECT-TYPE
            	SYNTAX  OCTET STRING (SIZE (0..30))  
              MAX-ACCESS  read-only
              STATUS  current
              DESCRIPTION
                      "Defines the type of Power-Via-MDI advertised by the local device."
              ::= { lldpMedLocalInfoEntry 12 }
              
          lldpMedLocalPowerSource OBJECT-TYPE
            	SYNTAX  OCTET STRING (SIZE (0..30))  
              MAX-ACCESS  read-only
              STATUS  current
              DESCRIPTION
                      "Defines the type of PSE Power Source advertised by the local device."
              ::= { lldpMedLocalInfoEntry 13 }

           lldpMedLocalPowerPriority OBJECT-TYPE
            	SYNTAX  OCTET STRING (SIZE (0..30))  
              MAX-ACCESS  read-only
              STATUS  current
              DESCRIPTION
                      "Reflects the PD power priority that is being advertised on this PSE port."
              ::= { lldpMedLocalInfoEntry 14 }
              
          lldpMedLocalPowerValue OBJECT-TYPE
            	SYNTAX  OCTET STRING (SIZE (0..30))  
              MAX-ACCESS  read-only
              STATUS  current
              DESCRIPTION
                      "Contain the value of the power available from the PSE via this port."
              ::= { lldpMedLocalInfoEntry 15 } 
              
          lldpMedLocalInventoryHardwareRevision OBJECT-TYPE
            	SYNTAX  OCTET STRING (SIZE (0..32)) 
              MAX-ACCESS  read-only
              STATUS  current
              DESCRIPTION
                      "The vendor-specific hardware revision string as advertised by the local system."
              ::= { lldpMedLocalInfoEntry 16 } 
          
          lldpMedLocalInventoryFirmwareRevision OBJECT-TYPE
            	SYNTAX  OCTET STRING (SIZE (0..32)) 
              MAX-ACCESS  read-only
              STATUS  current
              DESCRIPTION
                      "The vendor-specific firmware revision string as advertised by the local system."
              ::= { lldpMedLocalInfoEntry 17 } 
			  
          lldpMedLocalInventorySoftwareRevision OBJECT-TYPE
            	SYNTAX  OCTET STRING (SIZE (0..32)) 
              MAX-ACCESS  read-only
              STATUS  current
              DESCRIPTION
                      "The vendor-specific software revision string as advertised by the local system."
              ::= { lldpMedLocalInfoEntry 18 } 
			  
          lldpMedLocalInventorySerialNumber OBJECT-TYPE
            	SYNTAX  OCTET STRING (SIZE (0..32)) 
              MAX-ACCESS  read-only
              STATUS  current
              DESCRIPTION
                      "The vendor-specific serial number as advertised by the local system."
              ::= { lldpMedLocalInfoEntry 19 } 
 
          lldpMedLocalInventoryManufacturerName OBJECT-TYPE
            	SYNTAX  OCTET STRING (SIZE (0..32)) 
              MAX-ACCESS  read-only
              STATUS  current
              DESCRIPTION
                      "The vendor-specific manufacturer name as advertised by the local system."
              ::= { lldpMedLocalInfoEntry 20 } 

          lldpMedLocalInventoryModelName OBJECT-TYPE
            	SYNTAX  OCTET STRING (SIZE (0..32)) 
              MAX-ACCESS  read-only
              STATUS  current
              DESCRIPTION
                      "The vendor-specific model name as advertised by the local system."
              ::= { lldpMedLocalInfoEntry 21 } 

          lldpMedLocalInventoryAssetID OBJECT-TYPE
            	SYNTAX  OCTET STRING (SIZE (0..32)) 
              MAX-ACCESS  read-only
              STATUS  current
              DESCRIPTION
                      "The vendor-specific asset tracking identifier as advertised by the local system."
              ::= { lldpMedLocalInfoEntry 22 }
			  
		lldpMedNeighborInfo MODULE-IDENTITY
			LAST-UPDATED    "201109270000Z"
			ORGANIZATION    "TPLINK"
			CONTACT-INFO		"www.tplink.com.cn"
			DESCRIPTION			"LLDP-MED Private MIB."
			REVISION        "201109270000Z"
			DESCRIPTION			"Initial version of this MIB module."
			::= { lldpMed 5 }		
			
       lldpMedNeighborInfoTable OBJECT-TYPE
              SYNTAX  SEQUENCE OF LLDPMEDNEIGHBORINFOENTRY
              MAX-ACCESS  not-accessible
              STATUS  current
              DESCRIPTION
                      "Neighbor port information  entries."
              ::= { lldpMedNeighborInfo 1 }

          lldpMedNeighborInfoEntry OBJECT-TYPE
              SYNTAX  LLDPMEDNEIGHBORINFOENTRY
              MAX-ACCESS  not-accessible
              STATUS  current
              DESCRIPTION
                      "An entry contains of the information of neighbor port except the network policy information."
              INDEX   { ifIndex , lldpMedNeighborPortIndexId}
              ::= { lldpMedNeighborInfoTable 1 }
      
           LLDPMEDNEIGHBORINFOENTRY ::=
              SEQUENCE {
              		lldpMedNeighborPortId
              				OCTET STRING,
					lldpMedNeighborPortIndexId
							INTEGER,
                  lldpMEDNeighborCapabilities
                  		OCTET STRING,
                  lldpMedNeighborDeviceType
                      OCTET STRING,
                  lldpMedNeighborLocationDataFormat
                      OCTET STRING,
                  lldpMedNeighborLocationID
                      OCTET STRING,
                  lldpMedNeighborPowerType
                      OCTET STRING,
                  lldpMedNeighborPowerSource
                      OCTET STRING,
                  lldpMedNeighborPowerPriority
                      OCTET STRING,
                  lldpMedNeighborPowerValue
                      OCTET STRING,
                  lldpMedNeighborInventoryHardwareRevision
                      OCTET STRING,
                  lldpMedNeighborInventoryFirmwareRevision
                      OCTET STRING,
                  lldpMedNeighborInventorySoftwareRevision
                      OCTET STRING,
                  lldpMedNeighborInventorySerialNumber
                      OCTET STRING,
                  lldpMedNeighborInventoryManufacturerName
                      OCTET STRING,
                  lldpMedNeighborInventoryModelName
                      OCTET STRING,
                  lldpMedNeighborInventoryAssetID
                      OCTET STRING
              	}
              	
              
          lldpMedNeighborPortId OBJECT-TYPE
            	SYNTAX  OCTET STRING (SIZE (0..255))  
              MAX-ACCESS  read-only
              STATUS  current
              DESCRIPTION
                      "Display the port index."
              ::= { lldpMedNeighborInfoEntry 1 }
			  
           lldpMedNeighborPortIndexId OBJECT-TYPE
            	SYNTAX  INTEGER  
              MAX-ACCESS  read-only
              STATUS  current
              DESCRIPTION
                      "Display the neighbor index."
              ::= { lldpMedNeighborInfoEntry 2 }  
			  
          lldpMEDNeighborCapabilities OBJECT-TYPE
            	SYNTAX  OCTET STRING (SIZE (0..200))  
              MAX-ACCESS  read-only
              STATUS  current
              DESCRIPTION
                      "LLDP-MED capabilities of remote devices connected to the device ports and
					  communicating via LLDP-MED."
              ::= { lldpMedNeighborInfoEntry 3 }
                      
          lldpMedNeighborDeviceType OBJECT-TYPE
            	SYNTAX  OCTET STRING (SIZE (0..30))  
              MAX-ACCESS  read-only
              STATUS  current
              DESCRIPTION
                      "Device Class as advertised by the device remotely connected to the port."
              ::= { lldpMedNeighborInfoEntry 4 }
  			  
          lldpMedNeighborLocationDataFormat OBJECT-TYPE
            	SYNTAX  OCTET STRING (SIZE (0..30))  
              MAX-ACCESS  read-only
              STATUS  current
              DESCRIPTION
                      "The location subtype advertised by the remote endpoint."
              ::= { lldpMedNeighborInfoEntry 5 }
              
          lldpMedNeighborLocationID OBJECT-TYPE
            	SYNTAX  OCTET STRING (SIZE (0..512))  
              MAX-ACCESS  read-only
              STATUS  current
              DESCRIPTION
                      "The location information advertised by the remote endpoint."
              ::= { lldpMedNeighborInfoEntry 6 }
              
          lldpMedNeighborPowerType OBJECT-TYPE
            	SYNTAX  OCTET STRING (SIZE (0..30))  
              MAX-ACCESS  read-only
              STATUS  current
              DESCRIPTION
                      "Defines the type of Power-Via-MDI advertised by the remote device."
              ::= { lldpMedNeighborInfoEntry 7 }
              
          lldpMedNeighborPowerSource OBJECT-TYPE
            	SYNTAX  OCTET STRING (SIZE (0..30))  
              MAX-ACCESS  read-only
              STATUS  current
              DESCRIPTION
                      "Defines the type of Power Source advertised as being used by the device
					  connected remotely to the port."
              ::= { lldpMedNeighborInfoEntry 8 }

           lldpMedNeighborPowerPriority OBJECT-TYPE
            	SYNTAX  OCTET STRING (SIZE (0..30))  
              MAX-ACCESS  read-only
              STATUS  current
              DESCRIPTION
                      "Definces the priority advertised as being required by the PD connected 
					  remotely to the port."
              ::= { lldpMedNeighborInfoEntry 9 }
              
          lldpMedNeighborPowerValue OBJECT-TYPE
            	SYNTAX  OCTET STRING (SIZE (0..30))  
              MAX-ACCESS  read-only
              STATUS  current
              DESCRIPTION
                      "Conatin the value of the power required by a PD connected remotely to the port."
              ::= { lldpMedNeighborInfoEntry 10 } 
              
          lldpMedNeighborInventoryHardwareRevision OBJECT-TYPE
            	SYNTAX  OCTET STRING (SIZE (0..32)) 
              MAX-ACCESS  read-only
              STATUS  current
              DESCRIPTION
                      "The vendor-specific hardware revision string as advertised by the remote endpoint."
              ::= { lldpMedNeighborInfoEntry 11 } 
          
          lldpMedNeighborInventoryFirmwareRevision OBJECT-TYPE
            	SYNTAX  OCTET STRING (SIZE (0..32)) 
              MAX-ACCESS  read-only
              STATUS  current
              DESCRIPTION
                      "The vendor-specific firmware revision string as advertised by the remote endpoint."
              ::= { lldpMedNeighborInfoEntry 12 } 
			  
          lldpMedNeighborInventorySoftwareRevision OBJECT-TYPE
            	SYNTAX  OCTET STRING (SIZE (0..32)) 
              MAX-ACCESS  read-only
              STATUS  current
              DESCRIPTION
                      "The vendor-specific software revision string as advertised by the remote endpoint."
              ::= { lldpMedNeighborInfoEntry 13 } 
			  
          lldpMedNeighborInventorySerialNumber OBJECT-TYPE
            	SYNTAX  OCTET STRING (SIZE (0..32)) 
              MAX-ACCESS  read-only
              STATUS  current
              DESCRIPTION
                      "The vendor-specific serial number as advertised by the remote endpoint."
              ::= { lldpMedNeighborInfoEntry 14 } 
 
          lldpMedNeighborInventoryManufacturerName OBJECT-TYPE
            	SYNTAX  OCTET STRING (SIZE (0..32)) 
              MAX-ACCESS  read-only
              STATUS  current
              DESCRIPTION
                      "The vendor-specific manufacturer name as advertised by the remote endpoint."
              ::= { lldpMedNeighborInfoEntry 15 } 

          lldpMedNeighborInventoryModelName OBJECT-TYPE
            	SYNTAX  OCTET STRING (SIZE (0..32)) 
              MAX-ACCESS  read-only
              STATUS  current
              DESCRIPTION
                      "The vendor-specific model name as advertised by the remote endpoint."
              ::= { lldpMedNeighborInfoEntry 16 } 

          lldpMedNeighborInventoryAssetID OBJECT-TYPE
            	SYNTAX  OCTET STRING (SIZE (0..32)) 
              MAX-ACCESS  read-only
              STATUS  current
              DESCRIPTION
                      "The vendor-specific asset tracking identifier as advertised by the remote endpoint."
              ::= { lldpMedNeighborInfoEntry 17 } 
			  
		lldpMedNeighborMediaPolicyInfoTable OBJECT-TYPE
              SYNTAX  SEQUENCE OF LLDPMEDNEIGHBORINFOAPPENTRY
              MAX-ACCESS  not-accessible
              STATUS  current
              DESCRIPTION
                      "Neighbor port media policy information  entries."
              ::= { lldpMedNeighborInfo 2 }
			  
		lldpMedNeighborMediaPolicyInfoEntry OBJECT-TYPE
              SYNTAX  LLDPMEDNEIGHBORINFOAPPENTRY
              MAX-ACCESS  not-accessible
              STATUS  current
              DESCRIPTION
                      "Information about a particular policy on a specific port component."
              INDEX   { ifIndex, lldpMedNeighborPortIndex, lldpMedNeighborMediaPolicyIndex}
              ::= { lldpMedNeighborMediaPolicyInfoTable 1 }
      
           LLDPMEDNEIGHBORINFOAPPENTRY ::=
				SEQUENCE {
              		lldpMedNeighborPort
              				OCTET STRING,
					lldpMedNeighborPortIndex
							INTEGER,
					lldpMedNeighborMediaPolicyIndex
							INTEGER,							
                  lldpMedNeighborApplicationType
                      OCTET STRING,
                  lldpMedNeighborUnknownPolicy
                      OCTET STRING,
                  lldpMedNeighborAppTagged
                      OCTET STRING,
                  lldpMedNeighborAppVLANID
                      INTEGER,
                  lldpMedNeighborAppLayer2Priority
                      INTEGER,
                  lldpMedNeighborAppDSCP
                      INTEGER
				}
          lldpMedNeighborPort OBJECT-TYPE
            	SYNTAX  OCTET STRING (SIZE (0..255))  
              MAX-ACCESS  read-only
              STATUS  current
              DESCRIPTION
                      "Display the port index."
              ::= { lldpMedNeighborMediaPolicyInfoEntry 1 }
			  
           lldpMedNeighborPortIndex OBJECT-TYPE
            	SYNTAX  INTEGER  
              MAX-ACCESS  read-only
              STATUS  current
              DESCRIPTION
                      "Display the neighbor index."
              ::= { lldpMedNeighborMediaPolicyInfoEntry 2 }  	

           lldpMedNeighborMediaPolicyIndex OBJECT-TYPE
            	SYNTAX  INTEGER  
              MAX-ACCESS  read-only
              STATUS  current
              DESCRIPTION
                      "Display the neighbor media policy index."
              ::= { lldpMedNeighborMediaPolicyInfoEntry 3 }  
			  
          lldpMedNeighborApplicationType OBJECT-TYPE
            	SYNTAX  OCTET STRING (SIZE (0..30))  
              MAX-ACCESS  read-only
              STATUS  current
              DESCRIPTION
                      "The media type that defines the primary function of the application for the
					  policy advertised by the endpoint connected remotely to this port."
              ::= { lldpMedNeighborMediaPolicyInfoEntry 4 }
           
          lldpMedNeighborUnknownPolicy OBJECT-TYPE
            	SYNTAX  OCTET STRING (SIZE (0..10))  
              MAX-ACCESS  read-only
              STATUS  current
              DESCRIPTION
                      "A value of 'Yes' indicates that the network policy for the specified application
					  type is currently unknown. In this case, the VLAN ID, the layer 2 priority and the
					  DSCP value fields are ignored. A value of 'No' indicates that this network policy
					  is defined."
              ::= { lldpMedNeighborMediaPolicyInfoEntry 5 }
              
          lldpMedNeighborAppTagged OBJECT-TYPE
            	SYNTAX  OCTET STRING (SIZE (0..10))  
              MAX-ACCESS  read-only
              STATUS  current
              DESCRIPTION
                      "Indicate whether the specified application type is using a 'tagged' or an 'untagged' VLAN."
              ::= { lldpMedNeighborMediaPolicyInfoEntry 6 }
 
          lldpMedNeighborAppVLANID OBJECT-TYPE
            	SYNTAX  INTEGER 
              MAX-ACCESS  read-only
              STATUS  current
              DESCRIPTION
                      "An extension of the VLAN Identifier for the remote system connected to this port,
					  as defined in IEEE 802.1P-1998."
              ::= { lldpMedNeighborMediaPolicyInfoEntry 7 }

          lldpMedNeighborAppLayer2Priority OBJECT-TYPE
            	SYNTAX  INTEGER 
              MAX-ACCESS  read-only
              STATUS  current
              DESCRIPTION
                      "Contain the value of the 802.1p priority which is associated with the remote
					  system connected at given port."
              ::= { lldpMedNeighborMediaPolicyInfoEntry 8 }	
			  
          lldpMedNeighborAppDSCP OBJECT-TYPE
            	SYNTAX  INTEGER 
              MAX-ACCESS  read-only
              STATUS  current
              DESCRIPTION
                      "Contain the value of the Differentiated Service Code Point (DSCP) as defined
					  in IETF 2474 and RFC 2475 which is assocaited with remote system connected
					  at the port."
              ::= { lldpMedNeighborMediaPolicyInfoEntry 9 }	
			  
	 END
