TPLINK-PORTCONFIG-MIB DEFINITIONS ::= BEGIN
IMPORTS
	OBJECT-TYPE,MODULE-IDENTITY
			FROM SNMPv2-SMI
	ifIndex						
						FROM RFC1213-MIB
	DisplayString 
						FROM SNMPv2-TC        	  	         	
	tplinkMgmt	          
			FROM TPLINK-MIB;

tplinkPortConfigMIB MODULE-IDENTITY
    LAST-UPDATED  "201211290000Z"
    ORGANIZATION  "TP-LINK"
    CONTACT-INFO  "www.tplink.com.cn"
    DESCRIPTION
         "This MIB module contain a collection of managed objects
          for port configuration."

    REVISION    "201211290000Z"
    DESCRIPTION
        "Initial version of this MIB module."
    ::= { tplinkMgmt 8 }

tplinkPortConfigMIBObjects OBJECT IDENTIFIER ::= {tplinkPortConfigMIB 1}
tplinkPortConfigNotifications OBJECT IDENTIFIER ::= {tplinkPortConfigMIB 2}
																											  

tpPortConfigTable OBJECT-TYPE
	SYNTAX	SEQUENCE OF TpPortConfigEntry
	MAX-ACCESS	not-accessible
	STATUS	current
	DESCRIPTION
	"A table that contains information about every port. You can 
	configure the basic parameters for the ports. The parameters 
	will affect the working mode of the port, please set the 
	parameters appropriate to your needs."
	::= {tplinkPortConfigMIBObjects 1}

tpPortConfigEntry OBJECT-TYPE
	SYNTAX	TpPortConfigEntry
	MAX-ACCESS	not-accessible
	STATUS	current
	DESCRIPTION
	"A list of information for each port of the device."
	INDEX{ifIndex}
	::= {tpPortConfigTable 1}
						
TpPortConfigEntry ::=
	SEQUENCE 
	{
		tpPortConfigDescription
			DisplayString,
		tpPortConfigStatus
			INTEGER,
		tpPortConfigSpeed
			INTEGER,
		tpPortConfigDuplex
			INTEGER,
		tpPortConfigFlowCtrl
			INTEGER,
		tpPortConfigJumbo
			INTEGER,
		tpPortConfigLAG
			DisplayString
	}
					
tpPortConfigDescription	OBJECT-TYPE
	SYNTAX	DisplayString
	MAX-ACCESS	read-write
	STATUS	current
	DESCRIPTION
	"This object indicate the description of the port."
	::= {tpPortConfigEntry 2}
	
tpPortConfigStatus	OBJECT-TYPE
	SYNTAX						
		INTEGER
		{
			disable(0),
			enable(1)
		}
	MAX-ACCESS	read-write
	STATUS	current
	DESCRIPTION
	"This object indicates the link status of the port. When enable 
	is selected, the port can forward the packets normall."
	::= {tpPortConfigEntry 3}

tpPortConfigSpeed	OBJECT-TYPE
	SYNTAX
		INTEGER
		{
			speed-10Mbps(0),
			speed-100Mbps(1),
			speed-1Gigabps(2), 
			speed-10Gigabps(3),
			auto(4)
		}
	MAX-ACCESS	read-write
	STATUS	current
	DESCRIPTION
	"This object indicates the speed and duplex mode of the port. 
	The device connected to the switch should be in the same Speed
	and Duplex mode with the switch. When auto is selected, the 
	Speed and Duplex mode will be determined by auto negotiation."
	::= {tpPortConfigEntry 4}
	
tpPortConfigDuplex	OBJECT-TYPE
	SYNTAX
		INTEGER
		{
			half(0),
			full(1),
			auto(2)
		}
	MAX-ACCESS	read-write
	STATUS	current
	DESCRIPTION
	"This object indicates the speed and duplex mode of the port. 
	The device connected to the switch should be in the same Speed
	and Duplex mode with the switch. When auto is selected, the 
	Speed and Duplex mode will be determined by auto negotiation."
	::= {tpPortConfigEntry 5}						

tpPortConfigFlowCtrl	OBJECT-TYPE
	SYNTAX
		INTEGER
		{
			disable(0),
			enable(1)
		}
	MAX-ACCESS	read-write
	STATUS	current
	DESCRIPTION
	"This object indicates the port status of the flow control. When
	Flow Control is enabled, the switch can synchronize the speed 
	with its peer to avoid the packet loss caused by congestion."
	::= {tpPortConfigEntry 6}
	
tpPortConfigJumbo	OBJECT-TYPE
	SYNTAX
		INTEGER
		{
			disable(0),
			enable(1)
		}
	MAX-ACCESS	read-write
	STATUS	current
	DESCRIPTION
	"This object indicates the port status of the jumbo. 
	The default maximum transmission unit (MTU) size is 1518 bytes. 
	When Jumbo is enabled, the MTU size is 9216 bytes."
	::= {tpPortConfigEntry 7}

tpPortConfigLAG	OBJECT-TYPE
	SYNTAX	DisplayString
	MAX-ACCESS	read-only
	STATUS	current
	DESCRIPTION
	"This object indicates the lag number of the port."
	::= {tpPortConfigEntry 8}
END
