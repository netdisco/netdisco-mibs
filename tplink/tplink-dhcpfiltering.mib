TPLINK-DHCPFILTERING-MIB DEFINITIONS ::= BEGIN

         IMPORTS
            MODULE-IDENTITY, OBJECT-TYPE
          	  	        FROM SNMPv2-SMI
          	ifIndex
						FROM RFC1213-MIB
            tplinkMgmt
						FROM TPLINK-MIB; 
	    
			tplinkDhcpFilteringMIB MODULE-IDENTITY
				LAST-UPDATED    "201212171014Z"
				ORGANIZATION    "TPLINK"
				CONTACT-INFO    "www.tplink.com.cn"
				DESCRIPTION	    "Private MIB for DHCP Filtering configuration."
				REVISION        "201212171014Z"
				DESCRIPTION
				"Initial version of this MIB module."
			::= { tplinkMgmt 48 }
		
			tplinkDhcpFilteringMIBObjects		OBJECT IDENTIFIER	::= { tplinkDhcpFilteringMIB 1 }
			tplinkDhcpFilteringNotifications		OBJECT IDENTIFIER	::= { tplinkDhcpFilteringMIB 2 }
  			
  			dhcpFilteringGlobalConfig		OBJECT IDENTIFIER	::= { tplinkDhcpFilteringMIBObjects 1 }
            dhcpFilteringPortConfig     		OBJECT IDENTIFIER	::= { tplinkDhcpFilteringMIBObjects 3 }
				
				dhcpFilteringEnable OBJECT-TYPE
	          		SYNTAX  INTEGER{
	      				disable(0), 						
	      				enable(1)						
	      			}
	            MAX-ACCESS  read-write
	            STATUS  current
	            DESCRIPTION
	                    "0. disable 
	                     1. enable
	                     Enable or disable the DHCP Filtering function globally."
	            ::= { dhcpFilteringGlobalConfig 1 }
      
				dhcpFilteringVlanConfigTable OBJECT-TYPE
					SYNTAX  	SEQUENCE OF DhcpFilteringVlanConfigTable
					MAX-ACCESS  not-accessible
					STATUS  	current
					DESCRIPTION
							"Here you can view and modify the DHCP Filtering VLAN config table."
				::= { dhcpFilteringGlobalConfig 2 }

				dhcpFilteringVlanConfigEntry OBJECT-TYPE
					SYNTAX  	DhcpFilteringVlanConfigTable
					MAX-ACCESS  not-accessible
					STATUS  	current
					DESCRIPTION
							"An entry contains of the DHCP Filtering function enable status information of a VLAN."
					INDEX   { dhcpFilteringVlanId }
				::= { dhcpFilteringVlanConfigTable 1 }

				DhcpFilteringVlanConfigTable ::=
					SEQUENCE {
						dhcpFilteringVlanId
								INTEGER(1..4094),
						dhcpFilteringVlanStatus
								INTEGER
					}

				dhcpFilteringVlanId OBJECT-TYPE
					SYNTAX 	 	INTEGER(1..4094)
					MAX-ACCESS  read-create
					STATUS  	current
					DESCRIPTION
							"Enter the ID number of VLAN,1-4094."
				::= { dhcpFilteringVlanConfigEntry 1 }
				
        		dhcpFilteringVlanStatus OBJECT-TYPE
	          		SYNTAX  INTEGER{
	      				disable(0), 						
	      				enable(1)						
	      			}
	            	MAX-ACCESS  read-create
	            	STATUS  current
	            	DESCRIPTION
	                    "0. disable 
	                     1. enable
	                     Enable or disable DHCP Filtering function in specified VLAN. "
	            ::= { dhcpFilteringVlanConfigEntry 2 }	            
       -- the dhcp Filter port config
         
       			dhcpFilteringPortConfigTable OBJECT-TYPE
          			SYNTAX  SEQUENCE OF DhcpFilteringPortConfigEntry
          			MAX-ACCESS  not-accessible
          			STATUS  current
          			DESCRIPTION
                  		"A list of DHCP Filtering port config entries.
                   		Here you can configure the port parameters for the DHCP Filtering."
          		::= { dhcpFilteringPortConfig 1 }

      			dhcpFilteringPortConfigEntry OBJECT-TYPE
          			SYNTAX  DhcpFilteringPortConfigEntry
          			MAX-ACCESS  not-accessible
          			STATUS  current
          			DESCRIPTION
                  		"An entry contains of the information of DHCP Filtering port config."
          			INDEX   {ifIndex}
          		::= { dhcpFilteringPortConfigTable 1 }
  
      			DhcpFilteringPortConfigEntry ::=
          			SEQUENCE {
          					dhcpFilteringPort
          						    OCTET STRING (SIZE (0..255)),
							dhcpFilteringPortConfigTrustedPort
									INTEGER, 
							dhcpFilteringPortConfigPortLag
									OCTET STRING  
          			}
          			
                dhcpFilteringPort OBJECT-TYPE
					SYNTAX  	OCTET STRING (SIZE (0..255))
					MAX-ACCESS  read-only
					STATUS  	current
					DESCRIPTION
						"Display port number"
				::= { dhcpFilteringPortConfigEntry 1 }
               
      			dhcpFilteringPortConfigTrustedPort OBJECT-TYPE
          			SYNTAX  INTEGER{
      					disable(0), 						
      					enable(1)			
      				}
          			MAX-ACCESS  read-write
          			STATUS  current
          			DESCRIPTION
                  		"0. disable
                   		 1. enable
                   		 Select Enable/Disable the port to be a Trusted Port. 
                   		 Only the Trusted Port can receive the DHCP packets from DHCP servers."
          		::= { dhcpFilteringPortConfigEntry 2 }
       
      			dhcpFilteringPortConfigPortLag OBJECT-TYPE
            		SYNTAX  OCTET STRING (SIZE (1..255))  
            		MAX-ACCESS  read-only
            		STATUS  current
            		DESCRIPTION
                    	"The LAG to which the port belongs to."
            	::= { dhcpFilteringPortConfigEntry 3 }
          
END
