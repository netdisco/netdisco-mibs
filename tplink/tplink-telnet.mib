TPLINK-TELNET-MIB DEFINITIONS ::= BEGIN

		IMPORTS
			OBJECT-TYPE,MODULE-IDENTITY
				FROM SNMPv2-SMI
			tplinkMgmt
				FROM TPLINK-MIB;

		tplinkTelnet MODULE-IDENTITY  
			LAST-UPDATED	"201602261110Z"
			ORGANIZATION	"TPLINK"
			CONTACT-INFO	"www.tplink.com.cn"
			DESCRIPTION		"Private MIB for Telnet configuration."
			REVISION		"201602261110Z"
			DESCRIPTION		"Initial version of this MIB module."
			::= { tplinkMgmt 52 }

		tplinkTelnetMIBObjects		OBJECT IDENTIFIER ::= {tplinkTelnet 1}
		tplinkTelnetMIBNotifications	OBJECT IDENTIFIER ::= {tplinkTelnet 2}

		telnetConfig	OBJECT-TYPE
			SYNTAX  INTEGER{
					disable(0),
					enable(1)
					}
			MAX-ACCESS  read-write
			STATUS  current
			DESCRIPTION
					"0. disable
					1. enable"
			::= { tplinkTelnetMIBObjects 1 }


		END
