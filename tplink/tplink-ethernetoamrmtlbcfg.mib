TPLINK-ETHERNETOAMRMTLBCFG-MIB DEFINITIONS ::= BEGIN
		IMPORTS
			OBJECT-TYPE					FROM SNMPv2-SMI
			ethernetOamRmtLbConfig		FROM TPLINK-ETHERNETOAM-MIB
			DisplayString
							FROM SNMPv2-TC
			ifIndex
							FROM RFC1213-MIB;

		ethernetOamRmtLbCfgTable OBJECT-TYPE
			SYNTAX SEQUENCE OF EthernetOamRmtLbCfgEntry
			MAX-ACCESS	not-accessible
			STATUS	current
			DESCRIPTION
			"A table that contains remote loopback configuration of each port. 
			A local OAM entity can send a remote loopback OAMPDU to the remote OAM entity, requesting the remote OAM entity to perform loopback.
			This function can provide necessary help for troubleshooting. In the loopback mode, all packets except OAMPDUs are returned along the way they are sent."
			::= {ethernetOamRmtLbConfig 1}

		ethernetOamRmtLbCfgEntry OBJECT-TYPE
			SYNTAX EthernetOamRmtLbCfgEntry      
			MAX-ACCESS	not-accessible
			STATUS	current
			DESCRIPTION
			"An entry that contains the remote loopback configuration of each port."
			INDEX {ifIndex}
			::= {ethernetOamRmtLbCfgTable 1}

		EthernetOamRmtLbCfgEntry ::=
		SEQUENCE
		{
			ethernetOamRmtLbCfgPort					DisplayString,
			ethernetOamRmtLbCfgReceivedRemoteLoopback	INTEGER,
			ethernetOamRmtLbCfgRemoteLoopback			INTEGER,
			ethernetOamRmtLbCfgLAG						OCTET STRING(SIZE(0..10))
		}

		ethernetOamRmtLbCfgPort OBJECT-TYPE
			SYNTAX DisplayString
			MAX-ACCESS	read-only
			STATUS	current
			DESCRIPTION
			"Displays the port number."
			::= {ethernetOamRmtLbCfgEntry 1}

		ethernetOamRmtLbCfgReceivedRemoteLoopback OBJECT-TYPE
			SYNTAX INTEGER {ignore(0),process(1)}
			MAX-ACCESS	read-write
			STATUS	current
			DESCRIPTION
			"Select to Process or Ignore the received Ethernet OAM remote loopback command."
			::= {ethernetOamRmtLbCfgEntry 2}

		ethernetOamRmtLbCfgRemoteLoopback OBJECT-TYPE
			SYNTAX INTEGER {stop(0),start(1),unchanged(2)}
			MAX-ACCESS	read-write
			STATUS	current
			DESCRIPTION
			"Select to Start or Stop the Ethernet OAM remote loopback function."
			::= {ethernetOamRmtLbCfgEntry 3}

		ethernetOamRmtLbCfgLAG OBJECT-TYPE
			SYNTAX OCTET STRING(SIZE(0..10))
			MAX-ACCESS	read-only
			STATUS	current
			DESCRIPTION
			"Displays the LAG number of the port."
			::= {ethernetOamRmtLbCfgEntry 4}

END
