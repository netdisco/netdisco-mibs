TPLINK-USERSECURITY-MIB DEFINITIONS ::= BEGIN

          IMPORTS
			  TPRowStatus       	 
  					FROM TPLINK-TC-MIB
              OBJECT-TYPE,MODULE-IDENTITY,IpAddress
          	  	         	FROM SNMPv2-SMI
              tplinkMgmt	          
          	  	          FROM TPLINK-MIB
			  ifIndex 
							FROM  RFC1213-MIB;
  	  	
  	  	MacAddress ::= OCTET STRING (SIZE (6))          	
  	  	
	      tplinkUserSecurity MODULE-IDENTITY  
		    LAST-UPDATED    "2009070900Z"
		    ORGANIZATION    "TPLINK"
		    CONTACT-INFO    "www.tplink.com.cn"
		    DESCRIPTION
		             "Implementation of the user security is mandatory for the
					swtich."
		    REVISION        "2009070900Z"
		    DESCRIPTION
				"Initial version of this MIB module."
		    ::= { tplinkMgmt 41 }      	               
          
		   tplinkUserSecurityMIBObjects   OBJECT IDENTIFIER    ::=  {tplinkUserSecurity 1}
		   tplinkUserSecurityMIBNotifications OBJECT IDENTIFIER ::=   {tplinkUserSecurity 2}
          userSecurityUserAuth OBJECT IDENTIFIER ::= { tplinkUserSecurityMIBObjects 1}   
          
          userSecurityUserAuthType OBJECT-TYPE
              SYNTAX INTEGER{
	      		disable(0), 					
	      		ip(1),
	      		mac(2),
	      		port(3)					
	      	   }
              MAX-ACCESS  read-only
              STATUS  current
              DESCRIPTION
                      "disable(0), 					
	      		ip(1),
	      		mac(2),
	      		port(3)
	      		The mode of user authentication."
              ::= { userSecurityUserAuth 1 }
          
         userSecurityUserAuthPort OBJECT IDENTIFIER ::= { userSecurityUserAuth 2 }
         
         userSecurityUserAuthPortEnable OBJECT-TYPE
              SYNTAX  INTEGER{
	      		disable(0), 					
	      		enable(1)					
	      		}
              MAX-ACCESS  read-write
              STATUS  current
              DESCRIPTION
                       "0. disable
                      1.enable"
              ::= { userSecurityUserAuthPort 1 }
			  
		  userSecurityUserAuthPortAccessSnmp OBJECT-TYPE
              SYNTAX  INTEGER{
	      		disable(0), 					
	      		enable(1)					
	      		}
              MAX-ACCESS  read-write
              STATUS  current
              DESCRIPTION
                      "0. disable -- SNMP frame sent to the switch will be accepted by default
					  1. enable -- SNMP frame sent to the switch will be accepted only if it comes from the auth port(s)"
              ::= { userSecurityUserAuthPort 2 }
			  
			userSecurityUserAuthPortAccessTelnet OBJECT-TYPE
              SYNTAX  INTEGER{
	      		disable(0), 					
	      		enable(1)					
	      		}
              MAX-ACCESS  read-write
              STATUS  current
              DESCRIPTION
                      "0. disable -- Telnet frame sent to the switch will be accepted by default
					  1. enable -- Telnet frame sent to the switch will be accepted only if it comes from the auth port(s)"
              ::= { userSecurityUserAuthPort 3 }
			  
			userSecurityUserAuthPortAccessSsh OBJECT-TYPE
              SYNTAX  INTEGER{
	      		disable(0), 					
	      		enable(1)					
	      		}
              MAX-ACCESS  read-write
              STATUS  current
              DESCRIPTION
                      "0. disable -- SSH frame sent to the switch will be accepted by default
					  1. enable -- SSH frame sent to the switch will be accepted only if it comes from the auth port(s)"
              ::= { userSecurityUserAuthPort 4 }
			  
			userSecurityUserAuthPortAccessHttp OBJECT-TYPE
              SYNTAX  INTEGER{
	      		disable(0), 					
	      		enable(1)					
	      		}
              MAX-ACCESS  read-write
              STATUS  current
              DESCRIPTION
                      "0. disable -- HTTP frame sent to the switch will be accepted by default
					  1. enable -- HTTP frame sent to the switch will be accepted only if it comes from the auth port(s)"
              ::= { userSecurityUserAuthPort 5 }
			  
			userSecurityUserAuthPortAccessHttps OBJECT-TYPE
              SYNTAX  INTEGER{
	      		disable(0), 					
	      		enable(1)					
	      		}
              MAX-ACCESS  read-write
              STATUS  current
              DESCRIPTION
                      "0. disable -- HTTPS frame sent to the switch will be accepted by default
					  1. enable -- HTTPS frame sent to the switch will be accepted only if it comes from the auth port(s)"
              ::= { userSecurityUserAuthPort 6 }
			  
			userSecurityUserAuthPortAccessPing OBJECT-TYPE
              SYNTAX  INTEGER{
	      		disable(0), 					
	      		enable(1)					
	      		}
              MAX-ACCESS  read-write
              STATUS  current
              DESCRIPTION
                      "0. disable -- Ping request frame sent to the switch will be accepted by default
					  1. enable -- Ping request frame sent to the switch will be accepted only if it comes from the auth port(s)"
              ::= { userSecurityUserAuthPort 7 }
              
         
          userSecurityUserAuthPortTable OBJECT-TYPE
              SYNTAX  SEQUENCE OF USERSECURITYUSERAUTHPORTENTRY
              MAX-ACCESS  not-accessible
              STATUS  current
              DESCRIPTION
                      "A list of port."
              ::= { userSecurityUserAuthPort 8 }
          
          userSecurityUserAuthPortEntry OBJECT-TYPE
              SYNTAX  USERSECURITYUSERAUTHPORTENTRY
              MAX-ACCESS  not-accessible
              STATUS  current
              DESCRIPTION
                      "An entry contains of the port for user auth ."
              INDEX   { ifIndex }
              ::= { userSecurityUserAuthPortTable 1 }
              
              
          USERSECURITYUSERAUTHPORTENTRY ::=
           SEQUENCE {
                  userSecurityUserAuthPortConf
                      INTEGER
          }
        
            userSecurityUserAuthPortConf OBJECT-TYPE
              SYNTAX  INTEGER{
	      		disable(0), 					
	      		enable(1)					
	      		}
              MAX-ACCESS  read-write
              STATUS  current
              DESCRIPTION
                      "0. disable
                      1.enable"
              ::= { userSecurityUserAuthPortEntry 2 }
              
          --IP     
		  userSecurityUserAuthIp  OBJECT IDENTIFIER ::= { userSecurityUserAuth 3 }
          
          userSecurityUserAuthIpEnable OBJECT-TYPE
              SYNTAX  INTEGER{
	      		disable(0), 					
	      		enable(1)					
	      		}
              MAX-ACCESS  read-write
              STATUS  current
              DESCRIPTION
                       "0. disable
                      1.enable"
              ::= { userSecurityUserAuthIp 1 }
          
          userSecurityUserAuthIpTable OBJECT-TYPE
              SYNTAX  SEQUENCE OF USERSECURITYAUTHIPENTRY
              MAX-ACCESS  not-accessible
              STATUS  current
              DESCRIPTION
                      "A list of IP."
              ::= { userSecurityUserAuthIp 2 }
          
          userSecurityUserAuthIpEntry OBJECT-TYPE
              SYNTAX  USERSECURITYAUTHIPENTRY
              MAX-ACCESS  not-accessible
              STATUS  current
              DESCRIPTION
                      "An entry contains of the IP for user authentication ."
              INDEX   { userSecurityUserAuthIndex }
              ::= { userSecurityUserAuthIpTable 1 }
          
          USERSECURITYAUTHIPENTRY ::=
           SEQUENCE {
           	  userSecurityUserAuthIpIndex  	INTEGER,
				userSecurityUserAuthIpAccessSnmp INTEGER,
				userSecurityUserAuthIpAccessTelnet INTEGER,
				userSecurityUserAuthIpAccessSsh INTEGER,
				userSecurityUserAuthIpAccessHttp INTEGER,
				userSecurityUserAuthIpAccessHttps INTEGER,
				userSecurityUserAuthIpAccessPing INTEGER,
                  userSecurityUserAuthIpAddress IpAddress,                
                      userSecurityUserAuthIpMask    IpAddress                      
          }
          
          userSecurityUserAuthIpIndex OBJECT-TYPE
              SYNTAX  INTEGER
              MAX-ACCESS  read-only
              STATUS  current
              DESCRIPTION
                      "IP entry ID"
              ::= { userSecurityUserAuthIpEntry 1 }
             
	  userSecurityUserAuthIpAccessSnmp OBJECT-TYPE
              SYNTAX  INTEGER{
	      		disable(0), 					
	      		enable(1)					
	      		}
              MAX-ACCESS  read-write
              STATUS  current
              DESCRIPTION
                       "0. disable -- SNMP frame sent to the switch will be accepted by default
                      1.enable -- SNMP frame sent to the switch will be accepted only if its source ip is in the same network segment with auth ip"
              ::= { userSecurityUserAuthIpEntry 2 }
			  
	  userSecurityUserAuthIpAccessTelnet OBJECT-TYPE
              SYNTAX  INTEGER{
	      		disable(0), 					
	      		enable(1)					
	      		}
              MAX-ACCESS  read-write
              STATUS  current
              DESCRIPTION
                       "0. disable -- Telnet frame sent to the switch will be accepted by default
                      1.enable -- Telnet frame sent to the switch will be accepted only if its source ip is in the same network segment with auth ip"
              ::= { userSecurityUserAuthIpEntry 3 }
			  
	  userSecurityUserAuthIpAccessSsh OBJECT-TYPE
              SYNTAX  INTEGER{
	      		disable(0), 					
	      		enable(1)					
	      		}
              MAX-ACCESS  read-write
              STATUS  current
              DESCRIPTION
                       "0. disable -- SSH frame sent to the switch will be accepted by default
                      1.enable -- SSH frame sent to the switch will be accepted only if its source ip is in the same network segment with auth ip"
              ::= { userSecurityUserAuthIpEntry 4 }
		
	  userSecurityUserAuthIpAccessHttp OBJECT-TYPE
              SYNTAX  INTEGER{
	      		disable(0), 					
	      		enable(1)					
	      		}
              MAX-ACCESS  read-write
              STATUS  current
              DESCRIPTION
                       "0. disable -- HTTP frame sent to the switch will be accepted by default
                      1.enable -- HTTP frame sent to the switch will be accepted only if its source ip is in the same network segment with auth ip"
              ::= { userSecurityUserAuthIpEntry 5 }
			  
	  userSecurityUserAuthIpAccessHttps OBJECT-TYPE
              SYNTAX  INTEGER{
	      		disable(0), 					
	      		enable(1)					
	      		}
              MAX-ACCESS  read-write
              STATUS  current
              DESCRIPTION
                       "0. disable -- HTTPS frame sent to the switch will be accepted by default
                      1.enable -- HTTPS frame sent to the switch will be accepted only if its source ip is in the same network segment with auth ip"
              ::= { userSecurityUserAuthIpEntry 6 }
			  
	  userSecurityUserAuthIpAccessPing OBJECT-TYPE
              SYNTAX  INTEGER{
	      		disable(0), 					
	      		enable(1)					
	      		}
              MAX-ACCESS  read-write
              STATUS  current
              DESCRIPTION
                       "0. disable -- Ping request frame sent to the switch will be accepted by default
                      1.enable -- Ping request frame sent to the switch will be accepted only if its source ip is in the same network segment with auth ip"
              ::= { userSecurityUserAuthIpEntry 7 }
                  
          userSecurityUserAuthIpAddress OBJECT-TYPE
              SYNTAX  IpAddress
              MAX-ACCESS  read-write
              STATUS  current
              DESCRIPTION
                      "the auth ip address.for example: 192.168.0.1"
              ::= { userSecurityUserAuthIpEntry 8 }
              
          userSecurityUserAuthIpMask OBJECT-TYPE
              SYNTAX  IpAddress
              MAX-ACCESS  read-write
              STATUS  current
              DESCRIPTION
                      "the subnet mask of the auth ip address.for example: 255.255.255.0"
              ::= { userSecurityUserAuthIpEntry 9 }
          
          --MAC
         userSecurityUserAuthMac  OBJECT IDENTIFIER ::= { userSecurityUserAuth 4 }
              
          userSecurityUserAuthMacEnable OBJECT-TYPE
              SYNTAX  INTEGER{
	      		disable(0), 					
	      		enable(1)					
	      		}
              MAX-ACCESS  read-write
              STATUS  current
              DESCRIPTION
                       "0. disable
                      1.enable"
              ::= { userSecurityUserAuthMac 1 }
		  
		  userSecurityUserAuthMacAccessSnmp OBJECT-TYPE
              SYNTAX  INTEGER{
	      		disable(0), 					
	      		enable(1)					
	      		}
              MAX-ACCESS  read-write
              STATUS  current
              DESCRIPTION
                      "0. disable -- SNMP frame sent to the switch will be accepted by default
					  1. enable -- SNMP frame sent to the switch will be accepted only if its source mac is auth mac"
              ::= { userSecurityUserAuthMac 2 }
			  
			userSecurityUserAuthMacAccessTelnet OBJECT-TYPE
              SYNTAX  INTEGER{
	      		disable(0), 					
	      		enable(1)					
	      		}
              MAX-ACCESS  read-write
              STATUS  current
              DESCRIPTION
                      "0. disable -- Telnet frame sent to the switch will be accepted by default
					  1. enable -- Telnet frame sent to the switch will be accepted only if its source mac is auth mac"
              ::= { userSecurityUserAuthMac 3 }
			  
			userSecurityUserAuthMacAccessSsh OBJECT-TYPE
              SYNTAX  INTEGER{
	      		disable(0), 					
	      		enable(1)					
	      		}
              MAX-ACCESS  read-write
              STATUS  current
              DESCRIPTION
                      "0. disable -- SSH frame sent to the switch will be accepted by default
					  1. enable -- SSH frame sent to the switch will be accepted only if its source mac is auth mac"
              ::= { userSecurityUserAuthMac 4 }
			  
			userSecurityUserAuthMacAccessHttp OBJECT-TYPE
              SYNTAX  INTEGER{
	      		disable(0), 					
	      		enable(1)					
	      		}
              MAX-ACCESS  read-write
              STATUS  current
              DESCRIPTION
                      "0. disable -- HTTP frame sent to the switch will be accepted by default
					  1. enable -- HTTP frame sent to the switch will be accepted only if its source mac is auth mac"
              ::= { userSecurityUserAuthMac 5 }
			  
			userSecurityUserAuthMacAccessHttps OBJECT-TYPE
              SYNTAX  INTEGER{
	      		disable(0), 					
	      		enable(1)					
	      		}
              MAX-ACCESS  read-write
              STATUS  current
              DESCRIPTION
                      "0. disable -- HTTPS frame sent to the switch will be accepted by default
					  1. enable -- HTTPS frame sent to the switch will be accepted only if its source mac is auth mac"
              ::= { userSecurityUserAuthMac 6 }
			  
			userSecurityUserAuthMacAccessPing OBJECT-TYPE
              SYNTAX  INTEGER{
	      		disable(0), 					
	      		enable(1)					
	      		}
              MAX-ACCESS  read-write
              STATUS  current
              DESCRIPTION
                      "0. disable -- Ping request frame sent to the switch will be accepted by default
					  1. enable -- Ping request frame sent to the switch will be accepted only if its source mac is auth mac"
              ::= { userSecurityUserAuthMac 7 }
              
          userSecurityUserAuthMacAddress OBJECT-TYPE
              SYNTAX  OCTET STRING (SIZE (0..255))
              MAX-ACCESS  read-write
              STATUS  current
              DESCRIPTION
                      "the auth mac"
              ::= { userSecurityUserAuthMac 8 }
				
			
          
            
          END
