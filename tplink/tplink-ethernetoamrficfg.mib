TPLINK-ETHERNETOAMRFICFG-MIB DEFINITIONS ::= BEGIN
		IMPORTS
			OBJECT-TYPE				FROM SNMPv2-SMI
			ethernetOamRfiConfig	FROM TPLINK-ETHERNETOAM-MIB
			DisplayString
							FROM SNMPv2-TC
			ifIndex
							FROM RFC1213-MIB;

		ethernetOamRfiCfgTable OBJECT-TYPE
			SYNTAX SEQUENCE OF EthernetOamRfiCfgEntry
			MAX-ACCESS	not-accessible
			STATUS	current
			DESCRIPTION
			"A table that contains remote failure indication configuration of each port.
			Ethernet faults are difficult to diagnose, especially when physical communication is still maintained but network performance is decreasing gradually.
			OAMPDU defines a flag to allow an OAM entity to send information to the peer. The flag defines an emergency link event supported by OAM."
			::= {ethernetOamRfiConfig 1}

		ethernetOamRfiCfgEntry OBJECT-TYPE
			SYNTAX EthernetOamRfiCfgEntry      
			MAX-ACCESS	not-accessible
			STATUS	current
			DESCRIPTION
			"An entry that contains the remote failure indication configuration of each port."
			INDEX {ifIndex}
			::= {ethernetOamRfiCfgTable 1}

		EthernetOamRfiCfgEntry ::=
		SEQUENCE
		{
			ethernetOamRfiCfgPort					DisplayString,
			ethernetOamRfiCfgDyingGaspNotify		INTEGER,
			ethernetOamRfiCfgCriticalEventNotify	INTEGER,
			ethernetOamRfiCfgLAG					OCTET STRING(SIZE(0..10))
		}

		ethernetOamRfiCfgPort OBJECT-TYPE
			SYNTAX DisplayString
			MAX-ACCESS	read-only
			STATUS	current
			DESCRIPTION
			"Displays the port number."
			::= {ethernetOamRfiCfgEntry 1}

		ethernetOamRfiCfgDyingGaspNotify OBJECT-TYPE
			SYNTAX INTEGER {disable(0),enable(1)}
			MAX-ACCESS	read-write
			STATUS	current
			DESCRIPTION
			"Select to enable or disable the event notification when critical link event is Dying Gasp."
			::= {ethernetOamRfiCfgEntry 2}

		ethernetOamRfiCfgCriticalEventNotify OBJECT-TYPE
			SYNTAX INTEGER {disable(0),enable(1)}
			MAX-ACCESS	read-write
			STATUS	current
			DESCRIPTION
			"Select to enable or disable the event notification when critical link event is Critical Event."
			::= {ethernetOamRfiCfgEntry 3}

		ethernetOamRfiCfgLAG OBJECT-TYPE
			SYNTAX OCTET STRING(SIZE(0..10))
			MAX-ACCESS	read-only
			STATUS	current
			DESCRIPTION
			"Displays the LAG number of the port."
			::= {ethernetOamRfiCfgEntry 4}

END
