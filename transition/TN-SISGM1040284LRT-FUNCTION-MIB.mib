TN-SISGM1040284LRT-FUNCTION-MIB DEFINITIONS ::= BEGIN

IMPORTS
    DisplayString,MacAddress,TEXTUAL-CONVENTION,RowStatus                                              FROM SNMPv2-TC
    MODULE-COMPLIANCE,OBJECT-GROUP, NOTIFICATION-GROUP                                                 FROM SNMPv2-CONF
    ifIndex                                                                                            FROM IF-MIB
    enterprises,MODULE-IDENTITY,OBJECT-TYPE,NOTIFICATION-TYPE,Unsigned32,Integer32,Counter32,Counter64,IpAddress  FROM SNMPv2-SMI
--  PortList                                                                                           FROM Q-BRIDGE-MIB
    InetAddress, InetAddressType                                                                       FROM INET-ADDRESS-MIB
    OwnerString                                                                                        FROM RMON-MIB
    SnmpAdminString                                                                                    FROM SNMP-FRAMEWORK-MIB;
--  MacAddress FROM BRIDGE-MIB;

transition MODULE-IDENTITY
        LAST-UPDATED "202203150934Z"
        ORGANIZATION "Corp."
        CONTACT-INFO
            " "
        DESCRIPTION "Hardened Managed Switch, (8) 10/100/1000Base-T + (4) 100/1000Base-X SFP Slots"
		REVISION      "201405300000Z"
        DESCRIPTION
		"Rev 1.0 Initial version."
        ::= { enterprises 868 }


-- =======================================================================================================================

     OperState ::= TEXTUAL-CONVENTION
       STATUS         current
       DESCRIPTION
                      "Oper state."
       SYNTAX         INTEGER  { up ( 1 ) , down ( 2 ) }

     AdminMode ::= TEXTUAL-CONVENTION
       STATUS      current
       DESCRIPTION
            "The Admin state - default: disable(0)."
       SYNTAX  INTEGER { disable(0), enable(1) }

     AdminMode2 ::= TEXTUAL-CONVENTION
       STATUS      current
       DESCRIPTION
            "The Admin state - default: disable(0)."
       SYNTAX  INTEGER { disable(0), enable(1), notSupported(2) }

     ActivateCmd ::= TEXTUAL-CONVENTION
       STATUS      current
       DESCRIPTION
            "Used to activate commands. default: noAction(0). "
       SYNTAX         INTEGER  {  noAction ( 0 ),
                                  activate ( 1 )
                               }

     KeyType ::= TEXTUAL-CONVENTION
       STATUS      current
       DESCRIPTION
           "The key type specifying the key generated for frames received
            on the port.
            0 : Normal,
            1 : Double Tag,
            2 : IP Address,
            3 : MAC and IP Address."
        SYNTAX      INTEGER  { normal  ( 0 ),
                               doubleTag ( 1 ),
                               ipAddr ( 2 ),
                               macAndIpAddr ( 3 )
                             }

     FrameRate ::= TEXTUAL-CONVENTION
       STATUS      current
       DESCRIPTION
           "The values for frame rate"
       SYNTAX       INTEGER {
                            threeHundredFramesPerSec (0),
                            oneHundredFramesPerSec (1),
                            tenFramesPerSec (2),
                            oneFramePerSec (3),
                            sixFramesPerMin (4),
                            oneFramePerMin  (5),
                            sixFramesPerHour (6)
                            }

     DayOfWeek ::= TEXTUAL-CONVENTION
       STATUS      current
       DESCRIPTION
            "Used to set the days of the week."
       SYNTAX       INTEGER {mon(1),tue(2),wed(3),thur(4),
                             fri(5),sat(6),sun(7) }

     Month ::= TEXTUAL-CONVENTION
       STATUS      current
       DESCRIPTION
            "Used to set the month."
       SYNTAX       INTEGER {jan(1),feb(2),march(3),april(4),
                             may(5),june(6),july(7),aug(8),
                             sept(9),oct(10),nov(11),dec(12)}


switch                                                          OBJECT IDENTIFIER ::= { transition 2 }

sisgm1040284lrtProductLevel1  OBJECT IDENTIFIER ::= { switch 80 }
sisgm1040284lrtProductId  OBJECT IDENTIFIER ::= { sisgm1040284lrtProductLevel1 9 }


sisgm1040284lrtSystem                                                OBJECT IDENTIFIER ::= { sisgm1040284lrtProductId 1 }

sisgm1040284lrtSystemInformation                                     OBJECT IDENTIFIER ::= { sisgm1040284lrtSystem 1 }

sisgm1040284lrtSystemInfoTable OBJECT-TYPE
   SYNTAX      SEQUENCE OF SISGM1040284LRTSystemInfoEntry
   MAX-ACCESS  not-accessible
   STATUS      current
   DESCRIPTION
       " Configure System Information Table. "
   ::= { sisgm1040284lrtSystemInformation 1 }

sisgm1040284lrtSystemInfoEntry OBJECT-TYPE
   SYNTAX      SISGM1040284LRTSystemInfoEntry
   MAX-ACCESS  not-accessible
   STATUS      current
   DESCRIPTION
       " "
   INDEX    { sisgm1040284lrtSystemInfoSwitchIndex }
   ::= { sisgm1040284lrtSystemInfoTable 1 }

SISGM1040284LRTSystemInfoEntry ::= SEQUENCE {
   sisgm1040284lrtSystemInfoSwitchIndex        Integer32,
   sisgm1040284lrtSystemInfoModelName          DisplayString,
   sisgm1040284lrtSystemInfoSystemDescript     DisplayString,
   sisgm1040284lrtSystemInfoLocation           DisplayString,
   sisgm1040284lrtSystemInfoContact            DisplayString,
   sisgm1040284lrtSystemInfoSystemName         DisplayString,
   sisgm1040284lrtSystemInfoSystemDate         DisplayString,
   sisgm1040284lrtSystemInfoSystemUptime       DisplayString,
   sisgm1040284lrtSystemInfoBootloaderVersion  DisplayString,
   sisgm1040284lrtSystemInfoFirmwareVersion    DisplayString,
   sisgm1040284lrtSystemInfoHardwareVersion    DisplayString,
   sisgm1040284lrtSystemInfoMechanicalVersion  DisplayString,
   sisgm1040284lrtSystemInfoSerialNumber       DisplayString,
   sisgm1040284lrtSystemInfoHostMACAddress     DisplayString,
   sisgm1040284lrtSystemInfoMemory             DisplayString,
   sisgm1040284lrtSystemInfoFlash              DisplayString,
   sisgm1040284lrtSystemInfoPowerStatus        DisplayString,
   sisgm1040284lrtSystemInfoPowers             DisplayString,
   sisgm1040284lrtSystemInfoTemperatureStatus  DisplayString,
   sisgm1040284lrtSystemInfoTemperature1       DisplayString,
   sisgm1040284lrtSystemInfoTemperature2       DisplayString,
   sisgm1040284lrtSystemInfoCPULoad            DisplayString
}

sisgm1040284lrtSystemInfoSwitchIndex OBJECT-TYPE
   SYNTAX      Integer32 (1..16)
   MAX-ACCESS  not-accessible
   STATUS      current
   DESCRIPTION
       "Switch Index."
   ::= { sisgm1040284lrtSystemInfoEntry 1 }

sisgm1040284lrtSystemInfoModelName OBJECT-TYPE
   SYNTAX       DisplayString
   MAX-ACCESS   read-only
   STATUS       current
   DESCRIPTION
       " "
   ::= { sisgm1040284lrtSystemInfoEntry 2 }

sisgm1040284lrtSystemInfoSystemDescript OBJECT-TYPE
   SYNTAX       DisplayString
   MAX-ACCESS   read-only
   STATUS       current
   DESCRIPTION
       " "
   ::= { sisgm1040284lrtSystemInfoEntry 3 }

sisgm1040284lrtSystemInfoLocation OBJECT-TYPE
   SYNTAX       DisplayString
   MAX-ACCESS   read-write
   STATUS       current
   DESCRIPTION
       " "
   ::= { sisgm1040284lrtSystemInfoEntry 4 }

sisgm1040284lrtSystemInfoContact OBJECT-TYPE
   SYNTAX       DisplayString
   MAX-ACCESS   read-write
   STATUS       current
   DESCRIPTION
       " "
   ::= { sisgm1040284lrtSystemInfoEntry 5 }

sisgm1040284lrtSystemInfoSystemName OBJECT-TYPE
   SYNTAX       DisplayString
   MAX-ACCESS   read-write
   STATUS       current
   DESCRIPTION
       " "
   ::= { sisgm1040284lrtSystemInfoEntry 6 }

sisgm1040284lrtSystemInfoSystemDate OBJECT-TYPE
   SYNTAX       DisplayString
   MAX-ACCESS   read-only
   STATUS       current
   DESCRIPTION
       " "
   ::= { sisgm1040284lrtSystemInfoEntry 7 }

sisgm1040284lrtSystemInfoSystemUptime OBJECT-TYPE
   SYNTAX       DisplayString
   MAX-ACCESS   read-only
   STATUS       current
   DESCRIPTION
       " "
   ::= { sisgm1040284lrtSystemInfoEntry 8 }

sisgm1040284lrtSystemInfoBootloaderVersion OBJECT-TYPE
   SYNTAX       DisplayString
   MAX-ACCESS   read-only
   STATUS       current
   DESCRIPTION
       " "
   ::= { sisgm1040284lrtSystemInfoEntry 9 }

sisgm1040284lrtSystemInfoFirmwareVersion OBJECT-TYPE
   SYNTAX       DisplayString
   MAX-ACCESS   read-only
   STATUS       current
   DESCRIPTION
       " "
   ::= { sisgm1040284lrtSystemInfoEntry 10 }

sisgm1040284lrtSystemInfoHardwareVersion OBJECT-TYPE
   SYNTAX       DisplayString
   MAX-ACCESS   read-only
   STATUS       current
   DESCRIPTION
       " "
   ::= { sisgm1040284lrtSystemInfoEntry 11 }

sisgm1040284lrtSystemInfoMechanicalVersion OBJECT-TYPE
   SYNTAX       DisplayString
   MAX-ACCESS   read-only
   STATUS       current
   DESCRIPTION
       " "
   ::= { sisgm1040284lrtSystemInfoEntry 12 }

sisgm1040284lrtSystemInfoSerialNumber OBJECT-TYPE
   SYNTAX       DisplayString
   MAX-ACCESS   read-only
   STATUS       current
   DESCRIPTION
       " "
   ::= { sisgm1040284lrtSystemInfoEntry 13 }

sisgm1040284lrtSystemInfoHostMACAddress OBJECT-TYPE
   SYNTAX       DisplayString
   MAX-ACCESS   read-only
   STATUS       current
   DESCRIPTION
       " "
   ::= { sisgm1040284lrtSystemInfoEntry 14 }

sisgm1040284lrtSystemInfoMemory OBJECT-TYPE
   SYNTAX       DisplayString
   MAX-ACCESS   read-only
   STATUS       current
   DESCRIPTION
       " "
   ::= { sisgm1040284lrtSystemInfoEntry 15 }

sisgm1040284lrtSystemInfoFlash OBJECT-TYPE
   SYNTAX       DisplayString
   MAX-ACCESS   read-only
   STATUS       current
   DESCRIPTION
       " "
   ::= { sisgm1040284lrtSystemInfoEntry 16 }

sisgm1040284lrtSystemInfoPowerStatus OBJECT-TYPE
   SYNTAX       DisplayString
   MAX-ACCESS   read-only
   STATUS       current
   DESCRIPTION
       " "
   ::= { sisgm1040284lrtSystemInfoEntry 19 }
   
sisgm1040284lrtSystemInfoPowers OBJECT-TYPE
   SYNTAX       DisplayString
   MAX-ACCESS   read-only
   STATUS       current
   DESCRIPTION
       " "
   ::= { sisgm1040284lrtSystemInfoEntry 20 }
   
sisgm1040284lrtSystemInfoTemperatureStatus OBJECT-TYPE
   SYNTAX       DisplayString
   MAX-ACCESS   read-only
   STATUS       current
   DESCRIPTION
       " "
   ::= { sisgm1040284lrtSystemInfoEntry 21 }   

sisgm1040284lrtSystemInfoTemperature1 OBJECT-TYPE
   SYNTAX       DisplayString
   MAX-ACCESS   read-only
   STATUS       current
   DESCRIPTION
       " "
   ::= { sisgm1040284lrtSystemInfoEntry 22 }

sisgm1040284lrtSystemInfoTemperature2 OBJECT-TYPE
   SYNTAX       DisplayString
   MAX-ACCESS   read-only
   STATUS       current
   DESCRIPTION
       " "
   ::= { sisgm1040284lrtSystemInfoEntry 23 }
   
sisgm1040284lrtSystemInfoCPULoad OBJECT-TYPE
   SYNTAX       DisplayString
   MAX-ACCESS   read-only
   STATUS       current
   DESCRIPTION
       "CPU Utilization."
   ::= { sisgm1040284lrtSystemInfoEntry 24 }     
   
sisgm1040284lrtSystemTimeConf                                    OBJECT IDENTIFIER ::= { sisgm1040284lrtSystem 2 }

sisgm1040284lrtSystemNTP                                      OBJECT IDENTIFIER ::= { sisgm1040284lrtSystemTimeConf  1 }

sisgm1040284lrtSystemTime                                      OBJECT IDENTIFIER ::= { sisgm1040284lrtSystemTimeConf  2 }
sisgm1040284lrtSystemTimeZone                              OBJECT IDENTIFIER ::= { sisgm1040284lrtSystemTime 1 }
sisgm1040284lrtSystemTimeDaylightSaving             OBJECT IDENTIFIER ::= { sisgm1040284lrtSystemTime 2 }
sisgm1040284lrtSystemTimeConfiguration              OBJECT IDENTIFIER ::= { sisgm1040284lrtSystemTime 3 }

    --
-- =======================================================================================================================
-- Objects in the sisgm1040284lrtSystemNTP Group
-- =======================================================================================================================
    sisgm1040284lrtSystemNTPMode OBJECT-TYPE
               SYNTAX       INTEGER {useLocal(0),useNTP(1)}
               MAX-ACCESS   read-write
               STATUS       current
               DESCRIPTION
                   "The system NTP Mode.
                    useLocal(0) : Use Local Settings,
                    useNTP(1)   : Use NTP Server."
               DEFVAL  { useLocal }
               ::= {     sisgm1040284lrtSystemNTP 1 }

    sisgm1040284lrtSystemNTPServer1    OBJECT-TYPE
               SYNTAX            DisplayString
               MAX-ACCESS        read-write
               STATUS            current
               DESCRIPTION
                   "Get/Set the NTP Time Server1.
                    You can use the IP address or domain name."
               ::= {     sisgm1040284lrtSystemNTP 2 }

    sisgm1040284lrtSystemNTPServer2    OBJECT-TYPE
               SYNTAX            DisplayString
               MAX-ACCESS        read-write
               STATUS            current
               DESCRIPTION
                   "Get/Set the NTP Time Server2.
                    You can use the IP address or domain name."
               ::= {     sisgm1040284lrtSystemNTP 3 }

    sisgm1040284lrtSystemNTPServer3    OBJECT-TYPE
               SYNTAX            DisplayString
               MAX-ACCESS        read-write
               STATUS            current
               DESCRIPTION
                   "Get/Set the NTP Time Server3.
                    You can use the IP address or domain name."
               ::= {     sisgm1040284lrtSystemNTP 4 }

    sisgm1040284lrtSystemNTPServer4    OBJECT-TYPE
               SYNTAX            DisplayString
               MAX-ACCESS        read-write
               STATUS            current
               DESCRIPTION
                   "Get/Set the NTP Time Server4.
                    You can use the IP address or domain name."
               ::= {     sisgm1040284lrtSystemNTP 5 }

    sisgm1040284lrtSystemNTPServer5    OBJECT-TYPE
               SYNTAX            DisplayString
               MAX-ACCESS        read-write
               STATUS            current
               DESCRIPTION
                   "Get/Set the NTP Time Server5.
                    You can use the IP address or domain name."
               ::= {     sisgm1040284lrtSystemNTP 6 }


--
-- =======================================================================================================================
-- Objects in the sisgm1040284lrtSystemTime Group
-- =======================================================================================================================
--sisgm1040284lrtSystemTimeZone

    sisgm1040284lrtSystemTimeZoneConf OBJECT-TYPE
               SYNTAX       Integer32(-7200..7201)
               MAX-ACCESS   read-write
               STATUS       current
               DESCRIPTION
                   "Get/Set the NTP Time Zone.
                    The value range is between -7200 and 7201 (minutes).
                    0 : None.
                    -7200 : (GMT-12:00).
                    -6600 : (GMT-11:00).
                    -6000 : (GMT-10:00).
                    -5400 : (GMT-09:00).
                    -4800 : (GMT-08:00)Pacific Time.
                    -4801 : (GMT-08:00)Tijuana, Baja California.
                    -4200 : (GMT-07:00)Arizona.
                    -4201 : (GMT-07:00)Chihuahua, La Paz, Mazatlan - New.
                    -4202 : (GMT-07:00)Chihuahua, La Paz, Mazatlan - Old.
                    -4203 : (GMT-07:00)Mountain Time.
                    -3600 : (GMT-06:00)Central America.
                    -3601 : (GMT-06:00)Central Time.
                    -3602 : (GMT-06:00)Guadalajara, Mexico City, Monterrey - New.
                    -3603 : (GMT-06:00)Guadalajara, Mexico City, Monterrey - Old.
                    -3604 : (GMT-06:00)Saskatchewan.
                    -3000 : (GMT-05:00)Bogota, Lima, Quito, Rio Branco.
                    -3001 : (GMT-05:00)Eastern Time.
                    -3002 : (GMT-05:00)Indiana.
                    -2700 : (GMT-04:30).
                    -2400 : (GMT-04:00)Atlantic Time.
                    -2401 : (GMT-04:00)La Paz.
                    -2402 : (GMT-04:00)Manaus.
                    -2403 : (GMT-04:00)Santiago.
                    -2100 : (GMT-03:30).
                    -1800 : (GMT-03:00)Brasilia.
                    -1801 : (GMT-03:00)Buenos Aires.
                    -1802 : (GMT-03:00)Georgetown.
                    -1803 : (GMT-03:00)Greenland.
                    -1804 : (GMT-03:00)Montevideo.
                    -1805 : (GMT-02:00).
                    -600 : (GMT-01:00)Azores.
                    -601 : (GMT-01:00)Cape Verde Is.
                    1 : (GMT) Casablanca.
                    2 : (GMT) Greenwich Mean Time.
                    3 : (GMT) Monrovia, Reykjavik.
                    600 : (GMT+01:00) Amsterdam, Berlin, Bern, Rome, Stockholm, Vienna.
                    601 : (GMT+01:00) Belgrade, Bratislava, Budapest, Ljubljana, Prague.
                    602 : (GMT+01:00) Brussels, Copenhagen, Madrid, Paris.
                    603 : (GMT+01:00) Sarajevo, Skopje, Warsaw, Zagreb.
                    604 : (GMT+01:00) West Central Africa.
                    1200 : (GMT+02:00) Amman.
                    1201 : (GMT+02:00) Athens, Bucharest, Istanbul.
                    1202 : (GMT+02:00) Beirut.
                    1203 : (GMT+02:00) Cairo.
                    1204 : (GMT+02:00) Harare, Pretoria.
                    1205 : (GMT+02:00) Helsinki, Kyiv, Riga, Sofia, Tallinn, Vilnius.
                    1206 : (GMT+02:00) Jerusalem.
                    1207 : (GMT+02:00) Minsk.
                    1208 : (GMT+02:00) Windhoek.
                    1800 : (GMT+03:00) Baghdad.
                    1801 : (GMT+03:00) Kuwait, Riyadh.
                    1802 : (GMT+03:00) Moscow, St. Petersburg, Volgograd.
                    1803 : (GMT+03:00) Nairobi.
                    1804 : (GMT+03:00) Tbilisi.
                    2100 : (GMT+03:30) Tehran.
                    2400 : (GMT+04:00) Abu Dhabi, Muscat.
                    2401 : (GMT+04:00) Baku.
                    2402 : (GMT+04:00) Caucasus Standard Time.
                    2403 : (GMT+04:00) Port Louis.
                    2404 : (GMT+04:00) Yerevan.
                    2700 : (GMT+04:30) Kabul.
                    3000 : (GMT+05:00) Ekaterinburg.
                    3001 : (GMT+05:00) Islamabad, Karachi.
                    3002 : (GMT+05:00) Tashkent.
                    3300 : (GMT+05:30) Chennai, Kolkata, Mumbai, New Delhi.
                    3301 : (GMT+05:30) Sri Jayawardenepura.
                    3455 : (GMT+05:45) Kathmandu.
                    3600 : (GMT+06:00) Almaty, Novosibirsk.
                    3601 : (GMT+06:00) Astana, Dhaka.
                    3600 : (GMT+06:30) Yangon (Rangoon).
                    4200 : (GMT+07:00) Bangkok, Hanoi, Jakarta.
                    4201 : (GMT+07:00) Krasnoyarsk.
                    4800 : (GMT+08:00) Beijing, Chongqing, Hong Kong, Urumqi.
                    4801 : (GMT+08:00) Irkutsk, Ulaan Bataar.
                    4802 : (GMT+08:00) Kuala Lumpur, Singapore.
                    4803 : (GMT+08:00) Perth.
                    4804 : (GMT+08:00) Taipei.
                    5400 : (GMT+09:00) Osaka, Sapporo, Tokyo.
                    5401 : (GMT+09:00) Seoul.
                    5402 : (GMT+09:00) Yakutsk.
                    5700 : (GMT+09:30) Adelaide.
                    5701 : (GMT+09:30) Darwin.
                    6000 : (GMT+10:00) Brisbane.
                    6001 : (GMT+10:00) Canberra, Melbourne, Sydney.
                    6002 : (GMT+10:00) Guam, Port Moresby.
                    6003 : (GMT+10:00) Hobart.
                    6004 : (GMT+10:00) Vladivostok.
                    6600 : (GMT+11:00) Magadan, Solomon Is., New Caledonia.
                    7200 : (GMT+12:00) Auckland, Wellington.
                    7201 : (GMT+12:00) Fiji, Kamchatka, Marshall Is."
               ::= {     sisgm1040284lrtSystemTimeZone 1 }

    sisgm1040284lrtSystemTimeZoneAcronym OBJECT-TYPE
               SYNTAX       DisplayString
               MAX-ACCESS   read-write
               STATUS       current
               DESCRIPTION
                   "Acronym - User can set the acronym of the time zone.
                    This is a User configurable acronym to identify the time zone.
                    Range : 0 - 16 characters."
               ::= {     sisgm1040284lrtSystemTimeZone 2 }

--sisgm1040284lrtSystemTimeDaylightSaving

    sisgm1040284lrtSystemTimeDaylightSavingMode OBJECT-TYPE
               SYNTAX       INTEGER { disable(0), recurring(1), nonRecurring(2) }
               MAX-ACCESS   read-write
               STATUS       current
               DESCRIPTION
                   "The system Daylight Savings Mode.
                    disable(0)   : Disable.
                    recurring(1) : Recurring
                        - configure the Daylight Saving Time duration
                        to repeat the configuration every year.
                    nonRecurring(2): Non-Recurring - configure the Daylight Saving Time
                        duration for single time configuration."
               DEFVAL  { disable }
               ::= {     sisgm1040284lrtSystemTimeDaylightSaving 1 }

    sisgm1040284lrtSystemTimeDaylightSavingStartWeek OBJECT-TYPE
               SYNTAX       Integer32 (1..5)
               MAX-ACCESS   read-write
               STATUS       current
               DESCRIPTION
                   "Start time Week. Use in Recurring Mode.
                    Range : 1 - 5.
                    Default : 1."
               ::= {     sisgm1040284lrtSystemTimeDaylightSaving 2 }

    sisgm1040284lrtSystemTimeDaylightSavingStartDay OBJECT-TYPE
               SYNTAX       DayOfWeek
               MAX-ACCESS   read-write
               STATUS       current
               DESCRIPTION
                   "Start time Day. Use in Recurring Mode."
               DEFVAL  { mon }
               ::= {     sisgm1040284lrtSystemTimeDaylightSaving 3 }

    sisgm1040284lrtSystemTimeDaylightSavingStartMonth OBJECT-TYPE
               SYNTAX       Month
               MAX-ACCESS   read-write
               STATUS       current
               DESCRIPTION
                   "Start time Month."
               DEFVAL  { jan }
               ::= {     sisgm1040284lrtSystemTimeDaylightSaving 4 }

    sisgm1040284lrtSystemTimeDaylightSavingStartDate OBJECT-TYPE
               SYNTAX       Integer32 (1..31)
               MAX-ACCESS   read-write
               STATUS       current
               DESCRIPTION
                   "Start time Date. Use in Non-Recurring Mode.
                    Range : 1 - 31.
                    Default : 1."
               ::= {     sisgm1040284lrtSystemTimeDaylightSaving 5 }

    sisgm1040284lrtSystemTimeDaylightSavingStartYear OBJECT-TYPE
               SYNTAX       Integer32 (2000..2097)
               MAX-ACCESS   read-write
               STATUS       current
               DESCRIPTION
                   "Start time Year. Use in Non-Recurring Mode.
                    Range : 2000 - 2097.
                    Default : 2000."
               ::= {     sisgm1040284lrtSystemTimeDaylightSaving 6 }

    sisgm1040284lrtSystemTimeDaylightSavingStartHours OBJECT-TYPE
               SYNTAX       Integer32 (0..23)
               MAX-ACCESS   read-write
               STATUS       current
               DESCRIPTION
                   "Start time Hours.
                     Range : 0 - 23.
                     Default : 0."
               ::= {     sisgm1040284lrtSystemTimeDaylightSaving 7 }

    sisgm1040284lrtSystemTimeDaylightSavingStartMinutes OBJECT-TYPE
               SYNTAX       Integer32 (0..59)
               MAX-ACCESS   read-write
               STATUS       current
               DESCRIPTION
                   "Start time Minutes.
                    Range : 0 - 59.
                    Default : 0."
               ::= {     sisgm1040284lrtSystemTimeDaylightSaving 8 }

    sisgm1040284lrtSystemTimeDaylightSavingEndWeek OBJECT-TYPE
               SYNTAX       Integer32 (1..5)
               MAX-ACCESS   read-write
               STATUS       current
               DESCRIPTION
                   "End time Week. Use in Recurring Mode.
                    Range : 1 - 5.
                    Default : 1."
               ::= {     sisgm1040284lrtSystemTimeDaylightSaving 9 }

    sisgm1040284lrtSystemTimeDaylightSavingEndDay OBJECT-TYPE
               SYNTAX       DayOfWeek
               MAX-ACCESS   read-write
               STATUS       current
               DESCRIPTION
                   "End time Day. Use in Recurring Mode."
               DEFVAL  { mon }
               ::= {     sisgm1040284lrtSystemTimeDaylightSaving 10 }

    sisgm1040284lrtSystemTimeDaylightSavingEndMonth OBJECT-TYPE
               SYNTAX       Month
               MAX-ACCESS   read-write
               STATUS       current
               DESCRIPTION
                   "End time Month."
              DEFVAL  { jan }
              ::= {     sisgm1040284lrtSystemTimeDaylightSaving 11 }

    sisgm1040284lrtSystemTimeDaylightSavingEndDate OBJECT-TYPE
               SYNTAX       Integer32 (1..31)
               MAX-ACCESS   read-write
               STATUS       current
               DESCRIPTION
                   "End time Date. Use in Non-Recurring Mode.
                    Range : 1 - 31.
                    Default : 1."
               ::= {     sisgm1040284lrtSystemTimeDaylightSaving 12 }

    sisgm1040284lrtSystemTimeDaylightSavingEndYear OBJECT-TYPE
               SYNTAX       Integer32 (2000..2097)
               MAX-ACCESS   read-write
               STATUS       current
               DESCRIPTION
                   "End time Year. Use in Non-Recurring Mode.
                    Range : 2000 - 2097.
                    Default : 2000."
               ::= {     sisgm1040284lrtSystemTimeDaylightSaving 13 }

    sisgm1040284lrtSystemTimeDaylightSavingEndHours OBJECT-TYPE
               SYNTAX       Integer32 (0..23)
               MAX-ACCESS   read-write
               STATUS       current
               DESCRIPTION
                   "End time Hours.
                    Range : 0 - 23.
                    Default : 0."
               ::= {     sisgm1040284lrtSystemTimeDaylightSaving 14 }

    sisgm1040284lrtSystemTimeDaylightSavingEndMinutes OBJECT-TYPE
               SYNTAX       Integer32 (0..59)
               MAX-ACCESS   read-write
               STATUS       current
               DESCRIPTION
                   "End time Minutes.
                    Range : 0 - 59.
                    Default : 0."
               ::= {     sisgm1040284lrtSystemTimeDaylightSaving 15 }

    sisgm1040284lrtSystemTimeDaylightSavingOffset OBJECT-TYPE
               SYNTAX       Integer32 (1..1440)
               MAX-ACCESS   read-write
               STATUS       current
               DESCRIPTION
                   "Offset - the number of minutes to add during Daylight Saving Time.
                    Range : 1 - 1440(Minutes).
                    Default : 1."
               ::= {     sisgm1040284lrtSystemTimeDaylightSaving 16 }

    sisgm1040284lrtSystemTimeConfigurationClockSource OBJECT-TYPE
               SYNTAX       Integer32
               MAX-ACCESS   read-write
               STATUS       current
               DESCRIPTION
                   "0:Use Local Settings.
                    1:Use NTP Server."
	           ::= {     sisgm1040284lrtSystemTimeConfiguration 1}

    sisgm1040284lrtSystemTimeConfigurationDateFormat OBJECT-TYPE
               SYNTAX       Integer32 (0|1|2)
               MAX-ACCESS   read-write
               STATUS       current
               DESCRIPTION
                   "The date format of the system.
				   0:yyyy-mm-dd
				   1:mm-dd-yyyy
				   2:dd-mm-yyyy"
	           ::= {     sisgm1040284lrtSystemTimeConfiguration 2}
			   
    sisgm1040284lrtSystemTimeConfigurationTimeFormat OBJECT-TYPE
               SYNTAX       Integer32 (0|1)
               MAX-ACCESS   read-write
               STATUS       current
               DESCRIPTION
                   "The time format of the system.
				   0:24-hr, format:hh:mm:ss
				   1:12-hr, format:hh:mm:ss am/pm"
	           ::= {     sisgm1040284lrtSystemTimeConfiguration 3}
			   
    sisgm1040284lrtSystemTimeConfigurationSystemDate OBJECT-TYPE
               SYNTAX       DisplayString
               MAX-ACCESS   read-write
               STATUS       current
               DESCRIPTION
                   "System date. Default format:yyyy-mm-dd.
                    When ClockSource is Use Local Settings, you can set this field."
	           ::= {     sisgm1040284lrtSystemTimeConfiguration 4}
			   
    sisgm1040284lrtSystemTimeConfigurationSystemTime OBJECT-TYPE
               SYNTAX       DisplayString
               MAX-ACCESS   read-write
               STATUS       current
               DESCRIPTION
                   "System date.
				    24-hr, format:hh:mm:ss
				    12-hr, format:hh:mm:ss am/pm
                    When ClockSource is Use Local Settings, you can set this field."
	           ::= {     sisgm1040284lrtSystemTimeConfiguration 5}			   

-- =======================================================================================================================
sisgm1040284lrtSystemAccount                                         OBJECT IDENTIFIER ::= { sisgm1040284lrtSystem 3 }

sisgm1040284lrtSystemAccountUsers                                     OBJECT IDENTIFIER  ::= { sisgm1040284lrtSystemAccount 1 }

--
-- =======================================================================================================================
-- Start sisgm1040284lrtUserConfig group
-- =======================================================================================================================
--sisgm1040284lrtUserConfigTable

    sisgm1040284lrtUserConfigTable OBJECT-TYPE
               SYNTAX      SEQUENCE OF     SISGM1040284LRTUserConfigEntry
               MAX-ACCESS  not-accessible
               STATUS      current
               DESCRIPTION
                   "The User Config Table. "
               ::= {     sisgm1040284lrtSystemAccountUsers 1 }

    sisgm1040284lrtUserConfigEntry OBJECT-TYPE
               SYNTAX          SISGM1040284LRTUserConfigEntry
               MAX-ACCESS  not-accessible
               STATUS      current
               DESCRIPTION
                   "The User Config Entry."
               INDEX    {    sisgm1040284lrtUserConfigIndex  }
               ::= {     sisgm1040284lrtUserConfigTable 1 }

    SISGM1040284LRTUserConfigEntry             ::= SEQUENCE {
                 sisgm1040284lrtUserConfigIndex            Integer32,
                 sisgm1040284lrtUserConfigUserName         DisplayString,
                 sisgm1040284lrtUserConfigPassword         DisplayString,
                 sisgm1040284lrtUserConfigPrivilegeLevel   Integer32,
                 sisgm1040284lrtUserConfigRowStatus        RowStatus
                }

    sisgm1040284lrtUserConfigIndex OBJECT-TYPE
               SYNTAX      Integer32 (1..4095)
               MAX-ACCESS  not-accessible
               STATUS      current
               DESCRIPTION
                   "The user Config Index. "
               ::= {     sisgm1040284lrtUserConfigEntry 1 }

    sisgm1040284lrtUserConfigUserName OBJECT-TYPE
               SYNTAX      DisplayString(SIZE (1..31))
               MAX-ACCESS  read-create
               STATUS      current
               DESCRIPTION
                   "A string identifying the user name for the entry.
                    string length: 1-31. "
               ::= {     sisgm1040284lrtUserConfigEntry 2 }

    sisgm1040284lrtUserConfigPassword OBJECT-TYPE
               SYNTAX      DisplayString(SIZE (0..31))
               MAX-ACCESS  read-create
               STATUS      current
               DESCRIPTION
                   "The password of the user.
                    string length: 0-31. "
               ::= {     sisgm1040284lrtUserConfigEntry 3 }

    sisgm1040284lrtUserConfigPrivilegeLevel OBJECT-TYPE
               SYNTAX      Integer32(1..15)
               MAX-ACCESS  read-create
               STATUS      current
               DESCRIPTION
                   "The privilege level of the user.If the privilege level
                    value is 15, it can access all groups.range: 1-15. "
               ::= {     sisgm1040284lrtUserConfigEntry 4 }

    sisgm1040284lrtUserConfigRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sisgm1040284lrtUserConfigEntry 5 }


--
-- =======================================================================================================================
-- Start sisgm1040284lrtPrivilegeLevelConfig group
-- =======================================================================================================================
--sisgm1040284lrtPrivilegeLevelConfigTable

    sisgm1040284lrtPrivilegeLevelConfigTable OBJECT-TYPE
               SYNTAX      SEQUENCE OF     SISGM1040284LRTPrivilegeLevelConfigEntry
               MAX-ACCESS  not-accessible
               STATUS      current
               DESCRIPTION
                   "The Privilege Level Config Table. "
               ::= {     sisgm1040284lrtSystemAccountUsers 2 }

    sisgm1040284lrtPrivilegeLevelConfigEntry OBJECT-TYPE
               SYNTAX          SISGM1040284LRTPrivilegeLevelConfigEntry
               MAX-ACCESS  not-accessible
               STATUS      current
               DESCRIPTION
                   "The Privilege Level Config Entry."
               INDEX    {    sisgm1040284lrtPrivilegeLevelIndex  }
               ::= {     sisgm1040284lrtPrivilegeLevelConfigTable 1 }

    SISGM1040284LRTPrivilegeLevelConfigEntry             ::= SEQUENCE {
                 sisgm1040284lrtPrivilegeLevelIndex                Integer32,
                 sisgm1040284lrtPrivilegeLevelGroupName            DisplayString,
                 sisgm1040284lrtPrivilegeLevelConfigReadOnly       Integer32,
                 sisgm1040284lrtPrivilegeLevelConfigReadWrite      Integer32,
                 sisgm1040284lrtPrivilegeLevelStatusReadOnly       Integer32,
                 sisgm1040284lrtPrivilegeLevelStatusReadWrite      Integer32
                 }

    sisgm1040284lrtPrivilegeLevelIndex OBJECT-TYPE
               SYNTAX      Integer32 (1..4095)
               MAX-ACCESS  not-accessible
               STATUS      current
               DESCRIPTION
                   "The Privilege Level Index. "
               ::= {     sisgm1040284lrtPrivilegeLevelConfigEntry 1 }

    sisgm1040284lrtPrivilegeLevelGroupName OBJECT-TYPE
               SYNTAX      DisplayString
               MAX-ACCESS  read-only
               STATUS      current
               DESCRIPTION
                   "The name identifying the privilege group."
               ::= {     sisgm1040284lrtPrivilegeLevelConfigEntry 2 }

    sisgm1040284lrtPrivilegeLevelConfigReadOnly OBJECT-TYPE
               SYNTAX      Integer32(1..15)
               MAX-ACCESS  read-write
               STATUS      current
               DESCRIPTION
                   "The privilege level of configuration read-only.If the
                    privilege level value is 15,it can access all groups.
                    range: 1-15.  "
               ::= {     sisgm1040284lrtPrivilegeLevelConfigEntry 3 }

    sisgm1040284lrtPrivilegeLevelConfigReadWrite OBJECT-TYPE
               SYNTAX      Integer32(1..15)
               MAX-ACCESS  read-write
               STATUS      current
               DESCRIPTION
                   "The privilege level of configuration/execute read/write.
                    If the privilege level value is 15,it can access all groups.
                    range: 1-15. "
               ::= {     sisgm1040284lrtPrivilegeLevelConfigEntry 4 }

    sisgm1040284lrtPrivilegeLevelStatusReadOnly OBJECT-TYPE
               SYNTAX      Integer32(1..15)
               MAX-ACCESS  read-write
               STATUS      current
               DESCRIPTION
                   "The privilege level of status/statistics read-only.
                    If the privilege level value is 15,it can access all groups.
                    range: 1-15. "
               ::= {     sisgm1040284lrtPrivilegeLevelConfigEntry 5 }

    sisgm1040284lrtPrivilegeLevelStatusReadWrite OBJECT-TYPE
               SYNTAX      Integer32(1..15)
               MAX-ACCESS  read-write
               STATUS      current
               DESCRIPTION
                   "The privilege level of status/statistics read-write.
                    If the privilege level value is 15,it can access all groups.
                    range: 1-15. "
               ::= {     sisgm1040284lrtPrivilegeLevelConfigEntry 6 }
-- =======================================================================================================================
sisgm1040284lrtIP                                                    OBJECT IDENTIFIER ::= { sisgm1040284lrtSystem 4 }

sisgm1040284lrtIPConfiguration OBJECT IDENTIFIER ::= { sisgm1040284lrtIP 1 }

sisgm1040284lrtMode OBJECT-TYPE
   SYNTAX      Integer32 (0|1)
   MAX-ACCESS  read-write
   STATUS      current
   DESCRIPTION
       "IP Configuration Mode.
        default:0
        0: Host
        1: Router"
   ::= {sisgm1040284lrtIPConfiguration 2 }

sisgm1040284lrtDNSServerSource1 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sisgm1040284lrtIPConfiguration 3 }
   
sisgm1040284lrtDNSServerSource2 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
		4. DNS configuration is derived from DHCPv6.
		5. DNS configuration is derived from DHCPv6 on specific VLAN.
		"
   ::= {sisgm1040284lrtIPConfiguration 4 }   
   
sisgm1040284lrtDNSServerSource3 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sisgm1040284lrtIPConfiguration 5 }  
   
sisgm1040284lrtDNSServerSource4 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sisgm1040284lrtIPConfiguration 6 }    

sisgm1040284lrtDNSServerValue1 OBJECT-TYPE
   SYNTAX      DisplayString
   MAX-ACCESS  read-write
   STATUS      current
   DESCRIPTION
       "DNS IPv4/IPv6 Address or VLAN value."
   ::= {sisgm1040284lrtIPConfiguration 7 }
   
sisgm1040284lrtDNSServerValue2 OBJECT-TYPE
   SYNTAX      DisplayString
   MAX-ACCESS  read-write
   STATUS      current
   DESCRIPTION
      "DNS IPv4/IPv6 Address or VLAN value."
   ::= {sisgm1040284lrtIPConfiguration 8 }   
   
sisgm1040284lrtDNSServerValue3 OBJECT-TYPE
   SYNTAX      DisplayString
   MAX-ACCESS  read-write
   STATUS      current
   DESCRIPTION
       "DNS IPv4/IPv6 Address or VLAN value."
   ::= {sisgm1040284lrtIPConfiguration 9 }    
   
sisgm1040284lrtDNSServerValue4 OBJECT-TYPE
   SYNTAX      DisplayString
   MAX-ACCESS  read-write
   STATUS      current
   DESCRIPTION
       "DNS IPv4/IPv6 Address or VLAN value."
   ::= {sisgm1040284lrtIPConfiguration 10 }   
   
sisgm1040284lrtDNSProxy OBJECT-TYPE
   SYNTAX      Integer32 (0|1)
   MAX-ACCESS  read-write
   STATUS      current
   DESCRIPTION
       "DNS Proxy enable/disable.
        default:0
        0: disable
        1: enable"
   ::= {sisgm1040284lrtIPConfiguration 11 }


sisgm1040284lrtIPInterfaces OBJECT IDENTIFIER ::= { sisgm1040284lrtIP 2 }

sisgm1040284lrtIPInterfacesDHCPPerPortMode OBJECT-TYPE
   SYNTAX      INTEGER { disable(0), enable(1) }
   MAX-ACCESS  read-write
   STATUS      current
   DESCRIPTION
       "The dhcp per-port mode for the interface.
        0: Disable,
        1: Enable,
        default: Disable. "
   ::= { sisgm1040284lrtIPInterfaces 1 }

sisgm1040284lrtIPInterfacesDHCPPerPortIPRangeLow OBJECT-TYPE
   SYNTAX      IpAddress
   MAX-ACCESS  read-write
   STATUS      current
   DESCRIPTION
       "The dhcp per-port ip low for the interface."
   ::= { sisgm1040284lrtIPInterfaces 2 }

sisgm1040284lrtIPInterfacesDHCPPerPortIPRangeHigh OBJECT-TYPE
   SYNTAX      IpAddress
   MAX-ACCESS  read-write
   STATUS      current
   DESCRIPTION
       "The dhcp per-port ip high for the interface."
   ::= { sisgm1040284lrtIPInterfaces 3 }

sisgm1040284lrtIPInterfacesDHCPPerPortApply OBJECT-TYPE
   SYNTAX      Integer32 (1)
   MAX-ACCESS  read-write
   STATUS      current
   DESCRIPTION
       "1: Apply DHCP Per Port settings."
   ::= { sisgm1040284lrtIPInterfaces 4 }

sisgm1040284lrtIPInterfacesDHCPPerPortVLAN OBJECT-TYPE
   SYNTAX      Integer32 (1..4095)
   MAX-ACCESS  read-write
   STATUS      current
   DESCRIPTION
       "dhcp per-port VLAN."
   ::= { sisgm1040284lrtIPInterfaces 6 } 

sisgm1040284lrtIPInterfacesTable OBJECT-TYPE
   SYNTAX      SEQUENCE OF SISGM1040284LRTIPInterfacesEntry
   MAX-ACCESS  not-accessible
   STATUS      current
   DESCRIPTION
       "A table of IP interface for switch."
    ::= { sisgm1040284lrtIPInterfaces 5 }

sisgm1040284lrtIPInterfacesEntry OBJECT-TYPE
    SYNTAX        SISGM1040284LRTIPInterfacesEntry
    MAX-ACCESS    not-accessible
    STATUS        current
    DESCRIPTION
        "An entry in the sisgm1040284lrtIPInterfacesTable."
    INDEX        { sisgm1040284lrtIPInterfacesIndex }
    ::= { sisgm1040284lrtIPInterfacesTable 1 }

SISGM1040284LRTIPInterfacesEntry ::=
    SEQUENCE {
        sisgm1040284lrtIPInterfacesIndex                       Integer32,
        sisgm1040284lrtIPInterfacesVLAN                        Integer32,
        sisgm1040284lrtIPInterfacesIPv4DHCP                    Integer32,
        sisgm1040284lrtIPInterfacesIPv4DHCPFallback            DisplayString,
        sisgm1040284lrtIPInterfacesIPv4DHCPCurrentLease        IpAddress,
        sisgm1040284lrtIPInterfacesIPv4Address                 IpAddress,
        sisgm1040284lrtIPInterfacesIPv4Mask                    Integer32,
	sisgm1040284lrtIPInterfacesIPv6DHCP                    Integer32,
	sisgm1040284lrtIPInterfacesIPv6RapidCommit             Integer32,
	sisgm1040284lrtIPInterfacesIPv6CurrentLease            DisplayString,
        sisgm1040284lrtIPInterfacesIPv6Address                 DisplayString,
        sisgm1040284lrtIPInterfacesIPv6Mask                    Integer32,
	sisgm1040284lrtIPInterfacesRowStatus                   RowStatus
    }

sisgm1040284lrtIPInterfacesIndex OBJECT-TYPE
   SYNTAX      Integer32 (1..128)
   MAX-ACCESS  not-accessible
   STATUS      current
   DESCRIPTION
       "interface table index"
   ::= {sisgm1040284lrtIPInterfacesEntry 1 }

sisgm1040284lrtIPInterfacesVLAN OBJECT-TYPE
   SYNTAX      Integer32 (1..4095)
   MAX-ACCESS  read-write
   STATUS      current
   DESCRIPTION
       "VLAN ID for interface, range: 1-4095."
   ::= {sisgm1040284lrtIPInterfacesEntry 2 }

sisgm1040284lrtIPInterfacesIPv4DHCP OBJECT-TYPE
   SYNTAX      Integer32 (0|1)
   MAX-ACCESS  read-write
   STATUS      current
   DESCRIPTION
       "IPv4 DHCP Setting for interface.
        default:0
        0: disable
        1: enable"
   ::= {sisgm1040284lrtIPInterfacesEntry 3 }

sisgm1040284lrtIPInterfacesIPv4DHCPFallback OBJECT-TYPE
   SYNTAX      DisplayString
   MAX-ACCESS  read-write
   STATUS      current
   DESCRIPTION
       "IPv4 DHCP fallbcak. range: 1-4294967295 seconds."
   ::= {sisgm1040284lrtIPInterfacesEntry 4 }


sisgm1040284lrtIPInterfacesIPv4DHCPCurrentLease OBJECT-TYPE
   SYNTAX      IpAddress
   MAX-ACCESS  read-only
   STATUS      current
   DESCRIPTION
       "IPv4 DHCP Current Lease Address for interface."
   ::= {sisgm1040284lrtIPInterfacesEntry 5 }


sisgm1040284lrtIPInterfacesIPv4Address OBJECT-TYPE
   SYNTAX      IpAddress
   MAX-ACCESS  read-write
   STATUS      current
   DESCRIPTION
       "IPv4 address for interface."
   ::= {sisgm1040284lrtIPInterfacesEntry 6 }

sisgm1040284lrtIPInterfacesIPv4Mask OBJECT-TYPE
   SYNTAX      Integer32 (1..32)
   MAX-ACCESS  read-write
   STATUS      current
   DESCRIPTION
       "IPv4 mask for interface."
   ::= { sisgm1040284lrtIPInterfacesEntry 7 }

sisgm1040284lrtIPInterfacesIPv6DHCP OBJECT-TYPE
   SYNTAX      Integer32 (0|1)
   MAX-ACCESS  read-write
   STATUS      current
   DESCRIPTION
       "IPv6 DHCP Setting for interface.
        default:0
        0: disable
        1: enable"
   ::= {sisgm1040284lrtIPInterfacesEntry 8 } 
   
sisgm1040284lrtIPInterfacesIPv6RapidCommit OBJECT-TYPE
   SYNTAX      Integer32 (0|1)
   MAX-ACCESS  read-write
   STATUS      current
   DESCRIPTION
       "Enable the DHCPv6 Rapid-Commit option.
        default:0
        0: disable
        1: enable"
   ::= {sisgm1040284lrtIPInterfacesEntry 9 }    
   
sisgm1040284lrtIPInterfacesIPv6CurrentLease OBJECT-TYPE
   SYNTAX      DisplayString
   MAX-ACCESS  read-only
   STATUS      current
   DESCRIPTION
       "IPv6 DHCP Current Lease Address for interface."
   ::= {sisgm1040284lrtIPInterfacesEntry 10 }

   
sisgm1040284lrtIPInterfacesIPv6Address OBJECT-TYPE
   SYNTAX      DisplayString (SIZE (0..30))
   MAX-ACCESS  read-write
   STATUS      current
   DESCRIPTION
       "IPv6 address for interface."
   ::= { sisgm1040284lrtIPInterfacesEntry 11 }

sisgm1040284lrtIPInterfacesIPv6Mask OBJECT-TYPE
   SYNTAX      Integer32 (1..128)
   MAX-ACCESS  read-write
   STATUS      current
   DESCRIPTION
       "IPv6 mask for interface."
   ::= { sisgm1040284lrtIPInterfacesEntry 12 }

sisgm1040284lrtIPInterfacesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sisgm1040284lrtIPInterfacesEntry 13 }
   

sisgm1040284lrtIPRoutes OBJECT IDENTIFIER ::= { sisgm1040284lrtIP 3 }

sisgm1040284lrtIPRoutesTable OBJECT-TYPE
   SYNTAX      SEQUENCE OF SISGM1040284LRTIPRoutesEntry
   MAX-ACCESS  not-accessible
   STATUS      current
   DESCRIPTION
       "IP routes table for switch."
    ::= { sisgm1040284lrtIPRoutes 1 }

sisgm1040284lrtIPRoutesEntry OBJECT-TYPE
    SYNTAX        SISGM1040284LRTIPRoutesEntry
    MAX-ACCESS    not-accessible
    STATUS        current
    DESCRIPTION
        "Entry in the sisgm1040284lrtIPRoutesTable."
    INDEX        { sisgm1040284lrtIPRoutesIndex }
    ::= { sisgm1040284lrtIPRoutesTable 1 }

SISGM1040284LRTIPRoutesEntry ::=
    SEQUENCE {
        sisgm1040284lrtIPRoutesIndex                       Integer32,
        sisgm1040284lrtIPRoutesNetwork                     DisplayString,
        sisgm1040284lrtIPRoutesMaskLength                  Integer32,
        sisgm1040284lrtIPRoutesGateway                     DisplayString,
        sisgm1040284lrtIPRoutesNextHopVLAN                 Integer32,
	sisgm1040284lrtIPRoutesRowStatus                   RowStatus
    }

sisgm1040284lrtIPRoutesIndex OBJECT-TYPE
   SYNTAX      Integer32 (1..32)
   MAX-ACCESS  not-accessible
   STATUS      current
   DESCRIPTION
       "routes table index"
   ::= {sisgm1040284lrtIPRoutesEntry 2 }

sisgm1040284lrtIPRoutesNetwork OBJECT-TYPE
   SYNTAX      DisplayString (SIZE (0..30))
   MAX-ACCESS  read-write
   STATUS      current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= {sisgm1040284lrtIPRoutesEntry 3 }

sisgm1040284lrtIPRoutesMaskLength OBJECT-TYPE
   SYNTAX      Integer32 (1..32)
   MAX-ACCESS  read-write
   STATUS      current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sisgm1040284lrtIPRoutesEntry 4 }

sisgm1040284lrtIPRoutesGateway OBJECT-TYPE
   SYNTAX      DisplayString (SIZE (0..30))
   MAX-ACCESS  read-write
   STATUS      current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= {sisgm1040284lrtIPRoutesEntry 5 }

sisgm1040284lrtIPRoutesNextHopVLAN OBJECT-TYPE
   SYNTAX      Integer32 (1..4095)
   MAX-ACCESS  read-write
   STATUS      current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= {sisgm1040284lrtIPRoutesEntry 6 }

sisgm1040284lrtIPRoutesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sisgm1040284lrtIPRoutesEntry 7 }

sisgm1040284lrtIPConfigurationConfigured OBJECT IDENTIFIER ::= { sisgm1040284lrtIP 4 }

sisgm1040284lrtModeConfigured OBJECT-TYPE
   SYNTAX      Integer32 (0|1)
   MAX-ACCESS  read-only
   STATUS      current
   DESCRIPTION
       "IP Configuration Mode
	default:0
        0: Host
        1: Router"
   ::= {sisgm1040284lrtIPConfigurationConfigured 2 }

sisgm1040284lrtDNSServerSource1Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sisgm1040284lrtIPConfigurationConfigured 3 }
   
sisgm1040284lrtDNSServerSource2Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sisgm1040284lrtIPConfigurationConfigured 4 }
   
sisgm1040284lrtDNSServerSource3Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sisgm1040284lrtIPConfigurationConfigured 5 }   

sisgm1040284lrtDNSServerSource4Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sisgm1040284lrtIPConfigurationConfigured 6 }   

sisgm1040284lrtDNSServerValue1Configured OBJECT-TYPE
   SYNTAX      DisplayString
   MAX-ACCESS  read-only
   STATUS      current
   DESCRIPTION
       "DNS IPv4/IPv6 Address or VLAN value."
   ::= {sisgm1040284lrtIPConfigurationConfigured 7 }  

sisgm1040284lrtDNSServerValue2Configured OBJECT-TYPE
   SYNTAX      DisplayString
   MAX-ACCESS  read-only
   STATUS      current
   DESCRIPTION
       "DNS IPv4/IPv6 Address or VLAN value."
   ::= {sisgm1040284lrtIPConfigurationConfigured 8 } 
   
sisgm1040284lrtDNSServerValue3Configured OBJECT-TYPE
   SYNTAX      DisplayString
   MAX-ACCESS  read-only
   STATUS      current
   DESCRIPTION
       "DNS IPv4/IPv6 Address or VLAN value."
   ::= {sisgm1040284lrtIPConfigurationConfigured 9 } 

sisgm1040284lrtDNSServerValue4Configured OBJECT-TYPE
   SYNTAX      DisplayString
   MAX-ACCESS  read-only
   STATUS      current
   DESCRIPTION
       "DNS IPv4/IPv6 Address or VLAN value."
   ::= {sisgm1040284lrtIPConfigurationConfigured 10 }    
      
sisgm1040284lrtDNSProxyConfigured OBJECT-TYPE
   SYNTAX      Integer32 (0|1)
   MAX-ACCESS  read-only
   STATUS      current
   DESCRIPTION
       "DNS Proxy enable/disable.
        default:0
        0: disable
        1: enable"
   ::= {sisgm1040284lrtIPConfigurationConfigured 11 }


sisgm1040284lrtIPInterfacesConfigured OBJECT IDENTIFIER ::= { sisgm1040284lrtIP 5 }

sisgm1040284lrtIPInterfacesConfiguredTable OBJECT-TYPE
   SYNTAX      SEQUENCE OF SISGM1040284LRTIPInterfacesConfiguredEntry
   MAX-ACCESS  not-accessible
   STATUS      current
   DESCRIPTION
        "A table of ip interface for switch."
    ::= { sisgm1040284lrtIPInterfacesConfigured 1 }

sisgm1040284lrtIPInterfacesConfiguredEntry OBJECT-TYPE
    SYNTAX        SISGM1040284LRTIPInterfacesConfiguredEntry
    MAX-ACCESS    not-accessible
    STATUS        current
    DESCRIPTION
        "An entry in the sisgm1040284lrtIPInterfacesConfiguredTable."
    INDEX        { sisgm1040284lrtIPInterfacesIndexConfigured }
    ::= { sisgm1040284lrtIPInterfacesConfiguredTable 1 }

SISGM1040284LRTIPInterfacesConfiguredEntry ::=
    SEQUENCE {
        sisgm1040284lrtIPInterfacesIndexConfigured                       Integer32,
        sisgm1040284lrtIPInterfacesVLANConfigured                        Integer32,
        sisgm1040284lrtIPInterfacesIPv4DHCPConfigured                    Integer32,
        sisgm1040284lrtIPInterfacesIPv4DHCPFallbackConfigured            DisplayString,
        sisgm1040284lrtIPInterfacesIPv4AddressConfigured                 IpAddress,
        sisgm1040284lrtIPInterfacesIPv4MaskConfigured                    Integer32,
	sisgm1040284lrtIPInterfacesIPv6DHCPConfigured                    Integer32, 
	sisgm1040284lrtIPInterfacesIPv6RapidCommitConfigured             Integer32,
        sisgm1040284lrtIPInterfacesIPv6AddressConfigured                 DisplayString,
        sisgm1040284lrtIPInterfacesIPv6MaskConfigured                    Integer32
    }

sisgm1040284lrtIPInterfacesIndexConfigured OBJECT-TYPE
   SYNTAX      Integer32 (1..128)
   MAX-ACCESS  not-accessible
   STATUS      current
   DESCRIPTION
       "interface table index"
   ::= {sisgm1040284lrtIPInterfacesConfiguredEntry 2 }

sisgm1040284lrtIPInterfacesVLANConfigured OBJECT-TYPE
   SYNTAX      Integer32 (1..4095)
   MAX-ACCESS  read-only
   STATUS      current
   DESCRIPTION
       "VLAN ID for interface, range: 1-4095."
   ::= {sisgm1040284lrtIPInterfacesConfiguredEntry 3 }

sisgm1040284lrtIPInterfacesIPv4DHCPConfigured OBJECT-TYPE
   SYNTAX      Integer32 (0|1)
   MAX-ACCESS  read-only
   STATUS      current
   DESCRIPTION
       "IPv4 DHCP Setting for interface.
	default:0
        0: disable
        1: enable"
   ::= {sisgm1040284lrtIPInterfacesConfiguredEntry 4 }

sisgm1040284lrtIPInterfacesIPv4DHCPFallbackConfigured OBJECT-TYPE
   SYNTAX      DisplayString
   MAX-ACCESS  read-only
   STATUS      current
   DESCRIPTION
       "IPv4 DHCP fallbcak. range: 1-4294967295 seconds."
   ::= {sisgm1040284lrtIPInterfacesConfiguredEntry 5 }

sisgm1040284lrtIPInterfacesIPv4AddressConfigured OBJECT-TYPE
   SYNTAX      IpAddress
   MAX-ACCESS  read-only
   STATUS      current
   DESCRIPTION
       "IPv4 address for interface."
   ::= {sisgm1040284lrtIPInterfacesConfiguredEntry 6 }

sisgm1040284lrtIPInterfacesIPv4MaskConfigured OBJECT-TYPE
   SYNTAX      Integer32 (1..32)
   MAX-ACCESS  read-only
   STATUS      current
   DESCRIPTION
       "IPv4 mask for interface."
   ::= { sisgm1040284lrtIPInterfacesConfiguredEntry 7 }

sisgm1040284lrtIPInterfacesIPv6DHCPConfigured OBJECT-TYPE
   SYNTAX      Integer32 (0|1)
   MAX-ACCESS  read-only
   STATUS      current
   DESCRIPTION
       "IPv6 DHCP Setting for interface.
        default:0
        0: disable
        1: enable"
   ::= {sisgm1040284lrtIPInterfacesConfiguredEntry 8 } 
   
sisgm1040284lrtIPInterfacesIPv6RapidCommitConfigured OBJECT-TYPE
   SYNTAX      Integer32 (0|1)
   MAX-ACCESS  read-only
   STATUS      current
   DESCRIPTION
       "Enable the DHCPv6 Rapid-Commit option.
        default:0
        0: disable
        1: enable"
   ::= {sisgm1040284lrtIPInterfacesConfiguredEntry 9 } 

sisgm1040284lrtIPInterfacesIPv6AddressConfigured OBJECT-TYPE
   SYNTAX      DisplayString (SIZE (0..30))
   MAX-ACCESS  read-only
   STATUS      current
   DESCRIPTION
       "IPv6 address for interface."
   ::= { sisgm1040284lrtIPInterfacesConfiguredEntry 10 }

sisgm1040284lrtIPInterfacesIPv6MaskConfigured OBJECT-TYPE
   SYNTAX      Integer32 (1..128)
   MAX-ACCESS  read-only
   STATUS      current
   DESCRIPTION
       "IPv6 mask for interface."
   ::= { sisgm1040284lrtIPInterfacesConfiguredEntry 11 }

sisgm1040284lrtIPRoutesConfigured OBJECT IDENTIFIER ::= { sisgm1040284lrtIP 6 }

sisgm1040284lrtIPRoutesConfiguredTable OBJECT-TYPE
   SYNTAX      SEQUENCE OF SISGM1040284LRTIPRoutesConfiguredEntry
   MAX-ACCESS  not-accessible
   STATUS      current
   DESCRIPTION
        "IP routes table for switch."
    ::= { sisgm1040284lrtIPRoutesConfigured 1 }

sisgm1040284lrtIPRoutesConfiguredEntry OBJECT-TYPE
    SYNTAX        SISGM1040284LRTIPRoutesConfiguredEntry
    MAX-ACCESS    not-accessible
    STATUS        current
    DESCRIPTION
        "Entry in the sisgm1040284lrtIPRoutesConfiguredTable."
    INDEX        { sisgm1040284lrtIPRoutesIndexConfigured }
    ::= { sisgm1040284lrtIPRoutesConfiguredTable 1 }

SISGM1040284LRTIPRoutesConfiguredEntry ::=
    SEQUENCE {
        sisgm1040284lrtIPRoutesIndexConfigured                       Integer32,
        sisgm1040284lrtIPRoutesNetworkConfigured                     DisplayString,
        sisgm1040284lrtIPRoutesMaskLengthConfigured                  Integer32,
        sisgm1040284lrtIPRoutesGatewayConfigured                     DisplayString,
        sisgm1040284lrtIPRoutesNextHopVLANConfigured                 Integer32
    }

sisgm1040284lrtIPRoutesIndexConfigured OBJECT-TYPE
   SYNTAX      Integer32 (1..32)
   MAX-ACCESS  not-accessible
   STATUS      current
   DESCRIPTION
       "routes table index"
   ::= {sisgm1040284lrtIPRoutesConfiguredEntry 2 }

sisgm1040284lrtIPRoutesNetworkConfigured OBJECT-TYPE
   SYNTAX      DisplayString (SIZE (0..30))
   MAX-ACCESS  read-only
   STATUS      current
   DESCRIPTION
       "IPv4/IPv6 Network address.
        Note: All entries in routes table will be sort by 1.network address 2.mask length 3. gateway 4. next hop VLAN, if you add/modify an entry, all entries will be reordered. Please check all entries in table to find your modified entry after set/add an entry."
   ::= {sisgm1040284lrtIPRoutesConfiguredEntry 3 }

sisgm1040284lrtIPRoutesMaskLengthConfigured OBJECT-TYPE
   SYNTAX      Integer32 (1..32)
   MAX-ACCESS  read-only
   STATUS      current
   DESCRIPTION
       "IPv4/IPv6 mask length.
        Note: All entries in routes table will be sort by 1.network address 2.mask length 3. gateway 4. next hop VLAN, if you add/modify an entry, all entries will be reordered. Please check all entries in table to find your modified entry after set/add an entry."
   ::= { sisgm1040284lrtIPRoutesConfiguredEntry 4 }

sisgm1040284lrtIPRoutesGatewayConfigured OBJECT-TYPE
   SYNTAX      DisplayString (SIZE (0..30))
   MAX-ACCESS  read-only
   STATUS      current
   DESCRIPTION
       "IPv4/IPv6 Gateway.
        Note: All entries in routes table will be sort by 1.network address 2.mask length 3. gateway 4. next hop VLAN, if you add/modify an entry, all entries will be reordered. Please check all entries in table to find your modified entry after set/add an entry."
   ::= {sisgm1040284lrtIPRoutesConfiguredEntry 5 }

sisgm1040284lrtIPRoutesNextHopVLANConfigured OBJECT-TYPE
   SYNTAX      Integer32 (1..4095)
   MAX-ACCESS  read-only
   STATUS      current
   DESCRIPTION
       "Next Hop VLAN ID, range: 1-4095.
        Note: All entries in routes table will be sort by 1.network address 2.mask length 3. gateway 4. next hop VLAN, if you add/modify an entry, all entries will be reordered. Please check all entries in table to find your modified entry after set/add an entry."
   ::= {sisgm1040284lrtIPRoutesConfiguredEntry 6 }

sisgm1040284lrtIPStatusInterface OBJECT IDENTIFIER ::= { sisgm1040284lrtIP 7 }

sisgm1040284lrtIPStatusInterfaceTable OBJECT-TYPE
              SYNTAX      SEQUENCE OF     SISGM1040284LRTIPStatusInterfaceEntry
              MAX-ACCESS  not-accessible
              STATUS      current
              DESCRIPTION
                       "The system IP Status table to show all IP interfaces."
                   ::= {     sisgm1040284lrtIPStatusInterface 1 }

    sisgm1040284lrtIPStatusInterfaceEntry OBJECT-TYPE
               SYNTAX          SISGM1040284LRTIPStatusInterfaceEntry
               MAX-ACCESS  not-accessible
               STATUS      current
               DESCRIPTION
                       "An entry in the IP Status Table."
               INDEX    {    sisgm1040284lrtIPStatusInterfaceIndex  }
               ::= {     sisgm1040284lrtIPStatusInterfaceTable 1 }

    SISGM1040284LRTIPStatusInterfaceEntry             ::= SEQUENCE {
            sisgm1040284lrtIPStatusInterfaceIndex         Integer32,
            sisgm1040284lrtIPStatusInterfaceName          DisplayString,
            sisgm1040284lrtIPStatusInterfaceType          DisplayString,
            sisgm1040284lrtIPStatusInterfaceAddress       DisplayString,
            sisgm1040284lrtIPStatusInterfaceStatus        DisplayString
            }

    sisgm1040284lrtIPStatusInterfaceIndex OBJECT-TYPE
               SYNTAX      Integer32(1..1024)
               MAX-ACCESS  not-accessible
               STATUS      current
               DESCRIPTION
                   "The entry of table to show all IP interfaces."
               ::= {     sisgm1040284lrtIPStatusInterfaceEntry 1 }

    sisgm1040284lrtIPStatusInterfaceName OBJECT-TYPE
               SYNTAX      DisplayString
               MAX-ACCESS  read-only
               STATUS      current
               DESCRIPTION
                   "The name of the interface."
               ::= {     sisgm1040284lrtIPStatusInterfaceEntry 2 }

    sisgm1040284lrtIPStatusInterfaceType OBJECT-TYPE
               SYNTAX      DisplayString
               MAX-ACCESS  read-only
               STATUS      current
               DESCRIPTION
                   "The address type of the entry. This may be LINK or IPv4."
               ::= {     sisgm1040284lrtIPStatusInterfaceEntry 3 }

    sisgm1040284lrtIPStatusInterfaceAddress OBJECT-TYPE
               SYNTAX      DisplayString
               MAX-ACCESS  read-only
               STATUS      current
               DESCRIPTION
                   "The current address of the interface (of the given type)."
               ::= {     sisgm1040284lrtIPStatusInterfaceEntry 4 }

    sisgm1040284lrtIPStatusInterfaceStatus OBJECT-TYPE
               SYNTAX      DisplayString
               MAX-ACCESS  read-only
               STATUS      current
               DESCRIPTION
                   "The status flags of the interface (and/or address)."
               ::= {     sisgm1040284lrtIPStatusInterfaceEntry 5 }

sisgm1040284lrtIPStatusRoute OBJECT IDENTIFIER ::= { sisgm1040284lrtIP 8 }

    sisgm1040284lrtIPStatusRouteTable OBJECT-TYPE
              SYNTAX      SEQUENCE OF     SISGM1040284LRTIPStatusRouteEntry
              MAX-ACCESS  not-accessible
              STATUS      current
              DESCRIPTION
                       "The IP Status Route table show all routing entries."
                   ::= {     sisgm1040284lrtIPStatusRoute 1 }

    sisgm1040284lrtIPStatusRouteEntry OBJECT-TYPE
               SYNTAX          SISGM1040284LRTIPStatusRouteEntry
               MAX-ACCESS  not-accessible
               STATUS      current
               DESCRIPTION
                       "an entry in the IP Status route table."
               INDEX    {     sisgm1040284lrtIPStatusRouteIndex  }
               ::= {     sisgm1040284lrtIPStatusRouteTable 1 }

    SISGM1040284LRTIPStatusRouteEntry             ::= SEQUENCE {
            sisgm1040284lrtIPStatusRouteIndex          Integer32,
            sisgm1040284lrtIPStatusRouteNetwork        DisplayString,
            sisgm1040284lrtIPStatusRouteGateway        DisplayString,
            sisgm1040284lrtIPStatusRouteAddress        DisplayString
     }

    sisgm1040284lrtIPStatusRouteIndex OBJECT-TYPE
               SYNTAX      Integer32(1..2048)
               MAX-ACCESS  not-accessible
               STATUS      current
               DESCRIPTION
                   "The entry of table to show all routing entries."
               ::= {     sisgm1040284lrtIPStatusRouteEntry 1 }

    sisgm1040284lrtIPStatusRouteNetwork OBJECT-TYPE
               SYNTAX      DisplayString
               MAX-ACCESS  read-only
               STATUS      current
               DESCRIPTION
                   "The destination IP network or host address of this route."
               ::= {     sisgm1040284lrtIPStatusRouteEntry 2 }

    sisgm1040284lrtIPStatusRouteGateway OBJECT-TYPE
               SYNTAX      DisplayString
               MAX-ACCESS  read-only
               STATUS      current
               DESCRIPTION
                   "The gateway address of this route."
               ::= {     sisgm1040284lrtIPStatusRouteEntry 3 }

    sisgm1040284lrtIPStatusRouteAddress OBJECT-TYPE
               SYNTAX      DisplayString
               MAX-ACCESS  read-only
               STATUS      current
               DESCRIPTION
                   "The route address."
               ::= {     sisgm1040284lrtIPStatusRouteEntry 4 }

sisgm1040284lrtIPStatusNeighborCache OBJECT IDENTIFIER ::= { sisgm1040284lrtIP 9 }

    sisgm1040284lrtIPStatusNeighborCacheTable OBJECT-TYPE
               SYNTAX      SEQUENCE OF     SISGM1040284LRTIPStatusNeighborCacheEntry
               MAX-ACCESS  not-accessible
               STATUS      current
               DESCRIPTION
                       "The Ip Status Neighbor Cache Table."
                   ::= {     sisgm1040284lrtIPStatusNeighborCache 1 }

    sisgm1040284lrtIPStatusNeighborCacheEntry OBJECT-TYPE
               SYNTAX          SISGM1040284LRTIPStatusNeighborCacheEntry
               MAX-ACCESS  not-accessible
               STATUS      current
               DESCRIPTION
                       "An entry in the Ip Status Neighbor Cache Table."
               INDEX    {     sisgm1040284lrtIPStatusNeighborCacheIndex  }
               ::= {     sisgm1040284lrtIPStatusNeighborCacheTable 1 }

    SISGM1040284LRTIPStatusNeighborCacheEntry             ::= SEQUENCE {
            sisgm1040284lrtIPStatusNeighborCacheIndex            Integer32,
            sisgm1040284lrtIPStatusNeighborCacheIPAddress        DisplayString,
            sisgm1040284lrtIPStatusNeighborCacheLinkAddress      DisplayString
            }

    sisgm1040284lrtIPStatusNeighborCacheIndex OBJECT-TYPE
               SYNTAX      Integer32(1..1024)
               MAX-ACCESS  not-accessible
               STATUS      current
               DESCRIPTION
                   "The index for the Ip Status Neighbor Cache Table."
               ::= {     sisgm1040284lrtIPStatusNeighborCacheEntry 1 }

    sisgm1040284lrtIPStatusNeighborCacheIPAddress OBJECT-TYPE
               SYNTAX      DisplayString
               MAX-ACCESS  read-only
               STATUS      current
               DESCRIPTION
                   "The IP address of the entry."
               ::= {     sisgm1040284lrtIPStatusNeighborCacheEntry 2 }

    sisgm1040284lrtIPStatusNeighborCacheLinkAddress OBJECT-TYPE
               SYNTAX      DisplayString
               MAX-ACCESS  read-only
               STATUS      current
               DESCRIPTION
                   "The Link (MAC) address for which a binding to the
                    IP address given exist."
               ::= {     sisgm1040284lrtIPStatusNeighborCacheEntry 3 }

sisgm1040284lrtIPStatusDNSServer OBJECT IDENTIFIER ::= { sisgm1040284lrtIP 10 }

    sisgm1040284lrtIPStatusDNSServerType OBJECT-TYPE
               SYNTAX      DisplayString
               MAX-ACCESS  read-only
               STATUS      current
               DESCRIPTION
                   "The configuration type of DNS server."
               ::= {     sisgm1040284lrtIPStatusDNSServer 1 }

    sisgm1040284lrtIPStatusDNSServerIPAddress OBJECT-TYPE
               SYNTAX      DisplayString
               MAX-ACCESS  read-only
               STATUS      current
               DESCRIPTION
                   "The IP address of the DNS server."
               ::= {     sisgm1040284lrtIPStatusDNSServer 2 }

    sisgm1040284lrtIPStatusDNSServerInterface OBJECT-TYPE
               SYNTAX      DisplayString
               MAX-ACCESS  read-only
               STATUS      current
               DESCRIPTION
                   "The name of the interface."
               ::= {     sisgm1040284lrtIPStatusDNSServer 3 }			   
			   
-- =======================================================================================================================
sisgm1040284lrtSyslog                                                OBJECT IDENTIFIER ::= { sisgm1040284lrtSystem 5 }

sisgm1040284lrtSyslogConf                                            OBJECT IDENTIFIER ::= { sisgm1040284lrtSyslog 1 }

sisgm1040284lrtSysLogInfo                                            OBJECT IDENTIFIER   ::= {  sisgm1040284lrtSyslog 2 }
--
-- =======================================================================================================================
-- Objects in the sisgm1040284lrtSystemLog Group
-- =======================================================================================================================
--sisgm1040284lrtSystemLogConf

    sisgm1040284lrtSystemLogServerMode OBJECT-TYPE
               SYNTAX      AdminMode
               MAX-ACCESS  read-write
               STATUS      current
               DESCRIPTION
                   "The System log server mode admin state."
               DEFVAL  { disable }
               ::= {     sisgm1040284lrtSyslogConf 1 }

    sisgm1040284lrtSystemLogServerAddress OBJECT-TYPE
               SYNTAX      DisplayString
               MAX-ACCESS  read-write
               STATUS      current
               DESCRIPTION
                   "The Host address of syslog server."
               ::= {     sisgm1040284lrtSyslogConf 2 }

--    sisgm1040284lrtSystemLogSyslogLevel OBJECT-TYPE
--               SYNTAX      INTEGER {
--                    info(0),
--                    warning(1),
--                    error(2)
--               }
--               MAX-ACCESS  read-write
--               STATUS      current
--               DESCRIPTION
--                   "The syslog level.
--                       info(0)   : Info.
--                       warning(1): Warning.
--                       error(2)  : Error."
--               DEFVAL  { info }
--               ::= {     sisgm1040284lrtSyslogConf 3 }

    sisgm1040284lrtSystemLogServerPort OBJECT-TYPE
                 SYNTAX      Integer32(1..65535)
                 MAX-ACCESS  read-write
                 STATUS      current
                 DESCRIPTION
                      "syslog service port number.
                 range : 1-65535, default : 514."
               ::= {     sisgm1040284lrtSyslogConf 4 }

--sisgm1040284lrtSystemLogInfo
    sisgm1040284lrtSystemLogInfoLevel OBJECT-TYPE
               SYNTAX      INTEGER { emergency(0), alert(1), critical(2), error(3), warning(4), notice(5), information(6), debug(7), all(8) }
               MAX-ACCESS  read-write
               STATUS      current
               DESCRIPTION
                  "The Level input field is used to filter the display system log entries.
                   0: Emergency.
                   1: Alert.
                   2: Critical.
                   3: Error.
                   4: Warning.
                   5: Notice.
                   6: Information.
                   7: Debug.
                   8: All."
               DEFVAL  { all }
               ::= {     sisgm1040284lrtSysLogInfo 1 }

    sisgm1040284lrtSystemLogInfoClearLevel OBJECT-TYPE
               SYNTAX      INTEGER { emergency(0), alert(1), critical(2), error(3), warning(4), notice(5), information(6), debug(7), all(8) }
               MAX-ACCESS  read-write
               STATUS      current
               DESCRIPTION
                  "The Clear Level input field is used to specify which
                  system log entries will be cleared.
                  default: 8 (All).
                   0: Emergency.
                   1: Alert.
                   2: Critical.
                   3: Error.
                   4: Warning.
                   5: Notice.
                   6: Information.
                   7: Debug.
                   8: All."
               DEFVAL  { all }
               ::= {     sisgm1040284lrtSysLogInfo 2 }

    sisgm1040284lrtSystemLogInfoClearCmd OBJECT-TYPE
               SYNTAX      ActivateCmd
               MAX-ACCESS  read-write
               STATUS      current
               DESCRIPTION
                  "Command to clear the syslog.
                   noAction(0) : do nothing  (read only).
                   activate(1) : Clear Syslog."
               DEFVAL  { noAction }
               ::= {     sisgm1040284lrtSysLogInfo 3 }

    sisgm1040284lrtSystemLogDetailedInfoTable OBJECT-TYPE
              SYNTAX      SEQUENCE OF     SISGM1040284LRTSystemLogDetailedInfoEntry
              MAX-ACCESS  not-accessible
              STATUS      current
              DESCRIPTION
                       "The system detailed Log Info table."
                   ::= {     sisgm1040284lrtSysLogInfo 4 }

    sisgm1040284lrtSystemLogDetailedInfoEntry OBJECT-TYPE
               SYNTAX          SISGM1040284LRTSystemLogDetailedInfoEntry
               MAX-ACCESS  not-accessible
               STATUS      current
               DESCRIPTION
                       "An entry in the system detailed Log Info table."
               INDEX    {     sisgm1040284lrtSystemLogDetailedInfoID  }
               ::= {     sisgm1040284lrtSystemLogDetailedInfoTable 1 }

    SISGM1040284LRTSystemLogDetailedInfoEntry             ::= SEQUENCE {
                sisgm1040284lrtSystemLogDetailedSwitchIndex       Integer32,
                sisgm1040284lrtSystemLogDetailedInfoID            Integer32,
                sisgm1040284lrtSystemLogDetailedInfoLevel         DisplayString,
                sisgm1040284lrtSystemLogDetailedInfoTime          DisplayString,
                sisgm1040284lrtSystemLogDetailedInfoMessage       DisplayString
                }

    sisgm1040284lrtSystemLogDetailedSwitchIndex OBJECT-TYPE
               SYNTAX      Integer32(1..16)
               MAX-ACCESS  not-accessible
               STATUS      current
               DESCRIPTION
                   "The switch index for the system detailed Log Info table."
               ::= {     sisgm1040284lrtSystemLogDetailedInfoEntry 1 }

    sisgm1040284lrtSystemLogDetailedInfoID OBJECT-TYPE
               SYNTAX      Integer32(1..999)
               MAX-ACCESS  not-accessible
               STATUS      current
               DESCRIPTION
                   "The index for the system detailed Log Info table."
               ::= {     sisgm1040284lrtSystemLogDetailedInfoEntry 2 }

    sisgm1040284lrtSystemLogDetailedInfoLevel OBJECT-TYPE
               SYNTAX      DisplayString
               MAX-ACCESS  read-only
               STATUS      current
               DESCRIPTION
                   "The Info Level."
               ::= {     sisgm1040284lrtSystemLogDetailedInfoEntry 3 }

    sisgm1040284lrtSystemLogDetailedInfoTime OBJECT-TYPE
               SYNTAX      DisplayString(SIZE (0..20))
               MAX-ACCESS  read-only
               STATUS      current
               DESCRIPTION
                   "The time"
               ::= {     sisgm1040284lrtSystemLogDetailedInfoEntry 4 }

    sisgm1040284lrtSystemLogDetailedInfoMessage OBJECT-TYPE
               SYNTAX      DisplayString
               MAX-ACCESS  read-only
               STATUS      current
               DESCRIPTION
                   "The message of this entry."
               ::= {     sisgm1040284lrtSystemLogDetailedInfoEntry 5 }
		
    sisgm1040284lrtSystemDORelayOpenClose OBJECT-TYPE
               SYNTAX      Integer32
               MAX-ACCESS  read-write
               STATUS      current
               DESCRIPTION
                  "DO Relay Open/Close.
				  1:open
				  0:close"
               ::= {     sisgm1040284lrtSysLogInfo 5 }		
-- =======================================================================================================================
sisgm1040284lrtSnmp                                                OBJECT IDENTIFIER ::= { sisgm1040284lrtSystem 6 }

sisgm1040284lrtSnmpSystem                                            OBJECT IDENTIFIER ::= { sisgm1040284lrtSnmp 1 }

sisgm1040284lrtSnmpSystemMode OBJECT-TYPE
   SYNTAX       Integer32
   MAX-ACCESS   read-write
   STATUS       current
   DESCRIPTION
       "SNMP mode operation.
        default : 1, 0: disable, 1: enable. "
   ::= { sisgm1040284lrtSnmpSystem 1 }

sisgm1040284lrtSnmpSystemVersion OBJECT-TYPE
   SYNTAX       Integer32
   MAX-ACCESS   read-write
   STATUS       current
   DESCRIPTION
       "SNMP supported version.
       default : snmpv2c.
       0: snmpv1
       1: snmpv2c
       2: snmpv3."
   ::= { sisgm1040284lrtSnmpSystem 2 }

sisgm1040284lrtSnmpSystemReadCommunity OBJECT-TYPE
   SYNTAX       DisplayString
   MAX-ACCESS   read-write
   STATUS       current
   DESCRIPTION
       "Indicates the community read access string to permit access to SNMP agent.
       The allowed string length is 0 to 255.
       The field is applicable only when SNMP version is SNMPv1 or SNMPv2c."
   ::= { sisgm1040284lrtSnmpSystem 3 }

sisgm1040284lrtSnmpSystemWriteCommunity OBJECT-TYPE
   SYNTAX       DisplayString
   MAX-ACCESS   read-write
   STATUS       current
   DESCRIPTION
       "Indicates the community write access string to permit access to SNMP agent.
       The allowed string length is 0 to 255.
       The field is applicable only when SNMP version is SNMPv1 or SNMPv2c."
   ::= { sisgm1040284lrtSnmpSystem 4 }

sisgm1040284lrtSnmpSystemEngineID OBJECT-TYPE
   SYNTAX       DisplayString
   MAX-ACCESS   read-only
   STATUS       current
   DESCRIPTION
       "Indicates the SNMPv3 engine ID.
        The string must contain an even number(in hexadecimal format) with number of digits between 10 and 64,
	but all-zeros and all-'F's are not allowed.
	Allow string length is 10 to 32.
	Change of the Engine ID will clear all original local users."
   ::= { sisgm1040284lrtSnmpSystem 5 }

sisgm1040284lrtSnmpSystemWriteCommunityMode OBJECT-TYPE
   SYNTAX       Integer32
   MAX-ACCESS   read-write
   STATUS       current
   DESCRIPTION
       "SNMP write community mode operation.
        default : 1, 0: disable, 1: enable. "
   ::= { sisgm1040284lrtSnmpSystem 6 }

sisgm1040284lrtSnmpTrapGlobalMode OBJECT-TYPE
   SYNTAX       Integer32
   MAX-ACCESS   read-write
   STATUS       current
   DESCRIPTION
       "Indicates the trap mode operation.
        0:Disable.
	1:Enable."
   ::= { sisgm1040284lrtSnmp 2 }

sisgm1040284lrtTrapDestinationConfTable OBJECT-TYPE
   SYNTAX      SEQUENCE OF SISGM1040284LRTTrapDestinationConfEntry
   MAX-ACCESS  not-accessible
   STATUS      current
   DESCRIPTION
       "A list of trap host entry. The numbers of entries are given by the value of TrapHostConfNumber."
   ::= { sisgm1040284lrtSnmp 3 }

sisgm1040284lrtTrapDestinationConfEntry OBJECT-TYPE
   SYNTAX      SISGM1040284LRTTrapDestinationConfEntry
   MAX-ACCESS  not-accessible
   STATUS      current
   DESCRIPTION
       "This is the entry information for trap host."
   INDEX    { sisgm1040284lrtTrapDestinationConfIndex  }
   ::= { sisgm1040284lrtTrapDestinationConfTable 1 }

SISGM1040284LRTTrapDestinationConfEntry ::= SEQUENCE {
    sisgm1040284lrtTrapDestinationConfIndex                      Integer32,
    sisgm1040284lrtTrapDestinationConfTrapConfigName             DisplayString,
    sisgm1040284lrtTrapDestinationConfTrapMode                   Integer32,
    sisgm1040284lrtTrapDestinationConfTrapVersion                Integer32,
    sisgm1040284lrtTrapDestinationConfTrapCommunity              DisplayString,
    sisgm1040284lrtTrapDestinationConfTrapDestinationAddres      DisplayString,
    sisgm1040284lrtTrapDestinationConfTrapDestinationPort        Integer32,
    sisgm1040284lrtTrapDestinationConfTrapInformMode             Integer32,
    sisgm1040284lrtTrapDestinationConfTrapInformTimeout          Integer32,
    sisgm1040284lrtTrapDestinationConfTrapInformRetryTimes       Integer32,
    sisgm1040284lrtTrapDestinationConfTrapProbeSecurityEngineID  Integer32,
    sisgm1040284lrtTrapDestinationConfTrapSecurityEngineID       DisplayString,
    sisgm1040284lrtTrapDestinationConfTrapSecurityName           DisplayString,
    sisgm1040284lrtTrapDestinationConfTrapRowStatus              Integer32
}

sisgm1040284lrtTrapDestinationConfIndex OBJECT-TYPE
   SYNTAX       Integer32
   MAX-ACCESS   not-accessible
   STATUS       current
   DESCRIPTION
       "Index of tarp destination configurations."
   ::= { sisgm1040284lrtTrapDestinationConfEntry 1 }

sisgm1040284lrtTrapDestinationConfTrapConfigName OBJECT-TYPE
   SYNTAX       DisplayString
   MAX-ACCESS   read-write
   STATUS       current
   DESCRIPTION
       "Indicates which trap Configuration's name for configuring.
       The allowed string length is 0 to 255, and the allowed content is
       ASCII characters from 33 to 126."
   ::= { sisgm1040284lrtTrapDestinationConfEntry 2 }

sisgm1040284lrtTrapDestinationConfTrapMode OBJECT-TYPE
   SYNTAX       Integer32
   MAX-ACCESS   read-write
   STATUS       current
   DESCRIPTION
       "Indicates the SNMP mode operation. Possible modes are:
        2: Enable TCP SNMP mode operation.
        1: Enable UDP SNMP mode operation.
        0: Disable SNMP mode operation. "
   ::= { sisgm1040284lrtTrapDestinationConfEntry 3 }

sisgm1040284lrtTrapDestinationConfTrapVersion OBJECT-TYPE
   SYNTAX       Integer32
   MAX-ACCESS   read-write
   STATUS       current
   DESCRIPTION
       "0: snmpv1
        1: snmpv2c
        3: snmpv3.
        "
   ::= { sisgm1040284lrtTrapDestinationConfEntry 4 }

sisgm1040284lrtTrapDestinationConfTrapCommunity OBJECT-TYPE
   SYNTAX       DisplayString
   MAX-ACCESS   read-write
   STATUS       current
   DESCRIPTION
       "Indicates the community access string when sending SNMP trap packet.
       The allowed string length is 0 to 255, and the allowed content is
       ASCII characters from 33 to 126."
   ::= { sisgm1040284lrtTrapDestinationConfEntry 5 }

sisgm1040284lrtTrapDestinationConfTrapDestinationAddres OBJECT-TYPE
   SYNTAX       DisplayString
   MAX-ACCESS   read-write
   STATUS       current
   DESCRIPTION
       "Indicates the SNMP trap destination address.
       It allow a valid IP address in dotted decimal notation ('x.y.z.w').
    And it also allow a valid hostname.
    A valid hostname is a string drawn from the alphabet (A-Za-z), digits (0-9),
    dot (.), dash (-). Spaces are not allowed, the first character must be an alpha character,
    and the first and last characters must not be a dot or a dash.
    Indicates the SNMP trap destination IPv6 address.
    IPv6 address is in 128-bit records represented as eight fields of up to four hexadecimal digits
    with a colon separating each field (:).
    For example, 'fe80::215:c5ff:fe03:4dc7'. The symbol '::' is a special syntax
    that can be used as a shorthand way of representing multiple 16-bit groups of contiguous zeros;
    but it can appear only once.
    It can also represent a legally valid IPv4 address.
    For example, '::192.1.2.34'."
   ::= { sisgm1040284lrtTrapDestinationConfEntry 6 }

sisgm1040284lrtTrapDestinationConfTrapDestinationPort OBJECT-TYPE
   SYNTAX       Integer32
   MAX-ACCESS   read-write
   STATUS       current
   DESCRIPTION
       "Indicates the SNMP trap destination port.
       SNMP Agent will send SNMP message via this port,
       the port range is 1~65535."
   ::= { sisgm1040284lrtTrapDestinationConfEntry 7 }

sisgm1040284lrtTrapDestinationConfTrapInformMode OBJECT-TYPE
   SYNTAX       Integer32
   MAX-ACCESS   read-write
   STATUS       current
   DESCRIPTION
       "Indicates the SNMP trap inform mode operation. Possible modes are:
        1: Enable SNMP trap inform mode operation.
        0: Disable SNMP trap inform mode operation. "
   ::= { sisgm1040284lrtTrapDestinationConfEntry 8 }

sisgm1040284lrtTrapDestinationConfTrapInformTimeout OBJECT-TYPE
   SYNTAX       Integer32
   MAX-ACCESS   read-write
   STATUS       current
   DESCRIPTION
       "Indicates the SNMP trap inform timeout. The allowed range is 0 to 2147."
   ::= { sisgm1040284lrtTrapDestinationConfEntry 9 }

sisgm1040284lrtTrapDestinationConfTrapInformRetryTimes OBJECT-TYPE
   SYNTAX       Integer32
   MAX-ACCESS   read-write
   STATUS       current
   DESCRIPTION
       "Indicates the SNMP trap inform retry times. The allowed range is 0 to 255."
   ::= { sisgm1040284lrtTrapDestinationConfEntry 10 }

sisgm1040284lrtTrapDestinationConfTrapProbeSecurityEngineID OBJECT-TYPE
   SYNTAX       Integer32
   MAX-ACCESS   read-write
   STATUS       current
   DESCRIPTION
       "Indicates the SNMP trap probe security engine ID mode of operation.
       Possible values are:
       1: Enable SNMP trap probe security engine ID mode of operation.
       0: Disable SNMP trap probe security engine ID mode of operation."
   ::= { sisgm1040284lrtTrapDestinationConfEntry 11 }

sisgm1040284lrtTrapDestinationConfTrapSecurityEngineID OBJECT-TYPE
   SYNTAX       DisplayString
   MAX-ACCESS   read-write
   STATUS       current
   DESCRIPTION
       "Indicates the SNMP trap security engine ID.
       SNMPv3 sends traps and informs using USM for authentication and privacy.
       A unique engine ID for these traps and informs is needed.
       When Trap Probe Security Engine ID is enabled, the ID will be probed automatically.
       Otherwise, the ID specified in this field is used.
       The string must contain an even number(in hexadecimal format) with
       number of digits between 10 and 64, but all-zeros and all-'F's are not allowed."
   ::= { sisgm1040284lrtTrapDestinationConfEntry 12 }

sisgm1040284lrtTrapDestinationConfTrapSecurityName OBJECT-TYPE
   SYNTAX       DisplayString
   MAX-ACCESS   read-write
   STATUS       current
   DESCRIPTION
       "Indicates the SNMP trap security name.
       SNMPv3 traps and informs using USM for authentication and privacy.
       A unique security name is needed when traps and informs are enabled.
       This name from user name of user configuration."
   ::= { sisgm1040284lrtTrapDestinationConfEntry 13 }

sisgm1040284lrtTrapDestinationConfTrapRowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sisgm1040284lrtTrapDestinationConfEntry 14 }


sisgm1040284lrtSNMPCommunityConfTable OBJECT-TYPE
   SYNTAX      SEQUENCE OF SISGM1040284LRTSNMPCommunityConfEntry
   MAX-ACCESS  not-accessible
   STATUS      current
   DESCRIPTION
       "A list of snmp community configuration entry."
   ::= { sisgm1040284lrtSnmp 5 }

sisgm1040284lrtSNMPCommunityConfEntry OBJECT-TYPE
   SYNTAX      SISGM1040284LRTSNMPCommunityConfEntry
   MAX-ACCESS  not-accessible
   STATUS      current
   DESCRIPTION
       "This is the entry information for snmp community configuration."
   INDEX    { sisgm1040284lrtSNMPCommunityConfIndex  }
   ::= { sisgm1040284lrtSNMPCommunityConfTable 1 }

SISGM1040284LRTSNMPCommunityConfEntry ::= SEQUENCE {
    sisgm1040284lrtSNMPCommunityConfIndex                       Integer32,
    sisgm1040284lrtSNMPCommunityConfSNMPv3Community             DisplayString,
    sisgm1040284lrtSNMPCommunityConfSNMPv3SourceIP              IpAddress,
    sisgm1040284lrtSNMPCommunityConfSNMPv3SourceMask            IpAddress,
    sisgm1040284lrtSNMPCommunityConfSNMPv3RowStatus             Integer32
}

sisgm1040284lrtSNMPCommunityConfIndex OBJECT-TYPE
   SYNTAX       Integer32
   MAX-ACCESS   read-write
   STATUS       current
   DESCRIPTION
       "Community configuration index."
   ::= { sisgm1040284lrtSNMPCommunityConfEntry 1 }

sisgm1040284lrtSNMPCommunityConfSNMPv3Community OBJECT-TYPE
   SYNTAX       DisplayString
   MAX-ACCESS   read-write
   STATUS       current
   DESCRIPTION
       "Indicates the community access string to permit access to SNMPv3 agent.
       The allowed string length is 1 to 32, and the allowed content is
       ASCII characters from 33 to 126.
       The community string will be treated as security name and map a SNMPv1
       or SNMPv2c community string."
   ::= { sisgm1040284lrtSNMPCommunityConfEntry 2 }


sisgm1040284lrtSNMPCommunityConfSNMPv3SourceIP OBJECT-TYPE
   SYNTAX      IpAddress
   MAX-ACCESS  read-write
   STATUS      current
   DESCRIPTION
       "Indicates the SNMP access source address.
       A particular range of source addresses can be used to restrict source subnet
       when combined with source mask."
   ::= {sisgm1040284lrtSNMPCommunityConfEntry 3 }

sisgm1040284lrtSNMPCommunityConfSNMPv3SourceMask OBJECT-TYPE
   SYNTAX      IpAddress
   MAX-ACCESS  read-write
   STATUS      current
   DESCRIPTION
       "Indicates the SNMP access source address mask."
   ::= {sisgm1040284lrtSNMPCommunityConfEntry 4 }

sisgm1040284lrtSNMPCommunityConfSNMPv3RowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sisgm1040284lrtSNMPCommunityConfEntry 5 }

sisgm1040284lrtSNMPv3UserConfTable OBJECT-TYPE
   SYNTAX      SEQUENCE OF SISGM1040284LRTSNMPv3UserConfEntry
   MAX-ACCESS  not-accessible
   STATUS      current
   DESCRIPTION
       "A list of snmpv3 user configuration entry."
   ::= { sisgm1040284lrtSnmp 6 }

sisgm1040284lrtSNMPv3UserConfEntry OBJECT-TYPE
   SYNTAX      SISGM1040284LRTSNMPv3UserConfEntry
   MAX-ACCESS  not-accessible
   STATUS      current
   DESCRIPTION
       "This is the entry information for snmpv3 user configuration."
   INDEX    { sisgm1040284lrtSNMPv3UserConfIndex  }
   ::= { sisgm1040284lrtSNMPv3UserConfTable 1 }

SISGM1040284LRTSNMPv3UserConfEntry ::= SEQUENCE {
    sisgm1040284lrtSNMPv3UserConfIndex                     Integer32,
    sisgm1040284lrtSNMPv3UserConfEngineID                  DisplayString,
    sisgm1040284lrtSNMPv3UserConfUserName                  DisplayString,
    sisgm1040284lrtSNMPv3UserConfSecurityLevel             Integer32,
    sisgm1040284lrtSNMPv3UserConfAuthenticationProtocol    Integer32,
    sisgm1040284lrtSNMPv3UserConfAuthenticationPassword    DisplayString,
    sisgm1040284lrtSNMPv3UserConfPrivacyProtocol           Integer32,
    sisgm1040284lrtSNMPv3UserConfPrivacyPassword           DisplayString,
    sisgm1040284lrtSNMPv3UserConfRowStatus                 RowStatus
}

sisgm1040284lrtSNMPv3UserConfIndex OBJECT-TYPE
   SYNTAX       Integer32
   MAX-ACCESS   read-write
   STATUS       current
   DESCRIPTION
       "User configuration index."
   ::= { sisgm1040284lrtSNMPv3UserConfEntry 1 }

sisgm1040284lrtSNMPv3UserConfEngineID OBJECT-TYPE
   SYNTAX       DisplayString
   MAX-ACCESS   read-write
   STATUS       current
   DESCRIPTION
       "An octet string identifying the engine ID that this entry should belong to.
       The string must contain an even number(in hexadecimal format) with
       number of digits between 10 and 64, but all-zeros and all-'F's are not allowed.
       The SNMPv3 architecture uses the User-based Security Model (USM)
       for message security and the View-based Access Control Model (VACM) for access control.
       For the USM entry, the usmUserEngineID and usmUserName are the entry's keys.
       In a simple agent, usmUserEngineID is always that agent's own snmpEngineID value.
       The value can also take the value of the snmpEngineID of a remote SNMP engine with
       which this user can communicate. In other words, if user engine ID equal system engine ID
       then it is local user; otherwise it's remote user. "
   ::= { sisgm1040284lrtSNMPv3UserConfEntry 2 }

sisgm1040284lrtSNMPv3UserConfUserName OBJECT-TYPE
   SYNTAX       DisplayString
   MAX-ACCESS   read-write
   STATUS       current
   DESCRIPTION
       "A string identifying the user name that this entry should belong to.
       The allowed string length is 1 to 32, and the allowed content is
       ASCII characters from 33 to 126."
   ::= { sisgm1040284lrtSNMPv3UserConfEntry 3 }

sisgm1040284lrtSNMPv3UserConfSecurityLevel OBJECT-TYPE
   SYNTAX       Integer32
   MAX-ACCESS   read-write
   STATUS       current
   DESCRIPTION
       "1:NoAuth, NoPriv
        2:Auth, NoPriv
	3:Auth, Priv"
   ::= { sisgm1040284lrtSNMPv3UserConfEntry 4 }

sisgm1040284lrtSNMPv3UserConfAuthenticationProtocol OBJECT-TYPE
   SYNTAX       Integer32
   MAX-ACCESS   read-write
   STATUS       current
   DESCRIPTION
       "0:None
        1:MD5
	2:SHA"
   ::= { sisgm1040284lrtSNMPv3UserConfEntry 5 }

sisgm1040284lrtSNMPv3UserConfAuthenticationPassword OBJECT-TYPE
   SYNTAX       DisplayString
   MAX-ACCESS   read-write
   STATUS       current
   DESCRIPTION
       "A string identifying the authentication password phrase.
       For MD5 authentication protocol, the allowed string length is 8 to 32.
       For SHA authentication protocol, the allowed string length is 8 to 40.
       The allowed content is ASCII characters from 33 to 126."
   ::= { sisgm1040284lrtSNMPv3UserConfEntry 6 }

sisgm1040284lrtSNMPv3UserConfPrivacyProtocol OBJECT-TYPE
   SYNTAX       Integer32
   MAX-ACCESS   read-write
   STATUS       current
   DESCRIPTION
       "0:None
        1:DES
        2:AES"
   ::= { sisgm1040284lrtSNMPv3UserConfEntry 7 }

sisgm1040284lrtSNMPv3UserConfPrivacyPassword OBJECT-TYPE
   SYNTAX       DisplayString
   MAX-ACCESS   read-write
   STATUS       current
   DESCRIPTION
       "A string identifying the privacy password phrase.
       The allowed string length is 8 to 32, and the allowed content is
       ASCII characters from 33 to 126."
   ::= { sisgm1040284lrtSNMPv3UserConfEntry 8 }

sisgm1040284lrtSNMPv3UserConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sisgm1040284lrtSNMPv3UserConfEntry 9 }

sisgm1040284lrtSNMPv3GroupConfTable OBJECT-TYPE
   SYNTAX      SEQUENCE OF SISGM1040284LRTSNMPv3GroupConfEntry
   MAX-ACCESS  not-accessible
   STATUS      current
   DESCRIPTION
       "A list of snmpv3 group configuration entry."
   ::= { sisgm1040284lrtSnmp 7 }

sisgm1040284lrtSNMPv3GroupConfEntry OBJECT-TYPE
   SYNTAX      SISGM1040284LRTSNMPv3GroupConfEntry
   MAX-ACCESS  not-accessible
   STATUS      current
   DESCRIPTION
       "This is the entry information for snmpv3 group configuration."
   INDEX    { sisgm1040284lrtSNMPv3GroupConfIndex  }
   ::= { sisgm1040284lrtSNMPv3GroupConfTable 1 }

SISGM1040284LRTSNMPv3GroupConfEntry ::= SEQUENCE {
    sisgm1040284lrtSNMPv3GroupConfIndex                     Integer32,
    sisgm1040284lrtSNMPv3GroupConfSecurityModel             Integer32,
    sisgm1040284lrtSNMPv3GroupConfSecurityName          DisplayString,
    sisgm1040284lrtSNMPv3GroupConfGroupName             DisplayString,
    sisgm1040284lrtSNMPv3GroupConfRowStatus                 RowStatus
}

sisgm1040284lrtSNMPv3GroupConfIndex OBJECT-TYPE
   SYNTAX       Integer32
   MAX-ACCESS   read-write
   STATUS       current
   DESCRIPTION
       "Group configuration index."
   ::= { sisgm1040284lrtSNMPv3GroupConfEntry 1 }

sisgm1040284lrtSNMPv3GroupConfSecurityModel OBJECT-TYPE
   SYNTAX       Integer32
   MAX-ACCESS   read-write
   STATUS       current
   DESCRIPTION
       "1:v1
        2:v2c
	3:usm"
   ::= { sisgm1040284lrtSNMPv3GroupConfEntry 2 }

sisgm1040284lrtSNMPv3GroupConfSecurityName OBJECT-TYPE
   SYNTAX       DisplayString
   MAX-ACCESS   read-write
   STATUS       current
   DESCRIPTION
       "A string identifying the security name that this entry should belong to.
       The allowed string length is 1 to 32, and the allowed content is
       ASCII characters from 33 to 126.
       This name is from the Community of Community configuration."
   ::= { sisgm1040284lrtSNMPv3GroupConfEntry 3 }

sisgm1040284lrtSNMPv3GroupConfGroupName OBJECT-TYPE
   SYNTAX       DisplayString
   MAX-ACCESS   read-write
   STATUS       current
   DESCRIPTION
       "A string identifying the group name that this entry should belong to.
       The allowed string length is 1 to 32, and the allowed content is
       ASCII characters from 33 to 126. "
   ::= { sisgm1040284lrtSNMPv3GroupConfEntry 4 }


sisgm1040284lrtSNMPv3GroupConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sisgm1040284lrtSNMPv3GroupConfEntry 5 }

sisgm1040284lrtSNMPv3ViewsConfTable OBJECT-TYPE
   SYNTAX      SEQUENCE OF SISGM1040284LRTSNMPv3ViewsConfEntry
   MAX-ACCESS  not-accessible
   STATUS      current
   DESCRIPTION
       "A list of snmpv3 view configuration entry."
   ::= { sisgm1040284lrtSnmp 8 }

sisgm1040284lrtSNMPv3ViewsConfEntry OBJECT-TYPE
   SYNTAX      SISGM1040284LRTSNMPv3ViewsConfEntry
   MAX-ACCESS  not-accessible
   STATUS      current
   DESCRIPTION
       "This is the entry information for snmpv3 view configuration."
   INDEX    { sisgm1040284lrtSNMPv3ViewsConfIndex  }
   ::= { sisgm1040284lrtSNMPv3ViewsConfTable 1 }

SISGM1040284LRTSNMPv3ViewsConfEntry ::= SEQUENCE {
    sisgm1040284lrtSNMPv3ViewsConfIndex                   Integer32,
    sisgm1040284lrtSNMPv3ViewsConfViewName            DisplayString,
    sisgm1040284lrtSNMPv3ViewsConfViewType                Integer32,
    sisgm1040284lrtSNMPv3ViewsConfOIDSubtree          DisplayString,
    sisgm1040284lrtSNMPv3ViewsConfRowStatus               RowStatus
}

sisgm1040284lrtSNMPv3ViewsConfIndex OBJECT-TYPE
   SYNTAX       Integer32
   MAX-ACCESS   read-write
   STATUS       current
   DESCRIPTION
       "view configuration index."
   ::= { sisgm1040284lrtSNMPv3ViewsConfEntry 1 }

sisgm1040284lrtSNMPv3ViewsConfViewName OBJECT-TYPE
   SYNTAX       DisplayString
   MAX-ACCESS   read-write
   STATUS       current
   DESCRIPTION
       "A string identifying the view name that this entry should belong to.
       The allowed string length is 1 to 32, and the allowed content is
       ASCII characters from 33 to 126. "
   ::= { sisgm1040284lrtSNMPv3ViewsConfEntry 2 }

sisgm1040284lrtSNMPv3ViewsConfViewType OBJECT-TYPE
   SYNTAX       Integer32
   MAX-ACCESS   read-write
   STATUS       current
   DESCRIPTION
       "1:included
       2:excluded"
   ::= { sisgm1040284lrtSNMPv3ViewsConfEntry 3 }

sisgm1040284lrtSNMPv3ViewsConfOIDSubtree OBJECT-TYPE
   SYNTAX       DisplayString
   MAX-ACCESS   read-write
   STATUS       current
   DESCRIPTION
       "The OID defining the root of the subtree to add to the named view.
       The allowed OID length is 1 to 128. The allowed string content is
       digital number or asterisk(*)"
   ::= { sisgm1040284lrtSNMPv3ViewsConfEntry 4 }

sisgm1040284lrtSNMPv3ViewsConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sisgm1040284lrtSNMPv3ViewsConfEntry 5 }


sisgm1040284lrtSNMPv3AccessConfTable OBJECT-TYPE
   SYNTAX      SEQUENCE OF SISGM1040284LRTSNMPv3AccessConfEntry
   MAX-ACCESS  not-accessible
   STATUS      current
   DESCRIPTION
       "A list of snmpv3 access configuration entry."
   ::= { sisgm1040284lrtSnmp 9 }

sisgm1040284lrtSNMPv3AccessConfEntry OBJECT-TYPE
   SYNTAX      SISGM1040284LRTSNMPv3AccessConfEntry
   MAX-ACCESS  not-accessible
   STATUS      current
   DESCRIPTION
       "This is the entry information for snmpv3 access configuration."
   INDEX    { sisgm1040284lrtSNMPv3AccessConfIndex  }
   ::= { sisgm1040284lrtSNMPv3AccessConfTable 1 }

SISGM1040284LRTSNMPv3AccessConfEntry ::= SEQUENCE {
    sisgm1040284lrtSNMPv3AccessConfIndex                    Integer32,
    sisgm1040284lrtSNMPv3AccessConfGroupName            DisplayString,
    sisgm1040284lrtSNMPv3AccessConfSecurityModel            Integer32,
    sisgm1040284lrtSNMPv3AccessConfSecurityLevel            Integer32,
    sisgm1040284lrtSNMPv3AccessConfReadViewName         DisplayString,
    sisgm1040284lrtSNMPv3AccessConfWriteViewName        DisplayString,
    sisgm1040284lrtSNMPv3AccessConfRowStatus                RowStatus
}

sisgm1040284lrtSNMPv3AccessConfIndex OBJECT-TYPE
   SYNTAX       Integer32
   MAX-ACCESS   read-write
   STATUS       current
   DESCRIPTION
       "Access configuration index"
   ::= { sisgm1040284lrtSNMPv3AccessConfEntry 1 }

sisgm1040284lrtSNMPv3AccessConfGroupName OBJECT-TYPE
   SYNTAX       DisplayString
   MAX-ACCESS   read-write
   STATUS       current
   DESCRIPTION
       "Group name from Group configuration."
   ::= { sisgm1040284lrtSNMPv3AccessConfEntry 2 }

sisgm1040284lrtSNMPv3AccessConfSecurityModel OBJECT-TYPE
   SYNTAX       Integer32
   MAX-ACCESS   read-write
   STATUS       current
   DESCRIPTION
       "0:any
        1:v1
	2:v2c
	3:usm"
   ::= { sisgm1040284lrtSNMPv3AccessConfEntry 3 }

sisgm1040284lrtSNMPv3AccessConfSecurityLevel OBJECT-TYPE
   SYNTAX       Integer32
   MAX-ACCESS   read-write
   STATUS       current
   DESCRIPTION
       "1:NoAuth, NoPriv
       2:Auth, NoPriv
       3:Auth, Priv"
   ::= { sisgm1040284lrtSNMPv3AccessConfEntry 4 }

sisgm1040284lrtSNMPv3AccessConfReadViewName OBJECT-TYPE
   SYNTAX       DisplayString
   MAX-ACCESS   read-write
   STATUS       current
   DESCRIPTION
       "Read View Name from View configuration."
   ::= { sisgm1040284lrtSNMPv3AccessConfEntry 5 }

sisgm1040284lrtSNMPv3AccessConfWriteViewName OBJECT-TYPE
   SYNTAX       DisplayString
   MAX-ACCESS   read-write
   STATUS       current
   DESCRIPTION
       "Write View Name from View configuration."
   ::= { sisgm1040284lrtSNMPv3AccessConfEntry 6 }

sisgm1040284lrtSNMPv3AccessConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sisgm1040284lrtSNMPv3AccessConfEntry 7 }

-- =======================================================================================================================
sisgm1040284lrtDHCPServer                                     OBJECT IDENTIFIER ::= { sisgm1040284lrtSystem 9 }

sisgm1040284lrtDHCPServerConf                                 OBJECT IDENTIFIER ::= { sisgm1040284lrtDHCPServer 1 }

sisgm1040284lrtDHCPServerMode OBJECT-TYPE
   SYNTAX      Integer32 (0|1)
   MAX-ACCESS  read-write
   STATUS      current
   DESCRIPTION
       "default: 0,
        Global Mode :
        0: Disable,
        1: Enable.
       "
   ::= { sisgm1040284lrtDHCPServerConf 1 }

sisgm1040284lrtVLANModeTable OBJECT-TYPE
   SYNTAX      SEQUENCE OF SISGM1040284LRTVLANModeEntry
   MAX-ACCESS  not-accessible
   STATUS      current
   DESCRIPTION
       "A table of VLAN Mode for DHCP Server."
    ::= { sisgm1040284lrtDHCPServerConf 2 }

sisgm1040284lrtVLANModeEntry OBJECT-TYPE
    SYNTAX        SISGM1040284LRTVLANModeEntry
    MAX-ACCESS    not-accessible
    STATUS        current
    DESCRIPTION
        "An entry in the sisgm1040284lrtVLANModeTable."
    INDEX        { sisgm1040284lrtVLANModeIndex }
    ::= { sisgm1040284lrtVLANModeTable 1 }

SISGM1040284LRTVLANModeEntry ::=
    SEQUENCE {
        sisgm1040284lrtVLANModeIndex                            Integer32,
        sisgm1040284lrtVLANModeRangeLow                         Integer32,
        sisgm1040284lrtVLANModeRangeHigh                        Integer32,
        sisgm1040284lrtVLANModeEnable                           Integer32,
		sisgm1040284lrtVLANModeRowStatus                        RowStatus
    }

sisgm1040284lrtVLANModeIndex OBJECT-TYPE
   SYNTAX      Integer32 (1..2048)
   MAX-ACCESS  not-accessible
   STATUS      current
   DESCRIPTION
       "VLAN Mode table index, range: 1-2048."
   ::= {sisgm1040284lrtVLANModeEntry 1 }

sisgm1040284lrtVLANModeRangeLow OBJECT-TYPE
   SYNTAX      Integer32 (1..4095)
   MAX-ACCESS  read-create
   STATUS      current
   DESCRIPTION
       "VLAN Mode low range: 1-4095."
   ::= {sisgm1040284lrtVLANModeEntry 2 }

sisgm1040284lrtVLANModeRangeHigh OBJECT-TYPE
   SYNTAX      Integer32 (1..4095)
   MAX-ACCESS  read-create
   STATUS      current
   DESCRIPTION
       "VLAN Mode high range: 1-4095."
   ::= {sisgm1040284lrtVLANModeEntry 3 }

sisgm1040284lrtVLANModeEnable OBJECT-TYPE
   SYNTAX      Integer32 (0..1)
   MAX-ACCESS  read-create
   STATUS      current
   DESCRIPTION
       "VLAN Mode Enable, Enable:1, Disable:0."
   ::= {sisgm1040284lrtVLANModeEntry 4 }

sisgm1040284lrtVLANModeRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {     sisgm1040284lrtVLANModeEntry 5 }



-- sisgm1040284lrtDHCPServerBindingType OBJECT-TYPE
--   SYNTAX      Integer32 (0|1|2|3)
--   MAX-ACCESS  read-only
--   STATUS      current
--   DESCRIPTION
--       "default: None,
--        Global Mode :
--        0: None,
--        1: Automatic,
--        2: Manual,
--        3: Expired.
--       "
--   ::= { sisgm1040284lrtDHCPServerConf 2 }

-- sisgm1040284lrtDHCPServerBindingState OBJECT-TYPE
--   SYNTAX      Integer32 (0|1|2|3)
--   MAX-ACCESS  read-only
--   STATUS      current
--   DESCRIPTION
--       "default: None,
--        Global Mode :
--        0: None,
--        1: Allocated,
--        2: Committed,
--        3: Expired.
--       "
--   ::= { sisgm1040284lrtDHCPServerConf 3 }

-- sisgm1040284lrtDHCPServerBindingIP OBJECT-TYPE
--   SYNTAX      DisplayString
--   MAX-ACCESS  read-only
--   STATUS      current
--   DESCRIPTION
--       "The DHCP Server Binding IP"
--   ::= { sisgm1040284lrtDHCPServerConf 4 }


sisgm1040284lrtDHCPServerExcludedIP                                 OBJECT IDENTIFIER ::= { sisgm1040284lrtDHCPServer 2 }

sisgm1040284lrtExcludedIPTable OBJECT-TYPE
   SYNTAX      SEQUENCE OF SISGM1040284LRTExcludedIPEntry
   MAX-ACCESS  not-accessible
   STATUS      current
   DESCRIPTION
       "A table of Excluded IP for DHCP Server."
    ::= { sisgm1040284lrtDHCPServerExcludedIP 1 }

sisgm1040284lrtExcludedIPEntry OBJECT-TYPE
    SYNTAX        SISGM1040284LRTExcludedIPEntry
    MAX-ACCESS    not-accessible
    STATUS        current
    DESCRIPTION
        "An entry in the sisgm1040284lrtExcludedIPTable."
    INDEX        { sisgm1040284lrtExcludedIPIndex }
    ::= { sisgm1040284lrtExcludedIPTable 1 }

SISGM1040284LRTExcludedIPEntry ::=
    SEQUENCE {
        sisgm1040284lrtExcludedIPIndex                            Integer32,
        sisgm1040284lrtExcludedIPRangeLow                         IpAddress,
        sisgm1040284lrtExcludedIPRangeHigh                        IpAddress,
		sisgm1040284lrtExcludedIPRowStatus                        RowStatus
    }

sisgm1040284lrtExcludedIPIndex OBJECT-TYPE
   SYNTAX      Integer32 (1..16)
   MAX-ACCESS  not-accessible
   STATUS      current
   DESCRIPTION
       "Excluded IP table index, range: 1-16."
   ::= {sisgm1040284lrtExcludedIPEntry 1 }

sisgm1040284lrtExcludedIPRangeLow OBJECT-TYPE
   SYNTAX      IpAddress
   MAX-ACCESS  read-create
   STATUS      current
   DESCRIPTION
       "ExcludedIP low range: 1-4095."
   ::= {sisgm1040284lrtExcludedIPEntry 2 }

sisgm1040284lrtExcludedIPRangeHigh OBJECT-TYPE
   SYNTAX      IpAddress
   MAX-ACCESS  read-create
   STATUS      current
   DESCRIPTION
       "ExcludedIP high range: 1-4095."
   ::= {sisgm1040284lrtExcludedIPEntry 3 }

sisgm1040284lrtExcludedIPRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {sisgm1040284lrtExcludedIPEntry 4 }



sisgm1040284lrtDHCPServerPoolConf                                 OBJECT IDENTIFIER ::= { sisgm1040284lrtDHCPServer 3 }

sisgm1040284lrtDHCPServerPoolTable OBJECT-TYPE
   SYNTAX      SEQUENCE OF SISGM1040284LRTDHCPServerPoolEntry
   MAX-ACCESS  not-accessible
   STATUS      current
   DESCRIPTION
       "This is the entry information for DHCP Pool."
   ::= { sisgm1040284lrtDHCPServerPoolConf 1 }

sisgm1040284lrtDHCPServerPoolEntry OBJECT-TYPE
   SYNTAX      SISGM1040284LRTDHCPServerPoolEntry
   MAX-ACCESS  not-accessible
   STATUS      current
   DESCRIPTION
       " "
   INDEX    { sisgm1040284lrtDHCPServerConfIndex  }
   ::= { sisgm1040284lrtDHCPServerPoolTable 1 }

SISGM1040284LRTDHCPServerPoolEntry ::= SEQUENCE {
    sisgm1040284lrtDHCPServerConfIndex               Integer32,
    sisgm1040284lrtDHCPServerPoolName                DisplayString,
    sisgm1040284lrtDHCPServerPoolType                Integer32,
    sisgm1040284lrtDHCPServerIP                      IpAddress,
    sisgm1040284lrtDHCPServerSubnetMask              IpAddress,
    sisgm1040284lrtDHCPServerLeaseTimeDays           Integer32,
    sisgm1040284lrtDHCPServerLeaseTimeHours          Integer32,
    sisgm1040284lrtDHCPServerLeaseTimeMinutes        Integer32,
    sisgm1040284lrtDHCPServerDomainName              DisplayString,
    sisgm1040284lrtDHCPServerBroadcastAddress        IpAddress,
    sisgm1040284lrtDHCPServerDefRouter1              IpAddress,
    sisgm1040284lrtDHCPServerDefRouter2              IpAddress,
    sisgm1040284lrtDHCPServerDefRouter3              IpAddress,
    sisgm1040284lrtDHCPServerDefRouter4              IpAddress,
    sisgm1040284lrtDHCPServerDNSServer1              IpAddress,
    sisgm1040284lrtDHCPServerDNSServer2              IpAddress,
    sisgm1040284lrtDHCPServerDNSServer3              IpAddress,
    sisgm1040284lrtDHCPServerDNSServer4              IpAddress,
    sisgm1040284lrtDHCPServerNTPServer1              IpAddress,
    sisgm1040284lrtDHCPServerNTPServer2              IpAddress,
    sisgm1040284lrtDHCPServerNTPServer3              IpAddress,
    sisgm1040284lrtDHCPServerNTPServer4              IpAddress,
    sisgm1040284lrtDHCPServerNetbiosType             Integer32,
    sisgm1040284lrtDHCPServerNetbiosScope            DisplayString,
    sisgm1040284lrtDHCPServerNetbiosNameServer1      IpAddress,
    sisgm1040284lrtDHCPServerNetbiosNameServer2      IpAddress,
    sisgm1040284lrtDHCPServerNetbiosNameServer3      IpAddress,
    sisgm1040284lrtDHCPServerNetbiosNameServer4      IpAddress,
    sisgm1040284lrtDHCPServerNisDomainName           DisplayString,
    sisgm1040284lrtDHCPServerNisServer1              IpAddress,
    sisgm1040284lrtDHCPServerNisServer2              IpAddress,
    sisgm1040284lrtDHCPServerNisServer3              IpAddress,
    sisgm1040284lrtDHCPServerNisServer4              IpAddress,
    sisgm1040284lrtDHCPServerClientIDType            Integer32,
    sisgm1040284lrtDHCPServerClientID                DisplayString,
    sisgm1040284lrtDHCPServerHWAddr                  DisplayString,
    sisgm1040284lrtDHCPServerClientName              DisplayString,
    sisgm1040284lrtDHCPServerVendorClassID1          DisplayString,
    sisgm1040284lrtDHCPServerVendorSpecificInfo1     DisplayString,
    sisgm1040284lrtDHCPServerVendorClassID2          DisplayString,
    sisgm1040284lrtDHCPServerVendorSpecificInfo2     DisplayString,
    sisgm1040284lrtDHCPServerVendorClassID3          DisplayString,
    sisgm1040284lrtDHCPServerVendorSpecificInfo3     DisplayString,
    sisgm1040284lrtDHCPServerVendorClassID4          DisplayString,
    sisgm1040284lrtDHCPServerVendorSpecificInfo4     DisplayString,
--    sisgm1040284lrtDHCPServerVendorClassID5          DisplayString,
--    sisgm1040284lrtDHCPServerVendorSpecificInfo5     DisplayString,
--    sisgm1040284lrtDHCPServerVendorClassID6          DisplayString,
--    sisgm1040284lrtDHCPServerVendorSpecificInfo6     DisplayString,
--    sisgm1040284lrtDHCPServerVendorClassID7          DisplayString,
--    sisgm1040284lrtDHCPServerVendorSpecificInfo7     DisplayString,
--    sisgm1040284lrtDHCPServerVendorClassID8          DisplayString,
--    sisgm1040284lrtDHCPServerVendorSpecificInfo8     DisplayString,
    sisgm1040284lrtDHCPServerLightingServer          DisplayString,
    sisgm1040284lrtDHCPServerRowStatus               RowStatus
}

sisgm1040284lrtDHCPServerConfIndex OBJECT-TYPE
   SYNTAX      Integer32 (1..64)
   MAX-ACCESS  not-accessible
   STATUS      current
   DESCRIPTION
       " pool, range : 1 - 64. "
   ::= { sisgm1040284lrtDHCPServerPoolEntry 1 }

sisgm1040284lrtDHCPServerPoolName OBJECT-TYPE
   SYNTAX      DisplayString(SIZE (1..32))
   MAX-ACCESS  read-create
   STATUS      current
   DESCRIPTION
       " DHCP pool name. "
   ::= { sisgm1040284lrtDHCPServerPoolEntry 2 }

sisgm1040284lrtDHCPServerPoolType OBJECT-TYPE
   SYNTAX      Integer32(0|1|2)
   MAX-ACCESS  read-create
   STATUS      current
   DESCRIPTION
       " DHCP Server Pool Type.
	   0:None
	   1:Network
	   2:Host, please set DHCP Server IP first."
   ::= { sisgm1040284lrtDHCPServerPoolEntry 3 }

sisgm1040284lrtDHCPServerIP OBJECT-TYPE
   SYNTAX      IpAddress
   MAX-ACCESS  read-create
   STATUS      current
   DESCRIPTION
       " DHCP Server IP. "
   ::= { sisgm1040284lrtDHCPServerPoolEntry 4 }

sisgm1040284lrtDHCPServerSubnetMask OBJECT-TYPE
   SYNTAX      IpAddress
   MAX-ACCESS  read-create
   STATUS      current
   DESCRIPTION
       " DHCP Server IPv4 Subnet Mask. "
   ::= { sisgm1040284lrtDHCPServerPoolEntry 5}

sisgm1040284lrtDHCPServerLeaseTimeDays OBJECT-TYPE
   SYNTAX      Integer32(0..365)
   MAX-ACCESS  read-create
   STATUS      current
   DESCRIPTION
       " DHCP Server IPv4 Lease Time:Days. "
   ::= { sisgm1040284lrtDHCPServerPoolEntry 6 }

sisgm1040284lrtDHCPServerLeaseTimeHours OBJECT-TYPE
   SYNTAX      Integer32(0..23)
   MAX-ACCESS  read-create
   STATUS      current
   DESCRIPTION
       " DHCP Server IPv4 Lease Time:Hours. "
   ::= { sisgm1040284lrtDHCPServerPoolEntry 7 }

sisgm1040284lrtDHCPServerLeaseTimeMinutes OBJECT-TYPE
   SYNTAX      Integer32(0..59)
   MAX-ACCESS  read-create
   STATUS      current
   DESCRIPTION
       " DHCP Server IPv4 Lease Time:Minutes. "
   ::= { sisgm1040284lrtDHCPServerPoolEntry 8 }

sisgm1040284lrtDHCPServerDomainName OBJECT-TYPE
   SYNTAX      DisplayString(SIZE (0..128))
   MAX-ACCESS  read-create
   STATUS      current
   DESCRIPTION
       " DHCP Server Domain Name. "
   ::= { sisgm1040284lrtDHCPServerPoolEntry 9 }

sisgm1040284lrtDHCPServerBroadcastAddress OBJECT-TYPE
   SYNTAX      IpAddress
   MAX-ACCESS  read-create
   STATUS      current
   DESCRIPTION
       " DHCP Server IPv4 Broadcast Address. "
   ::= { sisgm1040284lrtDHCPServerPoolEntry 10 }

sisgm1040284lrtDHCPServerDefRouter1 OBJECT-TYPE
   SYNTAX      IpAddress
   MAX-ACCESS  read-create
   STATUS      current
   DESCRIPTION
       " DHCP Server IPv4 Default Router 1. "
   ::= { sisgm1040284lrtDHCPServerPoolEntry 11 }

sisgm1040284lrtDHCPServerDefRouter2 OBJECT-TYPE
   SYNTAX      IpAddress
   MAX-ACCESS  read-create
   STATUS      current
   DESCRIPTION
       " DHCP Server IPv4 Default Router 2. "
   ::= { sisgm1040284lrtDHCPServerPoolEntry 12 }

sisgm1040284lrtDHCPServerDefRouter3 OBJECT-TYPE
   SYNTAX      IpAddress
   MAX-ACCESS  read-create
   STATUS      current
   DESCRIPTION
       " DHCP Server IPv4 Default Router 3. "
   ::= { sisgm1040284lrtDHCPServerPoolEntry 13 }

sisgm1040284lrtDHCPServerDefRouter4 OBJECT-TYPE
   SYNTAX      IpAddress
   MAX-ACCESS  read-create
   STATUS      current
   DESCRIPTION
       " DHCP Server IPv4 Default Router 4. "
   ::= { sisgm1040284lrtDHCPServerPoolEntry 14 }

sisgm1040284lrtDHCPServerDNSServer1 OBJECT-TYPE
   SYNTAX      IpAddress
   MAX-ACCESS  read-create
   STATUS      current
   DESCRIPTION
       " DHCP Server DNS Server 1. "
   ::= { sisgm1040284lrtDHCPServerPoolEntry 15 }

sisgm1040284lrtDHCPServerDNSServer2 OBJECT-TYPE
   SYNTAX      IpAddress
   MAX-ACCESS  read-create
   STATUS      current
   DESCRIPTION
       " DHCP Server DNS Server 2. "
   ::= { sisgm1040284lrtDHCPServerPoolEntry 16 }

sisgm1040284lrtDHCPServerDNSServer3 OBJECT-TYPE
   SYNTAX      IpAddress
   MAX-ACCESS  read-create
   STATUS      current
   DESCRIPTION
       " DHCP Server DNS Server 3. "
   ::= { sisgm1040284lrtDHCPServerPoolEntry 17 }

sisgm1040284lrtDHCPServerDNSServer4 OBJECT-TYPE
   SYNTAX      IpAddress
   MAX-ACCESS  read-create
   STATUS      current
   DESCRIPTION
       " DHCP Server DNS Server 4. "
   ::= { sisgm1040284lrtDHCPServerPoolEntry 18 }

sisgm1040284lrtDHCPServerNTPServer1 OBJECT-TYPE
   SYNTAX      IpAddress
   MAX-ACCESS  read-create
   STATUS      current
   DESCRIPTION
       " DHCP Server NTP Server 1. "
   ::= { sisgm1040284lrtDHCPServerPoolEntry 19 }

sisgm1040284lrtDHCPServerNTPServer2 OBJECT-TYPE
   SYNTAX      IpAddress
   MAX-ACCESS  read-create
   STATUS      current
   DESCRIPTION
       " DHCP Server NTP Server 2. "
   ::= { sisgm1040284lrtDHCPServerPoolEntry 20 }

sisgm1040284lrtDHCPServerNTPServer3 OBJECT-TYPE
   SYNTAX      IpAddress
   MAX-ACCESS  read-create
   STATUS      current
   DESCRIPTION
       " DHCP Server NTP Server 3. "
   ::= { sisgm1040284lrtDHCPServerPoolEntry 21 }

sisgm1040284lrtDHCPServerNTPServer4 OBJECT-TYPE
   SYNTAX      IpAddress
   MAX-ACCESS  read-create
   STATUS      current
   DESCRIPTION
       " DHCP Server NTP Server 4. "
   ::= { sisgm1040284lrtDHCPServerPoolEntry 22 }

sisgm1040284lrtDHCPServerNetbiosType OBJECT-TYPE
   SYNTAX      Integer32(1..4)
   MAX-ACCESS  read-create
   STATUS      current
   DESCRIPTION
       " DHCP Server Netbios Node Type.
	   0:None
	   1:B-node
	   2:P-node
	   3:M-node
	   4:H-node"
   ::= { sisgm1040284lrtDHCPServerPoolEntry 23 }

sisgm1040284lrtDHCPServerNetbiosScope OBJECT-TYPE
   SYNTAX      DisplayString(SIZE (0..128))
   MAX-ACCESS  read-create
   STATUS      current
   DESCRIPTION
       " DHCP Server Netbios Scope. "
   ::= { sisgm1040284lrtDHCPServerPoolEntry 24 }

sisgm1040284lrtDHCPServerNetbiosNameServer1 OBJECT-TYPE
   SYNTAX      IpAddress
   MAX-ACCESS  read-create
   STATUS      current
   DESCRIPTION
       " DHCP Server Netbios Name Server 1. "
   ::= { sisgm1040284lrtDHCPServerPoolEntry 25 }

sisgm1040284lrtDHCPServerNetbiosNameServer2 OBJECT-TYPE
   SYNTAX      IpAddress
   MAX-ACCESS  read-create
   STATUS      current
   DESCRIPTION
       " DHCP Server Netbios Name Server 2. "
   ::= { sisgm1040284lrtDHCPServerPoolEntry 26 }

sisgm1040284lrtDHCPServerNetbiosNameServer3 OBJECT-TYPE
   SYNTAX      IpAddress
   MAX-ACCESS  read-create
   STATUS      current
   DESCRIPTION
       " DHCP Server Netbios Name Server 3. "
   ::= { sisgm1040284lrtDHCPServerPoolEntry 27 }

sisgm1040284lrtDHCPServerNetbiosNameServer4 OBJECT-TYPE
   SYNTAX      IpAddress
   MAX-ACCESS  read-create
   STATUS      current
   DESCRIPTION
       " DHCP Server Netbios Name Server 4. "
   ::= { sisgm1040284lrtDHCPServerPoolEntry 28 }

sisgm1040284lrtDHCPServerNisDomainName OBJECT-TYPE
   SYNTAX      DisplayString(SIZE (0..128))
   MAX-ACCESS  read-create
   STATUS      current
   DESCRIPTION
       " DHCP Server Nis Domain Name. "
   ::= { sisgm1040284lrtDHCPServerPoolEntry 29 }

sisgm1040284lrtDHCPServerNisServer1 OBJECT-TYPE
   SYNTAX      IpAddress
   MAX-ACCESS  read-create
   STATUS      current
   DESCRIPTION
       " DHCP Server Nis Server 1. "
   ::= { sisgm1040284lrtDHCPServerPoolEntry 30 }

sisgm1040284lrtDHCPServerNisServer2 OBJECT-TYPE
   SYNTAX      IpAddress
   MAX-ACCESS  read-create
   STATUS      current
   DESCRIPTION
       " DHCP Server Nis Server 2. "
   ::= { sisgm1040284lrtDHCPServerPoolEntry 31 }

sisgm1040284lrtDHCPServerNisServer3 OBJECT-TYPE
   SYNTAX      IpAddress
   MAX-ACCESS  read-create
   STATUS      current
   DESCRIPTION
       " DHCP Server Nis Server 3. "
   ::= { sisgm1040284lrtDHCPServerPoolEntry 32 }

sisgm1040284lrtDHCPServerNisServer4 OBJECT-TYPE
   SYNTAX      IpAddress
   MAX-ACCESS  read-create
   STATUS      current
   DESCRIPTION
       " DHCP Server Nis Server 4. "
   ::= { sisgm1040284lrtDHCPServerPoolEntry 33 }

sisgm1040284lrtDHCPServerClientIDType OBJECT-TYPE
   SYNTAX      Integer32(0..2)
   MAX-ACCESS  read-create
   STATUS      current
   DESCRIPTION
       " DHCP Server Client ID Type.
	   0:None
	   1:FQDN
	   2:MAC"
   ::= { sisgm1040284lrtDHCPServerPoolEntry 34 }

sisgm1040284lrtDHCPServerClientID OBJECT-TYPE
   SYNTAX      DisplayString(SIZE (0..128))
   MAX-ACCESS  read-create
   STATUS      current
   DESCRIPTION
       " DHCP Server Pool Client ID. "
   ::= { sisgm1040284lrtDHCPServerPoolEntry 35 }

sisgm1040284lrtDHCPServerHWAddr OBJECT-TYPE
   SYNTAX      DisplayString(SIZE (0..17))
   MAX-ACCESS  read-create
   STATUS      current
   DESCRIPTION
       " DHCP Server Pool Hardware Address. "
   ::= { sisgm1040284lrtDHCPServerPoolEntry 36 }

sisgm1040284lrtDHCPServerClientName OBJECT-TYPE
   SYNTAX      DisplayString(SIZE (0..32))
   MAX-ACCESS  read-create
   STATUS      current
   DESCRIPTION
       " DHCP Server Pool Client Name. "
   ::= { sisgm1040284lrtDHCPServerPoolEntry 37 }

sisgm1040284lrtDHCPServerVendorClassID1 OBJECT-TYPE
   SYNTAX      DisplayString(SIZE (0..64))
   MAX-ACCESS  read-create
   STATUS      current
   DESCRIPTION
       " DHCP Server Vendor Class ID 1. Please also set VendorSpecificInfo1."
   ::= { sisgm1040284lrtDHCPServerPoolEntry 38 }

sisgm1040284lrtDHCPServerVendorSpecificInfo1 OBJECT-TYPE
   SYNTAX      DisplayString(SIZE (0..32))
   MAX-ACCESS  read-create
   STATUS      current
   DESCRIPTION
       " DHCP Server Vendor Specific Info 1. Please also set VendorClassID1."
   ::= { sisgm1040284lrtDHCPServerPoolEntry 39 }

sisgm1040284lrtDHCPServerVendorClassID2 OBJECT-TYPE
   SYNTAX      DisplayString(SIZE (0..64))
   MAX-ACCESS  read-create
   STATUS      current
   DESCRIPTION
       " DHCP Server Vendor Class ID 2. Please also set VendorSpecificInfo2."
   ::= { sisgm1040284lrtDHCPServerPoolEntry 40 }

sisgm1040284lrtDHCPServerVendorSpecificInfo2 OBJECT-TYPE
   SYNTAX      DisplayString(SIZE (0..32))
   MAX-ACCESS  read-create
   STATUS      current
   DESCRIPTION
       " DHCP Server Vendor Specific Info 2. Please also set VendorClassID2."
   ::= { sisgm1040284lrtDHCPServerPoolEntry 41 }

sisgm1040284lrtDHCPServerVendorClassID3 OBJECT-TYPE
   SYNTAX      DisplayString(SIZE (0..64))
   MAX-ACCESS  read-create
   STATUS      current
   DESCRIPTION
       " DHCP Server Vendor Class ID 3. Please also set VendorSpecificInfo3."
   ::= { sisgm1040284lrtDHCPServerPoolEntry 42 }

sisgm1040284lrtDHCPServerVendorSpecificInfo3 OBJECT-TYPE
   SYNTAX      DisplayString(SIZE (0..32))
   MAX-ACCESS  read-create
   STATUS      current
   DESCRIPTION
       " DHCP Server Vendor Specific Info 3. Please also set VendorClassID3."
   ::= { sisgm1040284lrtDHCPServerPoolEntry 43 }

sisgm1040284lrtDHCPServerVendorClassID4 OBJECT-TYPE
   SYNTAX      DisplayString(SIZE (0..64))
   MAX-ACCESS  read-create
   STATUS      current
   DESCRIPTION
       " DHCP Server Vendor Class ID 4. Please also set VendorSpecificInfo4."
   ::= { sisgm1040284lrtDHCPServerPoolEntry 44 }

sisgm1040284lrtDHCPServerVendorSpecificInfo4 OBJECT-TYPE
   SYNTAX      DisplayString(SIZE (0..32))
   MAX-ACCESS  read-create
   STATUS      current
   DESCRIPTION
       " DHCP Server Vendor Specific Info 4. Please also set VendorClassID4."
   ::= { sisgm1040284lrtDHCPServerPoolEntry 45 }

--sisgm1040284lrtDHCPServerVendorClassID5 OBJECT-TYPE
--   SYNTAX      DisplayString(SIZE (0..64))
--   MAX-ACCESS  read-create
--   STATUS      current
--   DESCRIPTION
--       " DHCP Server Vendor Class ID 5. Please also set VendorSpecificInfo5."
--   ::= { sisgm1040284lrtDHCPServerPoolEntry 46 }
--
--sisgm1040284lrtDHCPServerVendorSpecificInfo5 OBJECT-TYPE
--   SYNTAX      DisplayString(SIZE (0..32))
--   MAX-ACCESS  read-create
--   STATUS      current
--   DESCRIPTION
--       " DHCP Server Vendor Specific Info 5. Please also set VendorClassID5."
--   ::= { sisgm1040284lrtDHCPServerPoolEntry 47 }
--
--sisgm1040284lrtDHCPServerVendorClassID6 OBJECT-TYPE
--   SYNTAX      DisplayString(SIZE (0..64))
--   MAX-ACCESS  read-create
--   STATUS      current
--   DESCRIPTION
--       " DHCP Server Vendor Class ID 6. Please also set VendorSpecificInfo6."
--   ::= { sisgm1040284lrtDHCPServerPoolEntry 48 }
--
--sisgm1040284lrtDHCPServerVendorSpecificInfo6 OBJECT-TYPE
--   SYNTAX      DisplayString(SIZE (0..32))
--   MAX-ACCESS  read-create
--   STATUS      current
--   DESCRIPTION
--       " DHCP Server Vendor Specific Info 6. Please also set VendorClassID6."
--   ::= { sisgm1040284lrtDHCPServerPoolEntry 49 }
--
--sisgm1040284lrtDHCPServerVendorClassID7 OBJECT-TYPE
--   SYNTAX      DisplayString(SIZE (0..64))
--   MAX-ACCESS  read-create
--   STATUS      current
--   DESCRIPTION
--       " DHCP Server Vendor Class ID 7. Please also set VendorSpecificInfo7."
--   ::= { sisgm1040284lrtDHCPServerPoolEntry 50 }
--
--sisgm1040284lrtDHCPServerVendorSpecificInfo7 OBJECT-TYPE
--   SYNTAX      DisplayString(SIZE (0..32))
--   MAX-ACCESS  read-create
--   STATUS      current
--   DESCRIPTION
--       " DHCP Server Vendor Specific Info 7. Please also set VendorClassID7."
--   ::= { sisgm1040284lrtDHCPServerPoolEntry 51 }
--
--sisgm1040284lrtDHCPServerVendorClassID8 OBJECT-TYPE
--   SYNTAX      DisplayString(SIZE (0..64))
--   MAX-ACCESS  read-create
--   STATUS      current
--   DESCRIPTION
--       " DHCP Server Vendor Class ID 8. Please also set VendorSpecificInfo8."
--   ::= { sisgm1040284lrtDHCPServerPoolEntry 52 }
--
--sisgm1040284lrtDHCPServerVendorSpecificInfo8 OBJECT-TYPE
--   SYNTAX      DisplayString(SIZE (0..32))
--   MAX-ACCESS  read-create
--   STATUS      current
--   DESCRIPTION
--       " DHCP Server Vendor Specific Info 8. Please also set VendorClassID8."
--   ::= { sisgm1040284lrtDHCPServerPoolEntry 53 }

sisgm1040284lrtDHCPServerLightingServer OBJECT-TYPE
   SYNTAX      DisplayString(SIZE (7..15))
   MAX-ACCESS  read-create
   STATUS      current
   DESCRIPTION
       "DHCP option 229.
        Specify a lighting server available to the client."
   ::= { sisgm1040284lrtDHCPServerPoolEntry 54 }

sisgm1040284lrtDHCPServerRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {sisgm1040284lrtDHCPServerPoolEntry 55 }

-- =======================================================================================================================
sisgm1040284lrtVLANConf                                     OBJECT IDENTIFIER ::= { sisgm1040284lrtSystem 10 }

sisgm1040284lrtVLAN                                     OBJECT IDENTIFIER ::= { sisgm1040284lrtVLANConf 2}

sisgm1040284lrtVlanStatus              OBJECT IDENTIFIER   ::= { sisgm1040284lrtVLAN 6 }

--
-- =======================================================================================================================
-- Start sisgm1040284lrtVlan group
-- =======================================================================================================================
    sisgm1040284lrtVlanExistingVLANs  OBJECT-TYPE
               SYNTAX      DisplayString
               MAX-ACCESS  read-write
               STATUS      current
               DESCRIPTION
                   "This field shows the VLANs that are created on the switch.
                    More VLANs may be created by using a
                    list syntax where the individual elements are separated by commas.
                    Ranges are specified with a
                    dash separating the lower and upper bound.
                    The following example will create VLANs 1, 10, 11, 12
                    , 13, 200, and 300: 1,10-13,200,300.
                    default: 1."
               ::= {     sisgm1040284lrtVLAN 1 }

    sisgm1040284lrtVlanEthertypeforCustomSPorts  OBJECT-TYPE
               SYNTAX      DisplayString
               MAX-ACCESS  read-write
               STATUS      current
               DESCRIPTION
                   "This field specifies the ethertype/TPID (specified in hexadecimal)
                    used for Custom S-ports. The
                    setting is in force for all ports whose Port Type
                    is set to S-Custom-Port.
                    range: 0600-ffff,
                    default: 88a8."
               ::= {     sisgm1040284lrtVLAN 2 }

    sisgm1040284lrtVlanTable OBJECT-TYPE
               SYNTAX      SEQUENCE OF     SISGM1040284LRTVlanEntry
               MAX-ACCESS  not-accessible
               STATUS      current
               DESCRIPTION
                   "Configure Vlan ports Configuration mode.
                    INDEX for this table is ifIndex which is
                    equivalent to the panel port number."
               ::= {     sisgm1040284lrtVLAN 3 }

    sisgm1040284lrtVlanEntry OBJECT-TYPE
               SYNTAX          SISGM1040284LRTVlanEntry
               MAX-ACCESS  not-accessible
               STATUS      current
               DESCRIPTION
                   "The Vlan entry."
               INDEX    {     ifIndex  }
               ::= {     sisgm1040284lrtVlanTable 1 }

    SISGM1040284LRTVlanEntry             ::= SEQUENCE {
                sisgm1040284lrtVlanMode              INTEGER,
                sisgm1040284lrtVlanPortVLAN          Integer32,
                sisgm1040284lrtVlanPortType          INTEGER,
                sisgm1040284lrtVlanIngressFiltering  AdminMode,
                sisgm1040284lrtVlanVLANTrunking      AdminMode,
                sisgm1040284lrtVlanIngressAcceptance INTEGER,
                sisgm1040284lrtVlanEgressTagging     INTEGER,
                sisgm1040284lrtVlanAllowedVLANs      DisplayString,
                sisgm1040284lrtVlanForbiddenVLANs    DisplayString
                }

    sisgm1040284lrtVlanMode OBJECT-TYPE
               SYNTAX      INTEGER{access(0), trunk(1), hybrid(2)}
               MAX-ACCESS  read-write
               STATUS      current
               DESCRIPTION
                   "The port mode determines the fundamental
                    behavior of the port in question.
                    A port can be in one of three modes as described below.
                    0: access,
                    1: trunk,
                    2: hybrid."
               DEFVAL  { access }
               ::= {     sisgm1040284lrtVlanEntry 2 }

    sisgm1040284lrtVlanPortVLAN OBJECT-TYPE
               SYNTAX      Integer32(1..4094)
               MAX-ACCESS  read-write
               STATUS      current
               DESCRIPTION
                   "Determines the port's VLAN ID (a.k.a. PVID).
                    range: 1-4095,
                    default: 1."
               ::= {     sisgm1040284lrtVlanEntry 3 }

    sisgm1040284lrtVlanPortType OBJECT-TYPE
               SYNTAX      INTEGER { unaware(0), cPort(1), sPort(2), sCustomPort(3) }
               MAX-ACCESS  read-write
               STATUS      current
               DESCRIPTION
                   "Ports in hybrid mode allow for changing the port type,
                    that is, whether a frame's VLAN tag is
                    used to classify the frame on ingress to a particular VLAN,
                    and if so, which TPID it reacts on.
                    Likewise, on egress, the Port Type determines the
                    TPID of the tag, if a tag is required.
                    0: unaware,
                    1: c-Port,
                    2: s-Port,
                    3: s-Custom-Port."
                DEFVAL  { cPort }
               ::= {     sisgm1040284lrtVlanEntry 4 }

    sisgm1040284lrtVlanIngressFiltering OBJECT-TYPE
               SYNTAX      AdminMode
               MAX-ACCESS  read-write
               STATUS      current
               DESCRIPTION
                   "Hybrid ports allow for changing ingress filtering.
                    Access and Trunk ports always have ingress
                    filtering enabled.If ingress filtering is enabled,
                    frames classified to
                    a VLAN that the port is not a member of get discarded."
               ::= {     sisgm1040284lrtVlanEntry 5 }

    sisgm1040284lrtVlanVLANTrunking OBJECT-TYPE
               SYNTAX      AdminMode
               MAX-ACCESS  read-write
               STATUS      current
               DESCRIPTION
                   "Trunk and Hybrid ports allow for enabling VLAN trunking.
                    When VLAN trunking is enabled, frames
                    classified to unknown VLANs are accepted on the port
                    whether ingress filtering is enabled or not."
               DEFVAL  { disable }
               ::= {     sisgm1040284lrtVlanEntry 6 }

    sisgm1040284lrtVlanIngressAcceptance OBJECT-TYPE
               SYNTAX      INTEGER  { taggedAndUntagged  ( 0 ),
                                      taggedOnly ( 1 ),
                                      untaggedOnly ( 2 )
                                    }
               MAX-ACCESS  read-write
               STATUS      current
               DESCRIPTION
                   "Hybrid ports allow for changing the type of frames that are
                    accepted on ingress.
                    0: Tagged and Untagged,
                    1: Tagged Only,
                    2: Untagged Only."
               ::= {     sisgm1040284lrtVlanEntry 7 }

    sisgm1040284lrtVlanEgressTagging OBJECT-TYPE
               SYNTAX      INTEGER  { untagPortVlan  ( 0 ),
                                      tagAll ( 1 ),
                                      untagAll ( 2 )
                                    }
               MAX-ACCESS  read-write
               STATUS      current
               DESCRIPTION
                   "Ports in Trunk and Hybrid mode may control the
                    tagging of frames on egress.
                    0: Untag Port VLAN,
                    1: Tag All,
                    2: Untag All."
               ::= {     sisgm1040284lrtVlanEntry 8 }

    sisgm1040284lrtVlanAllowedVLANs OBJECT-TYPE
               SYNTAX      DisplayString
               MAX-ACCESS  read-write
               STATUS      current
               DESCRIPTION
                   "Ports in Trunk and Hybrid mode may control which
                    VLANs they are allowed to become members of.
                    Access ports can only be member of one VLAN, the Access VLAN.
                    range: 1~4095.
                    '-': Allowed VLANs is empty."
               ::= {     sisgm1040284lrtVlanEntry 9 }

    sisgm1040284lrtVlanForbiddenVLANs OBJECT-TYPE
               SYNTAX      DisplayString
               MAX-ACCESS  read-write
               STATUS      current
               DESCRIPTION
                   "A port may be configured to never be member of one or
                    more VLANs. This is particularly useful
                    when dynamic VLAN protocols like MVRP and GVRP
                    must be prevented from dynamically adding ports
                    to VLANs.
                    range: 1~4095.
                    '-': Forbidden VLANs is empty."
               ::= {     sisgm1040284lrtVlanEntry 10 }

--sisgm1040284lrtVLANMembershipStatusTable

    sisgm1040284lrtVLANMembershipStatusTable OBJECT-TYPE
               SYNTAX      SEQUENCE OF     SISGM1040284LRTVLANMembershipStatusEntry
               MAX-ACCESS  not-accessible
               STATUS      current
               DESCRIPTION
                   "Vlan membership Status table.
                    INDEX for this table is ifIndex which is
                    equivalent to the panel port number."
               ::= {     sisgm1040284lrtVlanStatus 1 }

    sisgm1040284lrtVLANMembershipStatusEntry OBJECT-TYPE
               SYNTAX          SISGM1040284LRTVLANMembershipStatusEntry
               MAX-ACCESS  not-accessible
               STATUS      current
               DESCRIPTION
                   "Vlan membership Status entry."
               INDEX    {     ifIndex, sisgm1040284lrtVLANMembershipVlanID    }
               ::= {     sisgm1040284lrtVLANMembershipStatusTable 1 }

    SISGM1040284LRTVLANMembershipStatusEntry             ::= SEQUENCE {
                sisgm1040284lrtVLANMembershipVlanID      Integer32,
                sisgm1040284lrtVLANMembershipStatus      INTEGER
                }

    sisgm1040284lrtVLANMembershipVlanID OBJECT-TYPE
               SYNTAX      Integer32(1..4095)
               MAX-ACCESS  not-accessible
               STATUS      current
               DESCRIPTION
                   "VLAN ID for which the Port members are displayed."
               ::= {     sisgm1040284lrtVLANMembershipStatusEntry 2 }

    sisgm1040284lrtVLANMembershipStatus OBJECT-TYPE
               SYNTAX      INTEGER  { portIsNotInVlan  ( 0 ),
                                      portIncludedInVlan ( 1 ),
                                      portInForbiddenPortList( 2 ),
                                      portInForbiddenPortListAndVlan( 3 )
                                    }
               MAX-ACCESS  read-only
               STATUS      current
               DESCRIPTION
                   "portIsNotInVlan(0): A port is nothing in a VLAN.
                    portIncludedInVlan(1): A port is included in a VLAN.
                    portInForbiddenPortList(2): A port is in the forbidden port list.
                    portInForbiddenPortListAndVlan(3):
                     A port is in the forbidden port list and at the same
                     time attempted included in the VLAN."
               ::= {     sisgm1040284lrtVLANMembershipStatusEntry 3 }

--sisgm1040284lrtVLANPortStatusTable
    sisgm1040284lrtVLANPortStatusTable OBJECT-TYPE
               SYNTAX      SEQUENCE OF     SISGM1040284LRTVLANPortStatusEntry
               MAX-ACCESS  not-accessible
               STATUS      current
               DESCRIPTION
                   "The vlan port status table.
                    INDEX for this table is ifIndex which is
                    equivalent to the panel port number."
               ::= {     sisgm1040284lrtVlanStatus 2 }

    sisgm1040284lrtVLANPortStatusEntry OBJECT-TYPE
               SYNTAX          SISGM1040284LRTVLANPortStatusEntry
               MAX-ACCESS  not-accessible
               STATUS      current
               DESCRIPTION
                   "The vlan port status entry."
               INDEX    {     ifIndex }
               ::= {     sisgm1040284lrtVLANPortStatusTable 1 }

    SISGM1040284LRTVLANPortStatusEntry             ::= SEQUENCE {
                sisgm1040284lrtVLANPortStatusPortType          DisplayString,
                sisgm1040284lrtVLANPortStatusIngressFiltering  AdminMode,
                sisgm1040284lrtVLANPortStatusFrameType         DisplayString,
                sisgm1040284lrtVLANPortStatusPortVLANID        Integer32,
                sisgm1040284lrtVLANPortStatusTxTag             DisplayString,
                sisgm1040284lrtVLANPortStatusUntaggedVLANID    Integer32,
                sisgm1040284lrtVLANPortStatusConflicts         DisplayString
                }

    sisgm1040284lrtVLANPortStatusPortType OBJECT-TYPE
               SYNTAX      DisplayString
               MAX-ACCESS  read-only
               STATUS      current
               DESCRIPTION
                   "Shows the port type (Unaware, C-Port, S-Port,
                    S-Custom-Port.) that a given user wants to configure on
                    the port.The field is empty if not overridden by the selected user."
               ::= {     sisgm1040284lrtVLANPortStatusEntry 2 }

    sisgm1040284lrtVLANPortStatusIngressFiltering OBJECT-TYPE
               SYNTAX      AdminMode
               MAX-ACCESS  read-only
               STATUS      current
               DESCRIPTION
                   "Shows whether a given user wants ingress filtering enabled or not."
               ::= {     sisgm1040284lrtVLANPortStatusEntry 3 }

    sisgm1040284lrtVLANPortStatusFrameType OBJECT-TYPE
               SYNTAX      DisplayString
               MAX-ACCESS  read-only
               STATUS      current
               DESCRIPTION
                   "Shows the acceptable frame types (All, Taged,
                    Untagged) that a given user wants to configure on the port.
                    The field is empty if not overridden by the selected user."
               ::= {     sisgm1040284lrtVLANPortStatusEntry 4 }

    sisgm1040284lrtVLANPortStatusPortVLANID OBJECT-TYPE
               SYNTAX      Integer32 (1..4095)
               MAX-ACCESS  read-only
               STATUS      current
               DESCRIPTION
                   "Shows the Port VLAN ID (PVID) that a given user
                    wants the port to have.
                    The field is 0 if not overridden by the selected user."
               ::= {     sisgm1040284lrtVLANPortStatusEntry 5 }

    sisgm1040284lrtVLANPortStatusTxTag OBJECT-TYPE
               SYNTAX      DisplayString
               MAX-ACCESS  read-only
               STATUS      current
               DESCRIPTION
                   "Shows the Tx Tag requirements (Tag All, Tag PVID,
                    Tag UVID, Untag All, Untag PVID, Untag UVID)
                    that a given user has on a port.The field is empty
                    if not overridden by the selected user."
               ::= {     sisgm1040284lrtVLANPortStatusEntry 6 }

    sisgm1040284lrtVLANPortStatusUntaggedVLANID OBJECT-TYPE
               SYNTAX      Integer32(1..4095)
               MAX-ACCESS  read-only
               STATUS      current
               DESCRIPTION
                   "If Tx Tag is overridden by the selected user and is
                    set to Tag or Untag UVID, then this field will show
                    the VLAN ID the user wants to tag or untag on egress.
                    The field is 0 if not overridden by the selected
                    user."
               ::= {     sisgm1040284lrtVLANPortStatusEntry 7 }

    sisgm1040284lrtVLANPortStatusConflicts OBJECT-TYPE
               SYNTAX      DisplayString
               MAX-ACCESS  read-only
               STATUS      current
               DESCRIPTION
                   "Two users may have conflicting requirements to a port's
                    configuration. For instance, one user may require
                    all frames to be tagged on egress while another requires
                    all frames to be untagged on egress.Since both
                    users cannot win, this gives rise to a conflict,
                    which is solved in a prioritized way. The Administrator
                    has the least priority. Other software modules are
                    prioritized according to their position in the drop-down
                    list: The higher in the list, the higher priority.
                    If conflicts exist, it will be displayed as 'Yes'."
               ::= {     sisgm1040284lrtVLANPortStatusEntry 8 }
			   
			   
sisgm1040284lrtSystemDIDO                                     OBJECT IDENTIFIER ::= { sisgm1040284lrtSystem 11 }
    sisgm1040284lrtSystemDIMode OBJECT-TYPE
               SYNTAX       Integer32 (0..1)
               MAX-ACCESS   read-write
               STATUS       current
               DESCRIPTION
                   "System digital in mode.
				   0:Low
				   1:High
				   "
               ::= {     sisgm1040284lrtSystemDIDO 1 }
			   
    sisgm1040284lrtSystemDOMode OBJECT-TYPE
               SYNTAX       Integer32 (0..1)
               MAX-ACCESS   read-write
               STATUS       current
               DESCRIPTION
                   "System digital out mode.
				   0:Close
				   1:Open
				   "
               ::= {     sisgm1040284lrtSystemDIDO 2 }	

    sisgm1040284lrtSystemDIEventDescNormal   OBJECT-TYPE
               SYNTAX      DisplayString
               MAX-ACCESS  read-write
               STATUS      current
               DESCRIPTION
                   "Customize event message. You can describe the event in detail. "
               ::= {     sisgm1040284lrtSystemDIDO 3 }  
               
    sisgm1040284lrtSystemDIEventDescAbnormal   OBJECT-TYPE
               SYNTAX      DisplayString
               MAX-ACCESS  read-write
               STATUS      current
               DESCRIPTION
                   "Customize event message. You can describe the event in detail. "
               ::= {     sisgm1040284lrtSystemDIDO 4 }                

    sisgm1040284lrtSystemDOAutoRecovery OBJECT-TYPE
               SYNTAX       Integer32 (0..1)
               MAX-ACCESS   read-write
               STATUS       current
               DESCRIPTION
                   "Enable the function of Auto Recovery.
				   0:Disable
				   1:Enable
				   "
               ::= {    sisgm1040284lrtSystemDIDO 5 }	

    sisgm1040284lrtSystemDIRebootSystem OBJECT-TYPE
               SYNTAX       Integer32 (0..1)
               MAX-ACCESS   read-write
               STATUS       current
               DESCRIPTION
                   "Enable the function of DI Reboot System.
				   0:Disable
				   1:When DI was changed to abnormal.
				   "
               ::= {    sisgm1040284lrtSystemDIDO 6 }

sisgm1040284lrtNTPConf   OBJECT IDENTIFIER ::= { sisgm1040284lrtSystem 12 }

sisgm1040284lrtNTPConfigAutomatic   OBJECT-TYPE
               SYNTAX      Integer32 (0|1)
               MAX-ACCESS  read-write
               STATUS      current
               DESCRIPTION
                   "Indicates the Automatic mode operation. Possible modes are:
                   0:Disable, NTP servers available from the config. 
                   1:Enable, NTP servers available from the DHCP."
               ::= { sisgm1040284lrtNTPConf 2 }
               
sisgm1040284lrtNTPConfigTimeSyncInterval   OBJECT-TYPE
               SYNTAX      Integer32 (5|10|15|30|60|120)
               MAX-ACCESS  read-write
               STATUS      current
               DESCRIPTION
                   "Time-Sync Interval.
                   Valid values are restricted to 5,10,15,30,60,120 minutes. "
               ::= { sisgm1040284lrtNTPConf 3 }   

sisgm1040284lrtNTPConfigServerAddress1   OBJECT-TYPE
               SYNTAX      DisplayString
               MAX-ACCESS  read-write
               STATUS      current
               DESCRIPTION
                   "Provide the IPv4 or IPv6 address of a NTP server."
               ::= { sisgm1040284lrtNTPConf 4 }   

sisgm1040284lrtNTPConfigServerAddress2   OBJECT-TYPE
               SYNTAX      DisplayString
               MAX-ACCESS  read-write
               STATUS      current
               DESCRIPTION
                   "Provide the IPv4 or IPv6 address of a NTP server."
               ::= { sisgm1040284lrtNTPConf 5 }                
        
sisgm1040284lrtNTPConfigServerAddress3   OBJECT-TYPE
               SYNTAX      DisplayString
               MAX-ACCESS  read-write
               STATUS      current
               DESCRIPTION
                   "Provide the IPv4 or IPv6 address of a NTP server."
               ::= { sisgm1040284lrtNTPConf 6 }          
               
sisgm1040284lrtNTPConfigServerAddress4   OBJECT-TYPE
               SYNTAX      DisplayString
               MAX-ACCESS  read-write
               STATUS      current
               DESCRIPTION
                   "Provide the IPv4 or IPv6 address of a NTP server."
               ::= { sisgm1040284lrtNTPConf 7 }                    
    
sisgm1040284lrtNTPConfigServerAddress5   OBJECT-TYPE
               SYNTAX      DisplayString
               MAX-ACCESS  read-write
               STATUS      current
               DESCRIPTION
                   "Provide the IPv4 or IPv6 address of a NTP server."
               ::= { sisgm1040284lrtNTPConf 8 }  
               
-- =======================================================================================================================
sisgm1040284lrtConfiguration                                         OBJECT IDENTIFIER ::= { sisgm1040284lrtProductId 2 }

sisgm1040284lrtPort                                                  OBJECT IDENTIFIER ::= { sisgm1040284lrtConfiguration 1 }

sisgm1040284lrtPortConfigurationTable OBJECT-TYPE
   SYNTAX      SEQUENCE OF SISGM1040284LRTPortConfigurationEntry
   MAX-ACCESS  not-accessible
   STATUS      current
   DESCRIPTION
       " Show port configurations. "
   ::= { sisgm1040284lrtPort 1 }

sisgm1040284lrtPortConfigurationEntry OBJECT-TYPE
   SYNTAX      SISGM1040284LRTPortConfigurationEntry
   MAX-ACCESS  not-accessible
   STATUS      current
   DESCRIPTION
       " "
   INDEX    { sisgm1040284lrtPortConfPort  }
   ::= { sisgm1040284lrtPortConfigurationTable 1 }

SISGM1040284LRTPortConfigurationEntry ::= SEQUENCE {
   sisgm1040284lrtPortConfPort                     Integer32,
   sisgm1040284lrtPortConfPortMedia                DisplayString,
   sisgm1040284lrtPortConfLink                     DisplayString,
   sisgm1040284lrtPortConfCurrentSpeed             DisplayString,
   sisgm1040284lrtPortConfSpeed                    Integer32,
   sisgm1040284lrtPortConfCurrentFlowControlRx     Integer32,
   sisgm1040284lrtPortConfCurrentFlowControlTx     Integer32,
   sisgm1040284lrtPortConfFlowControl              Integer32,
   sisgm1040284lrtPortConfMaxFrameSize             Integer32,
   sisgm1040284lrtPortConfExcessiveCollisionMode   Integer32,
-- sisgm1040284lrtPortConfPowerControl             Integer32,
   sisgm1040284lrtPortConfDescription              DisplayString,
   sisgm1040284lrtPortConfFrameLengthCheck         Integer32
}

sisgm1040284lrtPortConfPort OBJECT-TYPE
   SYNTAX      Integer32 (1..4095)
   MAX-ACCESS  not-accessible
   STATUS      current
   DESCRIPTION
       " port, range : 1 - port number. "
   ::= { sisgm1040284lrtPortConfigurationEntry 1 }

sisgm1040284lrtPortConfPortMedia OBJECT-TYPE
   SYNTAX      DisplayString(SIZE (1..4))
   MAX-ACCESS  read-only
   STATUS      current
   DESCRIPTION
       " Show port media. "
   ::= { sisgm1040284lrtPortConfigurationEntry 2 }

sisgm1040284lrtPortConfLink OBJECT-TYPE
   SYNTAX      DisplayString(SIZE (2..4))
   MAX-ACCESS  read-only
   STATUS      current
   DESCRIPTION
       " The current link state. "
   ::= { sisgm1040284lrtPortConfigurationEntry 3 }

sisgm1040284lrtPortConfCurrentSpeed OBJECT-TYPE
   SYNTAX      DisplayString(SIZE (6..12))
   MAX-ACCESS  read-only
   STATUS      current
   DESCRIPTION
       " The current link speed of the port. "
   ::= { sisgm1040284lrtPortConfigurationEntry 4 }

sisgm1040284lrtPortConfSpeed OBJECT-TYPE
   SYNTAX      Integer32 (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X,
        12: 10G Full. "
   ::= { sisgm1040284lrtPortConfigurationEntry 5 }

sisgm1040284lrtPortConfCurrentFlowControlRx OBJECT-TYPE
   SYNTAX      Integer32 (0|1)
   MAX-ACCESS  read-only
   STATUS      current
   DESCRIPTION
       "0: disable
        1: enable
        2: not support.  "
   ::= { sisgm1040284lrtPortConfigurationEntry 6 }

sisgm1040284lrtPortConfCurrentFlowControlTx OBJECT-TYPE
   SYNTAX      Integer32 (0|1)
   MAX-ACCESS  read-only
   STATUS      current
   DESCRIPTION
       "0: disable
        1: enable
        2: not support.  "
   ::= { sisgm1040284lrtPortConfigurationEntry 7 }

sisgm1040284lrtPortConfFlowControl OBJECT-TYPE
   SYNTAX      Integer32 (0|1)
   MAX-ACCESS  read-write
   STATUS      current
   DESCRIPTION
       "default: 0,
        0: disable
        1: enable
        2: not support. "
   ::= { sisgm1040284lrtPortConfigurationEntry 8 }

sisgm1040284lrtPortConfMaxFrameSize OBJECT-TYPE
   SYNTAX      Integer32 (1518..9600)
   MAX-ACCESS  read-write
   STATUS      current
   DESCRIPTION
       "default: 9600 , range : 1518 - 9600 "
   ::= { sisgm1040284lrtPortConfigurationEntry 9 }

sisgm1040284lrtPortConfExcessiveCollisionMode OBJECT-TYPE
   SYNTAX      Integer32 (0|1)
   MAX-ACCESS  read-write
   STATUS      current
   DESCRIPTION
       "default: 0,
        Excessive Collision Mode :
        0: Discard,
        1: Restart,
        2: not support.
       "
   ::= { sisgm1040284lrtPortConfigurationEntry 10 }

--sisgm1040284lrtPortConfPowerControl OBJECT-TYPE
--   SYNTAX      Integer32 (0..3)
--   MAX-ACCESS  read-write
--   STATUS      current
--   DESCRIPTION
--       "default: 0,
--        PowerControl :
--        0: disable,
--        1: Actiphy,
--        2: Dynamic (perfectReach),
--        3: Enable,
--        4: not support.
--       "
--   ::= { sisgm1040284lrtPortConfigurationEntry 11 }

sisgm1040284lrtPortConfDescription OBJECT-TYPE
   SYNTAX      DisplayString
   MAX-ACCESS  read-write
   STATUS      current
   DESCRIPTION
       " Interface specific description.
         Up to 47 characters describing this interface. "
   ::= { sisgm1040284lrtPortConfigurationEntry 12 }

sisgm1040284lrtPortConfFrameLengthCheck OBJECT-TYPE
   SYNTAX      Integer32 (0|1)
   MAX-ACCESS  read-write
   STATUS      current
   DESCRIPTION
       "default: 0,
        0: disable
        1: enable"
   ::= { sisgm1040284lrtPortConfigurationEntry 13 } 

sisgm1040284lrtPortTrafficStatisticsTable OBJECT-TYPE
   SYNTAX      SEQUENCE OF SISGM1040284LRTPortTrafficStatisticsEntry
   MAX-ACCESS  not-accessible
   STATUS      current
   DESCRIPTION
       " "
   ::= { sisgm1040284lrtPort 2 }

sisgm1040284lrtPortTrafficStatisticsEntry OBJECT-TYPE
   SYNTAX      SISGM1040284LRTPortTrafficStatisticsEntry
   MAX-ACCESS  not-accessible
   STATUS      current
   DESCRIPTION
       " "
   INDEX    { sisgm1040284lrtPortTrafficStatisticsPort  }
   ::= { sisgm1040284lrtPortTrafficStatisticsTable 1 }

SISGM1040284LRTPortTrafficStatisticsEntry ::= SEQUENCE {
   sisgm1040284lrtPortTrafficStatisticsPort          Integer32,
   sisgm1040284lrtPortTrafficStatisticsClear         Integer32,
   sisgm1040284lrtPortTrafficRxPackets               Counter64,
   sisgm1040284lrtPortTrafficRxOctets                Counter64,
   sisgm1040284lrtPortTrafficRxUnicast               Counter64,
   sisgm1040284lrtPortTrafficRxMulticast             Counter64,
   sisgm1040284lrtPortTrafficRxBroadcast             Counter64,
   sisgm1040284lrtPortTrafficRxPause                 Counter64,
   sisgm1040284lrtPortTrafficRx64Bytes               Counter64,
   sisgm1040284lrtPortTrafficRx65to127Bytes          Counter64,
   sisgm1040284lrtPortTrafficRx128to255Bytes         Counter64,
   sisgm1040284lrtPortTrafficRx256to511Bytes         Counter64,
   sisgm1040284lrtPortTrafficRx512to1023Bytes        Counter64,
   sisgm1040284lrtPortTrafficRx1024to1526Bytes       Counter64,
   sisgm1040284lrtPortTrafficRxExceecd1527Bytes      Counter64,
   sisgm1040284lrtPortTrafficRxQ0                    Counter64,
   sisgm1040284lrtPortTrafficRxQ1                    Counter64,
   sisgm1040284lrtPortTrafficRxQ2                    Counter64,
   sisgm1040284lrtPortTrafficRxQ3                    Counter64,
   sisgm1040284lrtPortTrafficRxQ4                    Counter64,
   sisgm1040284lrtPortTrafficRxQ5                    Counter64,
   sisgm1040284lrtPortTrafficRxQ6                    Counter64,
   sisgm1040284lrtPortTrafficRxQ7                    Counter64,
   sisgm1040284lrtPortTrafficRxDrops                 Counter64,
   sisgm1040284lrtPortTrafficRxCRCorAlignment        Counter64,
   sisgm1040284lrtPortTrafficRxUndersize             Counter64,
   sisgm1040284lrtPortTrafficRxOversize              Counter64,
   sisgm1040284lrtPortTrafficRxFragments             Counter64,
   sisgm1040284lrtPortTrafficRxJabber                Counter64,
   sisgm1040284lrtPortTrafficRxFiltered              Counter64,
   sisgm1040284lrtPortTrafficTxPackets               Counter64,
   sisgm1040284lrtPortTrafficTxOctets                Counter64,
   sisgm1040284lrtPortTrafficTxUnicast               Counter64,
   sisgm1040284lrtPortTrafficTxMulticast             Counter64,
   sisgm1040284lrtPortTrafficTxBroadcast             Counter64,
   sisgm1040284lrtPortTrafficTxPause                 Counter64,
   sisgm1040284lrtPortTrafficTx64Bytes               Counter64,
   sisgm1040284lrtPortTrafficTx65to127Bytes          Counter64,
   sisgm1040284lrtPortTrafficTx128to255Bytes         Counter64,
   sisgm1040284lrtPortTrafficTx256to511Bytes         Counter64,
   sisgm1040284lrtPortTrafficTx512to1023Bytes        Counter64,
   sisgm1040284lrtPortTrafficTx1024to1526Bytes       Counter64,
   sisgm1040284lrtPortTrafficTxExceecd1527Bytes      Counter64,
   sisgm1040284lrtPortTrafficTxQ0                    Counter64,
   sisgm1040284lrtPortTrafficTxQ1                    Counter64,
   sisgm1040284lrtPortTrafficTxQ2                    Counter64,
   sisgm1040284lrtPortTrafficTxQ3                    Counter64,
   sisgm1040284lrtPortTrafficTxQ4                    Counter64,
   sisgm1040284lrtPortTrafficTxQ5                    Counter64,
   sisgm1040284lrtPortTrafficTxQ6                    Counter64,
   sisgm1040284lrtPortTrafficTxQ7                    Counter64,
   sisgm1040284lrtPortTrafficTxDrops                 Counter64,
   sisgm1040284lrtPortTrafficTxLateOrExcColl         Counter64
}

sisgm1040284lrtPortTrafficStatisticsPort OBJECT-TYPE
   SYNTAX      Integer32 (1..4095)
   MAX-ACCESS  not-accessible
   STATUS      current
   DESCRIPTION
       " "
   ::= { sisgm1040284lrtPortTrafficStatisticsEntry 1 }

sisgm1040284lrtPortTrafficStatisticsClear OBJECT-TYPE
   SYNTAX      Integer32(0|1)
   MAX-ACCESS  read-write
   STATUS      current
   DESCRIPTION
       " "
   ::= { sisgm1040284lrtPortTrafficStatisticsEntry 2 }

sisgm1040284lrtPortTrafficRxPackets OBJECT-TYPE
   SYNTAX      Counter64
   MAX-ACCESS  read-only
   STATUS      current
   DESCRIPTION
       " "
   ::= { sisgm1040284lrtPortTrafficStatisticsEntry 3 }

sisgm1040284lrtPortTrafficRxOctets OBJECT-TYPE
   SYNTAX      Counter64
   MAX-ACCESS  read-only
   STATUS      current
   DESCRIPTION
       " "
   ::= { sisgm1040284lrtPortTrafficStatisticsEntry 4 }

sisgm1040284lrtPortTrafficRxUnicast OBJECT-TYPE
   SYNTAX      Counter64
   MAX-ACCESS  read-only
   STATUS      current
   DESCRIPTION
       " "
   ::= { sisgm1040284lrtPortTrafficStatisticsEntry 5 }

sisgm1040284lrtPortTrafficRxMulticast OBJECT-TYPE
   SYNTAX      Counter64
   MAX-ACCESS  read-only
   STATUS      current
   DESCRIPTION
       " "
   ::= { sisgm1040284lrtPortTrafficStatisticsEntry 6 }

sisgm1040284lrtPortTrafficRxBroadcast OBJECT-TYPE
   SYNTAX      Counter64
   MAX-ACCESS  read-only
   STATUS      current
   DESCRIPTION
       " "
   ::= { sisgm1040284lrtPortTrafficStatisticsEntry 7 }

sisgm1040284lrtPortTrafficRxPause OBJECT-TYPE
   SYNTAX      Counter64
   MAX-ACCESS  read-only
   STATUS      current
   DESCRIPTION
       " "
   ::= { sisgm1040284lrtPortTrafficStatisticsEntry 8 }

sisgm1040284lrtPortTrafficRx64Bytes OBJECT-TYPE
   SYNTAX      Counter64
   MAX-ACCESS  read-only
   STATUS      current
   DESCRIPTION
       " "
   ::= { sisgm1040284lrtPortTrafficStatisticsEntry 9 }

sisgm1040284lrtPortTrafficRx65to127Bytes OBJECT-TYPE
   SYNTAX      Counter64
   MAX-ACCESS  read-only
   STATUS      current
   DESCRIPTION
       " "
   ::= { sisgm1040284lrtPortTrafficStatisticsEntry 10 }

sisgm1040284lrtPortTrafficRx128to255Bytes OBJECT-TYPE
   SYNTAX      Counter64
   MAX-ACCESS  read-only
   STATUS      current
   DESCRIPTION
       " "
   ::= { sisgm1040284lrtPortTrafficStatisticsEntry 11 }

sisgm1040284lrtPortTrafficRx256to511Bytes OBJECT-TYPE
   SYNTAX      Counter64
   MAX-ACCESS  read-only
   STATUS      current
   DESCRIPTION
       " "
   ::= { sisgm1040284lrtPortTrafficStatisticsEntry 12 }

sisgm1040284lrtPortTrafficRx512to1023Bytes OBJECT-TYPE
   SYNTAX      Counter64
   MAX-ACCESS  read-only
   STATUS      current
   DESCRIPTION
       " "
   ::= { sisgm1040284lrtPortTrafficStatisticsEntry 13 }

sisgm1040284lrtPortTrafficRx1024to1526Bytes OBJECT-TYPE
   SYNTAX      Counter64
   MAX-ACCESS  read-only
   STATUS      current
   DESCRIPTION
       " "
   ::= { sisgm1040284lrtPortTrafficStatisticsEntry 14 }

sisgm1040284lrtPortTrafficRxExceecd1527Bytes OBJECT-TYPE
   SYNTAX      Counter64
   MAX-ACCESS  read-only
   STATUS      current
   DESCRIPTION
       " "
   ::= { sisgm1040284lrtPortTrafficStatisticsEntry 15 }

sisgm1040284lrtPortTrafficRxQ0 OBJECT-TYPE
   SYNTAX      Counter64
   MAX-ACCESS  read-only
   STATUS      current
   DESCRIPTION
       " "
   ::= { sisgm1040284lrtPortTrafficStatisticsEntry 16 }

sisgm1040284lrtPortTrafficRxQ1 OBJECT-TYPE
   SYNTAX      Counter64
   MAX-ACCESS  read-only
   STATUS      current
   DESCRIPTION
       " "
   ::= { sisgm1040284lrtPortTrafficStatisticsEntry 17 }

sisgm1040284lrtPortTrafficRxQ2 OBJECT-TYPE
   SYNTAX      Counter64
   MAX-ACCESS  read-only
   STATUS      current
   DESCRIPTION
       " "
   ::= { sisgm1040284lrtPortTrafficStatisticsEntry 18 }

sisgm1040284lrtPortTrafficRxQ3 OBJECT-TYPE
   SYNTAX      Counter64
   MAX-ACCESS  read-only
   STATUS      current
   DESCRIPTION
       " "
   ::= { sisgm1040284lrtPortTrafficStatisticsEntry 19 }

sisgm1040284lrtPortTrafficRxQ4 OBJECT-TYPE
   SYNTAX      Counter64
   MAX-ACCESS  read-only
   STATUS      current
   DESCRIPTION
       " "
   ::= { sisgm1040284lrtPortTrafficStatisticsEntry 20 }

sisgm1040284lrtPortTrafficRxQ5 OBJECT-TYPE
   SYNTAX      Counter64
   MAX-ACCESS  read-only
   STATUS      current
   DESCRIPTION
       " "
   ::= { sisgm1040284lrtPortTrafficStatisticsEntry 21 }

sisgm1040284lrtPortTrafficRxQ6 OBJECT-TYPE
   SYNTAX      Counter64
   MAX-ACCESS  read-only
   STATUS      current
   DESCRIPTION
       " "
   ::= { sisgm1040284lrtPortTrafficStatisticsEntry 22 }

sisgm1040284lrtPortTrafficRxQ7 OBJECT-TYPE
   SYNTAX      Counter64
   MAX-ACCESS  read-only
   STATUS      current
   DESCRIPTION
       " "
   ::= { sisgm1040284lrtPortTrafficStatisticsEntry 23 }

sisgm1040284lrtPortTrafficRxDrops OBJECT-TYPE
   SYNTAX      Counter64
   MAX-ACCESS  read-only
   STATUS      current
   DESCRIPTION
       " "
   ::= { sisgm1040284lrtPortTrafficStatisticsEntry 24 }

sisgm1040284lrtPortTrafficRxCRCorAlignment OBJECT-TYPE
   SYNTAX      Counter64
   MAX-ACCESS  read-only
   STATUS      current
   DESCRIPTION
       " "
   ::= { sisgm1040284lrtPortTrafficStatisticsEntry 25 }

sisgm1040284lrtPortTrafficRxUndersize OBJECT-TYPE
   SYNTAX      Counter64
   MAX-ACCESS  read-only
   STATUS      current
   DESCRIPTION
       " "
   ::= { sisgm1040284lrtPortTrafficStatisticsEntry 26 }

sisgm1040284lrtPortTrafficRxOversize OBJECT-TYPE
   SYNTAX      Counter64
   MAX-ACCESS  read-only
   STATUS      current
   DESCRIPTION
       " "
   ::= { sisgm1040284lrtPortTrafficStatisticsEntry 27 }

sisgm1040284lrtPortTrafficRxFragments OBJECT-TYPE
   SYNTAX      Counter64
   MAX-ACCESS  read-only
   STATUS      current
   DESCRIPTION
       " "
   ::= { sisgm1040284lrtPortTrafficStatisticsEntry 28 }

sisgm1040284lrtPortTrafficRxJabber OBJECT-TYPE
   SYNTAX      Counter64
   MAX-ACCESS  read-only
   STATUS      current
   DESCRIPTION
       " "
   ::= { sisgm1040284lrtPortTrafficStatisticsEntry 29 }

sisgm1040284lrtPortTrafficRxFiltered OBJECT-TYPE
   SYNTAX      Counter64
   MAX-ACCESS  read-only
   STATUS      current
   DESCRIPTION
       " "
   ::= { sisgm1040284lrtPortTrafficStatisticsEntry 30 }

sisgm1040284lrtPortTrafficTxPackets OBJECT-TYPE
   SYNTAX      Counter64
   MAX-ACCESS  read-only
   STATUS      current
   DESCRIPTION
       " "
   ::= { sisgm1040284lrtPortTrafficStatisticsEntry 31 }

sisgm1040284lrtPortTrafficTxOctets OBJECT-TYPE
   SYNTAX      Counter64
   MAX-ACCESS  read-only
   STATUS      current
   DESCRIPTION
       " "
   ::= { sisgm1040284lrtPortTrafficStatisticsEntry 32 }

sisgm1040284lrtPortTrafficTxUnicast OBJECT-TYPE
   SYNTAX      Counter64
   MAX-ACCESS  read-only
   STATUS      current
   DESCRIPTION
       " "
   ::= { sisgm1040284lrtPortTrafficStatisticsEntry 33 }

sisgm1040284lrtPortTrafficTxMulticast OBJECT-TYPE
   SYNTAX      Counter64
   MAX-ACCESS  read-only
   STATUS      current
   DESCRIPTION
       " "
   ::= { sisgm1040284lrtPortTrafficStatisticsEntry 34 }

sisgm1040284lrtPortTrafficTxBroadcast OBJECT-TYPE
   SYNTAX      Counter64
   MAX-ACCESS  read-only
   STATUS      current
   DESCRIPTION
       " "
   ::= { sisgm1040284lrtPortTrafficStatisticsEntry 35 }

sisgm1040284lrtPortTrafficTxPause OBJECT-TYPE
   SYNTAX      Counter64
   MAX-ACCESS  read-only
   STATUS      current
   DESCRIPTION
       " "
   ::= { sisgm1040284lrtPortTrafficStatisticsEntry 36 }

sisgm1040284lrtPortTrafficTx64Bytes OBJECT-TYPE
   SYNTAX      Counter64
   MAX-ACCESS  read-only
   STATUS      current
   DESCRIPTION
       " "
   ::= { sisgm1040284lrtPortTrafficStatisticsEntry 37 }

sisgm1040284lrtPortTrafficTx65to127Bytes OBJECT-TYPE
   SYNTAX      Counter64
   MAX-ACCESS  read-only
   STATUS      current
   DESCRIPTION
       " "
   ::= { sisgm1040284lrtPortTrafficStatisticsEntry 38 }

sisgm1040284lrtPortTrafficTx128to255Bytes OBJECT-TYPE
   SYNTAX      Counter64
   MAX-ACCESS  read-only
   STATUS      current
   DESCRIPTION
       " "
   ::= { sisgm1040284lrtPortTrafficStatisticsEntry 39 }

sisgm1040284lrtPortTrafficTx256to511Bytes OBJECT-TYPE
   SYNTAX      Counter64
   MAX-ACCESS  read-only
   STATUS      current
   DESCRIPTION
       " "
   ::= { sisgm1040284lrtPortTrafficStatisticsEntry 40 }

sisgm1040284lrtPortTrafficTx512to1023Bytes OBJECT-TYPE
   SYNTAX      Counter64
   MAX-ACCESS  read-only
   STATUS      current
   DESCRIPTION
       " "
   ::= { sisgm1040284lrtPortTrafficStatisticsEntry 41 }

sisgm1040284lrtPortTrafficTx1024to1526Bytes OBJECT-TYPE
   SYNTAX      Counter64
   MAX-ACCESS  read-only
   STATUS      current
   DESCRIPTION
       " "
   ::= { sisgm1040284lrtPortTrafficStatisticsEntry 42 }

sisgm1040284lrtPortTrafficTxExceecd1527Bytes OBJECT-TYPE
   SYNTAX      Counter64
   MAX-ACCESS  read-only
   STATUS      current
   DESCRIPTION
       " "
   ::= { sisgm1040284lrtPortTrafficStatisticsEntry 43 }

sisgm1040284lrtPortTrafficTxQ0 OBJECT-TYPE
   SYNTAX      Counter64
   MAX-ACCESS  read-only
   STATUS      current
   DESCRIPTION
       " "
   ::= { sisgm1040284lrtPortTrafficStatisticsEntry 44 }

sisgm1040284lrtPortTrafficTxQ1 OBJECT-TYPE
   SYNTAX      Counter64
   MAX-ACCESS  read-only
   STATUS      current
   DESCRIPTION
       " "
   ::= { sisgm1040284lrtPortTrafficStatisticsEntry 45 }

sisgm1040284lrtPortTrafficTxQ2 OBJECT-TYPE
   SYNTAX      Counter64
   MAX-ACCESS  read-only
   STATUS      current
   DESCRIPTION
       " "
   ::= { sisgm1040284lrtPortTrafficStatisticsEntry 46 }

sisgm1040284lrtPortTrafficTxQ3 OBJECT-TYPE
   SYNTAX      Counter64
   MAX-ACCESS  read-only
   STATUS      current
   DESCRIPTION
       " "
   ::= { sisgm1040284lrtPortTrafficStatisticsEntry 47 }

sisgm1040284lrtPortTrafficTxQ4 OBJECT-TYPE
   SYNTAX      Counter64
   MAX-ACCESS  read-only
   STATUS      current
   DESCRIPTION
       " "
   ::= { sisgm1040284lrtPortTrafficStatisticsEntry 48 }

sisgm1040284lrtPortTrafficTxQ5 OBJECT-TYPE
   SYNTAX      Counter64
   MAX-ACCESS  read-only
   STATUS      current
   DESCRIPTION
       " "
   ::= { sisgm1040284lrtPortTrafficStatisticsEntry 49 }

sisgm1040284lrtPortTrafficTxQ6 OBJECT-TYPE
   SYNTAX      Counter64
   MAX-ACCESS  read-only
   STATUS      current
   DESCRIPTION
       " "
   ::= { sisgm1040284lrtPortTrafficStatisticsEntry 50 }


sisgm1040284lrtPortTrafficTxQ7 OBJECT-TYPE
   SYNTAX      Counter64
   MAX-ACCESS  read-only
   STATUS      current
   DESCRIPTION
       " "
   ::= { sisgm1040284lrtPortTrafficStatisticsEntry 51 }

sisgm1040284lrtPortTrafficTxDrops OBJECT-TYPE
   SYNTAX      Counter64
   MAX-ACCESS  read-only
   STATUS      current
   DESCRIPTION
       " "
   ::= { sisgm1040284lrtPortTrafficStatisticsEntry 52 }

sisgm1040284lrtPortTrafficTxLateOrExcColl OBJECT-TYPE
   SYNTAX      Counter64
   MAX-ACCESS  read-only
   STATUS      current
   DESCRIPTION
       " "
   ::= { sisgm1040284lrtPortTrafficStatisticsEntry 53 }


sisgm1040284lrtPortQoSStatistics                                     OBJECT IDENTIFIER ::= { sisgm1040284lrtPort 3 }

sisgm1040284lrtPortQoSStatisticsClear OBJECT-TYPE
   SYNTAX      Integer32(0|1)
   MAX-ACCESS  read-only
   STATUS      current
   DESCRIPTION
       "default: 0
       0: none
       1: clear "
   ::= { sisgm1040284lrtPortQoSStatistics 1 }

sisgm1040284lrtPortQoSStatisticsTable OBJECT-TYPE
   SYNTAX      SEQUENCE OF SISGM1040284LRTPortQoSStatisticsEntry
   MAX-ACCESS  not-accessible
   STATUS      current
   DESCRIPTION
       " "
   ::= { sisgm1040284lrtPortQoSStatistics 2 }

sisgm1040284lrtPortQoSStatisticsEntry OBJECT-TYPE
   SYNTAX      SISGM1040284LRTPortQoSStatisticsEntry
   MAX-ACCESS  not-accessible
   STATUS      current
   DESCRIPTION
       " "
   INDEX    { sisgm1040284lrtPortQoSStatisticsPort  }
   ::= { sisgm1040284lrtPortQoSStatisticsTable 1 }

SISGM1040284LRTPortQoSStatisticsEntry ::= SEQUENCE {
   sisgm1040284lrtPortQoSStatisticsPort      Integer32,
   sisgm1040284lrtPortQoSQ0Rx                Counter64,
   sisgm1040284lrtPortQoSQ0Tx                Counter64,
   sisgm1040284lrtPortQoSQ1Rx                Counter64,
   sisgm1040284lrtPortQoSQ1Tx                Counter64,
   sisgm1040284lrtPortQoSQ2Rx                Counter64,
   sisgm1040284lrtPortQoSQ2Tx                Counter64,
   sisgm1040284lrtPortQoSQ3Rx                Counter64,
   sisgm1040284lrtPortQoSQ3Tx                Counter64,
   sisgm1040284lrtPortQoSQ4Rx                Counter64,
   sisgm1040284lrtPortQoSQ4Tx                Counter64,
   sisgm1040284lrtPortQoSQ5Rx                Counter64,
   sisgm1040284lrtPortQoSQ5Tx                Counter64,
   sisgm1040284lrtPortQoSQ6Rx                Counter64,
   sisgm1040284lrtPortQoSQ6Tx                Counter64,
   sisgm1040284lrtPortQoSQ7Rx                Counter64,
   sisgm1040284lrtPortQoSQ7Tx                Counter64
}

sisgm1040284lrtPortQoSStatisticsPort OBJECT-TYPE
   SYNTAX      Integer32 (1..4095)
   MAX-ACCESS  not-accessible
   STATUS      current
   DESCRIPTION
       " "
   ::= { sisgm1040284lrtPortQoSStatisticsEntry 1 }

sisgm1040284lrtPortQoSQ0Rx OBJECT-TYPE
   SYNTAX      Counter64
   MAX-ACCESS  read-only
   STATUS      current
   DESCRIPTION
       " "
   ::= { sisgm1040284lrtPortQoSStatisticsEntry 2 }

sisgm1040284lrtPortQoSQ0Tx OBJECT-TYPE
   SYNTAX      Counter64
   MAX-ACCESS  read-only
   STATUS      current
   DESCRIPTION
       " "
   ::= { sisgm1040284lrtPortQoSStatisticsEntry 3 }

sisgm1040284lrtPortQoSQ1Rx OBJECT-TYPE
   SYNTAX      Counter64
   MAX-ACCESS  read-only
   STATUS      current
   DESCRIPTION
       " "
   ::= { sisgm1040284lrtPortQoSStatisticsEntry 4 }

sisgm1040284lrtPortQoSQ1Tx OBJECT-TYPE
   SYNTAX      Counter64
   MAX-ACCESS  read-only
   STATUS      current
   DESCRIPTION
       " "
   ::= { sisgm1040284lrtPortQoSStatisticsEntry 5 }

sisgm1040284lrtPortQoSQ2Rx OBJECT-TYPE
   SYNTAX      Counter64
   MAX-ACCESS  read-only
   STATUS      current
   DESCRIPTION
       " "
   ::= { sisgm1040284lrtPortQoSStatisticsEntry 6 }

sisgm1040284lrtPortQoSQ2Tx OBJECT-TYPE
   SYNTAX      Counter64
   MAX-ACCESS  read-only
   STATUS      current
   DESCRIPTION
       " "
   ::= { sisgm1040284lrtPortQoSStatisticsEntry 7 }

sisgm1040284lrtPortQoSQ3Rx OBJECT-TYPE
   SYNTAX      Counter64
   MAX-ACCESS  read-only
   STATUS      current
   DESCRIPTION
       " "
   ::= { sisgm1040284lrtPortQoSStatisticsEntry 8 }

sisgm1040284lrtPortQoSQ3Tx OBJECT-TYPE
   SYNTAX      Counter64
   MAX-ACCESS  read-only
   STATUS      current
   DESCRIPTION
       " "
   ::= { sisgm1040284lrtPortQoSStatisticsEntry 9 }

sisgm1040284lrtPortQoSQ4Rx OBJECT-TYPE
   SYNTAX      Counter64
   MAX-ACCESS  read-only
   STATUS      current
   DESCRIPTION
       " "
   ::= { sisgm1040284lrtPortQoSStatisticsEntry 10 }

sisgm1040284lrtPortQoSQ4Tx OBJECT-TYPE
   SYNTAX      Counter64
   MAX-ACCESS  read-only
   STATUS      current
   DESCRIPTION
       " "
   ::= { sisgm1040284lrtPortQoSStatisticsEntry 11 }

sisgm1040284lrtPortQoSQ5Rx OBJECT-TYPE
   SYNTAX      Counter64
   MAX-ACCESS  read-only
   STATUS      current
   DESCRIPTION
       " "
   ::= { sisgm1040284lrtPortQoSStatisticsEntry 12 }

sisgm1040284lrtPortQoSQ5Tx OBJECT-TYPE
   SYNTAX      Counter64
   MAX-ACCESS  read-only
   STATUS      current
   DESCRIPTION
       " "
   ::= { sisgm1040284lrtPortQoSStatisticsEntry 13 }

sisgm1040284lrtPortQoSQ6Rx OBJECT-TYPE
   SYNTAX      Counter64
   MAX-ACCESS  read-only
   STATUS      current
   DESCRIPTION
       " "
   ::= { sisgm1040284lrtPortQoSStatisticsEntry 14 }

sisgm1040284lrtPortQoSQ6Tx OBJECT-TYPE
   SYNTAX      Counter64
   MAX-ACCESS  read-only
   STATUS      current
   DESCRIPTION
       " "
   ::= { sisgm1040284lrtPortQoSStatisticsEntry 15 }

sisgm1040284lrtPortQoSQ7Rx OBJECT-TYPE
   SYNTAX      Counter64
   MAX-ACCESS  read-only
   STATUS      current
   DESCRIPTION
       " "
   ::= { sisgm1040284lrtPortQoSStatisticsEntry 16 }

sisgm1040284lrtPortQoSQ7Tx OBJECT-TYPE
   SYNTAX      Counter64
   MAX-ACCESS  read-only
   STATUS      current
   DESCRIPTION
       " "
   ::= { sisgm1040284lrtPortQoSStatisticsEntry 17 }

sisgm1040284lrtSFPInfoTable OBJECT-TYPE
   SYNTAX      SEQUENCE OF SISGM1040284LRTSFPInfoEntry
   MAX-ACCESS  not-accessible
   STATUS      current
   DESCRIPTION
       " "
   ::= { sisgm1040284lrtPort 4 }

sisgm1040284lrtSFPInfoEntry OBJECT-TYPE
   SYNTAX      SISGM1040284LRTSFPInfoEntry
   MAX-ACCESS  not-accessible
   STATUS      current
   DESCRIPTION
       " "
   INDEX    { sisgm1040284lrtSFPInfoIndex }
   ::= { sisgm1040284lrtSFPInfoTable 1 }

SISGM1040284LRTSFPInfoEntry ::= SEQUENCE {
   sisgm1040284lrtSFPInfoIndex               Integer32,
   sisgm1040284lrtSFPInfoPort                DisplayString,
   sisgm1040284lrtSFPConnectorType           DisplayString,
   sisgm1040284lrtSFPFiberType               DisplayString,
   sisgm1040284lrtSFPTxCentralWavelength     DisplayString,
   sisgm1040284lrtSFPBaudRate                DisplayString,
   sisgm1040284lrtSFPVendorOUI               DisplayString,
   sisgm1040284lrtSFPVendorName              DisplayString,
   sisgm1040284lrtSFPVendorPN                DisplayString,
   sisgm1040284lrtSFPVendorRev               DisplayString,
   sisgm1040284lrtSFPVendorSN                DisplayString,
   sisgm1040284lrtSFPDateCode                DisplayString,
   sisgm1040284lrtSFPTemperature             DisplayString,
   sisgm1040284lrtSFPVcc                     DisplayString,
   sisgm1040284lrtSFPMon1Bias                DisplayString,
   sisgm1040284lrtSFPMon2TxPWR               DisplayString,
   sisgm1040284lrtSFPMon3RxPWR               DisplayString
}

sisgm1040284lrtSFPInfoIndex OBJECT-TYPE
   SYNTAX      Integer32 (1..4095)
   MAX-ACCESS  not-accessible
   STATUS      current
   DESCRIPTION
       " "
   ::= { sisgm1040284lrtSFPInfoEntry 1 }

sisgm1040284lrtSFPInfoPort OBJECT-TYPE
   SYNTAX      DisplayString
   MAX-ACCESS  read-only
   STATUS      current
   DESCRIPTION
       " "
   ::= { sisgm1040284lrtSFPInfoEntry 2 }

sisgm1040284lrtSFPConnectorType OBJECT-TYPE
   SYNTAX      DisplayString
   MAX-ACCESS  read-only
   STATUS      current
   DESCRIPTION
       " "
   ::= { sisgm1040284lrtSFPInfoEntry 3 }

sisgm1040284lrtSFPFiberType OBJECT-TYPE
   SYNTAX      DisplayString
   MAX-ACCESS  read-only
   STATUS      current
   DESCRIPTION
       " "
   ::= { sisgm1040284lrtSFPInfoEntry 4 }

sisgm1040284lrtSFPTxCentralWavelength OBJECT-TYPE
   SYNTAX      DisplayString
   MAX-ACCESS  read-only
   STATUS      current
   DESCRIPTION
       " "
   ::= { sisgm1040284lrtSFPInfoEntry 5 }

sisgm1040284lrtSFPBaudRate OBJECT-TYPE
   SYNTAX      DisplayString
   MAX-ACCESS  read-only
   STATUS      current
   DESCRIPTION
       " "
   ::= { sisgm1040284lrtSFPInfoEntry 6 }

sisgm1040284lrtSFPVendorOUI OBJECT-TYPE
   SYNTAX      DisplayString
   MAX-ACCESS  read-only
   STATUS      current
   DESCRIPTION
       " "
   ::= { sisgm1040284lrtSFPInfoEntry 7 }

sisgm1040284lrtSFPVendorName OBJECT-TYPE
   SYNTAX      DisplayString
   MAX-ACCESS  read-only
   STATUS      current
   DESCRIPTION
       " "
   ::= { sisgm1040284lrtSFPInfoEntry 8 }

sisgm1040284lrtSFPVendorPN OBJECT-TYPE
   SYNTAX      DisplayString
   MAX-ACCESS  read-only
   STATUS      current
   DESCRIPTION
       " "
   ::= { sisgm1040284lrtSFPInfoEntry 9 }

sisgm1040284lrtSFPVendorRev OBJECT-TYPE
   SYNTAX      DisplayString
   MAX-ACCESS  read-only
   STATUS      current
   DESCRIPTION
       " "
   ::= { sisgm1040284lrtSFPInfoEntry 10 }

sisgm1040284lrtSFPVendorSN OBJECT-TYPE
   SYNTAX      DisplayString
   MAX-ACCESS  read-only
   STATUS      current
   DESCRIPTION
       " "
   ::= { sisgm1040284lrtSFPInfoEntry 11 }

sisgm1040284lrtSFPDateCode OBJECT-TYPE
   SYNTAX      DisplayString
   MAX-ACCESS  read-only
   STATUS      current
   DESCRIPTION
       " "
   ::= { sisgm1040284lrtSFPInfoEntry 12 }

sisgm1040284lrtSFPTemperature OBJECT-TYPE
   SYNTAX      DisplayString
   MAX-ACCESS  read-only
   STATUS      current
   DESCRIPTION
       " "
   ::= { sisgm1040284lrtSFPInfoEntry 13 }

sisgm1040284lrtSFPVcc OBJECT-TYPE
   SYNTAX      DisplayString
   MAX-ACCESS  read-only
   STATUS      current
   DESCRIPTION
       " "
   ::= { sisgm1040284lrtSFPInfoEntry 14 }

sisgm1040284lrtSFPMon1Bias OBJECT-TYPE
   SYNTAX      DisplayString
   MAX-ACCESS  read-only
   STATUS      current
   DESCRIPTION
       " "
   ::= { sisgm1040284lrtSFPInfoEntry 15 }

sisgm1040284lrtSFPMon2TxPWR OBJECT-TYPE
   SYNTAX      DisplayString
   MAX-ACCESS  read-only
   STATUS      current
   DESCRIPTION
       " "
   ::= { sisgm1040284lrtSFPInfoEntry 16 }

sisgm1040284lrtSFPMon3RxPWR OBJECT-TYPE
   SYNTAX      DisplayString
   MAX-ACCESS  read-only
   STATUS      current
   DESCRIPTION
       " "
   ::= { sisgm1040284lrtSFPInfoEntry 17 }


sisgm1040284lrtVoiceVLAN                                             OBJECT IDENTIFIER ::= { sisgm1040284lrtConfiguration 2 }

sisgm1040284lrtVoiceVLANConf                                         OBJECT IDENTIFIER ::= { sisgm1040284lrtVoiceVLAN 1 }

sisgm1040284lrtVoiceVLANMode OBJECT-TYPE
   SYNTAX      Integer32 (0|1)
   MAX-ACCESS  read-write
   STATUS      current
   DESCRIPTION
       " Voice VLAN mode operation.
       default: 0,
       0: disable
       1: enable"
   ::= { sisgm1040284lrtVoiceVLANConf 1 }

sisgm1040284lrtVoiceVLANVLANId OBJECT-TYPE
   SYNTAX      Integer32 (1..4094)
   MAX-ACCESS  read-write
   STATUS      current
   DESCRIPTION
       "Voice VLAN ID.
        default: 1000,
        range : 1-4094. "
   ::= { sisgm1040284lrtVoiceVLANConf 2 }

sisgm1040284lrtVoiceVLANAgingTime OBJECT-TYPE
   SYNTAX      Integer32 (10..10000000)
   MAX-ACCESS  read-write
   STATUS      current
   DESCRIPTION
       " Voice VLAN secure learning aging time.
         default: 86400,
         range : 10 - 10000000. "
   ::= { sisgm1040284lrtVoiceVLANConf 3 }

sisgm1040284lrtVoiceVLANTrafficClass OBJECT-TYPE
   SYNTAX      Integer32 (0..7)
   MAX-ACCESS  read-write
   STATUS      current
   DESCRIPTION
       " Voice VLAN traffic class, all traffic on the Voice VLAN
         will apply this class, available value is from 0(Low)
         to 7(High).
         default: 7. "
   ::= { sisgm1040284lrtVoiceVLANConf 4 }


sisgm1040284lrtVoiceVLANPortTable OBJECT-TYPE
   SYNTAX      SEQUENCE OF SISGM1040284LRTVoiceVLANPortEntry
   MAX-ACCESS  not-accessible
   STATUS      current
   DESCRIPTION
       " Show Voice Vlan configuration. "
   ::= { sisgm1040284lrtVoiceVLANConf 5 }

sisgm1040284lrtVoiceVLANPortEntry OBJECT-TYPE
   SYNTAX      SISGM1040284LRTVoiceVLANPortEntry
   MAX-ACCESS  not-accessible
   STATUS      current
   DESCRIPTION
       " "
   INDEX    { sisgm1040284lrtVoiceVLANPort  }
   ::= { sisgm1040284lrtVoiceVLANPortTable 1 }

SISGM1040284LRTVoiceVLANPortEntry ::= SEQUENCE {
   sisgm1040284lrtVoiceVLANPort                    Integer32,
   sisgm1040284lrtVoiceVLANPortMode                Integer32,
   sisgm1040284lrtVoiceVLANPortSecurity            Integer32,
   sisgm1040284lrtVoiceVLANPortDiscoveryProtocol   Integer32
}

sisgm1040284lrtVoiceVLANPort OBJECT-TYPE
   SYNTAX      Integer32 (1..4095)
   MAX-ACCESS  not-accessible
   STATUS      current
   DESCRIPTION
       " port, range : 1 - port number. "
   ::= { sisgm1040284lrtVoiceVLANPortEntry 1 }

sisgm1040284lrtVoiceVLANPortMode OBJECT-TYPE
   SYNTAX      Integer32 (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { sisgm1040284lrtVoiceVLANPortEntry 2 }

sisgm1040284lrtVoiceVLANPortSecurity OBJECT-TYPE
   SYNTAX      Integer32 (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { sisgm1040284lrtVoiceVLANPortEntry 3 }

sisgm1040284lrtVoiceVLANPortDiscoveryProtocol OBJECT-TYPE
   SYNTAX      Integer32 (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { sisgm1040284lrtVoiceVLANPortEntry 4 }


sisgm1040284lrtVoiceVLANOUI                                          OBJECT IDENTIFIER ::= { sisgm1040284lrtVoiceVLAN 2 }

sisgm1040284lrtVoiceVLANOUICreate OBJECT-TYPE
   SYNTAX       Integer32(0|1)
   MAX-ACCESS   read-write
   STATUS       current
   DESCRIPTION
       "default: 0
        0 : None  (read only)
        1 : Create an OUI entry"
   ::= { sisgm1040284lrtVoiceVLANOUI 1 }

sisgm1040284lrtVoiceVLANOUITable OBJECT-TYPE
   SYNTAX      SEQUENCE OF SISGM1040284LRTVoiceVLANOUIEntry
   MAX-ACCESS  not-accessible
   STATUS      current
   DESCRIPTION
       " Create Voice VLAN OUI entry. Modify OUI table will
         restart auto detect OUI process. "
   ::= { sisgm1040284lrtVoiceVLANOUI 2 }

sisgm1040284lrtVoiceVLANOUIEntry OBJECT-TYPE
   SYNTAX      SISGM1040284LRTVoiceVLANOUIEntry
   MAX-ACCESS  not-accessible
   STATUS      current
   DESCRIPTION
       " "
   INDEX    { sisgm1040284lrtVoiceVLANOUIIndex  }
   ::= { sisgm1040284lrtVoiceVLANOUITable 1 }

SISGM1040284LRTVoiceVLANOUIEntry ::= SEQUENCE {
   sisgm1040284lrtVoiceVLANOUIIndex         Integer32,
   sisgm1040284lrtVoiceVLANTelephonyOUI     DisplayString,
   sisgm1040284lrtVoiceVLANDescription      DisplayString,
   sisgm1040284lrtVoiceVLANOUIRowStatus     Integer32
}

sisgm1040284lrtVoiceVLANOUIIndex OBJECT-TYPE
   SYNTAX      Integer32 (1..16)
   MAX-ACCESS  not-accessible
   STATUS      current
   DESCRIPTION
       " "
   ::= { sisgm1040284lrtVoiceVLANOUIEntry 1 }

sisgm1040284lrtVoiceVLANTelephonyOUI OBJECT-TYPE
   SYNTAX      DisplayString (SIZE (1..32))
   MAX-ACCESS  read-write
   STATUS      current
   DESCRIPTION
       "OUI address, format : 0a 1b 2c "
   ::= { sisgm1040284lrtVoiceVLANOUIEntry 2 }

sisgm1040284lrtVoiceVLANDescription OBJECT-TYPE
   SYNTAX      DisplayString (SIZE (1..32))
   MAX-ACCESS  read-write
   STATUS      current
   DESCRIPTION
       " Up to 32 characters describing OUI address. "
   ::= { sisgm1040284lrtVoiceVLANOUIEntry 3 }

sisgm1040284lrtVoiceVLANOUIRowStatus OBJECT-TYPE
   SYNTAX      Integer32 (1..5)
   MAX-ACCESS  read-write
   STATUS      current
   DESCRIPTION
       "1: active
        2: notInservice
        4: destroy
        5: undo"
   ::= { sisgm1040284lrtVoiceVLANOUIEntry 4 }

--sisgm1040284lrtGARP                                                   OBJECT IDENTIFIER ::= { sisgm1040284lrtConfiguration 3 }

--sisgm1040284lrtGARPConfTable OBJECT-TYPE
--   SYNTAX      SEQUENCE OF SISGM1040284LRTGARPConfEntry
--   MAX-ACCESS  not-accessible
--   STATUS      current
--   DESCRIPTION
--       " "
--   ::= { sisgm1040284lrtGARP 1 }

--sisgm1040284lrtGARPConfEntry OBJECT-TYPE
--   SYNTAX      SISGM1040284LRTGARPConfEntry
--   MAX-ACCESS  not-accessible
--   STATUS      current
--   DESCRIPTION
--       " "
--   INDEX    { sisgm1040284lrtGARPConfPort  }
--   ::= { sisgm1040284lrtGARPConfTable 1 }

--SISGM1040284LRTGARPConfEntry ::= SEQUENCE {
--   sisgm1040284lrtGARPConfPort           Integer32,
--   sisgm1040284lrtGARPJoinTimer          Integer32,
--   sisgm1040284lrtGARPLeaveTimer         Integer32,
--   sisgm1040284lrtGARPLeaveAllTimer      Integer32,
--   sisgm1040284lrtGARPApplicantion       Integer32,
--   sisgm1040284lrtGARPAttributeType      Integer32,
--   sisgm1040284lrtGARPApplicant          Integer32
--}

--sisgm1040284lrtGARPConfPort OBJECT-TYPE
--   SYNTAX      Integer32 (1..4095)
--   MAX-ACCESS  not-accessible
--   STATUS      current
--   DESCRIPTION
--       " "
--   ::= { sisgm1040284lrtGARPConfEntry 1 }

--sisgm1040284lrtGARPJoinTimer OBJECT-TYPE
--   SYNTAX      Integer32 (200..1000)
--   MAX-ACCESS  read-write
--   STATUS      current
--   DESCRIPTION
--       "default: 200, range : 200 - 1000 "
--   ::= { sisgm1040284lrtGARPConfEntry 2 }

--sisgm1040284lrtGARPLeaveTimer OBJECT-TYPE
--   SYNTAX      Integer32 (600..3000)
--   MAX-ACCESS  read-write
--   STATUS      current
--   DESCRIPTION
--       "default: 600 , range : 600 - 3000"
--   ::= { sisgm1040284lrtGARPConfEntry 3 }

--sisgm1040284lrtGARPLeaveAllTimer OBJECT-TYPE
--   SYNTAX      Integer32 (10000..50000)
--   MAX-ACCESS  read-write
--   STATUS      current
--   DESCRIPTION
--       "default: 10000, range : 10000 - 50000 "
--   ::= { sisgm1040284lrtGARPConfEntry 4 }

--sisgm1040284lrtGARPApplicantion OBJECT-TYPE
--   SYNTAX      Integer32(1)
--   MAX-ACCESS  read-write
--   STATUS      current
--   DESCRIPTION
--       "default: 1
--       1: GVRP"
--   ::= { sisgm1040284lrtGARPConfEntry 5 }

--sisgm1040284lrtGARPAttributeType OBJECT-TYPE
--   SYNTAX      Integer32(1)
--   MAX-ACCESS  read-write
--   STATUS      current
--   DESCRIPTION
--       "default: 1
--       1: VLAN"
--   ::= { sisgm1040284lrtGARPConfEntry 6 }

--sisgm1040284lrtGARPApplicant OBJECT-TYPE
--   SYNTAX      Integer32(0|1)
--   MAX-ACCESS  read-write
--   STATUS      current
--   DESCRIPTION
--       "default: 0
--       0: normal-participant
--       1: non-participant"
--   ::= { sisgm1040284lrtGARPConfEntry 7 }

--sisgm1040284lrtGARPStatisticsTable OBJECT-TYPE
--   SYNTAX      SEQUENCE OF SISGM1040284LRTGARPStatisticsEntry
--   MAX-ACCESS  not-accessible
--   STATUS      current
--   DESCRIPTION
--       " Show the basic GARP port statistics. "
--   ::= { sisgm1040284lrtGARP 2 }

--sisgm1040284lrtGARPStatisticsEntry OBJECT-TYPE
--   SYNTAX      SISGM1040284LRTGARPStatisticsEntry
--   MAX-ACCESS  not-accessible
--   STATUS      current
--   DESCRIPTION
--       " "
--   INDEX    { sisgm1040284lrtGARPStatisticsPort  }
--   ::= { sisgm1040284lrtGARPStatisticsTable 1 }

--SISGM1040284LRTGARPStatisticsEntry ::= SEQUENCE {
--   sisgm1040284lrtGARPStatisticsPort             Integer32,
--   sisgm1040284lrtGARPStatisticsPeerMAC          DisplayString,
--   sisgm1040284lrtGARPStatisticsFailedCount      Counter32
--}

--sisgm1040284lrtGARPStatisticsPort OBJECT-TYPE
--   SYNTAX      Integer32 (1..4095)
--   MAX-ACCESS  not-accessible
--   STATUS      current
--   DESCRIPTION
--       " port, range : 1 - port number. "
--   ::= { sisgm1040284lrtGARPStatisticsEntry 1 }

--sisgm1040284lrtGARPStatisticsPeerMAC OBJECT-TYPE
--   SYNTAX      DisplayString
--   MAX-ACCESS  read-only
--   STATUS      current
--   DESCRIPTION
--       " Peer MAC is MAC address of the neighbour Switch from with GARP frame is received.  "
--   ::= { sisgm1040284lrtGARPStatisticsEntry 2 }

--sisgm1040284lrtGARPStatisticsFailedCount OBJECT-TYPE
--   SYNTAX      Counter32
--   MAX-ACCESS  read-only
--   STATUS      current
--   DESCRIPTION
--       " explain Failed count here. "
--   ::= { sisgm1040284lrtGARPStatisticsEntry 3 }

sisgm1040284lrtGVRP                                                   OBJECT IDENTIFIER ::= { sisgm1040284lrtConfiguration 4 }

sisgm1040284lrtGVRPConf                                                   OBJECT IDENTIFIER ::= { sisgm1040284lrtGVRP 1 }

sisgm1040284lrtGVRPMode OBJECT-TYPE
   SYNTAX      Integer32(0|1)
   MAX-ACCESS  read-write
   STATUS      current
   DESCRIPTION
       "default: 0,
        0: disable,
        1: enable. "
   ::= { sisgm1040284lrtGVRPConf 1 }

sisgm1040284lrtGVRPMaxVlan OBJECT-TYPE
   SYNTAX      Integer32(1..4095)
   MAX-ACCESS  read-write
   STATUS      current
   DESCRIPTION
       "Number of simultaniously VLANs that GVRP can control. "
   ::= { sisgm1040284lrtGVRPConf 2 }

sisgm1040284lrtGVRPJoinTime OBJECT-TYPE
   SYNTAX      Integer32(1..20)
   MAX-ACCESS  read-write
   STATUS      current
   DESCRIPTION
       "join-time in units of centi seconds. Range is 1-20. Default is 20. "
   ::= { sisgm1040284lrtGVRPConf 3 }

sisgm1040284lrtGVRPLeaveTime OBJECT-TYPE
   SYNTAX      Integer32(60..300)
   MAX-ACCESS  read-write
   STATUS      current
   DESCRIPTION
       "leave-time in units of centi seconds. Range is 60-300. Default is 60. "
   ::= { sisgm1040284lrtGVRPConf 4 }

sisgm1040284lrtGVRPLeaveAllTime OBJECT-TYPE
   SYNTAX      Integer32(1000..5000)
   MAX-ACCESS  read-write
   STATUS      current
   DESCRIPTION
       "leave-all-time in units of centi seconds Range is 1000-5000. Default is 1000"
   ::= { sisgm1040284lrtGVRPConf 5 }

sisgm1040284lrtGVRPConfTable OBJECT-TYPE
   SYNTAX      SEQUENCE OF SISGM1040284LRTGVRPConfEntry
   MAX-ACCESS  not-accessible
   STATUS      current
   DESCRIPTION
       " "
   ::= { sisgm1040284lrtGVRPConf 6 }

sisgm1040284lrtGVRPConfEntry OBJECT-TYPE
   SYNTAX      SISGM1040284LRTGVRPConfEntry
   MAX-ACCESS  not-accessible
   STATUS      current
   DESCRIPTION
       " "
   INDEX    { sisgm1040284lrtGVRPConfPort  }
   ::= { sisgm1040284lrtGVRPConfTable 1 }

SISGM1040284LRTGVRPConfEntry ::= SEQUENCE {
   sisgm1040284lrtGVRPConfPort           Integer32,
   sisgm1040284lrtGVRPConfPortMode       Integer32
-- sisgm1040284lrtGVRPConfPortRRole      Integer32
}

sisgm1040284lrtGVRPConfPort OBJECT-TYPE
   SYNTAX      Integer32 (1..4095)
   MAX-ACCESS  not-accessible
   STATUS      current
   DESCRIPTION
       " "
   ::= { sisgm1040284lrtGVRPConfEntry 1 }

sisgm1040284lrtGVRPConfPortMode OBJECT-TYPE
   SYNTAX      Integer32(0|1)
   MAX-ACCESS  read-write
   STATUS      current
   DESCRIPTION
       "default: 0
       1: enable
       0: disable"
   ::= { sisgm1040284lrtGVRPConfEntry 2 }

--sisgm1040284lrtGVRPConfPortRRole OBJECT-TYPE
--   SYNTAX      Integer32(0|1)
--   MAX-ACCESS  read-write
--   STATUS      current
--   DESCRIPTION
--       "default: 0
--       1: enable
--       0: disable"
--   ::= { sisgm1040284lrtGVRPConfEntry 3 }

--sisgm1040284lrtGVRPStatisticsTable OBJECT-TYPE
--   SYNTAX      SEQUENCE OF SISGM1040284LRTGVRPStatisticsEntry
--   MAX-ACCESS  not-accessible
--   STATUS      current
--   DESCRIPTION
--       " "
--   ::= { sisgm1040284lrtGVRP 2 }

--sisgm1040284lrtGVRPStatisticsEntry OBJECT-TYPE
--   SYNTAX      SISGM1040284LRTGVRPStatisticsEntry
--   MAX-ACCESS  not-accessible
--   STATUS      current
--   DESCRIPTION
--       " "
--   INDEX    { sisgm1040284lrtGVRPStatisticsPort  }
--   ::= { sisgm1040284lrtGVRPStatisticsTable 1 }

--SISGM1040284LRTGVRPStatisticsEntry ::= SEQUENCE {
--   sisgm1040284lrtGVRPStatisticsPort         Integer32,
--   sisgm1040284lrtGVRPStatisticsJoinTxCnt    Counter32,
--   sisgm1040284lrtGVRPStatisticsLeaveTxCnt   Counter32
--}

--sisgm1040284lrtGVRPStatisticsPort OBJECT-TYPE
--   SYNTAX      Integer32 (1..4095)
--   MAX-ACCESS  not-accessible
--   STATUS      current
--   DESCRIPTION
--       " "
--   ::= { sisgm1040284lrtGVRPStatisticsEntry 1 }

--sisgm1040284lrtGVRPStatisticsJoinTxCnt OBJECT-TYPE
--   SYNTAX      Counter32
--   MAX-ACCESS  read-only
--   STATUS      current
--   DESCRIPTION
--       " "
--   ::= { sisgm1040284lrtGVRPStatisticsEntry 2 }

--sisgm1040284lrtGVRPStatisticsLeaveTxCnt OBJECT-TYPE
--   SYNTAX      Counter32
--   MAX-ACCESS  read-only
--   STATUS      current
--   DESCRIPTION
--       " "
--   ::= { sisgm1040284lrtGVRPStatisticsEntry 3 }


sisgm1040284lrtMirroring                                             OBJECT IDENTIFIER ::= { sisgm1040284lrtConfiguration 6 }

--sisgm1040284lrtPortToMirrorOn OBJECT-TYPE
--   SYNTAX      Integer32(0..10)
--   MAX-ACCESS  read-write
--   STATUS      current
--   DESCRIPTION
--       "default: 0
--        0: disable,
--        range : 1 - port number. "
--   ::= { sisgm1040284lrtMirroring 2 }
--
--sisgm1040284lrtMirrorTable OBJECT-TYPE
--   SYNTAX      SEQUENCE OF SISGM1040284LRTMirrorEntry
--   MAX-ACCESS  not-accessible
--   STATUS      current
--   DESCRIPTION
--       " "
--   ::= { sisgm1040284lrtMirroring 3 }
--
--sisgm1040284lrtMirrorEntry OBJECT-TYPE
--   SYNTAX      SISGM1040284LRTMirrorEntry
--   MAX-ACCESS  not-accessible
--   STATUS      current
--   DESCRIPTION
--       " "
--   INDEX    { sisgm1040284lrtMirrorPort  }
--   ::= { sisgm1040284lrtMirrorTable 1 }
--
--SISGM1040284LRTMirrorEntry ::= SEQUENCE {
--   sisgm1040284lrtMirrorPort		Integer32,
--   sisgm1040284lrtMirrorMode		Integer32
--}
--
--sisgm1040284lrtMirrorPort OBJECT-TYPE
--   SYNTAX      Integer32 (1..4095)
--   MAX-ACCESS  not-accessible
--   STATUS      current
--   DESCRIPTION
--       " "
--   ::= { sisgm1040284lrtMirrorEntry 1 }
--
--sisgm1040284lrtMirrorMode OBJECT-TYPE
--   SYNTAX      Integer32(0..3)
--   MAX-ACCESS  read-write
--   STATUS      current
--   DESCRIPTION
--       "default: 0
--       0: disable
--       1: enable
--       2: rx only
--       3: tx only
--       Setting Tx mirroring for analyzer port has no effect. Tx mirroring ignored"
--   ::= { sisgm1040284lrtMirrorEntry 2 }

sisgm1040284lrtRMirrorMode OBJECT-TYPE
   SYNTAX      Integer32(0|1)
   MAX-ACCESS  read-write
   STATUS      current
   DESCRIPTION
       "default: 0
        0: disable,
        1: enable"
   ::= { sisgm1040284lrtMirroring 4 }

sisgm1040284lrtRMirrorType OBJECT-TYPE
   SYNTAX      Integer32(0..3)
   MAX-ACCESS  read-write
   STATUS      current
   DESCRIPTION
       "0: Mirror
        1: Source(RMirror)
        2: Intermediate(RMirror)
        3: Destination(RMirror)"
   ::= { sisgm1040284lrtMirroring 5 }

sisgm1040284lrtRMirrorVLANID OBJECT-TYPE
   SYNTAX      Integer32(1..4095)
   MAX-ACCESS  read-write
   STATUS      current
   DESCRIPTION
       "VLAN ID"
   ::= { sisgm1040284lrtMirroring 6 }

sisgm1040284lrtRMirrorReflectorPort OBJECT-TYPE
   SYNTAX      Integer32(1..4095)
   MAX-ACCESS  read-write
   STATUS      current
   DESCRIPTION
       "Reflector Port range: 1 - port number."
   ::= { sisgm1040284lrtMirroring 7 }
   
sisgm1040284lrtRMirrorSourceVLANs OBJECT-TYPE
   SYNTAX      DisplayString
   MAX-ACCESS  read-write
   STATUS      current
   DESCRIPTION
       "VLAN-based Mirroring."
   ::= { sisgm1040284lrtMirroring 8 }   
   
sisgm1040284lrtRMirrorCPUSource OBJECT-TYPE
   SYNTAX      Integer32(0..3)
   MAX-ACCESS  read-write
   STATUS      current
   DESCRIPTION
       "0: Disable
        1: RX Only
        2: TX Only
        3: Both"
   ::= { sisgm1040284lrtMirroring 9 }
   
sisgm1040284lrtRMirrorTable OBJECT-TYPE
   SYNTAX      SEQUENCE OF SISGM1040284LRTRMirrorEntry
   MAX-ACCESS  not-accessible
   STATUS      current
   DESCRIPTION
       " "
   ::= { sisgm1040284lrtMirroring 12 }

sisgm1040284lrtRMirrorEntry OBJECT-TYPE
   SYNTAX      SISGM1040284LRTRMirrorEntry
   MAX-ACCESS  not-accessible
   STATUS      current
   DESCRIPTION
       " "
   INDEX    { sisgm1040284lrtRMirrorPort  }
   ::= { sisgm1040284lrtRMirrorTable 1 }

SISGM1040284LRTRMirrorEntry ::= SEQUENCE {
   sisgm1040284lrtRMirrorPort             Integer32,
   sisgm1040284lrtRMirrorPortSource       Integer32,
   sisgm1040284lrtRMirrorPortIntermediate Integer32,
   sisgm1040284lrtRMirrorPortDestination  Integer32
}

sisgm1040284lrtRMirrorPort OBJECT-TYPE
   SYNTAX      Integer32
   MAX-ACCESS  not-accessible
   STATUS      current
   DESCRIPTION
       " "
   ::= { sisgm1040284lrtRMirrorEntry 1 }

sisgm1040284lrtRMirrorPortSource OBJECT-TYPE
   SYNTAX      Integer32(0..3)
   MAX-ACCESS  read-write
   STATUS      current
   DESCRIPTION
       "0: Disable
        1: RX Only
        2: TX Only
        3: Both"
   ::= { sisgm1040284lrtRMirrorEntry 2 }

sisgm1040284lrtRMirrorPortIntermediate OBJECT-TYPE
   SYNTAX      Integer32(0|1)
   MAX-ACCESS  read-write
   STATUS      current
   DESCRIPTION
       "0: disable,
        1: enable"
   ::= { sisgm1040284lrtRMirrorEntry 3 }

sisgm1040284lrtRMirrorPortDestination OBJECT-TYPE
   SYNTAX      Integer32(0|1)
   MAX-ACCESS  read-write
   STATUS      current
   DESCRIPTION
       "0: disable,
        1: enable"
   ::= { sisgm1040284lrtRMirrorEntry 4 }


sisgm1040284lrtTrapEventSeverity                                             OBJECT IDENTIFIER ::= { sisgm1040284lrtConfiguration 7 }

sisgm1040284lrtTrapEventSeverityTable OBJECT-TYPE
   SYNTAX      SEQUENCE OF SISGM1040284LRTTrapEventSeverityEntry
   MAX-ACCESS  not-accessible
   STATUS      current
   DESCRIPTION
       " "
   ::= { sisgm1040284lrtTrapEventSeverity 1 }

sisgm1040284lrtTrapEventSeverityEntry OBJECT-TYPE
   SYNTAX      SISGM1040284LRTTrapEventSeverityEntry
   MAX-ACCESS  not-accessible
   STATUS      current
   DESCRIPTION
       " "
   INDEX    { sisgm1040284lrtTrapEventSeverityIndex }
   ::= { sisgm1040284lrtTrapEventSeverityTable 1 }

SISGM1040284LRTTrapEventSeverityEntry ::= SEQUENCE {
   sisgm1040284lrtTrapEventSeverityIndex        Integer32,
   sisgm1040284lrtTrapEventSeverityGroupName    DisplayString,
   sisgm1040284lrtTrapEventSeverityLevel        Integer32,
   sisgm1040284lrtTrapEventSeveritySyslog       Integer32,
   sisgm1040284lrtTrapEventSeverityTrap         Integer32,
   sisgm1040284lrtTrapEventSeveritySMTP         Integer32,
   sisgm1040284lrtTrapEventSeveritySwitch2go    Integer32,
   sisgm1040284lrtTrapEventSeverityDigitalOut   Integer32
}

sisgm1040284lrtTrapEventSeverityIndex OBJECT-TYPE
   SYNTAX      Integer32
   MAX-ACCESS  not-accessible
   STATUS      current
   DESCRIPTION
       " "
   ::= { sisgm1040284lrtTrapEventSeverityEntry 1 }

sisgm1040284lrtTrapEventSeverityGroupName OBJECT-TYPE
   SYNTAX      DisplayString
   MAX-ACCESS  read-only
   STATUS      current
   DESCRIPTION
       "Group Name"
   ::= { sisgm1040284lrtTrapEventSeverityEntry 2 }

sisgm1040284lrtTrapEventSeverityLevel OBJECT-TYPE
   SYNTAX      Integer32
   MAX-ACCESS  not-accessible
   STATUS      current
   DESCRIPTION
       "0:Emergency
       1:Alert
       2:Critical
       3:Error
       4:Warning
       5:Notice
       6:Information
       7:Debug"
   ::= { sisgm1040284lrtTrapEventSeverityEntry 3 }

sisgm1040284lrtTrapEventSeveritySyslog OBJECT-TYPE
   SYNTAX      Integer32
   MAX-ACCESS  not-accessible
   STATUS      current
   DESCRIPTION
       "0:disable
       1:enable"
   ::= { sisgm1040284lrtTrapEventSeverityEntry 4 }

sisgm1040284lrtTrapEventSeverityTrap OBJECT-TYPE
   SYNTAX      Integer32
   MAX-ACCESS  not-accessible
   STATUS      current
   DESCRIPTION
       "0:disable
       1:enable"
   ::= { sisgm1040284lrtTrapEventSeverityEntry 5 }

sisgm1040284lrtTrapEventSeveritySMTP OBJECT-TYPE
   SYNTAX      Integer32
   MAX-ACCESS  not-accessible
   STATUS      current
   DESCRIPTION
       "0:disable
       1:enable"
   ::= { sisgm1040284lrtTrapEventSeverityEntry 6 }

sisgm1040284lrtTrapEventSeveritySwitch2go OBJECT-TYPE
   SYNTAX      Integer32
   MAX-ACCESS  not-accessible
   STATUS      current
   DESCRIPTION
       "0:disable
       1:enable"
   ::= { sisgm1040284lrtTrapEventSeverityEntry 7 }
   
sisgm1040284lrtTrapEventSeverityDigitalOut OBJECT-TYPE
   SYNTAX      Integer32
   MAX-ACCESS  not-accessible
   STATUS      current
   DESCRIPTION
       "0:disable
       1:enable
	   -1:not support"
   ::= { sisgm1040284lrtTrapEventSeverityEntry 8 }   


sisgm1040284lrtPortEventSettingTable OBJECT-TYPE
   SYNTAX      SEQUENCE OF SISGM1040284LRTPortEventSettingEntry
   MAX-ACCESS  not-accessible
   STATUS      current
   DESCRIPTION
       " "
   ::= { sisgm1040284lrtTrapEventSeverity 2 }

sisgm1040284lrtPortEventSettingEntry OBJECT-TYPE
   SYNTAX      SISGM1040284LRTPortEventSettingEntry
   MAX-ACCESS  not-accessible
   STATUS      current
   DESCRIPTION
       " "
   INDEX    { sisgm1040284lrtPortEventSettingIndex }
   ::= { sisgm1040284lrtPortEventSettingTable 1 }

SISGM1040284LRTPortEventSettingEntry ::= SEQUENCE {
   sisgm1040284lrtPortEventSettingIndex           Integer32,
   sisgm1040284lrtPortEventSettingActive          Integer32,
   sisgm1040284lrtPortEventSettingLinkOn          Integer32,
   sisgm1040284lrtPortEventSettingLinkOff         Integer32,
   sisgm1040284lrtPortEventSettingOverload        Integer32,
   sisgm1040284lrtPortEventSettingThreshold       Integer32,
   sisgm1040284lrtPortEventSettingTrafficDuration Integer32,
   sisgm1040284lrtPortEventSettingSyslog          Integer32,
   sisgm1040284lrtPortEventSettingTrap            Integer32,
   sisgm1040284lrtPortEventSettingSmtp            Integer32,
   sisgm1040284lrtPortEventSettingSwitch2go       Integer32,
   sisgm1040284lrtPortEventSettingDigitialout     Integer32,
   sisgm1040284lrtPortEventSettingSeverity        Integer32
}

sisgm1040284lrtPortEventSettingIndex OBJECT-TYPE
   SYNTAX      Integer32
   MAX-ACCESS  not-accessible
   STATUS      current
   DESCRIPTION
       " "
   ::= { sisgm1040284lrtPortEventSettingEntry 1 }

sisgm1040284lrtPortEventSettingActive OBJECT-TYPE
   SYNTAX      Integer32
   MAX-ACCESS  not-accessible
   STATUS      current
   DESCRIPTION
       "0:disable
       1:enable"
   ::= { sisgm1040284lrtPortEventSettingEntry 2}   
   
sisgm1040284lrtPortEventSettingLinkOn OBJECT-TYPE
   SYNTAX      Integer32
   MAX-ACCESS  not-accessible
   STATUS      current
   DESCRIPTION
       "0:disable
       1:enable"
   ::= { sisgm1040284lrtPortEventSettingEntry 3}      
   
sisgm1040284lrtPortEventSettingLinkOff OBJECT-TYPE
   SYNTAX      Integer32
   MAX-ACCESS  not-accessible
   STATUS      current
   DESCRIPTION
       "0:disable
       1:enable"
   ::= { sisgm1040284lrtPortEventSettingEntry 4}     
   
sisgm1040284lrtPortEventSettingOverload OBJECT-TYPE
   SYNTAX      Integer32
   MAX-ACCESS  not-accessible
   STATUS      current
   DESCRIPTION
       "0:disable
       1:enable"
   ::= { sisgm1040284lrtPortEventSettingEntry 5}    
 
sisgm1040284lrtPortEventSettingThreshold OBJECT-TYPE
   SYNTAX      Integer32
   MAX-ACCESS  not-accessible
   STATUS      current
   DESCRIPTION
       "Range:0-100"
   ::= { sisgm1040284lrtPortEventSettingEntry 6} 
 
sisgm1040284lrtPortEventSettingTrafficDuration OBJECT-TYPE
   SYNTAX      Integer32
   MAX-ACCESS  not-accessible
   STATUS      current
   DESCRIPTION
       "Range:1-300"
   ::= { sisgm1040284lrtPortEventSettingEntry 7} 
 
sisgm1040284lrtPortEventSettingSyslog OBJECT-TYPE
   SYNTAX      Integer32
   MAX-ACCESS  not-accessible
   STATUS      current
   DESCRIPTION
       "0:disable
       1:enable"
   ::= { sisgm1040284lrtPortEventSettingEntry 8}  

sisgm1040284lrtPortEventSettingTrap OBJECT-TYPE
   SYNTAX      Integer32
   MAX-ACCESS  not-accessible
   STATUS      current
   DESCRIPTION
       "0:disable
       1:enable"
   ::= { sisgm1040284lrtPortEventSettingEntry 9}  

sisgm1040284lrtPortEventSettingSmtp OBJECT-TYPE
   SYNTAX      Integer32
   MAX-ACCESS  not-accessible
   STATUS      current
   DESCRIPTION
       "0:disable
       1:enable"
   ::= { sisgm1040284lrtPortEventSettingEntry 10} 
   
sisgm1040284lrtPortEventSettingSwitch2go OBJECT-TYPE
   SYNTAX      Integer32
   MAX-ACCESS  not-accessible
   STATUS      current
   DESCRIPTION
       "0:disable
       1:enable"
   ::= { sisgm1040284lrtPortEventSettingEntry 11}    
 
sisgm1040284lrtPortEventSettingDigitialout OBJECT-TYPE
   SYNTAX      Integer32
   MAX-ACCESS  not-accessible
   STATUS      current
   DESCRIPTION
       "0:disable
       1:enable"
   ::= { sisgm1040284lrtPortEventSettingEntry 12}   
   
sisgm1040284lrtPortEventSettingSeverity OBJECT-TYPE
   SYNTAX      Integer32
   MAX-ACCESS  not-accessible
   STATUS      current
   DESCRIPTION
       "0:Emergency
       1:Alert
       2:Critical
       3:Error
       4:Warning
       5:Notice
       6:Information
       7:Debug"
   ::= { sisgm1040284lrtPortEventSettingEntry 13 }

-- =======================================================================================================================
sisgm1040284lrtSMTP                                             OBJECT IDENTIFIER ::= { sisgm1040284lrtConfiguration 8 }

sisgm1040284lrtSMTPMailServer OBJECT-TYPE
   SYNTAX      DisplayString
   MAX-ACCESS  read-write
   STATUS      current
   DESCRIPTION
       " Up to 47 characters describing email server. "
   ::= { sisgm1040284lrtSMTP 1 }

sisgm1040284lrtSMTPUserName OBJECT-TYPE
   SYNTAX      DisplayString
   MAX-ACCESS  read-write
   STATUS      current
   DESCRIPTION
       " Up to 47 characters describing user name. "
   ::= { sisgm1040284lrtSMTP 2 }

sisgm1040284lrtSMTPPassword OBJECT-TYPE
   SYNTAX      DisplayString
   MAX-ACCESS  read-write
   STATUS      current
   DESCRIPTION
       " Up to 47 characters describing password. "
   ::= { sisgm1040284lrtSMTP 3 }

sisgm1040284lrtSMTPSender OBJECT-TYPE
   SYNTAX      DisplayString
   MAX-ACCESS  read-write
   STATUS      current
   DESCRIPTION
       " Up to 47 characters describing sender. "
   ::= { sisgm1040284lrtSMTP 5 }

sisgm1040284lrtSMTPReturnPath OBJECT-TYPE
   SYNTAX      DisplayString
   MAX-ACCESS  read-write
   STATUS      current
   DESCRIPTION
       " Up to 47 characters describing return path. "
   ::= { sisgm1040284lrtSMTP 6 }

sisgm1040284lrtSMTPEmailAddress1 OBJECT-TYPE
   SYNTAX      DisplayString
   MAX-ACCESS  read-write
   STATUS      current
   DESCRIPTION
       " Up to 47 characters describing mail address. "
   ::= { sisgm1040284lrtSMTP 7 }

sisgm1040284lrtSMTPEmailAddress2 OBJECT-TYPE
   SYNTAX      DisplayString
   MAX-ACCESS  read-write
   STATUS      current
   DESCRIPTION
       " Up to 47 characters describing mail address. "
   ::= { sisgm1040284lrtSMTP 8 }

sisgm1040284lrtSMTPEmailAddress3 OBJECT-TYPE
   SYNTAX      DisplayString
   MAX-ACCESS  read-write
   STATUS      current
   DESCRIPTION
       " Up to 47 characters describing mail address. "
   ::= { sisgm1040284lrtSMTP 9 }

sisgm1040284lrtSMTPEmailAddress4 OBJECT-TYPE
   SYNTAX      DisplayString
   MAX-ACCESS  read-write
   STATUS      current
   DESCRIPTION
       " Up to 47 characters describing mail address. "
   ::= { sisgm1040284lrtSMTP 10 }

sisgm1040284lrtSMTPEmailAddress5 OBJECT-TYPE
   SYNTAX      DisplayString
   MAX-ACCESS  read-write
   STATUS      current
   DESCRIPTION
       " Up to 47 characters describing mail address. "
   ::= { sisgm1040284lrtSMTP 11 }

sisgm1040284lrtSMTPEmailAddress6 OBJECT-TYPE
   SYNTAX      DisplayString
   MAX-ACCESS  read-write
   STATUS      current
   DESCRIPTION
       " Up to 47 characters describing mail address. "
   ::= { sisgm1040284lrtSMTP 12 }

-- =======================================================================================================================
sisgm1040284lrtACLConf                                              OBJECT IDENTIFIER ::= { sisgm1040284lrtConfiguration 9 }

-- RowStatus Info:  createAndGo, notReady not supported.
-- =======================================================================================================================
-- Textual Conventions for the sisgm1040284lrt Acl Mib
-- =======================================================================================================================
--
    sisgm1040284lrtACL                     OBJECT IDENTIFIER  ::= { sisgm1040284lrtACLConf 1 }
    sisgm1040284lrtACLACE                  OBJECT IDENTIFIER  ::= { sisgm1040284lrtACLConf 3 }

--
-- =======================================================================================================================
-- Start sisgm1040284lrtACLPortConf group
-- =======================================================================================================================
--sisgm1040284lrtACLPortConfTable

    sisgm1040284lrtACLPortConfTable OBJECT-TYPE
               SYNTAX      SEQUENCE OF     SISGM1040284LRTACLPortConfEntry
               MAX-ACCESS  not-accessible
               STATUS      current
               DESCRIPTION
                   "The ACL Port Conf Table.
                    INDEX for this table is ifIndex which is
                    equivalent to the panel port number."
               ::= {     sisgm1040284lrtACL 1 }

    sisgm1040284lrtACLPortConfEntry OBJECT-TYPE
               SYNTAX          SISGM1040284LRTACLPortConfEntry
               MAX-ACCESS  not-accessible
               STATUS      current
               DESCRIPTION
                   "The ACL Port Conf Entry. "
               INDEX    {     ifIndex  }
               ::= {     sisgm1040284lrtACLPortConfTable 1 }

    SISGM1040284LRTACLPortConfEntry             ::=
            SEQUENCE {
                 sisgm1040284lrtACLPortConfPolicyID        Integer32,
                 sisgm1040284lrtACLPortConfAction          INTEGER,
                 sisgm1040284lrtACLPortConfRateLimiterID   Integer32,
                 sisgm1040284lrtACLPortConfPortRedirect    Integer32,
                 sisgm1040284lrtACLPortConfMirror          AdminMode,
                 sisgm1040284lrtACLPortConfLogging         AdminMode,
                 sisgm1040284lrtACLPortConfShutdown        AdminMode,
                 sisgm1040284lrtACLPortConfState           AdminMode,
                 sisgm1040284lrtACLPortConfCounter         Counter32
                 }

    sisgm1040284lrtACLPortConfPolicyID OBJECT-TYPE
               SYNTAX       Integer32 (0..63)
               MAX-ACCESS   read-write
               STATUS       current
               DESCRIPTION
                   "The policy to apply to this port.
                    default: 0, range : 0 - 63. "
               ::= {     sisgm1040284lrtACLPortConfEntry 2 }

    sisgm1040284lrtACLPortConfAction OBJECT-TYPE
               SYNTAX      INTEGER { deny(0), permit(1) }
               MAX-ACCESS  read-write
               STATUS      current
               DESCRIPTION
                   "Whether forwarding is permitted ('Permit') or denied ('Deny').
                    default: 1,
                    0: Deny,
                    1: Permit."
               ::= {     sisgm1040284lrtACLPortConfEntry 3 }

    sisgm1040284lrtACLPortConfRateLimiterID OBJECT-TYPE
               SYNTAX      Integer32 (0..16)
               MAX-ACCESS  read-write
               STATUS      current
               DESCRIPTION
                   "The rate limiter to apply on this port.
                    0: Disable,
                    range : 0 - 16. "
               ::= {     sisgm1040284lrtACLPortConfEntry 4 }

    sisgm1040284lrtACLPortConfPortRedirect OBJECT-TYPE
               SYNTAX      Integer32 (0..4095)
               MAX-ACCESS  read-write
               STATUS      current
               DESCRIPTION
                   "Port frames are redirected on.
                    0: Disable,
                    range : 0 - end port number. "
               ::= {     sisgm1040284lrtACLPortConfEntry 5 }

    sisgm1040284lrtACLPortConfMirror OBJECT-TYPE
               SYNTAX      AdminMode
               MAX-ACCESS  read-write
               STATUS      current
               DESCRIPTION
                   "The mirror operation of this port."
               ::= {     sisgm1040284lrtACLPortConfEntry 6 }

    sisgm1040284lrtACLPortConfLogging OBJECT-TYPE
               SYNTAX      AdminMode
               MAX-ACCESS  read-write
               STATUS      current
               DESCRIPTION
                   "Specify the logging operation of this port."
               ::= {     sisgm1040284lrtACLPortConfEntry 7 }

    sisgm1040284lrtACLPortConfShutdown OBJECT-TYPE
               SYNTAX      AdminMode
               MAX-ACCESS  read-write
               STATUS      current
               DESCRIPTION
                   "Specify the port shut down operation of this port."
               DEFVAL  { disable }
               ::= {     sisgm1040284lrtACLPortConfEntry 8 }

    sisgm1040284lrtACLPortConfState OBJECT-TYPE
               SYNTAX      AdminMode
               MAX-ACCESS  read-write
               STATUS      current
               DESCRIPTION
                   "Specify the port state of this port."
               DEFVAL  { enable }
               ::= {     sisgm1040284lrtACLPortConfEntry 9 }

    sisgm1040284lrtACLPortConfCounter OBJECT-TYPE
               SYNTAX      Counter32
               MAX-ACCESS  read-only
               STATUS      current
               DESCRIPTION
                   "Counts the number of frames that match this ACE. "
               ::= {     sisgm1040284lrtACLPortConfEntry 10 }

--
-- =======================================================================================================================
-- Start sisgm1040284lrtACLRateLimiter group
-- =======================================================================================================================
--sisgm1040284lrtACLRateLimiterTable

    sisgm1040284lrtACLRateLimiterTable OBJECT-TYPE
               SYNTAX      SEQUENCE OF     SISGM1040284LRTACLRateLimiterEntry
               MAX-ACCESS  not-accessible
               STATUS      current
               DESCRIPTION
                   "The ACL Rate Limiter Table."
               ::= {     sisgm1040284lrtACL 2 }

    sisgm1040284lrtACLRateLimiterEntry OBJECT-TYPE
               SYNTAX          SISGM1040284LRTACLRateLimiterEntry
               MAX-ACCESS  not-accessible
               STATUS      current
               DESCRIPTION
                   "The ACL Rate Limiter Entry. "
               INDEX    {     sisgm1040284lrtACLRateLimiterID  }
               ::= {     sisgm1040284lrtACLRateLimiterTable 1 }

    SISGM1040284LRTACLRateLimiterEntry             ::= SEQUENCE {
                 sisgm1040284lrtACLRateLimiterID       Integer32,
                 sisgm1040284lrtACLRateLimiterRate     Integer32,
                 sisgm1040284lrtACLRateLimiterUnit     INTEGER
                 }

    sisgm1040284lrtACLRateLimiterID OBJECT-TYPE
               SYNTAX      Integer32 (1..16)
               MAX-ACCESS  not-accessible
               STATUS      current
               DESCRIPTION
                   "Rate Limiter ID.
                    range : 1-16 "
               ::= {     sisgm1040284lrtACLRateLimiterEntry 1 }

    sisgm1040284lrtACLRateLimiterRate OBJECT-TYPE
               SYNTAX      Integer32(0..3276700)
               MAX-ACCESS  read-write
               STATUS      current
               DESCRIPTION
                   "default: 1,
                    range :
                    <0-3276700> pps,The valid rate is 0 - 99, 100, 200, 300,
                    ..., 3276700 in pps.
                    <0-10000> kbps,The valid rate is 0, 100, 200, 300,...,
                    1000000 in kbps."
               ::= {     sisgm1040284lrtACLRateLimiterEntry 2 }

    sisgm1040284lrtACLRateLimiterUnit OBJECT-TYPE
               SYNTAX      INTEGER { pps(0), kbps(1) }
               MAX-ACCESS  read-write
               STATUS      current
               DESCRIPTION
                   "Specify the rate unit.
                    sisgm1040284lrt(e){0: pps, 1: kbps.}
                    sisgm1040284lrt{0: pps}"
               ::= {     sisgm1040284lrtACLRateLimiterEntry 3 }

--
-- =======================================================================================================================
-- Start sisgm1040284lrtACLACE group
-- =======================================================================================================================
--sisgm1040284lrtACLACEClear

    sisgm1040284lrtACLACEClear OBJECT-TYPE
               SYNTAX      ActivateCmd
               MAX-ACCESS  read-write
               STATUS      current
               DESCRIPTION
                   "Clear all ACE counters."
               ::= {     sisgm1040284lrtACLACE 1 }

--sisgm1040284lrtACLACETable

    sisgm1040284lrtACLACETable OBJECT-TYPE
               SYNTAX      SEQUENCE OF     SISGM1040284LRTACLACEEntry
               MAX-ACCESS  not-accessible
               STATUS      current
               DESCRIPTION
                   "Create ACL ACE entry. "
               ::= {     sisgm1040284lrtACLACE 2 }

    sisgm1040284lrtACLACEEntry OBJECT-TYPE
               SYNTAX          SISGM1040284LRTACLACEEntry
               MAX-ACCESS  not-accessible
               STATUS      current
               DESCRIPTION
                   "The ACLACE Table."
               INDEX    {     sisgm1040284lrtACLACEIndex  }
               ::= {     sisgm1040284lrtACLACETable 1 }

    SISGM1040284LRTACLACEEntry             ::= SEQUENCE {
                 sisgm1040284lrtACLACEIndex                Integer32,
                 sisgm1040284lrtACLACEID                   Integer32,
                 sisgm1040284lrtACLACENextID               Integer32,
--               sisgm1040284lrtACLACELoopUp               AdminMode,
                 sisgm1040284lrtACLACEIngressPort          DisplayString,
                 sisgm1040284lrtACLACEPortPolicyNumber     Integer32,
                 sisgm1040284lrtACLACEPortPolicyBitmask    Integer32,
                 sisgm1040284lrtACLACEFrameType            INTEGER,
                 sisgm1040284lrtACLACEAction               INTEGER,
                 sisgm1040284lrtACLACEFilterPort           Integer32,
                 sisgm1040284lrtACLACEDenyPortRedirect     DisplayString,
                 sisgm1040284lrtACLACERateLimiter          Integer32,
                 sisgm1040284lrtACLACEMirror               AdminMode,
                 sisgm1040284lrtACLACELogging              AdminMode,
                 sisgm1040284lrtACLACEShutdown             AdminMode,
                 sisgm1040284lrtACLACECounter              Counter32,
                 sisgm1040284lrtACLACEVLAN8021QTagged      INTEGER,
                 sisgm1040284lrtACLACEVLANVID              Integer32,
                 sisgm1040284lrtACLACEVLANTagPriority      DisplayString,
                 sisgm1040284lrtACLACESMAC                 DisplayString,
                 sisgm1040284lrtACLACEDMACType             INTEGER,
                 sisgm1040284lrtACLACEDMAC                 DisplayString,
                 sisgm1040284lrtACLACEEtherType            Integer32,
                 sisgm1040284lrtACLACEArpOpCode            INTEGER,
                 sisgm1040284lrtACLACEArpFlagsRequestReply INTEGER,
                 sisgm1040284lrtACLACEArpFlagsArpSMac      INTEGER,
                 sisgm1040284lrtACLACEArpFlagsRarpDmac     INTEGER,
                 sisgm1040284lrtACLACEArpFlagsLength       INTEGER,
                 sisgm1040284lrtACLACEArpFlagsIp           INTEGER,
                 sisgm1040284lrtACLACEArpFlagsEthernet     INTEGER,
                 sisgm1040284lrtACLACESIPType              INTEGER,
                 sisgm1040284lrtACLACESIPIPAddress         IpAddress,
                 sisgm1040284lrtACLACESIPIPMask            IpAddress,
                 sisgm1040284lrtACLACEDIPType              INTEGER,
                 sisgm1040284lrtACLACEDIPIPAddress         IpAddress,
                 sisgm1040284lrtACLACEDIPIPMask            IpAddress,
                 sisgm1040284lrtACLACEIPProtocol           INTEGER,
                 sisgm1040284lrtACLACEIPProtocolValue      Integer32,
                 sisgm1040284lrtACLACEIPFlagsTTL           INTEGER,
                 sisgm1040284lrtACLACEIPFlagsFragment      INTEGER,
                 sisgm1040284lrtACLACEIPFlagsOptions       INTEGER,
                 sisgm1040284lrtACLACEICMPType             Integer32,
                 sisgm1040284lrtACLACEICMPCode             Integer32,
                 sisgm1040284lrtACLACESourcePort           DisplayString,
                 sisgm1040284lrtACLACEDestPort             DisplayString,
                 sisgm1040284lrtACLACETCPFlagsFin          INTEGER,
                 sisgm1040284lrtACLACETCPFlagsSyn          INTEGER,
                 sisgm1040284lrtACLACETCPFlagsRst          INTEGER,
                 sisgm1040284lrtACLACETCPFlagsPsh          INTEGER,
                 sisgm1040284lrtACLACETCPFlagsAck          INTEGER,
                 sisgm1040284lrtACLACETCPFlagsUrg          INTEGER,
                 sisgm1040284lrtACLACEIPv6SIPAddress       DisplayString,
                 sisgm1040284lrtACLACEIPv6SIPBitmask       DisplayString,
                 sisgm1040284lrtACLACEIPv6HopLimit         INTEGER,
                 sisgm1040284lrtACLACERowStatus            RowStatus
                 }

    sisgm1040284lrtACLACEIndex OBJECT-TYPE
               SYNTAX      Integer32(1..256)
               MAX-ACCESS  not-accessible
               STATUS      current
               DESCRIPTION
                   "The index. "
               ::= {     sisgm1040284lrtACLACEEntry 1 }

    sisgm1040284lrtACLACEID OBJECT-TYPE
               SYNTAX      Integer32(1..256)
               MAX-ACCESS  read-create
               STATUS      current
               DESCRIPTION
                   "If the ACE ID is specified and an entry with this ACE ID
                    already exists, the ACE will be modified. Otherwise, a
                    new ACE will be added.
                    range : 1 - 256. "
               ::= {     sisgm1040284lrtACLACEEntry 2 }

    sisgm1040284lrtACLACENextID OBJECT-TYPE
               SYNTAX      Integer32 (0..256)
               MAX-ACCESS  read-create
               STATUS      current
               DESCRIPTION
                   "If the next ACE ID is non zero, the ACE will be placed
                    before this ACE in the list. If the next ACE ID is zero,
                    the ACE will be placed last in the list.
                    range : 0 - 256. "
               ::= {     sisgm1040284lrtACLACEEntry 3 }

--    sisgm1040284lrtACLACELoopUp OBJECT-TYPE
--               SYNTAX      AdminMode
--               MAX-ACCESS  read-create
--               STATUS      current
--               DESCRIPTION
--                   "Specify the second lookup operation of the ACE."
--               ::= {     sisgm1040284lrtACLACEEntry 4 }

    sisgm1040284lrtACLACEIngressPort OBJECT-TYPE
               SYNTAX      DisplayString
               MAX-ACCESS  read-create
               STATUS      current
               DESCRIPTION
                   "Indicates the ingress port of the ACE. Possible values are:
                    0: All,The ACE will match all ingress port.
                    Port n: The ACE will match a specific ingress port."
               ::= {     sisgm1040284lrtACLACEEntry 5 }

    sisgm1040284lrtACLACEPortPolicyNumber OBJECT-TYPE
               SYNTAX      Integer32(0..64)
               MAX-ACCESS  read-create
               STATUS      current
               DESCRIPTION
                   "policy value.
                    range : 0 - 64.
                    64: Any. "
               ::= {     sisgm1040284lrtACLACEEntry 6 }

    sisgm1040284lrtACLACEPortPolicyBitmask OBJECT-TYPE
               SYNTAX      Integer32(0..256)
               MAX-ACCESS  read-create
               STATUS      current
               DESCRIPTION
                   "When 'Specific' is selected for the policy filter,
                    you can enter a specific policy bitmask.
                    sisgm1040284lrt{range : 0 - 63(0x3f), 64: no data.}
                    sisgm1040284lrt{range : 0 - 255(0xff), 256: no data.}"
               ::= {     sisgm1040284lrtACLACEEntry 7 }

    sisgm1040284lrtACLACEFrameType OBJECT-TYPE
               SYNTAX      INTEGER {   any(0), etype(1), arp(2),
                                       ipv4(3), ipv6(4) }
               MAX-ACCESS  read-create
               STATUS      current
               DESCRIPTION
                   "Select the frame type for this ACE.
                    When change the type Related oid will set default.
                    0: any,
                    1: etype,
                    2: arp,
                    3: ipv4,
                    4: ipv6."
               ::= {     sisgm1040284lrtACLACEEntry 8 }

    sisgm1040284lrtACLACEAction OBJECT-TYPE
               SYNTAX      INTEGER { deny(0), permit(1), filter(2) }
               MAX-ACCESS  read-create
               STATUS      current
               DESCRIPTION
                   "sisgm1040284lrt{0: Deny,1: Permit,2: Filter, range: 0-2.}
                    sisgm1040284lrt{0: Deny,1: Permit }"
               ::= {     sisgm1040284lrtACLACEEntry 9 }

    sisgm1040284lrtACLACEFilterPort OBJECT-TYPE
               SYNTAX      Integer32(-1..255)
               MAX-ACCESS  read-create
               STATUS      current
               DESCRIPTION
                   "When 'Action' is 'Filter' can set.
                    0: All,
                    Port n: The ACE applies to this port number, where n is
                    the number of the switch port.
                    -1: no data.
                    range: -1 - Port number."
               ::= {     sisgm1040284lrtACLACEEntry 10 }

    sisgm1040284lrtACLACEDenyPortRedirect OBJECT-TYPE
               SYNTAX      DisplayString
               MAX-ACCESS  read-create
               STATUS      current
               DESCRIPTION
                   "Frames that hit the ACE are redirected to the port
                    number specified here.Disabled,indicates that the port
                    redirect operation is disabled.
                    When 'Action' is 'Deny' can set.
                    0: disabled,
                    Port no: The ACE applies to this port number, where n is
                    the number of the switch port."
               ::= {     sisgm1040284lrtACLACEEntry 11 }

    sisgm1040284lrtACLACERateLimiter OBJECT-TYPE
               SYNTAX      Integer32(0..16)
               MAX-ACCESS  read-create
               STATUS      current
               DESCRIPTION
                   "default: 0,
                    0: Disable
                    range : 0 - 16 "
               ::= {     sisgm1040284lrtACLACEEntry 12 }

    sisgm1040284lrtACLACEMirror OBJECT-TYPE
               SYNTAX      AdminMode
               MAX-ACCESS  read-create
               STATUS      current
               DESCRIPTION
                   "default: 0,
                    0: disable - Frames matching the ACE are not mirrored.
                    1: enable - Frames matching the ACE are mirrored."
               ::= {     sisgm1040284lrtACLACEEntry 13 }

    sisgm1040284lrtACLACELogging OBJECT-TYPE
               SYNTAX      AdminMode
               MAX-ACCESS  read-create
               STATUS      current
               DESCRIPTION
                   "default: 0,
                    0: disable - Frames matching the ACE are not logged.
                    1: enable - Frames matching the ACE are stored in the
                   system log."
               ::= {     sisgm1040284lrtACLACEEntry 14 }

    sisgm1040284lrtACLACEShutdown OBJECT-TYPE
               SYNTAX      AdminMode
               MAX-ACCESS  read-create
               STATUS      current
               DESCRIPTION
                   "default: 0,
                    0: disable - Port shut down is disabled for the AC.
                    1: enable - If a frame matches the ACE, the ingress port
                    will be disabled."
               ::= {     sisgm1040284lrtACLACEEntry 15 }

    sisgm1040284lrtACLACECounter OBJECT-TYPE
               SYNTAX      Counter32
               MAX-ACCESS  read-only
               STATUS      current
               DESCRIPTION
                   "The counter indicates the number of times the ACE was
                    hit by a frame. "
               ::= {     sisgm1040284lrtACLACEEntry 16 }

    sisgm1040284lrtACLACEVLAN8021QTagged OBJECT-TYPE
               SYNTAX      INTEGER { disable(0), enable(1), any(2) }
               MAX-ACCESS  read-create
               STATUS      current
               DESCRIPTION
                   "Specify whether frames can hit the action according to
                    the 802.1Q tagged.
                    default: 2,
                    0: disable - Untagged frame only.
                    1: enable - Tagged frame only.
                    2: Any - Any value is allowed."
               ::= {     sisgm1040284lrtACLACEEntry 17 }

    sisgm1040284lrtACLACEVLANVID OBJECT-TYPE
               SYNTAX      Integer32(0..4095)
               MAX-ACCESS  read-create
               STATUS      current
               DESCRIPTION
                   "Specify the VLAN ID filter for this ACE.
                    The vid can't be set when 802.1Q Tagged is disabled.
                    default: 0,
                    0: Any - No VLAN ID filter is specified.
                    range : 0 - 4095 "
               ::= {     sisgm1040284lrtACLACEEntry 18 }

    sisgm1040284lrtACLACEVLANTagPriority OBJECT-TYPE
               SYNTAX      DisplayString
               MAX-ACCESS  read-create
               STATUS      current
               DESCRIPTION
                   "Specify the tag priority for this ACE.
                    The tag priority can't be set when 802.1Q Tagged is disabled.
                    range: 0~7,0-1,2-3,4-5,6-7,0-3,4-7."
               ::= {     sisgm1040284lrtACLACEEntry 19 }

    sisgm1040284lrtACLACESMAC OBJECT-TYPE
               SYNTAX      DisplayString
               MAX-ACCESS  read-create
               STATUS      current
               DESCRIPTION
                   "Configure source MAC address for this ACE.
                    <mac-address>: A frame that hits this ACE matches this
                    source MAC address value. xx-xx-xx-xx-xx-xx.
                    Any: Don't care."
               ::= {    sisgm1040284lrtACLACEEntry 20 }

    sisgm1040284lrtACLACEDMACType OBJECT-TYPE
               SYNTAX      INTEGER { any(0), mc(1), bc(2), uc(3) ,
                                     macAddress(4) , noData(5) }
               MAX-ACCESS  read-create
               STATUS      current
               DESCRIPTION
                   "DMAC Type.
                    default: 0,
                    0: Any - Don't care.
                    1: Multicast - Frame must be multicast.
                    2: Broadcast - Frame must be broadcast.
                    3: Unicast - Frame must be unicast.
                    4: mac address.
                    5: no data."
               DEFVAL  { any }
               ::= {    sisgm1040284lrtACLACEEntry 21 }

    sisgm1040284lrtACLACEDMAC OBJECT-TYPE
               SYNTAX      DisplayString
               MAX-ACCESS  read-create
               STATUS      current
               DESCRIPTION
                   "Configure destination MAC address for this ACE.
                    <mac-address>: A frame that hits this ACE matches this
                    destination MAC address value. xx-xx-xx-xx-xx-xx."
               ::= {     sisgm1040284lrtACLACEEntry 22 }

    sisgm1040284lrtACLACEEtherType OBJECT-TYPE
               SYNTAX      Integer32(-1..65535)
               MAX-ACCESS  read-create
               STATUS      current
               DESCRIPTION
                   "0: Any - Any but excluding 0x0800(IPv4) 0x0806(ARP) and
                    0x86DD(IPv6).
                    range : 0 or 1536(0x0600), 65535(0xffff).
                    -1: No data. "
               ::= {     sisgm1040284lrtACLACEEntry 23 }

    sisgm1040284lrtACLACEArpOpCode OBJECT-TYPE
               SYNTAX      INTEGER { any(0), arp(1), rarp(2),
                                     other(3), noData(4) }
               MAX-ACCESS  read-create
               STATUS      current
               DESCRIPTION
                   "Configure ARP opcode for this ACE.
                    default: 0,
                    0: Any - Don't care.
                    1: arp.
                    2: rarp.
                    3: other.
                    4: No data."
               DEFVAL  { any }
               ::= {     sisgm1040284lrtACLACEEntry 24 }

    sisgm1040284lrtACLACEArpFlagsRequestReply OBJECT-TYPE
               SYNTAX      INTEGER { reply(0), request(1), any(2), noData(3)}
               MAX-ACCESS  read-create
               STATUS      current
               DESCRIPTION
                   "Specify the available ARP/RARP opcode (OP) flag for this ACE.
                    default: 2,
                    0: Frame must have ARP Reply or RARP Reply OP flag.
                    1: Frame must have ARP Request or RARP Request OP flag set.
                    2: Any - Don't care.
                    3: No data."
               DEFVAL  { any }
               ::= {     sisgm1040284lrtACLACEEntry 25 }

    sisgm1040284lrtACLACEArpFlagsArpSMac OBJECT-TYPE
               SYNTAX      INTEGER { notEqualSMAC(0), equalSMAC(1),
                                     any(2), noData(3)}
               MAX-ACCESS  read-create
               STATUS      current
               DESCRIPTION
                   "Specify whether frames can hit the action according to their
                    sender hardware address field (SHA) settings.
                    default: 2,
                    0: ARP frames where SHA is not equal to the SMAC address.
                    1: ARP frames where SHA is equal to the SMAC address.
                    2: Any - Don't care.
                    3: No data."
               DEFVAL  { any }
               ::= {     sisgm1040284lrtACLACEEntry 26 }

    sisgm1040284lrtACLACEArpFlagsRarpDmac OBJECT-TYPE
               SYNTAX      INTEGER { notEqualDMAC(0), equalDMAC(1),
                                     any(2), noData(3)}
               MAX-ACCESS  read-create
               STATUS      current
               DESCRIPTION
                   "Specify whether frames can hit the action according to
                    their target hardware address field (THA) settings.
                    default: 2,
                    0: RARP frames where THA is not equal to the DMAC address.
                    1: RARP frames where THA is equal to the DMAC address.
                    2: Any - Don't care.
                    3: No data."
               DEFVAL  { any }
               ::= {     sisgm1040284lrtACLACEEntry 27 }

    sisgm1040284lrtACLACEArpFlagsLength OBJECT-TYPE
               SYNTAX      INTEGER { notEqualEthIpV4 (0), equalEthIpV4(1),
                                     any(2), noData(3)}
               MAX-ACCESS  read-create
               STATUS      current
               DESCRIPTION
                   "Specify whether frames can hit the action according to
                    their ARP/RARP hardware address length (HLN) and protocol
                    address length (PLN) settings.
                    default: 2,
                    0: ARP/RARP frames where the HLN is not equal to
                    Ethernet(0x06) or the (PLN) is not equal to IPv4(0x04).
                    1: ARP/RARP frames where the HLN is equal to Ethernet (0x06)
                    and the (PLN) is equal to IPv4(0x04).
                    2: Any - Don't care.
                    3: No data."
                DEFVAL  { any }
                ::= {     sisgm1040284lrtACLACEEntry 28 }

    sisgm1040284lrtACLACEArpFlagsIp OBJECT-TYPE
               SYNTAX      INTEGER { notEqualEth(0), equalEth(1),
                                     any(2), noData(3)}
               MAX-ACCESS  read-create
               STATUS      current
               DESCRIPTION
                   "Specify whether frames can hit the action according to
                    their ARP/RARP hardware address space (HRD) settings.
                    default: 2,
                    0: ARP/RARP frames where the HLD is not equal to Ethernet(1).
                    1: ARP/RARP frames where the HLD is equal to Ethernet(1).
                    2: Any - Don't care.
                    3: No data."
               DEFVAL  { any }
               ::= {     sisgm1040284lrtACLACEEntry 29 }

    sisgm1040284lrtACLACEArpFlagsEthernet OBJECT-TYPE
               SYNTAX      INTEGER { notEqualIp(0), equalIp(1),
                                     any(2), noData(3)}
               MAX-ACCESS  read-create
               STATUS      current
               DESCRIPTION
                   "Specify whether frames can hit the action
                    according to their ARP/RARP protocol address space (PRO) settings.
                    default: 2,
                    0: ARP/RARP frames where the PRO is not equal to IP\n(0x800).
                    1: ARP/RARP frames where the PRO is equal to IP(0x800).
                    2: Any - Don't care.
                    3: No data."
               DEFVAL  { any }
               ::= {     sisgm1040284lrtACLACEEntry 30 }

    sisgm1040284lrtACLACESIPType OBJECT-TYPE
               SYNTAX      INTEGER { any(0), ip(1), network(2), noData(3) }
               MAX-ACCESS  read-create
               STATUS      current
               DESCRIPTION
                   "Configure source IP address for this ACE.
                    default: 0,
                    0: Any - Don't care.
                    1: IP Address.
                    2: Network.
                    3: No data."
               DEFVAL  { any }
               ::= {     sisgm1040284lrtACLACEEntry 31 }

    sisgm1040284lrtACLACESIPIPAddress OBJECT-TYPE
               SYNTAX      IpAddress
               MAX-ACCESS  read-create
               STATUS      current
               DESCRIPTION
                   "A frame that hits this ACE matches this source IP address
                    value."
               ::= {     sisgm1040284lrtACLACEEntry 32 }

    sisgm1040284lrtACLACESIPIPMask OBJECT-TYPE
               SYNTAX      IpAddress
               MAX-ACCESS  read-create
               STATUS      current
               DESCRIPTION
                   "Specific sender IP mask in dotted decimal notation."
               ::= {     sisgm1040284lrtACLACEEntry 33 }

    sisgm1040284lrtACLACEDIPType OBJECT-TYPE
               SYNTAX      INTEGER { any(0), ip(1), network(2), noData(3) }
               MAX-ACCESS  read-create
               STATUS      current
               DESCRIPTION
                   "Configure destination IP address for this ACE.
                    default: 0,
                    0: Any - Don't care.
                    1: IP Address.
                    2: Network.
                    3: No data."
               DEFVAL  { any }
               ::= {     sisgm1040284lrtACLACEEntry 34 }

    sisgm1040284lrtACLACEDIPIPAddress OBJECT-TYPE
               SYNTAX      IpAddress
               MAX-ACCESS  read-create
               STATUS      current
               DESCRIPTION
                   "A frame that hits this ACE matches this destination IP
                    address value."
               ::= {     sisgm1040284lrtACLACEEntry 35 }

    sisgm1040284lrtACLACEDIPIPMask OBJECT-TYPE
               SYNTAX      IpAddress
               MAX-ACCESS  read-create
               STATUS      current
               DESCRIPTION
                   "Specific sender IP mask in dotted decimal notation."
               ::= {     sisgm1040284lrtACLACEEntry 36 }

    sisgm1040284lrtACLACEIPProtocol OBJECT-TYPE
               SYNTAX      INTEGER{ any(0), icmp(1), udp(2), tcp(3),
                                    other(4), noData(5)}
               MAX-ACCESS  read-create
               STATUS      current
               DESCRIPTION
                   "Specify the IP protocol filter for this ACE.
                    default: 0,
                    0: Any,
                    1: ICMP,
                    2: UDP,
                    3: TCP,
                    4: Other,
                    5: no data."
               DEFVAL  { any }
               ::= {     sisgm1040284lrtACLACEEntry 37 }

    sisgm1040284lrtACLACEIPProtocolValue OBJECT-TYPE
               SYNTAX      Integer32(0..256)
               MAX-ACCESS  read-create
               STATUS      current
               DESCRIPTION
                   "Configure IP protocol value for this ACE when IP Protocol
                    is 'other'.
                    default: 256,
                    256: No data.
                    range : 0 - 256"
               ::= {     sisgm1040284lrtACLACEEntry 38 }

    sisgm1040284lrtACLACEIPFlagsTTL OBJECT-TYPE
               SYNTAX      INTEGER { nonZero(0), zero(1), any(2), noData(3) }
               MAX-ACCESS  read-create
               STATUS      current
               DESCRIPTION
                   "Specify the Time-to-Live settings for this ACE.
                    default: 0,
                    0: zero,
                    1: Non-Zero
                    2: Any,,
                    3: No data."
               DEFVAL  { nonZero }
               ::= {     sisgm1040284lrtACLACEEntry 39 }

    sisgm1040284lrtACLACEIPFlagsFragment OBJECT-TYPE
               SYNTAX      INTEGER{yes(0), no(1), any(2), noData(3)}
               MAX-ACCESS  read-create
               STATUS      current
               DESCRIPTION
                   "Specify the fragment offset settings for this ACE.
                    default: 2,
                    0: No,
                    1: Yes,
                    2: Any,
                    3: No data."
               DEFVAL  { any }
               ::= {     sisgm1040284lrtACLACEEntry 40 }

    sisgm1040284lrtACLACEIPFlagsOptions OBJECT-TYPE
               SYNTAX      INTEGER{yes(0), no(1), any(2),  noData(3)}
               MAX-ACCESS  read-create
               STATUS      current
               DESCRIPTION
                   "Specify the options flag setting for this ACE.
                    default: 2,
                    0: No,
                    1: Yes,
                    2: Any,
                    3: No data."
               DEFVAL  { any }
               ::= {     sisgm1040284lrtACLACEEntry 41 }

    sisgm1040284lrtACLACEICMPType OBJECT-TYPE
               SYNTAX      Integer32(0..257)
               MAX-ACCESS  read-create
               STATUS      current
               DESCRIPTION
                   "Configure ICMP type for this ACE.
                    default: 256,
                    256: Any - Don't care.
                    257: No data.
                    range : 0 - 257."
               ::= { sisgm1040284lrtACLACEEntry 42 }

    sisgm1040284lrtACLACEICMPCode OBJECT-TYPE
               SYNTAX      Integer32(0..257)
               MAX-ACCESS  read-create
               STATUS      current
               DESCRIPTION
                   "Configure ICMP code for this ACE.
                    default: 256,
                    256: Any - Don't care.
                    257: No data.
                    range : 0 - 257."
               ::= {     sisgm1040284lrtACLACEEntry 43 }

    sisgm1040284lrtACLACESourcePort OBJECT-TYPE
               SYNTAX      DisplayString
               MAX-ACCESS  read-create
               STATUS      current
               DESCRIPTION
                   "Configure Source UDP/TCP port range for this ACE.
                    default: any,
                    specific: 0~65535,
                    range : 0 - 65535."
               ::= {     sisgm1040284lrtACLACEEntry 44 }

    sisgm1040284lrtACLACEDestPort OBJECT-TYPE
               SYNTAX      DisplayString
               MAX-ACCESS  read-create
               STATUS      current
               DESCRIPTION
                   "Configure Destination UDP/TCP port range for this ACE.
                    default: any,
                    specific: 0~65535,
                    range : 0 - 65535."
               ::= {     sisgm1040284lrtACLACEEntry 45 }

    sisgm1040284lrtACLACETCPFlagsFin OBJECT-TYPE
               SYNTAX      INTEGER { unset(0), set(1), any(2), noData(3) }
               MAX-ACCESS  read-create
               STATUS      current
               DESCRIPTION
                   "Configure TCP (FIN) flags for this ACE.
                    default: 2,
                    0: TCP frames where the FIN field is unset.
                    1: TCP frames where the FIN field is set.
                    2: Any - Don't care.
                    3: No data."
               DEFVAL  { any }
               ::= {     sisgm1040284lrtACLACEEntry 46 }

    sisgm1040284lrtACLACETCPFlagsSyn OBJECT-TYPE
               SYNTAX      INTEGER { unset(0), set(1), any(2), noData(3) }
               MAX-ACCESS  read-create
               STATUS      current
               DESCRIPTION
                   "Configure TCP (SYN) flags for this ACE.
                    default: 2,
                    0: TCP frames where the SYN field is unset.
                    1: TCP frames where the SYN field is set.
                    2: Any - Don't care.
                    3: No data."
               DEFVAL  { any }
               ::= {     sisgm1040284lrtACLACEEntry 47 }

    sisgm1040284lrtACLACETCPFlagsRst OBJECT-TYPE
               SYNTAX      INTEGER { unset(0), set(1), any(2), noData(3) }
               MAX-ACCESS  read-create
               STATUS      current
               DESCRIPTION
                   "Configure TCP (RST) flags for this ACE.
                    default: 2,
                    0: TCP frames where the RST field is unset.
                    1: TCP frames where the RST field is set.
                    2: Any - Don't care.
                    3: No data."
               DEFVAL  { any }
               ::= {     sisgm1040284lrtACLACEEntry 48 }

    sisgm1040284lrtACLACETCPFlagsPsh OBJECT-TYPE
               SYNTAX      INTEGER { unset(0), set(1), any(2), noData(3) }
               MAX-ACCESS  read-create
               STATUS      current
               DESCRIPTION
                   "Configure TCP (PSH) flags for this ACE.
                    default: 2,
                    0: TCP frames where the PSH field is unset.
                    1: TCP frames where the PSH field is set.
                    2: Any - Don't care.
                    3: No data."
               DEFVAL  { any }
               ::= {     sisgm1040284lrtACLACEEntry 49 }

    sisgm1040284lrtACLACETCPFlagsAck OBJECT-TYPE
               SYNTAX      INTEGER { unset(0), set(1), any(2), noData(3) }
               MAX-ACCESS  read-create
               STATUS      current
               DESCRIPTION
                   "Configure TCP (ACK) flags for this ACE.
                    default: 2,
                    0: TCP frames where the ACK field is unset.
                    1: TCP frames where the ACK field is set.
                    2: Any - Don't care.
                    3: No data."
               DEFVAL  { any }
               ::= {     sisgm1040284lrtACLACEEntry 50 }

    sisgm1040284lrtACLACETCPFlagsUrg OBJECT-TYPE
               SYNTAX      INTEGER { unset(0), set(1), any(2), noData(3) }
               MAX-ACCESS  read-create
               STATUS      current
               DESCRIPTION
                   "Configure TCP (URG) flags for this ACE.
                    default: 2,
                    0: TCP frames where the URG field is unset.
                    1: TCP frames where the URG field is set.
                    2: Any - Don't care.
                    3: No data."
               DEFVAL  { any }
               ::= {     sisgm1040284lrtACLACEEntry 51 }

    sisgm1040284lrtACLACEIPv6SIPAddress OBJECT-TYPE
               SYNTAX      DisplayString
               MAX-ACCESS  read-create
               STATUS      current
               DESCRIPTION
                   "When 'Specific' is selected for the source IPv6 filter,
                    you can enter a specific SIPv6 address.
                    The field only supported last 32 bits for IPv6 address. "
               ::= {     sisgm1040284lrtACLACEEntry 52 }

    sisgm1040284lrtACLACEIPv6SIPBitmask OBJECT-TYPE
               SYNTAX      DisplayString
               MAX-ACCESS  read-create
               STATUS      current
               DESCRIPTION
                   "When 'Specific' is selected for the source IPv6 filter,
                    you can enter a specific SIPv6 mask.
                    The field only supported last 32 bits for IPv6 address. "
               ::= {     sisgm1040284lrtACLACEEntry 53 }

    sisgm1040284lrtACLACEIPv6HopLimit OBJECT-TYPE
               SYNTAX      INTEGER { unset(0), set(1), any(2), noData(3) }
               MAX-ACCESS  read-create
               STATUS      current
               DESCRIPTION
                   "Specify the hop limit settings for this ACE.
                    default: 2,
                    0: Where the Hop Limit field is unset.
                    1: Where the Hop Limit field is set.
                    2: Any - Don't care,
                    3: No data."
               DEFVAL  { any }
               ::= {     sisgm1040284lrtACLACEEntry 54 }

    sisgm1040284lrtACLACERowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sisgm1040284lrtACLACEEntry 56 }

--
-- =======================================================================================================================
-- Start sisgm1040284lrtACLStatus group
-- =======================================================================================================================
--sisgm1040284lrtACLStatusTable

    sisgm1040284lrtACLStatusTable OBJECT-TYPE
               SYNTAX      SEQUENCE OF     SISGM1040284LRTACLStatusEntry
               MAX-ACCESS  not-accessible
               STATUS      current
               DESCRIPTION
                   " ACL ACE Status entry. "
               ::= {     sisgm1040284lrtACL 4 }

    sisgm1040284lrtACLStatusEntry OBJECT-TYPE
               SYNTAX          SISGM1040284LRTACLStatusEntry
               MAX-ACCESS  not-accessible
               STATUS      current
               DESCRIPTION
                   "The ACL Status Entry."
               INDEX    {    sisgm1040284lrtACLStatusIndex  }
               ::= {     sisgm1040284lrtACLStatusTable 1 }

    SISGM1040284LRTACLStatusEntry             ::= SEQUENCE {
                 sisgm1040284lrtACLStatusIndex          Integer32,
                 sisgm1040284lrtACLStatusUser           DisplayString,
                 sisgm1040284lrtACLStatusID             Integer32,
                 sisgm1040284lrtACLStatusIngressPort    DisplayString,
                 sisgm1040284lrtACLStatusFrameType      DisplayString,
                 sisgm1040284lrtACLStatusAction         DisplayString,
                 sisgm1040284lrtACLStatusRateLimiter    DisplayString,
                 sisgm1040284lrtACLStatusPortRedirect   DisplayString,
                 sisgm1040284lrtACLStatusMirror         DisplayString,
                 sisgm1040284lrtACLStatusCPU            DisplayString,
--               sisgm1040284lrtACLStatusCPUOnce        DisplayString,
                 sisgm1040284lrtACLStatusCounter        Counter32,
                 sisgm1040284lrtACLStatusConflict       DisplayString
                 }

    sisgm1040284lrtACLStatusIndex OBJECT-TYPE
               SYNTAX      Integer32(1..256)
               MAX-ACCESS  not-accessible
               STATUS      current
               DESCRIPTION
                   "The ACL status index. "
               ::= {     sisgm1040284lrtACLStatusEntry 1 }

    sisgm1040284lrtACLStatusUser OBJECT-TYPE
               SYNTAX      DisplayString
               MAX-ACCESS  read-only
               STATUS      current
               DESCRIPTION
                   "Indicates the ACL user.
                    S : Static,
                    IPMG : IP Management,
                    IPSG : IP Source Guard,
                    IPMC : IPMC,
                    ARPI : Arp Inspection,
                    UPnP : UPnP,
                    DHCP : DHCP. "
               ::= {     sisgm1040284lrtACLStatusEntry 2 }

    sisgm1040284lrtACLStatusID OBJECT-TYPE
               SYNTAX      Integer32(1..256)
               MAX-ACCESS  read-only
               STATUS      current
               DESCRIPTION
                   "ACE ID.
                    range : 1 - 256. "
               ::= {     sisgm1040284lrtACLStatusEntry 3 }

    sisgm1040284lrtACLStatusIngressPort OBJECT-TYPE
               SYNTAX      DisplayString
               MAX-ACCESS  read-only
               STATUS      current
               DESCRIPTION
                   "Indicates the ingress port of the ACE. Possible values are:
                    All: The ACE will match all ingress port.
                    Port: The ACE will match a specific ingress port. "
               ::= {     sisgm1040284lrtACLStatusEntry 4 }

    sisgm1040284lrtACLStatusFrameType OBJECT-TYPE
               SYNTAX      DisplayString
               MAX-ACCESS  read-only
               STATUS      current
               DESCRIPTION
                   "Indicates the frame type of the ACE.
                    Any: The ACE will match any frame type.
                    EType: The ACE will match Ethernet Type frames.
                    Note that an Ethernet Type based ACE will not get matched
                    by IP and ARP frames.
                    ARP: The ACE will match ARP/RARP frames.
                    IPv4: The ACE will match all IPv4 frames.
                    IPv4/ICMP: The ACE will match IPv4 frames with ICMP protocol.
                    IPv4/UDP: The ACE will match IPv4 frames with UDP protocol.
                    IPv4/TCP: The ACE will match IPv4 frames with TCP protocol.
                    IPv4/Other: The ACE will match IPv4 frames, which are not
                    ICMP/UDP/TCP.
                    IPv6: The ACE will match all IPv6 standard frames. "
               ::= {     sisgm1040284lrtACLStatusEntry 5 }

    sisgm1040284lrtACLStatusAction OBJECT-TYPE
               SYNTAX      DisplayString
               MAX-ACCESS  read-only
               STATUS      current
               DESCRIPTION
                   "Indicates the forwarding action of the ACE. "
               ::= {     sisgm1040284lrtACLStatusEntry 6 }

    sisgm1040284lrtACLStatusRateLimiter OBJECT-TYPE
               SYNTAX      DisplayString
               MAX-ACCESS  read-only
               STATUS      current
               DESCRIPTION
                   "Indicates the rate limiter number of the ACE. "
               ::= {     sisgm1040284lrtACLStatusEntry 7 }

    sisgm1040284lrtACLStatusPortRedirect OBJECT-TYPE
               SYNTAX      DisplayString
               MAX-ACCESS  read-only
               STATUS      current
               DESCRIPTION
                   "Indicates the port redirect operation of the ACE.
                    Frames matching the ACE are redirected to the port number. "
               ::= {     sisgm1040284lrtACLStatusEntry 8 }

    sisgm1040284lrtACLStatusMirror OBJECT-TYPE
               SYNTAX      DisplayString
               MAX-ACCESS  read-only
               STATUS      current
               DESCRIPTION
                   "Specify the mirror operation of this port.
                    Not support 'sisgm1040284lrt'."
               ::= {     sisgm1040284lrtACLStatusEntry 9 }

    sisgm1040284lrtACLStatusCPU OBJECT-TYPE
               SYNTAX      DisplayString
               MAX-ACCESS  read-only
               STATUS      current
               DESCRIPTION
                   "Forward packet that matched the specific ACE to CPU. "
               ::= {     sisgm1040284lrtACLStatusEntry 10 }

--    sisgm1040284lrtACLStatusCPUOnce OBJECT-TYPE
--               SYNTAX      DisplayString
--               MAX-ACCESS  read-only
--               STATUS      current
--               DESCRIPTION
--                   "Forward first packet that matched the specific ACE to CPU. "
--               ::= {     sisgm1040284lrtACLStatusEntry 11 }

    sisgm1040284lrtACLStatusCounter OBJECT-TYPE
               SYNTAX      Counter32
               MAX-ACCESS  read-only
               STATUS      current
               DESCRIPTION
                   "The counter indicates the number of times the ACE was hit
                    by a frame. "
               ::= {     sisgm1040284lrtACLStatusEntry 12 }

    sisgm1040284lrtACLStatusConflict OBJECT-TYPE
               SYNTAX      DisplayString
               MAX-ACCESS  read-only
               STATUS      current
               DESCRIPTION
                   "Indicates the hardware status of the specific ACE.
                    The specific ACE is not applied to the hardware due to
                    hardware limitations. "
               ::= {     sisgm1040284lrtACLStatusEntry 13 }


-- =======================================================================================================================
-- sisgm1040284lrtAclConformance
-- =======================================================================================================================
sisgm1040284lrtAclConformance OBJECT IDENTIFIER ::= { sisgm1040284lrtACL 200 }

sisgm1040284lrtAclCompliances OBJECT IDENTIFIER ::= { sisgm1040284lrtAclConformance 1 }

sisgm1040284lrtAclGroups    OBJECT IDENTIFIER ::= { sisgm1040284lrtAclConformance 2 }

sisgm1040284lrtACLPortConfGroup OBJECT-GROUP
    OBJECTS {
                -- sisgm1040284lrtACLPortConfTable
                 sisgm1040284lrtACLPortConfPolicyID,
                 sisgm1040284lrtACLPortConfAction,
                 sisgm1040284lrtACLPortConfRateLimiterID,
                 sisgm1040284lrtACLPortConfPortRedirect,
--               sisgm1040284lrtACLPortConfMirror,
                 sisgm1040284lrtACLPortConfLogging,
                 sisgm1040284lrtACLPortConfShutdown,
                 sisgm1040284lrtACLPortConfState,
                 sisgm1040284lrtACLPortConfCounter
            }
     STATUS  current
     DESCRIPTION
            "The collection of objects which are used to indicate
            sisgm1040284lrt ACL information."
    ::= { sisgm1040284lrtAclGroups 1 }

sisgm1040284lrtACLRateLimiterGroup OBJECT-GROUP
    OBJECTS {
                -- sisgm1040284lrtACLRateLimiterTable
                 sisgm1040284lrtACLRateLimiterRate
--               sisgm1040284lrtACLRateLimiterUnit
            }
     STATUS  current
     DESCRIPTION
            "The collection of objects which are used to indicate
            sisgm1040284lrt ACL information."
    ::= { sisgm1040284lrtAclGroups 2 }

sisgm1040284lrtACLACEGroup OBJECT-GROUP
    OBJECTS {
                -- sisgm1040284lrtACLACEClear
                 sisgm1040284lrtACLACEClear,

                -- sisgm1040284lrtACLACETable
                 sisgm1040284lrtACLACEID,
                 sisgm1040284lrtACLACENextID,
--               sisgm1040284lrtACLACELoopUp,
                 sisgm1040284lrtACLACEIngressPort,
                 sisgm1040284lrtACLACEPortPolicyNumber,
                 sisgm1040284lrtACLACEPortPolicyBitmask,
                 sisgm1040284lrtACLACEFrameType,
                 sisgm1040284lrtACLACEAction,
--               sisgm1040284lrtACLACEFilterPort,
                 sisgm1040284lrtACLACEDenyPortRedirect,
                 sisgm1040284lrtACLACERateLimiter,
--               sisgm1040284lrtACLACEMirror,
                 sisgm1040284lrtACLACELogging,
                 sisgm1040284lrtACLACEShutdown,
                 sisgm1040284lrtACLACECounter,
--               sisgm1040284lrtACLACEVLAN8021QTagged,
                 sisgm1040284lrtACLACEVLANVID,
                 sisgm1040284lrtACLACEVLANTagPriority,
                 sisgm1040284lrtACLACESMAC,
                 sisgm1040284lrtACLACEDMACType,
                 sisgm1040284lrtACLACEDMAC,
                 sisgm1040284lrtACLACEEtherType,
                 sisgm1040284lrtACLACEArpOpCode,
                 sisgm1040284lrtACLACEArpFlagsRequestReply,
                 sisgm1040284lrtACLACEArpFlagsArpSMac,
                 sisgm1040284lrtACLACEArpFlagsRarpDmac,
                 sisgm1040284lrtACLACEArpFlagsLength,
                 sisgm1040284lrtACLACEArpFlagsIp,
                 sisgm1040284lrtACLACEArpFlagsEthernet,
                 sisgm1040284lrtACLACESIPType,
                 sisgm1040284lrtACLACESIPIPAddress,
                 sisgm1040284lrtACLACESIPIPMask,
                 sisgm1040284lrtACLACEDIPType,
                 sisgm1040284lrtACLACEDIPIPAddress,
                 sisgm1040284lrtACLACEDIPIPMask,
                 sisgm1040284lrtACLACEIPProtocol,
                 sisgm1040284lrtACLACEIPProtocolValue,
                 sisgm1040284lrtACLACEIPFlagsTTL,
                 sisgm1040284lrtACLACEIPFlagsFragment,
                 sisgm1040284lrtACLACEIPFlagsOptions,
                 sisgm1040284lrtACLACEICMPType,
                 sisgm1040284lrtACLACEICMPCode,
                 sisgm1040284lrtACLACESourcePort,
                 sisgm1040284lrtACLACEDestPort,
                 sisgm1040284lrtACLACETCPFlagsFin,
                 sisgm1040284lrtACLACETCPFlagsSyn,
                 sisgm1040284lrtACLACETCPFlagsRst,
                 sisgm1040284lrtACLACETCPFlagsPsh,
                 sisgm1040284lrtACLACETCPFlagsAck,
                 sisgm1040284lrtACLACETCPFlagsUrg,
                 sisgm1040284lrtACLACEIPv6SIPAddress,
                 sisgm1040284lrtACLACEIPv6SIPBitmask,
                 sisgm1040284lrtACLACEIPv6HopLimit,
                 sisgm1040284lrtACLACERowStatus
            }
     STATUS  current
     DESCRIPTION
            "The collection of objects which are used to indicate
            sisgm1040284lrt ACL information."
    ::= { sisgm1040284lrtAclGroups 3 }

sisgm1040284lrtACLStatusGroup OBJECT-GROUP
    OBJECTS {
                -- sisgm1040284lrtACLStatusTable
                 sisgm1040284lrtACLStatusUser,
                 sisgm1040284lrtACLStatusID,
                 sisgm1040284lrtACLStatusIngressPort,
                 sisgm1040284lrtACLStatusFrameType,
                 sisgm1040284lrtACLStatusAction,
                 sisgm1040284lrtACLStatusRateLimiter,
                 sisgm1040284lrtACLStatusPortRedirect,
                 sisgm1040284lrtACLStatusMirror,
                 sisgm1040284lrtACLStatusCPU,
--               sisgm1040284lrtACLStatusCPUOnce,
                 sisgm1040284lrtACLStatusCounter,
                 sisgm1040284lrtACLStatusConflict
            }
     STATUS  current
     DESCRIPTION
            "The collection of objects which are used to indicate
            sisgm1040284lrt ACL information."
    ::= { sisgm1040284lrtAclGroups 4 }


-- =======================================================================================================================
-- =======================================================================================================================
 -- RowStatus Info:  createAndGo, notReady not supported.
-- =======================================================================================================================
-- Textual Conventions for the sisgm1040284lrt Qos Mib
-- =======================================================================================================================
--
sisgm1040284lrtQosConf                    OBJECT IDENTIFIER ::= { sisgm1040284lrtConfiguration 10 }
    sisgm1040284lrtQos                        OBJECT IDENTIFIER   ::= { sisgm1040284lrtQosConf  1  }
    sisgm1040284lrtQosPortClassification      OBJECT IDENTIFIER   ::= { sisgm1040284lrtQos 1 }
    sisgm1040284lrtQosPortPolicing            OBJECT IDENTIFIER   ::= { sisgm1040284lrtQos 2 }
    sisgm1040284lrtQosQueuePolicing           OBJECT IDENTIFIER   ::= { sisgm1040284lrtQos 3 }
    sisgm1040284lrtQosPortScheduler           OBJECT IDENTIFIER   ::= { sisgm1040284lrtQos 4 }
    sisgm1040284lrtQosPortEgressTagRemarking  OBJECT IDENTIFIER   ::= { sisgm1040284lrtQos 6 }
    sisgm1040284lrtQosPortDSCP                OBJECT IDENTIFIER   ::= { sisgm1040284lrtQos 7 }
    sisgm1040284lrtQosDSCP                    OBJECT IDENTIFIER   ::= { sisgm1040284lrtQos 8 }
    sisgm1040284lrtQosDSCPTranslation         OBJECT IDENTIFIER   ::= { sisgm1040284lrtQos 9 }
    sisgm1040284lrtQosDSCPClassification      OBJECT IDENTIFIER   ::= { sisgm1040284lrtQos 10 }
    sisgm1040284lrtQosControlList             OBJECT IDENTIFIER   ::= { sisgm1040284lrtQos 11 }
    sisgm1040284lrtQosStormControl            OBJECT IDENTIFIER   ::= { sisgm1040284lrtQos 12 }
--    sisgm1040284lrtQosPortStormControl        OBJECT IDENTIFIER   ::= { sisgm1040284lrtQos 13 }
--    sisgm1040284lrtQosWRED                    OBJECT IDENTIFIER   ::= { sisgm1040284lrtQos 14 }
    sisgm1040284lrtQosQCLStatus               OBJECT IDENTIFIER   ::= { sisgm1040284lrtQos 15 }


--
-- =======================================================================================================================
-- Start sisgm1040284lrtQosPortClassification group
-- =======================================================================================================================
--sisgm1040284lrtQosPortClassificationTable

     sisgm1040284lrtQosPortClassificationTable OBJECT-TYPE
               SYNTAX      SEQUENCE OF     SISGM1040284LRTQosPortClassificationEntry
               MAX-ACCESS  not-accessible
               STATUS      current
               DESCRIPTION
                   "QoS Ingress Port Classification.
                    INDEX for this table is ifIndex which is
                    equivalent to the panel port number."
               ::= {     sisgm1040284lrtQosPortClassification  1 }

    sisgm1040284lrtQosPortClassificationEntry OBJECT-TYPE
               SYNTAX          SISGM1040284LRTQosPortClassificationEntry
               MAX-ACCESS  not-accessible
               STATUS      current
               DESCRIPTION
                   "The Qos Port Classification Table."
               INDEX    {     ifIndex  }
               ::= {     sisgm1040284lrtQosPortClassificationTable 1 }

    SISGM1040284LRTQosPortClassificationEntry             ::= SEQUENCE {
                sisgm1040284lrtQosPortClassificationQoSClass        Integer32,
                sisgm1040284lrtQosPortClassificationDPlevel         Integer32,
                sisgm1040284lrtQosPortClassificationPCP             Integer32,
                sisgm1040284lrtQosPortClassificationDEI             Integer32,
                sisgm1040284lrtQosPortClassificationTagClass        AdminMode,
                sisgm1040284lrtQosPortClassificationDSCPBased       AdminMode,
                sisgm1040284lrtQosPortClassificationQCLAddr         INTEGER,
                sisgm1040284lrtQosPortClassificationKeyType         KeyType,
		sisgm1040284lrtQosPortClassificationWredGroup       Integer32 
                }

    sisgm1040284lrtQosPortClassificationQoSClass OBJECT-TYPE
               SYNTAX      Integer32(0..7)
               MAX-ACCESS  read-write
               STATUS      current
               DESCRIPTION
                  "Controls the default QoS class, i.e., the QoS class for
                   frames not classified
                   in any way. There is a one to one mapping between
                   QoS class, queue and
                   priority. A QoS class of 0 (zero) has the lowest priority.
                   NOTe: If the QoS class has been dynamically changed, then
                   the actual QoS class
                   is shown in parentheses after the configured QoS class.
                   range: 0~7,
                   default: 0."
               ::= {     sisgm1040284lrtQosPortClassificationEntry 2 }

    sisgm1040284lrtQosPortClassificationDPlevel OBJECT-TYPE
               SYNTAX      Integer32(0..1)
               MAX-ACCESS  read-write
               STATUS      current
               DESCRIPTION
                   "DP level for frames not classified in any way.
                    range: 0~1,
                    default: 0."
               ::= {     sisgm1040284lrtQosPortClassificationEntry 3 }

    sisgm1040284lrtQosPortClassificationPCP OBJECT-TYPE
               SYNTAX      Integer32(0..7)
               MAX-ACCESS  read-write
               STATUS      current
               DESCRIPTION
                  "Priority Code Point. It is a 3-bit field storing
                   the priority level for the 802.1Q frame.
                   range: 0~7,
                   default: 0.
                   Not support JAGUAR."
               ::= {     sisgm1040284lrtQosPortClassificationEntry 4 }

    sisgm1040284lrtQosPortClassificationDEI OBJECT-TYPE
               SYNTAX      Integer32(0|1)
               MAX-ACCESS  read-write
               STATUS      current
               DESCRIPTION
                  "Drop Eligible Indicator. It is a 1-bit field in the VLAN.
                   range 0~1,
                   default: 0.
                   Not support JAGUAR."
               ::= {     sisgm1040284lrtQosPortClassificationEntry 5 }

    sisgm1040284lrtQosPortClassificationTagClass OBJECT-TYPE
               SYNTAX      AdminMode
               MAX-ACCESS  read-write
               STATUS      current
               DESCRIPTION
                  "Configure the classification mode for tagged frames.
                  Not support SMB and JAGUAR."
               DEFVAL  { disable }
               ::= {     sisgm1040284lrtQosPortClassificationEntry 6 }

    sisgm1040284lrtQosPortClassificationDSCPBased OBJECT-TYPE
               SYNTAX      AdminMode
               MAX-ACCESS  read-write
               STATUS      current
               DESCRIPTION
                  "Click to Enable DSCP Based QoS Ingress Port Classification."
               DEFVAL  { disable }
               ::= {     sisgm1040284lrtQosPortClassificationEntry 7 }

    sisgm1040284lrtQosPortClassificationQCLAddr OBJECT-TYPE
               SYNTAX      INTEGER { sMacSip(0), dMacDip (1) }
               MAX-ACCESS  read-write
               STATUS      current
               DESCRIPTION
                  "Controls the QCL address matching mode.
                   0: SMAC/SIP,
                   1: DMAC/DIP,
                  default: SMAC/SIP.
                  Only support SPARX_III."
               DEFVAL  { sMacSip }
               ::= {     sisgm1040284lrtQosPortClassificationEntry 8 }

    sisgm1040284lrtQosPortClassificationKeyType OBJECT-TYPE
               SYNTAX      KeyType
               MAX-ACCESS  read-write
               STATUS      current
               DESCRIPTION
                  "The key type specifying the key generated for frames received
                   on the port.
                   0: Normal, Half key, match outer tag, SIP/DIP and SMAC/DMAC.
                   1: Double Tag: Quarter key, match inner and outer tag.
                   2: IP Address: Half key, match inner and outer tag, SIP and
                      DIP. For non-IP frames, match outer tag only.
                   3: MAC and IP Address: Full key, match inner and outer tag,
                      SMAC, DMAC, SIP and DIP.
                   Only support on SERVAL version."
               DEFVAL  { normal }
               ::= {     sisgm1040284lrtQosPortClassificationEntry 9 }
			   
    sisgm1040284lrtQosPortClassificationWredGroup OBJECT-TYPE
               SYNTAX      Integer32
               MAX-ACCESS  read-write
               STATUS      current
               DESCRIPTION
                  "Controls the WRED group membership. Range:1-3."
               ::= {     sisgm1040284lrtQosPortClassificationEntry 10 }			   

--sisgm1040284lrtQoSIngressPortTagClassificationTable
    sisgm1040284lrtQoSIngressPortTagClassificationTable OBJECT-TYPE
               SYNTAX      SEQUENCE OF     SISGM1040284LRTQoSIngressPortTagClassificationEntry
               MAX-ACCESS  not-accessible
               STATUS      current
               DESCRIPTION
                   "Show QoS Ingress Port Tag Classification.
                    INDEX for this table is ifIndex which is
                    equivalent to the panel port number."
               ::= {     sisgm1040284lrtQosPortClassification 2 }

    sisgm1040284lrtQoSIngressPortTagClassificationEntry OBJECT-TYPE
               SYNTAX          SISGM1040284LRTQoSIngressPortTagClassificationEntry
               MAX-ACCESS  not-accessible
               STATUS      current
               DESCRIPTION
                   "QoS Ingress Port Tag Classification entry."
               INDEX    {     ifIndex,
                              sisgm1040284lrtQoSIngressPortTagPCP,
                              sisgm1040284lrtQoSIngressPortTagDEI  }
               ::= {     sisgm1040284lrtQoSIngressPortTagClassificationTable 1 }

    SISGM1040284LRTQoSIngressPortTagClassificationEntry             ::= SEQUENCE {
                sisgm1040284lrtQoSIngressPortTagPCP                   INTEGER,
                sisgm1040284lrtQoSIngressPortTagDEI                   INTEGER,
                sisgm1040284lrtQoSIngressPortTagQosClass              Integer32,
                sisgm1040284lrtQoSIngressPortTagDPLevel               Integer32
                }

    sisgm1040284lrtQoSIngressPortTagPCP OBJECT-TYPE
               SYNTAX      INTEGER { pcp0(1),
                                     pcp1(2),
                                     pcp2(3),
                                     pcp3(4),
                                     pcp4(5),
                                     pcp5(6),
                                     pcp6(7),
                                     pcp7(8) }
               MAX-ACCESS  not-accessible
               STATUS      current
               DESCRIPTION
                   "range: 1-8,
                    PCP0:1, PCP1:2..."
               ::= {     sisgm1040284lrtQoSIngressPortTagClassificationEntry 2 }

    sisgm1040284lrtQoSIngressPortTagDEI OBJECT-TYPE
               SYNTAX      INTEGER { dei0(1), dei1(2) }
               MAX-ACCESS  not-accessible
               STATUS      current
               DESCRIPTION
                   "Ingress Port Tag dei,
                    DEI0:1, DEI1:2."
               ::= {     sisgm1040284lrtQoSIngressPortTagClassificationEntry 3 }

    sisgm1040284lrtQoSIngressPortTagQosClass OBJECT-TYPE
               SYNTAX      Integer32(0..7)
               MAX-ACCESS  read-write
               STATUS      current
               DESCRIPTION
                   "range: 0-7."
               ::= {     sisgm1040284lrtQoSIngressPortTagClassificationEntry 4 }

    sisgm1040284lrtQoSIngressPortTagDPLevel OBJECT-TYPE
               SYNTAX      Integer32(0|1)
               MAX-ACCESS  read-write
               STATUS      current
               DESCRIPTION
                   "range: 0-1."
               ::= {     sisgm1040284lrtQoSIngressPortTagClassificationEntry 5 }


--
-- =======================================================================================================================
-- Start sisgm1040284lrtQosPortPolicing group
-- =======================================================================================================================
--sisgm1040284lrtQosPortPolicingTable
   sisgm1040284lrtQosPortPolicingTable OBJECT-TYPE
               SYNTAX      SEQUENCE OF     SISGM1040284LRTQosPortPolicingEntry
               MAX-ACCESS  not-accessible
               STATUS      current
               DESCRIPTION
                   "The Policer settings.
                    INDEX for this table is ifIndex which is
                    equivalent to the panel port number."
               ::= {     sisgm1040284lrtQosPortPolicing 1 }

    sisgm1040284lrtQosPortPolicingEntry OBJECT-TYPE
               SYNTAX          SISGM1040284LRTQosPortPolicingEntry
               MAX-ACCESS  not-accessible
               STATUS      current
               DESCRIPTION
                   "The Policer setting entry."
               INDEX    {     ifIndex  }
               ::= {     sisgm1040284lrtQosPortPolicingTable 1 }

    SISGM1040284LRTQosPortPolicingEntry             ::= SEQUENCE {
                sisgm1040284lrtQosPortPolicingEnabled         AdminMode,
                sisgm1040284lrtQosPortPolicingRate            Integer32,
                sisgm1040284lrtQosPortPolicingUnit            Integer32,
                sisgm1040284lrtQosPortPolicingFlowControl     AdminMode
                }

    sisgm1040284lrtQosPortPolicingEnabled OBJECT-TYPE
               SYNTAX      AdminMode
               MAX-ACCESS  read-write
               STATUS      current
               DESCRIPTION
                  "Controls whether the policer is enabled on this switch port."
               DEFVAL  { disable }
               ::= {     sisgm1040284lrtQosPortPolicingEntry 2 }

    sisgm1040284lrtQosPortPolicingRate OBJECT-TYPE
               SYNTAX      Integer32
               MAX-ACCESS  read-write
               STATUS      current
               DESCRIPTION
                   "Controls the rate for the policer.
                    default: 500(kbps)."
               ::= {     sisgm1040284lrtQosPortPolicingEntry 3 }

    sisgm1040284lrtQosPortPolicingUnit OBJECT-TYPE
               SYNTAX      Integer32
               MAX-ACCESS  read-write
               STATUS      current
               DESCRIPTION
                   "Controls the unit of measure for the policer rate.
                    0: kbps
                    1: Mbps
		    2: fps
		    3: kfps
		    "
               ::= {     sisgm1040284lrtQosPortPolicingEntry 4 }

    sisgm1040284lrtQosPortPolicingFlowControl OBJECT-TYPE
               SYNTAX      AdminMode
               MAX-ACCESS  read-write
               STATUS      current
               DESCRIPTION
                   "If flow control is enabled and the port is in flow control mode,
                    then pause frames are sent instead of discarding frames."
               DEFVAL  { disable }
               ::= {     sisgm1040284lrtQosPortPolicingEntry 5 }

--
-- =======================================================================================================================
-- Start sisgm1040284lrtQosQueuePolicing group
-- =======================================================================================================================
--sisgm1040284lrtQosQueuePolicingTable
    sisgm1040284lrtQosQueuePolicingTable OBJECT-TYPE
               SYNTAX      SEQUENCE OF     SISGM1040284LRTQosQueuePolicingEntry
               MAX-ACCESS  not-accessible
               STATUS      current
               DESCRIPTION
                   "The Queue Policer settings.
                    INDEX for this table is ifIndex which is
                    equivalent to the panel port number."
               ::= {     sisgm1040284lrtQosQueuePolicing 1 }

    sisgm1040284lrtQosQueuePolicingEntry OBJECT-TYPE
               SYNTAX          SISGM1040284LRTQosQueuePolicingEntry
               MAX-ACCESS  not-accessible
               STATUS      current
               DESCRIPTION
                   "The Qos Queue Policing Entry."
               INDEX    {     ifIndex  }
               ::= {     sisgm1040284lrtQosQueuePolicingTable 1 }

    SISGM1040284LRTQosQueuePolicingEntry             ::= SEQUENCE {
                sisgm1040284lrtQosQueuePolicingQueue0Enable   AdminMode,
                sisgm1040284lrtQosQueuePolicingQueue0Rate     Integer32,
		sisgm1040284lrtQosQueuePolicingQueue0Unit     Integer32,
                sisgm1040284lrtQosQueuePolicingQueue1Enable   AdminMode,
                sisgm1040284lrtQosQueuePolicingQueue1Rate     Integer32,
		sisgm1040284lrtQosQueuePolicingQueue1Unit     Integer32,
                sisgm1040284lrtQosQueuePolicingQueue2Enable   AdminMode,
                sisgm1040284lrtQosQueuePolicingQueue2Rate     Integer32,
                sisgm1040284lrtQosQueuePolicingQueue2Unit     Integer32,
                sisgm1040284lrtQosQueuePolicingQueue3Enable   AdminMode,
                sisgm1040284lrtQosQueuePolicingQueue3Rate     Integer32,
                sisgm1040284lrtQosQueuePolicingQueue3Unit     Integer32,
                sisgm1040284lrtQosQueuePolicingQueue4Enable   AdminMode,
                sisgm1040284lrtQosQueuePolicingQueue4Rate     Integer32,
		sisgm1040284lrtQosQueuePolicingQueue4Unit     Integer32,
                sisgm1040284lrtQosQueuePolicingQueue5Enable   AdminMode,
                sisgm1040284lrtQosQueuePolicingQueue5Rate     Integer32,
		sisgm1040284lrtQosQueuePolicingQueue5Unit     Integer32,
                sisgm1040284lrtQosQueuePolicingQueue6Enable   AdminMode,
                sisgm1040284lrtQosQueuePolicingQueue6Rate     Integer32,
		sisgm1040284lrtQosQueuePolicingQueue6Unit     Integer32,
                sisgm1040284lrtQosQueuePolicingQueue7Enable   AdminMode,
                sisgm1040284lrtQosQueuePolicingQueue7Rate     Integer32,
		sisgm1040284lrtQosQueuePolicingQueue7Unit     Integer32
                }

    sisgm1040284lrtQosQueuePolicingQueue0Enable OBJECT-TYPE
               SYNTAX      AdminMode
               MAX-ACCESS  read-write
               STATUS      current
               DESCRIPTION
                   "Controls whether the queue 0 policer is enabled on this switch port."
               DEFVAL  { disable }
               ::= {     sisgm1040284lrtQosQueuePolicingEntry 3 }

    sisgm1040284lrtQosQueuePolicingQueue0Rate OBJECT-TYPE
               SYNTAX      Integer32
               MAX-ACCESS  read-write
               STATUS      current
               DESCRIPTION
                   "Controls whether the queue 0 policer is enabled on this switch port.
                    default: 500(Kbps)"
               ::= {     sisgm1040284lrtQosQueuePolicingEntry 4 }

    sisgm1040284lrtQosQueuePolicingQueue0Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 5 }			   
			   
    sisgm1040284lrtQosQueuePolicingQueue1Enable OBJECT-TYPE
               SYNTAX      AdminMode
               MAX-ACCESS  read-write
               STATUS      current
               DESCRIPTION
                   "Controls whether the queue 1 policer is enabled on this switch port."
               DEFVAL  { disable }
               ::= {     sisgm1040284lrtQosQueuePolicingEntry 6 }

    sisgm1040284lrtQosQueuePolicingQueue1Rate OBJECT-TYPE
               SYNTAX      Integer32
               MAX-ACCESS  read-write
               STATUS      current
               DESCRIPTION
                   "Controls whether the queue 1 policer is enabled on this switch port.,
                    default: 500(Kbps)"
               ::= {     sisgm1040284lrtQosQueuePolicingEntry 7 }
			   
    sisgm1040284lrtQosQueuePolicingQueue1Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 8 }			   
			   
    sisgm1040284lrtQosQueuePolicingQueue2Enable OBJECT-TYPE
               SYNTAX      AdminMode
               MAX-ACCESS  read-write
               STATUS      current
               DESCRIPTION
                   "Controls whether the queue 2 policer is enabled on this switch port."
               DEFVAL  { disable }
               ::= {     sisgm1040284lrtQosQueuePolicingEntry 9 }

    sisgm1040284lrtQosQueuePolicingQueue2Rate OBJECT-TYPE
               SYNTAX      Integer32
               MAX-ACCESS  read-write
               STATUS      current
               DESCRIPTION
                   "Controls whether the queue 2 policer is enabled on this switch port.
                    default: 500(Kbps)"
               ::= {     sisgm1040284lrtQosQueuePolicingEntry 10 }
			   
    sisgm1040284lrtQosQueuePolicingQueue2Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 11 }			   
			  
    sisgm1040284lrtQosQueuePolicingQueue3Enable OBJECT-TYPE
               SYNTAX      AdminMode
               MAX-ACCESS  read-write
               STATUS      current
               DESCRIPTION
                   "Controls whether the queue 3 policer is enabled on this switch port."
               DEFVAL  { disable }
               ::= {     sisgm1040284lrtQosQueuePolicingEntry 12 }

    sisgm1040284lrtQosQueuePolicingQueue3Rate OBJECT-TYPE
               SYNTAX      Integer32
               MAX-ACCESS  read-write
               STATUS      current
               DESCRIPTION
                   "Controls whether the queue 3 policer is enabled on this switch port.
                    default: 500(Kbps)"
               ::= {     sisgm1040284lrtQosQueuePolicingEntry 13 }
			   
    sisgm1040284lrtQosQueuePolicingQueue3Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 14 }			   
			   
    sisgm1040284lrtQosQueuePolicingQueue4Enable OBJECT-TYPE
               SYNTAX      AdminMode
               MAX-ACCESS  read-write
               STATUS      current
               DESCRIPTION
                   "Controls whether the queue 4 policer is enabled on this switch port."
               DEFVAL  { disable }
               ::= {     sisgm1040284lrtQosQueuePolicingEntry 15 }

    sisgm1040284lrtQosQueuePolicingQueue4Rate OBJECT-TYPE
               SYNTAX      Integer32
               MAX-ACCESS  read-write
               STATUS      current
               DESCRIPTION
                   "Controls whether the queue 4 policer is enabled on this switch port.
                    default: 500(Kbps)"
               ::= {     sisgm1040284lrtQosQueuePolicingEntry 16 }
			   
    sisgm1040284lrtQosQueuePolicingQueue4Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 17 }			   
			   
    sisgm1040284lrtQosQueuePolicingQueue5Enable OBJECT-TYPE
               SYNTAX      AdminMode
               MAX-ACCESS  read-write
               STATUS      current
               DESCRIPTION
                   "Controls whether the queue 5 policer is enabled on this switch port."
               DEFVAL  { disable }
               ::= {     sisgm1040284lrtQosQueuePolicingEntry 18 }

    sisgm1040284lrtQosQueuePolicingQueue5Rate OBJECT-TYPE
               SYNTAX      Integer32
               MAX-ACCESS  read-write
               STATUS      current
               DESCRIPTION
                   "Controls whether the queue 5 policer is enabled on this switch port.
                    default: 500(Kbps)"
               ::= {     sisgm1040284lrtQosQueuePolicingEntry 19 }

    sisgm1040284lrtQosQueuePolicingQueue5Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 20 }			   
			   			   
    sisgm1040284lrtQosQueuePolicingQueue6Enable OBJECT-TYPE
               SYNTAX      AdminMode
               MAX-ACCESS  read-write
               STATUS      current
               DESCRIPTION
                   "Controls whether the queue 6 policer is enabled on this switch port."
               DEFVAL  { disable }
               ::= {     sisgm1040284lrtQosQueuePolicingEntry 21 }

    sisgm1040284lrtQosQueuePolicingQueue6Rate OBJECT-TYPE
               SYNTAX      Integer32
               MAX-ACCESS  read-write
               STATUS      current
               DESCRIPTION
                   "Controls whether the queue 6 policer is enabled on this switch port.
                    default: 500(Kbps)"
               ::= {     sisgm1040284lrtQosQueuePolicingEntry 22 }
			   
    sisgm1040284lrtQosQueuePolicingQueue6Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 23 }			   
			   
    sisgm1040284lrtQosQueuePolicingQueue7Enable OBJECT-TYPE
               SYNTAX      AdminMode
               MAX-ACCESS  read-write
               STATUS      current
               DESCRIPTION
                   "Controls whether the queue 7 policer is enabled on this switch port."
               DEFVAL  { disable }
               ::= {     sisgm1040284lrtQosQueuePolicingEntry 24 }

    sisgm1040284lrtQosQueuePolicingQueue7Rate OBJECT-TYPE
               SYNTAX      Integer32
               MAX-ACCESS  read-write
               STATUS      current
               DESCRIPTION
                   "Controls whether the queue 7 policer is enabled on this switch port.
                    default: 500(Kbps)"
               ::= {     sisgm1040284lrtQosQueuePolicingEntry 25 }

    sisgm1040284lrtQosQueuePolicingQueue7Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sisgm1040284lrtQosQueuePolicingEntry 26 }			   

--
-- =======================================================================================================================
-- Start sisgm1040284lrtQosPortScheduler group
-- =======================================================================================================================
--sisgm1040284lrtQosPortSchedulerModeTable

     sisgm1040284lrtQosPortSchedulerModeTable OBJECT-TYPE
               SYNTAX      SEQUENCE OF     SISGM1040284LRTQosPortSchedulerModeEntry
               MAX-ACCESS  not-accessible
               STATUS      current
               DESCRIPTION
                   "The basic QoS Port Scheduler Mode settings.
                    INDEX for this table is ifIndex which is
                    equivalent to the panel port number."
               ::= {     sisgm1040284lrtQosPortScheduler  1 }

    sisgm1040284lrtQosPortSchedulerModeEntry OBJECT-TYPE
               SYNTAX          SISGM1040284LRTQosPortSchedulerModeEntry
               MAX-ACCESS  not-accessible
               STATUS      current
               DESCRIPTION
                   "The Qos Port Scheduler Mode entry."
               INDEX    {     ifIndex  }
               ::= {     sisgm1040284lrtQosPortSchedulerModeTable 1 }

    SISGM1040284LRTQosPortSchedulerModeEntry             ::= SEQUENCE {
                sisgm1040284lrtQosSchedulerMode            Integer32,
                sisgm1040284lrtQosSchedulerShaper          AdminMode,
                sisgm1040284lrtQosSchedulerShaperRate      Integer32
                }

    sisgm1040284lrtQosSchedulerMode OBJECT-TYPE
               SYNTAX      Integer32
               MAX-ACCESS  read-write
               STATUS      current
               DESCRIPTION
                   "Controls whether the scheduler mode is Strict Priority or Weighted
                    on this switch port.
                    0:Strict Priority,
		    2: 2 Queues Weighted
		    3: 3 Queues Weighted: only Jaguar2 support
		    4: 4 Queues Weighted: only Jaguar2 support
		    5: 5 Queues Weighted: only Jaguar2 support
                    6: 6 Queues Weighted
		    7: 7 Queues Weighted: only Jaguar2 support
		    8: 8 Queues Weighted: only Jaguar2 support"
               ::= {     sisgm1040284lrtQosPortSchedulerModeEntry 2 }

    sisgm1040284lrtQosSchedulerShaper OBJECT-TYPE
               SYNTAX      AdminMode
               MAX-ACCESS  read-write
               STATUS      current
               DESCRIPTION
                   "Controls whether the port shaper is enabled."
               DEFVAL  { disable }
               ::= {     sisgm1040284lrtQosPortSchedulerModeEntry 3 }

    sisgm1040284lrtQosSchedulerShaperRate OBJECT-TYPE
               SYNTAX      Integer32
               MAX-ACCESS  read-write
               STATUS      current
               DESCRIPTION
                   "Controls the rate for the port shaper.
                    default: 500 kbps."
               ::= {     sisgm1040284lrtQosPortSchedulerModeEntry 4 }

--sisgm1040284lrtQosPortSchedulerTable
    sisgm1040284lrtQosPortSchedulerTable OBJECT-TYPE
               SYNTAX      SEQUENCE OF     SISGM1040284LRTQosPortSchedulerEntry
               MAX-ACCESS  not-accessible
               STATUS      current
               DESCRIPTION
                   "Show Qos Port Scheduler.
                    INDEX for this table is ifIndex which is
                    equivalent to the panel port number."
               ::= {     sisgm1040284lrtQosPortScheduler 2 }

    sisgm1040284lrtQosPortSchedulerEntry OBJECT-TYPE
               SYNTAX          SISGM1040284LRTQosPortSchedulerEntry
               MAX-ACCESS  not-accessible
               STATUS      current
               DESCRIPTION
                   "The Qos Port Scheduler Entry."
               INDEX    {     ifIndex,
                              sisgm1040284lrtQosSchedulerPortQueue}
               ::= {     sisgm1040284lrtQosPortSchedulerTable 1 }

    SISGM1040284LRTQosPortSchedulerEntry             ::= SEQUENCE {
                sisgm1040284lrtQosSchedulerPortQueue                  INTEGER,
                sisgm1040284lrtQosSchedulerPortQueueShaper            AdminMode,
                sisgm1040284lrtQosSchedulerPortQueueShaperRate        Integer32,
                sisgm1040284lrtQosSchedulerPortQueueShaperExcess      AdminMode,
                sisgm1040284lrtQosSchedulerPortQueueSchedulerWeight   Integer32,
                sisgm1040284lrtQosSchedulerPortQueueSchedulerPercent  DisplayString
                }

    sisgm1040284lrtQosSchedulerPortQueue OBJECT-TYPE
               SYNTAX      INTEGER { q0(1),
                                     q1(2),
                                     q2(3),
                                     q3(4),
                                     q4(5),
                                     q5(6),
                                     q6(7),
                                     q7(8) }
               MAX-ACCESS  not-accessible
               STATUS      current
               DESCRIPTION
                   "range: 1-8.
                    Q0: 1, Q1: 2, ..."
               ::= {     sisgm1040284lrtQosPortSchedulerEntry 2 }

    sisgm1040284lrtQosSchedulerPortQueueShaper OBJECT-TYPE
               SYNTAX     AdminMode
               MAX-ACCESS  read-write
               STATUS      current
               DESCRIPTION
                   "Qos scheduler admin state."
               DEFVAL  { disable }
               ::= {     sisgm1040284lrtQosPortSchedulerEntry 3 }

    sisgm1040284lrtQosSchedulerPortQueueShaperRate OBJECT-TYPE
               SYNTAX      Integer32(100..1000000)
               MAX-ACCESS  read-write
               STATUS      current
               DESCRIPTION
                   "range: 100..1000000 kbps. "
               ::= {     sisgm1040284lrtQosPortSchedulerEntry 4 }

    sisgm1040284lrtQosSchedulerPortQueueShaperExcess OBJECT-TYPE
               SYNTAX      AdminMode
               MAX-ACCESS  read-write
               STATUS      current
               DESCRIPTION
                   "admin state sisgm1040284lrtQosSchedulerPortQueueShaperExcess"
               DEFVAL  { disable }
               ::= {     sisgm1040284lrtQosPortSchedulerEntry 5 }

    sisgm1040284lrtQosSchedulerPortQueueSchedulerWeight OBJECT-TYPE
               SYNTAX      Integer32(0..100)
               MAX-ACCESS  read-write
               STATUS      current
               DESCRIPTION
                   "range: 1-100,
                    default: 17.
                    Only use in Q0 - Q5.  Q6 & Q7 show 0"
               ::= {     sisgm1040284lrtQosPortSchedulerEntry 6 }

    sisgm1040284lrtQosSchedulerPortQueueSchedulerPercent OBJECT-TYPE
               SYNTAX      DisplayString
               MAX-ACCESS  read-only
               STATUS      current
               DESCRIPTION
                   "Only use in Q0 - Q5. Q6 & Q7 show empty"
               ::= {     sisgm1040284lrtQosPortSchedulerEntry 7 }
--
-- =======================================================================================================================
-- Start sisgm1040284lrtQosPortEgressTagRemarking group
-- =======================================================================================================================
--sisgm1040284lrtQosPortEgressTagRemarkingTable
    sisgm1040284lrtQosPortEgressTagRemarkingTable OBJECT-TYPE
               SYNTAX      SEQUENCE OF     SISGM1040284LRTQosPortEgressTagRemarkingEntry
               MAX-ACCESS  not-accessible
               STATUS      current
               DESCRIPTION
                   "The basic QoS Port Egress Tag Remark
                    Configuration settings.
                    INDEX for this table is ifIndex which is
                    equivalent to the panel port number."
               ::= {     sisgm1040284lrtQosPortEgressTagRemarking  1 }

    sisgm1040284lrtQosPortEgressTagRemarkingEntry OBJECT-TYPE
               SYNTAX          SISGM1040284LRTQosPortEgressTagRemarkingEntry
               MAX-ACCESS  not-accessible
               STATUS      current
               DESCRIPTION
                   "The Qos Port Egress Tag Remarking Entry."
               INDEX    {     ifIndex  }
               ::= {     sisgm1040284lrtQosPortEgressTagRemarkingTable 1 }

    SISGM1040284LRTQosPortEgressTagRemarkingEntry             ::= SEQUENCE {
                sisgm1040284lrtQosEgressTagRemarkingMode                    INTEGER
                }

    sisgm1040284lrtQosEgressTagRemarkingMode OBJECT-TYPE
               SYNTAX      INTEGER { classified(0), default(1), mapped(2) }
               MAX-ACCESS  read-write
               STATUS      current
               DESCRIPTION
                   "the tag remarking mode for this port.
                    0:Classified, Use classified PCP/DEI values.
                    1:Default, Use default PCP/DEI values.
                    2:Mapped, Use mapped versions of QoS class and DP level."
               ::= {     sisgm1040284lrtQosPortEgressTagRemarkingEntry 2 }

--sisgm1040284lrtQosPortEgressTagRemarkingDefTable
    sisgm1040284lrtQosPortEgressTagRemarkingDefTable OBJECT-TYPE
               SYNTAX      SEQUENCE OF     SISGM1040284LRTQosPortEgressTagRemarkingDefEntry
               MAX-ACCESS  not-accessible
               STATUS      current
               DESCRIPTION
                   "The basic QoS Port Egress Tag Remark
                    Configuration settings.
                    INDEX for this table is ifIndex which is
                    equivalent to the panel port number."
               ::= {     sisgm1040284lrtQosPortEgressTagRemarking  2 }

    sisgm1040284lrtQosPortEgressTagRemarkingDefEntry OBJECT-TYPE
               SYNTAX          SISGM1040284LRTQosPortEgressTagRemarkingDefEntry
               MAX-ACCESS  not-accessible
               STATUS      current
               DESCRIPTION
                   "The oQos Port Egress Tag Remarking Default Entry."
               INDEX    {     ifIndex  }
               ::= {     sisgm1040284lrtQosPortEgressTagRemarkingDefTable 1 }

    SISGM1040284LRTQosPortEgressTagRemarkingDefEntry             ::= SEQUENCE {
                sisgm1040284lrtQosEgressTagRemarkingDefPCP                Integer32,
                sisgm1040284lrtQosEgressTagRemarkingDefDEI                AdminMode
                }

    sisgm1040284lrtQosEgressTagRemarkingDefPCP OBJECT-TYPE
               SYNTAX      Integer32(0..7)
               MAX-ACCESS  read-write
               STATUS      current
               DESCRIPTION
                   "Controls the default PCP
                    Range : 0-7"
               ::= {     sisgm1040284lrtQosPortEgressTagRemarkingDefEntry 2 }

    sisgm1040284lrtQosEgressTagRemarkingDefDEI OBJECT-TYPE
               SYNTAX      AdminMode
               MAX-ACCESS  read-write
               STATUS      current
               DESCRIPTION
                   "controls the admin state of DEI"
               ::= {     sisgm1040284lrtQosPortEgressTagRemarkingDefEntry 3 }

--sisgm1040284lrtQosPortEgressTagRemarkingMapDPTable
--    sisgm1040284lrtQosPortEgressTagRemarkingMapDPTable OBJECT-TYPE
--               SYNTAX      SEQUENCE OF     SISGM1040284LRTQosPortEgressTagRemarkingMapDPEntry
--               MAX-ACCESS  not-accessible
--               STATUS      current
--               DESCRIPTION
--                   "Show Qos Port Egress Tag Remarking Map DP.
--                    INDEX for this table is ifIndex which is
--                    equivalent to the panel port number."
--               ::= {     sisgm1040284lrtQosPortEgressTagRemarking 3 }

--    sisgm1040284lrtQosPortEgressTagRemarkingMapDPEntry OBJECT-TYPE
--               SYNTAX          SISGM1040284LRTQosPortEgressTagRemarkingMapDPEntry
--               MAX-ACCESS  not-accessible
--               STATUS      current
--               DESCRIPTION
--                   "The Qos Port Egress Tag Remarking Map DP Entry."
--               INDEX    {     ifIndex,
--                              sisgm1040284lrtQosPortEgressTagRemarkingClassifiedDPLevel}
--               ::= {     sisgm1040284lrtQosPortEgressTagRemarkingMapDPTable 1 }

--    SISGM1040284LRTQosPortEgressTagRemarkingMapDPEntry             ::= SEQUENCE {
--                sisgm1040284lrtQosPortEgressTagRemarkingClassifiedDPLevel      Integer32,
--                sisgm1040284lrtQosPortEgressTagRemarkingDPLevel                AdminMode
--                }

--    sisgm1040284lrtQosPortEgressTagRemarkingClassifiedDPLevel OBJECT-TYPE
--               SYNTAX      Integer32(1..4)
--               MAX-ACCESS  not-accessible
--               STATUS      current
--               DESCRIPTION
--                   "range: 1-4."
--               ::= {     sisgm1040284lrtQosPortEgressTagRemarkingMapDPEntry 2 }

--    sisgm1040284lrtQosPortEgressTagRemarkingDPLevel OBJECT-TYPE
--               SYNTAX      AdminMode
--               MAX-ACCESS  read-write
--               STATUS      current
--               DESCRIPTION
--                   "admin state of Tag remark"
--               ::= {     sisgm1040284lrtQosPortEgressTagRemarkingMapDPEntry 3 }

--sisgm1040284lrtQosPortEgressTagRemarkingMapTable
    sisgm1040284lrtQosPortEgressTagRemarkingMapTable OBJECT-TYPE
               SYNTAX      SEQUENCE OF     SISGM1040284LRTQosPortEgressTagRemarkingMapEntry
               MAX-ACCESS  not-accessible
               STATUS      current
               DESCRIPTION
                   "Show Qos Port Egress Tag Remarking Map.
                    INDEX for this table is ifIndex which is
                    equivalent to the panel port number."
               ::= {     sisgm1040284lrtQosPortEgressTagRemarking 4 }

    sisgm1040284lrtQosPortEgressTagRemarkingMapEntry OBJECT-TYPE
               SYNTAX          SISGM1040284LRTQosPortEgressTagRemarkingMapEntry
               MAX-ACCESS  not-accessible
               STATUS      current
               DESCRIPTION
                   "The Qos Port Egress Tag Remarking Map Entry."
               INDEX    {     ifIndex,
                              sisgm1040284lrtQosTagRemarkingQoSClass,
                              sisgm1040284lrtQosTagRemarkingDPLevel  }
               ::= {     sisgm1040284lrtQosPortEgressTagRemarkingMapTable 1 }

    SISGM1040284LRTQosPortEgressTagRemarkingMapEntry             ::= SEQUENCE {
                sisgm1040284lrtQosTagRemarkingQoSClass               INTEGER,
                sisgm1040284lrtQosTagRemarkingDPLevel                INTEGER,
                sisgm1040284lrtQosTagRemarkingPCP                    Integer32,
                sisgm1040284lrtQosTagRemarkingDEI                    Integer32
                }

    sisgm1040284lrtQosTagRemarkingQoSClass OBJECT-TYPE
               SYNTAX      INTEGER {
                        class0(1),
                        class1(2),
                        class2(3),
                        class3(4),
                        class4(5),
                        class5(6),
                        class6(7),
                        class7(8)
                        }
               MAX-ACCESS  not-accessible
               STATUS      current
               DESCRIPTION
                   "range: 1-8,
                    QoS Class0: 1, QoS Class1: 2..."
               ::= {     sisgm1040284lrtQosPortEgressTagRemarkingMapEntry 2 }

    sisgm1040284lrtQosTagRemarkingDPLevel OBJECT-TYPE
               SYNTAX      INTEGER { level0(1), level1(2) }
               MAX-ACCESS  not-accessible
               STATUS      current
               DESCRIPTION
                   "range: 1-2,
                    DP Level0: 1, DP Level1: 2."
               ::= {     sisgm1040284lrtQosPortEgressTagRemarkingMapEntry 3 }

    sisgm1040284lrtQosTagRemarkingPCP OBJECT-TYPE
               SYNTAX      Integer32(0..7)
               MAX-ACCESS  read-write
               STATUS      current
               DESCRIPTION
                   "range: 0-7."
               ::= {     sisgm1040284lrtQosPortEgressTagRemarkingMapEntry 4 }

    sisgm1040284lrtQosTagRemarkingDEI OBJECT-TYPE
               SYNTAX      Integer32 (0|1)
               MAX-ACCESS  read-write
               STATUS      current
               DESCRIPTION
                   "range: 0-1."
               ::= {     sisgm1040284lrtQosPortEgressTagRemarkingMapEntry 5 }

--
-- =======================================================================================================================
-- Start sisgm1040284lrtQosPortDSCP group
-- =======================================================================================================================
--sisgm1040284lrtQosPortDSCPTable
    sisgm1040284lrtQosPortDSCPTable OBJECT-TYPE
               SYNTAX      SEQUENCE OF     SISGM1040284LRTQosPortDSCPEntry
               MAX-ACCESS  not-accessible
               STATUS      current
               DESCRIPTION
                   "The basic QoS Port DSCP Configuration settings.
                    INDEX for this table is ifIndex which is
                    equivalent to the panel port number."
               ::= {     sisgm1040284lrtQosPortDSCP 1 }

    sisgm1040284lrtQosPortDSCPEntry OBJECT-TYPE
               SYNTAX          SISGM1040284LRTQosPortDSCPEntry
               MAX-ACCESS  not-accessible
               STATUS      current
               DESCRIPTION
                   "The Qos Port DSCP Entry."
               INDEX    {     ifIndex  }
               ::= {     sisgm1040284lrtQosPortDSCPTable 1 }

    SISGM1040284LRTQosPortDSCPEntry             ::= SEQUENCE {
                sisgm1040284lrtQosPortDSCPIngressTranslate        AdminMode,
                sisgm1040284lrtQosPortDSCPIngressClassify         INTEGER,
                sisgm1040284lrtQosPortDSCPEgressRewrite           INTEGER
                }

    sisgm1040284lrtQosPortDSCPIngressTranslate OBJECT-TYPE
               SYNTAX      AdminMode
               MAX-ACCESS  read-write
               STATUS      current
               DESCRIPTION
                  "Configure DSCP ingress translation mode."
               DEFVAL  { disable }
               ::= {     sisgm1040284lrtQosPortDSCPEntry 2 }

    sisgm1040284lrtQosPortDSCPIngressClassify OBJECT-TYPE
               SYNTAX      INTEGER { disable (0), dscp (1), selected (2), all(3) }
               MAX-ACCESS  read-write
               STATUS      current
               DESCRIPTION
                   "Classification for a port have 4 different values.
                    0: disable,
                    1: DSCP=0,
                    2: Selected,
                    3: All."
               DEFVAL  { disable }
               ::= {     sisgm1040284lrtQosPortDSCPEntry 3 }

    sisgm1040284lrtQosPortDSCPEgressRewrite OBJECT-TYPE
               SYNTAX      INTEGER { disable (0),enable (1),
                                     remapDPUnaware (2), remapDPaware (3) }
               MAX-ACCESS  read-write
               STATUS      current
               DESCRIPTION
                   "Configure the port egress rewriting mode.
                    LUTON26:{0: Disable,1: Enable,2: Remap DP Unaware,
                    3: Remap DP Aware,range: 0-3}
                    Others:{0: Disable,1: Enable,2: Remap,range: 0-2}"
               ::= {     sisgm1040284lrtQosPortDSCPEntry 4 }

--
-- =======================================================================================================================
-- Start sisgm1040284lrtQosDSCP group
-- =======================================================================================================================
    sisgm1040284lrtQosDSCPTable OBJECT-TYPE
               SYNTAX      SEQUENCE OF     SISGM1040284LRTQosDSCPEntry
               MAX-ACCESS  not-accessible
               STATUS      current
               DESCRIPTION
                   "configure the basic QoS DSCP based QoS Ingress
                    Classification settings for all switches."
               ::= {     sisgm1040284lrtQosDSCP 1 }

    sisgm1040284lrtQosDSCPEntry OBJECT-TYPE
               SYNTAX          SISGM1040284LRTQosDSCPEntry
               MAX-ACCESS  not-accessible
               STATUS      current
               DESCRIPTION
                   "The Qos DSCP Entry."
               INDEX    {     sisgm1040284lrtQosDSCPList  }
               ::= {     sisgm1040284lrtQosDSCPTable 1 }

    SISGM1040284LRTQosDSCPEntry             ::= SEQUENCE {
                sisgm1040284lrtQosDSCPList       Integer32,
                sisgm1040284lrtQosBasedDSCP      DisplayString,
                sisgm1040284lrtQosDSCPTrust      AdminMode,
                sisgm1040284lrtQosDSCPQosClass   Integer32,
                sisgm1040284lrtQosDSCPDPL        Integer32
                }

    sisgm1040284lrtQosDSCPList OBJECT-TYPE
               SYNTAX      Integer32(1..64)
               MAX-ACCESS  not-accessible
               STATUS      current
               DESCRIPTION
                  "DSCP mapping table index(1-64)."
               ::= {     sisgm1040284lrtQosDSCPEntry 1 }

    sisgm1040284lrtQosBasedDSCP OBJECT-TYPE
               SYNTAX      DisplayString
               MAX-ACCESS  read-only
               STATUS      current
               DESCRIPTION
                  "Maximum number of supported DSCP values are 64."
               ::= {     sisgm1040284lrtQosDSCPEntry 2 }

    sisgm1040284lrtQosDSCPTrust OBJECT-TYPE
               SYNTAX      AdminMode
               MAX-ACCESS  read-write
               STATUS      current
               DESCRIPTION
                  "Controls whether a specific DSCP value is trusted. Only frames with
                   trusted DSCP values are mapped to a specific QoS class
                   and Drop Precedence
                   Level. Frames with untrusted DSCP values are
                   treated as a non-IP frame."
               DEFVAL  { disable }
              ::= {     sisgm1040284lrtQosDSCPEntry 3 }

    sisgm1040284lrtQosDSCPQosClass OBJECT-TYPE
               SYNTAX      Integer32(0..7)
               MAX-ACCESS  read-write
               STATUS      current
               DESCRIPTION
                  "QoS class.
                   range: 0-7,
                   default: 0."
               ::= {     sisgm1040284lrtQosDSCPEntry 4 }

    sisgm1040284lrtQosDSCPDPL OBJECT-TYPE
               SYNTAX      Integer32(0|1)
               MAX-ACCESS  read-write
               STATUS      current
               DESCRIPTION
                  "Drop Precedence Level.
                   range: 0-1,
                   default: 0."
               ::= {     sisgm1040284lrtQosDSCPEntry 5 }

--
-- =======================================================================================================================
-- Start sisgm1040284lrtQosDSCPTranslation group
-- =======================================================================================================================
--sisgm1040284lrtQosDSCPTranslationTable
    sisgm1040284lrtQosDSCPTranslationTable OBJECT-TYPE
               SYNTAX      SEQUENCE OF     SISGM1040284LRTQosDSCPTranslationEntry
               MAX-ACCESS  not-accessible
               STATUS      current
               DESCRIPTION
                   "The basic QoS DSCP Translation settings for all switches."
               ::= {     sisgm1040284lrtQosDSCPTranslation  1 }

    sisgm1040284lrtQosDSCPTranslationEntry OBJECT-TYPE
               SYNTAX          SISGM1040284LRTQosDSCPTranslationEntry
               MAX-ACCESS  not-accessible
               STATUS      current
               DESCRIPTION
                   "The Qos DSCP Translation Entry."
               INDEX    {     sisgm1040284lrtQosDSCPTranslationList  }
               ::= {     sisgm1040284lrtQosDSCPTranslationTable 1 }

    SISGM1040284LRTQosDSCPTranslationEntry             ::= SEQUENCE {
                sisgm1040284lrtQosDSCPTranslationList                 Integer32,
                sisgm1040284lrtQosDSCPTranslationDSCPBasedId          DisplayString,
                sisgm1040284lrtQosDSCPTranslationIngressTranslate     Integer32,
                sisgm1040284lrtQosDSCPTranslationIngressClassify      AdminMode,
                sisgm1040284lrtQosDSCPTranslationEgressRemapDP0       Integer32,
                sisgm1040284lrtQosDSCPTranslationEgressRemapDP1       Integer32
                }

    sisgm1040284lrtQosDSCPTranslationList OBJECT-TYPE
               SYNTAX      Integer32(1..64)
               MAX-ACCESS  not-accessible
               STATUS      current
               DESCRIPTION
                  "DSCP translation table index(1-64)."
               ::= {     sisgm1040284lrtQosDSCPTranslationEntry 1 }

    sisgm1040284lrtQosDSCPTranslationDSCPBasedId OBJECT-TYPE
               SYNTAX      DisplayString
               MAX-ACCESS  read-only
               STATUS      current
               DESCRIPTION
                  "Configure global ingress DSCP translation table."
               ::= {     sisgm1040284lrtQosDSCPTranslationEntry 2 }

    sisgm1040284lrtQosDSCPTranslationIngressTranslate OBJECT-TYPE
               SYNTAX      Integer32(0..63)
               MAX-ACCESS  read-write
               STATUS      current
               DESCRIPTION
                  "DSCP at Ingress side can be translated to any of DSCP values.
                   range: 0-63,
                   default: 0."
               ::= {     sisgm1040284lrtQosDSCPTranslationEntry 3 }

    sisgm1040284lrtQosDSCPTranslationIngressClassify OBJECT-TYPE
               SYNTAX      AdminMode
               MAX-ACCESS  read-write
               STATUS      current
               DESCRIPTION
                  "Configure DSCP ingress classification."
               DEFVAL  { disable }
               ::= {     sisgm1040284lrtQosDSCPTranslationEntry 4 }

    sisgm1040284lrtQosDSCPTranslationEgressRemapDP0 OBJECT-TYPE
               SYNTAX      Integer32(0..63)
               MAX-ACCESS  read-write
               STATUS      current
               DESCRIPTION
                  "Select the DSCP value from select menu to which you want to remap.
                   range: 0-63,
                   default: 0."
               ::= {     sisgm1040284lrtQosDSCPTranslationEntry 5 }

    sisgm1040284lrtQosDSCPTranslationEgressRemapDP1 OBJECT-TYPE
               SYNTAX      Integer32(0..63)
               MAX-ACCESS  read-write
               STATUS      current
               DESCRIPTION
                  "Select the DSCP value from select menu to which you want to remap.
                   range: 0-63,
                   default: 0.
                   Only support LUTON26."
               ::= {     sisgm1040284lrtQosDSCPTranslationEntry 6 }

--
-- =======================================================================================================================
-- Start sisgm1040284lrtQosDSCPClassification group
-- =======================================================================================================================
--sisgm1040284lrtQosDSCPClassificationTable
    sisgm1040284lrtQosDSCPClassificationTable OBJECT-TYPE
               SYNTAX      SEQUENCE OF     SISGM1040284LRTQosDSCPClassificationEntry
               MAX-ACCESS  not-accessible
               STATUS      current
               DESCRIPTION
                   "The mapping of QoS class  to DSCP value."
               ::= {     sisgm1040284lrtQosDSCPClassification 1 }

    sisgm1040284lrtQosDSCPClassificationEntry OBJECT-TYPE
               SYNTAX          SISGM1040284LRTQosDSCPClassificationEntry
               MAX-ACCESS  not-accessible
               STATUS      current
               DESCRIPTION
                   "The Qos DSCP Classification Entry."
               INDEX    {     sisgm1040284lrtQosDSCPClassificationQoSClass  }
               ::= {     sisgm1040284lrtQosDSCPClassificationTable 1 }

    SISGM1040284LRTQosDSCPClassificationEntry             ::= SEQUENCE {
                sisgm1040284lrtQosDSCPClassificationQoSClass   Integer32,
                sisgm1040284lrtQosDSCPClassificationDSCPDP0    Integer32,
		sisgm1040284lrtQosDSCPClassificationDSCPDP1    Integer32,
		sisgm1040284lrtQosDSCPClassificationDSCPDP2    Integer32,
		sisgm1040284lrtQosDSCPClassificationDSCPDP3    Integer32
                }

    sisgm1040284lrtQosDSCPClassificationQoSClass OBJECT-TYPE
               SYNTAX      Integer32(1..8)
               MAX-ACCESS  not-accessible
               STATUS      current
               DESCRIPTION
                  "This page allows you to configure the mapping of QoS class
                   and Drop Precedence Level to DSCP value.
                   range: 1-8}"
               ::= {     sisgm1040284lrtQosDSCPClassificationEntry 1 }

    sisgm1040284lrtQosDSCPClassificationDSCPDP0 OBJECT-TYPE
               SYNTAX      Integer32(0..63)
               MAX-ACCESS  read-write
               STATUS      current
               DESCRIPTION
                  "Select the classified DSCP value.
                   range: 0-63,
                   default: 0."
               ::= {     sisgm1040284lrtQosDSCPClassificationEntry 2 }

    sisgm1040284lrtQosDSCPClassificationDSCPDP1 OBJECT-TYPE
               SYNTAX      Integer32(0..63)
               MAX-ACCESS  read-write
               STATUS      current
               DESCRIPTION
                  "Select the classified DSCP value.
                   range: 0-63,
                   default: 0."
               ::= {     sisgm1040284lrtQosDSCPClassificationEntry 3 }

    sisgm1040284lrtQosDSCPClassificationDSCPDP2 OBJECT-TYPE
               SYNTAX      Integer32(0..63)
               MAX-ACCESS  read-write
               STATUS      current
               DESCRIPTION
                  "Select the classified DSCP value.
                   range: 0-63,
                   default: 0."
               ::= {     sisgm1040284lrtQosDSCPClassificationEntry 4 }

    sisgm1040284lrtQosDSCPClassificationDSCPDP3 OBJECT-TYPE
               SYNTAX      Integer32(0..63)
               MAX-ACCESS  read-write
               STATUS      current
               DESCRIPTION
                  "Select the classified DSCP value.
                   range: 0-63,
                   default: 0."
               ::= {     sisgm1040284lrtQosDSCPClassificationEntry 5 }
			   
--
-- =======================================================================================================================
-- Start sisgm1040284lrtQosControlList group
-- =======================================================================================================================
--sisgm1040284lrtQosQceTable

    sisgm1040284lrtQosQceTable OBJECT-TYPE
               SYNTAX      SEQUENCE OF     SISGM1040284LRTQosQceEntry
               MAX-ACCESS  not-accessible
               STATUS      current
               DESCRIPTION
                   "Create Qos QCE entry."
               ::= {     sisgm1040284lrtQosControlList 1 }

    sisgm1040284lrtQosQceEntry OBJECT-TYPE
               SYNTAX          SISGM1040284LRTQosQceEntry
               MAX-ACCESS  not-accessible
               STATUS      current
               DESCRIPTION
                   "Qos Qce Entry."
               INDEX    {     sisgm1040284lrtQosQceIndex  }
               ::= {     sisgm1040284lrtQosQceTable 1 }

    SISGM1040284LRTQosQceEntry             ::= SEQUENCE {
                sisgm1040284lrtQosQceIndex                Integer32,
                sisgm1040284lrtQosQceID                   Integer32,
                sisgm1040284lrtQosQceList                 Integer32,
                sisgm1040284lrtQosQcePortMembersSwitch    Integer32,
                sisgm1040284lrtQosQcePortMembers          DisplayString,
                sisgm1040284lrtQosQceTag                  DisplayString,
                sisgm1040284lrtQosQceVID                  DisplayString,
                sisgm1040284lrtQosPCP                     DisplayString,
                sisgm1040284lrtQosDEI                     DisplayString,
                sisgm1040284lrtQosSMAC                    DisplayString,
                sisgm1040284lrtQosDMACType                DisplayString,
                sisgm1040284lrtQosDMACValue               DisplayString,
                sisgm1040284lrtQosQceInnerTag             DisplayString,
                sisgm1040284lrtQosQceInnerVID             DisplayString,
                sisgm1040284lrtQosInnerPCP                DisplayString,
                sisgm1040284lrtQosInnerDEI                DisplayString,
                sisgm1040284lrtQosFrameType               INTEGER,
                sisgm1040284lrtQosMacEtherType            DisplayString,
                sisgm1040284lrtQosLLCSSAPAddr             DisplayString,
                sisgm1040284lrtQosLLCDSAPAddr             DisplayString,
                sisgm1040284lrtQosLLCControl              DisplayString,
                sisgm1040284lrtQosSNAPPID                 DisplayString,
                sisgm1040284lrtQosIpv4Protocol            DisplayString,
                sisgm1040284lrtQosIpv4ProtocolValue       Integer32,
                sisgm1040284lrtQosIpv4ProtocolUDPSPort    DisplayString,
                sisgm1040284lrtQosIpv4ProtocolUDPDPort    DisplayString,
                sisgm1040284lrtQosIpv4ProtocolTCPSPort    DisplayString,
                sisgm1040284lrtQosIpv4ProtocolTCPDPort    DisplayString,
                sisgm1040284lrtQosIpv4SourceIp            DisplayString,
                sisgm1040284lrtQosIpv4SourceMask          DisplayString,
                sisgm1040284lrtQosIpv4IPFragment          INTEGER,
                sisgm1040284lrtQosIpv4DSCP                DisplayString,
                sisgm1040284lrtQosIpv6Protocol            DisplayString,
                sisgm1040284lrtQosIpv6ProtocolValue       Integer32,
                sisgm1040284lrtQosIpv6ProtocolUDPSPort    DisplayString,
                sisgm1040284lrtQosIpv6ProtocolUDPDPort    DisplayString,
                sisgm1040284lrtQosIpv6ProtocolTCPSPort    DisplayString,
                sisgm1040284lrtQosIpv6ProtocolTCPDPort    DisplayString,
                sisgm1040284lrtQosIpv6SourceIp            DisplayString,
                sisgm1040284lrtQosIpv6SourceMask          DisplayString,
                sisgm1040284lrtQosIpv6DSCP                DisplayString,
                sisgm1040284lrtQosActionClass             Integer32,
                sisgm1040284lrtQosActionDPL               Integer32,
                sisgm1040284lrtQosActionDSCP              Integer32,
                sisgm1040284lrtQosActionPCP               Integer32,
                sisgm1040284lrtQosActionDEI               Integer32,
                sisgm1040284lrtQosActionPolicy            Integer32,
                sisgm1040284lrtQosQceRowStatus            RowStatus
                }

    sisgm1040284lrtQosQceIndex OBJECT-TYPE
               SYNTAX      Integer32(1..256)
               MAX-ACCESS  not-accessible
               STATUS      current
               DESCRIPTION
                   "the index to this table."
               ::= {     sisgm1040284lrtQosQceEntry 1 }

    sisgm1040284lrtQosQceID OBJECT-TYPE
               SYNTAX      Integer32(1..256)
               MAX-ACCESS  read-only
               STATUS      current
               DESCRIPTION
                   "If the QCE ID is specified and an entry with this QCE ID
                    already exists, the QCE will be modified. Otherwise, a
                    new QCE will be added.
                    range : 1 - 256."
               ::= {     sisgm1040284lrtQosQceEntry 2 }

    sisgm1040284lrtQosQceList OBJECT-TYPE
               SYNTAX      Integer32(0..256)
               MAX-ACCESS  read-create
               STATUS      current
               DESCRIPTION
                   "If the QCE List is non zero, the QCE will be placed in the list.
                    If the QCE List is zero, the QCE will be placed last in the list.
                    range : 0 - 256."
               ::= {     sisgm1040284lrtQosQceEntry 3 }

    sisgm1040284lrtQosQcePortMembersSwitch OBJECT-TYPE
               SYNTAX      Integer32
               MAX-ACCESS  read-create
               STATUS      current
               DESCRIPTION
                   "Switch number for port members.
                   -1:Any.
                   Only support stacking switch."
               ::= {     sisgm1040284lrtQosQceEntry 4 }

    sisgm1040284lrtQosQcePortMembers OBJECT-TYPE
               SYNTAX      DisplayString
               MAX-ACCESS  read-create
               STATUS      current
               DESCRIPTION
                   "Indicates the ingress port of the QCE. Possible values are:
                    All: The QCE will match all ingress port.
                    Port: The QCE will match a specific ingress port.Format: 1,3-6."
               ::= {     sisgm1040284lrtQosQceEntry 5 }

    sisgm1040284lrtQosQceTag OBJECT-TYPE
               SYNTAX      DisplayString
               MAX-ACCESS  read-create
               STATUS      current
               DESCRIPTION
                  "SERVAL:{'Any', 'Untag' or 'Tag' or 'cTag' or 'sTag'}.
                   Others:{'Any', 'Untag' or 'Tag'}."
               ::= {     sisgm1040284lrtQosQceEntry 6 }

    sisgm1040284lrtQosQceVID OBJECT-TYPE
               SYNTAX      DisplayString
               MAX-ACCESS  read-create
               STATUS      current
               DESCRIPTION
                   "Valid value of VLAN ID can be any value in
                   'Specific 1~4095' or 'range 1-4095' or 'Any'."
               ::= {     sisgm1040284lrtQosQceEntry 7 }

    sisgm1040284lrtQosPCP OBJECT-TYPE
               SYNTAX      DisplayString
               MAX-ACCESS  read-create
               STATUS      current
               DESCRIPTION
                   "Priority Code Point: Valid value PCP are
                    specific(0, 1, 2, 3, 4, 5, 6, 7)
                    or range(0-1, 2-3, 4-5, 6-7, 0-3, 4-7) or 'Any'."
               ::= {     sisgm1040284lrtQosQceEntry 8 }

    sisgm1040284lrtQosDEI OBJECT-TYPE
               SYNTAX      DisplayString
               MAX-ACCESS  read-create
               STATUS      current
               DESCRIPTION
                   "Drop Eligible Indicator: Valid value of DEI can be
                    any of values between 0, 1 or 'Any'."
               ::= {     sisgm1040284lrtQosQceEntry 9 }

    sisgm1040284lrtQosSMAC  OBJECT-TYPE
               SYNTAX      DisplayString
               MAX-ACCESS  read-create
               STATUS      current
               DESCRIPTION
                   "JAGUAR:{Source MAC address: 24 MS bits OUI(00-00-00
                    ~ FF-FF-FF) or 'Any'.}
                    Others:{Source MAC address:  xx-xx-xx-xx-xx-xx or
                    'Any'.}"
               ::= {     sisgm1040284lrtQosQceEntry 10 }

    sisgm1040284lrtQosDMACType OBJECT-TYPE
               SYNTAX      DisplayString
               MAX-ACCESS  read-create
               STATUS      current
               DESCRIPTION
                   "Destination MAC type: possible values are 'UC'(unicast),
                    'MC'(multicast), 'BC'(broadcast) or 'Any'.
                    'SP' only support SERVAL version."
               ::= {     sisgm1040284lrtQosQceEntry 11 }

    sisgm1040284lrtQosDMACValue OBJECT-TYPE
               SYNTAX      DisplayString
               MAX-ACCESS  read-create
               STATUS      current
               DESCRIPTION
                   "when sisgm1040284lrtQosDMACType is 'SP'(specific) can set mac address.
                    Only support SERVAL version."
               ::= {     sisgm1040284lrtQosQceEntry 12 }

    sisgm1040284lrtQosQceInnerTag OBJECT-TYPE
               SYNTAX      DisplayString
               MAX-ACCESS  read-create
               STATUS      current
               DESCRIPTION
                   "Value of Inner Tag field can be 'Any', 'Untag' or 'Tag' or
                    'cTag' or 'sTag'.
                    Only support SERVAL version."
               ::= {     sisgm1040284lrtQosQceEntry 13 }

    sisgm1040284lrtQosQceInnerVID OBJECT-TYPE
               SYNTAX      DisplayString
               MAX-ACCESS  read-create
               STATUS      current
               DESCRIPTION
                   "Valid value of Inner VLAN ID can be any value in
                    'Specific 1~4095' or 'range 1-4095' or 'Any'.
                    Only support SERVAL version."
               ::= {     sisgm1040284lrtQosQceEntry 14 }

    sisgm1040284lrtQosInnerPCP OBJECT-TYPE
               SYNTAX      DisplayString
               MAX-ACCESS  read-create
               STATUS      current
               DESCRIPTION
                   "Valid value Inner PCP are specific(0, 1, 2, 3, 4, 5, 6, 7)
                    or range(0-1, 2-3, 4-5, 6-7, 0-3, 4-7) or 'Any'.
                    Only support SERVAL version."
               ::= {     sisgm1040284lrtQosQceEntry 15 }

    sisgm1040284lrtQosInnerDEI OBJECT-TYPE
               SYNTAX      DisplayString
               MAX-ACCESS  read-create
               STATUS      current
               DESCRIPTION
                   "Valid value of Inner DEI can be any of values between
                    0, 1 or 'Any'.
                    Only support SERVAL version."
               ::= {     sisgm1040284lrtQosQceEntry 16 }

    sisgm1040284lrtQosFrameType OBJECT-TYPE
               SYNTAX      INTEGER {
                            any(1),
                            ethernet(2),
                            llc(3),
                            snap(4),
                            ipv4(5),
                            ipv6(6)
                           }
               MAX-ACCESS  read-create
               STATUS      current
               DESCRIPTION
                   "Frame Type can have any of the following values:
                    1: Any,
                    2: Ethernet,
                    3: LLC,
                    4: SNAP,
                    5: IPv4,
                    6: IPv6."
               ::= {     sisgm1040284lrtQosQceEntry 17 }

    sisgm1040284lrtQosMacEtherType OBJECT-TYPE
               SYNTAX      DisplayString
               MAX-ACCESS  read-create
               STATUS      current
               DESCRIPTION
                   "Valid ethernet type can have a value within 0x600-0xFFFF or 'Any' ,
                    but excluding 0x800(IPv4) and 0x86DD(IPv6),
                    range: 0000-FFFF,
                    default: Any."
               ::= {     sisgm1040284lrtQosQceEntry 18 }

    sisgm1040284lrtQosLLCSSAPAddr OBJECT-TYPE
               SYNTAX      DisplayString
               MAX-ACCESS  read-create
               STATUS      current
               DESCRIPTION
                   "Valid SSAP(Source Service Access Point) can vary from
                    0x00 to 0xFF or 'Any',
                    range: 00-FF,
                    default: Any."
               ::= {     sisgm1040284lrtQosQceEntry 19 }

    sisgm1040284lrtQosLLCDSAPAddr OBJECT-TYPE
               SYNTAX      DisplayString
               MAX-ACCESS  read-create
               STATUS      current
               DESCRIPTION
                   "Valid DSAP(Destination Service Access Point) can
                    vary from 0x00 to 0xFF or 'Any',
                    range: 00-FF,
                    default: Any."
               ::= {     sisgm1040284lrtQosQceEntry 20 }

    sisgm1040284lrtQosLLCControl OBJECT-TYPE
               SYNTAX      DisplayString
               MAX-ACCESS  read-create
               STATUS      current
               DESCRIPTION
                   "Valid Control field can vary from 0x00 to 0xFF or 'Any',
                    range: 00-FF,
                    default: Any."
               ::= {     sisgm1040284lrtQosQceEntry 21 }

    sisgm1040284lrtQosSNAPPID OBJECT-TYPE
               SYNTAX      DisplayString
               MAX-ACCESS  read-create
               STATUS      current
               DESCRIPTION
                   "Valid PID(a.k.a ethernet type) can have value within
                    0x00-0xFFFF or 'Any',
                    range: 0000-FFFF,
                    default: Any."
               ::= {     sisgm1040284lrtQosQceEntry 22 }

   sisgm1040284lrtQosIpv4Protocol OBJECT-TYPE
               SYNTAX      DisplayString
               MAX-ACCESS  read-create
               STATUS      current
               DESCRIPTION
                   "IP protocol number: (Other, TCP or UDP) or 'Any'."
               ::= {     sisgm1040284lrtQosQceEntry 23 }

    sisgm1040284lrtQosIpv4ProtocolValue  OBJECT-TYPE
               SYNTAX      Integer32(0..255)
               MAX-ACCESS  read-create
               STATUS      current
               DESCRIPTION
                   "Ipv4 Protocol is Other.
                    range: 0-255
                    default: 0."
               ::= {     sisgm1040284lrtQosQceEntry 24 }

    sisgm1040284lrtQosIpv4ProtocolUDPSPort OBJECT-TYPE
               SYNTAX      DisplayString
               MAX-ACCESS  read-create
               STATUS      current
               DESCRIPTION
                   "Source  TCP/UDP Port:(0-65535) or 'Any',
                    specific or port range applicable for IP protocol UDP/TCP."
               ::= {     sisgm1040284lrtQosQceEntry 25 }

    sisgm1040284lrtQosIpv4ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sisgm1040284lrtQosQceEntry 26 }

    sisgm1040284lrtQosIpv4ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sisgm1040284lrtQosQceEntry 27 }

    sisgm1040284lrtQosIpv4ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sisgm1040284lrtQosQceEntry 28 }

    sisgm1040284lrtQosIpv4SourceIp OBJECT-TYPE
               SYNTAX      DisplayString
               MAX-ACCESS  read-create
               STATUS      current
               DESCRIPTION
                   "Specific Source IP address in value format or value 0.0.0.0 is 'Any'.
                    if Ipv4 Mask value 0.0.0.0 is 'Any' ,IP address value also is 'Any'.
                    (x.y.z.w),x=0 unless y.z.w also 0,x not is 127 or greater than 223."
               ::= {     sisgm1040284lrtQosQceEntry 29 }

    sisgm1040284lrtQosIpv4SourceMask OBJECT-TYPE
               SYNTAX      DisplayString
               MAX-ACCESS  read-create
               STATUS      current
               DESCRIPTION
                   "Specific Source IP address in mask format or value 0.0.0.0 is 'Any'."
               ::= {     sisgm1040284lrtQosQceEntry 30 }

    sisgm1040284lrtQosIpv4IPFragment OBJECT-TYPE
               SYNTAX      INTEGER { any(0), no(1), yes(2) }
               MAX-ACCESS  read-create
               STATUS      current
               DESCRIPTION
                   "IPv4 frame fragmented option:
                    2: yes,
                    1: no,
                    0: any."
               ::= {     sisgm1040284lrtQosQceEntry 31 }

    sisgm1040284lrtQosIpv4DSCP OBJECT-TYPE
               SYNTAX      DisplayString
               MAX-ACCESS  read-create
               STATUS      current
               DESCRIPTION
                   "Diffserv Code Point value (DSCP): It can be a specific value,
                    range of values or 'Any'. DSCP values are in the range 0-63."
               ::= {     sisgm1040284lrtQosQceEntry 32 }

    sisgm1040284lrtQosIpv6Protocol OBJECT-TYPE
               SYNTAX      DisplayString
               MAX-ACCESS  read-create
               STATUS      current
               DESCRIPTION
                   "IP protocol number: (Other, TCP or UDP) or 'Any'."
               ::= {     sisgm1040284lrtQosQceEntry 33 }

    sisgm1040284lrtQosIpv6ProtocolValue OBJECT-TYPE
               SYNTAX      Integer32(0..255)
               MAX-ACCESS  read-create
               STATUS      current
               DESCRIPTION
                   "when IPv6 protocol is Other ,
                    range: 0-255."
               ::= {     sisgm1040284lrtQosQceEntry 34 }

    sisgm1040284lrtQosIpv6ProtocolUDPSPort OBJECT-TYPE
               SYNTAX      DisplayString
               MAX-ACCESS  read-create
               STATUS      current
               DESCRIPTION
                   "Source TCP/UDP port:(0-65535) or 'Any',
                    specific or port range applicable for IP protocol UDP/TCP."
               ::= {     sisgm1040284lrtQosQceEntry 35 }

    sisgm1040284lrtQosIpv6ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sisgm1040284lrtQosQceEntry 36 }

    sisgm1040284lrtQosIpv6ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sisgm1040284lrtQosQceEntry 37 }


    sisgm1040284lrtQosIpv6ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sisgm1040284lrtQosQceEntry 38 }

    sisgm1040284lrtQosIpv6SourceIp OBJECT-TYPE
               SYNTAX      DisplayString
               MAX-ACCESS  read-create
               STATUS      current
               DESCRIPTION
                   "IPv6 source address: (a.b.c.d) or value 0.0.0.0 is 'Any', 32 LS bits."
               ::= {     sisgm1040284lrtQosQceEntry 39 }

    sisgm1040284lrtQosIpv6SourceMask OBJECT-TYPE
               SYNTAX      DisplayString
               MAX-ACCESS  read-create
               STATUS      current
               DESCRIPTION
                   "IPv6 mask address: (a.b.c.d) or value 0.0.0.0 is 'Any', 32 LS bits."
               ::= {     sisgm1040284lrtQosQceEntry 40 }

    sisgm1040284lrtQosIpv6DSCP OBJECT-TYPE
               SYNTAX      DisplayString
               MAX-ACCESS  read-create
               STATUS      current
               DESCRIPTION
                   "Diffserv Code Point value (DSCP): It can be a specific value,
                    range of values or 'Any'. DSCP values are in the
                    range 0-63 including BE,
                    CS1-CS7, EF or AF11-AF43."
               ::= {     sisgm1040284lrtQosQceEntry 41 }

    sisgm1040284lrtQosActionClass  OBJECT-TYPE
               SYNTAX      Integer32(0..8)
               MAX-ACCESS  read-create
               STATUS      current
               DESCRIPTION
                   "QoS class: (0-7) or 8: Default."
               ::= {     sisgm1040284lrtQosQceEntry 42 }

    sisgm1040284lrtQosActionDPL OBJECT-TYPE
               SYNTAX      Integer32 (0..4)
               MAX-ACCESS  read-create
               STATUS      current
               DESCRIPTION
                   "JAGUAR:{range:0-4. 4: Default}
                    Others:{range:0-2. 2: Default}."
               ::= {     sisgm1040284lrtQosQceEntry 43 }

    sisgm1040284lrtQosActionDSCP OBJECT-TYPE
               SYNTAX      Integer32(0..64)
               MAX-ACCESS  read-create
               STATUS      current
               DESCRIPTION
                   "Valid DSCP value can be (0-63, BE, CS1-CS7,
                    EF or AF11-AF43) or 64: Default."
               ::= {     sisgm1040284lrtQosQceEntry 44 }

    sisgm1040284lrtQosActionPCP  OBJECT-TYPE
               SYNTAX      Integer32(0..8)
               MAX-ACCESS  read-create
               STATUS      current
               DESCRIPTION
                   "pcp: (0-7) or 8: Default.
                    Only support SERVAL version."
               ::= {     sisgm1040284lrtQosQceEntry 45 }

    sisgm1040284lrtQosActionDEI OBJECT-TYPE
               SYNTAX      Integer32 (0..2)
               MAX-ACCESS  read-create
               STATUS      current
               DESCRIPTION
                   "dei: (0-1) or 2: Default.
                    Only support SERVAL version."
               ::= {     sisgm1040284lrtQosQceEntry 46 }

    sisgm1040284lrtQosActionPolicy OBJECT-TYPE
               SYNTAX      Integer32(0..64)
               MAX-ACCESS  read-create
               STATUS      current
               DESCRIPTION
                   "ACL Policy number: (0-63) or 'empty' (64 field). Default: empty.
                    Only support SERVAL version."
               ::= {     sisgm1040284lrtQosQceEntry 47 }

    sisgm1040284lrtQosQceRowStatus OBJECT-TYPE
               SYNTAX      RowStatus
               MAX-ACCESS  read-create
               STATUS      current
               DESCRIPTION
                   "This object indicates the status of this entry, and is used
                   to create/delete entries.  Any object in an entry of this table
                   may be modified while the value of the corresponding instance
                   of this object is active(1).
                   createAndGo, notReady not supported."
               ::= {     sisgm1040284lrtQosQceEntry 48 }

--
-- =======================================================================================================================
-- Start  sisgm1040284lrtQosStormControl group
-- =======================================================================================================================
--sisgm1040284lrtQosStormControlTable
    sisgm1040284lrtQosStormControlTable OBJECT-TYPE
               SYNTAX      SEQUENCE OF     SISGM1040284LRTQosStormControlEntry
               MAX-ACCESS  not-accessible
               STATUS      current
               DESCRIPTION
                   "The basic QoS DSCP Translation settings for all switches."
               ::= {     sisgm1040284lrtQosStormControl  1 }

    sisgm1040284lrtQosStormControlEntry OBJECT-TYPE
               SYNTAX          SISGM1040284LRTQosStormControlEntry
               MAX-ACCESS  not-accessible
               STATUS      current
               DESCRIPTION
                   "The Qos Storm Control Entry."
               INDEX    {     sisgm1040284lrtQosStormControlFrameType  }
               ::= {     sisgm1040284lrtQosStormControlTable 1 }

    SISGM1040284LRTQosStormControlEntry             ::= SEQUENCE {
                sisgm1040284lrtQosStormControlFrameType        INTEGER,
                sisgm1040284lrtQosStormControlEnabled          AdminMode,
                sisgm1040284lrtQosStormControlRate             Integer32,
		sisgm1040284lrtQosStormControlUnit             Integer32
                }

    sisgm1040284lrtQosStormControlFrameType OBJECT-TYPE
               SYNTAX      INTEGER { unicast(1), multicast (2), broadcast (3)}
               MAX-ACCESS  not-accessible
               STATUS      current
               DESCRIPTION
                   "The settings in a particular row apply to the frame type listed here.
                    1:Unicast,
                    2:Multicast,
                    3:Broadcast."
               ::= {     sisgm1040284lrtQosStormControlEntry 1 }

    sisgm1040284lrtQosStormControlEnabled OBJECT-TYPE
               SYNTAX      AdminMode
               MAX-ACCESS  read-write
               STATUS      current
               DESCRIPTION
                  "Enable or disable the global storm policer for the given frame type."
               ::= {     sisgm1040284lrtQosStormControlEntry 2 }

    sisgm1040284lrtQosStormControlRate OBJECT-TYPE
               SYNTAX      Integer32
               MAX-ACCESS  read-write
               STATUS      current
               DESCRIPTION
                   "Controls the rate for the global storm policer."
               ::= {     sisgm1040284lrtQosStormControlEntry 3 }
			   
    sisgm1040284lrtQosStormControlUnit OBJECT-TYPE
               SYNTAX      Integer32
               MAX-ACCESS  read-write
               STATUS      current
               DESCRIPTION
                   "Controls the unit of measure for the global storm policer rate as fps or kfps.
		   0: kbps
		   1: Mbps				   
	           2: fps
                   3: kbps"				   
               ::= {     sisgm1040284lrtQosStormControlEntry 4 }			   

--
-- =======================================================================================================================
-- Start  sisgm1040284lrtQosPortStormControl group
-- =======================================================================================================================
--sisgm1040284lrtQosPortStormControlTable
--    sisgm1040284lrtQosPortStormControlTable OBJECT-TYPE
--               SYNTAX      SEQUENCE OF     SISGM1040284LRTQosPortStormControlEntry
--               MAX-ACCESS  not-accessible
--               STATUS      current
--               DESCRIPTION
--                   "Configure the storm control settings.
--                    INDEX for this table is ifIndex which is
--                    equivalent to the panel port number."
--               ::= {     sisgm1040284lrtQosPortStormControl  1 }
--
--    sisgm1040284lrtQosPortStormControlEntry OBJECT-TYPE
--               SYNTAX      SISGM1040284LRTQosPortStormControlEntry
--               MAX-ACCESS  not-accessible
--               STATUS      current
--               DESCRIPTION
--                   "The Qos Port Storm Control Entry."
--               INDEX    {     ifIndex  }
--               ::= {     sisgm1040284lrtQosPortStormControlTable 1 }
--
--    SISGM1040284LRTQosPortStormControlEntry             ::= SEQUENCE {
--                sisgm1040284lrtQosPortStormControlUnicastEnabled   AdminMode,
--                sisgm1040284lrtQosPortStormControlUnicastRate      Integer32,
--                sisgm1040284lrtQosPortStormControlUnicastUnit      Integer32,
--                sisgm1040284lrtQosPortStormControlBroadcastEnabled AdminMode,
--                sisgm1040284lrtQosPortStormControlBroadcastRate    Integer32,
--                sisgm1040284lrtQosPortStormControlBroadcastUnit    Integer32,
--                sisgm1040284lrtQosPortStormControlUnknownEnabled   AdminMode,
--                sisgm1040284lrtQosPortStormControlUnknownRate      Integer32,
--                sisgm1040284lrtQosPortStormControlUnknownUnit      Integer32
--                }
--
--     sisgm1040284lrtQosPortStormControlUnicastEnabled OBJECT-TYPE
--               SYNTAX      AdminMode
--               MAX-ACCESS  read-write
--               STATUS      current
--               DESCRIPTION
--                  "Controls whether the storm control is enabled on this
--                   switch port."
--               ::= {     sisgm1040284lrtQosPortStormControlEntry 2 }
--
--    sisgm1040284lrtQosPortStormControlUnicastRate OBJECT-TYPE
--               SYNTAX      Integer32
--               MAX-ACCESS  read-write
--               STATUS      current
--               DESCRIPTION
--                   "Controls the rate for the storm control."
--               ::= {     sisgm1040284lrtQosPortStormControlEntry 3 }
--
--    sisgm1040284lrtQosPortStormControlUnicastUnit OBJECT-TYPE
--               SYNTAX      Integer32
--               MAX-ACCESS  read-write
--               STATUS      current
--               DESCRIPTION
--                   "Controls the unit of measure for the storm control rate.
--		   0: kbps
--		   1: Mbps				   
--		   2: fps
--                   3: kbps"
--               ::= {     sisgm1040284lrtQosPortStormControlEntry 4 }
--
--     sisgm1040284lrtQosPortStormControlBroadcastEnabled  OBJECT-TYPE
--               SYNTAX      AdminMode
--               MAX-ACCESS  read-write
--               STATUS      current
--               DESCRIPTION
--                  "Controls whether the storm control is enabled on this
--                   switch port."
--               ::= {     sisgm1040284lrtQosPortStormControlEntry 5 }
--
--    sisgm1040284lrtQosPortStormControlBroadcastRate OBJECT-TYPE
--               SYNTAX      Integer32
--               MAX-ACCESS  read-write
--               STATUS      current
--               DESCRIPTION
--                   "Controls the rate for the storm control."
--               ::= {     sisgm1040284lrtQosPortStormControlEntry 6 }
--
--    sisgm1040284lrtQosPortStormControlBroadcastUnit OBJECT-TYPE
--               SYNTAX      Integer32
--               MAX-ACCESS  read-write
--               STATUS      current
--               DESCRIPTION
--                   "Controls the unit of measure for the storm control rate.
--		   0: kbps
--		   1: Mbps				   
--	           2: fps
--                   3: kbps"
--               ::= {     sisgm1040284lrtQosPortStormControlEntry 7 }
--
--    sisgm1040284lrtQosPortStormControlUnknownEnabled  OBJECT-TYPE
--               SYNTAX      AdminMode
--               MAX-ACCESS  read-write
--               STATUS      current
--               DESCRIPTION
--                  "Controls whether the storm control is enabled on this
--                   switch port."
--               ::= {     sisgm1040284lrtQosPortStormControlEntry 8 }
--
--    sisgm1040284lrtQosPortStormControlUnknownRate OBJECT-TYPE
--               SYNTAX      Integer32
--               MAX-ACCESS  read-write
--               STATUS      current
--               DESCRIPTION
--                   "Controls the rate for the storm control."
--               ::= {     sisgm1040284lrtQosPortStormControlEntry 9 }
--
--    sisgm1040284lrtQosPortStormControlUnknownUnit OBJECT-TYPE
--               SYNTAX      Integer32
--               MAX-ACCESS  read-write
--               STATUS      current
--               DESCRIPTION
--                   "Controls the unit of measure for the storm control rate.
--		   0: kbps
--		   1: Mbps				   
--	           2: fps
--                   3: kbps"
--               ::= {     sisgm1040284lrtQosPortStormControlEntry 10 }

--
-- =======================================================================================================================
-- Start  sisgm1040284lrtQosWRED group
-- =======================================================================================================================
--sisgm1040284lrtQosWREDTable
--    sisgm1040284lrtQosWREDTable OBJECT-TYPE
--               SYNTAX      SEQUENCE OF     SISGM1040284LRTQosWREDEntry
--               MAX-ACCESS  not-accessible
--               STATUS      current
--               DESCRIPTION
--                   "The basic QoS DSCP Translation settings for all switches."
--               ::= {     sisgm1040284lrtQosWRED  1 }
--
--    sisgm1040284lrtQosWREDEntry OBJECT-TYPE
--               SYNTAX          SISGM1040284LRTQosWREDEntry
--               MAX-ACCESS  not-accessible
--               STATUS      current
--               DESCRIPTION
--                   "The Qos WRED Entry."
--               INDEX    {     sisgm1040284lrtQosWREDQueue  }
--               ::= {     sisgm1040284lrtQosWREDTable 1 }
--
--    SISGM1040284LRTQosWREDEntry             ::= SEQUENCE {
--                sisgm1040284lrtQosWREDGroupIndex      Integer32,
--                sisgm1040284lrtQosWREDQueue           Integer32,
--		sisgm1040284lrtQosWREDDPL             Integer32,
--                sisgm1040284lrtQosWREDEnable          AdminMode,
--                sisgm1040284lrtQosWREDMinThreshold    Integer32,
--                sisgm1040284lrtQosWREDMaxThreshold    Integer32,
--                sisgm1040284lrtQosWREDMaxUnit         INTEGER
--                }
--
--    sisgm1040284lrtQosWREDGroupIndex OBJECT-TYPE
--               SYNTAX      Integer32
--               MAX-ACCESS  not-accessible
--               STATUS      current
--               DESCRIPTION
--                   "The group number for which the configuration
--                    below applies."
--               ::= {     sisgm1040284lrtQosWREDEntry 1 }
--
--    sisgm1040284lrtQosWREDQueue OBJECT-TYPE
--               SYNTAX      Integer32
--               MAX-ACCESS  not-accessible
--               STATUS      current
--               DESCRIPTION
--                   "The queue number (QoS class) for which the configuration
--                    below applies."
--               ::= {     sisgm1040284lrtQosWREDEntry 2 }
--
--    sisgm1040284lrtQosWREDDPL OBJECT-TYPE
--               SYNTAX      Integer32
--               MAX-ACCESS  not-accessible
--               STATUS      current
--               DESCRIPTION
--                   "The dpl number for which the configuration
--                    below applies."
--               ::= {     sisgm1040284lrtQosWREDEntry 3 }
--			   
--			   
--    sisgm1040284lrtQosWREDEnable OBJECT-TYPE
--               SYNTAX      AdminMode
--               MAX-ACCESS  read-write
--               STATUS      current
--               DESCRIPTION
--                  "Controls whether RED is enabled for this queue.
--                  "
--               DEFVAL  { disable }
--               ::= {     sisgm1040284lrtQosWREDEntry 4 }
--
--    sisgm1040284lrtQosWREDMinThreshold OBJECT-TYPE
--               SYNTAX      Integer32(0..100)
--               MAX-ACCESS  read-write
--               STATUS      current
--               DESCRIPTION
--                   "Controls the lower RED fill level threshold. If the queue filling
--                    level is below this threshold, the drop probability is zero.
--                    range:0-100%,
--                    default: 0.
--                  "
--               ::= {     sisgm1040284lrtQosWREDEntry 5 }
--
--    sisgm1040284lrtQosWREDMaxThreshold OBJECT-TYPE
--               SYNTAX      Integer32(0..100)
--               MAX-ACCESS  read-write
--               STATUS      current
--               DESCRIPTION
--                   "Controls the upper RED drop probability or fill level threshold
--                    for frames marked with Drop Precedence Level 1 (yellow frames).
--                    range:0-100%,
--                    default: 50.
--                  "
--               ::= {     sisgm1040284lrtQosWREDEntry 6 }
--
--    sisgm1040284lrtQosWREDMaxUnit OBJECT-TYPE
--               SYNTAX      INTEGER {dropProbability (0), fillLevel (1) }
--               MAX-ACCESS  read-write
--               STATUS      current
--               DESCRIPTION
--                   "Selects the unit for Max.
--                    0: Drop Probability,
--                    1: Fill Level,
--                    default: Drop Probability.
--                  "
--               DEFVAL  { dropProbability }
--               ::= {     sisgm1040284lrtQosWREDEntry 7 }

--
-- =======================================================================================================================
-- Start  sisgm1040284lrtQosQCLStatus
-- =======================================================================================================================

--sisgm1040284lrtQosQCLStatusTable
    sisgm1040284lrtQosQCLStatusTable OBJECT-TYPE
               SYNTAX      SEQUENCE OF     SISGM1040284LRTQosQCLStatusEntry
               MAX-ACCESS  not-accessible
               STATUS      current
               DESCRIPTION
                   "The basic QoS DSCP Translation settings for all switches."
               ::= {     sisgm1040284lrtQosQCLStatus 1 }

    sisgm1040284lrtQosQCLStatusEntry OBJECT-TYPE
               SYNTAX          SISGM1040284LRTQosQCLStatusEntry
               MAX-ACCESS  not-accessible
               STATUS      current
               DESCRIPTION
                   "The Qos QCL Status Entry."
               INDEX    {     sisgm1040284lrtQosQCLStatusList  }
               ::= {     sisgm1040284lrtQosQCLStatusTable 1 }

    SISGM1040284LRTQosQCLStatusEntry             ::= SEQUENCE {
                sisgm1040284lrtQosQCLStatusList               Integer32,
                sisgm1040284lrtQosQCLStatusUser               DisplayString,
                sisgm1040284lrtQosQCLStatusQCEId              DisplayString,
                sisgm1040284lrtQosQCLStatusFrameType          DisplayString,
                sisgm1040284lrtQosQCLStatusPortlist           DisplayString,
                sisgm1040284lrtQosQCLStatusActionClass        DisplayString,
                sisgm1040284lrtQosQCLStatusActionDPL          DisplayString,
                sisgm1040284lrtQosQCLStatusActionDSCP         DisplayString,
                sisgm1040284lrtQosQCLStatusActionPCP          DisplayString,
                sisgm1040284lrtQosQCLStatusActionDEL          DisplayString,
                sisgm1040284lrtQosQCLStatusActionPolicy       DisplayString,
                sisgm1040284lrtQosQCLStatusConflict           DisplayString,
		sisgm1040284lrtQosQCLStatusSwitch             Integer32,
		sisgm1040284lrtQosQCLStatusDMAC               DisplayString,
		sisgm1040284lrtQosQCLStatusSMAC               DisplayString,
		sisgm1040284lrtQosQCLStatusTag                DisplayString,
		sisgm1040284lrtQosQCLStatusVID                DisplayString,
		sisgm1040284lrtQosQCLStatusPCP                DisplayString,
		sisgm1040284lrtQosQCLStatusDEI                DisplayString
                }

    sisgm1040284lrtQosQCLStatusList OBJECT-TYPE
               SYNTAX      Integer32(1..4095)
               MAX-ACCESS  not-accessible
               STATUS      current
               DESCRIPTION
                   "QCL table index."
               ::= {     sisgm1040284lrtQosQCLStatusEntry 1}

    sisgm1040284lrtQosQCLStatusUser OBJECT-TYPE
               SYNTAX      DisplayString
               MAX-ACCESS  read-only
               STATUS      current
               DESCRIPTION
                   "Indicates the QCL user."
               ::= {     sisgm1040284lrtQosQCLStatusEntry 2 }

    sisgm1040284lrtQosQCLStatusQCEId OBJECT-TYPE
               SYNTAX      DisplayString
               MAX-ACCESS  read-only
               STATUS      current
               DESCRIPTION
                  "Indicates the index of QCE."
               ::= {     sisgm1040284lrtQosQCLStatusEntry 3}

    sisgm1040284lrtQosQCLStatusFrameType OBJECT-TYPE
               SYNTAX      DisplayString
               MAX-ACCESS  read-only
               STATUS      current
               DESCRIPTION
                   "Indicates the type of frame to look for incomming frames.
                    Any: The QCE will match all frame type.
                    Ethernet: Only Ethernet frames (with Ether Type 0x600-0xFFFF)
                    are allowed.
                    LLC: Only (LLC) frames are allowed.
                    SNAP: Only (SNAP) frames are allowed.
                    IPv4: The QCE will match only IPV4 frames.
                    IPv6: The QCE will match only IPV6 frames."
               ::= {     sisgm1040284lrtQosQCLStatusEntry 4}

    sisgm1040284lrtQosQCLStatusPortlist OBJECT-TYPE
               SYNTAX      DisplayString
               MAX-ACCESS  read-only
               STATUS      current
               DESCRIPTION
                   "Indicates the list of ports configured with the QCE."
               ::= {     sisgm1040284lrtQosQCLStatusEntry 5}

    sisgm1040284lrtQosQCLStatusActionClass OBJECT-TYPE
               SYNTAX      DisplayString
               MAX-ACCESS  read-only
               STATUS      current
               DESCRIPTION
                   "Classified QoS class; if a frame matches the
                    QCE it will be put in the  queue."
               ::= {     sisgm1040284lrtQosQCLStatusEntry 6}

    sisgm1040284lrtQosQCLStatusActionDPL OBJECT-TYPE
               SYNTAX      DisplayString
               MAX-ACCESS  read-only
               STATUS      current
               DESCRIPTION
                   "Drop Precedence Level; if a frame matches the QCE then
                    DP level will set to value displayed under DPL column."
               ::= {     sisgm1040284lrtQosQCLStatusEntry 7}

    sisgm1040284lrtQosQCLStatusActionDSCP OBJECT-TYPE
               SYNTAX      DisplayString
               MAX-ACCESS  read-only
               STATUS      current
               DESCRIPTION
                   "If a frame matches the QCE then DSCP will be
                    classified with the value
                    displayed under DSCP column."
               ::= {     sisgm1040284lrtQosQCLStatusEntry 8}

    sisgm1040284lrtQosQCLStatusActionPCP OBJECT-TYPE
               SYNTAX      DisplayString
               MAX-ACCESS  read-only
               STATUS      current
               DESCRIPTION
                   "Classify PCP value.
                    Only support SERVAL."
               ::= {     sisgm1040284lrtQosQCLStatusEntry 9}

    sisgm1040284lrtQosQCLStatusActionDEL OBJECT-TYPE
               SYNTAX      DisplayString
               MAX-ACCESS  read-only
               STATUS      current
               DESCRIPTION
                   "Classify DEI value.
                    Only support SERVAL."
               ::= {     sisgm1040284lrtQosQCLStatusEntry 10}

    sisgm1040284lrtQosQCLStatusActionPolicy OBJECT-TYPE
               SYNTAX      DisplayString
               MAX-ACCESS  read-only
               STATUS      current
               DESCRIPTION
                   "Classify ACL Policy number.
                    Only support SERVAL."
               ::= {     sisgm1040284lrtQosQCLStatusEntry 11}

    sisgm1040284lrtQosQCLStatusConflict OBJECT-TYPE
               SYNTAX      DisplayString
               MAX-ACCESS  read-only
               STATUS      current
               DESCRIPTION
                   "Displays Conflict status of QCL entries."
               ::= {     sisgm1040284lrtQosQCLStatusEntry 12}

    sisgm1040284lrtQosQCLStatusSwitch OBJECT-TYPE
               SYNTAX      Integer32
               MAX-ACCESS  read-only
               STATUS      current
               DESCRIPTION
                   "Switch number for port members. -1:Any.
                    Only support stacking switch."
               ::= {     sisgm1040284lrtQosQCLStatusEntry 13}
			   
    sisgm1040284lrtQosQCLStatusDMAC OBJECT-TYPE
               SYNTAX      DisplayString
               MAX-ACCESS  read-only
               STATUS      current
               DESCRIPTION
                   "Destination MAC address: Possible values are 'Unicast', 'Multicast', 'Broadcast' or 'Any'."
               ::= {     sisgm1040284lrtQosQCLStatusEntry 14}

    sisgm1040284lrtQosQCLStatusSMAC OBJECT-TYPE
               SYNTAX      DisplayString
               MAX-ACCESS  read-only
               STATUS      current
               DESCRIPTION
                   "Source MAC address: xx-xx-xx-xx-xx-xx or 'Any'."
               ::= {     sisgm1040284lrtQosQCLStatusEntry 15}

    sisgm1040284lrtQosQCLStatusTag OBJECT-TYPE
               SYNTAX      DisplayString
               MAX-ACCESS  read-only
               STATUS      current
               DESCRIPTION
                   "Value of Tag field can be 'Untagged', 'Tagged', 'C-Tagged', 'S-Tagged' or 'Any'."
               ::= {     sisgm1040284lrtQosQCLStatusEntry 16}

    sisgm1040284lrtQosQCLStatusVID OBJECT-TYPE
               SYNTAX      DisplayString
               MAX-ACCESS  read-only
               STATUS      current
               DESCRIPTION
                   "Valid value of VLAN ID can be any value in the range 1-4095 or 'Any'"
               ::= {     sisgm1040284lrtQosQCLStatusEntry 17}			   

    sisgm1040284lrtQosQCLStatusPCP OBJECT-TYPE
               SYNTAX      DisplayString
               MAX-ACCESS  read-only
               STATUS      current
               DESCRIPTION
                   "Valid value PCP are specific (0, 1, 2, 3, 4, 5, 6, 7) or range (0-1, 2-3, 4-5, 6-7, 0-3, 4-7) or 'Any'."
               ::= {     sisgm1040284lrtQosQCLStatusEntry 18}	

    sisgm1040284lrtQosQCLStatusDEI OBJECT-TYPE
               SYNTAX      DisplayString
               MAX-ACCESS  read-only
               STATUS      current
               DESCRIPTION
                   "Valid value of DEI can be '0', '1' or 'Any'."
               ::= {     sisgm1040284lrtQosQCLStatusEntry 19}				   
-- =======================================================================================================================
-- sisgm1040284lrtQosConformance
-- =======================================================================================================================
sisgm1040284lrtQosConformance OBJECT IDENTIFIER ::= { sisgm1040284lrtQosConf 200 }

sisgm1040284lrtQosCompliances OBJECT IDENTIFIER ::= { sisgm1040284lrtQosConformance 1 }

sisgm1040284lrtQosGroups      OBJECT IDENTIFIER ::= { sisgm1040284lrtQosConformance 2 }


sisgm1040284lrtQosPortClassificationGroup OBJECT-GROUP
    OBJECTS {
                --sisgm1040284lrtQosPortClassificationTable
                sisgm1040284lrtQosPortClassificationQoSClass,
                sisgm1040284lrtQosPortClassificationDPlevel,
                sisgm1040284lrtQosPortClassificationPCP,
                sisgm1040284lrtQosPortClassificationDEI,
                sisgm1040284lrtQosPortClassificationTagClass,
                sisgm1040284lrtQosPortClassificationDSCPBased,
                sisgm1040284lrtQosPortClassificationQCLAddr,
                sisgm1040284lrtQosPortClassificationKeyType,

                --sisgm1040284lrtQoSIngressPortTagClassificationTable
                sisgm1040284lrtQoSIngressPortTagQosClass,
                sisgm1040284lrtQoSIngressPortTagDPLevel
            }
    STATUS  current
    DESCRIPTION
            "The collection of objects which are used to indicate
            sisgm1040284lrt qos information."
    ::= { sisgm1040284lrtQosGroups 1}


sisgm1040284lrtQosPortPolicingGroup OBJECT-GROUP
    OBJECTS {
                --sisgm1040284lrtQosPortPolicingTable
                sisgm1040284lrtQosPortPolicingEnabled,
                sisgm1040284lrtQosPortPolicingRate,
                sisgm1040284lrtQosPortPolicingUnit,
                sisgm1040284lrtQosPortPolicingFlowControl
            }
    STATUS  current
    DESCRIPTION
            "The collection of objects which are used to indicate
            sisgm1040284lrt qos information."
    ::= { sisgm1040284lrtQosGroups 2}


sisgm1040284lrtQosQueuePolicingGroup OBJECT-GROUP
    OBJECTS {
                --sisgm1040284lrtQosPortPolicingTable
                sisgm1040284lrtQosQueuePolicingQueue0Enable,
                sisgm1040284lrtQosQueuePolicingQueue0Rate,
                sisgm1040284lrtQosQueuePolicingQueue1Enable,
                sisgm1040284lrtQosQueuePolicingQueue1Rate,
                sisgm1040284lrtQosQueuePolicingQueue2Enable,
                sisgm1040284lrtQosQueuePolicingQueue2Rate,
                sisgm1040284lrtQosQueuePolicingQueue3Enable,
                sisgm1040284lrtQosQueuePolicingQueue3Rate,
                sisgm1040284lrtQosQueuePolicingQueue4Enable,
                sisgm1040284lrtQosQueuePolicingQueue4Rate,
                sisgm1040284lrtQosQueuePolicingQueue5Enable,
                sisgm1040284lrtQosQueuePolicingQueue5Rate,
                sisgm1040284lrtQosQueuePolicingQueue6Enable,
                sisgm1040284lrtQosQueuePolicingQueue6Rate,
                sisgm1040284lrtQosQueuePolicingQueue7Enable,
                sisgm1040284lrtQosQueuePolicingQueue7Rate
            }
    STATUS  current
    DESCRIPTION
            "The collection of objects which are used to indicate
            sisgm1040284lrt qos information."
    ::= { sisgm1040284lrtQosGroups 3}

sisgm1040284lrtQosPortSchedulerGroup OBJECT-GROUP
    OBJECTS {
                --sisgm1040284lrtQosPortSchedulerModeTable
                sisgm1040284lrtQosSchedulerMode,
                sisgm1040284lrtQosSchedulerShaper,
                sisgm1040284lrtQosSchedulerShaperRate,

                --sisgm1040284lrtQosPortSchedulerTable
                 sisgm1040284lrtQosSchedulerPortQueueShaper,
                sisgm1040284lrtQosSchedulerPortQueueShaperRate,
                sisgm1040284lrtQosSchedulerPortQueueShaperExcess,
                sisgm1040284lrtQosSchedulerPortQueueSchedulerWeight,
                sisgm1040284lrtQosSchedulerPortQueueSchedulerPercent,

                --sisgm1040284lrtQosPortEgressTagRemarkingMapTable
                 sisgm1040284lrtQosTagRemarkingPCP,
                 sisgm1040284lrtQosTagRemarkingDEI
            }
    STATUS  current
    DESCRIPTION
            "The collection of objects which are used to indicate
            sisgm1040284lrt qos information."
    ::= { sisgm1040284lrtQosGroups 4}

sisgm1040284lrtQosPortEgressTagRemarkingGroup OBJECT-GROUP
    OBJECTS {
                --sisgm1040284lrtQosPortEgressTagRemarkingTable
                sisgm1040284lrtQosEgressTagRemarkingMode,

                --sisgm1040284lrtQosPortEgressTagRemarkingDefTable
               sisgm1040284lrtQosEgressTagRemarkingDefPCP,
               sisgm1040284lrtQosEgressTagRemarkingDefDEI

               --sisgm1040284lrtQosPortEgressTagRemarkingMapDPTable
--             sisgm1040284lrtQosPortEgressTagRemarkingDPLevel
            }
    STATUS  current
    DESCRIPTION
            "The collection of objects which are used to indicate
            sisgm1040284lrt qos information."
    ::= { sisgm1040284lrtQosGroups 6}


sisgm1040284lrtQosPortDSCPGroup OBJECT-GROUP
    OBJECTS {
                --sisgm1040284lrtQosPortDSCPTable
                sisgm1040284lrtQosPortDSCPIngressTranslate,
                sisgm1040284lrtQosPortDSCPIngressClassify,
                sisgm1040284lrtQosPortDSCPEgressRewrite
            }
    STATUS  current
    DESCRIPTION
            "The collection of objects which are used to indicate
            sisgm1040284lrt qos information."
    ::= { sisgm1040284lrtQosGroups 7}

sisgm1040284lrtQosDSCPGroup OBJECT-GROUP
    OBJECTS {
                --sisgm1040284lrtQosDSCPTable
                sisgm1040284lrtQosBasedDSCP,
                sisgm1040284lrtQosDSCPTrust,
                sisgm1040284lrtQosDSCPQosClass,
                sisgm1040284lrtQosDSCPDPL
             }
    STATUS  current
    DESCRIPTION
            "The collection of objects which are used to indicate
            sisgm1040284lrt qos information."
    ::= { sisgm1040284lrtQosGroups 8}

sisgm1040284lrtQosDSCPTranslationGroup OBJECT-GROUP
    OBJECTS {
                --sisgm1040284lrtQosDSCPTranslationTable
                sisgm1040284lrtQosDSCPTranslationDSCPBasedId,
                sisgm1040284lrtQosDSCPTranslationIngressTranslate,
                sisgm1040284lrtQosDSCPTranslationIngressClassify,
                sisgm1040284lrtQosDSCPTranslationEgressRemapDP0,
                sisgm1040284lrtQosDSCPTranslationEgressRemapDP1
            }
    STATUS  current
    DESCRIPTION
            "The collection of objects which are used to indicate
            sisgm1040284lrt qos information."
    ::= { sisgm1040284lrtQosGroups 9}

--sisgm1040284lrtQosDSCPClassificationGroup OBJECT-GROUP
--    OBJECTS {
--                sisgm1040284lrtQosDSCPClassificationTable
--                sisgm1040284lrtQosDSCPClassificationDSCP
--            }
--    STATUS  current
--    DESCRIPTION
--            "The collection of objects which are used to indicate
--            sisgm1040284lrt qos information."
--    ::= { sisgm1040284lrtQosGroups 10}

sisgm1040284lrtQosControlListGroup OBJECT-GROUP
    OBJECTS {
                --sisgm1040284lrtQosQceTable
                sisgm1040284lrtQosQceID,
                sisgm1040284lrtQosQceList,
                sisgm1040284lrtQosQcePortMembers,
                sisgm1040284lrtQosQceTag,
                sisgm1040284lrtQosQceVID,
                sisgm1040284lrtQosPCP,
                sisgm1040284lrtQosDEI,
                sisgm1040284lrtQosSMAC,
                sisgm1040284lrtQosDMACType,
                sisgm1040284lrtQosDMACValue,
                sisgm1040284lrtQosQceInnerTag,
                sisgm1040284lrtQosQceInnerVID,
                sisgm1040284lrtQosInnerPCP,
                sisgm1040284lrtQosInnerDEI,
                sisgm1040284lrtQosFrameType,
                sisgm1040284lrtQosMacEtherType,
                sisgm1040284lrtQosLLCSSAPAddr,
                sisgm1040284lrtQosLLCDSAPAddr,
                sisgm1040284lrtQosLLCControl,
                sisgm1040284lrtQosSNAPPID,
                sisgm1040284lrtQosIpv4Protocol,
                sisgm1040284lrtQosIpv4ProtocolValue,
                sisgm1040284lrtQosIpv4ProtocolUDPSPort,
                sisgm1040284lrtQosIpv4ProtocolUDPDPort,
                sisgm1040284lrtQosIpv4ProtocolTCPSPort,
                sisgm1040284lrtQosIpv4ProtocolTCPDPort,
                sisgm1040284lrtQosIpv4SourceIp,
                sisgm1040284lrtQosIpv4SourceMask,
                sisgm1040284lrtQosIpv4IPFragment,
                sisgm1040284lrtQosIpv4DSCP,
                sisgm1040284lrtQosIpv6Protocol,
                sisgm1040284lrtQosIpv6ProtocolValue,
                sisgm1040284lrtQosIpv6ProtocolUDPSPort,
                sisgm1040284lrtQosIpv6ProtocolUDPDPort,
                sisgm1040284lrtQosIpv6ProtocolTCPSPort,
                sisgm1040284lrtQosIpv6ProtocolTCPDPort,
                sisgm1040284lrtQosIpv6SourceIp,
                sisgm1040284lrtQosIpv6SourceMask,
                sisgm1040284lrtQosIpv6DSCP,
                sisgm1040284lrtQosActionClass,
                sisgm1040284lrtQosActionDPL,
                sisgm1040284lrtQosActionDSCP,
                sisgm1040284lrtQosActionPCP,
                sisgm1040284lrtQosActionDEI,
                sisgm1040284lrtQosActionPolicy,
                sisgm1040284lrtQosQceRowStatus
            }
    STATUS  current
    DESCRIPTION
            "The collection of objects which are used to indicate
             sisgm1040284lrt qos information."
    ::= { sisgm1040284lrtQosGroups 11}


sisgm1040284lrtQosStormControlGroup OBJECT-GROUP
    OBJECTS {
                --sisgm1040284lrtQosStormControlTable
                sisgm1040284lrtQosStormControlEnabled,
                sisgm1040284lrtQosStormControlRate
            }
    STATUS  current
    DESCRIPTION
            "The collection of objects which are used to indicate
            sisgm1040284lrt qos information."
    ::= { sisgm1040284lrtQosGroups 12}

--sisgm1040284lrtQosPortStormControlGroup OBJECT-GROUP
--    OBJECTS {
--                sisgm1040284lrtQosPortStormControlTable
--                sisgm1040284lrtQosPortStormControlUnicastEnabled,
--                sisgm1040284lrtQosPortStormControlUnicastRate,
--                sisgm1040284lrtQosPortStormControlUnicastUnit,
--                sisgm1040284lrtQosPortStormControlBroadcastEnabled,
--                sisgm1040284lrtQosPortStormControlBroadcastRate,
--                sisgm1040284lrtQosPortStormControlBroadcastUnit,
--                sisgm1040284lrtQosPortStormControlUnknownEnabled,
--                sisgm1040284lrtQosPortStormControlUnknownRate,
--                sisgm1040284lrtQosPortStormControlUnknownUnit
--            }
--    STATUS  current
--    DESCRIPTION
--            "The collection of objects which are used to indicate
--            sisgm1040284lrt qos information."
--    ::= { sisgm1040284lrtQosGroups 13}

--sisgm1040284lrtQosWREDGroup OBJECT-GROUP
--    OBJECTS {
--                sisgm1040284lrtQosWREDTable
--                sisgm1040284lrtQosWREDEnable,
--                sisgm1040284lrtQosWREDMinThreshold,
--
--                sisgm1040284lrtQosWREDMaxThreshold,
--                sisgm1040284lrtQosWREDMaxUnit
--            }
--    STATUS  current
--    DESCRIPTION
--            "The collection of objects which are used to indicate
--            sisgm1040284lrt qos information."
--    ::= { sisgm1040284lrtQosGroups 14}

sisgm1040284lrtQosQCLStatusGroup OBJECT-GROUP
    OBJECTS {
                --sisgm1040284lrtQosQCLStatusTable
                sisgm1040284lrtQosQCLStatusUser,
                sisgm1040284lrtQosQCLStatusQCEId,
                sisgm1040284lrtQosQCLStatusFrameType,
                sisgm1040284lrtQosQCLStatusPortlist,
                sisgm1040284lrtQosQCLStatusActionClass,
                sisgm1040284lrtQosQCLStatusActionDPL,
                sisgm1040284lrtQosQCLStatusActionDSCP,
                sisgm1040284lrtQosQCLStatusActionPCP,
                sisgm1040284lrtQosQCLStatusActionDEL,
                sisgm1040284lrtQosQCLStatusActionPolicy,
                sisgm1040284lrtQosQCLStatusConflict
            }
    STATUS  current
    DESCRIPTION
            "The collection of objects which are used to indicate
            sisgm1040284lrt qos information."
    ::= { sisgm1040284lrtQosGroups 15}

-- =======================================================================================================================

sisgm1040284lrtLoopProtection                                                  OBJECT IDENTIFIER ::= { sisgm1040284lrtConfiguration 12 }

sisgm1040284lrtLoopProtectionConfig                                            OBJECT IDENTIFIER ::= { sisgm1040284lrtLoopProtection 1 }

sisgm1040284lrtLoopProtectionGlobalEnable OBJECT-TYPE
   SYNTAX      Integer32(0|1)
   MAX-ACCESS  read-write
   STATUS      current
   DESCRIPTION
       "Configure loop protection mode.
        0: disable,
        1: enable,
        default: disable. "
   ::= { sisgm1040284lrtLoopProtectionConfig 1 }

sisgm1040284lrtLoopProtectionTranmisstionTime OBJECT-TYPE
   SYNTAX      Integer32(1..10)
   MAX-ACCESS  read-write
   STATUS      current
   DESCRIPTION
       "Configure loop protection transmit interval.
        default: 5,
        range: 1-10. "
   ::= { sisgm1040284lrtLoopProtectionConfig 2 }

sisgm1040284lrtLoopProtectionShutdownTime OBJECT-TYPE
   SYNTAX      Integer32(0..604800)
   MAX-ACCESS  read-write
   STATUS      current
   DESCRIPTION
       "Configure loop protection shutdown time.
        default: 180,
        range: 0-604800. "
   ::= { sisgm1040284lrtLoopProtectionConfig 3 }

sisgm1040284lrtLoopProtectionConfigurationTable OBJECT-TYPE
   SYNTAX      SEQUENCE OF SISGM1040284LRTLoopProtectionConfigurationEntry
   MAX-ACCESS  not-accessible
   STATUS      current
   DESCRIPTION
       " Show Loop Protection configurations. "
   ::= { sisgm1040284lrtLoopProtectionConfig 4 }

sisgm1040284lrtLoopProtectionConfigurationEntry OBJECT-TYPE
   SYNTAX      SISGM1040284LRTLoopProtectionConfigurationEntry
   MAX-ACCESS  not-accessible
   STATUS      current
   DESCRIPTION
       " "
   INDEX    { sisgm1040284lrtLoopProtectionConfPort  }
   ::= { sisgm1040284lrtLoopProtectionConfigurationTable 1 }

SISGM1040284LRTLoopProtectionConfigurationEntry ::= SEQUENCE {
   sisgm1040284lrtLoopProtectionConfPort	    Integer32,
   sisgm1040284lrtLoopProtectionConfEnable	Integer32,
   sisgm1040284lrtLoopProtectionConfAction	Integer32,
   sisgm1040284lrtLoopProtectionConfTxmode	Integer32
}

sisgm1040284lrtLoopProtectionConfPort OBJECT-TYPE
   SYNTAX      Integer32 (1..4095)
   MAX-ACCESS  not-accessible
   STATUS      current
   DESCRIPTION
       " port, range : 1 - port number. "
   ::= { sisgm1040284lrtLoopProtectionConfigurationEntry 1 }

sisgm1040284lrtLoopProtectionConfEnable OBJECT-TYPE
   SYNTAX      Integer32(0|1)
   MAX-ACCESS  read-write
   STATUS      current
   DESCRIPTION
       "Configure loop protection port mode.
        0: disable,
        1: enable,
        default: enable. "
   ::= { sisgm1040284lrtLoopProtectionConfigurationEntry 2 }

sisgm1040284lrtLoopProtectionConfAction OBJECT-TYPE
   SYNTAX      Integer32(0..2)
   MAX-ACCESS  read-write
   STATUS      current
   DESCRIPTION
       " Configure loop protection port action.
         0: Shutdown port,
         1: Shutdown port and Log,
         2: Log Only,
         default: Shutdown port. "
   ::= { sisgm1040284lrtLoopProtectionConfigurationEntry 3 }

sisgm1040284lrtLoopProtectionConfTxmode OBJECT-TYPE
   SYNTAX      Integer32(0|1)
   MAX-ACCESS  read-write
   STATUS      current
   DESCRIPTION
       "Configure loop protection port transmit mode.
        0: disable,
        1: enable,
        default: enable. "
   ::= { sisgm1040284lrtLoopProtectionConfigurationEntry 4 }

sisgm1040284lrtLoopProtectionStatusTable OBJECT-TYPE
   SYNTAX      SEQUENCE OF SISGM1040284LRTLoopProtectionStatusEntry
   MAX-ACCESS  not-accessible
   STATUS      current
   DESCRIPTION
       " Show Loop Protection Status. "
   ::= { sisgm1040284lrtLoopProtection 2 }

sisgm1040284lrtLoopProtectionStatusEntry OBJECT-TYPE
   SYNTAX      SISGM1040284LRTLoopProtectionStatusEntry
   MAX-ACCESS  not-accessible
   STATUS      current
   DESCRIPTION
       " "
   INDEX    { sisgm1040284lrtLoopProtectionStatusPort  }
   ::= { sisgm1040284lrtLoopProtectionStatusTable 1 }

SISGM1040284LRTLoopProtectionStatusEntry ::= SEQUENCE {
   sisgm1040284lrtLoopProtectionStatusPort	       Integer32,
   sisgm1040284lrtLoopProtectionStatusAction	       DisplayString,
   sisgm1040284lrtLoopProtectionStatusTransmit	   DisplayString,
   sisgm1040284lrtLoopProtectionStatusLoops	       Integer32,
   sisgm1040284lrtLoopProtectionStatusStatus	       DisplayString,
   sisgm1040284lrtLoopProtectionStatusLoop	       DisplayString,
   sisgm1040284lrtLoopProtectionStatusTimeLastLoop  DisplayString
}

sisgm1040284lrtLoopProtectionStatusPort OBJECT-TYPE
   SYNTAX      Integer32 (1..4095)
   MAX-ACCESS  not-accessible
   STATUS      current
   DESCRIPTION
       " port, range : 1 - port number. "
   ::= { sisgm1040284lrtLoopProtectionStatusEntry 1 }

sisgm1040284lrtLoopProtectionStatusAction OBJECT-TYPE
   SYNTAX      DisplayString
   MAX-ACCESS  read-only
   STATUS      current
   DESCRIPTION
       " The currently configured port action. "
   ::= { sisgm1040284lrtLoopProtectionStatusEntry 2 }

sisgm1040284lrtLoopProtectionStatusTransmit OBJECT-TYPE
   SYNTAX      DisplayString
   MAX-ACCESS  read-only
   STATUS      current
   DESCRIPTION
       " The currently configured port transmit mode. "
   ::= { sisgm1040284lrtLoopProtectionStatusEntry 3 }

sisgm1040284lrtLoopProtectionStatusLoops OBJECT-TYPE
   SYNTAX      Integer32 (0..1000000)
   MAX-ACCESS  read-only
   STATUS      current
   DESCRIPTION
       " The number of loops detected on this port. "
   ::= { sisgm1040284lrtLoopProtectionStatusEntry 4 }

sisgm1040284lrtLoopProtectionStatusStatus OBJECT-TYPE
   SYNTAX      DisplayString
   MAX-ACCESS  read-only
   STATUS      current
   DESCRIPTION
       " The current loop protection status of the port. "
   ::= { sisgm1040284lrtLoopProtectionStatusEntry 5 }

sisgm1040284lrtLoopProtectionStatusLoop OBJECT-TYPE
   SYNTAX      DisplayString
   MAX-ACCESS  read-only
   STATUS      current
   DESCRIPTION
       " Whether a loop is currently detected on the port. "
   ::= { sisgm1040284lrtLoopProtectionStatusEntry 6 }

sisgm1040284lrtLoopProtectionStatusTimeLastLoop OBJECT-TYPE
   SYNTAX      DisplayString
   MAX-ACCESS  read-only
   STATUS      current
   DESCRIPTION
       " The time of the last loop event detected. "
   ::= { sisgm1040284lrtLoopProtectionStatusEntry 7 }
-- =======================================================================================================================
-- =======================================================================================================================
-- RowStatus Info:  createAndWait, notReady, notInService not supported.
-- =======================================================================================================================
-- Textual Conventions for the sisgm1040284lrt AAA Mib
-- =======================================================================================================================
--
sisgm1040284lrtAAAMIB                   OBJECT IDENTIFIER  ::= { sisgm1040284lrtConfiguration 15 }
    sisgm1040284lrtAAA                  OBJECT IDENTIFIER  ::= { sisgm1040284lrtAAAMIB 1 }
    sisgm1040284lrtRADIUS               OBJECT IDENTIFIER  ::= { sisgm1040284lrtAAA 1 }
    sisgm1040284lrtRADIUSGlobalConfig   OBJECT IDENTIFIER  ::= { sisgm1040284lrtRADIUS 1 }

    sisgm1040284lrtTACACS               OBJECT IDENTIFIER  ::= { sisgm1040284lrtAAA 2 }

--
-- =======================================================================================================================
-- Start sisgm1040284lrtRADIUS group
-- =======================================================================================================================
--sisgm1040284lrtRADIUSGlobalConfig

    sisgm1040284lrtRADIUSGlobalConfigTimeout OBJECT-TYPE
               SYNTAX      Integer32(1..1000)
               MAX-ACCESS  read-write
               STATUS      current
               DESCRIPTION
                   "Timeout is the number of seconds, to wait for a reply
                    from a RADIUS server before retransmitting the request.
                    range: 1-1000."
               ::= {     sisgm1040284lrtRADIUSGlobalConfig 1 }

    sisgm1040284lrtRADIUSGlobalConfigRetransmit OBJECT-TYPE
               SYNTAX      Integer32(1..1000)
               MAX-ACCESS  read-write
               STATUS      current
               DESCRIPTION
                   "Retransmit is the number of times,a RADIUS request is
                    retransmitted to a server that is not responding.If the
                    server has not responded after the last retransmit it is
                    considered to be dead.
                    range: 1-1000."
               ::= {     sisgm1040284lrtRADIUSGlobalConfig 2 }

    sisgm1040284lrtRADIUSGlobalConfigDeadtime OBJECT-TYPE
               SYNTAX      Integer32(0..1440)
               MAX-ACCESS  read-write
               STATUS      current
               DESCRIPTION
                   "This will stop the switch from continually trying to
                    contact a server that it has already determined as dead.
                    range: 0-1440."
               ::= {     sisgm1040284lrtRADIUSGlobalConfig 3 }

    sisgm1040284lrtRADIUSGlobalConfigKey OBJECT-TYPE
               SYNTAX      DisplayString
               MAX-ACCESS  read-write
               STATUS      current
               DESCRIPTION
                   "The secret key shared between the RADIUS server and
                    the switch."
               ::= {     sisgm1040284lrtRADIUSGlobalConfig 4 }

    sisgm1040284lrtRADIUSGlobalConfigNASIPv4 OBJECT-TYPE
               SYNTAX      IpAddress
               MAX-ACCESS  read-write
               STATUS      current
               DESCRIPTION
                   "The IPv4 address to be used as attribute 4 in RADIUS
                    Access-Request packets."
               ::= {     sisgm1040284lrtRADIUSGlobalConfig 5 }

    sisgm1040284lrtRADIUSGlobalConfigNASIPv6 OBJECT-TYPE
               SYNTAX      DisplayString
               MAX-ACCESS  read-write
               STATUS      current
               DESCRIPTION
                   "The IPv6 address to be used as attribute 95 in RADIUS
                    Access-Request packets. "
               ::= {     sisgm1040284lrtRADIUSGlobalConfig 6 }

    sisgm1040284lrtRADIUSGlobalConfigNASIdentifier OBJECT-TYPE
               SYNTAX      DisplayString
               MAX-ACCESS  read-write
               STATUS      current
               DESCRIPTION
                   "The identifier to be used as attribute 32 in RADIUS
                    Access-Request packets. "
               ::= {     sisgm1040284lrtRADIUSGlobalConfig 7 }

--sisgm1040284lrtRADIUSServerConfigTable

    sisgm1040284lrtRADIUSServerConfigTable OBJECT-TYPE
               SYNTAX      SEQUENCE OF     SISGM1040284LRTRADIUSServerConfigEntry
               MAX-ACCESS  not-accessible
               STATUS      current
               DESCRIPTION
                   "The RADIUS Server Configuration Table."
               ::= {     sisgm1040284lrtRADIUS 2 }

    sisgm1040284lrtRADIUSServerConfigEntry OBJECT-TYPE
               SYNTAX          SISGM1040284LRTRADIUSServerConfigEntry
               MAX-ACCESS  not-accessible
               STATUS      current
               DESCRIPTION
                   "The RADIUS Server Configuration Entry."
               INDEX    {    sisgm1040284lrtRADIUSServerConfServerNo  }
               ::= {     sisgm1040284lrtRADIUSServerConfigTable 1 }

    SISGM1040284LRTRADIUSServerConfigEntry             ::= SEQUENCE {
                 sisgm1040284lrtRADIUSServerConfServerNo      Integer32,
                 sisgm1040284lrtRADIUSServerConfHostname      DisplayString,
                 sisgm1040284lrtRADIUSServerConfAuthPort      Integer32,
                 sisgm1040284lrtRADIUSServerConfAcctPort      Integer32,
                 sisgm1040284lrtRADIUSServerConfTimeout       Integer32,
                 sisgm1040284lrtRADIUSServerConfRetransmit    Integer32,
                 sisgm1040284lrtRADIUSServerConfKey           DisplayString,
                 sisgm1040284lrtRADIUSServerConfRowStatus     RowStatus
                 }

    sisgm1040284lrtRADIUSServerConfServerNo OBJECT-TYPE
               SYNTAX      Integer32(1..5)
               MAX-ACCESS  not-accessible
               STATUS      current
               DESCRIPTION
                   "The RADIUS server number.
                    max: 5."
               ::= {     sisgm1040284lrtRADIUSServerConfigEntry 1 }

    sisgm1040284lrtRADIUSServerConfHostname OBJECT-TYPE
               SYNTAX      DisplayString
               MAX-ACCESS  read-create
               STATUS      current
               DESCRIPTION
                   "The IP address or hostname of the RADIUS server. "
               ::= {     sisgm1040284lrtRADIUSServerConfigEntry 2 }

    sisgm1040284lrtRADIUSServerConfAuthPort OBJECT-TYPE
               SYNTAX      Integer32(0..65535)
               MAX-ACCESS  read-create
               STATUS      current
               DESCRIPTION
                   "The UDP port to use on the RADIUS server for
                    authentication.
                    range: 0-65535. "
               ::= {     sisgm1040284lrtRADIUSServerConfigEntry 3 }

    sisgm1040284lrtRADIUSServerConfAcctPort OBJECT-TYPE
               SYNTAX      Integer32(0..65535)
               MAX-ACCESS  read-create
               STATUS      current
               DESCRIPTION
                   "The UDP port to use on the RADIUS server for accounting.
                    range: 0-65535. "
               ::= {     sisgm1040284lrtRADIUSServerConfigEntry 4 }

    sisgm1040284lrtRADIUSServerConfTimeout OBJECT-TYPE
               SYNTAX      Integer32(1..1000)
               MAX-ACCESS  read-create
               STATUS      current
               DESCRIPTION
                   "This optional setting overrides the global timeout value.
                    Leaving it blank will use the global timeout value.
                    range: 1-1000. "
               ::= {     sisgm1040284lrtRADIUSServerConfigEntry 5 }

    sisgm1040284lrtRADIUSServerConfRetransmit OBJECT-TYPE
               SYNTAX      Integer32(1..1000)
               MAX-ACCESS  read-create
               STATUS      current
               DESCRIPTION
                   "This optional setting overrides the global retransmit value.
                    Leaving it blank will use the global retransmit value.
                    range: 1-1000. "
               ::= {     sisgm1040284lrtRADIUSServerConfigEntry 6 }

    sisgm1040284lrtRADIUSServerConfKey OBJECT-TYPE
               SYNTAX      DisplayString
               MAX-ACCESS  read-create
               STATUS      current
               DESCRIPTION
                   "This optional setting overrides the global key. Leaving
                    it blank will use the global key."
               ::= {     sisgm1040284lrtRADIUSServerConfigEntry 7 }

    sisgm1040284lrtRADIUSServerConfRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sisgm1040284lrtRADIUSServerConfigEntry 8 }

--sisgm1040284lrtRADIUSDetailTable

    sisgm1040284lrtRADIUSDetailTable OBJECT-TYPE
               SYNTAX      SEQUENCE OF     SISGM1040284LRTRADIUSDetailEntry
               MAX-ACCESS  not-accessible
               STATUS      current
               DESCRIPTION
                   "The RADIUS Detail Table."
               ::= {     sisgm1040284lrtRADIUS 3 }

    sisgm1040284lrtRADIUSDetailEntry OBJECT-TYPE
               SYNTAX          SISGM1040284LRTRADIUSDetailEntry
               MAX-ACCESS  not-accessible
               STATUS      current
               DESCRIPTION
                   "The RADIUS Detail Entry."
               INDEX    {    sisgm1040284lrtRADIUSServerConfServerNo  }
               ::= {     sisgm1040284lrtRADIUSDetailTable 1 }

    SISGM1040284LRTRADIUSDetailEntry             ::= SEQUENCE {
                 sisgm1040284lrtRADIUSAuthIPAddress               DisplayString,
                 sisgm1040284lrtRADIUSAuthStatus                  DisplayString,
                 sisgm1040284lrtRADIUSAuthRoundTripTime           Integer32,
                 sisgm1040284lrtRADIUSAuthRxAccessAccept          Counter32,
                 sisgm1040284lrtRADIUSAuthRxAccessReject          Counter32,
                 sisgm1040284lrtRADIUSAuthRxAccessChallenge       Counter32,
                 sisgm1040284lrtRADIUSAuthRxAccessResponse        Counter32,
                 sisgm1040284lrtRADIUSAuthRxBadAuth               Counter32,
                 sisgm1040284lrtRADIUSAuthRxUnknownType           Counter32,
                 sisgm1040284lrtRADIUSAuthRxPacketsDropped        Counter32,
                 sisgm1040284lrtRADIUSAuthTxAccessRequest         Counter32,
                 sisgm1040284lrtRADIUSAuthTxAccessRetransmission  Counter32,
                 sisgm1040284lrtRADIUSAuthTxPendingRequest        Counter32,
                 sisgm1040284lrtRADIUSAuthTxTimeout               Counter32,
                 sisgm1040284lrtRADIUSAccountIPAddress            IpAddress,
                 sisgm1040284lrtRADIUSAccountStatus               DisplayString,
                 sisgm1040284lrtRADIUSAccountRoundTripTime        Integer32,
                 sisgm1040284lrtRADIUSAccountRxResponses          Counter32,
                 sisgm1040284lrtRADIUSAccountRxMalformedResponse  Counter32,
                 sisgm1040284lrtRADIUSAccountRxBadAuth            Counter32,
                 sisgm1040284lrtRADIUSAccountRxUnknownType        Counter32,
                 sisgm1040284lrtRADIUSAccountRxPacketsDrop        Counter32,
                 sisgm1040284lrtRADIUSAccountTxRequest            Counter32,
                 sisgm1040284lrtRADIUSAccountTxRetransmission     Counter32,
                 sisgm1040284lrtRADIUSAccountTxPendingRequest     Counter32,
                 sisgm1040284lrtRADIUSAccountTxTimeout            Counter32,
                 sisgm1040284lrtRADIUSDetailClearCmd              ActivateCmd
                 }

    sisgm1040284lrtRADIUSAuthIPAddress OBJECT-TYPE
               SYNTAX      DisplayString
               MAX-ACCESS  read-only
               STATUS      current
               DESCRIPTION
                   "IP address and UDP port for the authentication
                    server in question."
               ::= {     sisgm1040284lrtRADIUSDetailEntry 2 }

    sisgm1040284lrtRADIUSAuthStatus OBJECT-TYPE
               SYNTAX      DisplayString
               MAX-ACCESS  read-only
               STATUS      current
               DESCRIPTION
                   "Shows the state of the server."
               ::= {     sisgm1040284lrtRADIUSDetailEntry 3 }

    sisgm1040284lrtRADIUSAuthRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sisgm1040284lrtRADIUSDetailEntry 4 }

    sisgm1040284lrtRADIUSAuthRxAccessAccept OBJECT-TYPE
               SYNTAX      Counter32
               MAX-ACCESS  read-only
               STATUS      current
               DESCRIPTION
                   "The number of RADIUS Access-Accept packets
                   (valid or invalid) received from the server."
               ::= {     sisgm1040284lrtRADIUSDetailEntry 5 }

    sisgm1040284lrtRADIUSAuthRxAccessReject OBJECT-TYPE
               SYNTAX      Counter32
               MAX-ACCESS  read-only
               STATUS      current
               DESCRIPTION
                   "The number of RADIUS Access-Reject packets
                    (valid or invalid) received from the server."
               ::= {     sisgm1040284lrtRADIUSDetailEntry 6 }

    sisgm1040284lrtRADIUSAuthRxAccessChallenge OBJECT-TYPE
               SYNTAX      Counter32
               MAX-ACCESS  read-only
               STATUS      current
               DESCRIPTION
                   "The number of RADIUS Access-Challenge packets
                    (valid or invalid) received from the server."
               ::= {     sisgm1040284lrtRADIUSDetailEntry 7 }

    sisgm1040284lrtRADIUSAuthRxAccessResponse OBJECT-TYPE
               SYNTAX      Counter32
               MAX-ACCESS  read-only
               STATUS      current
               DESCRIPTION
                   "The number of malformed RADIUS Access-Response
                    packets received from the server."
               ::= {     sisgm1040284lrtRADIUSDetailEntry 8 }

    sisgm1040284lrtRADIUSAuthRxBadAuth OBJECT-TYPE
               SYNTAX      Counter32
               MAX-ACCESS  read-only
               STATUS      current
               DESCRIPTION
                   "The number of RADIUS Access-Response packets containing
                    invalid authenticators or Message Authenticator
                    attributes received from the server."
               ::= {     sisgm1040284lrtRADIUSDetailEntry 9 }

    sisgm1040284lrtRADIUSAuthRxUnknownType OBJECT-TYPE
               SYNTAX      Counter32
               MAX-ACCESS  read-only
               STATUS      current
               DESCRIPTION
                   "The number of RADIUS packets that were received with
                    unknown types from the server on the authentication
                    port and dropped."
               ::= {     sisgm1040284lrtRADIUSDetailEntry 10 }

    sisgm1040284lrtRADIUSAuthRxPacketsDropped OBJECT-TYPE
               SYNTAX      Counter32
               MAX-ACCESS  read-only
               STATUS      current
               DESCRIPTION
                   "The number of RADIUS packets that were received from
                    the server on the authentication port and dropped for
                    some other reason."
               ::= {     sisgm1040284lrtRADIUSDetailEntry 11 }

    sisgm1040284lrtRADIUSAuthTxAccessRequest OBJECT-TYPE
               SYNTAX      Counter32
               MAX-ACCESS  read-only
               STATUS      current
               DESCRIPTION
                   "The number of RADIUS Access-Request packets sent to
                    the server. This does not include retransmissions."
               ::= {     sisgm1040284lrtRADIUSDetailEntry 12 }

    sisgm1040284lrtRADIUSAuthTxAccessRetransmission OBJECT-TYPE
               SYNTAX      Counter32
               MAX-ACCESS  read-only
               STATUS      current
               DESCRIPTION
                   "The number of RADIUS Access-Request packets
                    retransmitted to the RADIUS authentication server."
               ::= {     sisgm1040284lrtRADIUSDetailEntry 13 }

    sisgm1040284lrtRADIUSAuthTxPendingRequest OBJECT-TYPE
               SYNTAX      Counter32
               MAX-ACCESS  read-only
               STATUS      current
               DESCRIPTION
                   "The number of RADIUS Access-Request packets destined
                    for the server that have not yet timed out or received
                    a response. "
               ::= {     sisgm1040284lrtRADIUSDetailEntry 14 }

    sisgm1040284lrtRADIUSAuthTxTimeout OBJECT-TYPE
               SYNTAX      Counter32
               MAX-ACCESS  read-only
               STATUS      current
               DESCRIPTION
                   "The number of authentication timeouts to the server.
                    After a timeout, the client may retry to the same server,
                    send to a different server, or give up."
               ::= {     sisgm1040284lrtRADIUSDetailEntry 15 }

    sisgm1040284lrtRADIUSAccountIPAddress OBJECT-TYPE
               SYNTAX      IpAddress
               MAX-ACCESS  read-only
               STATUS      current
               DESCRIPTION
                   "IP address and UDP port for the authentication server
                    in question."
               ::= {     sisgm1040284lrtRADIUSDetailEntry 16 }

    sisgm1040284lrtRADIUSAccountStatus OBJECT-TYPE
               SYNTAX      DisplayString
               MAX-ACCESS  read-only
               STATUS      current
               DESCRIPTION
                   "Shows the state of the server. "
               ::= {     sisgm1040284lrtRADIUSDetailEntry 17 }

    sisgm1040284lrtRADIUSAccountRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sisgm1040284lrtRADIUSDetailEntry 18 }

    sisgm1040284lrtRADIUSAccountRxResponses OBJECT-TYPE
               SYNTAX      Counter32
               MAX-ACCESS  read-only
               STATUS      current
               DESCRIPTION
                   "The number of RADIUS packets (valid or invalid)
                    received from the server."
               ::= {     sisgm1040284lrtRADIUSDetailEntry 19 }

    sisgm1040284lrtRADIUSAccountRxMalformedResponse OBJECT-TYPE
               SYNTAX      Counter32
               MAX-ACCESS  read-only
               STATUS      current
               DESCRIPTION
                   "The number of malformed RADIUS packets received from
                    the server. "
               ::= {     sisgm1040284lrtRADIUSDetailEntry 20 }

    sisgm1040284lrtRADIUSAccountRxBadAuth OBJECT-TYPE
               SYNTAX      Counter32
               MAX-ACCESS  read-only
               STATUS      current
               DESCRIPTION
                   "The number of RADIUS packets containing invalid
                    authenticators received from the server."
               ::= {     sisgm1040284lrtRADIUSDetailEntry 21 }

    sisgm1040284lrtRADIUSAccountRxUnknownType OBJECT-TYPE
               SYNTAX      Counter32
               MAX-ACCESS  read-only
               STATUS      current
               DESCRIPTION
                   "The number of RADIUS packets of unknown types that were
                    received from the server on the accounting port. "
               ::= {     sisgm1040284lrtRADIUSDetailEntry 22 }

    sisgm1040284lrtRADIUSAccountRxPacketsDrop OBJECT-TYPE
               SYNTAX      Counter32
               MAX-ACCESS  read-only
               STATUS      current
               DESCRIPTION
                   "The number of RADIUS packets that were received from
                    the server on the accounting port and dropped for some
                    other reason."
               ::= {     sisgm1040284lrtRADIUSDetailEntry 23 }

    sisgm1040284lrtRADIUSAccountTxRequest OBJECT-TYPE
               SYNTAX      Counter32
               MAX-ACCESS  read-only
               STATUS      current
               DESCRIPTION
                   "The number of RADIUS packets sent to the server.
                    This does not include retransmissions."
               ::= {     sisgm1040284lrtRADIUSDetailEntry 24 }

    sisgm1040284lrtRADIUSAccountTxRetransmission OBJECT-TYPE
               SYNTAX      Counter32
               MAX-ACCESS  read-only
               STATUS      current
               DESCRIPTION
                   "The number of RADIUS packets retransmitted to the RADIUS
                    accounting server."
               ::= {     sisgm1040284lrtRADIUSDetailEntry 25 }

    sisgm1040284lrtRADIUSAccountTxPendingRequest OBJECT-TYPE
               SYNTAX      Counter32
               MAX-ACCESS  read-only
               STATUS      current
               DESCRIPTION
                   "The number of RADIUS packets destined for the server
                    that have not yet timed out or received a response."
               ::= {     sisgm1040284lrtRADIUSDetailEntry 26 }

    sisgm1040284lrtRADIUSAccountTxTimeout OBJECT-TYPE
               SYNTAX      Counter32
               MAX-ACCESS  read-only
               STATUS      current
               DESCRIPTION
                   "The number of accounting timeouts to the server.
                    After a timeout, the client may retry to the same
                    server, send to a different server, or give up."
               ::= {     sisgm1040284lrtRADIUSDetailEntry 27 }

    sisgm1040284lrtRADIUSDetailClearCmd OBJECT-TYPE
               SYNTAX      ActivateCmd
               MAX-ACCESS  read-only
               STATUS      current
               DESCRIPTION
                   "Clears the counters for the selected server."
               ::= {     sisgm1040284lrtRADIUSDetailEntry 28 }

--
-- =======================================================================================================================
-- Start sisgm1040284lrtTACACS group
-- =======================================================================================================================
--sisgm1040284lrtTACACSGlobalConfig

    sisgm1040284lrtTACACSGlobalConfigTimeout OBJECT-TYPE
               SYNTAX      Integer32(1..1000)
               MAX-ACCESS  read-write
               STATUS      current
               DESCRIPTION
                   "Timeout is the number of seconds,to wait for a reply
                    from a TACACS+ server before it is considered to be dead.
                    range: 1-1000 seconds,
                    default: 5 seconds."
               ::= {     sisgm1040284lrtTACACS 1 }

    sisgm1040284lrtTACACSGlobalConfigDeadtime OBJECT-TYPE
               SYNTAX      Integer32(0..1440)
               MAX-ACCESS  read-write
               STATUS      current
               DESCRIPTION
                   "The period during which the switch will not send new
                    requests to a server that has failed to respond to a
                    previous request. This will stop the switch from
                    continually trying to contact a server that it has
                    already determined as dead.
                    range: 0-1440 minutes,
                    default: 0 minutes."
               ::= {     sisgm1040284lrtTACACS 2 }

    sisgm1040284lrtTACACSGlobalConfigKey OBJECT-TYPE
               SYNTAX      DisplayString
               MAX-ACCESS  read-write
               STATUS      current
               DESCRIPTION
                   "The secret key shared between the TACACS+ server and
                    the switch."
               ::= {     sisgm1040284lrtTACACS 3 }

--sisgm1040284lrtTACACSServerConfigTable

    sisgm1040284lrtTACACSServerConfigTable OBJECT-TYPE
               SYNTAX      SEQUENCE OF     SISGM1040284LRTTACACSServerConfigEntry
               MAX-ACCESS  not-accessible
               STATUS      current
               DESCRIPTION
                   "The TACACS Server configuration Table."
               ::= {     sisgm1040284lrtTACACS 4 }

    sisgm1040284lrtTACACSServerConfigEntry OBJECT-TYPE
               SYNTAX          SISGM1040284LRTTACACSServerConfigEntry
               MAX-ACCESS  not-accessible
               STATUS      current
               DESCRIPTION
                   "The TACACS Server configuration Entry."
               INDEX    {    sisgm1040284lrtTACACSServerConfigServerNo  }
               ::= {     sisgm1040284lrtTACACSServerConfigTable 1 }

    SISGM1040284LRTTACACSServerConfigEntry             ::= SEQUENCE {
                 sisgm1040284lrtTACACSServerConfigServerNo        Integer32,
                 sisgm1040284lrtTACACSServerConfigHostname        DisplayString,
                 sisgm1040284lrtTACACSServerConfigPort            Integer32,
                 sisgm1040284lrtTACACSServerConfigTimeout         Integer32,
                 sisgm1040284lrtTACACSServerConfigKey             DisplayString,
                 sisgm1040284lrtTACACSServerConfigRowStatus       RowStatus
                 }

    sisgm1040284lrtTACACSServerConfigServerNo OBJECT-TYPE
               SYNTAX      Integer32(1..5)
               MAX-ACCESS  not-accessible
               STATUS      current
               DESCRIPTION
                   "The TACACS server number.
                    max: 5."
               ::= {     sisgm1040284lrtTACACSServerConfigEntry 1 }

    sisgm1040284lrtTACACSServerConfigHostname OBJECT-TYPE
               SYNTAX      DisplayString
               MAX-ACCESS  read-create
               STATUS      current
               DESCRIPTION
                   "The IP address or hostname of the TACACS+ server."
               ::= {     sisgm1040284lrtTACACSServerConfigEntry 2 }

    sisgm1040284lrtTACACSServerConfigPort OBJECT-TYPE
               SYNTAX      Integer32(0..65535)
               MAX-ACCESS  read-create
               STATUS      current
               DESCRIPTION
                   "The TCP port to use on the TACACS+ server for
                    authentication."
               ::= {     sisgm1040284lrtTACACSServerConfigEntry 3 }

    sisgm1040284lrtTACACSServerConfigTimeout OBJECT-TYPE
               SYNTAX      Integer32(1..1000)
               MAX-ACCESS  read-create
               STATUS      current
               DESCRIPTION
                   "This optional setting overrides the global timeout
                    value. Leaving it blank will use the global timeout
                    value.
                    range: 1-1000."
               ::= {     sisgm1040284lrtTACACSServerConfigEntry 4 }

    sisgm1040284lrtTACACSServerConfigKey OBJECT-TYPE
               SYNTAX      DisplayString
               MAX-ACCESS  read-create
               STATUS      current
               DESCRIPTION
                   "This optional setting overrides the global key.
                    Leaving it blank will use the global key. "
               ::= {     sisgm1040284lrtTACACSServerConfigEntry 5 }

    sisgm1040284lrtTACACSServerConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sisgm1040284lrtTACACSServerConfigEntry 6 }

-- =======================================================================================================================
--
-- =======================================================================================================================
-- Textual Conventions for the sisgm1040284lrt Nas Mib
-- =======================================================================================================================
--
sisgm1040284lrtNasMIB                   OBJECT IDENTIFIER  ::= { sisgm1040284lrtConfiguration 16 }
    sisgm1040284lrtNAS                  OBJECT IDENTIFIER  ::= { sisgm1040284lrtNasMIB 1 }
    sisgm1040284lrtNASConf              OBJECT IDENTIFIER  ::= { sisgm1040284lrtNAS 1 }
    sisgm1040284lrtNASStatus            OBJECT IDENTIFIER  ::= { sisgm1040284lrtNAS 2 }

--
-- =======================================================================================================================
-- Start sisgm1040284lrtNAS group
-- =======================================================================================================================
--sisgm1040284lrtNASConf

    sisgm1040284lrtNASConfMode OBJECT-TYPE
               SYNTAX      AdminMode
               MAX-ACCESS  read-write
               STATUS      current
               DESCRIPTION
                   "Indicates if NAS is globally enabled or disabled on
                    the switch."
               DEFVAL  { disable }
               ::= {     sisgm1040284lrtNASConf 1 }

    sisgm1040284lrtNASConfReauthenticationEnabled OBJECT-TYPE
               SYNTAX      AdminMode
               MAX-ACCESS  read-write
               STATUS      current
               DESCRIPTION
                   "If enable, successfully authenticated supplicants/clients
                    are reauthenticated after the interval specified by the
                    Reauthentication Period."
               DEFVAL  { disable }
               ::= {     sisgm1040284lrtNASConf 2 }

    sisgm1040284lrtNASConfReauthenticationPeriod OBJECT-TYPE
               SYNTAX      Integer32(1..3600)
               MAX-ACCESS  read-write
               STATUS      current
               DESCRIPTION
                   "Determines the period, in seconds, after which a
                    connected client must be reauthenticated.
                    default: 3600 sec,
                    range: 1-3600 sec."
               ::= {     sisgm1040284lrtNASConf 3 }

    sisgm1040284lrtNASConfEAPOLTimeout OBJECT-TYPE
               SYNTAX      Integer32(1..65535)
               MAX-ACCESS  read-write
               STATUS      current
               DESCRIPTION
                   "Determines the time for retransmission of Request
                    Identity EAPOL frames.
                    default: 30 sec,
                    range: 1-65535 sec."
               ::= {     sisgm1040284lrtNASConf 4 }

    sisgm1040284lrtNASConfAgingPeriod OBJECT-TYPE
               SYNTAX      Integer32(0|10..1000000)
               MAX-ACCESS  read-write
               STATUS      current
               DESCRIPTION
                   "When the NAS module uses the Port Security module to
                    secure MAC addresses, the Port Security module needs to
                    check for activity on the MAC address in question at regular
                    intervals and free resources if no activity is seen within
                    a given period of time.
                    default: 300 sec,
                    0: no support.
                    range: 0,10-1000000 sec."
               ::= {     sisgm1040284lrtNASConf 5 }

    sisgm1040284lrtNASConfHoldTime OBJECT-TYPE
               SYNTAX      Integer32(0|10..1000000)
               MAX-ACCESS  read-write
               STATUS      current
               DESCRIPTION
                   "If a client is denied access - either because the RADIUS
                    server denies the client access or because the RADIUS server
                    request times out - the client is put on hold in the
                    Unauthorized state.
                    default: 10 sec,
                    0: no support.
                    range: 0,10-1000000 sec."
               ::= {     sisgm1040284lrtNASConf 6 }

    sisgm1040284lrtNASConfRADIUSQoSEnabled OBJECT-TYPE
               SYNTAX      AdminMode
               MAX-ACCESS  read-write
               STATUS      current
               DESCRIPTION
                   "RADIUS-assigned QoS provides a means to centrally control
                    the traffic class to which traffic coming from a successfully
                    authenticated supplicant is assigned on the switch."
               DEFVAL  { disable }
               ::= {     sisgm1040284lrtNASConf 7 }

    sisgm1040284lrtNASConfRADIUSVLANEnabled OBJECT-TYPE
               SYNTAX      AdminMode
               MAX-ACCESS  read-write
               STATUS      current
               DESCRIPTION
                   "RADIUS-assigned VLAN provides a means to centrally control
                    the VLAN on which a successfully authenticated supplicant
                    is placed on the switch."
               DEFVAL  { disable }
               ::= {     sisgm1040284lrtNASConf 8 }

    sisgm1040284lrtNASConfGuestVLANEnabled OBJECT-TYPE
               SYNTAX      AdminMode
               MAX-ACCESS  read-write
               STATUS      current
               DESCRIPTION
                   "A Guest VLAN is a special VLAN - typically with limited
                    network access - on which 802.1X-unaware clients are placed
                    after a network administrator-defined timeout."
               DEFVAL  { disable }
               ::= {     sisgm1040284lrtNASConf 9 }

    sisgm1040284lrtNASConfGuestVLANID OBJECT-TYPE
               SYNTAX      Integer32(1..4095)
               MAX-ACCESS  read-write
               STATUS      current
               DESCRIPTION
                   "This is the value that a port's Port VLAN ID is set to if
                    a port is moved into the Guest VLAN.
                    default: 1,
                    range: 1-4095."
               ::= {     sisgm1040284lrtNASConf 10 }

    sisgm1040284lrtNASConfMaxReauthCount OBJECT-TYPE
               SYNTAX      Integer32(1..255)
               MAX-ACCESS  read-write
               STATUS      current
               DESCRIPTION
                   "The number of times the switch transmits an EAPOL Request
                    Identity frame without response before considering entering
                    the Guest VLAN is adjusted with this setting.
                    default: 2,
                    range: 1-255."
               ::= {     sisgm1040284lrtNASConf 11 }

    sisgm1040284lrtNASConfAllowGuestVLAN OBJECT-TYPE
               SYNTAX      AdminMode
               MAX-ACCESS  read-write
               STATUS      current
               DESCRIPTION
                   "The switch remembers if an EAPOL frame has been received
                    on the port for the life-time of the port."
               DEFVAL  { disable }
               ::= {     sisgm1040284lrtNASConf 12 }

--sisgm1040284lrtNASPortConfTable

    sisgm1040284lrtNASPortConfTable OBJECT-TYPE
               SYNTAX      SEQUENCE OF     SISGM1040284LRTNASPortConfEntry
               MAX-ACCESS  not-accessible
               STATUS      current
               DESCRIPTION
                   "The NAS Port Configuration Table.
                    INDEX for this table is ifIndex which is
                    equivalent to the panel port number."
               ::= {     sisgm1040284lrtNASConf 13 }

    sisgm1040284lrtNASPortConfEntry OBJECT-TYPE
               SYNTAX          SISGM1040284LRTNASPortConfEntry
               MAX-ACCESS  not-accessible
               STATUS      current
               DESCRIPTION
                   "The NAS Port Configuration Entry."
               INDEX    {    ifIndex  }
               ::= {     sisgm1040284lrtNASPortConfTable 1 }

    SISGM1040284LRTNASPortConfEntry             ::= SEQUENCE {
                 sisgm1040284lrtNASPortConfAdminState         Integer32,
                 sisgm1040284lrtNASPortConfRADIUSQoSEnabled   AdminMode,
                 sisgm1040284lrtNASPortConfRADIUSVLANEnabled  AdminMode,
                 sisgm1040284lrtNASPortConfGuestVLANEnabled   AdminMode,
                 sisgm1040284lrtNASPortConfPortState          DisplayString,
                 sisgm1040284lrtNASPortConfReauthenticateCmd  INTEGER,
                 sisgm1040284lrtNASPortConfReinitializeCmd    INTEGER
                 }

    sisgm1040284lrtNASPortConfAdminState OBJECT-TYPE
               SYNTAX      Integer32(0..5)
               MAX-ACCESS  read-write
               STATUS      current
               DESCRIPTION
                   "This selection controls the port's authentication mode.
                    0: Force Authorized,
                    1: Force Unauthorized,
                    2: Port-based 802.1X,
                    3: Single 802.1X,
                    4: Multi 802.1X,
                    5: MAC-based Auth,
                    range: 0-5."
               ::= {     sisgm1040284lrtNASPortConfEntry 2 }

    sisgm1040284lrtNASPortConfRADIUSQoSEnabled OBJECT-TYPE
               SYNTAX      AdminMode
               MAX-ACCESS  read-write
               STATUS      current
               DESCRIPTION
                   "When RADIUS-Assigned QoS is both globally enabled and
                    enabled on a given port, the switch reacts to QoS Class
                    information carried in the RADIUS Access-Accept packet
                    transmitted by the RADIUS server when a supplicant is
                    successfully authenticated."
               ::= {     sisgm1040284lrtNASPortConfEntry 3 }

    sisgm1040284lrtNASPortConfRADIUSVLANEnabled OBJECT-TYPE
               SYNTAX      AdminMode
               MAX-ACCESS  read-write
               STATUS      current
               DESCRIPTION
                   "When RADIUS-Assigned VLAN is both globally enabled and
                    enabled for a given port, the switch reacts to VLAN ID
                    information carried in the RADIUS Access-Accept packet
                    transmitted by the RADIUS server when a supplicant is
                    successfully authenticated."
               ::= {     sisgm1040284lrtNASPortConfEntry 4 }

    sisgm1040284lrtNASPortConfGuestVLANEnabled OBJECT-TYPE
               SYNTAX      AdminMode
               MAX-ACCESS  read-write
               STATUS      current
               DESCRIPTION
                   "When Guest VLAN is both globally enabled and enabled for
                    a given port, the switch considers moving the port into
                    the Guest VLAN according to the rules."
               ::= {     sisgm1040284lrtNASPortConfEntry 5 }

    sisgm1040284lrtNASPortConfPortState OBJECT-TYPE
               SYNTAX      DisplayString
               MAX-ACCESS  read-only
               STATUS      current
               DESCRIPTION
                   "The current state of the port."
               ::= {     sisgm1040284lrtNASPortConfEntry 6 }

    sisgm1040284lrtNASPortConfReauthenticateCmd OBJECT-TYPE
               SYNTAX      ActivateCmd
               MAX-ACCESS  read-write
               STATUS      current
               DESCRIPTION
                   "Schedules a reauthentication whenever the quiet-period of
                    the port runs out (EAPOL-based authentication). For
                    MAC-based authentication, reauthentication will be attempted
                    immediately.The button only has effect for successfully
                    authenticated clients on the port and will not cause the
                    clients to get temporarily unauthorized."
               DEFVAL  { noAction }
               ::= {     sisgm1040284lrtNASPortConfEntry 7 }

    sisgm1040284lrtNASPortConfReinitializeCmd OBJECT-TYPE
               SYNTAX      ActivateCmd
               MAX-ACCESS  read-write
               STATUS      current
               DESCRIPTION
                   "Forces a reinitialization of the clients on the port and
                    thereby a reauthentication immediately. The clients will
                    transfer to the unauthorized state while the
                    reauthentication is in progress."
               DEFVAL  { noAction }
               ::= {     sisgm1040284lrtNASPortConfEntry 8 }

--sisgm1040284lrtNASSwitchStatusTable

    sisgm1040284lrtNASSwitchStatusTable OBJECT-TYPE
               SYNTAX      SEQUENCE OF     SISGM1040284LRTNASSwitchStatusEntry
               MAX-ACCESS  not-accessible
               STATUS      current
               DESCRIPTION
                   "The NAS Switch Status Table.
                    INDEX for this table is ifIndex which is
                    equivalent to the panel port number."
               ::= {     sisgm1040284lrtNASStatus 1 }

    sisgm1040284lrtNASSwitchStatusEntry OBJECT-TYPE
               SYNTAX          SISGM1040284LRTNASSwitchStatusEntry
               MAX-ACCESS  not-accessible
               STATUS      current
               DESCRIPTION
                   "The NAS Switch Status Entry."
               INDEX    {    ifIndex  }
               ::= {     sisgm1040284lrtNASSwitchStatusTable 1 }

    SISGM1040284LRTNASSwitchStatusEntry             ::= SEQUENCE {
                 sisgm1040284lrtNASSwitchStatusAdminState   DisplayString,
                 sisgm1040284lrtNASSwitchStatusPortState    DisplayString,
                 sisgm1040284lrtNASSwitchStatusLastSource   DisplayString,
                 sisgm1040284lrtNASSwitchStatusLastID       DisplayString,
                 sisgm1040284lrtNASSwitchStatusQoSClass     DisplayString,
                 sisgm1040284lrtNASSwitchStatusPortVLANID   DisplayString
                 }

    sisgm1040284lrtNASSwitchStatusAdminState OBJECT-TYPE
               SYNTAX      DisplayString
               MAX-ACCESS  read-only
               STATUS      current
               DESCRIPTION
                   "The port's current administrative state."
               ::= {     sisgm1040284lrtNASSwitchStatusEntry 2 }

    sisgm1040284lrtNASSwitchStatusPortState OBJECT-TYPE
               SYNTAX      DisplayString
               MAX-ACCESS  read-only
               STATUS      current
               DESCRIPTION
                   "The current state of the port."
               ::= {     sisgm1040284lrtNASSwitchStatusEntry 3 }

    sisgm1040284lrtNASSwitchStatusLastSource OBJECT-TYPE
               SYNTAX      DisplayString
               MAX-ACCESS  read-only
               STATUS      current
               DESCRIPTION
                   "The source MAC address carried in the most recently
                    received EAPOL frame for EAPOL-based authentication,
                    and the most recently received frame from a new client
                    for MAC-based authentication."
               ::= {     sisgm1040284lrtNASSwitchStatusEntry 4 }

    sisgm1040284lrtNASSwitchStatusLastID OBJECT-TYPE
               SYNTAX      DisplayString
               MAX-ACCESS  read-only
               STATUS      current
               DESCRIPTION
                   "The user name (supplicant identity) carried in the most
                    recently received Response Identity EAPOL frame for
                    EAPOL-based authentication, and the source MAC address
                    from the most recently received frame from a new client
                    for MAC-based authentication."
               ::= {     sisgm1040284lrtNASSwitchStatusEntry 5 }

    sisgm1040284lrtNASSwitchStatusQoSClass OBJECT-TYPE
               SYNTAX      DisplayString
               MAX-ACCESS  read-only
               STATUS      current
               DESCRIPTION
                   "QoS Class assigned to the port by the RADIUS server
                    if enabled."
               ::= {     sisgm1040284lrtNASSwitchStatusEntry 6 }

    sisgm1040284lrtNASSwitchStatusPortVLANID OBJECT-TYPE
               SYNTAX      DisplayString
               MAX-ACCESS  read-only
               STATUS      current
               DESCRIPTION
                   "The VLAN ID that NAS has put the port in."
               ::= {     sisgm1040284lrtNASSwitchStatusEntry 7 }

--sisgm1040284lrtNASPortCounterTable

    sisgm1040284lrtNASPortCounterTable OBJECT-TYPE
               SYNTAX      SEQUENCE OF     SISGM1040284LRTNASPortCounterEntry
               MAX-ACCESS  not-accessible
               STATUS      current
               DESCRIPTION
                   "The NAS Port Counter Table.
                    INDEX for this table is ifIndex which is
                    equivalent to the panel port number."
               ::= {     sisgm1040284lrtNASStatus 2 }

    sisgm1040284lrtNASPortCounterEntry OBJECT-TYPE
               SYNTAX          SISGM1040284LRTNASPortCounterEntry
               MAX-ACCESS  not-accessible
               STATUS      current
               DESCRIPTION
                   "The NAS Port Counter Entry."
               INDEX    {    ifIndex  }
               ::= {     sisgm1040284lrtNASPortCounterTable 1 }

    SISGM1040284LRTNASPortCounterEntry             ::= SEQUENCE {
                 sisgm1040284lrtNASReceiveEAPOLTotal          Integer32,
                 sisgm1040284lrtNASReceiveEAPOLResponseID     Integer32,
                 sisgm1040284lrtNASReceiveEAPOLResponses      Integer32,
                 sisgm1040284lrtNASReceiveEAPOLStart          Integer32,
                 sisgm1040284lrtNASReceiveEAPOLLogoff         Integer32,
                 sisgm1040284lrtNASReceiveEAPOLInvalidType    Integer32,
                 sisgm1040284lrtNASReceiveEAPOLInvalidLength  Integer32,
                 sisgm1040284lrtNASTransmitEAPOLTotal         Integer32,
                 sisgm1040284lrtNASTransmitEAPOLRequestID     Integer32,
                 sisgm1040284lrtNASTransmitEAPOLRequests      Integer32,
                 sisgm1040284lrtNASPortReceiveBackendServerAccessChallenges    Integer32,
                 sisgm1040284lrtNASPortReceiveBackendServerOtherRequests       Integer32,
                 sisgm1040284lrtNASPortReceiveBackendServerAuthSuccesses       Integer32,
                 sisgm1040284lrtNASPortReceiveBackendServerAuthFailures        Integer32,
                 sisgm1040284lrtNASPortTransmitBackendServerResponses          Integer32,
                 sisgm1040284lrtNASSupplicantInfoMAC          DisplayString,
                 sisgm1040284lrtNASSupplicantInfoVlanID       Integer32,
                 sisgm1040284lrtNASSupplicantInfoVersion      Integer32,
                 sisgm1040284lrtNASSupplicantInfoIdentity     DisplayString,
                 sisgm1040284lrtNASPortCounterClearCmd        ActivateCmd
                 }

    sisgm1040284lrtNASReceiveEAPOLTotal OBJECT-TYPE
               SYNTAX      Integer32(-1..1000000)
               MAX-ACCESS  read-only
               STATUS      current
               DESCRIPTION
                   "The number of valid EAPOL frames of any type that have
                    been received by the switch.
                    -1: no support."
               ::= {     sisgm1040284lrtNASPortCounterEntry 2 }

    sisgm1040284lrtNASReceiveEAPOLResponseID OBJECT-TYPE
               SYNTAX      Integer32(-1..1000000)
               MAX-ACCESS  read-only
               STATUS      current
               DESCRIPTION
                   "The number of valid EAPOL Response Identity frames that
                    have been received by the switch.
                    -1: no support."
               ::= {     sisgm1040284lrtNASPortCounterEntry 3 }

    sisgm1040284lrtNASReceiveEAPOLResponses OBJECT-TYPE
               SYNTAX      Integer32(-1..1000000)
               MAX-ACCESS  read-only
               STATUS      current
               DESCRIPTION
                   "The number of valid EAPOL response frames (other than
                    Response Identity frames) that have been received by
                    the switch.
                    -1: no support."
               ::= {     sisgm1040284lrtNASPortCounterEntry 4 }

    sisgm1040284lrtNASReceiveEAPOLStart OBJECT-TYPE
               SYNTAX      Integer32(-1..1000000)
               MAX-ACCESS  read-only
               STATUS      current
               DESCRIPTION
                   "The number of EAPOL Start frames that have been received
                    by the switch.
                    -1: no support."
               ::= {     sisgm1040284lrtNASPortCounterEntry 5 }

    sisgm1040284lrtNASReceiveEAPOLLogoff OBJECT-TYPE
               SYNTAX      Integer32(-1..1000000)
               MAX-ACCESS  read-only
               STATUS      current
               DESCRIPTION
                   "The number of valid EAPOL Logoff frames that have been
                    received by the switch.
                    -1: no support."
               ::= {     sisgm1040284lrtNASPortCounterEntry 6 }

    sisgm1040284lrtNASReceiveEAPOLInvalidType OBJECT-TYPE
               SYNTAX      Integer32(-1..1000000)
               MAX-ACCESS  read-only
               STATUS      current
               DESCRIPTION
                   "The number of EAPOL frames that have been received by
                    the switch in which the frame type is not recognized.
                    -1: no support."
               ::= {     sisgm1040284lrtNASPortCounterEntry 7 }

    sisgm1040284lrtNASReceiveEAPOLInvalidLength OBJECT-TYPE
               SYNTAX      Integer32(-1..1000000)
               MAX-ACCESS  read-only
               STATUS      current
               DESCRIPTION
                   "The number of EAPOL frames that have been received
                    by the switch in which the Packet Body Length field
                    is invalid.
                    -1: no support."
               ::= {     sisgm1040284lrtNASPortCounterEntry 8 }

    sisgm1040284lrtNASTransmitEAPOLTotal OBJECT-TYPE
               SYNTAX      Integer32(-1..1000000)
               MAX-ACCESS  read-only
               STATUS      current
               DESCRIPTION
                   "The number of EAPOL frames of any type that have been
                    transmitted by the switch.
                    -1: no support."
               ::= {     sisgm1040284lrtNASPortCounterEntry 9 }

    sisgm1040284lrtNASTransmitEAPOLRequestID OBJECT-TYPE
               SYNTAX      Integer32(-1..1000000)
               MAX-ACCESS  read-only
               STATUS      current
               DESCRIPTION
                   "The number of EAPOL Request Identity frames that have
                    been transmitted by the switch.
                    -1: no support."
               ::= {     sisgm1040284lrtNASPortCounterEntry 10 }

    sisgm1040284lrtNASTransmitEAPOLRequests OBJECT-TYPE
               SYNTAX      Integer32(-1..1000000)
               MAX-ACCESS  read-only
               STATUS      current
               DESCRIPTION
                   "The number of valid EAPOL Request frames (other than
                    Request Identity frames) that have been transmitted
                    by the switch.
                    -1: no support."
               ::= {     sisgm1040284lrtNASPortCounterEntry 11 }

    sisgm1040284lrtNASPortReceiveBackendServerAccessChallenges OBJECT-TYPE
               SYNTAX      Integer32(-1..1000000)
               MAX-ACCESS  read-only
               STATUS      current
               DESCRIPTION
                   "802.1X-based: Counts the number of times that the switch
                    receives the first request from the backend server following
                    the first response from the supplicant. Indicates that the
                    backend server has communication with the switch.
                    MAC-based:Counts all Access Challenges received from the
                    backend server for this port (left-most table).
                    -1: no support."
               ::= {     sisgm1040284lrtNASPortCounterEntry 12 }

    sisgm1040284lrtNASPortReceiveBackendServerOtherRequests OBJECT-TYPE
               SYNTAX      Integer32(-1..1000000)
               MAX-ACCESS  read-only
               STATUS      current
               DESCRIPTION
                   "802.1X-based: Counts the number of times that the switch
                    sends an EAP Request packet following the first to the
                    supplicant. Indicates that the backend server chose an
                    EAP-method.
                    MAC-based: Not applicable.
                    -1: no support."
               ::= {     sisgm1040284lrtNASPortCounterEntry 13 }

    sisgm1040284lrtNASPortReceiveBackendServerAuthSuccesses OBJECT-TYPE
               SYNTAX      Integer32(-1..1000000)
               MAX-ACCESS  read-only
               STATUS      current
               DESCRIPTION
                   "802.1X- and MAC-based: Counts the number of times that
                    the switch receives a success indication.Indicates that
                    the supplicant has successfully authenticated to
                    the backend server.
                    -1: no support."
               ::= {     sisgm1040284lrtNASPortCounterEntry 14 }

    sisgm1040284lrtNASPortReceiveBackendServerAuthFailures OBJECT-TYPE
               SYNTAX      Integer32(-1..1000000)
               MAX-ACCESS  read-only
               STATUS      current
               DESCRIPTION
                   "802.1X- and MAC-based:Counts the number of times that the
                    switch receives a failure message.This indicates that the
                    supplicant has not authenticated to the backend
                    server.
                    -1: no support."
               ::= {     sisgm1040284lrtNASPortCounterEntry 15 }

    sisgm1040284lrtNASPortTransmitBackendServerResponses OBJECT-TYPE
               SYNTAX      Integer32(-1..1000000)
               MAX-ACCESS  read-only
               STATUS      current
               DESCRIPTION
                   "802.1X-based:Counts the number of times that the switch
                    attempts to send a supplicant's first response packet to
                    the backend server. Indicates the switch attempted
                    communication with the backend server. Possible
                    retransmissions are not counted.
                    MAC-based: Counts all the backend server packets sent from
                    the switch towards the backend server for a given port
                    (left-most table). Possible retransmissions are not
                    counted.
                    -1: no support."
               ::= {     sisgm1040284lrtNASPortCounterEntry 16 }

    sisgm1040284lrtNASSupplicantInfoMAC OBJECT-TYPE
               SYNTAX      DisplayString
               MAX-ACCESS  read-only
               STATUS      current
               DESCRIPTION
                   "The MAC address of the last supplicant. "
               ::= {     sisgm1040284lrtNASPortCounterEntry 17 }

    sisgm1040284lrtNASSupplicantInfoVlanID OBJECT-TYPE
               SYNTAX      Integer32(-1..1000000)
               MAX-ACCESS  read-only
               STATUS      current
               DESCRIPTION
                   "The VLAN ID on which the last frame from the last
                    supplicant was received.
                    -1: no support."
               ::= {     sisgm1040284lrtNASPortCounterEntry 18 }

    sisgm1040284lrtNASSupplicantInfoVersion OBJECT-TYPE
               SYNTAX      Integer32(-1..1000000)
               MAX-ACCESS  read-only
               STATUS      current
               DESCRIPTION
                   "802.1X-based:The protocol version number carried in
                    the most recently received EAPOL frame.
                    MAC-based: Not applicable.
                    -1: no support."
               ::= {     sisgm1040284lrtNASPortCounterEntry 19 }

    sisgm1040284lrtNASSupplicantInfoIdentity OBJECT-TYPE
               SYNTAX      DisplayString
               MAX-ACCESS  read-only
               STATUS      current
               DESCRIPTION
                   "802.1X-based:The user name (supplicant identity) carried
                    in the most recently received Response Identity EAPOL frame.
                    MAC-based: Not applicable. "
               ::= {     sisgm1040284lrtNASPortCounterEntry 20 }

    sisgm1040284lrtNASPortCounterClearCmd OBJECT-TYPE
               SYNTAX      ActivateCmd
               MAX-ACCESS  read-write
               STATUS      current
               DESCRIPTION
                   "Clear the counters for the selected port."
               ::= {     sisgm1040284lrtNASPortCounterEntry 21 }


-- =======================================================================================================================
sisgm1040284lrtMACConf 						OBJECT IDENTIFIER ::= { sisgm1040284lrtConfiguration 17 }

    sisgm1040284lrtMAC                                                    OBJECT IDENTIFIER   ::= { sisgm1040284lrtMACConf 1 }

--
-- =======================================================================================================================
-- Start sisgm1040284lrtMAC group
-- =======================================================================================================================
    sisgm1040284lrtMACDisableAutomaticAging   OBJECT-TYPE
               SYNTAX       AdminMode
               MAX-ACCESS   read-write
               STATUS       current
               DESCRIPTION
                   "Disable the automatic aging of dynamic entries."
                ::= {     sisgm1040284lrtMAC 1 }

    sisgm1040284lrtMACAgingTime  OBJECT-TYPE
               SYNTAX       Integer32 (-1 | 10..1000000)
               MAX-ACCESS   read-write
               STATUS       current
               DESCRIPTION
                   "Configure aging time by entering a value here in seconds.
                   range: 10-1000000 seconds.
                   -1: Automatic Aging is disable."
                ::= {     sisgm1040284lrtMAC 2 }

--sisgm1040284lrtMACLearningTable
    sisgm1040284lrtMACLearningTable OBJECT-TYPE
               SYNTAX      SEQUENCE OF     SISGM1040284LRTMACLearningEntry
               MAX-ACCESS  not-accessible
               STATUS      current
               DESCRIPTION
                   "The mac learning table.
                    INDEX for this table is ifIndex which is
                    equivalent to the panel port number."
               ::= {     sisgm1040284lrtMAC 3 }

    sisgm1040284lrtMACLearningEntry OBJECT-TYPE
               SYNTAX          SISGM1040284LRTMACLearningEntry
               MAX-ACCESS  not-accessible
               STATUS      current
               DESCRIPTION
                   "The mac learning entry."
               INDEX    {     ifIndex  }
               ::= {     sisgm1040284lrtMACLearningTable 1 }

    SISGM1040284LRTMACLearningEntry             ::= SEQUENCE {
                sisgm1040284lrtMACTableLearning     INTEGER
                }

    sisgm1040284lrtMACTableLearning OBJECT-TYPE
               SYNTAX      INTEGER{ auto(0), disable(1), secure(2)}
               MAX-ACCESS  read-write
               STATUS      current
               DESCRIPTION
                   "auto(0)   : Learning is done automatically as soon as a
                                frame with unknown SMAC is received.
                    disable(1): Disable, No learning is done.
                    secure(2) : Secure, Only static MAC entries are learned,
                                all other frames are dropped."
               ::= {     sisgm1040284lrtMACLearningEntry 2 }

--sisgm1040284lrtMACStaticConfigTable
    sisgm1040284lrtMACStaticConfigTable OBJECT-TYPE
               SYNTAX      SEQUENCE OF     SISGM1040284LRTMACStaticConfigEntry
               MAX-ACCESS  not-accessible
               STATUS      current
               DESCRIPTION
                   "The static Mac config table."
               ::= {     sisgm1040284lrtMAC 4 }

    sisgm1040284lrtMACStaticConfigEntry OBJECT-TYPE
               SYNTAX          SISGM1040284LRTMACStaticConfigEntry
               MAX-ACCESS  not-accessible
               STATUS      current
               DESCRIPTION
                   "The static Mac config entry."
               INDEX    {     sisgm1040284lrtMACStaticConfigIndex  }
               ::= {     sisgm1040284lrtMACStaticConfigTable 1 }

    SISGM1040284LRTMACStaticConfigEntry             ::= SEQUENCE {
                sisgm1040284lrtMACStaticConfigSwitchIndex Integer32,
                sisgm1040284lrtMACStaticConfigIndex       Integer32,
                sisgm1040284lrtMACStaticConfigVID         Integer32,
                sisgm1040284lrtMACStaticConfigMACaddress  DisplayString,
                sisgm1040284lrtMACStaticConfigPortList    DisplayString,
                sisgm1040284lrtMACStaticConfigRowStatus   RowStatus
                }

    sisgm1040284lrtMACStaticConfigSwitchIndex OBJECT-TYPE
               SYNTAX      Integer32(1..16)
               MAX-ACCESS  not-accessible
               STATUS      current
               DESCRIPTION
                   "Switch Index."
               ::= {     sisgm1040284lrtMACStaticConfigEntry 1 }



    sisgm1040284lrtMACStaticConfigIndex OBJECT-TYPE
               SYNTAX      Integer32(1..64)
               MAX-ACCESS  not-accessible
               STATUS      current
               DESCRIPTION
                   "The static entries in the MAC table are shown in this table.
                    The static MAC table can contain 64 entries."
               ::= {     sisgm1040284lrtMACStaticConfigEntry 2 }

    sisgm1040284lrtMACStaticConfigVID OBJECT-TYPE
               SYNTAX      Integer32(1..4095)
               MAX-ACCESS  read-create
               STATUS      current
               DESCRIPTION
                   "The VLAN ID of the entry.
                    range: 1-4095."
               ::= {     sisgm1040284lrtMACStaticConfigEntry 3 }

    sisgm1040284lrtMACStaticConfigMACaddress OBJECT-TYPE
               SYNTAX      DisplayString
               MAX-ACCESS  read-create
               STATUS      current
               DESCRIPTION
                   "The MAC address of the entry."
               ::= {     sisgm1040284lrtMACStaticConfigEntry 4 }

    sisgm1040284lrtMACStaticConfigPortList OBJECT-TYPE
               SYNTAX      DisplayString
               MAX-ACCESS  read-create
               STATUS      current
               DESCRIPTION
                   "Checkmarks indicate which ports are members of the entry.
                    Check or uncheck as needed to
                    modify the entry."
               ::= {     sisgm1040284lrtMACStaticConfigEntry 5 }

    sisgm1040284lrtMACStaticConfigRowStatus OBJECT-TYPE
               SYNTAX      RowStatus
               MAX-ACCESS  read-create
               STATUS      current
               DESCRIPTION
                   "This object indicates the status of this entry,
                    and is used to create/delete entries. Any
                    object in an entry of this table may be modified
                    while the value of the corresponding instance
                    of this object is active(1).
                    createAndGo, notReady not supported."
               ::= {     sisgm1040284lrtMACStaticConfigEntry 6 }


-- =======================================================================================================================
sisgm1040284lrtSpanningTree 						OBJECT IDENTIFIER ::= { sisgm1040284lrtConfiguration 18 }

sisgm1040284lrtBridgeSettings                     OBJECT IDENTIFIER ::= { sisgm1040284lrtSpanningTree 1 }

sisgm1040284lrtSTPProtocolVersion    OBJECT-TYPE
               SYNTAX      Integer32
               MAX-ACCESS  read-write
               STATUS      current
               DESCRIPTION
                   "0:STP
				    2:RSTP
					3:MSTP"
               ::= {     sisgm1040284lrtBridgeSettings 1 }

sisgm1040284lrtBridgePriority    OBJECT-TYPE
               SYNTAX      Integer32
               MAX-ACCESS  read-write
               STATUS      current
               DESCRIPTION
                   "Bridge Priority, range: 0-61440, multiple of 4096."
               ::= {     sisgm1040284lrtBridgeSettings 2 }

sisgm1040284lrtBridgeForwardDelay    OBJECT-TYPE
               SYNTAX      Integer32
               MAX-ACCESS  read-write
               STATUS      current
               DESCRIPTION
                   "Bridge Forward Delay, range: 4-30 seconds."
               ::= {     sisgm1040284lrtBridgeSettings 3 }

sisgm1040284lrtBridgeMaxAge    OBJECT-TYPE
               SYNTAX      Integer32
               MAX-ACCESS  read-write
               STATUS      current
               DESCRIPTION
                   "Bridge MaxAge, range:6-40 seconds."
               ::= {     sisgm1040284lrtBridgeSettings 4 }

sisgm1040284lrtBridgeMaxHops    OBJECT-TYPE
               SYNTAX      Integer32
               MAX-ACCESS  read-write
               STATUS      current
               DESCRIPTION
                   "Bridge Max Hops, range:6-40 hops."
               ::= {     sisgm1040284lrtBridgeSettings 5 }

sisgm1040284lrtBridgetxHoldCount    OBJECT-TYPE
               SYNTAX      Integer32
               MAX-ACCESS  read-write
               STATUS      current
               DESCRIPTION
                   "Bridge Transmit Hold Count,range: 1-10 bpdu's per second. "
               ::= {     sisgm1040284lrtBridgeSettings 6 }

sisgm1040284lrtBridgeBPDUFilter    OBJECT-TYPE
               SYNTAX      Integer32
               MAX-ACCESS  read-write
               STATUS      current
               DESCRIPTION
                   "Bridge BPD UFilter
              		0:disable
                    1:enable					"
               ::= {     sisgm1040284lrtBridgeSettings 7 }

sisgm1040284lrtBridgeBPDUGuard    OBJECT-TYPE
               SYNTAX      Integer32
               MAX-ACCESS  read-write
               STATUS      current
               DESCRIPTION
                   "Bridge BPDU Guard
              		0:disable
                    1:enable					   "
               ::= {     sisgm1040284lrtBridgeSettings 8 }

sisgm1040284lrtBridgeerrorRecoveryDelay    OBJECT-TYPE
               SYNTAX      Integer32
               MAX-ACCESS  read-write
               STATUS      current
               DESCRIPTION
                   "Bridge error Recovery Delay
				   range:30-86400 seconds
				   0:disable
				   "
               ::= {     sisgm1040284lrtBridgeSettings 9 }

sisgm1040284lrtBridgeHelloTime    OBJECT-TYPE
               SYNTAX      Integer32
               MAX-ACCESS  read-write
               STATUS      current
               DESCRIPTION
                   "The interval between sending STP BPDU's. Valid values are in the range 1 to 10 seconds, 
				   default:2 seconds."
               ::= {     sisgm1040284lrtBridgeSettings 10 }			   

sisgm1040284lrtMSTIMapping                        OBJECT IDENTIFIER ::= { sisgm1040284lrtSpanningTree 2 }
sisgm1040284lrtConfigName    OBJECT-TYPE
               SYNTAX      DisplayString
               MAX-ACCESS  read-write
               STATUS      current
               DESCRIPTION
                   "Configuration Name, identify the VLAN to MSTI mapping"
               ::= {     sisgm1040284lrtMSTIMapping 1 }

sisgm1040284lrtConfigRevision    OBJECT-TYPE
               SYNTAX      Integer32
               MAX-ACCESS  read-write
               STATUS      current
               DESCRIPTION
                   "Configuration Revision. range:0-65535 "
               ::= {     sisgm1040284lrtMSTIMapping 2 }

sisgm1040284lrtMSTIMappingVLAN                    OBJECT IDENTIFIER ::= { sisgm1040284lrtSpanningTree 3 }
sisgm1040284lrtConfigMstiName1    OBJECT-TYPE
               SYNTAX      DisplayString
               MAX-ACCESS  read-write
               STATUS      current
               DESCRIPTION
                   "The list of VLANs mapped to the MSTI1.
				    The VLANs can be given as a single (xx, xx being between 1 and 4094) VLAN, or a range (xx-yy), each of which must be separated with comma and/or space. "
               ::= {     sisgm1040284lrtMSTIMappingVLAN 1 }

sisgm1040284lrtConfigMstiName2    OBJECT-TYPE
               SYNTAX      DisplayString
               MAX-ACCESS  read-write
               STATUS      current
               DESCRIPTION
                   "The list of VLANs mapped to the MSTI2.
				    The VLANs can be given as a single (xx, xx being between 1 and 4094) VLAN, or a range (xx-yy), each of which must be separated with comma and/or space.  "
               ::= {     sisgm1040284lrtMSTIMappingVLAN 2 }

sisgm1040284lrtConfigMstiName3    OBJECT-TYPE
               SYNTAX      DisplayString
               MAX-ACCESS  read-write
               STATUS      current
               DESCRIPTION
                   "The list of VLANs mapped to the MSTI3.
				    The VLANs can be given as a single (xx, xx being between 1 and 4094) VLAN, or a range (xx-yy), each of which must be separated with comma and/or space. "
               ::= {     sisgm1040284lrtMSTIMappingVLAN 3 }

sisgm1040284lrtConfigMstiName4    OBJECT-TYPE
               SYNTAX      DisplayString
               MAX-ACCESS  read-write
               STATUS      current
               DESCRIPTION
                   "The list of VLANs mapped to the MSTI4.
				    The VLANs can be given as a single (xx, xx being between 1 and 4094) VLAN, or a range (xx-yy), each of which must be separated with comma and/or space. "
               ::= {     sisgm1040284lrtMSTIMappingVLAN 4 }

sisgm1040284lrtConfigMstiName5    OBJECT-TYPE
               SYNTAX      DisplayString
               MAX-ACCESS  read-write
               STATUS      current
               DESCRIPTION
                   "The list of VLANs mapped to the MSTI5.
				    The VLANs can be given as a single (xx, xx being between 1 and 4094) VLAN, or a range (xx-yy), each of which must be separated with comma and/or space. "
               ::= {     sisgm1040284lrtMSTIMappingVLAN 5 }

sisgm1040284lrtConfigMstiName6    OBJECT-TYPE
               SYNTAX      DisplayString
               MAX-ACCESS  read-write
               STATUS      current
               DESCRIPTION
                   "The list of VLANs mapped to the MSTI6.
				    The VLANs can be given as a single (xx, xx being between 1 and 4094) VLAN, or a range (xx-yy), each of which must be separated with comma and/or space. "
               ::= {     sisgm1040284lrtMSTIMappingVLAN 6 }

sisgm1040284lrtConfigMstiName7    OBJECT-TYPE
               SYNTAX      DisplayString
               MAX-ACCESS  read-write
               STATUS      current
               DESCRIPTION
                   "The list of VLANs mapped to the MSTI7.
				    The VLANs can be given as a single (xx, xx being between 1 and 4094) VLAN, or a range (xx-yy), each of which must be separated with comma and/or space. "
               ::= {     sisgm1040284lrtMSTIMappingVLAN 7 }

sisgm1040284lrtMSTIPriorities                     OBJECT IDENTIFIER ::= { sisgm1040284lrtSpanningTree 4 }

sisgm1040284lrtCSTIPriority   OBJECT-TYPE
               SYNTAX      Integer32
               MAX-ACCESS  read-write
               STATUS      current
               DESCRIPTION
                   "CSTI Priority. range: 0-61440, multiple of 4096. Lower numeric values have better priority."
               ::= {     sisgm1040284lrtMSTIPriorities 1 }

sisgm1040284lrtMSTI1Priority   OBJECT-TYPE
               SYNTAX      Integer32
               MAX-ACCESS  read-write
               STATUS      current
               DESCRIPTION
                   "MSTI1 Priority. range: 0-61440, multiple of 4096. Lower numeric values have better priority."
               ::= {     sisgm1040284lrtMSTIPriorities 2 }

sisgm1040284lrtMSTI2Priority   OBJECT-TYPE
               SYNTAX      Integer32
               MAX-ACCESS  read-write
               STATUS      current
               DESCRIPTION
                   "MSTI2 Priority. range: 0-61440, multiple of 4096. Lower numeric values have better priority."
               ::= {     sisgm1040284lrtMSTIPriorities 3 }

sisgm1040284lrtMSTI3Priority   OBJECT-TYPE
               SYNTAX      Integer32
               MAX-ACCESS  read-write
               STATUS      current
               DESCRIPTION
                   "MSTI3 Priority. range: 0-61440, multiple of 4096. Lower numeric values have better priority."
               ::= {     sisgm1040284lrtMSTIPriorities 4 }
sisgm1040284lrtMSTI4Priority   OBJECT-TYPE
               SYNTAX      Integer32
               MAX-ACCESS  read-write
               STATUS      current
               DESCRIPTION
                   "MSTI4 Priority. range: 0-61440, multiple of 4096. Lower numeric values have better priority."
               ::= {     sisgm1040284lrtMSTIPriorities 5 }
sisgm1040284lrtMSTI5Priority   OBJECT-TYPE
               SYNTAX      Integer32
               MAX-ACCESS  read-write
               STATUS      current
               DESCRIPTION
                   "MSTI5 Priority. range: 0-61440, multiple of 4096. Lower numeric values have better priority."
               ::= {     sisgm1040284lrtMSTIPriorities 6 }

sisgm1040284lrtMSTI6Priority   OBJECT-TYPE
               SYNTAX      Integer32
               MAX-ACCESS  read-write
               STATUS      current
               DESCRIPTION
                   "MSTI6 Priority. range: 0-61440, multiple of 4096. Lower numeric values have better priority."
               ::= {     sisgm1040284lrtMSTIPriorities 7 }
sisgm1040284lrtMSTI7Priority   OBJECT-TYPE
               SYNTAX      Integer32
               MAX-ACCESS  read-write
               STATUS      current
               DESCRIPTION
                   "MSTI7 Priority. range: 0-61440, multiple of 4096. Lower numeric values have better priority."
               ::= {     sisgm1040284lrtMSTIPriorities 8 }


sisgm1040284lrtCISTPorts                          OBJECT IDENTIFIER ::= { sisgm1040284lrtSpanningTree 5 }

sisgm1040284lrtCISTAggregatedEnable   OBJECT-TYPE
               SYNTAX      Integer32 (0|1)
               MAX-ACCESS  read-write
               STATUS      current
               DESCRIPTION
                   "CIST Port Enable. range: 0-1.
				   0:disable
				   1:enable."
               ::= {     sisgm1040284lrtCISTPorts 1 }

sisgm1040284lrtCISTAggregatedPathCost   OBJECT-TYPE
               SYNTAX      Integer32 (0..200000000)
               MAX-ACCESS  read-write
               STATUS      current
               DESCRIPTION
                   "CIST Port Path Cost. range: 0-200000000. 0 is Auto."
               ::= {     sisgm1040284lrtCISTPorts 2 }

sisgm1040284lrtCISTAggregatedPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sisgm1040284lrtCISTPorts 3 }

sisgm1040284lrtCISTAggregatedAdminEdge   OBJECT-TYPE
               SYNTAX      Integer32 (0|1)
               MAX-ACCESS  read-write
               STATUS      current
               DESCRIPTION
                   "CIST Port Admin Edge. range: 0-1.
				   0:Non-Edge
				   1:Edge."
               ::= {     sisgm1040284lrtCISTPorts 4 }

sisgm1040284lrtCISTAggregatedAutoEdge   OBJECT-TYPE
               SYNTAX      Integer32 (0|1)
               MAX-ACCESS  read-write
               STATUS      current
               DESCRIPTION
                   "CIST Port Auto Edge. range: 0-1.
				   0:disable
				   1:enable."
               ::= {     sisgm1040284lrtCISTPorts 5 }

sisgm1040284lrtCISTAggregatedrestrictedRole   OBJECT-TYPE
               SYNTAX      Integer32 (0|1)
               MAX-ACCESS  read-write
               STATUS      current
               DESCRIPTION
                   "CIST Port restricted Role. range: 0-1.
				   0:disable
				   1:enable."
               ::= {     sisgm1040284lrtCISTPorts 6 }

sisgm1040284lrtCISTAggregatedrestrictedTcn   OBJECT-TYPE
               SYNTAX      Integer32 (0|1)
               MAX-ACCESS  read-write
               STATUS      current
               DESCRIPTION
                   "CIST Port restricted Tcn. range: 0-1.
				   0:disable
				   1:enable."
               ::= {     sisgm1040284lrtCISTPorts 7 }

sisgm1040284lrtCISTAggregatedbpduGuard   OBJECT-TYPE
               SYNTAX      Integer32 (0|1)
               MAX-ACCESS  read-write
               STATUS      current
               DESCRIPTION
                   "CIST Port bpdu Guard. range: 0-1.
				   0:disable
				   1:enable."
               ::= {     sisgm1040284lrtCISTPorts 8 }

sisgm1040284lrtCISTAggregatedPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sisgm1040284lrtCISTPorts 9 }


sisgm1040284lrtCISTPortsTable OBJECT-TYPE
   SYNTAX      SEQUENCE OF SISGM1040284LRTCISTPortsEntry
   MAX-ACCESS  not-accessible
   STATUS      current
   DESCRIPTION
        "CIST port table."
    ::= { sisgm1040284lrtCISTPorts 10 }

sisgm1040284lrtCISTPortsEntry OBJECT-TYPE
    SYNTAX        SISGM1040284LRTCISTPortsEntry
    MAX-ACCESS    not-accessible
    STATUS        current
    DESCRIPTION
        "An entry in the CIST Ports Table."
    INDEX        { sisgm1040284lrtCISTPortIndex }
    ::= { sisgm1040284lrtCISTPortsTable 1 }

SISGM1040284LRTCISTPortsEntry ::=
    SEQUENCE {
        sisgm1040284lrtCISTPortIndex                 Integer32,
        sisgm1040284lrtCISTPortEnable                Integer32,
        sisgm1040284lrtCISTPortPathCost              Integer32,
        sisgm1040284lrtCISTPortPortPriority          Integer32,
        sisgm1040284lrtCISTPortAdminEdge             Integer32,
        sisgm1040284lrtCISTPortAutoEdge              Integer32,
        sisgm1040284lrtCISTPortrestrictedRole        Integer32,
        sisgm1040284lrtCISTPortrestrictedTcn         Integer32,
        sisgm1040284lrtCISTPortbpduGuard             Integer32,
        sisgm1040284lrtCISTPortPointToPoint          Integer32
    }

sisgm1040284lrtCISTPortIndex   OBJECT-TYPE
               SYNTAX      Integer32 (1..53)
               MAX-ACCESS  not-accessible
               STATUS      current
               DESCRIPTION
                   "CIST Port Index. range: 1-53. 53 is Aggregated Port Configuration."
               ::= {     sisgm1040284lrtCISTPortsEntry 1 }

sisgm1040284lrtCISTPortEnable   OBJECT-TYPE
               SYNTAX      Integer32 (0|1)
               MAX-ACCESS  read-write
               STATUS      current
               DESCRIPTION
                   "CIST Port Enable. range: 0-1.
				   0:disable
				   1:enable."
               ::= {     sisgm1040284lrtCISTPortsEntry 2 }

sisgm1040284lrtCISTPortPathCost   OBJECT-TYPE
               SYNTAX      Integer32 (0..200000000)
               MAX-ACCESS  read-write
               STATUS      current
               DESCRIPTION
                   "CIST Port Path Cost. range: 0-200000000. 0 is Auto."
               ::= {     sisgm1040284lrtCISTPortsEntry 3 }

sisgm1040284lrtCISTPortPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sisgm1040284lrtCISTPortsEntry 4 }

sisgm1040284lrtCISTPortAdminEdge   OBJECT-TYPE
               SYNTAX      Integer32 (0|1)
               MAX-ACCESS  read-write
               STATUS      current
               DESCRIPTION
                   "CIST Port Admin Edge. range: 0-1.
				   0:Non-Edge
				   1:Edge."
               ::= {     sisgm1040284lrtCISTPortsEntry 5 }

sisgm1040284lrtCISTPortAutoEdge   OBJECT-TYPE
               SYNTAX      Integer32 (0|1)
               MAX-ACCESS  read-write
               STATUS      current
               DESCRIPTION
                   "CIST Port Auto Edge. range: 0-1.
				   0:disable
				   1:enable."
               ::= {     sisgm1040284lrtCISTPortsEntry 6 }

sisgm1040284lrtCISTPortrestrictedRole   OBJECT-TYPE
               SYNTAX      Integer32 (0|1)
               MAX-ACCESS  read-write
               STATUS      current
               DESCRIPTION
                   "CIST Port restricted Role. range: 0-1.
				   0:disable
				   1:enable."
               ::= {     sisgm1040284lrtCISTPortsEntry 7 }

sisgm1040284lrtCISTPortrestrictedTcn   OBJECT-TYPE
               SYNTAX      Integer32 (0|1)
               MAX-ACCESS  read-write
               STATUS      current
               DESCRIPTION
                   "CIST Port restricted Tcn. range: 0-1.
				   0:disable
				   1:enable."
               ::= {     sisgm1040284lrtCISTPortsEntry 8 }

sisgm1040284lrtCISTPortbpduGuard   OBJECT-TYPE
               SYNTAX      Integer32 (0|1)
               MAX-ACCESS  read-write
               STATUS      current
               DESCRIPTION
                   "CIST Port bpdu Guard. range: 0-1.
				   0:disable
				   1:enable."
               ::= {     sisgm1040284lrtCISTPortsEntry 9 }

sisgm1040284lrtCISTPortPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sisgm1040284lrtCISTPortsEntry 10 }

sisgm1040284lrtMSTIPorts                          OBJECT IDENTIFIER ::= { sisgm1040284lrtSpanningTree 6 }


sisgm1040284lrtMSTIAggregatedPortsTable OBJECT-TYPE
   SYNTAX      SEQUENCE OF SISGM1040284LRTMSTIAggregatedPortsEntry
   MAX-ACCESS  not-accessible
   STATUS      current
   DESCRIPTION
       "A table of MSTI ports."
    ::= { sisgm1040284lrtMSTIPorts 1 }

sisgm1040284lrtMSTIAggregatedPortsEntry OBJECT-TYPE
    SYNTAX        SISGM1040284LRTMSTIAggregatedPortsEntry
    MAX-ACCESS    not-accessible
    STATUS        current
    DESCRIPTION
        "An entry in the MSTI ports Table."
    INDEX        { sisgm1040284lrtMSTIAggregatedPortsMSTIndex }
    ::= { sisgm1040284lrtMSTIAggregatedPortsTable 1 }

SISGM1040284LRTMSTIAggregatedPortsEntry ::=
    SEQUENCE {
        sisgm1040284lrtMSTIAggregatedPortsMSTIndex                        Integer32,
        sisgm1040284lrtMSTIAggregatedPortsPathCost                        Integer32,
        sisgm1040284lrtMSTIAggregatedPortsPortPriority                    Integer32
    }

sisgm1040284lrtMSTIAggregatedPortsMSTIndex OBJECT-TYPE
   SYNTAX      Integer32 (1..7)
   MAX-ACCESS  not-accessible
   STATUS      current
   DESCRIPTION
       "MST index, range:1-7"
   ::= {sisgm1040284lrtMSTIAggregatedPortsEntry 1 }

sisgm1040284lrtMSTIAggregatedPortsPathCost   OBJECT-TYPE
   SYNTAX      Integer32 (0..200000000)
   MAX-ACCESS  read-write
   STATUS      current
   DESCRIPTION
       "MST Path Cost. range: 0-200000000. 0 is Auto."
   ::= {sisgm1040284lrtMSTIAggregatedPortsEntry 3 }

sisgm1040284lrtMSTIAggregatedPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sisgm1040284lrtMSTIAggregatedPortsEntry 4 }


sisgm1040284lrtMSTIPortsTable OBJECT-TYPE
   SYNTAX      SEQUENCE OF SISGM1040284LRTMSTIPortsEntry
   MAX-ACCESS  not-accessible
   STATUS      current
   DESCRIPTION
       "A table of MSTI ports."
    ::= { sisgm1040284lrtMSTIPorts 2 }

sisgm1040284lrtMSTIPortsEntry OBJECT-TYPE
    SYNTAX        SISGM1040284LRTMSTIPortsEntry
    MAX-ACCESS    not-accessible
    STATUS        current
    DESCRIPTION
        "An entry in the MSTI ports Table."
    INDEX        { sisgm1040284lrtMSTIPortsMSTIndex, sisgm1040284lrtMSTIPortsPortIndex }
    ::= { sisgm1040284lrtMSTIPortsTable 1 }

SISGM1040284LRTMSTIPortsEntry ::=
    SEQUENCE {
        sisgm1040284lrtMSTIPortsMSTIndex                        Integer32,
        sisgm1040284lrtMSTIPortsPortIndex                       Integer32,
        sisgm1040284lrtMSTIPortsPathCost                        Integer32,
        sisgm1040284lrtMSTIPortsPortPriority                    Integer32
    }

sisgm1040284lrtMSTIPortsMSTIndex OBJECT-TYPE
   SYNTAX      Integer32 (1..7)
   MAX-ACCESS  not-accessible
   STATUS      current
   DESCRIPTION
       "MST index, range:1-7"
   ::= {sisgm1040284lrtMSTIPortsEntry 1 }

sisgm1040284lrtMSTIPortsPortIndex OBJECT-TYPE
   SYNTAX      Integer32 (1..53)
   MAX-ACCESS  not-accessible
   STATUS      current
   DESCRIPTION
       "Port index, range 1-53, 53 is Aggregated Ports Configuration."
   ::= {sisgm1040284lrtMSTIPortsEntry 2 }

sisgm1040284lrtMSTIPortsPathCost   OBJECT-TYPE
   SYNTAX      Integer32 (0..200000000)
   MAX-ACCESS  read-write
   STATUS      current
   DESCRIPTION
       "MST Path Cost. range: 0-200000000. 0 is Auto."
   ::= {sisgm1040284lrtMSTIPortsEntry 3 }

sisgm1040284lrtMSTIPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sisgm1040284lrtMSTIPortsEntry 4 }

-- =======================================================================================================================
sisgm1040284lrtPrivateVLANs 						OBJECT IDENTIFIER ::= { sisgm1040284lrtConfiguration 19 }

sisgm1040284lrtPVLANMembershipTable  OBJECT-TYPE
   SYNTAX      SEQUENCE OF SISGM1040284LRTPVLANMembershipEntry
   MAX-ACCESS  not-accessible
   STATUS      current
   DESCRIPTION
       "A table of Private VLAN Membership."
 ::= { sisgm1040284lrtPrivateVLANs 1 }

sisgm1040284lrtPVLANMembershipEntry OBJECT-TYPE
    SYNTAX        SISGM1040284LRTPVLANMembershipEntry
    MAX-ACCESS    not-accessible
    STATUS        current
    DESCRIPTION
        "An entry in the private VLAN table."
    INDEX        { sisgm1040284lrtPVLANMembershipIndex }
    ::= { sisgm1040284lrtPVLANMembershipTable 1 }

SISGM1040284LRTPVLANMembershipEntry ::=
    SEQUENCE {
        sisgm1040284lrtPVLANMembershipIndex                    Integer32,
        sisgm1040284lrtPVLANID                                 Integer32,
        sisgm1040284lrtPVLANMembers                            DisplayString,
        sisgm1040284lrtPVLANRowStatus                          RowStatus
    }

sisgm1040284lrtPVLANMembershipIndex OBJECT-TYPE
   SYNTAX      Integer32 (1..28)
   MAX-ACCESS  not-accessible
   STATUS      current
   DESCRIPTION
       "PVLAN membership index. Range:1-28."
   ::= {sisgm1040284lrtPVLANMembershipEntry 1 }

sisgm1040284lrtPVLANID OBJECT-TYPE
   SYNTAX      Integer32 (1..28)
   MAX-ACCESS  read-create
   STATUS      current
   DESCRIPTION
       "PVLAN ID. Range:1-28."
   ::= {sisgm1040284lrtPVLANMembershipEntry 2 }

sisgm1040284lrtPVLANMembers OBJECT-TYPE
   SYNTAX      DisplayString
   MAX-ACCESS  read-create
   STATUS      current
   DESCRIPTION
       "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
   ::= {sisgm1040284lrtPVLANMembershipEntry 3 }

sisgm1040284lrtPVLANRowStatus OBJECT-TYPE
   SYNTAX      RowStatus
   MAX-ACCESS  read-create
   STATUS      current
   DESCRIPTION
       "PVLAN Row Status."
   ::= {sisgm1040284lrtPVLANMembershipEntry 4 }

sisgm1040284lrtPVLANPortIsolationTable  OBJECT-TYPE
   SYNTAX      SEQUENCE OF SISGM1040284LRTPVLANPortIsolationEntry
   MAX-ACCESS  not-accessible
   STATUS      current
   DESCRIPTION
       "A table of Private VLAN Port Isolation."
 ::= { sisgm1040284lrtPrivateVLANs 2 }

sisgm1040284lrtPVLANPortIsolationEntry OBJECT-TYPE
    SYNTAX        SISGM1040284LRTPVLANPortIsolationEntry
    MAX-ACCESS    not-accessible
    STATUS        current
    DESCRIPTION
        "An entry in the private VLAN table."
    INDEX        { sisgm1040284lrtPVLANPortIsolationIndex }
    ::= { sisgm1040284lrtPVLANPortIsolationTable 1 }

SISGM1040284LRTPVLANPortIsolationEntry ::=
    SEQUENCE {
        sisgm1040284lrtPVLANPortIsolationIndex                 Integer32,
        sisgm1040284lrtPVLANPortIsolationPortMembers           Integer32
    }

sisgm1040284lrtPVLANPortIsolationIndex OBJECT-TYPE
   SYNTAX      Integer32 (1..28)
   MAX-ACCESS  not-accessible
   STATUS      current
   DESCRIPTION
       "PVLAN Port Isolation Index. Range:1-28."
   ::= {sisgm1040284lrtPVLANPortIsolationEntry 1 }

sisgm1040284lrtPVLANPortIsolationPortMembers OBJECT-TYPE
   SYNTAX      Integer32 (0|1)
   MAX-ACCESS  read-write
   STATUS      current
   DESCRIPTION
       "PVLAN Port Isolation Port Members enable/disable. Range:0-1.
	   1:Port Isolation enable  on that port.
	   0:Port Isolation disable on that port."
   ::= {sisgm1040284lrtPVLANPortIsolationEntry 2 }

-- =======================================================================================================================


sisgm1040284lrtsFlow 						OBJECT IDENTIFIER ::= { sisgm1040284lrtConfiguration 20 }

      sisgm1040284lrtsFlowVersion OBJECT-TYPE
              SYNTAX      SnmpAdminString
              MAX-ACCESS  read-only
              STATUS      current
              DESCRIPTION "Uniquely identifies the version and implementation of this MIB. The version string must have the following structure: <MIB Version>;<Organization>;<Software Revision> where: <MIB Version>  must be '1.3', the version of this MIB.
                    <Organization> the name of the organization responsible for the agent implementation. <Revision>     the specific software build of this agent.
                 As an example, the string '1.3;InMon Corp.;2.1.1' indicates that this agent implements version '1.2' of the SFLOW MIB, that
                 it was developed by 'InMon Corp.' and that the software build is '2.1.1'.
                 The MIB Version will change with each revision of the SFLOW MIB.
                 Management entities must check the MIB Version and not attempt to manage agents with MIB Versions greater than that for which
                 they were designed.
                 Note: The sFlow Datagram Format has an independent version number which may change independently from <MIB Version>.
                       <MIB Version> applies to the structure and semantics of the SFLOW MIB only." DEFVAL { "1.3;;" }
              ::= { sisgm1040284lrtsFlow 1 }

      sisgm1040284lrtsFlowAgentAddressType OBJECT-TYPE
              SYNTAX      InetAddressType
              MAX-ACCESS  read-only
              STATUS      current
              DESCRIPTION "The address type of the address associated with this agent. Only ipv4 and ipv6 types are supported. ipv4:1, ipv6:2."
              ::= { sisgm1040284lrtsFlow 2 }

      sisgm1040284lrtsFlowAgentAddress OBJECT-TYPE
              SYNTAX      IpAddress
              MAX-ACCESS  read-write
              STATUS      current
              DESCRIPTION "The IP address associated with this agent. In the case of a multi-homed agent, this should be the loopback address of the
                 agent. The sFlowAgent address must provide SNMP connectivity to the agent. The address should be an invariant that does not
                 change as interfaces are reconfigured, enabled, disabled, added or removed. A manager should be able to use the
                 sFlowAgentAddress as a unique key that will identify this agent over extended periods of time so that a history can
                 be maintained."
              ::= { sisgm1040284lrtsFlow 3 }
      --
      -- Receiver Table
      --
      sisgm1040284lrtsFlowRcvrTable OBJECT-TYPE
              SYNTAX      SEQUENCE OF SISGM1040284LRTSFlowRcvrEntry
              MAX-ACCESS  not-accessible
              STATUS      current
              DESCRIPTION "A table of the receivers of sFlow information."
              ::= { sisgm1040284lrtsFlow 4 }

      sisgm1040284lrtsFlowRcvrEntry OBJECT-TYPE
              SYNTAX SISGM1040284LRTSFlowRcvrEntry
              MAX-ACCESS  not-accessible
              STATUS      current
              DESCRIPTION "Attributes of an sFlow Receiver."
              INDEX { sisgm1040284lrtsFlowRcvrIndex }
              ::= { sisgm1040284lrtsFlowRcvrTable 1 }

      SISGM1040284LRTSFlowRcvrEntry ::= SEQUENCE {
              sisgm1040284lrtsFlowRcvrIndex                    Integer32,
              sisgm1040284lrtsFlowRcvrOwner                    OwnerString,
              sisgm1040284lrtsFlowRcvrTimeout                  Integer32,
              sisgm1040284lrtsFlowRcvrMaximumDatagramSize      Integer32,
              sisgm1040284lrtsFlowRcvrAddressType              InetAddressType,
              sisgm1040284lrtsFlowRcvrAddress                  IpAddress,
              sisgm1040284lrtsFlowRcvrPort                     Integer32,
              sisgm1040284lrtsFlowRcvrDatagramVersion          Integer32 }

      sisgm1040284lrtsFlowRcvrIndex OBJECT-TYPE
              SYNTAX      Integer32 (1..65535)
              MAX-ACCESS  not-accessible
              STATUS      current
              DESCRIPTION "Index into sFlowReceiverTable."
              ::= { sisgm1040284lrtsFlowRcvrEntry 1 }

      sisgm1040284lrtsFlowRcvrOwner OBJECT-TYPE
              SYNTAX      OwnerString
              MAX-ACCESS  read-write
              STATUS      current
              DESCRIPTION "The entity making use of this sFlowRcvrTable entry. The empty string indicates that the entry is currently unclaimed.
                 An entity wishing to claim an sFlowRcvrTable entry must ensure that the entry is unclaimed before trying to claim it.
                 The entry is claimed by setting the owner string. The entry must be claimed before any changes can be made to other sampler
                 objects.
                 In order to avoid a race condition, the entity taking control of the sampler must set both the owner and a value for
                 sFlowRcvrTimeout in the same SNMP set request.
                 When a management entity is finished using the sampler, it should set the value of sFlowRcvrOwner back to unclaimed.
                 The agent must restore all other entities this row to their default values when the owner is set to unclaimed. It must
                 also free all other resources associated with this sFlowRcvrTable entry.
                 This mechanism provides no enforcement and relies on the cooperation of management entities in order to ensure that
                 competition for a receiver entry is fairly resolved." DEFVAL { "" }
              ::= { sisgm1040284lrtsFlowRcvrEntry 2 }

      sisgm1040284lrtsFlowRcvrTimeout OBJECT-TYPE
              SYNTAX      Integer32
              MAX-ACCESS  read-write
              STATUS      current
              DESCRIPTION "The time (in seconds) remaining before the sampler is released and stops sampling. When set, the owner establishes control
                 for the specified period. When read, the remaining time in the interval is returned.
                 A management entity wanting to maintain control of the sampler is responsible for setting a new value before the old one
                 expires.
                 When the interval expires, the agent is responsible for restoring all other entities in this row to their default
                 values. It must also free all other resources associated with this sFlowRcvrTable entry." DEFVAL { 0 }
              ::= { sisgm1040284lrtsFlowRcvrEntry 3 }

      sisgm1040284lrtsFlowRcvrMaximumDatagramSize OBJECT-TYPE
              SYNTAX      Integer32
              MAX-ACCESS  read-write
              STATUS      current
              DESCRIPTION "The maximum number of data bytes that can be sent in a single sample datagram. The manager should set this value to avoid fragmentation of the sFlow datagrams." DEFVAL { 1400 }
              ::= { sisgm1040284lrtsFlowRcvrEntry 4 }

      sisgm1040284lrtsFlowRcvrAddressType OBJECT-TYPE
              SYNTAX      InetAddressType
              MAX-ACCESS  read-write
              STATUS      current
              DESCRIPTION "The type of sFlowRcvrCollectorAddress." DEFVAL { ipv4 }
              ::= { sisgm1040284lrtsFlowRcvrEntry 5 }

      sisgm1040284lrtsFlowRcvrAddress OBJECT-TYPE
              SYNTAX      IpAddress
              MAX-ACCESS  read-write
              STATUS      current
              DESCRIPTION "The IP address of the sFlow collector. If set to 0.0.0.0 not sFlow datagrams will be sent." DEFVAL { '00000000'h }  -- 0.0.0.0
              ::= { sisgm1040284lrtsFlowRcvrEntry 6 }

      sisgm1040284lrtsFlowRcvrPort OBJECT-TYPE
              SYNTAX      Integer32
              MAX-ACCESS  read-write
              STATUS      current
              DESCRIPTION "The destination port for sFlow datagrams." DEFVAL { 6343 }
              ::= { sisgm1040284lrtsFlowRcvrEntry 7 }

      sisgm1040284lrtsFlowRcvrDatagramVersion OBJECT-TYPE
              SYNTAX      Integer32
              MAX-ACCESS  read-write
              STATUS      current
              DESCRIPTION "The version of sFlow datagrams that should be sent.
                 When set to a value not support by the agent, the agent should adjust the value to the highest supported value less than the
                 requested value, or return an SNMP bad value error if no such value exists." DEFVAL { 5 }
              ::= { sisgm1040284lrtsFlowRcvrEntry 8 }

      --
      -- Flow Sampling Table
      --
      sisgm1040284lrtsFlowFsTable OBJECT-TYPE
              SYNTAX      SEQUENCE OF SISGM1040284LRTSFlowFsEntry
              MAX-ACCESS  not-accessible
              STATUS      current
              DESCRIPTION "A table of the flow samplers within a device."
              ::= { sisgm1040284lrtsFlow 5 }

      sisgm1040284lrtsFlowFsEntry OBJECT-TYPE
              SYNTAX      SISGM1040284LRTSFlowFsEntry
              MAX-ACCESS  not-accessible
              STATUS      current
              DESCRIPTION "Attributes of a flow sampler."
              INDEX { sisgm1040284lrtsFlowFsDataSource, sisgm1040284lrtsFlowFsInstance }
              ::= { sisgm1040284lrtsFlowFsTable 1 }

      SISGM1040284LRTSFlowFsEntry ::= SEQUENCE {
              sisgm1040284lrtsFlowFsDataSource               OBJECT IDENTIFIER,
              sisgm1040284lrtsFlowFsInstance                 Integer32,
              sisgm1040284lrtsFlowFsReceiver                 Integer32,
              sisgm1040284lrtsFlowFsPacketSamplingRate       Integer32,
              sisgm1040284lrtsFlowFsMaximumHeaderSize        Integer32,
              sisgm1040284lrtsFlowFsType                     Integer32
              }

      sisgm1040284lrtsFlowFsDataSource OBJECT-TYPE
              SYNTAX      OBJECT IDENTIFIER
              MAX-ACCESS  not-accessible
              STATUS      current
              DESCRIPTION "sFlowDataSource for this flow sampler."
              ::= { sisgm1040284lrtsFlowFsEntry 1 }

      sisgm1040284lrtsFlowFsInstance OBJECT-TYPE
              SYNTAX      Integer32 (1..65535)
              MAX-ACCESS  not-accessible
              STATUS      current
              DESCRIPTION "The sFlow instance for this flow sampler."
              ::= { sisgm1040284lrtsFlowFsEntry 2 }

      sisgm1040284lrtsFlowFsReceiver OBJECT-TYPE
              SYNTAX      Integer32
              MAX-ACCESS  read-write
              STATUS      current
              DESCRIPTION "The SFlowReceiver for this flow sampler." DEFVAL { 0 }
              ::= { sisgm1040284lrtsFlowFsEntry 3 }

      sisgm1040284lrtsFlowFsPacketSamplingRate OBJECT-TYPE
              SYNTAX      Integer32
              MAX-ACCESS  read-write
              STATUS      current
              DESCRIPTION "The statistical sampling rate for packet sampling from this source.
                 Set to N to sample 1/Nth of the packets in the monitored flows. An agent should choose its own algorithm to introduce variance
                 into the sampling so that exactly every Nth packet is not counted. A sampling rate of 1 counts all packets. A sampling
                 rate of 0 disables sampling.
                 The agent is permitted to have minimum and maximum allowable values for the sampling rate. A minimum rate lets the agent
                 designer set an upper bound on the overhead associated with sampling, and a maximum rate may be the result of hardware
                 restrictions (such as counter size). In addition not all values between the maximum and minimum may be realizable as the
                 sampling rate (again because of implementation considerations).
                 When the sampling rate is set the agent is free to adjust the value so that it lies between the maximum and minimum values
                 and has the closest achievable value.
                 When read, the agent must return the actual sampling rate it will be using (after the adjustments previously described). The
                 sampling algorithm must converge so that over time the number of packets sampled approaches 1/Nth of the total number of
                 packets in the monitored flows." DEFVAL { 0 }
              ::= { sisgm1040284lrtsFlowFsEntry 4 }

      sisgm1040284lrtsFlowFsMaximumHeaderSize OBJECT-TYPE
              SYNTAX      Integer32
              MAX-ACCESS  read-write
              STATUS      current
              DESCRIPTION "The maximum number of bytes that should be copied from a sampled packet. The agent may have an internal maximum and
                 minimum permissible sizes. If an attempt is made to set this value outside the permissible range then the agent should
                 adjust the value to the closest permissible value." DEFVAL { 128 }
              ::= { sisgm1040284lrtsFlowFsEntry 5 }

      sisgm1040284lrtsFlowFsType OBJECT-TYPE
              SYNTAX      Integer32
              MAX-ACCESS  read-write
              STATUS      current
              DESCRIPTION "Flow Sample Type.
			  1:Rx
			  2:Tx
			  3:All."
			  DEFVAL { 2 }
              ::= { sisgm1040284lrtsFlowFsEntry 6 }
      --
      -- Counter Polling Table
      --
      sisgm1040284lrtsFlowCpTable OBJECT-TYPE
              SYNTAX      SEQUENCE OF SISGM1040284LRTSFlowCpEntry
              MAX-ACCESS  not-accessible
              STATUS      current
              DESCRIPTION "A table of the counter pollers within a device."
              ::= { sisgm1040284lrtsFlow 6 }

      sisgm1040284lrtsFlowCpEntry OBJECT-TYPE
              SYNTAX      SISGM1040284LRTSFlowCpEntry
              MAX-ACCESS  not-accessible
              STATUS      current
              DESCRIPTION "Attributes of a counter poller."
              INDEX { sisgm1040284lrtsFlowCpDataSource, sisgm1040284lrtsFlowCpInstance }
              ::= { sisgm1040284lrtsFlowCpTable 1 }

      SISGM1040284LRTSFlowCpEntry ::= SEQUENCE {
              sisgm1040284lrtsFlowCpDataSource               OBJECT IDENTIFIER,
              sisgm1040284lrtsFlowCpInstance                 Integer32,
              sisgm1040284lrtsFlowCpReceiver                 Integer32,
              sisgm1040284lrtsFlowCpInterval                 Integer32
              }

      sisgm1040284lrtsFlowCpDataSource OBJECT-TYPE
              SYNTAX      OBJECT IDENTIFIER
              MAX-ACCESS  not-accessible
              STATUS      current
              DESCRIPTION "Identifies the source of the data for the counter poller."
              ::= { sisgm1040284lrtsFlowCpEntry 1 }

      sisgm1040284lrtsFlowCpInstance OBJECT-TYPE
              SYNTAX      Integer32 (1..65535)
              MAX-ACCESS  not-accessible
              STATUS      current
              DESCRIPTION "The sFlowInstance for this counter poller."
              ::= { sisgm1040284lrtsFlowCpEntry 2 }

      sisgm1040284lrtsFlowCpReceiver OBJECT-TYPE
              SYNTAX      Integer32
              MAX-ACCESS  read-write
              STATUS      current
              DESCRIPTION "The SFlowReciever associated with this counter poller." DEFVAL { 0 }
              ::= { sisgm1040284lrtsFlowCpEntry 3 }

      sisgm1040284lrtsFlowCpInterval OBJECT-TYPE
              SYNTAX      Integer32
              MAX-ACCESS  read-write
              STATUS      current
              DESCRIPTION "The maximum number of seconds between successive samples of the counters associated with this data source. A sampling interval
                 of 0 disables counter sampling.
                 The agent is permitted to have minimum and maximum allowable values for the counter polling interval. A minimum interval
                 lets the agent designer set an upper bound on the overhead associated with polling, and a maximum interval may be the
                 result of implementation restrictions (such as counter size). In addition not all values between the maximum and minimum may
                 be realizable as the sampling interval (again because of implementation considerations).
                 When the sampling rate is set the agent is free to adjust the value so that it lies between the maximum and minimum values
                 and has the closest achievable value.
                 When read, the agent must return the actual sampling interval it will be using (after the adjustments previously described).
                 The sampling algorithm must converge so that over time the number of packets sampled approaches 1/Nth of the total number
                 of packets in the monitored flows." DEFVAL { 0 }
              ::= { sisgm1040284lrtsFlowCpEntry 4 }

sisgm1040284lrtLLDP                  OBJECT IDENTIFIER ::= { sisgm1040284lrtConfiguration 21 }

    sisgm1040284lrtLLDPConfTable OBJECT-TYPE
               SYNTAX      SEQUENCE OF     SISGM1040284LRTLLDPConfEntry
               MAX-ACCESS  not-accessible
               STATUS      current
               DESCRIPTION
                   " "
               ::= {     sisgm1040284lrtLLDP 1 }

    sisgm1040284lrtLLDPConfEntry OBJECT-TYPE
               SYNTAX          SISGM1040284LRTLLDPConfEntry
               MAX-ACCESS  not-accessible
               STATUS      current
               DESCRIPTION
                   " "
               INDEX    {    sisgm1040284lrtLLDPIndex  }
               ::= {     sisgm1040284lrtLLDPConfTable 1 }

    SISGM1040284LRTLLDPConfEntry             ::= SEQUENCE {
                 sisgm1040284lrtLLDPIndex        Integer32,
                 sisgm1040284lrtLLDPMode         Integer32,
                 sisgm1040284lrtLLDPCDPAware     Integer32,
                 sisgm1040284lrtLLDPPortDescr    Integer32,
		 sisgm1040284lrtLLDPSysName      Integer32,
		 sisgm1040284lrtLLDPSysDescr     Integer32,
		 sisgm1040284lrtLLDPSysCapa      Integer32,
		 sisgm1040284lrtLLDPMgmtAddr     Integer32
    }

    sisgm1040284lrtLLDPIndex OBJECT-TYPE
               SYNTAX      Integer32
               MAX-ACCESS  read-write
               STATUS      current
               DESCRIPTION
                   "LLDP configuration index."
               ::= {     sisgm1040284lrtLLDPConfEntry 1 }

    sisgm1040284lrtLLDPMode OBJECT-TYPE
               SYNTAX      Integer32
               MAX-ACCESS  read-write
               STATUS      current
               DESCRIPTION
                   "0:Disable
		   1:Tx only
		   2:Rx only
		   3:Enabled"
               ::= {     sisgm1040284lrtLLDPConfEntry 2 }

    sisgm1040284lrtLLDPCDPAware OBJECT-TYPE
               SYNTAX      Integer32
               MAX-ACCESS  read-write
               STATUS      current
               DESCRIPTION
                   "0:Disable
		   1:Enable"
               ::= {     sisgm1040284lrtLLDPConfEntry 3 }

    sisgm1040284lrtLLDPPortDescr OBJECT-TYPE
               SYNTAX      Integer32
               MAX-ACCESS  read-write
               STATUS      current
               DESCRIPTION
                   "0:Disable
		   1:Enable"
               ::= {     sisgm1040284lrtLLDPConfEntry 4 }

    sisgm1040284lrtLLDPSysName OBJECT-TYPE
               SYNTAX      Integer32
               MAX-ACCESS  read-write
               STATUS      current
               DESCRIPTION
                   "0:Disable
		   1:Enable"
               ::= {     sisgm1040284lrtLLDPConfEntry 5 }

    sisgm1040284lrtLLDPSysDescr OBJECT-TYPE
               SYNTAX      Integer32
               MAX-ACCESS  read-write
               STATUS      current
               DESCRIPTION
                   "0:Disable
		   1:Enable"
               ::= {     sisgm1040284lrtLLDPConfEntry 6 }

    sisgm1040284lrtLLDPSysCapa OBJECT-TYPE
               SYNTAX      Integer32
               MAX-ACCESS  read-write
               STATUS      current
               DESCRIPTION
                   "0:Disable
		   1:Enable"
               ::= {     sisgm1040284lrtLLDPConfEntry 7 }

    sisgm1040284lrtLLDPMgmtAddr OBJECT-TYPE
               SYNTAX      Integer32
               MAX-ACCESS  read-write
               STATUS      current
               DESCRIPTION
                   "0:Disable
		   1:Enable"
               ::= {     sisgm1040284lrtLLDPConfEntry 8 }

sisgm1040284lrtLLDPMEDCoordinatesLocation                          OBJECT IDENTIFIER ::= { sisgm1040284lrtLLDP 2 }   
			   
sisgm1040284lrtLLDPMEDLatitude   OBJECT-TYPE
   SYNTAX      DisplayString
   MAX-ACCESS  read-write
   STATUS      current
   DESCRIPTION
	   "Latitude SHOULD be normalized to within 0-90 degrees with a maximum of 4 digits."
   ::= { sisgm1040284lrtLLDPMEDCoordinatesLocation 2 }
			   
sisgm1040284lrtLLDPMEDLatitudeDirection OBJECT-TYPE
   SYNTAX      Integer32(0|1)
   MAX-ACCESS  read-write
   STATUS      current
   DESCRIPTION
       "0:North 
	    1:South"
   ::= { sisgm1040284lrtLLDPMEDCoordinatesLocation 3 }
			  
sisgm1040284lrtLLDPMEDLongitude   OBJECT-TYPE
   SYNTAX      DisplayString
   MAX-ACCESS  read-write
   STATUS      current
   DESCRIPTION
	   "Longitude SHOULD be normalized to within 0-180 degrees with a maximum of 4 digits."
   ::= { sisgm1040284lrtLLDPMEDCoordinatesLocation 4 }
			   
sisgm1040284lrtLLDPMEDLongitudeDirection OBJECT-TYPE
   SYNTAX      Integer32(0|1)
   MAX-ACCESS  read-write
   STATUS      current
   DESCRIPTION
       "0:East 
	    1:West"
   ::= { sisgm1040284lrtLLDPMEDCoordinatesLocation 5 }
			  
sisgm1040284lrtLLDPMEDAltitude   OBJECT-TYPE
   SYNTAX      DisplayString
   MAX-ACCESS  read-write
   STATUS      current
   DESCRIPTION
	   "Altitude SHOULD be normalized to within -2097151.9 to 2097151.9 with a maximum of 1 digits."
   ::= { sisgm1040284lrtLLDPMEDCoordinatesLocation 6 }
			   
sisgm1040284lrtLLDPMEDAltitudeType OBJECT-TYPE
   SYNTAX      Integer32(1|2)
   MAX-ACCESS  read-write
   STATUS      current
   DESCRIPTION
       "1:Meters 
	    2:Floors"
   ::= { sisgm1040284lrtLLDPMEDCoordinatesLocation 7 } 
   
sisgm1040284lrtLLDPMEDMapDatum OBJECT-TYPE
   SYNTAX      Integer32(0..2)
   MAX-ACCESS  read-write
   STATUS      current
   DESCRIPTION
       "The Map Datum is used for the coordinates given in these options:
	    1:WGS84
	    2:NAD83/NAVD88 
	    3:NAD83/MLLW
		"
   ::= { sisgm1040284lrtLLDPMEDCoordinatesLocation 8 }    

   
sisgm1040284lrtLLDPMEDTransmitTLVsTable OBJECT-TYPE
   SYNTAX      SEQUENCE OF SISGM1040284LRTLLDPMEDTransmitTLVsEntry
   MAX-ACCESS  not-accessible
   STATUS      current
   DESCRIPTION
       " "
   ::= { sisgm1040284lrtLLDP 3 }

sisgm1040284lrtLLDPMEDTransmitTLVsEntry OBJECT-TYPE
   SYNTAX      SISGM1040284LRTLLDPMEDTransmitTLVsEntry
   MAX-ACCESS  not-accessible
   STATUS      current
   DESCRIPTION
       " "
   INDEX    { sisgm1040284lrtLLDPMEDTransmitTLVsPort  }
   ::= { sisgm1040284lrtLLDPMEDTransmitTLVsTable 1 }
  
SISGM1040284LRTLLDPMEDTransmitTLVsEntry ::= SEQUENCE {
   sisgm1040284lrtLLDPMEDTransmitTLVsPort          Integer32,
   sisgm1040284lrtLLDPMEDTransmitTLVsCapabilities  Integer32,
   sisgm1040284lrtLLDPMEDTransmitTLVsPolicies      Integer32,
   sisgm1040284lrtLLDPMEDTransmitTLVsLocation      Integer32,
   sisgm1040284lrtLLDPMEDTransmitTLVsPoE           Integer32
}

sisgm1040284lrtLLDPMEDTransmitTLVsPort OBJECT-TYPE
   SYNTAX      Integer32
   MAX-ACCESS  not-accessible
   STATUS      current
   DESCRIPTION
       "Index"
   ::= { sisgm1040284lrtLLDPMEDTransmitTLVsEntry 1 }

sisgm1040284lrtLLDPMEDTransmitTLVsCapabilities OBJECT-TYPE
   SYNTAX      Integer32 (0|1)
   MAX-ACCESS  read-write
   STATUS      current
   DESCRIPTION
       "0:Disable
	    1:Enable"
   ::= { sisgm1040284lrtLLDPMEDTransmitTLVsEntry 2 }
			   
sisgm1040284lrtLLDPMEDTransmitTLVsPolicies OBJECT-TYPE
   SYNTAX      Integer32 (0|1)
   MAX-ACCESS  read-write
   STATUS      current
   DESCRIPTION
       "0:Disable
	    1:Enable"
   ::= { sisgm1040284lrtLLDPMEDTransmitTLVsEntry 3 }
   
sisgm1040284lrtLLDPMEDTransmitTLVsLocation OBJECT-TYPE
   SYNTAX      Integer32 (0|1)
   MAX-ACCESS  read-write
   STATUS      current
   DESCRIPTION
       "0:Disable
	    1:Enable"
   ::= { sisgm1040284lrtLLDPMEDTransmitTLVsEntry 4 }
   
sisgm1040284lrtLLDPMEDTransmitTLVsPoE OBJECT-TYPE
   SYNTAX      Integer32 (0|1)
   MAX-ACCESS  read-write
   STATUS      current
   DESCRIPTION
       "0:Disable
	    1:Enable"
   ::= { sisgm1040284lrtLLDPMEDTransmitTLVsEntry 5 }
   
sisgm1040284lrtLLDPMEDCivicAddressLocation                          OBJECT IDENTIFIER ::= { sisgm1040284lrtLLDP 4 }   

sisgm1040284lrtLLDPMEDCivicAddressLocationCountryCode   OBJECT-TYPE
   SYNTAX      DisplayString
   MAX-ACCESS  read-write
   STATUS      current
   DESCRIPTION
	   " "
   ::= { sisgm1040284lrtLLDPMEDCivicAddressLocation 2 }

sisgm1040284lrtLLDPMEDCivicAddressLocationStateProvince   OBJECT-TYPE
   SYNTAX      DisplayString
   MAX-ACCESS  read-write
   STATUS      current
   DESCRIPTION
	   " "
   ::= { sisgm1040284lrtLLDPMEDCivicAddressLocation 3 }
	
sisgm1040284lrtLLDPMEDCivicAddressLocationCounty   OBJECT-TYPE
   SYNTAX      DisplayString
   MAX-ACCESS  read-write
   STATUS      current
   DESCRIPTION
	   " "
   ::= { sisgm1040284lrtLLDPMEDCivicAddressLocation 4 }
   
sisgm1040284lrtLLDPMEDCivicAddressLocationCity   OBJECT-TYPE
   SYNTAX      DisplayString
   MAX-ACCESS  read-write
   STATUS      current
   DESCRIPTION
	   " "
   ::= { sisgm1040284lrtLLDPMEDCivicAddressLocation 5 }
   
sisgm1040284lrtLLDPMEDCivicAddressLocationCityDistrict   OBJECT-TYPE
   SYNTAX      DisplayString
   MAX-ACCESS  read-write
   STATUS      current
   DESCRIPTION
	   " "
   ::= { sisgm1040284lrtLLDPMEDCivicAddressLocation 6 }
   
sisgm1040284lrtLLDPMEDCivicAddressLocationBlockNeighborhood   OBJECT-TYPE
   SYNTAX      DisplayString
   MAX-ACCESS  read-write
   STATUS      current
   DESCRIPTION
	   " "
   ::= { sisgm1040284lrtLLDPMEDCivicAddressLocation 7 }
   
sisgm1040284lrtLLDPMEDCivicAddressLocationStreet   OBJECT-TYPE
   SYNTAX      DisplayString
   MAX-ACCESS  read-write
   STATUS      current
   DESCRIPTION
	   " "
   ::= { sisgm1040284lrtLLDPMEDCivicAddressLocation 8 }
   
sisgm1040284lrtLLDPMEDCivicAddressLocationLeadingStreetDirection   OBJECT-TYPE
   SYNTAX      DisplayString
   MAX-ACCESS  read-write
   STATUS      current
   DESCRIPTION
	   " "
   ::= { sisgm1040284lrtLLDPMEDCivicAddressLocation 9 }
   
sisgm1040284lrtLLDPMEDCivicAddressLocationTrailingStreetSuffix   OBJECT-TYPE
   SYNTAX      DisplayString
   MAX-ACCESS  read-write
   STATUS      current
   DESCRIPTION
	   " "
   ::= { sisgm1040284lrtLLDPMEDCivicAddressLocation 10 }
   
sisgm1040284lrtLLDPMEDCivicAddressLocationStreetSuffix   OBJECT-TYPE
   SYNTAX      DisplayString
   MAX-ACCESS  read-write
   STATUS      current
   DESCRIPTION
	   " "
   ::= { sisgm1040284lrtLLDPMEDCivicAddressLocation 11 }
   
sisgm1040284lrtLLDPMEDCivicAddressLocationHouseNo   OBJECT-TYPE
   SYNTAX      DisplayString
   MAX-ACCESS  read-write
   STATUS      current
   DESCRIPTION
	   " "
   ::= { sisgm1040284lrtLLDPMEDCivicAddressLocation 12 }
	
sisgm1040284lrtLLDPMEDCivicAddressLocationHouseNoSuffix   OBJECT-TYPE
   SYNTAX      DisplayString
   MAX-ACCESS  read-write
   STATUS      current
   DESCRIPTION
	   " "
   ::= { sisgm1040284lrtLLDPMEDCivicAddressLocation 13 }
	
sisgm1040284lrtLLDPMEDCivicAddressLocationLandmark   OBJECT-TYPE
   SYNTAX      DisplayString
   MAX-ACCESS  read-write
   STATUS      current
   DESCRIPTION
	   " "
   ::= { sisgm1040284lrtLLDPMEDCivicAddressLocation 14 }
   
sisgm1040284lrtLLDPMEDCivicAddressLocationAdditionalLocationInfo   OBJECT-TYPE
   SYNTAX      DisplayString
   MAX-ACCESS  read-write
   STATUS      current
   DESCRIPTION
	   " "
   ::= { sisgm1040284lrtLLDPMEDCivicAddressLocation 15 }
   
sisgm1040284lrtLLDPMEDCivicAddressLocationName   OBJECT-TYPE
   SYNTAX      DisplayString
   MAX-ACCESS  read-write
   STATUS      current
   DESCRIPTION
	   " "
   ::= { sisgm1040284lrtLLDPMEDCivicAddressLocation 16 }
   
sisgm1040284lrtLLDPMEDCivicAddressLocationZipCode   OBJECT-TYPE
   SYNTAX      DisplayString
   MAX-ACCESS  read-write
   STATUS      current
   DESCRIPTION
	   " "
   ::= { sisgm1040284lrtLLDPMEDCivicAddressLocation 17 }
	
sisgm1040284lrtLLDPMEDCivicAddressLocationBuilding   OBJECT-TYPE
   SYNTAX      DisplayString
   MAX-ACCESS  read-write
   STATUS      current
   DESCRIPTION
	   " "
   ::= { sisgm1040284lrtLLDPMEDCivicAddressLocation 18 }
   
sisgm1040284lrtLLDPMEDCivicAddressLocationApartment   OBJECT-TYPE
   SYNTAX      DisplayString
   MAX-ACCESS  read-write
   STATUS      current
   DESCRIPTION
	   " "
   ::= { sisgm1040284lrtLLDPMEDCivicAddressLocation 19 }   
   
sisgm1040284lrtLLDPMEDCivicAddressLocationFloor   OBJECT-TYPE
   SYNTAX      DisplayString
   MAX-ACCESS  read-write
   STATUS      current
   DESCRIPTION
	   " "
   ::= { sisgm1040284lrtLLDPMEDCivicAddressLocation 20 } 
   
sisgm1040284lrtLLDPMEDCivicAddressLocationRoomNo   OBJECT-TYPE
   SYNTAX      DisplayString
   MAX-ACCESS  read-write
   STATUS      current
   DESCRIPTION
	   " "
   ::= { sisgm1040284lrtLLDPMEDCivicAddressLocation 21 }    
   
sisgm1040284lrtLLDPMEDCivicAddressLocationPlaceType   OBJECT-TYPE
   SYNTAX      DisplayString
   MAX-ACCESS  read-write
   STATUS      current
   DESCRIPTION
	   " "
   ::= { sisgm1040284lrtLLDPMEDCivicAddressLocation 22 }     
   
sisgm1040284lrtLLDPMEDCivicAddressLocationPostalCommunityName   OBJECT-TYPE
   SYNTAX      DisplayString
   MAX-ACCESS  read-write
   STATUS      current
   DESCRIPTION
	   " "
   ::= { sisgm1040284lrtLLDPMEDCivicAddressLocation 23 }    

sisgm1040284lrtLLDPMEDCivicAddressLocationPOBox   OBJECT-TYPE
   SYNTAX      DisplayString
   MAX-ACCESS  read-write
   STATUS      current
   DESCRIPTION
	   " "
   ::= { sisgm1040284lrtLLDPMEDCivicAddressLocation 24 }     
   
sisgm1040284lrtLLDPMEDCivicAddressLocationAdditionalCode   OBJECT-TYPE
   SYNTAX      DisplayString
   MAX-ACCESS  read-write
   STATUS      current
   DESCRIPTION
	   " "
   ::= { sisgm1040284lrtLLDPMEDCivicAddressLocation 25 }

   
sisgm1040284lrtLLDPMEDPoliciesTable OBJECT-TYPE
   SYNTAX      SEQUENCE OF SISGM1040284LRTLLDPMEDPoliciesEntry
   MAX-ACCESS  not-accessible
   STATUS      current
   DESCRIPTION
       " "
   ::= { sisgm1040284lrtLLDP 5 }

sisgm1040284lrtLLDPMEDPoliciesEntry OBJECT-TYPE
   SYNTAX      SISGM1040284LRTLLDPMEDPoliciesEntry
   MAX-ACCESS  not-accessible
   STATUS      current
   DESCRIPTION
       " "
   INDEX    { sisgm1040284lrtLLDPMEDPoliciesIndex  }
   ::= { sisgm1040284lrtLLDPMEDPoliciesTable 1 }
  
SISGM1040284LRTLLDPMEDPoliciesEntry ::= SEQUENCE {
   sisgm1040284lrtLLDPMEDPoliciesIndex            Integer32,
   sisgm1040284lrtLLDPMEDPoliciesPolicyID         Integer32,
   sisgm1040284lrtLLDPMEDPoliciesApplicationType  Integer32,
   sisgm1040284lrtLLDPMEDPoliciesTag              Integer32,
   sisgm1040284lrtLLDPMEDPoliciesVLANID           Integer32,
   sisgm1040284lrtLLDPMEDPoliciesL2Priority       Integer32,
   sisgm1040284lrtLLDPMEDPoliciesDSCP             Integer32,
   sisgm1040284lrtLLDPMEDPoliciesRowStatus        RowStatus
}

sisgm1040284lrtLLDPMEDPoliciesIndex OBJECT-TYPE
   SYNTAX      Integer32
   MAX-ACCESS  not-accessible
   STATUS      current
   DESCRIPTION
       "Index"
   ::= { sisgm1040284lrtLLDPMEDPoliciesEntry 1 }

sisgm1040284lrtLLDPMEDPoliciesPolicyID OBJECT-TYPE
   SYNTAX      Integer32
   MAX-ACCESS  read-only
   STATUS      current
   DESCRIPTION
       " "
   ::= { sisgm1040284lrtLLDPMEDPoliciesEntry 2 }
			   
sisgm1040284lrtLLDPMEDPoliciesApplicationType OBJECT-TYPE
   SYNTAX      Integer32 (1..8)
   MAX-ACCESS  read-write
   STATUS      current
   DESCRIPTION
       "1:Voice
		2:Voice Signalling
		3:Guest Voice
		4:Guest Voice Signalling
		5:Softphone Voice
		6:Video Conferencing
		7:Streaming Video 
		8:Video Signalling"
   ::= { sisgm1040284lrtLLDPMEDPoliciesEntry 3 }
   
sisgm1040284lrtLLDPMEDPoliciesTag OBJECT-TYPE
   SYNTAX      Integer32 (0|1)
   MAX-ACCESS  read-write
   STATUS      current
   DESCRIPTION
       "0:Untagged
	    1:Tagged"
   ::= { sisgm1040284lrtLLDPMEDPoliciesEntry 4 }
   
sisgm1040284lrtLLDPMEDPoliciesVLANID OBJECT-TYPE
   SYNTAX      Integer32 (1..4095)
   MAX-ACCESS  read-write
   STATUS      current
   DESCRIPTION
       "Range:1-4095"
   ::= { sisgm1040284lrtLLDPMEDPoliciesEntry 5 }

sisgm1040284lrtLLDPMEDPoliciesL2Priority OBJECT-TYPE
   SYNTAX      Integer32 (0..7)
   MAX-ACCESS  read-write
   STATUS      current
   DESCRIPTION
       "Range:0-7"
   ::= { sisgm1040284lrtLLDPMEDPoliciesEntry 6 }
   
sisgm1040284lrtLLDPMEDPoliciesDSCP OBJECT-TYPE
   SYNTAX      Integer32 (0..63)
   MAX-ACCESS  read-write
   STATUS      current
   DESCRIPTION
       "Range:0-63"
   ::= { sisgm1040284lrtLLDPMEDPoliciesEntry 7 }	
   
sisgm1040284lrtLLDPMEDPoliciesRowStatus OBJECT-TYPE
   SYNTAX      RowStatus
   MAX-ACCESS  read-create
   STATUS      current
   DESCRIPTION
       "Row Status."
   ::= { sisgm1040284lrtLLDPMEDPoliciesEntry 8 }
	
sisgm1040284lrtLLDPMEDPolicyPortConfTable OBJECT-TYPE
   SYNTAX      SEQUENCE OF SISGM1040284LRTLLDPMEDPolicyPortConfEntry
   MAX-ACCESS  not-accessible
   STATUS      current
   DESCRIPTION
       " "
   ::= { sisgm1040284lrtLLDP 6 }

sisgm1040284lrtLLDPMEDPolicyPortConfEntry OBJECT-TYPE
   SYNTAX      SISGM1040284LRTLLDPMEDPolicyPortConfEntry
   MAX-ACCESS  not-accessible
   STATUS      current
   DESCRIPTION
       " "
   INDEX    { sisgm1040284lrtLLDPMEDPolicyPortConfPort  }
   ::= { sisgm1040284lrtLLDPMEDPolicyPortConfTable 1 }

SISGM1040284LRTLLDPMEDPolicyPortConfEntry ::= SEQUENCE {
   sisgm1040284lrtLLDPMEDPolicyPortConfPort        Integer32,
   sisgm1040284lrtLLDPMEDPolicyPortConf            Integer32
}
	
sisgm1040284lrtLLDPMEDPolicyPortConfPort OBJECT-TYPE
   SYNTAX      Integer32
   MAX-ACCESS  not-accessible
   STATUS      current
   DESCRIPTION
       "Index"
   ::= { sisgm1040284lrtLLDPMEDPolicyPortConfEntry 1 }

sisgm1040284lrtLLDPMEDPolicyPortConf OBJECT-TYPE
   SYNTAX      Integer32 (0|1)
   MAX-ACCESS  read-write
   STATUS      current
   DESCRIPTION
       "0:Disable
	    1:Enable"
   ::= { sisgm1040284lrtLLDPMEDPolicyPortConfEntry 2 }
	
sisgm1040284lrtLLDPMEDFastStartRepeatCount OBJECT-TYPE
   SYNTAX      Integer32 (1..10)
   MAX-ACCESS  read-write
   STATUS      current
   DESCRIPTION
       "Range:1-10"
   ::= { sisgm1040284lrtLLDP 7 }
	
sisgm1040284lrtLLDPMEDEmergencyCallService OBJECT-TYPE
   SYNTAX      DisplayString
   MAX-ACCESS  read-write
   STATUS      current
   DESCRIPTION
       " "
   ::= { sisgm1040284lrtLLDP 8 }
			   
sisgm1040284lrtUDLD    OBJECT IDENTIFIER ::= { sisgm1040284lrtConfiguration 22 }

sisgm1040284lrtUDLDPortConfigTable OBJECT-TYPE
   SYNTAX      SEQUENCE OF SISGM1040284LRTUDLDPortConfigEntry
   MAX-ACCESS  not-accessible
   STATUS      current
   DESCRIPTION
       " "
   ::= { sisgm1040284lrtUDLD 1 }

sisgm1040284lrtUDLDPortConfigEntry OBJECT-TYPE
   SYNTAX      SISGM1040284LRTUDLDPortConfigEntry
   MAX-ACCESS  not-accessible
   STATUS      current
   DESCRIPTION
       " "
   INDEX    { sisgm1040284lrtUDLDPort  }
   ::= { sisgm1040284lrtUDLDPortConfigTable 1 }

SISGM1040284LRTUDLDPortConfigEntry ::= SEQUENCE {
   sisgm1040284lrtUDLDPort                       Integer32,
   sisgm1040284lrtUDLDPortMode                   Integer32,
   sisgm1040284lrtUDLDPortMessageInterval        Integer32
}

sisgm1040284lrtUDLDPort OBJECT-TYPE
   SYNTAX      Integer32
   MAX-ACCESS  not-accessible
   STATUS      current
   DESCRIPTION
       " "
   ::= { sisgm1040284lrtUDLDPortConfigEntry 1 }

sisgm1040284lrtUDLDPortMode OBJECT-TYPE
   SYNTAX      Integer32 (0|1|2)
   MAX-ACCESS  read-write
   STATUS      current
   DESCRIPTION
       "default: 0
       0: disable
       1: Normal
	   2: Aggressive"
   ::= { sisgm1040284lrtUDLDPortConfigEntry 2 }

sisgm1040284lrtUDLDPortMessageInterval OBJECT-TYPE
   SYNTAX      Integer32(7..90)
   MAX-ACCESS  read-write
   STATUS      current
   DESCRIPTION
       "default: 7, range: 7-90"
   ::= { sisgm1040284lrtUDLDPortConfigEntry 3 }


sisgm1040284lrtUDLDPortStatusTable OBJECT-TYPE
   SYNTAX      SEQUENCE OF SISGM1040284LRTUDLDPortStatusEntry
   MAX-ACCESS  not-accessible
   STATUS      current
   DESCRIPTION
       " "
   ::= { sisgm1040284lrtUDLD 2 }

sisgm1040284lrtUDLDPortStatusEntry OBJECT-TYPE
   SYNTAX      SISGM1040284LRTUDLDPortStatusEntry
   MAX-ACCESS  not-accessible
   STATUS      current
   DESCRIPTION
       " "
   INDEX    { sisgm1040284lrtUDLDPortStatusPort  }
   ::= { sisgm1040284lrtUDLDPortStatusTable 1 }

SISGM1040284LRTUDLDPortStatusEntry ::= SEQUENCE {
   sisgm1040284lrtUDLDPortStatusPort                   Integer32,
   sisgm1040284lrtUDLDStatusAdminState                 Integer32,
   sisgm1040284lrtUDLDStatusDeviceIDLocal          DisplayString,
   sisgm1040284lrtUDLDStatusDeviceNameLocal        DisplayString,
   sisgm1040284lrtUDLDStatusBidirectionalState     DisplayString
}

sisgm1040284lrtUDLDPortStatusPort OBJECT-TYPE
   SYNTAX      Integer32
   MAX-ACCESS  not-accessible
   STATUS      current
   DESCRIPTION
       "Port index"
   ::= { sisgm1040284lrtUDLDPortStatusEntry 1 }

sisgm1040284lrtUDLDStatusAdminState OBJECT-TYPE
   SYNTAX      Integer32
   MAX-ACCESS  read-only
   STATUS      current
   DESCRIPTION
       "0:disable
	   1:enable"
   ::= { sisgm1040284lrtUDLDPortStatusEntry 2 }

sisgm1040284lrtUDLDStatusDeviceIDLocal OBJECT-TYPE
   SYNTAX      DisplayString
   MAX-ACCESS  read-only
   STATUS      current
   DESCRIPTION
       " "
   ::= { sisgm1040284lrtUDLDPortStatusEntry 3 }

sisgm1040284lrtUDLDStatusDeviceNameLocal OBJECT-TYPE
   SYNTAX      DisplayString
   MAX-ACCESS  read-only
   STATUS      current
   DESCRIPTION
       " "
   ::= { sisgm1040284lrtUDLDPortStatusEntry 4 }

sisgm1040284lrtUDLDStatusBidirectionalState OBJECT-TYPE
   SYNTAX      DisplayString
   MAX-ACCESS  read-only
   STATUS      current
   DESCRIPTION
       " "
   ::= { sisgm1040284lrtUDLDPortStatusEntry 5 }


sisgm1040284lrtUDLDStatusPort OBJECT-TYPE
   SYNTAX      Integer32
   MAX-ACCESS  read-write
   STATUS      current
   DESCRIPTION
       "Specify port number for check neighbour status"
   ::= { sisgm1040284lrtUDLD 3 }

sisgm1040284lrtUDLDPortNeighbourStatusTable OBJECT-TYPE
   SYNTAX      SEQUENCE OF SISGM1040284LRTUDLDPortNeighbourStatusEntry
   MAX-ACCESS  not-accessible
   STATUS      current
   DESCRIPTION
       " "
   ::= { sisgm1040284lrtUDLD 4 }

sisgm1040284lrtUDLDPortNeighbourStatusEntry OBJECT-TYPE
   SYNTAX      SISGM1040284LRTUDLDPortNeighbourStatusEntry
   MAX-ACCESS  not-accessible
   STATUS      current
   DESCRIPTION
       " "
   INDEX    { sisgm1040284lrtUDLDNeighbourPort  }
   ::= { sisgm1040284lrtUDLDPortNeighbourStatusTable 1 }

SISGM1040284LRTUDLDPortNeighbourStatusEntry ::= SEQUENCE {
   sisgm1040284lrtUDLDNeighbourPort                 Integer32,
   sisgm1040284lrtUDLDNeighbourStatusPort           DisplayString,
   sisgm1040284lrtUDLDNeighbourStatusDeviceId       DisplayString,
   sisgm1040284lrtUDLDNeighbourStatusLinkStatus     DisplayString,
   sisgm1040284lrtUDLDNeighbourStatusDeviceName     DisplayString
}

sisgm1040284lrtUDLDNeighbourPort OBJECT-TYPE
   SYNTAX      Integer32
   MAX-ACCESS  not-accessible
   STATUS      current
   DESCRIPTION
       "Index"
   ::= { sisgm1040284lrtUDLDPortNeighbourStatusEntry 1 }

sisgm1040284lrtUDLDNeighbourStatusPort OBJECT-TYPE
   SYNTAX      DisplayString
   MAX-ACCESS  read-only
   STATUS      current
   DESCRIPTION
       " "
   ::= { sisgm1040284lrtUDLDPortNeighbourStatusEntry 2 }

sisgm1040284lrtUDLDNeighbourStatusDeviceId OBJECT-TYPE
   SYNTAX      DisplayString
   MAX-ACCESS  read-only
   STATUS      current
   DESCRIPTION
       " "
   ::= { sisgm1040284lrtUDLDPortNeighbourStatusEntry 3 }

sisgm1040284lrtUDLDNeighbourStatusLinkStatus OBJECT-TYPE
   SYNTAX      DisplayString
   MAX-ACCESS  read-only
   STATUS      current
   DESCRIPTION
       " "
   ::= { sisgm1040284lrtUDLDPortNeighbourStatusEntry 4 }

sisgm1040284lrtUDLDNeighbourStatusDeviceName OBJECT-TYPE
   SYNTAX      DisplayString
   MAX-ACCESS  read-only
   STATUS      current
   DESCRIPTION
       " "
   ::= { sisgm1040284lrtUDLDPortNeighbourStatusEntry 5 }
-- =======================================================================================================================
sisgm1040284lrtEPS    OBJECT IDENTIFIER ::= { sisgm1040284lrtConfiguration 23 }

sisgm1040284lrtEPSTable  OBJECT-TYPE
   SYNTAX      SEQUENCE OF SISGM1040284LRTEPSEntry
   MAX-ACCESS  not-accessible
   STATUS      current
   DESCRIPTION
       "A table of EPS."
 ::= { sisgm1040284lrtEPS 1 }

sisgm1040284lrtEPSEntry OBJECT-TYPE
    SYNTAX        SISGM1040284LRTEPSEntry
    MAX-ACCESS    not-accessible
    STATUS        current
    DESCRIPTION
        ""
    INDEX        { sisgm1040284lrtEPSIndex }
    ::= { sisgm1040284lrtEPSTable 1 }

SISGM1040284LRTEPSEntry ::=
    SEQUENCE {
        sisgm1040284lrtEPSIndex                                Integer32,
        sisgm1040284lrtEpsID                                   Integer32,
		sisgm1040284lrtEpsDomain                               Integer32,
        sisgm1040284lrtEpsArchitecture                         Integer32,
        sisgm1040284lrtEpsWFlow                                Integer32,
        sisgm1040284lrtEpsPFlow                                Integer32,	
        sisgm1040284lrtEpsWSFMEP                               Integer32,		
        sisgm1040284lrtEpsPSFMEP                               Integer32,		
        sisgm1040284lrtEpsAPSMEP                               Integer32,		
        sisgm1040284lrtEpsAlarm                                Integer32,		
        sisgm1040284lrtEpsRowStatus                            RowStatus
    }

sisgm1040284lrtEPSIndex OBJECT-TYPE
   SYNTAX      Integer32
   MAX-ACCESS  not-accessible
   STATUS      current
   DESCRIPTION
       "Index"
   ::= { sisgm1040284lrtEPSEntry 1 }

sisgm1040284lrtEpsID OBJECT-TYPE
   SYNTAX      Integer32 (1..100)
   MAX-ACCESS  read-create
   STATUS      current
   DESCRIPTION
       "EPS ID. Range:1-100."
   ::= {sisgm1040284lrtEPSEntry 2 }

sisgm1040284lrtEpsDomain OBJECT-TYPE
   SYNTAX      Integer32
   MAX-ACCESS  read-create
   STATUS      current
   DESCRIPTION
       "EPS Domain. Range:0.
	   0:Domain is Port"
   ::= {sisgm1040284lrtEPSEntry 3 }   
   
sisgm1040284lrtEpsArchitecture OBJECT-TYPE
   SYNTAX      Integer32
   MAX-ACCESS  read-create
   STATUS      current
   DESCRIPTION
       "EPS Architecture. Range:0-1.
	   0:Architecture is 1+1
	   1:Architecture is 1:1"
   ::= {sisgm1040284lrtEPSEntry 4 }   
   
sisgm1040284lrtEpsWFlow OBJECT-TYPE
   SYNTAX      Integer32
   MAX-ACCESS  read-create
   STATUS      current
   DESCRIPTION
       "The working flow for the EPS."
   ::= {sisgm1040284lrtEPSEntry 5 }  

sisgm1040284lrtEpsPFlow OBJECT-TYPE
   SYNTAX      Integer32
   MAX-ACCESS  read-create
   STATUS      current
   DESCRIPTION
       "The protecting flow for the EPS"
   ::= {sisgm1040284lrtEPSEntry 6 }    
   
sisgm1040284lrtEpsWSFMEP OBJECT-TYPE
   SYNTAX      Integer32
   MAX-ACCESS  read-create
   STATUS      current
   DESCRIPTION
       "The working Signal Fail reporting MEP."
   ::= {sisgm1040284lrtEPSEntry 7 }     
   
sisgm1040284lrtEpsPSFMEP OBJECT-TYPE
   SYNTAX      Integer32
   MAX-ACCESS  read-create
   STATUS      current
   DESCRIPTION
       "The protecting Signal Fail reporting MEP."
   ::= {sisgm1040284lrtEPSEntry 8 }        
   
sisgm1040284lrtEpsAPSMEP OBJECT-TYPE
   SYNTAX      Integer32
   MAX-ACCESS  read-create
   STATUS      current
   DESCRIPTION
       "The APS PDU handling MEP."
   ::= {sisgm1040284lrtEPSEntry 9 }
   
sisgm1040284lrtEpsAlarm OBJECT-TYPE
   SYNTAX      Integer32
   MAX-ACCESS  read-only
   STATUS      current
   DESCRIPTION
       "There is an active alarm on the EPS."
   ::= {sisgm1040284lrtEPSEntry 10 }  
   
sisgm1040284lrtEpsRowStatus OBJECT-TYPE
   SYNTAX      RowStatus
   MAX-ACCESS  read-create
   STATUS      current
   DESCRIPTION
       "EPS Row Status."
   ::= {sisgm1040284lrtEPSEntry 11 }
   
sisgm1040284lrtEpsConfigInstanceEpsID   OBJECT-TYPE
   SYNTAX      Integer32
   MAX-ACCESS  read-write
   STATUS      current
   DESCRIPTION
	   "Specify EPS ID for table uesd."
   ::= {sisgm1040284lrtEPS 2 }
   
   
sisgm1040284lrtEPSConfigInstanceEntry    OBJECT IDENTIFIER ::= { sisgm1040284lrtEPS 3 } 

sisgm1040284lrtEpsConfigInstanceProtectionType OBJECT-TYPE
   SYNTAX      Integer32
   MAX-ACCESS  read-write
   STATUS      current
   DESCRIPTION
       "Range:0-1.
	   0:Unidirectional: EPS in the two ends can select traffic from different working/protecting flow. This is only possible in case of 1+1.
       1:Bidirectional: EPS in the two ends is selecting traffic from the same working/protecting flow. This requires APS enabled. This is mandatory for 1:1"
   ::= { sisgm1040284lrtEPSConfigInstanceEntry 2 }

sisgm1040284lrtEpsConfigInstanceAPS OBJECT-TYPE
   SYNTAX      Integer32
   MAX-ACCESS  read-write
   STATUS      current
   DESCRIPTION
       "Range:0-1.
	    0:disable
	    1:enable
	    The Automatic Protection Switching protocol can be enabled/disabled. This is mandatory for 1:1."
   ::= { sisgm1040284lrtEPSConfigInstanceEntry 3 }

sisgm1040284lrtEpsConfigInstanceRevertive OBJECT-TYPE
   SYNTAX      Integer32
   MAX-ACCESS  read-write
   STATUS      current
   DESCRIPTION
       "Range:0-1.
	    0:disable
	    1:enable
		The revertive switching to working flow can be enabled/disabled.
		"
   ::= { sisgm1040284lrtEPSConfigInstanceEntry 4 }   
   
sisgm1040284lrtEpsConfigInstanceWTRTime OBJECT-TYPE
   SYNTAX      Integer32
   MAX-ACCESS  read-write
   STATUS      current
   DESCRIPTION
       "The Wait To Restore timing value to be used in revertive switching. Range is 1 to 720 seconds.
		"
   ::= { sisgm1040284lrtEPSConfigInstanceEntry 5 }      
   
sisgm1040284lrtEpsConfigInstanceHoldOffTime OBJECT-TYPE
   SYNTAX      Integer32
   MAX-ACCESS  read-write
   STATUS      current
   DESCRIPTION
       "The timing value to be used to make persistent check on Signal Fail before switching. This is in 100 ms. and the max value is 100 (10 sec)."
   ::= { sisgm1040284lrtEPSConfigInstanceEntry 6 }     
   
sisgm1040284lrtEpsConfigInstanceCommand OBJECT-TYPE
   SYNTAX      Integer32
   MAX-ACCESS  read-write
   STATUS      current
   DESCRIPTION
       "0:None
	    1:Clear
		2:Lock Out
		3:Forced switch
		4:Manual switch P
		5:Manual switch W
		6:Exercise
		7:Freeze
		8:Lock Out Local
	   "
   ::= { sisgm1040284lrtEPSConfigInstanceEntry 7 }     

sisgm1040284lrtEpsStatusProtectionState OBJECT-TYPE
   SYNTAX      DisplayString
   MAX-ACCESS  read-only
   STATUS      current
   DESCRIPTION
       "EPS state according to State Transition Tables in G.8031.
	   "
   ::= { sisgm1040284lrtEPSConfigInstanceEntry 8 }
   
sisgm1040284lrtEpsStatusWorkingFlowState OBJECT-TYPE
   SYNTAX      DisplayString
   MAX-ACCESS  read-only
   STATUS      current
   DESCRIPTION
       "OK: State of working flow is ok
        SF: State of working flow is Signal Fail
		SD: State of working flow is Signal Degrade (for future use)
	   "
   ::= { sisgm1040284lrtEPSConfigInstanceEntry 9 }   
   
sisgm1040284lrtEpsStatusProtectingFlowState OBJECT-TYPE
   SYNTAX      DisplayString
   MAX-ACCESS  read-only
   STATUS      current
   DESCRIPTION
       "OK: State of protecting flow is ok
        SF: State of protecting flow is Signal Fail
        SD: State of protecting flow is Signal Degrade (for future use)
	   "
   ::= { sisgm1040284lrtEPSConfigInstanceEntry 10 }     
   
sisgm1040284lrtEpsStatusTransmittedApsRequest OBJECT-TYPE
   SYNTAX      DisplayString
   MAX-ACCESS  read-only
   STATUS      current
   DESCRIPTION
       "The transmitted APS according to State Transition Tables in G.8031.
	   "
   ::= { sisgm1040284lrtEPSConfigInstanceEntry 11 }     
   
sisgm1040284lrtEpsStatusTransmittedApsReSignal OBJECT-TYPE
   SYNTAX      Integer32
   MAX-ACCESS  read-only
   STATUS      current
   DESCRIPTION
       "The transmitted APS according to State Transition Tables in G.8031.
	   "
   ::= { sisgm1040284lrtEPSConfigInstanceEntry 12 }    
   
sisgm1040284lrtEpsStatusTransmittedApsBrSignal OBJECT-TYPE
   SYNTAX      Integer32
   MAX-ACCESS  read-only
   STATUS      current
   DESCRIPTION
       "The transmitted APS according to State Transition Tables in G.8031.
	   "
   ::= { sisgm1040284lrtEPSConfigInstanceEntry 13 }
   
sisgm1040284lrtEpsStatusReceivedApsRequest OBJECT-TYPE
   SYNTAX      DisplayString
   MAX-ACCESS  read-only
   STATUS      current
   DESCRIPTION
       "The received APS according to State Transition Tables in G.8031.
	   "
   ::= { sisgm1040284lrtEPSConfigInstanceEntry 14 }   
   
sisgm1040284lrtEpsStatusReceivedApsReSignal OBJECT-TYPE
   SYNTAX      Integer32
   MAX-ACCESS  read-only
   STATUS      current
   DESCRIPTION
       "The received APS according to State Transition Tables in G.8031.
	   "
   ::= { sisgm1040284lrtEPSConfigInstanceEntry 15 }      
   
sisgm1040284lrtEpsStatusReceivedApsBrSignal OBJECT-TYPE
   SYNTAX      Integer32
   MAX-ACCESS  read-only
   STATUS      current
   DESCRIPTION
       "The received APS according to State Transition Tables in G.8031.
	   "
   ::= { sisgm1040284lrtEPSConfigInstanceEntry 16 }    

sisgm1040284lrtEpsStatusArchitectureMismatch OBJECT-TYPE
   SYNTAX      DisplayString
   MAX-ACCESS  read-only
   STATUS      current
   DESCRIPTION
       "The architecture indicated in the received APS does not match the locally configured.
	   "
   ::= { sisgm1040284lrtEPSConfigInstanceEntry 17 }    

sisgm1040284lrtEpsStatusAPSOnWorking OBJECT-TYPE
   SYNTAX      DisplayString
   MAX-ACCESS  read-only
   STATUS      current
   DESCRIPTION
       "APS is received on the working flow.
	   "
   ::= { sisgm1040284lrtEPSConfigInstanceEntry 18 }     
   
sisgm1040284lrtEpsStatusSwitchingIncomplete OBJECT-TYPE
   SYNTAX      DisplayString
   MAX-ACCESS  read-only
   STATUS      current
   DESCRIPTION
       "Traffic is not selected from the same flow instance in the two ends.
	   "
   ::= { sisgm1040284lrtEPSConfigInstanceEntry 19 }     
   
sisgm1040284lrtEpsStatusNoApsReceived OBJECT-TYPE
   SYNTAX      DisplayString
   MAX-ACCESS  read-only
   STATUS      current
   DESCRIPTION
       "APS PDU is not received from the other end.
	   "
   ::= { sisgm1040284lrtEPSConfigInstanceEntry 20 }      
   
-- =======================================================================================================================
 
sisgm1040284lrtERPS    OBJECT IDENTIFIER ::= { sisgm1040284lrtConfiguration 24 }

sisgm1040284lrtERPSTable  OBJECT-TYPE
   SYNTAX      SEQUENCE OF SISGM1040284LRTERPSEntry
   MAX-ACCESS  not-accessible
   STATUS      current
   DESCRIPTION
       "A table of ERPS."
 ::= { sisgm1040284lrtERPS 1 }

sisgm1040284lrtERPSEntry OBJECT-TYPE
    SYNTAX        SISGM1040284LRTERPSEntry
    MAX-ACCESS    not-accessible
    STATUS        current
    DESCRIPTION
        ""
    INDEX        { sisgm1040284lrtErpsIndex }
    ::= { sisgm1040284lrtERPSTable 1 }

SISGM1040284LRTERPSEntry ::=
    SEQUENCE {
        sisgm1040284lrtErpsIndex                                Integer32,
        sisgm1040284lrtErpsID                                   Integer32,
		sisgm1040284lrtErpsPort0                                Integer32,
		sisgm1040284lrtErpsPort1                                Integer32,
		sisgm1040284lrtErpsPort0APSMEP                          Integer32,		
        sisgm1040284lrtErpsPort1APSMEP                          Integer32,
        sisgm1040284lrtErpsPort0SFMEP                           Integer32,
        sisgm1040284lrtErpsPort1SFMEP                           Integer32,	
        sisgm1040284lrtErpsRingType                             Integer32,		
        sisgm1040284lrtErpsInterconnectedNode                   Integer32,		
        sisgm1040284lrtErpsVirtualChannel                       Integer32,		
        sisgm1040284lrtErpsMajorRingID                          Integer32,	
        sisgm1040284lrtErpsAlarm		                          Integer32,
        sisgm1040284lrtErpsRowStatus                            RowStatus
    }

sisgm1040284lrtErpsIndex OBJECT-TYPE
   SYNTAX      Integer32
   MAX-ACCESS  not-accessible
   STATUS      current
   DESCRIPTION
       "Index"
   ::= { sisgm1040284lrtERPSEntry 1 }

sisgm1040284lrtErpsID OBJECT-TYPE
   SYNTAX      Integer32 (1..64)
   MAX-ACCESS  read-create
   STATUS      current
   DESCRIPTION
       "ERPS ID. Range:1-64."
   ::= {sisgm1040284lrtERPSEntry 2 }

sisgm1040284lrtErpsPort0 OBJECT-TYPE
   SYNTAX      Integer32
   MAX-ACCESS  read-create
   STATUS      current
   DESCRIPTION
       "This will create a Port 0 of the switch in the ring."
   ::= {sisgm1040284lrtERPSEntry 3 }   
   
sisgm1040284lrtErpsPort1 OBJECT-TYPE
   SYNTAX      Integer32
   MAX-ACCESS  read-create
   STATUS      current
   DESCRIPTION
       "This will create Port 1 of the switch in the Ring. 
	   As interconnected sub-ring will have only one ring port, Port 1 is configured as 0 for interconnected sub-ring.
	   0 in this field indicates that no Port 1 is associated with this instance"
   ::= {sisgm1040284lrtERPSEntry 4 }   
   
sisgm1040284lrtErpsPort0APSMEP OBJECT-TYPE
   SYNTAX      Integer32
   MAX-ACCESS  read-create
   STATUS      current
   DESCRIPTION
       "The Port 0 APS PDU handling MEP.
	   Range: 1-100."
   ::= {sisgm1040284lrtERPSEntry 5 }  
   
sisgm1040284lrtErpsPort1APSMEP OBJECT-TYPE
   SYNTAX      Integer32
   MAX-ACCESS  read-create
   STATUS      current
   DESCRIPTION
       "The Port 1 APS PDU handling MEP.
	   Range: 1-100."
   ::= {sisgm1040284lrtERPSEntry 6 }     

sisgm1040284lrtErpsPort0SFMEP OBJECT-TYPE
   SYNTAX      Integer32
   MAX-ACCESS  read-create
   STATUS      current
   DESCRIPTION
       "The Port 0 Signal Fail reporting MEP.
	   Range: 1-100."
   ::= {sisgm1040284lrtERPSEntry 7 }      
   
 sisgm1040284lrtErpsPort1SFMEP OBJECT-TYPE
   SYNTAX      Integer32
   MAX-ACCESS  read-create
   STATUS      current
   DESCRIPTION
       "The Port 1 Signal Fail reporting MEP.
	   Range: 1-100."
   ::= {sisgm1040284lrtERPSEntry 8 }      
   
sisgm1040284lrtErpsRingType OBJECT-TYPE
   SYNTAX      Integer32
   MAX-ACCESS  read-create
   STATUS      current
   DESCRIPTION
       "Type of Protecting ring. It can be either major ring or sub-ring.
	   0:Major
	   1:Sub"
   ::= {sisgm1040284lrtERPSEntry 9 }
   
sisgm1040284lrtErpsInterconnectedNode OBJECT-TYPE
   SYNTAX      Integer32
   MAX-ACCESS  read-create
   STATUS      current
   DESCRIPTION
       "Interconnected Node indicates that the ring instance is interconnected. 
	   0: not interconnected
	   1: interconnected"
   ::= {sisgm1040284lrtERPSEntry 10 }  
   
sisgm1040284lrtErpsVirtualChannel OBJECT-TYPE
   SYNTAX      Integer32
   MAX-ACCESS  read-create
   STATUS      current
   DESCRIPTION
       "1: indicates it is a sub-ring with virtual channel. 
	    0: indicates, sub-ring doesn't have virtual channel."
   ::= {sisgm1040284lrtERPSEntry 11 }
   
sisgm1040284lrtErpsMajorRingID OBJECT-TYPE
   SYNTAX      Integer32
   MAX-ACCESS  read-create
   STATUS      current
   DESCRIPTION
       "Major ring group ID for the interconnected sub-ring.
	   Range:1-64"
   ::= {sisgm1040284lrtERPSEntry 12 }   

sisgm1040284lrtErpsAlarm OBJECT-TYPE
   SYNTAX      Integer32
   MAX-ACCESS  read-create
   STATUS      current
   DESCRIPTION
       "There is an active alarm on the ERPS."
   ::= {sisgm1040284lrtERPSEntry 13 }  
   
sisgm1040284lrtErpsRowStatus OBJECT-TYPE
   SYNTAX      RowStatus
   MAX-ACCESS  read-create
   STATUS      current
   DESCRIPTION
       "ERPS Row Status."
   ::= {sisgm1040284lrtERPSEntry 14 }      
  
   
sisgm1040284lrtErpsConfigInstanceErpsID   OBJECT-TYPE
   SYNTAX      Integer32
   MAX-ACCESS  read-write
   STATUS      current
   DESCRIPTION
	   "Specify ERPS ID for ERPSConfigInstanceEntry and ErpsConfigInstanceVLANConfigTable uesd."
   ::= {sisgm1040284lrtERPS 2 }
   

sisgm1040284lrtERPSConfigInstanceEntry    OBJECT IDENTIFIER ::= { sisgm1040284lrtERPS 3 } 

sisgm1040284lrtErpsConfigInstanceConfigured OBJECT-TYPE
   SYNTAX      DisplayString
   MAX-ACCESS  read-only
   STATUS      current
   DESCRIPTION
       "Down: This ERPS is only created and has not yet been configured - is not active.
        Up: This ERPS is configured - is active."
   ::= { sisgm1040284lrtERPSConfigInstanceEntry 2 }

sisgm1040284lrtErpsConfigInstanceGuardTime OBJECT-TYPE
   SYNTAX      Integer32
   MAX-ACCESS  read-write
   STATUS      current
   DESCRIPTION
       "The period of the guard timer can be configured in 10 ms steps between 10 ms and 2 seconds, with a default value of 500 ms.
	    Guard timeout value to be used to prevent ring nodes from receiving outdated R-APS messages."
   ::= { sisgm1040284lrtERPSConfigInstanceEntry 3 }

sisgm1040284lrtErpsConfigInstanceWTRTime OBJECT-TYPE
   SYNTAX      Integer32
   MAX-ACCESS  read-write
   STATUS      current
   DESCRIPTION
       "The Wait To Restore timing value to be used in revertive switching.
        The period of the WTR time can be configured by the operator in 1 minute steps between 5 and 12 minutes with a default value of 5 minutes.
		"
   ::= { sisgm1040284lrtERPSConfigInstanceEntry 4 }   
   
sisgm1040284lrtErpsConfigInstanceHoldOffTime OBJECT-TYPE
   SYNTAX      Integer32
   MAX-ACCESS  read-write
   STATUS      current
   DESCRIPTION
       "The timing value to be used to make persistent check on Signal Fail before switching.
        The range of the hold off timer is 0 to 10 seconds in steps of 100 ms
		"
   ::= { sisgm1040284lrtERPSConfigInstanceEntry 5 }      
   
sisgm1040284lrtErpsConfigInstanceVersion OBJECT-TYPE
   SYNTAX      Integer32
   MAX-ACCESS  read-write
   STATUS      current
   DESCRIPTION
       "ERPS Protocol Version - v1 or v2
	   1:v1
	   2:v2"
   ::= { sisgm1040284lrtERPSConfigInstanceEntry 6 }     
   
sisgm1040284lrtErpsConfigInstanceRevertive OBJECT-TYPE
   SYNTAX      Integer32
   MAX-ACCESS  read-write
   STATUS      current
   DESCRIPTION
       "1:Revertive mode
	    0:Non-Revertive mode"
   ::= { sisgm1040284lrtERPSConfigInstanceEntry 7 }     

sisgm1040284lrtErpsConfigInstanceRPLRole OBJECT-TYPE
   SYNTAX      Integer32
   MAX-ACCESS  read-write
   STATUS      current
   DESCRIPTION
       "It can be either RPL owner or RPL Neighbor.
	   0:None 
	   1:RPL owner
	   2:RPL Neighbor
	   Please set RPLPort first.
	   "
   ::= { sisgm1040284lrtERPSConfigInstanceEntry 8 }
   
sisgm1040284lrtErpsConfigInstanceRPLPort OBJECT-TYPE
   SYNTAX      Integer32
   MAX-ACCESS  read-write
   STATUS      current
   DESCRIPTION
       "This allows to select the east port or west port as the RPL block.
	   0:None
	   1:Port0
	   2:Port1
	   Please set RPLRole after specify RPLPort.
	   "
   ::= { sisgm1040284lrtERPSConfigInstanceEntry 9 }   
   
sisgm1040284lrtErpsConfigInstanceClear OBJECT-TYPE
   SYNTAX      Integer32
   MAX-ACCESS  read-write
   STATUS      current
   DESCRIPTION
       "If the owner has to be changed, then the clear check box allows to clear the RPL owner for that ERPS ring.
	   0: no clear
	   1: clear
	   "
   ::= { sisgm1040284lrtERPSConfigInstanceEntry 10 }     
   
sisgm1040284lrtErpsConfigInstanceTopologyChange OBJECT-TYPE
   SYNTAX      Integer32
   MAX-ACCESS  read-write
   STATUS      current
   DESCRIPTION
       "1: indicates that the topology changes in the sub-ring are propagated in the major ring.
	    0: indicates that the topology changes in the sub-ring are not propagated in the major ring.
	   "
   ::= { sisgm1040284lrtERPSConfigInstanceEntry 11 }     
 
sisgm1040284lrtErpsConfigInstanceCommand OBJECT-TYPE
   SYNTAX      Integer32
   MAX-ACCESS  read-write
   STATUS      current
   DESCRIPTION
       "0:None
	    1:Manual Switch
		2:Forced Switch
		3:Clear
		Please set InstancePort first.
	   "
   ::= { sisgm1040284lrtERPSConfigInstanceEntry 12 }  
 
sisgm1040284lrtErpsConfigInstancePort OBJECT-TYPE
   SYNTAX      Integer32
   MAX-ACCESS  read-write
   STATUS      current
   DESCRIPTION
       "0:None
	   1:Port0
	   2:Port1
	   Please set InstanceCommand after specify InstancePort.
	   "
   ::= { sisgm1040284lrtERPSConfigInstanceEntry 13 }     
   
sisgm1040284lrtErpsStatusProtectionState OBJECT-TYPE
   SYNTAX      DisplayString
   MAX-ACCESS  read-only
   STATUS      current
   DESCRIPTION
       "ERPS state according to State Transition Tables in G.8032.
	   "
   ::= { sisgm1040284lrtERPSConfigInstanceEntry 14 }        
   
sisgm1040284lrtErpsStatusPort0 OBJECT-TYPE
   SYNTAX      DisplayString
   MAX-ACCESS  read-only
   STATUS      current
   DESCRIPTION
       "OK: State of East port is ok
        SF: State of East port is Signal Fail
	   "
   ::= { sisgm1040284lrtERPSConfigInstanceEntry 15 }        
   
sisgm1040284lrtErpsStatusPort1 OBJECT-TYPE
   SYNTAX      DisplayString
   MAX-ACCESS  read-only
   STATUS      current
   DESCRIPTION
       "OK: State of West port is ok
        SF: State of West port is Signal Fail
	   "
   ::= { sisgm1040284lrtERPSConfigInstanceEntry 16 }    
   
sisgm1040284lrtErpsStatusTransmitAPS OBJECT-TYPE
   SYNTAX      DisplayString
   MAX-ACCESS  read-only
   STATUS      current
   DESCRIPTION
       "The transmitted APS according to State Transition Tables in G.8032.
	   "
   ::= { sisgm1040284lrtERPSConfigInstanceEntry 17 }    

sisgm1040284lrtErpsStatusPort0ReceiveAPS OBJECT-TYPE
   SYNTAX      DisplayString
   MAX-ACCESS  read-only
   STATUS      current
   DESCRIPTION
       "The received APS on Port 0 according to State Transition Tables in G.8032.
	   "
   ::= { sisgm1040284lrtERPSConfigInstanceEntry 18 } 

sisgm1040284lrtErpsStatusPort1ReceiveAPS OBJECT-TYPE
   SYNTAX      DisplayString
   MAX-ACCESS  read-only
   STATUS      current
   DESCRIPTION
       "The received APS on Port 1 according to State Transition Tables in G.8032.
	   "
   ::= { sisgm1040284lrtERPSConfigInstanceEntry 19 }    
   
sisgm1040284lrtErpsStatusWTRRemaining OBJECT-TYPE
   SYNTAX      Integer32
   MAX-ACCESS  read-only
   STATUS      current
   DESCRIPTION
       "Remaining WTR timeout in milliseconds.
	   "
   ::= { sisgm1040284lrtERPSConfigInstanceEntry 20 }   
   
sisgm1040284lrtErpsStatusRPLUnblocked OBJECT-TYPE
   SYNTAX      DisplayString
   MAX-ACCESS  read-only
   STATUS      current
   DESCRIPTION
       "APS is received on the working flow.
	   "
   ::= { sisgm1040284lrtERPSConfigInstanceEntry 21 }      
   
sisgm1040284lrtErpsStatusNoAPSReceived OBJECT-TYPE
   SYNTAX      DisplayString
   MAX-ACCESS  read-only
   STATUS      current
   DESCRIPTION
       "RAPS PDU is not received from the other end.
	   "
   ::= { sisgm1040284lrtERPSConfigInstanceEntry 22 }   
   
sisgm1040284lrtErpsStatusPort0BlockStatus OBJECT-TYPE
   SYNTAX      DisplayString
   MAX-ACCESS  read-only
   STATUS      current
   DESCRIPTION
       "Block status for Port 0 (Both traffic and R-APS block status). R-APS channel is never blocked on sub-rings without virtual channel.
	   "
   ::= { sisgm1040284lrtERPSConfigInstanceEntry 23 }      
   
sisgm1040284lrtErpsStatusPort1BlockStatus OBJECT-TYPE
   SYNTAX      DisplayString
   MAX-ACCESS  read-only
   STATUS      current
   DESCRIPTION
       "Block status for Port 1 (Both traffic and R-APS block status). R-APS channel is never blocked on sub-rings without virtual channel.
	   "
   ::= { sisgm1040284lrtERPSConfigInstanceEntry 24 }       
   
sisgm1040284lrtErpsStatusFOPAlarm OBJECT-TYPE
   SYNTAX      DisplayString
   MAX-ACCESS  read-only
   STATUS      current
   DESCRIPTION
       "Failure of Protocol Defect(FOP) status:
	   FOP is not detected
	   FOP is detected
	   "
   ::= { sisgm1040284lrtERPSConfigInstanceEntry 25 }      
   
sisgm1040284lrtErpsConfigInstanceVLANConfigTable  OBJECT-TYPE
   SYNTAX      SEQUENCE OF SISGM1040284LRTErpsConfigInstanceVLANConfigEntry
   MAX-ACCESS  not-accessible
   STATUS      current
   DESCRIPTION
       "A table of ERPS VLANConfig."
 ::= { sisgm1040284lrtERPS 4 }

sisgm1040284lrtErpsConfigInstanceVLANConfigEntry OBJECT-TYPE
    SYNTAX        SISGM1040284LRTErpsConfigInstanceVLANConfigEntry
    MAX-ACCESS    not-accessible
    STATUS        current
    DESCRIPTION
        ""
    INDEX        { sisgm1040284lrtErpsConfigInstanceVLANConfigIndex }
    ::= { sisgm1040284lrtErpsConfigInstanceVLANConfigTable 1 }

SISGM1040284LRTErpsConfigInstanceVLANConfigEntry ::=
    SEQUENCE {
        sisgm1040284lrtErpsConfigInstanceVLANConfigIndex            Integer32,
        sisgm1040284lrtErpsConfigInstanceVLANConfigVLANID           Integer32,
        sisgm1040284lrtErpsConfigInstanceVLANConfigRowStatus        RowStatus
    }

sisgm1040284lrtErpsConfigInstanceVLANConfigIndex OBJECT-TYPE
   SYNTAX      Integer32
   MAX-ACCESS  not-accessible
   STATUS      current
   DESCRIPTION
       "Index"
   ::= { sisgm1040284lrtErpsConfigInstanceVLANConfigEntry 1 }

sisgm1040284lrtErpsConfigInstanceVLANConfigVLANID OBJECT-TYPE
   SYNTAX      Integer32 (1..4095)
   MAX-ACCESS  read-create
   STATUS      current
   DESCRIPTION
       "ERPS VLAN Config ID. Range:1-4095."
   ::= {sisgm1040284lrtErpsConfigInstanceVLANConfigEntry 2 }

sisgm1040284lrtErpsConfigInstanceVLANConfigRowStatus OBJECT-TYPE
   SYNTAX      RowStatus
   MAX-ACCESS  read-create
   STATUS      current
   DESCRIPTION
       "ERPS VLAN Config Row Status."
   ::= {sisgm1040284lrtErpsConfigInstanceVLANConfigEntry 3 }   
-- =======================================================================================================================

sisgm1040284lrtVLANTranslation    OBJECT IDENTIFIER ::= { sisgm1040284lrtConfiguration 25 }

sisgm1040284lrtVLANTranslationPortTable  OBJECT-TYPE
   SYNTAX      SEQUENCE OF SISGM1040284LRTVLANTranslationPortEntry
   MAX-ACCESS  not-accessible
   STATUS      current
   DESCRIPTION
       "A table of VLANTranslationPort."
 ::= { sisgm1040284lrtVLANTranslation 1 }

sisgm1040284lrtVLANTranslationPortEntry OBJECT-TYPE
    SYNTAX        SISGM1040284LRTVLANTranslationPortEntry
    MAX-ACCESS    not-accessible
    STATUS        current
    DESCRIPTION
        "An entry in the VLANTranslationPort table."
    INDEX        { sisgm1040284lrtVLANTranslationPortIndex }
    ::= { sisgm1040284lrtVLANTranslationPortTable 1 }

SISGM1040284LRTVLANTranslationPortEntry ::=
    SEQUENCE {
        sisgm1040284lrtVLANTranslationPortIndex                Integer32,
        sisgm1040284lrtVLANTranslationPortDefault              Integer32,
        sisgm1040284lrtVLANTranslationPortGroupID              Integer32
    }

sisgm1040284lrtVLANTranslationPortIndex OBJECT-TYPE
   SYNTAX      Integer32
   MAX-ACCESS  not-accessible
   STATUS      current
   DESCRIPTION
       "VLANTranslationPort index."
   ::= {sisgm1040284lrtVLANTranslationPortEntry 1 }

sisgm1040284lrtVLANTranslationPortDefault OBJECT-TYPE
   SYNTAX      Integer32
   MAX-ACCESS  read-write
   STATUS      current
   DESCRIPTION
       "Set the switch port to use the default VLAN Translation Group.
	   1:set
	   0:not set"
   ::= {sisgm1040284lrtVLANTranslationPortEntry 2 }

sisgm1040284lrtVLANTranslationPortGroupID OBJECT-TYPE
   SYNTAX      Integer32
   MAX-ACCESS  read-write
   STATUS      current
   DESCRIPTION
       "The VLAN Translation mappings are organized into Groups, identified by the Group ID."
   ::= {sisgm1040284lrtVLANTranslationPortEntry 3 }
   
   
   
sisgm1040284lrtVLANTranslationMappingTable  OBJECT-TYPE
   SYNTAX      SEQUENCE OF SISGM1040284LRTVLANTranslationMappingEntry
   MAX-ACCESS  not-accessible
   STATUS      current
   DESCRIPTION
       "A table of VLANTranslationMapping."
 ::= { sisgm1040284lrtVLANTranslation 2 }

sisgm1040284lrtVLANTranslationMappingEntry OBJECT-TYPE
    SYNTAX        SISGM1040284LRTVLANTranslationMappingEntry
    MAX-ACCESS    not-accessible
    STATUS        current
    DESCRIPTION
        "An entry in the VLANTranslationMapping table."
    INDEX        { sisgm1040284lrtVLANTranslationMappingIndex }
    ::= { sisgm1040284lrtVLANTranslationMappingTable 1 }

SISGM1040284LRTVLANTranslationMappingEntry ::=
    SEQUENCE {
        sisgm1040284lrtVLANTranslationMappingIndex                Integer32,
        sisgm1040284lrtVLANTranslationMappingGroupID              Integer32,
        sisgm1040284lrtVLANTranslationMappingVID                  Integer32,
		sisgm1040284lrtVLANTranslationMappingTVID                 Integer32,
		sisgm1040284lrtVLANTranslationMappingRowStatus            RowStatus
    }

sisgm1040284lrtVLANTranslationMappingIndex OBJECT-TYPE
   SYNTAX      Integer32
   MAX-ACCESS  not-accessible
   STATUS      current
   DESCRIPTION
       "VLANTranslationMapping index."
   ::= {sisgm1040284lrtVLANTranslationMappingEntry 1 }

sisgm1040284lrtVLANTranslationMappingGroupID OBJECT-TYPE
   SYNTAX      Integer32
   MAX-ACCESS  read-create
   STATUS      current
   DESCRIPTION
       "The VLAN Translation mappings are organized into Groups, identified by the Group ID."
   ::= {sisgm1040284lrtVLANTranslationMappingEntry 2 }

sisgm1040284lrtVLANTranslationMappingVID OBJECT-TYPE
   SYNTAX      Integer32
   MAX-ACCESS  read-create
   STATUS      current
   DESCRIPTION
       "Range:1-4095"
   ::= {sisgm1040284lrtVLANTranslationMappingEntry 3 }

sisgm1040284lrtVLANTranslationMappingTVID OBJECT-TYPE
   SYNTAX      Integer32
   MAX-ACCESS  read-create
   STATUS      current
   DESCRIPTION
       "Range:1-4095"
   ::= {sisgm1040284lrtVLANTranslationMappingEntry 4 }   
   
sisgm1040284lrtVLANTranslationMappingRowStatus OBJECT-TYPE
   SYNTAX      RowStatus
   MAX-ACCESS  read-create
   STATUS      current
   DESCRIPTION
       "VLANTranslationMapping Row Status."
   ::= {sisgm1040284lrtVLANTranslationMappingEntry 5 }
   
sisgm1040284lrtMEP    OBJECT IDENTIFIER ::= { sisgm1040284lrtConfiguration 26 }    

sisgm1040284lrtMEPTable  OBJECT-TYPE
   SYNTAX      SEQUENCE OF SISGM1040284LRTMEPEntry
   MAX-ACCESS  not-accessible
   STATUS      current
   DESCRIPTION
       "A table of MEP."
 ::= { sisgm1040284lrtMEP 1 }

sisgm1040284lrtMEPEntry OBJECT-TYPE
    SYNTAX        SISGM1040284LRTMEPEntry
    MAX-ACCESS    not-accessible
    STATUS        current
    DESCRIPTION
        "An entry in the MEP table."
    INDEX        { sisgm1040284lrtMEPIndex }
    ::= { sisgm1040284lrtMEPTable 1 }

SISGM1040284LRTMEPEntry ::=
    SEQUENCE {
        sisgm1040284lrtMEPIndex                         Integer32,
        sisgm1040284lrtMepInstance                      Integer32,
        sisgm1040284lrtMepDomain                        Integer32,
        sisgm1040284lrtMepMode                          Integer32,
		sisgm1040284lrtMepDirection                     Integer32,
		sisgm1040284lrtMepResidencePort                 Integer32,
		sisgm1040284lrtMepLevel                         Integer32,
		sisgm1040284lrtMepFlowInstance                  Integer32,
		sisgm1040284lrtMepTaggedVID                     Integer32,
		sisgm1040284lrtMepEPSInstance                   DisplayString,
		sisgm1040284lrtMepThisMAC                       DisplayString,
		sisgm1040284lrtMepAlarm                         DisplayString,
        sisgm1040284lrtMepRowStatus                     RowStatus
    }

sisgm1040284lrtMEPIndex OBJECT-TYPE
   SYNTAX      Integer32
   MAX-ACCESS  not-accessible
   STATUS      current
   DESCRIPTION
       "MEP Table index."
   ::= {sisgm1040284lrtMEPEntry 1 }

sisgm1040284lrtMepInstance OBJECT-TYPE
   SYNTAX      Integer32
   MAX-ACCESS  read-create
   STATUS      current
   DESCRIPTION
       ""
   ::= {sisgm1040284lrtMEPEntry 2 }

sisgm1040284lrtMepDomain OBJECT-TYPE
   SYNTAX      Integer32
   MAX-ACCESS  read-create
   STATUS      current
   DESCRIPTION
       ""
   ::= {sisgm1040284lrtMEPEntry 3 }  
   
sisgm1040284lrtMepMode OBJECT-TYPE
   SYNTAX      Integer32
   MAX-ACCESS  read-create
   STATUS      current
   DESCRIPTION
       ""
   ::= {sisgm1040284lrtMEPEntry 4 }    

sisgm1040284lrtMepDirection OBJECT-TYPE
   SYNTAX      Integer32
   MAX-ACCESS  read-create
   STATUS      current
   DESCRIPTION
       ""
   ::= {sisgm1040284lrtMEPEntry 5 }  

sisgm1040284lrtMepResidencePort OBJECT-TYPE
   SYNTAX      Integer32
   MAX-ACCESS  read-create
   STATUS      current
   DESCRIPTION
       ""
   ::= {sisgm1040284lrtMEPEntry 6 }  

sisgm1040284lrtMepLevel OBJECT-TYPE
   SYNTAX      Integer32
   MAX-ACCESS  read-create
   STATUS      current
   DESCRIPTION
       ""
   ::= {sisgm1040284lrtMEPEntry 7 }  

sisgm1040284lrtMepFlowInstance OBJECT-TYPE
   SYNTAX      Integer32
   MAX-ACCESS  read-create
   STATUS      current
   DESCRIPTION
       ""
   ::= {sisgm1040284lrtMEPEntry 8 }  

sisgm1040284lrtMepTaggedVID OBJECT-TYPE
   SYNTAX      Integer32
   MAX-ACCESS  read-create
   STATUS      current
   DESCRIPTION
       ""
   ::= {sisgm1040284lrtMEPEntry 9 }    

sisgm1040284lrtMepEPSInstance OBJECT-TYPE
   SYNTAX      DisplayString
   MAX-ACCESS  read-only
   STATUS      current
   DESCRIPTION
       ""
   ::= {sisgm1040284lrtMEPEntry 10 }     
   
sisgm1040284lrtMepThisMAC OBJECT-TYPE
   SYNTAX      DisplayString
   MAX-ACCESS  read-only
   STATUS      current
   DESCRIPTION
       ""
   ::= {sisgm1040284lrtMEPEntry 11 }

sisgm1040284lrtMepAlarm OBJECT-TYPE
   SYNTAX      DisplayString
   MAX-ACCESS  read-only
   STATUS      current
   DESCRIPTION
       ""
   ::= {sisgm1040284lrtMEPEntry 12 }  
   
sisgm1040284lrtMepRowStatus OBJECT-TYPE
   SYNTAX      RowStatus
   MAX-ACCESS  read-create
   STATUS      current
   DESCRIPTION
       "MEP Row Status."
   ::= {sisgm1040284lrtMEPEntry 13 }
 
sisgm1040284lrtMepInstanceID   OBJECT-TYPE
   SYNTAX      Integer32
   MAX-ACCESS  read-write
   STATUS      current
   DESCRIPTION
	   "Specify MEP Instance ID for the following item and table uesd."
   ::= {sisgm1040284lrtMEP 2 } 
 

sisgm1040284lrtMepInstanceConfEntry    OBJECT IDENTIFIER ::= { sisgm1040284lrtMEP 3 }

sisgm1040284lrtMepInstanceConfLevel OBJECT-TYPE
   SYNTAX      Integer32
   MAX-ACCESS  read-write
   STATUS      current
   DESCRIPTION
       ""
   ::= {sisgm1040284lrtMepInstanceConfEntry 2 }  

sisgm1040284lrtMepInstanceConfFormat OBJECT-TYPE
   SYNTAX      Integer32
   MAX-ACCESS  read-write
   STATUS      current
   DESCRIPTION
       ""
   ::= {sisgm1040284lrtMepInstanceConfEntry 3 }  

sisgm1040284lrtMepInstanceConfDomainName OBJECT-TYPE
   SYNTAX      DisplayString
   MAX-ACCESS  read-write
   STATUS      current
   DESCRIPTION
       ""
   ::= {sisgm1040284lrtMepInstanceConfEntry 4 }  

sisgm1040284lrtMepInstanceConfMEGid OBJECT-TYPE
   SYNTAX      DisplayString
   MAX-ACCESS  read-write
   STATUS      current
   DESCRIPTION
       ""
   ::= {sisgm1040284lrtMepInstanceConfEntry 5 } 

sisgm1040284lrtMepInstanceConfMEPid OBJECT-TYPE
   SYNTAX      Integer32
   MAX-ACCESS  read-write
   STATUS      current
   DESCRIPTION
       ""
   ::= {sisgm1040284lrtMepInstanceConfEntry 6 }   

sisgm1040284lrtMepInstanceConfTaggedVID OBJECT-TYPE
   SYNTAX      Integer32
   MAX-ACCESS  read-write
   STATUS      current
   DESCRIPTION
       ""
   ::= {sisgm1040284lrtMepInstanceConfEntry 7 }      
  
sisgm1040284lrtMepInstanceConfSyslog OBJECT-TYPE
   SYNTAX      Integer32
   MAX-ACCESS  read-write
   STATUS      current
   DESCRIPTION
       ""
   ::= {sisgm1040284lrtMepInstanceConfEntry 8 }  
  
sisgm1040284lrtMepInstanceConfcLevel OBJECT-TYPE
   SYNTAX      DisplayString
   MAX-ACCESS  read-only
   STATUS      current
   DESCRIPTION
       ""
   ::= {sisgm1040284lrtMepInstanceConfEntry 9 }  
 
sisgm1040284lrtMepInstanceConfcMEG OBJECT-TYPE
   SYNTAX      DisplayString
   MAX-ACCESS  read-only
   STATUS      current
   DESCRIPTION
       ""
   ::= {sisgm1040284lrtMepInstanceConfEntry 10 }   
 
sisgm1040284lrtMepInstanceConfcMEP OBJECT-TYPE
   SYNTAX      DisplayString
   MAX-ACCESS  read-only
   STATUS      current
   DESCRIPTION
       ""
   ::= {sisgm1040284lrtMepInstanceConfEntry 11 }   
 
sisgm1040284lrtMepInstanceConfcAIS OBJECT-TYPE
   SYNTAX      DisplayString
   MAX-ACCESS  read-only
   STATUS      current
   DESCRIPTION
       ""
   ::= {sisgm1040284lrtMepInstanceConfEntry 12 }   
   
sisgm1040284lrtMepInstanceConfcLCK OBJECT-TYPE
   SYNTAX      DisplayString
   MAX-ACCESS  read-only
   STATUS      current
   DESCRIPTION
       ""
   ::= {sisgm1040284lrtMepInstanceConfEntry 13 }   
 
sisgm1040284lrtMepInstanceConfcLoop OBJECT-TYPE
   SYNTAX      DisplayString
   MAX-ACCESS  read-only
   STATUS      current
   DESCRIPTION
       ""
   ::= {sisgm1040284lrtMepInstanceConfEntry 14 }  

sisgm1040284lrtMepInstanceConfcConfig OBJECT-TYPE
   SYNTAX      DisplayString
   MAX-ACCESS  read-only
   STATUS      current
   DESCRIPTION
       ""
   ::= {sisgm1040284lrtMepInstanceConfEntry 15 }  

sisgm1040284lrtMepInstanceConfcDEG OBJECT-TYPE
   SYNTAX      DisplayString
   MAX-ACCESS  read-only
   STATUS      current
   DESCRIPTION
       ""
   ::= {sisgm1040284lrtMepInstanceConfEntry 16 }  

sisgm1040284lrtMepInstanceConfcSSF OBJECT-TYPE
   SYNTAX      DisplayString
   MAX-ACCESS  read-only
   STATUS      current
   DESCRIPTION
       ""
   ::= {sisgm1040284lrtMepInstanceConfEntry 17 }  

sisgm1040284lrtMepInstanceConfaBLK OBJECT-TYPE
   SYNTAX      DisplayString
   MAX-ACCESS  read-only
   STATUS      current
   DESCRIPTION
       ""
   ::= {sisgm1040284lrtMepInstanceConfEntry 18 }  

sisgm1040284lrtMepInstanceConfaTSD OBJECT-TYPE
   SYNTAX      DisplayString
   MAX-ACCESS  read-only
   STATUS      current
   DESCRIPTION
       ""
   ::= {sisgm1040284lrtMepInstanceConfEntry 19 }  

sisgm1040284lrtMepInstanceConfaTSF OBJECT-TYPE
   SYNTAX      DisplayString
   MAX-ACCESS  read-only
   STATUS      current
   DESCRIPTION
       ""
   ::= {sisgm1040284lrtMepInstanceConfEntry 20 }     
 
 
sisgm1040284lrtPeerMepConfTable  OBJECT-TYPE
   SYNTAX      SEQUENCE OF SISGM1040284LRTPeerMepConfEntry
   MAX-ACCESS  not-accessible
   STATUS      current
   DESCRIPTION
       "A table of MEP."
 ::= { sisgm1040284lrtMEP 4 }

sisgm1040284lrtPeerMepConfEntry OBJECT-TYPE
    SYNTAX        SISGM1040284LRTPeerMepConfEntry
    MAX-ACCESS    not-accessible
    STATUS        current
    DESCRIPTION
        ""
    INDEX        { sisgm1040284lrtPeerMepConfIndex }
    ::= { sisgm1040284lrtPeerMepConfTable 1 }

SISGM1040284LRTPeerMepConfEntry ::=
    SEQUENCE {
        sisgm1040284lrtPeerMepConfIndex                       Integer32,
        sisgm1040284lrtPeerMepConfPeerMEPID                   Integer32,
		sisgm1040284lrtPeerMepConfUnicastPeerMAC              DisplayString,
        sisgm1040284lrtPeerMepConfcLOC                        DisplayString,
        sisgm1040284lrtPeerMepConfcRDI                        DisplayString,
        sisgm1040284lrtPeerMepConfcPeriod                     DisplayString,	
        sisgm1040284lrtPeerMepConfcPriority                   DisplayString,			
        sisgm1040284lrtPeerMepConfRowStatus                   RowStatus
    }

sisgm1040284lrtPeerMepConfIndex OBJECT-TYPE
   SYNTAX      Integer32
   MAX-ACCESS  not-accessible
   STATUS      current
   DESCRIPTION
       "Index"
   ::= { sisgm1040284lrtPeerMepConfEntry 1 }

sisgm1040284lrtPeerMepConfPeerMEPID OBJECT-TYPE
   SYNTAX      Integer32 
   MAX-ACCESS  read-create
   STATUS      current
   DESCRIPTION
       "Peer MEP ID"
   ::= {sisgm1040284lrtPeerMepConfEntry 2 }

sisgm1040284lrtPeerMepConfUnicastPeerMAC OBJECT-TYPE
   SYNTAX      DisplayString
   MAX-ACCESS  read-create
   STATUS      current
   DESCRIPTION
       ""
   ::= {sisgm1040284lrtPeerMepConfEntry 3 }   
   
sisgm1040284lrtPeerMepConfcLOC OBJECT-TYPE
   SYNTAX      DisplayString
   MAX-ACCESS  read-create
   STATUS      current
   DESCRIPTION
       ""
   ::= {sisgm1040284lrtPeerMepConfEntry 4 }      
   
sisgm1040284lrtPeerMepConfcRDI OBJECT-TYPE
   SYNTAX      DisplayString
   MAX-ACCESS  read-create
   STATUS      current
   DESCRIPTION
       ""
   ::= {sisgm1040284lrtPeerMepConfEntry 5 }    
   
sisgm1040284lrtPeerMepConfcPeriod OBJECT-TYPE
   SYNTAX      DisplayString
   MAX-ACCESS  read-create
   STATUS      current
   DESCRIPTION
       ""
   ::= {sisgm1040284lrtPeerMepConfEntry 6 }  

sisgm1040284lrtPeerMepConfcPriority OBJECT-TYPE
   SYNTAX      DisplayString
   MAX-ACCESS  read-create
   STATUS      current
   DESCRIPTION
       ""
   ::= {sisgm1040284lrtPeerMepConfEntry 7 }  
   
sisgm1040284lrtPeerMepConfRowStatus OBJECT-TYPE
   SYNTAX      RowStatus
   MAX-ACCESS  read-create
   STATUS      current
   DESCRIPTION
       "Peer Mep Conf Row Status."
   ::= {sisgm1040284lrtPeerMepConfEntry 8 }
   
sisgm1040284lrtFunctionalConf    OBJECT IDENTIFIER ::= { sisgm1040284lrtMEP 5 }

sisgm1040284lrtFunctionalConfContinuityCheckEnable OBJECT-TYPE
   SYNTAX      Integer32
   MAX-ACCESS  read-write
   STATUS      current
   DESCRIPTION
       "0:disable
	   1:enable"
   ::= {sisgm1040284lrtFunctionalConf 2 } 
   
sisgm1040284lrtFunctionalConfContinuityCheckPriority OBJECT-TYPE
   SYNTAX      Integer32
   MAX-ACCESS  read-write
   STATUS      current
   DESCRIPTION
       "range:0-7"
   ::= {sisgm1040284lrtFunctionalConf 3 } 
   
sisgm1040284lrtFunctionalConfContinuityCheckFrameRate OBJECT-TYPE
   SYNTAX      Integer32
   MAX-ACCESS  read-write
   STATUS      current
   DESCRIPTION
       "range:1-7
	   1: 300 f/sec
	   2: 100 f/sec
	   3: 10 f/sec
	   4: 1 f/sec
	   5: 6 f/min
	   6: 1 f/min
	   7: 6 f/hour"
   ::= {sisgm1040284lrtFunctionalConf 4 }    

sisgm1040284lrtFunctionalConfContinuityCheckTLV OBJECT-TYPE
   SYNTAX      Integer32
   MAX-ACCESS  read-write
   STATUS      current
   DESCRIPTION
       "0:disable
	   1:enable"
   ::= {sisgm1040284lrtFunctionalConf 5 } 

sisgm1040284lrtFunctionalConfAPSProtocolEnable OBJECT-TYPE
   SYNTAX      Integer32
   MAX-ACCESS  read-write
   STATUS      current
   DESCRIPTION
       "0:disable
	   1:enable"
   ::= {sisgm1040284lrtFunctionalConf 6 }   

sisgm1040284lrtFunctionalConfAPSProtocolPriority OBJECT-TYPE
   SYNTAX      Integer32
   MAX-ACCESS  read-write
   STATUS      current
   DESCRIPTION
       "range:0-7"
   ::= {sisgm1040284lrtFunctionalConf 7 }   
   
sisgm1040284lrtFunctionalConfAPSProtocolCast OBJECT-TYPE
   SYNTAX      Integer32
   MAX-ACCESS  read-write
   STATUS      current
   DESCRIPTION
       "0: Unicast destination address
	   1: Multicast destination address"
   ::= {sisgm1040284lrtFunctionalConf 8 }     

sisgm1040284lrtFunctionalConfAPSProtocolType OBJECT-TYPE
   SYNTAX      Integer32
   MAX-ACCESS  read-write
   STATUS      current
   DESCRIPTION
       "1: Linear protection APS
	   2: Ring protection APS"
   ::= {sisgm1040284lrtFunctionalConf 9 }  

sisgm1040284lrtFunctionalConfAPSProtocolLastOctet OBJECT-TYPE
   SYNTAX      Integer32
   MAX-ACCESS  read-write
   STATUS      current
   DESCRIPTION
       "range:0-255"
   ::= {sisgm1040284lrtFunctionalConf 10 }    
   
sisgm1040284lrtTLVConf    OBJECT IDENTIFIER ::= { sisgm1040284lrtMEP 6 }   

sisgm1040284lrtTLVConfOUIFirst OBJECT-TYPE
   SYNTAX      Integer32
   MAX-ACCESS  read-write
   STATUS      current
   DESCRIPTION
       "range:0-255"
   ::= {sisgm1040284lrtTLVConf 2 } 
   
sisgm1040284lrtTLVConfOUISecond OBJECT-TYPE
   SYNTAX      Integer32
   MAX-ACCESS  read-write
   STATUS      current
   DESCRIPTION
       "range:0-255"
   ::= {sisgm1040284lrtTLVConf 3 } 
   
sisgm1040284lrtTLVConfOUIThird OBJECT-TYPE
   SYNTAX      Integer32
   MAX-ACCESS  read-write
   STATUS      current
   DESCRIPTION
       "range:0-255"
   ::= {sisgm1040284lrtTLVConf 4 } 
   
sisgm1040284lrtTLVConfSubType OBJECT-TYPE
   SYNTAX      Integer32
   MAX-ACCESS  read-write
   STATUS      current
   DESCRIPTION
       "range:0-255"
   ::= {sisgm1040284lrtTLVConf 5 }    
   
sisgm1040284lrtTLVConfValue OBJECT-TYPE
   SYNTAX      Integer32
   MAX-ACCESS  read-write
   STATUS      current
   DESCRIPTION
       "range:0-255"
   ::= {sisgm1040284lrtTLVConf 6 }  


sisgm1040284lrtTLVConfStateTable OBJECT-TYPE
   SYNTAX      SEQUENCE OF SISGM1040284LRTTLVConfStateEntry
   MAX-ACCESS  not-accessible
   STATUS      current
   DESCRIPTION
       "TLV Conf State Table"
   ::= { sisgm1040284lrtMEP 7 }

sisgm1040284lrtTLVConfStateEntry OBJECT-TYPE
   SYNTAX      SISGM1040284LRTTLVConfStateEntry
   MAX-ACCESS  not-accessible
   STATUS      current
   DESCRIPTION
       "TLV Conf State Entry"
   INDEX    { sisgm1040284lrtTLVConfStateIndex  }
   ::= { sisgm1040284lrtTLVConfStateTable 1 }

SISGM1040284LRTTLVConfStateEntry ::= SEQUENCE {
   sisgm1040284lrtTLVConfStateIndex                                Integer32,
   sisgm1040284lrtTLVConfStatePeerMEPID                            Integer32,
   sisgm1040284lrtTLVConfStateCCOrganizationSpecificOUIFirst       Integer32,
   sisgm1040284lrtTLVConfStateCCOrganizationSpecificOUISecond      Integer32,
   sisgm1040284lrtTLVConfStateCCOrganizationSpecificOUIThird       Integer32,  
   sisgm1040284lrtTLVConfStateCCOrganizationSpecificSubType        Integer32,  
   sisgm1040284lrtTLVConfStateCCOrganizationSpecificValue          Integer32,  
   sisgm1040284lrtTLVConfStateCCOrganizationSpecificLastRX         DisplayString, 
   sisgm1040284lrtTLVConfStateCCPortStatusValue                    Integer32,
   sisgm1040284lrtTLVConfStateCCPortStatusLastRX                   DisplayString, 
   sisgm1040284lrtTLVConfStateCCInterfaceStatusValue               Integer32,
   sisgm1040284lrtTLVConfStateCCInterfaceStatusLastRX              DisplayString
}

sisgm1040284lrtTLVConfStateIndex OBJECT-TYPE
   SYNTAX      Integer32
   MAX-ACCESS  not-accessible
   STATUS      current
   DESCRIPTION
       "Index"
   ::= { sisgm1040284lrtTLVConfStateEntry 1 }
   
sisgm1040284lrtTLVConfStatePeerMEPID OBJECT-TYPE
   SYNTAX      Integer32
   MAX-ACCESS  read-only
   STATUS      current
   DESCRIPTION
       "Peer MEP ID"
   ::= { sisgm1040284lrtTLVConfStateEntry 2 }   
   
sisgm1040284lrtTLVConfStateCCOrganizationSpecificOUIFirst OBJECT-TYPE
   SYNTAX      Integer32
   MAX-ACCESS  read-only
   STATUS      current
   DESCRIPTION
       "The last received first value in the OUI field."
   ::= { sisgm1040284lrtTLVConfStateEntry 3 }      
   
sisgm1040284lrtTLVConfStateCCOrganizationSpecificOUISecond OBJECT-TYPE
   SYNTAX      Integer32
   MAX-ACCESS  read-only
   STATUS      current
   DESCRIPTION
       "The last received second value in the OS TLV OUI field."
   ::= { sisgm1040284lrtTLVConfStateEntry 4 }    
   
sisgm1040284lrtTLVConfStateCCOrganizationSpecificOUIThird OBJECT-TYPE
   SYNTAX      Integer32
   MAX-ACCESS  read-only
   STATUS      current
   DESCRIPTION
       "The last received third value in the OS TLV OUI field."
   ::= { sisgm1040284lrtTLVConfStateEntry 5 }  
   
sisgm1040284lrtTLVConfStateCCOrganizationSpecificSubType OBJECT-TYPE
   SYNTAX      Integer32
   MAX-ACCESS  read-only
   STATUS      current
   DESCRIPTION
       "The last received value in the OS TLV Sub-Type field."
   ::= { sisgm1040284lrtTLVConfStateEntry 6 }   

sisgm1040284lrtTLVConfStateCCOrganizationSpecificValue OBJECT-TYPE
   SYNTAX      Integer32
   MAX-ACCESS  read-only
   STATUS      current
   DESCRIPTION
       "The last received value in the OS TLV Value field."
   ::= { sisgm1040284lrtTLVConfStateEntry 7 }  

sisgm1040284lrtTLVConfStateCCOrganizationSpecificLastRX OBJECT-TYPE
   SYNTAX      DisplayString
   MAX-ACCESS  read-only
   STATUS      current
   DESCRIPTION
       "OS TLV was received in the last received CCM PDU."
   ::= { sisgm1040284lrtTLVConfStateEntry 8 }  

sisgm1040284lrtTLVConfStateCCPortStatusValue OBJECT-TYPE
   SYNTAX      Integer32
   MAX-ACCESS  read-only
   STATUS      current
   DESCRIPTION
       "The last received value in the PS TLV Value field."
   ::= { sisgm1040284lrtTLVConfStateEntry 9 }

sisgm1040284lrtTLVConfStateCCPortStatusLastRX OBJECT-TYPE
   SYNTAX      DisplayString
   MAX-ACCESS  read-only
   STATUS      current
   DESCRIPTION
       "PS TLV was received in the last received CCM PDU."
   ::= { sisgm1040284lrtTLVConfStateEntry 10 }  
   
sisgm1040284lrtTLVConfStateCCInterfaceStatusValue OBJECT-TYPE
   SYNTAX      Integer32
   MAX-ACCESS  read-only
   STATUS      current
   DESCRIPTION
       "The last received value in the IS TLV Value field."
   ::= { sisgm1040284lrtTLVConfStateEntry 11 }   
   
sisgm1040284lrtTLVConfStateCCInterfaceStatusLastRX OBJECT-TYPE
   SYNTAX      DisplayString
   MAX-ACCESS  read-only
   STATUS      current
   DESCRIPTION
       "IS TLV was received in the last received CCM PDU."
   ::= { sisgm1040284lrtTLVConfStateEntry 12 } 

sisgm1040284lrtLinkStateTracking OBJECT-TYPE
   SYNTAX      Integer32
   MAX-ACCESS  read-write
   STATUS      current
   DESCRIPTION
       "0:disable
	   1:enable"
   ::= { sisgm1040284lrtMEP 8 } 

   
sisgm1040284lrtFaultManagement    OBJECT IDENTIFIER ::= { sisgm1040284lrtMEP 9 }   

sisgm1040284lrtFaultMgmtLoopBackConfEnable OBJECT-TYPE
   SYNTAX      Integer32
   MAX-ACCESS  read-write
   STATUS      current
   DESCRIPTION
       "0:disable
	   1:enable"
   ::= { sisgm1040284lrtFaultManagement 2 } 

sisgm1040284lrtFaultMgmtLoopBackConfDEI OBJECT-TYPE
   SYNTAX      Integer32
   MAX-ACCESS  read-write
   STATUS      current
   DESCRIPTION
       "0:disable
	   1:enable"
   ::= { sisgm1040284lrtFaultManagement 3 } 
   
sisgm1040284lrtFaultMgmtLoopBackConfPriority OBJECT-TYPE
   SYNTAX      Integer32
   MAX-ACCESS  read-write
   STATUS      current
   DESCRIPTION
       "range:0-7"
   ::= { sisgm1040284lrtFaultManagement 4 } 
 
sisgm1040284lrtFaultMgmtLoopBackConfCast OBJECT-TYPE
   SYNTAX      Integer32
   MAX-ACCESS  read-write
   STATUS      current
   DESCRIPTION
       "0:Unicast destination address
	   1:Multicast destination address"
   ::= { sisgm1040284lrtFaultManagement 5 }  
 
sisgm1040284lrtFaultMgmtLoopBackConfPeerMEP OBJECT-TYPE
   SYNTAX      Integer32
   MAX-ACCESS  read-write
   STATUS      current
   DESCRIPTION
       "This is only used if the 'Unicast MAC' is configured to all zero. 
	   The LBM unicast MAC will be taken from the 'Unicast Peer MAC' configuration of this peer."
   ::= { sisgm1040284lrtFaultManagement 6 }  
 
sisgm1040284lrtFaultMgmtLoopBackConfUnicastMAC OBJECT-TYPE
   SYNTAX      DisplayString
   MAX-ACCESS  read-write
   STATUS      current
   DESCRIPTION
       "This is only used if NOT configured to all zero. 
	   This will be used as the LBM PDU unicast MAC. 
	   This is the only way to configure Loop Back to-wards a MIP. "
   ::= { sisgm1040284lrtFaultManagement 7 }  
   
sisgm1040284lrtFaultMgmtLoopBackConfToSend OBJECT-TYPE
   SYNTAX      Integer32
   MAX-ACCESS  read-write
   STATUS      current
   DESCRIPTION
       "The number of LBM PDU to send in one loop test. 
	   The value 0 indicate infinite transmission (test behaviour). 
	   This is HW based LBM/LBR and Requires VOE."
   ::= { sisgm1040284lrtFaultManagement 8 } 
   
sisgm1040284lrtFaultMgmtLoopBackConfSize OBJECT-TYPE
   SYNTAX      Integer32
   MAX-ACCESS  read-write
   STATUS      current
   DESCRIPTION
       "The LBM frame size."
   ::= { sisgm1040284lrtFaultManagement 9 } 
   
sisgm1040284lrtFaultMgmtLoopBackConfInterval OBJECT-TYPE
   SYNTAX      Integer32
   MAX-ACCESS  read-write
   STATUS      current
   DESCRIPTION
       "The interval between transmitting LBM PDU."
   ::= { sisgm1040284lrtFaultManagement 10 } 
   
   
sisgm1040284lrtFaultManagementState    OBJECT IDENTIFIER ::= { sisgm1040284lrtMEP 10 }  
   
   
sisgm1040284lrtFaultMgmtStateTransactionID OBJECT-TYPE
   SYNTAX      Integer32
   MAX-ACCESS  read-only
   STATUS      current
   DESCRIPTION
       "The transaction id of the first LBM transmitted. 
	   For each LBM transmitted the transaction id in the PDU is incremented."
   ::= { sisgm1040284lrtFaultManagementState 1 } 
   

sisgm1040284lrtFaultMgmtStateTransmitted OBJECT-TYPE
   SYNTAX      Integer32
   MAX-ACCESS  read-only
   STATUS      current
   DESCRIPTION
       "The total number of LBM PDU transmitted."
   ::= { sisgm1040284lrtFaultManagementState 2 } 
   
   
sisgm1040284lrtFaultMgmtStateTable OBJECT-TYPE
   SYNTAX      SEQUENCE OF SISGM1040284LRTFaultMgmtStateEntry
   MAX-ACCESS  not-accessible
   STATUS      current
   DESCRIPTION
       " "
   ::= { sisgm1040284lrtFaultManagementState 3 }

sisgm1040284lrtFaultMgmtStateEntry OBJECT-TYPE
   SYNTAX      SISGM1040284LRTFaultMgmtStateEntry
   MAX-ACCESS  not-accessible
   STATUS      current
   DESCRIPTION
       " "
   INDEX    { sisgm1040284lrtFaultMgmtStateIndex  }
   ::= { sisgm1040284lrtFaultMgmtStateTable 1 }

SISGM1040284LRTFaultMgmtStateEntry ::= SEQUENCE {
   sisgm1040284lrtFaultMgmtStateIndex               Integer32,
   sisgm1040284lrtFaultMgmtStateReplyMAC            DisplayString,
   sisgm1040284lrtFaultMgmtStateReceived            Integer32,
   sisgm1040284lrtFaultMgmtStateOutOfOrder          Integer32
}

sisgm1040284lrtFaultMgmtStateIndex OBJECT-TYPE
   SYNTAX      Integer32
   MAX-ACCESS  not-accessible
   STATUS      current
   DESCRIPTION
       "Index"
   ::= { sisgm1040284lrtFaultMgmtStateEntry 1 }

sisgm1040284lrtFaultMgmtStateReplyMAC OBJECT-TYPE
   SYNTAX      DisplayString
   MAX-ACCESS  read-only
   STATUS      current
   DESCRIPTION
       "The MAC of the replying MEP/MIP. 
	   In case of multi-cast LBM, replies can be received from all peer MEP in the group. 
	   This MAC is not shown in case of 'To Send' == 0."
   ::= { sisgm1040284lrtFaultMgmtStateEntry 2 }

sisgm1040284lrtFaultMgmtStateReceived OBJECT-TYPE
   SYNTAX      Integer32
   MAX-ACCESS  read-only
   STATUS      current
   DESCRIPTION
       "The total number of LBR PDU received from this 'Reply MAC'."
   ::= { sisgm1040284lrtFaultMgmtStateEntry 3 }   
   
sisgm1040284lrtFaultMgmtStateOutOfOrder OBJECT-TYPE
   SYNTAX      Integer32
   MAX-ACCESS  read-only
   STATUS      current
   DESCRIPTION
       "The number of LBR PDU received from this 'Reply MAC' with incorrect 'Transaction ID'."
   ::= { sisgm1040284lrtFaultMgmtStateEntry 4 }  
   
sisgm1040284lrtFaultMgmtTestSignal    OBJECT IDENTIFIER ::= { sisgm1040284lrtMEP 11 }  

sisgm1040284lrtFaultMgmtTestSignalTx OBJECT-TYPE
   SYNTAX      Integer32
   MAX-ACCESS  read-write
   STATUS      current
   DESCRIPTION
       "Test Signal based on transmitting TST PDU can be enabled/disabled.
	   0:disable
	   1:enable"
   ::= { sisgm1040284lrtFaultMgmtTestSignal 2 }  
   
sisgm1040284lrtFaultMgmtTestSignalRx OBJECT-TYPE
   SYNTAX      Integer32
   MAX-ACCESS  read-write
   STATUS      current
   DESCRIPTION
       "Test Signal based on transmitting TST PDU can be enabled/disabled.
	   0:disable
	   1:enable"
   ::= { sisgm1040284lrtFaultMgmtTestSignal 3 }  
   
sisgm1040284lrtFaultMgmtTestSignalDEI OBJECT-TYPE
   SYNTAX      Integer32
   MAX-ACCESS  read-write
   STATUS      current
   DESCRIPTION
       "The DEI to be inserted as PCP bits in TAG (if any).
	   0:disable
	   1:enable"
   ::= { sisgm1040284lrtFaultMgmtTestSignal 4 }  

sisgm1040284lrtFaultMgmtTestSignalPriority OBJECT-TYPE
   SYNTAX      Integer32
   MAX-ACCESS  read-write
   STATUS      current
   DESCRIPTION
       "The priority to be inserted as PCP bits in TAG (if any).
       Range:0-7"
   ::= { sisgm1040284lrtFaultMgmtTestSignal 5 }    
   
sisgm1040284lrtFaultMgmtTestSignalPeerMEP OBJECT-TYPE
   SYNTAX      Integer32
   MAX-ACCESS  read-write
   STATUS      current
   DESCRIPTION
       "The TST frame destination MAC will be taken from the 'Unicast Peer MAC' configuration of this peer."
   ::= { sisgm1040284lrtFaultMgmtTestSignal 6 }    
   
sisgm1040284lrtFaultMgmtTestSignalRate OBJECT-TYPE
   SYNTAX      Integer32
   MAX-ACCESS  read-write
   STATUS      current
   DESCRIPTION
       "The TST frame transmission bit rate - in Mega bits pr. second. 
	   Limit is 400 Mbps. This is the bit rate of a standard frame without any encapsulation. 
	   If 1 Mbps rate is selected in a EVC MEP, the added tag will give a higher bitrate on the wire."
   ::= { sisgm1040284lrtFaultMgmtTestSignal 7 }  
   
sisgm1040284lrtFaultMgmtTestSignalSize OBJECT-TYPE
   SYNTAX      Integer32
   MAX-ACCESS  read-write
   STATUS      current
   DESCRIPTION
       "The TST frame size. This is entered as the wanted size (in bytes) of a un-tagged frame containing TST OAM PDU - including CRC (four bytes)."
   ::= { sisgm1040284lrtFaultMgmtTestSignal 8 }  
   
sisgm1040284lrtFaultMgmtTestSignalPattern OBJECT-TYPE
   SYNTAX      Integer32
   MAX-ACCESS  read-write
   STATUS      current
   DESCRIPTION
       "The 'empty' TST PDU has the size of 12 bytes. 
	   In order to achieve the configured frame size a data TLV will be added with a pattern.
	   0:All Zero
	   1:All One
	   2:10101010"
   ::= { sisgm1040284lrtFaultMgmtTestSignal 9 }  
   
sisgm1040284lrtFaultMgmtTestSignalSequenceNumber OBJECT-TYPE
   SYNTAX      Integer32
   MAX-ACCESS  read-write
   STATUS      current
   DESCRIPTION
       "0:disable
	   1:enable"
   ::= { sisgm1040284lrtFaultMgmtTestSignal 10 }  
   
sisgm1040284lrtFaultMgmtTestSignalState    OBJECT IDENTIFIER ::= { sisgm1040284lrtMEP 12 }  
   
sisgm1040284lrtFaultMgmtTestSignalStateTXFrameCount OBJECT-TYPE
   SYNTAX      Integer32
   MAX-ACCESS  read-only
   STATUS      current
   DESCRIPTION
       "The number of transmitted TST frames since last 'Clear'."
   ::= { sisgm1040284lrtFaultMgmtTestSignalState 2 }  
   
sisgm1040284lrtFaultMgmtTestSignalStateRXFrameCount OBJECT-TYPE
   SYNTAX      Integer32
   MAX-ACCESS  read-only
   STATUS      current
   DESCRIPTION
       "The number of received TST frames since last 'Clear'."
   ::= { sisgm1040284lrtFaultMgmtTestSignalState 3 }  
   
sisgm1040284lrtFaultMgmtTestSignalStateRXRate OBJECT-TYPE
   SYNTAX      Integer32
   MAX-ACCESS  read-only
   STATUS      current
   DESCRIPTION
       "The current received TST frame bit rate in Kbps. 
	   This is calculated on a 1 s. basis, starting when first TST frame is received after 'Clear'. 
	   The frame size used for this calculation is the first received after 'Clear'"
   ::= { sisgm1040284lrtFaultMgmtTestSignalState 4 }  
   
sisgm1040284lrtFaultMgmtTestSignalStateTestTime OBJECT-TYPE
   SYNTAX      Integer32
   MAX-ACCESS  read-only
   STATUS      current
   DESCRIPTION
       "The number of seconds passed since first TST frame received after last 'Clear'."
   ::= { sisgm1040284lrtFaultMgmtTestSignalState 5 }  
   
   
sisgm1040284lrtFaultMgmtTestSignalStateClear OBJECT-TYPE
   SYNTAX      Integer32
   MAX-ACCESS  read-write
   STATUS      current
   DESCRIPTION
       "This will clear all Test Signal State. 
	   Transmission of TST frame will be restarted. 
	   Calculation of 'Rx frame count', 'RX rate' and 'Test time' will be started when receiving first TST frame."
   ::= { sisgm1040284lrtFaultMgmtTestSignalState 6 }     
   
   
sisgm1040284lrtFaultMgmtClientConfigFlow    OBJECT IDENTIFIER ::= { sisgm1040284lrtMEP 13 }  

sisgm1040284lrtFaultMgmtClientConfigFlowTable OBJECT-TYPE
   SYNTAX      SEQUENCE OF SISGM1040284LRTFaultMgmtClientConfigFlowEntry
   MAX-ACCESS  not-accessible
   STATUS      current
   DESCRIPTION
       " "
   ::= { sisgm1040284lrtFaultMgmtClientConfigFlow 1 }

sisgm1040284lrtFaultMgmtClientConfigFlowEntry OBJECT-TYPE
   SYNTAX      SISGM1040284LRTFaultMgmtClientConfigFlowEntry
   MAX-ACCESS  not-accessible
   STATUS      current
   DESCRIPTION
       " "
   INDEX    { sisgm1040284lrtFaultMgmtClientConfigFlowIndex  }
   ::= { sisgm1040284lrtFaultMgmtClientConfigFlowTable 1 }

SISGM1040284LRTFaultMgmtClientConfigFlowEntry ::= SEQUENCE {
   sisgm1040284lrtFaultMgmtClientConfigFlowIndex     Integer32,
   sisgm1040284lrtFaultMgmtClientConfigFlowDomain    Integer32,
   sisgm1040284lrtFaultMgmtClientConfigFlowInstance  Integer32,
   sisgm1040284lrtFaultMgmtClientConfigFlowLevel     Integer32,
   sisgm1040284lrtFaultMgmtClientConfigFlowAISprio   Integer32,
   sisgm1040284lrtFaultMgmtClientConfigFlowLCKprio   Integer32,
   sisgm1040284lrtFaultMgmtClientConfigFlowRowStatus RowStatus
}

sisgm1040284lrtFaultMgmtClientConfigFlowIndex OBJECT-TYPE
   SYNTAX      Integer32
   MAX-ACCESS  not-accessible
   STATUS      current
   DESCRIPTION
       "Index"
   ::= { sisgm1040284lrtFaultMgmtClientConfigFlowEntry 1 }

sisgm1040284lrtFaultMgmtClientConfigFlowDomain OBJECT-TYPE
   SYNTAX      Integer32
   MAX-ACCESS  read-create
   STATUS      current
   DESCRIPTION
       "The domain of the client layer flow.
	   Ranfew:0-6
	   0:Port
	   1:EVC
	   2:VLAN
	   3:MPLS_LINK
	   4:MPLS_TUNNEL
	   5:MPLS_PW
	   6:MPLS_LSP"
   ::= { sisgm1040284lrtFaultMgmtClientConfigFlowEntry 2 }  

sisgm1040284lrtFaultMgmtClientConfigFlowInstance OBJECT-TYPE
   SYNTAX      Integer32
   MAX-ACCESS  read-create
   STATUS      current
   DESCRIPTION
       "Client layer flow instance numbers."
   ::= { sisgm1040284lrtFaultMgmtClientConfigFlowEntry 3 }  
   
sisgm1040284lrtFaultMgmtClientConfigFlowLevel OBJECT-TYPE
   SYNTAX      Integer32
   MAX-ACCESS  read-create
   STATUS      current
   DESCRIPTION
       "Client layer level - AIS and LCK PDU transmitted in this client layer flow will be on this level."
   ::= { sisgm1040284lrtFaultMgmtClientConfigFlowEntry 4 }  
   
sisgm1040284lrtFaultMgmtClientConfigFlowAISprio OBJECT-TYPE
   SYNTAX      Integer32
   MAX-ACCESS  read-create
   STATUS      current
   DESCRIPTION
       "The priority to be used when transmitting AIS in each client flow. 
	   Priority resulting in highest possible PCP can be selected.
	   Range:0-7. 255 indicate highest possible is requested"
   ::= { sisgm1040284lrtFaultMgmtClientConfigFlowEntry 5 }  
   
sisgm1040284lrtFaultMgmtClientConfigFlowLCKprio OBJECT-TYPE
   SYNTAX      Integer32
   MAX-ACCESS  read-create
   STATUS      current
   DESCRIPTION
       "The priority to be used when transmitting LCK in each client flow. 
	   Priority resulting in highest possible PCP can be selected.
	   Range:0-7. 255 indicate highest possible is requested"
   ::= { sisgm1040284lrtFaultMgmtClientConfigFlowEntry 6 }  
   
sisgm1040284lrtFaultMgmtClientConfigFlowRowStatus OBJECT-TYPE
   SYNTAX      RowStatus
   MAX-ACCESS  read-create
   STATUS      current
   DESCRIPTION
       "FaultMgmtClientConfigFlow Row Status."
   ::= {sisgm1040284lrtFaultMgmtClientConfigFlowEntry 7 }
   
   
sisgm1040284lrtFaultMgmtAISLOCK    OBJECT IDENTIFIER ::= { sisgm1040284lrtMEP 14 }  
   
sisgm1040284lrtFaultMgmtAISEnable OBJECT-TYPE
   SYNTAX      Integer32
   MAX-ACCESS  read-write
   STATUS      current
   DESCRIPTION
       "Insertion of AIS signal (AIS PDU transmission) in client layer flows, can be enable/disabled.
	   0:disable
	   1:enable"
   ::= { sisgm1040284lrtFaultMgmtAISLOCK 2 }  
   
sisgm1040284lrtFaultMgmtAISFrameRate OBJECT-TYPE
   SYNTAX      Integer32
   MAX-ACCESS  read-write
   STATUS      current
   DESCRIPTION
       "Selecting the frame rate of AIS PDU. 
	   This is the inverse of transmission period as described in Y.1731.
       1: 300 frames per second
	   2: 100 frames per second
	   3: 10 frames per second
	   4: 1 frames per second
	   5: 6 frames per minute
	   6: 1 frames per minute
	   7: 6 frames per hour"
   ::= { sisgm1040284lrtFaultMgmtAISLOCK 3 }  
   
sisgm1040284lrtFaultMgmtAISProtection OBJECT-TYPE
   SYNTAX      Integer32
   MAX-ACCESS  read-write
   STATUS      current
   DESCRIPTION
       "Selecting this means that the first 3 AIS PDU is transmitted as fast as possible - in case of using this for protection in the end point.
	   0:disable
	   1:enable"
   ::= { sisgm1040284lrtFaultMgmtAISLOCK 4 }     
   
   
sisgm1040284lrtFaultMgmtLOCKEnable OBJECT-TYPE
   SYNTAX      Integer32
   MAX-ACCESS  read-write
   STATUS      current
   DESCRIPTION
       "Insertion of LOCK signal (LCK PDU transmission) in client layer flows, can be enable/disabled.
	   0:disable
	   1:enable"
   ::= { sisgm1040284lrtFaultMgmtAISLOCK 5 }   
   
sisgm1040284lrtFaultMgmtLOCKFrameRate OBJECT-TYPE
   SYNTAX      Integer32
   MAX-ACCESS  read-write
   STATUS      current
   DESCRIPTION
       "Selecting the frame rate of LCK PDU. This is the inverse of transmission period as described in Y.1731.
       1: 300 frames per second
	   2: 100 frames per second
	   3: 10 frames per second
	   4: 1 frames per second
	   5: 6 frames per minute
	   6: 1 frames per minute
	   7: 6 frames per hour"
   ::= { sisgm1040284lrtFaultMgmtAISLOCK 6 }  

sisgm1040284lrtPerformanceMonitor  OBJECT IDENTIFIER ::= { sisgm1040284lrtMEP 15 }  

sisgm1040284lrtPerformanceMonitorDataSetEnable OBJECT-TYPE
   SYNTAX      Integer32
   MAX-ACCESS  read-write
   STATUS      current
   DESCRIPTION
       "
	   When enabled this MEP instance will contribute to the 'PM Data Set' gathered by the PM Session.
	   0:disable
	   1:enable"
   ::= { sisgm1040284lrtPerformanceMonitor 2 }   
   
sisgm1040284lrtPerformanceMonitorLossMeasurementEnable OBJECT-TYPE
   SYNTAX      Integer32
   MAX-ACCESS  read-write
   STATUS      current
   DESCRIPTION
       "
	   Loss Measurement based on transmitting/receiving CCM or LMM/LMR PDU can be enabled/disabled - see 'Ended'. 
	   This is only valid with one Peer MEP configured.
	   0:disable
	   1:enable"
   ::= { sisgm1040284lrtPerformanceMonitor 3 }     
   
sisgm1040284lrtPerformanceMonitorLossMeasurementPriority OBJECT-TYPE
   SYNTAX      Integer32
   MAX-ACCESS  read-write
   STATUS      current
   DESCRIPTION
       "
	   The priority to be inserted as PCP bits in TAG (if any). 
	   In case of enable of Continuity Check and Loss Measurement both implemented on SW based CCM, 'Priority' has to be the same.
	   range:0-7"
   ::= { sisgm1040284lrtPerformanceMonitor 4 } 
   
sisgm1040284lrtPerformanceMonitorLossMeasurementFrameRate OBJECT-TYPE
   SYNTAX      Integer32
   MAX-ACCESS  read-write
   STATUS      current
   DESCRIPTION
       "
	   1: 300 frames per second
	   2: 100 frames per second
	   3: 10 frames per second
	   4: 1 frames per second
	   5: 6 frames per minute
	   6: 1 frames per minute
	   7: 6 frames per hour"
   ::= { sisgm1040284lrtPerformanceMonitor 5 }   
   
sisgm1040284lrtPerformanceMonitorLossMeasurementCast OBJECT-TYPE
   SYNTAX      Integer32
   MAX-ACCESS  read-write
   STATUS      current
   DESCRIPTION
       "
	   0: Unicast destination address
	   1: Multicast destination address 
	   "
   ::= { sisgm1040284lrtPerformanceMonitor 6 }  
   
sisgm1040284lrtPerformanceMonitorLossMeasurementEnded OBJECT-TYPE
   SYNTAX      Integer32
   MAX-ACCESS  read-write
   STATUS      current
   DESCRIPTION
       "
	   0: Single ended LM based on LMM/LMR or DM based on DMM/DMR 
	   1: Dual ended LM based on CCM or DM based on 1DM
	   "
   ::= { sisgm1040284lrtPerformanceMonitor 7 }  
   
sisgm1040284lrtPerformanceMonitorLossMeasurementFLRInterval OBJECT-TYPE
   SYNTAX      Integer32
   MAX-ACCESS  read-write
   STATUS      current
   DESCRIPTION
       "
       This is the interval in seconds where the Frame Loss Ratio is calculated.
	   "
   ::= { sisgm1040284lrtPerformanceMonitor 8 }  
   
sisgm1040284lrtPerformanceMonitorLossMeasurementLossThreshold OBJECT-TYPE
   SYNTAX      Integer32
   MAX-ACCESS  read-write
   STATUS      current
   DESCRIPTION
       "
       Far end loss threshold count is incremented if a loss measurement is above this threshold.
	   "
   ::= { sisgm1040284lrtPerformanceMonitor 9 }   
    
sisgm1040284lrtPerformanceMonitorLossMeasurementStateTx OBJECT-TYPE
   SYNTAX      Integer32
   MAX-ACCESS  read-only
   STATUS      current
   DESCRIPTION
       "
	   "
   ::= { sisgm1040284lrtPerformanceMonitor 10 }     
    
sisgm1040284lrtPerformanceMonitorLossMeasurementStateRx OBJECT-TYPE
   SYNTAX      Integer32
   MAX-ACCESS  read-only
   STATUS      current
   DESCRIPTION
       "
	   "
   ::= { sisgm1040284lrtPerformanceMonitor 11 }
   
sisgm1040284lrtPerformanceMonitorLossMeasurementStateNearEndLossCount OBJECT-TYPE
   SYNTAX      Integer32
   MAX-ACCESS  read-only
   STATUS      current
   DESCRIPTION
       "The accumulated near end frame loss count - since last 'clear'.
	   "
   ::= { sisgm1040284lrtPerformanceMonitor 12 }
   
sisgm1040284lrtPerformanceMonitorLossMeasurementStateFarEndLossCount OBJECT-TYPE
   SYNTAX      Integer32
   MAX-ACCESS  read-only
   STATUS      current
   DESCRIPTION
       "The accumulated far end frame loss count - since last 'clear'.
	   "
   ::= { sisgm1040284lrtPerformanceMonitor 13 }
   
sisgm1040284lrtPerformanceMonitorLossMeasurementStateNearEndLossRatio OBJECT-TYPE
   SYNTAX      Integer32
   MAX-ACCESS  read-only
   STATUS      current
   DESCRIPTION
       "The near end frame loss ratio calculated based on the near end frame loss count and far end frame transmitted - in the latest 'FLR Interval'. 
	   The result is given in percent.
	   "
   ::= { sisgm1040284lrtPerformanceMonitor 14 }
   
sisgm1040284lrtPerformanceMonitorLossMeasurementStateFarEndLossRatio OBJECT-TYPE
   SYNTAX      Integer32
   MAX-ACCESS  read-only
   STATUS      current
   DESCRIPTION
       "The far end frame loss ratio calculated based on the far end frame loss count and near end frame transmitted - in the latest 'FLR Interval'. 
	   The result is given in percent.
	   "
   ::= { sisgm1040284lrtPerformanceMonitor 15 }
   
sisgm1040284lrtPerformanceMonitorLossMeasurementStateClear OBJECT-TYPE
   SYNTAX      Integer32
   MAX-ACCESS  read-write
   STATUS      current
   DESCRIPTION
       "Set of this check and save will clear the accumulated counters and restart ratio calculation.
	   "
   ::= { sisgm1040284lrtPerformanceMonitor 16 }
   
sisgm1040284lrtPerformanceMonitorLossMeasurementAvailabilityEnable OBJECT-TYPE
   SYNTAX      Integer32
   MAX-ACCESS  read-write
   STATUS      current
   DESCRIPTION
       "Enable/disable of loss measurement availability.
	   0:disable
	   1:enable	   
	   "
   ::= { sisgm1040284lrtPerformanceMonitor 17 }
   
sisgm1040284lrtPerformanceMonitorLossMeasurementAvailabilityInterval OBJECT-TYPE
   SYNTAX      Integer32
   MAX-ACCESS  read-write
   STATUS      current
   DESCRIPTION
       "Availability interval - number of measurements with same availability in order to change availability state.
	   
	   "
   ::= { sisgm1040284lrtPerformanceMonitor 18 }
   
sisgm1040284lrtPerformanceMonitorLossMeasurementAvailabilityFLRThreshold OBJECT-TYPE
   SYNTAX      Integer32
   MAX-ACCESS  read-write
   STATUS      current
   DESCRIPTION
       "Availability frame loss ratio threshold in per mille.
	   "
   ::= { sisgm1040284lrtPerformanceMonitor 19 }
   
sisgm1040284lrtPerformanceMonitorLossMeasurementAvailabilityMaintenance OBJECT-TYPE
   SYNTAX      Integer32
   MAX-ACCESS  read-write
   STATUS      current
   DESCRIPTION
       "Enable/disable of loss measurement availability maintenance.
	   "
   ::= { sisgm1040284lrtPerformanceMonitor 20 }  
   
   
sisgm1040284lrtPerformanceMonitorLossMeasurementAvailabilityStateNearAvailabilityCount OBJECT-TYPE
   SYNTAX      Integer32
   MAX-ACCESS  read-only
   STATUS      current
   DESCRIPTION
       "Near end availability count.
	   "
   ::= { sisgm1040284lrtPerformanceMonitor 21 }     
   
sisgm1040284lrtPerformanceMonitorLossMeasurementAvailabilityStateFarAvailabilityCount OBJECT-TYPE
   SYNTAX      Integer32
   MAX-ACCESS  read-only
   STATUS      current
   DESCRIPTION
       "Far end availability count.
	   "
   ::= { sisgm1040284lrtPerformanceMonitor 22 }  
   
sisgm1040284lrtPerformanceMonitorLossMeasurementAvailabilityStateNearUnavailabilityCount OBJECT-TYPE
   SYNTAX      Integer32
   MAX-ACCESS  read-only
   STATUS      current
   DESCRIPTION
       "Near end unavailability count.
	   "
   ::= { sisgm1040284lrtPerformanceMonitor 23 }  
   
sisgm1040284lrtPerformanceMonitorLossMeasurementAvailabilityStateFarUnavailabilityCount OBJECT-TYPE
   SYNTAX      Integer32
   MAX-ACCESS  read-only
   STATUS      current
   DESCRIPTION
       "Far end unavailability count.
	   "
   ::= { sisgm1040284lrtPerformanceMonitor 24 }  
   
sisgm1040284lrtPerformanceMonitorLossMeasurementAvailabilityStateNearState OBJECT-TYPE
   SYNTAX      Integer32
   MAX-ACCESS  read-only
   STATUS      current
   DESCRIPTION
       "Near end availability state.
	   "
   ::= { sisgm1040284lrtPerformanceMonitor 25 }  
   
sisgm1040284lrtPerformanceMonitorLossMeasurementAvailabilityStateFarState OBJECT-TYPE
   SYNTAX      Integer32
   MAX-ACCESS  read-only
   STATUS      current
   DESCRIPTION
       "Far end availability state.
	   "
   ::= { sisgm1040284lrtPerformanceMonitor 26 }  
   
sisgm1040284lrtPerformanceMonitorLossMeasurementHighLossIntervalEnable OBJECT-TYPE
   SYNTAX      Integer32
   MAX-ACCESS  read-write
   STATUS      current
   DESCRIPTION
       "Enable/disable of loss measurement high loss interval.
	   0:disable
	   1:enable	 
	   "
   ::= { sisgm1040284lrtPerformanceMonitor 27 }  
   
sisgm1040284lrtPerformanceMonitorLossMeasurementHighLossIntervalFLRThreshold OBJECT-TYPE
   SYNTAX      Integer32
   MAX-ACCESS  read-write
   STATUS      current
   DESCRIPTION
       "High Loss Interval frame loss ratio threshold in per mille.
	   "
   ::= { sisgm1040284lrtPerformanceMonitor 28 }  
   
sisgm1040284lrtPerformanceMonitorLossMeasurementHighLossIntervalConsecutiveInterval OBJECT-TYPE
   SYNTAX      Integer32
   MAX-ACCESS  read-write
   STATUS      current
   DESCRIPTION
       "High Loss Interval consecutive interval (number of measurements).
	   "
   ::= { sisgm1040284lrtPerformanceMonitor 29 }   
   
sisgm1040284lrtPerformanceMonitorLossMeasurementHighLossIntervalStateNearCount OBJECT-TYPE
   SYNTAX      Integer32
   MAX-ACCESS  read-only
   STATUS      current
   DESCRIPTION
       "Near end high loss interval count (number of measurements where availability state is available and FLR is above high loss interval FLR threshold.
	   "
   ::= { sisgm1040284lrtPerformanceMonitor 30 }   
   
sisgm1040284lrtPerformanceMonitorLossMeasurementHighLossIntervalStateFarCount OBJECT-TYPE
   SYNTAX      Integer32
   MAX-ACCESS  read-only
   STATUS      current
   DESCRIPTION
       "Far end high loss interval count (number of measurements where availability state is available and FLR is above high loss interval FLR threshold.
	   "
   ::= { sisgm1040284lrtPerformanceMonitor 31 }  
   
sisgm1040284lrtPerformanceMonitorLossMeasurementHighLossIntervalStateNearConsecutiveCount OBJECT-TYPE
   SYNTAX      Integer32
   MAX-ACCESS  read-only
   STATUS      current
   DESCRIPTION
       "Near end high loss interval consecutive count.
	   "
   ::= { sisgm1040284lrtPerformanceMonitor 32 }  
   
sisgm1040284lrtPerformanceMonitorLossMeasurementHighLossIntervalStateFarConsecutiveCount OBJECT-TYPE
   SYNTAX      Integer32
   MAX-ACCESS  read-only
   STATUS      current
   DESCRIPTION
       "Far end high loss interval consecutive count.
	   "
   ::= { sisgm1040284lrtPerformanceMonitor 33 } 
   
sisgm1040284lrtPerformanceMonitorLossMeasurementSignalDegradeEnable OBJECT-TYPE
   SYNTAX      Integer32
   MAX-ACCESS  read-write
   STATUS      current
   DESCRIPTION
       "Enable/disable of loss measurement signal degrade.
	   0:disable
	   1:enable	 	   
	   "
   ::= { sisgm1040284lrtPerformanceMonitor 34 } 
   
sisgm1040284lrtPerformanceMonitorLossMeasurementSignalDegradeTXMinimum OBJECT-TYPE
   SYNTAX      Integer32
   MAX-ACCESS  read-write
   STATUS      current
   DESCRIPTION
       "Minimum number of frames that must be transmitted in a measurement before frame loss ratio is tested against loss ratio threshold.
 	   
	   "
   ::= { sisgm1040284lrtPerformanceMonitor 35 } 
   
sisgm1040284lrtPerformanceMonitorLossMeasurementSignalDegradeFLRThreshold OBJECT-TYPE
   SYNTAX      Integer32
   MAX-ACCESS  read-write
   STATUS      current
   DESCRIPTION
       "Signal Degraded frame loss ratio threshold in per mille.
	   "
   ::= { sisgm1040284lrtPerformanceMonitor 36 } 
   
sisgm1040284lrtPerformanceMonitorLossMeasurementSignalDegradeBadThreshold OBJECT-TYPE
   SYNTAX      Integer32
   MAX-ACCESS  read-write
   STATUS      current
   DESCRIPTION
       "Number of consecutive bad interval measurements required to set degrade state.
	   "
   ::= { sisgm1040284lrtPerformanceMonitor 37 }    
   
sisgm1040284lrtPerformanceMonitorLossMeasurementSignalDegradeGoodThreshold OBJECT-TYPE
   SYNTAX      Integer32
   MAX-ACCESS  read-write
   STATUS      current
   DESCRIPTION
       "Number of consecutive good interval measurements required to clear degrade state.
	   "
   ::= { sisgm1040284lrtPerformanceMonitor 38 } 
   
sisgm1040284lrtPerformanceMonitorDelayMeasurementEnable OBJECT-TYPE
   SYNTAX      Integer32
   MAX-ACCESS  read-write
   STATUS      current
   DESCRIPTION
       "Delay Measurement based on transmitting 1DM/DMM PDU can be enabled/disabled. 
	   Delay Measurement based on receiving and handling 1DM/DMR PDU is always enabled.
	   0:disable
	   1:enable		   
	   "
   ::= { sisgm1040284lrtPerformanceMonitor 39 } 
   
sisgm1040284lrtPerformanceMonitorDelayMeasurementPriority OBJECT-TYPE
   SYNTAX      Integer32
   MAX-ACCESS  read-write
   STATUS      current
   DESCRIPTION
       "The priority to be inserted as PCP bits in TAG (if any).
       Range:0-7	   
	   "
   ::= { sisgm1040284lrtPerformanceMonitor 40 }  
   
sisgm1040284lrtPerformanceMonitorDelayMeasurementCast OBJECT-TYPE
   SYNTAX      Integer32
   MAX-ACCESS  read-write
   STATUS      current
   DESCRIPTION
       "Selection of 1DM/DMM PDU transmitted unicast or multicast. 
	   The unicast MAC will be configured through 'Peer MEP'.   
	   0: Unicast destination address
	   1: Multicast destination address 	   
	   "
   ::= { sisgm1040284lrtPerformanceMonitor 41 } 
   
sisgm1040284lrtPerformanceMonitorDelayMeasurementPeerMEP OBJECT-TYPE
   SYNTAX      Integer32
   MAX-ACCESS  read-write
   STATUS      current
   DESCRIPTION
       "This is only used if the 'Cast' is configured to Uni. 
	   The 1DM/DMR unicast MAC will be taken from the 'Unicast Peer MAC' configuration of this peer. 
	   "
   ::= { sisgm1040284lrtPerformanceMonitor 42 } 
   
sisgm1040284lrtPerformanceMonitorDelayMeasurementEnded OBJECT-TYPE
   SYNTAX      Integer32
   MAX-ACCESS  read-write
   STATUS      current
   DESCRIPTION
       "0:One-Way: One-Way Delay Measurement implemented on 1DM.
        1:Two-Way: Two-Way Delay Measurement implemented on DMM/DMR.
	   "
   ::= { sisgm1040284lrtPerformanceMonitor 43 } 
   
sisgm1040284lrtPerformanceMonitorDelayMeasurementTxMode OBJECT-TYPE
   SYNTAX      Integer32
   MAX-ACCESS  read-write
   STATUS      current
   DESCRIPTION
       "0:Standardize: Y.1731 standardize way to transmit 1DM/DMR.
        1:Proprietary: Vitesse proprietary way with follow-up packets to transmit 1DM/DMR.
	   "
   ::= { sisgm1040284lrtPerformanceMonitor 44 } 
   
sisgm1040284lrtPerformanceMonitorDelayMeasurementCalc OBJECT-TYPE
   SYNTAX      Integer32
   MAX-ACCESS  read-write
   STATUS      current
   DESCRIPTION
       "This is only used if the 'Way' is configured to Two-way.
        0:Round trip: The frame delay calculated by the transmitting and receiving timestamps of initiators. 
		    Frame Delay = RxTimeb-TxTimeStampf
        1:Flow: The frame delay calculated by the transmitting and receiving timestamps of initiators and remotes. 
		    Frame Delay = (RxTimeb-TxTimeStampf)-(TxTimeStampb-RxTimeStampf)
	   "
   ::= { sisgm1040284lrtPerformanceMonitor 45 } 
   
sisgm1040284lrtPerformanceMonitorDelayMeasurementGap OBJECT-TYPE
   SYNTAX      Integer32
   MAX-ACCESS  read-write
   STATUS      current
   DESCRIPTION
       "The gap between transmitting 1DM/DMM PDU in 10ms. The range is 10 to 65535.
	   "
   ::= { sisgm1040284lrtPerformanceMonitor 46 } 

sisgm1040284lrtPerformanceMonitorDelayMeasurementCount OBJECT-TYPE
   SYNTAX      Integer32
   MAX-ACCESS  read-write
   STATUS      current
   DESCRIPTION
       "The number of last records to calculate. The range is 10 to 2000.
	   "
   ::= { sisgm1040284lrtPerformanceMonitor 47 } 
   
sisgm1040284lrtPerformanceMonitorDelayMeasurementUnit OBJECT-TYPE
   SYNTAX      Integer32
   MAX-ACCESS  read-write
   STATUS      current
   DESCRIPTION
       "The time resolution.
	   0:us
	   1:ns
	   "
   ::= { sisgm1040284lrtPerformanceMonitor 48 }  
   
sisgm1040284lrtPerformanceMonitorDelayMeasurementD2forD1 OBJECT-TYPE
   SYNTAX      Integer32
   MAX-ACCESS  read-write
   STATUS      current
   DESCRIPTION
       "Enable to use DMM/DMR packet to calculate one-way DM.
	   0:disable
	   1:enable	
	   "
   ::= { sisgm1040284lrtPerformanceMonitor 49 }  
   
sisgm1040284lrtPerformanceMonitorDelayMeasurementCounterOverflowAction OBJECT-TYPE
   SYNTAX      Integer32
   MAX-ACCESS  read-write
   STATUS      current
   DESCRIPTION
       "The action to counter when overflow happens.
	   0: Keep:When internal total delay counter overflow, DM is disabled automatically
	   1: Reset:When internal total delay counter overflow, counter is reset and DM continues running
	   "
   ::= { sisgm1040284lrtPerformanceMonitor 50 }  
   
sisgm1040284lrtPerformanceMonitorDelayMeasurementStateOnewayTx OBJECT-TYPE
   SYNTAX      DisplayString
   MAX-ACCESS  read-only
   STATUS      current
   DESCRIPTION
       "The accumulated transmit count - since last 'clear'.
	   "
   ::= { sisgm1040284lrtPerformanceMonitor 51 } 
   
sisgm1040284lrtPerformanceMonitorDelayMeasurementStateOnewayRx OBJECT-TYPE
   SYNTAX      DisplayString
   MAX-ACCESS  read-only
   STATUS      current
   DESCRIPTION
       "The accumulated receive count - since last 'clear'.
	   "
   ::= { sisgm1040284lrtPerformanceMonitor 52 } 
   
sisgm1040284lrtPerformanceMonitorDelayMeasurementStateOnewayRxTimeout OBJECT-TYPE
   SYNTAX      DisplayString
   MAX-ACCESS  read-only
   STATUS      current
   DESCRIPTION
       "The accumulated receive timeout count for two-way only - since last 'clear'.
	   "
   ::= { sisgm1040284lrtPerformanceMonitor 53 } 
   
sisgm1040284lrtPerformanceMonitorDelayMeasurementStateOnewayRxError OBJECT-TYPE
   SYNTAX      DisplayString
   MAX-ACCESS  read-only
   STATUS      current
   DESCRIPTION
       "The accumulated receive error count - since last 'clear'. 
	   This is counting if the frame delay is larger than 1 second or if far end residence time is larger than the round trip time.
	   "
   ::= { sisgm1040284lrtPerformanceMonitor 54 }
   
sisgm1040284lrtPerformanceMonitorDelayMeasurementStateOnewayAvDelayTot OBJECT-TYPE
   SYNTAX      DisplayString
   MAX-ACCESS  read-only
   STATUS      current
   DESCRIPTION
       "The average total delay - since last 'clear'.
	   "
   ::= { sisgm1040284lrtPerformanceMonitor 55 }
   
sisgm1040284lrtPerformanceMonitorDelayMeasurementStateOnewayAvDelaylastN OBJECT-TYPE
   SYNTAX      DisplayString
   MAX-ACCESS  read-only
   STATUS      current
   DESCRIPTION
       "The average delay of the last n packets - since last 'clear'.
	   "
   ::= { sisgm1040284lrtPerformanceMonitor 56 }
   
sisgm1040284lrtPerformanceMonitorDelayMeasurementStateOnewayDelayMin OBJECT-TYPE
   SYNTAX      DisplayString
   MAX-ACCESS  read-only
   STATUS      current
   DESCRIPTION
       "The minimum delay - since last 'clear'.
	   "
   ::= { sisgm1040284lrtPerformanceMonitor 57 }
   
sisgm1040284lrtPerformanceMonitorDelayMeasurementStateOnewayDelayMax OBJECT-TYPE
   SYNTAX      DisplayString
   MAX-ACCESS  read-only
   STATUS      current
   DESCRIPTION
       "The maximum delay - since last 'clear'.
	   "
   ::= { sisgm1040284lrtPerformanceMonitor 58 }
   
sisgm1040284lrtPerformanceMonitorDelayMeasurementStateOnewayAvDelayVarTot OBJECT-TYPE
   SYNTAX      DisplayString
   MAX-ACCESS  read-only
   STATUS      current
   DESCRIPTION
       "The average total delay variation - since last 'clear'.
	   "
   ::= { sisgm1040284lrtPerformanceMonitor 59 }
   
sisgm1040284lrtPerformanceMonitorDelayMeasurementStateOnewayAvDelayVarlastN OBJECT-TYPE
   SYNTAX      DisplayString
   MAX-ACCESS  read-only
   STATUS      current
   DESCRIPTION
       "The average delay variation of the last n packets - since last 'clear'.
	   "
   ::= { sisgm1040284lrtPerformanceMonitor 60 }
   
sisgm1040284lrtPerformanceMonitorDelayMeasurementStateOnewayDelayVarMin OBJECT-TYPE
   SYNTAX      DisplayString
   MAX-ACCESS  read-only
   STATUS      current
   DESCRIPTION
       "The minimum delay variation - since last 'clear'.
	   "
   ::= { sisgm1040284lrtPerformanceMonitor 61 }
   
sisgm1040284lrtPerformanceMonitorDelayMeasurementStateOnewayDelayVarMax OBJECT-TYPE
   SYNTAX      DisplayString
   MAX-ACCESS  read-only
   STATUS      current
   DESCRIPTION
       "The maximum delay variation - since last 'clear'.
	   "
   ::= { sisgm1040284lrtPerformanceMonitor 62 }
   
sisgm1040284lrtPerformanceMonitorDelayMeasurementStateOnewayOverflow OBJECT-TYPE
   SYNTAX      DisplayString
   MAX-ACCESS  read-only
   STATUS      current
   DESCRIPTION
       "The number of counter overflow - since last 'clear'.
	   "
   ::= { sisgm1040284lrtPerformanceMonitor 63 }
   
sisgm1040284lrtPerformanceMonitorDelayMeasurementStateFtoNTx OBJECT-TYPE
   SYNTAX      Integer32
   MAX-ACCESS  read-only
   STATUS      current
   DESCRIPTION
       "The accumulated transmit count - since last 'clear'.
	   "
   ::= { sisgm1040284lrtPerformanceMonitor 64 } 
   
sisgm1040284lrtPerformanceMonitorDelayMeasurementStateFtoNRx OBJECT-TYPE
   SYNTAX      Integer32
   MAX-ACCESS  read-only
   STATUS      current
   DESCRIPTION
       "The accumulated receive count - since last 'clear'.
	   "
   ::= { sisgm1040284lrtPerformanceMonitor 65 } 
   
sisgm1040284lrtPerformanceMonitorDelayMeasurementStateFtoNRxTimeout OBJECT-TYPE
   SYNTAX      Integer32
   MAX-ACCESS  read-only
   STATUS      current
   DESCRIPTION
       "The accumulated receive timeout count for two-way only - since last 'clear'.
	   "
   ::= { sisgm1040284lrtPerformanceMonitor 66 } 
   
sisgm1040284lrtPerformanceMonitorDelayMeasurementStateFtoNRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sisgm1040284lrtPerformanceMonitor 67 }
   
sisgm1040284lrtPerformanceMonitorDelayMeasurementStateFtoNAvDelayTot OBJECT-TYPE
   SYNTAX      Integer32
   MAX-ACCESS  read-only
   STATUS      current
   DESCRIPTION
       "The average total delay - since last 'clear'.
	   "
   ::= { sisgm1040284lrtPerformanceMonitor 68 }
   
sisgm1040284lrtPerformanceMonitorDelayMeasurementStateFtoNAvDelaylastN OBJECT-TYPE
   SYNTAX      Integer32
   MAX-ACCESS  read-only
   STATUS      current
   DESCRIPTION
       "The average delay of the last n packets - since last 'clear'.
	   "
   ::= { sisgm1040284lrtPerformanceMonitor 69 }
   
sisgm1040284lrtPerformanceMonitorDelayMeasurementStateFtoNDelayMin OBJECT-TYPE
   SYNTAX      Integer32
   MAX-ACCESS  read-only
   STATUS      current
   DESCRIPTION
       "The minimum delay - since last 'clear'.
	   "
   ::= { sisgm1040284lrtPerformanceMonitor 70 }
   
sisgm1040284lrtPerformanceMonitorDelayMeasurementStateFtoNDelayMax OBJECT-TYPE
   SYNTAX      Integer32
   MAX-ACCESS  read-only
   STATUS      current
   DESCRIPTION
       "The maximum delay - since last 'clear'.
	   "
   ::= { sisgm1040284lrtPerformanceMonitor 71 }
   
sisgm1040284lrtPerformanceMonitorDelayMeasurementStateFtoNAvDelayVarTot OBJECT-TYPE
   SYNTAX      Integer32
   MAX-ACCESS  read-only
   STATUS      current
   DESCRIPTION
       "The average total delay variation - since last 'clear'.
	   "
   ::= { sisgm1040284lrtPerformanceMonitor 72 }
   
sisgm1040284lrtPerformanceMonitorDelayMeasurementStateFtoNAvDelayVarlastN OBJECT-TYPE
   SYNTAX      Integer32
   MAX-ACCESS  read-only
   STATUS      current
   DESCRIPTION
       "The average delay variation of the last n packets - since last 'clear'.
	   "
   ::= { sisgm1040284lrtPerformanceMonitor 73 }
   
sisgm1040284lrtPerformanceMonitorDelayMeasurementStateFtoNDelayVarMin OBJECT-TYPE
   SYNTAX      Integer32
   MAX-ACCESS  read-only
   STATUS      current
   DESCRIPTION
       "The minimum delay variation - since last 'clear'.
	   "
   ::= { sisgm1040284lrtPerformanceMonitor 74 }
   
sisgm1040284lrtPerformanceMonitorDelayMeasurementStateFtoNDelayVarMax OBJECT-TYPE
   SYNTAX      Integer32
   MAX-ACCESS  read-only
   STATUS      current
   DESCRIPTION
       "The maximum delay variation - since last 'clear'.
	   "
   ::= { sisgm1040284lrtPerformanceMonitor 75 }
   
sisgm1040284lrtPerformanceMonitorDelayMeasurementStateFtoNOverflow OBJECT-TYPE
   SYNTAX      Integer32
   MAX-ACCESS  read-only
   STATUS      current
   DESCRIPTION
       "The number of counter overflow - since last 'clear'.
	   "
   ::= { sisgm1040284lrtPerformanceMonitor 76 }
   
sisgm1040284lrtPerformanceMonitorDelayMeasurementStateNtoFTx OBJECT-TYPE
   SYNTAX      Integer32
   MAX-ACCESS  read-only
   STATUS      current
   DESCRIPTION
       "The accumulated transmit count - since last 'clear'.
	   "
   ::= { sisgm1040284lrtPerformanceMonitor 77 } 
   
sisgm1040284lrtPerformanceMonitorDelayMeasurementStateNtoFRx OBJECT-TYPE
   SYNTAX      Integer32
   MAX-ACCESS  read-only
   STATUS      current
   DESCRIPTION
       "The accumulated receive count - since last 'clear'.
	   "
   ::= { sisgm1040284lrtPerformanceMonitor 78 } 
   
sisgm1040284lrtPerformanceMonitorDelayMeasurementStateNtoFRxTimeout OBJECT-TYPE
   SYNTAX      Integer32
   MAX-ACCESS  read-only
   STATUS      current
   DESCRIPTION
       "The accumulated receive timeout count for two-way only - since last 'clear'.
	   "
   ::= { sisgm1040284lrtPerformanceMonitor 79 } 
   
sisgm1040284lrtPerformanceMonitorDelayMeasurementStateNtoFRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sisgm1040284lrtPerformanceMonitor 80 }
   
sisgm1040284lrtPerformanceMonitorDelayMeasurementStateNtoFAvDelayTot OBJECT-TYPE
   SYNTAX      Integer32
   MAX-ACCESS  read-only
   STATUS      current
   DESCRIPTION
       "The average total delay - since last 'clear'.
	   "
   ::= { sisgm1040284lrtPerformanceMonitor 81 }
   
sisgm1040284lrtPerformanceMonitorDelayMeasurementStateNtoFAvDelaylastN OBJECT-TYPE
   SYNTAX      Integer32
   MAX-ACCESS  read-only
   STATUS      current
   DESCRIPTION
       "The average delay of the last n packets - since last 'clear'.
	   "
   ::= { sisgm1040284lrtPerformanceMonitor 82 }
   
sisgm1040284lrtPerformanceMonitorDelayMeasurementStateNtoFDelayMin OBJECT-TYPE
   SYNTAX      Integer32
   MAX-ACCESS  read-only
   STATUS      current
   DESCRIPTION
       "The minimum delay - since last 'clear'.
	   "
   ::= { sisgm1040284lrtPerformanceMonitor 83 }
   
sisgm1040284lrtPerformanceMonitorDelayMeasurementStateNtoFDelayMax OBJECT-TYPE
   SYNTAX      Integer32
   MAX-ACCESS  read-only
   STATUS      current
   DESCRIPTION
       "The maximum delay - since last 'clear'.
	   "
   ::= { sisgm1040284lrtPerformanceMonitor 84 }
   
sisgm1040284lrtPerformanceMonitorDelayMeasurementStateNtoFAvDelayVarTot OBJECT-TYPE
   SYNTAX      Integer32
   MAX-ACCESS  read-only
   STATUS      current
   DESCRIPTION
       "The average total delay variation - since last 'clear'.
	   "
   ::= { sisgm1040284lrtPerformanceMonitor 85 }
   
sisgm1040284lrtPerformanceMonitorDelayMeasurementStateNtoFAvDelayVarlastN OBJECT-TYPE
   SYNTAX      Integer32
   MAX-ACCESS  read-only
   STATUS      current
   DESCRIPTION
       "The average delay variation of the last n packets - since last 'clear'.
	   "
   ::= { sisgm1040284lrtPerformanceMonitor 86 }
   
sisgm1040284lrtPerformanceMonitorDelayMeasurementStateNtoFDelayVarMin OBJECT-TYPE
   SYNTAX      Integer32
   MAX-ACCESS  read-only
   STATUS      current
   DESCRIPTION
       "The minimum delay variation - since last 'clear'.
	   "
   ::= { sisgm1040284lrtPerformanceMonitor 87 }
   
sisgm1040284lrtPerformanceMonitorDelayMeasurementStateNtoFDelayVarMax OBJECT-TYPE
   SYNTAX      Integer32
   MAX-ACCESS  read-only
   STATUS      current
   DESCRIPTION
       "The maximum delay variation - since last 'clear'.
	   "
   ::= { sisgm1040284lrtPerformanceMonitor 88 }
   
sisgm1040284lrtPerformanceMonitorDelayMeasurementStateNtoFOverflow OBJECT-TYPE
   SYNTAX      Integer32
   MAX-ACCESS  read-only
   STATUS      current
   DESCRIPTION
       "The number of counter overflow - since last 'clear'.
	   "
   ::= { sisgm1040284lrtPerformanceMonitor 89 }
   
sisgm1040284lrtPerformanceMonitorDelayMeasurementStateTwowayTx OBJECT-TYPE
   SYNTAX      Integer32
   MAX-ACCESS  read-only
   STATUS      current
   DESCRIPTION
       "The accumulated transmit count - since last 'clear'.
	   "
   ::= { sisgm1040284lrtPerformanceMonitor 90 } 
   
sisgm1040284lrtPerformanceMonitorDelayMeasurementStateTwowayRx OBJECT-TYPE
   SYNTAX      Integer32
   MAX-ACCESS  read-only
   STATUS      current
   DESCRIPTION
       "The accumulated receive count - since last 'clear'.
	   "
   ::= { sisgm1040284lrtPerformanceMonitor 91 } 
   
sisgm1040284lrtPerformanceMonitorDelayMeasurementStateTwowayRxTimeout OBJECT-TYPE
   SYNTAX      Integer32
   MAX-ACCESS  read-only
   STATUS      current
   DESCRIPTION
       "The accumulated receive timeout count for two-way only - since last 'clear'.
	   "
   ::= { sisgm1040284lrtPerformanceMonitor 92 } 
   
sisgm1040284lrtPerformanceMonitorDelayMeasurementStateTwowayRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sisgm1040284lrtPerformanceMonitor 93 }
   
sisgm1040284lrtPerformanceMonitorDelayMeasurementStateTwowayAvDelayTot OBJECT-TYPE
   SYNTAX      Integer32
   MAX-ACCESS  read-only
   STATUS      current
   DESCRIPTION
       "The average total delay - since last 'clear'.
	   "
   ::= { sisgm1040284lrtPerformanceMonitor 94 }
   
sisgm1040284lrtPerformanceMonitorDelayMeasurementStateTwowayAvDelaylastN OBJECT-TYPE
   SYNTAX      Integer32
   MAX-ACCESS  read-only
   STATUS      current
   DESCRIPTION
       "The average delay of the last n packets - since last 'clear'.
	   "
   ::= { sisgm1040284lrtPerformanceMonitor 95 }
   
sisgm1040284lrtPerformanceMonitorDelayMeasurementStateTwowayDelayMin OBJECT-TYPE
   SYNTAX      Integer32
   MAX-ACCESS  read-only
   STATUS      current
   DESCRIPTION
       "The minimum delay - since last 'clear'.
	   "
   ::= { sisgm1040284lrtPerformanceMonitor 96 }
   
sisgm1040284lrtPerformanceMonitorDelayMeasurementStateTwowayDelayMax OBJECT-TYPE
   SYNTAX      Integer32
   MAX-ACCESS  read-only
   STATUS      current
   DESCRIPTION
       "The maximum delay - since last 'clear'.
	   "
   ::= { sisgm1040284lrtPerformanceMonitor 97 }
   
sisgm1040284lrtPerformanceMonitorDelayMeasurementStateTwowayAvDelayVarTot OBJECT-TYPE
   SYNTAX      Integer32
   MAX-ACCESS  read-only
   STATUS      current
   DESCRIPTION
       "The average total delay variation - since last 'clear'.
	   "
   ::= { sisgm1040284lrtPerformanceMonitor 98 }
   
sisgm1040284lrtPerformanceMonitorDelayMeasurementStateTwowayAvDelayVarlastN OBJECT-TYPE
   SYNTAX      Integer32
   MAX-ACCESS  read-only
   STATUS      current
   DESCRIPTION
       "The average delay variation of the last n packets - since last 'clear'.
	   "
   ::= { sisgm1040284lrtPerformanceMonitor 99 }
   
sisgm1040284lrtPerformanceMonitorDelayMeasurementStateTwowayDelayVarMin OBJECT-TYPE
   SYNTAX      Integer32
   MAX-ACCESS  read-only
   STATUS      current
   DESCRIPTION
       "The minimum delay variation - since last 'clear'.
	   "
   ::= { sisgm1040284lrtPerformanceMonitor 100 }
   
sisgm1040284lrtPerformanceMonitorDelayMeasurementStateTwowayDelayVarMax OBJECT-TYPE
   SYNTAX      Integer32
   MAX-ACCESS  read-only
   STATUS      current
   DESCRIPTION
       "The maximum delay variation - since last 'clear'.
	   "
   ::= { sisgm1040284lrtPerformanceMonitor 101 }
   
sisgm1040284lrtPerformanceMonitorDelayMeasurementStateTwowayOverflow OBJECT-TYPE
   SYNTAX      Integer32
   MAX-ACCESS  read-only
   STATUS      current
   DESCRIPTION
       "The number of counter overflow - since last 'clear'.
	   "
   ::= { sisgm1040284lrtPerformanceMonitor 102 }
   
sisgm1040284lrtPerformanceMonitorDelayMeasurementStateClear OBJECT-TYPE
   SYNTAX      Integer32
   MAX-ACCESS  read-write
   STATUS      current
   DESCRIPTION
       "Set of this check and save will clear the accumulated counters.
	   1:clear
	   "
   ::= { sisgm1040284lrtPerformanceMonitor 103 }
   
sisgm1040284lrtPerformanceMonitorDelayMeasurementBinsMeasurementBinsforFD OBJECT-TYPE
   SYNTAX      Integer32
   MAX-ACCESS  read-write
   STATUS      current
   DESCRIPTION
       "Configurable number of Frame Delay Measurement Bins per Measurement Interval.
	   range: 2-10
	   "
   ::= { sisgm1040284lrtPerformanceMonitor 104 }
   
sisgm1040284lrtPerformanceMonitorDelayMeasurementBinsMeasurementBinsforIFDV OBJECT-TYPE
   SYNTAX      Integer32
   MAX-ACCESS  read-write
   STATUS      current
   DESCRIPTION
       "Configurable number of Inter-Frame Delay Variation Measurement Bins per Measurement Interval.
	   range: 2-10
	   "
   ::= { sisgm1040284lrtPerformanceMonitor 105 }
   
sisgm1040284lrtPerformanceMonitorDelayMeasurementBinsMeasurementThreshold OBJECT-TYPE
   SYNTAX      Integer32
   MAX-ACCESS  read-write
   STATUS      current
   DESCRIPTION
       "Configurable the Measurement Threshold for each Measurement Bin.
	   "
   ::= { sisgm1040284lrtPerformanceMonitor 106 }
   
   
   
   
sisgm1040284lrtPerformanceMonitorDelayMeasurementBinsforFDTable OBJECT-TYPE
   SYNTAX      SEQUENCE OF SISGM1040284LRTPerformanceMonitorDelayMeasurementBinsforFDEntry
   MAX-ACCESS  not-accessible
   STATUS      current
   DESCRIPTION
       " "
   ::= { sisgm1040284lrtMEP 16 }

sisgm1040284lrtPerformanceMonitorDelayMeasurementBinsforFDEntry OBJECT-TYPE
   SYNTAX      SISGM1040284LRTPerformanceMonitorDelayMeasurementBinsforFDEntry
   MAX-ACCESS  not-accessible
   STATUS      current
   DESCRIPTION
       " "
   INDEX    { sisgm1040284lrtPerformanceMonitorDelayMeasurementBinsforFDIndex  }
   ::= { sisgm1040284lrtPerformanceMonitorDelayMeasurementBinsforFDTable 1 }

SISGM1040284LRTPerformanceMonitorDelayMeasurementBinsforFDEntry ::= SEQUENCE {
   sisgm1040284lrtPerformanceMonitorDelayMeasurementBinsforFDIndex    Integer32,
   sisgm1040284lrtPerformanceMonitorDelayMeasurementBinsforFDOneway   Integer32,
   sisgm1040284lrtPerformanceMonitorDelayMeasurementBinsforFDFtoN     Integer32,
   sisgm1040284lrtPerformanceMonitorDelayMeasurementBinsforFDNtoF     Integer32,
   sisgm1040284lrtPerformanceMonitorDelayMeasurementBinsforFDTwoway   Integer32
   
}

sisgm1040284lrtPerformanceMonitorDelayMeasurementBinsforFDIndex OBJECT-TYPE
   SYNTAX      Integer32
   MAX-ACCESS  not-accessible
   STATUS      current
   DESCRIPTION
       "Index"
   ::= { sisgm1040284lrtPerformanceMonitorDelayMeasurementBinsforFDEntry 1 }

sisgm1040284lrtPerformanceMonitorDelayMeasurementBinsforFDOneway OBJECT-TYPE
   SYNTAX      Integer32
   MAX-ACCESS  read-only
   STATUS      current
   DESCRIPTION
       " "
   ::= { sisgm1040284lrtPerformanceMonitorDelayMeasurementBinsforFDEntry 2 }

sisgm1040284lrtPerformanceMonitorDelayMeasurementBinsforFDFtoN OBJECT-TYPE
   SYNTAX      Integer32
   MAX-ACCESS  read-only
   STATUS      current
   DESCRIPTION
       " "
   ::= { sisgm1040284lrtPerformanceMonitorDelayMeasurementBinsforFDEntry 3 }
   
sisgm1040284lrtPerformanceMonitorDelayMeasurementBinsforFDNtoF OBJECT-TYPE
   SYNTAX      Integer32
   MAX-ACCESS  read-only
   STATUS      current
   DESCRIPTION
       " "
   ::= { sisgm1040284lrtPerformanceMonitorDelayMeasurementBinsforFDEntry 4 }  
   
sisgm1040284lrtPerformanceMonitorDelayMeasurementBinsforFDTwoway OBJECT-TYPE
   SYNTAX      Integer32
   MAX-ACCESS  read-only
   STATUS      current
   DESCRIPTION
       " "
   ::= { sisgm1040284lrtPerformanceMonitorDelayMeasurementBinsforFDEntry 5 } 
   
   
   
   
sisgm1040284lrtPerformanceMonitorDelayMeasurementBinsforIFDVTable OBJECT-TYPE
   SYNTAX      SEQUENCE OF SISGM1040284LRTPerformanceMonitorDelayMeasurementBinsforIFDVEntry
   MAX-ACCESS  not-accessible
   STATUS      current
   DESCRIPTION
       " "
   ::= { sisgm1040284lrtMEP 17 }

sisgm1040284lrtPerformanceMonitorDelayMeasurementBinsforIFDVEntry OBJECT-TYPE
   SYNTAX      SISGM1040284LRTPerformanceMonitorDelayMeasurementBinsforIFDVEntry
   MAX-ACCESS  not-accessible
   STATUS      current
   DESCRIPTION
       " "
   INDEX    { sisgm1040284lrtPerformanceMonitorDelayMeasurementBinsforIFDVIndex  }
   ::= { sisgm1040284lrtPerformanceMonitorDelayMeasurementBinsforIFDVTable 1 }

SISGM1040284LRTPerformanceMonitorDelayMeasurementBinsforIFDVEntry ::= SEQUENCE {
   sisgm1040284lrtPerformanceMonitorDelayMeasurementBinsforIFDVIndex    Integer32,
   sisgm1040284lrtPerformanceMonitorDelayMeasurementBinsforIFDVOneway   Integer32,
   sisgm1040284lrtPerformanceMonitorDelayMeasurementBinsforIFDVFtoN     Integer32,
   sisgm1040284lrtPerformanceMonitorDelayMeasurementBinsforIFDVNtoF     Integer32,
   sisgm1040284lrtPerformanceMonitorDelayMeasurementBinsforIFDVTwoway   Integer32
   
}

sisgm1040284lrtPerformanceMonitorDelayMeasurementBinsforIFDVIndex OBJECT-TYPE
   SYNTAX      Integer32
   MAX-ACCESS  not-accessible
   STATUS      current
   DESCRIPTION
       "Index"
   ::= { sisgm1040284lrtPerformanceMonitorDelayMeasurementBinsforIFDVEntry 1 }

sisgm1040284lrtPerformanceMonitorDelayMeasurementBinsforIFDVOneway OBJECT-TYPE
   SYNTAX      Integer32
   MAX-ACCESS  read-only
   STATUS      current
   DESCRIPTION
       " "
   ::= { sisgm1040284lrtPerformanceMonitorDelayMeasurementBinsforIFDVEntry 2 }

sisgm1040284lrtPerformanceMonitorDelayMeasurementBinsforIFDVFtoN OBJECT-TYPE
   SYNTAX      Integer32
   MAX-ACCESS  read-only
   STATUS      current
   DESCRIPTION
       " "
   ::= { sisgm1040284lrtPerformanceMonitorDelayMeasurementBinsforIFDVEntry 3 }
   
sisgm1040284lrtPerformanceMonitorDelayMeasurementBinsforIFDVNtoF OBJECT-TYPE
   SYNTAX      Integer32
   MAX-ACCESS  read-only
   STATUS      current
   DESCRIPTION
       " "
   ::= { sisgm1040284lrtPerformanceMonitorDelayMeasurementBinsforIFDVEntry 4 }  
   
sisgm1040284lrtPerformanceMonitorDelayMeasurementBinsforIFDVTwoway OBJECT-TYPE
   SYNTAX      Integer32
   MAX-ACCESS  read-only
   STATUS      current
   DESCRIPTION
       " "
   ::= { sisgm1040284lrtPerformanceMonitorDelayMeasurementBinsforIFDVEntry 5 } 
   
sisgm1040284lrtRRING    OBJECT IDENTIFIER ::= { sisgm1040284lrtConfiguration 27 }   
   
sisgm1040284lrtRRINGTable OBJECT-TYPE
   SYNTAX      SEQUENCE OF SISGM1040284LRTRRINGEntry
   MAX-ACCESS  not-accessible
   STATUS      current
   DESCRIPTION
       " "
   ::= { sisgm1040284lrtRRING 1 }

sisgm1040284lrtRRINGEntry OBJECT-TYPE
   SYNTAX      SISGM1040284LRTRRINGEntry
   MAX-ACCESS  not-accessible
   STATUS      current
   DESCRIPTION
       " "
   INDEX    { sisgm1040284lrtRRINGIndex  }
   ::= { sisgm1040284lrtRRINGTable 1 }

SISGM1040284LRTRRINGEntry ::= SEQUENCE {
   sisgm1040284lrtRRINGIndex     Integer32,
   sisgm1040284lrtRRINGRole      Integer32,
   sisgm1040284lrtRRINGPort1     Integer32,
   sisgm1040284lrtRRINGPort2     Integer32,
   sisgm1040284lrtRRINGStatus1   DisplayString,
   sisgm1040284lrtRRINGStatus2   DisplayString
}

sisgm1040284lrtRRINGIndex OBJECT-TYPE
   SYNTAX      Integer32
   MAX-ACCESS  not-accessible
   STATUS      current
   DESCRIPTION
       "Index"
   ::= { sisgm1040284lrtRRINGEntry 1 }

sisgm1040284lrtRRINGRole OBJECT-TYPE
   SYNTAX      Integer32
   MAX-ACCESS  read-write
   STATUS      current
   DESCRIPTION
       "Set role value.
	   0:Disabled
	   1:Master
	   2:Member
	   3:Rapid-Chain
	   "
   ::= { sisgm1040284lrtRRINGEntry 2 }

sisgm1040284lrtRRINGPort1 OBJECT-TYPE
   SYNTAX      Integer32
   MAX-ACCESS  read-write
   STATUS      current
   DESCRIPTION
       "The switch port number of the port1 .
	   "
   ::= { sisgm1040284lrtRRINGEntry 3 }
   
sisgm1040284lrtRRINGPort2 OBJECT-TYPE
   SYNTAX      Integer32
   MAX-ACCESS  read-write
   STATUS      current
   DESCRIPTION
       "The switch port number of the port2 .
	   "
   ::= { sisgm1040284lrtRRINGEntry 4 }  
   
sisgm1040284lrtRRINGStatus1 OBJECT-TYPE
   SYNTAX      DisplayString
   MAX-ACCESS  read-only
   STATUS      current
   DESCRIPTION
       "The current Rapid Ring status of the port1. "
   ::= { sisgm1040284lrtRRINGEntry 5 } 
   
sisgm1040284lrtRRINGStatus2 OBJECT-TYPE
   SYNTAX      DisplayString
   MAX-ACCESS  read-only
   STATUS      current
   DESCRIPTION
       "The current Rapid Ring status of the port2. "
   ::= { sisgm1040284lrtRRINGEntry 6 }    

sisgm1040284lrtRINGtoRINGRole OBJECT-TYPE
   SYNTAX      Integer32
   MAX-ACCESS  read-write
   STATUS      current
   DESCRIPTION
       "Set ring-to-ring role value.
	   0:Disabled
	   1:Active
	   2:Backup
	   "
   ::= { sisgm1040284lrtRRING 2 }

sisgm1040284lrtRINGtoRINGPort OBJECT-TYPE
   SYNTAX      Integer32
   MAX-ACCESS  read-write
   STATUS      current
   DESCRIPTION
       "The switch port number of the ring-to-ring port.
	   "
   ::= { sisgm1040284lrtRRING 3 }
   

sisgm1040284lrtRINGtoRINGStatus OBJECT-TYPE
   SYNTAX      DisplayString
   MAX-ACCESS  read-only
   STATUS      current
   DESCRIPTION
       "The current ring-to-ring status of the port."
   ::= { sisgm1040284lrtRRING 4 }
   
   
sisgm1040284lrtPTP    OBJECT IDENTIFIER ::= { sisgm1040284lrtConfiguration 28 }   

sisgm1040284lrtPTPOnePPSMode OBJECT-TYPE
   SYNTAX      Integer32
   MAX-ACCESS  read-write
   STATUS      current
   DESCRIPTION
       "This Selection box will allow you to select the One_pps_mode configuration.
		The following values are possible:
		0:Disable
		1. Output
		2. Input
		3. Output Input
		"
   ::= { sisgm1040284lrtPTP 1 }
   
sisgm1040284lrtPTPExternalEnable OBJECT-TYPE
   SYNTAX      Integer32
   MAX-ACCESS  read-write
   STATUS      current
   DESCRIPTION
       "This Selection box will allow you to configure the External Clock output.
		The following values are possible:
		1. True : Enable the external clock output
		0. False : Disable the external clock output
		"
   ::= { sisgm1040284lrtPTP 2 }   
   
sisgm1040284lrtPTPAdjustMethod OBJECT-TYPE
   SYNTAX      Integer32
   MAX-ACCESS  read-write
   STATUS      current
   DESCRIPTION
       "This Selection box will allow you to configure the Frequency adjustment configuration.
		0: LTC frequency : Select Local Time Counter (LTC) frequency control
		1: SyncE-DPLL : Select SyncE DPLL frequency control, if allowed by SyncE
		2: Oscillator : Select an oscillator independent of SyncE for frequency control, if supported by the HW
		3: LTC phase : Select Local Time Counter (LTC) phase control (assumes that the frequency is locked by means of SyncE)
		"
   ::= { sisgm1040284lrtPTP 3 }      
   
sisgm1040284lrtPTPClockFrequency OBJECT-TYPE
   SYNTAX      Integer32
   MAX-ACCESS  read-write
   STATUS      current
   DESCRIPTION
       "This will allow to set the Clock Frequency.
        The possible range of values are 1 - 25000000 (1 - 25MHz)
	   "
   ::= { sisgm1040284lrtPTP 4 }   
   


sisgm1040284lrtPTPClockConfTable  OBJECT-TYPE
   SYNTAX      SEQUENCE OF SISGM1040284LRTPTPClockConfEntry
   MAX-ACCESS  not-accessible
   STATUS      current
   DESCRIPTION
       "A table of PTP Clock Conf."
 ::= { sisgm1040284lrtPTP 5 }

sisgm1040284lrtPTPClockConfEntry OBJECT-TYPE
    SYNTAX        SISGM1040284LRTPTPClockConfEntry
    MAX-ACCESS    not-accessible
    STATUS        current
    DESCRIPTION
        "An entry in the PTP Clock Conf table."
    INDEX        { sisgm1040284lrtPTPClockConfIndex }
    ::= { sisgm1040284lrtPTPClockConfTable 1 }

SISGM1040284LRTPTPClockConfEntry ::=
    SEQUENCE {
        sisgm1040284lrtPTPClockConfIndex                    Integer32,
        sisgm1040284lrtPTPClockConfClockInstance            Integer32,
        sisgm1040284lrtPTPClockConfDeviceType               Integer32,
		sisgm1040284lrtPTPClockConfProfile                  Integer32,
        sisgm1040284lrtPTPClockConfRowStatus                RowStatus
    }

sisgm1040284lrtPTPClockConfIndex OBJECT-TYPE
   SYNTAX      Integer32
   MAX-ACCESS  not-accessible
   STATUS      current
   DESCRIPTION
       "PTP Clock Conf index."
   ::= {sisgm1040284lrtPTPClockConfEntry 1 }

sisgm1040284lrtPTPClockConfClockInstance OBJECT-TYPE
   SYNTAX      Integer32
   MAX-ACCESS  read-create
   STATUS      current
   DESCRIPTION
       "Indicates the Instance of a particular Clock Instance [0..3]."
   ::= {sisgm1040284lrtPTPClockConfEntry 2 }

sisgm1040284lrtPTPClockConfDeviceType OBJECT-TYPE
   SYNTAX      Integer32
   MAX-ACCESS  read-create
   STATUS      current
   DESCRIPTION
       "Indicates the Type of the Clock Instance. There are five Device Types.
	    0: Inactive - passive clock instance
		1: Ord-Bound - clock's Device Type is Ordinary-Boundary Clock.
		2: P2p Transp - clock's Device Type is Peer to Peer Transparent Clock.
		3: E2e Transp - clock's Device Type is End to End Transparent Clock.
		4: Master Only - clock's Device Type is Master Only.
		5: Slave Only - clock's Device Type is Slave Only.
		6: Boundary Clock frontend clock instance, only 1-step, 1-way is supported."
   ::= {sisgm1040284lrtPTPClockConfEntry 3 }
   
sisgm1040284lrtPTPClockConfProfile OBJECT-TYPE
   SYNTAX      Integer32
   MAX-ACCESS  read-create
   STATUS      current
   DESCRIPTION
       "0:No profile
	   1:1588
	   2:G8265.1
	   3:G8275.1
	   "
   ::= {sisgm1040284lrtPTPClockConfEntry 4 }   
   
sisgm1040284lrtPTPClockConfRowStatus OBJECT-TYPE
   SYNTAX      RowStatus
   MAX-ACCESS  read-create
   STATUS      current
   DESCRIPTION
       "PTP Clock Conf Row Status."
   ::= {sisgm1040284lrtPTPClockConfEntry 5 }
   
sisgm1040284lrtPTPClockInstance OBJECT-TYPE
   SYNTAX      Integer32
   MAX-ACCESS  read-write
   STATUS      current
   DESCRIPTION
       "Specify the PTP clock instance for the following item used [0..3]."
   ::= {sisgm1040284lrtPTP 6 }
   
   
sisgm1040284lrtPTPClockConfAndStatus    OBJECT IDENTIFIER ::= { sisgm1040284lrtPTP 7 }

sisgm1040284lrtPTPClockConfEntryClockInstance OBJECT-TYPE
   SYNTAX      Integer32
   MAX-ACCESS  read-only
   STATUS      current
   DESCRIPTION
       ""
   ::= {sisgm1040284lrtPTPClockConfAndStatus 2 }

sisgm1040284lrtPTPClockConfEntryDeviceType OBJECT-TYPE
   SYNTAX      DisplayString
   MAX-ACCESS  read-only
   STATUS      current
   DESCRIPTION
       ""
   ::= {sisgm1040284lrtPTPClockConfAndStatus 3 }   
   
sisgm1040284lrtPTPClockConfEntryProfile OBJECT-TYPE
   SYNTAX      DisplayString
   MAX-ACCESS  read-only
   STATUS      current
   DESCRIPTION
       ""
   ::= {sisgm1040284lrtPTPClockConfAndStatus 4 }    

sisgm1040284lrtPTPClockConfEntryApplyProfileDefaults OBJECT-TYPE
   SYNTAX      Integer32
   MAX-ACCESS  read-write
   STATUS      current
   DESCRIPTION
       "-1:n/a
	   0:normal state
	   1:apply profile default"
   ::= {sisgm1040284lrtPTPClockConfAndStatus 5 }   
   
sisgm1040284lrtPTPClockConfEntryPTPTime OBJECT-TYPE
   SYNTAX      DisplayString
   MAX-ACCESS  read-only
   STATUS      current
   DESCRIPTION
       "Shows the actual PTP time with nanosecond resolution."
   ::= {sisgm1040284lrtPTPClockConfAndStatus 6 }    
   
sisgm1040284lrtPTPClockConfEntryClockAdjustmentMethod OBJECT-TYPE
   SYNTAX      DisplayString
   MAX-ACCESS  read-only
   STATUS      current
   DESCRIPTION
       "Shows the actual clock adjustment method. The method depends on the available hardware."
   ::= {sisgm1040284lrtPTPClockConfAndStatus 7 }     
   
sisgm1040284lrtPTPClockConfEntrySynchronizeToSystemClock OBJECT-TYPE
   SYNTAX      Integer32
   MAX-ACCESS  read-write
   STATUS      current
   DESCRIPTION
       "Activate this button to synchronize the System Clock to PTP Time.
	   1:Synchronize to system clock."
   ::= {sisgm1040284lrtPTPClockConfAndStatus 8 }    

sisgm1040284lrtPTPClockConfEntryClockCurrentDataSetstpRm OBJECT-TYPE
   SYNTAX      Integer32
   MAX-ACCESS  read-only
   STATUS      current
   DESCRIPTION
       "Steps Removed : It is the number of PTP clocks traversed from the grandmaster to the local slave clock."
   ::= {sisgm1040284lrtPTPClockConfAndStatus 9 }   
   
sisgm1040284lrtPTPClockConfEntryClockCurrentDataSetOffsetFromMaster OBJECT-TYPE
   SYNTAX      DisplayString
   MAX-ACCESS  read-only
   STATUS      current
   DESCRIPTION
       "Time difference between the master clock and the local slave clock, measured in ns."
   ::= {sisgm1040284lrtPTPClockConfAndStatus 10 }      
  
sisgm1040284lrtPTPClockConfEntryClockCurrentDataSetMeanPathDelay OBJECT-TYPE
   SYNTAX      DisplayString
   MAX-ACCESS  read-only
   STATUS      current
   DESCRIPTION
       "The mean propagation time for the link between the master and the local slave."
   ::= {sisgm1040284lrtPTPClockConfAndStatus 11 }   
   
sisgm1040284lrtPTPClockConfEntryClockCurrentDataSetSlavePort OBJECT-TYPE
   SYNTAX      Integer32
   MAX-ACCESS  read-only
   STATUS      current
   DESCRIPTION
       "Shows which port is in slave mode. The value is 0 if no ports are in slave mode."
   ::= {sisgm1040284lrtPTPClockConfAndStatus 12 }  
   
sisgm1040284lrtPTPClockConfEntryClockCurrentDataSetSlaveState OBJECT-TYPE
   SYNTAX      DisplayString
   MAX-ACCESS  read-only
   STATUS      current
   DESCRIPTION
       "Shows synchronization state of the slave."
   ::= {sisgm1040284lrtPTPClockConfAndStatus 13 }  
   
sisgm1040284lrtPTPClockConfEntryClockCurrentDataSetHoldover OBJECT-TYPE
   SYNTAX      DisplayString
   MAX-ACCESS  read-only
   STATUS      current
   DESCRIPTION
       "After the slave has been in Locked mode during the stabilization period, 
	   this value shows the actual clock offset between the freerun and the actual holdover frequency, 
	   the value is shown in parts pr billion (ppb). 
	   During the stabilization period, the value is shown as N.A. 
	   The stabilization period is 60 sec as default, it can be changed from the CLI interface."
   ::= {sisgm1040284lrtPTPClockConfAndStatus 14 } 

sisgm1040284lrtPTPClockConfEntryClockParentDataSetParentPortID OBJECT-TYPE
   SYNTAX      DisplayString
   MAX-ACCESS  read-only
   STATUS      current
   DESCRIPTION
       "Clock identity for the parent clock, if the local clock is not a slave, the value is the clocks own id."
   ::= {sisgm1040284lrtPTPClockConfAndStatus 15 }     
  
sisgm1040284lrtPTPClockConfEntryClockParentDataSetPort OBJECT-TYPE
   SYNTAX      Integer32
   MAX-ACCESS  read-only
   STATUS      current
   DESCRIPTION
       "Port Id for the parent master port"
   ::= {sisgm1040284lrtPTPClockConfAndStatus 16 }

sisgm1040284lrtPTPClockConfEntryClockParentDataSetPStat OBJECT-TYPE
   SYNTAX      DisplayString
   MAX-ACCESS  read-only
   STATUS      current
   DESCRIPTION
       "Parents Stats (always false)."
   ::= {sisgm1040284lrtPTPClockConfAndStatus 17 }     
   
sisgm1040284lrtPTPClockConfEntryClockParentDataSetVar OBJECT-TYPE
   SYNTAX      Integer32
   MAX-ACCESS  read-only
   STATUS      current
   DESCRIPTION
       "It is observed parent offset scaled log variance"
   ::= {sisgm1040284lrtPTPClockConfAndStatus 18 }    
   
sisgm1040284lrtPTPClockConfEntryClockParentDataSetRate OBJECT-TYPE
   SYNTAX      Integer32
   MAX-ACCESS  read-only
   STATUS      current
   DESCRIPTION
       "Observed Parent Clock Phase Change Rate. i.e. the slave clocks rate offset compared to the master. 
	   (unit = ns per s)."
   ::= {sisgm1040284lrtPTPClockConfAndStatus 19 }  

sisgm1040284lrtPTPClockConfEntryClockParentDataSetGrandMasterID OBJECT-TYPE
   SYNTAX      DisplayString
   MAX-ACCESS  read-only
   STATUS      current
   DESCRIPTION
       "Clock identity for the grand master clock, if the local clock is not a slave, the value is the clocks own id."
   ::= {sisgm1040284lrtPTPClockConfAndStatus 20 }   

sisgm1040284lrtPTPClockConfEntryClockParentDataSetGrandMasterClockQuality OBJECT-TYPE
   SYNTAX      DisplayString
   MAX-ACCESS  read-only
   STATUS      current
   DESCRIPTION
       "The clock quality announced by the grand master (See description of Clock Default DataSet:Clock Quality)"
   ::= {sisgm1040284lrtPTPClockConfAndStatus 21 }     
   
sisgm1040284lrtPTPClockConfEntryClockParentDataSetPri1 OBJECT-TYPE
   SYNTAX      Integer32
   MAX-ACCESS  read-only
   STATUS      current
   DESCRIPTION
       "Clock priority 1 announced by the grand master"
   ::= {sisgm1040284lrtPTPClockConfAndStatus 22 }   

sisgm1040284lrtPTPClockConfEntryClockParentDataSetPri2 OBJECT-TYPE
   SYNTAX      Integer32
   MAX-ACCESS  read-only
   STATUS      current
   DESCRIPTION
       "Clock priority 2 announced by the grand master."
   ::= {sisgm1040284lrtPTPClockConfAndStatus 23 }      
   
sisgm1040284lrtPTPClockConfEntryClockDefaultDataSetClockID OBJECT-TYPE
   SYNTAX      Integer32
   MAX-ACCESS  read-only
   STATUS      current
   DESCRIPTION
       "An internal instance id (0..3)"
   ::= {sisgm1040284lrtPTPClockConfAndStatus 24 }     
   
sisgm1040284lrtPTPClockConfEntryClockDefaultDataSetDeviceType OBJECT-TYPE
   SYNTAX      DisplayString
   MAX-ACCESS  read-only
   STATUS      current
   DESCRIPTION
       "Indicates the Type of the Clock Instance. There are five Device Types.
		1. Ord-Bound - Clock's Device Type is Ordinary-Boundary Clock.
		2. P2p Transp - Clock's Device Type is Peer to Peer Transparent Clock.
		3. E2e Transp - Clock's Device Type is End to End Transparent Clock.
		4. Master Only - Clock's Device Type is Master Only.
		5. Slave Only - Clock's Device Type is Slave Only."
   ::= {sisgm1040284lrtPTPClockConfAndStatus 25 }    

sisgm1040284lrtPTPClockConfEntryClockDefaultDataSet2StepFlag OBJECT-TYPE
   SYNTAX      Integer32
   MAX-ACCESS  read-write
   STATUS      current
   DESCRIPTION
       "True if two-step Sync events and Pdelay_Resp events are used
	   0:false
	   1:true"
   ::= {sisgm1040284lrtPTPClockConfAndStatus 26 }   
   
sisgm1040284lrtPTPClockConfEntryClockDefaultDataSetPorts OBJECT-TYPE
   SYNTAX      Integer32
   MAX-ACCESS  read-only
   STATUS      current
   DESCRIPTION
       "The total number of physical ports in the node"
   ::= {sisgm1040284lrtPTPClockConfAndStatus 27 }     
   
sisgm1040284lrtPTPClockConfEntryClockDefaultDataSetClockIdentity OBJECT-TYPE
   SYNTAX      DisplayString
   MAX-ACCESS  read-only
   STATUS      current
   DESCRIPTION
       "It shows unique clock identifier"
   ::= {sisgm1040284lrtPTPClockConfAndStatus 28 }    

sisgm1040284lrtPTPClockConfEntryClockDefaultDataSetDom OBJECT-TYPE
   SYNTAX      Integer32
   MAX-ACCESS  read-write
   STATUS      current
   DESCRIPTION
       "Clock domain [0..127]."
   ::= {sisgm1040284lrtPTPClockConfAndStatus 29 }     
   
sisgm1040284lrtPTPClockConfEntryClockDefaultDataSetClockQuality OBJECT-TYPE
   SYNTAX      DisplayString
   MAX-ACCESS  read-only
   STATUS      current
   DESCRIPTION
       "The clock quality is determined by the system, and holds 3 parts: Clock Class, Clock Accuracy and OffsetScaledLog Variance as defined in IEEE1588.
The Clock Accuracy values are defined in IEEE1588 table 6 (Currently the clock Accuracy is set to 'Unknown' as default)."
   ::= {sisgm1040284lrtPTPClockConfAndStatus 30 }  
   
sisgm1040284lrtPTPClockConfEntryClockDefaultDataSetPri1 OBJECT-TYPE
   SYNTAX      Integer32
   MAX-ACCESS  read-write
   STATUS      current
   DESCRIPTION
       "Clock priority 1 [0..255] used by the BMC master select algorithm."
   ::= {sisgm1040284lrtPTPClockConfAndStatus 31 }
   
sisgm1040284lrtPTPClockConfEntryClockDefaultDataSetPri2 OBJECT-TYPE
   SYNTAX      Integer32
   MAX-ACCESS  read-write
   STATUS      current
   DESCRIPTION
       "Clock priority 2 [0..255] used by the BMC master select algorithm."
   ::= {sisgm1040284lrtPTPClockConfAndStatus 32 }   
   
sisgm1040284lrtPTPClockConfEntryClockDefaultDataSetProtocol OBJECT-TYPE
   SYNTAX      Integer32
   MAX-ACCESS  read-write
   STATUS      current
   DESCRIPTION
       "0:Ethernet
	   1:Ethernet Mixed
	   2:IP4Multi
	   3:IP4Mixed
	   4:IP4Uni
	   5:OAM
	   6:OnePPS"
   ::= {sisgm1040284lrtPTPClockConfAndStatus 33 }     
   
sisgm1040284lrtPTPClockConfEntryClockDefaultDataSetOneWay OBJECT-TYPE
   SYNTAX      Integer32
   MAX-ACCESS  read-write
   STATUS      current
   DESCRIPTION
       "If true, one way measurements are used. 
	   This parameter applies only to a slave. 
	   In one-way mode no delay measurements are performed, i.e. this is applicable only if frequency synchronization is needed. 
	   The master always responds to delay requests.
	   0:false
	   1:true"
   ::= {sisgm1040284lrtPTPClockConfAndStatus 34 }     
   
sisgm1040284lrtPTPClockConfEntryClockDefaultDataSetVLANTagEnable OBJECT-TYPE
   SYNTAX      Integer32
   MAX-ACCESS  read-write
   STATUS      current
   DESCRIPTION
       "The VLAN Tag Enable parameter is ignored, because the tagging is controlled by the VLAN configuration.
	   0:false
	   1:true"
   ::= {sisgm1040284lrtPTPClockConfAndStatus 35 }   

sisgm1040284lrtPTPClockConfEntryClockDefaultDataSetVID OBJECT-TYPE
   SYNTAX      Integer32
   MAX-ACCESS  read-write
   STATUS      current
   DESCRIPTION
       "TVLAN Identifier used for tagging the VLAN packets.
	   range:1-4095"
   ::= {sisgm1040284lrtPTPClockConfAndStatus 36 }    

sisgm1040284lrtPTPClockConfEntryClockDefaultDataSetPCP OBJECT-TYPE
   SYNTAX      Integer32
   MAX-ACCESS  read-write
   STATUS      current
   DESCRIPTION
       "Priority Code Point value used for PTP frames. range:0-7"
   ::= {sisgm1040284lrtPTPClockConfAndStatus 37 }     
   
sisgm1040284lrtPTPClockConfEntryClockDefaultDataSetDSCP OBJECT-TYPE
   SYNTAX      Integer32
   MAX-ACCESS  read-write
   STATUS      current
   DESCRIPTION
       ""
   ::= {sisgm1040284lrtPTPClockConfAndStatus 38 }  
   
sisgm1040284lrtPTPClockConfEntryClockTimePropertiesDataSetUtcOffset OBJECT-TYPE
   SYNTAX      Integer32
   MAX-ACCESS  read-write
   STATUS      current
   DESCRIPTION
       "range: 0-10000"
   ::= {sisgm1040284lrtPTPClockConfAndStatus 39 }     
 
sisgm1040284lrtPTPClockConfEntryClockTimePropertiesDataSetValid OBJECT-TYPE
   SYNTAX      Integer32
   MAX-ACCESS  read-write
   STATUS      current
   DESCRIPTION
       "0:false
	   1:true"
   ::= {sisgm1040284lrtPTPClockConfAndStatus 40 }     
   
sisgm1040284lrtPTPClockConfEntryClockTimePropertiesDataSetLeap59 OBJECT-TYPE
   SYNTAX      Integer32
   MAX-ACCESS  read-write
   STATUS      current
   DESCRIPTION
       "0:false
	   1:true"
   ::= {sisgm1040284lrtPTPClockConfAndStatus 41 }   
   
sisgm1040284lrtPTPClockConfEntryClockTimePropertiesDataSetLeap61 OBJECT-TYPE
   SYNTAX      Integer32
   MAX-ACCESS  read-write
   STATUS      current
   DESCRIPTION
       "0:false
	   1:true"
   ::= {sisgm1040284lrtPTPClockConfAndStatus 42 }    
   
sisgm1040284lrtPTPClockConfEntryClockTimePropertiesDataSetTimeTrac OBJECT-TYPE
   SYNTAX      Integer32
   MAX-ACCESS  read-write
   STATUS      current
   DESCRIPTION
       "0:false
	   1:true"
   ::= {sisgm1040284lrtPTPClockConfAndStatus 43 }           
   
sisgm1040284lrtPTPClockConfEntryClockTimePropertiesDataSetFreqTrac OBJECT-TYPE
   SYNTAX      Integer32
   MAX-ACCESS  read-write
   STATUS      current
   DESCRIPTION
       "0:false
	   1:true"
   ::= {sisgm1040284lrtPTPClockConfAndStatus 44 }    
   
sisgm1040284lrtPTPClockConfEntryClockTimePropertiesDataSetPTPTimeScale OBJECT-TYPE
   SYNTAX      Integer32
   MAX-ACCESS  read-write
   STATUS      current
   DESCRIPTION
       "0:false
	   1:true"
   ::= {sisgm1040284lrtPTPClockConfAndStatus 45 }    
   
sisgm1040284lrtPTPClockConfEntryClockTimePropertiesDataSetTimeSource OBJECT-TYPE
   SYNTAX      Integer32
   MAX-ACCESS  read-write
   STATUS      current
   DESCRIPTION
       "range: 0-255"
   ::= {sisgm1040284lrtPTPClockConfAndStatus 46 }      
   
sisgm1040284lrtPTPClockConfEntryFilterParametersFilterType OBJECT-TYPE
   SYNTAX      Integer32
   MAX-ACCESS  read-write
   STATUS      current
   DESCRIPTION
       "Shows the filter type used which can be either the basic filter or an advanced filter that can be configured to use only a fraction of the packets received 
	   (i.e. the packets that have experienced the least latency).
	   0:BASIC"
   ::= {sisgm1040284lrtPTPClockConfAndStatus 47 }  
   
sisgm1040284lrtPTPClockConfEntryFilterParametersDelayFilter OBJECT-TYPE
   SYNTAX      Integer32
   MAX-ACCESS  read-write
   STATUS      current
   DESCRIPTION
       "range:0-6"
   ::= {sisgm1040284lrtPTPClockConfAndStatus 48 }   
   
sisgm1040284lrtPTPClockConfEntryFilterParametersPeriod OBJECT-TYPE
   SYNTAX      Integer32
   MAX-ACCESS  read-write
   STATUS      current
   DESCRIPTION
       "range:1-10000"
   ::= {sisgm1040284lrtPTPClockConfAndStatus 49 }    

sisgm1040284lrtPTPClockConfEntryFilterParametersDist OBJECT-TYPE
   SYNTAX      Integer32
   MAX-ACCESS  read-write
   STATUS      current
   DESCRIPTION
       "range:1-10"
   ::= {sisgm1040284lrtPTPClockConfAndStatus 50 }     

sisgm1040284lrtPTPClockConfEntryServoParametersDisplay OBJECT-TYPE
   SYNTAX      Integer32
   MAX-ACCESS  read-write
   STATUS      current
   DESCRIPTION
       "If true then Offset From Master, MeanPathDelay and clockAdjustment are logged on the debug terminal
	   0:false
	   1:true"
   ::= {sisgm1040284lrtPTPClockConfAndStatus 51 }    

sisgm1040284lrtPTPClockConfEntryServoParametersPEnable OBJECT-TYPE
   SYNTAX      Integer32
   MAX-ACCESS  read-write
   STATUS      current
   DESCRIPTION
       "If true the P part of the algorithm is included
	   0:false
	   1:true"
   ::= {sisgm1040284lrtPTPClockConfAndStatus 52 }    
   
sisgm1040284lrtPTPClockConfEntryServoParametersIEnable OBJECT-TYPE
   SYNTAX      Integer32
   MAX-ACCESS  read-write
   STATUS      current
   DESCRIPTION
       "If true the I part of the algorithm is included
	   0:false
	   1:true"
   ::= {sisgm1040284lrtPTPClockConfAndStatus 53 }       
   
sisgm1040284lrtPTPClockConfEntryServoParametersDEnable OBJECT-TYPE
   SYNTAX      Integer32
   MAX-ACCESS  read-write
   STATUS      current
   DESCRIPTION
       "If true the D part of the algorithm is included
	   0:false
	   1:true"
   ::= {sisgm1040284lrtPTPClockConfAndStatus 54 }          
   
sisgm1040284lrtPTPClockConfEntryServoParametersPConstant OBJECT-TYPE
   SYNTAX      Integer32
   MAX-ACCESS  read-write
   STATUS      current
   DESCRIPTION
       "range:0-1000"
   ::= {sisgm1040284lrtPTPClockConfAndStatus 55 }      
   
sisgm1040284lrtPTPClockConfEntryServoParametersIConstant OBJECT-TYPE
   SYNTAX      Integer32
   MAX-ACCESS  read-write
   STATUS      current
   DESCRIPTION
       "range:0-10000"
   ::= {sisgm1040284lrtPTPClockConfAndStatus 56 }     

sisgm1040284lrtPTPClockConfEntryServoParametersDConstant OBJECT-TYPE
   SYNTAX      Integer32
   MAX-ACCESS  read-write
   STATUS      current
   DESCRIPTION
       "range:0-1000"
   ::= {sisgm1040284lrtPTPClockConfAndStatus 57 }     

   
sisgm1040284lrtPTPClockPortDataSetConfTable OBJECT-TYPE
   SYNTAX      SEQUENCE OF SISGM1040284LRTPTPClockPortDataSetConfEntry
   MAX-ACCESS  not-accessible
   STATUS      current
   DESCRIPTION
       " "
   ::= { sisgm1040284lrtPTP 8 }

sisgm1040284lrtPTPClockPortDataSetConfEntry OBJECT-TYPE
   SYNTAX      SISGM1040284LRTPTPClockPortDataSetConfEntry
   MAX-ACCESS  not-accessible
   STATUS      current
   DESCRIPTION
       " "
   INDEX    { sisgm1040284lrtPTPClockPortDataSetConfPort  }
   ::= { sisgm1040284lrtPTPClockPortDataSetConfTable 1 }

SISGM1040284LRTPTPClockPortDataSetConfEntry ::= SEQUENCE {
   sisgm1040284lrtPTPClockPortDataSetConfPort               Integer32,
   sisgm1040284lrtPTPClockConfEntryPortConfEnable           Integer32,
   sisgm1040284lrtPTPClockConfEntryPortConfStat             DisplayString,
   sisgm1040284lrtPTPClockConfEntryPortConfMDR              Integer32,
   sisgm1040284lrtPTPClockConfEntryPortConfPeerMeanPathDel  DisplayString,
   sisgm1040284lrtPTPClockConfEntryPortConfAnv              Integer32,
   sisgm1040284lrtPTPClockConfEntryPortConfATo              Integer32,
   sisgm1040284lrtPTPClockConfEntryPortConfSyv              Integer32,
   sisgm1040284lrtPTPClockConfEntryPortConfDlm              Integer32,
   sisgm1040284lrtPTPClockConfEntryPortConfMPR              Integer32,
   sisgm1040284lrtPTPClockConfEntryPortConfDelayAsymmetry   Integer32,
   sisgm1040284lrtPTPClockConfEntryPortConfIngressLatency   Integer32,
   sisgm1040284lrtPTPClockConfEntryPortConfEgressLatency    Integer32,
   sisgm1040284lrtPTPClockConfEntryPortConfVersion          Integer32
}

sisgm1040284lrtPTPClockPortDataSetConfPort OBJECT-TYPE
   SYNTAX      Integer32
   MAX-ACCESS  not-accessible
   STATUS      current
   DESCRIPTION
       "Index"
   ::= { sisgm1040284lrtPTPClockPortDataSetConfEntry 1 }

sisgm1040284lrtPTPClockConfEntryPortConfEnable OBJECT-TYPE
   SYNTAX      Integer32
   MAX-ACCESS  read-write
   STATUS      current
   DESCRIPTION
       "0:false
	   1:true"
   ::= { sisgm1040284lrtPTPClockPortDataSetConfEntry 2 }
   
sisgm1040284lrtPTPClockConfEntryPortConfStat OBJECT-TYPE
   SYNTAX      DisplayString
   MAX-ACCESS  read-only
   STATUS      current
   DESCRIPTION
       "Dynamic member portState: Current state of the port."
   ::= { sisgm1040284lrtPTPClockPortDataSetConfEntry 3 }   
   
sisgm1040284lrtPTPClockConfEntryPortConfMDR OBJECT-TYPE
   SYNTAX      Integer32
   MAX-ACCESS  read-only
   STATUS      current
   DESCRIPTION
       "Dynamic member log Min Delay Req Interval: The delay request interval announced by the master."
   ::= { sisgm1040284lrtPTPClockPortDataSetConfEntry 4 }      

sisgm1040284lrtPTPClockConfEntryPortConfPeerMeanPathDel OBJECT-TYPE
   SYNTAX      DisplayString
   MAX-ACCESS  read-only
   STATUS      current
   DESCRIPTION
       "The path delay measured by the port in P2P mode. In E2E mode this value is 0"
   ::= { sisgm1040284lrtPTPClockPortDataSetConfEntry 5 }  
   

   
sisgm1040284lrtPTPClockConfEntryPortConfAnv OBJECT-TYPE
   SYNTAX      Integer32
   MAX-ACCESS  read-write
   STATUS      current
   DESCRIPTION
       "The interval for issuing announce messages in master state. Range is -3 to 4."
   ::= { sisgm1040284lrtPTPClockPortDataSetConfEntry 6 }     
   
sisgm1040284lrtPTPClockConfEntryPortConfATo OBJECT-TYPE
   SYNTAX      Integer32
   MAX-ACCESS  read-write
   STATUS      current
   DESCRIPTION
       "The timeout for receiving announce messages on the port. Range is 1 to 10."
   ::= { sisgm1040284lrtPTPClockPortDataSetConfEntry 7 }    
   
sisgm1040284lrtPTPClockConfEntryPortConfSyv OBJECT-TYPE
   SYNTAX      Integer32
   MAX-ACCESS  read-write
   STATUS      current
   DESCRIPTION
       "The interval for issuing sync messages in master. Range is -7 to 4."
   ::= { sisgm1040284lrtPTPClockPortDataSetConfEntry 8 }     

sisgm1040284lrtPTPClockConfEntryPortConfDlm OBJECT-TYPE
   SYNTAX      Integer32
   MAX-ACCESS  read-write
   STATUS      current
   DESCRIPTION
       "Configurable member delayMechanism: The delay mechanism used for the port:
		e2e	End to end delay measurement
		p2p	Peer to peer delay measurement.
		Can be defined per port in an Ordinary/Boundary clock.
		In a transparent clock all ports use the same delay mechanism, determined by the clock type.
		1:e2e
		2:p2p"
   ::= { sisgm1040284lrtPTPClockPortDataSetConfEntry 9 }    

sisgm1040284lrtPTPClockConfEntryPortConfMPR OBJECT-TYPE
   SYNTAX      Integer32
   MAX-ACCESS  read-write
   STATUS      current
   DESCRIPTION
       "The interval for issuing Delay_Req messages for the port in E2e mode. This value is announced from the master to the slave in an announce message. The value is reflected in the MDR field in the Slave
The interval for issuing Pdelay_Req messages for the port in P2P mode
Note: The interpretation of this parameter has changed from release 2.40. In earlier versions the value was interpreted relative to the Sync interval, this was a violation of the standard, so now the value is interpreted as an interval. I.e. MPR = 0 => 1 Delay_Req pr sec, independent of the Sync rate.
Range is -7 to 5."
   ::= { sisgm1040284lrtPTPClockPortDataSetConfEntry 10 }    

sisgm1040284lrtPTPClockConfEntryPortConfDelayAsymmetry OBJECT-TYPE
   SYNTAX      Integer32
   MAX-ACCESS  read-write
   STATUS      current
   DESCRIPTION
       "If the transmission delay for a link in not symmetric, the asymmetry can be configured here, see IEEE 1588 Section 7.4.2 Communication path asymmetry
Range is -100000 to 100000."
   ::= { sisgm1040284lrtPTPClockPortDataSetConfEntry 11 }    
   
sisgm1040284lrtPTPClockConfEntryPortConfIngressLatency OBJECT-TYPE
   SYNTAX      Integer32
   MAX-ACCESS  read-write
   STATUS      current
   DESCRIPTION
       "Ingress latency measured in ns, as defined in IEEE 1588 Section 7.3.4.2.
Range is -100000 to 100000."
   ::= { sisgm1040284lrtPTPClockPortDataSetConfEntry 12 }     
   
sisgm1040284lrtPTPClockConfEntryPortConfEgressLatency OBJECT-TYPE
   SYNTAX      Integer32
   MAX-ACCESS  read-write
   STATUS      current
   DESCRIPTION
       "Egress latency measured in ns, as defined in IEEE 1588 Section 7.3.4.2.
Range is -100000 to 100000."
   ::= { sisgm1040284lrtPTPClockPortDataSetConfEntry 13 }     
   
sisgm1040284lrtPTPClockConfEntryPortConfVersion OBJECT-TYPE
   SYNTAX      Integer32
   MAX-ACCESS  read-only
   STATUS      current
   DESCRIPTION
       "The current implementation only supports PTP version 2"
   ::= { sisgm1040284lrtPTPClockPortDataSetConfEntry 14 }    
   
  
sisgm1040284lrtPTPClockUnicastSlaveConfTable OBJECT-TYPE
   SYNTAX      SEQUENCE OF SISGM1040284LRTPTPClockUnicastSlaveConfEntry
   MAX-ACCESS  not-accessible
   STATUS      current
   DESCRIPTION
       " "
   ::= { sisgm1040284lrtPTP 9 }

sisgm1040284lrtPTPClockUnicastSlaveConfEntry OBJECT-TYPE
   SYNTAX      SISGM1040284LRTPTPClockUnicastSlaveConfEntry
   MAX-ACCESS  not-accessible
   STATUS      current
   DESCRIPTION
       " "
   INDEX    { sisgm1040284lrtPTPClockConfEntryUnicastSlaveConfIndex  }
   ::= { sisgm1040284lrtPTPClockUnicastSlaveConfTable 1 }

SISGM1040284LRTPTPClockUnicastSlaveConfEntry ::= SEQUENCE {
   sisgm1040284lrtPTPClockConfEntryUnicastSlaveConfIndex              Integer32,
   sisgm1040284lrtPTPClockConfEntryUnicastSlaveConfDuration           Integer32,
   sisgm1040284lrtPTPClockConfEntryUnicastSlaveConfIPAddress          IpAddress,
   sisgm1040284lrtPTPClockConfEntryUnicastSlaveConfGrant              Integer32,
   sisgm1040284lrtPTPClockConfEntryUnicastSlaveConfCommState          DisplayString
}

sisgm1040284lrtPTPClockConfEntryUnicastSlaveConfIndex OBJECT-TYPE
   SYNTAX      Integer32
   MAX-ACCESS  not-accessible
   STATUS      current
   DESCRIPTION
       "Index"
   ::= { sisgm1040284lrtPTPClockUnicastSlaveConfEntry 1 }

sisgm1040284lrtPTPClockConfEntryUnicastSlaveConfDuration OBJECT-TYPE
   SYNTAX      Integer32
   MAX-ACCESS  read-write
   STATUS      current
   DESCRIPTION
       "The number of seconds a master is requested to send Announce/Sync messages. 
	   The request is repeated from the slave each Duration/4 seconds.
	   range:10-1000"
   ::= { sisgm1040284lrtPTPClockUnicastSlaveConfEntry 2 }
      
sisgm1040284lrtPTPClockConfEntryUnicastSlaveConfIPAddress OBJECT-TYPE
   SYNTAX      IpAddress
   MAX-ACCESS  read-write
   STATUS      current
   DESCRIPTION
       "IPv4 Address of the Master clock"
   ::= { sisgm1040284lrtPTPClockUnicastSlaveConfEntry 3 }
   
sisgm1040284lrtPTPClockConfEntryUnicastSlaveConfGrant OBJECT-TYPE
   SYNTAX      Integer32
   MAX-ACCESS  read-only
   STATUS      current
   DESCRIPTION
       "The granted repetition period for the sync message"
   ::= { sisgm1040284lrtPTPClockUnicastSlaveConfEntry 4 }   
   
sisgm1040284lrtPTPClockConfEntryUnicastSlaveConfCommState OBJECT-TYPE
   SYNTAX      DisplayString
   MAX-ACCESS  read-only
   STATUS      current
   DESCRIPTION
       "The state of the communication with the master, possible values are:
		IDLE : The entry is not in use.
		INIT : Announce is sent to the master (Waiting for a response).
		CONN : The master has responded.
		SELL : The assigned master is selected as current master.
		SYNC : The master is sending Sync messages."
   ::= { sisgm1040284lrtPTPClockUnicastSlaveConfEntry 5 }   

sisgm1040284lrtETHLINKOAM    OBJECT IDENTIFIER ::= { sisgm1040284lrtConfiguration 29 } 

sisgm1040284lrtEthLinkOAMPortConfTable OBJECT-TYPE
   SYNTAX      SEQUENCE OF SISGM1040284LRTEthLinkOAMPortConfEntry
   MAX-ACCESS  not-accessible
   STATUS      current
   DESCRIPTION
       " "
   ::= { sisgm1040284lrtETHLINKOAM 1 }

sisgm1040284lrtEthLinkOAMPortConfEntry OBJECT-TYPE
   SYNTAX      SISGM1040284LRTEthLinkOAMPortConfEntry
   MAX-ACCESS  not-accessible
   STATUS      current
   DESCRIPTION
       " "
   INDEX    { sisgm1040284lrtEthLinkOAMPortConfIndex  }
   ::= { sisgm1040284lrtEthLinkOAMPortConfTable 1 }

SISGM1040284LRTEthLinkOAMPortConfEntry ::= SEQUENCE {
   sisgm1040284lrtEthLinkOAMPortConfIndex               Integer32,
   sisgm1040284lrtEthLinkOAMPortConfOAMEnable           Integer32,
   sisgm1040284lrtEthLinkOAMPortConfOAMMode             Integer32,
   sisgm1040284lrtEthLinkOAMPortConfLoopbackSupport     Integer32,
   sisgm1040284lrtEthLinkOAMPortConfLinkMonitorSupport  Integer32,
   sisgm1040284lrtEthLinkOAMPortConfMIBRetrievalSupport Integer32,
   sisgm1040284lrtEthLinkOAMPortConfLoopbackOperation   Integer32
}

sisgm1040284lrtEthLinkOAMPortConfIndex OBJECT-TYPE
   SYNTAX      Integer32
   MAX-ACCESS  not-accessible
   STATUS      current
   DESCRIPTION
       "Index"
   ::= { sisgm1040284lrtEthLinkOAMPortConfEntry 1 }

sisgm1040284lrtEthLinkOAMPortConfOAMEnable OBJECT-TYPE
   SYNTAX      Integer32
   MAX-ACCESS  read-write
   STATUS      current
   DESCRIPTION
       "Controls whether Link OAM is enabled on this switch port. 
	   Enabling Link OAM provides the network operators the ability to monitor the health of the network and 
	   quickly determine the location of failing links or fault conditions.
	   0:disable
	   1:enable"
   ::= { sisgm1040284lrtEthLinkOAMPortConfEntry 2 }
   
sisgm1040284lrtEthLinkOAMPortConfOAMMode OBJECT-TYPE
   SYNTAX      Integer32
   MAX-ACCESS  read-write
   STATUS      current
   DESCRIPTION
       "Configures the OAM Mode as Active or Passive. The default mode is Passive.
	   0:Passive mode
	   1:Active mode"
   ::= { sisgm1040284lrtEthLinkOAMPortConfEntry 3 }   
   
sisgm1040284lrtEthLinkOAMPortConfLoopbackSupport OBJECT-TYPE
   SYNTAX      Integer32
   MAX-ACCESS  read-write
   STATUS      current
   DESCRIPTION
       "Controls whether the loopback support is enabled for the switch port. 
	   0:disable
	   1:enable"
   ::= { sisgm1040284lrtEthLinkOAMPortConfEntry 4 }     
   
sisgm1040284lrtEthLinkOAMPortConfLinkMonitorSupport OBJECT-TYPE
   SYNTAX      Integer32
   MAX-ACCESS  read-write
   STATUS      current
   DESCRIPTION
       "Controls whether the Link Monitor support is enabled for the switch port.
	   0:disable
	   1:enable"
   ::= { sisgm1040284lrtEthLinkOAMPortConfEntry 5 }

sisgm1040284lrtEthLinkOAMPortConfMIBRetrievalSupport OBJECT-TYPE
   SYNTAX      Integer32
   MAX-ACCESS  read-write
   STATUS      current
   DESCRIPTION
       "Controls whether the MIB Retrieval Support is enabled for the switch port. 
	   0:disable
	   1:enable"
   ::= { sisgm1040284lrtEthLinkOAMPortConfEntry 6 }    
   
sisgm1040284lrtEthLinkOAMPortConfLoopbackOperation OBJECT-TYPE
   SYNTAX      Integer32
   MAX-ACCESS  read-write
   STATUS      current
   DESCRIPTION
       "If the Loopback support is enabled, enabling this field will start a loopback operation for the port.
	   0:disable
	   1:enable"
   ::= { sisgm1040284lrtEthLinkOAMPortConfEntry 7 }       
   
   
   
sisgm1040284lrtEthLinkOAMPortDetailStatusTable OBJECT-TYPE
   SYNTAX      SEQUENCE OF SISGM1040284LRTEthLinkOAMPortDetailStatusEntry
   MAX-ACCESS  not-accessible
   STATUS      current
   DESCRIPTION
       "Eth Link OAM Port Detail Status table"
   ::= { sisgm1040284lrtETHLINKOAM 2 }

sisgm1040284lrtEthLinkOAMPortDetailStatusEntry OBJECT-TYPE
   SYNTAX      SISGM1040284LRTEthLinkOAMPortDetailStatusEntry
   MAX-ACCESS  not-accessible
   STATUS      current
   DESCRIPTION
       "Eth Link OAM Port Detail Status entry"
   INDEX    { sisgm1040284lrtEthLinkOAMPortDetailStatusIndex  }
   ::= { sisgm1040284lrtEthLinkOAMPortDetailStatusTable 1 }

SISGM1040284LRTEthLinkOAMPortDetailStatusEntry ::= SEQUENCE {
   sisgm1040284lrtEthLinkOAMPortDetailStatusIndex                       Integer32,
   sisgm1040284lrtEthLinkOAMPortPDUPermission                           DisplayString,
   sisgm1040284lrtEthLinkOAMPortDiscoveryState                          DisplayString,
   sisgm1040284lrtEthLinkOAMPortPeerMACAddress                          DisplayString,
   sisgm1040284lrtEthLinkOAMPortLocalMode                               DisplayString,
   sisgm1040284lrtEthLinkOAMPortLocalUnidirectionalOperationSupport     DisplayString,
   sisgm1040284lrtEthLinkOAMPortLocalRemoteLoopbackSupport              DisplayString,
   sisgm1040284lrtEthLinkOAMPortLocalLinkMonitoringSupport              DisplayString,
   sisgm1040284lrtEthLinkOAMPortLocalMIBRetrievalSupport                DisplayString,
   sisgm1040284lrtEthLinkOAMPortLocalMTUSize                            Integer32,  
   sisgm1040284lrtEthLinkOAMPortLocalMultiplexerState                   DisplayString,  
   sisgm1040284lrtEthLinkOAMPortLocalParserState                        DisplayString,  
   sisgm1040284lrtEthLinkOAMPortLocalOrganizationalUniqueIdentification DisplayString,  
   sisgm1040284lrtEthLinkOAMPortLocalPDURevision                        Integer32,  
   sisgm1040284lrtEthLinkOAMPortPeerMode                                DisplayString,  
   sisgm1040284lrtEthLinkOAMPortPeerUnidirectionalOperationSupport      DisplayString,  
   sisgm1040284lrtEthLinkOAMPortPeerRemoteLoopbackSupport               DisplayString,  
   sisgm1040284lrtEthLinkOAMPortPeerLinkMonitoringSupport               DisplayString,  
   sisgm1040284lrtEthLinkOAMPortPeerMIBRetrievalSupport                 DisplayString,  
   sisgm1040284lrtEthLinkOAMPortPeerMTUSize                             DisplayString,  
   sisgm1040284lrtEthLinkOAMPortPeerMultiplexerState                    DisplayString,  
   sisgm1040284lrtEthLinkOAMPortPeerParserState                         DisplayString,  
   sisgm1040284lrtEthLinkOAMPortPeerOrganizationalUniqueIdentification  DisplayString,  
   sisgm1040284lrtEthLinkOAMPortPDURevision                             DisplayString     
}

sisgm1040284lrtEthLinkOAMPortDetailStatusIndex OBJECT-TYPE
   SYNTAX      Integer32
   MAX-ACCESS  not-accessible
   STATUS      current
   DESCRIPTION
       "Index"
   ::= { sisgm1040284lrtEthLinkOAMPortDetailStatusEntry 1 }

sisgm1040284lrtEthLinkOAMPortPDUPermission OBJECT-TYPE
   SYNTAX      DisplayString
   MAX-ACCESS  read-only
   STATUS      current
   DESCRIPTION
       "This field is available only for the Local DTE. 
	   It displays the current permission rules set for the local DTE. 
	   Possible values are Link fault, Receive only, Information exchange only, ANY."
   ::= { sisgm1040284lrtEthLinkOAMPortDetailStatusEntry 2 }
   
sisgm1040284lrtEthLinkOAMPortDiscoveryState OBJECT-TYPE
   SYNTAX      DisplayString
   MAX-ACCESS  read-only
   STATUS      current
   DESCRIPTION
       "Displays the current state of the discovery process. 
	   Possible states are Fault state, Active state, Passive state, 
	   SEND_LOCAL_REMOTE_STATE, SEND_LOCAL_REMOTE_OK_STATE, SEND_ANY_STATE."
   ::= { sisgm1040284lrtEthLinkOAMPortDetailStatusEntry 3 }   
   
sisgm1040284lrtEthLinkOAMPortPeerMACAddress OBJECT-TYPE
   SYNTAX      DisplayString
   MAX-ACCESS  read-only
   STATUS      current
   DESCRIPTION
       " "
   ::= { sisgm1040284lrtEthLinkOAMPortDetailStatusEntry 4 }     
   
sisgm1040284lrtEthLinkOAMPortLocalMode OBJECT-TYPE
   SYNTAX      DisplayString
   MAX-ACCESS  read-only
   STATUS      current
   DESCRIPTION
       "The Mode in which the Link OAM is operating, Active or Passive."
   ::= { sisgm1040284lrtEthLinkOAMPortDetailStatusEntry 5 }

sisgm1040284lrtEthLinkOAMPortLocalUnidirectionalOperationSupport OBJECT-TYPE
   SYNTAX      DisplayString
   MAX-ACCESS  read-only
   STATUS      current
   DESCRIPTION
       "This feature is not available to be configured by the user. The status of this configuration is retrieved from the PHY."
   ::= { sisgm1040284lrtEthLinkOAMPortDetailStatusEntry 6 }    
   
sisgm1040284lrtEthLinkOAMPortLocalRemoteLoopbackSupport OBJECT-TYPE
   SYNTAX      DisplayString
   MAX-ACCESS  read-only
   STATUS      current
   DESCRIPTION
       "If status is enabled, DTE is capable of OAM remote loopback mode."
   ::= { sisgm1040284lrtEthLinkOAMPortDetailStatusEntry 7 }       
   
sisgm1040284lrtEthLinkOAMPortLocalLinkMonitoringSupport OBJECT-TYPE
   SYNTAX      DisplayString
   MAX-ACCESS  read-only
   STATUS      current
   DESCRIPTION
       "If status is enabled, DTE supports interpreting Link Events."
   ::= { sisgm1040284lrtEthLinkOAMPortDetailStatusEntry 8 }   

sisgm1040284lrtEthLinkOAMPortLocalMIBRetrievalSupport OBJECT-TYPE
   SYNTAX      DisplayString
   MAX-ACCESS  read-only
   STATUS      current
   DESCRIPTION
       "If status ie enabled DTE supports sending Variable Response OAMPDUs."
   ::= { sisgm1040284lrtEthLinkOAMPortDetailStatusEntry 9 }   

sisgm1040284lrtEthLinkOAMPortLocalMTUSize OBJECT-TYPE
   SYNTAX      Integer32
   MAX-ACCESS  read-only
   STATUS      current
   DESCRIPTION
       "It represents the largest OAMPDU, in octets, supported by the DTE. 
	   This value is compared to the remotes Maximum PDU Size and the smaller of the two is used."
   ::= { sisgm1040284lrtEthLinkOAMPortDetailStatusEntry 10 }   
   
sisgm1040284lrtEthLinkOAMPortLocalMultiplexerState OBJECT-TYPE
   SYNTAX      DisplayString
   MAX-ACCESS  read-only
   STATUS      current
   DESCRIPTION
       "When in forwarding state, the Device is forwarding non-OAMPDUs to the lower sublayer. 
	   Incase of discarding, the device discards all the non-OAMPDU's."
   ::= { sisgm1040284lrtEthLinkOAMPortDetailStatusEntry 11 }  
   
sisgm1040284lrtEthLinkOAMPortLocalParserState OBJECT-TYPE
   SYNTAX      DisplayString
   MAX-ACCESS  read-only
   STATUS      current
   DESCRIPTION
       "When in forwarding state, Device is forwarding non-OAMPDUs to higher sublayer. 
	   When in loopback, Device is looping back non-OAMPDUs to the lower sublayer. 
	   When in discarding state, Device is discarding non-OAMPDUs."
   ::= { sisgm1040284lrtEthLinkOAMPortDetailStatusEntry 12 }  
   
sisgm1040284lrtEthLinkOAMPortLocalOrganizationalUniqueIdentification OBJECT-TYPE
   SYNTAX      DisplayString
   MAX-ACCESS  read-only
   STATUS      current
   DESCRIPTION
       "24-bit Organizationally Unique Identifier of the vendor."
   ::= { sisgm1040284lrtEthLinkOAMPortDetailStatusEntry 13 }   
   
sisgm1040284lrtEthLinkOAMPortLocalPDURevision OBJECT-TYPE
   SYNTAX      Integer32
   MAX-ACCESS  read-only
   STATUS      current
   DESCRIPTION
       "It indicates the current revision of the Information TLV. 
	   The value of this field shall start at zero and be incremented each time something in the Information TLV changes. 
	   Upon reception of an Information TLV from a peer, an OAM client may use this field to decide if it needs to be processed 
	   (an Information TLV that is identical to the previous Information TLV doesn't need to be parsed as nothing in it has changed)."
   ::= { sisgm1040284lrtEthLinkOAMPortDetailStatusEntry 14 } 
   
sisgm1040284lrtEthLinkOAMPortPeerMode OBJECT-TYPE
   SYNTAX      DisplayString
   MAX-ACCESS  read-only
   STATUS      current
   DESCRIPTION
       "The Mode in which the Link OAM is operating, Active or Passive."
   ::= { sisgm1040284lrtEthLinkOAMPortDetailStatusEntry 15 }  
   
sisgm1040284lrtEthLinkOAMPortPeerUnidirectionalOperationSupport OBJECT-TYPE
   SYNTAX      DisplayString
   MAX-ACCESS  read-only
   STATUS      current
   DESCRIPTION
       "This feature is not available to be configured by the user. 
	   The status of this configuration is retrieved from the PHY."
   ::= { sisgm1040284lrtEthLinkOAMPortDetailStatusEntry 16 } 
   
sisgm1040284lrtEthLinkOAMPortPeerRemoteLoopbackSupport OBJECT-TYPE
   SYNTAX      DisplayString
   MAX-ACCESS  read-only
   STATUS      current
   DESCRIPTION
       "If status is enabled, DTE is capable of OAM remote loopback mode."
   ::= { sisgm1040284lrtEthLinkOAMPortDetailStatusEntry 17 } 
   
sisgm1040284lrtEthLinkOAMPortPeerLinkMonitoringSupport OBJECT-TYPE
   SYNTAX      DisplayString
   MAX-ACCESS  read-only
   STATUS      current
   DESCRIPTION
       "If status is enabled, DTE supports interpreting Link Events."
   ::= { sisgm1040284lrtEthLinkOAMPortDetailStatusEntry 18 } 
   
sisgm1040284lrtEthLinkOAMPortPeerMIBRetrievalSupport OBJECT-TYPE
   SYNTAX      DisplayString
   MAX-ACCESS  read-only
   STATUS      current
   DESCRIPTION
       "If status ie enabled DTE supports sending Variable Response OAMPDUs."
   ::= { sisgm1040284lrtEthLinkOAMPortDetailStatusEntry 19 } 
   
sisgm1040284lrtEthLinkOAMPortPeerMTUSize OBJECT-TYPE
   SYNTAX      DisplayString
   MAX-ACCESS  read-only
   STATUS      current
   DESCRIPTION
       "It represents the largest OAMPDU, in octets, supported by the DTE. 
	   This value is compared to the remotes Maximum PDU Size and the smaller of the two is used."
   ::= { sisgm1040284lrtEthLinkOAMPortDetailStatusEntry 20 } 
   
sisgm1040284lrtEthLinkOAMPortPeerMultiplexerState OBJECT-TYPE
   SYNTAX      DisplayString
   MAX-ACCESS  read-only
   STATUS      current
   DESCRIPTION
       "When in forwarding state, the Device is forwarding non-OAMPDUs to the lower sublayer. 
	   Incase of discarding, the device discards all the non-OAMPDU's."
   ::= { sisgm1040284lrtEthLinkOAMPortDetailStatusEntry 21 } 
   
sisgm1040284lrtEthLinkOAMPortPeerParserState OBJECT-TYPE
   SYNTAX      DisplayString
   MAX-ACCESS  read-only
   STATUS      current
   DESCRIPTION
       "When in forwarding state, Device is forwarding non-OAMPDUs to higher sublayer. 
	   When in loopback, Device is looping back non-OAMPDUs to the lower sublayer. 
	   When in discarding state, Device is discarding non-OAMPDUs."
   ::= { sisgm1040284lrtEthLinkOAMPortDetailStatusEntry 22 } 
   
sisgm1040284lrtEthLinkOAMPortPeerOrganizationalUniqueIdentification OBJECT-TYPE
   SYNTAX      DisplayString
   MAX-ACCESS  read-only
   STATUS      current
   DESCRIPTION
       "24-bit Organizationally Unique Identifier of the vendor."
   ::= { sisgm1040284lrtEthLinkOAMPortDetailStatusEntry 23 }      
   
sisgm1040284lrtEthLinkOAMPortPDURevision                              OBJECT-TYPE
   SYNTAX      DisplayString
   MAX-ACCESS  read-only
   STATUS      current
   DESCRIPTION
       "It indicates the current revision of the Information TLV. 
	   The value of this field shall start at zero and be incremented each time something in the Information TLV changes. 
	   Upon reception of an Information TLV from a peer, an OAM client may use this field to decide if it needs to be processed 
	   (an Information TLV that is identical to the previous Information TLV doesn't need to be parsed as nothing in it has changed)."
   ::= { sisgm1040284lrtEthLinkOAMPortDetailStatusEntry 24 }   


sisgm1040284lrtEthLinkOAMPortLinkEventConfTable OBJECT-TYPE
   SYNTAX      SEQUENCE OF SISGM1040284LRTEthLinkOAMPortLinkEventConfEntry
   MAX-ACCESS  not-accessible
   STATUS      current
   DESCRIPTION
       "Eth Link OAM Port Link Event Conf Table"
   ::= { sisgm1040284lrtETHLINKOAM 3 }

sisgm1040284lrtEthLinkOAMPortLinkEventConfEntry OBJECT-TYPE
   SYNTAX      SISGM1040284LRTEthLinkOAMPortLinkEventConfEntry
   MAX-ACCESS  not-accessible
   STATUS      current
   DESCRIPTION
       "Eth Link OAM Port Link Event Conf Entry"
   INDEX    { sisgm1040284lrtEthLinkOAMPortLinkEventConfIndex  }
   ::= { sisgm1040284lrtEthLinkOAMPortLinkEventConfTable 1 }

SISGM1040284LRTEthLinkOAMPortLinkEventConfEntry ::= SEQUENCE {
   sisgm1040284lrtEthLinkOAMPortLinkEventConfIndex                                 Integer32,
   sisgm1040284lrtEthLinkOAMPortLinkEventConfErrorFrameEventErrorWindow            Integer32,
   sisgm1040284lrtEthLinkOAMPortLinkEventConfErrorFrameEventErrorThreshold         Integer32,
   sisgm1040284lrtEthLinkOAMPortLinkEventConfSymbolPeriodErrorEventErrorWindow     Integer32,
   sisgm1040284lrtEthLinkOAMPortLinkEventConfSymbolPeriodErrorEventErrorThreshold  Integer32,
   sisgm1040284lrtEthLinkOAMPortLinkEventConfSecondsSummaryEventErrorWindow        Integer32,
   sisgm1040284lrtEthLinkOAMPortLinkEventConfSecondsSummaryEventErrorThreshold     Integer32
}

sisgm1040284lrtEthLinkOAMPortLinkEventConfIndex OBJECT-TYPE
   SYNTAX      Integer32
   MAX-ACCESS  not-accessible
   STATUS      current
   DESCRIPTION
       "Index"
   ::= { sisgm1040284lrtEthLinkOAMPortLinkEventConfEntry 1 }

sisgm1040284lrtEthLinkOAMPortLinkEventConfErrorFrameEventErrorWindow OBJECT-TYPE
   SYNTAX      Integer32
   MAX-ACCESS  read-write
   STATUS      current
   DESCRIPTION
       "The Errored Frame Event counts the number of errored frames detected during the specified period. 
	   Represents the window period in the order of 1 sec for the observation of various link events.
	   range: 1-60"
   ::= { sisgm1040284lrtEthLinkOAMPortLinkEventConfEntry 2 }
   
sisgm1040284lrtEthLinkOAMPortLinkEventConfErrorFrameEventErrorThreshold OBJECT-TYPE
   SYNTAX      Integer32
   MAX-ACCESS  read-write
   STATUS      current
   DESCRIPTION
       "The Errored Frame Event counts the number of errored frames detected during the specified period. 
	   Represents the threshold value for the window period for the appropriate Link event so as to notify the peer of this error.
	   range:0-0xffffffff"
   ::= { sisgm1040284lrtEthLinkOAMPortLinkEventConfEntry 3 }
   
sisgm1040284lrtEthLinkOAMPortLinkEventConfSymbolPeriodErrorEventErrorWindow OBJECT-TYPE
   SYNTAX      Integer32
   MAX-ACCESS  read-write
   STATUS      current
   DESCRIPTION
       "The Errored Symbol Period Event counts the number of symbol errors that occurred during the specified period.
	   Represents the window period in the order of 1 sec for the observation of various link events.
	   range: 1-60"
   ::= { sisgm1040284lrtEthLinkOAMPortLinkEventConfEntry 4 }

sisgm1040284lrtEthLinkOAMPortLinkEventConfSymbolPeriodErrorEventErrorThreshold OBJECT-TYPE
   SYNTAX      Integer32
   MAX-ACCESS  read-write
   STATUS      current
   DESCRIPTION
       "The Errored Symbol Period Event counts the number of symbol errors that occurred during the specified period.
	   Represents the threshold value for the window period for the appropriate Link event so as to notify the peer of this error.
	   range:0-0xffffffff"
   ::= { sisgm1040284lrtEthLinkOAMPortLinkEventConfEntry 5 }

sisgm1040284lrtEthLinkOAMPortLinkEventConfSecondsSummaryEventErrorWindow OBJECT-TYPE
   SYNTAX      Integer32
   MAX-ACCESS  read-write
   STATUS      current
   DESCRIPTION
       "The Errored Frame Seconds Summary Event TLV counts the number of errored frame seconds that occurred during the specified period. 
	   Represents the window period in the order of 1 sec for the observation of various link events.
	   range: 10-900"
   ::= { sisgm1040284lrtEthLinkOAMPortLinkEventConfEntry 6 }   
   
sisgm1040284lrtEthLinkOAMPortLinkEventConfSecondsSummaryEventErrorThreshold OBJECT-TYPE
   SYNTAX      Integer32
   MAX-ACCESS  read-write
   STATUS      current
   DESCRIPTION
       "The Errored Frame Seconds Summary Event TLV counts the number of errored frame seconds that occurred during the specified period. 
	   Represents the threshold value for the window period for the appropriate Link event so as to notify the peer of this error.
	   range:0-0xffff"
   ::= { sisgm1040284lrtEthLinkOAMPortLinkEventConfEntry 7 } 




sisgm1040284lrtEthLinkOAMPortDetailedStatisticsTable OBJECT-TYPE
   SYNTAX      SEQUENCE OF SISGM1040284LRTEthLinkOAMPortDetailedStatisticsEntry
   MAX-ACCESS  not-accessible
   STATUS      current
   DESCRIPTION
       "Eth Link OAM Port Detailed Statistics Table"
   ::= { sisgm1040284lrtETHLINKOAM 4 }

sisgm1040284lrtEthLinkOAMPortDetailedStatisticsEntry OBJECT-TYPE
   SYNTAX      SISGM1040284LRTEthLinkOAMPortDetailedStatisticsEntry
   MAX-ACCESS  not-accessible
   STATUS      current
   DESCRIPTION
       "Eth Link OAM Port Detailed Statistics Entry"
   INDEX    { sisgm1040284lrtEthLinkOAMPortDetailedStatisticsIndex  }
   ::= { sisgm1040284lrtEthLinkOAMPortDetailedStatisticsTable 1 }

SISGM1040284LRTEthLinkOAMPortDetailedStatisticsEntry ::= SEQUENCE {
   sisgm1040284lrtEthLinkOAMPortDetailedStatisticsIndex                             Integer32,
   sisgm1040284lrtEthLinkOAMPortDetailedStatisticsRxOAMInformationPDUs              Integer32,
   sisgm1040284lrtEthLinkOAMPortDetailedStatisticsRxUniqueErrorEventNotification    Integer32,
   sisgm1040284lrtEthLinkOAMPortDetailedStatisticsRxDuplicateErrorEventNotification Integer32,
   sisgm1040284lrtEthLinkOAMPortDetailedStatisticsRxLoopbackControl                 Integer32,
   sisgm1040284lrtEthLinkOAMPortDetailedStatisticsRxVariableRequest                 Integer32,
   sisgm1040284lrtEthLinkOAMPortDetailedStatisticsRxVariableResponse                Integer32,
   sisgm1040284lrtEthLinkOAMPortDetailedStatisticsRxOrgSpecificPDUs                 Integer32,
   sisgm1040284lrtEthLinkOAMPortDetailedStatisticsRxUnsupportedCodes                Integer32,
   sisgm1040284lrtEthLinkOAMPortDetailedStatisticsRxLinkFaultPDUs                   Integer32,
   sisgm1040284lrtEthLinkOAMPortDetailedStatisticsRxDyingGasp                       Integer32,
   sisgm1040284lrtEthLinkOAMPortDetailedStatisticsRxCriticalEventPDUs               Integer32,
   sisgm1040284lrtEthLinkOAMPortDetailedStatisticsTxOAMInformationPDUs              Integer32,
   sisgm1040284lrtEthLinkOAMPortDetailedStatisticsTxUniqueErrorEventNotification    Integer32,
   sisgm1040284lrtEthLinkOAMPortDetailedStatisticsTxDuplicateErrorEventNotification Integer32,
   sisgm1040284lrtEthLinkOAMPortDetailedStatisticsTxLoopbackControl                 Integer32,
   sisgm1040284lrtEthLinkOAMPortDetailedStatisticsTxVariableRequest                 Integer32,
   sisgm1040284lrtEthLinkOAMPortDetailedStatisticsTxVariableResponse                Integer32,
   sisgm1040284lrtEthLinkOAMPortDetailedStatisticsTxOrgSpecificPDUs                 Integer32,
   sisgm1040284lrtEthLinkOAMPortDetailedStatisticsTxUnsupportedCodes                Integer32,
   sisgm1040284lrtEthLinkOAMPortDetailedStatisticsTxLinkFaultPDUs                   Integer32,
   sisgm1040284lrtEthLinkOAMPortDetailedStatisticsTxDyingGasp                       Integer32,
   sisgm1040284lrtEthLinkOAMPortDetailedStatisticsTxCriticalEventPDUs               Integer32,
   sisgm1040284lrtEthLinkOAMPortDetailedStatisticsClear                             Integer32
}

sisgm1040284lrtEthLinkOAMPortDetailedStatisticsIndex OBJECT-TYPE
   SYNTAX      Integer32
   MAX-ACCESS  not-accessible
   STATUS      current
   DESCRIPTION
       "Index"
   ::= { sisgm1040284lrtEthLinkOAMPortDetailedStatisticsEntry 1 }

sisgm1040284lrtEthLinkOAMPortDetailedStatisticsRxOAMInformationPDUs OBJECT-TYPE
   SYNTAX      Integer32
   MAX-ACCESS  read-only
   STATUS      current
   DESCRIPTION
       "The number of received and transmitted OAM Information PDU's. 
	   Discontinuities of this counter can occur at re-initialization of the management system."
   ::= { sisgm1040284lrtEthLinkOAMPortDetailedStatisticsEntry 2 }
   
sisgm1040284lrtEthLinkOAMPortDetailedStatisticsRxUniqueErrorEventNotification OBJECT-TYPE
   SYNTAX      Integer32
   MAX-ACCESS  read-only
   STATUS      current
   DESCRIPTION
       "A count of the number of unique Event OAMPDUs received and transmitted on this interface. 
	   Event Notifications may be sent in duplicate to increase the probability of successfully being received, 
	   given the possibility that a frame may be lost in transit. 
	   Duplicate Event Notification transmissions are counted by 
	   Duplicate Event Notification counters for Tx and Rx respectively. 
	   A unique Event Notification OAMPDU is indicated as an Event Notification OAMPDU with
	   a Sequence Number field that is distinct from the previously transmitted Event Notification OAMPDU Sequence Number."
   ::= { sisgm1040284lrtEthLinkOAMPortDetailedStatisticsEntry 3 }
   
sisgm1040284lrtEthLinkOAMPortDetailedStatisticsRxDuplicateErrorEventNotification OBJECT-TYPE
   SYNTAX      Integer32
   MAX-ACCESS  read-only
   STATUS      current
   DESCRIPTION
       "A count of the number of duplicate Event OAMPDUs received and transmitted on this interface. 
	   Event Notification OAMPDUs may be sent in duplicate to increase the probability of successfully being received, 
	   given the possibility that a frame may be lost in transit. 
	   A duplicate Event Notification OAMPDU is indicated as an Event Notification OAMPDU with
	   a Sequence Number field that is identical to the previously transmitted Event Notification OAMPDU Sequence Number."
   ::= { sisgm1040284lrtEthLinkOAMPortDetailedStatisticsEntry 4 }
   
sisgm1040284lrtEthLinkOAMPortDetailedStatisticsRxLoopbackControl OBJECT-TYPE
   SYNTAX      Integer32
   MAX-ACCESS  read-only
   STATUS      current
   DESCRIPTION
       "A count of the number of Loopback Control OAMPDUs received and transmitted on this interface."
   ::= { sisgm1040284lrtEthLinkOAMPortDetailedStatisticsEntry 5 }
   
sisgm1040284lrtEthLinkOAMPortDetailedStatisticsRxVariableRequest OBJECT-TYPE
   SYNTAX      Integer32
   MAX-ACCESS  read-only
   STATUS      current
   DESCRIPTION
       "A count of the number of Variable Request OAMPDUs received and transmitted on this interface."
   ::= { sisgm1040284lrtEthLinkOAMPortDetailedStatisticsEntry 6 }
   
sisgm1040284lrtEthLinkOAMPortDetailedStatisticsRxVariableResponse OBJECT-TYPE
   SYNTAX      Integer32
   MAX-ACCESS  read-only
   STATUS      current
   DESCRIPTION
       "A count of the number of Variable Response OAMPDUs received and transmitted on this interface."
   ::= { sisgm1040284lrtEthLinkOAMPortDetailedStatisticsEntry 7 }
   
sisgm1040284lrtEthLinkOAMPortDetailedStatisticsRxOrgSpecificPDUs OBJECT-TYPE
   SYNTAX      Integer32
   MAX-ACCESS  read-only
   STATUS      current
   DESCRIPTION
       "A count of the number of Organization Specific OAMPDUs transmitted on this interface."
   ::= { sisgm1040284lrtEthLinkOAMPortDetailedStatisticsEntry 8 }
   
sisgm1040284lrtEthLinkOAMPortDetailedStatisticsRxUnsupportedCodes OBJECT-TYPE
   SYNTAX      Integer32
   MAX-ACCESS  read-only
   STATUS      current
   DESCRIPTION
       "A count of the number of OAMPDUs transmitted on this interface with an unsupported op-code."
   ::= { sisgm1040284lrtEthLinkOAMPortDetailedStatisticsEntry 9 }
   
sisgm1040284lrtEthLinkOAMPortDetailedStatisticsRxLinkFaultPDUs OBJECT-TYPE
   SYNTAX      Integer32
   MAX-ACCESS  read-only
   STATUS      current
   DESCRIPTION
       "A count of the number of Link fault PDU's received and transmitted on this interface."
   ::= { sisgm1040284lrtEthLinkOAMPortDetailedStatisticsEntry 10 }
   
sisgm1040284lrtEthLinkOAMPortDetailedStatisticsRxDyingGasp OBJECT-TYPE
   SYNTAX      Integer32
   MAX-ACCESS  read-only
   STATUS      current
   DESCRIPTION
       "A count of the number of Dying Gasp events received and transmitted on this interface."
   ::= { sisgm1040284lrtEthLinkOAMPortDetailedStatisticsEntry 11 }
   
sisgm1040284lrtEthLinkOAMPortDetailedStatisticsRxCriticalEventPDUs OBJECT-TYPE
   SYNTAX      Integer32
   MAX-ACCESS  read-only
   STATUS      current
   DESCRIPTION
       "A count of the number of Critical event PDU's received and transmitted on this interface."
   ::= { sisgm1040284lrtEthLinkOAMPortDetailedStatisticsEntry 12 }
   
sisgm1040284lrtEthLinkOAMPortDetailedStatisticsTxOAMInformationPDUs OBJECT-TYPE
   SYNTAX      Integer32
   MAX-ACCESS  read-only
   STATUS      current
   DESCRIPTION
       "The number of received and transmitted OAM Information PDU's. 
	   Discontinuities of this counter can occur at re-initialization of the management system."
   ::= { sisgm1040284lrtEthLinkOAMPortDetailedStatisticsEntry 13 }
   
sisgm1040284lrtEthLinkOAMPortDetailedStatisticsTxUniqueErrorEventNotification OBJECT-TYPE
   SYNTAX      Integer32
   MAX-ACCESS  read-only
   STATUS      current
   DESCRIPTION
       "A count of the number of unique Event OAMPDUs received and transmitted on this interface. 
	   Event Notifications may be sent in duplicate to increase the probability of successfully being received, 
	   given the possibility that a frame may be lost in transit. 
	   Duplicate Event Notification transmissions are counted by 
	   Duplicate Event Notification counters for Tx and Rx respectively. 
	   A unique Event Notification OAMPDU is indicated as an Event Notification OAMPDU with
	   a Sequence Number field that is distinct from the previously transmitted Event Notification OAMPDU Sequence Number."
   ::= { sisgm1040284lrtEthLinkOAMPortDetailedStatisticsEntry 14 }
   
sisgm1040284lrtEthLinkOAMPortDetailedStatisticsTxDuplicateErrorEventNotification OBJECT-TYPE
   SYNTAX      Integer32
   MAX-ACCESS  read-only
   STATUS      current
   DESCRIPTION
       "A count of the number of duplicate Event OAMPDUs received and transmitted on this interface. 
	   Event Notification OAMPDUs may be sent in duplicate to increase the probability of successfully being received, 
	   given the possibility that a frame may be lost in transit. 
	   A duplicate Event Notification OAMPDU is indicated as an Event Notification OAMPDU with
	   a Sequence Number field that is identical to the previously transmitted Event Notification OAMPDU Sequence Number."
   ::= { sisgm1040284lrtEthLinkOAMPortDetailedStatisticsEntry 15 }
   
sisgm1040284lrtEthLinkOAMPortDetailedStatisticsTxLoopbackControl OBJECT-TYPE
   SYNTAX      Integer32
   MAX-ACCESS  read-only
   STATUS      current
   DESCRIPTION
       "A count of the number of Loopback Control OAMPDUs received and transmitted on this interface."
   ::= { sisgm1040284lrtEthLinkOAMPortDetailedStatisticsEntry 16 }
   
sisgm1040284lrtEthLinkOAMPortDetailedStatisticsTxVariableRequest OBJECT-TYPE
   SYNTAX      Integer32
   MAX-ACCESS  read-only
   STATUS      current
   DESCRIPTION
       "A count of the number of Variable Request OAMPDUs received and transmitted on this interface."
   ::= { sisgm1040284lrtEthLinkOAMPortDetailedStatisticsEntry 17 }
   
sisgm1040284lrtEthLinkOAMPortDetailedStatisticsTxVariableResponse OBJECT-TYPE
   SYNTAX      Integer32
   MAX-ACCESS  read-only
   STATUS      current
   DESCRIPTION
       "A count of the number of Variable Response OAMPDUs received and transmitted on this interface."
   ::= { sisgm1040284lrtEthLinkOAMPortDetailedStatisticsEntry 18 }
   
sisgm1040284lrtEthLinkOAMPortDetailedStatisticsTxOrgSpecificPDUs OBJECT-TYPE
   SYNTAX      Integer32
   MAX-ACCESS  read-only
   STATUS      current
   DESCRIPTION
       "A count of the number of Organization Specific OAMPDUs transmitted on this interface."
   ::= { sisgm1040284lrtEthLinkOAMPortDetailedStatisticsEntry 19 }
   
sisgm1040284lrtEthLinkOAMPortDetailedStatisticsTxUnsupportedCodes OBJECT-TYPE
   SYNTAX      Integer32
   MAX-ACCESS  read-only
   STATUS      current
   DESCRIPTION
       "A count of the number of OAMPDUs transmitted on this interface with an unsupported op-code."
   ::= { sisgm1040284lrtEthLinkOAMPortDetailedStatisticsEntry 20 }
   
sisgm1040284lrtEthLinkOAMPortDetailedStatisticsTxLinkFaultPDUs OBJECT-TYPE
   SYNTAX      Integer32
   MAX-ACCESS  read-only
   STATUS      current
   DESCRIPTION
       "A count of the number of Link fault PDU's received and transmitted on this interface."
   ::= { sisgm1040284lrtEthLinkOAMPortDetailedStatisticsEntry 21 }
   
sisgm1040284lrtEthLinkOAMPortDetailedStatisticsTxDyingGasp OBJECT-TYPE
   SYNTAX      Integer32
   MAX-ACCESS  read-only
   STATUS      current
   DESCRIPTION
       "A count of the number of Dying Gasp events received and transmitted on this interface."
   ::= { sisgm1040284lrtEthLinkOAMPortDetailedStatisticsEntry 22 }
   
sisgm1040284lrtEthLinkOAMPortDetailedStatisticsTxCriticalEventPDUs OBJECT-TYPE
   SYNTAX      Integer32
   MAX-ACCESS  read-only
   STATUS      current
   DESCRIPTION
       "A count of the number of Critical event PDU's received and transmitted on this interface."
   ::= { sisgm1040284lrtEthLinkOAMPortDetailedStatisticsEntry 23 }
   
sisgm1040284lrtEthLinkOAMPortDetailedStatisticsClear OBJECT-TYPE
   SYNTAX      Integer32
   MAX-ACCESS  read-write
   STATUS      current
   DESCRIPTION
       "Clears the counters for the selected port."
   ::= { sisgm1040284lrtEthLinkOAMPortDetailedStatisticsEntry 24 }
   
   
sisgm1040284lrtEthLinkOAMPortEventDetailedStatisticsTable OBJECT-TYPE
   SYNTAX      SEQUENCE OF SISGM1040284LRTEthLinkOAMPortEventDetailedStatisticsEntry
   MAX-ACCESS  not-accessible
   STATUS      current
   DESCRIPTION
       "Eth Link OAM Port Event Detailed Statistics Table"
   ::= { sisgm1040284lrtETHLINKOAM 5 }

sisgm1040284lrtEthLinkOAMPortEventDetailedStatisticsEntry OBJECT-TYPE
   SYNTAX      SISGM1040284LRTEthLinkOAMPortEventDetailedStatisticsEntry
   MAX-ACCESS  not-accessible
   STATUS      current
   DESCRIPTION
       "Eth Link OAM Port Event Detailed Statistics Entry"
   INDEX    { sisgm1040284lrtEthLinkOAMPortEventDetailedStatisticsIndex  }
   ::= { sisgm1040284lrtEthLinkOAMPortEventDetailedStatisticsTable 1 }

SISGM1040284LRTEthLinkOAMPortEventDetailedStatisticsEntry ::= SEQUENCE {
   sisgm1040284lrtEthLinkOAMPortEventDetailedStatisticsIndex                                  Integer32,
   sisgm1040284lrtEthLinkOAMPortEventDetailedStatisticsLocalSequenceNumber                    Integer32,
   sisgm1040284lrtEthLinkOAMPortEventDetailedStatisticsLocalFrameErrorEventTimestamp          Integer32,
   sisgm1040284lrtEthLinkOAMPortEventDetailedStatisticsLocalFrameErrorEventWindow             Integer32,
   sisgm1040284lrtEthLinkOAMPortEventDetailedStatisticsLocalFrameErrorEventThreshold          Integer32,
   sisgm1040284lrtEthLinkOAMPortEventDetailedStatisticsLocalFrameErrors                       Integer32,
   sisgm1040284lrtEthLinkOAMPortEventDetailedStatisticsLocalTotalFrameErrors                  Counter64,
   sisgm1040284lrtEthLinkOAMPortEventDetailedStatisticsLocalTotalFrameErrorEvents             Integer32,
   sisgm1040284lrtEthLinkOAMPortEventDetailedStatisticsLocalFramePeriodErrorEventTimestamp    Integer32,
   sisgm1040284lrtEthLinkOAMPortEventDetailedStatisticsLocalFramePeriodErrorEventWindow       Integer32,
   sisgm1040284lrtEthLinkOAMPortEventDetailedStatisticsLocalFramePeriodErrorEventThreshold    Integer32,
   sisgm1040284lrtEthLinkOAMPortEventDetailedStatisticsLocalFramePeriodErrors                 Integer32,
   sisgm1040284lrtEthLinkOAMPortEventDetailedStatisticsLocalTotalFramePeriodErrors            Counter64,
   sisgm1040284lrtEthLinkOAMPortEventDetailedStatisticsLocalTotalFramePeriodErrorEvents       Integer32,
   sisgm1040284lrtEthLinkOAMPortEventDetailedStatisticsLocalSymbolPeriodErrorEventTimestamp   Integer32,
   sisgm1040284lrtEthLinkOAMPortEventDetailedStatisticsLocalSymbolPeriodErrorEventWindow      Counter64,
   sisgm1040284lrtEthLinkOAMPortEventDetailedStatisticsLocalSymbolPeriodErrorEventThreshold   Counter64,
   sisgm1040284lrtEthLinkOAMPortEventDetailedStatisticsLocalSymbolPeriodErrors                Counter64,
   sisgm1040284lrtEthLinkOAMPortEventDetailedStatisticsLocalSymbolFramePeriodErrors           Counter64,
   sisgm1040284lrtEthLinkOAMPortEventDetailedStatisticsLocalSymbolFramePeriodErrorEvents      Integer32,
   sisgm1040284lrtEthLinkOAMPortEventDetailedStatisticsLocalEventSecondsSummaryTimeStamp      Integer32,
   sisgm1040284lrtEthLinkOAMPortEventDetailedStatisticsLocalEventSecondsSummaryWindow         Integer32,
   sisgm1040284lrtEthLinkOAMPortEventDetailedStatisticsLocalEventSecondsSummaryThreshold      Integer32,
   sisgm1040284lrtEthLinkOAMPortEventDetailedStatisticsLocalEventSecondsSummaryEvents         Integer32,
   sisgm1040284lrtEthLinkOAMPortEventDetailedStatisticsLocalEventSecondsSummaryErrorTotal     Integer32,
   sisgm1040284lrtEthLinkOAMPortEventDetailedStatisticsLocalEventSecondsSummaryEventTotal     Integer32,
   sisgm1040284lrtEthLinkOAMPortEventDetailedStatisticsRemoteFrameErrorEventTimestamp         Integer32,
   sisgm1040284lrtEthLinkOAMPortEventDetailedStatisticsRemoteFrameErrorEventWindow            Integer32,
   sisgm1040284lrtEthLinkOAMPortEventDetailedStatisticsRemoteFrameErrorEventThreshold         Integer32,
   sisgm1040284lrtEthLinkOAMPortEventDetailedStatisticsRemoteFrameErrors                      Integer32,
   sisgm1040284lrtEthLinkOAMPortEventDetailedStatisticsRemoteTotalFrameErrors                 Counter64,
   sisgm1040284lrtEthLinkOAMPortEventDetailedStatisticsRemoteTotalFrameErrorEvents            Integer32,
   sisgm1040284lrtEthLinkOAMPortEventDetailedStatisticsRemoteFramePeriodErrorEventTimestamp   Integer32,
   sisgm1040284lrtEthLinkOAMPortEventDetailedStatisticsRemoteFramePeriodErrorEventWindow      Integer32,
   sisgm1040284lrtEthLinkOAMPortEventDetailedStatisticsRemoteFramePeriodErrorEventThreshold   Integer32,
   sisgm1040284lrtEthLinkOAMPortEventDetailedStatisticsRemoteFramePeriodErrors                Integer32,
   sisgm1040284lrtEthLinkOAMPortEventDetailedStatisticsRemoteTotalFramePeriodErrors           Counter64,
   sisgm1040284lrtEthLinkOAMPortEventDetailedStatisticsRemoteTotalFramePeriodErrorEvents      Integer32,
   sisgm1040284lrtEthLinkOAMPortEventDetailedStatisticsRemoteSymbolPeriodErrorEventTimestamp  Integer32,
   sisgm1040284lrtEthLinkOAMPortEventDetailedStatisticsRemoteSymbolPeriodErrorEventWindow     Counter64,
   sisgm1040284lrtEthLinkOAMPortEventDetailedStatisticsRemoteSymbolPeriodErrorEventThreshold  Counter64,
   sisgm1040284lrtEthLinkOAMPortEventDetailedStatisticsRemoteSymbolPeriodErrors               Counter64,
   sisgm1040284lrtEthLinkOAMPortEventDetailedStatisticsRemoteSymbolFramePeriodErrors          Counter64,
   sisgm1040284lrtEthLinkOAMPortEventDetailedStatisticsRemoteSymbolFramePeriodErrorEvents     Integer32,
   sisgm1040284lrtEthLinkOAMPortEventDetailedStatisticsRemoteEventSecondsSummaryTimeStamp     Integer32,
   sisgm1040284lrtEthLinkOAMPortEventDetailedStatisticsRemoteEventSecondsSummaryWindow        Integer32,
   sisgm1040284lrtEthLinkOAMPortEventDetailedStatisticsRemoteEventSecondsSummaryThreshold     Integer32,   
   sisgm1040284lrtEthLinkOAMPortEventDetailedStatisticsRemoteEventSecondsSummaryEvents        Integer32,
   sisgm1040284lrtEthLinkOAMPortEventDetailedStatisticsRemoteEventSecondsSummaryErrorTotal    Integer32,
   sisgm1040284lrtEthLinkOAMPortEventDetailedStatisticsRemoteEventSecondsSummaryEventTotal    Integer32   
}

sisgm1040284lrtEthLinkOAMPortEventDetailedStatisticsIndex OBJECT-TYPE
   SYNTAX      Integer32
   MAX-ACCESS  not-accessible
   STATUS      current
   DESCRIPTION
       "Index"
   ::= { sisgm1040284lrtEthLinkOAMPortEventDetailedStatisticsEntry 1 }

sisgm1040284lrtEthLinkOAMPortEventDetailedStatisticsLocalSequenceNumber OBJECT-TYPE
   SYNTAX      Integer32
   MAX-ACCESS  read-only
   STATUS      current
   DESCRIPTION
       "This two-octet field indicates the total number of events occurred at the remote end."   
   ::= { sisgm1040284lrtEthLinkOAMPortEventDetailedStatisticsEntry 2 }
   
sisgm1040284lrtEthLinkOAMPortEventDetailedStatisticsLocalFrameErrorEventTimestamp OBJECT-TYPE
   SYNTAX      Integer32
   MAX-ACCESS  read-only
   STATUS      current
   DESCRIPTION
       "This two-octet field indicates the time reference when the event was generated, in terms of 100 ms intervals."   
   ::= { sisgm1040284lrtEthLinkOAMPortEventDetailedStatisticsEntry 3 }

sisgm1040284lrtEthLinkOAMPortEventDetailedStatisticsLocalFrameErrorEventWindow OBJECT-TYPE
   SYNTAX      Integer32
   MAX-ACCESS  read-only
   STATUS      current
   DESCRIPTION
       "This two-octet field indicates the duration of the period in terms of 100 ms intervals. 1) 
	   The default value is one second. 2) The lower bound is one second. 3) 
	   The upper bound is one minute."   
   ::= { sisgm1040284lrtEthLinkOAMPortEventDetailedStatisticsEntry 4 }

sisgm1040284lrtEthLinkOAMPortEventDetailedStatisticsLocalFrameErrorEventThreshold OBJECT-TYPE
   SYNTAX      Integer32
   MAX-ACCESS  read-only
   STATUS      current
   DESCRIPTION
       "This four-octet field indicates the number of detected errored frames in the period is required
	   to be equal to or greater than in order for the event to be generated. 1) 
	   The default value is one frame error. 2) 
	   The lower bound is zero frame errors. 3) 
	   The upper bound is unspecified."   
   ::= { sisgm1040284lrtEthLinkOAMPortEventDetailedStatisticsEntry 5 }

sisgm1040284lrtEthLinkOAMPortEventDetailedStatisticsLocalFrameErrors OBJECT-TYPE
   SYNTAX      Integer32
   MAX-ACCESS  read-only
   STATUS      current
   DESCRIPTION
       "This four-octet field indicates the number of detected errored frames in the period."   
   ::= { sisgm1040284lrtEthLinkOAMPortEventDetailedStatisticsEntry 6 }

sisgm1040284lrtEthLinkOAMPortEventDetailedStatisticsLocalTotalFrameErrors OBJECT-TYPE
   SYNTAX      Counter64
   MAX-ACCESS  read-only
   STATUS      current
   DESCRIPTION
       "This eight-octet field indicates the sum of errored frames that have been detected since the OAM sublayer was reset."   
   ::= { sisgm1040284lrtEthLinkOAMPortEventDetailedStatisticsEntry 7 }

sisgm1040284lrtEthLinkOAMPortEventDetailedStatisticsLocalTotalFrameErrorEvents OBJECT-TYPE
   SYNTAX      Integer32
   MAX-ACCESS  read-only
   STATUS      current
   DESCRIPTION
       "This four-octet field indicates the number of Errored Frame Event TLVs that 
	   have been generated since the OAM sublayer was reset."   
   ::= { sisgm1040284lrtEthLinkOAMPortEventDetailedStatisticsEntry 8 }

sisgm1040284lrtEthLinkOAMPortEventDetailedStatisticsLocalFramePeriodErrorEventTimestamp OBJECT-TYPE
   SYNTAX      Integer32
   MAX-ACCESS  read-only
   STATUS      current
   DESCRIPTION
       "This two-octet field indicates the time reference when the event was generated, in terms of 100 ms intervals."   
   ::= { sisgm1040284lrtEthLinkOAMPortEventDetailedStatisticsEntry 9 }

sisgm1040284lrtEthLinkOAMPortEventDetailedStatisticsLocalFramePeriodErrorEventWindow OBJECT-TYPE
   SYNTAX      Integer32
   MAX-ACCESS  read-only
   STATUS      current
   DESCRIPTION
       "This four-octet field indicates the duration of period in terms of frames."   
   ::= { sisgm1040284lrtEthLinkOAMPortEventDetailedStatisticsEntry 10 }

sisgm1040284lrtEthLinkOAMPortEventDetailedStatisticsLocalFramePeriodErrorEventThreshold OBJECT-TYPE
   SYNTAX      Integer32
   MAX-ACCESS  read-only
   STATUS      current
   DESCRIPTION
       "This four-octet field indicates the number of errored frames in the period is required
	   to be equal to or greater than in order for the event to be generated."   
   ::= { sisgm1040284lrtEthLinkOAMPortEventDetailedStatisticsEntry 11 }

sisgm1040284lrtEthLinkOAMPortEventDetailedStatisticsLocalFramePeriodErrors OBJECT-TYPE
   SYNTAX      Integer32
   MAX-ACCESS  read-only
   STATUS      current
   DESCRIPTION
       "This four-octet field indicates the number of frame errors in the period."   
   ::= { sisgm1040284lrtEthLinkOAMPortEventDetailedStatisticsEntry 12 }

sisgm1040284lrtEthLinkOAMPortEventDetailedStatisticsLocalTotalFramePeriodErrors OBJECT-TYPE
   SYNTAX      Counter64
   MAX-ACCESS  read-only
   STATUS      current
   DESCRIPTION
       "This eight-octet field indicates the sum of frame errors that have been detected since the OAM sublayer was reset."   
   ::= { sisgm1040284lrtEthLinkOAMPortEventDetailedStatisticsEntry 13 }

sisgm1040284lrtEthLinkOAMPortEventDetailedStatisticsLocalTotalFramePeriodErrorEvents OBJECT-TYPE
   SYNTAX      Integer32
   MAX-ACCESS  read-only
   STATUS      current
   DESCRIPTION
       "This four-octet field indicates the number of Errored Frame Period Event TLVs 
	   that have been generated since the OAM sublayer was reset."   
   ::= { sisgm1040284lrtEthLinkOAMPortEventDetailedStatisticsEntry 14 }

sisgm1040284lrtEthLinkOAMPortEventDetailedStatisticsLocalSymbolPeriodErrorEventTimestamp OBJECT-TYPE
   SYNTAX      Integer32
   MAX-ACCESS  read-only
   STATUS      current
   DESCRIPTION
       "This two-octet field indicates the time reference when the event was generated, in terms of 100 ms intervals."   
   ::= { sisgm1040284lrtEthLinkOAMPortEventDetailedStatisticsEntry 15 }

sisgm1040284lrtEthLinkOAMPortEventDetailedStatisticsLocalSymbolPeriodErrorEventWindow OBJECT-TYPE
   SYNTAX      Counter64
   MAX-ACCESS  read-only
   STATUS      current
   DESCRIPTION
       "This eight-octet field indicates the number of symbols in the period."   
   ::= { sisgm1040284lrtEthLinkOAMPortEventDetailedStatisticsEntry 16 }

sisgm1040284lrtEthLinkOAMPortEventDetailedStatisticsLocalSymbolPeriodErrorEventThreshold OBJECT-TYPE
   SYNTAX      Counter64
   MAX-ACCESS  read-only
   STATUS      current
   DESCRIPTION
       "This eight-octet field indicates the number of errored symbols in the period is required to
	   be equal to or greater than in order for the event to be generated."   
   ::= { sisgm1040284lrtEthLinkOAMPortEventDetailedStatisticsEntry 17 }

sisgm1040284lrtEthLinkOAMPortEventDetailedStatisticsLocalSymbolPeriodErrors OBJECT-TYPE
   SYNTAX      Counter64
   MAX-ACCESS  read-only
   STATUS      current
   DESCRIPTION
       "This eight-octet field indicates the number of symbol errors in the period."   
   ::= { sisgm1040284lrtEthLinkOAMPortEventDetailedStatisticsEntry 18 }

sisgm1040284lrtEthLinkOAMPortEventDetailedStatisticsLocalSymbolFramePeriodErrors OBJECT-TYPE
   SYNTAX      Counter64
   MAX-ACCESS  read-only
   STATUS      current
   DESCRIPTION
       "This eight-octet field indicates the sum of symbol errors since the OAM sublayer was reset."   
   ::= { sisgm1040284lrtEthLinkOAMPortEventDetailedStatisticsEntry 19 }

sisgm1040284lrtEthLinkOAMPortEventDetailedStatisticsLocalSymbolFramePeriodErrorEvents OBJECT-TYPE
   SYNTAX      Integer32
   MAX-ACCESS  read-only
   STATUS      current
   DESCRIPTION
       "This four-octet field indicates the number of Errored Symbol Period Event TLVs that
	   have been generated since the OAM sublayer was reset."   
   ::= { sisgm1040284lrtEthLinkOAMPortEventDetailedStatisticsEntry 20 }

sisgm1040284lrtEthLinkOAMPortEventDetailedStatisticsLocalEventSecondsSummaryTimeStamp OBJECT-TYPE
   SYNTAX      Integer32
   MAX-ACCESS  read-only
   STATUS      current
   DESCRIPTION
       "This two-octet field indicates the time reference when the event was generated, 
	   in terms of 100 ms intervals, encoded as a 16-bit unsigned integer."   
   ::= { sisgm1040284lrtEthLinkOAMPortEventDetailedStatisticsEntry 21 }

sisgm1040284lrtEthLinkOAMPortEventDetailedStatisticsLocalEventSecondsSummaryWindow OBJECT-TYPE
   SYNTAX      Integer32
   MAX-ACCESS  read-only
   STATUS      current
   DESCRIPTION
       "This two-octet field indicates the duration of the period in terms of 100 ms intervals, encoded as a 16-bit unsigned integer."   
   ::= { sisgm1040284lrtEthLinkOAMPortEventDetailedStatisticsEntry 22 }

sisgm1040284lrtEthLinkOAMPortEventDetailedStatisticsLocalEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."   
   ::= { sisgm1040284lrtEthLinkOAMPortEventDetailedStatisticsEntry 23 }

sisgm1040284lrtEthLinkOAMPortEventDetailedStatisticsLocalEventSecondsSummaryEvents OBJECT-TYPE
   SYNTAX      Integer32
   MAX-ACCESS  read-only
   STATUS      current
   DESCRIPTION
       "This two-octet field indicates the number of errored frame seconds in the period, encoded as a 16-bit unsigned integer."   
   ::= { sisgm1040284lrtEthLinkOAMPortEventDetailedStatisticsEntry 24 }

sisgm1040284lrtEthLinkOAMPortEventDetailedStatisticsLocalEventSecondsSummaryErrorTotal OBJECT-TYPE
   SYNTAX      Integer32
   MAX-ACCESS  read-only
   STATUS      current
   DESCRIPTION
       "This four-octet field indicates the sum of errored frame seconds that have been detected since the OAM sublayer was reset."   
   ::= { sisgm1040284lrtEthLinkOAMPortEventDetailedStatisticsEntry 25 }

sisgm1040284lrtEthLinkOAMPortEventDetailedStatisticsLocalEventSecondsSummaryEventTotal OBJECT-TYPE
   SYNTAX      Integer32
   MAX-ACCESS  read-only
   STATUS      current
   DESCRIPTION
       "This four-octet field indicates the number of Errored Frame Seconds Summary Event TLVs that 
	   have been generated since the OAM sublayer was reset, encoded as a 32bit unsigned integer."   
   ::= { sisgm1040284lrtEthLinkOAMPortEventDetailedStatisticsEntry 26 }

sisgm1040284lrtEthLinkOAMPortEventDetailedStatisticsRemoteFrameErrorEventTimestamp OBJECT-TYPE
   SYNTAX      Integer32
   MAX-ACCESS  read-only
   STATUS      current
   DESCRIPTION
       "This two-octet field indicates the time reference when the event was generated, in terms of 100 ms intervals."   
   ::= { sisgm1040284lrtEthLinkOAMPortEventDetailedStatisticsEntry 27 }
   
sisgm1040284lrtEthLinkOAMPortEventDetailedStatisticsRemoteFrameErrorEventWindow OBJECT-TYPE
   SYNTAX      Integer32
   MAX-ACCESS  read-only
   STATUS      current
   DESCRIPTION
       "This two-octet field indicates the duration of the period in terms of 100 ms intervals. 1) 
	   The default value is one second. 2) The lower bound is one second. 3) 
	   The upper bound is one minute."   
   ::= { sisgm1040284lrtEthLinkOAMPortEventDetailedStatisticsEntry 28 }   
   
sisgm1040284lrtEthLinkOAMPortEventDetailedStatisticsRemoteFrameErrorEventThreshold OBJECT-TYPE
   SYNTAX      Integer32
   MAX-ACCESS  read-only
   STATUS      current
   DESCRIPTION
       "This four-octet field indicates the number of detected errored frames in the period is required
	   to be equal to or greater than in order for the event to be generated. 1) 
	   The default value is one frame error. 2) 
	   The lower bound is zero frame errors. 3) 
	   The upper bound is unspecified."   
   ::= { sisgm1040284lrtEthLinkOAMPortEventDetailedStatisticsEntry 29 }

sisgm1040284lrtEthLinkOAMPortEventDetailedStatisticsRemoteFrameErrors OBJECT-TYPE
   SYNTAX      Integer32
   MAX-ACCESS  read-only
   STATUS      current
   DESCRIPTION
       "This four-octet field indicates the number of detected errored frames in the period."   
   ::= { sisgm1040284lrtEthLinkOAMPortEventDetailedStatisticsEntry 30 }
   
sisgm1040284lrtEthLinkOAMPortEventDetailedStatisticsRemoteTotalFrameErrors OBJECT-TYPE
   SYNTAX      Counter64
   MAX-ACCESS  read-only
   STATUS      current
   DESCRIPTION
       "This eight-octet field indicates the sum of errored frames that have been detected since the OAM sublayer was reset."   
   ::= { sisgm1040284lrtEthLinkOAMPortEventDetailedStatisticsEntry 31 }
   
sisgm1040284lrtEthLinkOAMPortEventDetailedStatisticsRemoteTotalFrameErrorEvents OBJECT-TYPE
   SYNTAX      Integer32
   MAX-ACCESS  read-only
   STATUS      current
   DESCRIPTION
       "This four-octet field indicates the number of Errored Frame Event TLVs that 
	   have been generated since the OAM sublayer was reset."   
   ::= { sisgm1040284lrtEthLinkOAMPortEventDetailedStatisticsEntry 32 }
   
sisgm1040284lrtEthLinkOAMPortEventDetailedStatisticsRemoteFramePeriodErrorEventTimestamp OBJECT-TYPE
   SYNTAX      Integer32
   MAX-ACCESS  read-only
   STATUS      current
   DESCRIPTION
       "This two-octet field indicates the time reference when the event was generated, in terms of 100 ms intervals."   
   ::= { sisgm1040284lrtEthLinkOAMPortEventDetailedStatisticsEntry 33 }
   
sisgm1040284lrtEthLinkOAMPortEventDetailedStatisticsRemoteFramePeriodErrorEventWindow OBJECT-TYPE
   SYNTAX      Integer32
   MAX-ACCESS  read-only
   STATUS      current
   DESCRIPTION
       "This four-octet field indicates the duration of period in terms of frames."   
   ::= { sisgm1040284lrtEthLinkOAMPortEventDetailedStatisticsEntry 34 }
   
sisgm1040284lrtEthLinkOAMPortEventDetailedStatisticsRemoteFramePeriodErrorEventThreshold OBJECT-TYPE
   SYNTAX      Integer32
   MAX-ACCESS  read-only
   STATUS      current
   DESCRIPTION
       "This four-octet field indicates the number of errored frames in the period is required
	   to be equal to or greater than in order for the event to be generated."   
   ::= { sisgm1040284lrtEthLinkOAMPortEventDetailedStatisticsEntry 35 }
   
sisgm1040284lrtEthLinkOAMPortEventDetailedStatisticsRemoteFramePeriodErrors OBJECT-TYPE
   SYNTAX      Integer32
   MAX-ACCESS  read-only
   STATUS      current
   DESCRIPTION
       "This four-octet field indicates the number of frame errors in the period."   
   ::= { sisgm1040284lrtEthLinkOAMPortEventDetailedStatisticsEntry 36 }
   
sisgm1040284lrtEthLinkOAMPortEventDetailedStatisticsRemoteTotalFramePeriodErrors OBJECT-TYPE
   SYNTAX      Counter64
   MAX-ACCESS  read-only
   STATUS      current
   DESCRIPTION
       "This eight-octet field indicates the sum of frame errors that have been detected since the OAM sublayer was reset."   
   ::= { sisgm1040284lrtEthLinkOAMPortEventDetailedStatisticsEntry 37 }
   
sisgm1040284lrtEthLinkOAMPortEventDetailedStatisticsRemoteTotalFramePeriodErrorEvents OBJECT-TYPE
   SYNTAX      Integer32
   MAX-ACCESS  read-only
   STATUS      current
   DESCRIPTION
       "This four-octet field indicates the number of Errored Frame Period Event TLVs 
	   that have been generated since the OAM sublayer was reset."   
   ::= { sisgm1040284lrtEthLinkOAMPortEventDetailedStatisticsEntry 38 }
   
sisgm1040284lrtEthLinkOAMPortEventDetailedStatisticsRemoteSymbolPeriodErrorEventTimestamp OBJECT-TYPE
   SYNTAX      Integer32
   MAX-ACCESS  read-only
   STATUS      current
   DESCRIPTION
       "This two-octet field indicates the time reference when the event was generated, in terms of 100 ms intervals."   
   ::= { sisgm1040284lrtEthLinkOAMPortEventDetailedStatisticsEntry 39 }
   
sisgm1040284lrtEthLinkOAMPortEventDetailedStatisticsRemoteSymbolPeriodErrorEventWindow OBJECT-TYPE
   SYNTAX      Counter64
   MAX-ACCESS  read-only
   STATUS      current
   DESCRIPTION
       "This eight-octet field indicates the number of symbols in the period."   
   ::= { sisgm1040284lrtEthLinkOAMPortEventDetailedStatisticsEntry 40 }
   
sisgm1040284lrtEthLinkOAMPortEventDetailedStatisticsRemoteSymbolPeriodErrorEventThreshold OBJECT-TYPE
   SYNTAX      Counter64
   MAX-ACCESS  read-only
   STATUS      current
   DESCRIPTION
       "This eight-octet field indicates the number of errored symbols in the period is required to
	   be equal to or greater than in order for the event to be generated."   
   ::= { sisgm1040284lrtEthLinkOAMPortEventDetailedStatisticsEntry 41 }
   
sisgm1040284lrtEthLinkOAMPortEventDetailedStatisticsRemoteSymbolPeriodErrors OBJECT-TYPE
   SYNTAX      Counter64
   MAX-ACCESS  read-only
   STATUS      current
   DESCRIPTION
       "This eight-octet field indicates the number of symbol errors in the period."   
   ::= { sisgm1040284lrtEthLinkOAMPortEventDetailedStatisticsEntry 42 }
   
sisgm1040284lrtEthLinkOAMPortEventDetailedStatisticsRemoteSymbolFramePeriodErrors OBJECT-TYPE
   SYNTAX      Counter64
   MAX-ACCESS  read-only
   STATUS      current
   DESCRIPTION
       "This eight-octet field indicates the sum of symbol errors since the OAM sublayer was reset."   
   ::= { sisgm1040284lrtEthLinkOAMPortEventDetailedStatisticsEntry 43 }
   
sisgm1040284lrtEthLinkOAMPortEventDetailedStatisticsRemoteSymbolFramePeriodErrorEvents OBJECT-TYPE
   SYNTAX      Integer32
   MAX-ACCESS  read-only
   STATUS      current
   DESCRIPTION
       "This four-octet field indicates the number of Errored Symbol Period Event TLVs that
	   have been generated since the OAM sublayer was reset."   
   ::= { sisgm1040284lrtEthLinkOAMPortEventDetailedStatisticsEntry 44 }
   
sisgm1040284lrtEthLinkOAMPortEventDetailedStatisticsRemoteEventSecondsSummaryTimeStamp OBJECT-TYPE
   SYNTAX      Integer32
   MAX-ACCESS  read-only
   STATUS      current
   DESCRIPTION
       "This two-octet field indicates the time reference when the event was generated, 
	   in terms of 100 ms intervals, encoded as a 16-bit unsigned integer."   
   ::= { sisgm1040284lrtEthLinkOAMPortEventDetailedStatisticsEntry 45 }
   
sisgm1040284lrtEthLinkOAMPortEventDetailedStatisticsRemoteEventSecondsSummaryWindow OBJECT-TYPE
   SYNTAX      Integer32
   MAX-ACCESS  read-only
   STATUS      current
   DESCRIPTION
       "This two-octet field indicates the duration of the period in terms of 100 ms intervals, encoded as a 16-bit unsigned integer."   
   ::= { sisgm1040284lrtEthLinkOAMPortEventDetailedStatisticsEntry 46 }
   
sisgm1040284lrtEthLinkOAMPortEventDetailedStatisticsRemoteEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."   
   ::= { sisgm1040284lrtEthLinkOAMPortEventDetailedStatisticsEntry 47 }
   
sisgm1040284lrtEthLinkOAMPortEventDetailedStatisticsRemoteEventSecondsSummaryEvents OBJECT-TYPE
   SYNTAX      Integer32
   MAX-ACCESS  read-only
   STATUS      current
   DESCRIPTION
       "This two-octet field indicates the number of errored frame seconds in the period, encoded as a 16-bit unsigned integer."   
   ::= { sisgm1040284lrtEthLinkOAMPortEventDetailedStatisticsEntry 48 }
   
sisgm1040284lrtEthLinkOAMPortEventDetailedStatisticsRemoteEventSecondsSummaryErrorTotal OBJECT-TYPE
   SYNTAX      Integer32
   MAX-ACCESS  read-only
   STATUS      current
   DESCRIPTION
       "This four-octet field indicates the sum of errored frame seconds that have been detected since the OAM sublayer was reset."   
   ::= { sisgm1040284lrtEthLinkOAMPortEventDetailedStatisticsEntry 49 }
   
sisgm1040284lrtEthLinkOAMPortEventDetailedStatisticsRemoteEventSecondsSummaryEventTotal OBJECT-TYPE
   SYNTAX      Integer32
   MAX-ACCESS  read-only
   STATUS      current
   DESCRIPTION
       "This four-octet field indicates the number of Errored Frame Seconds Summary Event TLVs that 
	   have been generated since the OAM sublayer was reset, encoded as a 32bit unsigned integer."   
   ::= { sisgm1040284lrtEthLinkOAMPortEventDetailedStatisticsEntry 50 }
   
   
   
sisgm1040284lrtEVC    OBJECT IDENTIFIER ::= { sisgm1040284lrtConfiguration 30 } 

sisgm1040284lrtEVCPortConfTable OBJECT-TYPE
   SYNTAX      SEQUENCE OF SISGM1040284LRTEVCPortConfEntry
   MAX-ACCESS  not-accessible
   STATUS      current
   DESCRIPTION
       " "
   ::= { sisgm1040284lrtEVC 1 }

sisgm1040284lrtEVCPortConfEntry OBJECT-TYPE
   SYNTAX      SISGM1040284LRTEVCPortConfEntry
   MAX-ACCESS  not-accessible
   STATUS      current
   DESCRIPTION
       " "
   INDEX    { sisgm1040284lrtEVCPortConfIndex  }
   ::= { sisgm1040284lrtEVCPortConfTable 1 }

SISGM1040284LRTEVCPortConfEntry ::= SEQUENCE {
   sisgm1040284lrtEVCPortConfIndex           Integer32,
   sisgm1040284lrtEVCPortConfDEIMode         Integer32,
   sisgm1040284lrtEVCPortConfTagMode         Integer32,
   sisgm1040284lrtEVCPortConfAddressMode     Integer32
}

sisgm1040284lrtEVCPortConfIndex OBJECT-TYPE
   SYNTAX      Integer32
   MAX-ACCESS  not-accessible
   STATUS      current
   DESCRIPTION
       "Index"
   ::= { sisgm1040284lrtEVCPortConfEntry 1 }

sisgm1040284lrtEVCPortConfDEIMode OBJECT-TYPE
   SYNTAX      Integer32
   MAX-ACCESS  read-write
   STATUS      current
   DESCRIPTION
       "The DEI mode for an NNI port determines whether frames transmitted on the port 
	   will have the DEI field in the outer tag marked based on the colour of the frame. 
	   The allowed values are: 
	   0:Fixed: The DEI value is determined by ECE rules.
       1:Coloured: The DEI is 1 for yellow frames and 0 for green frames. 
       "
   ::= { sisgm1040284lrtEVCPortConfEntry 2 }

sisgm1040284lrtEVCPortConfTagMode OBJECT-TYPE
   SYNTAX      Integer32
   MAX-ACCESS  read-write
   STATUS      current
   DESCRIPTION
       "The tag mode specifying whether the EVC classification must be based on the outer or inner tag. 
	   This can be used on NNI ports connected to another service provider, 
	   where an outer tunnel tag is added together with the inner tag identifying the EVC. 
	   The allowed values are: 
		0:Inner: Enable inner tag in EVC classification. 
		1:Outer: Enable outer tag in EVC classification."
   ::= { sisgm1040284lrtEVCPortConfEntry 3 }
   
sisgm1040284lrtEVCPortConfAddressMode OBJECT-TYPE
   SYNTAX      Integer32
   MAX-ACCESS  read-write
   STATUS      current
   DESCRIPTION
       "The IP/MAC address mode specifying whether the EVC classification must be based on source (SMAC/SIP) or 
	   destination (DMAC/DIP) addresses. 
	   The allowed values are: 
	   0:Source: Enable SMAC/SIP matching. 
	   1:Destination: Enable DMAC/DIP matching."
   ::= { sisgm1040284lrtEVCPortConfEntry 4 }

   
   
sisgm1040284lrtEVCBandwidthProfilesConfTable OBJECT-TYPE
   SYNTAX      SEQUENCE OF SISGM1040284LRTEVCBandwidthProfilesConfEntry
   MAX-ACCESS  not-accessible
   STATUS      current
   DESCRIPTION
       " "
   ::= { sisgm1040284lrtEVC 2 }

sisgm1040284lrtEVCBandwidthProfilesConfEntry OBJECT-TYPE
   SYNTAX      SISGM1040284LRTEVCBandwidthProfilesConfEntry
   MAX-ACCESS  not-accessible
   STATUS      current
   DESCRIPTION
       " "
   INDEX    { sisgm1040284lrtEVCBandwidthProfilesConfIndex  }
   ::= { sisgm1040284lrtEVCBandwidthProfilesConfTable 1 }

SISGM1040284LRTEVCBandwidthProfilesConfEntry ::= SEQUENCE {
   sisgm1040284lrtEVCBandwidthProfilesConfIndex           Integer32,
   sisgm1040284lrtEVCBandwidthProfilesConfState           Integer32,
   sisgm1040284lrtEVCBandwidthProfilesConfType            Integer32,
   sisgm1040284lrtEVCBandwidthProfilesConfPolicerMode     Integer32,
   sisgm1040284lrtEVCBandwidthProfilesConfRateType        Integer32,
   sisgm1040284lrtEVCBandwidthProfilesConfCIRkbps         Integer32,
   sisgm1040284lrtEVCBandwidthProfilesConfCBSbytes        Integer32,
   sisgm1040284lrtEVCBandwidthProfilesConfEIRkbps         Integer32,  
   sisgm1040284lrtEVCBandwidthProfilesConfEBSbytes        Integer32   
}

sisgm1040284lrtEVCBandwidthProfilesConfIndex OBJECT-TYPE
   SYNTAX      Integer32
   MAX-ACCESS  not-accessible
   STATUS      current
   DESCRIPTION
       "Index"
   ::= { sisgm1040284lrtEVCBandwidthProfilesConfEntry 1 }

sisgm1040284lrtEVCBandwidthProfilesConfState OBJECT-TYPE
   SYNTAX      Integer32
   MAX-ACCESS  read-write
   STATUS      current
   DESCRIPTION
       "The administrative state of the bandwidth profile. The allowed values are: 
		1:Enabled: The bandwidth profile enabled. 
		0:Disabled: The bandwidth profile is disabled.
       "
   ::= { sisgm1040284lrtEVCBandwidthProfilesConfEntry 2 }

sisgm1040284lrtEVCBandwidthProfilesConfType OBJECT-TYPE
   SYNTAX      Integer32
   MAX-ACCESS  read-write
   STATUS      current
   DESCRIPTION
       "The policer type of the bandwidth profile. The allowed values are: 
		0:MEF: MEF ingress bandwidth profile. 
		1:Single: Single bucket policer."
   ::= { sisgm1040284lrtEVCBandwidthProfilesConfEntry 3 }
   
sisgm1040284lrtEVCBandwidthProfilesConfPolicerMode OBJECT-TYPE
   SYNTAX      Integer32
   MAX-ACCESS  read-write
   STATUS      current
   DESCRIPTION
       "The colour mode of the bandwidth profile. The allowed values are: 
		0:Coupled: Colour-aware mode with coupling enabled. 
		1:Aware: Colour-aware mode with coupling disabled."
   ::= { sisgm1040284lrtEVCBandwidthProfilesConfEntry 4 }
   
sisgm1040284lrtEVCBandwidthProfilesConfRateType OBJECT-TYPE
   SYNTAX      Integer32
   MAX-ACCESS  read-write
   STATUS      current
   DESCRIPTION
       "The rate type of the bandwidth profile. The allowed values are: 
		0:Data: Specify that this bandwidth profile operates on data rate. 
		1:Line: Specify that this bandwidth profile operates on line rate."
   ::= { sisgm1040284lrtEVCBandwidthProfilesConfEntry 5 }

sisgm1040284lrtEVCBandwidthProfilesConfCIRkbps OBJECT-TYPE
   SYNTAX      Integer32
   MAX-ACCESS  read-write
   STATUS      current
   DESCRIPTION
       "The Committed Information Rate of the bandwidth profile. 
	   The allowed range is from 0 through 10000000 kilobit per second."
   ::= { sisgm1040284lrtEVCBandwidthProfilesConfEntry 6 }

sisgm1040284lrtEVCBandwidthProfilesConfCBSbytes OBJECT-TYPE
   SYNTAX      Integer32
   MAX-ACCESS  read-write
   STATUS      current
   DESCRIPTION
       "The Committed Burst Size of the bandwidth profile. 
	   The allowed range is from 0 through 100000 bytes."
   ::= { sisgm1040284lrtEVCBandwidthProfilesConfEntry 7 }

sisgm1040284lrtEVCBandwidthProfilesConfEIRkbps OBJECT-TYPE
   SYNTAX      Integer32
   MAX-ACCESS  read-write
   STATUS      current
   DESCRIPTION
       "The Excess Information Rate for MEF type bandwidth profile. 
	   The allowed range is from 0 through 10000000 kilobit per second."
   ::= { sisgm1040284lrtEVCBandwidthProfilesConfEntry 8 }

sisgm1040284lrtEVCBandwidthProfilesConfEBSbytes OBJECT-TYPE
   SYNTAX      Integer32
   MAX-ACCESS  read-write
   STATUS      current
   DESCRIPTION
       "The Excess Burst Size for MEF type bandwidth profile. 
	   The allowed range is from 0 through 100000 bytes."
   ::= { sisgm1040284lrtEVCBandwidthProfilesConfEntry 9 }   


   
sisgm1040284lrtEVCControlListConfTable  OBJECT-TYPE
   SYNTAX      SEQUENCE OF SISGM1040284LRTEVCControlListConfEntry
   MAX-ACCESS  not-accessible
   STATUS      current
   DESCRIPTION
       "A table of EVC Control List Conf."
   ::= { sisgm1040284lrtEVC 3 }

sisgm1040284lrtEVCControlListConfEntry OBJECT-TYPE
    SYNTAX        SISGM1040284LRTEVCControlListConfEntry
    MAX-ACCESS    not-accessible
    STATUS        current
    DESCRIPTION
        "An entry of EVC Control List Conf table."
    INDEX        { sisgm1040284lrtEVCControlListConfIndex }
    ::= { sisgm1040284lrtEVCControlListConfTable 1 }

SISGM1040284LRTEVCControlListConfEntry ::=
    SEQUENCE {
        sisgm1040284lrtEVCControlListConfIndex                       Integer32,
        sisgm1040284lrtEVCControlListConfEVCID                       Integer32,
        sisgm1040284lrtEVCControlListConfVID                         Integer32,
        sisgm1040284lrtEVCControlListConfIVID                        Integer32,
        sisgm1040284lrtEVCControlListConfLearning                    Integer32,
        sisgm1040284lrtEVCControlListConfPolicerIDFilter             Integer32,
        sisgm1040284lrtEVCControlListConfPolicerID                   Integer32,
        sisgm1040284lrtEVCControlListConfInnerTagType                Integer32,
        sisgm1040284lrtEVCControlListConfInnerTagVIDMode             Integer32,
        sisgm1040284lrtEVCControlListConfInnerTagVLANID              Integer32,
        sisgm1040284lrtEVCControlListConfInnerTagPCPDEIPreservation  Integer32,
        sisgm1040284lrtEVCControlListConfInnerTagPCP                 Integer32,
        sisgm1040284lrtEVCControlListConfInnerTagDEI                 Integer32,        
		sisgm1040284lrtEVCControlListConfOuterTagVLANID              Integer32,
        sisgm1040284lrtEVCControlListConfNNIPorts                    DisplayString,
		sisgm1040284lrtEVCControlListConfLeafVID                     Integer32,
        sisgm1040284lrtEVCControlListConfLeafIVID                    Integer32,
		sisgm1040284lrtEVCControlListConfLeafPorts                   DisplayString,
        sisgm1040284lrtEVCControlListConfRowStatus                   RowStatus
    }

sisgm1040284lrtEVCControlListConfIndex OBJECT-TYPE
   SYNTAX      Integer32
   MAX-ACCESS  not-accessible
   STATUS      current
   DESCRIPTION
       "index"
   ::= {sisgm1040284lrtEVCControlListConfEntry 1 }

sisgm1040284lrtEVCControlListConfEVCID OBJECT-TYPE
   SYNTAX      Integer32
   MAX-ACCESS  read-create
   STATUS      current
   DESCRIPTION
       "The EVC ID identifies the EVC. The allowed range is from 1 through 256."
   ::= {sisgm1040284lrtEVCControlListConfEntry 2 }

sisgm1040284lrtEVCControlListConfVID OBJECT-TYPE
   SYNTAX      Integer32
   MAX-ACCESS  read-create
   STATUS      current
   DESCRIPTION
       "The VLAN ID in the PB network. It may be inserted in a C-tag, S-tag or S-custom tag 
	   depending on the NNI port VLAN configuration. 
	   The allowed range is from 1 through 4095."
   ::= {sisgm1040284lrtEVCControlListConfEntry 3 }
   
sisgm1040284lrtEVCControlListConfIVID OBJECT-TYPE
   SYNTAX      Integer32
   MAX-ACCESS  read-create
   STATUS      current
   DESCRIPTION
       "The Internal/classified VLAN ID in the PB network. 
	   The allowed range is from 1 through 4095."
   ::= {sisgm1040284lrtEVCControlListConfEntry 4 }
   
sisgm1040284lrtEVCControlListConfLearning OBJECT-TYPE
   SYNTAX      Integer32
   MAX-ACCESS  read-create
   STATUS      current
   DESCRIPTION
       "The learning mode for the EVC controls whether source MAC addresses are learned for frames matching the EVC. 
	   Learning may be disabled if the EVC only includes two UNI/NNI ports. The possible values are: 
		1:Enabled: Learning is enabled (MAC addresses are learned). 
		0:Disabled: Learning is disabled (MAC addresses are not learned)."
   ::= {sisgm1040284lrtEVCControlListConfEntry 5 }
   
sisgm1040284lrtEVCControlListConfPolicerIDFilter OBJECT-TYPE
   SYNTAX      Integer32
   MAX-ACCESS  read-create
   STATUS      current
   DESCRIPTION
       "The ingress bandwidth profile mode for the EVC. The possible values are:
	   0:Specific.
	   1:Discard: All received frames are discarded for the EVC.
	   2:None: None bandwidth profile for the EVC.
	   "
   ::= {sisgm1040284lrtEVCControlListConfEntry 6 }   
   
sisgm1040284lrtEVCControlListConfPolicerID OBJECT-TYPE
   SYNTAX      Integer32
   MAX-ACCESS  read-create
   STATUS      current
   DESCRIPTION
       "The ingress bandwidth profile ID for the EVC."
   ::= {sisgm1040284lrtEVCControlListConfEntry 7 }    
   
sisgm1040284lrtEVCControlListConfInnerTagType OBJECT-TYPE
   SYNTAX      Integer32
   MAX-ACCESS  read-create
   STATUS      current
   DESCRIPTION
       "The inner tag type is used to determine whether an inner tag is inserted in frames forwarded to NNI ports. The possible values are: 
		0:None: An inner tag is not inserted. 
		1:C-tag: An inner C-tag is inserted. 
		2:S-tag: An inner S-tag is inserted. 
		3:S-custom-tag: An inner tag is inserted and the tag type is determined by the VLAN port configuration of the NNI."
   ::= {sisgm1040284lrtEVCControlListConfEntry 8 }     
   
sisgm1040284lrtEVCControlListConfInnerTagVIDMode OBJECT-TYPE
   SYNTAX      Integer32
   MAX-ACCESS  read-create
   STATUS      current
   DESCRIPTION
       "The inner VID Mode affects the VID in the inner and outer tag. 
	   The possible values are: 
		0:Normal: The VID of the two outer tags aren't swapped. 
		1:Tunnel: The VID of the two outer tags are swapped, 
		so that the VID of the outer tag is taken from the Inner Tag configuration and the VID of the inner tag is the EVC VID. 
		In this mode, the NNI ports are normally configured to do EVC classification based on the inner tag."
   ::= {sisgm1040284lrtEVCControlListConfEntry 9 }   

sisgm1040284lrtEVCControlListConfInnerTagVLANID OBJECT-TYPE
   SYNTAX      Integer32
   MAX-ACCESS  read-create
   STATUS      current
   DESCRIPTION
       "The Inner tag VLAN ID. The allowed range is from 1 through 4095."
   ::= {sisgm1040284lrtEVCControlListConfEntry 10 }    

 sisgm1040284lrtEVCControlListConfInnerTagPCPDEIPreservation OBJECT-TYPE
   SYNTAX      Integer32
   MAX-ACCESS  read-create
   STATUS      current
   DESCRIPTION
       "The inner tag PCP and DEI preservation. The possible values are: 
		1:Preserved: The inner tag PCP and DEI is preserved. 
		0:Fixed: The inner tag PCP and DEI is fixed."
   ::= {sisgm1040284lrtEVCControlListConfEntry 11 }  
   
sisgm1040284lrtEVCControlListConfInnerTagPCP OBJECT-TYPE
   SYNTAX      Integer32
   MAX-ACCESS  read-create
   STATUS      current
   DESCRIPTION
       "The inner tag PCP value. The allowed range is from 0 through 7."
   ::= {sisgm1040284lrtEVCControlListConfEntry 12 }     
   
sisgm1040284lrtEVCControlListConfInnerTagDEI OBJECT-TYPE
   SYNTAX      Integer32
   MAX-ACCESS  read-create
   STATUS      current
   DESCRIPTION
       "The inner tag DEI value. The allowed value is 0 or 1."
   ::= {sisgm1040284lrtEVCControlListConfEntry 13 }     

sisgm1040284lrtEVCControlListConfOuterTagVLANID OBJECT-TYPE
   SYNTAX      Integer32
   MAX-ACCESS  read-create
   STATUS      current
   DESCRIPTION
       "The EVC outer tag VID for UNI ports. The allowed range is from 1 through 4095."
   ::= {sisgm1040284lrtEVCControlListConfEntry 14 }    

sisgm1040284lrtEVCControlListConfNNIPorts OBJECT-TYPE
   SYNTAX      DisplayString
   MAX-ACCESS  read-create
   STATUS      current
   DESCRIPTION
       "The list of Network to Network Interfaces for the EVC."
   ::= {sisgm1040284lrtEVCControlListConfEntry 15 }     
   
sisgm1040284lrtEVCControlListConfLeafVID OBJECT-TYPE
   SYNTAX      Integer32
   MAX-ACCESS  read-create
   STATUS      current
   DESCRIPTION
       " The leaf VLAN ID used in the outer tag for the EVC. range:1-4095"
   ::= {sisgm1040284lrtEVCControlListConfEntry 16 }  

sisgm1040284lrtEVCControlListConfLeafIVID OBJECT-TYPE
   SYNTAX      Integer32
   MAX-ACCESS  read-create
   STATUS      current
   DESCRIPTION
       "The leaf internal classified VLAN ID for the EVC. range:1-4095"
   ::= {sisgm1040284lrtEVCControlListConfEntry 17 }      
   
sisgm1040284lrtEVCControlListConfLeafPorts OBJECT-TYPE
   SYNTAX      DisplayString
   MAX-ACCESS  read-create
   STATUS      current
   DESCRIPTION
       " The list of leaf ports for the EVC."
   ::= {sisgm1040284lrtEVCControlListConfEntry 18 }    

sisgm1040284lrtEVCControlListConfRowStatus OBJECT-TYPE
   SYNTAX      RowStatus
   MAX-ACCESS  read-create
   STATUS      current
   DESCRIPTION
       "EVC Control List Conf Row Status."
   ::= {sisgm1040284lrtEVCControlListConfEntry 19 }

   
   
sisgm1040284lrtECEControlListConfTable  OBJECT-TYPE
   SYNTAX      SEQUENCE OF SISGM1040284LRTECEControlListConfEntry
   MAX-ACCESS  not-accessible
   STATUS      current
   DESCRIPTION
       "A table of ECE Control List Conf."
   ::= { sisgm1040284lrtEVC 4 }

sisgm1040284lrtECEControlListConfEntry OBJECT-TYPE
    SYNTAX        SISGM1040284LRTECEControlListConfEntry
    MAX-ACCESS    not-accessible
    STATUS        current
    DESCRIPTION
        "An entry of ECE Control List Conf table."
    INDEX        { sisgm1040284lrtECEControlListConfIndex }
    ::= { sisgm1040284lrtECEControlListConfTable 1 }

SISGM1040284LRTECEControlListConfEntry ::=
    SEQUENCE {
        sisgm1040284lrtECEControlListConfIndex                               Integer32,
        sisgm1040284lrtECEControlListConfECEID                               Integer32,
        sisgm1040284lrtECEControlListConfUNIPorts                            DisplayString,
        sisgm1040284lrtECEControlListConfIngressMatchingTagType              Integer32,
        sisgm1040284lrtECEControlListConfIngressMatchingVLANIDFilter         Integer32,
        sisgm1040284lrtECEControlListConfIngressMatchingVLANIDRangeLow       Integer32,
        sisgm1040284lrtECEControlListConfIngressMatchingVLANIDRangeHigh      Integer32,
        sisgm1040284lrtECEControlListConfIngressMatchingPCP                  Integer32,
        sisgm1040284lrtECEControlListConfIngressMatchingDEI                  Integer32,
        sisgm1040284lrtECEControlListConfIngressMatchingFrameType            Integer32,
        sisgm1040284lrtECEControlListConfActionsDirection                    Integer32,
        sisgm1040284lrtECEControlListConfActionsEVCIDFilter                  Integer32,
        sisgm1040284lrtECEControlListConfActionsEVCIDValue                   Integer32,        
		sisgm1040284lrtECEControlListConfActionsTagPopCount                  Integer32,
        sisgm1040284lrtECEControlListConfActionsPolicyID                     Integer32,
		sisgm1040284lrtECEControlListConfActionsClass                        Integer32,
        sisgm1040284lrtECEControlListConfMACParametersDMACType               Integer32,
		sisgm1040284lrtECEControlListConfMACParametersSMACFilter             Integer32,
		sisgm1040284lrtECEControlListConfMACParametersSMACValue              DisplayString,
		sisgm1040284lrtECEControlListConfIPv4Protocol                        Integer32,
		sisgm1040284lrtECEControlListConfIPv4ProtocolValue                   Integer32,
		sisgm1040284lrtECEControlListConfIPv4SIPDIPFilter                    Integer32,
		sisgm1040284lrtECEControlListConfIPv4SIPDIPAddress                   IpAddress,
		sisgm1040284lrtECEControlListConfIPv4SIPDIPMask                      IpAddress,
		sisgm1040284lrtECEControlListConfIPv4DSCPFilter                      Integer32,
		sisgm1040284lrtECEControlListConfIPv4DSCPRangeLow                    Integer32,
		sisgm1040284lrtECEControlListConfIPv4DSCPRangeHigh                   Integer32,
		sisgm1040284lrtECEControlListConfIPv4Fragment                        Integer32,
		sisgm1040284lrtECEControlListConfIPv4SourcePortFilter                Integer32,
		sisgm1040284lrtECEControlListConfIPv4SourceRangeLow                  Integer32,
		sisgm1040284lrtECEControlListConfIPv4SourceRangeHigh                 Integer32,
		sisgm1040284lrtECEControlListConfIPv4DestPortFilter                  Integer32,
		sisgm1040284lrtECEControlListConfIPv4DestRangeLow                    Integer32,
		sisgm1040284lrtECEControlListConfIPv4DestRangeHigh                   Integer32,
		sisgm1040284lrtECEControlListConfIPv6Protocol                        Integer32,
		sisgm1040284lrtECEControlListConfIPv6ProtocolValue                   Integer32,
		sisgm1040284lrtECEControlListConfIPv6SIPDIPFilter                    Integer32,
		sisgm1040284lrtECEControlListConfIPv6SIPDIPAddress                   IpAddress,
		sisgm1040284lrtECEControlListConfIPv6SIPDIPMask                      IpAddress,
		sisgm1040284lrtECEControlListConfIPv6DSCPFilter                      Integer32,
		sisgm1040284lrtECEControlListConfIPv6DSCPRangeLow                    Integer32,
		sisgm1040284lrtECEControlListConfIPv6DSCPRangeHigh                   Integer32,
		sisgm1040284lrtECEControlListConfIPv6SourcePortFilter                Integer32,
		sisgm1040284lrtECEControlListConfIPv6SourceRangeLow                  Integer32,
		sisgm1040284lrtECEControlListConfIPv6SourceRangeHigh                 Integer32,
		sisgm1040284lrtECEControlListConfIPv6DestPortFilter                  Integer32,
		sisgm1040284lrtECEControlListConfIPv6DestRangeLow                    Integer32,
		sisgm1040284lrtECEControlListConfIPv6DestRangeHigh                   Integer32,
		sisgm1040284lrtECEControlListConfEgressOuterTagMode                  Integer32,
		sisgm1040284lrtECEControlListConfEgressOuterTagPCPDEIPreservation    Integer32,
		sisgm1040284lrtECEControlListConfEgressOuterTagPCP                   Integer32,
		sisgm1040284lrtECEControlListConfEgressOuterTagDEI                   Integer32,
		sisgm1040284lrtECEControlListConfConflict                            Integer32,
        sisgm1040284lrtECEControlListConfRowStatus                           RowStatus
    }

sisgm1040284lrtECEControlListConfIndex OBJECT-TYPE
   SYNTAX      Integer32
   MAX-ACCESS  not-accessible
   STATUS      current
   DESCRIPTION
       "index"
   ::= {sisgm1040284lrtECEControlListConfEntry 1 }

sisgm1040284lrtECEControlListConfECEID OBJECT-TYPE
   SYNTAX      Integer32
   MAX-ACCESS  read-create
   STATUS      current
   DESCRIPTION
       "The ECE ID identifies the ECE. Unique ECE IDs are automatically assigned to ECEs added. 
	   The possible range is from 1 through 256."
   ::= {sisgm1040284lrtECEControlListConfEntry 2 }  
   
sisgm1040284lrtECEControlListConfUNIPorts OBJECT-TYPE
   SYNTAX      DisplayString
   MAX-ACCESS  read-create
   STATUS      current
   DESCRIPTION
       "The list of User Network Interfaces for the ECE. Ex:1,2 1-5"
   ::= {sisgm1040284lrtECEControlListConfEntry 3 }  

sisgm1040284lrtECEControlListConfIngressMatchingTagType OBJECT-TYPE
   SYNTAX      Integer32
   MAX-ACCESS  read-create
   STATUS      current
   DESCRIPTION
       "The tag type for the ECE. The possible values are: 
		0:Any: The ECE will match both tagged and untagged frames. 
		1:Untagged: The ECE will match untagged frames only. 
		2:C-Tagged: The ECE will match custom tagged frames only. 
		3:S-Tagged: The ECE will match service tagged frames only. 
		4:Tagged: The ECE will match tagged frames only."
   ::= {sisgm1040284lrtECEControlListConfEntry 4 }  

sisgm1040284lrtECEControlListConfIngressMatchingVLANIDFilter OBJECT-TYPE
   SYNTAX      Integer32
   MAX-ACCESS  read-create
   STATUS      current
   DESCRIPTION
       "The VLAN ID filter for matching the ECE. It only significant if tag type 'Tagged' is selected. The possible values are: 
		0:Any: No VLAN ID filter is specified. (VLAN ID filter status is don't-care.) 
		1:Specific: If you want to filter a specific VLAN ID value with this ECE, choose this value. A field for entering a specific value appears. 
		2:Range: If you want to filter a specific VLAN ID range filter with this ECE, choose this value. A field for entering a range appears."
   ::= {sisgm1040284lrtECEControlListConfEntry 5 }  
   
sisgm1040284lrtECEControlListConfIngressMatchingVLANIDRangeLow OBJECT-TYPE
   SYNTAX      Integer32
   MAX-ACCESS  read-create
   STATUS      current
   DESCRIPTION
       "When Specific is selected for the VLAN ID filter, you can enter a specific value. 
	   The allowed value is from 0 through 4095."
   ::= {sisgm1040284lrtECEControlListConfEntry 6 }     
   
sisgm1040284lrtECEControlListConfIngressMatchingVLANIDRangeHigh OBJECT-TYPE
   SYNTAX      Integer32
   MAX-ACCESS  read-create
   STATUS      current
   DESCRIPTION
       "When Specific is selected for the VLAN ID filter, you can enter a specific value. 
	   The allowed value is from 0 through 4095."
   ::= {sisgm1040284lrtECEControlListConfEntry 7 }     
   
sisgm1040284lrtECEControlListConfIngressMatchingPCP OBJECT-TYPE
   SYNTAX      Integer32
   MAX-ACCESS  read-create
   STATUS      current
   DESCRIPTION
       "The PCP value for matching the ECE. It only significant if tag type 'Tagged' is selected. The possible values are: 
        14:Any: The ECE will match any PCP value. 
		0-7:Specific: The ECE will match a specific PCP in the range 0 through 7. 
		8-13:Range: The ECE will match PCP values in the selected range 0-1, 2-3, 4-5, 6-7, 0-3 or 4-7."
   ::= {sisgm1040284lrtECEControlListConfEntry 8 }    
   
sisgm1040284lrtECEControlListConfIngressMatchingDEI OBJECT-TYPE
   SYNTAX      Integer32
   MAX-ACCESS  read-create
   STATUS      current
   DESCRIPTION
       "The DEI value for matching the ECE. It only significant if tag type 'Tagged' is selected. 
	   The allowed value is: 
	   0:Any
	   1:0
	   2:1"
   ::= {sisgm1040284lrtECEControlListConfEntry 9 }    
   
sisgm1040284lrtECEControlListConfIngressMatchingFrameType OBJECT-TYPE
   SYNTAX      Integer32
   MAX-ACCESS  read-create
   STATUS      current
   DESCRIPTION
       "The frame type for the ECE. The possible values are: 
		0:Any: The ECE will match any frame type. 
		1:IPv4: The ECE will match IPv4 frames only. 
		2:IPv6: The ECE will match IPv6 frames only."
   ::= {sisgm1040284lrtECEControlListConfEntry 16 }  
   
sisgm1040284lrtECEControlListConfActionsDirection OBJECT-TYPE
   SYNTAX      Integer32
   MAX-ACCESS  read-create
   STATUS      current
   DESCRIPTION
       "The EVCs and ECEs are used to setup flows in one or both directions as determined by the ECE Direction parameter. 
	   If the ECE is bidirectional, the ingress rules of the NNI ports will be setup to match the traffic being forwarded to NNI ports. 
	   The possible values are: 
		0:Both: Bidirectional. 
		1:UNI-to-NNI: Unidirectional from UNI to NNI. 
		2:NNI-to-UNI: Unidirectional from NNI to UNI."
   ::= {sisgm1040284lrtECEControlListConfEntry 17 }  
   
sisgm1040284lrtECEControlListConfActionsEVCIDFilter OBJECT-TYPE
   SYNTAX      Integer32
   MAX-ACCESS  read-create
   STATUS      current
   DESCRIPTION
       "The EVC ID for the ECE. 
	   The ECE is only active when mapping to an existing EVC. 
	   The possible values are: 
		0:None: No EVC ID filter is specified. (EVC ID filter status is don't-care.) 
		1:Specific: If you want to filter a specific EVC ID with this ECE, choose this value. A field for entering a specific value appears."
   ::= {sisgm1040284lrtECEControlListConfEntry 18 }     
   
sisgm1040284lrtECEControlListConfActionsEVCIDValue OBJECT-TYPE
   SYNTAX      Integer32
   MAX-ACCESS  read-create
   STATUS      current
   DESCRIPTION
       "When Specific is selected for the VLAN ID filter, you can enter a specific value. 
	   The allowed value is from 1 through 256."
   ::= {sisgm1040284lrtECEControlListConfEntry 19 }      
   
sisgm1040284lrtECEControlListConfActionsTagPopCount OBJECT-TYPE
   SYNTAX      Integer32
   MAX-ACCESS  read-create
   STATUS      current
   DESCRIPTION
       "The ingress tag pop count for the ECE. The allowed range is from 0 through 2."
   ::= {sisgm1040284lrtECEControlListConfEntry 22 }   

sisgm1040284lrtECEControlListConfActionsPolicyID OBJECT-TYPE
   SYNTAX      Integer32
   MAX-ACCESS  read-create
   STATUS      current
   DESCRIPTION
       "The ACL Policy ID for the ECE for matching ACL rules. 
	   The allowed range is from 0 through 255."
   ::= {sisgm1040284lrtECEControlListConfEntry 23 }     
   
sisgm1040284lrtECEControlListConfActionsClass OBJECT-TYPE
   SYNTAX      Integer32
   MAX-ACCESS  read-create
   STATUS      current
   DESCRIPTION
       "The traffic class for the ECE. The allowed range is from 0 through 7 or disabled(8)."
   ::= {sisgm1040284lrtECEControlListConfEntry 24 }   

sisgm1040284lrtECEControlListConfMACParametersDMACType OBJECT-TYPE
   SYNTAX      Integer32
   MAX-ACCESS  read-create
   STATUS      current
   DESCRIPTION
       "The destination MAC address type for matching the ECE. The possible values are: 
		0:Any: No DMAC tyoe is specified. (DMAC filter status is don't-care.) 
		1:Unicast: Frame must be unicast. 
		2:Multicast: Frame must be multicast. 
		3:Broadcast: Frame must be broadcast."
   ::= {sisgm1040284lrtECEControlListConfEntry 25 }      
   
sisgm1040284lrtECEControlListConfMACParametersSMACFilter OBJECT-TYPE
   SYNTAX      Integer32
   MAX-ACCESS  read-create
   STATUS      current
   DESCRIPTION
       "The source MAC address for matching the ECE. The possible values are: 
		0:Any: No SMAC filter is specified. (SMAC filter status is don't-care.) 
		1:Specific: If you want to filter a specific SMAC value with this ECE, choose this value. A field for entering a specific value appears."
   ::= {sisgm1040284lrtECEControlListConfEntry 28 }    
   
sisgm1040284lrtECEControlListConfMACParametersSMACValue OBJECT-TYPE
   SYNTAX      DisplayString
   MAX-ACCESS  read-create
   STATUS      current
   DESCRIPTION
       "When Specific is selected for the SMAC filter, you can enter a specific value. 
	   The legal format is xx-xx-xx-xx-xx-xx (x is a hexadecimal digit)."
   ::= {sisgm1040284lrtECEControlListConfEntry 29 }     
   
sisgm1040284lrtECEControlListConfIPv4Protocol OBJECT-TYPE
   SYNTAX      Integer32
   MAX-ACCESS  read-create
   STATUS      current
   DESCRIPTION
       "The IP protocol for matching the ECE. The possible values are: 
		0:Any: No protocol filter is specified. (Protocol filter status is don't-care.) 
		1:UDP: Specify the UDP for matching the ECE. 
		2:TCP: Specify the TCP for matching the ECE. 
		3:Specific: If you want to filter a specific protocol value with this ECE, choose this value. A field for entering a specific value appears."
   ::= {sisgm1040284lrtECEControlListConfEntry 30 }
   
sisgm1040284lrtECEControlListConfIPv4ProtocolValue OBJECT-TYPE
   SYNTAX      Integer32
   MAX-ACCESS  read-create
   STATUS      current
   DESCRIPTION
       "When Specific is selected for the protocol filter, you can enter a specific value. 
	   The allowed value is from 0 through 255."
   ::= {sisgm1040284lrtECEControlListConfEntry 31 }   
   
sisgm1040284lrtECEControlListConfIPv4SIPDIPFilter OBJECT-TYPE
   SYNTAX      Integer32
   MAX-ACCESS  read-create
   STATUS      current
   DESCRIPTION
       "The source/destination IP address for matching the ECE. 
	   It depend on by the port address mode, when port address mode is set to 'Source' then the field is used for source address. 
	   Similarly when port address mode is set to 'Destination' then the field is used for destination address. 
	   The possible values are: 
		0:Any: No SIP/DIP filter is specified. (SIP/DIP filter status is don't-care.) 
		1:Host: When IPv4 is selected for the Frame Type, if you want to filter a specific host address with this ECE, choose this value. A field for entering a host address appears. 
		2:Network: When IPv4 is selected for the Frame Type, if you want to filter a specific network address with this ECE, choose this value. Two fields for entering a specific network address and network mask appears. "
   ::= {sisgm1040284lrtECEControlListConfEntry 32 }    
   
sisgm1040284lrtECEControlListConfIPv4SIPDIPAddress OBJECT-TYPE
   SYNTAX      IpAddress
   MAX-ACCESS  read-create
   STATUS      current
   DESCRIPTION
       "When IPv4 is selected for the Frame Type and Host or Network is selected for the SIP/DIP filter, 
	   you can enter a specific host or network address. 
	   "
   ::= {sisgm1040284lrtECEControlListConfEntry 33 }    
   
sisgm1040284lrtECEControlListConfIPv4SIPDIPMask OBJECT-TYPE
   SYNTAX      IpAddress
   MAX-ACCESS  read-create
   STATUS      current
   DESCRIPTION
       "When IPv4 is selected for the Frame Type and Host or Network is selected for the SIP/DIP filter, 
	   you can enter a specific network mask. "
   ::= {sisgm1040284lrtECEControlListConfEntry 34 }     
   
sisgm1040284lrtECEControlListConfIPv4DSCPFilter OBJECT-TYPE
   SYNTAX      Integer32
   MAX-ACCESS  read-create
   STATUS      current
   DESCRIPTION
       "The DSCP filter for matching the ECE. The possible values are: 
		0:Any: No DSCP filter is specified. (DSCP filter status is don't-care.) 
		1:Specific: If you want to filter a specific DSCP value with this ECE, choose this value. A field for entering a specific value appears. 
		2:Range: If you want to filter a specific DSCP range filter with this ECE, choose this value. A field for entering a range appears."
   ::= {sisgm1040284lrtECEControlListConfEntry 35 }    
   
sisgm1040284lrtECEControlListConfIPv4DSCPRangeLow OBJECT-TYPE
   SYNTAX      Integer32
   MAX-ACCESS  read-create
   STATUS      current
   DESCRIPTION
       "When Specific is selected for the DSCP filter, you can enter a specific value. 
	   The allowed value is from 0 through 63."
   ::= {sisgm1040284lrtECEControlListConfEntry 36 }    

sisgm1040284lrtECEControlListConfIPv4DSCPRangeHigh OBJECT-TYPE
   SYNTAX      Integer32
   MAX-ACCESS  read-create
   STATUS      current
   DESCRIPTION
       "When Range is selected for the DSCP filter, you can enter a specific range. 
	   The allowed range is from 0 through 63."
   ::= {sisgm1040284lrtECEControlListConfEntry 37 }   

sisgm1040284lrtECEControlListConfIPv4Fragment OBJECT-TYPE
   SYNTAX      Integer32
   MAX-ACCESS  read-create
   STATUS      current
   DESCRIPTION
       "The IPv4 Fragment for matching the ECE. 
	   This involves the settings for the More Fragments (MF) bit and the Fragment Offset (FRAG OFFSET) field for an IPv4 frame. 
	   The possible values are: 
		0:Any: The ECE will match any MF bit. 
		1:Non-Fragment: IPv4 frames where the MF bit is set or the FRAG OFFSET field is greater than zero must not be able to match this entry. 
		2:Fragment: IPv4 frames where the MF bit is set or the FRAG OFFSET field is greater than zero must be able to match this entry."
   ::= {sisgm1040284lrtECEControlListConfEntry 38 }    

sisgm1040284lrtECEControlListConfIPv4SourcePortFilter OBJECT-TYPE
   SYNTAX      Integer32
   MAX-ACCESS  read-create
   STATUS      current
   DESCRIPTION
       "The TCP/UDP source port for matching the ECE. 
	   It only significant if protocol filter 'UDP' or 'TCP' is selected. 
	   The possible values are: 
		0:Any: No TCP/UDP source port filter is specified. (Source port filter status is don't-care.) 
		1:Specific: If you want to filter a specific TCP/UDP source port No. with this ECE, choose this value. A field for entering a specific No. appears. 
		2:Range: If you want to filter a specific TCP/UDP source port range filter with this ECE, choose this value. A field for entering a range appears."
   ::= {sisgm1040284lrtECEControlListConfEntry 39 }     
   
sisgm1040284lrtECEControlListConfIPv4SourceRangeLow OBJECT-TYPE
   SYNTAX      Integer32
   MAX-ACCESS  read-create
   STATUS      current
   DESCRIPTION
       "When Range is selected for the source port filter, you can enter a specific range. 
	   The allowed range is from 0 through 65535."
   ::= {sisgm1040284lrtECEControlListConfEntry 40 }    
   
sisgm1040284lrtECEControlListConfIPv4SourceRangeHigh OBJECT-TYPE
   SYNTAX      Integer32
   MAX-ACCESS  read-create
   STATUS      current
   DESCRIPTION
       "When Range is selected for the source port filter, you can enter a specific range. 
	   The allowed range is from 0 through 65535."
   ::= {sisgm1040284lrtECEControlListConfEntry 41 }    
   
sisgm1040284lrtECEControlListConfIPv4DestPortFilter OBJECT-TYPE
   SYNTAX      Integer32
   MAX-ACCESS  read-create
   STATUS      current
   DESCRIPTION
       "The TCP/UDP destination port for matching the ECE. It only significant if protocol filter 'UDP' or 'TCP' is selected. The possible values are: 
		0:Any: No TCP/UDP destination port filter is specified. (Destination port filter status is don't-care.) 
		1:Specific: If you want to filter a specific TCP/UDP destination port No. with this ECE, choose this value. A field for entering a specific No. appears. 
		2:Range: If you want to filter a specific TCP/UDP destination port range filter with this ECE, choose this value. A field for entering a range appears."
   ::= {sisgm1040284lrtECEControlListConfEntry 42 }    

sisgm1040284lrtECEControlListConfIPv4DestRangeLow OBJECT-TYPE
   SYNTAX      Integer32
   MAX-ACCESS  read-create
   STATUS      current
   DESCRIPTION
       "When Range is selected for the destination port filter, you can enter a specific range. 
	   The allowed range is from 0 through 65535."
   ::= {sisgm1040284lrtECEControlListConfEntry 43 }    

sisgm1040284lrtECEControlListConfIPv4DestRangeHigh OBJECT-TYPE
   SYNTAX      Integer32
   MAX-ACCESS  read-create
   STATUS      current
   DESCRIPTION
       "When Range is selected for the destination port filter, you can enter a specific range. 
	   The allowed range is from 0 through 65535."
   ::= {sisgm1040284lrtECEControlListConfEntry 44 }  

sisgm1040284lrtECEControlListConfIPv6Protocol OBJECT-TYPE
   SYNTAX      Integer32
   MAX-ACCESS  read-create
   STATUS      current
   DESCRIPTION
       "The IP protocol for matching the ECE. The possible values are: 
		0:Any: No protocol filter is specified. (Protocol filter status is don't-care.) 
		1:UDP: Specify the UDP for matching the ECE. 
		2:TCP: Specify the TCP for matching the ECE. 
		3:Specific: If you want to filter a specific protocol value with this ECE, choose this value. A field for entering a specific value appears."
   ::= {sisgm1040284lrtECEControlListConfEntry 45 }     
   
sisgm1040284lrtECEControlListConfIPv6ProtocolValue OBJECT-TYPE
   SYNTAX      Integer32
   MAX-ACCESS  read-create
   STATUS      current
   DESCRIPTION
       "When Specific is selected for the protocol filter, you can enter a specific value. 
	   The allowed value is from 0 through 255."
   ::= {sisgm1040284lrtECEControlListConfEntry 46 }     
   
sisgm1040284lrtECEControlListConfIPv6SIPDIPFilter OBJECT-TYPE
   SYNTAX      Integer32
   MAX-ACCESS  read-create
   STATUS      current
   DESCRIPTION
       "The source/destination IP address for matching the ECE. 
	   It depend on by the port address mode, when port address mode is set to 'Source' then the field is used for source address. Similarly when port address mode is set to 'Destination' then the field is used for destination address. 
	   The possible values are: 
		0:Any: No SIP/DIP filter is specified. (SIP/DIP filter status is don't-care.) 
		1:Specific: When IPv6 is selected for the Frame Type, if you want to filter a specific network address with this ECE, choose this value. Two fields for entering a specific network address and network mask appears."
   ::= {sisgm1040284lrtECEControlListConfEntry 47 } 

sisgm1040284lrtECEControlListConfIPv6SIPDIPAddress OBJECT-TYPE
   SYNTAX      IpAddress
   MAX-ACCESS  read-create
   STATUS      current
   DESCRIPTION
	   "When IPv6 is selected for the Frame Type, the field only supported 32 bits for IPv6 address."
   ::= {sisgm1040284lrtECEControlListConfEntry 48 }    

sisgm1040284lrtECEControlListConfIPv6SIPDIPMask OBJECT-TYPE
   SYNTAX      IpAddress
   MAX-ACCESS  read-create
   STATUS      current
   DESCRIPTION
	   "When IPv6 is selected for the Frame Type, the field only supported 32 bits for IPv6 mask."
   ::= {sisgm1040284lrtECEControlListConfEntry 49 }   

sisgm1040284lrtECEControlListConfIPv6DSCPFilter OBJECT-TYPE
   SYNTAX      Integer32
   MAX-ACCESS  read-create
   STATUS      current
   DESCRIPTION
       "The DSCP filter for matching the ECE. The possible values are: 
		0:Any: No DSCP filter is specified. (DSCP filter status is don't-care.) 
		1:Specific: If you want to filter a specific DSCP value with this ECE, choose this value. A field for entering a specific value appears. 
		2:Range: If you want to filter a specific DSCP range filter with this ECE, choose this value. A field for entering a range appears."
   ::= {sisgm1040284lrtECEControlListConfEntry 50 }    
   
sisgm1040284lrtECEControlListConfIPv6DSCPRangeLow OBJECT-TYPE
   SYNTAX      Integer32
   MAX-ACCESS  read-create
   STATUS      current
   DESCRIPTION
       "When Range is selected for the DSCP filter, you can enter a specific range. The allowed range is from 0 through 63."
   ::= {sisgm1040284lrtECEControlListConfEntry 51 }     
   
sisgm1040284lrtECEControlListConfIPv6DSCPRangeHigh OBJECT-TYPE
   SYNTAX      Integer32
   MAX-ACCESS  read-create
   STATUS      current
   DESCRIPTION
       "When Range is selected for the DSCP filter, you can enter a specific range. The allowed range is from 0 through 63."
   ::= {sisgm1040284lrtECEControlListConfEntry 52 }      
   
sisgm1040284lrtECEControlListConfIPv6SourcePortFilter OBJECT-TYPE
   SYNTAX      Integer32
   MAX-ACCESS  read-create
   STATUS      current
   DESCRIPTION
       "The TCP/UDP source port for matching the ECE. 
	   It only significant if protocol filter 'UDP' or 'TCP' is selected. The possible values are: 
		0:Any: No TCP/UDP source port filter is specified. (Source port filter status is don't-care.) 
		1:Specific: If you want to filter a specific TCP/UDP source port No. with this ECE, choose this value. A field for entering a specific No. appears. 
		2:Range: If you want to filter a specific TCP/UDP source port range filter with this ECE, choose this value. A field for entering a range appears."
   ::= {sisgm1040284lrtECEControlListConfEntry 53 }    

sisgm1040284lrtECEControlListConfIPv6SourceRangeLow OBJECT-TYPE
   SYNTAX      Integer32
   MAX-ACCESS  read-create
   STATUS      current
   DESCRIPTION
       "When Range is selected for the source port filter, you can enter a specific range. 
	   The allowed range is from 0 through 65535."
   ::= {sisgm1040284lrtECEControlListConfEntry 54 }    

sisgm1040284lrtECEControlListConfIPv6SourceRangeHigh OBJECT-TYPE
   SYNTAX      Integer32
   MAX-ACCESS  read-create
   STATUS      current
   DESCRIPTION
       "When Range is selected for the source port filter, you can enter a specific range. 
	   The allowed range is from 0 through 65535."
   ::= {sisgm1040284lrtECEControlListConfEntry 55 }    
   
sisgm1040284lrtECEControlListConfIPv6DestPortFilter OBJECT-TYPE
   SYNTAX      Integer32
   MAX-ACCESS  read-create
   STATUS      current
   DESCRIPTION
       "The TCP/UDP destination port for matching the ECE. 
	   It only significant if protocol filter 'UDP' or 'TCP' is selected. 
	   The possible values are: 
		0:Any: No TCP/UDP destination port filter is specified. (Destination port filter status is don't-care.) 
		1:Specific: If you want to filter a specific TCP/UDP destination port No. with this ECE, choose this value. A field for entering a specific No. appears. 
		2:Range: If you want to filter a specific TCP/UDP destination port range filter with this ECE, choose this value. A field for entering a range appears."
   ::= {sisgm1040284lrtECEControlListConfEntry 56 }   
   
sisgm1040284lrtECEControlListConfIPv6DestRangeLow OBJECT-TYPE
   SYNTAX      Integer32
   MAX-ACCESS  read-create
   STATUS      current
   DESCRIPTION
       "When Range is selected for the destination port filter, you can enter a specific range. 
	   The allowed range is from 0 through 65535."
   ::= {sisgm1040284lrtECEControlListConfEntry 57 }    
   
sisgm1040284lrtECEControlListConfIPv6DestRangeHigh OBJECT-TYPE
   SYNTAX      Integer32
   MAX-ACCESS  read-create
   STATUS      current
   DESCRIPTION
       "When Range is selected for the destination port filter, you can enter a specific range. 
	   The allowed range is from 0 through 65535."
   ::= {sisgm1040284lrtECEControlListConfEntry 58 }    
   
sisgm1040284lrtECEControlListConfEgressOuterTagMode OBJECT-TYPE
   SYNTAX      Integer32
   MAX-ACCESS  read-create
   STATUS      current
   DESCRIPTION
       "The outer tag for nni-to-uni direction for the ECE. The possible values are: 
		1:Enable: Enable outer tag for nni-to-uni direction for the ECE. 
		0:Disable: Disable outer tag for nni-to-uni direction for the ECE."
   ::= {sisgm1040284lrtECEControlListConfEntry 59 }    
   
sisgm1040284lrtECEControlListConfEgressOuterTagPCPDEIPreservation OBJECT-TYPE
   SYNTAX      Integer32
   MAX-ACCESS  read-create
   STATUS      current
   DESCRIPTION
       "The outer tag PCP and DEI preservation for the ECE. The possible values are: 
		1:Preserved: The outer tag PCP and DEI is preserved. 
		0:Fixed: The outer tag PCP and DEI is fixed."
   ::= {sisgm1040284lrtECEControlListConfEntry 61 }    
   
sisgm1040284lrtECEControlListConfEgressOuterTagPCP OBJECT-TYPE
   SYNTAX      Integer32
   MAX-ACCESS  read-create
   STATUS      current
   DESCRIPTION
       "The outer tag PCP value for the ECE. The allowed range is from 0 through 7."
   ::= {sisgm1040284lrtECEControlListConfEntry 62 }      

sisgm1040284lrtECEControlListConfEgressOuterTagDEI OBJECT-TYPE
   SYNTAX      Integer32
   MAX-ACCESS  read-create
   STATUS      current
   DESCRIPTION
       "The outer tag DEI value for the ECE. The allowed value is 0 or 1."
   ::= {sisgm1040284lrtECEControlListConfEntry 63 }   

sisgm1040284lrtECEControlListConfConflict OBJECT-TYPE
   SYNTAX      Integer32
   MAX-ACCESS  read-only
   STATUS      current
   DESCRIPTION
       "Indicates the hardware status of the specific ECE. 
	   The specific ECE is not applied to the hardware due to hardware limitations.
	   0:No
	   1:Yes"
   ::= {sisgm1040284lrtECEControlListConfEntry 69 }      
   
sisgm1040284lrtECEControlListConfRowStatus OBJECT-TYPE
   SYNTAX      RowStatus
   MAX-ACCESS  read-create
   STATUS      current
   DESCRIPTION
       "ECE Control List Conf Row Status."
   ::= {sisgm1040284lrtECEControlListConfEntry 70 }
   
   
sisgm1040284lrtEVCStatisticsTable  OBJECT-TYPE
   SYNTAX      SEQUENCE OF SISGM1040284LRTEVCStatisticsEntry
   MAX-ACCESS  not-accessible
   STATUS      current
   DESCRIPTION
       "A table of EVC Statistics."
   ::= { sisgm1040284lrtEVC 5 }

sisgm1040284lrtEVCStatisticsEntry OBJECT-TYPE
    SYNTAX        SISGM1040284LRTEVCStatisticsEntry
    MAX-ACCESS    not-accessible
    STATUS        current
    DESCRIPTION
        "An entry of EVC Statistics table."
    INDEX        { sisgm1040284lrtEVCStatisticsPort, sisgm1040284lrtEVCStatisticsClass}
    ::= { sisgm1040284lrtEVCStatisticsTable 1 }

SISGM1040284LRTEVCStatisticsEntry ::=
    SEQUENCE {
        sisgm1040284lrtEVCStatisticsPort                                     Integer32,
		sisgm1040284lrtEVCStatisticsClass                                    Integer32,
        sisgm1040284lrtEVCStatisticsGreenFramesRx                            Integer32,
		sisgm1040284lrtEVCStatisticsGreenFramesTx                            Integer32,
		sisgm1040284lrtEVCStatisticsYellowFramesRx                           Integer32,
		sisgm1040284lrtEVCStatisticsYellowFramesTx                           Integer32,
		sisgm1040284lrtEVCStatisticsRedFramesRx                              Integer32,
		sisgm1040284lrtEVCStatisticsDiscardedFramesGreen                     Integer32,
		sisgm1040284lrtEVCStatisticsDiscardedFramesYellow                    Integer32
    }

sisgm1040284lrtEVCStatisticsPort OBJECT-TYPE
   SYNTAX      Integer32
   MAX-ACCESS  not-accessible
   STATUS      current
   DESCRIPTION
       "Port Index"
   ::= {sisgm1040284lrtEVCStatisticsEntry 1 }
   
sisgm1040284lrtEVCStatisticsClass OBJECT-TYPE
   SYNTAX      Integer32
   MAX-ACCESS  not-accessible
   STATUS      current
   DESCRIPTION
       "Class Index, from 1-8"
   ::= {sisgm1040284lrtEVCStatisticsEntry 2 }

sisgm1040284lrtEVCStatisticsGreenFramesRx OBJECT-TYPE
   SYNTAX      Integer32
   MAX-ACCESS  read-only
   STATUS      current
   DESCRIPTION
       "The number of green received."
   ::= {sisgm1040284lrtEVCStatisticsEntry 3 }  
   
sisgm1040284lrtEVCStatisticsGreenFramesTx OBJECT-TYPE
   SYNTAX      Integer32
   MAX-ACCESS  read-only
   STATUS      current
   DESCRIPTION
       "The number of green transmitted."
   ::= {sisgm1040284lrtEVCStatisticsEntry 4 }   

sisgm1040284lrtEVCStatisticsYellowFramesRx OBJECT-TYPE
   SYNTAX      Integer32
   MAX-ACCESS  read-only
   STATUS      current
   DESCRIPTION
       "The number of yellow received."
   ::= {sisgm1040284lrtEVCStatisticsEntry 5 }    
   
sisgm1040284lrtEVCStatisticsYellowFramesTx OBJECT-TYPE
   SYNTAX      Integer32
   MAX-ACCESS  read-only
   STATUS      current
   DESCRIPTION
       "The number of yellow transmitted."
   ::= {sisgm1040284lrtEVCStatisticsEntry 6 }     
   
sisgm1040284lrtEVCStatisticsRedFramesRx OBJECT-TYPE
   SYNTAX      Integer32
   MAX-ACCESS  read-only
   STATUS      current
   DESCRIPTION
       "The number of red received."
   ::= {sisgm1040284lrtEVCStatisticsEntry 7 }    
   
sisgm1040284lrtEVCStatisticsDiscardedFramesGreen OBJECT-TYPE
   SYNTAX      Integer32
   MAX-ACCESS  read-only
   STATUS      current
   DESCRIPTION
       "The number of discarded in the green color."
   ::= {sisgm1040284lrtEVCStatisticsEntry 8 }    
  
sisgm1040284lrtEVCStatisticsDiscardedFramesYellow OBJECT-TYPE
   SYNTAX      Integer32
   MAX-ACCESS  read-only
   STATUS      current
   DESCRIPTION
       "The number of discarded in the yellow color."
   ::= {sisgm1040284lrtEVCStatisticsEntry 9 }    
   
   
sisgm1040284lrtEVCStatisticsClearTable  OBJECT-TYPE
   SYNTAX      SEQUENCE OF SISGM1040284LRTEVCStatisticsClearEntry
   MAX-ACCESS  not-accessible
   STATUS      current
   DESCRIPTION
       "A table of EVC Statistics Clear."
   ::= { sisgm1040284lrtEVC 6 }

sisgm1040284lrtEVCStatisticsClearEntry OBJECT-TYPE
    SYNTAX        SISGM1040284LRTEVCStatisticsClearEntry
    MAX-ACCESS    not-accessible
    STATUS        current
    DESCRIPTION
        "An entry of EVC Statistics Clear table."
    INDEX        { sisgm1040284lrtEVCStatisticsClearPort}
    ::= { sisgm1040284lrtEVCStatisticsClearTable 1 }

SISGM1040284LRTEVCStatisticsClearEntry ::=
    SEQUENCE {
        sisgm1040284lrtEVCStatisticsClearPort                Integer32,
		sisgm1040284lrtEVCStatisticsClear                    Integer32
    }


sisgm1040284lrtEVCStatisticsClearPort OBJECT-TYPE
   SYNTAX      Integer32
   MAX-ACCESS  not-accessible
   STATUS      current
   DESCRIPTION
       "Port Index"
   ::= {sisgm1040284lrtEVCStatisticsClearEntry 1 }
   
sisgm1040284lrtEVCStatisticsClear OBJECT-TYPE
   SYNTAX      Integer32
   MAX-ACCESS  read-write
   STATUS      current
   DESCRIPTION
       "Clears the counters for selected ports."
   ::= {sisgm1040284lrtEVCStatisticsClearEntry 2 }

-- =======================================================================================================================

sisgm1040284lrtAggregation    OBJECT IDENTIFIER ::= { sisgm1040284lrtConfiguration 31 } 
    
sisgm1040284lrtAggregationStatic    OBJECT IDENTIFIER ::= { sisgm1040284lrtAggregation 1 } 

sisgm1040284lrtAggrSourceMACAddress   OBJECT-TYPE
               SYNTAX      Integer32 (0|1)
               MAX-ACCESS  read-write
               STATUS      current
               DESCRIPTION
                   "Source MAC Address"
               ::= { sisgm1040284lrtAggregationStatic 2 }

sisgm1040284lrtAggrDestinationMACAddress   OBJECT-TYPE
               SYNTAX      Integer32 (0|1)
               MAX-ACCESS  read-write
               STATUS      current
               DESCRIPTION
                   "Destination MAC Address"
               ::= { sisgm1040284lrtAggregationStatic 3 }
               
sisgm1040284lrtAggrIPAddress   OBJECT-TYPE
               SYNTAX      Integer32 (0|1)
               MAX-ACCESS  read-write
               STATUS      current
               DESCRIPTION
                   "IP Address"
               ::= { sisgm1040284lrtAggregationStatic 4 }

sisgm1040284lrtAggrTCPUDPPortNumber   OBJECT-TYPE
               SYNTAX      Integer32 (0|1)
               MAX-ACCESS  read-write
               STATUS      current
               DESCRIPTION
                   "TCP/UDP Port Number"
               ::= { sisgm1040284lrtAggregationStatic 5 }
               
               
sisgm1040284lrtAggrGroupConfigTable OBJECT-TYPE
   SYNTAX      SEQUENCE OF SISGM1040284LRTAggrGroupConfigEntry
   MAX-ACCESS  not-accessible
   STATUS      current
   DESCRIPTION
       " "
   ::= { sisgm1040284lrtAggregationStatic 6 }

sisgm1040284lrtAggrGroupConfigEntry OBJECT-TYPE
   SYNTAX      SISGM1040284LRTAggrGroupConfigEntry
   MAX-ACCESS  not-accessible
   STATUS      current
   DESCRIPTION
       " "
   INDEX    { sisgm1040284lrtAggrGroupConfigPort  }
   ::= { sisgm1040284lrtAggrGroupConfigTable 1 }

SISGM1040284LRTAggrGroupConfigEntry ::= SEQUENCE {
   sisgm1040284lrtAggrGroupConfigPort                 Integer32,
   sisgm1040284lrtAggrGroupConfigGroup                Integer32,
   sisgm1040284lrtAggrGroupConfig                     Integer32
}

sisgm1040284lrtAggrGroupConfigPort OBJECT-TYPE
   SYNTAX      Integer32
   MAX-ACCESS  not-accessible
   STATUS      current
   DESCRIPTION
       "port index"
   ::= { sisgm1040284lrtAggrGroupConfigEntry 1 }
      
sisgm1040284lrtAggrGroupConfigGroup OBJECT-TYPE
   SYNTAX      Integer32
   MAX-ACCESS  not-accessible
   STATUS      current
   DESCRIPTION
       "group index"
   ::= { sisgm1040284lrtAggrGroupConfigEntry 2 }   

sisgm1040284lrtAggrGroupConfig OBJECT-TYPE
   SYNTAX      Integer32 (0|1)
   MAX-ACCESS  read-write
   STATUS      current
   DESCRIPTION
       "Aggregation Group Configuration"
   ::= { sisgm1040284lrtAggrGroupConfigEntry 3 }
   
   
sisgm1040284lrtAggrGroupStateTable OBJECT-TYPE
   SYNTAX      SEQUENCE OF SISGM1040284LRTAggrGroupStateEntry
   MAX-ACCESS  not-accessible
   STATUS      current
   DESCRIPTION
       " "
   ::= { sisgm1040284lrtAggregation 2 }

sisgm1040284lrtAggrGroupStateEntry OBJECT-TYPE
   SYNTAX      SISGM1040284LRTAggrGroupStateEntry
   MAX-ACCESS  not-accessible
   STATUS      current
   DESCRIPTION
       " "
   INDEX    { sisgm1040284lrtAggrGroupStateIndex  }
   ::= { sisgm1040284lrtAggrGroupStateTable 1 }

SISGM1040284LRTAggrGroupStateEntry ::= SEQUENCE {
   sisgm1040284lrtAggrGroupStateIndex             Integer32,
   sisgm1040284lrtAggrGroupStateAggrID            DisplayString,
   sisgm1040284lrtAggrGroupStateName              DisplayString,
   sisgm1040284lrtAggrGroupStateType              DisplayString,
   sisgm1040284lrtAggrGroupStateSpeed             DisplayString,   
   sisgm1040284lrtAggrGroupStateConfiguredPorts   DisplayString,
   sisgm1040284lrtAggrGroupStateAggregatedPorts   DisplayString, 
   sisgm1040284lrtAggrGroupStateAggregatedBandwidth   DisplayString 
}

sisgm1040284lrtAggrGroupStateIndex OBJECT-TYPE
   SYNTAX      Integer32
   MAX-ACCESS  not-accessible
   STATUS      current
   DESCRIPTION
       "index"
   ::= { sisgm1040284lrtAggrGroupStateEntry 1 }
   
sisgm1040284lrtAggrGroupStateAggrID OBJECT-TYPE
   SYNTAX      DisplayString
   MAX-ACCESS  read-only
   STATUS      current
   DESCRIPTION
       "AggrID"
   ::= { sisgm1040284lrtAggrGroupStateEntry 2 }

sisgm1040284lrtAggrGroupStateName OBJECT-TYPE
   SYNTAX      DisplayString
   MAX-ACCESS  read-only
   STATUS      current
   DESCRIPTION
       "Name"
   ::= { sisgm1040284lrtAggrGroupStateEntry 3 }
   
sisgm1040284lrtAggrGroupStateType OBJECT-TYPE
   SYNTAX      DisplayString
   MAX-ACCESS  read-only
   STATUS      current
   DESCRIPTION
       "Type"
   ::= { sisgm1040284lrtAggrGroupStateEntry 4 }   
   
sisgm1040284lrtAggrGroupStateSpeed OBJECT-TYPE
   SYNTAX      DisplayString
   MAX-ACCESS  read-only
   STATUS      current
   DESCRIPTION
       "Speed"
   ::= { sisgm1040284lrtAggrGroupStateEntry 5 }
   
sisgm1040284lrtAggrGroupStateConfiguredPorts OBJECT-TYPE
   SYNTAX      DisplayString
   MAX-ACCESS  read-only
   STATUS      current
   DESCRIPTION
       "Configured Ports"
   ::= { sisgm1040284lrtAggrGroupStateEntry 6 }

sisgm1040284lrtAggrGroupStateAggregatedPorts OBJECT-TYPE
   SYNTAX      DisplayString
   MAX-ACCESS  read-only
   STATUS      current
   DESCRIPTION
       "Aggregated Ports"
   ::= { sisgm1040284lrtAggrGroupStateEntry 7 }   
   
sisgm1040284lrtAggrGroupStateAggregatedBandwidth OBJECT-TYPE
   SYNTAX      DisplayString
   MAX-ACCESS  read-only
   STATUS      current
   DESCRIPTION
       "Aggregated Bandwidth"
   ::= { sisgm1040284lrtAggrGroupStateEntry 8 }   
   

-- =======================================================================================================================
sisgm1040284lrtSecurity                                              OBJECT IDENTIFIER ::= { sisgm1040284lrtProductId 3 }

sisgm1040284lrtIPSourceGuard                                         OBJECT IDENTIFIER ::= { sisgm1040284lrtSecurity 1 }

sisgm1040284lrtIPSourceGuardConf                                     OBJECT IDENTIFIER ::= { sisgm1040284lrtIPSourceGuard 1 }

-- RowStatus Info:  createAndGo, notReady not supported.
-- =======================================================================================================================
-- Textual Conventions for the SISGM1040284LRT IP Source Guard Mib
-- =======================================================================================================================
--
--    sisgm1040284lrtIPSourceGuard        OBJECT IDENTIFIER  ::= { sisgm1040284lrtIPSourceGuardMIB 1 }
--    sisgm1040284lrtIPSourceGuardConf    OBJECT IDENTIFIER  ::= { sisgm1040284lrtIPSourceGuard 1 }

--
-- =======================================================================================================================
-- Start sisgm1040284lrtIPSourceGuard group
-- =======================================================================================================================
--sisgm1040284lrtIPSourceGuardConf

    sisgm1040284lrtIPSourceGuardMode OBJECT-TYPE
               SYNTAX      AdminMode
               MAX-ACCESS  read-write
               STATUS      current
               DESCRIPTION
                   "Enable the Global IP Source Guard or disable the
                    Global IP Source Guard."
               ::= {     sisgm1040284lrtIPSourceGuardConf 1 }

    sisgm1040284lrtIPSourceGuardDynamicToStaticCmd OBJECT-TYPE
               SYNTAX      ActivateCmd
               MAX-ACCESS  read-write
               STATUS      current
               DESCRIPTION
                   "Translate all dynamic entries to static entries."
               DEFVAL  { noAction }
               ::= {     sisgm1040284lrtIPSourceGuardConf 2 }

--sisgm1040284lrtIPSourceGuardPortConfigTable

    sisgm1040284lrtIPSourceGuardPortConfigTable OBJECT-TYPE
               SYNTAX      SEQUENCE OF     SISGM1040284LRTIPSourceGuardPortConfigEntry
               MAX-ACCESS  not-accessible
               STATUS      current
               DESCRIPTION
                   "The IP Source Guard Port Configuration Table.
                    INDEX for this table is ifIndex which is
                    equivalent to the panel port number."
               ::= {     sisgm1040284lrtIPSourceGuardConf 3 }

    sisgm1040284lrtIPSourceGuardPortConfigEntry OBJECT-TYPE
               SYNTAX          SISGM1040284LRTIPSourceGuardPortConfigEntry
               MAX-ACCESS  not-accessible
               STATUS      current
               DESCRIPTION
                   "The IP Source Guard Port Configuration Entry."
               INDEX    {    ifIndex  }
               ::= {     sisgm1040284lrtIPSourceGuardPortConfigTable 1 }

    SISGM1040284LRTIPSourceGuardPortConfigEntry             ::= SEQUENCE {
                 sisgm1040284lrtIPSourceGuardPortConfigMode            AdminMode,
                 sisgm1040284lrtIPSourceGuardPortMaxDynamicClients     Integer32
                 }

    sisgm1040284lrtIPSourceGuardPortConfigMode OBJECT-TYPE
               SYNTAX      AdminMode
               MAX-ACCESS  read-write
               STATUS      current
               DESCRIPTION
                   "Specify IP Source Guard is enabled on which ports."
               ::= {     sisgm1040284lrtIPSourceGuardPortConfigEntry 2 }

    sisgm1040284lrtIPSourceGuardPortMaxDynamicClients OBJECT-TYPE
               SYNTAX      Integer32(0..2|99)
               MAX-ACCESS  read-write
               STATUS      current
               DESCRIPTION
                   "Specify the maximum number of dynamic clients that can
                    be learned on given port.
                    default: 99
                    0~2: Max Dynamic clients
                    99:Unlimited "
               ::= {     sisgm1040284lrtIPSourceGuardPortConfigEntry 3 }

--sisgm1040284lrtIPSourceGuardStaticTable

    sisgm1040284lrtIPSourceGuardStaticTable OBJECT-TYPE
               SYNTAX      SEQUENCE OF     SISGM1040284LRTIPSourceGuardStaticEntry
               MAX-ACCESS  not-accessible
               STATUS      current
               DESCRIPTION
                   "The IP Source Guard Static Table."
               ::= {     sisgm1040284lrtIPSourceGuard 2 }

    sisgm1040284lrtIPSourceGuardStaticEntry OBJECT-TYPE
               SYNTAX          SISGM1040284LRTIPSourceGuardStaticEntry
               MAX-ACCESS  not-accessible
               STATUS      current
               DESCRIPTION
                   "The IP Source Guard Static Entry."
               INDEX    {    sisgm1040284lrtIPSourceGuardStaticIndex  }
               ::= {     sisgm1040284lrtIPSourceGuardStaticTable 1 }

    SISGM1040284LRTIPSourceGuardStaticEntry             ::= SEQUENCE {
                 sisgm1040284lrtIPSourceGuardStaticSwitchIndex   Integer32,
                 sisgm1040284lrtIPSourceGuardStaticIndex         Integer32,
                 sisgm1040284lrtIPSourceGuardStaticPort          Integer32,
                 sisgm1040284lrtIPSourceGuardStaticVLANId        Integer32,
                 sisgm1040284lrtIPSourceGuardStaticIPAddress     IpAddress,
                 sisgm1040284lrtIPSourceGuardStaticIPMask        IpAddress,
                 sisgm1040284lrtIPSourceGuardStaticMACAddress    DisplayString,
                 sisgm1040284lrtIPSourceGuardStaticRowStatus     RowStatus
                 }

    sisgm1040284lrtIPSourceGuardStaticSwitchIndex OBJECT-TYPE
               SYNTAX      Integer32(1..16)
               MAX-ACCESS  not-accessible
               STATUS      current
               DESCRIPTION
                   "Switch Index."
               ::= {     sisgm1040284lrtIPSourceGuardStaticEntry 1 }

    sisgm1040284lrtIPSourceGuardStaticIndex OBJECT-TYPE
               SYNTAX      Integer32(1..28)
               MAX-ACCESS  not-accessible
               STATUS      current
               DESCRIPTION
                   "The entry of table."
               ::= {     sisgm1040284lrtIPSourceGuardStaticEntry 2 }

    sisgm1040284lrtIPSourceGuardStaticPort OBJECT-TYPE
               SYNTAX      Integer32(1..255)
               MAX-ACCESS  read-create
               STATUS      current
               DESCRIPTION
                   "The port number of table.
                    range: 1 - port number."
               ::= {     sisgm1040284lrtIPSourceGuardStaticEntry 3 }

    sisgm1040284lrtIPSourceGuardStaticVLANId OBJECT-TYPE
               SYNTAX      Integer32(1..4095)
               MAX-ACCESS  read-create
               STATUS      current
               DESCRIPTION
                   "VLAN ID, range: 1 - 4095."
               ::= {     sisgm1040284lrtIPSourceGuardStaticEntry 4 }

    sisgm1040284lrtIPSourceGuardStaticIPAddress OBJECT-TYPE
               SYNTAX      IpAddress
               MAX-ACCESS  read-create
               STATUS      current
               DESCRIPTION
                   "IP address allowed for doing IP source guard."
               ::= {     sisgm1040284lrtIPSourceGuardStaticEntry 5 }

    sisgm1040284lrtIPSourceGuardStaticIPMask OBJECT-TYPE
               SYNTAX      IpAddress
               MAX-ACCESS  read-create
               STATUS      current
               DESCRIPTION
                   "IP Mask allowed for doing IP source guard."
               ::= {     sisgm1040284lrtIPSourceGuardStaticEntry 6 }

    sisgm1040284lrtIPSourceGuardStaticMACAddress OBJECT-TYPE
               SYNTAX      DisplayString
               MAX-ACCESS  read-create
               STATUS      current
               DESCRIPTION
                   "Allowed Source MAC address, format: 0a 1b 2c 3d 4e 5f."
               ::= {     sisgm1040284lrtIPSourceGuardStaticEntry 7 }

    sisgm1040284lrtIPSourceGuardStaticRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sisgm1040284lrtIPSourceGuardStaticEntry 8 }

--sisgm1040284lrtIPSourceGuardDynamicTable

    sisgm1040284lrtIPSourceGuardDynamicTable OBJECT-TYPE
               SYNTAX      SEQUENCE OF     SISGM1040284LRTIPSourceGuardDynamicEntry
               MAX-ACCESS  not-accessible
               STATUS      current
               DESCRIPTION
                   "The IP Source Guard Dynamic Table."
               ::= {     sisgm1040284lrtIPSourceGuard 3 }

    sisgm1040284lrtIPSourceGuardDynamicEntry OBJECT-TYPE
               SYNTAX          SISGM1040284LRTIPSourceGuardDynamicEntry
               MAX-ACCESS  not-accessible
               STATUS      current
               DESCRIPTION
                   "The IP Source Guard Dynamic Entry."
               INDEX    {    sisgm1040284lrtIPSourceGuardDynamicIndex  }
               ::= {     sisgm1040284lrtIPSourceGuardDynamicTable 1 }

    SISGM1040284LRTIPSourceGuardDynamicEntry             ::= SEQUENCE {
                 sisgm1040284lrtIPSourceGuardDynamicSwitchIndex    Integer32,
                 sisgm1040284lrtIPSourceGuardDynamicIndex          Integer32,
                 sisgm1040284lrtIPSourceGuardDynamicPort           Integer32,
                 sisgm1040284lrtIPSourceGuardDynamicVLANId         Integer32,
                 sisgm1040284lrtIPSourceGuardDynamicIPAddress      IpAddress,
                 sisgm1040284lrtIPSourceGuardDynamicMACAddress     DisplayString
                 }

    sisgm1040284lrtIPSourceGuardDynamicSwitchIndex OBJECT-TYPE
               SYNTAX      Integer32(1..16)
               MAX-ACCESS  not-accessible
               STATUS      current
               DESCRIPTION
                   "Switch Index."
               ::= {     sisgm1040284lrtIPSourceGuardDynamicEntry 1 }

    sisgm1040284lrtIPSourceGuardDynamicIndex OBJECT-TYPE
               SYNTAX      Integer32(1..4095)
               MAX-ACCESS  not-accessible
               STATUS      current
               DESCRIPTION
                   "The entry of table."
               ::= {     sisgm1040284lrtIPSourceGuardDynamicEntry 2 }

    sisgm1040284lrtIPSourceGuardDynamicPort OBJECT-TYPE
               SYNTAX      Integer32(1..255)
               MAX-ACCESS  read-only
               STATUS      current
               DESCRIPTION
                   "The logical port for the settings."
               ::= {     sisgm1040284lrtIPSourceGuardDynamicEntry 3 }

    sisgm1040284lrtIPSourceGuardDynamicVLANId OBJECT-TYPE
               SYNTAX      Integer32(1..4094)
               MAX-ACCESS  read-only
               STATUS      current
               DESCRIPTION
                   "The vlan id for the settings."
               ::= {     sisgm1040284lrtIPSourceGuardDynamicEntry 4 }

    sisgm1040284lrtIPSourceGuardDynamicIPAddress OBJECT-TYPE
               SYNTAX      IpAddress
               MAX-ACCESS  read-only
               STATUS      current
               DESCRIPTION
                   "Allowed Source IP address."
               ::= {     sisgm1040284lrtIPSourceGuardDynamicEntry 5 }

    sisgm1040284lrtIPSourceGuardDynamicMACAddress OBJECT-TYPE
               SYNTAX      DisplayString
               MAX-ACCESS  read-only
               STATUS      current
               DESCRIPTION
                   "Allowed Source MAC address."
               ::= {     sisgm1040284lrtIPSourceGuardDynamicEntry 6 }
-- =======================================================================================================================
sisgm1040284lrtARPInspection                                          OBJECT IDENTIFIER ::= { sisgm1040284lrtSecurity 2 }
-- RowStatus Info:  createAndGo, notReady not supported.
-- =======================================================================================================================
-- Textual Conventions for the sisgm1040284lrt Arp Mib
-- =======================================================================================================================
--
    sisgm1040284lrtARP                  OBJECT IDENTIFIER  ::= { sisgm1040284lrtARPInspection 1 }
    sisgm1040284lrtARPConfig            OBJECT IDENTIFIER  ::= { sisgm1040284lrtARP 1 }

--
-- =======================================================================================================================
-- Start sisgm1040284lrtARP group
-- =======================================================================================================================
--sisgm1040284lrtARPConfig

    sisgm1040284lrtARPConfMode OBJECT-TYPE
               SYNTAX      AdminMode
               MAX-ACCESS  read-write
               STATUS      current
               DESCRIPTION
                   "Enable the Global ARP Inspection or disable the Global
                    ARP Inspection."
               ::= {     sisgm1040284lrtARPConfig 1 }

--sisgm1040284lrtARPPortConfTable

    sisgm1040284lrtARPPortConfTable OBJECT-TYPE
               SYNTAX      SEQUENCE OF     SISGM1040284LRTARPPortConfEntry
               MAX-ACCESS  not-accessible
               STATUS      current
               DESCRIPTION
                   "The ARP Port Configuration Table."
               ::= {     sisgm1040284lrtARPConfig 3 }

    sisgm1040284lrtARPPortConfEntry OBJECT-TYPE
               SYNTAX          SISGM1040284LRTARPPortConfEntry
               MAX-ACCESS  not-accessible
               STATUS      current
               DESCRIPTION
                   "The ARP Port Configuration Entry."
               INDEX    {    sisgm1040284lrtARPPortConfPort  }
               ::= {     sisgm1040284lrtARPPortConfTable 1 }

    SISGM1040284LRTARPPortConfEntry             ::= SEQUENCE {
                 sisgm1040284lrtARPPortConfPort            Integer32,
                 sisgm1040284lrtARPPortConfMode            AdminMode,
                 sisgm1040284lrtARPPortConfCheckVLAN       AdminMode,
                 sisgm1040284lrtARPPortConfLogType         INTEGER
                 }

    sisgm1040284lrtARPPortConfPort OBJECT-TYPE
               SYNTAX      Integer32(1..255)
               MAX-ACCESS  not-accessible
               STATUS      current
               DESCRIPTION
                   "The port number for which the configuration below applies.
                    range: 1 - port number."
               ::= {     sisgm1040284lrtARPPortConfEntry 1 }

    sisgm1040284lrtARPPortConfMode OBJECT-TYPE
               SYNTAX      AdminMode
               MAX-ACCESS  read-write
               STATUS      current
               DESCRIPTION
                   "Specify ARP Inspection is enabled on which ports."
               ::= {     sisgm1040284lrtARPPortConfEntry 2 }

    sisgm1040284lrtARPPortConfCheckVLAN OBJECT-TYPE
               SYNTAX      AdminMode
               MAX-ACCESS  read-write
               STATUS      current
               DESCRIPTION
                   "When the setting of 'Check VLAN' is disabled, the log
                   type of ARP Inspection will refer to the port setting.
                   And the setting of 'Check VLAN' is enabled, the log type
                   of ARP Inspection will refer to the VLAN setting."
               ::= {     sisgm1040284lrtARPPortConfEntry 3 }

    sisgm1040284lrtARPPortConfLogType OBJECT-TYPE
               SYNTAX      INTEGER{none(0),deny(1),permit(2),all(3)}
               MAX-ACCESS  read-write
               STATUS      current
               DESCRIPTION
                   "The log type of ARP Inspection will refer to the
                    port setting.
                    0: none,
                    1: deny,
                    2: permit,
                    3: all,
                    range: 0-3."
               ::= {     sisgm1040284lrtARPPortConfEntry 4 }

--sisgm1040284lrtARPVlanConfig

    sisgm1040284lrtARPVlanConfigTable OBJECT-TYPE
               SYNTAX      SEQUENCE OF     SISGM1040284LRTARPVlanConfigEntry
               MAX-ACCESS  not-accessible
               STATUS      current
               DESCRIPTION
                   "The ARP Vlan Configuration Table."
               ::= {     sisgm1040284lrtARP 2 }

    sisgm1040284lrtARPVlanConfigEntry OBJECT-TYPE
               SYNTAX          SISGM1040284LRTARPVlanConfigEntry
               MAX-ACCESS  not-accessible
               STATUS      current
               DESCRIPTION
                   "The ARP Vlan Configuration Entry."
               INDEX    {    sisgm1040284lrtARPVlanConfigVlan  }
               ::= {     sisgm1040284lrtARPVlanConfigTable 1 }

    SISGM1040284LRTARPVlanConfigEntry             ::= SEQUENCE {
                 sisgm1040284lrtARPVlanConfigVlan       Integer32,
                 sisgm1040284lrtARPVlanConfigLogType    INTEGER,
                 sisgm1040284lrtARPVlanConfigRowStatus  RowStatus
                 }

    sisgm1040284lrtARPVlanConfigVlan OBJECT-TYPE
               SYNTAX      Integer32(1..4095)
               MAX-ACCESS  not-accessible
               STATUS      current
               DESCRIPTION
                   "Specify ARP Inspection is enabled on which VLANs.
                    range: 1 - 4095."
               ::= {     sisgm1040284lrtARPVlanConfigEntry 1 }

    sisgm1040284lrtARPVlanConfigLogType OBJECT-TYPE
               SYNTAX      INTEGER{none(0),deny(1),permit(2),all(3)}
               MAX-ACCESS  read-create
               STATUS      current
               DESCRIPTION
                   "The log type also can be configured on per VLAN setting.
                    0: none,
                    1: deny,
                    2: permit,
                    3: all,
                    range: 0-3."
               ::= {     sisgm1040284lrtARPVlanConfigEntry 2 }

    sisgm1040284lrtARPVlanConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sisgm1040284lrtARPVlanConfigEntry 3 }

--sisgm1040284lrtARPStaticTable

    sisgm1040284lrtARPStaticTable OBJECT-TYPE
               SYNTAX      SEQUENCE OF     SISGM1040284LRTARPStaticEntry
               MAX-ACCESS  not-accessible
               STATUS      current
               DESCRIPTION
                   "The ARP Static Table."
               ::= {     sisgm1040284lrtARP 3 }

    sisgm1040284lrtARPStaticEntry OBJECT-TYPE
               SYNTAX          SISGM1040284LRTARPStaticEntry
               MAX-ACCESS  not-accessible
               STATUS      current
               DESCRIPTION
                   "The ARP Static Entry."
               INDEX    {    sisgm1040284lrtARPStaticIndex  }
               ::= {     sisgm1040284lrtARPStaticTable 1 }

    SISGM1040284LRTARPStaticEntry             ::= SEQUENCE {
                 sisgm1040284lrtARPStaticSwitchIndex   Integer32,
                 sisgm1040284lrtARPStaticIndex         Integer32,
                 sisgm1040284lrtARPStaticPort          Integer32,
                 sisgm1040284lrtARPStaticVlanID        Integer32,
                 sisgm1040284lrtARPStaticMACAddress    DisplayString,
                 sisgm1040284lrtARPStaticIPAddress     IpAddress,
                 sisgm1040284lrtARPStaticRowStatus     RowStatus
                 }


    sisgm1040284lrtARPStaticSwitchIndex OBJECT-TYPE
               SYNTAX      Integer32(1..16)
               MAX-ACCESS  not-accessible
               STATUS      current
               DESCRIPTION
                   "Switch Index."
               ::= {     sisgm1040284lrtARPStaticEntry 1 }

    sisgm1040284lrtARPStaticIndex OBJECT-TYPE
               SYNTAX      Integer32(1..255)
               MAX-ACCESS  not-accessible
               STATUS      current
               DESCRIPTION
                   "The entry of table."
               ::= {     sisgm1040284lrtARPStaticEntry 2 }

    sisgm1040284lrtARPStaticPort OBJECT-TYPE
               SYNTAX      Integer32(1..255)
               MAX-ACCESS  read-create
               STATUS      current
               DESCRIPTION
                   "The logical port for the settings.
                    range: 1 - port number."
               ::= {     sisgm1040284lrtARPStaticEntry 3 }

    sisgm1040284lrtARPStaticVlanID OBJECT-TYPE
               SYNTAX      Integer32(1..4095)
               MAX-ACCESS  read-create
               STATUS      current
               DESCRIPTION
                   "The vlan id for the settings.
                    range: 1-4095."
               ::= {     sisgm1040284lrtARPStaticEntry 4 }

    sisgm1040284lrtARPStaticMACAddress OBJECT-TYPE
               SYNTAX      DisplayString
               MAX-ACCESS  read-create
               STATUS      current
               DESCRIPTION
                   "Allowed Source MAC address in ARP request packets."
               ::= {     sisgm1040284lrtARPStaticEntry 5 }

    sisgm1040284lrtARPStaticIPAddress OBJECT-TYPE
               SYNTAX      IpAddress
               MAX-ACCESS  read-create
               STATUS      current
               DESCRIPTION
                   "Allowed Source IP address in ARP request packets."
               ::= {     sisgm1040284lrtARPStaticEntry 6 }

    sisgm1040284lrtARPStaticRowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sisgm1040284lrtARPStaticEntry 7 }

--sisgm1040284lrtARPDynamicTable

    sisgm1040284lrtARPDynamicTable OBJECT-TYPE
               SYNTAX      SEQUENCE OF     SISGM1040284LRTARPDynamicEntry
               MAX-ACCESS  not-accessible
               STATUS      current
               DESCRIPTION
                   "The ARP Dynamic Table."
               ::= {    sisgm1040284lrtARP 4 }

    sisgm1040284lrtARPDynamicEntry OBJECT-TYPE
               SYNTAX          SISGM1040284LRTARPDynamicEntry
               MAX-ACCESS  not-accessible
               STATUS      current
               DESCRIPTION
                   "The ARP Dynamic Entry."
               INDEX    {   sisgm1040284lrtARPDynamicIndex  }
               ::= {    sisgm1040284lrtARPDynamicTable 1 }

    SISGM1040284LRTARPDynamicEntry             ::= SEQUENCE {
                 sisgm1040284lrtARPDynamicIndex          Integer32,
                 sisgm1040284lrtARPDynamicPort           Integer32,
                 sisgm1040284lrtARPDynamicVLANId         Integer32,
                 sisgm1040284lrtARPDynamicMACAddress     MacAddress,
                 sisgm1040284lrtARPDynamicIPAddress      IpAddress,
                 sisgm1040284lrtARPDynamicToStaticCmd    INTEGER
                 }

    sisgm1040284lrtARPDynamicIndex OBJECT-TYPE
               SYNTAX      Integer32(1..4095)
               MAX-ACCESS  not-accessible
               STATUS      current
               DESCRIPTION
                   "The entry of table."
               ::= {    sisgm1040284lrtARPDynamicEntry 1 }

    sisgm1040284lrtARPDynamicPort OBJECT-TYPE
               SYNTAX      Integer32(1..255)
               MAX-ACCESS  read-only
               STATUS      current
               DESCRIPTION
                   "Switch Port Number for which the entries are displayed."
               ::= {    sisgm1040284lrtARPDynamicEntry 2 }

    sisgm1040284lrtARPDynamicVLANId OBJECT-TYPE
               SYNTAX      Integer32(1..4095)
               MAX-ACCESS  read-only
               STATUS      current
               DESCRIPTION
                   "VLAN-ID in which the ARP traffic is permitted."
               ::= {    sisgm1040284lrtARPDynamicEntry 3 }

    sisgm1040284lrtARPDynamicMACAddress OBJECT-TYPE
               SYNTAX      MacAddress
               MAX-ACCESS  read-only
               STATUS      current
               DESCRIPTION
                   "User MAC address of the entry."
               ::= {    sisgm1040284lrtARPDynamicEntry 4 }

    sisgm1040284lrtARPDynamicIPAddress OBJECT-TYPE
               SYNTAX      IpAddress
               MAX-ACCESS  read-only
               STATUS      current
               DESCRIPTION
                   "User IP address of the entry."
               ::= {    sisgm1040284lrtARPDynamicEntry 5 }

    sisgm1040284lrtARPDynamicToStaticCmd OBJECT-TYPE
               SYNTAX      ActivateCmd
               MAX-ACCESS  read-write
               STATUS      current
               DESCRIPTION
                   "Enable the Global ARP Inspection or disable the Global
                    ARP Inspection."
               ::= {     sisgm1040284lrtARPDynamicEntry 6 }


-- =======================================================================================================================
-- sisgm1040284lrtARPConformance
-- =======================================================================================================================
sisgm1040284lrtARPConformance OBJECT IDENTIFIER ::= { sisgm1040284lrtARPInspection 200 }

sisgm1040284lrtARPCompliances OBJECT IDENTIFIER ::= { sisgm1040284lrtARPConformance 1 }

sisgm1040284lrtARPGroups      OBJECT IDENTIFIER ::= { sisgm1040284lrtARPConformance 2 }

sisgm1040284lrtARPGroup OBJECT-GROUP
    OBJECTS {
                -- sisgm1040284lrtARPConfig
                sisgm1040284lrtARPConfMode,

                --sisgm1040284lrtARPPortConfTable
                sisgm1040284lrtARPPortConfMode,
                sisgm1040284lrtARPPortConfCheckVLAN,
                sisgm1040284lrtARPPortConfLogType,

                --sisgm1040284lrtARPVlanConfig
                sisgm1040284lrtARPVlanConfigLogType,
                sisgm1040284lrtARPVlanConfigRowStatus,

                --sisgm1040284lrtARPStaticTable
                sisgm1040284lrtARPStaticPort,
                sisgm1040284lrtARPStaticVlanID,
                sisgm1040284lrtARPStaticMACAddress,
                sisgm1040284lrtARPStaticIPAddress,
                sisgm1040284lrtARPStaticRowStatus,

                --sisgm1040284lrtARPDynamicTable
                sisgm1040284lrtARPDynamicPort,
                sisgm1040284lrtARPDynamicVLANId,
                sisgm1040284lrtARPDynamicMACAddress,
                sisgm1040284lrtARPDynamicIPAddress,
                sisgm1040284lrtARPDynamicToStaticCmd
            }
     STATUS  current
     DESCRIPTION
            "The collection of objects which are used to indicate
            sisgm1040284lrt ARP information."
    ::= { sisgm1040284lrtARPGroups 1 }

-- =======================================================================================================================
sisgm1040284lrtDHCPSnooping                                          OBJECT IDENTIFIER ::= { sisgm1040284lrtSecurity 3 }

sisgm1040284lrtDHCPSnoopingConf                                          OBJECT IDENTIFIER ::= { sisgm1040284lrtDHCPSnooping 1 }

sisgm1040284lrtDHCPSnoopingMode OBJECT-TYPE
   SYNTAX      Integer32(0|1)
   MAX-ACCESS  read-write
   STATUS      current
   DESCRIPTION
       "default: 0
       0: disable
       1: enable"
   ::= { sisgm1040284lrtDHCPSnoopingConf 1 }

sisgm1040284lrtDHCPSnoopingPortModeConfigurationTable OBJECT-TYPE
   SYNTAX      SEQUENCE OF SISGM1040284LRTDHCPSnoopingPortModeConfigurationEntry
   MAX-ACCESS  not-accessible
   STATUS      current
   DESCRIPTION
       " "
   ::= { sisgm1040284lrtDHCPSnoopingConf 2 }

sisgm1040284lrtDHCPSnoopingPortModeConfigurationEntry OBJECT-TYPE
   SYNTAX      SISGM1040284LRTDHCPSnoopingPortModeConfigurationEntry
   MAX-ACCESS  not-accessible
   STATUS      current
   DESCRIPTION
       " "
   INDEX    { sisgm1040284lrtDHCPSnoopingPortModeConfigurationPort  }
   ::= { sisgm1040284lrtDHCPSnoopingPortModeConfigurationTable 1 }

SISGM1040284LRTDHCPSnoopingPortModeConfigurationEntry ::= SEQUENCE {
   sisgm1040284lrtDHCPSnoopingPortModeConfigurationPort	Integer32,
   sisgm1040284lrtDHCPSnoopingPortModeConfigurationMode	Integer32
}

sisgm1040284lrtDHCPSnoopingPortModeConfigurationPort OBJECT-TYPE
   SYNTAX      Integer32(1..4095)
   MAX-ACCESS  not-accessible
   STATUS      current
   DESCRIPTION
       " "
   ::= { sisgm1040284lrtDHCPSnoopingPortModeConfigurationEntry 1 }

sisgm1040284lrtDHCPSnoopingPortModeConfigurationMode OBJECT-TYPE
   SYNTAX      Integer32 (0|1)
   MAX-ACCESS  read-write
   STATUS      current
   DESCRIPTION
       "default: 1
       0: trust port mode
       1: untrust port mode"
   ::= { sisgm1040284lrtDHCPSnoopingPortModeConfigurationEntry 2 }

sisgm1040284lrtDHCPSnoopingStatisticsTable OBJECT-TYPE
   SYNTAX      SEQUENCE OF SISGM1040284LRTDHCPSnoopingStatisticsEntry
   MAX-ACCESS  not-accessible
   STATUS      current
   DESCRIPTION
       " "
   ::= { sisgm1040284lrtDHCPSnooping 2 }

sisgm1040284lrtDHCPSnoopingStatisticsEntry OBJECT-TYPE
   SYNTAX      SISGM1040284LRTDHCPSnoopingStatisticsEntry
   MAX-ACCESS  not-accessible
   STATUS      current
   DESCRIPTION
       " "
   INDEX    { sisgm1040284lrtDHCPSnoopingStatisticsPort  }
   ::= { sisgm1040284lrtDHCPSnoopingStatisticsTable 1 }

SISGM1040284LRTDHCPSnoopingStatisticsEntry ::= SEQUENCE {
   sisgm1040284lrtDHCPSnoopingStatisticsPort         Integer32,
   sisgm1040284lrtDHCPSnoopingStatisticsClear        Integer32,
   sisgm1040284lrtDHCPSnoopingRxDiscover             Counter32,
   sisgm1040284lrtDHCPSnoopingRxOffer                Counter32,
   sisgm1040284lrtDHCPSnoopingRxRequest              Counter32,
   sisgm1040284lrtDHCPSnoopingRxDecline              Counter32,
   sisgm1040284lrtDHCPSnoopingRxACK                  Counter32,
   sisgm1040284lrtDHCPSnoopingRxNAK                  Counter32,
   sisgm1040284lrtDHCPSnoopingRxRelease              Counter32,
   sisgm1040284lrtDHCPSnoopingRxInform               Counter32,
   sisgm1040284lrtDHCPSnoopingRxLeaseQuery           Counter32,
   sisgm1040284lrtDHCPSnoopingRxLeaseUnassigned      Counter32,
   sisgm1040284lrtDHCPSnoopingRxLeaseUnknown         Counter32,
   sisgm1040284lrtDHCPSnoopingRxLeaseActive          Counter32,
   sisgm1040284lrtDHCPSnoopingTxDiscover             Counter32,
   sisgm1040284lrtDHCPSnoopingTxOffer                Counter32,
   sisgm1040284lrtDHCPSnoopingTxRequest              Counter32,
   sisgm1040284lrtDHCPSnoopingTxDecline              Counter32,
   sisgm1040284lrtDHCPSnoopingTxACK                  Counter32,
   sisgm1040284lrtDHCPSnoopingTxNAK                  Counter32,
   sisgm1040284lrtDHCPSnoopingTxRelease              Counter32,
   sisgm1040284lrtDHCPSnoopingTxInform               Counter32,
   sisgm1040284lrtDHCPSnoopingTxLeaseQuery           Counter32,
   sisgm1040284lrtDHCPSnoopingTxLeaseUnassigned      Counter32,
   sisgm1040284lrtDHCPSnoopingTxLeaseUnknown         Counter32,
   sisgm1040284lrtDHCPSnoopingTxLeaseActive          Counter32,
   sisgm1040284lrtDHCPSnoopingRxDiscardedChecksumError  Counter32,
   sisgm1040284lrtDHCPSnoopingRxDiscardedFromUntrusted  Counter32
}

sisgm1040284lrtDHCPSnoopingStatisticsPort OBJECT-TYPE
   SYNTAX      Integer32(1..4095)
   MAX-ACCESS  not-accessible
   STATUS      current
   DESCRIPTION
       " "
   ::= { sisgm1040284lrtDHCPSnoopingStatisticsEntry 1 }

sisgm1040284lrtDHCPSnoopingStatisticsClear OBJECT-TYPE
   SYNTAX      Integer32 (0|1)
   MAX-ACCESS  read-write
   STATUS      current
   DESCRIPTION
       "default: 0
       0: none
       1: clear"
   ::= { sisgm1040284lrtDHCPSnoopingStatisticsEntry 2 }

sisgm1040284lrtDHCPSnoopingRxDiscover OBJECT-TYPE
   SYNTAX      Counter32
   MAX-ACCESS  read-only
   STATUS      current
   DESCRIPTION
       " "
   ::= { sisgm1040284lrtDHCPSnoopingStatisticsEntry 3 }

sisgm1040284lrtDHCPSnoopingRxOffer OBJECT-TYPE
   SYNTAX      Counter32
   MAX-ACCESS  read-only
   STATUS      current
   DESCRIPTION
       " "
   ::= { sisgm1040284lrtDHCPSnoopingStatisticsEntry 4 }

sisgm1040284lrtDHCPSnoopingRxRequest OBJECT-TYPE
   SYNTAX      Counter32
   MAX-ACCESS  read-only
   STATUS      current
   DESCRIPTION
       " "
   ::= { sisgm1040284lrtDHCPSnoopingStatisticsEntry 5 }

sisgm1040284lrtDHCPSnoopingRxDecline OBJECT-TYPE
   SYNTAX      Counter32
   MAX-ACCESS  read-only
   STATUS      current
   DESCRIPTION
       " "
   ::= { sisgm1040284lrtDHCPSnoopingStatisticsEntry 6 }

sisgm1040284lrtDHCPSnoopingRxACK OBJECT-TYPE
   SYNTAX      Counter32
   MAX-ACCESS  read-only
   STATUS      current
   DESCRIPTION
       " "
   ::= { sisgm1040284lrtDHCPSnoopingStatisticsEntry 7 }

sisgm1040284lrtDHCPSnoopingRxNAK OBJECT-TYPE
   SYNTAX      Counter32
   MAX-ACCESS  read-only
   STATUS      current
   DESCRIPTION
       " "
   ::= { sisgm1040284lrtDHCPSnoopingStatisticsEntry 8 }

sisgm1040284lrtDHCPSnoopingRxRelease OBJECT-TYPE
   SYNTAX      Counter32
   MAX-ACCESS  read-only
   STATUS      current
   DESCRIPTION
       " "
   ::= { sisgm1040284lrtDHCPSnoopingStatisticsEntry 9 }

sisgm1040284lrtDHCPSnoopingRxInform OBJECT-TYPE
   SYNTAX      Counter32
   MAX-ACCESS  read-only
   STATUS      current
   DESCRIPTION
       " "
   ::= { sisgm1040284lrtDHCPSnoopingStatisticsEntry 10 }

sisgm1040284lrtDHCPSnoopingRxLeaseQuery OBJECT-TYPE
   SYNTAX      Counter32
   MAX-ACCESS  read-only
   STATUS      current
   DESCRIPTION
       " "
   ::= { sisgm1040284lrtDHCPSnoopingStatisticsEntry 11 }

sisgm1040284lrtDHCPSnoopingRxLeaseUnassigned OBJECT-TYPE
   SYNTAX      Counter32
   MAX-ACCESS  read-only
   STATUS      current
   DESCRIPTION
       " "
   ::= { sisgm1040284lrtDHCPSnoopingStatisticsEntry 12 }

sisgm1040284lrtDHCPSnoopingRxLeaseUnknown OBJECT-TYPE
   SYNTAX      Counter32
   MAX-ACCESS  read-only
   STATUS      current
   DESCRIPTION
       " "
   ::= { sisgm1040284lrtDHCPSnoopingStatisticsEntry 13 }

sisgm1040284lrtDHCPSnoopingRxLeaseActive OBJECT-TYPE
   SYNTAX      Counter32
   MAX-ACCESS  read-only
   STATUS      current
   DESCRIPTION
       " "
   ::= { sisgm1040284lrtDHCPSnoopingStatisticsEntry 14 }

sisgm1040284lrtDHCPSnoopingTxDiscover OBJECT-TYPE
   SYNTAX      Counter32
   MAX-ACCESS  read-only
   STATUS      current
   DESCRIPTION
       " "
   ::= { sisgm1040284lrtDHCPSnoopingStatisticsEntry 15 }

sisgm1040284lrtDHCPSnoopingTxOffer OBJECT-TYPE
   SYNTAX      Counter32
   MAX-ACCESS  read-only
   STATUS      current
   DESCRIPTION
       " "
   ::= { sisgm1040284lrtDHCPSnoopingStatisticsEntry 16 }

sisgm1040284lrtDHCPSnoopingTxRequest OBJECT-TYPE
   SYNTAX      Counter32
   MAX-ACCESS  read-only
   STATUS      current
   DESCRIPTION
       " "
   ::= { sisgm1040284lrtDHCPSnoopingStatisticsEntry 17 }

sisgm1040284lrtDHCPSnoopingTxDecline OBJECT-TYPE
   SYNTAX      Counter32
   MAX-ACCESS  read-only
   STATUS      current
   DESCRIPTION
       " "
   ::= { sisgm1040284lrtDHCPSnoopingStatisticsEntry 18 }

sisgm1040284lrtDHCPSnoopingTxACK OBJECT-TYPE
   SYNTAX      Counter32
   MAX-ACCESS  read-only
   STATUS      current
   DESCRIPTION
       " "
   ::= { sisgm1040284lrtDHCPSnoopingStatisticsEntry 19 }

sisgm1040284lrtDHCPSnoopingTxNAK OBJECT-TYPE
   SYNTAX      Counter32
   MAX-ACCESS  read-only
   STATUS      current
   DESCRIPTION
       " "
   ::= { sisgm1040284lrtDHCPSnoopingStatisticsEntry 20 }

sisgm1040284lrtDHCPSnoopingTxRelease OBJECT-TYPE
   SYNTAX      Counter32
   MAX-ACCESS  read-only
   STATUS      current
   DESCRIPTION
       " "
   ::= { sisgm1040284lrtDHCPSnoopingStatisticsEntry 21 }

sisgm1040284lrtDHCPSnoopingTxInform OBJECT-TYPE
   SYNTAX      Counter32
   MAX-ACCESS  read-only
   STATUS      current
   DESCRIPTION
       " "
   ::= { sisgm1040284lrtDHCPSnoopingStatisticsEntry 22 }

sisgm1040284lrtDHCPSnoopingTxLeaseQuery OBJECT-TYPE
   SYNTAX      Counter32
   MAX-ACCESS  read-only
   STATUS      current
   DESCRIPTION
       " "
   ::= { sisgm1040284lrtDHCPSnoopingStatisticsEntry 23 }

sisgm1040284lrtDHCPSnoopingTxLeaseUnassigned OBJECT-TYPE
   SYNTAX      Counter32
   MAX-ACCESS  read-only
   STATUS      current
   DESCRIPTION
       " "
   ::= { sisgm1040284lrtDHCPSnoopingStatisticsEntry 24 }

sisgm1040284lrtDHCPSnoopingTxLeaseUnknown OBJECT-TYPE
   SYNTAX      Counter32
   MAX-ACCESS  read-only
   STATUS      current
   DESCRIPTION
       " "
   ::= { sisgm1040284lrtDHCPSnoopingStatisticsEntry 25 }

sisgm1040284lrtDHCPSnoopingTxLeaseActive OBJECT-TYPE
   SYNTAX      Counter32
   MAX-ACCESS  read-only
   STATUS      current
   DESCRIPTION
       " "
   ::= { sisgm1040284lrtDHCPSnoopingStatisticsEntry 26 }

sisgm1040284lrtDHCPSnoopingRxDiscardedChecksumError OBJECT-TYPE
   SYNTAX      Counter32
   MAX-ACCESS  read-only
   STATUS      current
   DESCRIPTION
       " "
   ::= { sisgm1040284lrtDHCPSnoopingStatisticsEntry 27 }

sisgm1040284lrtDHCPSnoopingRxDiscardedFromUntrusted OBJECT-TYPE
   SYNTAX      Counter32
   MAX-ACCESS  read-only
   STATUS      current
   DESCRIPTION
       " "
   ::= { sisgm1040284lrtDHCPSnoopingStatisticsEntry 28 }

sisgm1040284lrtDHCPRelay                                             OBJECT IDENTIFIER ::= { sisgm1040284lrtSecurity 4 }

sisgm1040284lrtDHCPRelayConfiguration                                         OBJECT IDENTIFIER ::= { sisgm1040284lrtDHCPRelay 1 }

sisgm1040284lrtDHCPRelayMode OBJECT-TYPE
   SYNTAX      Integer32(0|1)
   MAX-ACCESS  read-write
   STATUS      current
   DESCRIPTION
       "default: 0
       0: disable
       1: enable
       We need at least one server"
   ::= { sisgm1040284lrtDHCPRelayConfiguration 1 }

sisgm1040284lrtDHCPRelayServer OBJECT-TYPE
   SYNTAX      IpAddress
   MAX-ACCESS  read-write
   STATUS      current
   DESCRIPTION
       " "
   ::= { sisgm1040284lrtDHCPRelayConfiguration 2 }

sisgm1040284lrtDHCPRelayInformationMode OBJECT-TYPE
   SYNTAX      Integer32(0|1)
   MAX-ACCESS  read-write
   STATUS      current
   DESCRIPTION
       "default: 0
       0: disable
       1: enable "
   ::= { sisgm1040284lrtDHCPRelayConfiguration 3 }

sisgm1040284lrtDHCPRelayInformationPolicy OBJECT-TYPE
   SYNTAX      Integer32(0..2)
   MAX-ACCESS  read-write
   STATUS      current
   DESCRIPTION
       "default: 0
       0: replace
       1: keep
       2: drop "
   ::= { sisgm1040284lrtDHCPRelayConfiguration 4 }

sisgm1040284lrtDHCPRelayStatistics                                   OBJECT IDENTIFIER ::= { sisgm1040284lrtDHCPRelay 2 }

sisgm1040284lrtDHCPRelayServerStatistics                                   OBJECT IDENTIFIER ::= { sisgm1040284lrtDHCPRelayStatistics 1 }

sisgm1040284lrtServerStatTransmitToServer OBJECT-TYPE
   SYNTAX      Counter32
   MAX-ACCESS  read-only
   STATUS      current
   DESCRIPTION
       " "
   ::= { sisgm1040284lrtDHCPRelayServerStatistics 1 }

sisgm1040284lrtServerStatTransmitError OBJECT-TYPE
   SYNTAX      Counter32
   MAX-ACCESS  read-only
   STATUS      current
   DESCRIPTION
       " "
   ::= { sisgm1040284lrtDHCPRelayServerStatistics 2 }

sisgm1040284lrtServerStatReceiveFromServer OBJECT-TYPE
   SYNTAX      Counter32
   MAX-ACCESS  read-only
   STATUS      current
   DESCRIPTION
       " "
   ::= { sisgm1040284lrtDHCPRelayServerStatistics 3 }

sisgm1040284lrtServerStatReceiveMissingAgentOption OBJECT-TYPE
   SYNTAX      Counter32
   MAX-ACCESS  read-only
   STATUS      current
   DESCRIPTION
       " "
   ::= { sisgm1040284lrtDHCPRelayServerStatistics 4 }

sisgm1040284lrtServerStatReceiveMissingCircuitID OBJECT-TYPE
   SYNTAX      Counter32
   MAX-ACCESS  read-only
   STATUS      current
   DESCRIPTION
       " "
   ::= { sisgm1040284lrtDHCPRelayServerStatistics 5 }

sisgm1040284lrtServerStatReceiveMissingRemoteID OBJECT-TYPE
   SYNTAX      Counter32
   MAX-ACCESS  read-only
   STATUS      current
   DESCRIPTION
       " "
   ::= { sisgm1040284lrtDHCPRelayServerStatistics 6 }

sisgm1040284lrtServerStatReceiveBadCircuitID OBJECT-TYPE
   SYNTAX      Counter32
   MAX-ACCESS  read-only
   STATUS      current
   DESCRIPTION
       " "
   ::= { sisgm1040284lrtDHCPRelayServerStatistics 7 }

sisgm1040284lrtServerStatReceiveBadRemoteID OBJECT-TYPE
   SYNTAX      Counter32
   MAX-ACCESS  read-only
   STATUS      current
   DESCRIPTION
       " "
   ::= { sisgm1040284lrtDHCPRelayServerStatistics 8 }

sisgm1040284lrtDHCPRelayClientStatistics                                   OBJECT IDENTIFIER ::= { sisgm1040284lrtDHCPRelayStatistics 2 }

sisgm1040284lrtClientStatTransmitToClient OBJECT-TYPE
   SYNTAX      Counter32
   MAX-ACCESS  read-only
   STATUS      current
   DESCRIPTION
       " "
   ::= { sisgm1040284lrtDHCPRelayClientStatistics 1 }

sisgm1040284lrtClientStatTransmitError OBJECT-TYPE
   SYNTAX      Counter32
   MAX-ACCESS  read-only
   STATUS      current
   DESCRIPTION
       " "
   ::= { sisgm1040284lrtDHCPRelayClientStatistics 2 }

sisgm1040284lrtClientStatReceivefromClient OBJECT-TYPE
   SYNTAX      Counter32
   MAX-ACCESS  read-only
   STATUS      current
   DESCRIPTION
       " "
   ::= { sisgm1040284lrtDHCPRelayClientStatistics 3 }

sisgm1040284lrtClientStatReceiveAgentOption OBJECT-TYPE
   SYNTAX      Counter32
   MAX-ACCESS  read-only
   STATUS      current
   DESCRIPTION
       " "
   ::= { sisgm1040284lrtDHCPRelayClientStatistics 4 }

sisgm1040284lrtClientStatReplaceAgentOption OBJECT-TYPE
   SYNTAX      Counter32
   MAX-ACCESS  read-only
   STATUS      current
   DESCRIPTION
       " "
   ::= { sisgm1040284lrtDHCPRelayClientStatistics 5 }

sisgm1040284lrtClientStatKeepAgentOption OBJECT-TYPE
   SYNTAX      Counter32
   MAX-ACCESS  read-only
   STATUS      current
   DESCRIPTION
       " "
   ::= { sisgm1040284lrtDHCPRelayClientStatistics 6 }

sisgm1040284lrtClientStatDropAgentOption OBJECT-TYPE
   SYNTAX      Counter32
   MAX-ACCESS  read-only
   STATUS      current
   DESCRIPTION
       " "
   ::= { sisgm1040284lrtDHCPRelayClientStatistics 7 }

sisgm1040284lrtPortSecurity                                          OBJECT IDENTIFIER ::= { sisgm1040284lrtSecurity 5 }

sisgm1040284lrtPortSecLimitCtrl                                      OBJECT IDENTIFIER ::= { sisgm1040284lrtPortSecurity 1 }

sisgm1040284lrtPortSecLimitCtrlSystemConf                                      OBJECT IDENTIFIER ::= { sisgm1040284lrtPortSecLimitCtrl 1 }

sisgm1040284lrtPortSecurityMode OBJECT-TYPE
   SYNTAX      Integer32(0|1)
   MAX-ACCESS  read-write
   STATUS      current
   DESCRIPTION
       "default: 0
       0: disable
       1: enable "
   ::= { sisgm1040284lrtPortSecLimitCtrlSystemConf 1 }

sisgm1040284lrtPortSecurityAging OBJECT-TYPE
   SYNTAX      Integer32(0|1)
   MAX-ACCESS  read-write
   STATUS      current
   DESCRIPTION
       "default: 0
       0: disable
       1: enable "
   ::= { sisgm1040284lrtPortSecLimitCtrlSystemConf 2 }

sisgm1040284lrtPortSecurityAgingPeriod OBJECT-TYPE
   SYNTAX      Integer32(10..10000000)
   MAX-ACCESS  read-write
   STATUS      current
   DESCRIPTION
       "default: 3600, range: 10-10000000 "
   ::= { sisgm1040284lrtPortSecLimitCtrlSystemConf 3 }

sisgm1040284lrtPortSecLimitCtrlTable OBJECT-TYPE
   SYNTAX      SEQUENCE OF SISGM1040284LRTPortSecLimitCtrlEntry
   MAX-ACCESS  not-accessible
   STATUS      current
   DESCRIPTION
       " "
   ::= { sisgm1040284lrtPortSecLimitCtrl 2 }

sisgm1040284lrtPortSecLimitCtrlEntry OBJECT-TYPE
   SYNTAX      SISGM1040284LRTPortSecLimitCtrlEntry
   MAX-ACCESS  not-accessible
   STATUS      current
   DESCRIPTION
       " "
   INDEX    { sisgm1040284lrtPortSecLimitCtrlPort  }
   ::= { sisgm1040284lrtPortSecLimitCtrlTable 1 }

SISGM1040284LRTPortSecLimitCtrlEntry ::= SEQUENCE {
   sisgm1040284lrtPortSecLimitCtrlPort           Integer32,
   sisgm1040284lrtPortSecLimitCtrlPortMode       Integer32,
   sisgm1040284lrtPortSecLimitCtrlPortLimit      Integer32,
   sisgm1040284lrtPortSecLimitCtrlPortAction     Integer32,
   sisgm1040284lrtPortSecLimitCtrlPortState      DisplayString,
   sisgm1040284lrtPortSecLimitCtrlPortReOpen     Integer32,
   sisgm1040284lrtPortSecLimitCtrlPortSticky     Integer32,
   sisgm1040284lrtPortSecLimitCtrlPortClear      Integer32
}

sisgm1040284lrtPortSecLimitCtrlPort OBJECT-TYPE
   SYNTAX      Integer32 (1..4095)
   MAX-ACCESS  not-accessible
   STATUS      current
   DESCRIPTION
       " "
   ::= { sisgm1040284lrtPortSecLimitCtrlEntry 1 }

sisgm1040284lrtPortSecLimitCtrlPortMode OBJECT-TYPE
   SYNTAX      Integer32 (0|1)
   MAX-ACCESS  read-write
   STATUS      current
   DESCRIPTION
       "default: 0
       0: disable
       1: enable"
   ::= { sisgm1040284lrtPortSecLimitCtrlEntry 2 }

sisgm1040284lrtPortSecLimitCtrlPortLimit OBJECT-TYPE
   SYNTAX      Integer32(1..1024)
   MAX-ACCESS  read-write
   STATUS      current
   DESCRIPTION
       "default: 4, range: 1-1024"
   ::= { sisgm1040284lrtPortSecLimitCtrlEntry 3 }

sisgm1040284lrtPortSecLimitCtrlPortAction OBJECT-TYPE
   SYNTAX      Integer32(0..3)
   MAX-ACCESS  read-write
   STATUS      current
   DESCRIPTION
       "default: 0
       0: none
       1: trap
       2: shutdown
       3: trap&shutdown"
   ::= { sisgm1040284lrtPortSecLimitCtrlEntry 4 }

sisgm1040284lrtPortSecLimitCtrlPortState OBJECT-TYPE
   SYNTAX      DisplayString
   MAX-ACCESS  read-only
   STATUS      current
   DESCRIPTION
       " "
   ::= { sisgm1040284lrtPortSecLimitCtrlEntry 5 }

sisgm1040284lrtPortSecLimitCtrlPortReOpen OBJECT-TYPE
   SYNTAX      Integer32 (0|1)
   MAX-ACCESS  read-write
   STATUS      current
   DESCRIPTION
       "default: 0
       0: none
       1: reopen"
   ::= { sisgm1040284lrtPortSecLimitCtrlEntry 6 }

sisgm1040284lrtPortSecLimitCtrlPortSticky OBJECT-TYPE
   SYNTAX      Integer32 (0|1)
   MAX-ACCESS  read-write
   STATUS      current
   DESCRIPTION
       "default: 0
       0: disable
       1: enable"
   ::= { sisgm1040284lrtPortSecLimitCtrlEntry 7 }

sisgm1040284lrtPortSecLimitCtrlPortClear OBJECT-TYPE
   SYNTAX      Integer32 (0|1)
   MAX-ACCESS  read-write
   STATUS      current
   DESCRIPTION
       "default: 0
       1: clear"
   ::= { sisgm1040284lrtPortSecLimitCtrlEntry 8 }
   
sisgm1040284lrtPortSecSwitchStatusTable OBJECT-TYPE
   SYNTAX      SEQUENCE OF SISGM1040284LRTPortSecSwitchStatusEntry
   MAX-ACCESS  not-accessible
   STATUS      current
   DESCRIPTION
       " "
   ::= { sisgm1040284lrtPortSecurity 2 }

sisgm1040284lrtPortSecSwitchStatusEntry OBJECT-TYPE
   SYNTAX      SISGM1040284LRTPortSecSwitchStatusEntry
   MAX-ACCESS  not-accessible
   STATUS      current
   DESCRIPTION
       " "
   INDEX    { sisgm1040284lrtPortSecSwitchStatusPort  }
   ::= { sisgm1040284lrtPortSecSwitchStatusTable 1 }

SISGM1040284LRTPortSecSwitchStatusEntry ::= SEQUENCE {
   sisgm1040284lrtPortSecSwitchStatusPort                Integer32,
   sisgm1040284lrtPortSecSwitchStatusUsers               DisplayString,
   sisgm1040284lrtPortSecSwitchStatusState               DisplayString,
   sisgm1040284lrtPortSecSwitchStatusMACCountCurrent     Integer32,
   sisgm1040284lrtPortSecSwitchStatusMACCountLimit       Integer32
}

sisgm1040284lrtPortSecSwitchStatusPort OBJECT-TYPE
   SYNTAX      Integer32 (1..4095)
   MAX-ACCESS  not-accessible
   STATUS      current
   DESCRIPTION
       " "
   ::= { sisgm1040284lrtPortSecSwitchStatusEntry 1 }

sisgm1040284lrtPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { sisgm1040284lrtPortSecSwitchStatusEntry 2 }

sisgm1040284lrtPortSecSwitchStatusState OBJECT-TYPE
   SYNTAX      DisplayString
   MAX-ACCESS  read-only
   STATUS      current
   DESCRIPTION
       " Shows the current state of the port : Disabled, Ready, Limit Reached, Shutdown. "
   ::= { sisgm1040284lrtPortSecSwitchStatusEntry 3 }

sisgm1040284lrtPortSecSwitchStatusMACCountCurrent OBJECT-TYPE
   SYNTAX      Integer32 (1..4095)
   MAX-ACCESS  read-only
   STATUS      current
   DESCRIPTION
       " "
   ::= { sisgm1040284lrtPortSecSwitchStatusEntry 4 }

sisgm1040284lrtPortSecSwitchStatusMACCountLimit OBJECT-TYPE
   SYNTAX      Integer32(1..4095)
   MAX-ACCESS  read-only
   STATUS      current
   DESCRIPTION
       " "
   ::= { sisgm1040284lrtPortSecSwitchStatusEntry 5 }

sisgm1040284lrtPortSecPortStatus                                      OBJECT IDENTIFIER ::= { sisgm1040284lrtPortSecurity 3 }

sisgm1040284lrtPortSecPortStatusPort OBJECT-TYPE
   SYNTAX       Integer32 (1..4095)
   MAX-ACCESS   read-write
   STATUS       current
   DESCRIPTION
       "port number
        default: 1
        range: 1 - port number."
   ::= { sisgm1040284lrtPortSecPortStatus 1 }

sisgm1040284lrtPortSecPortStatusTable OBJECT-TYPE
   SYNTAX      SEQUENCE OF SISGM1040284LRTPortSecPortStatusEntry
   MAX-ACCESS  not-accessible
   STATUS      current
   DESCRIPTION
      " "
   ::= { sisgm1040284lrtPortSecPortStatus 2 }

sisgm1040284lrtPortSecPortStatusEntry OBJECT-TYPE
   SYNTAX      SISGM1040284LRTPortSecPortStatusEntry
   MAX-ACCESS  not-accessible
   STATUS      current
   DESCRIPTION
       " "
   INDEX    { sisgm1040284lrtPortSecPortStatusIndex  }
   ::= { sisgm1040284lrtPortSecPortStatusTable 1 }

SISGM1040284LRTPortSecPortStatusEntry ::= SEQUENCE {
   sisgm1040284lrtPortSecPortStatusIndex              Integer32,
   sisgm1040284lrtPortSecPortStatusMACAddress         MacAddress,
   sisgm1040284lrtPortSecPortStatusVLANId             Integer32,
   sisgm1040284lrtPortSecPortStatusState              DisplayString,
   sisgm1040284lrtPortSecPortStatusTimeOfAddition     DisplayString,
   sisgm1040284lrtPortSecPortStatusAgeAndHold         DisplayString
}

sisgm1040284lrtPortSecPortStatusIndex OBJECT-TYPE
   SYNTAX      Integer32(1..4095)
   MAX-ACCESS  not-accessible
   STATUS      current
   DESCRIPTION
       " "
   ::= { sisgm1040284lrtPortSecPortStatusEntry 1 }

sisgm1040284lrtPortSecPortStatusMACAddress OBJECT-TYPE
   SYNTAX      MacAddress
   MAX-ACCESS  read-only
   STATUS      current
   DESCRIPTION
       " "
   ::= { sisgm1040284lrtPortSecPortStatusEntry 2 }

sisgm1040284lrtPortSecPortStatusVLANId OBJECT-TYPE
   SYNTAX      Integer32(1..4094)
   MAX-ACCESS  read-only
   STATUS      current
   DESCRIPTION
       " "
   ::= { sisgm1040284lrtPortSecPortStatusEntry 3 }

sisgm1040284lrtPortSecPortStatusState OBJECT-TYPE
   SYNTAX      DisplayString
   MAX-ACCESS  read-only
   STATUS      current
   DESCRIPTION
       "Blocked / Forwarding "
   ::= { sisgm1040284lrtPortSecPortStatusEntry 4 }

sisgm1040284lrtPortSecPortStatusTimeOfAddition OBJECT-TYPE
   SYNTAX      DisplayString
   MAX-ACCESS  read-only
   STATUS      current
   DESCRIPTION
       " "
   ::= { sisgm1040284lrtPortSecPortStatusEntry 5 }

sisgm1040284lrtPortSecPortStatusAgeAndHold OBJECT-TYPE
   SYNTAX      DisplayString
   MAX-ACCESS  read-only
   STATUS      current
   DESCRIPTION
       " "
   ::= { sisgm1040284lrtPortSecPortStatusEntry 6 }


sisgm1040284lrtAccessManagement                                      OBJECT IDENTIFIER ::= { sisgm1040284lrtSecurity 6 }

sisgm1040284lrtAccessMgmtConf                                         OBJECT IDENTIFIER ::= { sisgm1040284lrtAccessManagement 1 }

sisgm1040284lrtAccessMgmtStatistics                                   OBJECT IDENTIFIER ::= { sisgm1040284lrtAccessManagement 2 }
--
-- =======================================================================================================================
-- Start sisgm1040284lrtAccessManagement group
-- =======================================================================================================================
--sisgm1040284lrtAccessMgmtConf

    sisgm1040284lrtAccessMgmtConfMode OBJECT-TYPE
               SYNTAX      AdminMode
               MAX-ACCESS  read-write
               STATUS      current
               DESCRIPTION
                   "Indicates the access management mode operation."
               DEFVAL  { disable }
               ::= {     sisgm1040284lrtAccessMgmtConf 1 }

--sisgm1040284lrtAccessMgmtConfTable

    sisgm1040284lrtAccessMgmtConfTable OBJECT-TYPE
               SYNTAX      SEQUENCE OF     SISGM1040284LRTAccessMgmtConfEntry
               MAX-ACCESS  not-accessible
               STATUS      current
               DESCRIPTION
                   "The Access Mgmt Conf Table. "
               ::= {     sisgm1040284lrtAccessMgmtConf 2 }

    sisgm1040284lrtAccessMgmtConfEntry OBJECT-TYPE
               SYNTAX          SISGM1040284LRTAccessMgmtConfEntry
               MAX-ACCESS  not-accessible
               STATUS      current
               DESCRIPTION
                   "The Access Mgmt Conf Entry "
               INDEX    {    sisgm1040284lrtAccessMgmtIndex  }
               ::= {     sisgm1040284lrtAccessMgmtConfTable 1 }

    SISGM1040284LRTAccessMgmtConfEntry             ::= SEQUENCE {
                 sisgm1040284lrtAccessMgmtIndex            Integer32,
                 sisgm1040284lrtAccessMgmtVlanID           Integer32,
                 sisgm1040284lrtAccessMgmtStartIpAddress   IpAddress,
                 sisgm1040284lrtAccessMgmtEndIpAddress     IpAddress,
                 sisgm1040284lrtAccessMgmtHttpHttps        AdminMode,
                 sisgm1040284lrtAccessMgmtSNMP             AdminMode,
                 sisgm1040284lrtAccessMgmtTelnetSSH        AdminMode,
                 sisgm1040284lrtAccessMgmtRowStatus        RowStatus
                 }

    sisgm1040284lrtAccessMgmtIndex OBJECT-TYPE
               SYNTAX      Integer32(1..16)
               MAX-ACCESS  not-accessible
               STATUS      current
               DESCRIPTION
                   "The Access Management config index.
                    range : 1-16."
               ::= {     sisgm1040284lrtAccessMgmtConfEntry 1 }

    sisgm1040284lrtAccessMgmtVlanID OBJECT-TYPE
               SYNTAX      Integer32 (1..4095)
               MAX-ACCESS  read-create
               STATUS      current
               DESCRIPTION
                   "The VLAN ID for the access management entry.
                    range: 1-4095."
               ::= {     sisgm1040284lrtAccessMgmtConfEntry 2 }

    sisgm1040284lrtAccessMgmtStartIpAddress OBJECT-TYPE
               SYNTAX      IpAddress
               MAX-ACCESS  read-create
               STATUS      current
               DESCRIPTION
                   "The start IP address for the access management
                    entry."
               ::= {     sisgm1040284lrtAccessMgmtConfEntry 3 }

    sisgm1040284lrtAccessMgmtEndIpAddress OBJECT-TYPE
               SYNTAX      IpAddress
               MAX-ACCESS  read-create
               STATUS      current
               DESCRIPTION
                   "The end IP address for the access management
                    entry. "
               ::= {     sisgm1040284lrtAccessMgmtConfEntry 4 }

    sisgm1040284lrtAccessMgmtHttpHttps OBJECT-TYPE
               SYNTAX      AdminMode
               MAX-ACCESS  read-create
               STATUS      current
               DESCRIPTION
                   "Indicates that the host can access the switch from
                    HTTP/HTTPS interface if the host IP address matches the IP
                    address range provided in the entry."
               DEFVAL  { disable }
               ::= {     sisgm1040284lrtAccessMgmtConfEntry 5 }

    sisgm1040284lrtAccessMgmtSNMP OBJECT-TYPE
               SYNTAX      AdminMode
               MAX-ACCESS  read-create
               STATUS      current
               DESCRIPTION
                   "Indicates that the host can access the switch from SNMP
                    interface if the host IP address matches the IP address
                    range provided in the entry."
               DEFVAL  { disable }
               ::= {     sisgm1040284lrtAccessMgmtConfEntry 6 }

    sisgm1040284lrtAccessMgmtTelnetSSH OBJECT-TYPE
               SYNTAX      AdminMode
               MAX-ACCESS  read-create
               STATUS      current
               DESCRIPTION
                   "Indicates that the host can access the switch from
                    TELNET/SSH interface if the host IP address matches
                    the IP address range provided in the entry."
               DEFVAL  { disable }
               ::= {     sisgm1040284lrtAccessMgmtConfEntry 7 }

    sisgm1040284lrtAccessMgmtRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sisgm1040284lrtAccessMgmtConfEntry 8 }

--sisgm1040284lrtAccessMgmtStatistics

    sisgm1040284lrtAccessMgmtStatisticsClear OBJECT-TYPE
               SYNTAX      ActivateCmd
               MAX-ACCESS  read-write
               STATUS      current
               DESCRIPTION
                   "Clear all statistics."
               ::= {     sisgm1040284lrtAccessMgmtStatistics 1 }

--sisgm1040284lrtAccessMgmtStatisticsTable

    sisgm1040284lrtAccessMgmtStatisticsTable OBJECT-TYPE
               SYNTAX      SEQUENCE OF     SISGM1040284LRTAccessMgmtStatisticsEntry
               MAX-ACCESS  not-accessible
               STATUS      current
               DESCRIPTION
                   "The Access Mgmt Statistics Table. "
               ::= {     sisgm1040284lrtAccessMgmtStatistics 2 }

    sisgm1040284lrtAccessMgmtStatisticsEntry OBJECT-TYPE
               SYNTAX          SISGM1040284LRTAccessMgmtStatisticsEntry
               MAX-ACCESS  not-accessible
               STATUS      current
               DESCRIPTION
                   "The Access Mgmt Statistics Entry. "
               INDEX    {    sisgm1040284lrtAccessMgmtStatisticsInterface  }
               ::= {     sisgm1040284lrtAccessMgmtStatisticsTable 1 }

    SISGM1040284LRTAccessMgmtStatisticsEntry ::= SEQUENCE {
                 sisgm1040284lrtAccessMgmtStatisticsInterface         INTEGER,
                 sisgm1040284lrtAccessMgmtStatisticsReceivedPackets   Integer32,
                 sisgm1040284lrtAccessMgmtStatisticsAllowedPackets    Integer32,
                 sisgm1040284lrtAccessMgmtStatisticsDiscardedPackets  Integer32
                 }

    sisgm1040284lrtAccessMgmtStatisticsInterface OBJECT-TYPE
               SYNTAX      INTEGER { http(1), https(2), snmp(3), telnet(4), ssh (5) }
               MAX-ACCESS  not-accessible
               STATUS      current
               DESCRIPTION
                   "The interface type through which the remote host can
                    access the switch.
                    1: HTTP,
                    2: HTTPs,
                    3: SNMP,
                    4: TELNET,
                    5: SSH"
               ::= {     sisgm1040284lrtAccessMgmtStatisticsEntry 1 }

    sisgm1040284lrtAccessMgmtStatisticsReceivedPackets OBJECT-TYPE
               SYNTAX      Integer32(1..10000000)
               MAX-ACCESS  read-only
               STATUS      current
               DESCRIPTION
                   "Number of received packets from the interface when
                    access management mode is enabled. "
               ::= {     sisgm1040284lrtAccessMgmtStatisticsEntry 2 }

    sisgm1040284lrtAccessMgmtStatisticsAllowedPackets OBJECT-TYPE
               SYNTAX      Integer32(1..10000000)
               MAX-ACCESS  read-only
               STATUS      current
               DESCRIPTION
                   "Number of allowed packets from the interface when
                    access management mode is enabled. "
               ::= {     sisgm1040284lrtAccessMgmtStatisticsEntry 3 }

    sisgm1040284lrtAccessMgmtStatisticsDiscardedPackets OBJECT-TYPE
               SYNTAX      Integer32(1..10000000)
               MAX-ACCESS  read-only
               STATUS      current
               DESCRIPTION
                   "Number of discarded packets from the interface when
                    access management mode is enabled. "
               ::= {     sisgm1040284lrtAccessMgmtStatisticsEntry 4 }

-- =======================================================================================================================

--sisgm1040284lrtSSH                                                   OBJECT IDENTIFIER ::= { sisgm1040284lrtSecurity 7 }
--
--sisgm1040284lrtSSHMode OBJECT-TYPE
--   SYNTAX      Integer32(0|1)
--   MAX-ACCESS  read-write
--   STATUS      current
--   DESCRIPTION
--       "default: 1
--        0: disable
--        1: enable"
--   ::= { sisgm1040284lrtSSH 1 }
--
--sisgm1040284lrtSSHPort OBJECT-TYPE
--   SYNTAX      Integer32(1..65534)
--   MAX-ACCESS  read-write
--   STATUS      current
--   DESCRIPTION
--       "SSH service port number.
--        range : 1-65534, default : 22."
--   ::= { sisgm1040284lrtSSH 2 }

sisgm1040284lrtHTTPS                                                 OBJECT IDENTIFIER ::= { sisgm1040284lrtSecurity 8 }

--sisgm1040284lrtHTTPSMode OBJECT-TYPE
--   SYNTAX      Integer32(0|1)
--   MAX-ACCESS  read-write
--   STATUS      current
--   DESCRIPTION
--       "default: 1
--        0: disable
--        1: enable"
--   ::= { sisgm1040284lrtHTTPS 1 }
--
--sisgm1040284lrtHTTPSAutoRedirect OBJECT-TYPE
--   SYNTAX      Integer32(0|1)
--   MAX-ACCESS  read-write
--   STATUS      current
--   DESCRIPTION
--       "default: 0
--        0: disable
--        1: enable"
--   ::= { sisgm1040284lrtHTTPS 2 }
--
--sisgm1040284lrtHTTPSPort OBJECT-TYPE
--   SYNTAX      Integer32(1..65534)
--   MAX-ACCESS  read-write
--   STATUS      current
--   DESCRIPTION
--       "HTTPS service port number.
--        range : 1-65534, default : 443."
--   ::= { sisgm1040284lrtHTTPS 3 }

sisgm1040284lrtHTTPSCertificateMaintain OBJECT-TYPE
   SYNTAX      Integer32(2..3)
   MAX-ACCESS  read-write
   STATUS      current
   DESCRIPTION
       "2: Upload
		3: Generate"
   ::= { sisgm1040284lrtHTTPS 4 }

sisgm1040284lrtHTTPSCertificatePassPhrase OBJECT-TYPE
   SYNTAX      DisplayString
   MAX-ACCESS  read-write
   STATUS      current
   DESCRIPTION
       "Enter the pass phrase in this field if your uploading certificate is protected by a specific passphrase."
   ::= { sisgm1040284lrtHTTPS 5 }
   
sisgm1040284lrtHTTPSCertificateUpload OBJECT-TYPE
   SYNTAX      Integer32(0|1)
   MAX-ACCESS  read-write
   STATUS      current
   DESCRIPTION
       "default: 0
        0: TFTP
        1: URL"
   ::= { sisgm1040284lrtHTTPS 6 }
   
sisgm1040284lrtHTTPSFileUploadFileURL OBJECT-TYPE
   SYNTAX      DisplayString
   MAX-ACCESS  read-write
   STATUS      current
   DESCRIPTION
       "TFTP: filename
	    URL: URL"
   ::= { sisgm1040284lrtHTTPS 7 }
   
sisgm1040284lrtHTTPSFileUploadTFTPServer OBJECT-TYPE
   SYNTAX       IpAddress
   MAX-ACCESS   read-write
   STATUS       current
   DESCRIPTION
		"TFTP server IP address"
   ::= { sisgm1040284lrtHTTPS 8 }
   
sisgm1040284lrtHTTPSApply OBJECT-TYPE
   SYNTAX      Integer32(0|1)
   MAX-ACCESS  read-write
   STATUS      current
   DESCRIPTION
       "1: apply the above https settings"
   ::= { sisgm1040284lrtHTTPS 9 }
   
sisgm1040284lrtHTTPSCertificateStatus OBJECT-TYPE
   SYNTAX      DisplayString
   MAX-ACCESS  read-only
   STATUS      current
   DESCRIPTION
       "Display the current status of certificate on the switch."
   ::= { sisgm1040284lrtHTTPS 10 }   

sisgm1040284lrtAuthMethod                                            OBJECT IDENTIFIER ::= { sisgm1040284lrtSecurity 9 }

--
-- =======================================================================================================================
-- Start sisgm1040284lrtAuthMethodConfig group
-- =======================================================================================================================
--sisgm1040284lrtAuthMethodConfigTable

    sisgm1040284lrtAuthMethodConfigTable OBJECT-TYPE
               SYNTAX      SEQUENCE OF     SISGM1040284LRTAuthMethodConfigEntry
               MAX-ACCESS  not-accessible
               STATUS      current
               DESCRIPTION
                   "The Auth Method Config Table."
               ::= {     sisgm1040284lrtAuthMethod 1 }

    sisgm1040284lrtAuthMethodConfigEntry OBJECT-TYPE
               SYNTAX          SISGM1040284LRTAuthMethodConfigEntry
               MAX-ACCESS  not-accessible
               STATUS      current
               DESCRIPTION
                   "The Auth Method Config Entry."
               INDEX    {    sisgm1040284lrtAuthMethodConfigClient  }
               ::= {     sisgm1040284lrtAuthMethodConfigTable 1 }

    SISGM1040284LRTAuthMethodConfigEntry             ::= SEQUENCE {
                 sisgm1040284lrtAuthMethodConfigClient        INTEGER,
                 sisgm1040284lrtAuthMethodConfigMethod1       INTEGER,
                 sisgm1040284lrtAuthMethodConfigMethod2       INTEGER,
                 sisgm1040284lrtAuthMethodConfigMethod3       INTEGER,
                 sisgm1040284lrtAuthMethodConfigMethod4       INTEGER,
                 sisgm1040284lrtAuthMethodConfigServicePort   Integer32,
                 sisgm1040284lrtAuthMethodConfigFallback      Integer32
                 }

    sisgm1040284lrtAuthMethodConfigClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sisgm1040284lrtAuthMethodConfigEntry 1 }

    sisgm1040284lrtAuthMethodConfigMethod1 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sisgm1040284lrtAuthMethodConfigEntry 2 }

    sisgm1040284lrtAuthMethodConfigMethod2 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sisgm1040284lrtAuthMethodConfigEntry 3 }

    sisgm1040284lrtAuthMethodConfigMethod3 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sisgm1040284lrtAuthMethodConfigEntry 4 }

    sisgm1040284lrtAuthMethodConfigMethod4 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sisgm1040284lrtAuthMethodConfigEntry 5 }
               
    sisgm1040284lrtAuthMethodConfigServicePort OBJECT-TYPE
               SYNTAX      Integer32 (1..65535)
               MAX-ACCESS  read-write
               STATUS      current
               DESCRIPTION
                   "The network port number this client bound to provide service."
               ::= {     sisgm1040284lrtAuthMethodConfigEntry 6 }   

    sisgm1040284lrtAuthMethodConfigFallback OBJECT-TYPE
               SYNTAX      Integer32 (0..1)
               MAX-ACCESS  read-write
               STATUS      current
               DESCRIPTION
                   "Enable/Disable fallback to local authentication
                   0:Disable
                   1:Enable"
               ::= {     sisgm1040284lrtAuthMethodConfigEntry 7 }                 

               
    sisgm1040284lrtCommandAuthorizationMethodTable OBJECT-TYPE
               SYNTAX      SEQUENCE OF     SISGM1040284LRTCommandAuthorizationMethodEntry
               MAX-ACCESS  not-accessible
               STATUS      current
               DESCRIPTION
                   "The Command Authorized Method Config Table."
               ::= {     sisgm1040284lrtAuthMethod 2 }

    sisgm1040284lrtCommandAuthorizationMethodEntry OBJECT-TYPE
               SYNTAX          SISGM1040284LRTCommandAuthorizationMethodEntry
               MAX-ACCESS  not-accessible
               STATUS      current
               DESCRIPTION
                   "The Command Authorized Method Config Entry."
               INDEX    {    sisgm1040284lrtCommandAuthorizationMethodClient  }
               ::= {     sisgm1040284lrtCommandAuthorizationMethodTable 1 }

    SISGM1040284LRTCommandAuthorizationMethodEntry             ::= SEQUENCE {
                 sisgm1040284lrtCommandAuthorizationMethodClient       INTEGER,
                 sisgm1040284lrtCommandAuthorizationMethodMethod       Integer32,
                 sisgm1040284lrtCommandAuthorizationMethodCmdLvl       Integer32,
                 sisgm1040284lrtCommandAuthorizationMethodCfgCmd       Integer32,
                 sisgm1040284lrtCommandAuthorizationMethodFallback     Integer32
                 }

    sisgm1040284lrtCommandAuthorizationMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sisgm1040284lrtCommandAuthorizationMethodEntry 1 }

    sisgm1040284lrtCommandAuthorizationMethodMethod OBJECT-TYPE
               SYNTAX      Integer32
               MAX-ACCESS  read-write
               STATUS      current
               DESCRIPTION
                   "Method can be set to one of the following values:
                    0:no: Command authorization is disabled. 
					  User is granted access to CLI commands according to his privilege level.
                    3:tacacs: Use remote TACACS+ server(s) for command authorization. 
					  If all remote servers are offline, the user is granted access to CLI commands
					  according to his privilege level."
               ::= {     sisgm1040284lrtCommandAuthorizationMethodEntry 2 }

    sisgm1040284lrtCommandAuthorizationMethodCmdLvl OBJECT-TYPE
               SYNTAX      Integer32
               MAX-ACCESS  read-write
               STATUS      current
               DESCRIPTION
                   "Authorize all commands with a privilege level higher than or equal to this level.
                    Valid values are in the range 0 to 15."
               ::= {     sisgm1040284lrtCommandAuthorizationMethodEntry 3 }

    sisgm1040284lrtCommandAuthorizationMethodCfgCmd OBJECT-TYPE
               SYNTAX      Integer32
               MAX-ACCESS  read-write
               STATUS      current
               DESCRIPTION
                   "Also authorize configuration commands.
				   0:Disable
				   1:Enable"
               ::= {     sisgm1040284lrtCommandAuthorizationMethodEntry 4 }

    sisgm1040284lrtCommandAuthorizationMethodFallback OBJECT-TYPE
               SYNTAX      Integer32
               MAX-ACCESS  read-write
               STATUS      current
               DESCRIPTION
                   "This function is an auxiliary function of Authorization.
				   0:Disable
				   1:Enable"
               ::= {     sisgm1040284lrtCommandAuthorizationMethodEntry 5 }		   
               
    sisgm1040284lrtAccountingMethodTable OBJECT-TYPE
               SYNTAX      SEQUENCE OF     SISGM1040284LRTAccountingMethodEntry
               MAX-ACCESS  not-accessible
               STATUS      current
               DESCRIPTION
                   "The Accounting Method Config Table."
               ::= {     sisgm1040284lrtAuthMethod 3 }

    sisgm1040284lrtAccountingMethodEntry OBJECT-TYPE
               SYNTAX          SISGM1040284LRTAccountingMethodEntry
               MAX-ACCESS  not-accessible
               STATUS      current
               DESCRIPTION
                   "The Accounting Method Config Entry."
               INDEX    {    sisgm1040284lrtAccountingMethodClient  }
               ::= {     sisgm1040284lrtAccountingMethodTable 1 }

    SISGM1040284LRTAccountingMethodEntry             ::= SEQUENCE {
                 sisgm1040284lrtAccountingMethodClient       INTEGER,
                 sisgm1040284lrtAccountingMethodMethod       Integer32,
                 sisgm1040284lrtAccountingMethodCmdLvl       Integer32,
                 sisgm1040284lrtAccountingMethodCfgCmd       Integer32
                 }

    sisgm1040284lrtAccountingMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sisgm1040284lrtAccountingMethodEntry 1 }

    sisgm1040284lrtAccountingMethodMethod OBJECT-TYPE
               SYNTAX      Integer32
               MAX-ACCESS  read-write
               STATUS      current
               DESCRIPTION
                   "Method can be set to one of the following values:
                    0:no: Accounting is disabled.
                    3:tacacs: Use remote TACACS+ server(s) for accounting."
               ::= {     sisgm1040284lrtAccountingMethodEntry 2 }

    sisgm1040284lrtAccountingMethodCmdLvl OBJECT-TYPE
               SYNTAX      Integer32
               MAX-ACCESS  read-write
               STATUS      current
               DESCRIPTION
                   "Enable accounting of all commands with a privilege level higher than or equal to this level.
                    Valid values are in the range 0 to 15. Leave the field empty to disable command accounting."
               ::= {     sisgm1040284lrtAccountingMethodEntry 3 }

    sisgm1040284lrtAccountingMethodCfgCmd OBJECT-TYPE
               SYNTAX      Integer32
               MAX-ACCESS  read-write
               STATUS      current
               DESCRIPTION
                   "Enable exec (login) accounting.
				   0:Disable
				   1:Enable"
               ::= {     sisgm1040284lrtAccountingMethodEntry 4 }			          

--sisgm1040284lrtTELNET                                                 OBJECT IDENTIFIER ::= { sisgm1040284lrtSecurity 10 }
--
--sisgm1040284lrtTELNETPort OBJECT-TYPE
--   SYNTAX      Integer32(1..65534)
--   MAX-ACCESS  read-write
--   STATUS      current
--   DESCRIPTION
--       "TELNET service port number.
--        range : 1-65534, default : 23."
--   ::= { sisgm1040284lrtTELNET 1 }
--
--sisgm1040284lrtHTTP                                                   OBJECT IDENTIFIER ::= { sisgm1040284lrtSecurity 11 }
--
--sisgm1040284lrtHTTPPort OBJECT-TYPE
--   SYNTAX      Integer32(1..65534)
--   MAX-ACCESS  read-write
--   STATUS      current
--   DESCRIPTION
--       "HTTP service port number.
--        range : 1-65534, default : 80."
--   ::= { sisgm1040284lrtHTTP 1 }

-- =======================================================================================================================
sisgm1040284lrtMaintenance                                           OBJECT IDENTIFIER ::= { sisgm1040284lrtProductId 4 }

sisgm1040284lrtSoftware                      OBJECT IDENTIFIER   ::= {  sisgm1040284lrtMaintenance 3 }
sisgm1040284lrtConfig                        OBJECT IDENTIFIER   ::= {  sisgm1040284lrtMaintenance 4 }

--
-- =======================================================================================================================
-- Objects in the sisgm1040284lrtMaintenance Group
-- =======================================================================================================================
    sisgm1040284lrtRestartDevice OBJECT-TYPE
               SYNTAX      ActivateCmd
               MAX-ACCESS  read-write
               STATUS      current
               DESCRIPTION
                   "Command to restart the device."
               DEFVAL  { noAction }
               ::= {     sisgm1040284lrtMaintenance 1 }

    sisgm1040284lrtFactoryDefaults OBJECT-TYPE
               SYNTAX      ActivateCmd
               MAX-ACCESS  read-write
               STATUS      current
               DESCRIPTION
                   "Reset the configuration to Factory Defaults keep-ip."
               DEFVAL  { noAction }
               ::= {     sisgm1040284lrtMaintenance 2 }

--sisgm1040284lrtSoftware

    sisgm1040284lrtSoftwareUsername OBJECT-TYPE
               SYNTAX       DisplayString
               MAX-ACCESS   read-write
               STATUS       current
               DESCRIPTION
                    "Get/Set the username for 'tftp' firmware upgrading."
               ::= {     sisgm1040284lrtSoftware 1 }

    sisgm1040284lrtSoftwarePassword OBJECT-TYPE
               SYNTAX       DisplayString
               MAX-ACCESS   read-write
               STATUS       current
               DESCRIPTION
                    "Get/Set the password for 'tftp' firmware upgrading."
               ::= {     sisgm1040284lrtSoftware 2 }

    sisgm1040284lrtSoftwareIpAddress OBJECT-TYPE
               SYNTAX       IpAddress
               MAX-ACCESS   read-write
               STATUS       current
               DESCRIPTION
                    "Get/Set the firmware tftp server."
               ::= {     sisgm1040284lrtSoftware 3 }

    sisgm1040284lrtSoftwareFileName OBJECT-TYPE
               SYNTAX       DisplayString
               MAX-ACCESS   read-write
               STATUS       current
               DESCRIPTION
                    "Get/Set the path and filename for firmware upgrading."
               ::= {     sisgm1040284lrtSoftware 4 }

    sisgm1040284lrtSoftwareUpgradeCmd OBJECT-TYPE
               SYNTAX       INTEGER  {  noAction ( 0 ),
                                        tftpUpgrade ( 1 ),
                                        ftpUpgrade ( 2 )
                                     }
               MAX-ACCESS   read-write
               STATUS       current
               DESCRIPTION
                    "Firmware upgrade command.
                     noAction(0) - do nothing   (read only).
                     tftpUpgrade(1) - activate 'tftp' firmware upgrade
                     ftpUpgrade(2) - activate 'ftp' firmware upgrade"

               DEFVAL  { noAction }
               ::= {     sisgm1040284lrtSoftware 5 }

    sisgm1040284lrtSoftwareImageSelectionCmd OBJECT-TYPE
               SYNTAX       ActivateCmd
               MAX-ACCESS   read-write
               STATUS       current
               DESCRIPTION
                    "Activate firmware image selection.
                     noAction(0) - do nothing - returned upon get.
                     activate(1) - activate firmware image selection."
               DEFVAL  { noAction }
               ::= {     sisgm1040284lrtSoftware 6 }

    sisgm1040284lrtSaveStartCmd OBJECT-TYPE
               SYNTAX      ActivateCmd
               MAX-ACCESS  read-write
               STATUS      current
               DESCRIPTION
                   "This copies running-config to startup-config,
                   thereby ensuring that the currently active
                   configuration will be used at the next reboot. "
               DEFVAL  { noAction }
               ::= {     sisgm1040284lrtConfig 1 }

    sisgm1040284lrtConfigUsername OBJECT-TYPE
               SYNTAX       DisplayString
               MAX-ACCESS   read-write
               STATUS       current
               DESCRIPTION
                    "Get/Set the username for 'tftp' 'upload config' or 'download config'."
               ::= {     sisgm1040284lrtConfig 2 }

    sisgm1040284lrtConfigPassword OBJECT-TYPE
               SYNTAX       DisplayString
               MAX-ACCESS   read-write
               STATUS       current
               DESCRIPTION
                    "Get/Set the password for 'tftp' 'upload config' or 'download config'."
               ::= {     sisgm1040284lrtConfig 3 }

    sisgm1040284lrtConfigIpAddress OBJECT-TYPE
               SYNTAX       IpAddress
               MAX-ACCESS   read-write
               STATUS       current
               DESCRIPTION
                    "Get/Set the IP address for 'tftp' 'upload config'
                    or 'download config'."
               ::= {     sisgm1040284lrtConfig 4 }

    sisgm1040284lrtConfigFilename OBJECT-TYPE
               SYNTAX       DisplayString
               MAX-ACCESS   read-write
               STATUS       current
               DESCRIPTION
                    "Get/Set the filename in switch for 'tftp'
                    'upload config' or 'download config'."
               ::= {     sisgm1040284lrtConfig 5 }

    sisgm1040284lrtConfigFileTable OBJECT-TYPE
               SYNTAX      SEQUENCE OF     SISGM1040284LRTConfigFileEntry
               MAX-ACCESS  not-accessible
               STATUS      current
               DESCRIPTION
                   "The config file tabe."
               ::= {     sisgm1040284lrtConfig 6 }

    sisgm1040284lrtConfigFileEntry OBJECT-TYPE
               SYNTAX          SISGM1040284LRTConfigFileEntry
               MAX-ACCESS  not-accessible
               STATUS      current
               DESCRIPTION
                   "an entry in the config file tabe."
               INDEX    {     sisgm1040284lrtConfigFileIndex }
               ::= {     sisgm1040284lrtConfigFileTable 1 }

    SISGM1040284LRTConfigFileEntry             ::= SEQUENCE {
                sisgm1040284lrtConfigFileIndex         Integer32,
                sisgm1040284lrtShowConfigFileName      DisplayString,
                sisgm1040284lrtActivateConfigCmd       ActivateCmd,
                sisgm1040284lrtDeleteConfigCmd         ActivateCmd,
                sisgm1040284lrtUploadConfigCmd         INTEGER,
                sisgm1040284lrtDownloadConfigCmd       INTEGER
                }

    sisgm1040284lrtConfigFileIndex OBJECT-TYPE
               SYNTAX      Integer32(1..255)
               MAX-ACCESS  not-accessible
               STATUS      current
               DESCRIPTION
                   "The config file index."
               ::= {     sisgm1040284lrtConfigFileEntry 1 }

    sisgm1040284lrtShowConfigFileName OBJECT-TYPE
               SYNTAX      DisplayString
               MAX-ACCESS  read-write
               STATUS      current
               DESCRIPTION
                   "Shows the config file name. Without config filename:'NewConfig'
                   is temp file when 'activate upload
                   config' can 'create new file' and 'change create filename'."
               ::= {     sisgm1040284lrtConfigFileEntry 2 }

    sisgm1040284lrtActivateConfigCmd OBJECT-TYPE
               SYNTAX       ActivateCmd
               MAX-ACCESS   read-write
               STATUS       current
               DESCRIPTION
                    "Activate config command.
                     noAction(0) : do nothing  (read only).
                     activate(1) : activate the config"
               DEFVAL  { noAction }
               ::= {     sisgm1040284lrtConfigFileEntry 3 }

    sisgm1040284lrtDeleteConfigCmd OBJECT-TYPE
               SYNTAX       ActivateCmd
               MAX-ACCESS   read-write
               STATUS       current
               DESCRIPTION
                    "Delete config command.
                     noAction(0) : do nothing  (read only).
                     activate(1) : delete the config"
               DEFVAL  { noAction }
               ::= {     sisgm1040284lrtConfigFileEntry 4 }

    sisgm1040284lrtDownloadConfigCmd OBJECT-TYPE
               SYNTAX       INTEGER  {  noAction ( 0 ),
                                        tftpDownload ( 1 )
                                        --ftpDownload ( 2 )
                                     }
               MAX-ACCESS   read-write
               STATUS       current
               DESCRIPTION
                    "Download config command.
                     noAction   (0) - do nothing   (read only).
                     tftpDownload (1) - activate 'tftp' config download."
               DEFVAL  { noAction }
               ::= {     sisgm1040284lrtConfigFileEntry 5 }

    sisgm1040284lrtUploadConfigCmd OBJECT-TYPE
               SYNTAX       INTEGER  {  noAction ( 0 ),
                                        tftpUpload ( 1 )
                                        --ftpUpload ( 2 )
                                     }
               MAX-ACCESS   read-write
               STATUS       current
               DESCRIPTION
                    "Upload config command.
                     noAction   (0) - do nothing   (read only).
                     tftpUpload (1) - activate 'tftp' config upload.
					 For merge/replace running-config:
					 1:merge
					 3:replace"
               DEFVAL  { noAction }
               ::= {     sisgm1040284lrtConfigFileEntry 6 }

-- =======================================================================================================================
sisgm1040284lrtDiagnostics                                           OBJECT IDENTIFIER ::= { sisgm1040284lrtMaintenance 5 }

sisgm1040284lrtPingIpAddress OBJECT-TYPE
   SYNTAX      IpAddress
   MAX-ACCESS  read-write
   STATUS      current
   DESCRIPTION
       " The destination IP Address. "
   ::= { sisgm1040284lrtDiagnostics 1 }

sisgm1040284lrtPingSize OBJECT-TYPE
   SYNTAX      Integer32(60..1400)
   MAX-ACCESS  read-write
   STATUS      current
   DESCRIPTION
       " Size of ICMP echo packet.
         range : 60-1400, default : 64. "
   ::= { sisgm1040284lrtDiagnostics 2 }

sisgm1040284lrtDoPingConfig OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sisgm1040284lrtDiagnostics 3 }

sisgm1040284lrtPingResult OBJECT-TYPE
   SYNTAX      DisplayString
   MAX-ACCESS  read-only
   STATUS      current
   DESCRIPTION
       " Show ping result. "
   ::= { sisgm1040284lrtDiagnostics 4 }

sisgm1040284lrtPing6IpAddress OBJECT-TYPE
   SYNTAX      DisplayString
   MAX-ACCESS  read-write
   STATUS      current
   DESCRIPTION
       " The destination IPv6 Address. "
   ::= { sisgm1040284lrtDiagnostics 5 }

sisgm1040284lrtPing6Size OBJECT-TYPE
   SYNTAX      Integer32(60..1400)
   MAX-ACCESS  read-write
   STATUS      current
   DESCRIPTION
       " Size of ICMP echo packet.
         range : 60-1400. "
   ::= { sisgm1040284lrtDiagnostics 6 }

sisgm1040284lrtPing6EgressInterface OBJECT-TYPE
   SYNTAX      Integer32(1..4095)
   MAX-ACCESS  read-write
   STATUS      current
   DESCRIPTION
       "The VLAN ID (VID) of the specific egress IPv6 interface which ICMP packet goes."
   ::= { sisgm1040284lrtDiagnostics 7 }
   
sisgm1040284lrtDoPing6Config OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sisgm1040284lrtDiagnostics 8 }

sisgm1040284lrtPing6Result OBJECT-TYPE
   SYNTAX      DisplayString
   MAX-ACCESS  read-only
   STATUS      current
   DESCRIPTION
       " Show ping result. "
   ::= { sisgm1040284lrtDiagnostics 9 }

sisgm1040284lrttracerouteIpAddress OBJECT-TYPE
   SYNTAX      DisplayString
   MAX-ACCESS  read-write
   STATUS      current
   DESCRIPTION
       " The destination IP Address. "
   ::= { sisgm1040284lrtDiagnostics 10 }

sisgm1040284lrttracerouteProtocol OBJECT-TYPE
   SYNTAX      Integer32(0..2)
   MAX-ACCESS  read-write
   STATUS      current
   DESCRIPTION
       " Specify protocol including icmp=0, udp=1 and tcp=2.
         range : 0-2, default : 0. "
   ::= { sisgm1040284lrtDiagnostics 11 }

sisgm1040284lrttracerouteWaittime OBJECT-TYPE
   SYNTAX      Integer32(1..60)
   MAX-ACCESS  read-write
   STATUS      current
   DESCRIPTION
       " Specify wait time for waiting probe packets come back.
         range : 1-60(sec), default : 5(sec). "
   ::= { sisgm1040284lrtDiagnostics 12 }

sisgm1040284lrttracerouteMaxTTL OBJECT-TYPE
   SYNTAX      Integer32(1..255)
   MAX-ACCESS  read-write
   STATUS      current
   DESCRIPTION
       " Specify max TTL.
         range : 1-255, default : 30. "
   ::= { sisgm1040284lrtDiagnostics 13 }

sisgm1040284lrttracerouteNqueries OBJECT-TYPE
   SYNTAX      Integer32(1..10)
   MAX-ACCESS  read-write
   STATUS      current
   DESCRIPTION
       " Specify number of probe packets.
         range : 1-10, default : 3. "
   ::= { sisgm1040284lrtDiagnostics 14 }

sisgm1040284lrtDotracerouteConfig OBJECT-TYPE
   SYNTAX      Integer32(1)
   MAX-ACCESS  read-write
   STATUS      current
   DESCRIPTION
       "Do traceroute-config.
         Get this OID always return zero.
         1 - ping. Uses the traceroute program to get
         ip address of the middle gateway. "
   ::= { sisgm1040284lrtDiagnostics 15 }

sisgm1040284lrttracerouteResult OBJECT-TYPE
   SYNTAX      DisplayString
   MAX-ACCESS  read-only
   STATUS      current
   DESCRIPTION
       " Show traceroute result. "
   ::= { sisgm1040284lrtDiagnostics 16 }

sisgm1040284lrtCableDiagnostics                                           OBJECT IDENTIFIER ::= { sisgm1040284lrtDiagnostics 17 }

sisgm1040284lrtCableDiagnosticsTest OBJECT-TYPE
   SYNTAX      Integer32
   MAX-ACCESS  read-write
   STATUS      current
   DESCRIPTION
       "Run Cable Diagnostics.
        port, range : 1 - port number."
   ::= { sisgm1040284lrtCableDiagnostics 1 }

sisgm1040284lrtCableDiagnosticsTable OBJECT-TYPE
   SYNTAX      SEQUENCE OF SISGM1040284LRTCableDiagnosticsEntry
   MAX-ACCESS  not-accessible
   STATUS      current
   DESCRIPTION
       " "
   ::= { sisgm1040284lrtCableDiagnostics 2 }

sisgm1040284lrtCableDiagnosticsEntry OBJECT-TYPE
   SYNTAX      SISGM1040284LRTCableDiagnosticsEntry
   MAX-ACCESS  not-accessible
   STATUS      current
   DESCRIPTION
       " "
   INDEX    { sisgm1040284lrtCableDiagnosticsPort  }
   ::= { sisgm1040284lrtCableDiagnosticsTable 1 }

SISGM1040284LRTCableDiagnosticsEntry ::= SEQUENCE {
   sisgm1040284lrtCableDiagnosticsPort        Integer32,
   sisgm1040284lrtCableDiagnosticsLinkStatus  DisplayString,
   sisgm1040284lrtCableDiagnosticsTestResult  DisplayString,
   sisgm1040284lrtCableDiagnosticsLength      DisplayString
}

sisgm1040284lrtCableDiagnosticsPort OBJECT-TYPE
   SYNTAX      Integer32
   MAX-ACCESS  not-accessible
   STATUS      current
   DESCRIPTION
       "port index"
   ::= { sisgm1040284lrtCableDiagnosticsEntry 1 }

sisgm1040284lrtCableDiagnosticsLinkStatus OBJECT-TYPE
   SYNTAX      DisplayString
   MAX-ACCESS  read-only
   STATUS      current
   DESCRIPTION
       "The status of the cable."
   ::= { sisgm1040284lrtCableDiagnosticsEntry 2 }

sisgm1040284lrtCableDiagnosticsTestResult OBJECT-TYPE
   SYNTAX      DisplayString
   MAX-ACCESS  read-only
   STATUS      current
   DESCRIPTION
       "Test Result of the cable."
   ::= { sisgm1040284lrtCableDiagnosticsEntry 3 }

sisgm1040284lrtCableDiagnosticsLength OBJECT-TYPE
   SYNTAX      DisplayString
   MAX-ACCESS  read-only
   STATUS      current
   DESCRIPTION
       "The length (in meters) of the cable."
   ::= { sisgm1040284lrtCableDiagnosticsEntry 4 }

sisgm1040284lrtSwitchRebootSchedule OBJECT IDENTIFIER ::= { sisgm1040284lrtMaintenance 6 }   

sisgm1040284lrtSwitchRebootMode OBJECT-TYPE
   SYNTAX      Integer32
   MAX-ACCESS  read-write
   STATUS      current
   DESCRIPTION
       "Switch Reboot Mode.
	    0:disable
		1:enable"
   ::= { sisgm1040284lrtSwitchRebootSchedule 1 }

sisgm1040284lrtSwitchRebootTimeTable OBJECT-TYPE
   SYNTAX      SEQUENCE OF SISGM1040284LRTSwitchRebootTimeEntry
   MAX-ACCESS  not-accessible
   STATUS      current
   DESCRIPTION
       " Configure the Switch reboot time. "
   ::= { sisgm1040284lrtSwitchRebootSchedule 2 }

sisgm1040284lrtSwitchRebootTimeEntry OBJECT-TYPE
   SYNTAX      SISGM1040284LRTSwitchRebootTimeEntry
   MAX-ACCESS  not-accessible
   STATUS      current
   DESCRIPTION
       " "
   INDEX    { sisgm1040284lrtSwitchRebootWeekIndex  }
   ::= { sisgm1040284lrtSwitchRebootTimeTable 1 }

SISGM1040284LRTSwitchRebootTimeEntry ::= SEQUENCE {
   sisgm1040284lrtSwitchRebootWeekIndex	       Integer32,
   sisgm1040284lrtSwitchRebootTimeHour           Integer32,
   sisgm1040284lrtSwitchRebootTimeMinute         Integer32
}

sisgm1040284lrtSwitchRebootWeekIndex OBJECT-TYPE
   SYNTAX      Integer32 (1..7)
   MAX-ACCESS  not-accessible
   STATUS      current
   DESCRIPTION
       "Switch reboot week index.
	   1: Sun, 2: Mon, 3:Tue, 4: Wed, 5: Thu, 6: Fri, 7: Sat"
   ::= { sisgm1040284lrtSwitchRebootTimeEntry 1 }

sisgm1040284lrtSwitchRebootTimeHour OBJECT-TYPE
   SYNTAX      Integer32 (-1..23)
   MAX-ACCESS  read-write
   STATUS      current
   DESCRIPTION
       "Switch Reboot Time (Hour). Range: 0-23. 
	   -1:disable"
   ::= { sisgm1040284lrtSwitchRebootTimeEntry 2 }

sisgm1040284lrtSwitchRebootTimeMinute OBJECT-TYPE
   SYNTAX      Integer32 (-1..55)
   MAX-ACCESS  read-write
   STATUS      current
   DESCRIPTION
       "Switch Reboot Time (Minute). Range:0,5,10,...,55. 
	   -1:disable"
   ::= { sisgm1040284lrtSwitchRebootTimeEntry 3 }    
   
-- =======================================================================================================================
sisgm1040284lrtTrap                                                  OBJECT IDENTIFIER ::= { sisgm1040284lrtProductId 5 }

sisgm1040284lrtTrapEvent                                             OBJECT IDENTIFIER ::= { sisgm1040284lrtTrap 1 }

sisgm1040284lrtTrapEventNotifications                                OBJECT IDENTIFIER ::= { sisgm1040284lrtTrapEvent 0 }

sisgm1040284lrtEmergency NOTIFICATION-TYPE
  OBJECTS   { sisgm1040284lrtInformation }
  STATUS        current
    DESCRIPTION
        "The severity level is Emergency. Emergency conditions."
    ::= { sisgm1040284lrtTrapEventNotifications 1 }

sisgm1040284lrtAlert NOTIFICATION-TYPE
  OBJECTS   { sisgm1040284lrtInformation }
  STATUS        current
    DESCRIPTION
        "The severity level is Alert. Alert conditions."
    ::= { sisgm1040284lrtTrapEventNotifications 2 }

sisgm1040284lrtCritical NOTIFICATION-TYPE
  OBJECTS   { sisgm1040284lrtInformation }
  STATUS        current
    DESCRIPTION
        "The severity level is Critical. Critical conditions."
    ::= { sisgm1040284lrtTrapEventNotifications 3 }

sisgm1040284lrtError NOTIFICATION-TYPE
  OBJECTS   { sisgm1040284lrtInformation }
  STATUS        current
    DESCRIPTION
        "The severity level is Error. Error conditions."
    ::= { sisgm1040284lrtTrapEventNotifications 4 }

sisgm1040284lrtWarning NOTIFICATION-TYPE
  OBJECTS   { sisgm1040284lrtInformation }
  STATUS        current
    DESCRIPTION
        "The severity level is Warning. Warning conditions."
    ::= { sisgm1040284lrtTrapEventNotifications 5 }

sisgm1040284lrtNotice NOTIFICATION-TYPE
  OBJECTS   { sisgm1040284lrtInformation }
  STATUS        current
    DESCRIPTION
        "The severity level is Notice. Notice conditions."
    ::= { sisgm1040284lrtTrapEventNotifications 6 }

sisgm1040284lrtInformational NOTIFICATION-TYPE
  OBJECTS   { sisgm1040284lrtInformation }
  STATUS        current
    DESCRIPTION
        "The severity level is Informational. Informational conditions."
    ::= { sisgm1040284lrtTrapEventNotifications 7 }

sisgm1040284lrtDebug NOTIFICATION-TYPE
  OBJECTS   { sisgm1040284lrtInformation }
  STATUS        current
    DESCRIPTION
        "The severity level is Debug. Debug conditions."
    ::= { sisgm1040284lrtTrapEventNotifications 8 }

sisgm1040284lrtTrapVariable                                          OBJECT IDENTIFIER ::= { sisgm1040284lrtTrap 2 }

sisgm1040284lrtInformation OBJECT-TYPE
    SYNTAX      DisplayString
    MAX-ACCESS  read-only
    STATUS      current
    DESCRIPTION
        "Trap information."
    ::= { sisgm1040284lrtTrapVariable 1 }
	
sisgm1040284lrtZTPTrap                                             OBJECT IDENTIFIER ::= { sisgm1040284lrtTrap 3 }

sisgm1040284lrtZTPTrapEvent                                        OBJECT IDENTIFIER ::= { sisgm1040284lrtZTPTrap 0 }

sisgm1040284lrtZTPOnboardTrap NOTIFICATION-TYPE
  OBJECTS   { sysObjectID, sisgm1040284lrtSnmpSystemVersion, sisgm1040284lrtSnmpSystemReadCommunity,
              sisgm1040284lrtSnmpSystemWriteCommunity, sisgm1040284lrtSystemInfoSerialNumber, 
              sisgm1040284lrtSystemInfoHostMACAddress, sisgm1040284lrtIPInterfacesIPv4Address }
  STATUS        current
    DESCRIPTION
        "The switch information."
    ::= { sisgm1040284lrtZTPTrapEvent 1 }


END
