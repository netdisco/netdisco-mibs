TN-SISPM1040582LRT-FUNCTION-MIB DEFINITIONS ::= BEGIN

IMPORTS
    DisplayString,MacAddress,TEXTUAL-CONVENTION,RowStatus                                              FROM SNMPv2-TC
    MODULE-COMPLIANCE,OBJECT-GROUP, NOTIFICATION-GROUP                                                 FROM SNMPv2-CONF
    ifIndex                                                                                            FROM IF-MIB
    enterprises,MODULE-IDENTITY,OBJECT-TYPE,NOTIFICATION-TYPE,Unsigned32,Integer32,Counter32,Counter64,IpAddress  FROM SNMPv2-SMI
--  PortList                                                                                           FROM Q-BRIDGE-MIB
    InetAddress, InetAddressType                                                                       FROM INET-ADDRESS-MIB
    OwnerString                                                                                        FROM RMON-MIB
    SnmpAdminString                                                                                    FROM SNMP-FRAMEWORK-MIB;
--  MacAddress FROM BRIDGE-MIB;

transition MODULE-IDENTITY
        LAST-UPDATED "202203160733Z"
        ORGANIZATION "Corp."
        CONTACT-INFO
            " "
        DESCRIPTION "Managed Hardened PoE++ Switch (8) 10/100/1000Base-T PoE++ Ports + (2) 100/1000Base-X SFP Slot"
		REVISION      "201405300000Z"
        DESCRIPTION
		"Rev 1.0 Initial version."
        ::= { enterprises 868 }


-- =======================================================================================================================

     OperState ::= TEXTUAL-CONVENTION
       STATUS         current
       DESCRIPTION
                      "Oper state."
       SYNTAX         INTEGER  { up ( 1 ) , down ( 2 ) }

     AdminMode ::= TEXTUAL-CONVENTION
       STATUS      current
       DESCRIPTION
            "The Admin state - default: disable(0)."
       SYNTAX  INTEGER { disable(0), enable(1) }

     AdminMode2 ::= TEXTUAL-CONVENTION
       STATUS      current
       DESCRIPTION
            "The Admin state - default: disable(0)."
       SYNTAX  INTEGER { disable(0), enable(1), notSupported(2) }

     ActivateCmd ::= TEXTUAL-CONVENTION
       STATUS      current
       DESCRIPTION
            "Used to activate commands. default: noAction(0). "
       SYNTAX         INTEGER  {  noAction ( 0 ),
                                  activate ( 1 )
                               }

     KeyType ::= TEXTUAL-CONVENTION
       STATUS      current
       DESCRIPTION
           "The key type specifying the key generated for frames received
            on the port.
            0 : Normal,
            1 : Double Tag,
            2 : IP Address,
            3 : MAC and IP Address."
        SYNTAX      INTEGER  { normal  ( 0 ),
                               doubleTag ( 1 ),
                               ipAddr ( 2 ),
                               macAndIpAddr ( 3 )
                             }

     FrameRate ::= TEXTUAL-CONVENTION
       STATUS      current
       DESCRIPTION
           "The values for frame rate"
       SYNTAX       INTEGER {
                            threeHundredFramesPerSec (0),
                            oneHundredFramesPerSec (1),
                            tenFramesPerSec (2),
                            oneFramePerSec (3),
                            sixFramesPerMin (4),
                            oneFramePerMin  (5),
                            sixFramesPerHour (6)
                            }

     DayOfWeek ::= TEXTUAL-CONVENTION
       STATUS      current
       DESCRIPTION
            "Used to set the days of the week."
       SYNTAX       INTEGER {mon(1),tue(2),wed(3),thur(4),
                             fri(5),sat(6),sun(7) }

     Month ::= TEXTUAL-CONVENTION
       STATUS      current
       DESCRIPTION
            "Used to set the month."
       SYNTAX       INTEGER {jan(1),feb(2),march(3),april(4),
                             may(5),june(6),july(7),aug(8),
                             sept(9),oct(10),nov(11),dec(12)}


switch                                                          OBJECT IDENTIFIER ::= { transition 2 }

sispm1040582lrtProductLevel1  OBJECT IDENTIFIER ::= { switch 80 }
sispm1040582lrtProductId  OBJECT IDENTIFIER ::= { sispm1040582lrtProductLevel1 8 }


sispm1040582lrtSystem                                                OBJECT IDENTIFIER ::= { sispm1040582lrtProductId 1 }

sispm1040582lrtSystemInformation                                     OBJECT IDENTIFIER ::= { sispm1040582lrtSystem 1 }

sispm1040582lrtSystemInfoTable OBJECT-TYPE
   SYNTAX      SEQUENCE OF SISPM1040582LRTSystemInfoEntry
   MAX-ACCESS  not-accessible
   STATUS      current
   DESCRIPTION
       " Configure System Information Table. "
   ::= { sispm1040582lrtSystemInformation 1 }

sispm1040582lrtSystemInfoEntry OBJECT-TYPE
   SYNTAX      SISPM1040582LRTSystemInfoEntry
   MAX-ACCESS  not-accessible
   STATUS      current
   DESCRIPTION
       " "
   INDEX    { sispm1040582lrtSystemInfoSwitchIndex }
   ::= { sispm1040582lrtSystemInfoTable 1 }

SISPM1040582LRTSystemInfoEntry ::= SEQUENCE {
   sispm1040582lrtSystemInfoSwitchIndex        Integer32,
   sispm1040582lrtSystemInfoModelName          DisplayString,
   sispm1040582lrtSystemInfoSystemDescript     DisplayString,
   sispm1040582lrtSystemInfoLocation           DisplayString,
   sispm1040582lrtSystemInfoContact            DisplayString,
   sispm1040582lrtSystemInfoSystemName         DisplayString,
   sispm1040582lrtSystemInfoSystemDate         DisplayString,
   sispm1040582lrtSystemInfoSystemUptime       DisplayString,
   sispm1040582lrtSystemInfoBootloaderVersion  DisplayString,
   sispm1040582lrtSystemInfoFirmwareVersion    DisplayString,
   sispm1040582lrtSystemInfoHardwareVersion    DisplayString,
   sispm1040582lrtSystemInfoMechanicalVersion  DisplayString,
   sispm1040582lrtSystemInfoSerialNumber       DisplayString,
   sispm1040582lrtSystemInfoHostMACAddress     DisplayString,
   sispm1040582lrtSystemInfoMemory             DisplayString,
   sispm1040582lrtSystemInfoFlash              DisplayString,
   sispm1040582lrtSystemInfoPowerStatus        DisplayString,
   sispm1040582lrtSystemInfoPowers             DisplayString,
   sispm1040582lrtSystemInfoTemperatureStatus  DisplayString,
--   sispm1040582lrtSystemInfoTemperature1       DisplayString,
--   sispm1040582lrtSystemInfoTemperature2       DisplayString,
   sispm1040582lrtSystemInfoCPULoad            DisplayString,
   sispm1040582lrtSystemInfoPoEFirmwareVersion DisplayString
}

sispm1040582lrtSystemInfoSwitchIndex OBJECT-TYPE
   SYNTAX      Integer32 (1..16)
   MAX-ACCESS  not-accessible
   STATUS      current
   DESCRIPTION
       "Switch Index."
   ::= { sispm1040582lrtSystemInfoEntry 1 }

sispm1040582lrtSystemInfoModelName OBJECT-TYPE
   SYNTAX       DisplayString
   MAX-ACCESS   read-only
   STATUS       current
   DESCRIPTION
       " "
   ::= { sispm1040582lrtSystemInfoEntry 2 }

sispm1040582lrtSystemInfoSystemDescript OBJECT-TYPE
   SYNTAX       DisplayString
   MAX-ACCESS   read-only
   STATUS       current
   DESCRIPTION
       " "
   ::= { sispm1040582lrtSystemInfoEntry 3 }

sispm1040582lrtSystemInfoLocation OBJECT-TYPE
   SYNTAX       DisplayString
   MAX-ACCESS   read-write
   STATUS       current
   DESCRIPTION
       " "
   ::= { sispm1040582lrtSystemInfoEntry 4 }

sispm1040582lrtSystemInfoContact OBJECT-TYPE
   SYNTAX       DisplayString
   MAX-ACCESS   read-write
   STATUS       current
   DESCRIPTION
       " "
   ::= { sispm1040582lrtSystemInfoEntry 5 }

sispm1040582lrtSystemInfoSystemName OBJECT-TYPE
   SYNTAX       DisplayString
   MAX-ACCESS   read-write
   STATUS       current
   DESCRIPTION
       " "
   ::= { sispm1040582lrtSystemInfoEntry 6 }

sispm1040582lrtSystemInfoSystemDate OBJECT-TYPE
   SYNTAX       DisplayString
   MAX-ACCESS   read-only
   STATUS       current
   DESCRIPTION
       " "
   ::= { sispm1040582lrtSystemInfoEntry 7 }

sispm1040582lrtSystemInfoSystemUptime OBJECT-TYPE
   SYNTAX       DisplayString
   MAX-ACCESS   read-only
   STATUS       current
   DESCRIPTION
       " "
   ::= { sispm1040582lrtSystemInfoEntry 8 }

sispm1040582lrtSystemInfoBootloaderVersion OBJECT-TYPE
   SYNTAX       DisplayString
   MAX-ACCESS   read-only
   STATUS       current
   DESCRIPTION
       " "
   ::= { sispm1040582lrtSystemInfoEntry 9 }

sispm1040582lrtSystemInfoFirmwareVersion OBJECT-TYPE
   SYNTAX       DisplayString
   MAX-ACCESS   read-only
   STATUS       current
   DESCRIPTION
       " "
   ::= { sispm1040582lrtSystemInfoEntry 10 }

sispm1040582lrtSystemInfoHardwareVersion OBJECT-TYPE
   SYNTAX       DisplayString
   MAX-ACCESS   read-only
   STATUS       current
   DESCRIPTION
       " "
   ::= { sispm1040582lrtSystemInfoEntry 11 }

sispm1040582lrtSystemInfoMechanicalVersion OBJECT-TYPE
   SYNTAX       DisplayString
   MAX-ACCESS   read-only
   STATUS       current
   DESCRIPTION
       " "
   ::= { sispm1040582lrtSystemInfoEntry 12 }

sispm1040582lrtSystemInfoSerialNumber OBJECT-TYPE
   SYNTAX       DisplayString
   MAX-ACCESS   read-only
   STATUS       current
   DESCRIPTION
       " "
   ::= { sispm1040582lrtSystemInfoEntry 13 }

sispm1040582lrtSystemInfoHostMACAddress OBJECT-TYPE
   SYNTAX       DisplayString
   MAX-ACCESS   read-only
   STATUS       current
   DESCRIPTION
       " "
   ::= { sispm1040582lrtSystemInfoEntry 14 }

sispm1040582lrtSystemInfoMemory OBJECT-TYPE
   SYNTAX       DisplayString
   MAX-ACCESS   read-only
   STATUS       current
   DESCRIPTION
       " "
   ::= { sispm1040582lrtSystemInfoEntry 15 }

sispm1040582lrtSystemInfoFlash OBJECT-TYPE
   SYNTAX       DisplayString
   MAX-ACCESS   read-only
   STATUS       current
   DESCRIPTION
       " "
   ::= { sispm1040582lrtSystemInfoEntry 16 }

sispm1040582lrtSystemInfoPowerStatus OBJECT-TYPE
   SYNTAX       DisplayString
   MAX-ACCESS   read-only
   STATUS       current
   DESCRIPTION
       " "
   ::= { sispm1040582lrtSystemInfoEntry 19 }
   
sispm1040582lrtSystemInfoPowers OBJECT-TYPE
   SYNTAX       DisplayString
   MAX-ACCESS   read-only
   STATUS       current
   DESCRIPTION
       " "
   ::= { sispm1040582lrtSystemInfoEntry 20 }
   
sispm1040582lrtSystemInfoTemperatureStatus OBJECT-TYPE
   SYNTAX       DisplayString
   MAX-ACCESS   read-only
   STATUS       current
   DESCRIPTION
       " "
   ::= { sispm1040582lrtSystemInfoEntry 21 }   

--sispm1040582lrtSystemInfoTemperature1 OBJECT-TYPE
--   SYNTAX       DisplayString
--   MAX-ACCESS   read-only
--   STATUS       current
--   DESCRIPTION
--       " "
--   ::= { sispm1040582lrtSystemInfoEntry 22 }
--
--sispm1040582lrtSystemInfoTemperature2 OBJECT-TYPE
--   SYNTAX       DisplayString
--   MAX-ACCESS   read-only
--   STATUS       current
--   DESCRIPTION
--       " "
--   ::= { sispm1040582lrtSystemInfoEntry 23 }
   
sispm1040582lrtSystemInfoCPULoad OBJECT-TYPE
   SYNTAX       DisplayString
   MAX-ACCESS   read-only
   STATUS       current
   DESCRIPTION
       "CPU Utilization."
   ::= { sispm1040582lrtSystemInfoEntry 24 }     
 
sispm1040582lrtSystemInfoPoEFirmwareVersion OBJECT-TYPE
   SYNTAX       DisplayString
   MAX-ACCESS   read-only
   STATUS       current
   DESCRIPTION
       " "
   ::= { sispm1040582lrtSystemInfoEntry 26 } 
   
sispm1040582lrtSystemTimeConf                                    OBJECT IDENTIFIER ::= { sispm1040582lrtSystem 2 }

sispm1040582lrtSystemNTP                                      OBJECT IDENTIFIER ::= { sispm1040582lrtSystemTimeConf  1 }

sispm1040582lrtSystemTime                                      OBJECT IDENTIFIER ::= { sispm1040582lrtSystemTimeConf  2 }
sispm1040582lrtSystemTimeZone                              OBJECT IDENTIFIER ::= { sispm1040582lrtSystemTime 1 }
sispm1040582lrtSystemTimeDaylightSaving             OBJECT IDENTIFIER ::= { sispm1040582lrtSystemTime 2 }
sispm1040582lrtSystemTimeConfiguration              OBJECT IDENTIFIER ::= { sispm1040582lrtSystemTime 3 }

    --
-- =======================================================================================================================
-- Objects in the sispm1040582lrtSystemNTP Group
-- =======================================================================================================================
    sispm1040582lrtSystemNTPMode OBJECT-TYPE
               SYNTAX       INTEGER {useLocal(0),useNTP(1)}
               MAX-ACCESS   read-write
               STATUS       current
               DESCRIPTION
                   "The system NTP Mode.
                    useLocal(0) : Use Local Settings,
                    useNTP(1)   : Use NTP Server."
               DEFVAL  { useLocal }
               ::= {     sispm1040582lrtSystemNTP 1 }

    sispm1040582lrtSystemNTPServer1    OBJECT-TYPE
               SYNTAX            DisplayString
               MAX-ACCESS        read-write
               STATUS            current
               DESCRIPTION
                   "Get/Set the NTP Time Server1.
                    You can use the IP address or domain name."
               ::= {     sispm1040582lrtSystemNTP 2 }

    sispm1040582lrtSystemNTPServer2    OBJECT-TYPE
               SYNTAX            DisplayString
               MAX-ACCESS        read-write
               STATUS            current
               DESCRIPTION
                   "Get/Set the NTP Time Server2.
                    You can use the IP address or domain name."
               ::= {     sispm1040582lrtSystemNTP 3 }

    sispm1040582lrtSystemNTPServer3    OBJECT-TYPE
               SYNTAX            DisplayString
               MAX-ACCESS        read-write
               STATUS            current
               DESCRIPTION
                   "Get/Set the NTP Time Server3.
                    You can use the IP address or domain name."
               ::= {     sispm1040582lrtSystemNTP 4 }

    sispm1040582lrtSystemNTPServer4    OBJECT-TYPE
               SYNTAX            DisplayString
               MAX-ACCESS        read-write
               STATUS            current
               DESCRIPTION
                   "Get/Set the NTP Time Server4.
                    You can use the IP address or domain name."
               ::= {     sispm1040582lrtSystemNTP 5 }

    sispm1040582lrtSystemNTPServer5    OBJECT-TYPE
               SYNTAX            DisplayString
               MAX-ACCESS        read-write
               STATUS            current
               DESCRIPTION
                   "Get/Set the NTP Time Server5.
                    You can use the IP address or domain name."
               ::= {     sispm1040582lrtSystemNTP 6 }


--
-- =======================================================================================================================
-- Objects in the sispm1040582lrtSystemTime Group
-- =======================================================================================================================
--sispm1040582lrtSystemTimeZone

    sispm1040582lrtSystemTimeZoneConf OBJECT-TYPE
               SYNTAX       Integer32(-7200..7201)
               MAX-ACCESS   read-write
               STATUS       current
               DESCRIPTION
                   "Get/Set the NTP Time Zone.
                    The value range is between -7200 and 7201 (minutes).
                    0 : None.
                    -7200 : (GMT-12:00).
                    -6600 : (GMT-11:00).
                    -6000 : (GMT-10:00).
                    -5400 : (GMT-09:00).
                    -4800 : (GMT-08:00)Pacific Time.
                    -4801 : (GMT-08:00)Tijuana, Baja California.
                    -4200 : (GMT-07:00)Arizona.
                    -4201 : (GMT-07:00)Chihuahua, La Paz, Mazatlan - New.
                    -4202 : (GMT-07:00)Chihuahua, La Paz, Mazatlan - Old.
                    -4203 : (GMT-07:00)Mountain Time.
                    -3600 : (GMT-06:00)Central America.
                    -3601 : (GMT-06:00)Central Time.
                    -3602 : (GMT-06:00)Guadalajara, Mexico City, Monterrey - New.
                    -3603 : (GMT-06:00)Guadalajara, Mexico City, Monterrey - Old.
                    -3604 : (GMT-06:00)Saskatchewan.
                    -3000 : (GMT-05:00)Bogota, Lima, Quito, Rio Branco.
                    -3001 : (GMT-05:00)Eastern Time.
                    -3002 : (GMT-05:00)Indiana.
                    -2700 : (GMT-04:30).
                    -2400 : (GMT-04:00)Atlantic Time.
                    -2401 : (GMT-04:00)La Paz.
                    -2402 : (GMT-04:00)Manaus.
                    -2403 : (GMT-04:00)Santiago.
                    -2100 : (GMT-03:30).
                    -1800 : (GMT-03:00)Brasilia.
                    -1801 : (GMT-03:00)Buenos Aires.
                    -1802 : (GMT-03:00)Georgetown.
                    -1803 : (GMT-03:00)Greenland.
                    -1804 : (GMT-03:00)Montevideo.
                    -1805 : (GMT-02:00).
                    -600 : (GMT-01:00)Azores.
                    -601 : (GMT-01:00)Cape Verde Is.
                    1 : (GMT) Casablanca.
                    2 : (GMT) Greenwich Mean Time.
                    3 : (GMT) Monrovia, Reykjavik.
                    600 : (GMT+01:00) Amsterdam, Berlin, Bern, Rome, Stockholm, Vienna.
                    601 : (GMT+01:00) Belgrade, Bratislava, Budapest, Ljubljana, Prague.
                    602 : (GMT+01:00) Brussels, Copenhagen, Madrid, Paris.
                    603 : (GMT+01:00) Sarajevo, Skopje, Warsaw, Zagreb.
                    604 : (GMT+01:00) West Central Africa.
                    1200 : (GMT+02:00) Amman.
                    1201 : (GMT+02:00) Athens, Bucharest, Istanbul.
                    1202 : (GMT+02:00) Beirut.
                    1203 : (GMT+02:00) Cairo.
                    1204 : (GMT+02:00) Harare, Pretoria.
                    1205 : (GMT+02:00) Helsinki, Kyiv, Riga, Sofia, Tallinn, Vilnius.
                    1206 : (GMT+02:00) Jerusalem.
                    1207 : (GMT+02:00) Minsk.
                    1208 : (GMT+02:00) Windhoek.
                    1800 : (GMT+03:00) Baghdad.
                    1801 : (GMT+03:00) Kuwait, Riyadh.
                    1802 : (GMT+03:00) Moscow, St. Petersburg, Volgograd.
                    1803 : (GMT+03:00) Nairobi.
                    1804 : (GMT+03:00) Tbilisi.
                    2100 : (GMT+03:30) Tehran.
                    2400 : (GMT+04:00) Abu Dhabi, Muscat.
                    2401 : (GMT+04:00) Baku.
                    2402 : (GMT+04:00) Caucasus Standard Time.
                    2403 : (GMT+04:00) Port Louis.
                    2404 : (GMT+04:00) Yerevan.
                    2700 : (GMT+04:30) Kabul.
                    3000 : (GMT+05:00) Ekaterinburg.
                    3001 : (GMT+05:00) Islamabad, Karachi.
                    3002 : (GMT+05:00) Tashkent.
                    3300 : (GMT+05:30) Chennai, Kolkata, Mumbai, New Delhi.
                    3301 : (GMT+05:30) Sri Jayawardenepura.
                    3455 : (GMT+05:45) Kathmandu.
                    3600 : (GMT+06:00) Almaty, Novosibirsk.
                    3601 : (GMT+06:00) Astana, Dhaka.
                    3600 : (GMT+06:30) Yangon (Rangoon).
                    4200 : (GMT+07:00) Bangkok, Hanoi, Jakarta.
                    4201 : (GMT+07:00) Krasnoyarsk.
                    4800 : (GMT+08:00) Beijing, Chongqing, Hong Kong, Urumqi.
                    4801 : (GMT+08:00) Irkutsk, Ulaan Bataar.
                    4802 : (GMT+08:00) Kuala Lumpur, Singapore.
                    4803 : (GMT+08:00) Perth.
                    4804 : (GMT+08:00) Taipei.
                    5400 : (GMT+09:00) Osaka, Sapporo, Tokyo.
                    5401 : (GMT+09:00) Seoul.
                    5402 : (GMT+09:00) Yakutsk.
                    5700 : (GMT+09:30) Adelaide.
                    5701 : (GMT+09:30) Darwin.
                    6000 : (GMT+10:00) Brisbane.
                    6001 : (GMT+10:00) Canberra, Melbourne, Sydney.
                    6002 : (GMT+10:00) Guam, Port Moresby.
                    6003 : (GMT+10:00) Hobart.
                    6004 : (GMT+10:00) Vladivostok.
                    6600 : (GMT+11:00) Magadan, Solomon Is., New Caledonia.
                    7200 : (GMT+12:00) Auckland, Wellington.
                    7201 : (GMT+12:00) Fiji, Kamchatka, Marshall Is."
               ::= {     sispm1040582lrtSystemTimeZone 1 }

    sispm1040582lrtSystemTimeZoneAcronym OBJECT-TYPE
               SYNTAX       DisplayString
               MAX-ACCESS   read-write
               STATUS       current
               DESCRIPTION
                   "Acronym - User can set the acronym of the time zone.
                    This is a User configurable acronym to identify the time zone.
                    Range : 0 - 16 characters."
               ::= {     sispm1040582lrtSystemTimeZone 2 }

--sispm1040582lrtSystemTimeDaylightSaving

    sispm1040582lrtSystemTimeDaylightSavingMode OBJECT-TYPE
               SYNTAX       INTEGER { disable(0), recurring(1), nonRecurring(2) }
               MAX-ACCESS   read-write
               STATUS       current
               DESCRIPTION
                   "The system Daylight Savings Mode.
                    disable(0)   : Disable.
                    recurring(1) : Recurring
                        - configure the Daylight Saving Time duration
                        to repeat the configuration every year.
                    nonRecurring(2): Non-Recurring - configure the Daylight Saving Time
                        duration for single time configuration."
               DEFVAL  { disable }
               ::= {     sispm1040582lrtSystemTimeDaylightSaving 1 }

    sispm1040582lrtSystemTimeDaylightSavingStartWeek OBJECT-TYPE
               SYNTAX       Integer32 (1..5)
               MAX-ACCESS   read-write
               STATUS       current
               DESCRIPTION
                   "Start time Week. Use in Recurring Mode.
                    Range : 1 - 5.
                    Default : 1."
               ::= {     sispm1040582lrtSystemTimeDaylightSaving 2 }

    sispm1040582lrtSystemTimeDaylightSavingStartDay OBJECT-TYPE
               SYNTAX       DayOfWeek
               MAX-ACCESS   read-write
               STATUS       current
               DESCRIPTION
                   "Start time Day. Use in Recurring Mode."
               DEFVAL  { mon }
               ::= {     sispm1040582lrtSystemTimeDaylightSaving 3 }

    sispm1040582lrtSystemTimeDaylightSavingStartMonth OBJECT-TYPE
               SYNTAX       Month
               MAX-ACCESS   read-write
               STATUS       current
               DESCRIPTION
                   "Start time Month."
               DEFVAL  { jan }
               ::= {     sispm1040582lrtSystemTimeDaylightSaving 4 }

    sispm1040582lrtSystemTimeDaylightSavingStartDate OBJECT-TYPE
               SYNTAX       Integer32 (1..31)
               MAX-ACCESS   read-write
               STATUS       current
               DESCRIPTION
                   "Start time Date. Use in Non-Recurring Mode.
                    Range : 1 - 31.
                    Default : 1."
               ::= {     sispm1040582lrtSystemTimeDaylightSaving 5 }

    sispm1040582lrtSystemTimeDaylightSavingStartYear OBJECT-TYPE
               SYNTAX       Integer32 (2000..2097)
               MAX-ACCESS   read-write
               STATUS       current
               DESCRIPTION
                   "Start time Year. Use in Non-Recurring Mode.
                    Range : 2000 - 2097.
                    Default : 2000."
               ::= {     sispm1040582lrtSystemTimeDaylightSaving 6 }

    sispm1040582lrtSystemTimeDaylightSavingStartHours OBJECT-TYPE
               SYNTAX       Integer32 (0..23)
               MAX-ACCESS   read-write
               STATUS       current
               DESCRIPTION
                   "Start time Hours.
                     Range : 0 - 23.
                     Default : 0."
               ::= {     sispm1040582lrtSystemTimeDaylightSaving 7 }

    sispm1040582lrtSystemTimeDaylightSavingStartMinutes OBJECT-TYPE
               SYNTAX       Integer32 (0..59)
               MAX-ACCESS   read-write
               STATUS       current
               DESCRIPTION
                   "Start time Minutes.
                    Range : 0 - 59.
                    Default : 0."
               ::= {     sispm1040582lrtSystemTimeDaylightSaving 8 }

    sispm1040582lrtSystemTimeDaylightSavingEndWeek OBJECT-TYPE
               SYNTAX       Integer32 (1..5)
               MAX-ACCESS   read-write
               STATUS       current
               DESCRIPTION
                   "End time Week. Use in Recurring Mode.
                    Range : 1 - 5.
                    Default : 1."
               ::= {     sispm1040582lrtSystemTimeDaylightSaving 9 }

    sispm1040582lrtSystemTimeDaylightSavingEndDay OBJECT-TYPE
               SYNTAX       DayOfWeek
               MAX-ACCESS   read-write
               STATUS       current
               DESCRIPTION
                   "End time Day. Use in Recurring Mode."
               DEFVAL  { mon }
               ::= {     sispm1040582lrtSystemTimeDaylightSaving 10 }

    sispm1040582lrtSystemTimeDaylightSavingEndMonth OBJECT-TYPE
               SYNTAX       Month
               MAX-ACCESS   read-write
               STATUS       current
               DESCRIPTION
                   "End time Month."
              DEFVAL  { jan }
              ::= {     sispm1040582lrtSystemTimeDaylightSaving 11 }

    sispm1040582lrtSystemTimeDaylightSavingEndDate OBJECT-TYPE
               SYNTAX       Integer32 (1..31)
               MAX-ACCESS   read-write
               STATUS       current
               DESCRIPTION
                   "End time Date. Use in Non-Recurring Mode.
                    Range : 1 - 31.
                    Default : 1."
               ::= {     sispm1040582lrtSystemTimeDaylightSaving 12 }

    sispm1040582lrtSystemTimeDaylightSavingEndYear OBJECT-TYPE
               SYNTAX       Integer32 (2000..2097)
               MAX-ACCESS   read-write
               STATUS       current
               DESCRIPTION
                   "End time Year. Use in Non-Recurring Mode.
                    Range : 2000 - 2097.
                    Default : 2000."
               ::= {     sispm1040582lrtSystemTimeDaylightSaving 13 }

    sispm1040582lrtSystemTimeDaylightSavingEndHours OBJECT-TYPE
               SYNTAX       Integer32 (0..23)
               MAX-ACCESS   read-write
               STATUS       current
               DESCRIPTION
                   "End time Hours.
                    Range : 0 - 23.
                    Default : 0."
               ::= {     sispm1040582lrtSystemTimeDaylightSaving 14 }

    sispm1040582lrtSystemTimeDaylightSavingEndMinutes OBJECT-TYPE
               SYNTAX       Integer32 (0..59)
               MAX-ACCESS   read-write
               STATUS       current
               DESCRIPTION
                   "End time Minutes.
                    Range : 0 - 59.
                    Default : 0."
               ::= {     sispm1040582lrtSystemTimeDaylightSaving 15 }

    sispm1040582lrtSystemTimeDaylightSavingOffset OBJECT-TYPE
               SYNTAX       Integer32 (1..1440)
               MAX-ACCESS   read-write
               STATUS       current
               DESCRIPTION
                   "Offset - the number of minutes to add during Daylight Saving Time.
                    Range : 1 - 1440(Minutes).
                    Default : 1."
               ::= {     sispm1040582lrtSystemTimeDaylightSaving 16 }

    sispm1040582lrtSystemTimeConfigurationClockSource OBJECT-TYPE
               SYNTAX       Integer32
               MAX-ACCESS   read-write
               STATUS       current
               DESCRIPTION
                   "0:Use Local Settings.
                    1:Use NTP Server."
	           ::= {     sispm1040582lrtSystemTimeConfiguration 1}

    sispm1040582lrtSystemTimeConfigurationDateFormat OBJECT-TYPE
               SYNTAX       Integer32 (0|1|2)
               MAX-ACCESS   read-write
               STATUS       current
               DESCRIPTION
                   "The date format of the system.
				   0:yyyy-mm-dd
				   1:mm-dd-yyyy
				   2:dd-mm-yyyy"
	           ::= {     sispm1040582lrtSystemTimeConfiguration 2}
			   
    sispm1040582lrtSystemTimeConfigurationTimeFormat OBJECT-TYPE
               SYNTAX       Integer32 (0|1)
               MAX-ACCESS   read-write
               STATUS       current
               DESCRIPTION
                   "The time format of the system.
				   0:24-hr, format:hh:mm:ss
				   1:12-hr, format:hh:mm:ss am/pm"
	           ::= {     sispm1040582lrtSystemTimeConfiguration 3}
			   
    sispm1040582lrtSystemTimeConfigurationSystemDate OBJECT-TYPE
               SYNTAX       DisplayString
               MAX-ACCESS   read-write
               STATUS       current
               DESCRIPTION
                   "System date. Default format:yyyy-mm-dd.
                    When ClockSource is Use Local Settings, you can set this field."
	           ::= {     sispm1040582lrtSystemTimeConfiguration 4}
			   
    sispm1040582lrtSystemTimeConfigurationSystemTime OBJECT-TYPE
               SYNTAX       DisplayString
               MAX-ACCESS   read-write
               STATUS       current
               DESCRIPTION
                   "System date.
				    24-hr, format:hh:mm:ss
				    12-hr, format:hh:mm:ss am/pm
                    When ClockSource is Use Local Settings, you can set this field."
	           ::= {     sispm1040582lrtSystemTimeConfiguration 5}			   

-- =======================================================================================================================
sispm1040582lrtSystemAccount                                         OBJECT IDENTIFIER ::= { sispm1040582lrtSystem 3 }

sispm1040582lrtSystemAccountUsers                                     OBJECT IDENTIFIER  ::= { sispm1040582lrtSystemAccount 1 }

--
-- =======================================================================================================================
-- Start sispm1040582lrtUserConfig group
-- =======================================================================================================================
--sispm1040582lrtUserConfigTable

    sispm1040582lrtUserConfigTable OBJECT-TYPE
               SYNTAX      SEQUENCE OF     SISPM1040582LRTUserConfigEntry
               MAX-ACCESS  not-accessible
               STATUS      current
               DESCRIPTION
                   "The User Config Table. "
               ::= {     sispm1040582lrtSystemAccountUsers 1 }

    sispm1040582lrtUserConfigEntry OBJECT-TYPE
               SYNTAX          SISPM1040582LRTUserConfigEntry
               MAX-ACCESS  not-accessible
               STATUS      current
               DESCRIPTION
                   "The User Config Entry."
               INDEX    {    sispm1040582lrtUserConfigIndex  }
               ::= {     sispm1040582lrtUserConfigTable 1 }

    SISPM1040582LRTUserConfigEntry             ::= SEQUENCE {
                 sispm1040582lrtUserConfigIndex            Integer32,
                 sispm1040582lrtUserConfigUserName         DisplayString,
                 sispm1040582lrtUserConfigPassword         DisplayString,
                 sispm1040582lrtUserConfigPrivilegeLevel   Integer32,
                 sispm1040582lrtUserConfigRowStatus        RowStatus
                }

    sispm1040582lrtUserConfigIndex OBJECT-TYPE
               SYNTAX      Integer32 (1..4095)
               MAX-ACCESS  not-accessible
               STATUS      current
               DESCRIPTION
                   "The user Config Index. "
               ::= {     sispm1040582lrtUserConfigEntry 1 }

    sispm1040582lrtUserConfigUserName OBJECT-TYPE
               SYNTAX      DisplayString(SIZE (1..31))
               MAX-ACCESS  read-create
               STATUS      current
               DESCRIPTION
                   "A string identifying the user name for the entry.
                    string length: 1-31. "
               ::= {     sispm1040582lrtUserConfigEntry 2 }

    sispm1040582lrtUserConfigPassword OBJECT-TYPE
               SYNTAX      DisplayString(SIZE (0..31))
               MAX-ACCESS  read-create
               STATUS      current
               DESCRIPTION
                   "The password of the user.
                    string length: 0-31. "
               ::= {     sispm1040582lrtUserConfigEntry 3 }

    sispm1040582lrtUserConfigPrivilegeLevel OBJECT-TYPE
               SYNTAX      Integer32(1..15)
               MAX-ACCESS  read-create
               STATUS      current
               DESCRIPTION
                   "The privilege level of the user.If the privilege level
                    value is 15, it can access all groups.range: 1-15. "
               ::= {     sispm1040582lrtUserConfigEntry 4 }

    sispm1040582lrtUserConfigRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sispm1040582lrtUserConfigEntry 5 }


--
-- =======================================================================================================================
-- Start sispm1040582lrtPrivilegeLevelConfig group
-- =======================================================================================================================
--sispm1040582lrtPrivilegeLevelConfigTable

    sispm1040582lrtPrivilegeLevelConfigTable OBJECT-TYPE
               SYNTAX      SEQUENCE OF     SISPM1040582LRTPrivilegeLevelConfigEntry
               MAX-ACCESS  not-accessible
               STATUS      current
               DESCRIPTION
                   "The Privilege Level Config Table. "
               ::= {     sispm1040582lrtSystemAccountUsers 2 }

    sispm1040582lrtPrivilegeLevelConfigEntry OBJECT-TYPE
               SYNTAX          SISPM1040582LRTPrivilegeLevelConfigEntry
               MAX-ACCESS  not-accessible
               STATUS      current
               DESCRIPTION
                   "The Privilege Level Config Entry."
               INDEX    {    sispm1040582lrtPrivilegeLevelIndex  }
               ::= {     sispm1040582lrtPrivilegeLevelConfigTable 1 }

    SISPM1040582LRTPrivilegeLevelConfigEntry             ::= SEQUENCE {
                 sispm1040582lrtPrivilegeLevelIndex                Integer32,
                 sispm1040582lrtPrivilegeLevelGroupName            DisplayString,
                 sispm1040582lrtPrivilegeLevelConfigReadOnly       Integer32,
                 sispm1040582lrtPrivilegeLevelConfigReadWrite      Integer32,
                 sispm1040582lrtPrivilegeLevelStatusReadOnly       Integer32,
                 sispm1040582lrtPrivilegeLevelStatusReadWrite      Integer32
                 }

    sispm1040582lrtPrivilegeLevelIndex OBJECT-TYPE
               SYNTAX      Integer32 (1..4095)
               MAX-ACCESS  not-accessible
               STATUS      current
               DESCRIPTION
                   "The Privilege Level Index. "
               ::= {     sispm1040582lrtPrivilegeLevelConfigEntry 1 }

    sispm1040582lrtPrivilegeLevelGroupName OBJECT-TYPE
               SYNTAX      DisplayString
               MAX-ACCESS  read-only
               STATUS      current
               DESCRIPTION
                   "The name identifying the privilege group."
               ::= {     sispm1040582lrtPrivilegeLevelConfigEntry 2 }

    sispm1040582lrtPrivilegeLevelConfigReadOnly OBJECT-TYPE
               SYNTAX      Integer32(1..15)
               MAX-ACCESS  read-write
               STATUS      current
               DESCRIPTION
                   "The privilege level of configuration read-only.If the
                    privilege level value is 15,it can access all groups.
                    range: 1-15.  "
               ::= {     sispm1040582lrtPrivilegeLevelConfigEntry 3 }

    sispm1040582lrtPrivilegeLevelConfigReadWrite OBJECT-TYPE
               SYNTAX      Integer32(1..15)
               MAX-ACCESS  read-write
               STATUS      current
               DESCRIPTION
                   "The privilege level of configuration/execute read/write.
                    If the privilege level value is 15,it can access all groups.
                    range: 1-15. "
               ::= {     sispm1040582lrtPrivilegeLevelConfigEntry 4 }

    sispm1040582lrtPrivilegeLevelStatusReadOnly OBJECT-TYPE
               SYNTAX      Integer32(1..15)
               MAX-ACCESS  read-write
               STATUS      current
               DESCRIPTION
                   "The privilege level of status/statistics read-only.
                    If the privilege level value is 15,it can access all groups.
                    range: 1-15. "
               ::= {     sispm1040582lrtPrivilegeLevelConfigEntry 5 }

    sispm1040582lrtPrivilegeLevelStatusReadWrite OBJECT-TYPE
               SYNTAX      Integer32(1..15)
               MAX-ACCESS  read-write
               STATUS      current
               DESCRIPTION
                   "The privilege level of status/statistics read-write.
                    If the privilege level value is 15,it can access all groups.
                    range: 1-15. "
               ::= {     sispm1040582lrtPrivilegeLevelConfigEntry 6 }
-- =======================================================================================================================
sispm1040582lrtIP                                                    OBJECT IDENTIFIER ::= { sispm1040582lrtSystem 4 }

sispm1040582lrtIPConfiguration OBJECT IDENTIFIER ::= { sispm1040582lrtIP 1 }

sispm1040582lrtMode OBJECT-TYPE
   SYNTAX      Integer32 (0|1)
   MAX-ACCESS  read-write
   STATUS      current
   DESCRIPTION
       "IP Configuration Mode.
        default:0
        0: Host
        1: Router"
   ::= {sispm1040582lrtIPConfiguration 2 }

sispm1040582lrtDNSServerSource1 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm1040582lrtIPConfiguration 3 }
   
sispm1040582lrtDNSServerSource2 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
		4. DNS configuration is derived from DHCPv6.
		5. DNS configuration is derived from DHCPv6 on specific VLAN.
		"
   ::= {sispm1040582lrtIPConfiguration 4 }   
   
sispm1040582lrtDNSServerSource3 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm1040582lrtIPConfiguration 5 }  
   
sispm1040582lrtDNSServerSource4 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm1040582lrtIPConfiguration 6 }    

sispm1040582lrtDNSServerValue1 OBJECT-TYPE
   SYNTAX      DisplayString
   MAX-ACCESS  read-write
   STATUS      current
   DESCRIPTION
       "DNS IPv4/IPv6 Address or VLAN value."
   ::= {sispm1040582lrtIPConfiguration 7 }
   
sispm1040582lrtDNSServerValue2 OBJECT-TYPE
   SYNTAX      DisplayString
   MAX-ACCESS  read-write
   STATUS      current
   DESCRIPTION
      "DNS IPv4/IPv6 Address or VLAN value."
   ::= {sispm1040582lrtIPConfiguration 8 }   
   
sispm1040582lrtDNSServerValue3 OBJECT-TYPE
   SYNTAX      DisplayString
   MAX-ACCESS  read-write
   STATUS      current
   DESCRIPTION
       "DNS IPv4/IPv6 Address or VLAN value."
   ::= {sispm1040582lrtIPConfiguration 9 }    
   
sispm1040582lrtDNSServerValue4 OBJECT-TYPE
   SYNTAX      DisplayString
   MAX-ACCESS  read-write
   STATUS      current
   DESCRIPTION
       "DNS IPv4/IPv6 Address or VLAN value."
   ::= {sispm1040582lrtIPConfiguration 10 }   
   
sispm1040582lrtDNSProxy OBJECT-TYPE
   SYNTAX      Integer32 (0|1)
   MAX-ACCESS  read-write
   STATUS      current
   DESCRIPTION
       "DNS Proxy enable/disable.
        default:0
        0: disable
        1: enable"
   ::= {sispm1040582lrtIPConfiguration 11 }


sispm1040582lrtIPInterfaces OBJECT IDENTIFIER ::= { sispm1040582lrtIP 2 }

sispm1040582lrtIPInterfacesDHCPPerPortMode OBJECT-TYPE
   SYNTAX      INTEGER { disable(0), enable(1) }
   MAX-ACCESS  read-write
   STATUS      current
   DESCRIPTION
       "The dhcp per-port mode for the interface.
        0: Disable,
        1: Enable,
        default: Disable. "
   ::= { sispm1040582lrtIPInterfaces 1 }

sispm1040582lrtIPInterfacesDHCPPerPortIPRangeLow OBJECT-TYPE
   SYNTAX      IpAddress
   MAX-ACCESS  read-write
   STATUS      current
   DESCRIPTION
       "The dhcp per-port ip low for the interface."
   ::= { sispm1040582lrtIPInterfaces 2 }

sispm1040582lrtIPInterfacesDHCPPerPortIPRangeHigh OBJECT-TYPE
   SYNTAX      IpAddress
   MAX-ACCESS  read-write
   STATUS      current
   DESCRIPTION
       "The dhcp per-port ip high for the interface."
   ::= { sispm1040582lrtIPInterfaces 3 }

sispm1040582lrtIPInterfacesDHCPPerPortApply OBJECT-TYPE
   SYNTAX      Integer32 (1)
   MAX-ACCESS  read-write
   STATUS      current
   DESCRIPTION
       "1: Apply DHCP Per Port settings."
   ::= { sispm1040582lrtIPInterfaces 4 }
   
sispm1040582lrtIPInterfacesDHCPPerPortVLAN OBJECT-TYPE
   SYNTAX      Integer32 (1..4095)
   MAX-ACCESS  read-write
   STATUS      current
   DESCRIPTION
       "dhcp per-port VLAN."
   ::= { sispm1040582lrtIPInterfaces 6 } 
   
sispm1040582lrtIPInterfacesTable OBJECT-TYPE
   SYNTAX      SEQUENCE OF SISPM1040582LRTIPInterfacesEntry
   MAX-ACCESS  not-accessible
   STATUS      current
   DESCRIPTION
       "A table of IP interface for switch."
    ::= { sispm1040582lrtIPInterfaces 5 }

sispm1040582lrtIPInterfacesEntry OBJECT-TYPE
    SYNTAX        SISPM1040582LRTIPInterfacesEntry
    MAX-ACCESS    not-accessible
    STATUS        current
    DESCRIPTION
        "An entry in the sispm1040582lrtIPInterfacesTable."
    INDEX        { sispm1040582lrtIPInterfacesIndex }
    ::= { sispm1040582lrtIPInterfacesTable 1 }

SISPM1040582LRTIPInterfacesEntry ::=
    SEQUENCE {
        sispm1040582lrtIPInterfacesIndex                       Integer32,
        sispm1040582lrtIPInterfacesVLAN                        Integer32,
        sispm1040582lrtIPInterfacesIPv4DHCP                    Integer32,
        sispm1040582lrtIPInterfacesIPv4DHCPFallback            DisplayString,
        sispm1040582lrtIPInterfacesIPv4DHCPCurrentLease        IpAddress,
        sispm1040582lrtIPInterfacesIPv4Address                 IpAddress,
        sispm1040582lrtIPInterfacesIPv4Mask                    Integer32,
	sispm1040582lrtIPInterfacesIPv6DHCP                    Integer32,
	sispm1040582lrtIPInterfacesIPv6RapidCommit             Integer32,
	sispm1040582lrtIPInterfacesIPv6CurrentLease            DisplayString,
        sispm1040582lrtIPInterfacesIPv6Address                 DisplayString,
        sispm1040582lrtIPInterfacesIPv6Mask                    Integer32,
	sispm1040582lrtIPInterfacesRowStatus                   RowStatus
    }

sispm1040582lrtIPInterfacesIndex OBJECT-TYPE
   SYNTAX      Integer32 (1..128)
   MAX-ACCESS  not-accessible
   STATUS      current
   DESCRIPTION
       "interface table index"
   ::= {sispm1040582lrtIPInterfacesEntry 1 }

sispm1040582lrtIPInterfacesVLAN OBJECT-TYPE
   SYNTAX      Integer32 (1..4095)
   MAX-ACCESS  read-write
   STATUS      current
   DESCRIPTION
       "VLAN ID for interface, range: 1-4095."
   ::= {sispm1040582lrtIPInterfacesEntry 2 }

sispm1040582lrtIPInterfacesIPv4DHCP OBJECT-TYPE
   SYNTAX      Integer32 (0|1)
   MAX-ACCESS  read-write
   STATUS      current
   DESCRIPTION
       "IPv4 DHCP Setting for interface.
        default:0
        0: disable
        1: enable"
   ::= {sispm1040582lrtIPInterfacesEntry 3 }

sispm1040582lrtIPInterfacesIPv4DHCPFallback OBJECT-TYPE
   SYNTAX      DisplayString
   MAX-ACCESS  read-write
   STATUS      current
   DESCRIPTION
       "IPv4 DHCP fallbcak. range: 1-4294967295 seconds."
   ::= {sispm1040582lrtIPInterfacesEntry 4 }


sispm1040582lrtIPInterfacesIPv4DHCPCurrentLease OBJECT-TYPE
   SYNTAX      IpAddress
   MAX-ACCESS  read-only
   STATUS      current
   DESCRIPTION
       "IPv4 DHCP Current Lease Address for interface."
   ::= {sispm1040582lrtIPInterfacesEntry 5 }


sispm1040582lrtIPInterfacesIPv4Address OBJECT-TYPE
   SYNTAX      IpAddress
   MAX-ACCESS  read-write
   STATUS      current
   DESCRIPTION
       "IPv4 address for interface."
   ::= {sispm1040582lrtIPInterfacesEntry 6 }

sispm1040582lrtIPInterfacesIPv4Mask OBJECT-TYPE
   SYNTAX      Integer32 (1..32)
   MAX-ACCESS  read-write
   STATUS      current
   DESCRIPTION
       "IPv4 mask for interface."
   ::= { sispm1040582lrtIPInterfacesEntry 7 }

sispm1040582lrtIPInterfacesIPv6DHCP OBJECT-TYPE
   SYNTAX      Integer32 (0|1)
   MAX-ACCESS  read-write
   STATUS      current
   DESCRIPTION
       "IPv6 DHCP Setting for interface.
        default:0
        0: disable
        1: enable"
   ::= {sispm1040582lrtIPInterfacesEntry 8 } 
   
sispm1040582lrtIPInterfacesIPv6RapidCommit OBJECT-TYPE
   SYNTAX      Integer32 (0|1)
   MAX-ACCESS  read-write
   STATUS      current
   DESCRIPTION
       "Enable the DHCPv6 Rapid-Commit option.
        default:0
        0: disable
        1: enable"
   ::= {sispm1040582lrtIPInterfacesEntry 9 }    
   
sispm1040582lrtIPInterfacesIPv6CurrentLease OBJECT-TYPE
   SYNTAX      DisplayString
   MAX-ACCESS  read-only
   STATUS      current
   DESCRIPTION
       "IPv6 DHCP Current Lease Address for interface."
   ::= {sispm1040582lrtIPInterfacesEntry 10 }

   
sispm1040582lrtIPInterfacesIPv6Address OBJECT-TYPE
   SYNTAX      DisplayString (SIZE (0..30))
   MAX-ACCESS  read-write
   STATUS      current
   DESCRIPTION
       "IPv6 address for interface."
   ::= { sispm1040582lrtIPInterfacesEntry 11 }

sispm1040582lrtIPInterfacesIPv6Mask OBJECT-TYPE
   SYNTAX      Integer32 (1..128)
   MAX-ACCESS  read-write
   STATUS      current
   DESCRIPTION
       "IPv6 mask for interface."
   ::= { sispm1040582lrtIPInterfacesEntry 12 }

sispm1040582lrtIPInterfacesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sispm1040582lrtIPInterfacesEntry 13 }
   

sispm1040582lrtIPRoutes OBJECT IDENTIFIER ::= { sispm1040582lrtIP 3 }

sispm1040582lrtIPRoutesTable OBJECT-TYPE
   SYNTAX      SEQUENCE OF SISPM1040582LRTIPRoutesEntry
   MAX-ACCESS  not-accessible
   STATUS      current
   DESCRIPTION
       "IP routes table for switch."
    ::= { sispm1040582lrtIPRoutes 1 }

sispm1040582lrtIPRoutesEntry OBJECT-TYPE
    SYNTAX        SISPM1040582LRTIPRoutesEntry
    MAX-ACCESS    not-accessible
    STATUS        current
    DESCRIPTION
        "Entry in the sispm1040582lrtIPRoutesTable."
    INDEX        { sispm1040582lrtIPRoutesIndex }
    ::= { sispm1040582lrtIPRoutesTable 1 }

SISPM1040582LRTIPRoutesEntry ::=
    SEQUENCE {
        sispm1040582lrtIPRoutesIndex                       Integer32,
        sispm1040582lrtIPRoutesNetwork                     DisplayString,
        sispm1040582lrtIPRoutesMaskLength                  Integer32,
        sispm1040582lrtIPRoutesGateway                     DisplayString,
        sispm1040582lrtIPRoutesNextHopVLAN                 Integer32,
	sispm1040582lrtIPRoutesRowStatus                   RowStatus
    }

sispm1040582lrtIPRoutesIndex OBJECT-TYPE
   SYNTAX      Integer32 (1..32)
   MAX-ACCESS  not-accessible
   STATUS      current
   DESCRIPTION
       "routes table index"
   ::= {sispm1040582lrtIPRoutesEntry 2 }

sispm1040582lrtIPRoutesNetwork OBJECT-TYPE
   SYNTAX      DisplayString (SIZE (0..30))
   MAX-ACCESS  read-write
   STATUS      current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= {sispm1040582lrtIPRoutesEntry 3 }

sispm1040582lrtIPRoutesMaskLength OBJECT-TYPE
   SYNTAX      Integer32 (1..32)
   MAX-ACCESS  read-write
   STATUS      current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sispm1040582lrtIPRoutesEntry 4 }

sispm1040582lrtIPRoutesGateway OBJECT-TYPE
   SYNTAX      DisplayString (SIZE (0..30))
   MAX-ACCESS  read-write
   STATUS      current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= {sispm1040582lrtIPRoutesEntry 5 }

sispm1040582lrtIPRoutesNextHopVLAN OBJECT-TYPE
   SYNTAX      Integer32 (1..4095)
   MAX-ACCESS  read-write
   STATUS      current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= {sispm1040582lrtIPRoutesEntry 6 }

sispm1040582lrtIPRoutesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sispm1040582lrtIPRoutesEntry 7 }

sispm1040582lrtIPConfigurationConfigured OBJECT IDENTIFIER ::= { sispm1040582lrtIP 4 }

sispm1040582lrtModeConfigured OBJECT-TYPE
   SYNTAX      Integer32 (0|1)
   MAX-ACCESS  read-only
   STATUS      current
   DESCRIPTION
       "IP Configuration Mode
	default:0
        0: Host
        1: Router"
   ::= {sispm1040582lrtIPConfigurationConfigured 2 }

sispm1040582lrtDNSServerSource1Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sispm1040582lrtIPConfigurationConfigured 3 }
   
sispm1040582lrtDNSServerSource2Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sispm1040582lrtIPConfigurationConfigured 4 }
   
sispm1040582lrtDNSServerSource3Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sispm1040582lrtIPConfigurationConfigured 5 }   

sispm1040582lrtDNSServerSource4Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sispm1040582lrtIPConfigurationConfigured 6 }   

sispm1040582lrtDNSServerValue1Configured OBJECT-TYPE
   SYNTAX      DisplayString
   MAX-ACCESS  read-only
   STATUS      current
   DESCRIPTION
       "DNS IPv4/IPv6 Address or VLAN value."
   ::= {sispm1040582lrtIPConfigurationConfigured 7 }  

sispm1040582lrtDNSServerValue2Configured OBJECT-TYPE
   SYNTAX      DisplayString
   MAX-ACCESS  read-only
   STATUS      current
   DESCRIPTION
       "DNS IPv4/IPv6 Address or VLAN value."
   ::= {sispm1040582lrtIPConfigurationConfigured 8 } 
   
sispm1040582lrtDNSServerValue3Configured OBJECT-TYPE
   SYNTAX      DisplayString
   MAX-ACCESS  read-only
   STATUS      current
   DESCRIPTION
       "DNS IPv4/IPv6 Address or VLAN value."
   ::= {sispm1040582lrtIPConfigurationConfigured 9 } 

sispm1040582lrtDNSServerValue4Configured OBJECT-TYPE
   SYNTAX      DisplayString
   MAX-ACCESS  read-only
   STATUS      current
   DESCRIPTION
       "DNS IPv4/IPv6 Address or VLAN value."
   ::= {sispm1040582lrtIPConfigurationConfigured 10 }    
      
sispm1040582lrtDNSProxyConfigured OBJECT-TYPE
   SYNTAX      Integer32 (0|1)
   MAX-ACCESS  read-only
   STATUS      current
   DESCRIPTION
       "DNS Proxy enable/disable.
        default:0
        0: disable
        1: enable"
   ::= {sispm1040582lrtIPConfigurationConfigured 11 }


sispm1040582lrtIPInterfacesConfigured OBJECT IDENTIFIER ::= { sispm1040582lrtIP 5 }

sispm1040582lrtIPInterfacesConfiguredTable OBJECT-TYPE
   SYNTAX      SEQUENCE OF SISPM1040582LRTIPInterfacesConfiguredEntry
   MAX-ACCESS  not-accessible
   STATUS      current
   DESCRIPTION
        "A table of ip interface for switch."
    ::= { sispm1040582lrtIPInterfacesConfigured 1 }

sispm1040582lrtIPInterfacesConfiguredEntry OBJECT-TYPE
    SYNTAX        SISPM1040582LRTIPInterfacesConfiguredEntry
    MAX-ACCESS    not-accessible
    STATUS        current
    DESCRIPTION
        "An entry in the sispm1040582lrtIPInterfacesConfiguredTable."
    INDEX        { sispm1040582lrtIPInterfacesIndexConfigured }
    ::= { sispm1040582lrtIPInterfacesConfiguredTable 1 }

SISPM1040582LRTIPInterfacesConfiguredEntry ::=
    SEQUENCE {
        sispm1040582lrtIPInterfacesIndexConfigured                       Integer32,
        sispm1040582lrtIPInterfacesVLANConfigured                        Integer32,
        sispm1040582lrtIPInterfacesIPv4DHCPConfigured                    Integer32,
        sispm1040582lrtIPInterfacesIPv4DHCPFallbackConfigured            DisplayString,
        sispm1040582lrtIPInterfacesIPv4AddressConfigured                 IpAddress,
        sispm1040582lrtIPInterfacesIPv4MaskConfigured                    Integer32,
	sispm1040582lrtIPInterfacesIPv6DHCPConfigured                    Integer32, 
	sispm1040582lrtIPInterfacesIPv6RapidCommitConfigured             Integer32,
        sispm1040582lrtIPInterfacesIPv6AddressConfigured                 DisplayString,
        sispm1040582lrtIPInterfacesIPv6MaskConfigured                    Integer32
    }

sispm1040582lrtIPInterfacesIndexConfigured OBJECT-TYPE
   SYNTAX      Integer32 (1..128)
   MAX-ACCESS  not-accessible
   STATUS      current
   DESCRIPTION
       "interface table index"
   ::= {sispm1040582lrtIPInterfacesConfiguredEntry 2 }

sispm1040582lrtIPInterfacesVLANConfigured OBJECT-TYPE
   SYNTAX      Integer32 (1..4095)
   MAX-ACCESS  read-only
   STATUS      current
   DESCRIPTION
       "VLAN ID for interface, range: 1-4095."
   ::= {sispm1040582lrtIPInterfacesConfiguredEntry 3 }

sispm1040582lrtIPInterfacesIPv4DHCPConfigured OBJECT-TYPE
   SYNTAX      Integer32 (0|1)
   MAX-ACCESS  read-only
   STATUS      current
   DESCRIPTION
       "IPv4 DHCP Setting for interface.
	default:0
        0: disable
        1: enable"
   ::= {sispm1040582lrtIPInterfacesConfiguredEntry 4 }

sispm1040582lrtIPInterfacesIPv4DHCPFallbackConfigured OBJECT-TYPE
   SYNTAX      DisplayString
   MAX-ACCESS  read-only
   STATUS      current
   DESCRIPTION
       "IPv4 DHCP fallbcak. range: 1-4294967295 seconds."
   ::= {sispm1040582lrtIPInterfacesConfiguredEntry 5 }

sispm1040582lrtIPInterfacesIPv4AddressConfigured OBJECT-TYPE
   SYNTAX      IpAddress
   MAX-ACCESS  read-only
   STATUS      current
   DESCRIPTION
       "IPv4 address for interface."
   ::= {sispm1040582lrtIPInterfacesConfiguredEntry 6 }

sispm1040582lrtIPInterfacesIPv4MaskConfigured OBJECT-TYPE
   SYNTAX      Integer32 (1..32)
   MAX-ACCESS  read-only
   STATUS      current
   DESCRIPTION
       "IPv4 mask for interface."
   ::= { sispm1040582lrtIPInterfacesConfiguredEntry 7 }

sispm1040582lrtIPInterfacesIPv6DHCPConfigured OBJECT-TYPE
   SYNTAX      Integer32 (0|1)
   MAX-ACCESS  read-only
   STATUS      current
   DESCRIPTION
       "IPv6 DHCP Setting for interface.
        default:0
        0: disable
        1: enable"
   ::= {sispm1040582lrtIPInterfacesConfiguredEntry 8 } 
   
sispm1040582lrtIPInterfacesIPv6RapidCommitConfigured OBJECT-TYPE
   SYNTAX      Integer32 (0|1)
   MAX-ACCESS  read-only
   STATUS      current
   DESCRIPTION
       "Enable the DHCPv6 Rapid-Commit option.
        default:0
        0: disable
        1: enable"
   ::= {sispm1040582lrtIPInterfacesConfiguredEntry 9 } 

sispm1040582lrtIPInterfacesIPv6AddressConfigured OBJECT-TYPE
   SYNTAX      DisplayString (SIZE (0..30))
   MAX-ACCESS  read-only
   STATUS      current
   DESCRIPTION
       "IPv6 address for interface."
   ::= { sispm1040582lrtIPInterfacesConfiguredEntry 10 }

sispm1040582lrtIPInterfacesIPv6MaskConfigured OBJECT-TYPE
   SYNTAX      Integer32 (1..128)
   MAX-ACCESS  read-only
   STATUS      current
   DESCRIPTION
       "IPv6 mask for interface."
   ::= { sispm1040582lrtIPInterfacesConfiguredEntry 11 }

sispm1040582lrtIPRoutesConfigured OBJECT IDENTIFIER ::= { sispm1040582lrtIP 6 }

sispm1040582lrtIPRoutesConfiguredTable OBJECT-TYPE
   SYNTAX      SEQUENCE OF SISPM1040582LRTIPRoutesConfiguredEntry
   MAX-ACCESS  not-accessible
   STATUS      current
   DESCRIPTION
        "IP routes table for switch."
    ::= { sispm1040582lrtIPRoutesConfigured 1 }

sispm1040582lrtIPRoutesConfiguredEntry OBJECT-TYPE
    SYNTAX        SISPM1040582LRTIPRoutesConfiguredEntry
    MAX-ACCESS    not-accessible
    STATUS        current
    DESCRIPTION
        "Entry in the sispm1040582lrtIPRoutesConfiguredTable."
    INDEX        { sispm1040582lrtIPRoutesIndexConfigured }
    ::= { sispm1040582lrtIPRoutesConfiguredTable 1 }

SISPM1040582LRTIPRoutesConfiguredEntry ::=
    SEQUENCE {
        sispm1040582lrtIPRoutesIndexConfigured                       Integer32,
        sispm1040582lrtIPRoutesNetworkConfigured                     DisplayString,
        sispm1040582lrtIPRoutesMaskLengthConfigured                  Integer32,
        sispm1040582lrtIPRoutesGatewayConfigured                     DisplayString,
        sispm1040582lrtIPRoutesNextHopVLANConfigured                 Integer32
    }

sispm1040582lrtIPRoutesIndexConfigured OBJECT-TYPE
   SYNTAX      Integer32 (1..32)
   MAX-ACCESS  not-accessible
   STATUS      current
   DESCRIPTION
       "routes table index"
   ::= {sispm1040582lrtIPRoutesConfiguredEntry 2 }

sispm1040582lrtIPRoutesNetworkConfigured OBJECT-TYPE
   SYNTAX      DisplayString (SIZE (0..30))
   MAX-ACCESS  read-only
   STATUS      current
   DESCRIPTION
       "IPv4/IPv6 Network address.
        Note: All entries in routes table will be sort by 1.network address 2.mask length 3. gateway 4. next hop VLAN, if you add/modify an entry, all entries will be reordered. Please check all entries in table to find your modified entry after set/add an entry."
   ::= {sispm1040582lrtIPRoutesConfiguredEntry 3 }

sispm1040582lrtIPRoutesMaskLengthConfigured OBJECT-TYPE
   SYNTAX      Integer32 (1..32)
   MAX-ACCESS  read-only
   STATUS      current
   DESCRIPTION
       "IPv4/IPv6 mask length.
        Note: All entries in routes table will be sort by 1.network address 2.mask length 3. gateway 4. next hop VLAN, if you add/modify an entry, all entries will be reordered. Please check all entries in table to find your modified entry after set/add an entry."
   ::= { sispm1040582lrtIPRoutesConfiguredEntry 4 }

sispm1040582lrtIPRoutesGatewayConfigured OBJECT-TYPE
   SYNTAX      DisplayString (SIZE (0..30))
   MAX-ACCESS  read-only
   STATUS      current
   DESCRIPTION
       "IPv4/IPv6 Gateway.
        Note: All entries in routes table will be sort by 1.network address 2.mask length 3. gateway 4. next hop VLAN, if you add/modify an entry, all entries will be reordered. Please check all entries in table to find your modified entry after set/add an entry."
   ::= {sispm1040582lrtIPRoutesConfiguredEntry 5 }

sispm1040582lrtIPRoutesNextHopVLANConfigured OBJECT-TYPE
   SYNTAX      Integer32 (1..4095)
   MAX-ACCESS  read-only
   STATUS      current
   DESCRIPTION
       "Next Hop VLAN ID, range: 1-4095.
        Note: All entries in routes table will be sort by 1.network address 2.mask length 3. gateway 4. next hop VLAN, if you add/modify an entry, all entries will be reordered. Please check all entries in table to find your modified entry after set/add an entry."
   ::= {sispm1040582lrtIPRoutesConfiguredEntry 6 }

sispm1040582lrtIPStatusInterface OBJECT IDENTIFIER ::= { sispm1040582lrtIP 7 }

sispm1040582lrtIPStatusInterfaceTable OBJECT-TYPE
              SYNTAX      SEQUENCE OF     SISPM1040582LRTIPStatusInterfaceEntry
              MAX-ACCESS  not-accessible
              STATUS      current
              DESCRIPTION
                       "The system IP Status table to show all IP interfaces."
                   ::= {     sispm1040582lrtIPStatusInterface 1 }

    sispm1040582lrtIPStatusInterfaceEntry OBJECT-TYPE
               SYNTAX          SISPM1040582LRTIPStatusInterfaceEntry
               MAX-ACCESS  not-accessible
               STATUS      current
               DESCRIPTION
                       "An entry in the IP Status Table."
               INDEX    {    sispm1040582lrtIPStatusInterfaceIndex  }
               ::= {     sispm1040582lrtIPStatusInterfaceTable 1 }

    SISPM1040582LRTIPStatusInterfaceEntry             ::= SEQUENCE {
            sispm1040582lrtIPStatusInterfaceIndex         Integer32,
            sispm1040582lrtIPStatusInterfaceName          DisplayString,
            sispm1040582lrtIPStatusInterfaceType          DisplayString,
            sispm1040582lrtIPStatusInterfaceAddress       DisplayString,
            sispm1040582lrtIPStatusInterfaceStatus        DisplayString
            }

    sispm1040582lrtIPStatusInterfaceIndex OBJECT-TYPE
               SYNTAX      Integer32(1..1024)
               MAX-ACCESS  not-accessible
               STATUS      current
               DESCRIPTION
                   "The entry of table to show all IP interfaces."
               ::= {     sispm1040582lrtIPStatusInterfaceEntry 1 }

    sispm1040582lrtIPStatusInterfaceName OBJECT-TYPE
               SYNTAX      DisplayString
               MAX-ACCESS  read-only
               STATUS      current
               DESCRIPTION
                   "The name of the interface."
               ::= {     sispm1040582lrtIPStatusInterfaceEntry 2 }

    sispm1040582lrtIPStatusInterfaceType OBJECT-TYPE
               SYNTAX      DisplayString
               MAX-ACCESS  read-only
               STATUS      current
               DESCRIPTION
                   "The address type of the entry. This may be LINK or IPv4."
               ::= {     sispm1040582lrtIPStatusInterfaceEntry 3 }

    sispm1040582lrtIPStatusInterfaceAddress OBJECT-TYPE
               SYNTAX      DisplayString
               MAX-ACCESS  read-only
               STATUS      current
               DESCRIPTION
                   "The current address of the interface (of the given type)."
               ::= {     sispm1040582lrtIPStatusInterfaceEntry 4 }

    sispm1040582lrtIPStatusInterfaceStatus OBJECT-TYPE
               SYNTAX      DisplayString
               MAX-ACCESS  read-only
               STATUS      current
               DESCRIPTION
                   "The status flags of the interface (and/or address)."
               ::= {     sispm1040582lrtIPStatusInterfaceEntry 5 }

sispm1040582lrtIPStatusRoute OBJECT IDENTIFIER ::= { sispm1040582lrtIP 8 }

    sispm1040582lrtIPStatusRouteTable OBJECT-TYPE
              SYNTAX      SEQUENCE OF     SISPM1040582LRTIPStatusRouteEntry
              MAX-ACCESS  not-accessible
              STATUS      current
              DESCRIPTION
                       "The IP Status Route table show all routing entries."
                   ::= {     sispm1040582lrtIPStatusRoute 1 }

    sispm1040582lrtIPStatusRouteEntry OBJECT-TYPE
               SYNTAX          SISPM1040582LRTIPStatusRouteEntry
               MAX-ACCESS  not-accessible
               STATUS      current
               DESCRIPTION
                       "an entry in the IP Status route table."
               INDEX    {     sispm1040582lrtIPStatusRouteIndex  }
               ::= {     sispm1040582lrtIPStatusRouteTable 1 }

    SISPM1040582LRTIPStatusRouteEntry             ::= SEQUENCE {
            sispm1040582lrtIPStatusRouteIndex          Integer32,
            sispm1040582lrtIPStatusRouteNetwork        DisplayString,
            sispm1040582lrtIPStatusRouteGateway        DisplayString,
            sispm1040582lrtIPStatusRouteAddress        DisplayString
     }

    sispm1040582lrtIPStatusRouteIndex OBJECT-TYPE
               SYNTAX      Integer32(1..2048)
               MAX-ACCESS  not-accessible
               STATUS      current
               DESCRIPTION
                   "The entry of table to show all routing entries."
               ::= {     sispm1040582lrtIPStatusRouteEntry 1 }

    sispm1040582lrtIPStatusRouteNetwork OBJECT-TYPE
               SYNTAX      DisplayString
               MAX-ACCESS  read-only
               STATUS      current
               DESCRIPTION
                   "The destination IP network or host address of this route."
               ::= {     sispm1040582lrtIPStatusRouteEntry 2 }

    sispm1040582lrtIPStatusRouteGateway OBJECT-TYPE
               SYNTAX      DisplayString
               MAX-ACCESS  read-only
               STATUS      current
               DESCRIPTION
                   "The gateway address of this route."
               ::= {     sispm1040582lrtIPStatusRouteEntry 3 }

    sispm1040582lrtIPStatusRouteAddress OBJECT-TYPE
               SYNTAX      DisplayString
               MAX-ACCESS  read-only
               STATUS      current
               DESCRIPTION
                   "The route address."
               ::= {     sispm1040582lrtIPStatusRouteEntry 4 }

sispm1040582lrtIPStatusNeighborCache OBJECT IDENTIFIER ::= { sispm1040582lrtIP 9 }

    sispm1040582lrtIPStatusNeighborCacheTable OBJECT-TYPE
               SYNTAX      SEQUENCE OF     SISPM1040582LRTIPStatusNeighborCacheEntry
               MAX-ACCESS  not-accessible
               STATUS      current
               DESCRIPTION
                       "The Ip Status Neighbor Cache Table."
                   ::= {     sispm1040582lrtIPStatusNeighborCache 1 }

    sispm1040582lrtIPStatusNeighborCacheEntry OBJECT-TYPE
               SYNTAX          SISPM1040582LRTIPStatusNeighborCacheEntry
               MAX-ACCESS  not-accessible
               STATUS      current
               DESCRIPTION
                       "An entry in the Ip Status Neighbor Cache Table."
               INDEX    {     sispm1040582lrtIPStatusNeighborCacheIndex  }
               ::= {     sispm1040582lrtIPStatusNeighborCacheTable 1 }

    SISPM1040582LRTIPStatusNeighborCacheEntry             ::= SEQUENCE {
            sispm1040582lrtIPStatusNeighborCacheIndex            Integer32,
            sispm1040582lrtIPStatusNeighborCacheIPAddress        DisplayString,
            sispm1040582lrtIPStatusNeighborCacheLinkAddress      DisplayString
            }

    sispm1040582lrtIPStatusNeighborCacheIndex OBJECT-TYPE
               SYNTAX      Integer32(1..1024)
               MAX-ACCESS  not-accessible
               STATUS      current
               DESCRIPTION
                   "The index for the Ip Status Neighbor Cache Table."
               ::= {     sispm1040582lrtIPStatusNeighborCacheEntry 1 }

    sispm1040582lrtIPStatusNeighborCacheIPAddress OBJECT-TYPE
               SYNTAX      DisplayString
               MAX-ACCESS  read-only
               STATUS      current
               DESCRIPTION
                   "The IP address of the entry."
               ::= {     sispm1040582lrtIPStatusNeighborCacheEntry 2 }

    sispm1040582lrtIPStatusNeighborCacheLinkAddress OBJECT-TYPE
               SYNTAX      DisplayString
               MAX-ACCESS  read-only
               STATUS      current
               DESCRIPTION
                   "The Link (MAC) address for which a binding to the
                    IP address given exist."
               ::= {     sispm1040582lrtIPStatusNeighborCacheEntry 3 }

sispm1040582lrtIPStatusDNSServer OBJECT IDENTIFIER ::= { sispm1040582lrtIP 10 }

    sispm1040582lrtIPStatusDNSServerType OBJECT-TYPE
               SYNTAX      DisplayString
               MAX-ACCESS  read-only
               STATUS      current
               DESCRIPTION
                   "The configuration type of DNS server."
               ::= {     sispm1040582lrtIPStatusDNSServer 1 }

    sispm1040582lrtIPStatusDNSServerIPAddress OBJECT-TYPE
               SYNTAX      DisplayString
               MAX-ACCESS  read-only
               STATUS      current
               DESCRIPTION
                   "The IP address of the DNS server."
               ::= {     sispm1040582lrtIPStatusDNSServer 2 }

    sispm1040582lrtIPStatusDNSServerInterface OBJECT-TYPE
               SYNTAX      DisplayString
               MAX-ACCESS  read-only
               STATUS      current
               DESCRIPTION
                   "The name of the interface."
               ::= {     sispm1040582lrtIPStatusDNSServer 3 }			   
			   
-- =======================================================================================================================
sispm1040582lrtSyslog                                                OBJECT IDENTIFIER ::= { sispm1040582lrtSystem 5 }

sispm1040582lrtSyslogConf                                            OBJECT IDENTIFIER ::= { sispm1040582lrtSyslog 1 }

sispm1040582lrtSysLogInfo                                            OBJECT IDENTIFIER   ::= {  sispm1040582lrtSyslog 2 }
--
-- =======================================================================================================================
-- Objects in the sispm1040582lrtSystemLog Group
-- =======================================================================================================================
--sispm1040582lrtSystemLogConf

    sispm1040582lrtSystemLogServerMode OBJECT-TYPE
               SYNTAX      AdminMode
               MAX-ACCESS  read-write
               STATUS      current
               DESCRIPTION
                   "The System log server mode admin state."
               DEFVAL  { disable }
               ::= {     sispm1040582lrtSyslogConf 1 }

    sispm1040582lrtSystemLogServerAddress OBJECT-TYPE
               SYNTAX      DisplayString
               MAX-ACCESS  read-write
               STATUS      current
               DESCRIPTION
                   "The Host address of syslog server."
               ::= {     sispm1040582lrtSyslogConf 2 }

--    sispm1040582lrtSystemLogSyslogLevel OBJECT-TYPE
--               SYNTAX      INTEGER {
--                    info(0),
--                    warning(1),
--                    error(2)
--               }
--               MAX-ACCESS  read-write
--               STATUS      current
--               DESCRIPTION
--                   "The syslog level.
--                       info(0)   : Info.
--                       warning(1): Warning.
--                       error(2)  : Error."
--               DEFVAL  { info }
--               ::= {     sispm1040582lrtSyslogConf 3 }

    sispm1040582lrtSystemLogServerPort OBJECT-TYPE
                 SYNTAX      Integer32(1..65535)
                 MAX-ACCESS  read-write
                 STATUS      current
                 DESCRIPTION
                      "syslog service port number.
                 range : 1-65535, default : 514."
               ::= {     sispm1040582lrtSyslogConf 4 }

--sispm1040582lrtSystemLogInfo
    sispm1040582lrtSystemLogInfoLevel OBJECT-TYPE
               SYNTAX      INTEGER { emergency(0), alert(1), critical(2), error(3), warning(4), notice(5), information(6), debug(7), all(8) }
               MAX-ACCESS  read-write
               STATUS      current
               DESCRIPTION
                  "The Level input field is used to filter the display system log entries.
                   0: Emergency.
                   1: Alert.
                   2: Critical.
                   3: Error.
                   4: Warning.
                   5: Notice.
                   6: Information.
                   7: Debug.
                   8: All."
               DEFVAL  { all }
               ::= {     sispm1040582lrtSysLogInfo 1 }

    sispm1040582lrtSystemLogInfoClearLevel OBJECT-TYPE
               SYNTAX      INTEGER { emergency(0), alert(1), critical(2), error(3), warning(4), notice(5), information(6), debug(7), all(8) }
               MAX-ACCESS  read-write
               STATUS      current
               DESCRIPTION
                  "The Clear Level input field is used to specify which
                  system log entries will be cleared.
                  default: 8 (All).
                   0: Emergency.
                   1: Alert.
                   2: Critical.
                   3: Error.
                   4: Warning.
                   5: Notice.
                   6: Information.
                   7: Debug.
                   8: All."
               DEFVAL  { all }
               ::= {     sispm1040582lrtSysLogInfo 2 }

    sispm1040582lrtSystemLogInfoClearCmd OBJECT-TYPE
               SYNTAX      ActivateCmd
               MAX-ACCESS  read-write
               STATUS      current
               DESCRIPTION
                  "Command to clear the syslog.
                   noAction(0) : do nothing  (read only).
                   activate(1) : Clear Syslog."
               DEFVAL  { noAction }
               ::= {     sispm1040582lrtSysLogInfo 3 }

    sispm1040582lrtSystemLogDetailedInfoTable OBJECT-TYPE
              SYNTAX      SEQUENCE OF     SISPM1040582LRTSystemLogDetailedInfoEntry
              MAX-ACCESS  not-accessible
              STATUS      current
              DESCRIPTION
                       "The system detailed Log Info table."
                   ::= {     sispm1040582lrtSysLogInfo 4 }

    sispm1040582lrtSystemLogDetailedInfoEntry OBJECT-TYPE
               SYNTAX          SISPM1040582LRTSystemLogDetailedInfoEntry
               MAX-ACCESS  not-accessible
               STATUS      current
               DESCRIPTION
                       "An entry in the system detailed Log Info table."
               INDEX    {     sispm1040582lrtSystemLogDetailedInfoID  }
               ::= {     sispm1040582lrtSystemLogDetailedInfoTable 1 }

    SISPM1040582LRTSystemLogDetailedInfoEntry             ::= SEQUENCE {
                sispm1040582lrtSystemLogDetailedSwitchIndex       Integer32,
                sispm1040582lrtSystemLogDetailedInfoID            Integer32,
                sispm1040582lrtSystemLogDetailedInfoLevel         DisplayString,
                sispm1040582lrtSystemLogDetailedInfoTime          DisplayString,
                sispm1040582lrtSystemLogDetailedInfoMessage       DisplayString
                }

    sispm1040582lrtSystemLogDetailedSwitchIndex OBJECT-TYPE
               SYNTAX      Integer32(1..16)
               MAX-ACCESS  not-accessible
               STATUS      current
               DESCRIPTION
                   "The switch index for the system detailed Log Info table."
               ::= {     sispm1040582lrtSystemLogDetailedInfoEntry 1 }

    sispm1040582lrtSystemLogDetailedInfoID OBJECT-TYPE
               SYNTAX      Integer32(1..999)
               MAX-ACCESS  not-accessible
               STATUS      current
               DESCRIPTION
                   "The index for the system detailed Log Info table."
               ::= {     sispm1040582lrtSystemLogDetailedInfoEntry 2 }

    sispm1040582lrtSystemLogDetailedInfoLevel OBJECT-TYPE
               SYNTAX      DisplayString
               MAX-ACCESS  read-only
               STATUS      current
               DESCRIPTION
                   "The Info Level."
               ::= {     sispm1040582lrtSystemLogDetailedInfoEntry 3 }

    sispm1040582lrtSystemLogDetailedInfoTime OBJECT-TYPE
               SYNTAX      DisplayString(SIZE (0..20))
               MAX-ACCESS  read-only
               STATUS      current
               DESCRIPTION
                   "The time"
               ::= {     sispm1040582lrtSystemLogDetailedInfoEntry 4 }

    sispm1040582lrtSystemLogDetailedInfoMessage OBJECT-TYPE
               SYNTAX      DisplayString
               MAX-ACCESS  read-only
               STATUS      current
               DESCRIPTION
                   "The message of this entry."
               ::= {     sispm1040582lrtSystemLogDetailedInfoEntry 5 }
               
    sispm1040582lrtSystemDORelayOpenClose OBJECT-TYPE
               SYNTAX      Integer32
               MAX-ACCESS  read-write
               STATUS      current
               DESCRIPTION
                  "DO Relay Open/Close.
				  1:Open
				  0:Close"
               ::= {     sispm1040582lrtSysLogInfo 5 }
-- =======================================================================================================================
sispm1040582lrtSnmp                                                OBJECT IDENTIFIER ::= { sispm1040582lrtSystem 6 }

sispm1040582lrtSnmpSystem                                            OBJECT IDENTIFIER ::= { sispm1040582lrtSnmp 1 }

sispm1040582lrtSnmpSystemMode OBJECT-TYPE
   SYNTAX       Integer32
   MAX-ACCESS   read-write
   STATUS       current
   DESCRIPTION
       "SNMP mode operation.
        default : 1, 0: disable, 1: enable. "
   ::= { sispm1040582lrtSnmpSystem 1 }

sispm1040582lrtSnmpSystemVersion OBJECT-TYPE
   SYNTAX       Integer32
   MAX-ACCESS   read-write
   STATUS       current
   DESCRIPTION
       "SNMP supported version.
       default : snmpv2c.
       0: snmpv1
       1: snmpv2c
       2: snmpv3."
   ::= { sispm1040582lrtSnmpSystem 2 }

sispm1040582lrtSnmpSystemReadCommunity OBJECT-TYPE
   SYNTAX       DisplayString
   MAX-ACCESS   read-write
   STATUS       current
   DESCRIPTION
       "Indicates the community read access string to permit access to SNMP agent.
       The allowed string length is 0 to 255.
       The field is applicable only when SNMP version is SNMPv1 or SNMPv2c."
   ::= { sispm1040582lrtSnmpSystem 3 }

sispm1040582lrtSnmpSystemWriteCommunity OBJECT-TYPE
   SYNTAX       DisplayString
   MAX-ACCESS   read-write
   STATUS       current
   DESCRIPTION
       "Indicates the community write access string to permit access to SNMP agent.
       The allowed string length is 0 to 255.
       The field is applicable only when SNMP version is SNMPv1 or SNMPv2c."
   ::= { sispm1040582lrtSnmpSystem 4 }

sispm1040582lrtSnmpSystemEngineID OBJECT-TYPE
   SYNTAX       DisplayString
   MAX-ACCESS   read-write
   STATUS       current
   DESCRIPTION
       "Indicates the SNMPv3 engine ID.
        The string must contain an even number(in hexadecimal format) with number of digits between 10 and 64,
	but all-zeros and all-'F's are not allowed.
	Allow string length is 10 to 32.
	Change of the Engine ID will clear all original local users."
   ::= { sispm1040582lrtSnmpSystem 5 }

sispm1040582lrtSnmpSystemWriteCommunityMode OBJECT-TYPE
   SYNTAX       Integer32
   MAX-ACCESS   read-write
   STATUS       current
   DESCRIPTION
       "SNMP write community mode operation.
        default : 1, 0: disable, 1: enable. "
   ::= { sispm1040582lrtSnmpSystem 6 }

sispm1040582lrtSnmpTrapGlobalMode OBJECT-TYPE
   SYNTAX       Integer32
   MAX-ACCESS   read-write
   STATUS       current
   DESCRIPTION
       "Indicates the trap mode operation.
        0:Disable.
	1:Enable."
   ::= { sispm1040582lrtSnmp 2 }

sispm1040582lrtTrapDestinationConfTable OBJECT-TYPE
   SYNTAX      SEQUENCE OF SISPM1040582LRTTrapDestinationConfEntry
   MAX-ACCESS  not-accessible
   STATUS      current
   DESCRIPTION
       "A list of trap host entry. The numbers of entries are given by the value of TrapHostConfNumber."
   ::= { sispm1040582lrtSnmp 3 }

sispm1040582lrtTrapDestinationConfEntry OBJECT-TYPE
   SYNTAX      SISPM1040582LRTTrapDestinationConfEntry
   MAX-ACCESS  not-accessible
   STATUS      current
   DESCRIPTION
       "This is the entry information for trap host."
   INDEX    { sispm1040582lrtTrapDestinationConfIndex  }
   ::= { sispm1040582lrtTrapDestinationConfTable 1 }

SISPM1040582LRTTrapDestinationConfEntry ::= SEQUENCE {
    sispm1040582lrtTrapDestinationConfIndex                      Integer32,
    sispm1040582lrtTrapDestinationConfTrapConfigName             DisplayString,
    sispm1040582lrtTrapDestinationConfTrapMode                   Integer32,
    sispm1040582lrtTrapDestinationConfTrapVersion                Integer32,
    sispm1040582lrtTrapDestinationConfTrapCommunity              DisplayString,
    sispm1040582lrtTrapDestinationConfTrapDestinationAddres      DisplayString,
    sispm1040582lrtTrapDestinationConfTrapDestinationPort        Integer32,
    sispm1040582lrtTrapDestinationConfTrapInformMode             Integer32,
    sispm1040582lrtTrapDestinationConfTrapInformTimeout          Integer32,
    sispm1040582lrtTrapDestinationConfTrapInformRetryTimes       Integer32,
    sispm1040582lrtTrapDestinationConfTrapProbeSecurityEngineID  Integer32,
    sispm1040582lrtTrapDestinationConfTrapSecurityEngineID       DisplayString,
    sispm1040582lrtTrapDestinationConfTrapSecurityName           DisplayString,
    sispm1040582lrtTrapDestinationConfTrapRowStatus              Integer32
}

sispm1040582lrtTrapDestinationConfIndex OBJECT-TYPE
   SYNTAX       Integer32
   MAX-ACCESS   not-accessible
   STATUS       current
   DESCRIPTION
       "Index of tarp destination configurations."
   ::= { sispm1040582lrtTrapDestinationConfEntry 1 }

sispm1040582lrtTrapDestinationConfTrapConfigName OBJECT-TYPE
   SYNTAX       DisplayString
   MAX-ACCESS   read-write
   STATUS       current
   DESCRIPTION
       "Indicates which trap Configuration's name for configuring.
       The allowed string length is 0 to 255, and the allowed content is
       ASCII characters from 33 to 126."
   ::= { sispm1040582lrtTrapDestinationConfEntry 2 }

sispm1040582lrtTrapDestinationConfTrapMode OBJECT-TYPE
   SYNTAX       Integer32
   MAX-ACCESS   read-write
   STATUS       current
   DESCRIPTION
       "Indicates the SNMP mode operation. Possible modes are:
        2: Enable TCP SNMP mode operation.
        1: Enable UDP SNMP mode operation.
        0: Disable SNMP mode operation. "
   ::= { sispm1040582lrtTrapDestinationConfEntry 3 }

sispm1040582lrtTrapDestinationConfTrapVersion OBJECT-TYPE
   SYNTAX       Integer32
   MAX-ACCESS   read-write
   STATUS       current
   DESCRIPTION
       "0: snmpv1
        1: snmpv2c
        3: snmpv3.
        "
   ::= { sispm1040582lrtTrapDestinationConfEntry 4 }

sispm1040582lrtTrapDestinationConfTrapCommunity OBJECT-TYPE
   SYNTAX       DisplayString
   MAX-ACCESS   read-write
   STATUS       current
   DESCRIPTION
       "Indicates the community access string when sending SNMP trap packet.
       The allowed string length is 0 to 255, and the allowed content is
       ASCII characters from 33 to 126."
   ::= { sispm1040582lrtTrapDestinationConfEntry 5 }

sispm1040582lrtTrapDestinationConfTrapDestinationAddres OBJECT-TYPE
   SYNTAX       DisplayString
   MAX-ACCESS   read-write
   STATUS       current
   DESCRIPTION
       "Indicates the SNMP trap destination address.
       It allow a valid IP address in dotted decimal notation ('x.y.z.w').
    And it also allow a valid hostname.
    A valid hostname is a string drawn from the alphabet (A-Za-z), digits (0-9),
    dot (.), dash (-). Spaces are not allowed, the first character must be an alpha character,
    and the first and last characters must not be a dot or a dash.
    Indicates the SNMP trap destination IPv6 address.
    IPv6 address is in 128-bit records represented as eight fields of up to four hexadecimal digits
    with a colon separating each field (:).
    For example, 'fe80::215:c5ff:fe03:4dc7'. The symbol '::' is a special syntax
    that can be used as a shorthand way of representing multiple 16-bit groups of contiguous zeros;
    but it can appear only once.
    It can also represent a legally valid IPv4 address.
    For example, '::192.1.2.34'."
   ::= { sispm1040582lrtTrapDestinationConfEntry 6 }

sispm1040582lrtTrapDestinationConfTrapDestinationPort OBJECT-TYPE
   SYNTAX       Integer32
   MAX-ACCESS   read-write
   STATUS       current
   DESCRIPTION
       "Indicates the SNMP trap destination port.
       SNMP Agent will send SNMP message via this port,
       the port range is 1~65535."
   ::= { sispm1040582lrtTrapDestinationConfEntry 7 }

sispm1040582lrtTrapDestinationConfTrapInformMode OBJECT-TYPE
   SYNTAX       Integer32
   MAX-ACCESS   read-write
   STATUS       current
   DESCRIPTION
       "Indicates the SNMP trap inform mode operation. Possible modes are:
        1: Enable SNMP trap inform mode operation.
        0: Disable SNMP trap inform mode operation. "
   ::= { sispm1040582lrtTrapDestinationConfEntry 8 }

sispm1040582lrtTrapDestinationConfTrapInformTimeout OBJECT-TYPE
   SYNTAX       Integer32
   MAX-ACCESS   read-write
   STATUS       current
   DESCRIPTION
       "Indicates the SNMP trap inform timeout. The allowed range is 0 to 2147."
   ::= { sispm1040582lrtTrapDestinationConfEntry 9 }

sispm1040582lrtTrapDestinationConfTrapInformRetryTimes OBJECT-TYPE
   SYNTAX       Integer32
   MAX-ACCESS   read-write
   STATUS       current
   DESCRIPTION
       "Indicates the SNMP trap inform retry times. The allowed range is 0 to 255."
   ::= { sispm1040582lrtTrapDestinationConfEntry 10 }

sispm1040582lrtTrapDestinationConfTrapProbeSecurityEngineID OBJECT-TYPE
   SYNTAX       Integer32
   MAX-ACCESS   read-write
   STATUS       current
   DESCRIPTION
       "Indicates the SNMP trap probe security engine ID mode of operation.
       Possible values are:
       1: Enable SNMP trap probe security engine ID mode of operation.
       0: Disable SNMP trap probe security engine ID mode of operation."
   ::= { sispm1040582lrtTrapDestinationConfEntry 11 }

sispm1040582lrtTrapDestinationConfTrapSecurityEngineID OBJECT-TYPE
   SYNTAX       DisplayString
   MAX-ACCESS   read-write
   STATUS       current
   DESCRIPTION
       "Indicates the SNMP trap security engine ID.
       SNMPv3 sends traps and informs using USM for authentication and privacy.
       A unique engine ID for these traps and informs is needed.
       When Trap Probe Security Engine ID is enabled, the ID will be probed automatically.
       Otherwise, the ID specified in this field is used.
       The string must contain an even number(in hexadecimal format) with
       number of digits between 10 and 64, but all-zeros and all-'F's are not allowed."
   ::= { sispm1040582lrtTrapDestinationConfEntry 12 }

sispm1040582lrtTrapDestinationConfTrapSecurityName OBJECT-TYPE
   SYNTAX       DisplayString
   MAX-ACCESS   read-write
   STATUS       current
   DESCRIPTION
       "Indicates the SNMP trap security name.
       SNMPv3 traps and informs using USM for authentication and privacy.
       A unique security name is needed when traps and informs are enabled.
       This name from user name of user configuration."
   ::= { sispm1040582lrtTrapDestinationConfEntry 13 }

sispm1040582lrtTrapDestinationConfTrapRowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sispm1040582lrtTrapDestinationConfEntry 14 }


sispm1040582lrtSNMPCommunityConfTable OBJECT-TYPE
   SYNTAX      SEQUENCE OF SISPM1040582LRTSNMPCommunityConfEntry
   MAX-ACCESS  not-accessible
   STATUS      current
   DESCRIPTION
       "A list of snmp community configuration entry."
   ::= { sispm1040582lrtSnmp 5 }

sispm1040582lrtSNMPCommunityConfEntry OBJECT-TYPE
   SYNTAX      SISPM1040582LRTSNMPCommunityConfEntry
   MAX-ACCESS  not-accessible
   STATUS      current
   DESCRIPTION
       "This is the entry information for snmp community configuration."
   INDEX    { sispm1040582lrtSNMPCommunityConfIndex  }
   ::= { sispm1040582lrtSNMPCommunityConfTable 1 }

SISPM1040582LRTSNMPCommunityConfEntry ::= SEQUENCE {
    sispm1040582lrtSNMPCommunityConfIndex                       Integer32,
    sispm1040582lrtSNMPCommunityConfSNMPv3Community             DisplayString,
    sispm1040582lrtSNMPCommunityConfSNMPv3SourceIP              IpAddress,
    sispm1040582lrtSNMPCommunityConfSNMPv3SourceMask            IpAddress,
    sispm1040582lrtSNMPCommunityConfSNMPv3RowStatus             Integer32
}

sispm1040582lrtSNMPCommunityConfIndex OBJECT-TYPE
   SYNTAX       Integer32
   MAX-ACCESS   read-write
   STATUS       current
   DESCRIPTION
       "Community configuration index."
   ::= { sispm1040582lrtSNMPCommunityConfEntry 1 }

sispm1040582lrtSNMPCommunityConfSNMPv3Community OBJECT-TYPE
   SYNTAX       DisplayString
   MAX-ACCESS   read-write
   STATUS       current
   DESCRIPTION
       "Indicates the community access string to permit access to SNMPv3 agent.
       The allowed string length is 1 to 32, and the allowed content is
       ASCII characters from 33 to 126.
       The community string will be treated as security name and map a SNMPv1
       or SNMPv2c community string."
   ::= { sispm1040582lrtSNMPCommunityConfEntry 2 }


sispm1040582lrtSNMPCommunityConfSNMPv3SourceIP OBJECT-TYPE
   SYNTAX      IpAddress
   MAX-ACCESS  read-write
   STATUS      current
   DESCRIPTION
       "Indicates the SNMP access source address.
       A particular range of source addresses can be used to restrict source subnet
       when combined with source mask."
   ::= {sispm1040582lrtSNMPCommunityConfEntry 3 }

sispm1040582lrtSNMPCommunityConfSNMPv3SourceMask OBJECT-TYPE
   SYNTAX      IpAddress
   MAX-ACCESS  read-write
   STATUS      current
   DESCRIPTION
       "Indicates the SNMP access source address mask."
   ::= {sispm1040582lrtSNMPCommunityConfEntry 4 }

sispm1040582lrtSNMPCommunityConfSNMPv3RowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sispm1040582lrtSNMPCommunityConfEntry 5 }

sispm1040582lrtSNMPv3UserConfTable OBJECT-TYPE
   SYNTAX      SEQUENCE OF SISPM1040582LRTSNMPv3UserConfEntry
   MAX-ACCESS  not-accessible
   STATUS      current
   DESCRIPTION
       "A list of snmpv3 user configuration entry."
   ::= { sispm1040582lrtSnmp 6 }

sispm1040582lrtSNMPv3UserConfEntry OBJECT-TYPE
   SYNTAX      SISPM1040582LRTSNMPv3UserConfEntry
   MAX-ACCESS  not-accessible
   STATUS      current
   DESCRIPTION
       "This is the entry information for snmpv3 user configuration."
   INDEX    { sispm1040582lrtSNMPv3UserConfIndex  }
   ::= { sispm1040582lrtSNMPv3UserConfTable 1 }

SISPM1040582LRTSNMPv3UserConfEntry ::= SEQUENCE {
    sispm1040582lrtSNMPv3UserConfIndex                     Integer32,
    sispm1040582lrtSNMPv3UserConfEngineID                  DisplayString,
    sispm1040582lrtSNMPv3UserConfUserName                  DisplayString,
    sispm1040582lrtSNMPv3UserConfSecurityLevel             Integer32,
    sispm1040582lrtSNMPv3UserConfAuthenticationProtocol    Integer32,
    sispm1040582lrtSNMPv3UserConfAuthenticationPassword    DisplayString,
    sispm1040582lrtSNMPv3UserConfPrivacyProtocol           Integer32,
    sispm1040582lrtSNMPv3UserConfPrivacyPassword           DisplayString,
    sispm1040582lrtSNMPv3UserConfRowStatus                 RowStatus
}

sispm1040582lrtSNMPv3UserConfIndex OBJECT-TYPE
   SYNTAX       Integer32
   MAX-ACCESS   read-write
   STATUS       current
   DESCRIPTION
       "User configuration index."
   ::= { sispm1040582lrtSNMPv3UserConfEntry 1 }

sispm1040582lrtSNMPv3UserConfEngineID OBJECT-TYPE
   SYNTAX       DisplayString
   MAX-ACCESS   read-write
   STATUS       current
   DESCRIPTION
       "An octet string identifying the engine ID that this entry should belong to.
       The string must contain an even number(in hexadecimal format) with
       number of digits between 10 and 64, but all-zeros and all-'F's are not allowed.
       The SNMPv3 architecture uses the User-based Security Model (USM)
       for message security and the View-based Access Control Model (VACM) for access control.
       For the USM entry, the usmUserEngineID and usmUserName are the entry's keys.
       In a simple agent, usmUserEngineID is always that agent's own snmpEngineID value.
       The value can also take the value of the snmpEngineID of a remote SNMP engine with
       which this user can communicate. In other words, if user engine ID equal system engine ID
       then it is local user; otherwise it's remote user. "
   ::= { sispm1040582lrtSNMPv3UserConfEntry 2 }

sispm1040582lrtSNMPv3UserConfUserName OBJECT-TYPE
   SYNTAX       DisplayString
   MAX-ACCESS   read-write
   STATUS       current
   DESCRIPTION
       "A string identifying the user name that this entry should belong to.
       The allowed string length is 1 to 32, and the allowed content is
       ASCII characters from 33 to 126."
   ::= { sispm1040582lrtSNMPv3UserConfEntry 3 }

sispm1040582lrtSNMPv3UserConfSecurityLevel OBJECT-TYPE
   SYNTAX       Integer32
   MAX-ACCESS   read-write
   STATUS       current
   DESCRIPTION
       "1:NoAuth, NoPriv
        2:Auth, NoPriv
	3:Auth, Priv"
   ::= { sispm1040582lrtSNMPv3UserConfEntry 4 }

sispm1040582lrtSNMPv3UserConfAuthenticationProtocol OBJECT-TYPE
   SYNTAX       Integer32
   MAX-ACCESS   read-write
   STATUS       current
   DESCRIPTION
       "0:None
        1:MD5
	2:SHA"
   ::= { sispm1040582lrtSNMPv3UserConfEntry 5 }

sispm1040582lrtSNMPv3UserConfAuthenticationPassword OBJECT-TYPE
   SYNTAX       DisplayString
   MAX-ACCESS   read-write
   STATUS       current
   DESCRIPTION
       "A string identifying the authentication password phrase.
       For MD5 authentication protocol, the allowed string length is 8 to 32.
       For SHA authentication protocol, the allowed string length is 8 to 40.
       The allowed content is ASCII characters from 33 to 126."
   ::= { sispm1040582lrtSNMPv3UserConfEntry 6 }

sispm1040582lrtSNMPv3UserConfPrivacyProtocol OBJECT-TYPE
   SYNTAX       Integer32
   MAX-ACCESS   read-write
   STATUS       current
   DESCRIPTION
       "0:None
        1:DES
        2:AES"
   ::= { sispm1040582lrtSNMPv3UserConfEntry 7 }

sispm1040582lrtSNMPv3UserConfPrivacyPassword OBJECT-TYPE
   SYNTAX       DisplayString
   MAX-ACCESS   read-write
   STATUS       current
   DESCRIPTION
       "A string identifying the privacy password phrase.
       The allowed string length is 8 to 32, and the allowed content is
       ASCII characters from 33 to 126."
   ::= { sispm1040582lrtSNMPv3UserConfEntry 8 }

sispm1040582lrtSNMPv3UserConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm1040582lrtSNMPv3UserConfEntry 9 }

sispm1040582lrtSNMPv3GroupConfTable OBJECT-TYPE
   SYNTAX      SEQUENCE OF SISPM1040582LRTSNMPv3GroupConfEntry
   MAX-ACCESS  not-accessible
   STATUS      current
   DESCRIPTION
       "A list of snmpv3 group configuration entry."
   ::= { sispm1040582lrtSnmp 7 }

sispm1040582lrtSNMPv3GroupConfEntry OBJECT-TYPE
   SYNTAX      SISPM1040582LRTSNMPv3GroupConfEntry
   MAX-ACCESS  not-accessible
   STATUS      current
   DESCRIPTION
       "This is the entry information for snmpv3 group configuration."
   INDEX    { sispm1040582lrtSNMPv3GroupConfIndex  }
   ::= { sispm1040582lrtSNMPv3GroupConfTable 1 }

SISPM1040582LRTSNMPv3GroupConfEntry ::= SEQUENCE {
    sispm1040582lrtSNMPv3GroupConfIndex                     Integer32,
    sispm1040582lrtSNMPv3GroupConfSecurityModel             Integer32,
    sispm1040582lrtSNMPv3GroupConfSecurityName          DisplayString,
    sispm1040582lrtSNMPv3GroupConfGroupName             DisplayString,
    sispm1040582lrtSNMPv3GroupConfRowStatus                 RowStatus
}

sispm1040582lrtSNMPv3GroupConfIndex OBJECT-TYPE
   SYNTAX       Integer32
   MAX-ACCESS   read-write
   STATUS       current
   DESCRIPTION
       "Group configuration index."
   ::= { sispm1040582lrtSNMPv3GroupConfEntry 1 }

sispm1040582lrtSNMPv3GroupConfSecurityModel OBJECT-TYPE
   SYNTAX       Integer32
   MAX-ACCESS   read-write
   STATUS       current
   DESCRIPTION
       "1:v1
        2:v2c
	3:usm"
   ::= { sispm1040582lrtSNMPv3GroupConfEntry 2 }

sispm1040582lrtSNMPv3GroupConfSecurityName OBJECT-TYPE
   SYNTAX       DisplayString
   MAX-ACCESS   read-write
   STATUS       current
   DESCRIPTION
       "A string identifying the security name that this entry should belong to.
       The allowed string length is 1 to 32, and the allowed content is
       ASCII characters from 33 to 126.
       This name is from the Community of Community configuration."
   ::= { sispm1040582lrtSNMPv3GroupConfEntry 3 }

sispm1040582lrtSNMPv3GroupConfGroupName OBJECT-TYPE
   SYNTAX       DisplayString
   MAX-ACCESS   read-write
   STATUS       current
   DESCRIPTION
       "A string identifying the group name that this entry should belong to.
       The allowed string length is 1 to 32, and the allowed content is
       ASCII characters from 33 to 126. "
   ::= { sispm1040582lrtSNMPv3GroupConfEntry 4 }


sispm1040582lrtSNMPv3GroupConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm1040582lrtSNMPv3GroupConfEntry 5 }

sispm1040582lrtSNMPv3ViewsConfTable OBJECT-TYPE
   SYNTAX      SEQUENCE OF SISPM1040582LRTSNMPv3ViewsConfEntry
   MAX-ACCESS  not-accessible
   STATUS      current
   DESCRIPTION
       "A list of snmpv3 view configuration entry."
   ::= { sispm1040582lrtSnmp 8 }

sispm1040582lrtSNMPv3ViewsConfEntry OBJECT-TYPE
   SYNTAX      SISPM1040582LRTSNMPv3ViewsConfEntry
   MAX-ACCESS  not-accessible
   STATUS      current
   DESCRIPTION
       "This is the entry information for snmpv3 view configuration."
   INDEX    { sispm1040582lrtSNMPv3ViewsConfIndex  }
   ::= { sispm1040582lrtSNMPv3ViewsConfTable 1 }

SISPM1040582LRTSNMPv3ViewsConfEntry ::= SEQUENCE {
    sispm1040582lrtSNMPv3ViewsConfIndex                   Integer32,
    sispm1040582lrtSNMPv3ViewsConfViewName            DisplayString,
    sispm1040582lrtSNMPv3ViewsConfViewType                Integer32,
    sispm1040582lrtSNMPv3ViewsConfOIDSubtree          DisplayString,
    sispm1040582lrtSNMPv3ViewsConfRowStatus               RowStatus
}

sispm1040582lrtSNMPv3ViewsConfIndex OBJECT-TYPE
   SYNTAX       Integer32
   MAX-ACCESS   read-write
   STATUS       current
   DESCRIPTION
       "view configuration index."
   ::= { sispm1040582lrtSNMPv3ViewsConfEntry 1 }

sispm1040582lrtSNMPv3ViewsConfViewName OBJECT-TYPE
   SYNTAX       DisplayString
   MAX-ACCESS   read-write
   STATUS       current
   DESCRIPTION
       "A string identifying the view name that this entry should belong to.
       The allowed string length is 1 to 32, and the allowed content is
       ASCII characters from 33 to 126. "
   ::= { sispm1040582lrtSNMPv3ViewsConfEntry 2 }

sispm1040582lrtSNMPv3ViewsConfViewType OBJECT-TYPE
   SYNTAX       Integer32
   MAX-ACCESS   read-write
   STATUS       current
   DESCRIPTION
       "1:included
       2:excluded"
   ::= { sispm1040582lrtSNMPv3ViewsConfEntry 3 }

sispm1040582lrtSNMPv3ViewsConfOIDSubtree OBJECT-TYPE
   SYNTAX       DisplayString
   MAX-ACCESS   read-write
   STATUS       current
   DESCRIPTION
       "The OID defining the root of the subtree to add to the named view.
       The allowed OID length is 1 to 128. The allowed string content is
       digital number or asterisk(*)"
   ::= { sispm1040582lrtSNMPv3ViewsConfEntry 4 }

sispm1040582lrtSNMPv3ViewsConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm1040582lrtSNMPv3ViewsConfEntry 5 }


sispm1040582lrtSNMPv3AccessConfTable OBJECT-TYPE
   SYNTAX      SEQUENCE OF SISPM1040582LRTSNMPv3AccessConfEntry
   MAX-ACCESS  not-accessible
   STATUS      current
   DESCRIPTION
       "A list of snmpv3 access configuration entry."
   ::= { sispm1040582lrtSnmp 9 }

sispm1040582lrtSNMPv3AccessConfEntry OBJECT-TYPE
   SYNTAX      SISPM1040582LRTSNMPv3AccessConfEntry
   MAX-ACCESS  not-accessible
   STATUS      current
   DESCRIPTION
       "This is the entry information for snmpv3 access configuration."
   INDEX    { sispm1040582lrtSNMPv3AccessConfIndex  }
   ::= { sispm1040582lrtSNMPv3AccessConfTable 1 }

SISPM1040582LRTSNMPv3AccessConfEntry ::= SEQUENCE {
    sispm1040582lrtSNMPv3AccessConfIndex                    Integer32,
    sispm1040582lrtSNMPv3AccessConfGroupName            DisplayString,
    sispm1040582lrtSNMPv3AccessConfSecurityModel            Integer32,
    sispm1040582lrtSNMPv3AccessConfSecurityLevel            Integer32,
    sispm1040582lrtSNMPv3AccessConfReadViewName         DisplayString,
    sispm1040582lrtSNMPv3AccessConfWriteViewName        DisplayString,
    sispm1040582lrtSNMPv3AccessConfRowStatus                RowStatus
}

sispm1040582lrtSNMPv3AccessConfIndex OBJECT-TYPE
   SYNTAX       Integer32
   MAX-ACCESS   read-write
   STATUS       current
   DESCRIPTION
       "Access configuration index"
   ::= { sispm1040582lrtSNMPv3AccessConfEntry 1 }

sispm1040582lrtSNMPv3AccessConfGroupName OBJECT-TYPE
   SYNTAX       DisplayString
   MAX-ACCESS   read-write
   STATUS       current
   DESCRIPTION
       "Group name from Group configuration."
   ::= { sispm1040582lrtSNMPv3AccessConfEntry 2 }

sispm1040582lrtSNMPv3AccessConfSecurityModel OBJECT-TYPE
   SYNTAX       Integer32
   MAX-ACCESS   read-write
   STATUS       current
   DESCRIPTION
       "0:any
        1:v1
	2:v2c
	3:usm"
   ::= { sispm1040582lrtSNMPv3AccessConfEntry 3 }

sispm1040582lrtSNMPv3AccessConfSecurityLevel OBJECT-TYPE
   SYNTAX       Integer32
   MAX-ACCESS   read-write
   STATUS       current
   DESCRIPTION
       "1:NoAuth, NoPriv
       2:Auth, NoPriv
       3:Auth, Priv"
   ::= { sispm1040582lrtSNMPv3AccessConfEntry 4 }

sispm1040582lrtSNMPv3AccessConfReadViewName OBJECT-TYPE
   SYNTAX       DisplayString
   MAX-ACCESS   read-write
   STATUS       current
   DESCRIPTION
       "Read View Name from View configuration."
   ::= { sispm1040582lrtSNMPv3AccessConfEntry 5 }

sispm1040582lrtSNMPv3AccessConfWriteViewName OBJECT-TYPE
   SYNTAX       DisplayString
   MAX-ACCESS   read-write
   STATUS       current
   DESCRIPTION
       "Write View Name from View configuration."
   ::= { sispm1040582lrtSNMPv3AccessConfEntry 6 }

sispm1040582lrtSNMPv3AccessConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm1040582lrtSNMPv3AccessConfEntry 7 }

-- =======================================================================================================================
sispm1040582lrtDHCPServer                                     OBJECT IDENTIFIER ::= { sispm1040582lrtSystem 9 }

sispm1040582lrtDHCPServerConf                                 OBJECT IDENTIFIER ::= { sispm1040582lrtDHCPServer 1 }

sispm1040582lrtDHCPServerMode OBJECT-TYPE
   SYNTAX      Integer32 (0|1)
   MAX-ACCESS  read-write
   STATUS      current
   DESCRIPTION
       "default: 0,
        Global Mode :
        0: Disable,
        1: Enable.
       "
   ::= { sispm1040582lrtDHCPServerConf 1 }

sispm1040582lrtVLANModeTable OBJECT-TYPE
   SYNTAX      SEQUENCE OF SISPM1040582LRTVLANModeEntry
   MAX-ACCESS  not-accessible
   STATUS      current
   DESCRIPTION
       "A table of VLAN Mode for DHCP Server."
    ::= { sispm1040582lrtDHCPServerConf 2 }

sispm1040582lrtVLANModeEntry OBJECT-TYPE
    SYNTAX        SISPM1040582LRTVLANModeEntry
    MAX-ACCESS    not-accessible
    STATUS        current
    DESCRIPTION
        "An entry in the sispm1040582lrtVLANModeTable."
    INDEX        { sispm1040582lrtVLANModeIndex }
    ::= { sispm1040582lrtVLANModeTable 1 }

SISPM1040582LRTVLANModeEntry ::=
    SEQUENCE {
        sispm1040582lrtVLANModeIndex                            Integer32,
        sispm1040582lrtVLANModeRangeLow                         Integer32,
        sispm1040582lrtVLANModeRangeHigh                        Integer32,
        sispm1040582lrtVLANModeEnable                           Integer32,
		sispm1040582lrtVLANModeRowStatus                        RowStatus
    }

sispm1040582lrtVLANModeIndex OBJECT-TYPE
   SYNTAX      Integer32 (1..2048)
   MAX-ACCESS  not-accessible
   STATUS      current
   DESCRIPTION
       "VLAN Mode table index, range: 1-2048."
   ::= {sispm1040582lrtVLANModeEntry 1 }

sispm1040582lrtVLANModeRangeLow OBJECT-TYPE
   SYNTAX      Integer32 (1..4095)
   MAX-ACCESS  read-create
   STATUS      current
   DESCRIPTION
       "VLAN Mode low range: 1-4095."
   ::= {sispm1040582lrtVLANModeEntry 2 }

sispm1040582lrtVLANModeRangeHigh OBJECT-TYPE
   SYNTAX      Integer32 (1..4095)
   MAX-ACCESS  read-create
   STATUS      current
   DESCRIPTION
       "VLAN Mode high range: 1-4095."
   ::= {sispm1040582lrtVLANModeEntry 3 }

sispm1040582lrtVLANModeEnable OBJECT-TYPE
   SYNTAX      Integer32 (0..1)
   MAX-ACCESS  read-create
   STATUS      current
   DESCRIPTION
       "VLAN Mode Enable, Enable:1, Disable:0."
   ::= {sispm1040582lrtVLANModeEntry 4 }

sispm1040582lrtVLANModeRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {     sispm1040582lrtVLANModeEntry 5 }



-- sispm1040582lrtDHCPServerBindingType OBJECT-TYPE
--   SYNTAX      Integer32 (0|1|2|3)
--   MAX-ACCESS  read-only
--   STATUS      current
--   DESCRIPTION
--       "default: None,
--        Global Mode :
--        0: None,
--        1: Automatic,
--        2: Manual,
--        3: Expired.
--       "
--   ::= { sispm1040582lrtDHCPServerConf 2 }

-- sispm1040582lrtDHCPServerBindingState OBJECT-TYPE
--   SYNTAX      Integer32 (0|1|2|3)
--   MAX-ACCESS  read-only
--   STATUS      current
--   DESCRIPTION
--       "default: None,
--        Global Mode :
--        0: None,
--        1: Allocated,
--        2: Committed,
--        3: Expired.
--       "
--   ::= { sispm1040582lrtDHCPServerConf 3 }

-- sispm1040582lrtDHCPServerBindingIP OBJECT-TYPE
--   SYNTAX      DisplayString
--   MAX-ACCESS  read-only
--   STATUS      current
--   DESCRIPTION
--       "The DHCP Server Binding IP"
--   ::= { sispm1040582lrtDHCPServerConf 4 }


sispm1040582lrtDHCPServerExcludedIP                                 OBJECT IDENTIFIER ::= { sispm1040582lrtDHCPServer 2 }

sispm1040582lrtExcludedIPTable OBJECT-TYPE
   SYNTAX      SEQUENCE OF SISPM1040582LRTExcludedIPEntry
   MAX-ACCESS  not-accessible
   STATUS      current
   DESCRIPTION
       "A table of Excluded IP for DHCP Server."
    ::= { sispm1040582lrtDHCPServerExcludedIP 1 }

sispm1040582lrtExcludedIPEntry OBJECT-TYPE
    SYNTAX        SISPM1040582LRTExcludedIPEntry
    MAX-ACCESS    not-accessible
    STATUS        current
    DESCRIPTION
        "An entry in the sispm1040582lrtExcludedIPTable."
    INDEX        { sispm1040582lrtExcludedIPIndex }
    ::= { sispm1040582lrtExcludedIPTable 1 }

SISPM1040582LRTExcludedIPEntry ::=
    SEQUENCE {
        sispm1040582lrtExcludedIPIndex                            Integer32,
        sispm1040582lrtExcludedIPRangeLow                         IpAddress,
        sispm1040582lrtExcludedIPRangeHigh                        IpAddress,
		sispm1040582lrtExcludedIPRowStatus                        RowStatus
    }

sispm1040582lrtExcludedIPIndex OBJECT-TYPE
   SYNTAX      Integer32 (1..16)
   MAX-ACCESS  not-accessible
   STATUS      current
   DESCRIPTION
       "Excluded IP table index, range: 1-16."
   ::= {sispm1040582lrtExcludedIPEntry 1 }

sispm1040582lrtExcludedIPRangeLow OBJECT-TYPE
   SYNTAX      IpAddress
   MAX-ACCESS  read-create
   STATUS      current
   DESCRIPTION
       "ExcludedIP low range: 1-4095."
   ::= {sispm1040582lrtExcludedIPEntry 2 }

sispm1040582lrtExcludedIPRangeHigh OBJECT-TYPE
   SYNTAX      IpAddress
   MAX-ACCESS  read-create
   STATUS      current
   DESCRIPTION
       "ExcludedIP high range: 1-4095."
   ::= {sispm1040582lrtExcludedIPEntry 3 }

sispm1040582lrtExcludedIPRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {sispm1040582lrtExcludedIPEntry 4 }



sispm1040582lrtDHCPServerPoolConf                                 OBJECT IDENTIFIER ::= { sispm1040582lrtDHCPServer 3 }

sispm1040582lrtDHCPServerPoolTable OBJECT-TYPE
   SYNTAX      SEQUENCE OF SISPM1040582LRTDHCPServerPoolEntry
   MAX-ACCESS  not-accessible
   STATUS      current
   DESCRIPTION
       "This is the entry information for DHCP Pool."
   ::= { sispm1040582lrtDHCPServerPoolConf 1 }

sispm1040582lrtDHCPServerPoolEntry OBJECT-TYPE
   SYNTAX      SISPM1040582LRTDHCPServerPoolEntry
   MAX-ACCESS  not-accessible
   STATUS      current
   DESCRIPTION
       " "
   INDEX    { sispm1040582lrtDHCPServerConfIndex  }
   ::= { sispm1040582lrtDHCPServerPoolTable 1 }

SISPM1040582LRTDHCPServerPoolEntry ::= SEQUENCE {
    sispm1040582lrtDHCPServerConfIndex               Integer32,
    sispm1040582lrtDHCPServerPoolName                DisplayString,
    sispm1040582lrtDHCPServerPoolType                Integer32,
    sispm1040582lrtDHCPServerIP                      IpAddress,
    sispm1040582lrtDHCPServerSubnetMask              IpAddress,
    sispm1040582lrtDHCPServerLeaseTimeDays           Integer32,
    sispm1040582lrtDHCPServerLeaseTimeHours          Integer32,
    sispm1040582lrtDHCPServerLeaseTimeMinutes        Integer32,
    sispm1040582lrtDHCPServerDomainName              DisplayString,
    sispm1040582lrtDHCPServerBroadcastAddress        IpAddress,
    sispm1040582lrtDHCPServerDefRouter1              IpAddress,
    sispm1040582lrtDHCPServerDefRouter2              IpAddress,
    sispm1040582lrtDHCPServerDefRouter3              IpAddress,
    sispm1040582lrtDHCPServerDefRouter4              IpAddress,
    sispm1040582lrtDHCPServerDNSServer1              IpAddress,
    sispm1040582lrtDHCPServerDNSServer2              IpAddress,
    sispm1040582lrtDHCPServerDNSServer3              IpAddress,
    sispm1040582lrtDHCPServerDNSServer4              IpAddress,
    sispm1040582lrtDHCPServerNTPServer1              IpAddress,
    sispm1040582lrtDHCPServerNTPServer2              IpAddress,
    sispm1040582lrtDHCPServerNTPServer3              IpAddress,
    sispm1040582lrtDHCPServerNTPServer4              IpAddress,
    sispm1040582lrtDHCPServerNetbiosType             Integer32,
    sispm1040582lrtDHCPServerNetbiosScope            DisplayString,
    sispm1040582lrtDHCPServerNetbiosNameServer1      IpAddress,
    sispm1040582lrtDHCPServerNetbiosNameServer2      IpAddress,
    sispm1040582lrtDHCPServerNetbiosNameServer3      IpAddress,
    sispm1040582lrtDHCPServerNetbiosNameServer4      IpAddress,
    sispm1040582lrtDHCPServerNisDomainName           DisplayString,
    sispm1040582lrtDHCPServerNisServer1              IpAddress,
    sispm1040582lrtDHCPServerNisServer2              IpAddress,
    sispm1040582lrtDHCPServerNisServer3              IpAddress,
    sispm1040582lrtDHCPServerNisServer4              IpAddress,
    sispm1040582lrtDHCPServerClientIDType            Integer32,
    sispm1040582lrtDHCPServerClientID                DisplayString,
    sispm1040582lrtDHCPServerHWAddr                  DisplayString,
    sispm1040582lrtDHCPServerClientName              DisplayString,
    sispm1040582lrtDHCPServerVendorClassID1          DisplayString,
    sispm1040582lrtDHCPServerVendorSpecificInfo1     DisplayString,
    sispm1040582lrtDHCPServerVendorClassID2          DisplayString,
    sispm1040582lrtDHCPServerVendorSpecificInfo2     DisplayString,
    sispm1040582lrtDHCPServerVendorClassID3          DisplayString,
    sispm1040582lrtDHCPServerVendorSpecificInfo3     DisplayString,
    sispm1040582lrtDHCPServerVendorClassID4          DisplayString,
    sispm1040582lrtDHCPServerVendorSpecificInfo4     DisplayString,
--    sispm1040582lrtDHCPServerVendorClassID5          DisplayString,
--    sispm1040582lrtDHCPServerVendorSpecificInfo5     DisplayString,
--    sispm1040582lrtDHCPServerVendorClassID6          DisplayString,
--    sispm1040582lrtDHCPServerVendorSpecificInfo6     DisplayString,
--    sispm1040582lrtDHCPServerVendorClassID7          DisplayString,
--    sispm1040582lrtDHCPServerVendorSpecificInfo7     DisplayString,
--    sispm1040582lrtDHCPServerVendorClassID8          DisplayString,
--    sispm1040582lrtDHCPServerVendorSpecificInfo8     DisplayString,
    sispm1040582lrtDHCPServerLightingServer          DisplayString,
    sispm1040582lrtDHCPServerRowStatus               RowStatus
}

sispm1040582lrtDHCPServerConfIndex OBJECT-TYPE
   SYNTAX      Integer32 (1..64)
   MAX-ACCESS  not-accessible
   STATUS      current
   DESCRIPTION
       " pool, range : 1 - 64. "
   ::= { sispm1040582lrtDHCPServerPoolEntry 1 }

sispm1040582lrtDHCPServerPoolName OBJECT-TYPE
   SYNTAX      DisplayString(SIZE (1..32))
   MAX-ACCESS  read-create
   STATUS      current
   DESCRIPTION
       " DHCP pool name. "
   ::= { sispm1040582lrtDHCPServerPoolEntry 2 }

sispm1040582lrtDHCPServerPoolType OBJECT-TYPE
   SYNTAX      Integer32(0|1|2)
   MAX-ACCESS  read-create
   STATUS      current
   DESCRIPTION
       " DHCP Server Pool Type.
	   0:None
	   1:Network
	   2:Host, please set DHCP Server IP first."
   ::= { sispm1040582lrtDHCPServerPoolEntry 3 }

sispm1040582lrtDHCPServerIP OBJECT-TYPE
   SYNTAX      IpAddress
   MAX-ACCESS  read-create
   STATUS      current
   DESCRIPTION
       " DHCP Server IP. "
   ::= { sispm1040582lrtDHCPServerPoolEntry 4 }

sispm1040582lrtDHCPServerSubnetMask OBJECT-TYPE
   SYNTAX      IpAddress
   MAX-ACCESS  read-create
   STATUS      current
   DESCRIPTION
       " DHCP Server IPv4 Subnet Mask. "
   ::= { sispm1040582lrtDHCPServerPoolEntry 5}

sispm1040582lrtDHCPServerLeaseTimeDays OBJECT-TYPE
   SYNTAX      Integer32(0..365)
   MAX-ACCESS  read-create
   STATUS      current
   DESCRIPTION
       " DHCP Server IPv4 Lease Time:Days. "
   ::= { sispm1040582lrtDHCPServerPoolEntry 6 }

sispm1040582lrtDHCPServerLeaseTimeHours OBJECT-TYPE
   SYNTAX      Integer32(0..23)
   MAX-ACCESS  read-create
   STATUS      current
   DESCRIPTION
       " DHCP Server IPv4 Lease Time:Hours. "
   ::= { sispm1040582lrtDHCPServerPoolEntry 7 }

sispm1040582lrtDHCPServerLeaseTimeMinutes OBJECT-TYPE
   SYNTAX      Integer32(0..59)
   MAX-ACCESS  read-create
   STATUS      current
   DESCRIPTION
       " DHCP Server IPv4 Lease Time:Minutes. "
   ::= { sispm1040582lrtDHCPServerPoolEntry 8 }

sispm1040582lrtDHCPServerDomainName OBJECT-TYPE
   SYNTAX      DisplayString(SIZE (0..128))
   MAX-ACCESS  read-create
   STATUS      current
   DESCRIPTION
       " DHCP Server Domain Name. "
   ::= { sispm1040582lrtDHCPServerPoolEntry 9 }

sispm1040582lrtDHCPServerBroadcastAddress OBJECT-TYPE
   SYNTAX      IpAddress
   MAX-ACCESS  read-create
   STATUS      current
   DESCRIPTION
       " DHCP Server IPv4 Broadcast Address. "
   ::= { sispm1040582lrtDHCPServerPoolEntry 10 }

sispm1040582lrtDHCPServerDefRouter1 OBJECT-TYPE
   SYNTAX      IpAddress
   MAX-ACCESS  read-create
   STATUS      current
   DESCRIPTION
       " DHCP Server IPv4 Default Router 1. "
   ::= { sispm1040582lrtDHCPServerPoolEntry 11 }

sispm1040582lrtDHCPServerDefRouter2 OBJECT-TYPE
   SYNTAX      IpAddress
   MAX-ACCESS  read-create
   STATUS      current
   DESCRIPTION
       " DHCP Server IPv4 Default Router 2. "
   ::= { sispm1040582lrtDHCPServerPoolEntry 12 }

sispm1040582lrtDHCPServerDefRouter3 OBJECT-TYPE
   SYNTAX      IpAddress
   MAX-ACCESS  read-create
   STATUS      current
   DESCRIPTION
       " DHCP Server IPv4 Default Router 3. "
   ::= { sispm1040582lrtDHCPServerPoolEntry 13 }

sispm1040582lrtDHCPServerDefRouter4 OBJECT-TYPE
   SYNTAX      IpAddress
   MAX-ACCESS  read-create
   STATUS      current
   DESCRIPTION
       " DHCP Server IPv4 Default Router 4. "
   ::= { sispm1040582lrtDHCPServerPoolEntry 14 }

sispm1040582lrtDHCPServerDNSServer1 OBJECT-TYPE
   SYNTAX      IpAddress
   MAX-ACCESS  read-create
   STATUS      current
   DESCRIPTION
       " DHCP Server DNS Server 1. "
   ::= { sispm1040582lrtDHCPServerPoolEntry 15 }

sispm1040582lrtDHCPServerDNSServer2 OBJECT-TYPE
   SYNTAX      IpAddress
   MAX-ACCESS  read-create
   STATUS      current
   DESCRIPTION
       " DHCP Server DNS Server 2. "
   ::= { sispm1040582lrtDHCPServerPoolEntry 16 }

sispm1040582lrtDHCPServerDNSServer3 OBJECT-TYPE
   SYNTAX      IpAddress
   MAX-ACCESS  read-create
   STATUS      current
   DESCRIPTION
       " DHCP Server DNS Server 3. "
   ::= { sispm1040582lrtDHCPServerPoolEntry 17 }

sispm1040582lrtDHCPServerDNSServer4 OBJECT-TYPE
   SYNTAX      IpAddress
   MAX-ACCESS  read-create
   STATUS      current
   DESCRIPTION
       " DHCP Server DNS Server 4. "
   ::= { sispm1040582lrtDHCPServerPoolEntry 18 }

sispm1040582lrtDHCPServerNTPServer1 OBJECT-TYPE
   SYNTAX      IpAddress
   MAX-ACCESS  read-create
   STATUS      current
   DESCRIPTION
       " DHCP Server NTP Server 1. "
   ::= { sispm1040582lrtDHCPServerPoolEntry 19 }

sispm1040582lrtDHCPServerNTPServer2 OBJECT-TYPE
   SYNTAX      IpAddress
   MAX-ACCESS  read-create
   STATUS      current
   DESCRIPTION
       " DHCP Server NTP Server 2. "
   ::= { sispm1040582lrtDHCPServerPoolEntry 20 }

sispm1040582lrtDHCPServerNTPServer3 OBJECT-TYPE
   SYNTAX      IpAddress
   MAX-ACCESS  read-create
   STATUS      current
   DESCRIPTION
       " DHCP Server NTP Server 3. "
   ::= { sispm1040582lrtDHCPServerPoolEntry 21 }

sispm1040582lrtDHCPServerNTPServer4 OBJECT-TYPE
   SYNTAX      IpAddress
   MAX-ACCESS  read-create
   STATUS      current
   DESCRIPTION
       " DHCP Server NTP Server 4. "
   ::= { sispm1040582lrtDHCPServerPoolEntry 22 }

sispm1040582lrtDHCPServerNetbiosType OBJECT-TYPE
   SYNTAX      Integer32(1..4)
   MAX-ACCESS  read-create
   STATUS      current
   DESCRIPTION
       " DHCP Server Netbios Node Type.
	   0:None
	   1:B-node
	   2:P-node
	   3:M-node
	   4:H-node"
   ::= { sispm1040582lrtDHCPServerPoolEntry 23 }

sispm1040582lrtDHCPServerNetbiosScope OBJECT-TYPE
   SYNTAX      DisplayString(SIZE (0..128))
   MAX-ACCESS  read-create
   STATUS      current
   DESCRIPTION
       " DHCP Server Netbios Scope. "
   ::= { sispm1040582lrtDHCPServerPoolEntry 24 }

sispm1040582lrtDHCPServerNetbiosNameServer1 OBJECT-TYPE
   SYNTAX      IpAddress
   MAX-ACCESS  read-create
   STATUS      current
   DESCRIPTION
       " DHCP Server Netbios Name Server 1. "
   ::= { sispm1040582lrtDHCPServerPoolEntry 25 }

sispm1040582lrtDHCPServerNetbiosNameServer2 OBJECT-TYPE
   SYNTAX      IpAddress
   MAX-ACCESS  read-create
   STATUS      current
   DESCRIPTION
       " DHCP Server Netbios Name Server 2. "
   ::= { sispm1040582lrtDHCPServerPoolEntry 26 }

sispm1040582lrtDHCPServerNetbiosNameServer3 OBJECT-TYPE
   SYNTAX      IpAddress
   MAX-ACCESS  read-create
   STATUS      current
   DESCRIPTION
       " DHCP Server Netbios Name Server 3. "
   ::= { sispm1040582lrtDHCPServerPoolEntry 27 }

sispm1040582lrtDHCPServerNetbiosNameServer4 OBJECT-TYPE
   SYNTAX      IpAddress
   MAX-ACCESS  read-create
   STATUS      current
   DESCRIPTION
       " DHCP Server Netbios Name Server 4. "
   ::= { sispm1040582lrtDHCPServerPoolEntry 28 }

sispm1040582lrtDHCPServerNisDomainName OBJECT-TYPE
   SYNTAX      DisplayString(SIZE (0..128))
   MAX-ACCESS  read-create
   STATUS      current
   DESCRIPTION
       " DHCP Server Nis Domain Name. "
   ::= { sispm1040582lrtDHCPServerPoolEntry 29 }

sispm1040582lrtDHCPServerNisServer1 OBJECT-TYPE
   SYNTAX      IpAddress
   MAX-ACCESS  read-create
   STATUS      current
   DESCRIPTION
       " DHCP Server Nis Server 1. "
   ::= { sispm1040582lrtDHCPServerPoolEntry 30 }

sispm1040582lrtDHCPServerNisServer2 OBJECT-TYPE
   SYNTAX      IpAddress
   MAX-ACCESS  read-create
   STATUS      current
   DESCRIPTION
       " DHCP Server Nis Server 2. "
   ::= { sispm1040582lrtDHCPServerPoolEntry 31 }

sispm1040582lrtDHCPServerNisServer3 OBJECT-TYPE
   SYNTAX      IpAddress
   MAX-ACCESS  read-create
   STATUS      current
   DESCRIPTION
       " DHCP Server Nis Server 3. "
   ::= { sispm1040582lrtDHCPServerPoolEntry 32 }

sispm1040582lrtDHCPServerNisServer4 OBJECT-TYPE
   SYNTAX      IpAddress
   MAX-ACCESS  read-create
   STATUS      current
   DESCRIPTION
       " DHCP Server Nis Server 4. "
   ::= { sispm1040582lrtDHCPServerPoolEntry 33 }

sispm1040582lrtDHCPServerClientIDType OBJECT-TYPE
   SYNTAX      Integer32(0..2)
   MAX-ACCESS  read-create
   STATUS      current
   DESCRIPTION
       " DHCP Server Client ID Type.
	   0:None
	   1:FQDN
	   2:MAC"
   ::= { sispm1040582lrtDHCPServerPoolEntry 34 }

sispm1040582lrtDHCPServerClientID OBJECT-TYPE
   SYNTAX      DisplayString(SIZE (0..128))
   MAX-ACCESS  read-create
   STATUS      current
   DESCRIPTION
       " DHCP Server Pool Client ID. "
   ::= { sispm1040582lrtDHCPServerPoolEntry 35 }

sispm1040582lrtDHCPServerHWAddr OBJECT-TYPE
   SYNTAX      DisplayString(SIZE (0..17))
   MAX-ACCESS  read-create
   STATUS      current
   DESCRIPTION
       " DHCP Server Pool Hardware Address. "
   ::= { sispm1040582lrtDHCPServerPoolEntry 36 }

sispm1040582lrtDHCPServerClientName OBJECT-TYPE
   SYNTAX      DisplayString(SIZE (0..32))
   MAX-ACCESS  read-create
   STATUS      current
   DESCRIPTION
       " DHCP Server Pool Client Name. "
   ::= { sispm1040582lrtDHCPServerPoolEntry 37 }

sispm1040582lrtDHCPServerVendorClassID1 OBJECT-TYPE
   SYNTAX      DisplayString(SIZE (0..64))
   MAX-ACCESS  read-create
   STATUS      current
   DESCRIPTION
       " DHCP Server Vendor Class ID 1. Please also set VendorSpecificInfo1."
   ::= { sispm1040582lrtDHCPServerPoolEntry 38 }

sispm1040582lrtDHCPServerVendorSpecificInfo1 OBJECT-TYPE
   SYNTAX      DisplayString(SIZE (0..32))
   MAX-ACCESS  read-create
   STATUS      current
   DESCRIPTION
       " DHCP Server Vendor Specific Info 1. Please also set VendorClassID1."
   ::= { sispm1040582lrtDHCPServerPoolEntry 39 }

sispm1040582lrtDHCPServerVendorClassID2 OBJECT-TYPE
   SYNTAX      DisplayString(SIZE (0..64))
   MAX-ACCESS  read-create
   STATUS      current
   DESCRIPTION
       " DHCP Server Vendor Class ID 2. Please also set VendorSpecificInfo2."
   ::= { sispm1040582lrtDHCPServerPoolEntry 40 }

sispm1040582lrtDHCPServerVendorSpecificInfo2 OBJECT-TYPE
   SYNTAX      DisplayString(SIZE (0..32))
   MAX-ACCESS  read-create
   STATUS      current
   DESCRIPTION
       " DHCP Server Vendor Specific Info 2. Please also set VendorClassID2."
   ::= { sispm1040582lrtDHCPServerPoolEntry 41 }

sispm1040582lrtDHCPServerVendorClassID3 OBJECT-TYPE
   SYNTAX      DisplayString(SIZE (0..64))
   MAX-ACCESS  read-create
   STATUS      current
   DESCRIPTION
       " DHCP Server Vendor Class ID 3. Please also set VendorSpecificInfo3."
   ::= { sispm1040582lrtDHCPServerPoolEntry 42 }

sispm1040582lrtDHCPServerVendorSpecificInfo3 OBJECT-TYPE
   SYNTAX      DisplayString(SIZE (0..32))
   MAX-ACCESS  read-create
   STATUS      current
   DESCRIPTION
       " DHCP Server Vendor Specific Info 3. Please also set VendorClassID3."
   ::= { sispm1040582lrtDHCPServerPoolEntry 43 }

sispm1040582lrtDHCPServerVendorClassID4 OBJECT-TYPE
   SYNTAX      DisplayString(SIZE (0..64))
   MAX-ACCESS  read-create
   STATUS      current
   DESCRIPTION
       " DHCP Server Vendor Class ID 4. Please also set VendorSpecificInfo4."
   ::= { sispm1040582lrtDHCPServerPoolEntry 44 }

sispm1040582lrtDHCPServerVendorSpecificInfo4 OBJECT-TYPE
   SYNTAX      DisplayString(SIZE (0..32))
   MAX-ACCESS  read-create
   STATUS      current
   DESCRIPTION
       " DHCP Server Vendor Specific Info 4. Please also set VendorClassID4."
   ::= { sispm1040582lrtDHCPServerPoolEntry 45 }

--sispm1040582lrtDHCPServerVendorClassID5 OBJECT-TYPE
--   SYNTAX      DisplayString(SIZE (0..64))
--   MAX-ACCESS  read-create
--   STATUS      current
--   DESCRIPTION
--       " DHCP Server Vendor Class ID 5. Please also set VendorSpecificInfo5."
--   ::= { sispm1040582lrtDHCPServerPoolEntry 46 }
--
--sispm1040582lrtDHCPServerVendorSpecificInfo5 OBJECT-TYPE
--   SYNTAX      DisplayString(SIZE (0..32))
--   MAX-ACCESS  read-create
--   STATUS      current
--   DESCRIPTION
--       " DHCP Server Vendor Specific Info 5. Please also set VendorClassID5."
--   ::= { sispm1040582lrtDHCPServerPoolEntry 47 }
--
--sispm1040582lrtDHCPServerVendorClassID6 OBJECT-TYPE
--   SYNTAX      DisplayString(SIZE (0..64))
--   MAX-ACCESS  read-create
--   STATUS      current
--   DESCRIPTION
--       " DHCP Server Vendor Class ID 6. Please also set VendorSpecificInfo6."
--   ::= { sispm1040582lrtDHCPServerPoolEntry 48 }
--
--sispm1040582lrtDHCPServerVendorSpecificInfo6 OBJECT-TYPE
--   SYNTAX      DisplayString(SIZE (0..32))
--   MAX-ACCESS  read-create
--   STATUS      current
--   DESCRIPTION
--       " DHCP Server Vendor Specific Info 6. Please also set VendorClassID6."
--   ::= { sispm1040582lrtDHCPServerPoolEntry 49 }
--
--sispm1040582lrtDHCPServerVendorClassID7 OBJECT-TYPE
--   SYNTAX      DisplayString(SIZE (0..64))
--   MAX-ACCESS  read-create
--   STATUS      current
--   DESCRIPTION
--       " DHCP Server Vendor Class ID 7. Please also set VendorSpecificInfo7."
--   ::= { sispm1040582lrtDHCPServerPoolEntry 50 }
--
--sispm1040582lrtDHCPServerVendorSpecificInfo7 OBJECT-TYPE
--   SYNTAX      DisplayString(SIZE (0..32))
--   MAX-ACCESS  read-create
--   STATUS      current
--   DESCRIPTION
--       " DHCP Server Vendor Specific Info 7. Please also set VendorClassID7."
--   ::= { sispm1040582lrtDHCPServerPoolEntry 51 }
--
--sispm1040582lrtDHCPServerVendorClassID8 OBJECT-TYPE
--   SYNTAX      DisplayString(SIZE (0..64))
--   MAX-ACCESS  read-create
--   STATUS      current
--   DESCRIPTION
--       " DHCP Server Vendor Class ID 8. Please also set VendorSpecificInfo8."
--   ::= { sispm1040582lrtDHCPServerPoolEntry 52 }
--
--sispm1040582lrtDHCPServerVendorSpecificInfo8 OBJECT-TYPE
--   SYNTAX      DisplayString(SIZE (0..32))
--   MAX-ACCESS  read-create
--   STATUS      current
--   DESCRIPTION
--       " DHCP Server Vendor Specific Info 8. Please also set VendorClassID8."
--   ::= { sispm1040582lrtDHCPServerPoolEntry 53 }

sispm1040582lrtDHCPServerLightingServer OBJECT-TYPE
   SYNTAX      DisplayString(SIZE (7..15))
   MAX-ACCESS  read-create
   STATUS      current
   DESCRIPTION
       "DHCP option 229.
        Specify a lighting server available to the client."
   ::= { sispm1040582lrtDHCPServerPoolEntry 54 }

sispm1040582lrtDHCPServerRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {sispm1040582lrtDHCPServerPoolEntry 55 }

-- =======================================================================================================================
sispm1040582lrtVLANConf                                     OBJECT IDENTIFIER ::= { sispm1040582lrtSystem 10 }

sispm1040582lrtVLAN                                     OBJECT IDENTIFIER ::= { sispm1040582lrtVLANConf 2}

sispm1040582lrtVlanStatus              OBJECT IDENTIFIER   ::= { sispm1040582lrtVLAN 6 }

--
-- =======================================================================================================================
-- Start sispm1040582lrtVlan group
-- =======================================================================================================================
    sispm1040582lrtVlanExistingVLANs  OBJECT-TYPE
               SYNTAX      DisplayString
               MAX-ACCESS  read-write
               STATUS      current
               DESCRIPTION
                   "This field shows the VLANs that are created on the switch.
                    More VLANs may be created by using a
                    list syntax where the individual elements are separated by commas.
                    Ranges are specified with a
                    dash separating the lower and upper bound.
                    The following example will create VLANs 1, 10, 11, 12
                    , 13, 200, and 300: 1,10-13,200,300.
                    default: 1."
               ::= {     sispm1040582lrtVLAN 1 }

    sispm1040582lrtVlanEthertypeforCustomSPorts  OBJECT-TYPE
               SYNTAX      DisplayString
               MAX-ACCESS  read-write
               STATUS      current
               DESCRIPTION
                   "This field specifies the ethertype/TPID (specified in hexadecimal)
                    used for Custom S-ports. The
                    setting is in force for all ports whose Port Type
                    is set to S-Custom-Port.
                    range: 0600-ffff,
                    default: 88a8."
               ::= {     sispm1040582lrtVLAN 2 }

    sispm1040582lrtVlanTable OBJECT-TYPE
               SYNTAX      SEQUENCE OF     SISPM1040582LRTVlanEntry
               MAX-ACCESS  not-accessible
               STATUS      current
               DESCRIPTION
                   "Configure Vlan ports Configuration mode.
                    INDEX for this table is ifIndex which is
                    equivalent to the panel port number."
               ::= {     sispm1040582lrtVLAN 3 }

    sispm1040582lrtVlanEntry OBJECT-TYPE
               SYNTAX          SISPM1040582LRTVlanEntry
               MAX-ACCESS  not-accessible
               STATUS      current
               DESCRIPTION
                   "The Vlan entry."
               INDEX    {     ifIndex  }
               ::= {     sispm1040582lrtVlanTable 1 }

    SISPM1040582LRTVlanEntry             ::= SEQUENCE {
                sispm1040582lrtVlanMode              INTEGER,
                sispm1040582lrtVlanPortVLAN          Integer32,
                sispm1040582lrtVlanPortType          INTEGER,
                sispm1040582lrtVlanIngressFiltering  AdminMode,
                sispm1040582lrtVlanVLANTrunking      AdminMode,
                sispm1040582lrtVlanIngressAcceptance INTEGER,
                sispm1040582lrtVlanEgressTagging     INTEGER,
                sispm1040582lrtVlanAllowedVLANs      DisplayString,
                sispm1040582lrtVlanForbiddenVLANs    DisplayString
                }

    sispm1040582lrtVlanMode OBJECT-TYPE
               SYNTAX      INTEGER{access(0), trunk(1), hybrid(2)}
               MAX-ACCESS  read-write
               STATUS      current
               DESCRIPTION
                   "The port mode determines the fundamental
                    behavior of the port in question.
                    A port can be in one of three modes as described below.
                    0: access,
                    1: trunk,
                    2: hybrid."
               DEFVAL  { access }
               ::= {     sispm1040582lrtVlanEntry 2 }

    sispm1040582lrtVlanPortVLAN OBJECT-TYPE
               SYNTAX      Integer32(1..4094)
               MAX-ACCESS  read-write
               STATUS      current
               DESCRIPTION
                   "Determines the port's VLAN ID (a.k.a. PVID).
                    range: 1-4095,
                    default: 1."
               ::= {     sispm1040582lrtVlanEntry 3 }

    sispm1040582lrtVlanPortType OBJECT-TYPE
               SYNTAX      INTEGER { unaware(0), cPort(1), sPort(2), sCustomPort(3) }
               MAX-ACCESS  read-write
               STATUS      current
               DESCRIPTION
                   "Ports in hybrid mode allow for changing the port type,
                    that is, whether a frame's VLAN tag is
                    used to classify the frame on ingress to a particular VLAN,
                    and if so, which TPID it reacts on.
                    Likewise, on egress, the Port Type determines the
                    TPID of the tag, if a tag is required.
                    0: unaware,
                    1: c-Port,
                    2: s-Port,
                    3: s-Custom-Port."
                DEFVAL  { cPort }
               ::= {     sispm1040582lrtVlanEntry 4 }

    sispm1040582lrtVlanIngressFiltering OBJECT-TYPE
               SYNTAX      AdminMode
               MAX-ACCESS  read-write
               STATUS      current
               DESCRIPTION
                   "Hybrid ports allow for changing ingress filtering.
                    Access and Trunk ports always have ingress
                    filtering enabled.If ingress filtering is enabled,
                    frames classified to
                    a VLAN that the port is not a member of get discarded."
               ::= {     sispm1040582lrtVlanEntry 5 }

    sispm1040582lrtVlanVLANTrunking OBJECT-TYPE
               SYNTAX      AdminMode
               MAX-ACCESS  read-write
               STATUS      current
               DESCRIPTION
                   "Trunk and Hybrid ports allow for enabling VLAN trunking.
                    When VLAN trunking is enabled, frames
                    classified to unknown VLANs are accepted on the port
                    whether ingress filtering is enabled or not."
               DEFVAL  { disable }
               ::= {     sispm1040582lrtVlanEntry 6 }

    sispm1040582lrtVlanIngressAcceptance OBJECT-TYPE
               SYNTAX      INTEGER  { taggedAndUntagged  ( 0 ),
                                      taggedOnly ( 1 ),
                                      untaggedOnly ( 2 )
                                    }
               MAX-ACCESS  read-write
               STATUS      current
               DESCRIPTION
                   "Hybrid ports allow for changing the type of frames that are
                    accepted on ingress.
                    0: Tagged and Untagged,
                    1: Tagged Only,
                    2: Untagged Only."
               ::= {     sispm1040582lrtVlanEntry 7 }

    sispm1040582lrtVlanEgressTagging OBJECT-TYPE
               SYNTAX      INTEGER  { untagPortVlan  ( 0 ),
                                      tagAll ( 1 ),
                                      untagAll ( 2 )
                                    }
               MAX-ACCESS  read-write
               STATUS      current
               DESCRIPTION
                   "Ports in Trunk and Hybrid mode may control the
                    tagging of frames on egress.
                    0: Untag Port VLAN,
                    1: Tag All,
                    2: Untag All."
               ::= {     sispm1040582lrtVlanEntry 8 }

    sispm1040582lrtVlanAllowedVLANs OBJECT-TYPE
               SYNTAX      DisplayString
               MAX-ACCESS  read-write
               STATUS      current
               DESCRIPTION
                   "Ports in Trunk and Hybrid mode may control which
                    VLANs they are allowed to become members of.
                    Access ports can only be member of one VLAN, the Access VLAN.
                    range: 1~4095.
                    '-': Allowed VLANs is empty."
               ::= {     sispm1040582lrtVlanEntry 9 }

    sispm1040582lrtVlanForbiddenVLANs OBJECT-TYPE
               SYNTAX      DisplayString
               MAX-ACCESS  read-write
               STATUS      current
               DESCRIPTION
                   "A port may be configured to never be member of one or
                    more VLANs. This is particularly useful
                    when dynamic VLAN protocols like MVRP and GVRP
                    must be prevented from dynamically adding ports
                    to VLANs.
                    range: 1~4095.
                    '-': Forbidden VLANs is empty."
               ::= {     sispm1040582lrtVlanEntry 10 }

--sispm1040582lrtVLANMembershipStatusTable

    sispm1040582lrtVLANMembershipStatusTable OBJECT-TYPE
               SYNTAX      SEQUENCE OF     SISPM1040582LRTVLANMembershipStatusEntry
               MAX-ACCESS  not-accessible
               STATUS      current
               DESCRIPTION
                   "Vlan membership Status table.
                    INDEX for this table is ifIndex which is
                    equivalent to the panel port number."
               ::= {     sispm1040582lrtVlanStatus 1 }

    sispm1040582lrtVLANMembershipStatusEntry OBJECT-TYPE
               SYNTAX          SISPM1040582LRTVLANMembershipStatusEntry
               MAX-ACCESS  not-accessible
               STATUS      current
               DESCRIPTION
                   "Vlan membership Status entry."
               INDEX    {     ifIndex, sispm1040582lrtVLANMembershipVlanID    }
               ::= {     sispm1040582lrtVLANMembershipStatusTable 1 }

    SISPM1040582LRTVLANMembershipStatusEntry             ::= SEQUENCE {
                sispm1040582lrtVLANMembershipVlanID      Integer32,
                sispm1040582lrtVLANMembershipStatus      INTEGER
                }

    sispm1040582lrtVLANMembershipVlanID OBJECT-TYPE
               SYNTAX      Integer32(1..4095)
               MAX-ACCESS  not-accessible
               STATUS      current
               DESCRIPTION
                   "VLAN ID for which the Port members are displayed."
               ::= {     sispm1040582lrtVLANMembershipStatusEntry 2 }

    sispm1040582lrtVLANMembershipStatus OBJECT-TYPE
               SYNTAX      INTEGER  { portIsNotInVlan  ( 0 ),
                                      portIncludedInVlan ( 1 ),
                                      portInForbiddenPortList( 2 ),
                                      portInForbiddenPortListAndVlan( 3 )
                                    }
               MAX-ACCESS  read-only
               STATUS      current
               DESCRIPTION
                   "portIsNotInVlan(0): A port is nothing in a VLAN.
                    portIncludedInVlan(1): A port is included in a VLAN.
                    portInForbiddenPortList(2): A port is in the forbidden port list.
                    portInForbiddenPortListAndVlan(3):
                     A port is in the forbidden port list and at the same
                     time attempted included in the VLAN."
               ::= {     sispm1040582lrtVLANMembershipStatusEntry 3 }

--sispm1040582lrtVLANPortStatusTable
    sispm1040582lrtVLANPortStatusTable OBJECT-TYPE
               SYNTAX      SEQUENCE OF     SISPM1040582LRTVLANPortStatusEntry
               MAX-ACCESS  not-accessible
               STATUS      current
               DESCRIPTION
                   "The vlan port status table.
                    INDEX for this table is ifIndex which is
                    equivalent to the panel port number."
               ::= {     sispm1040582lrtVlanStatus 2 }

    sispm1040582lrtVLANPortStatusEntry OBJECT-TYPE
               SYNTAX          SISPM1040582LRTVLANPortStatusEntry
               MAX-ACCESS  not-accessible
               STATUS      current
               DESCRIPTION
                   "The vlan port status entry."
               INDEX    {     ifIndex }
               ::= {     sispm1040582lrtVLANPortStatusTable 1 }

    SISPM1040582LRTVLANPortStatusEntry             ::= SEQUENCE {
                sispm1040582lrtVLANPortStatusPortType          DisplayString,
                sispm1040582lrtVLANPortStatusIngressFiltering  AdminMode,
                sispm1040582lrtVLANPortStatusFrameType         DisplayString,
                sispm1040582lrtVLANPortStatusPortVLANID        Integer32,
                sispm1040582lrtVLANPortStatusTxTag             DisplayString,
                sispm1040582lrtVLANPortStatusUntaggedVLANID    Integer32,
                sispm1040582lrtVLANPortStatusConflicts         DisplayString
                }

    sispm1040582lrtVLANPortStatusPortType OBJECT-TYPE
               SYNTAX      DisplayString
               MAX-ACCESS  read-only
               STATUS      current
               DESCRIPTION
                   "Shows the port type (Unaware, C-Port, S-Port,
                    S-Custom-Port.) that a given user wants to configure on
                    the port.The field is empty if not overridden by the selected user."
               ::= {     sispm1040582lrtVLANPortStatusEntry 2 }

    sispm1040582lrtVLANPortStatusIngressFiltering OBJECT-TYPE
               SYNTAX      AdminMode
               MAX-ACCESS  read-only
               STATUS      current
               DESCRIPTION
                   "Shows whether a given user wants ingress filtering enabled or not."
               ::= {     sispm1040582lrtVLANPortStatusEntry 3 }

    sispm1040582lrtVLANPortStatusFrameType OBJECT-TYPE
               SYNTAX      DisplayString
               MAX-ACCESS  read-only
               STATUS      current
               DESCRIPTION
                   "Shows the acceptable frame types (All, Taged,
                    Untagged) that a given user wants to configure on the port.
                    The field is empty if not overridden by the selected user."
               ::= {     sispm1040582lrtVLANPortStatusEntry 4 }

    sispm1040582lrtVLANPortStatusPortVLANID OBJECT-TYPE
               SYNTAX      Integer32 (1..4095)
               MAX-ACCESS  read-only
               STATUS      current
               DESCRIPTION
                   "Shows the Port VLAN ID (PVID) that a given user
                    wants the port to have.
                    The field is 0 if not overridden by the selected user."
               ::= {     sispm1040582lrtVLANPortStatusEntry 5 }

    sispm1040582lrtVLANPortStatusTxTag OBJECT-TYPE
               SYNTAX      DisplayString
               MAX-ACCESS  read-only
               STATUS      current
               DESCRIPTION
                   "Shows the Tx Tag requirements (Tag All, Tag PVID,
                    Tag UVID, Untag All, Untag PVID, Untag UVID)
                    that a given user has on a port.The field is empty
                    if not overridden by the selected user."
               ::= {     sispm1040582lrtVLANPortStatusEntry 6 }

    sispm1040582lrtVLANPortStatusUntaggedVLANID OBJECT-TYPE
               SYNTAX      Integer32(1..4095)
               MAX-ACCESS  read-only
               STATUS      current
               DESCRIPTION
                   "If Tx Tag is overridden by the selected user and is
                    set to Tag or Untag UVID, then this field will show
                    the VLAN ID the user wants to tag or untag on egress.
                    The field is 0 if not overridden by the selected
                    user."
               ::= {     sispm1040582lrtVLANPortStatusEntry 7 }

    sispm1040582lrtVLANPortStatusConflicts OBJECT-TYPE
               SYNTAX      DisplayString
               MAX-ACCESS  read-only
               STATUS      current
               DESCRIPTION
                   "Two users may have conflicting requirements to a port's
                    configuration. For instance, one user may require
                    all frames to be tagged on egress while another requires
                    all frames to be untagged on egress.Since both
                    users cannot win, this gives rise to a conflict,
                    which is solved in a prioritized way. The Administrator
                    has the least priority. Other software modules are
                    prioritized according to their position in the drop-down
                    list: The higher in the list, the higher priority.
                    If conflicts exist, it will be displayed as 'Yes'."
               ::= {     sispm1040582lrtVLANPortStatusEntry 8 }
               
sispm1040582lrtSystemDIDO                                     OBJECT IDENTIFIER ::= { sispm1040582lrtSystem 11 }
    sispm1040582lrtSystemDIMode OBJECT-TYPE
               SYNTAX       Integer32 (0..1)
               MAX-ACCESS   read-write
               STATUS       current
               DESCRIPTION
                   "System digital in mode.
				   0:Low
				   1:High
				   "
               ::= {     sispm1040582lrtSystemDIDO 1 }
			   
    sispm1040582lrtSystemDOMode OBJECT-TYPE
               SYNTAX       Integer32 (0..1)
               MAX-ACCESS   read-write
               STATUS       current
               DESCRIPTION
                   "System digital out mode.
				   0:Close
				   1:Open
				   "
               ::= {     sispm1040582lrtSystemDIDO 2 }			   

    sispm1040582lrtSystemDIEventDescNormal   OBJECT-TYPE
               SYNTAX      DisplayString
               MAX-ACCESS  read-write
               STATUS      current
               DESCRIPTION
                   "Customize event message. You can describe the event in detail. "
               ::= {     sispm1040582lrtSystemDIDO 3 }  
               
    sispm1040582lrtSystemDIEventDescAbnormal   OBJECT-TYPE
               SYNTAX      DisplayString
               MAX-ACCESS  read-write
               STATUS      current
               DESCRIPTION
                   "Customize event message. You can describe the event in detail. "
               ::= {     sispm1040582lrtSystemDIDO 4 }                

    sispm1040582lrtSystemDOAutoRecovery OBJECT-TYPE
               SYNTAX       Integer32 (0..1)
               MAX-ACCESS   read-write
               STATUS       current
               DESCRIPTION
                   "Enable the function of Auto Recovery.
				   0:Disable
				   1:Enable
				   "
               ::= {    sispm1040582lrtSystemDIDO 5 }
               
    sispm1040582lrtSystemDIRebootSystem OBJECT-TYPE
               SYNTAX       Integer32 (0..1)
               MAX-ACCESS   read-write
               STATUS       current
               DESCRIPTION
                   "Enable the function of DI Reboot System.
				   0:Disable
				   1:When DI was changed to abnormal.
				   "
               ::= {    sispm1040582lrtSystemDIDO 6 }
               
sispm1040582lrtNTPConf   OBJECT IDENTIFIER ::= { sispm1040582lrtSystem 12 }

sispm1040582lrtNTPConfigAutomatic   OBJECT-TYPE
               SYNTAX      Integer32 (0|1)
               MAX-ACCESS  read-write
               STATUS      current
               DESCRIPTION
                   "Indicates the Automatic mode operation. Possible modes are:
                   0:Disable, NTP servers available from the config. 
                   1:Enable, NTP servers available from the DHCP."
               ::= { sispm1040582lrtNTPConf 2 }
               
sispm1040582lrtNTPConfigTimeSyncInterval   OBJECT-TYPE
               SYNTAX      Integer32 (5|10|15|30|60|120)
               MAX-ACCESS  read-write
               STATUS      current
               DESCRIPTION
                   "Time-Sync Interval.
                   Valid values are restricted to 5,10,15,30,60,120 minutes. "
               ::= { sispm1040582lrtNTPConf 3 }   

sispm1040582lrtNTPConfigServerAddress1   OBJECT-TYPE
               SYNTAX      DisplayString
               MAX-ACCESS  read-write
               STATUS      current
               DESCRIPTION
                   "Provide the IPv4 or IPv6 address of a NTP server."
               ::= { sispm1040582lrtNTPConf 4 }   

sispm1040582lrtNTPConfigServerAddress2   OBJECT-TYPE
               SYNTAX      DisplayString
               MAX-ACCESS  read-write
               STATUS      current
               DESCRIPTION
                   "Provide the IPv4 or IPv6 address of a NTP server."
               ::= { sispm1040582lrtNTPConf 5 }                
        
sispm1040582lrtNTPConfigServerAddress3   OBJECT-TYPE
               SYNTAX      DisplayString
               MAX-ACCESS  read-write
               STATUS      current
               DESCRIPTION
                   "Provide the IPv4 or IPv6 address of a NTP server."
               ::= { sispm1040582lrtNTPConf 6 }          
               
sispm1040582lrtNTPConfigServerAddress4   OBJECT-TYPE
               SYNTAX      DisplayString
               MAX-ACCESS  read-write
               STATUS      current
               DESCRIPTION
                   "Provide the IPv4 or IPv6 address of a NTP server."
               ::= { sispm1040582lrtNTPConf 7 }                    
    
sispm1040582lrtNTPConfigServerAddress5   OBJECT-TYPE
               SYNTAX      DisplayString
               MAX-ACCESS  read-write
               STATUS      current
               DESCRIPTION
                   "Provide the IPv4 or IPv6 address of a NTP server."
               ::= { sispm1040582lrtNTPConf 8 }  


sispm1040582lrtTemperature   OBJECT IDENTIFIER ::= { sispm1040582lrtSystem 13 }

sispm1040582lrtTemperature1   OBJECT IDENTIFIER ::= { sispm1040582lrtTemperature 1 }

sispm1040582lrtTemperature1Celsius   OBJECT-TYPE
               SYNTAX      DisplayString
               MAX-ACCESS  read-only
               STATUS      current
               DESCRIPTION
                   "Value of Celsius"
               ::= { sispm1040582lrtTemperature1 1 } 

sispm1040582lrtTemperature1Fahrenheit   OBJECT-TYPE
               SYNTAX      DisplayString
               MAX-ACCESS  read-only
               STATUS      current
               DESCRIPTION
                   "Value of Fahrenheit"
               ::= { sispm1040582lrtTemperature1 2 } 
               
sispm1040582lrtTemperature2   OBJECT IDENTIFIER ::= { sispm1040582lrtTemperature 2 }

sispm1040582lrtTemperature2Celsius   OBJECT-TYPE
               SYNTAX      DisplayString
               MAX-ACCESS  read-only
               STATUS      current
               DESCRIPTION
                   "Value of Celsius"
               ::= { sispm1040582lrtTemperature2 1 } 

sispm1040582lrtTemperature2Fahrenheit   OBJECT-TYPE
               SYNTAX      DisplayString
               MAX-ACCESS  read-only
               STATUS      current
               DESCRIPTION
                   "Value of Fahrenheit"
               ::= { sispm1040582lrtTemperature2 2 }                

-- =======================================================================================================================
sispm1040582lrtConfiguration                                         OBJECT IDENTIFIER ::= { sispm1040582lrtProductId 2 }

sispm1040582lrtPort                                                  OBJECT IDENTIFIER ::= { sispm1040582lrtConfiguration 1 }

sispm1040582lrtPortConfigurationTable OBJECT-TYPE
   SYNTAX      SEQUENCE OF SISPM1040582LRTPortConfigurationEntry
   MAX-ACCESS  not-accessible
   STATUS      current
   DESCRIPTION
       " Show port configurations. "
   ::= { sispm1040582lrtPort 1 }

sispm1040582lrtPortConfigurationEntry OBJECT-TYPE
   SYNTAX      SISPM1040582LRTPortConfigurationEntry
   MAX-ACCESS  not-accessible
   STATUS      current
   DESCRIPTION
       " "
   INDEX    { sispm1040582lrtPortConfPort  }
   ::= { sispm1040582lrtPortConfigurationTable 1 }

SISPM1040582LRTPortConfigurationEntry ::= SEQUENCE {
   sispm1040582lrtPortConfPort                     Integer32,
   sispm1040582lrtPortConfPortMedia                DisplayString,
   sispm1040582lrtPortConfLink                     DisplayString,
   sispm1040582lrtPortConfCurrentSpeed             DisplayString,
   sispm1040582lrtPortConfSpeed                    Integer32,
   sispm1040582lrtPortConfCurrentFlowControlRx     Integer32,
   sispm1040582lrtPortConfCurrentFlowControlTx     Integer32,
   sispm1040582lrtPortConfFlowControl              Integer32,
   sispm1040582lrtPortConfMaxFrameSize             Integer32,
   sispm1040582lrtPortConfExcessiveCollisionMode   Integer32,
-- sispm1040582lrtPortConfPowerControl             Integer32,
   sispm1040582lrtPortConfDescription              DisplayString,
   sispm1040582lrtPortConfFrameLengthCheck         Integer32
}

sispm1040582lrtPortConfPort OBJECT-TYPE
   SYNTAX      Integer32 (1..4095)
   MAX-ACCESS  not-accessible
   STATUS      current
   DESCRIPTION
       " port, range : 1 - port number. "
   ::= { sispm1040582lrtPortConfigurationEntry 1 }

sispm1040582lrtPortConfPortMedia OBJECT-TYPE
   SYNTAX      DisplayString(SIZE (1..4))
   MAX-ACCESS  read-only
   STATUS      current
   DESCRIPTION
       " Show port media. "
   ::= { sispm1040582lrtPortConfigurationEntry 2 }

sispm1040582lrtPortConfLink OBJECT-TYPE
   SYNTAX      DisplayString(SIZE (2..4))
   MAX-ACCESS  read-only
   STATUS      current
   DESCRIPTION
       " The current link state. "
   ::= { sispm1040582lrtPortConfigurationEntry 3 }

sispm1040582lrtPortConfCurrentSpeed OBJECT-TYPE
   SYNTAX      DisplayString(SIZE (6..12))
   MAX-ACCESS  read-only
   STATUS      current
   DESCRIPTION
       " The current link speed of the port. "
   ::= { sispm1040582lrtPortConfigurationEntry 4 }

sispm1040582lrtPortConfSpeed OBJECT-TYPE
   SYNTAX      Integer32 (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X,
        12: 10G Full. "
   ::= { sispm1040582lrtPortConfigurationEntry 5 }

sispm1040582lrtPortConfCurrentFlowControlRx OBJECT-TYPE
   SYNTAX      Integer32 (0|1)
   MAX-ACCESS  read-only
   STATUS      current
   DESCRIPTION
       "0: disable
        1: enable
        2: not support.  "
   ::= { sispm1040582lrtPortConfigurationEntry 6 }

sispm1040582lrtPortConfCurrentFlowControlTx OBJECT-TYPE
   SYNTAX      Integer32 (0|1)
   MAX-ACCESS  read-only
   STATUS      current
   DESCRIPTION
       "0: disable
        1: enable
        2: not support.  "
   ::= { sispm1040582lrtPortConfigurationEntry 7 }

sispm1040582lrtPortConfFlowControl OBJECT-TYPE
   SYNTAX      Integer32 (0|1)
   MAX-ACCESS  read-write
   STATUS      current
   DESCRIPTION
       "default: 0,
        0: disable
        1: enable
        2: not support. "
   ::= { sispm1040582lrtPortConfigurationEntry 8 }

sispm1040582lrtPortConfMaxFrameSize OBJECT-TYPE
   SYNTAX      Integer32 (1518..9600)
   MAX-ACCESS  read-write
   STATUS      current
   DESCRIPTION
       "default: 9600 , range : 1518 - 9600 "
   ::= { sispm1040582lrtPortConfigurationEntry 9 }

sispm1040582lrtPortConfExcessiveCollisionMode OBJECT-TYPE
   SYNTAX      Integer32 (0|1)
   MAX-ACCESS  read-write
   STATUS      current
   DESCRIPTION
       "default: 0,
        Excessive Collision Mode :
        0: Discard,
        1: Restart,
        2: not support.
       "
   ::= { sispm1040582lrtPortConfigurationEntry 10 }

--sispm1040582lrtPortConfPowerControl OBJECT-TYPE
--   SYNTAX      Integer32 (0..3)
--   MAX-ACCESS  read-write
--   STATUS      current
--   DESCRIPTION
--       "default: 0,
--        PowerControl :
--        0: disable,
--        1: Actiphy,
--        2: Dynamic (perfectReach),
--        3: Enable,
--        4: not support.
--       "
--   ::= { sispm1040582lrtPortConfigurationEntry 11 }

sispm1040582lrtPortConfDescription OBJECT-TYPE
   SYNTAX      DisplayString
   MAX-ACCESS  read-write
   STATUS      current
   DESCRIPTION
       " Interface specific description.
         Up to 128 characters describing this interface. "
   ::= { sispm1040582lrtPortConfigurationEntry 12 }

sispm1040582lrtPortConfFrameLengthCheck OBJECT-TYPE
   SYNTAX      Integer32 (0|1)
   MAX-ACCESS  read-write
   STATUS      current
   DESCRIPTION
       "default: 0,
        0: disable
        1: enable"
   ::= { sispm1040582lrtPortConfigurationEntry 13 } 

sispm1040582lrtPortTrafficStatisticsTable OBJECT-TYPE
   SYNTAX      SEQUENCE OF SISPM1040582LRTPortTrafficStatisticsEntry
   MAX-ACCESS  not-accessible
   STATUS      current
   DESCRIPTION
       " "
   ::= { sispm1040582lrtPort 2 }

sispm1040582lrtPortTrafficStatisticsEntry OBJECT-TYPE
   SYNTAX      SISPM1040582LRTPortTrafficStatisticsEntry
   MAX-ACCESS  not-accessible
   STATUS      current
   DESCRIPTION
       " "
   INDEX    { sispm1040582lrtPortTrafficStatisticsPort  }
   ::= { sispm1040582lrtPortTrafficStatisticsTable 1 }

SISPM1040582LRTPortTrafficStatisticsEntry ::= SEQUENCE {
   sispm1040582lrtPortTrafficStatisticsPort          Integer32,
   sispm1040582lrtPortTrafficStatisticsClear         Integer32,
   sispm1040582lrtPortTrafficRxPackets               Counter64,
   sispm1040582lrtPortTrafficRxOctets                Counter64,
   sispm1040582lrtPortTrafficRxUnicast               Counter64,
   sispm1040582lrtPortTrafficRxMulticast             Counter64,
   sispm1040582lrtPortTrafficRxBroadcast             Counter64,
   sispm1040582lrtPortTrafficRxPause                 Counter64,
   sispm1040582lrtPortTrafficRx64Bytes               Counter64,
   sispm1040582lrtPortTrafficRx65to127Bytes          Counter64,
   sispm1040582lrtPortTrafficRx128to255Bytes         Counter64,
   sispm1040582lrtPortTrafficRx256to511Bytes         Counter64,
   sispm1040582lrtPortTrafficRx512to1023Bytes        Counter64,
   sispm1040582lrtPortTrafficRx1024to1526Bytes       Counter64,
   sispm1040582lrtPortTrafficRxExceecd1527Bytes      Counter64,
   sispm1040582lrtPortTrafficRxQ0                    Counter64,
   sispm1040582lrtPortTrafficRxQ1                    Counter64,
   sispm1040582lrtPortTrafficRxQ2                    Counter64,
   sispm1040582lrtPortTrafficRxQ3                    Counter64,
   sispm1040582lrtPortTrafficRxQ4                    Counter64,
   sispm1040582lrtPortTrafficRxQ5                    Counter64,
   sispm1040582lrtPortTrafficRxQ6                    Counter64,
   sispm1040582lrtPortTrafficRxQ7                    Counter64,
   sispm1040582lrtPortTrafficRxDrops                 Counter64,
   sispm1040582lrtPortTrafficRxCRCorAlignment        Counter64,
   sispm1040582lrtPortTrafficRxUndersize             Counter64,
   sispm1040582lrtPortTrafficRxOversize              Counter64,
   sispm1040582lrtPortTrafficRxFragments             Counter64,
   sispm1040582lrtPortTrafficRxJabber                Counter64,
   sispm1040582lrtPortTrafficRxFiltered              Counter64,
   sispm1040582lrtPortTrafficTxPackets               Counter64,
   sispm1040582lrtPortTrafficTxOctets                Counter64,
   sispm1040582lrtPortTrafficTxUnicast               Counter64,
   sispm1040582lrtPortTrafficTxMulticast             Counter64,
   sispm1040582lrtPortTrafficTxBroadcast             Counter64,
   sispm1040582lrtPortTrafficTxPause                 Counter64,
   sispm1040582lrtPortTrafficTx64Bytes               Counter64,
   sispm1040582lrtPortTrafficTx65to127Bytes          Counter64,
   sispm1040582lrtPortTrafficTx128to255Bytes         Counter64,
   sispm1040582lrtPortTrafficTx256to511Bytes         Counter64,
   sispm1040582lrtPortTrafficTx512to1023Bytes        Counter64,
   sispm1040582lrtPortTrafficTx1024to1526Bytes       Counter64,
   sispm1040582lrtPortTrafficTxExceecd1527Bytes      Counter64,
   sispm1040582lrtPortTrafficTxQ0                    Counter64,
   sispm1040582lrtPortTrafficTxQ1                    Counter64,
   sispm1040582lrtPortTrafficTxQ2                    Counter64,
   sispm1040582lrtPortTrafficTxQ3                    Counter64,
   sispm1040582lrtPortTrafficTxQ4                    Counter64,
   sispm1040582lrtPortTrafficTxQ5                    Counter64,
   sispm1040582lrtPortTrafficTxQ6                    Counter64,
   sispm1040582lrtPortTrafficTxQ7                    Counter64,
   sispm1040582lrtPortTrafficTxDrops                 Counter64,
   sispm1040582lrtPortTrafficTxLateOrExcColl         Counter64
}

sispm1040582lrtPortTrafficStatisticsPort OBJECT-TYPE
   SYNTAX      Integer32 (1..4095)
   MAX-ACCESS  not-accessible
   STATUS      current
   DESCRIPTION
       " "
   ::= { sispm1040582lrtPortTrafficStatisticsEntry 1 }

sispm1040582lrtPortTrafficStatisticsClear OBJECT-TYPE
   SYNTAX      Integer32(0|1)
   MAX-ACCESS  read-write
   STATUS      current
   DESCRIPTION
       " "
   ::= { sispm1040582lrtPortTrafficStatisticsEntry 2 }

sispm1040582lrtPortTrafficRxPackets OBJECT-TYPE
   SYNTAX      Counter64
   MAX-ACCESS  read-only
   STATUS      current
   DESCRIPTION
       " "
   ::= { sispm1040582lrtPortTrafficStatisticsEntry 3 }

sispm1040582lrtPortTrafficRxOctets OBJECT-TYPE
   SYNTAX      Counter64
   MAX-ACCESS  read-only
   STATUS      current
   DESCRIPTION
       " "
   ::= { sispm1040582lrtPortTrafficStatisticsEntry 4 }

sispm1040582lrtPortTrafficRxUnicast OBJECT-TYPE
   SYNTAX      Counter64
   MAX-ACCESS  read-only
   STATUS      current
   DESCRIPTION
       " "
   ::= { sispm1040582lrtPortTrafficStatisticsEntry 5 }

sispm1040582lrtPortTrafficRxMulticast OBJECT-TYPE
   SYNTAX      Counter64
   MAX-ACCESS  read-only
   STATUS      current
   DESCRIPTION
       " "
   ::= { sispm1040582lrtPortTrafficStatisticsEntry 6 }

sispm1040582lrtPortTrafficRxBroadcast OBJECT-TYPE
   SYNTAX      Counter64
   MAX-ACCESS  read-only
   STATUS      current
   DESCRIPTION
       " "
   ::= { sispm1040582lrtPortTrafficStatisticsEntry 7 }

sispm1040582lrtPortTrafficRxPause OBJECT-TYPE
   SYNTAX      Counter64
   MAX-ACCESS  read-only
   STATUS      current
   DESCRIPTION
       " "
   ::= { sispm1040582lrtPortTrafficStatisticsEntry 8 }

sispm1040582lrtPortTrafficRx64Bytes OBJECT-TYPE
   SYNTAX      Counter64
   MAX-ACCESS  read-only
   STATUS      current
   DESCRIPTION
       " "
   ::= { sispm1040582lrtPortTrafficStatisticsEntry 9 }

sispm1040582lrtPortTrafficRx65to127Bytes OBJECT-TYPE
   SYNTAX      Counter64
   MAX-ACCESS  read-only
   STATUS      current
   DESCRIPTION
       " "
   ::= { sispm1040582lrtPortTrafficStatisticsEntry 10 }

sispm1040582lrtPortTrafficRx128to255Bytes OBJECT-TYPE
   SYNTAX      Counter64
   MAX-ACCESS  read-only
   STATUS      current
   DESCRIPTION
       " "
   ::= { sispm1040582lrtPortTrafficStatisticsEntry 11 }

sispm1040582lrtPortTrafficRx256to511Bytes OBJECT-TYPE
   SYNTAX      Counter64
   MAX-ACCESS  read-only
   STATUS      current
   DESCRIPTION
       " "
   ::= { sispm1040582lrtPortTrafficStatisticsEntry 12 }

sispm1040582lrtPortTrafficRx512to1023Bytes OBJECT-TYPE
   SYNTAX      Counter64
   MAX-ACCESS  read-only
   STATUS      current
   DESCRIPTION
       " "
   ::= { sispm1040582lrtPortTrafficStatisticsEntry 13 }

sispm1040582lrtPortTrafficRx1024to1526Bytes OBJECT-TYPE
   SYNTAX      Counter64
   MAX-ACCESS  read-only
   STATUS      current
   DESCRIPTION
       " "
   ::= { sispm1040582lrtPortTrafficStatisticsEntry 14 }

sispm1040582lrtPortTrafficRxExceecd1527Bytes OBJECT-TYPE
   SYNTAX      Counter64
   MAX-ACCESS  read-only
   STATUS      current
   DESCRIPTION
       " "
   ::= { sispm1040582lrtPortTrafficStatisticsEntry 15 }

sispm1040582lrtPortTrafficRxQ0 OBJECT-TYPE
   SYNTAX      Counter64
   MAX-ACCESS  read-only
   STATUS      current
   DESCRIPTION
       " "
   ::= { sispm1040582lrtPortTrafficStatisticsEntry 16 }

sispm1040582lrtPortTrafficRxQ1 OBJECT-TYPE
   SYNTAX      Counter64
   MAX-ACCESS  read-only
   STATUS      current
   DESCRIPTION
       " "
   ::= { sispm1040582lrtPortTrafficStatisticsEntry 17 }

sispm1040582lrtPortTrafficRxQ2 OBJECT-TYPE
   SYNTAX      Counter64
   MAX-ACCESS  read-only
   STATUS      current
   DESCRIPTION
       " "
   ::= { sispm1040582lrtPortTrafficStatisticsEntry 18 }

sispm1040582lrtPortTrafficRxQ3 OBJECT-TYPE
   SYNTAX      Counter64
   MAX-ACCESS  read-only
   STATUS      current
   DESCRIPTION
       " "
   ::= { sispm1040582lrtPortTrafficStatisticsEntry 19 }

sispm1040582lrtPortTrafficRxQ4 OBJECT-TYPE
   SYNTAX      Counter64
   MAX-ACCESS  read-only
   STATUS      current
   DESCRIPTION
       " "
   ::= { sispm1040582lrtPortTrafficStatisticsEntry 20 }

sispm1040582lrtPortTrafficRxQ5 OBJECT-TYPE
   SYNTAX      Counter64
   MAX-ACCESS  read-only
   STATUS      current
   DESCRIPTION
       " "
   ::= { sispm1040582lrtPortTrafficStatisticsEntry 21 }

sispm1040582lrtPortTrafficRxQ6 OBJECT-TYPE
   SYNTAX      Counter64
   MAX-ACCESS  read-only
   STATUS      current
   DESCRIPTION
       " "
   ::= { sispm1040582lrtPortTrafficStatisticsEntry 22 }

sispm1040582lrtPortTrafficRxQ7 OBJECT-TYPE
   SYNTAX      Counter64
   MAX-ACCESS  read-only
   STATUS      current
   DESCRIPTION
       " "
   ::= { sispm1040582lrtPortTrafficStatisticsEntry 23 }

sispm1040582lrtPortTrafficRxDrops OBJECT-TYPE
   SYNTAX      Counter64
   MAX-ACCESS  read-only
   STATUS      current
   DESCRIPTION
       " "
   ::= { sispm1040582lrtPortTrafficStatisticsEntry 24 }

sispm1040582lrtPortTrafficRxCRCorAlignment OBJECT-TYPE
   SYNTAX      Counter64
   MAX-ACCESS  read-only
   STATUS      current
   DESCRIPTION
       " "
   ::= { sispm1040582lrtPortTrafficStatisticsEntry 25 }

sispm1040582lrtPortTrafficRxUndersize OBJECT-TYPE
   SYNTAX      Counter64
   MAX-ACCESS  read-only
   STATUS      current
   DESCRIPTION
       " "
   ::= { sispm1040582lrtPortTrafficStatisticsEntry 26 }

sispm1040582lrtPortTrafficRxOversize OBJECT-TYPE
   SYNTAX      Counter64
   MAX-ACCESS  read-only
   STATUS      current
   DESCRIPTION
       " "
   ::= { sispm1040582lrtPortTrafficStatisticsEntry 27 }

sispm1040582lrtPortTrafficRxFragments OBJECT-TYPE
   SYNTAX      Counter64
   MAX-ACCESS  read-only
   STATUS      current
   DESCRIPTION
       " "
   ::= { sispm1040582lrtPortTrafficStatisticsEntry 28 }

sispm1040582lrtPortTrafficRxJabber OBJECT-TYPE
   SYNTAX      Counter64
   MAX-ACCESS  read-only
   STATUS      current
   DESCRIPTION
       " "
   ::= { sispm1040582lrtPortTrafficStatisticsEntry 29 }

sispm1040582lrtPortTrafficRxFiltered OBJECT-TYPE
   SYNTAX      Counter64
   MAX-ACCESS  read-only
   STATUS      current
   DESCRIPTION
       " "
   ::= { sispm1040582lrtPortTrafficStatisticsEntry 30 }

sispm1040582lrtPortTrafficTxPackets OBJECT-TYPE
   SYNTAX      Counter64
   MAX-ACCESS  read-only
   STATUS      current
   DESCRIPTION
       " "
   ::= { sispm1040582lrtPortTrafficStatisticsEntry 31 }

sispm1040582lrtPortTrafficTxOctets OBJECT-TYPE
   SYNTAX      Counter64
   MAX-ACCESS  read-only
   STATUS      current
   DESCRIPTION
       " "
   ::= { sispm1040582lrtPortTrafficStatisticsEntry 32 }

sispm1040582lrtPortTrafficTxUnicast OBJECT-TYPE
   SYNTAX      Counter64
   MAX-ACCESS  read-only
   STATUS      current
   DESCRIPTION
       " "
   ::= { sispm1040582lrtPortTrafficStatisticsEntry 33 }

sispm1040582lrtPortTrafficTxMulticast OBJECT-TYPE
   SYNTAX      Counter64
   MAX-ACCESS  read-only
   STATUS      current
   DESCRIPTION
       " "
   ::= { sispm1040582lrtPortTrafficStatisticsEntry 34 }

sispm1040582lrtPortTrafficTxBroadcast OBJECT-TYPE
   SYNTAX      Counter64
   MAX-ACCESS  read-only
   STATUS      current
   DESCRIPTION
       " "
   ::= { sispm1040582lrtPortTrafficStatisticsEntry 35 }

sispm1040582lrtPortTrafficTxPause OBJECT-TYPE
   SYNTAX      Counter64
   MAX-ACCESS  read-only
   STATUS      current
   DESCRIPTION
       " "
   ::= { sispm1040582lrtPortTrafficStatisticsEntry 36 }

sispm1040582lrtPortTrafficTx64Bytes OBJECT-TYPE
   SYNTAX      Counter64
   MAX-ACCESS  read-only
   STATUS      current
   DESCRIPTION
       " "
   ::= { sispm1040582lrtPortTrafficStatisticsEntry 37 }

sispm1040582lrtPortTrafficTx65to127Bytes OBJECT-TYPE
   SYNTAX      Counter64
   MAX-ACCESS  read-only
   STATUS      current
   DESCRIPTION
       " "
   ::= { sispm1040582lrtPortTrafficStatisticsEntry 38 }

sispm1040582lrtPortTrafficTx128to255Bytes OBJECT-TYPE
   SYNTAX      Counter64
   MAX-ACCESS  read-only
   STATUS      current
   DESCRIPTION
       " "
   ::= { sispm1040582lrtPortTrafficStatisticsEntry 39 }

sispm1040582lrtPortTrafficTx256to511Bytes OBJECT-TYPE
   SYNTAX      Counter64
   MAX-ACCESS  read-only
   STATUS      current
   DESCRIPTION
       " "
   ::= { sispm1040582lrtPortTrafficStatisticsEntry 40 }

sispm1040582lrtPortTrafficTx512to1023Bytes OBJECT-TYPE
   SYNTAX      Counter64
   MAX-ACCESS  read-only
   STATUS      current
   DESCRIPTION
       " "
   ::= { sispm1040582lrtPortTrafficStatisticsEntry 41 }

sispm1040582lrtPortTrafficTx1024to1526Bytes OBJECT-TYPE
   SYNTAX      Counter64
   MAX-ACCESS  read-only
   STATUS      current
   DESCRIPTION
       " "
   ::= { sispm1040582lrtPortTrafficStatisticsEntry 42 }

sispm1040582lrtPortTrafficTxExceecd1527Bytes OBJECT-TYPE
   SYNTAX      Counter64
   MAX-ACCESS  read-only
   STATUS      current
   DESCRIPTION
       " "
   ::= { sispm1040582lrtPortTrafficStatisticsEntry 43 }

sispm1040582lrtPortTrafficTxQ0 OBJECT-TYPE
   SYNTAX      Counter64
   MAX-ACCESS  read-only
   STATUS      current
   DESCRIPTION
       " "
   ::= { sispm1040582lrtPortTrafficStatisticsEntry 44 }

sispm1040582lrtPortTrafficTxQ1 OBJECT-TYPE
   SYNTAX      Counter64
   MAX-ACCESS  read-only
   STATUS      current
   DESCRIPTION
       " "
   ::= { sispm1040582lrtPortTrafficStatisticsEntry 45 }

sispm1040582lrtPortTrafficTxQ2 OBJECT-TYPE
   SYNTAX      Counter64
   MAX-ACCESS  read-only
   STATUS      current
   DESCRIPTION
       " "
   ::= { sispm1040582lrtPortTrafficStatisticsEntry 46 }

sispm1040582lrtPortTrafficTxQ3 OBJECT-TYPE
   SYNTAX      Counter64
   MAX-ACCESS  read-only
   STATUS      current
   DESCRIPTION
       " "
   ::= { sispm1040582lrtPortTrafficStatisticsEntry 47 }

sispm1040582lrtPortTrafficTxQ4 OBJECT-TYPE
   SYNTAX      Counter64
   MAX-ACCESS  read-only
   STATUS      current
   DESCRIPTION
       " "
   ::= { sispm1040582lrtPortTrafficStatisticsEntry 48 }

sispm1040582lrtPortTrafficTxQ5 OBJECT-TYPE
   SYNTAX      Counter64
   MAX-ACCESS  read-only
   STATUS      current
   DESCRIPTION
       " "
   ::= { sispm1040582lrtPortTrafficStatisticsEntry 49 }

sispm1040582lrtPortTrafficTxQ6 OBJECT-TYPE
   SYNTAX      Counter64
   MAX-ACCESS  read-only
   STATUS      current
   DESCRIPTION
       " "
   ::= { sispm1040582lrtPortTrafficStatisticsEntry 50 }


sispm1040582lrtPortTrafficTxQ7 OBJECT-TYPE
   SYNTAX      Counter64
   MAX-ACCESS  read-only
   STATUS      current
   DESCRIPTION
       " "
   ::= { sispm1040582lrtPortTrafficStatisticsEntry 51 }

sispm1040582lrtPortTrafficTxDrops OBJECT-TYPE
   SYNTAX      Counter64
   MAX-ACCESS  read-only
   STATUS      current
   DESCRIPTION
       " "
   ::= { sispm1040582lrtPortTrafficStatisticsEntry 52 }

sispm1040582lrtPortTrafficTxLateOrExcColl OBJECT-TYPE
   SYNTAX      Counter64
   MAX-ACCESS  read-only
   STATUS      current
   DESCRIPTION
       " "
   ::= { sispm1040582lrtPortTrafficStatisticsEntry 53 }


sispm1040582lrtPortQoSStatistics                                     OBJECT IDENTIFIER ::= { sispm1040582lrtPort 3 }

sispm1040582lrtPortQoSStatisticsClear OBJECT-TYPE
   SYNTAX      Integer32(0|1)
   MAX-ACCESS  read-only
   STATUS      current
   DESCRIPTION
       "default: 0
       0: none
       1: clear "
   ::= { sispm1040582lrtPortQoSStatistics 1 }

sispm1040582lrtPortQoSStatisticsTable OBJECT-TYPE
   SYNTAX      SEQUENCE OF SISPM1040582LRTPortQoSStatisticsEntry
   MAX-ACCESS  not-accessible
   STATUS      current
   DESCRIPTION
       " "
   ::= { sispm1040582lrtPortQoSStatistics 2 }

sispm1040582lrtPortQoSStatisticsEntry OBJECT-TYPE
   SYNTAX      SISPM1040582LRTPortQoSStatisticsEntry
   MAX-ACCESS  not-accessible
   STATUS      current
   DESCRIPTION
       " "
   INDEX    { sispm1040582lrtPortQoSStatisticsPort  }
   ::= { sispm1040582lrtPortQoSStatisticsTable 1 }

SISPM1040582LRTPortQoSStatisticsEntry ::= SEQUENCE {
   sispm1040582lrtPortQoSStatisticsPort      Integer32,
   sispm1040582lrtPortQoSQ0Rx                Counter64,
   sispm1040582lrtPortQoSQ0Tx                Counter64,
   sispm1040582lrtPortQoSQ1Rx                Counter64,
   sispm1040582lrtPortQoSQ1Tx                Counter64,
   sispm1040582lrtPortQoSQ2Rx                Counter64,
   sispm1040582lrtPortQoSQ2Tx                Counter64,
   sispm1040582lrtPortQoSQ3Rx                Counter64,
   sispm1040582lrtPortQoSQ3Tx                Counter64,
   sispm1040582lrtPortQoSQ4Rx                Counter64,
   sispm1040582lrtPortQoSQ4Tx                Counter64,
   sispm1040582lrtPortQoSQ5Rx                Counter64,
   sispm1040582lrtPortQoSQ5Tx                Counter64,
   sispm1040582lrtPortQoSQ6Rx                Counter64,
   sispm1040582lrtPortQoSQ6Tx                Counter64,
   sispm1040582lrtPortQoSQ7Rx                Counter64,
   sispm1040582lrtPortQoSQ7Tx                Counter64
}

sispm1040582lrtPortQoSStatisticsPort OBJECT-TYPE
   SYNTAX      Integer32 (1..4095)
   MAX-ACCESS  not-accessible
   STATUS      current
   DESCRIPTION
       " "
   ::= { sispm1040582lrtPortQoSStatisticsEntry 1 }

sispm1040582lrtPortQoSQ0Rx OBJECT-TYPE
   SYNTAX      Counter64
   MAX-ACCESS  read-only
   STATUS      current
   DESCRIPTION
       " "
   ::= { sispm1040582lrtPortQoSStatisticsEntry 2 }

sispm1040582lrtPortQoSQ0Tx OBJECT-TYPE
   SYNTAX      Counter64
   MAX-ACCESS  read-only
   STATUS      current
   DESCRIPTION
       " "
   ::= { sispm1040582lrtPortQoSStatisticsEntry 3 }

sispm1040582lrtPortQoSQ1Rx OBJECT-TYPE
   SYNTAX      Counter64
   MAX-ACCESS  read-only
   STATUS      current
   DESCRIPTION
       " "
   ::= { sispm1040582lrtPortQoSStatisticsEntry 4 }

sispm1040582lrtPortQoSQ1Tx OBJECT-TYPE
   SYNTAX      Counter64
   MAX-ACCESS  read-only
   STATUS      current
   DESCRIPTION
       " "
   ::= { sispm1040582lrtPortQoSStatisticsEntry 5 }

sispm1040582lrtPortQoSQ2Rx OBJECT-TYPE
   SYNTAX      Counter64
   MAX-ACCESS  read-only
   STATUS      current
   DESCRIPTION
       " "
   ::= { sispm1040582lrtPortQoSStatisticsEntry 6 }

sispm1040582lrtPortQoSQ2Tx OBJECT-TYPE
   SYNTAX      Counter64
   MAX-ACCESS  read-only
   STATUS      current
   DESCRIPTION
       " "
   ::= { sispm1040582lrtPortQoSStatisticsEntry 7 }

sispm1040582lrtPortQoSQ3Rx OBJECT-TYPE
   SYNTAX      Counter64
   MAX-ACCESS  read-only
   STATUS      current
   DESCRIPTION
       " "
   ::= { sispm1040582lrtPortQoSStatisticsEntry 8 }

sispm1040582lrtPortQoSQ3Tx OBJECT-TYPE
   SYNTAX      Counter64
   MAX-ACCESS  read-only
   STATUS      current
   DESCRIPTION
       " "
   ::= { sispm1040582lrtPortQoSStatisticsEntry 9 }

sispm1040582lrtPortQoSQ4Rx OBJECT-TYPE
   SYNTAX      Counter64
   MAX-ACCESS  read-only
   STATUS      current
   DESCRIPTION
       " "
   ::= { sispm1040582lrtPortQoSStatisticsEntry 10 }

sispm1040582lrtPortQoSQ4Tx OBJECT-TYPE
   SYNTAX      Counter64
   MAX-ACCESS  read-only
   STATUS      current
   DESCRIPTION
       " "
   ::= { sispm1040582lrtPortQoSStatisticsEntry 11 }

sispm1040582lrtPortQoSQ5Rx OBJECT-TYPE
   SYNTAX      Counter64
   MAX-ACCESS  read-only
   STATUS      current
   DESCRIPTION
       " "
   ::= { sispm1040582lrtPortQoSStatisticsEntry 12 }

sispm1040582lrtPortQoSQ5Tx OBJECT-TYPE
   SYNTAX      Counter64
   MAX-ACCESS  read-only
   STATUS      current
   DESCRIPTION
       " "
   ::= { sispm1040582lrtPortQoSStatisticsEntry 13 }

sispm1040582lrtPortQoSQ6Rx OBJECT-TYPE
   SYNTAX      Counter64
   MAX-ACCESS  read-only
   STATUS      current
   DESCRIPTION
       " "
   ::= { sispm1040582lrtPortQoSStatisticsEntry 14 }

sispm1040582lrtPortQoSQ6Tx OBJECT-TYPE
   SYNTAX      Counter64
   MAX-ACCESS  read-only
   STATUS      current
   DESCRIPTION
       " "
   ::= { sispm1040582lrtPortQoSStatisticsEntry 15 }

sispm1040582lrtPortQoSQ7Rx OBJECT-TYPE
   SYNTAX      Counter64
   MAX-ACCESS  read-only
   STATUS      current
   DESCRIPTION
       " "
   ::= { sispm1040582lrtPortQoSStatisticsEntry 16 }

sispm1040582lrtPortQoSQ7Tx OBJECT-TYPE
   SYNTAX      Counter64
   MAX-ACCESS  read-only
   STATUS      current
   DESCRIPTION
       " "
   ::= { sispm1040582lrtPortQoSStatisticsEntry 17 }

sispm1040582lrtSFPInfoTable OBJECT-TYPE
   SYNTAX      SEQUENCE OF SISPM1040582LRTSFPInfoEntry
   MAX-ACCESS  not-accessible
   STATUS      current
   DESCRIPTION
       " "
   ::= { sispm1040582lrtPort 4 }

sispm1040582lrtSFPInfoEntry OBJECT-TYPE
   SYNTAX      SISPM1040582LRTSFPInfoEntry
   MAX-ACCESS  not-accessible
   STATUS      current
   DESCRIPTION
       " "
   INDEX    { sispm1040582lrtSFPInfoIndex }
   ::= { sispm1040582lrtSFPInfoTable 1 }

SISPM1040582LRTSFPInfoEntry ::= SEQUENCE {
   sispm1040582lrtSFPInfoIndex               Integer32,
   sispm1040582lrtSFPInfoPort                DisplayString,
   sispm1040582lrtSFPConnectorType           DisplayString,
   sispm1040582lrtSFPFiberType               DisplayString,
   sispm1040582lrtSFPTxCentralWavelength     DisplayString,
   sispm1040582lrtSFPBaudRate                DisplayString,
   sispm1040582lrtSFPVendorOUI               DisplayString,
   sispm1040582lrtSFPVendorName              DisplayString,
   sispm1040582lrtSFPVendorPN                DisplayString,
   sispm1040582lrtSFPVendorRev               DisplayString,
   sispm1040582lrtSFPVendorSN                DisplayString,
   sispm1040582lrtSFPDateCode                DisplayString,
   sispm1040582lrtSFPTemperature             DisplayString,
   sispm1040582lrtSFPVcc                     DisplayString,
   sispm1040582lrtSFPMon1Bias                DisplayString,
   sispm1040582lrtSFPMon2TxPWR               DisplayString,
   sispm1040582lrtSFPMon3RxPWR               DisplayString
}

sispm1040582lrtSFPInfoIndex OBJECT-TYPE
   SYNTAX      Integer32 (1..4095)
   MAX-ACCESS  not-accessible
   STATUS      current
   DESCRIPTION
       " "
   ::= { sispm1040582lrtSFPInfoEntry 1 }

sispm1040582lrtSFPInfoPort OBJECT-TYPE
   SYNTAX      DisplayString
   MAX-ACCESS  read-only
   STATUS      current
   DESCRIPTION
       " "
   ::= { sispm1040582lrtSFPInfoEntry 2 }

sispm1040582lrtSFPConnectorType OBJECT-TYPE
   SYNTAX      DisplayString
   MAX-ACCESS  read-only
   STATUS      current
   DESCRIPTION
       " "
   ::= { sispm1040582lrtSFPInfoEntry 3 }

sispm1040582lrtSFPFiberType OBJECT-TYPE
   SYNTAX      DisplayString
   MAX-ACCESS  read-only
   STATUS      current
   DESCRIPTION
       " "
   ::= { sispm1040582lrtSFPInfoEntry 4 }

sispm1040582lrtSFPTxCentralWavelength OBJECT-TYPE
   SYNTAX      DisplayString
   MAX-ACCESS  read-only
   STATUS      current
   DESCRIPTION
       " "
   ::= { sispm1040582lrtSFPInfoEntry 5 }

sispm1040582lrtSFPBaudRate OBJECT-TYPE
   SYNTAX      DisplayString
   MAX-ACCESS  read-only
   STATUS      current
   DESCRIPTION
       " "
   ::= { sispm1040582lrtSFPInfoEntry 6 }

sispm1040582lrtSFPVendorOUI OBJECT-TYPE
   SYNTAX      DisplayString
   MAX-ACCESS  read-only
   STATUS      current
   DESCRIPTION
       " "
   ::= { sispm1040582lrtSFPInfoEntry 7 }

sispm1040582lrtSFPVendorName OBJECT-TYPE
   SYNTAX      DisplayString
   MAX-ACCESS  read-only
   STATUS      current
   DESCRIPTION
       " "
   ::= { sispm1040582lrtSFPInfoEntry 8 }

sispm1040582lrtSFPVendorPN OBJECT-TYPE
   SYNTAX      DisplayString
   MAX-ACCESS  read-only
   STATUS      current
   DESCRIPTION
       " "
   ::= { sispm1040582lrtSFPInfoEntry 9 }

sispm1040582lrtSFPVendorRev OBJECT-TYPE
   SYNTAX      DisplayString
   MAX-ACCESS  read-only
   STATUS      current
   DESCRIPTION
       " "
   ::= { sispm1040582lrtSFPInfoEntry 10 }

sispm1040582lrtSFPVendorSN OBJECT-TYPE
   SYNTAX      DisplayString
   MAX-ACCESS  read-only
   STATUS      current
   DESCRIPTION
       " "
   ::= { sispm1040582lrtSFPInfoEntry 11 }

sispm1040582lrtSFPDateCode OBJECT-TYPE
   SYNTAX      DisplayString
   MAX-ACCESS  read-only
   STATUS      current
   DESCRIPTION
       " "
   ::= { sispm1040582lrtSFPInfoEntry 12 }

sispm1040582lrtSFPTemperature OBJECT-TYPE
   SYNTAX      DisplayString
   MAX-ACCESS  read-only
   STATUS      current
   DESCRIPTION
       "Value of Celsius"
   ::= { sispm1040582lrtSFPInfoEntry 13 }

sispm1040582lrtSFPVcc OBJECT-TYPE
   SYNTAX      DisplayString
   MAX-ACCESS  read-only
   STATUS      current
   DESCRIPTION
       "Value of V"
   ::= { sispm1040582lrtSFPInfoEntry 14 }

sispm1040582lrtSFPMon1Bias OBJECT-TYPE
   SYNTAX      DisplayString
   MAX-ACCESS  read-only
   STATUS      current
   DESCRIPTION
       "Value of mA"
   ::= { sispm1040582lrtSFPInfoEntry 15 }

sispm1040582lrtSFPMon2TxPWR OBJECT-TYPE
   SYNTAX      DisplayString
   MAX-ACCESS  read-only
   STATUS      current
   DESCRIPTION
       "Value of dBm"
   ::= { sispm1040582lrtSFPInfoEntry 16 }

sispm1040582lrtSFPMon3RxPWR OBJECT-TYPE
   SYNTAX      DisplayString
   MAX-ACCESS  read-only
   STATUS      current
   DESCRIPTION
       "Value of dBm"
   ::= { sispm1040582lrtSFPInfoEntry 17 }


sispm1040582lrtVoiceVLAN                                             OBJECT IDENTIFIER ::= { sispm1040582lrtConfiguration 2 }

sispm1040582lrtVoiceVLANConf                                         OBJECT IDENTIFIER ::= { sispm1040582lrtVoiceVLAN 1 }

sispm1040582lrtVoiceVLANMode OBJECT-TYPE
   SYNTAX      Integer32 (0|1)
   MAX-ACCESS  read-write
   STATUS      current
   DESCRIPTION
       " Voice VLAN mode operation.
       default: 0,
       0: disable
       1: enable"
   ::= { sispm1040582lrtVoiceVLANConf 1 }

sispm1040582lrtVoiceVLANVLANId OBJECT-TYPE
   SYNTAX      Integer32 (1..4094)
   MAX-ACCESS  read-write
   STATUS      current
   DESCRIPTION
       "Voice VLAN ID.
        default: 1000,
        range : 1-4094. "
   ::= { sispm1040582lrtVoiceVLANConf 2 }

sispm1040582lrtVoiceVLANAgingTime OBJECT-TYPE
   SYNTAX      Integer32 (10..10000000)
   MAX-ACCESS  read-write
   STATUS      current
   DESCRIPTION
       " Voice VLAN secure learning aging time.
         default: 86400,
         range : 10 - 10000000. "
   ::= { sispm1040582lrtVoiceVLANConf 3 }

sispm1040582lrtVoiceVLANTrafficClass OBJECT-TYPE
   SYNTAX      Integer32 (0..7)
   MAX-ACCESS  read-write
   STATUS      current
   DESCRIPTION
       " Voice VLAN traffic class, all traffic on the Voice VLAN
         will apply this class, available value is from 0(Low)
         to 7(High).
         default: 7. "
   ::= { sispm1040582lrtVoiceVLANConf 4 }


sispm1040582lrtVoiceVLANPortTable OBJECT-TYPE
   SYNTAX      SEQUENCE OF SISPM1040582LRTVoiceVLANPortEntry
   MAX-ACCESS  not-accessible
   STATUS      current
   DESCRIPTION
       " Show Voice Vlan configuration. "
   ::= { sispm1040582lrtVoiceVLANConf 5 }

sispm1040582lrtVoiceVLANPortEntry OBJECT-TYPE
   SYNTAX      SISPM1040582LRTVoiceVLANPortEntry
   MAX-ACCESS  not-accessible
   STATUS      current
   DESCRIPTION
       " "
   INDEX    { sispm1040582lrtVoiceVLANPort  }
   ::= { sispm1040582lrtVoiceVLANPortTable 1 }

SISPM1040582LRTVoiceVLANPortEntry ::= SEQUENCE {
   sispm1040582lrtVoiceVLANPort                    Integer32,
   sispm1040582lrtVoiceVLANPortMode                Integer32,
   sispm1040582lrtVoiceVLANPortSecurity            Integer32,
   sispm1040582lrtVoiceVLANPortDiscoveryProtocol   Integer32
}

sispm1040582lrtVoiceVLANPort OBJECT-TYPE
   SYNTAX      Integer32 (1..4095)
   MAX-ACCESS  not-accessible
   STATUS      current
   DESCRIPTION
       " port, range : 1 - port number. "
   ::= { sispm1040582lrtVoiceVLANPortEntry 1 }

sispm1040582lrtVoiceVLANPortMode OBJECT-TYPE
   SYNTAX      Integer32 (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { sispm1040582lrtVoiceVLANPortEntry 2 }

sispm1040582lrtVoiceVLANPortSecurity OBJECT-TYPE
   SYNTAX      Integer32 (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { sispm1040582lrtVoiceVLANPortEntry 3 }

sispm1040582lrtVoiceVLANPortDiscoveryProtocol OBJECT-TYPE
   SYNTAX      Integer32 (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { sispm1040582lrtVoiceVLANPortEntry 4 }


sispm1040582lrtVoiceVLANOUI                                          OBJECT IDENTIFIER ::= { sispm1040582lrtVoiceVLAN 2 }

sispm1040582lrtVoiceVLANOUICreate OBJECT-TYPE
   SYNTAX       Integer32(0|1)
   MAX-ACCESS   read-write
   STATUS       current
   DESCRIPTION
       "default: 0
        0 : None  (read only)
        1 : Create an OUI entry"
   ::= { sispm1040582lrtVoiceVLANOUI 1 }

sispm1040582lrtVoiceVLANOUITable OBJECT-TYPE
   SYNTAX      SEQUENCE OF SISPM1040582LRTVoiceVLANOUIEntry
   MAX-ACCESS  not-accessible
   STATUS      current
   DESCRIPTION
       " Create Voice VLAN OUI entry. Modify OUI table will
         restart auto detect OUI process. "
   ::= { sispm1040582lrtVoiceVLANOUI 2 }

sispm1040582lrtVoiceVLANOUIEntry OBJECT-TYPE
   SYNTAX      SISPM1040582LRTVoiceVLANOUIEntry
   MAX-ACCESS  not-accessible
   STATUS      current
   DESCRIPTION
       " "
   INDEX    { sispm1040582lrtVoiceVLANOUIIndex  }
   ::= { sispm1040582lrtVoiceVLANOUITable 1 }

SISPM1040582LRTVoiceVLANOUIEntry ::= SEQUENCE {
   sispm1040582lrtVoiceVLANOUIIndex         Integer32,
   sispm1040582lrtVoiceVLANTelephonyOUI     DisplayString,
   sispm1040582lrtVoiceVLANDescription      DisplayString,
   sispm1040582lrtVoiceVLANOUIRowStatus     Integer32
}

sispm1040582lrtVoiceVLANOUIIndex OBJECT-TYPE
   SYNTAX      Integer32 (1..16)
   MAX-ACCESS  not-accessible
   STATUS      current
   DESCRIPTION
       " "
   ::= { sispm1040582lrtVoiceVLANOUIEntry 1 }

sispm1040582lrtVoiceVLANTelephonyOUI OBJECT-TYPE
   SYNTAX      DisplayString (SIZE (1..32))
   MAX-ACCESS  read-write
   STATUS      current
   DESCRIPTION
       "OUI address, format : 0a 1b 2c "
   ::= { sispm1040582lrtVoiceVLANOUIEntry 2 }

sispm1040582lrtVoiceVLANDescription OBJECT-TYPE
   SYNTAX      DisplayString (SIZE (1..32))
   MAX-ACCESS  read-write
   STATUS      current
   DESCRIPTION
       " Up to 32 characters describing OUI address. "
   ::= { sispm1040582lrtVoiceVLANOUIEntry 3 }

sispm1040582lrtVoiceVLANOUIRowStatus OBJECT-TYPE
   SYNTAX      Integer32 (1..5)
   MAX-ACCESS  read-write
   STATUS      current
   DESCRIPTION
       "1: active
        2: notInservice
        4: destroy
        5: undo"
   ::= { sispm1040582lrtVoiceVLANOUIEntry 4 }

--sispm1040582lrtGARP                                                   OBJECT IDENTIFIER ::= { sispm1040582lrtConfiguration 3 }

--sispm1040582lrtGARPConfTable OBJECT-TYPE
--   SYNTAX      SEQUENCE OF SISPM1040582LRTGARPConfEntry
--   MAX-ACCESS  not-accessible
--   STATUS      current
--   DESCRIPTION
--       " "
--   ::= { sispm1040582lrtGARP 1 }

--sispm1040582lrtGARPConfEntry OBJECT-TYPE
--   SYNTAX      SISPM1040582LRTGARPConfEntry
--   MAX-ACCESS  not-accessible
--   STATUS      current
--   DESCRIPTION
--       " "
--   INDEX    { sispm1040582lrtGARPConfPort  }
--   ::= { sispm1040582lrtGARPConfTable 1 }

--SISPM1040582LRTGARPConfEntry ::= SEQUENCE {
--   sispm1040582lrtGARPConfPort           Integer32,
--   sispm1040582lrtGARPJoinTimer          Integer32,
--   sispm1040582lrtGARPLeaveTimer         Integer32,
--   sispm1040582lrtGARPLeaveAllTimer      Integer32,
--   sispm1040582lrtGARPApplicantion       Integer32,
--   sispm1040582lrtGARPAttributeType      Integer32,
--   sispm1040582lrtGARPApplicant          Integer32
--}

--sispm1040582lrtGARPConfPort OBJECT-TYPE
--   SYNTAX      Integer32 (1..4095)
--   MAX-ACCESS  not-accessible
--   STATUS      current
--   DESCRIPTION
--       " "
--   ::= { sispm1040582lrtGARPConfEntry 1 }

--sispm1040582lrtGARPJoinTimer OBJECT-TYPE
--   SYNTAX      Integer32 (200..1000)
--   MAX-ACCESS  read-write
--   STATUS      current
--   DESCRIPTION
--       "default: 200, range : 200 - 1000 "
--   ::= { sispm1040582lrtGARPConfEntry 2 }

--sispm1040582lrtGARPLeaveTimer OBJECT-TYPE
--   SYNTAX      Integer32 (600..3000)
--   MAX-ACCESS  read-write
--   STATUS      current
--   DESCRIPTION
--       "default: 600 , range : 600 - 3000"
--   ::= { sispm1040582lrtGARPConfEntry 3 }

--sispm1040582lrtGARPLeaveAllTimer OBJECT-TYPE
--   SYNTAX      Integer32 (10000..50000)
--   MAX-ACCESS  read-write
--   STATUS      current
--   DESCRIPTION
--       "default: 10000, range : 10000 - 50000 "
--   ::= { sispm1040582lrtGARPConfEntry 4 }

--sispm1040582lrtGARPApplicantion OBJECT-TYPE
--   SYNTAX      Integer32(1)
--   MAX-ACCESS  read-write
--   STATUS      current
--   DESCRIPTION
--       "default: 1
--       1: GVRP"
--   ::= { sispm1040582lrtGARPConfEntry 5 }

--sispm1040582lrtGARPAttributeType OBJECT-TYPE
--   SYNTAX      Integer32(1)
--   MAX-ACCESS  read-write
--   STATUS      current
--   DESCRIPTION
--       "default: 1
--       1: VLAN"
--   ::= { sispm1040582lrtGARPConfEntry 6 }

--sispm1040582lrtGARPApplicant OBJECT-TYPE
--   SYNTAX      Integer32(0|1)
--   MAX-ACCESS  read-write
--   STATUS      current
--   DESCRIPTION
--       "default: 0
--       0: normal-participant
--       1: non-participant"
--   ::= { sispm1040582lrtGARPConfEntry 7 }

--sispm1040582lrtGARPStatisticsTable OBJECT-TYPE
--   SYNTAX      SEQUENCE OF SISPM1040582LRTGARPStatisticsEntry
--   MAX-ACCESS  not-accessible
--   STATUS      current
--   DESCRIPTION
--       " Show the basic GARP port statistics. "
--   ::= { sispm1040582lrtGARP 2 }

--sispm1040582lrtGARPStatisticsEntry OBJECT-TYPE
--   SYNTAX      SISPM1040582LRTGARPStatisticsEntry
--   MAX-ACCESS  not-accessible
--   STATUS      current
--   DESCRIPTION
--       " "
--   INDEX    { sispm1040582lrtGARPStatisticsPort  }
--   ::= { sispm1040582lrtGARPStatisticsTable 1 }

--SISPM1040582LRTGARPStatisticsEntry ::= SEQUENCE {
--   sispm1040582lrtGARPStatisticsPort             Integer32,
--   sispm1040582lrtGARPStatisticsPeerMAC          DisplayString,
--   sispm1040582lrtGARPStatisticsFailedCount      Counter32
--}

--sispm1040582lrtGARPStatisticsPort OBJECT-TYPE
--   SYNTAX      Integer32 (1..4095)
--   MAX-ACCESS  not-accessible
--   STATUS      current
--   DESCRIPTION
--       " port, range : 1 - port number. "
--   ::= { sispm1040582lrtGARPStatisticsEntry 1 }

--sispm1040582lrtGARPStatisticsPeerMAC OBJECT-TYPE
--   SYNTAX      DisplayString
--   MAX-ACCESS  read-only
--   STATUS      current
--   DESCRIPTION
--       " Peer MAC is MAC address of the neighbour Switch from with GARP frame is received.  "
--   ::= { sispm1040582lrtGARPStatisticsEntry 2 }

--sispm1040582lrtGARPStatisticsFailedCount OBJECT-TYPE
--   SYNTAX      Counter32
--   MAX-ACCESS  read-only
--   STATUS      current
--   DESCRIPTION
--       " explain Failed count here. "
--   ::= { sispm1040582lrtGARPStatisticsEntry 3 }

sispm1040582lrtGVRP                                                   OBJECT IDENTIFIER ::= { sispm1040582lrtConfiguration 4 }

sispm1040582lrtGVRPConf                                                   OBJECT IDENTIFIER ::= { sispm1040582lrtGVRP 1 }

sispm1040582lrtGVRPMode OBJECT-TYPE
   SYNTAX      Integer32(0|1)
   MAX-ACCESS  read-write
   STATUS      current
   DESCRIPTION
       "default: 0,
        0: disable,
        1: enable. "
   ::= { sispm1040582lrtGVRPConf 1 }

sispm1040582lrtGVRPMaxVlan OBJECT-TYPE
   SYNTAX      Integer32(1..4095)
   MAX-ACCESS  read-write
   STATUS      current
   DESCRIPTION
       "Number of simultaniously VLANs that GVRP can control. "
   ::= { sispm1040582lrtGVRPConf 2 }

sispm1040582lrtGVRPJoinTime OBJECT-TYPE
   SYNTAX      Integer32(1..20)
   MAX-ACCESS  read-write
   STATUS      current
   DESCRIPTION
       "join-time in units of centi seconds. Range is 1-20. Default is 20. "
   ::= { sispm1040582lrtGVRPConf 3 }

sispm1040582lrtGVRPLeaveTime OBJECT-TYPE
   SYNTAX      Integer32(60..300)
   MAX-ACCESS  read-write
   STATUS      current
   DESCRIPTION
       "leave-time in units of centi seconds. Range is 60-300. Default is 60. "
   ::= { sispm1040582lrtGVRPConf 4 }

sispm1040582lrtGVRPLeaveAllTime OBJECT-TYPE
   SYNTAX      Integer32(1000..5000)
   MAX-ACCESS  read-write
   STATUS      current
   DESCRIPTION
       "leave-all-time in units of centi seconds Range is 1000-5000. Default is 1000"
   ::= { sispm1040582lrtGVRPConf 5 }

sispm1040582lrtGVRPConfTable OBJECT-TYPE
   SYNTAX      SEQUENCE OF SISPM1040582LRTGVRPConfEntry
   MAX-ACCESS  not-accessible
   STATUS      current
   DESCRIPTION
       " "
   ::= { sispm1040582lrtGVRPConf 6 }

sispm1040582lrtGVRPConfEntry OBJECT-TYPE
   SYNTAX      SISPM1040582LRTGVRPConfEntry
   MAX-ACCESS  not-accessible
   STATUS      current
   DESCRIPTION
       " "
   INDEX    { sispm1040582lrtGVRPConfPort  }
   ::= { sispm1040582lrtGVRPConfTable 1 }

SISPM1040582LRTGVRPConfEntry ::= SEQUENCE {
   sispm1040582lrtGVRPConfPort           Integer32,
   sispm1040582lrtGVRPConfPortMode       Integer32
-- sispm1040582lrtGVRPConfPortRRole      Integer32
}

sispm1040582lrtGVRPConfPort OBJECT-TYPE
   SYNTAX      Integer32 (1..4095)
   MAX-ACCESS  not-accessible
   STATUS      current
   DESCRIPTION
       " "
   ::= { sispm1040582lrtGVRPConfEntry 1 }

sispm1040582lrtGVRPConfPortMode OBJECT-TYPE
   SYNTAX      Integer32(0|1)
   MAX-ACCESS  read-write
   STATUS      current
   DESCRIPTION
       "default: 0
       1: enable
       0: disable"
   ::= { sispm1040582lrtGVRPConfEntry 2 }

--sispm1040582lrtGVRPConfPortRRole OBJECT-TYPE
--   SYNTAX      Integer32(0|1)
--   MAX-ACCESS  read-write
--   STATUS      current
--   DESCRIPTION
--       "default: 0
--       1: enable
--       0: disable"
--   ::= { sispm1040582lrtGVRPConfEntry 3 }

--sispm1040582lrtGVRPStatisticsTable OBJECT-TYPE
--   SYNTAX      SEQUENCE OF SISPM1040582LRTGVRPStatisticsEntry
--   MAX-ACCESS  not-accessible
--   STATUS      current
--   DESCRIPTION
--       " "
--   ::= { sispm1040582lrtGVRP 2 }

--sispm1040582lrtGVRPStatisticsEntry OBJECT-TYPE
--   SYNTAX      SISPM1040582LRTGVRPStatisticsEntry
--   MAX-ACCESS  not-accessible
--   STATUS      current
--   DESCRIPTION
--       " "
--   INDEX    { sispm1040582lrtGVRPStatisticsPort  }
--   ::= { sispm1040582lrtGVRPStatisticsTable 1 }

--SISPM1040582LRTGVRPStatisticsEntry ::= SEQUENCE {
--   sispm1040582lrtGVRPStatisticsPort         Integer32,
--   sispm1040582lrtGVRPStatisticsJoinTxCnt    Counter32,
--   sispm1040582lrtGVRPStatisticsLeaveTxCnt   Counter32
--}

--sispm1040582lrtGVRPStatisticsPort OBJECT-TYPE
--   SYNTAX      Integer32 (1..4095)
--   MAX-ACCESS  not-accessible
--   STATUS      current
--   DESCRIPTION
--       " "
--   ::= { sispm1040582lrtGVRPStatisticsEntry 1 }

--sispm1040582lrtGVRPStatisticsJoinTxCnt OBJECT-TYPE
--   SYNTAX      Counter32
--   MAX-ACCESS  read-only
--   STATUS      current
--   DESCRIPTION
--       " "
--   ::= { sispm1040582lrtGVRPStatisticsEntry 2 }

--sispm1040582lrtGVRPStatisticsLeaveTxCnt OBJECT-TYPE
--   SYNTAX      Counter32
--   MAX-ACCESS  read-only
--   STATUS      current
--   DESCRIPTION
--       " "
--   ::= { sispm1040582lrtGVRPStatisticsEntry 3 }


sispm1040582lrtMirroring                                             OBJECT IDENTIFIER ::= { sispm1040582lrtConfiguration 6 }

--sispm1040582lrtPortToMirrorOn OBJECT-TYPE
--   SYNTAX      Integer32(0..10)
--   MAX-ACCESS  read-write
--   STATUS      current
--   DESCRIPTION
--       "default: 0
--        0: disable,
--        range : 1 - port number. "
--   ::= { sispm1040582lrtMirroring 2 }
--
--sispm1040582lrtMirrorTable OBJECT-TYPE
--   SYNTAX      SEQUENCE OF SISPM1040582LRTMirrorEntry
--   MAX-ACCESS  not-accessible
--   STATUS      current
--   DESCRIPTION
--       " "
--   ::= { sispm1040582lrtMirroring 3 }
--
--sispm1040582lrtMirrorEntry OBJECT-TYPE
--   SYNTAX      SISPM1040582LRTMirrorEntry
--   MAX-ACCESS  not-accessible
--   STATUS      current
--   DESCRIPTION
--       " "
--   INDEX    { sispm1040582lrtMirrorPort  }
--   ::= { sispm1040582lrtMirrorTable 1 }
--
--SISPM1040582LRTMirrorEntry ::= SEQUENCE {
--   sispm1040582lrtMirrorPort		Integer32,
--   sispm1040582lrtMirrorMode		Integer32
--}
--
--sispm1040582lrtMirrorPort OBJECT-TYPE
--   SYNTAX      Integer32 (1..4095)
--   MAX-ACCESS  not-accessible
--   STATUS      current
--   DESCRIPTION
--       " "
--   ::= { sispm1040582lrtMirrorEntry 1 }
--
--sispm1040582lrtMirrorMode OBJECT-TYPE
--   SYNTAX      Integer32(0..3)
--   MAX-ACCESS  read-write
--   STATUS      current
--   DESCRIPTION
--       "default: 0
--       0: disable
--       1: enable
--       2: rx only
--       3: tx only
--       Setting Tx mirroring for analyzer port has no effect. Tx mirroring ignored"
--   ::= { sispm1040582lrtMirrorEntry 2 }

sispm1040582lrtRMirrorMode OBJECT-TYPE
   SYNTAX      Integer32(0|1)
   MAX-ACCESS  read-write
   STATUS      current
   DESCRIPTION
       "default: 0
        0: disable,
        1: enable"
   ::= { sispm1040582lrtMirroring 4 }

sispm1040582lrtRMirrorType OBJECT-TYPE
   SYNTAX      Integer32(0..3)
   MAX-ACCESS  read-write
   STATUS      current
   DESCRIPTION
       "0: Mirror
        1: Source(RMirror)
        2: Intermediate(RMirror)
        3: Destination(RMirror)"
   ::= { sispm1040582lrtMirroring 5 }

sispm1040582lrtRMirrorVLANID OBJECT-TYPE
   SYNTAX      Integer32(1..4095)
   MAX-ACCESS  read-write
   STATUS      current
   DESCRIPTION
       "VLAN ID"
   ::= { sispm1040582lrtMirroring 6 }

sispm1040582lrtRMirrorReflectorPort OBJECT-TYPE
   SYNTAX      Integer32(1..4095)
   MAX-ACCESS  read-write
   STATUS      current
   DESCRIPTION
       "Reflector Port range: 1 - port number."
   ::= { sispm1040582lrtMirroring 7 }
   
sispm1040582lrtRMirrorSourceVLANs OBJECT-TYPE
   SYNTAX      DisplayString
   MAX-ACCESS  read-write
   STATUS      current
   DESCRIPTION
       "VLAN-based Mirroring."
   ::= { sispm1040582lrtMirroring 8 }   
   
sispm1040582lrtRMirrorCPUSource OBJECT-TYPE
   SYNTAX      Integer32(0..3)
   MAX-ACCESS  read-write
   STATUS      current
   DESCRIPTION
       "0: Disable
        1: RX Only
        2: TX Only
        3: Both"
   ::= { sispm1040582lrtMirroring 9 }
   
sispm1040582lrtRMirrorTable OBJECT-TYPE
   SYNTAX      SEQUENCE OF SISPM1040582LRTRMirrorEntry
   MAX-ACCESS  not-accessible
   STATUS      current
   DESCRIPTION
       " "
   ::= { sispm1040582lrtMirroring 12 }

sispm1040582lrtRMirrorEntry OBJECT-TYPE
   SYNTAX      SISPM1040582LRTRMirrorEntry
   MAX-ACCESS  not-accessible
   STATUS      current
   DESCRIPTION
       " "
   INDEX    { sispm1040582lrtRMirrorPort  }
   ::= { sispm1040582lrtRMirrorTable 1 }

SISPM1040582LRTRMirrorEntry ::= SEQUENCE {
   sispm1040582lrtRMirrorPort             Integer32,
   sispm1040582lrtRMirrorPortSource       Integer32,
   sispm1040582lrtRMirrorPortIntermediate Integer32,
   sispm1040582lrtRMirrorPortDestination  Integer32
}

sispm1040582lrtRMirrorPort OBJECT-TYPE
   SYNTAX      Integer32
   MAX-ACCESS  not-accessible
   STATUS      current
   DESCRIPTION
       " "
   ::= { sispm1040582lrtRMirrorEntry 1 }

sispm1040582lrtRMirrorPortSource OBJECT-TYPE
   SYNTAX      Integer32(0..3)
   MAX-ACCESS  read-write
   STATUS      current
   DESCRIPTION
       "0: Disable
        1: RX Only
        2: TX Only
        3: Both"
   ::= { sispm1040582lrtRMirrorEntry 2 }

sispm1040582lrtRMirrorPortIntermediate OBJECT-TYPE
   SYNTAX      Integer32(0|1)
   MAX-ACCESS  read-write
   STATUS      current
   DESCRIPTION
       "0: disable,
        1: enable"
   ::= { sispm1040582lrtRMirrorEntry 3 }

sispm1040582lrtRMirrorPortDestination OBJECT-TYPE
   SYNTAX      Integer32(0|1)
   MAX-ACCESS  read-write
   STATUS      current
   DESCRIPTION
       "0: disable,
        1: enable"
   ::= { sispm1040582lrtRMirrorEntry 4 }


sispm1040582lrtTrapEventSeverity                                             OBJECT IDENTIFIER ::= { sispm1040582lrtConfiguration 7 }

sispm1040582lrtTrapEventSeverityTable OBJECT-TYPE
   SYNTAX      SEQUENCE OF SISPM1040582LRTTrapEventSeverityEntry
   MAX-ACCESS  not-accessible
   STATUS      current
   DESCRIPTION
       " "
   ::= { sispm1040582lrtTrapEventSeverity 1 }

sispm1040582lrtTrapEventSeverityEntry OBJECT-TYPE
   SYNTAX      SISPM1040582LRTTrapEventSeverityEntry
   MAX-ACCESS  not-accessible
   STATUS      current
   DESCRIPTION
       " "
   INDEX    { sispm1040582lrtTrapEventSeverityIndex }
   ::= { sispm1040582lrtTrapEventSeverityTable 1 }

SISPM1040582LRTTrapEventSeverityEntry ::= SEQUENCE {
   sispm1040582lrtTrapEventSeverityIndex        Integer32,
   sispm1040582lrtTrapEventSeverityGroupName    DisplayString,
   sispm1040582lrtTrapEventSeverityLevel        Integer32,
   sispm1040582lrtTrapEventSeveritySyslog       Integer32,
   sispm1040582lrtTrapEventSeverityTrap         Integer32,
   sispm1040582lrtTrapEventSeveritySMTP         Integer32,
   sispm1040582lrtTrapEventSeveritySwitch2go    Integer32
}

sispm1040582lrtTrapEventSeverityIndex OBJECT-TYPE
   SYNTAX      Integer32
   MAX-ACCESS  not-accessible
   STATUS      current
   DESCRIPTION
       " "
   ::= { sispm1040582lrtTrapEventSeverityEntry 1 }

sispm1040582lrtTrapEventSeverityGroupName OBJECT-TYPE
   SYNTAX      DisplayString
   MAX-ACCESS  read-only
   STATUS      current
   DESCRIPTION
       "Group Name"
   ::= { sispm1040582lrtTrapEventSeverityEntry 2 }

sispm1040582lrtTrapEventSeverityLevel OBJECT-TYPE
   SYNTAX      Integer32
   MAX-ACCESS  not-accessible
   STATUS      current
   DESCRIPTION
       "0:Emergency
       1:Alert
       2:Critical
       3:Error
       4:Warning
       5:Notice
       6:Information
       7:Debug"
   ::= { sispm1040582lrtTrapEventSeverityEntry 3 }

sispm1040582lrtTrapEventSeveritySyslog OBJECT-TYPE
   SYNTAX      Integer32
   MAX-ACCESS  not-accessible
   STATUS      current
   DESCRIPTION
       "0:disable
       1:enable"
   ::= { sispm1040582lrtTrapEventSeverityEntry 4 }

sispm1040582lrtTrapEventSeverityTrap OBJECT-TYPE
   SYNTAX      Integer32
   MAX-ACCESS  not-accessible
   STATUS      current
   DESCRIPTION
       "0:disable
       1:enable"
   ::= { sispm1040582lrtTrapEventSeverityEntry 5 }

sispm1040582lrtTrapEventSeveritySMTP OBJECT-TYPE
   SYNTAX      Integer32
   MAX-ACCESS  not-accessible
   STATUS      current
   DESCRIPTION
       "0:disable
       1:enable"
   ::= { sispm1040582lrtTrapEventSeverityEntry 6 }

sispm1040582lrtTrapEventSeveritySwitch2go OBJECT-TYPE
   SYNTAX      Integer32
   MAX-ACCESS  not-accessible
   STATUS      current
   DESCRIPTION
       "0:disable
       1:enable"
   ::= { sispm1040582lrtTrapEventSeverityEntry 7 }

-- =======================================================================================================================
sispm1040582lrtSMTP                                             OBJECT IDENTIFIER ::= { sispm1040582lrtConfiguration 8 }

sispm1040582lrtSMTPMailServer OBJECT-TYPE
   SYNTAX      DisplayString
   MAX-ACCESS  read-write
   STATUS      current
   DESCRIPTION
       " Up to 47 characters describing email server. "
   ::= { sispm1040582lrtSMTP 1 }

sispm1040582lrtSMTPUserName OBJECT-TYPE
   SYNTAX      DisplayString
   MAX-ACCESS  read-write
   STATUS      current
   DESCRIPTION
       " Up to 47 characters describing user name. "
   ::= { sispm1040582lrtSMTP 2 }

sispm1040582lrtSMTPPassword OBJECT-TYPE
   SYNTAX      DisplayString
   MAX-ACCESS  read-write
   STATUS      current
   DESCRIPTION
       " Up to 47 characters describing password. "
   ::= { sispm1040582lrtSMTP 3 }

sispm1040582lrtSMTPSender OBJECT-TYPE
   SYNTAX      DisplayString
   MAX-ACCESS  read-write
   STATUS      current
   DESCRIPTION
       " Up to 47 characters describing sender. "
   ::= { sispm1040582lrtSMTP 5 }

sispm1040582lrtSMTPReturnPath OBJECT-TYPE
   SYNTAX      DisplayString
   MAX-ACCESS  read-write
   STATUS      current
   DESCRIPTION
       " Up to 47 characters describing return path. "
   ::= { sispm1040582lrtSMTP 6 }

sispm1040582lrtSMTPEmailAddress1 OBJECT-TYPE
   SYNTAX      DisplayString
   MAX-ACCESS  read-write
   STATUS      current
   DESCRIPTION
       " Up to 47 characters describing mail address. "
   ::= { sispm1040582lrtSMTP 7 }

sispm1040582lrtSMTPEmailAddress2 OBJECT-TYPE
   SYNTAX      DisplayString
   MAX-ACCESS  read-write
   STATUS      current
   DESCRIPTION
       " Up to 47 characters describing mail address. "
   ::= { sispm1040582lrtSMTP 8 }

sispm1040582lrtSMTPEmailAddress3 OBJECT-TYPE
   SYNTAX      DisplayString
   MAX-ACCESS  read-write
   STATUS      current
   DESCRIPTION
       " Up to 47 characters describing mail address. "
   ::= { sispm1040582lrtSMTP 9 }

sispm1040582lrtSMTPEmailAddress4 OBJECT-TYPE
   SYNTAX      DisplayString
   MAX-ACCESS  read-write
   STATUS      current
   DESCRIPTION
       " Up to 47 characters describing mail address. "
   ::= { sispm1040582lrtSMTP 10 }

sispm1040582lrtSMTPEmailAddress5 OBJECT-TYPE
   SYNTAX      DisplayString
   MAX-ACCESS  read-write
   STATUS      current
   DESCRIPTION
       " Up to 47 characters describing mail address. "
   ::= { sispm1040582lrtSMTP 11 }

sispm1040582lrtSMTPEmailAddress6 OBJECT-TYPE
   SYNTAX      DisplayString
   MAX-ACCESS  read-write
   STATUS      current
   DESCRIPTION
       " Up to 47 characters describing mail address. "
   ::= { sispm1040582lrtSMTP 12 }

-- =======================================================================================================================
sispm1040582lrtACLConf                                              OBJECT IDENTIFIER ::= { sispm1040582lrtConfiguration 9 }

-- RowStatus Info:  createAndGo, notReady not supported.
-- =======================================================================================================================
-- Textual Conventions for the sispm1040582lrt Acl Mib
-- =======================================================================================================================
--
    sispm1040582lrtACL                     OBJECT IDENTIFIER  ::= { sispm1040582lrtACLConf 1 }
    sispm1040582lrtACLACE                  OBJECT IDENTIFIER  ::= { sispm1040582lrtACLConf 3 }

--
-- =======================================================================================================================
-- Start sispm1040582lrtACLPortConf group
-- =======================================================================================================================
--sispm1040582lrtACLPortConfTable

    sispm1040582lrtACLPortConfTable OBJECT-TYPE
               SYNTAX      SEQUENCE OF     SISPM1040582LRTACLPortConfEntry
               MAX-ACCESS  not-accessible
               STATUS      current
               DESCRIPTION
                   "The ACL Port Conf Table.
                    INDEX for this table is ifIndex which is
                    equivalent to the panel port number."
               ::= {     sispm1040582lrtACL 1 }

    sispm1040582lrtACLPortConfEntry OBJECT-TYPE
               SYNTAX          SISPM1040582LRTACLPortConfEntry
               MAX-ACCESS  not-accessible
               STATUS      current
               DESCRIPTION
                   "The ACL Port Conf Entry. "
               INDEX    {     ifIndex  }
               ::= {     sispm1040582lrtACLPortConfTable 1 }

    SISPM1040582LRTACLPortConfEntry             ::=
            SEQUENCE {
                 sispm1040582lrtACLPortConfPolicyID        Integer32,
                 sispm1040582lrtACLPortConfAction          INTEGER,
                 sispm1040582lrtACLPortConfRateLimiterID   Integer32,
                 sispm1040582lrtACLPortConfPortRedirect    Integer32,
                 sispm1040582lrtACLPortConfMirror          AdminMode,
                 sispm1040582lrtACLPortConfLogging         AdminMode,
                 sispm1040582lrtACLPortConfShutdown        AdminMode,
                 sispm1040582lrtACLPortConfState           AdminMode,
                 sispm1040582lrtACLPortConfCounter         Counter32
                 }

    sispm1040582lrtACLPortConfPolicyID OBJECT-TYPE
               SYNTAX       Integer32 (0..63)
               MAX-ACCESS   read-write
               STATUS       current
               DESCRIPTION
                   "The policy to apply to this port.
                    default: 0, range : 0 - 63. "
               ::= {     sispm1040582lrtACLPortConfEntry 2 }

    sispm1040582lrtACLPortConfAction OBJECT-TYPE
               SYNTAX      INTEGER { deny(0), permit(1) }
               MAX-ACCESS  read-write
               STATUS      current
               DESCRIPTION
                   "Whether forwarding is permitted ('Permit') or denied ('Deny').
                    default: 1,
                    0: Deny,
                    1: Permit."
               ::= {     sispm1040582lrtACLPortConfEntry 3 }

    sispm1040582lrtACLPortConfRateLimiterID OBJECT-TYPE
               SYNTAX      Integer32 (0..16)
               MAX-ACCESS  read-write
               STATUS      current
               DESCRIPTION
                   "The rate limiter to apply on this port.
                    0: Disable,
                    range : 0 - 16. "
               ::= {     sispm1040582lrtACLPortConfEntry 4 }

    sispm1040582lrtACLPortConfPortRedirect OBJECT-TYPE
               SYNTAX      Integer32 (0..4095)
               MAX-ACCESS  read-write
               STATUS      current
               DESCRIPTION
                   "Port frames are redirected on.
                    0: Disable,
                    range : 0 - end port number. "
               ::= {     sispm1040582lrtACLPortConfEntry 5 }

    sispm1040582lrtACLPortConfMirror OBJECT-TYPE
               SYNTAX      AdminMode
               MAX-ACCESS  read-write
               STATUS      current
               DESCRIPTION
                   "The mirror operation of this port."
               ::= {     sispm1040582lrtACLPortConfEntry 6 }

    sispm1040582lrtACLPortConfLogging OBJECT-TYPE
               SYNTAX      AdminMode
               MAX-ACCESS  read-write
               STATUS      current
               DESCRIPTION
                   "Specify the logging operation of this port."
               ::= {     sispm1040582lrtACLPortConfEntry 7 }

    sispm1040582lrtACLPortConfShutdown OBJECT-TYPE
               SYNTAX      AdminMode
               MAX-ACCESS  read-write
               STATUS      current
               DESCRIPTION
                   "Specify the port shut down operation of this port."
               DEFVAL  { disable }
               ::= {     sispm1040582lrtACLPortConfEntry 8 }

    sispm1040582lrtACLPortConfState OBJECT-TYPE
               SYNTAX      AdminMode
               MAX-ACCESS  read-write
               STATUS      current
               DESCRIPTION
                   "Specify the port state of this port."
               DEFVAL  { enable }
               ::= {     sispm1040582lrtACLPortConfEntry 9 }

    sispm1040582lrtACLPortConfCounter OBJECT-TYPE
               SYNTAX      Counter32
               MAX-ACCESS  read-only
               STATUS      current
               DESCRIPTION
                   "Counts the number of frames that match this ACE. "
               ::= {     sispm1040582lrtACLPortConfEntry 10 }

--
-- =======================================================================================================================
-- Start sispm1040582lrtACLRateLimiter group
-- =======================================================================================================================
--sispm1040582lrtACLRateLimiterTable

    sispm1040582lrtACLRateLimiterTable OBJECT-TYPE
               SYNTAX      SEQUENCE OF     SISPM1040582LRTACLRateLimiterEntry
               MAX-ACCESS  not-accessible
               STATUS      current
               DESCRIPTION
                   "The ACL Rate Limiter Table."
               ::= {     sispm1040582lrtACL 2 }

    sispm1040582lrtACLRateLimiterEntry OBJECT-TYPE
               SYNTAX          SISPM1040582LRTACLRateLimiterEntry
               MAX-ACCESS  not-accessible
               STATUS      current
               DESCRIPTION
                   "The ACL Rate Limiter Entry. "
               INDEX    {     sispm1040582lrtACLRateLimiterID  }
               ::= {     sispm1040582lrtACLRateLimiterTable 1 }

    SISPM1040582LRTACLRateLimiterEntry             ::= SEQUENCE {
                 sispm1040582lrtACLRateLimiterID       Integer32,
                 sispm1040582lrtACLRateLimiterRate     Integer32,
                 sispm1040582lrtACLRateLimiterUnit     INTEGER
                 }

    sispm1040582lrtACLRateLimiterID OBJECT-TYPE
               SYNTAX      Integer32 (1..16)
               MAX-ACCESS  not-accessible
               STATUS      current
               DESCRIPTION
                   "Rate Limiter ID.
                    range : 1-16 "
               ::= {     sispm1040582lrtACLRateLimiterEntry 1 }

    sispm1040582lrtACLRateLimiterRate OBJECT-TYPE
               SYNTAX      Integer32(0..3276700)
               MAX-ACCESS  read-write
               STATUS      current
               DESCRIPTION
                   "default: 1,
                    range :
                    <0-3276700> pps,The valid rate is 0 - 99, 100, 200, 300,
                    ..., 3276700 in pps.
                    <0-10000> kbps,The valid rate is 0, 100, 200, 300,...,
                    1000000 in kbps."
               ::= {     sispm1040582lrtACLRateLimiterEntry 2 }

    sispm1040582lrtACLRateLimiterUnit OBJECT-TYPE
               SYNTAX      INTEGER { pps(0), kbps(1) }
               MAX-ACCESS  read-write
               STATUS      current
               DESCRIPTION
                   "Specify the rate unit.
                    sispm1040582lrt(e){0: pps, 1: kbps.}
                    sispm1040582lrt{0: pps}"
               ::= {     sispm1040582lrtACLRateLimiterEntry 3 }

--
-- =======================================================================================================================
-- Start sispm1040582lrtACLACE group
-- =======================================================================================================================
--sispm1040582lrtACLACEClear

    sispm1040582lrtACLACEClear OBJECT-TYPE
               SYNTAX      ActivateCmd
               MAX-ACCESS  read-write
               STATUS      current
               DESCRIPTION
                   "Clear all ACE counters."
               ::= {     sispm1040582lrtACLACE 1 }

--sispm1040582lrtACLACETable

    sispm1040582lrtACLACETable OBJECT-TYPE
               SYNTAX      SEQUENCE OF     SISPM1040582LRTACLACEEntry
               MAX-ACCESS  not-accessible
               STATUS      current
               DESCRIPTION
                   "Create ACL ACE entry. "
               ::= {     sispm1040582lrtACLACE 2 }

    sispm1040582lrtACLACEEntry OBJECT-TYPE
               SYNTAX          SISPM1040582LRTACLACEEntry
               MAX-ACCESS  not-accessible
               STATUS      current
               DESCRIPTION
                   "The ACLACE Table."
               INDEX    {     sispm1040582lrtACLACEIndex  }
               ::= {     sispm1040582lrtACLACETable 1 }

    SISPM1040582LRTACLACEEntry             ::= SEQUENCE {
                 sispm1040582lrtACLACEIndex                Integer32,
                 sispm1040582lrtACLACEID                   Integer32,
                 sispm1040582lrtACLACENextID               Integer32,
--               sispm1040582lrtACLACELoopUp               AdminMode,
                 sispm1040582lrtACLACEIngressPort          DisplayString,
                 sispm1040582lrtACLACEPortPolicyNumber     Integer32,
                 sispm1040582lrtACLACEPortPolicyBitmask    Integer32,
                 sispm1040582lrtACLACEFrameType            INTEGER,
                 sispm1040582lrtACLACEAction               INTEGER,
                 sispm1040582lrtACLACEFilterPort           Integer32,
                 sispm1040582lrtACLACEDenyPortRedirect     DisplayString,
                 sispm1040582lrtACLACERateLimiter          Integer32,
                 sispm1040582lrtACLACEMirror               AdminMode,
                 sispm1040582lrtACLACELogging              AdminMode,
                 sispm1040582lrtACLACEShutdown             AdminMode,
                 sispm1040582lrtACLACECounter              Counter32,
                 sispm1040582lrtACLACEVLAN8021QTagged      INTEGER,
                 sispm1040582lrtACLACEVLANVID              Integer32,
                 sispm1040582lrtACLACEVLANTagPriority      DisplayString,
                 sispm1040582lrtACLACESMAC                 DisplayString,
                 sispm1040582lrtACLACEDMACType             INTEGER,
                 sispm1040582lrtACLACEDMAC                 DisplayString,
                 sispm1040582lrtACLACEEtherType            Integer32,
                 sispm1040582lrtACLACEArpOpCode            INTEGER,
                 sispm1040582lrtACLACEArpFlagsRequestReply INTEGER,
                 sispm1040582lrtACLACEArpFlagsArpSMac      INTEGER,
                 sispm1040582lrtACLACEArpFlagsRarpDmac     INTEGER,
                 sispm1040582lrtACLACEArpFlagsLength       INTEGER,
                 sispm1040582lrtACLACEArpFlagsIp           INTEGER,
                 sispm1040582lrtACLACEArpFlagsEthernet     INTEGER,
                 sispm1040582lrtACLACESIPType              INTEGER,
                 sispm1040582lrtACLACESIPIPAddress         IpAddress,
                 sispm1040582lrtACLACESIPIPMask            IpAddress,
                 sispm1040582lrtACLACEDIPType              INTEGER,
                 sispm1040582lrtACLACEDIPIPAddress         IpAddress,
                 sispm1040582lrtACLACEDIPIPMask            IpAddress,
                 sispm1040582lrtACLACEIPProtocol           INTEGER,
                 sispm1040582lrtACLACEIPProtocolValue      Integer32,
                 sispm1040582lrtACLACEIPFlagsTTL           INTEGER,
                 sispm1040582lrtACLACEIPFlagsFragment      INTEGER,
                 sispm1040582lrtACLACEIPFlagsOptions       INTEGER,
                 sispm1040582lrtACLACEICMPType             Integer32,
                 sispm1040582lrtACLACEICMPCode             Integer32,
                 sispm1040582lrtACLACESourcePort           DisplayString,
                 sispm1040582lrtACLACEDestPort             DisplayString,
                 sispm1040582lrtACLACETCPFlagsFin          INTEGER,
                 sispm1040582lrtACLACETCPFlagsSyn          INTEGER,
                 sispm1040582lrtACLACETCPFlagsRst          INTEGER,
                 sispm1040582lrtACLACETCPFlagsPsh          INTEGER,
                 sispm1040582lrtACLACETCPFlagsAck          INTEGER,
                 sispm1040582lrtACLACETCPFlagsUrg          INTEGER,
                 sispm1040582lrtACLACEIPv6SIPAddress       DisplayString,
                 sispm1040582lrtACLACEIPv6SIPBitmask       DisplayString,
                 sispm1040582lrtACLACEIPv6HopLimit         INTEGER,
                 sispm1040582lrtACLACERowStatus            RowStatus
                 }

    sispm1040582lrtACLACEIndex OBJECT-TYPE
               SYNTAX      Integer32(1..256)
               MAX-ACCESS  not-accessible
               STATUS      current
               DESCRIPTION
                   "The index. "
               ::= {     sispm1040582lrtACLACEEntry 1 }

    sispm1040582lrtACLACEID OBJECT-TYPE
               SYNTAX      Integer32(1..256)
               MAX-ACCESS  read-create
               STATUS      current
               DESCRIPTION
                   "If the ACE ID is specified and an entry with this ACE ID
                    already exists, the ACE will be modified. Otherwise, a
                    new ACE will be added.
                    range : 1 - 256. "
               ::= {     sispm1040582lrtACLACEEntry 2 }

    sispm1040582lrtACLACENextID OBJECT-TYPE
               SYNTAX      Integer32 (0..256)
               MAX-ACCESS  read-create
               STATUS      current
               DESCRIPTION
                   "If the next ACE ID is non zero, the ACE will be placed
                    before this ACE in the list. If the next ACE ID is zero,
                    the ACE will be placed last in the list.
                    range : 0 - 256. "
               ::= {     sispm1040582lrtACLACEEntry 3 }

--    sispm1040582lrtACLACELoopUp OBJECT-TYPE
--               SYNTAX      AdminMode
--               MAX-ACCESS  read-create
--               STATUS      current
--               DESCRIPTION
--                   "Specify the second lookup operation of the ACE."
--               ::= {     sispm1040582lrtACLACEEntry 4 }

    sispm1040582lrtACLACEIngressPort OBJECT-TYPE
               SYNTAX      DisplayString
               MAX-ACCESS  read-create
               STATUS      current
               DESCRIPTION
                   "Indicates the ingress port of the ACE. Possible values are:
                    0: All,The ACE will match all ingress port.
                    Port n: The ACE will match a specific ingress port."
               ::= {     sispm1040582lrtACLACEEntry 5 }

    sispm1040582lrtACLACEPortPolicyNumber OBJECT-TYPE
               SYNTAX      Integer32(0..64)
               MAX-ACCESS  read-create
               STATUS      current
               DESCRIPTION
                   "policy value.
                    range : 0 - 64.
                    64: Any. "
               ::= {     sispm1040582lrtACLACEEntry 6 }

    sispm1040582lrtACLACEPortPolicyBitmask OBJECT-TYPE
               SYNTAX      Integer32(0..256)
               MAX-ACCESS  read-create
               STATUS      current
               DESCRIPTION
                   "When 'Specific' is selected for the policy filter,
                    you can enter a specific policy bitmask.
                    sispm1040582lrt{range : 0 - 63(0x3f), 64: no data.}
                    sispm1040582lrt{range : 0 - 255(0xff), 256: no data.}"
               ::= {     sispm1040582lrtACLACEEntry 7 }

    sispm1040582lrtACLACEFrameType OBJECT-TYPE
               SYNTAX      INTEGER {   any(0), etype(1), arp(2),
                                       ipv4(3), ipv6(4) }
               MAX-ACCESS  read-create
               STATUS      current
               DESCRIPTION
                   "Select the frame type for this ACE.
                    When change the type Related oid will set default.
                    0: any,
                    1: etype,
                    2: arp,
                    3: ipv4,
                    4: ipv6."
               ::= {     sispm1040582lrtACLACEEntry 8 }

    sispm1040582lrtACLACEAction OBJECT-TYPE
               SYNTAX      INTEGER { deny(0), permit(1), filter(2) }
               MAX-ACCESS  read-create
               STATUS      current
               DESCRIPTION
                   "sispm1040582lrt{0: Deny,1: Permit,2: Filter, range: 0-2.}
                    sispm1040582lrt{0: Deny,1: Permit }"
               ::= {     sispm1040582lrtACLACEEntry 9 }

    sispm1040582lrtACLACEFilterPort OBJECT-TYPE
               SYNTAX      Integer32(-1..255)
               MAX-ACCESS  read-create
               STATUS      current
               DESCRIPTION
                   "When 'Action' is 'Filter' can set.
                    0: All,
                    Port n: The ACE applies to this port number, where n is
                    the number of the switch port.
                    -1: no data.
                    range: -1 - Port number."
               ::= {     sispm1040582lrtACLACEEntry 10 }

    sispm1040582lrtACLACEDenyPortRedirect OBJECT-TYPE
               SYNTAX      DisplayString
               MAX-ACCESS  read-create
               STATUS      current
               DESCRIPTION
                   "Frames that hit the ACE are redirected to the port
                    number specified here.Disabled,indicates that the port
                    redirect operation is disabled.
                    When 'Action' is 'Deny' can set.
                    0: disabled,
                    Port no: The ACE applies to this port number, where n is
                    the number of the switch port."
               ::= {     sispm1040582lrtACLACEEntry 11 }

    sispm1040582lrtACLACERateLimiter OBJECT-TYPE
               SYNTAX      Integer32(0..16)
               MAX-ACCESS  read-create
               STATUS      current
               DESCRIPTION
                   "default: 0,
                    0: Disable
                    range : 0 - 16 "
               ::= {     sispm1040582lrtACLACEEntry 12 }

    sispm1040582lrtACLACEMirror OBJECT-TYPE
               SYNTAX      AdminMode
               MAX-ACCESS  read-create
               STATUS      current
               DESCRIPTION
                   "default: 0,
                    0: disable - Frames matching the ACE are not mirrored.
                    1: enable - Frames matching the ACE are mirrored."
               ::= {     sispm1040582lrtACLACEEntry 13 }

    sispm1040582lrtACLACELogging OBJECT-TYPE
               SYNTAX      AdminMode
               MAX-ACCESS  read-create
               STATUS      current
               DESCRIPTION
                   "default: 0,
                    0: disable - Frames matching the ACE are not logged.
                    1: enable - Frames matching the ACE are stored in the
                   system log."
               ::= {     sispm1040582lrtACLACEEntry 14 }

    sispm1040582lrtACLACEShutdown OBJECT-TYPE
               SYNTAX      AdminMode
               MAX-ACCESS  read-create
               STATUS      current
               DESCRIPTION
                   "default: 0,
                    0: disable - Port shut down is disabled for the AC.
                    1: enable - If a frame matches the ACE, the ingress port
                    will be disabled."
               ::= {     sispm1040582lrtACLACEEntry 15 }

    sispm1040582lrtACLACECounter OBJECT-TYPE
               SYNTAX      Counter32
               MAX-ACCESS  read-only
               STATUS      current
               DESCRIPTION
                   "The counter indicates the number of times the ACE was
                    hit by a frame. "
               ::= {     sispm1040582lrtACLACEEntry 16 }

    sispm1040582lrtACLACEVLAN8021QTagged OBJECT-TYPE
               SYNTAX      INTEGER { disable(0), enable(1), any(2) }
               MAX-ACCESS  read-create
               STATUS      current
               DESCRIPTION
                   "Specify whether frames can hit the action according to
                    the 802.1Q tagged.
                    default: 2,
                    0: disable - Untagged frame only.
                    1: enable - Tagged frame only.
                    2: Any - Any value is allowed."
               ::= {     sispm1040582lrtACLACEEntry 17 }

    sispm1040582lrtACLACEVLANVID OBJECT-TYPE
               SYNTAX      Integer32(0..4095)
               MAX-ACCESS  read-create
               STATUS      current
               DESCRIPTION
                   "Specify the VLAN ID filter for this ACE.
                    The vid can't be set when 802.1Q Tagged is disabled.
                    default: 0,
                    0: Any - No VLAN ID filter is specified.
                    range : 0 - 4095 "
               ::= {     sispm1040582lrtACLACEEntry 18 }

    sispm1040582lrtACLACEVLANTagPriority OBJECT-TYPE
               SYNTAX      DisplayString
               MAX-ACCESS  read-create
               STATUS      current
               DESCRIPTION
                   "Specify the tag priority for this ACE.
                    The tag priority can't be set when 802.1Q Tagged is disabled.
                    range: 0~7,0-1,2-3,4-5,6-7,0-3,4-7."
               ::= {     sispm1040582lrtACLACEEntry 19 }

    sispm1040582lrtACLACESMAC OBJECT-TYPE
               SYNTAX      DisplayString
               MAX-ACCESS  read-create
               STATUS      current
               DESCRIPTION
                   "Configure source MAC address for this ACE.
                    <mac-address>: A frame that hits this ACE matches this
                    source MAC address value. xx-xx-xx-xx-xx-xx.
                    Any: Don't care."
               ::= {    sispm1040582lrtACLACEEntry 20 }

    sispm1040582lrtACLACEDMACType OBJECT-TYPE
               SYNTAX      INTEGER { any(0), mc(1), bc(2), uc(3) ,
                                     macAddress(4) , noData(5) }
               MAX-ACCESS  read-create
               STATUS      current
               DESCRIPTION
                   "DMAC Type.
                    default: 0,
                    0: Any - Don't care.
                    1: Multicast - Frame must be multicast.
                    2: Broadcast - Frame must be broadcast.
                    3: Unicast - Frame must be unicast.
                    4: mac address.
                    5: no data."
               DEFVAL  { any }
               ::= {    sispm1040582lrtACLACEEntry 21 }

    sispm1040582lrtACLACEDMAC OBJECT-TYPE
               SYNTAX      DisplayString
               MAX-ACCESS  read-create
               STATUS      current
               DESCRIPTION
                   "Configure destination MAC address for this ACE.
                    <mac-address>: A frame that hits this ACE matches this
                    destination MAC address value. xx-xx-xx-xx-xx-xx."
               ::= {     sispm1040582lrtACLACEEntry 22 }

    sispm1040582lrtACLACEEtherType OBJECT-TYPE
               SYNTAX      Integer32(-1..65535)
               MAX-ACCESS  read-create
               STATUS      current
               DESCRIPTION
                   "0: Any - Any but excluding 0x0800(IPv4) 0x0806(ARP) and
                    0x86DD(IPv6).
                    range : 0 or 1536(0x0600), 65535(0xffff).
                    -1: No data. "
               ::= {     sispm1040582lrtACLACEEntry 23 }

    sispm1040582lrtACLACEArpOpCode OBJECT-TYPE
               SYNTAX      INTEGER { any(0), arp(1), rarp(2),
                                     other(3), noData(4) }
               MAX-ACCESS  read-create
               STATUS      current
               DESCRIPTION
                   "Configure ARP opcode for this ACE.
                    default: 0,
                    0: Any - Don't care.
                    1: arp.
                    2: rarp.
                    3: other.
                    4: No data."
               DEFVAL  { any }
               ::= {     sispm1040582lrtACLACEEntry 24 }

    sispm1040582lrtACLACEArpFlagsRequestReply OBJECT-TYPE
               SYNTAX      INTEGER { reply(0), request(1), any(2), noData(3)}
               MAX-ACCESS  read-create
               STATUS      current
               DESCRIPTION
                   "Specify the available ARP/RARP opcode (OP) flag for this ACE.
                    default: 2,
                    0: Frame must have ARP Reply or RARP Reply OP flag.
                    1: Frame must have ARP Request or RARP Request OP flag set.
                    2: Any - Don't care.
                    3: No data."
               DEFVAL  { any }
               ::= {     sispm1040582lrtACLACEEntry 25 }

    sispm1040582lrtACLACEArpFlagsArpSMac OBJECT-TYPE
               SYNTAX      INTEGER { notEqualSMAC(0), equalSMAC(1),
                                     any(2), noData(3)}
               MAX-ACCESS  read-create
               STATUS      current
               DESCRIPTION
                   "Specify whether frames can hit the action according to their
                    sender hardware address field (SHA) settings.
                    default: 2,
                    0: ARP frames where SHA is not equal to the SMAC address.
                    1: ARP frames where SHA is equal to the SMAC address.
                    2: Any - Don't care.
                    3: No data."
               DEFVAL  { any }
               ::= {     sispm1040582lrtACLACEEntry 26 }

    sispm1040582lrtACLACEArpFlagsRarpDmac OBJECT-TYPE
               SYNTAX      INTEGER { notEqualDMAC(0), equalDMAC(1),
                                     any(2), noData(3)}
               MAX-ACCESS  read-create
               STATUS      current
               DESCRIPTION
                   "Specify whether frames can hit the action according to
                    their target hardware address field (THA) settings.
                    default: 2,
                    0: RARP frames where THA is not equal to the DMAC address.
                    1: RARP frames where THA is equal to the DMAC address.
                    2: Any - Don't care.
                    3: No data."
               DEFVAL  { any }
               ::= {     sispm1040582lrtACLACEEntry 27 }

    sispm1040582lrtACLACEArpFlagsLength OBJECT-TYPE
               SYNTAX      INTEGER { notEqualEthIpV4 (0), equalEthIpV4(1),
                                     any(2), noData(3)}
               MAX-ACCESS  read-create
               STATUS      current
               DESCRIPTION
                   "Specify whether frames can hit the action according to
                    their ARP/RARP hardware address length (HLN) and protocol
                    address length (PLN) settings.
                    default: 2,
                    0: ARP/RARP frames where the HLN is not equal to
                    Ethernet(0x06) or the (PLN) is not equal to IPv4(0x04).
                    1: ARP/RARP frames where the HLN is equal to Ethernet (0x06)
                    and the (PLN) is equal to IPv4(0x04).
                    2: Any - Don't care.
                    3: No data."
                DEFVAL  { any }
                ::= {     sispm1040582lrtACLACEEntry 28 }

    sispm1040582lrtACLACEArpFlagsIp OBJECT-TYPE
               SYNTAX      INTEGER { notEqualEth(0), equalEth(1),
                                     any(2), noData(3)}
               MAX-ACCESS  read-create
               STATUS      current
               DESCRIPTION
                   "Specify whether frames can hit the action according to
                    their ARP/RARP hardware address space (HRD) settings.
                    default: 2,
                    0: ARP/RARP frames where the HLD is not equal to Ethernet(1).
                    1: ARP/RARP frames where the HLD is equal to Ethernet(1).
                    2: Any - Don't care.
                    3: No data."
               DEFVAL  { any }
               ::= {     sispm1040582lrtACLACEEntry 29 }

    sispm1040582lrtACLACEArpFlagsEthernet OBJECT-TYPE
               SYNTAX      INTEGER { notEqualIp(0), equalIp(1),
                                     any(2), noData(3)}
               MAX-ACCESS  read-create
               STATUS      current
               DESCRIPTION
                   "Specify whether frames can hit the action
                    according to their ARP/RARP protocol address space (PRO) settings.
                    default: 2,
                    0: ARP/RARP frames where the PRO is not equal to IP\n(0x800).
                    1: ARP/RARP frames where the PRO is equal to IP(0x800).
                    2: Any - Don't care.
                    3: No data."
               DEFVAL  { any }
               ::= {     sispm1040582lrtACLACEEntry 30 }

    sispm1040582lrtACLACESIPType OBJECT-TYPE
               SYNTAX      INTEGER { any(0), ip(1), network(2), noData(3) }
               MAX-ACCESS  read-create
               STATUS      current
               DESCRIPTION
                   "Configure source IP address for this ACE.
                    default: 0,
                    0: Any - Don't care.
                    1: IP Address.
                    2: Network.
                    3: No data."
               DEFVAL  { any }
               ::= {     sispm1040582lrtACLACEEntry 31 }

    sispm1040582lrtACLACESIPIPAddress OBJECT-TYPE
               SYNTAX      IpAddress
               MAX-ACCESS  read-create
               STATUS      current
               DESCRIPTION
                   "A frame that hits this ACE matches this source IP address
                    value."
               ::= {     sispm1040582lrtACLACEEntry 32 }

    sispm1040582lrtACLACESIPIPMask OBJECT-TYPE
               SYNTAX      IpAddress
               MAX-ACCESS  read-create
               STATUS      current
               DESCRIPTION
                   "Specific sender IP mask in dotted decimal notation."
               ::= {     sispm1040582lrtACLACEEntry 33 }

    sispm1040582lrtACLACEDIPType OBJECT-TYPE
               SYNTAX      INTEGER { any(0), ip(1), network(2), noData(3) }
               MAX-ACCESS  read-create
               STATUS      current
               DESCRIPTION
                   "Configure destination IP address for this ACE.
                    default: 0,
                    0: Any - Don't care.
                    1: IP Address.
                    2: Network.
                    3: No data."
               DEFVAL  { any }
               ::= {     sispm1040582lrtACLACEEntry 34 }

    sispm1040582lrtACLACEDIPIPAddress OBJECT-TYPE
               SYNTAX      IpAddress
               MAX-ACCESS  read-create
               STATUS      current
               DESCRIPTION
                   "A frame that hits this ACE matches this destination IP
                    address value."
               ::= {     sispm1040582lrtACLACEEntry 35 }

    sispm1040582lrtACLACEDIPIPMask OBJECT-TYPE
               SYNTAX      IpAddress
               MAX-ACCESS  read-create
               STATUS      current
               DESCRIPTION
                   "Specific sender IP mask in dotted decimal notation."
               ::= {     sispm1040582lrtACLACEEntry 36 }

    sispm1040582lrtACLACEIPProtocol OBJECT-TYPE
               SYNTAX      INTEGER{ any(0), icmp(1), udp(2), tcp(3),
                                    other(4), noData(5)}
               MAX-ACCESS  read-create
               STATUS      current
               DESCRIPTION
                   "Specify the IP protocol filter for this ACE.
                    default: 0,
                    0: Any,
                    1: ICMP,
                    2: UDP,
                    3: TCP,
                    4: Other,
                    5: no data."
               DEFVAL  { any }
               ::= {     sispm1040582lrtACLACEEntry 37 }

    sispm1040582lrtACLACEIPProtocolValue OBJECT-TYPE
               SYNTAX      Integer32(0..256)
               MAX-ACCESS  read-create
               STATUS      current
               DESCRIPTION
                   "Configure IP protocol value for this ACE when IP Protocol
                    is 'other'.
                    default: 256,
                    256: No data.
                    range : 0 - 256"
               ::= {     sispm1040582lrtACLACEEntry 38 }

    sispm1040582lrtACLACEIPFlagsTTL OBJECT-TYPE
               SYNTAX      INTEGER { nonZero(0), zero(1), any(2), noData(3) }
               MAX-ACCESS  read-create
               STATUS      current
               DESCRIPTION
                   "Specify the Time-to-Live settings for this ACE.
                    default: 0,
                    0: zero,
                    1: Non-Zero
                    2: Any,,
                    3: No data."
               DEFVAL  { nonZero }
               ::= {     sispm1040582lrtACLACEEntry 39 }

    sispm1040582lrtACLACEIPFlagsFragment OBJECT-TYPE
               SYNTAX      INTEGER{yes(0), no(1), any(2), noData(3)}
               MAX-ACCESS  read-create
               STATUS      current
               DESCRIPTION
                   "Specify the fragment offset settings for this ACE.
                    default: 2,
                    0: No,
                    1: Yes,
                    2: Any,
                    3: No data."
               DEFVAL  { any }
               ::= {     sispm1040582lrtACLACEEntry 40 }

    sispm1040582lrtACLACEIPFlagsOptions OBJECT-TYPE
               SYNTAX      INTEGER{yes(0), no(1), any(2),  noData(3)}
               MAX-ACCESS  read-create
               STATUS      current
               DESCRIPTION
                   "Specify the options flag setting for this ACE.
                    default: 2,
                    0: No,
                    1: Yes,
                    2: Any,
                    3: No data."
               DEFVAL  { any }
               ::= {     sispm1040582lrtACLACEEntry 41 }

    sispm1040582lrtACLACEICMPType OBJECT-TYPE
               SYNTAX      Integer32(0..257)
               MAX-ACCESS  read-create
               STATUS      current
               DESCRIPTION
                   "Configure ICMP type for this ACE.
                    default: 256,
                    256: Any - Don't care.
                    257: No data.
                    range : 0 - 257."
               ::= { sispm1040582lrtACLACEEntry 42 }

    sispm1040582lrtACLACEICMPCode OBJECT-TYPE
               SYNTAX      Integer32(0..257)
               MAX-ACCESS  read-create
               STATUS      current
               DESCRIPTION
                   "Configure ICMP code for this ACE.
                    default: 256,
                    256: Any - Don't care.
                    257: No data.
                    range : 0 - 257."
               ::= {     sispm1040582lrtACLACEEntry 43 }

    sispm1040582lrtACLACESourcePort OBJECT-TYPE
               SYNTAX      DisplayString
               MAX-ACCESS  read-create
               STATUS      current
               DESCRIPTION
                   "Configure Source UDP/TCP port range for this ACE.
                    default: any,
                    specific: 0~65535,
                    range : 0 - 65535."
               ::= {     sispm1040582lrtACLACEEntry 44 }

    sispm1040582lrtACLACEDestPort OBJECT-TYPE
               SYNTAX      DisplayString
               MAX-ACCESS  read-create
               STATUS      current
               DESCRIPTION
                   "Configure Destination UDP/TCP port range for this ACE.
                    default: any,
                    specific: 0~65535,
                    range : 0 - 65535."
               ::= {     sispm1040582lrtACLACEEntry 45 }

    sispm1040582lrtACLACETCPFlagsFin OBJECT-TYPE
               SYNTAX      INTEGER { unset(0), set(1), any(2), noData(3) }
               MAX-ACCESS  read-create
               STATUS      current
               DESCRIPTION
                   "Configure TCP (FIN) flags for this ACE.
                    default: 2,
                    0: TCP frames where the FIN field is unset.
                    1: TCP frames where the FIN field is set.
                    2: Any - Don't care.
                    3: No data."
               DEFVAL  { any }
               ::= {     sispm1040582lrtACLACEEntry 46 }

    sispm1040582lrtACLACETCPFlagsSyn OBJECT-TYPE
               SYNTAX      INTEGER { unset(0), set(1), any(2), noData(3) }
               MAX-ACCESS  read-create
               STATUS      current
               DESCRIPTION
                   "Configure TCP (SYN) flags for this ACE.
                    default: 2,
                    0: TCP frames where the SYN field is unset.
                    1: TCP frames where the SYN field is set.
                    2: Any - Don't care.
                    3: No data."
               DEFVAL  { any }
               ::= {     sispm1040582lrtACLACEEntry 47 }

    sispm1040582lrtACLACETCPFlagsRst OBJECT-TYPE
               SYNTAX      INTEGER { unset(0), set(1), any(2), noData(3) }
               MAX-ACCESS  read-create
               STATUS      current
               DESCRIPTION
                   "Configure TCP (RST) flags for this ACE.
                    default: 2,
                    0: TCP frames where the RST field is unset.
                    1: TCP frames where the RST field is set.
                    2: Any - Don't care.
                    3: No data."
               DEFVAL  { any }
               ::= {     sispm1040582lrtACLACEEntry 48 }

    sispm1040582lrtACLACETCPFlagsPsh OBJECT-TYPE
               SYNTAX      INTEGER { unset(0), set(1), any(2), noData(3) }
               MAX-ACCESS  read-create
               STATUS      current
               DESCRIPTION
                   "Configure TCP (PSH) flags for this ACE.
                    default: 2,
                    0: TCP frames where the PSH field is unset.
                    1: TCP frames where the PSH field is set.
                    2: Any - Don't care.
                    3: No data."
               DEFVAL  { any }
               ::= {     sispm1040582lrtACLACEEntry 49 }

    sispm1040582lrtACLACETCPFlagsAck OBJECT-TYPE
               SYNTAX      INTEGER { unset(0), set(1), any(2), noData(3) }
               MAX-ACCESS  read-create
               STATUS      current
               DESCRIPTION
                   "Configure TCP (ACK) flags for this ACE.
                    default: 2,
                    0: TCP frames where the ACK field is unset.
                    1: TCP frames where the ACK field is set.
                    2: Any - Don't care.
                    3: No data."
               DEFVAL  { any }
               ::= {     sispm1040582lrtACLACEEntry 50 }

    sispm1040582lrtACLACETCPFlagsUrg OBJECT-TYPE
               SYNTAX      INTEGER { unset(0), set(1), any(2), noData(3) }
               MAX-ACCESS  read-create
               STATUS      current
               DESCRIPTION
                   "Configure TCP (URG) flags for this ACE.
                    default: 2,
                    0: TCP frames where the URG field is unset.
                    1: TCP frames where the URG field is set.
                    2: Any - Don't care.
                    3: No data."
               DEFVAL  { any }
               ::= {     sispm1040582lrtACLACEEntry 51 }

    sispm1040582lrtACLACEIPv6SIPAddress OBJECT-TYPE
               SYNTAX      DisplayString
               MAX-ACCESS  read-create
               STATUS      current
               DESCRIPTION
                   "When 'Specific' is selected for the source IPv6 filter,
                    you can enter a specific SIPv6 address.
                    The field only supported last 32 bits for IPv6 address. "
               ::= {     sispm1040582lrtACLACEEntry 52 }

    sispm1040582lrtACLACEIPv6SIPBitmask OBJECT-TYPE
               SYNTAX      DisplayString
               MAX-ACCESS  read-create
               STATUS      current
               DESCRIPTION
                   "When 'Specific' is selected for the source IPv6 filter,
                    you can enter a specific SIPv6 mask.
                    The field only supported last 32 bits for IPv6 address. "
               ::= {     sispm1040582lrtACLACEEntry 53 }

    sispm1040582lrtACLACEIPv6HopLimit OBJECT-TYPE
               SYNTAX      INTEGER { unset(0), set(1), any(2), noData(3) }
               MAX-ACCESS  read-create
               STATUS      current
               DESCRIPTION
                   "Specify the hop limit settings for this ACE.
                    default: 2,
                    0: Where the Hop Limit field is unset.
                    1: Where the Hop Limit field is set.
                    2: Any - Don't care,
                    3: No data."
               DEFVAL  { any }
               ::= {     sispm1040582lrtACLACEEntry 54 }

    sispm1040582lrtACLACERowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sispm1040582lrtACLACEEntry 56 }

--
-- =======================================================================================================================
-- Start sispm1040582lrtACLStatus group
-- =======================================================================================================================
--sispm1040582lrtACLStatusTable

    sispm1040582lrtACLStatusTable OBJECT-TYPE
               SYNTAX      SEQUENCE OF     SISPM1040582LRTACLStatusEntry
               MAX-ACCESS  not-accessible
               STATUS      current
               DESCRIPTION
                   " ACL ACE Status entry. "
               ::= {     sispm1040582lrtACL 4 }

    sispm1040582lrtACLStatusEntry OBJECT-TYPE
               SYNTAX          SISPM1040582LRTACLStatusEntry
               MAX-ACCESS  not-accessible
               STATUS      current
               DESCRIPTION
                   "The ACL Status Entry."
               INDEX    {    sispm1040582lrtACLStatusIndex  }
               ::= {     sispm1040582lrtACLStatusTable 1 }

    SISPM1040582LRTACLStatusEntry             ::= SEQUENCE {
                 sispm1040582lrtACLStatusIndex          Integer32,
                 sispm1040582lrtACLStatusUser           DisplayString,
                 sispm1040582lrtACLStatusID             Integer32,
                 sispm1040582lrtACLStatusIngressPort    DisplayString,
                 sispm1040582lrtACLStatusFrameType      DisplayString,
                 sispm1040582lrtACLStatusAction         DisplayString,
                 sispm1040582lrtACLStatusRateLimiter    DisplayString,
                 sispm1040582lrtACLStatusPortRedirect   DisplayString,
                 sispm1040582lrtACLStatusMirror         DisplayString,
                 sispm1040582lrtACLStatusCPU            DisplayString,
--               sispm1040582lrtACLStatusCPUOnce        DisplayString,
                 sispm1040582lrtACLStatusCounter        Counter32,
                 sispm1040582lrtACLStatusConflict       DisplayString
                 }

    sispm1040582lrtACLStatusIndex OBJECT-TYPE
               SYNTAX      Integer32(1..256)
               MAX-ACCESS  not-accessible
               STATUS      current
               DESCRIPTION
                   "The ACL status index. "
               ::= {     sispm1040582lrtACLStatusEntry 1 }

    sispm1040582lrtACLStatusUser OBJECT-TYPE
               SYNTAX      DisplayString
               MAX-ACCESS  read-only
               STATUS      current
               DESCRIPTION
                   "Indicates the ACL user.
                    S : Static,
                    IPMG : IP Management,
                    IPSG : IP Source Guard,
                    IPMC : IPMC,
                    ARPI : Arp Inspection,
                    UPnP : UPnP,
                    DHCP : DHCP. "
               ::= {     sispm1040582lrtACLStatusEntry 2 }

    sispm1040582lrtACLStatusID OBJECT-TYPE
               SYNTAX      Integer32(1..256)
               MAX-ACCESS  read-only
               STATUS      current
               DESCRIPTION
                   "ACE ID.
                    range : 1 - 256. "
               ::= {     sispm1040582lrtACLStatusEntry 3 }

    sispm1040582lrtACLStatusIngressPort OBJECT-TYPE
               SYNTAX      DisplayString
               MAX-ACCESS  read-only
               STATUS      current
               DESCRIPTION
                   "Indicates the ingress port of the ACE. Possible values are:
                    All: The ACE will match all ingress port.
                    Port: The ACE will match a specific ingress port. "
               ::= {     sispm1040582lrtACLStatusEntry 4 }

    sispm1040582lrtACLStatusFrameType OBJECT-TYPE
               SYNTAX      DisplayString
               MAX-ACCESS  read-only
               STATUS      current
               DESCRIPTION
                   "Indicates the frame type of the ACE.
                    Any: The ACE will match any frame type.
                    EType: The ACE will match Ethernet Type frames.
                    Note that an Ethernet Type based ACE will not get matched
                    by IP and ARP frames.
                    ARP: The ACE will match ARP/RARP frames.
                    IPv4: The ACE will match all IPv4 frames.
                    IPv4/ICMP: The ACE will match IPv4 frames with ICMP protocol.
                    IPv4/UDP: The ACE will match IPv4 frames with UDP protocol.
                    IPv4/TCP: The ACE will match IPv4 frames with TCP protocol.
                    IPv4/Other: The ACE will match IPv4 frames, which are not
                    ICMP/UDP/TCP.
                    IPv6: The ACE will match all IPv6 standard frames. "
               ::= {     sispm1040582lrtACLStatusEntry 5 }

    sispm1040582lrtACLStatusAction OBJECT-TYPE
               SYNTAX      DisplayString
               MAX-ACCESS  read-only
               STATUS      current
               DESCRIPTION
                   "Indicates the forwarding action of the ACE. "
               ::= {     sispm1040582lrtACLStatusEntry 6 }

    sispm1040582lrtACLStatusRateLimiter OBJECT-TYPE
               SYNTAX      DisplayString
               MAX-ACCESS  read-only
               STATUS      current
               DESCRIPTION
                   "Indicates the rate limiter number of the ACE. "
               ::= {     sispm1040582lrtACLStatusEntry 7 }

    sispm1040582lrtACLStatusPortRedirect OBJECT-TYPE
               SYNTAX      DisplayString
               MAX-ACCESS  read-only
               STATUS      current
               DESCRIPTION
                   "Indicates the port redirect operation of the ACE.
                    Frames matching the ACE are redirected to the port number. "
               ::= {     sispm1040582lrtACLStatusEntry 8 }

    sispm1040582lrtACLStatusMirror OBJECT-TYPE
               SYNTAX      DisplayString
               MAX-ACCESS  read-only
               STATUS      current
               DESCRIPTION
                   "Specify the mirror operation of this port.
                    Not support 'sispm1040582lrt'."
               ::= {     sispm1040582lrtACLStatusEntry 9 }

    sispm1040582lrtACLStatusCPU OBJECT-TYPE
               SYNTAX      DisplayString
               MAX-ACCESS  read-only
               STATUS      current
               DESCRIPTION
                   "Forward packet that matched the specific ACE to CPU. "
               ::= {     sispm1040582lrtACLStatusEntry 10 }

--    sispm1040582lrtACLStatusCPUOnce OBJECT-TYPE
--               SYNTAX      DisplayString
--               MAX-ACCESS  read-only
--               STATUS      current
--               DESCRIPTION
--                   "Forward first packet that matched the specific ACE to CPU. "
--               ::= {     sispm1040582lrtACLStatusEntry 11 }

    sispm1040582lrtACLStatusCounter OBJECT-TYPE
               SYNTAX      Counter32
               MAX-ACCESS  read-only
               STATUS      current
               DESCRIPTION
                   "The counter indicates the number of times the ACE was hit
                    by a frame. "
               ::= {     sispm1040582lrtACLStatusEntry 12 }

    sispm1040582lrtACLStatusConflict OBJECT-TYPE
               SYNTAX      DisplayString
               MAX-ACCESS  read-only
               STATUS      current
               DESCRIPTION
                   "Indicates the hardware status of the specific ACE.
                    The specific ACE is not applied to the hardware due to
                    hardware limitations. "
               ::= {     sispm1040582lrtACLStatusEntry 13 }


-- =======================================================================================================================
-- sispm1040582lrtAclConformance
-- =======================================================================================================================
sispm1040582lrtAclConformance OBJECT IDENTIFIER ::= { sispm1040582lrtACL 200 }

sispm1040582lrtAclCompliances OBJECT IDENTIFIER ::= { sispm1040582lrtAclConformance 1 }

sispm1040582lrtAclGroups    OBJECT IDENTIFIER ::= { sispm1040582lrtAclConformance 2 }

sispm1040582lrtACLPortConfGroup OBJECT-GROUP
    OBJECTS {
                -- sispm1040582lrtACLPortConfTable
                 sispm1040582lrtACLPortConfPolicyID,
                 sispm1040582lrtACLPortConfAction,
                 sispm1040582lrtACLPortConfRateLimiterID,
                 sispm1040582lrtACLPortConfPortRedirect,
--               sispm1040582lrtACLPortConfMirror,
                 sispm1040582lrtACLPortConfLogging,
                 sispm1040582lrtACLPortConfShutdown,
                 sispm1040582lrtACLPortConfState,
                 sispm1040582lrtACLPortConfCounter
            }
     STATUS  current
     DESCRIPTION
            "The collection of objects which are used to indicate
            sispm1040582lrt ACL information."
    ::= { sispm1040582lrtAclGroups 1 }

sispm1040582lrtACLRateLimiterGroup OBJECT-GROUP
    OBJECTS {
                -- sispm1040582lrtACLRateLimiterTable
                 sispm1040582lrtACLRateLimiterRate
--               sispm1040582lrtACLRateLimiterUnit
            }
     STATUS  current
     DESCRIPTION
            "The collection of objects which are used to indicate
            sispm1040582lrt ACL information."
    ::= { sispm1040582lrtAclGroups 2 }

sispm1040582lrtACLACEGroup OBJECT-GROUP
    OBJECTS {
                -- sispm1040582lrtACLACEClear
                 sispm1040582lrtACLACEClear,

                -- sispm1040582lrtACLACETable
                 sispm1040582lrtACLACEID,
                 sispm1040582lrtACLACENextID,
--               sispm1040582lrtACLACELoopUp,
                 sispm1040582lrtACLACEIngressPort,
                 sispm1040582lrtACLACEPortPolicyNumber,
                 sispm1040582lrtACLACEPortPolicyBitmask,
                 sispm1040582lrtACLACEFrameType,
                 sispm1040582lrtACLACEAction,
--               sispm1040582lrtACLACEFilterPort,
                 sispm1040582lrtACLACEDenyPortRedirect,
                 sispm1040582lrtACLACERateLimiter,
--               sispm1040582lrtACLACEMirror,
                 sispm1040582lrtACLACELogging,
                 sispm1040582lrtACLACEShutdown,
                 sispm1040582lrtACLACECounter,
--               sispm1040582lrtACLACEVLAN8021QTagged,
                 sispm1040582lrtACLACEVLANVID,
                 sispm1040582lrtACLACEVLANTagPriority,
                 sispm1040582lrtACLACESMAC,
                 sispm1040582lrtACLACEDMACType,
                 sispm1040582lrtACLACEDMAC,
                 sispm1040582lrtACLACEEtherType,
                 sispm1040582lrtACLACEArpOpCode,
                 sispm1040582lrtACLACEArpFlagsRequestReply,
                 sispm1040582lrtACLACEArpFlagsArpSMac,
                 sispm1040582lrtACLACEArpFlagsRarpDmac,
                 sispm1040582lrtACLACEArpFlagsLength,
                 sispm1040582lrtACLACEArpFlagsIp,
                 sispm1040582lrtACLACEArpFlagsEthernet,
                 sispm1040582lrtACLACESIPType,
                 sispm1040582lrtACLACESIPIPAddress,
                 sispm1040582lrtACLACESIPIPMask,
                 sispm1040582lrtACLACEDIPType,
                 sispm1040582lrtACLACEDIPIPAddress,
                 sispm1040582lrtACLACEDIPIPMask,
                 sispm1040582lrtACLACEIPProtocol,
                 sispm1040582lrtACLACEIPProtocolValue,
                 sispm1040582lrtACLACEIPFlagsTTL,
                 sispm1040582lrtACLACEIPFlagsFragment,
                 sispm1040582lrtACLACEIPFlagsOptions,
                 sispm1040582lrtACLACEICMPType,
                 sispm1040582lrtACLACEICMPCode,
                 sispm1040582lrtACLACESourcePort,
                 sispm1040582lrtACLACEDestPort,
                 sispm1040582lrtACLACETCPFlagsFin,
                 sispm1040582lrtACLACETCPFlagsSyn,
                 sispm1040582lrtACLACETCPFlagsRst,
                 sispm1040582lrtACLACETCPFlagsPsh,
                 sispm1040582lrtACLACETCPFlagsAck,
                 sispm1040582lrtACLACETCPFlagsUrg,
                 sispm1040582lrtACLACEIPv6SIPAddress,
                 sispm1040582lrtACLACEIPv6SIPBitmask,
                 sispm1040582lrtACLACEIPv6HopLimit,
                 sispm1040582lrtACLACERowStatus
            }
     STATUS  current
     DESCRIPTION
            "The collection of objects which are used to indicate
            sispm1040582lrt ACL information."
    ::= { sispm1040582lrtAclGroups 3 }

sispm1040582lrtACLStatusGroup OBJECT-GROUP
    OBJECTS {
                -- sispm1040582lrtACLStatusTable
                 sispm1040582lrtACLStatusUser,
                 sispm1040582lrtACLStatusID,
                 sispm1040582lrtACLStatusIngressPort,
                 sispm1040582lrtACLStatusFrameType,
                 sispm1040582lrtACLStatusAction,
                 sispm1040582lrtACLStatusRateLimiter,
                 sispm1040582lrtACLStatusPortRedirect,
                 sispm1040582lrtACLStatusMirror,
                 sispm1040582lrtACLStatusCPU,
--               sispm1040582lrtACLStatusCPUOnce,
                 sispm1040582lrtACLStatusCounter,
                 sispm1040582lrtACLStatusConflict
            }
     STATUS  current
     DESCRIPTION
            "The collection of objects which are used to indicate
            sispm1040582lrt ACL information."
    ::= { sispm1040582lrtAclGroups 4 }


-- =======================================================================================================================
-- =======================================================================================================================
 -- RowStatus Info:  createAndGo, notReady not supported.
-- =======================================================================================================================
-- Textual Conventions for the sispm1040582lrt Qos Mib
-- =======================================================================================================================
--
sispm1040582lrtQosConf                    OBJECT IDENTIFIER ::= { sispm1040582lrtConfiguration 10 }
    sispm1040582lrtQos                        OBJECT IDENTIFIER   ::= { sispm1040582lrtQosConf  1  }
    sispm1040582lrtQosPortClassification      OBJECT IDENTIFIER   ::= { sispm1040582lrtQos 1 }
    sispm1040582lrtQosPortPolicing            OBJECT IDENTIFIER   ::= { sispm1040582lrtQos 2 }
    sispm1040582lrtQosQueuePolicing           OBJECT IDENTIFIER   ::= { sispm1040582lrtQos 3 }
    sispm1040582lrtQosPortScheduler           OBJECT IDENTIFIER   ::= { sispm1040582lrtQos 4 }
    sispm1040582lrtQosPortEgressTagRemarking  OBJECT IDENTIFIER   ::= { sispm1040582lrtQos 6 }
    sispm1040582lrtQosPortDSCP                OBJECT IDENTIFIER   ::= { sispm1040582lrtQos 7 }
    sispm1040582lrtQosDSCP                    OBJECT IDENTIFIER   ::= { sispm1040582lrtQos 8 }
    sispm1040582lrtQosDSCPTranslation         OBJECT IDENTIFIER   ::= { sispm1040582lrtQos 9 }
    sispm1040582lrtQosDSCPClassification      OBJECT IDENTIFIER   ::= { sispm1040582lrtQos 10 }
    sispm1040582lrtQosControlList             OBJECT IDENTIFIER   ::= { sispm1040582lrtQos 11 }
    sispm1040582lrtQosStormControl            OBJECT IDENTIFIER   ::= { sispm1040582lrtQos 12 }
--    sispm1040582lrtQosPortStormControl        OBJECT IDENTIFIER   ::= { sispm1040582lrtQos 13 }
--    sispm1040582lrtQosWRED                    OBJECT IDENTIFIER   ::= { sispm1040582lrtQos 14 }
    sispm1040582lrtQosQCLStatus               OBJECT IDENTIFIER   ::= { sispm1040582lrtQos 15 }


--
-- =======================================================================================================================
-- Start sispm1040582lrtQosPortClassification group
-- =======================================================================================================================
--sispm1040582lrtQosPortClassificationTable

     sispm1040582lrtQosPortClassificationTable OBJECT-TYPE
               SYNTAX      SEQUENCE OF     SISPM1040582LRTQosPortClassificationEntry
               MAX-ACCESS  not-accessible
               STATUS      current
               DESCRIPTION
                   "QoS Ingress Port Classification.
                    INDEX for this table is ifIndex which is
                    equivalent to the panel port number."
               ::= {     sispm1040582lrtQosPortClassification  1 }

    sispm1040582lrtQosPortClassificationEntry OBJECT-TYPE
               SYNTAX          SISPM1040582LRTQosPortClassificationEntry
               MAX-ACCESS  not-accessible
               STATUS      current
               DESCRIPTION
                   "The Qos Port Classification Table."
               INDEX    {     ifIndex  }
               ::= {     sispm1040582lrtQosPortClassificationTable 1 }

    SISPM1040582LRTQosPortClassificationEntry             ::= SEQUENCE {
                sispm1040582lrtQosPortClassificationQoSClass        Integer32,
                sispm1040582lrtQosPortClassificationDPlevel         Integer32,
                sispm1040582lrtQosPortClassificationPCP             Integer32,
                sispm1040582lrtQosPortClassificationDEI             Integer32,
                sispm1040582lrtQosPortClassificationTagClass        AdminMode,
                sispm1040582lrtQosPortClassificationDSCPBased       AdminMode,
                sispm1040582lrtQosPortClassificationQCLAddr         INTEGER,
                sispm1040582lrtQosPortClassificationKeyType         KeyType,
		sispm1040582lrtQosPortClassificationWredGroup       Integer32 
                }

    sispm1040582lrtQosPortClassificationQoSClass OBJECT-TYPE
               SYNTAX      Integer32(0..7)
               MAX-ACCESS  read-write
               STATUS      current
               DESCRIPTION
                  "Controls the default QoS class, i.e., the QoS class for
                   frames not classified
                   in any way. There is a one to one mapping between
                   QoS class, queue and
                   priority. A QoS class of 0 (zero) has the lowest priority.
                   NOTe: If the QoS class has been dynamically changed, then
                   the actual QoS class
                   is shown in parentheses after the configured QoS class.
                   range: 0~7,
                   default: 0."
               ::= {     sispm1040582lrtQosPortClassificationEntry 2 }

    sispm1040582lrtQosPortClassificationDPlevel OBJECT-TYPE
               SYNTAX      Integer32(0..1)
               MAX-ACCESS  read-write
               STATUS      current
               DESCRIPTION
                   "DP level for frames not classified in any way.
                    range: 0~1,
                    default: 0."
               ::= {     sispm1040582lrtQosPortClassificationEntry 3 }

    sispm1040582lrtQosPortClassificationPCP OBJECT-TYPE
               SYNTAX      Integer32(0..7)
               MAX-ACCESS  read-write
               STATUS      current
               DESCRIPTION
                  "Priority Code Point. It is a 3-bit field storing
                   the priority level for the 802.1Q frame.
                   range: 0~7,
                   default: 0.
                   Not support JAGUAR."
               ::= {     sispm1040582lrtQosPortClassificationEntry 4 }

    sispm1040582lrtQosPortClassificationDEI OBJECT-TYPE
               SYNTAX      Integer32(0|1)
               MAX-ACCESS  read-write
               STATUS      current
               DESCRIPTION
                  "Drop Eligible Indicator. It is a 1-bit field in the VLAN.
                   range 0~1,
                   default: 0.
                   Not support JAGUAR."
               ::= {     sispm1040582lrtQosPortClassificationEntry 5 }

    sispm1040582lrtQosPortClassificationTagClass OBJECT-TYPE
               SYNTAX      AdminMode
               MAX-ACCESS  read-write
               STATUS      current
               DESCRIPTION
                  "Configure the classification mode for tagged frames.
                  Not support SMB and JAGUAR."
               DEFVAL  { disable }
               ::= {     sispm1040582lrtQosPortClassificationEntry 6 }

    sispm1040582lrtQosPortClassificationDSCPBased OBJECT-TYPE
               SYNTAX      AdminMode
               MAX-ACCESS  read-write
               STATUS      current
               DESCRIPTION
                  "Click to Enable DSCP Based QoS Ingress Port Classification."
               DEFVAL  { disable }
               ::= {     sispm1040582lrtQosPortClassificationEntry 7 }

    sispm1040582lrtQosPortClassificationQCLAddr OBJECT-TYPE
               SYNTAX      INTEGER { sMacSip(0), dMacDip (1) }
               MAX-ACCESS  read-write
               STATUS      current
               DESCRIPTION
                  "Controls the QCL address matching mode.
                   0: SMAC/SIP,
                   1: DMAC/DIP,
                  default: SMAC/SIP.
                  Only support SPARX_III."
               DEFVAL  { sMacSip }
               ::= {     sispm1040582lrtQosPortClassificationEntry 8 }

    sispm1040582lrtQosPortClassificationKeyType OBJECT-TYPE
               SYNTAX      KeyType
               MAX-ACCESS  read-write
               STATUS      current
               DESCRIPTION
                  "The key type specifying the key generated for frames received
                   on the port.
                   0: Normal, Half key, match outer tag, SIP/DIP and SMAC/DMAC.
                   1: Double Tag: Quarter key, match inner and outer tag.
                   2: IP Address: Half key, match inner and outer tag, SIP and
                      DIP. For non-IP frames, match outer tag only.
                   3: MAC and IP Address: Full key, match inner and outer tag,
                      SMAC, DMAC, SIP and DIP.
                   Only support on SERVAL version."
               DEFVAL  { normal }
               ::= {     sispm1040582lrtQosPortClassificationEntry 9 }
			   
    sispm1040582lrtQosPortClassificationWredGroup OBJECT-TYPE
               SYNTAX      Integer32
               MAX-ACCESS  read-write
               STATUS      current
               DESCRIPTION
                  "Controls the WRED group membership. Range:1-3."
               ::= {     sispm1040582lrtQosPortClassificationEntry 10 }			   

--sispm1040582lrtQoSIngressPortTagClassificationTable
    sispm1040582lrtQoSIngressPortTagClassificationTable OBJECT-TYPE
               SYNTAX      SEQUENCE OF     SISPM1040582LRTQoSIngressPortTagClassificationEntry
               MAX-ACCESS  not-accessible
               STATUS      current
               DESCRIPTION
                   "Show QoS Ingress Port Tag Classification.
                    INDEX for this table is ifIndex which is
                    equivalent to the panel port number."
               ::= {     sispm1040582lrtQosPortClassification 2 }

    sispm1040582lrtQoSIngressPortTagClassificationEntry OBJECT-TYPE
               SYNTAX          SISPM1040582LRTQoSIngressPortTagClassificationEntry
               MAX-ACCESS  not-accessible
               STATUS      current
               DESCRIPTION
                   "QoS Ingress Port Tag Classification entry."
               INDEX    {     ifIndex,
                              sispm1040582lrtQoSIngressPortTagPCP,
                              sispm1040582lrtQoSIngressPortTagDEI  }
               ::= {     sispm1040582lrtQoSIngressPortTagClassificationTable 1 }

    SISPM1040582LRTQoSIngressPortTagClassificationEntry             ::= SEQUENCE {
                sispm1040582lrtQoSIngressPortTagPCP                   INTEGER,
                sispm1040582lrtQoSIngressPortTagDEI                   INTEGER,
                sispm1040582lrtQoSIngressPortTagQosClass              Integer32,
                sispm1040582lrtQoSIngressPortTagDPLevel               Integer32
                }

    sispm1040582lrtQoSIngressPortTagPCP OBJECT-TYPE
               SYNTAX      INTEGER { pcp0(1),
                                     pcp1(2),
                                     pcp2(3),
                                     pcp3(4),
                                     pcp4(5),
                                     pcp5(6),
                                     pcp6(7),
                                     pcp7(8) }
               MAX-ACCESS  not-accessible
               STATUS      current
               DESCRIPTION
                   "range: 1-8,
                    PCP0:1, PCP1:2..."
               ::= {     sispm1040582lrtQoSIngressPortTagClassificationEntry 2 }

    sispm1040582lrtQoSIngressPortTagDEI OBJECT-TYPE
               SYNTAX      INTEGER { dei0(1), dei1(2) }
               MAX-ACCESS  not-accessible
               STATUS      current
               DESCRIPTION
                   "Ingress Port Tag dei,
                    DEI0:1, DEI1:2."
               ::= {     sispm1040582lrtQoSIngressPortTagClassificationEntry 3 }

    sispm1040582lrtQoSIngressPortTagQosClass OBJECT-TYPE
               SYNTAX      Integer32(0..7)
               MAX-ACCESS  read-write
               STATUS      current
               DESCRIPTION
                   "range: 0-7."
               ::= {     sispm1040582lrtQoSIngressPortTagClassificationEntry 4 }

    sispm1040582lrtQoSIngressPortTagDPLevel OBJECT-TYPE
               SYNTAX      Integer32(0|1)
               MAX-ACCESS  read-write
               STATUS      current
               DESCRIPTION
                   "range: 0-1."
               ::= {     sispm1040582lrtQoSIngressPortTagClassificationEntry 5 }


--
-- =======================================================================================================================
-- Start sispm1040582lrtQosPortPolicing group
-- =======================================================================================================================
--sispm1040582lrtQosPortPolicingTable
   sispm1040582lrtQosPortPolicingTable OBJECT-TYPE
               SYNTAX      SEQUENCE OF     SISPM1040582LRTQosPortPolicingEntry
               MAX-ACCESS  not-accessible
               STATUS      current
               DESCRIPTION
                   "The Policer settings.
                    INDEX for this table is ifIndex which is
                    equivalent to the panel port number."
               ::= {     sispm1040582lrtQosPortPolicing 1 }

    sispm1040582lrtQosPortPolicingEntry OBJECT-TYPE
               SYNTAX          SISPM1040582LRTQosPortPolicingEntry
               MAX-ACCESS  not-accessible
               STATUS      current
               DESCRIPTION
                   "The Policer setting entry."
               INDEX    {     ifIndex  }
               ::= {     sispm1040582lrtQosPortPolicingTable 1 }

    SISPM1040582LRTQosPortPolicingEntry             ::= SEQUENCE {
                sispm1040582lrtQosPortPolicingEnabled         AdminMode,
                sispm1040582lrtQosPortPolicingRate            Integer32,
                sispm1040582lrtQosPortPolicingUnit            Integer32,
                sispm1040582lrtQosPortPolicingFlowControl     AdminMode
                }

    sispm1040582lrtQosPortPolicingEnabled OBJECT-TYPE
               SYNTAX      AdminMode
               MAX-ACCESS  read-write
               STATUS      current
               DESCRIPTION
                  "Controls whether the policer is enabled on this switch port."
               DEFVAL  { disable }
               ::= {     sispm1040582lrtQosPortPolicingEntry 2 }

    sispm1040582lrtQosPortPolicingRate OBJECT-TYPE
               SYNTAX      Integer32
               MAX-ACCESS  read-write
               STATUS      current
               DESCRIPTION
                   "Controls the rate for the policer.
                    default: 500(kbps)."
               ::= {     sispm1040582lrtQosPortPolicingEntry 3 }

    sispm1040582lrtQosPortPolicingUnit OBJECT-TYPE
               SYNTAX      Integer32
               MAX-ACCESS  read-write
               STATUS      current
               DESCRIPTION
                   "Controls the unit of measure for the policer rate.
                    0: kbps
                    1: Mbps
		    2: fps
		    3: kfps
		    "
               ::= {     sispm1040582lrtQosPortPolicingEntry 4 }

    sispm1040582lrtQosPortPolicingFlowControl OBJECT-TYPE
               SYNTAX      AdminMode
               MAX-ACCESS  read-write
               STATUS      current
               DESCRIPTION
                   "If flow control is enabled and the port is in flow control mode,
                    then pause frames are sent instead of discarding frames."
               DEFVAL  { disable }
               ::= {     sispm1040582lrtQosPortPolicingEntry 5 }

--
-- =======================================================================================================================
-- Start sispm1040582lrtQosQueuePolicing group
-- =======================================================================================================================
--sispm1040582lrtQosQueuePolicingTable
    sispm1040582lrtQosQueuePolicingTable OBJECT-TYPE
               SYNTAX      SEQUENCE OF     SISPM1040582LRTQosQueuePolicingEntry
               MAX-ACCESS  not-accessible
               STATUS      current
               DESCRIPTION
                   "The Queue Policer settings.
                    INDEX for this table is ifIndex which is
                    equivalent to the panel port number."
               ::= {     sispm1040582lrtQosQueuePolicing 1 }

    sispm1040582lrtQosQueuePolicingEntry OBJECT-TYPE
               SYNTAX          SISPM1040582LRTQosQueuePolicingEntry
               MAX-ACCESS  not-accessible
               STATUS      current
               DESCRIPTION
                   "The Qos Queue Policing Entry."
               INDEX    {     ifIndex  }
               ::= {     sispm1040582lrtQosQueuePolicingTable 1 }

    SISPM1040582LRTQosQueuePolicingEntry             ::= SEQUENCE {
                sispm1040582lrtQosQueuePolicingQueue0Enable   AdminMode,
                sispm1040582lrtQosQueuePolicingQueue0Rate     Integer32,
		sispm1040582lrtQosQueuePolicingQueue0Unit     Integer32,
                sispm1040582lrtQosQueuePolicingQueue1Enable   AdminMode,
                sispm1040582lrtQosQueuePolicingQueue1Rate     Integer32,
		sispm1040582lrtQosQueuePolicingQueue1Unit     Integer32,
                sispm1040582lrtQosQueuePolicingQueue2Enable   AdminMode,
                sispm1040582lrtQosQueuePolicingQueue2Rate     Integer32,
                sispm1040582lrtQosQueuePolicingQueue2Unit     Integer32,
                sispm1040582lrtQosQueuePolicingQueue3Enable   AdminMode,
                sispm1040582lrtQosQueuePolicingQueue3Rate     Integer32,
                sispm1040582lrtQosQueuePolicingQueue3Unit     Integer32,
                sispm1040582lrtQosQueuePolicingQueue4Enable   AdminMode,
                sispm1040582lrtQosQueuePolicingQueue4Rate     Integer32,
		sispm1040582lrtQosQueuePolicingQueue4Unit     Integer32,
                sispm1040582lrtQosQueuePolicingQueue5Enable   AdminMode,
                sispm1040582lrtQosQueuePolicingQueue5Rate     Integer32,
		sispm1040582lrtQosQueuePolicingQueue5Unit     Integer32,
                sispm1040582lrtQosQueuePolicingQueue6Enable   AdminMode,
                sispm1040582lrtQosQueuePolicingQueue6Rate     Integer32,
		sispm1040582lrtQosQueuePolicingQueue6Unit     Integer32,
                sispm1040582lrtQosQueuePolicingQueue7Enable   AdminMode,
                sispm1040582lrtQosQueuePolicingQueue7Rate     Integer32,
		sispm1040582lrtQosQueuePolicingQueue7Unit     Integer32
                }

    sispm1040582lrtQosQueuePolicingQueue0Enable OBJECT-TYPE
               SYNTAX      AdminMode
               MAX-ACCESS  read-write
               STATUS      current
               DESCRIPTION
                   "Controls whether the queue 0 policer is enabled on this switch port."
               DEFVAL  { disable }
               ::= {     sispm1040582lrtQosQueuePolicingEntry 3 }

    sispm1040582lrtQosQueuePolicingQueue0Rate OBJECT-TYPE
               SYNTAX      Integer32
               MAX-ACCESS  read-write
               STATUS      current
               DESCRIPTION
                   "Controls whether the queue 0 policer is enabled on this switch port.
                    default: 500(Kbps)"
               ::= {     sispm1040582lrtQosQueuePolicingEntry 4 }

    sispm1040582lrtQosQueuePolicingQueue0Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 5 }			   
			   
    sispm1040582lrtQosQueuePolicingQueue1Enable OBJECT-TYPE
               SYNTAX      AdminMode
               MAX-ACCESS  read-write
               STATUS      current
               DESCRIPTION
                   "Controls whether the queue 1 policer is enabled on this switch port."
               DEFVAL  { disable }
               ::= {     sispm1040582lrtQosQueuePolicingEntry 6 }

    sispm1040582lrtQosQueuePolicingQueue1Rate OBJECT-TYPE
               SYNTAX      Integer32
               MAX-ACCESS  read-write
               STATUS      current
               DESCRIPTION
                   "Controls whether the queue 1 policer is enabled on this switch port.,
                    default: 500(Kbps)"
               ::= {     sispm1040582lrtQosQueuePolicingEntry 7 }
			   
    sispm1040582lrtQosQueuePolicingQueue1Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 8 }			   
			   
    sispm1040582lrtQosQueuePolicingQueue2Enable OBJECT-TYPE
               SYNTAX      AdminMode
               MAX-ACCESS  read-write
               STATUS      current
               DESCRIPTION
                   "Controls whether the queue 2 policer is enabled on this switch port."
               DEFVAL  { disable }
               ::= {     sispm1040582lrtQosQueuePolicingEntry 9 }

    sispm1040582lrtQosQueuePolicingQueue2Rate OBJECT-TYPE
               SYNTAX      Integer32
               MAX-ACCESS  read-write
               STATUS      current
               DESCRIPTION
                   "Controls whether the queue 2 policer is enabled on this switch port.
                    default: 500(Kbps)"
               ::= {     sispm1040582lrtQosQueuePolicingEntry 10 }
			   
    sispm1040582lrtQosQueuePolicingQueue2Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 11 }			   
			  
    sispm1040582lrtQosQueuePolicingQueue3Enable OBJECT-TYPE
               SYNTAX      AdminMode
               MAX-ACCESS  read-write
               STATUS      current
               DESCRIPTION
                   "Controls whether the queue 3 policer is enabled on this switch port."
               DEFVAL  { disable }
               ::= {     sispm1040582lrtQosQueuePolicingEntry 12 }

    sispm1040582lrtQosQueuePolicingQueue3Rate OBJECT-TYPE
               SYNTAX      Integer32
               MAX-ACCESS  read-write
               STATUS      current
               DESCRIPTION
                   "Controls whether the queue 3 policer is enabled on this switch port.
                    default: 500(Kbps)"
               ::= {     sispm1040582lrtQosQueuePolicingEntry 13 }
			   
    sispm1040582lrtQosQueuePolicingQueue3Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 14 }			   
			   
    sispm1040582lrtQosQueuePolicingQueue4Enable OBJECT-TYPE
               SYNTAX      AdminMode
               MAX-ACCESS  read-write
               STATUS      current
               DESCRIPTION
                   "Controls whether the queue 4 policer is enabled on this switch port."
               DEFVAL  { disable }
               ::= {     sispm1040582lrtQosQueuePolicingEntry 15 }

    sispm1040582lrtQosQueuePolicingQueue4Rate OBJECT-TYPE
               SYNTAX      Integer32
               MAX-ACCESS  read-write
               STATUS      current
               DESCRIPTION
                   "Controls whether the queue 4 policer is enabled on this switch port.
                    default: 500(Kbps)"
               ::= {     sispm1040582lrtQosQueuePolicingEntry 16 }
			   
    sispm1040582lrtQosQueuePolicingQueue4Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 17 }			   
			   
    sispm1040582lrtQosQueuePolicingQueue5Enable OBJECT-TYPE
               SYNTAX      AdminMode
               MAX-ACCESS  read-write
               STATUS      current
               DESCRIPTION
                   "Controls whether the queue 5 policer is enabled on this switch port."
               DEFVAL  { disable }
               ::= {     sispm1040582lrtQosQueuePolicingEntry 18 }

    sispm1040582lrtQosQueuePolicingQueue5Rate OBJECT-TYPE
               SYNTAX      Integer32
               MAX-ACCESS  read-write
               STATUS      current
               DESCRIPTION
                   "Controls whether the queue 5 policer is enabled on this switch port.
                    default: 500(Kbps)"
               ::= {     sispm1040582lrtQosQueuePolicingEntry 19 }

    sispm1040582lrtQosQueuePolicingQueue5Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 20 }			   
			   			   
    sispm1040582lrtQosQueuePolicingQueue6Enable OBJECT-TYPE
               SYNTAX      AdminMode
               MAX-ACCESS  read-write
               STATUS      current
               DESCRIPTION
                   "Controls whether the queue 6 policer is enabled on this switch port."
               DEFVAL  { disable }
               ::= {     sispm1040582lrtQosQueuePolicingEntry 21 }

    sispm1040582lrtQosQueuePolicingQueue6Rate OBJECT-TYPE
               SYNTAX      Integer32
               MAX-ACCESS  read-write
               STATUS      current
               DESCRIPTION
                   "Controls whether the queue 6 policer is enabled on this switch port.
                    default: 500(Kbps)"
               ::= {     sispm1040582lrtQosQueuePolicingEntry 22 }
			   
    sispm1040582lrtQosQueuePolicingQueue6Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 23 }			   
			   
    sispm1040582lrtQosQueuePolicingQueue7Enable OBJECT-TYPE
               SYNTAX      AdminMode
               MAX-ACCESS  read-write
               STATUS      current
               DESCRIPTION
                   "Controls whether the queue 7 policer is enabled on this switch port."
               DEFVAL  { disable }
               ::= {     sispm1040582lrtQosQueuePolicingEntry 24 }

    sispm1040582lrtQosQueuePolicingQueue7Rate OBJECT-TYPE
               SYNTAX      Integer32
               MAX-ACCESS  read-write
               STATUS      current
               DESCRIPTION
                   "Controls whether the queue 7 policer is enabled on this switch port.
                    default: 500(Kbps)"
               ::= {     sispm1040582lrtQosQueuePolicingEntry 25 }

    sispm1040582lrtQosQueuePolicingQueue7Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sispm1040582lrtQosQueuePolicingEntry 26 }			   

--
-- =======================================================================================================================
-- Start sispm1040582lrtQosPortScheduler group
-- =======================================================================================================================
--sispm1040582lrtQosPortSchedulerModeTable

     sispm1040582lrtQosPortSchedulerModeTable OBJECT-TYPE
               SYNTAX      SEQUENCE OF     SISPM1040582LRTQosPortSchedulerModeEntry
               MAX-ACCESS  not-accessible
               STATUS      current
               DESCRIPTION
                   "The basic QoS Port Scheduler Mode settings.
                    INDEX for this table is ifIndex which is
                    equivalent to the panel port number."
               ::= {     sispm1040582lrtQosPortScheduler  1 }

    sispm1040582lrtQosPortSchedulerModeEntry OBJECT-TYPE
               SYNTAX          SISPM1040582LRTQosPortSchedulerModeEntry
               MAX-ACCESS  not-accessible
               STATUS      current
               DESCRIPTION
                   "The Qos Port Scheduler Mode entry."
               INDEX    {     ifIndex  }
               ::= {     sispm1040582lrtQosPortSchedulerModeTable 1 }

    SISPM1040582LRTQosPortSchedulerModeEntry             ::= SEQUENCE {
                sispm1040582lrtQosSchedulerMode            Integer32,
                sispm1040582lrtQosSchedulerShaper          AdminMode,
                sispm1040582lrtQosSchedulerShaperRate      Integer32
                }

    sispm1040582lrtQosSchedulerMode OBJECT-TYPE
               SYNTAX      Integer32
               MAX-ACCESS  read-write
               STATUS      current
               DESCRIPTION
                   "Controls whether the scheduler mode is Strict Priority or Weighted
                    on this switch port.
                    0:Strict Priority,
		    2: 2 Queues Weighted
		    3: 3 Queues Weighted: only Jaguar2 support
		    4: 4 Queues Weighted: only Jaguar2 support
		    5: 5 Queues Weighted: only Jaguar2 support
                    6: 6 Queues Weighted
		    7: 7 Queues Weighted: only Jaguar2 support
		    8: 8 Queues Weighted: only Jaguar2 support"
               ::= {     sispm1040582lrtQosPortSchedulerModeEntry 2 }

    sispm1040582lrtQosSchedulerShaper OBJECT-TYPE
               SYNTAX      AdminMode
               MAX-ACCESS  read-write
               STATUS      current
               DESCRIPTION
                   "Controls whether the port shaper is enabled."
               DEFVAL  { disable }
               ::= {     sispm1040582lrtQosPortSchedulerModeEntry 3 }

    sispm1040582lrtQosSchedulerShaperRate OBJECT-TYPE
               SYNTAX      Integer32
               MAX-ACCESS  read-write
               STATUS      current
               DESCRIPTION
                   "Controls the rate for the port shaper.
                    default: 500 kbps."
               ::= {     sispm1040582lrtQosPortSchedulerModeEntry 4 }

--sispm1040582lrtQosPortSchedulerTable
    sispm1040582lrtQosPortSchedulerTable OBJECT-TYPE
               SYNTAX      SEQUENCE OF     SISPM1040582LRTQosPortSchedulerEntry
               MAX-ACCESS  not-accessible
               STATUS      current
               DESCRIPTION
                   "Show Qos Port Scheduler.
                    INDEX for this table is ifIndex which is
                    equivalent to the panel port number."
               ::= {     sispm1040582lrtQosPortScheduler 2 }

    sispm1040582lrtQosPortSchedulerEntry OBJECT-TYPE
               SYNTAX          SISPM1040582LRTQosPortSchedulerEntry
               MAX-ACCESS  not-accessible
               STATUS      current
               DESCRIPTION
                   "The Qos Port Scheduler Entry."
               INDEX    {     ifIndex,
                              sispm1040582lrtQosSchedulerPortQueue}
               ::= {     sispm1040582lrtQosPortSchedulerTable 1 }

    SISPM1040582LRTQosPortSchedulerEntry             ::= SEQUENCE {
                sispm1040582lrtQosSchedulerPortQueue                  INTEGER,
                sispm1040582lrtQosSchedulerPortQueueShaper            AdminMode,
                sispm1040582lrtQosSchedulerPortQueueShaperRate        Integer32,
                sispm1040582lrtQosSchedulerPortQueueShaperExcess      AdminMode,
                sispm1040582lrtQosSchedulerPortQueueSchedulerWeight   Integer32,
                sispm1040582lrtQosSchedulerPortQueueSchedulerPercent  DisplayString
                }

    sispm1040582lrtQosSchedulerPortQueue OBJECT-TYPE
               SYNTAX      INTEGER { q0(1),
                                     q1(2),
                                     q2(3),
                                     q3(4),
                                     q4(5),
                                     q5(6),
                                     q6(7),
                                     q7(8) }
               MAX-ACCESS  not-accessible
               STATUS      current
               DESCRIPTION
                   "range: 1-8.
                    Q0: 1, Q1: 2, ..."
               ::= {     sispm1040582lrtQosPortSchedulerEntry 2 }

    sispm1040582lrtQosSchedulerPortQueueShaper OBJECT-TYPE
               SYNTAX     AdminMode
               MAX-ACCESS  read-write
               STATUS      current
               DESCRIPTION
                   "Qos scheduler admin state."
               DEFVAL  { disable }
               ::= {     sispm1040582lrtQosPortSchedulerEntry 3 }

    sispm1040582lrtQosSchedulerPortQueueShaperRate OBJECT-TYPE
               SYNTAX      Integer32(100..1000000)
               MAX-ACCESS  read-write
               STATUS      current
               DESCRIPTION
                   "range: 100..1000000 kbps. "
               ::= {     sispm1040582lrtQosPortSchedulerEntry 4 }

    sispm1040582lrtQosSchedulerPortQueueShaperExcess OBJECT-TYPE
               SYNTAX      AdminMode
               MAX-ACCESS  read-write
               STATUS      current
               DESCRIPTION
                   "admin state sispm1040582lrtQosSchedulerPortQueueShaperExcess"
               DEFVAL  { disable }
               ::= {     sispm1040582lrtQosPortSchedulerEntry 5 }

    sispm1040582lrtQosSchedulerPortQueueSchedulerWeight OBJECT-TYPE
               SYNTAX      Integer32(0..100)
               MAX-ACCESS  read-write
               STATUS      current
               DESCRIPTION
                   "range: 1-100,
                    default: 17.
                    Only use in Q0 - Q5.  Q6 & Q7 show 0"
               ::= {     sispm1040582lrtQosPortSchedulerEntry 6 }

    sispm1040582lrtQosSchedulerPortQueueSchedulerPercent OBJECT-TYPE
               SYNTAX      DisplayString
               MAX-ACCESS  read-only
               STATUS      current
               DESCRIPTION
                   "Only use in Q0 - Q5. Q6 & Q7 show empty"
               ::= {     sispm1040582lrtQosPortSchedulerEntry 7 }
--
-- =======================================================================================================================
-- Start sispm1040582lrtQosPortEgressTagRemarking group
-- =======================================================================================================================
--sispm1040582lrtQosPortEgressTagRemarkingTable
    sispm1040582lrtQosPortEgressTagRemarkingTable OBJECT-TYPE
               SYNTAX      SEQUENCE OF     SISPM1040582LRTQosPortEgressTagRemarkingEntry
               MAX-ACCESS  not-accessible
               STATUS      current
               DESCRIPTION
                   "The basic QoS Port Egress Tag Remark
                    Configuration settings.
                    INDEX for this table is ifIndex which is
                    equivalent to the panel port number."
               ::= {     sispm1040582lrtQosPortEgressTagRemarking  1 }

    sispm1040582lrtQosPortEgressTagRemarkingEntry OBJECT-TYPE
               SYNTAX          SISPM1040582LRTQosPortEgressTagRemarkingEntry
               MAX-ACCESS  not-accessible
               STATUS      current
               DESCRIPTION
                   "The Qos Port Egress Tag Remarking Entry."
               INDEX    {     ifIndex  }
               ::= {     sispm1040582lrtQosPortEgressTagRemarkingTable 1 }

    SISPM1040582LRTQosPortEgressTagRemarkingEntry             ::= SEQUENCE {
                sispm1040582lrtQosEgressTagRemarkingMode                    INTEGER
                }

    sispm1040582lrtQosEgressTagRemarkingMode OBJECT-TYPE
               SYNTAX      INTEGER { classified(0), default(1), mapped(2) }
               MAX-ACCESS  read-write
               STATUS      current
               DESCRIPTION
                   "the tag remarking mode for this port.
                    0:Classified, Use classified PCP/DEI values.
                    1:Default, Use default PCP/DEI values.
                    2:Mapped, Use mapped versions of QoS class and DP level."
               ::= {     sispm1040582lrtQosPortEgressTagRemarkingEntry 2 }

--sispm1040582lrtQosPortEgressTagRemarkingDefTable
    sispm1040582lrtQosPortEgressTagRemarkingDefTable OBJECT-TYPE
               SYNTAX      SEQUENCE OF     SISPM1040582LRTQosPortEgressTagRemarkingDefEntry
               MAX-ACCESS  not-accessible
               STATUS      current
               DESCRIPTION
                   "The basic QoS Port Egress Tag Remark
                    Configuration settings.
                    INDEX for this table is ifIndex which is
                    equivalent to the panel port number."
               ::= {     sispm1040582lrtQosPortEgressTagRemarking  2 }

    sispm1040582lrtQosPortEgressTagRemarkingDefEntry OBJECT-TYPE
               SYNTAX          SISPM1040582LRTQosPortEgressTagRemarkingDefEntry
               MAX-ACCESS  not-accessible
               STATUS      current
               DESCRIPTION
                   "The oQos Port Egress Tag Remarking Default Entry."
               INDEX    {     ifIndex  }
               ::= {     sispm1040582lrtQosPortEgressTagRemarkingDefTable 1 }

    SISPM1040582LRTQosPortEgressTagRemarkingDefEntry             ::= SEQUENCE {
                sispm1040582lrtQosEgressTagRemarkingDefPCP                Integer32,
                sispm1040582lrtQosEgressTagRemarkingDefDEI                AdminMode
                }

    sispm1040582lrtQosEgressTagRemarkingDefPCP OBJECT-TYPE
               SYNTAX      Integer32(0..7)
               MAX-ACCESS  read-write
               STATUS      current
               DESCRIPTION
                   "Controls the default PCP
                    Range : 0-7"
               ::= {     sispm1040582lrtQosPortEgressTagRemarkingDefEntry 2 }

    sispm1040582lrtQosEgressTagRemarkingDefDEI OBJECT-TYPE
               SYNTAX      AdminMode
               MAX-ACCESS  read-write
               STATUS      current
               DESCRIPTION
                   "controls the admin state of DEI"
               ::= {     sispm1040582lrtQosPortEgressTagRemarkingDefEntry 3 }

--sispm1040582lrtQosPortEgressTagRemarkingMapDPTable
--    sispm1040582lrtQosPortEgressTagRemarkingMapDPTable OBJECT-TYPE
--               SYNTAX      SEQUENCE OF     SISPM1040582LRTQosPortEgressTagRemarkingMapDPEntry
--               MAX-ACCESS  not-accessible
--               STATUS      current
--               DESCRIPTION
--                   "Show Qos Port Egress Tag Remarking Map DP.
--                    INDEX for this table is ifIndex which is
--                    equivalent to the panel port number."
--               ::= {     sispm1040582lrtQosPortEgressTagRemarking 3 }

--    sispm1040582lrtQosPortEgressTagRemarkingMapDPEntry OBJECT-TYPE
--               SYNTAX          SISPM1040582LRTQosPortEgressTagRemarkingMapDPEntry
--               MAX-ACCESS  not-accessible
--               STATUS      current
--               DESCRIPTION
--                   "The Qos Port Egress Tag Remarking Map DP Entry."
--               INDEX    {     ifIndex,
--                              sispm1040582lrtQosPortEgressTagRemarkingClassifiedDPLevel}
--               ::= {     sispm1040582lrtQosPortEgressTagRemarkingMapDPTable 1 }

--    SISPM1040582LRTQosPortEgressTagRemarkingMapDPEntry             ::= SEQUENCE {
--                sispm1040582lrtQosPortEgressTagRemarkingClassifiedDPLevel      Integer32,
--                sispm1040582lrtQosPortEgressTagRemarkingDPLevel                AdminMode
--                }

--    sispm1040582lrtQosPortEgressTagRemarkingClassifiedDPLevel OBJECT-TYPE
--               SYNTAX      Integer32(1..4)
--               MAX-ACCESS  not-accessible
--               STATUS      current
--               DESCRIPTION
--                   "range: 1-4."
--               ::= {     sispm1040582lrtQosPortEgressTagRemarkingMapDPEntry 2 }

--    sispm1040582lrtQosPortEgressTagRemarkingDPLevel OBJECT-TYPE
--               SYNTAX      AdminMode
--               MAX-ACCESS  read-write
--               STATUS      current
--               DESCRIPTION
--                   "admin state of Tag remark"
--               ::= {     sispm1040582lrtQosPortEgressTagRemarkingMapDPEntry 3 }

--sispm1040582lrtQosPortEgressTagRemarkingMapTable
    sispm1040582lrtQosPortEgressTagRemarkingMapTable OBJECT-TYPE
               SYNTAX      SEQUENCE OF     SISPM1040582LRTQosPortEgressTagRemarkingMapEntry
               MAX-ACCESS  not-accessible
               STATUS      current
               DESCRIPTION
                   "Show Qos Port Egress Tag Remarking Map.
                    INDEX for this table is ifIndex which is
                    equivalent to the panel port number."
               ::= {     sispm1040582lrtQosPortEgressTagRemarking 4 }

    sispm1040582lrtQosPortEgressTagRemarkingMapEntry OBJECT-TYPE
               SYNTAX          SISPM1040582LRTQosPortEgressTagRemarkingMapEntry
               MAX-ACCESS  not-accessible
               STATUS      current
               DESCRIPTION
                   "The Qos Port Egress Tag Remarking Map Entry."
               INDEX    {     ifIndex,
                              sispm1040582lrtQosTagRemarkingQoSClass,
                              sispm1040582lrtQosTagRemarkingDPLevel  }
               ::= {     sispm1040582lrtQosPortEgressTagRemarkingMapTable 1 }

    SISPM1040582LRTQosPortEgressTagRemarkingMapEntry             ::= SEQUENCE {
                sispm1040582lrtQosTagRemarkingQoSClass               INTEGER,
                sispm1040582lrtQosTagRemarkingDPLevel                INTEGER,
                sispm1040582lrtQosTagRemarkingPCP                    Integer32,
                sispm1040582lrtQosTagRemarkingDEI                    Integer32
                }

    sispm1040582lrtQosTagRemarkingQoSClass OBJECT-TYPE
               SYNTAX      INTEGER {
                        class0(1),
                        class1(2),
                        class2(3),
                        class3(4),
                        class4(5),
                        class5(6),
                        class6(7),
                        class7(8)
                        }
               MAX-ACCESS  not-accessible
               STATUS      current
               DESCRIPTION
                   "range: 1-8,
                    QoS Class0: 1, QoS Class1: 2..."
               ::= {     sispm1040582lrtQosPortEgressTagRemarkingMapEntry 2 }

    sispm1040582lrtQosTagRemarkingDPLevel OBJECT-TYPE
               SYNTAX      INTEGER { level0(1), level1(2) }
               MAX-ACCESS  not-accessible
               STATUS      current
               DESCRIPTION
                   "range: 1-2,
                    DP Level0: 1, DP Level1: 2."
               ::= {     sispm1040582lrtQosPortEgressTagRemarkingMapEntry 3 }

    sispm1040582lrtQosTagRemarkingPCP OBJECT-TYPE
               SYNTAX      Integer32(0..7)
               MAX-ACCESS  read-write
               STATUS      current
               DESCRIPTION
                   "range: 0-7."
               ::= {     sispm1040582lrtQosPortEgressTagRemarkingMapEntry 4 }

    sispm1040582lrtQosTagRemarkingDEI OBJECT-TYPE
               SYNTAX      Integer32 (0|1)
               MAX-ACCESS  read-write
               STATUS      current
               DESCRIPTION
                   "range: 0-1."
               ::= {     sispm1040582lrtQosPortEgressTagRemarkingMapEntry 5 }

--
-- =======================================================================================================================
-- Start sispm1040582lrtQosPortDSCP group
-- =======================================================================================================================
--sispm1040582lrtQosPortDSCPTable
    sispm1040582lrtQosPortDSCPTable OBJECT-TYPE
               SYNTAX      SEQUENCE OF     SISPM1040582LRTQosPortDSCPEntry
               MAX-ACCESS  not-accessible
               STATUS      current
               DESCRIPTION
                   "The basic QoS Port DSCP Configuration settings.
                    INDEX for this table is ifIndex which is
                    equivalent to the panel port number."
               ::= {     sispm1040582lrtQosPortDSCP 1 }

    sispm1040582lrtQosPortDSCPEntry OBJECT-TYPE
               SYNTAX          SISPM1040582LRTQosPortDSCPEntry
               MAX-ACCESS  not-accessible
               STATUS      current
               DESCRIPTION
                   "The Qos Port DSCP Entry."
               INDEX    {     ifIndex  }
               ::= {     sispm1040582lrtQosPortDSCPTable 1 }

    SISPM1040582LRTQosPortDSCPEntry             ::= SEQUENCE {
                sispm1040582lrtQosPortDSCPIngressTranslate        AdminMode,
                sispm1040582lrtQosPortDSCPIngressClassify         INTEGER,
                sispm1040582lrtQosPortDSCPEgressRewrite           INTEGER
                }

    sispm1040582lrtQosPortDSCPIngressTranslate OBJECT-TYPE
               SYNTAX      AdminMode
               MAX-ACCESS  read-write
               STATUS      current
               DESCRIPTION
                  "Configure DSCP ingress translation mode."
               DEFVAL  { disable }
               ::= {     sispm1040582lrtQosPortDSCPEntry 2 }

    sispm1040582lrtQosPortDSCPIngressClassify OBJECT-TYPE
               SYNTAX      INTEGER { disable (0), dscp (1), selected (2), all(3) }
               MAX-ACCESS  read-write
               STATUS      current
               DESCRIPTION
                   "Classification for a port have 4 different values.
                    0: disable,
                    1: DSCP=0,
                    2: Selected,
                    3: All."
               DEFVAL  { disable }
               ::= {     sispm1040582lrtQosPortDSCPEntry 3 }

    sispm1040582lrtQosPortDSCPEgressRewrite OBJECT-TYPE
               SYNTAX      INTEGER { disable (0),enable (1),
                                     remapDPUnaware (2), remapDPaware (3) }
               MAX-ACCESS  read-write
               STATUS      current
               DESCRIPTION
                   "Configure the port egress rewriting mode.
                    LUTON26:{0: Disable,1: Enable,2: Remap DP Unaware,
                    3: Remap DP Aware,range: 0-3}
                    Others:{0: Disable,1: Enable,2: Remap,range: 0-2}"
               ::= {     sispm1040582lrtQosPortDSCPEntry 4 }

--
-- =======================================================================================================================
-- Start sispm1040582lrtQosDSCP group
-- =======================================================================================================================
    sispm1040582lrtQosDSCPTable OBJECT-TYPE
               SYNTAX      SEQUENCE OF     SISPM1040582LRTQosDSCPEntry
               MAX-ACCESS  not-accessible
               STATUS      current
               DESCRIPTION
                   "configure the basic QoS DSCP based QoS Ingress
                    Classification settings for all switches."
               ::= {     sispm1040582lrtQosDSCP 1 }

    sispm1040582lrtQosDSCPEntry OBJECT-TYPE
               SYNTAX          SISPM1040582LRTQosDSCPEntry
               MAX-ACCESS  not-accessible
               STATUS      current
               DESCRIPTION
                   "The Qos DSCP Entry."
               INDEX    {     sispm1040582lrtQosDSCPList  }
               ::= {     sispm1040582lrtQosDSCPTable 1 }

    SISPM1040582LRTQosDSCPEntry             ::= SEQUENCE {
                sispm1040582lrtQosDSCPList       Integer32,
                sispm1040582lrtQosBasedDSCP      DisplayString,
                sispm1040582lrtQosDSCPTrust      AdminMode,
                sispm1040582lrtQosDSCPQosClass   Integer32,
                sispm1040582lrtQosDSCPDPL        Integer32
                }

    sispm1040582lrtQosDSCPList OBJECT-TYPE
               SYNTAX      Integer32(1..64)
               MAX-ACCESS  not-accessible
               STATUS      current
               DESCRIPTION
                  "DSCP mapping table index(1-64)."
               ::= {     sispm1040582lrtQosDSCPEntry 1 }

    sispm1040582lrtQosBasedDSCP OBJECT-TYPE
               SYNTAX      DisplayString
               MAX-ACCESS  read-only
               STATUS      current
               DESCRIPTION
                  "Maximum number of supported DSCP values are 64."
               ::= {     sispm1040582lrtQosDSCPEntry 2 }

    sispm1040582lrtQosDSCPTrust OBJECT-TYPE
               SYNTAX      AdminMode
               MAX-ACCESS  read-write
               STATUS      current
               DESCRIPTION
                  "Controls whether a specific DSCP value is trusted. Only frames with
                   trusted DSCP values are mapped to a specific QoS class
                   and Drop Precedence
                   Level. Frames with untrusted DSCP values are
                   treated as a non-IP frame."
               DEFVAL  { disable }
              ::= {     sispm1040582lrtQosDSCPEntry 3 }

    sispm1040582lrtQosDSCPQosClass OBJECT-TYPE
               SYNTAX      Integer32(0..7)
               MAX-ACCESS  read-write
               STATUS      current
               DESCRIPTION
                  "QoS class.
                   range: 0-7,
                   default: 0."
               ::= {     sispm1040582lrtQosDSCPEntry 4 }

    sispm1040582lrtQosDSCPDPL OBJECT-TYPE
               SYNTAX      Integer32(0|1)
               MAX-ACCESS  read-write
               STATUS      current
               DESCRIPTION
                  "Drop Precedence Level.
                   range: 0-1,
                   default: 0."
               ::= {     sispm1040582lrtQosDSCPEntry 5 }

--
-- =======================================================================================================================
-- Start sispm1040582lrtQosDSCPTranslation group
-- =======================================================================================================================
--sispm1040582lrtQosDSCPTranslationTable
    sispm1040582lrtQosDSCPTranslationTable OBJECT-TYPE
               SYNTAX      SEQUENCE OF     SISPM1040582LRTQosDSCPTranslationEntry
               MAX-ACCESS  not-accessible
               STATUS      current
               DESCRIPTION
                   "The basic QoS DSCP Translation settings for all switches."
               ::= {     sispm1040582lrtQosDSCPTranslation  1 }

    sispm1040582lrtQosDSCPTranslationEntry OBJECT-TYPE
               SYNTAX          SISPM1040582LRTQosDSCPTranslationEntry
               MAX-ACCESS  not-accessible
               STATUS      current
               DESCRIPTION
                   "The Qos DSCP Translation Entry."
               INDEX    {     sispm1040582lrtQosDSCPTranslationList  }
               ::= {     sispm1040582lrtQosDSCPTranslationTable 1 }

    SISPM1040582LRTQosDSCPTranslationEntry             ::= SEQUENCE {
                sispm1040582lrtQosDSCPTranslationList                 Integer32,
                sispm1040582lrtQosDSCPTranslationDSCPBasedId          DisplayString,
                sispm1040582lrtQosDSCPTranslationIngressTranslate     Integer32,
                sispm1040582lrtQosDSCPTranslationIngressClassify      AdminMode,
                sispm1040582lrtQosDSCPTranslationEgressRemapDP0       Integer32,
                sispm1040582lrtQosDSCPTranslationEgressRemapDP1       Integer32
                }

    sispm1040582lrtQosDSCPTranslationList OBJECT-TYPE
               SYNTAX      Integer32(1..64)
               MAX-ACCESS  not-accessible
               STATUS      current
               DESCRIPTION
                  "DSCP translation table index(1-64)."
               ::= {     sispm1040582lrtQosDSCPTranslationEntry 1 }

    sispm1040582lrtQosDSCPTranslationDSCPBasedId OBJECT-TYPE
               SYNTAX      DisplayString
               MAX-ACCESS  read-only
               STATUS      current
               DESCRIPTION
                  "Configure global ingress DSCP translation table."
               ::= {     sispm1040582lrtQosDSCPTranslationEntry 2 }

    sispm1040582lrtQosDSCPTranslationIngressTranslate OBJECT-TYPE
               SYNTAX      Integer32(0..63)
               MAX-ACCESS  read-write
               STATUS      current
               DESCRIPTION
                  "DSCP at Ingress side can be translated to any of DSCP values.
                   range: 0-63,
                   default: 0."
               ::= {     sispm1040582lrtQosDSCPTranslationEntry 3 }

    sispm1040582lrtQosDSCPTranslationIngressClassify OBJECT-TYPE
               SYNTAX      AdminMode
               MAX-ACCESS  read-write
               STATUS      current
               DESCRIPTION
                  "Configure DSCP ingress classification."
               DEFVAL  { disable }
               ::= {     sispm1040582lrtQosDSCPTranslationEntry 4 }

    sispm1040582lrtQosDSCPTranslationEgressRemapDP0 OBJECT-TYPE
               SYNTAX      Integer32(0..63)
               MAX-ACCESS  read-write
               STATUS      current
               DESCRIPTION
                  "Select the DSCP value from select menu to which you want to remap.
                   range: 0-63,
                   default: 0."
               ::= {     sispm1040582lrtQosDSCPTranslationEntry 5 }

    sispm1040582lrtQosDSCPTranslationEgressRemapDP1 OBJECT-TYPE
               SYNTAX      Integer32(0..63)
               MAX-ACCESS  read-write
               STATUS      current
               DESCRIPTION
                  "Select the DSCP value from select menu to which you want to remap.
                   range: 0-63,
                   default: 0.
                   Only support LUTON26."
               ::= {     sispm1040582lrtQosDSCPTranslationEntry 6 }

--
-- =======================================================================================================================
-- Start sispm1040582lrtQosDSCPClassification group
-- =======================================================================================================================
--sispm1040582lrtQosDSCPClassificationTable
    sispm1040582lrtQosDSCPClassificationTable OBJECT-TYPE
               SYNTAX      SEQUENCE OF     SISPM1040582LRTQosDSCPClassificationEntry
               MAX-ACCESS  not-accessible
               STATUS      current
               DESCRIPTION
                   "The mapping of QoS class  to DSCP value."
               ::= {     sispm1040582lrtQosDSCPClassification 1 }

    sispm1040582lrtQosDSCPClassificationEntry OBJECT-TYPE
               SYNTAX          SISPM1040582LRTQosDSCPClassificationEntry
               MAX-ACCESS  not-accessible
               STATUS      current
               DESCRIPTION
                   "The Qos DSCP Classification Entry."
               INDEX    {     sispm1040582lrtQosDSCPClassificationQoSClass  }
               ::= {     sispm1040582lrtQosDSCPClassificationTable 1 }

    SISPM1040582LRTQosDSCPClassificationEntry             ::= SEQUENCE {
                sispm1040582lrtQosDSCPClassificationQoSClass   Integer32,
                sispm1040582lrtQosDSCPClassificationDSCPDP0    Integer32,
		sispm1040582lrtQosDSCPClassificationDSCPDP1    Integer32,
		sispm1040582lrtQosDSCPClassificationDSCPDP2    Integer32,
		sispm1040582lrtQosDSCPClassificationDSCPDP3    Integer32
                }

    sispm1040582lrtQosDSCPClassificationQoSClass OBJECT-TYPE
               SYNTAX      Integer32(1..8)
               MAX-ACCESS  not-accessible
               STATUS      current
               DESCRIPTION
                  "This page allows you to configure the mapping of QoS class
                   and Drop Precedence Level to DSCP value.
                   range: 1-8}"
               ::= {     sispm1040582lrtQosDSCPClassificationEntry 1 }

    sispm1040582lrtQosDSCPClassificationDSCPDP0 OBJECT-TYPE
               SYNTAX      Integer32(0..63)
               MAX-ACCESS  read-write
               STATUS      current
               DESCRIPTION
                  "Select the classified DSCP value.
                   range: 0-63,
                   default: 0."
               ::= {     sispm1040582lrtQosDSCPClassificationEntry 2 }

    sispm1040582lrtQosDSCPClassificationDSCPDP1 OBJECT-TYPE
               SYNTAX      Integer32(0..63)
               MAX-ACCESS  read-write
               STATUS      current
               DESCRIPTION
                  "Select the classified DSCP value.
                   range: 0-63,
                   default: 0."
               ::= {     sispm1040582lrtQosDSCPClassificationEntry 3 }

    sispm1040582lrtQosDSCPClassificationDSCPDP2 OBJECT-TYPE
               SYNTAX      Integer32(0..63)
               MAX-ACCESS  read-write
               STATUS      current
               DESCRIPTION
                  "Select the classified DSCP value.
                   range: 0-63,
                   default: 0."
               ::= {     sispm1040582lrtQosDSCPClassificationEntry 4 }

    sispm1040582lrtQosDSCPClassificationDSCPDP3 OBJECT-TYPE
               SYNTAX      Integer32(0..63)
               MAX-ACCESS  read-write
               STATUS      current
               DESCRIPTION
                  "Select the classified DSCP value.
                   range: 0-63,
                   default: 0."
               ::= {     sispm1040582lrtQosDSCPClassificationEntry 5 }
			   
--
-- =======================================================================================================================
-- Start sispm1040582lrtQosControlList group
-- =======================================================================================================================
--sispm1040582lrtQosQceTable

    sispm1040582lrtQosQceTable OBJECT-TYPE
               SYNTAX      SEQUENCE OF     SISPM1040582LRTQosQceEntry
               MAX-ACCESS  not-accessible
               STATUS      current
               DESCRIPTION
                   "Create Qos QCE entry."
               ::= {     sispm1040582lrtQosControlList 1 }

    sispm1040582lrtQosQceEntry OBJECT-TYPE
               SYNTAX          SISPM1040582LRTQosQceEntry
               MAX-ACCESS  not-accessible
               STATUS      current
               DESCRIPTION
                   "Qos Qce Entry."
               INDEX    {     sispm1040582lrtQosQceIndex  }
               ::= {     sispm1040582lrtQosQceTable 1 }

    SISPM1040582LRTQosQceEntry             ::= SEQUENCE {
                sispm1040582lrtQosQceIndex                Integer32,
                sispm1040582lrtQosQceID                   Integer32,
                sispm1040582lrtQosQceList                 Integer32,
                sispm1040582lrtQosQcePortMembersSwitch    Integer32,
                sispm1040582lrtQosQcePortMembers          DisplayString,
                sispm1040582lrtQosQceTag                  DisplayString,
                sispm1040582lrtQosQceVID                  DisplayString,
                sispm1040582lrtQosPCP                     DisplayString,
                sispm1040582lrtQosDEI                     DisplayString,
                sispm1040582lrtQosSMAC                    DisplayString,
                sispm1040582lrtQosDMACType                DisplayString,
                sispm1040582lrtQosDMACValue               DisplayString,
                sispm1040582lrtQosQceInnerTag             DisplayString,
                sispm1040582lrtQosQceInnerVID             DisplayString,
                sispm1040582lrtQosInnerPCP                DisplayString,
                sispm1040582lrtQosInnerDEI                DisplayString,
                sispm1040582lrtQosFrameType               INTEGER,
                sispm1040582lrtQosMacEtherType            DisplayString,
                sispm1040582lrtQosLLCSSAPAddr             DisplayString,
                sispm1040582lrtQosLLCDSAPAddr             DisplayString,
                sispm1040582lrtQosLLCControl              DisplayString,
                sispm1040582lrtQosSNAPPID                 DisplayString,
                sispm1040582lrtQosIpv4Protocol            DisplayString,
                sispm1040582lrtQosIpv4ProtocolValue       Integer32,
                sispm1040582lrtQosIpv4ProtocolUDPSPort    DisplayString,
                sispm1040582lrtQosIpv4ProtocolUDPDPort    DisplayString,
                sispm1040582lrtQosIpv4ProtocolTCPSPort    DisplayString,
                sispm1040582lrtQosIpv4ProtocolTCPDPort    DisplayString,
                sispm1040582lrtQosIpv4SourceIp            DisplayString,
                sispm1040582lrtQosIpv4SourceMask          DisplayString,
                sispm1040582lrtQosIpv4IPFragment          INTEGER,
                sispm1040582lrtQosIpv4DSCP                DisplayString,
                sispm1040582lrtQosIpv6Protocol            DisplayString,
                sispm1040582lrtQosIpv6ProtocolValue       Integer32,
                sispm1040582lrtQosIpv6ProtocolUDPSPort    DisplayString,
                sispm1040582lrtQosIpv6ProtocolUDPDPort    DisplayString,
                sispm1040582lrtQosIpv6ProtocolTCPSPort    DisplayString,
                sispm1040582lrtQosIpv6ProtocolTCPDPort    DisplayString,
                sispm1040582lrtQosIpv6SourceIp            DisplayString,
                sispm1040582lrtQosIpv6SourceMask          DisplayString,
                sispm1040582lrtQosIpv6DSCP                DisplayString,
                sispm1040582lrtQosActionClass             Integer32,
                sispm1040582lrtQosActionDPL               Integer32,
                sispm1040582lrtQosActionDSCP              Integer32,
                sispm1040582lrtQosActionPCP               Integer32,
                sispm1040582lrtQosActionDEI               Integer32,
                sispm1040582lrtQosActionPolicy            Integer32,
                sispm1040582lrtQosQceRowStatus            RowStatus
                }

    sispm1040582lrtQosQceIndex OBJECT-TYPE
               SYNTAX      Integer32(1..256)
               MAX-ACCESS  not-accessible
               STATUS      current
               DESCRIPTION
                   "the index to this table."
               ::= {     sispm1040582lrtQosQceEntry 1 }

    sispm1040582lrtQosQceID OBJECT-TYPE
               SYNTAX      Integer32(1..256)
               MAX-ACCESS  read-only
               STATUS      current
               DESCRIPTION
                   "If the QCE ID is specified and an entry with this QCE ID
                    already exists, the QCE will be modified. Otherwise, a
                    new QCE will be added.
                    range : 1 - 256."
               ::= {     sispm1040582lrtQosQceEntry 2 }

    sispm1040582lrtQosQceList OBJECT-TYPE
               SYNTAX      Integer32(0..256)
               MAX-ACCESS  read-create
               STATUS      current
               DESCRIPTION
                   "If the QCE List is non zero, the QCE will be placed in the list.
                    If the QCE List is zero, the QCE will be placed last in the list.
                    range : 0 - 256."
               ::= {     sispm1040582lrtQosQceEntry 3 }

    sispm1040582lrtQosQcePortMembersSwitch OBJECT-TYPE
               SYNTAX      Integer32
               MAX-ACCESS  read-create
               STATUS      current
               DESCRIPTION
                   "Switch number for port members.
                   -1:Any.
                   Only support stacking switch."
               ::= {     sispm1040582lrtQosQceEntry 4 }

    sispm1040582lrtQosQcePortMembers OBJECT-TYPE
               SYNTAX      DisplayString
               MAX-ACCESS  read-create
               STATUS      current
               DESCRIPTION
                   "Indicates the ingress port of the QCE. Possible values are:
                    All: The QCE will match all ingress port.
                    Port: The QCE will match a specific ingress port.Format: 1,3-6."
               ::= {     sispm1040582lrtQosQceEntry 5 }

    sispm1040582lrtQosQceTag OBJECT-TYPE
               SYNTAX      DisplayString
               MAX-ACCESS  read-create
               STATUS      current
               DESCRIPTION
                  "SERVAL:{'Any', 'Untag' or 'Tag' or 'cTag' or 'sTag'}.
                   Others:{'Any', 'Untag' or 'Tag'}."
               ::= {     sispm1040582lrtQosQceEntry 6 }

    sispm1040582lrtQosQceVID OBJECT-TYPE
               SYNTAX      DisplayString
               MAX-ACCESS  read-create
               STATUS      current
               DESCRIPTION
                   "Valid value of VLAN ID can be any value in
                   'Specific 1~4095' or 'range 1-4095' or 'Any'."
               ::= {     sispm1040582lrtQosQceEntry 7 }

    sispm1040582lrtQosPCP OBJECT-TYPE
               SYNTAX      DisplayString
               MAX-ACCESS  read-create
               STATUS      current
               DESCRIPTION
                   "Priority Code Point: Valid value PCP are
                    specific(0, 1, 2, 3, 4, 5, 6, 7)
                    or range(0-1, 2-3, 4-5, 6-7, 0-3, 4-7) or 'Any'."
               ::= {     sispm1040582lrtQosQceEntry 8 }

    sispm1040582lrtQosDEI OBJECT-TYPE
               SYNTAX      DisplayString
               MAX-ACCESS  read-create
               STATUS      current
               DESCRIPTION
                   "Drop Eligible Indicator: Valid value of DEI can be
                    any of values between 0, 1 or 'Any'."
               ::= {     sispm1040582lrtQosQceEntry 9 }

    sispm1040582lrtQosSMAC  OBJECT-TYPE
               SYNTAX      DisplayString
               MAX-ACCESS  read-create
               STATUS      current
               DESCRIPTION
                   "JAGUAR:{Source MAC address: 24 MS bits OUI(00-00-00
                    ~ FF-FF-FF) or 'Any'.}
                    Others:{Source MAC address:  xx-xx-xx-xx-xx-xx or
                    'Any'.}"
               ::= {     sispm1040582lrtQosQceEntry 10 }

    sispm1040582lrtQosDMACType OBJECT-TYPE
               SYNTAX      DisplayString
               MAX-ACCESS  read-create
               STATUS      current
               DESCRIPTION
                   "Destination MAC type: possible values are 'UC'(unicast),
                    'MC'(multicast), 'BC'(broadcast) or 'Any'.
                    'SP' only support SERVAL version."
               ::= {     sispm1040582lrtQosQceEntry 11 }

    sispm1040582lrtQosDMACValue OBJECT-TYPE
               SYNTAX      DisplayString
               MAX-ACCESS  read-create
               STATUS      current
               DESCRIPTION
                   "when sispm1040582lrtQosDMACType is 'SP'(specific) can set mac address.
                    Only support SERVAL version."
               ::= {     sispm1040582lrtQosQceEntry 12 }

    sispm1040582lrtQosQceInnerTag OBJECT-TYPE
               SYNTAX      DisplayString
               MAX-ACCESS  read-create
               STATUS      current
               DESCRIPTION
                   "Value of Inner Tag field can be 'Any', 'Untag' or 'Tag' or
                    'cTag' or 'sTag'.
                    Only support SERVAL version."
               ::= {     sispm1040582lrtQosQceEntry 13 }

    sispm1040582lrtQosQceInnerVID OBJECT-TYPE
               SYNTAX      DisplayString
               MAX-ACCESS  read-create
               STATUS      current
               DESCRIPTION
                   "Valid value of Inner VLAN ID can be any value in
                    'Specific 1~4095' or 'range 1-4095' or 'Any'.
                    Only support SERVAL version."
               ::= {     sispm1040582lrtQosQceEntry 14 }

    sispm1040582lrtQosInnerPCP OBJECT-TYPE
               SYNTAX      DisplayString
               MAX-ACCESS  read-create
               STATUS      current
               DESCRIPTION
                   "Valid value Inner PCP are specific(0, 1, 2, 3, 4, 5, 6, 7)
                    or range(0-1, 2-3, 4-5, 6-7, 0-3, 4-7) or 'Any'.
                    Only support SERVAL version."
               ::= {     sispm1040582lrtQosQceEntry 15 }

    sispm1040582lrtQosInnerDEI OBJECT-TYPE
               SYNTAX      DisplayString
               MAX-ACCESS  read-create
               STATUS      current
               DESCRIPTION
                   "Valid value of Inner DEI can be any of values between
                    0, 1 or 'Any'.
                    Only support SERVAL version."
               ::= {     sispm1040582lrtQosQceEntry 16 }

    sispm1040582lrtQosFrameType OBJECT-TYPE
               SYNTAX      INTEGER {
                            any(1),
                            ethernet(2),
                            llc(3),
                            snap(4),
                            ipv4(5),
                            ipv6(6)
                           }
               MAX-ACCESS  read-create
               STATUS      current
               DESCRIPTION
                   "Frame Type can have any of the following values:
                    1: Any,
                    2: Ethernet,
                    3: LLC,
                    4: SNAP,
                    5: IPv4,
                    6: IPv6."
               ::= {     sispm1040582lrtQosQceEntry 17 }

    sispm1040582lrtQosMacEtherType OBJECT-TYPE
               SYNTAX      DisplayString
               MAX-ACCESS  read-create
               STATUS      current
               DESCRIPTION
                   "Valid ethernet type can have a value within 0x600-0xFFFF or 'Any' ,
                    but excluding 0x800(IPv4) and 0x86DD(IPv6),
                    range: 0000-FFFF,
                    default: Any."
               ::= {     sispm1040582lrtQosQceEntry 18 }

    sispm1040582lrtQosLLCSSAPAddr OBJECT-TYPE
               SYNTAX      DisplayString
               MAX-ACCESS  read-create
               STATUS      current
               DESCRIPTION
                   "Valid SSAP(Source Service Access Point) can vary from
                    0x00 to 0xFF or 'Any',
                    range: 00-FF,
                    default: Any."
               ::= {     sispm1040582lrtQosQceEntry 19 }

    sispm1040582lrtQosLLCDSAPAddr OBJECT-TYPE
               SYNTAX      DisplayString
               MAX-ACCESS  read-create
               STATUS      current
               DESCRIPTION
                   "Valid DSAP(Destination Service Access Point) can
                    vary from 0x00 to 0xFF or 'Any',
                    range: 00-FF,
                    default: Any."
               ::= {     sispm1040582lrtQosQceEntry 20 }

    sispm1040582lrtQosLLCControl OBJECT-TYPE
               SYNTAX      DisplayString
               MAX-ACCESS  read-create
               STATUS      current
               DESCRIPTION
                   "Valid Control field can vary from 0x00 to 0xFF or 'Any',
                    range: 00-FF,
                    default: Any."
               ::= {     sispm1040582lrtQosQceEntry 21 }

    sispm1040582lrtQosSNAPPID OBJECT-TYPE
               SYNTAX      DisplayString
               MAX-ACCESS  read-create
               STATUS      current
               DESCRIPTION
                   "Valid PID(a.k.a ethernet type) can have value within
                    0x00-0xFFFF or 'Any',
                    range: 0000-FFFF,
                    default: Any."
               ::= {     sispm1040582lrtQosQceEntry 22 }

   sispm1040582lrtQosIpv4Protocol OBJECT-TYPE
               SYNTAX      DisplayString
               MAX-ACCESS  read-create
               STATUS      current
               DESCRIPTION
                   "IP protocol number: (Other, TCP or UDP) or 'Any'."
               ::= {     sispm1040582lrtQosQceEntry 23 }

    sispm1040582lrtQosIpv4ProtocolValue  OBJECT-TYPE
               SYNTAX      Integer32(0..255)
               MAX-ACCESS  read-create
               STATUS      current
               DESCRIPTION
                   "Ipv4 Protocol is Other.
                    range: 0-255
                    default: 0."
               ::= {     sispm1040582lrtQosQceEntry 24 }

    sispm1040582lrtQosIpv4ProtocolUDPSPort OBJECT-TYPE
               SYNTAX      DisplayString
               MAX-ACCESS  read-create
               STATUS      current
               DESCRIPTION
                   "Source  TCP/UDP Port:(0-65535) or 'Any',
                    specific or port range applicable for IP protocol UDP/TCP."
               ::= {     sispm1040582lrtQosQceEntry 25 }

    sispm1040582lrtQosIpv4ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sispm1040582lrtQosQceEntry 26 }

    sispm1040582lrtQosIpv4ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sispm1040582lrtQosQceEntry 27 }

    sispm1040582lrtQosIpv4ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sispm1040582lrtQosQceEntry 28 }

    sispm1040582lrtQosIpv4SourceIp OBJECT-TYPE
               SYNTAX      DisplayString
               MAX-ACCESS  read-create
               STATUS      current
               DESCRIPTION
                   "Specific Source IP address in value format or value 0.0.0.0 is 'Any'.
                    if Ipv4 Mask value 0.0.0.0 is 'Any' ,IP address value also is 'Any'.
                    (x.y.z.w),x=0 unless y.z.w also 0,x not is 127 or greater than 223."
               ::= {     sispm1040582lrtQosQceEntry 29 }

    sispm1040582lrtQosIpv4SourceMask OBJECT-TYPE
               SYNTAX      DisplayString
               MAX-ACCESS  read-create
               STATUS      current
               DESCRIPTION
                   "Specific Source IP address in mask format or value 0.0.0.0 is 'Any'."
               ::= {     sispm1040582lrtQosQceEntry 30 }

    sispm1040582lrtQosIpv4IPFragment OBJECT-TYPE
               SYNTAX      INTEGER { any(0), no(1), yes(2) }
               MAX-ACCESS  read-create
               STATUS      current
               DESCRIPTION
                   "IPv4 frame fragmented option:
                    2: yes,
                    1: no,
                    0: any."
               ::= {     sispm1040582lrtQosQceEntry 31 }

    sispm1040582lrtQosIpv4DSCP OBJECT-TYPE
               SYNTAX      DisplayString
               MAX-ACCESS  read-create
               STATUS      current
               DESCRIPTION
                   "Diffserv Code Point value (DSCP): It can be a specific value,
                    range of values or 'Any'. DSCP values are in the range 0-63."
               ::= {     sispm1040582lrtQosQceEntry 32 }

    sispm1040582lrtQosIpv6Protocol OBJECT-TYPE
               SYNTAX      DisplayString
               MAX-ACCESS  read-create
               STATUS      current
               DESCRIPTION
                   "IP protocol number: (Other, TCP or UDP) or 'Any'."
               ::= {     sispm1040582lrtQosQceEntry 33 }

    sispm1040582lrtQosIpv6ProtocolValue OBJECT-TYPE
               SYNTAX      Integer32(0..255)
               MAX-ACCESS  read-create
               STATUS      current
               DESCRIPTION
                   "when IPv6 protocol is Other ,
                    range: 0-255."
               ::= {     sispm1040582lrtQosQceEntry 34 }

    sispm1040582lrtQosIpv6ProtocolUDPSPort OBJECT-TYPE
               SYNTAX      DisplayString
               MAX-ACCESS  read-create
               STATUS      current
               DESCRIPTION
                   "Source TCP/UDP port:(0-65535) or 'Any',
                    specific or port range applicable for IP protocol UDP/TCP."
               ::= {     sispm1040582lrtQosQceEntry 35 }

    sispm1040582lrtQosIpv6ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sispm1040582lrtQosQceEntry 36 }

    sispm1040582lrtQosIpv6ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sispm1040582lrtQosQceEntry 37 }


    sispm1040582lrtQosIpv6ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sispm1040582lrtQosQceEntry 38 }

    sispm1040582lrtQosIpv6SourceIp OBJECT-TYPE
               SYNTAX      DisplayString
               MAX-ACCESS  read-create
               STATUS      current
               DESCRIPTION
                   "IPv6 source address: (a.b.c.d) or value 0.0.0.0 is 'Any', 32 LS bits."
               ::= {     sispm1040582lrtQosQceEntry 39 }

    sispm1040582lrtQosIpv6SourceMask OBJECT-TYPE
               SYNTAX      DisplayString
               MAX-ACCESS  read-create
               STATUS      current
               DESCRIPTION
                   "IPv6 mask address: (a.b.c.d) or value 0.0.0.0 is 'Any', 32 LS bits."
               ::= {     sispm1040582lrtQosQceEntry 40 }

    sispm1040582lrtQosIpv6DSCP OBJECT-TYPE
               SYNTAX      DisplayString
               MAX-ACCESS  read-create
               STATUS      current
               DESCRIPTION
                   "Diffserv Code Point value (DSCP): It can be a specific value,
                    range of values or 'Any'. DSCP values are in the
                    range 0-63 including BE,
                    CS1-CS7, EF or AF11-AF43."
               ::= {     sispm1040582lrtQosQceEntry 41 }

    sispm1040582lrtQosActionClass  OBJECT-TYPE
               SYNTAX      Integer32(0..8)
               MAX-ACCESS  read-create
               STATUS      current
               DESCRIPTION
                   "QoS class: (0-7) or 8: Default."
               ::= {     sispm1040582lrtQosQceEntry 42 }

    sispm1040582lrtQosActionDPL OBJECT-TYPE
               SYNTAX      Integer32 (0..4)
               MAX-ACCESS  read-create
               STATUS      current
               DESCRIPTION
                   "JAGUAR:{range:0-4. 4: Default}
                    Others:{range:0-2. 2: Default}."
               ::= {     sispm1040582lrtQosQceEntry 43 }

    sispm1040582lrtQosActionDSCP OBJECT-TYPE
               SYNTAX      Integer32(0..64)
               MAX-ACCESS  read-create
               STATUS      current
               DESCRIPTION
                   "Valid DSCP value can be (0-63, BE, CS1-CS7,
                    EF or AF11-AF43) or 64: Default."
               ::= {     sispm1040582lrtQosQceEntry 44 }

    sispm1040582lrtQosActionPCP  OBJECT-TYPE
               SYNTAX      Integer32(0..8)
               MAX-ACCESS  read-create
               STATUS      current
               DESCRIPTION
                   "pcp: (0-7) or 8: Default.
                    Only support SERVAL version."
               ::= {     sispm1040582lrtQosQceEntry 45 }

    sispm1040582lrtQosActionDEI OBJECT-TYPE
               SYNTAX      Integer32 (0..2)
               MAX-ACCESS  read-create
               STATUS      current
               DESCRIPTION
                   "dei: (0-1) or 2: Default.
                    Only support SERVAL version."
               ::= {     sispm1040582lrtQosQceEntry 46 }

    sispm1040582lrtQosActionPolicy OBJECT-TYPE
               SYNTAX      Integer32(0..64)
               MAX-ACCESS  read-create
               STATUS      current
               DESCRIPTION
                   "ACL Policy number: (0-63) or 'empty' (64 field). Default: empty.
                    Only support SERVAL version."
               ::= {     sispm1040582lrtQosQceEntry 47 }

    sispm1040582lrtQosQceRowStatus OBJECT-TYPE
               SYNTAX      RowStatus
               MAX-ACCESS  read-create
               STATUS      current
               DESCRIPTION
                   "This object indicates the status of this entry, and is used
                   to create/delete entries.  Any object in an entry of this table
                   may be modified while the value of the corresponding instance
                   of this object is active(1).
                   createAndGo, notReady not supported."
               ::= {     sispm1040582lrtQosQceEntry 48 }

--
-- =======================================================================================================================
-- Start  sispm1040582lrtQosStormControl group
-- =======================================================================================================================
--sispm1040582lrtQosStormControlTable
    sispm1040582lrtQosStormControlTable OBJECT-TYPE
               SYNTAX      SEQUENCE OF     SISPM1040582LRTQosStormControlEntry
               MAX-ACCESS  not-accessible
               STATUS      current
               DESCRIPTION
                   "The basic QoS DSCP Translation settings for all switches."
               ::= {     sispm1040582lrtQosStormControl  1 }

    sispm1040582lrtQosStormControlEntry OBJECT-TYPE
               SYNTAX          SISPM1040582LRTQosStormControlEntry
               MAX-ACCESS  not-accessible
               STATUS      current
               DESCRIPTION
                   "The Qos Storm Control Entry."
               INDEX    {     sispm1040582lrtQosStormControlFrameType  }
               ::= {     sispm1040582lrtQosStormControlTable 1 }

    SISPM1040582LRTQosStormControlEntry             ::= SEQUENCE {
                sispm1040582lrtQosStormControlFrameType        INTEGER,
                sispm1040582lrtQosStormControlEnabled          AdminMode,
                sispm1040582lrtQosStormControlRate             Integer32,
		sispm1040582lrtQosStormControlUnit             Integer32
                }

    sispm1040582lrtQosStormControlFrameType OBJECT-TYPE
               SYNTAX      INTEGER { unicast(1), multicast (2), broadcast (3)}
               MAX-ACCESS  not-accessible
               STATUS      current
               DESCRIPTION
                   "The settings in a particular row apply to the frame type listed here.
                    1:Unicast,
                    2:Multicast,
                    3:Broadcast."
               ::= {     sispm1040582lrtQosStormControlEntry 1 }

    sispm1040582lrtQosStormControlEnabled OBJECT-TYPE
               SYNTAX      AdminMode
               MAX-ACCESS  read-write
               STATUS      current
               DESCRIPTION
                  "Enable or disable the global storm policer for the given frame type."
               ::= {     sispm1040582lrtQosStormControlEntry 2 }

    sispm1040582lrtQosStormControlRate OBJECT-TYPE
               SYNTAX      Integer32
               MAX-ACCESS  read-write
               STATUS      current
               DESCRIPTION
                   "Controls the rate for the global storm policer."
               ::= {     sispm1040582lrtQosStormControlEntry 3 }
			   
    sispm1040582lrtQosStormControlUnit OBJECT-TYPE
               SYNTAX      Integer32
               MAX-ACCESS  read-write
               STATUS      current
               DESCRIPTION
                   "Controls the unit of measure for the global storm policer rate as fps or kfps.
		   0: kbps
		   1: Mbps				   
	           2: fps
                   3: kbps"				   
               ::= {     sispm1040582lrtQosStormControlEntry 4 }			   

--
-- =======================================================================================================================
-- Start  sispm1040582lrtQosPortStormControl group
-- =======================================================================================================================
--sispm1040582lrtQosPortStormControlTable
--    sispm1040582lrtQosPortStormControlTable OBJECT-TYPE
--               SYNTAX      SEQUENCE OF     SISPM1040582LRTQosPortStormControlEntry
--               MAX-ACCESS  not-accessible
--               STATUS      current
--               DESCRIPTION
--                   "Configure the storm control settings.
--                    INDEX for this table is ifIndex which is
--                    equivalent to the panel port number."
--               ::= {     sispm1040582lrtQosPortStormControl  1 }
--
--    sispm1040582lrtQosPortStormControlEntry OBJECT-TYPE
--               SYNTAX      SISPM1040582LRTQosPortStormControlEntry
--               MAX-ACCESS  not-accessible
--               STATUS      current
--               DESCRIPTION
--                   "The Qos Port Storm Control Entry."
--               INDEX    {     ifIndex  }
--               ::= {     sispm1040582lrtQosPortStormControlTable 1 }
--
--    SISPM1040582LRTQosPortStormControlEntry             ::= SEQUENCE {
--                sispm1040582lrtQosPortStormControlUnicastEnabled   AdminMode,
--                sispm1040582lrtQosPortStormControlUnicastRate      Integer32,
--                sispm1040582lrtQosPortStormControlUnicastUnit      Integer32,
--                sispm1040582lrtQosPortStormControlBroadcastEnabled AdminMode,
--                sispm1040582lrtQosPortStormControlBroadcastRate    Integer32,
--                sispm1040582lrtQosPortStormControlBroadcastUnit    Integer32,
--                sispm1040582lrtQosPortStormControlUnknownEnabled   AdminMode,
--                sispm1040582lrtQosPortStormControlUnknownRate      Integer32,
--                sispm1040582lrtQosPortStormControlUnknownUnit      Integer32
--                }
--
--     sispm1040582lrtQosPortStormControlUnicastEnabled OBJECT-TYPE
--               SYNTAX      AdminMode
--               MAX-ACCESS  read-write
--               STATUS      current
--               DESCRIPTION
--                  "Controls whether the storm control is enabled on this
--                   switch port."
--               ::= {     sispm1040582lrtQosPortStormControlEntry 2 }
--
--    sispm1040582lrtQosPortStormControlUnicastRate OBJECT-TYPE
--               SYNTAX      Integer32
--               MAX-ACCESS  read-write
--               STATUS      current
--               DESCRIPTION
--                   "Controls the rate for the storm control."
--               ::= {     sispm1040582lrtQosPortStormControlEntry 3 }
--
--    sispm1040582lrtQosPortStormControlUnicastUnit OBJECT-TYPE
--               SYNTAX      Integer32
--               MAX-ACCESS  read-write
--               STATUS      current
--               DESCRIPTION
--                   "Controls the unit of measure for the storm control rate.
--		   0: kbps
--		   1: Mbps				   
--		   2: fps
--                   3: kbps"
--               ::= {     sispm1040582lrtQosPortStormControlEntry 4 }
--
--     sispm1040582lrtQosPortStormControlBroadcastEnabled  OBJECT-TYPE
--               SYNTAX      AdminMode
--               MAX-ACCESS  read-write
--               STATUS      current
--               DESCRIPTION
--                  "Controls whether the storm control is enabled on this
--                   switch port."
--               ::= {     sispm1040582lrtQosPortStormControlEntry 5 }
--
--    sispm1040582lrtQosPortStormControlBroadcastRate OBJECT-TYPE
--               SYNTAX      Integer32
--               MAX-ACCESS  read-write
--               STATUS      current
--               DESCRIPTION
--                   "Controls the rate for the storm control."
--               ::= {     sispm1040582lrtQosPortStormControlEntry 6 }
--
--    sispm1040582lrtQosPortStormControlBroadcastUnit OBJECT-TYPE
--               SYNTAX      Integer32
--               MAX-ACCESS  read-write
--               STATUS      current
--               DESCRIPTION
--                   "Controls the unit of measure for the storm control rate.
--		   0: kbps
--		   1: Mbps				   
--	           2: fps
--                   3: kbps"
--               ::= {     sispm1040582lrtQosPortStormControlEntry 7 }
--
--    sispm1040582lrtQosPortStormControlUnknownEnabled  OBJECT-TYPE
--               SYNTAX      AdminMode
--               MAX-ACCESS  read-write
--               STATUS      current
--               DESCRIPTION
--                  "Controls whether the storm control is enabled on this
--                   switch port."
--               ::= {     sispm1040582lrtQosPortStormControlEntry 8 }
--
--    sispm1040582lrtQosPortStormControlUnknownRate OBJECT-TYPE
--               SYNTAX      Integer32
--               MAX-ACCESS  read-write
--               STATUS      current
--               DESCRIPTION
--                   "Controls the rate for the storm control."
--               ::= {     sispm1040582lrtQosPortStormControlEntry 9 }
--
--    sispm1040582lrtQosPortStormControlUnknownUnit OBJECT-TYPE
--               SYNTAX      Integer32
--               MAX-ACCESS  read-write
--               STATUS      current
--               DESCRIPTION
--                   "Controls the unit of measure for the storm control rate.
--		   0: kbps
--		   1: Mbps				   
--	           2: fps
--                   3: kbps"
--               ::= {     sispm1040582lrtQosPortStormControlEntry 10 }

--
-- =======================================================================================================================
-- Start  sispm1040582lrtQosWRED group
-- =======================================================================================================================
--sispm1040582lrtQosWREDTable
--    sispm1040582lrtQosWREDTable OBJECT-TYPE
--               SYNTAX      SEQUENCE OF     SISPM1040582LRTQosWREDEntry
--               MAX-ACCESS  not-accessible
--               STATUS      current
--               DESCRIPTION
--                   "The basic QoS DSCP Translation settings for all switches."
--               ::= {     sispm1040582lrtQosWRED  1 }
--
--    sispm1040582lrtQosWREDEntry OBJECT-TYPE
--               SYNTAX          SISPM1040582LRTQosWREDEntry
--               MAX-ACCESS  not-accessible
--               STATUS      current
--               DESCRIPTION
--                   "The Qos WRED Entry."
--               INDEX    {     sispm1040582lrtQosWREDQueue  }
--               ::= {     sispm1040582lrtQosWREDTable 1 }
--
--    SISPM1040582LRTQosWREDEntry             ::= SEQUENCE {
--                sispm1040582lrtQosWREDGroupIndex      Integer32,
--                sispm1040582lrtQosWREDQueue           Integer32,
--		sispm1040582lrtQosWREDDPL             Integer32,
--                sispm1040582lrtQosWREDEnable          AdminMode,
--                sispm1040582lrtQosWREDMinThreshold    Integer32,
--                sispm1040582lrtQosWREDMaxThreshold    Integer32,
--                sispm1040582lrtQosWREDMaxUnit         INTEGER
--                }
--
--    sispm1040582lrtQosWREDGroupIndex OBJECT-TYPE
--               SYNTAX      Integer32
--               MAX-ACCESS  not-accessible
--               STATUS      current
--               DESCRIPTION
--                   "The group number for which the configuration
--                    below applies."
--               ::= {     sispm1040582lrtQosWREDEntry 1 }
--
--    sispm1040582lrtQosWREDQueue OBJECT-TYPE
--               SYNTAX      Integer32
--               MAX-ACCESS  not-accessible
--               STATUS      current
--               DESCRIPTION
--                   "The queue number (QoS class) for which the configuration
--                    below applies."
--               ::= {     sispm1040582lrtQosWREDEntry 2 }
--
--    sispm1040582lrtQosWREDDPL OBJECT-TYPE
--               SYNTAX      Integer32
--               MAX-ACCESS  not-accessible
--               STATUS      current
--               DESCRIPTION
--                   "The dpl number for which the configuration
--                    below applies."
--               ::= {     sispm1040582lrtQosWREDEntry 3 }
--			   
--			   
--    sispm1040582lrtQosWREDEnable OBJECT-TYPE
--               SYNTAX      AdminMode
--               MAX-ACCESS  read-write
--               STATUS      current
--               DESCRIPTION
--                  "Controls whether RED is enabled for this queue.
--                  "
--               DEFVAL  { disable }
--               ::= {     sispm1040582lrtQosWREDEntry 4 }
--
--    sispm1040582lrtQosWREDMinThreshold OBJECT-TYPE
--               SYNTAX      Integer32(0..100)
--               MAX-ACCESS  read-write
--               STATUS      current
--               DESCRIPTION
--                   "Controls the lower RED fill level threshold. If the queue filling
--                    level is below this threshold, the drop probability is zero.
--                    range:0-100%,
--                    default: 0.
--                  "
--               ::= {     sispm1040582lrtQosWREDEntry 5 }
--
--    sispm1040582lrtQosWREDMaxThreshold OBJECT-TYPE
--               SYNTAX      Integer32(0..100)
--               MAX-ACCESS  read-write
--               STATUS      current
--               DESCRIPTION
--                   "Controls the upper RED drop probability or fill level threshold
--                    for frames marked with Drop Precedence Level 1 (yellow frames).
--                    range:0-100%,
--                    default: 50.
--                  "
--               ::= {     sispm1040582lrtQosWREDEntry 6 }
--
--    sispm1040582lrtQosWREDMaxUnit OBJECT-TYPE
--               SYNTAX      INTEGER {dropProbability (0), fillLevel (1) }
--               MAX-ACCESS  read-write
--               STATUS      current
--               DESCRIPTION
--                   "Selects the unit for Max.
--                    0: Drop Probability,
--                    1: Fill Level,
--                    default: Drop Probability.
--                  "
--               DEFVAL  { dropProbability }
--               ::= {     sispm1040582lrtQosWREDEntry 7 }

--
-- =======================================================================================================================
-- Start  sispm1040582lrtQosQCLStatus
-- =======================================================================================================================

--sispm1040582lrtQosQCLStatusTable
    sispm1040582lrtQosQCLStatusTable OBJECT-TYPE
               SYNTAX      SEQUENCE OF     SISPM1040582LRTQosQCLStatusEntry
               MAX-ACCESS  not-accessible
               STATUS      current
               DESCRIPTION
                   "The basic QoS DSCP Translation settings for all switches."
               ::= {     sispm1040582lrtQosQCLStatus 1 }

    sispm1040582lrtQosQCLStatusEntry OBJECT-TYPE
               SYNTAX          SISPM1040582LRTQosQCLStatusEntry
               MAX-ACCESS  not-accessible
               STATUS      current
               DESCRIPTION
                   "The Qos QCL Status Entry."
               INDEX    {     sispm1040582lrtQosQCLStatusList  }
               ::= {     sispm1040582lrtQosQCLStatusTable 1 }

    SISPM1040582LRTQosQCLStatusEntry             ::= SEQUENCE {
                sispm1040582lrtQosQCLStatusList               Integer32,
                sispm1040582lrtQosQCLStatusUser               DisplayString,
                sispm1040582lrtQosQCLStatusQCEId              DisplayString,
                sispm1040582lrtQosQCLStatusFrameType          DisplayString,
                sispm1040582lrtQosQCLStatusPortlist           DisplayString,
                sispm1040582lrtQosQCLStatusActionClass        DisplayString,
                sispm1040582lrtQosQCLStatusActionDPL          DisplayString,
                sispm1040582lrtQosQCLStatusActionDSCP         DisplayString,
                sispm1040582lrtQosQCLStatusActionPCP          DisplayString,
                sispm1040582lrtQosQCLStatusActionDEL          DisplayString,
                sispm1040582lrtQosQCLStatusActionPolicy       DisplayString,
                sispm1040582lrtQosQCLStatusConflict           DisplayString,
		sispm1040582lrtQosQCLStatusSwitch             Integer32,
		sispm1040582lrtQosQCLStatusDMAC               DisplayString,
		sispm1040582lrtQosQCLStatusSMAC               DisplayString,
		sispm1040582lrtQosQCLStatusTag                DisplayString,
		sispm1040582lrtQosQCLStatusVID                DisplayString,
		sispm1040582lrtQosQCLStatusPCP                DisplayString,
		sispm1040582lrtQosQCLStatusDEI                DisplayString
                }

    sispm1040582lrtQosQCLStatusList OBJECT-TYPE
               SYNTAX      Integer32(1..4095)
               MAX-ACCESS  not-accessible
               STATUS      current
               DESCRIPTION
                   "QCL table index."
               ::= {     sispm1040582lrtQosQCLStatusEntry 1}

    sispm1040582lrtQosQCLStatusUser OBJECT-TYPE
               SYNTAX      DisplayString
               MAX-ACCESS  read-only
               STATUS      current
               DESCRIPTION
                   "Indicates the QCL user."
               ::= {     sispm1040582lrtQosQCLStatusEntry 2 }

    sispm1040582lrtQosQCLStatusQCEId OBJECT-TYPE
               SYNTAX      DisplayString
               MAX-ACCESS  read-only
               STATUS      current
               DESCRIPTION
                  "Indicates the index of QCE."
               ::= {     sispm1040582lrtQosQCLStatusEntry 3}

    sispm1040582lrtQosQCLStatusFrameType OBJECT-TYPE
               SYNTAX      DisplayString
               MAX-ACCESS  read-only
               STATUS      current
               DESCRIPTION
                   "Indicates the type of frame to look for incomming frames.
                    Any: The QCE will match all frame type.
                    Ethernet: Only Ethernet frames (with Ether Type 0x600-0xFFFF)
                    are allowed.
                    LLC: Only (LLC) frames are allowed.
                    SNAP: Only (SNAP) frames are allowed.
                    IPv4: The QCE will match only IPV4 frames.
                    IPv6: The QCE will match only IPV6 frames."
               ::= {     sispm1040582lrtQosQCLStatusEntry 4}

    sispm1040582lrtQosQCLStatusPortlist OBJECT-TYPE
               SYNTAX      DisplayString
               MAX-ACCESS  read-only
               STATUS      current
               DESCRIPTION
                   "Indicates the list of ports configured with the QCE."
               ::= {     sispm1040582lrtQosQCLStatusEntry 5}

    sispm1040582lrtQosQCLStatusActionClass OBJECT-TYPE
               SYNTAX      DisplayString
               MAX-ACCESS  read-only
               STATUS      current
               DESCRIPTION
                   "Classified QoS class; if a frame matches the
                    QCE it will be put in the  queue."
               ::= {     sispm1040582lrtQosQCLStatusEntry 6}

    sispm1040582lrtQosQCLStatusActionDPL OBJECT-TYPE
               SYNTAX      DisplayString
               MAX-ACCESS  read-only
               STATUS      current
               DESCRIPTION
                   "Drop Precedence Level; if a frame matches the QCE then
                    DP level will set to value displayed under DPL column."
               ::= {     sispm1040582lrtQosQCLStatusEntry 7}

    sispm1040582lrtQosQCLStatusActionDSCP OBJECT-TYPE
               SYNTAX      DisplayString
               MAX-ACCESS  read-only
               STATUS      current
               DESCRIPTION
                   "If a frame matches the QCE then DSCP will be
                    classified with the value
                    displayed under DSCP column."
               ::= {     sispm1040582lrtQosQCLStatusEntry 8}

    sispm1040582lrtQosQCLStatusActionPCP OBJECT-TYPE
               SYNTAX      DisplayString
               MAX-ACCESS  read-only
               STATUS      current
               DESCRIPTION
                   "Classify PCP value.
                    Only support SERVAL."
               ::= {     sispm1040582lrtQosQCLStatusEntry 9}

    sispm1040582lrtQosQCLStatusActionDEL OBJECT-TYPE
               SYNTAX      DisplayString
               MAX-ACCESS  read-only
               STATUS      current
               DESCRIPTION
                   "Classify DEI value.
                    Only support SERVAL."
               ::= {     sispm1040582lrtQosQCLStatusEntry 10}

    sispm1040582lrtQosQCLStatusActionPolicy OBJECT-TYPE
               SYNTAX      DisplayString
               MAX-ACCESS  read-only
               STATUS      current
               DESCRIPTION
                   "Classify ACL Policy number.
                    Only support SERVAL."
               ::= {     sispm1040582lrtQosQCLStatusEntry 11}

    sispm1040582lrtQosQCLStatusConflict OBJECT-TYPE
               SYNTAX      DisplayString
               MAX-ACCESS  read-only
               STATUS      current
               DESCRIPTION
                   "Displays Conflict status of QCL entries."
               ::= {     sispm1040582lrtQosQCLStatusEntry 12}

    sispm1040582lrtQosQCLStatusSwitch OBJECT-TYPE
               SYNTAX      Integer32
               MAX-ACCESS  read-only
               STATUS      current
               DESCRIPTION
                   "Switch number for port members. -1:Any.
                    Only support stacking switch."
               ::= {     sispm1040582lrtQosQCLStatusEntry 13}
			   
    sispm1040582lrtQosQCLStatusDMAC OBJECT-TYPE
               SYNTAX      DisplayString
               MAX-ACCESS  read-only
               STATUS      current
               DESCRIPTION
                   "Destination MAC address: Possible values are 'Unicast', 'Multicast', 'Broadcast' or 'Any'."
               ::= {     sispm1040582lrtQosQCLStatusEntry 14}

    sispm1040582lrtQosQCLStatusSMAC OBJECT-TYPE
               SYNTAX      DisplayString
               MAX-ACCESS  read-only
               STATUS      current
               DESCRIPTION
                   "Source MAC address: xx-xx-xx-xx-xx-xx or 'Any'."
               ::= {     sispm1040582lrtQosQCLStatusEntry 15}

    sispm1040582lrtQosQCLStatusTag OBJECT-TYPE
               SYNTAX      DisplayString
               MAX-ACCESS  read-only
               STATUS      current
               DESCRIPTION
                   "Value of Tag field can be 'Untagged', 'Tagged', 'C-Tagged', 'S-Tagged' or 'Any'."
               ::= {     sispm1040582lrtQosQCLStatusEntry 16}

    sispm1040582lrtQosQCLStatusVID OBJECT-TYPE
               SYNTAX      DisplayString
               MAX-ACCESS  read-only
               STATUS      current
               DESCRIPTION
                   "Valid value of VLAN ID can be any value in the range 1-4095 or 'Any'"
               ::= {     sispm1040582lrtQosQCLStatusEntry 17}			   

    sispm1040582lrtQosQCLStatusPCP OBJECT-TYPE
               SYNTAX      DisplayString
               MAX-ACCESS  read-only
               STATUS      current
               DESCRIPTION
                   "Valid value PCP are specific (0, 1, 2, 3, 4, 5, 6, 7) or range (0-1, 2-3, 4-5, 6-7, 0-3, 4-7) or 'Any'."
               ::= {     sispm1040582lrtQosQCLStatusEntry 18}	

    sispm1040582lrtQosQCLStatusDEI OBJECT-TYPE
               SYNTAX      DisplayString
               MAX-ACCESS  read-only
               STATUS      current
               DESCRIPTION
                   "Valid value of DEI can be '0', '1' or 'Any'."
               ::= {     sispm1040582lrtQosQCLStatusEntry 19}				   
-- =======================================================================================================================
-- sispm1040582lrtQosConformance
-- =======================================================================================================================
sispm1040582lrtQosConformance OBJECT IDENTIFIER ::= { sispm1040582lrtQosConf 200 }

sispm1040582lrtQosCompliances OBJECT IDENTIFIER ::= { sispm1040582lrtQosConformance 1 }

sispm1040582lrtQosGroups      OBJECT IDENTIFIER ::= { sispm1040582lrtQosConformance 2 }


sispm1040582lrtQosPortClassificationGroup OBJECT-GROUP
    OBJECTS {
                --sispm1040582lrtQosPortClassificationTable
                sispm1040582lrtQosPortClassificationQoSClass,
                sispm1040582lrtQosPortClassificationDPlevel,
                sispm1040582lrtQosPortClassificationPCP,
                sispm1040582lrtQosPortClassificationDEI,
                sispm1040582lrtQosPortClassificationTagClass,
                sispm1040582lrtQosPortClassificationDSCPBased,
                sispm1040582lrtQosPortClassificationQCLAddr,
                sispm1040582lrtQosPortClassificationKeyType,

                --sispm1040582lrtQoSIngressPortTagClassificationTable
                sispm1040582lrtQoSIngressPortTagQosClass,
                sispm1040582lrtQoSIngressPortTagDPLevel
            }
    STATUS  current
    DESCRIPTION
            "The collection of objects which are used to indicate
            sispm1040582lrt qos information."
    ::= { sispm1040582lrtQosGroups 1}


sispm1040582lrtQosPortPolicingGroup OBJECT-GROUP
    OBJECTS {
                --sispm1040582lrtQosPortPolicingTable
                sispm1040582lrtQosPortPolicingEnabled,
                sispm1040582lrtQosPortPolicingRate,
                sispm1040582lrtQosPortPolicingUnit,
                sispm1040582lrtQosPortPolicingFlowControl
            }
    STATUS  current
    DESCRIPTION
            "The collection of objects which are used to indicate
            sispm1040582lrt qos information."
    ::= { sispm1040582lrtQosGroups 2}


sispm1040582lrtQosQueuePolicingGroup OBJECT-GROUP
    OBJECTS {
                --sispm1040582lrtQosPortPolicingTable
                sispm1040582lrtQosQueuePolicingQueue0Enable,
                sispm1040582lrtQosQueuePolicingQueue0Rate,
                sispm1040582lrtQosQueuePolicingQueue1Enable,
                sispm1040582lrtQosQueuePolicingQueue1Rate,
                sispm1040582lrtQosQueuePolicingQueue2Enable,
                sispm1040582lrtQosQueuePolicingQueue2Rate,
                sispm1040582lrtQosQueuePolicingQueue3Enable,
                sispm1040582lrtQosQueuePolicingQueue3Rate,
                sispm1040582lrtQosQueuePolicingQueue4Enable,
                sispm1040582lrtQosQueuePolicingQueue4Rate,
                sispm1040582lrtQosQueuePolicingQueue5Enable,
                sispm1040582lrtQosQueuePolicingQueue5Rate,
                sispm1040582lrtQosQueuePolicingQueue6Enable,
                sispm1040582lrtQosQueuePolicingQueue6Rate,
                sispm1040582lrtQosQueuePolicingQueue7Enable,
                sispm1040582lrtQosQueuePolicingQueue7Rate
            }
    STATUS  current
    DESCRIPTION
            "The collection of objects which are used to indicate
            sispm1040582lrt qos information."
    ::= { sispm1040582lrtQosGroups 3}

sispm1040582lrtQosPortSchedulerGroup OBJECT-GROUP
    OBJECTS {
                --sispm1040582lrtQosPortSchedulerModeTable
                sispm1040582lrtQosSchedulerMode,
                sispm1040582lrtQosSchedulerShaper,
                sispm1040582lrtQosSchedulerShaperRate,

                --sispm1040582lrtQosPortSchedulerTable
                 sispm1040582lrtQosSchedulerPortQueueShaper,
                sispm1040582lrtQosSchedulerPortQueueShaperRate,
                sispm1040582lrtQosSchedulerPortQueueShaperExcess,
                sispm1040582lrtQosSchedulerPortQueueSchedulerWeight,
                sispm1040582lrtQosSchedulerPortQueueSchedulerPercent,

                --sispm1040582lrtQosPortEgressTagRemarkingMapTable
                 sispm1040582lrtQosTagRemarkingPCP,
                 sispm1040582lrtQosTagRemarkingDEI
            }
    STATUS  current
    DESCRIPTION
            "The collection of objects which are used to indicate
            sispm1040582lrt qos information."
    ::= { sispm1040582lrtQosGroups 4}

sispm1040582lrtQosPortEgressTagRemarkingGroup OBJECT-GROUP
    OBJECTS {
                --sispm1040582lrtQosPortEgressTagRemarkingTable
                sispm1040582lrtQosEgressTagRemarkingMode,

                --sispm1040582lrtQosPortEgressTagRemarkingDefTable
               sispm1040582lrtQosEgressTagRemarkingDefPCP,
               sispm1040582lrtQosEgressTagRemarkingDefDEI

               --sispm1040582lrtQosPortEgressTagRemarkingMapDPTable
--             sispm1040582lrtQosPortEgressTagRemarkingDPLevel
            }
    STATUS  current
    DESCRIPTION
            "The collection of objects which are used to indicate
            sispm1040582lrt qos information."
    ::= { sispm1040582lrtQosGroups 6}


sispm1040582lrtQosPortDSCPGroup OBJECT-GROUP
    OBJECTS {
                --sispm1040582lrtQosPortDSCPTable
                sispm1040582lrtQosPortDSCPIngressTranslate,
                sispm1040582lrtQosPortDSCPIngressClassify,
                sispm1040582lrtQosPortDSCPEgressRewrite
            }
    STATUS  current
    DESCRIPTION
            "The collection of objects which are used to indicate
            sispm1040582lrt qos information."
    ::= { sispm1040582lrtQosGroups 7}

sispm1040582lrtQosDSCPGroup OBJECT-GROUP
    OBJECTS {
                --sispm1040582lrtQosDSCPTable
                sispm1040582lrtQosBasedDSCP,
                sispm1040582lrtQosDSCPTrust,
                sispm1040582lrtQosDSCPQosClass,
                sispm1040582lrtQosDSCPDPL
             }
    STATUS  current
    DESCRIPTION
            "The collection of objects which are used to indicate
            sispm1040582lrt qos information."
    ::= { sispm1040582lrtQosGroups 8}

sispm1040582lrtQosDSCPTranslationGroup OBJECT-GROUP
    OBJECTS {
                --sispm1040582lrtQosDSCPTranslationTable
                sispm1040582lrtQosDSCPTranslationDSCPBasedId,
                sispm1040582lrtQosDSCPTranslationIngressTranslate,
                sispm1040582lrtQosDSCPTranslationIngressClassify,
                sispm1040582lrtQosDSCPTranslationEgressRemapDP0,
                sispm1040582lrtQosDSCPTranslationEgressRemapDP1
            }
    STATUS  current
    DESCRIPTION
            "The collection of objects which are used to indicate
            sispm1040582lrt qos information."
    ::= { sispm1040582lrtQosGroups 9}

--sispm1040582lrtQosDSCPClassificationGroup OBJECT-GROUP
--    OBJECTS {
--                sispm1040582lrtQosDSCPClassificationTable
--                sispm1040582lrtQosDSCPClassificationDSCP
--            }
--    STATUS  current
--    DESCRIPTION
--            "The collection of objects which are used to indicate
--            sispm1040582lrt qos information."
--    ::= { sispm1040582lrtQosGroups 10}

sispm1040582lrtQosControlListGroup OBJECT-GROUP
    OBJECTS {
                --sispm1040582lrtQosQceTable
                sispm1040582lrtQosQceID,
                sispm1040582lrtQosQceList,
                sispm1040582lrtQosQcePortMembers,
                sispm1040582lrtQosQceTag,
                sispm1040582lrtQosQceVID,
                sispm1040582lrtQosPCP,
                sispm1040582lrtQosDEI,
                sispm1040582lrtQosSMAC,
                sispm1040582lrtQosDMACType,
                sispm1040582lrtQosDMACValue,
                sispm1040582lrtQosQceInnerTag,
                sispm1040582lrtQosQceInnerVID,
                sispm1040582lrtQosInnerPCP,
                sispm1040582lrtQosInnerDEI,
                sispm1040582lrtQosFrameType,
                sispm1040582lrtQosMacEtherType,
                sispm1040582lrtQosLLCSSAPAddr,
                sispm1040582lrtQosLLCDSAPAddr,
                sispm1040582lrtQosLLCControl,
                sispm1040582lrtQosSNAPPID,
                sispm1040582lrtQosIpv4Protocol,
                sispm1040582lrtQosIpv4ProtocolValue,
                sispm1040582lrtQosIpv4ProtocolUDPSPort,
                sispm1040582lrtQosIpv4ProtocolUDPDPort,
                sispm1040582lrtQosIpv4ProtocolTCPSPort,
                sispm1040582lrtQosIpv4ProtocolTCPDPort,
                sispm1040582lrtQosIpv4SourceIp,
                sispm1040582lrtQosIpv4SourceMask,
                sispm1040582lrtQosIpv4IPFragment,
                sispm1040582lrtQosIpv4DSCP,
                sispm1040582lrtQosIpv6Protocol,
                sispm1040582lrtQosIpv6ProtocolValue,
                sispm1040582lrtQosIpv6ProtocolUDPSPort,
                sispm1040582lrtQosIpv6ProtocolUDPDPort,
                sispm1040582lrtQosIpv6ProtocolTCPSPort,
                sispm1040582lrtQosIpv6ProtocolTCPDPort,
                sispm1040582lrtQosIpv6SourceIp,
                sispm1040582lrtQosIpv6SourceMask,
                sispm1040582lrtQosIpv6DSCP,
                sispm1040582lrtQosActionClass,
                sispm1040582lrtQosActionDPL,
                sispm1040582lrtQosActionDSCP,
                sispm1040582lrtQosActionPCP,
                sispm1040582lrtQosActionDEI,
                sispm1040582lrtQosActionPolicy,
                sispm1040582lrtQosQceRowStatus
            }
    STATUS  current
    DESCRIPTION
            "The collection of objects which are used to indicate
             sispm1040582lrt qos information."
    ::= { sispm1040582lrtQosGroups 11}


sispm1040582lrtQosStormControlGroup OBJECT-GROUP
    OBJECTS {
                --sispm1040582lrtQosStormControlTable
                sispm1040582lrtQosStormControlEnabled,
                sispm1040582lrtQosStormControlRate
            }
    STATUS  current
    DESCRIPTION
            "The collection of objects which are used to indicate
            sispm1040582lrt qos information."
    ::= { sispm1040582lrtQosGroups 12}

--sispm1040582lrtQosPortStormControlGroup OBJECT-GROUP
--    OBJECTS {
--                sispm1040582lrtQosPortStormControlTable
--                sispm1040582lrtQosPortStormControlUnicastEnabled,
--                sispm1040582lrtQosPortStormControlUnicastRate,
--                sispm1040582lrtQosPortStormControlUnicastUnit,
--                sispm1040582lrtQosPortStormControlBroadcastEnabled,
--                sispm1040582lrtQosPortStormControlBroadcastRate,
--                sispm1040582lrtQosPortStormControlBroadcastUnit,
--                sispm1040582lrtQosPortStormControlUnknownEnabled,
--                sispm1040582lrtQosPortStormControlUnknownRate,
--                sispm1040582lrtQosPortStormControlUnknownUnit
--            }
--    STATUS  current
--    DESCRIPTION
--            "The collection of objects which are used to indicate
--            sispm1040582lrt qos information."
--    ::= { sispm1040582lrtQosGroups 13}

--sispm1040582lrtQosWREDGroup OBJECT-GROUP
--    OBJECTS {
--                sispm1040582lrtQosWREDTable
--                sispm1040582lrtQosWREDEnable,
--                sispm1040582lrtQosWREDMinThreshold,
--
--                sispm1040582lrtQosWREDMaxThreshold,
--                sispm1040582lrtQosWREDMaxUnit
--            }
--    STATUS  current
--    DESCRIPTION
--            "The collection of objects which are used to indicate
--            sispm1040582lrt qos information."
--    ::= { sispm1040582lrtQosGroups 14}

sispm1040582lrtQosQCLStatusGroup OBJECT-GROUP
    OBJECTS {
                --sispm1040582lrtQosQCLStatusTable
                sispm1040582lrtQosQCLStatusUser,
                sispm1040582lrtQosQCLStatusQCEId,
                sispm1040582lrtQosQCLStatusFrameType,
                sispm1040582lrtQosQCLStatusPortlist,
                sispm1040582lrtQosQCLStatusActionClass,
                sispm1040582lrtQosQCLStatusActionDPL,
                sispm1040582lrtQosQCLStatusActionDSCP,
                sispm1040582lrtQosQCLStatusActionPCP,
                sispm1040582lrtQosQCLStatusActionDEL,
                sispm1040582lrtQosQCLStatusActionPolicy,
                sispm1040582lrtQosQCLStatusConflict
            }
    STATUS  current
    DESCRIPTION
            "The collection of objects which are used to indicate
            sispm1040582lrt qos information."
    ::= { sispm1040582lrtQosGroups 15}

-- =======================================================================================================================

sispm1040582lrtLoopProtection                                                  OBJECT IDENTIFIER ::= { sispm1040582lrtConfiguration 12 }

sispm1040582lrtLoopProtectionConfig                                            OBJECT IDENTIFIER ::= { sispm1040582lrtLoopProtection 1 }

sispm1040582lrtLoopProtectionGlobalEnable OBJECT-TYPE
   SYNTAX      Integer32(0|1)
   MAX-ACCESS  read-write
   STATUS      current
   DESCRIPTION
       "Configure loop protection mode.
        0: disable,
        1: enable,
        default: disable. "
   ::= { sispm1040582lrtLoopProtectionConfig 1 }

sispm1040582lrtLoopProtectionTranmisstionTime OBJECT-TYPE
   SYNTAX      Integer32(1..10)
   MAX-ACCESS  read-write
   STATUS      current
   DESCRIPTION
       "Configure loop protection transmit interval.
        default: 5,
        range: 1-10. "
   ::= { sispm1040582lrtLoopProtectionConfig 2 }

sispm1040582lrtLoopProtectionShutdownTime OBJECT-TYPE
   SYNTAX      Integer32(0..604800)
   MAX-ACCESS  read-write
   STATUS      current
   DESCRIPTION
       "Configure loop protection shutdown time.
        default: 180,
        range: 0-604800. "
   ::= { sispm1040582lrtLoopProtectionConfig 3 }

sispm1040582lrtLoopProtectionConfigurationTable OBJECT-TYPE
   SYNTAX      SEQUENCE OF SISPM1040582LRTLoopProtectionConfigurationEntry
   MAX-ACCESS  not-accessible
   STATUS      current
   DESCRIPTION
       " Show Loop Protection configurations. "
   ::= { sispm1040582lrtLoopProtectionConfig 4 }

sispm1040582lrtLoopProtectionConfigurationEntry OBJECT-TYPE
   SYNTAX      SISPM1040582LRTLoopProtectionConfigurationEntry
   MAX-ACCESS  not-accessible
   STATUS      current
   DESCRIPTION
       " "
   INDEX    { sispm1040582lrtLoopProtectionConfPort  }
   ::= { sispm1040582lrtLoopProtectionConfigurationTable 1 }

SISPM1040582LRTLoopProtectionConfigurationEntry ::= SEQUENCE {
   sispm1040582lrtLoopProtectionConfPort	    Integer32,
   sispm1040582lrtLoopProtectionConfEnable	Integer32,
   sispm1040582lrtLoopProtectionConfAction	Integer32,
   sispm1040582lrtLoopProtectionConfTxmode	Integer32
}

sispm1040582lrtLoopProtectionConfPort OBJECT-TYPE
   SYNTAX      Integer32 (1..4095)
   MAX-ACCESS  not-accessible
   STATUS      current
   DESCRIPTION
       " port, range : 1 - port number. "
   ::= { sispm1040582lrtLoopProtectionConfigurationEntry 1 }

sispm1040582lrtLoopProtectionConfEnable OBJECT-TYPE
   SYNTAX      Integer32(0|1)
   MAX-ACCESS  read-write
   STATUS      current
   DESCRIPTION
       "Configure loop protection port mode.
        0: disable,
        1: enable,
        default: enable. "
   ::= { sispm1040582lrtLoopProtectionConfigurationEntry 2 }

sispm1040582lrtLoopProtectionConfAction OBJECT-TYPE
   SYNTAX      Integer32(0..2)
   MAX-ACCESS  read-write
   STATUS      current
   DESCRIPTION
       " Configure loop protection port action.
         0: Shutdown port,
         1: Shutdown port and Log,
         2: Log Only,
         default: Shutdown port. "
   ::= { sispm1040582lrtLoopProtectionConfigurationEntry 3 }

sispm1040582lrtLoopProtectionConfTxmode OBJECT-TYPE
   SYNTAX      Integer32(0|1)
   MAX-ACCESS  read-write
   STATUS      current
   DESCRIPTION
       "Configure loop protection port transmit mode.
        0: disable,
        1: enable,
        default: enable. "
   ::= { sispm1040582lrtLoopProtectionConfigurationEntry 4 }

sispm1040582lrtLoopProtectionStatusTable OBJECT-TYPE
   SYNTAX      SEQUENCE OF SISPM1040582LRTLoopProtectionStatusEntry
   MAX-ACCESS  not-accessible
   STATUS      current
   DESCRIPTION
       " Show Loop Protection Status. "
   ::= { sispm1040582lrtLoopProtection 2 }

sispm1040582lrtLoopProtectionStatusEntry OBJECT-TYPE
   SYNTAX      SISPM1040582LRTLoopProtectionStatusEntry
   MAX-ACCESS  not-accessible
   STATUS      current
   DESCRIPTION
       " "
   INDEX    { sispm1040582lrtLoopProtectionStatusPort  }
   ::= { sispm1040582lrtLoopProtectionStatusTable 1 }

SISPM1040582LRTLoopProtectionStatusEntry ::= SEQUENCE {
   sispm1040582lrtLoopProtectionStatusPort	       Integer32,
   sispm1040582lrtLoopProtectionStatusAction	       DisplayString,
   sispm1040582lrtLoopProtectionStatusTransmit	   DisplayString,
   sispm1040582lrtLoopProtectionStatusLoops	       Integer32,
   sispm1040582lrtLoopProtectionStatusStatus	       DisplayString,
   sispm1040582lrtLoopProtectionStatusLoop	       DisplayString,
   sispm1040582lrtLoopProtectionStatusTimeLastLoop  DisplayString
}

sispm1040582lrtLoopProtectionStatusPort OBJECT-TYPE
   SYNTAX      Integer32 (1..4095)
   MAX-ACCESS  not-accessible
   STATUS      current
   DESCRIPTION
       " port, range : 1 - port number. "
   ::= { sispm1040582lrtLoopProtectionStatusEntry 1 }

sispm1040582lrtLoopProtectionStatusAction OBJECT-TYPE
   SYNTAX      DisplayString
   MAX-ACCESS  read-only
   STATUS      current
   DESCRIPTION
       " The currently configured port action. "
   ::= { sispm1040582lrtLoopProtectionStatusEntry 2 }

sispm1040582lrtLoopProtectionStatusTransmit OBJECT-TYPE
   SYNTAX      DisplayString
   MAX-ACCESS  read-only
   STATUS      current
   DESCRIPTION
       " The currently configured port transmit mode. "
   ::= { sispm1040582lrtLoopProtectionStatusEntry 3 }

sispm1040582lrtLoopProtectionStatusLoops OBJECT-TYPE
   SYNTAX      Integer32 (0..1000000)
   MAX-ACCESS  read-only
   STATUS      current
   DESCRIPTION
       " The number of loops detected on this port. "
   ::= { sispm1040582lrtLoopProtectionStatusEntry 4 }

sispm1040582lrtLoopProtectionStatusStatus OBJECT-TYPE
   SYNTAX      DisplayString
   MAX-ACCESS  read-only
   STATUS      current
   DESCRIPTION
       " The current loop protection status of the port. "
   ::= { sispm1040582lrtLoopProtectionStatusEntry 5 }

sispm1040582lrtLoopProtectionStatusLoop OBJECT-TYPE
   SYNTAX      DisplayString
   MAX-ACCESS  read-only
   STATUS      current
   DESCRIPTION
       " Whether a loop is currently detected on the port. "
   ::= { sispm1040582lrtLoopProtectionStatusEntry 6 }

sispm1040582lrtLoopProtectionStatusTimeLastLoop OBJECT-TYPE
   SYNTAX      DisplayString
   MAX-ACCESS  read-only
   STATUS      current
   DESCRIPTION
       " The time of the last loop event detected. "
   ::= { sispm1040582lrtLoopProtectionStatusEntry 7 }
-- =======================================================================================================================
sispm1040582lrtPoe                                                           OBJECT IDENTIFIER ::= { sispm1040582lrtConfiguration 13 }

sispm1040582lrtPoeStatus                                            OBJECT IDENTIFIER ::= { sispm1040582lrtPoe 1 }

sispm1040582lrtPoeStatusTable OBJECT-TYPE
   SYNTAX      SEQUENCE OF SISPM1040582LRTPoeStatusEntry
   MAX-ACCESS  not-accessible
   STATUS      current
   DESCRIPTION
       " Configure PoE Scheduling Table. "
   ::= { sispm1040582lrtPoeStatus 1 }

sispm1040582lrtPoeStatusEntry OBJECT-TYPE
   SYNTAX      SISPM1040582LRTPoeStatusEntry
   MAX-ACCESS  not-accessible
   STATUS      current
   DESCRIPTION
       " "
   INDEX    { sispm1040582lrtPoeStatusLocalPort }
   ::= { sispm1040582lrtPoeStatusTable 1 }

SISPM1040582LRTPoeStatusEntry ::= SEQUENCE {
   sispm1040582lrtPoeStatusLocalPort              Integer32,
   sispm1040582lrtPoeStatusPDclass	        DisplayString,
   sispm1040582lrtPoeStatusPowerRequested	    DisplayString,
   sispm1040582lrtPoeStatusPowerAllocated     DisplayString,
   sispm1040582lrtPoeStatusPowerUsed          DisplayString,
   sispm1040582lrtPoeStatusCurrentUsed        DisplayString,
   sispm1040582lrtPoeStatusPriority           DisplayString,
   sispm1040582lrtPoeStatusPortStatus         DisplayString
}

sispm1040582lrtPoeStatusLocalPort OBJECT-TYPE
   SYNTAX      Integer32 (1..10)
   MAX-ACCESS  not-accessible
   STATUS      current
   DESCRIPTION
       "Local port Index."
   ::= { sispm1040582lrtPoeStatusEntry 1 }


sispm1040582lrtPoeStatusPDclass OBJECT-TYPE
   SYNTAX      DisplayString
   MAX-ACCESS  read-only
   STATUS      current
   DESCRIPTION
       " Eight Classes are defined:
         1: Max. power 4.0 W,
         2: Max. power 7.0 W,
         3: Max. power 15.4 W,
         4: Max. power 30.0 W,
         5: Max. power 45.0 W,
         6: Max. power 60.0 W,
         7: Max. power 75.0 W,
         8: Max. power 90.0 W. 
         Format of Dual signature PD over 4 pairs according to IEEE802.3bt is (pd_class_a,pd_class_b)."
   ::= { sispm1040582lrtPoeStatusEntry 2 }

sispm1040582lrtPoeStatusPowerRequested OBJECT-TYPE
   SYNTAX      DisplayString
   MAX-ACCESS  read-only
   STATUS      current
   DESCRIPTION
      " The Power Requested shows the requested amount of power the PD wants to be reserved. "
   ::= { sispm1040582lrtPoeStatusEntry 3}

sispm1040582lrtPoeStatusPowerAllocated OBJECT-TYPE
   SYNTAX      DisplayString
   MAX-ACCESS  read-only
   STATUS      current
   DESCRIPTION
      " The Power Allocated shows the amount of power the switch has allocated for the PD. "
   ::= { sispm1040582lrtPoeStatusEntry 4}

sispm1040582lrtPoeStatusPowerUsed OBJECT-TYPE
   SYNTAX      DisplayString
   MAX-ACCESS  read-only
   STATUS      current
   DESCRIPTION
      " The Power Used shows how much power the PD currently is using. "
   ::= { sispm1040582lrtPoeStatusEntry 5}

sispm1040582lrtPoeStatusCurrentUsed OBJECT-TYPE
   SYNTAX      DisplayString
   MAX-ACCESS  read-only
   STATUS      current
   DESCRIPTION
      " The Power Used shows how much current the PD currently is using. "
   ::= { sispm1040582lrtPoeStatusEntry 6}

sispm1040582lrtPoeStatusPriority OBJECT-TYPE
   SYNTAX      DisplayString
   MAX-ACCESS  read-only
   STATUS      current
   DESCRIPTION
      " The Priority shows the port's priority configured by the user.  "
   ::= { sispm1040582lrtPoeStatusEntry 7}

sispm1040582lrtPoeStatusPortStatus OBJECT-TYPE
   SYNTAX      DisplayString
   MAX-ACCESS  read-only
   STATUS      current
   DESCRIPTION
      " The Port Status shows the port's status.  "
   ::= { sispm1040582lrtPoeStatusEntry 8}

sispm1040582lrtPoeStatusTotalTable OBJECT-TYPE
   SYNTAX      SEQUENCE OF SISPM1040582LRTPoeStatusTotalEntry
   MAX-ACCESS  not-accessible
   STATUS      current
   DESCRIPTION
       " Configure PoE Scheduling Total Table. "
   ::= { sispm1040582lrtPoeStatus 2 }

sispm1040582lrtPoeStatusTotalEntry OBJECT-TYPE
   SYNTAX      SISPM1040582LRTPoeStatusTotalEntry
   MAX-ACCESS  not-accessible
   STATUS      current
   DESCRIPTION
       " "
   INDEX    { sispm1040582lrtPoeStatusSwitchIndex }
   ::= { sispm1040582lrtPoeStatusTotalTable 1 }

SISPM1040582LRTPoeStatusTotalEntry ::= SEQUENCE {
   sispm1040582lrtPoeStatusSwitchIndex            Integer32,
   sispm1040582lrtPoeStatusTotalPowerRequested    DisplayString,
   sispm1040582lrtPoeStatusTotalPowerAllocated    DisplayString,
   sispm1040582lrtPoeStatusTotalPowerUsed         DisplayString,
   sispm1040582lrtPoeStatusTotalCurrentUsed       DisplayString
}

sispm1040582lrtPoeStatusSwitchIndex OBJECT-TYPE
   SYNTAX      Integer32 (1..16)
   MAX-ACCESS  not-accessible
   STATUS      current
   DESCRIPTION
       "Switch Index."
   ::= { sispm1040582lrtPoeStatusTotalEntry 1 }

sispm1040582lrtPoeStatusTotalPowerRequested OBJECT-TYPE
   SYNTAX      DisplayString
   MAX-ACCESS  read-only
   STATUS      current
   DESCRIPTION
      " Total Power Requested."
   ::= { sispm1040582lrtPoeStatusTotalEntry 2}

sispm1040582lrtPoeStatusTotalPowerAllocated OBJECT-TYPE
   SYNTAX      DisplayString
   MAX-ACCESS  read-only
   STATUS      current
   DESCRIPTION
      " Total Power allocated."
   ::= { sispm1040582lrtPoeStatusTotalEntry 3}

sispm1040582lrtPoeStatusTotalPowerUsed OBJECT-TYPE
   SYNTAX      DisplayString
   MAX-ACCESS  read-only
   STATUS      current
   DESCRIPTION
      " Total Power Used."
   ::= { sispm1040582lrtPoeStatusTotalEntry 4}

sispm1040582lrtPoeStatusTotalCurrentUsed OBJECT-TYPE
   SYNTAX      DisplayString
   MAX-ACCESS  read-only
   STATUS      current
   DESCRIPTION
      " Total Current Used."
   ::= { sispm1040582lrtPoeStatusTotalEntry 5}


sispm1040582lrtPoePowerDelay                                                 OBJECT IDENTIFIER ::= { sispm1040582lrtPoe 2 }

sispm1040582lrtPoePowerDelayTable OBJECT-TYPE
   SYNTAX      SEQUENCE OF SISPM1040582LRTPoePowerDelayEntry
   MAX-ACCESS  not-accessible
   STATUS      current
   DESCRIPTION
       " Configure PoE Power Delay mode. "
   ::= { sispm1040582lrtPoePowerDelay 1 }

sispm1040582lrtPoePowerDelayEntry OBJECT-TYPE
   SYNTAX      SISPM1040582LRTPoePowerDelayEntry
   MAX-ACCESS  not-accessible
   STATUS      current
   DESCRIPTION
       " "
   INDEX    { sispm1040582lrtPoePowerDelayPort  }
   ::= { sispm1040582lrtPoePowerDelayTable 1 }

SISPM1040582LRTPoePowerDelayEntry ::= SEQUENCE {
   sispm1040582lrtPoePowerDelayPort	        Integer32,
   sispm1040582lrtPoePowerDelayMode	        Integer32,
   sispm1040582lrtPoePowerDelayTime	        Integer32
}

sispm1040582lrtPoePowerDelayPort OBJECT-TYPE
   SYNTAX      Integer32 (1..4094)
   MAX-ACCESS  not-accessible
   STATUS      current
   DESCRIPTION
       " port, range : 1 - port number. "
   ::= { sispm1040582lrtPoePowerDelayEntry 1 }

sispm1040582lrtPoePowerDelayMode OBJECT-TYPE
   SYNTAX      Integer32(0|1)
   MAX-ACCESS  read-write
   STATUS      current
   DESCRIPTION
       "Turn on / off the power delay function,
        0: disable,
        1: enable,
        default: disable. "
   ::= { sispm1040582lrtPoePowerDelayEntry 2 }

sispm1040582lrtPoePowerDelayTime OBJECT-TYPE
   SYNTAX      Integer32(0..300)
   MAX-ACCESS  read-write
   STATUS      current
   DESCRIPTION
       "set Delay Time,
        default: 0,
        range: 0-300 sec. "
   ::= { sispm1040582lrtPoePowerDelayEntry 3 }

sispm1040582lrtPoeAutoPowerReset                                                 OBJECT IDENTIFIER ::= { sispm1040582lrtPoe 3 }

sispm1040582lrtPoeAutoPowerResetPingCheck OBJECT-TYPE
   SYNTAX      INTEGER { disable(0), enable(1) }
   MAX-ACCESS  read-write
   STATUS      current
   DESCRIPTION
       "connection between PoE port and power device.
        0: disable,
        1: enable,
        default: disable. "
   ::= { sispm1040582lrtPoeAutoPowerReset 1 }

sispm1040582lrtPoeAutoPowerResetTable OBJECT-TYPE
   SYNTAX      SEQUENCE OF SISPM1040582LRTPoeAutoPowerResetEntry
   MAX-ACCESS  not-accessible
   STATUS      current
   DESCRIPTION
       " Configure PoE Auto Power Reset mode. "
   ::= { sispm1040582lrtPoeAutoPowerReset 2 }

sispm1040582lrtPoeAutoPowerResetEntry OBJECT-TYPE
   SYNTAX      SISPM1040582LRTPoeAutoPowerResetEntry
   MAX-ACCESS  not-accessible
   STATUS      current
   DESCRIPTION
       " "
   INDEX    { sispm1040582lrtPoeAutoPowerResetPort  }
   ::= { sispm1040582lrtPoeAutoPowerResetTable 1 }

SISPM1040582LRTPoeAutoPowerResetEntry ::= SEQUENCE {
   sispm1040582lrtPoeAutoPowerResetPort	   Integer32,
   sispm1040582lrtPoeAutoPowerResetPingIPAddress  DisplayString,
   sispm1040582lrtPoeAutoPowerResetStartupTime    Integer32,
   sispm1040582lrtPoeAutoPowerResetIntervalTime   Integer32,
   sispm1040582lrtPoeAutoPowerResetRetryTime      Integer32,
   sispm1040582lrtPoeAutoPowerResetFailureLog     DisplayString,
   sispm1040582lrtPoeAutoPowerResetFailureAction  INTEGER,
   sispm1040582lrtPoeAutoPowerResetRebootTime     Integer32,
   sispm1040582lrtPoeAutoPowerResetMaxRebootTimes     Integer32
}

sispm1040582lrtPoeAutoPowerResetPort OBJECT-TYPE
   SYNTAX      Integer32(1..4094)
   MAX-ACCESS  not-accessible
   STATUS      current
   DESCRIPTION
       " port, range : 1 - port number. "
   ::= { sispm1040582lrtPoeAutoPowerResetEntry 1 }

sispm1040582lrtPoeAutoPowerResetPingIPAddress OBJECT-TYPE
   SYNTAX      DisplayString
   MAX-ACCESS  read-write
   STATUS      current
   DESCRIPTION
       "IP Address the system should ping.
        default: 0.0.0.0 . "
   ::= { sispm1040582lrtPoeAutoPowerResetEntry 2 }

sispm1040582lrtPoeAutoPowerResetStartupTime OBJECT-TYPE
   SYNTAX      Integer32(30..600)
   MAX-ACCESS  read-write
   STATUS      current
   DESCRIPTION
       "When PD has been start up, the Switch will wait Start up time to do PoE Auto Checking. default: 60, range: 30-600 sec. "
   ::= { sispm1040582lrtPoeAutoPowerResetEntry 3 }

sispm1040582lrtPoeAutoPowerResetIntervalTime OBJECT-TYPE
   SYNTAX      Integer32(10..120)
   MAX-ACCESS  read-write
   STATUS      current
   DESCRIPTION
       "Device will send checking message to PD each interval time.
        default: 30,
        range: 10-120 sec.  "
   ::= { sispm1040582lrtPoeAutoPowerResetEntry 4 }

sispm1040582lrtPoeAutoPowerResetRetryTime OBJECT-TYPE
   SYNTAX      Integer32(1..5)
   MAX-ACCESS  read-write
   STATUS      current
   DESCRIPTION
       "It will retry to send detection again.
        default: 3,
        range: 1-5.  "
   ::= { sispm1040582lrtPoeAutoPowerResetEntry 5 }

sispm1040582lrtPoeAutoPowerResetFailureLog OBJECT-TYPE
   SYNTAX      DisplayString
   MAX-ACCESS  read-only
   STATUS      current
   DESCRIPTION
       "Failure loggings counter. "
   ::= { sispm1040582lrtPoeAutoPowerResetEntry 6 }

sispm1040582lrtPoeAutoPowerResetFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { sispm1040582lrtPoeAutoPowerResetEntry 7 }

sispm1040582lrtPoeAutoPowerResetRebootTime OBJECT-TYPE
   SYNTAX      Integer32(3..120)
   MAX-ACCESS  read-write
   STATUS      current
   DESCRIPTION
       "When PD has been rebooted, the PoE port restored power after the specified time.
        default: 15,
        range: 3-120 sec. "
   ::= { sispm1040582lrtPoeAutoPowerResetEntry 8 }

sispm1040582lrtPoeAutoPowerResetMaxRebootTimes OBJECT-TYPE
   SYNTAX      Integer32(0..10)
   MAX-ACCESS  read-write
   STATUS      current
   DESCRIPTION
        "When Failure Action is Reboot Remote PD, it limits times of Reboot.
         default: 3,
         range: 0-10. 0 means without reboot limits."
   ::= { sispm1040582lrtPoeAutoPowerResetEntry 10 }

sispm1040582lrtPoeScheduling                                                 OBJECT IDENTIFIER ::= { sispm1040582lrtPoe 4 }

sispm1040582lrtPoeSchedulingProfileNumber OBJECT-TYPE
   SYNTAX      Integer32
   MAX-ACCESS  read-write
   STATUS      current
   DESCRIPTION
       "Specify the PoE Profile Number that want to configure. Range:1-16"
   ::= { sispm1040582lrtPoeScheduling 1 }

sispm1040582lrtPoeSchedulingPorofileName OBJECT-TYPE
   SYNTAX      DisplayString
   MAX-ACCESS  read-write
   STATUS      current
   DESCRIPTION
       "Profile Name. Maximum length:32."
   ::= { sispm1040582lrtPoeScheduling 2 }

sispm1040582lrtPoeSchedulingTimeTable OBJECT-TYPE
   SYNTAX      SEQUENCE OF SISPM1040582LRTPoeSchedulingTimeEntry
   MAX-ACCESS  not-accessible
   STATUS      current
   DESCRIPTION
       " Show Poe Scheduling Time Config. "
   ::= { sispm1040582lrtPoeScheduling 3 }

sispm1040582lrtPoeSchedulingTimeEntry OBJECT-TYPE
   SYNTAX      SISPM1040582LRTPoeSchedulingTimeEntry
   MAX-ACCESS  not-accessible
   STATUS      current
   DESCRIPTION
       " "
   INDEX    { sispm1040582lrtPoeSchedulingTimeWeekIndex  }
   ::= { sispm1040582lrtPoeSchedulingTimeTable 1 }

SISPM1040582LRTPoeSchedulingTimeEntry ::= SEQUENCE {
   sispm1040582lrtPoeSchedulingTimeWeekIndex        Integer32,
   sispm1040582lrtPoeSchedulingTimeStartTimeHourMinute  DisplayString,
   sispm1040582lrtPoeSchedulingTimeEndTimeHourMinute    DisplayString
}

sispm1040582lrtPoeSchedulingTimeWeekIndex OBJECT-TYPE
   SYNTAX      Integer32 (1..7)
   MAX-ACCESS  not-accessible
   STATUS      current
   DESCRIPTION
       "Week Index. 
	   1: Mon, 2:Tue, 3: Wed, 4: Thu, 5: Fri, 6: Sat, 7: Sun"
   ::= { sispm1040582lrtPoeSchedulingTimeEntry 1 }

sispm1040582lrtPoeSchedulingTimeStartTimeHourMinute OBJECT-TYPE
   SYNTAX      DisplayString
   MAX-ACCESS  read-write
   STATUS      current
   DESCRIPTION
       "PoE Scheduling Start Time. Format: HH:MM. Hour Range: 0-23. Minute Range:0,5,10,...,55."
   ::= { sispm1040582lrtPoeSchedulingTimeEntry 2 }

sispm1040582lrtPoeSchedulingTimeEndTimeHourMinute OBJECT-TYPE
   SYNTAX      DisplayString
   MAX-ACCESS  read-write
   STATUS      current
   DESCRIPTION
       "PoE Scheduling End Time. Format: HH:MM. Hour Range: 0-23. Minute Range:0,5,10,...,55."
   ::= { sispm1040582lrtPoeSchedulingTimeEntry 3 }

sispm1040582lrtPoeConfiguration                                                 OBJECT IDENTIFIER ::= { sispm1040582lrtPoe 5 }

--sispm1040582lrtPoeConfigurationPowerManagementMode OBJECT-TYPE
--   SYNTAX      Integer32(0..5)
--   MAX-ACCESS  read-write
--   STATUS      current
--   DESCRIPTION
--       "The power management mode for PoE port.
--        0: CLASS_RESERVED,
--        1: CLASS_CONSUMP,
--        2: ALLOCATED_RESERVED,
--        3: ALLOCATED_CONSUMP,
--        4: LLDPMED_RESERVED,
--        5: LLDPMED_CONSUMP,
--        default: CLASS_RESERVED. "
--   ::= { sispm1040582lrtPoeConfiguration 1 }
   
--sispm1040582lrtPoeConfigurationCapacitorDetection OBJECT-TYPE
--   SYNTAX      Integer32(0..1)
--   MAX-ACCESS  read-write
--   STATUS      current
--   DESCRIPTION
--       "The capacitor detection mode.
--        0: Disable
--        1: Enable
--       "
--   ::= { sispm1040582lrtPoeConfiguration 2 }

--sispm1040582lrtPoeConfigurationPowerExtraMode OBJECT-TYPE
--   SYNTAX      Integer32
--   MAX-ACCESS  read-write
--   STATUS      current
--   DESCRIPTION
--       "The power extra mode for PoE port.
--        0: Normal Mode
--        1: Extra Mode"
--   ::= { sispm1040582lrtPoeConfiguration 3 }
      
sispm1040582lrtPoeConfigurationTable OBJECT-TYPE
   SYNTAX      SEQUENCE OF SISPM1040582LRTPoeConfigurationEntry
   MAX-ACCESS  not-accessible
   STATUS      current
   DESCRIPTION
       " Configure PoE Configuration mode. "
   ::= { sispm1040582lrtPoeConfiguration 4 }

sispm1040582lrtPoeConfigurationEntry OBJECT-TYPE
   SYNTAX      SISPM1040582LRTPoeConfigurationEntry
   MAX-ACCESS  not-accessible
   STATUS      current
   DESCRIPTION
       " "
   INDEX    { sispm1040582lrtPoeConfigurationSwitch  }
   ::= { sispm1040582lrtPoeConfigurationTable 1 }

SISPM1040582LRTPoeConfigurationEntry ::= SEQUENCE {
   sispm1040582lrtPoeConfigurationSwitch	                  Integer32,
   sispm1040582lrtPoeConfigurationPrimaryPowerSupply        Integer32,
   sispm1040582lrtPoeConfigurationAlwaysONPoE        Integer32
}

sispm1040582lrtPoeConfigurationSwitch OBJECT-TYPE
   SYNTAX      Integer32 (1..16)
   MAX-ACCESS  not-accessible
   STATUS      current
   DESCRIPTION
       " switch index, range : 1 - 16. "
   ::= { sispm1040582lrtPoeConfigurationEntry 1 }


sispm1040582lrtPoeConfigurationPrimaryPowerSupply  OBJECT-TYPE
   SYNTAX      Integer32(0..2000)
   MAX-ACCESS  read-only
   STATUS      current
   DESCRIPTION
       "It must be defined what amount of power the primary and backup power sources
        can deliver. "
   ::= { sispm1040582lrtPoeConfigurationEntry 3 }

sispm1040582lrtPoeConfigurationAlwaysONPoE  OBJECT-TYPE
   SYNTAX      Integer32(0..1)
   MAX-ACCESS  read-write
   STATUS      current
   DESCRIPTION
       "Configure always-on-poe"
   ::= { sispm1040582lrtPoeConfigurationEntry 4 }

sispm1040582lrtPoeConfigurationPortTable OBJECT-TYPE
   SYNTAX      SEQUENCE OF SISPM1040582LRTPoeConfigurationPortEntry
   MAX-ACCESS  not-accessible
   STATUS      current
   DESCRIPTION
       " Configure PoE Port Configuration mode. "
   ::= { sispm1040582lrtPoeConfiguration 5 }

sispm1040582lrtPoeConfigurationPortEntry OBJECT-TYPE
   SYNTAX      SISPM1040582LRTPoeConfigurationPortEntry
   MAX-ACCESS  not-accessible
   STATUS      current
   DESCRIPTION
       " "
   INDEX    { sispm1040582lrtPoeConfigurationPort  }
   ::= { sispm1040582lrtPoeConfigurationPortTable 1 }

SISPM1040582LRTPoeConfigurationPortEntry ::= SEQUENCE {
   sispm1040582lrtPoeConfigurationPort	       Integer32,
   sispm1040582lrtPoeConfigurationPortPoEMode       INTEGER,
   sispm1040582lrtPoeConfigurationPortPriority      INTEGER,
-- sispm1040582lrtPoeConfigurationPortMaximumPower  DisplayString,
-- sispm1040582lrtPoeConfigurationPortDetection     Integer32,
-- sispm1040582lrtPoeConfigurationPortPoEScheduleByProfileID     Integer32,
   sispm1040582lrtPoeConfigurationPortPoEScheduleByProfileName   DisplayString,
   sispm1040582lrtPoeConfigurationlldp              Integer32,
   sispm1040582lrtPoeConfigurationlegacy              Integer32
}

sispm1040582lrtPoeConfigurationPort OBJECT-TYPE
   SYNTAX      Integer32
   MAX-ACCESS  not-accessible
   STATUS      current
   DESCRIPTION
       " port, range : 1 - port number. "
   ::= { sispm1040582lrtPoeConfigurationPortEntry 1 }

sispm1040582lrtPoeConfigurationPortPoEMode OBJECT-TYPE
   SYNTAX      INTEGER { disable(0), fourpair60w(1), fourpair90w(2), bt8023w90(3), bt8023w60(4), bt8023w30(5), force90w(6), force60w(7)}
   MAX-ACCESS  read-write
   STATUS      current
   DESCRIPTION
       "The PoE Mode represents the PoE operating mode for the port.
        0: Disable,
        1: 4-pair-60w,
        2: 4-pair-90w,
        3: 802.3bt-90w,
        4: 802.3bt-60w,
        5: 802.3bt-30w,
        6: force-90w,
        7: force-60w
        default: 802.3bt-60w. "
   ::= { sispm1040582lrtPoeConfigurationPortEntry 2 }

sispm1040582lrtPoeConfigurationPortPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { sispm1040582lrtPoeConfigurationPortEntry 3 }

--sispm1040582lrtPoeConfigurationPortMaximumPower OBJECT-TYPE
--   SYNTAX      DisplayString
--   MAX-ACCESS  read-write
--   STATUS      current
--   DESCRIPTION
--       "The Maximum Power value contains a numerical value that indicates the maximum
--        power in watts that can be delivered to a remote device.
--        max: 90[W]. "
--   ::= { sispm1040582lrtPoeConfigurationPortEntry 4 }

--sispm1040582lrtPoeConfigurationPortDetection OBJECT-TYPE
--   SYNTAX      Integer32(1..5)
--   MAX-ACCESS  read-write
--   STATUS      current
--   DESCRIPTION
--       "The Detection represents the PoE capacitor detection for the port.
--	      -1:Not support.
--	   1:Legacy : Legacy capacitive detection only.
--	   2:4-point : IEEE 802.3af 4-point detection only.
--	   3:4-point-legacy : IEEE 802.3af 4-point detection followed by Legacy detection.
--	   4:2-point : IEEE 802.3af 2-point detection only.
--	   5:2-point-legacy : IEEE 802.3af 2-point detection followed by Legacy detection.
--	   "
--   ::= { sispm1040582lrtPoeConfigurationPortEntry 5 }

-- sispm1040582lrtPoeConfigurationPortPoEScheduleByProfileID OBJECT-TYPE
--   SYNTAX      Integer32(0..16)
--   MAX-ACCESS  read-write
--   STATUS      current
--   DESCRIPTION
--       "Specify a valid PoE schedule profile by profile id. 0:disable,1-16:1-16 profile."
--   ::= { sispm1040582lrtPoeConfigurationPortEntry 6 }
   
sispm1040582lrtPoeConfigurationPortPoEScheduleByProfileName OBJECT-TYPE
   SYNTAX      DisplayString
   MAX-ACCESS  read-write
   STATUS      current
   DESCRIPTION
       "Specify a valid PoE schedule profile by profile name. disabled: disable profile schedule."
   ::= { sispm1040582lrtPoeConfigurationPortEntry 7 }   

sispm1040582lrtPoeConfigurationlldp OBJECT-TYPE
   SYNTAX      Integer32(0..1)
   MAX-ACCESS  read-write
   STATUS      current
   DESCRIPTION
       "Use poe lldp to enable PoE lldp functionality. 
	   0: Enable
        1: Disable"
   ::= { sispm1040582lrtPoeConfigurationPortEntry 8 }

sispm1040582lrtPoeConfigurationlegacy OBJECT-TYPE
   SYNTAX      Integer32(0..1)
   MAX-ACCESS  read-write
   STATUS      current
   DESCRIPTION
       "Use poe legacy to enable PoE legacy functionality. 
	   0: Enable
        1: Disable"
   ::= { sispm1040582lrtPoeConfigurationPortEntry 9 }
   
sispm1040582lrtPoeChipsetRebootSchedule OBJECT IDENTIFIER ::= { sispm1040582lrtPoe 6 }  

sispm1040582lrtPoeChipsetRebootMode OBJECT-TYPE
   SYNTAX      Integer32
   MAX-ACCESS  read-write
   STATUS      current
   DESCRIPTION
       "PoE Chipset Reboot Mode
	    0:disable
		1:enable"
   ::= { sispm1040582lrtPoeChipsetRebootSchedule 1 }

sispm1040582lrtPoeChipsetRebootTimeTable OBJECT-TYPE
   SYNTAX      SEQUENCE OF SISPM1040582LRTPoeChipsetRebootTimeEntry
   MAX-ACCESS  not-accessible
   STATUS      current
   DESCRIPTION
       " Configure PoE Chipset Reboot Time."
   ::= { sispm1040582lrtPoeChipsetRebootSchedule 2 }

sispm1040582lrtPoeChipsetRebootTimeEntry OBJECT-TYPE
   SYNTAX      SISPM1040582LRTPoeChipsetRebootTimeEntry
   MAX-ACCESS  not-accessible
   STATUS      current
   DESCRIPTION
       " "
   INDEX    { sispm1040582lrtPoeChipsetRebootWeekIndex  }
   ::= { sispm1040582lrtPoeChipsetRebootTimeTable 1 }

SISPM1040582LRTPoeChipsetRebootTimeEntry ::= SEQUENCE {
   sispm1040582lrtPoeChipsetRebootWeekIndex	       Integer32,
   sispm1040582lrtPoeChipsetRebootTimeHour           Integer32,
   sispm1040582lrtPoeChipsetRebootTimeMinute         Integer32
}

sispm1040582lrtPoeChipsetRebootWeekIndex OBJECT-TYPE
   SYNTAX      Integer32 (1..7)
   MAX-ACCESS  not-accessible
   STATUS      current
   DESCRIPTION
       "PoE chipset reboot week index.
	   1: Mon, 2:Tue, 3: Wed, 4: Thu, 5: Fri, 6: Sat, 7: Sun"
   ::= { sispm1040582lrtPoeChipsetRebootTimeEntry 1 }

sispm1040582lrtPoeChipsetRebootTimeHour OBJECT-TYPE
   SYNTAX      Integer32 (-1..23)
   MAX-ACCESS  read-write
   STATUS      current
   DESCRIPTION
       "PoE Chipset Reboot Time (Hour). Range: 0-23. 
	   -1:disable"
   ::= { sispm1040582lrtPoeChipsetRebootTimeEntry 2 }

sispm1040582lrtPoeChipsetRebootTimeMinute OBJECT-TYPE
   SYNTAX      Integer32 (-1..55)
   MAX-ACCESS  read-write
   STATUS      current
   DESCRIPTION
       "PoE Chipset Reboot Time (Minute). Range:0,5,10,...,55. 
	   -1:disable"
   ::= { sispm1040582lrtPoeChipsetRebootTimeEntry 3 }
   
-- =======================================================================================================================
-- RowStatus Info:  createAndWait, notReady, notInService not supported.
-- =======================================================================================================================
-- Textual Conventions for the sispm1040582lrt AAA Mib
-- =======================================================================================================================
--
sispm1040582lrtAAAMIB                   OBJECT IDENTIFIER  ::= { sispm1040582lrtConfiguration 15 }
    sispm1040582lrtAAA                  OBJECT IDENTIFIER  ::= { sispm1040582lrtAAAMIB 1 }
    sispm1040582lrtRADIUS               OBJECT IDENTIFIER  ::= { sispm1040582lrtAAA 1 }
    sispm1040582lrtRADIUSGlobalConfig   OBJECT IDENTIFIER  ::= { sispm1040582lrtRADIUS 1 }

    sispm1040582lrtTACACS               OBJECT IDENTIFIER  ::= { sispm1040582lrtAAA 2 }

--
-- =======================================================================================================================
-- Start sispm1040582lrtRADIUS group
-- =======================================================================================================================
--sispm1040582lrtRADIUSGlobalConfig

    sispm1040582lrtRADIUSGlobalConfigTimeout OBJECT-TYPE
               SYNTAX      Integer32(1..1000)
               MAX-ACCESS  read-write
               STATUS      current
               DESCRIPTION
                   "Timeout is the number of seconds, to wait for a reply
                    from a RADIUS server before retransmitting the request.
                    range: 1-1000."
               ::= {     sispm1040582lrtRADIUSGlobalConfig 1 }

    sispm1040582lrtRADIUSGlobalConfigRetransmit OBJECT-TYPE
               SYNTAX      Integer32(1..1000)
               MAX-ACCESS  read-write
               STATUS      current
               DESCRIPTION
                   "Retransmit is the number of times,a RADIUS request is
                    retransmitted to a server that is not responding.If the
                    server has not responded after the last retransmit it is
                    considered to be dead.
                    range: 1-1000."
               ::= {     sispm1040582lrtRADIUSGlobalConfig 2 }

    sispm1040582lrtRADIUSGlobalConfigDeadtime OBJECT-TYPE
               SYNTAX      Integer32(0..1440)
               MAX-ACCESS  read-write
               STATUS      current
               DESCRIPTION
                   "This will stop the switch from continually trying to
                    contact a server that it has already determined as dead.
                    range: 0-1440."
               ::= {     sispm1040582lrtRADIUSGlobalConfig 3 }

    sispm1040582lrtRADIUSGlobalConfigKey OBJECT-TYPE
               SYNTAX      DisplayString
               MAX-ACCESS  read-write
               STATUS      current
               DESCRIPTION
                   "The secret key shared between the RADIUS server and
                    the switch."
               ::= {     sispm1040582lrtRADIUSGlobalConfig 4 }

    sispm1040582lrtRADIUSGlobalConfigNASIPv4 OBJECT-TYPE
               SYNTAX      IpAddress
               MAX-ACCESS  read-write
               STATUS      current
               DESCRIPTION
                   "The IPv4 address to be used as attribute 4 in RADIUS
                    Access-Request packets."
               ::= {     sispm1040582lrtRADIUSGlobalConfig 5 }

    sispm1040582lrtRADIUSGlobalConfigNASIPv6 OBJECT-TYPE
               SYNTAX      DisplayString
               MAX-ACCESS  read-write
               STATUS      current
               DESCRIPTION
                   "The IPv6 address to be used as attribute 95 in RADIUS
                    Access-Request packets. "
               ::= {     sispm1040582lrtRADIUSGlobalConfig 6 }

    sispm1040582lrtRADIUSGlobalConfigNASIdentifier OBJECT-TYPE
               SYNTAX      DisplayString
               MAX-ACCESS  read-write
               STATUS      current
               DESCRIPTION
                   "The identifier to be used as attribute 32 in RADIUS
                    Access-Request packets. "
               ::= {     sispm1040582lrtRADIUSGlobalConfig 7 }

--sispm1040582lrtRADIUSServerConfigTable

    sispm1040582lrtRADIUSServerConfigTable OBJECT-TYPE
               SYNTAX      SEQUENCE OF     SISPM1040582LRTRADIUSServerConfigEntry
               MAX-ACCESS  not-accessible
               STATUS      current
               DESCRIPTION
                   "The RADIUS Server Configuration Table."
               ::= {     sispm1040582lrtRADIUS 2 }

    sispm1040582lrtRADIUSServerConfigEntry OBJECT-TYPE
               SYNTAX          SISPM1040582LRTRADIUSServerConfigEntry
               MAX-ACCESS  not-accessible
               STATUS      current
               DESCRIPTION
                   "The RADIUS Server Configuration Entry."
               INDEX    {    sispm1040582lrtRADIUSServerConfServerNo  }
               ::= {     sispm1040582lrtRADIUSServerConfigTable 1 }

    SISPM1040582LRTRADIUSServerConfigEntry             ::= SEQUENCE {
                 sispm1040582lrtRADIUSServerConfServerNo      Integer32,
                 sispm1040582lrtRADIUSServerConfHostname      DisplayString,
                 sispm1040582lrtRADIUSServerConfAuthPort      Integer32,
                 sispm1040582lrtRADIUSServerConfAcctPort      Integer32,
                 sispm1040582lrtRADIUSServerConfTimeout       Integer32,
                 sispm1040582lrtRADIUSServerConfRetransmit    Integer32,
                 sispm1040582lrtRADIUSServerConfKey           DisplayString,
                 sispm1040582lrtRADIUSServerConfRowStatus     RowStatus
                 }

    sispm1040582lrtRADIUSServerConfServerNo OBJECT-TYPE
               SYNTAX      Integer32(1..5)
               MAX-ACCESS  not-accessible
               STATUS      current
               DESCRIPTION
                   "The RADIUS server number.
                    max: 5."
               ::= {     sispm1040582lrtRADIUSServerConfigEntry 1 }

    sispm1040582lrtRADIUSServerConfHostname OBJECT-TYPE
               SYNTAX      DisplayString
               MAX-ACCESS  read-create
               STATUS      current
               DESCRIPTION
                   "The IP address or hostname of the RADIUS server. "
               ::= {     sispm1040582lrtRADIUSServerConfigEntry 2 }

    sispm1040582lrtRADIUSServerConfAuthPort OBJECT-TYPE
               SYNTAX      Integer32(0..65535)
               MAX-ACCESS  read-create
               STATUS      current
               DESCRIPTION
                   "The UDP port to use on the RADIUS server for
                    authentication.
                    range: 0-65535. "
               ::= {     sispm1040582lrtRADIUSServerConfigEntry 3 }

    sispm1040582lrtRADIUSServerConfAcctPort OBJECT-TYPE
               SYNTAX      Integer32(0..65535)
               MAX-ACCESS  read-create
               STATUS      current
               DESCRIPTION
                   "The UDP port to use on the RADIUS server for accounting.
                    range: 0-65535. "
               ::= {     sispm1040582lrtRADIUSServerConfigEntry 4 }

    sispm1040582lrtRADIUSServerConfTimeout OBJECT-TYPE
               SYNTAX      Integer32(1..1000)
               MAX-ACCESS  read-create
               STATUS      current
               DESCRIPTION
                   "This optional setting overrides the global timeout value.
                    Leaving it blank will use the global timeout value.
                    range: 1-1000. "
               ::= {     sispm1040582lrtRADIUSServerConfigEntry 5 }

    sispm1040582lrtRADIUSServerConfRetransmit OBJECT-TYPE
               SYNTAX      Integer32(1..1000)
               MAX-ACCESS  read-create
               STATUS      current
               DESCRIPTION
                   "This optional setting overrides the global retransmit value.
                    Leaving it blank will use the global retransmit value.
                    range: 1-1000. "
               ::= {     sispm1040582lrtRADIUSServerConfigEntry 6 }

    sispm1040582lrtRADIUSServerConfKey OBJECT-TYPE
               SYNTAX      DisplayString
               MAX-ACCESS  read-create
               STATUS      current
               DESCRIPTION
                   "This optional setting overrides the global key. Leaving
                    it blank will use the global key."
               ::= {     sispm1040582lrtRADIUSServerConfigEntry 7 }

    sispm1040582lrtRADIUSServerConfRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm1040582lrtRADIUSServerConfigEntry 8 }

--sispm1040582lrtRADIUSDetailTable

    sispm1040582lrtRADIUSDetailTable OBJECT-TYPE
               SYNTAX      SEQUENCE OF     SISPM1040582LRTRADIUSDetailEntry
               MAX-ACCESS  not-accessible
               STATUS      current
               DESCRIPTION
                   "The RADIUS Detail Table."
               ::= {     sispm1040582lrtRADIUS 3 }

    sispm1040582lrtRADIUSDetailEntry OBJECT-TYPE
               SYNTAX          SISPM1040582LRTRADIUSDetailEntry
               MAX-ACCESS  not-accessible
               STATUS      current
               DESCRIPTION
                   "The RADIUS Detail Entry."
               INDEX    {    sispm1040582lrtRADIUSServerConfServerNo  }
               ::= {     sispm1040582lrtRADIUSDetailTable 1 }

    SISPM1040582LRTRADIUSDetailEntry             ::= SEQUENCE {
                 sispm1040582lrtRADIUSAuthIPAddress               DisplayString,
                 sispm1040582lrtRADIUSAuthStatus                  DisplayString,
                 sispm1040582lrtRADIUSAuthRoundTripTime           Integer32,
                 sispm1040582lrtRADIUSAuthRxAccessAccept          Counter32,
                 sispm1040582lrtRADIUSAuthRxAccessReject          Counter32,
                 sispm1040582lrtRADIUSAuthRxAccessChallenge       Counter32,
                 sispm1040582lrtRADIUSAuthRxAccessResponse        Counter32,
                 sispm1040582lrtRADIUSAuthRxBadAuth               Counter32,
                 sispm1040582lrtRADIUSAuthRxUnknownType           Counter32,
                 sispm1040582lrtRADIUSAuthRxPacketsDropped        Counter32,
                 sispm1040582lrtRADIUSAuthTxAccessRequest         Counter32,
                 sispm1040582lrtRADIUSAuthTxAccessRetransmission  Counter32,
                 sispm1040582lrtRADIUSAuthTxPendingRequest        Counter32,
                 sispm1040582lrtRADIUSAuthTxTimeout               Counter32,
                 sispm1040582lrtRADIUSAccountIPAddress            IpAddress,
                 sispm1040582lrtRADIUSAccountStatus               DisplayString,
                 sispm1040582lrtRADIUSAccountRoundTripTime        Integer32,
                 sispm1040582lrtRADIUSAccountRxResponses          Counter32,
                 sispm1040582lrtRADIUSAccountRxMalformedResponse  Counter32,
                 sispm1040582lrtRADIUSAccountRxBadAuth            Counter32,
                 sispm1040582lrtRADIUSAccountRxUnknownType        Counter32,
                 sispm1040582lrtRADIUSAccountRxPacketsDrop        Counter32,
                 sispm1040582lrtRADIUSAccountTxRequest            Counter32,
                 sispm1040582lrtRADIUSAccountTxRetransmission     Counter32,
                 sispm1040582lrtRADIUSAccountTxPendingRequest     Counter32,
                 sispm1040582lrtRADIUSAccountTxTimeout            Counter32,
                 sispm1040582lrtRADIUSDetailClearCmd              ActivateCmd
                 }

    sispm1040582lrtRADIUSAuthIPAddress OBJECT-TYPE
               SYNTAX      DisplayString
               MAX-ACCESS  read-only
               STATUS      current
               DESCRIPTION
                   "IP address and UDP port for the authentication
                    server in question."
               ::= {     sispm1040582lrtRADIUSDetailEntry 2 }

    sispm1040582lrtRADIUSAuthStatus OBJECT-TYPE
               SYNTAX      DisplayString
               MAX-ACCESS  read-only
               STATUS      current
               DESCRIPTION
                   "Shows the state of the server."
               ::= {     sispm1040582lrtRADIUSDetailEntry 3 }

    sispm1040582lrtRADIUSAuthRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sispm1040582lrtRADIUSDetailEntry 4 }

    sispm1040582lrtRADIUSAuthRxAccessAccept OBJECT-TYPE
               SYNTAX      Counter32
               MAX-ACCESS  read-only
               STATUS      current
               DESCRIPTION
                   "The number of RADIUS Access-Accept packets
                   (valid or invalid) received from the server."
               ::= {     sispm1040582lrtRADIUSDetailEntry 5 }

    sispm1040582lrtRADIUSAuthRxAccessReject OBJECT-TYPE
               SYNTAX      Counter32
               MAX-ACCESS  read-only
               STATUS      current
               DESCRIPTION
                   "The number of RADIUS Access-Reject packets
                    (valid or invalid) received from the server."
               ::= {     sispm1040582lrtRADIUSDetailEntry 6 }

    sispm1040582lrtRADIUSAuthRxAccessChallenge OBJECT-TYPE
               SYNTAX      Counter32
               MAX-ACCESS  read-only
               STATUS      current
               DESCRIPTION
                   "The number of RADIUS Access-Challenge packets
                    (valid or invalid) received from the server."
               ::= {     sispm1040582lrtRADIUSDetailEntry 7 }

    sispm1040582lrtRADIUSAuthRxAccessResponse OBJECT-TYPE
               SYNTAX      Counter32
               MAX-ACCESS  read-only
               STATUS      current
               DESCRIPTION
                   "The number of malformed RADIUS Access-Response
                    packets received from the server."
               ::= {     sispm1040582lrtRADIUSDetailEntry 8 }

    sispm1040582lrtRADIUSAuthRxBadAuth OBJECT-TYPE
               SYNTAX      Counter32
               MAX-ACCESS  read-only
               STATUS      current
               DESCRIPTION
                   "The number of RADIUS Access-Response packets containing
                    invalid authenticators or Message Authenticator
                    attributes received from the server."
               ::= {     sispm1040582lrtRADIUSDetailEntry 9 }

    sispm1040582lrtRADIUSAuthRxUnknownType OBJECT-TYPE
               SYNTAX      Counter32
               MAX-ACCESS  read-only
               STATUS      current
               DESCRIPTION
                   "The number of RADIUS packets that were received with
                    unknown types from the server on the authentication
                    port and dropped."
               ::= {     sispm1040582lrtRADIUSDetailEntry 10 }

    sispm1040582lrtRADIUSAuthRxPacketsDropped OBJECT-TYPE
               SYNTAX      Counter32
               MAX-ACCESS  read-only
               STATUS      current
               DESCRIPTION
                   "The number of RADIUS packets that were received from
                    the server on the authentication port and dropped for
                    some other reason."
               ::= {     sispm1040582lrtRADIUSDetailEntry 11 }

    sispm1040582lrtRADIUSAuthTxAccessRequest OBJECT-TYPE
               SYNTAX      Counter32
               MAX-ACCESS  read-only
               STATUS      current
               DESCRIPTION
                   "The number of RADIUS Access-Request packets sent to
                    the server. This does not include retransmissions."
               ::= {     sispm1040582lrtRADIUSDetailEntry 12 }

    sispm1040582lrtRADIUSAuthTxAccessRetransmission OBJECT-TYPE
               SYNTAX      Counter32
               MAX-ACCESS  read-only
               STATUS      current
               DESCRIPTION
                   "The number of RADIUS Access-Request packets
                    retransmitted to the RADIUS authentication server."
               ::= {     sispm1040582lrtRADIUSDetailEntry 13 }

    sispm1040582lrtRADIUSAuthTxPendingRequest OBJECT-TYPE
               SYNTAX      Counter32
               MAX-ACCESS  read-only
               STATUS      current
               DESCRIPTION
                   "The number of RADIUS Access-Request packets destined
                    for the server that have not yet timed out or received
                    a response. "
               ::= {     sispm1040582lrtRADIUSDetailEntry 14 }

    sispm1040582lrtRADIUSAuthTxTimeout OBJECT-TYPE
               SYNTAX      Counter32
               MAX-ACCESS  read-only
               STATUS      current
               DESCRIPTION
                   "The number of authentication timeouts to the server.
                    After a timeout, the client may retry to the same server,
                    send to a different server, or give up."
               ::= {     sispm1040582lrtRADIUSDetailEntry 15 }

    sispm1040582lrtRADIUSAccountIPAddress OBJECT-TYPE
               SYNTAX      IpAddress
               MAX-ACCESS  read-only
               STATUS      current
               DESCRIPTION
                   "IP address and UDP port for the authentication server
                    in question."
               ::= {     sispm1040582lrtRADIUSDetailEntry 16 }

    sispm1040582lrtRADIUSAccountStatus OBJECT-TYPE
               SYNTAX      DisplayString
               MAX-ACCESS  read-only
               STATUS      current
               DESCRIPTION
                   "Shows the state of the server. "
               ::= {     sispm1040582lrtRADIUSDetailEntry 17 }

    sispm1040582lrtRADIUSAccountRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sispm1040582lrtRADIUSDetailEntry 18 }

    sispm1040582lrtRADIUSAccountRxResponses OBJECT-TYPE
               SYNTAX      Counter32
               MAX-ACCESS  read-only
               STATUS      current
               DESCRIPTION
                   "The number of RADIUS packets (valid or invalid)
                    received from the server."
               ::= {     sispm1040582lrtRADIUSDetailEntry 19 }

    sispm1040582lrtRADIUSAccountRxMalformedResponse OBJECT-TYPE
               SYNTAX      Counter32
               MAX-ACCESS  read-only
               STATUS      current
               DESCRIPTION
                   "The number of malformed RADIUS packets received from
                    the server. "
               ::= {     sispm1040582lrtRADIUSDetailEntry 20 }

    sispm1040582lrtRADIUSAccountRxBadAuth OBJECT-TYPE
               SYNTAX      Counter32
               MAX-ACCESS  read-only
               STATUS      current
               DESCRIPTION
                   "The number of RADIUS packets containing invalid
                    authenticators received from the server."
               ::= {     sispm1040582lrtRADIUSDetailEntry 21 }

    sispm1040582lrtRADIUSAccountRxUnknownType OBJECT-TYPE
               SYNTAX      Counter32
               MAX-ACCESS  read-only
               STATUS      current
               DESCRIPTION
                   "The number of RADIUS packets of unknown types that were
                    received from the server on the accounting port. "
               ::= {     sispm1040582lrtRADIUSDetailEntry 22 }

    sispm1040582lrtRADIUSAccountRxPacketsDrop OBJECT-TYPE
               SYNTAX      Counter32
               MAX-ACCESS  read-only
               STATUS      current
               DESCRIPTION
                   "The number of RADIUS packets that were received from
                    the server on the accounting port and dropped for some
                    other reason."
               ::= {     sispm1040582lrtRADIUSDetailEntry 23 }

    sispm1040582lrtRADIUSAccountTxRequest OBJECT-TYPE
               SYNTAX      Counter32
               MAX-ACCESS  read-only
               STATUS      current
               DESCRIPTION
                   "The number of RADIUS packets sent to the server.
                    This does not include retransmissions."
               ::= {     sispm1040582lrtRADIUSDetailEntry 24 }

    sispm1040582lrtRADIUSAccountTxRetransmission OBJECT-TYPE
               SYNTAX      Counter32
               MAX-ACCESS  read-only
               STATUS      current
               DESCRIPTION
                   "The number of RADIUS packets retransmitted to the RADIUS
                    accounting server."
               ::= {     sispm1040582lrtRADIUSDetailEntry 25 }

    sispm1040582lrtRADIUSAccountTxPendingRequest OBJECT-TYPE
               SYNTAX      Counter32
               MAX-ACCESS  read-only
               STATUS      current
               DESCRIPTION
                   "The number of RADIUS packets destined for the server
                    that have not yet timed out or received a response."
               ::= {     sispm1040582lrtRADIUSDetailEntry 26 }

    sispm1040582lrtRADIUSAccountTxTimeout OBJECT-TYPE
               SYNTAX      Counter32
               MAX-ACCESS  read-only
               STATUS      current
               DESCRIPTION
                   "The number of accounting timeouts to the server.
                    After a timeout, the client may retry to the same
                    server, send to a different server, or give up."
               ::= {     sispm1040582lrtRADIUSDetailEntry 27 }

    sispm1040582lrtRADIUSDetailClearCmd OBJECT-TYPE
               SYNTAX      ActivateCmd
               MAX-ACCESS  read-only
               STATUS      current
               DESCRIPTION
                   "Clears the counters for the selected server."
               ::= {     sispm1040582lrtRADIUSDetailEntry 28 }

--
-- =======================================================================================================================
-- Start sispm1040582lrtTACACS group
-- =======================================================================================================================
--sispm1040582lrtTACACSGlobalConfig

    sispm1040582lrtTACACSGlobalConfigTimeout OBJECT-TYPE
               SYNTAX      Integer32(1..1000)
               MAX-ACCESS  read-write
               STATUS      current
               DESCRIPTION
                   "Timeout is the number of seconds,to wait for a reply
                    from a TACACS+ server before it is considered to be dead.
                    range: 1-1000 seconds,
                    default: 5 seconds."
               ::= {     sispm1040582lrtTACACS 1 }

    sispm1040582lrtTACACSGlobalConfigDeadtime OBJECT-TYPE
               SYNTAX      Integer32(0..1440)
               MAX-ACCESS  read-write
               STATUS      current
               DESCRIPTION
                   "The period during which the switch will not send new
                    requests to a server that has failed to respond to a
                    previous request. This will stop the switch from
                    continually trying to contact a server that it has
                    already determined as dead.
                    range: 0-1440 minutes,
                    default: 0 minutes."
               ::= {     sispm1040582lrtTACACS 2 }

    sispm1040582lrtTACACSGlobalConfigKey OBJECT-TYPE
               SYNTAX      DisplayString
               MAX-ACCESS  read-write
               STATUS      current
               DESCRIPTION
                   "The secret key shared between the TACACS+ server and
                    the switch."
               ::= {     sispm1040582lrtTACACS 3 }

--sispm1040582lrtTACACSServerConfigTable

    sispm1040582lrtTACACSServerConfigTable OBJECT-TYPE
               SYNTAX      SEQUENCE OF     SISPM1040582LRTTACACSServerConfigEntry
               MAX-ACCESS  not-accessible
               STATUS      current
               DESCRIPTION
                   "The TACACS Server configuration Table."
               ::= {     sispm1040582lrtTACACS 4 }

    sispm1040582lrtTACACSServerConfigEntry OBJECT-TYPE
               SYNTAX          SISPM1040582LRTTACACSServerConfigEntry
               MAX-ACCESS  not-accessible
               STATUS      current
               DESCRIPTION
                   "The TACACS Server configuration Entry."
               INDEX    {    sispm1040582lrtTACACSServerConfigServerNo  }
               ::= {     sispm1040582lrtTACACSServerConfigTable 1 }

    SISPM1040582LRTTACACSServerConfigEntry             ::= SEQUENCE {
                 sispm1040582lrtTACACSServerConfigServerNo        Integer32,
                 sispm1040582lrtTACACSServerConfigHostname        DisplayString,
                 sispm1040582lrtTACACSServerConfigPort            Integer32,
                 sispm1040582lrtTACACSServerConfigTimeout         Integer32,
                 sispm1040582lrtTACACSServerConfigKey             DisplayString,
                 sispm1040582lrtTACACSServerConfigRowStatus       RowStatus
                 }

    sispm1040582lrtTACACSServerConfigServerNo OBJECT-TYPE
               SYNTAX      Integer32(1..5)
               MAX-ACCESS  not-accessible
               STATUS      current
               DESCRIPTION
                   "The TACACS server number.
                    max: 5."
               ::= {     sispm1040582lrtTACACSServerConfigEntry 1 }

    sispm1040582lrtTACACSServerConfigHostname OBJECT-TYPE
               SYNTAX      DisplayString
               MAX-ACCESS  read-create
               STATUS      current
               DESCRIPTION
                   "The IP address or hostname of the TACACS+ server."
               ::= {     sispm1040582lrtTACACSServerConfigEntry 2 }

    sispm1040582lrtTACACSServerConfigPort OBJECT-TYPE
               SYNTAX      Integer32(0..65535)
               MAX-ACCESS  read-create
               STATUS      current
               DESCRIPTION
                   "The TCP port to use on the TACACS+ server for
                    authentication."
               ::= {     sispm1040582lrtTACACSServerConfigEntry 3 }

    sispm1040582lrtTACACSServerConfigTimeout OBJECT-TYPE
               SYNTAX      Integer32(1..1000)
               MAX-ACCESS  read-create
               STATUS      current
               DESCRIPTION
                   "This optional setting overrides the global timeout
                    value. Leaving it blank will use the global timeout
                    value.
                    range: 1-1000."
               ::= {     sispm1040582lrtTACACSServerConfigEntry 4 }

    sispm1040582lrtTACACSServerConfigKey OBJECT-TYPE
               SYNTAX      DisplayString
               MAX-ACCESS  read-create
               STATUS      current
               DESCRIPTION
                   "This optional setting overrides the global key.
                    Leaving it blank will use the global key. "
               ::= {     sispm1040582lrtTACACSServerConfigEntry 5 }

    sispm1040582lrtTACACSServerConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm1040582lrtTACACSServerConfigEntry 6 }

-- =======================================================================================================================
--
-- =======================================================================================================================
-- Textual Conventions for the sispm1040582lrt Nas Mib
-- =======================================================================================================================
--
sispm1040582lrtNasMIB                   OBJECT IDENTIFIER  ::= { sispm1040582lrtConfiguration 16 }
    sispm1040582lrtNAS                  OBJECT IDENTIFIER  ::= { sispm1040582lrtNasMIB 1 }
    sispm1040582lrtNASConf              OBJECT IDENTIFIER  ::= { sispm1040582lrtNAS 1 }
    sispm1040582lrtNASStatus            OBJECT IDENTIFIER  ::= { sispm1040582lrtNAS 2 }

--
-- =======================================================================================================================
-- Start sispm1040582lrtNAS group
-- =======================================================================================================================
--sispm1040582lrtNASConf

    sispm1040582lrtNASConfMode OBJECT-TYPE
               SYNTAX      AdminMode
               MAX-ACCESS  read-write
               STATUS      current
               DESCRIPTION
                   "Indicates if NAS is globally enabled or disabled on
                    the switch."
               DEFVAL  { disable }
               ::= {     sispm1040582lrtNASConf 1 }

    sispm1040582lrtNASConfReauthenticationEnabled OBJECT-TYPE
               SYNTAX      AdminMode
               MAX-ACCESS  read-write
               STATUS      current
               DESCRIPTION
                   "If enable, successfully authenticated supplicants/clients
                    are reauthenticated after the interval specified by the
                    Reauthentication Period."
               DEFVAL  { disable }
               ::= {     sispm1040582lrtNASConf 2 }

    sispm1040582lrtNASConfReauthenticationPeriod OBJECT-TYPE
               SYNTAX      Integer32(1..3600)
               MAX-ACCESS  read-write
               STATUS      current
               DESCRIPTION
                   "Determines the period, in seconds, after which a
                    connected client must be reauthenticated.
                    default: 3600 sec,
                    range: 1-3600 sec."
               ::= {     sispm1040582lrtNASConf 3 }

    sispm1040582lrtNASConfEAPOLTimeout OBJECT-TYPE
               SYNTAX      Integer32(1..65535)
               MAX-ACCESS  read-write
               STATUS      current
               DESCRIPTION
                   "Determines the time for retransmission of Request
                    Identity EAPOL frames.
                    default: 30 sec,
                    range: 1-65535 sec."
               ::= {     sispm1040582lrtNASConf 4 }

    sispm1040582lrtNASConfAgingPeriod OBJECT-TYPE
               SYNTAX      Integer32(0|10..1000000)
               MAX-ACCESS  read-write
               STATUS      current
               DESCRIPTION
                   "When the NAS module uses the Port Security module to
                    secure MAC addresses, the Port Security module needs to
                    check for activity on the MAC address in question at regular
                    intervals and free resources if no activity is seen within
                    a given period of time.
                    default: 300 sec,
                    0: no support.
                    range: 0,10-1000000 sec."
               ::= {     sispm1040582lrtNASConf 5 }

    sispm1040582lrtNASConfHoldTime OBJECT-TYPE
               SYNTAX      Integer32(0|10..1000000)
               MAX-ACCESS  read-write
               STATUS      current
               DESCRIPTION
                   "If a client is denied access - either because the RADIUS
                    server denies the client access or because the RADIUS server
                    request times out - the client is put on hold in the
                    Unauthorized state.
                    default: 10 sec,
                    0: no support.
                    range: 0,10-1000000 sec."
               ::= {     sispm1040582lrtNASConf 6 }

    sispm1040582lrtNASConfRADIUSQoSEnabled OBJECT-TYPE
               SYNTAX      AdminMode
               MAX-ACCESS  read-write
               STATUS      current
               DESCRIPTION
                   "RADIUS-assigned QoS provides a means to centrally control
                    the traffic class to which traffic coming from a successfully
                    authenticated supplicant is assigned on the switch."
               DEFVAL  { disable }
               ::= {     sispm1040582lrtNASConf 7 }

    sispm1040582lrtNASConfRADIUSVLANEnabled OBJECT-TYPE
               SYNTAX      AdminMode
               MAX-ACCESS  read-write
               STATUS      current
               DESCRIPTION
                   "RADIUS-assigned VLAN provides a means to centrally control
                    the VLAN on which a successfully authenticated supplicant
                    is placed on the switch."
               DEFVAL  { disable }
               ::= {     sispm1040582lrtNASConf 8 }

    sispm1040582lrtNASConfGuestVLANEnabled OBJECT-TYPE
               SYNTAX      AdminMode
               MAX-ACCESS  read-write
               STATUS      current
               DESCRIPTION
                   "A Guest VLAN is a special VLAN - typically with limited
                    network access - on which 802.1X-unaware clients are placed
                    after a network administrator-defined timeout."
               DEFVAL  { disable }
               ::= {     sispm1040582lrtNASConf 9 }

    sispm1040582lrtNASConfGuestVLANID OBJECT-TYPE
               SYNTAX      Integer32(1..4095)
               MAX-ACCESS  read-write
               STATUS      current
               DESCRIPTION
                   "This is the value that a port's Port VLAN ID is set to if
                    a port is moved into the Guest VLAN.
                    default: 1,
                    range: 1-4095."
               ::= {     sispm1040582lrtNASConf 10 }

    sispm1040582lrtNASConfMaxReauthCount OBJECT-TYPE
               SYNTAX      Integer32(1..255)
               MAX-ACCESS  read-write
               STATUS      current
               DESCRIPTION
                   "The number of times the switch transmits an EAPOL Request
                    Identity frame without response before considering entering
                    the Guest VLAN is adjusted with this setting.
                    default: 2,
                    range: 1-255."
               ::= {     sispm1040582lrtNASConf 11 }

    sispm1040582lrtNASConfAllowGuestVLAN OBJECT-TYPE
               SYNTAX      AdminMode
               MAX-ACCESS  read-write
               STATUS      current
               DESCRIPTION
                   "The switch remembers if an EAPOL frame has been received
                    on the port for the life-time of the port."
               DEFVAL  { disable }
               ::= {     sispm1040582lrtNASConf 12 }

--sispm1040582lrtNASPortConfTable

    sispm1040582lrtNASPortConfTable OBJECT-TYPE
               SYNTAX      SEQUENCE OF     SISPM1040582LRTNASPortConfEntry
               MAX-ACCESS  not-accessible
               STATUS      current
               DESCRIPTION
                   "The NAS Port Configuration Table.
                    INDEX for this table is ifIndex which is
                    equivalent to the panel port number."
               ::= {     sispm1040582lrtNASConf 13 }

    sispm1040582lrtNASPortConfEntry OBJECT-TYPE
               SYNTAX          SISPM1040582LRTNASPortConfEntry
               MAX-ACCESS  not-accessible
               STATUS      current
               DESCRIPTION
                   "The NAS Port Configuration Entry."
               INDEX    {    ifIndex  }
               ::= {     sispm1040582lrtNASPortConfTable 1 }

    SISPM1040582LRTNASPortConfEntry             ::= SEQUENCE {
                 sispm1040582lrtNASPortConfAdminState         Integer32,
                 sispm1040582lrtNASPortConfRADIUSQoSEnabled   AdminMode,
                 sispm1040582lrtNASPortConfRADIUSVLANEnabled  AdminMode,
                 sispm1040582lrtNASPortConfGuestVLANEnabled   AdminMode,
                 sispm1040582lrtNASPortConfPortState          DisplayString,
                 sispm1040582lrtNASPortConfReauthenticateCmd  INTEGER,
                 sispm1040582lrtNASPortConfReinitializeCmd    INTEGER
                 }

    sispm1040582lrtNASPortConfAdminState OBJECT-TYPE
               SYNTAX      Integer32(0..5)
               MAX-ACCESS  read-write
               STATUS      current
               DESCRIPTION
                   "This selection controls the port's authentication mode.
                    0: Force Authorized,
                    1: Force Unauthorized,
                    2: Port-based 802.1X,
                    3: Single 802.1X,
                    4: Multi 802.1X,
                    5: MAC-based Auth,
                    range: 0-5."
               ::= {     sispm1040582lrtNASPortConfEntry 2 }

    sispm1040582lrtNASPortConfRADIUSQoSEnabled OBJECT-TYPE
               SYNTAX      AdminMode
               MAX-ACCESS  read-write
               STATUS      current
               DESCRIPTION
                   "When RADIUS-Assigned QoS is both globally enabled and
                    enabled on a given port, the switch reacts to QoS Class
                    information carried in the RADIUS Access-Accept packet
                    transmitted by the RADIUS server when a supplicant is
                    successfully authenticated."
               ::= {     sispm1040582lrtNASPortConfEntry 3 }

    sispm1040582lrtNASPortConfRADIUSVLANEnabled OBJECT-TYPE
               SYNTAX      AdminMode
               MAX-ACCESS  read-write
               STATUS      current
               DESCRIPTION
                   "When RADIUS-Assigned VLAN is both globally enabled and
                    enabled for a given port, the switch reacts to VLAN ID
                    information carried in the RADIUS Access-Accept packet
                    transmitted by the RADIUS server when a supplicant is
                    successfully authenticated."
               ::= {     sispm1040582lrtNASPortConfEntry 4 }

    sispm1040582lrtNASPortConfGuestVLANEnabled OBJECT-TYPE
               SYNTAX      AdminMode
               MAX-ACCESS  read-write
               STATUS      current
               DESCRIPTION
                   "When Guest VLAN is both globally enabled and enabled for
                    a given port, the switch considers moving the port into
                    the Guest VLAN according to the rules."
               ::= {     sispm1040582lrtNASPortConfEntry 5 }

    sispm1040582lrtNASPortConfPortState OBJECT-TYPE
               SYNTAX      DisplayString
               MAX-ACCESS  read-only
               STATUS      current
               DESCRIPTION
                   "The current state of the port."
               ::= {     sispm1040582lrtNASPortConfEntry 6 }

    sispm1040582lrtNASPortConfReauthenticateCmd OBJECT-TYPE
               SYNTAX      ActivateCmd
               MAX-ACCESS  read-write
               STATUS      current
               DESCRIPTION
                   "Schedules a reauthentication whenever the quiet-period of
                    the port runs out (EAPOL-based authentication). For
                    MAC-based authentication, reauthentication will be attempted
                    immediately.The button only has effect for successfully
                    authenticated clients on the port and will not cause the
                    clients to get temporarily unauthorized."
               DEFVAL  { noAction }
               ::= {     sispm1040582lrtNASPortConfEntry 7 }

    sispm1040582lrtNASPortConfReinitializeCmd OBJECT-TYPE
               SYNTAX      ActivateCmd
               MAX-ACCESS  read-write
               STATUS      current
               DESCRIPTION
                   "Forces a reinitialization of the clients on the port and
                    thereby a reauthentication immediately. The clients will
                    transfer to the unauthorized state while the
                    reauthentication is in progress."
               DEFVAL  { noAction }
               ::= {     sispm1040582lrtNASPortConfEntry 8 }

--sispm1040582lrtNASSwitchStatusTable

    sispm1040582lrtNASSwitchStatusTable OBJECT-TYPE
               SYNTAX      SEQUENCE OF     SISPM1040582LRTNASSwitchStatusEntry
               MAX-ACCESS  not-accessible
               STATUS      current
               DESCRIPTION
                   "The NAS Switch Status Table.
                    INDEX for this table is ifIndex which is
                    equivalent to the panel port number."
               ::= {     sispm1040582lrtNASStatus 1 }

    sispm1040582lrtNASSwitchStatusEntry OBJECT-TYPE
               SYNTAX          SISPM1040582LRTNASSwitchStatusEntry
               MAX-ACCESS  not-accessible
               STATUS      current
               DESCRIPTION
                   "The NAS Switch Status Entry."
               INDEX    {    ifIndex  }
               ::= {     sispm1040582lrtNASSwitchStatusTable 1 }

    SISPM1040582LRTNASSwitchStatusEntry             ::= SEQUENCE {
                 sispm1040582lrtNASSwitchStatusAdminState   DisplayString,
                 sispm1040582lrtNASSwitchStatusPortState    DisplayString,
                 sispm1040582lrtNASSwitchStatusLastSource   DisplayString,
                 sispm1040582lrtNASSwitchStatusLastID       DisplayString,
                 sispm1040582lrtNASSwitchStatusQoSClass     DisplayString,
                 sispm1040582lrtNASSwitchStatusPortVLANID   DisplayString
                 }

    sispm1040582lrtNASSwitchStatusAdminState OBJECT-TYPE
               SYNTAX      DisplayString
               MAX-ACCESS  read-only
               STATUS      current
               DESCRIPTION
                   "The port's current administrative state."
               ::= {     sispm1040582lrtNASSwitchStatusEntry 2 }

    sispm1040582lrtNASSwitchStatusPortState OBJECT-TYPE
               SYNTAX      DisplayString
               MAX-ACCESS  read-only
               STATUS      current
               DESCRIPTION
                   "The current state of the port."
               ::= {     sispm1040582lrtNASSwitchStatusEntry 3 }

    sispm1040582lrtNASSwitchStatusLastSource OBJECT-TYPE
               SYNTAX      DisplayString
               MAX-ACCESS  read-only
               STATUS      current
               DESCRIPTION
                   "The source MAC address carried in the most recently
                    received EAPOL frame for EAPOL-based authentication,
                    and the most recently received frame from a new client
                    for MAC-based authentication."
               ::= {     sispm1040582lrtNASSwitchStatusEntry 4 }

    sispm1040582lrtNASSwitchStatusLastID OBJECT-TYPE
               SYNTAX      DisplayString
               MAX-ACCESS  read-only
               STATUS      current
               DESCRIPTION
                   "The user name (supplicant identity) carried in the most
                    recently received Response Identity EAPOL frame for
                    EAPOL-based authentication, and the source MAC address
                    from the most recently received frame from a new client
                    for MAC-based authentication."
               ::= {     sispm1040582lrtNASSwitchStatusEntry 5 }

    sispm1040582lrtNASSwitchStatusQoSClass OBJECT-TYPE
               SYNTAX      DisplayString
               MAX-ACCESS  read-only
               STATUS      current
               DESCRIPTION
                   "QoS Class assigned to the port by the RADIUS server
                    if enabled."
               ::= {     sispm1040582lrtNASSwitchStatusEntry 6 }

    sispm1040582lrtNASSwitchStatusPortVLANID OBJECT-TYPE
               SYNTAX      DisplayString
               MAX-ACCESS  read-only
               STATUS      current
               DESCRIPTION
                   "The VLAN ID that NAS has put the port in."
               ::= {     sispm1040582lrtNASSwitchStatusEntry 7 }

--sispm1040582lrtNASPortCounterTable

    sispm1040582lrtNASPortCounterTable OBJECT-TYPE
               SYNTAX      SEQUENCE OF     SISPM1040582LRTNASPortCounterEntry
               MAX-ACCESS  not-accessible
               STATUS      current
               DESCRIPTION
                   "The NAS Port Counter Table.
                    INDEX for this table is ifIndex which is
                    equivalent to the panel port number."
               ::= {     sispm1040582lrtNASStatus 2 }

    sispm1040582lrtNASPortCounterEntry OBJECT-TYPE
               SYNTAX          SISPM1040582LRTNASPortCounterEntry
               MAX-ACCESS  not-accessible
               STATUS      current
               DESCRIPTION
                   "The NAS Port Counter Entry."
               INDEX    {    ifIndex  }
               ::= {     sispm1040582lrtNASPortCounterTable 1 }

    SISPM1040582LRTNASPortCounterEntry             ::= SEQUENCE {
                 sispm1040582lrtNASReceiveEAPOLTotal          Integer32,
                 sispm1040582lrtNASReceiveEAPOLResponseID     Integer32,
                 sispm1040582lrtNASReceiveEAPOLResponses      Integer32,
                 sispm1040582lrtNASReceiveEAPOLStart          Integer32,
                 sispm1040582lrtNASReceiveEAPOLLogoff         Integer32,
                 sispm1040582lrtNASReceiveEAPOLInvalidType    Integer32,
                 sispm1040582lrtNASReceiveEAPOLInvalidLength  Integer32,
                 sispm1040582lrtNASTransmitEAPOLTotal         Integer32,
                 sispm1040582lrtNASTransmitEAPOLRequestID     Integer32,
                 sispm1040582lrtNASTransmitEAPOLRequests      Integer32,
                 sispm1040582lrtNASPortReceiveBackendServerAccessChallenges    Integer32,
                 sispm1040582lrtNASPortReceiveBackendServerOtherRequests       Integer32,
                 sispm1040582lrtNASPortReceiveBackendServerAuthSuccesses       Integer32,
                 sispm1040582lrtNASPortReceiveBackendServerAuthFailures        Integer32,
                 sispm1040582lrtNASPortTransmitBackendServerResponses          Integer32,
                 sispm1040582lrtNASSupplicantInfoMAC          DisplayString,
                 sispm1040582lrtNASSupplicantInfoVlanID       Integer32,
                 sispm1040582lrtNASSupplicantInfoVersion      Integer32,
                 sispm1040582lrtNASSupplicantInfoIdentity     DisplayString,
                 sispm1040582lrtNASPortCounterClearCmd        ActivateCmd
                 }

    sispm1040582lrtNASReceiveEAPOLTotal OBJECT-TYPE
               SYNTAX      Integer32(-1..1000000)
               MAX-ACCESS  read-only
               STATUS      current
               DESCRIPTION
                   "The number of valid EAPOL frames of any type that have
                    been received by the switch.
                    -1: no support."
               ::= {     sispm1040582lrtNASPortCounterEntry 2 }

    sispm1040582lrtNASReceiveEAPOLResponseID OBJECT-TYPE
               SYNTAX      Integer32(-1..1000000)
               MAX-ACCESS  read-only
               STATUS      current
               DESCRIPTION
                   "The number of valid EAPOL Response Identity frames that
                    have been received by the switch.
                    -1: no support."
               ::= {     sispm1040582lrtNASPortCounterEntry 3 }

    sispm1040582lrtNASReceiveEAPOLResponses OBJECT-TYPE
               SYNTAX      Integer32(-1..1000000)
               MAX-ACCESS  read-only
               STATUS      current
               DESCRIPTION
                   "The number of valid EAPOL response frames (other than
                    Response Identity frames) that have been received by
                    the switch.
                    -1: no support."
               ::= {     sispm1040582lrtNASPortCounterEntry 4 }

    sispm1040582lrtNASReceiveEAPOLStart OBJECT-TYPE
               SYNTAX      Integer32(-1..1000000)
               MAX-ACCESS  read-only
               STATUS      current
               DESCRIPTION
                   "The number of EAPOL Start frames that have been received
                    by the switch.
                    -1: no support."
               ::= {     sispm1040582lrtNASPortCounterEntry 5 }

    sispm1040582lrtNASReceiveEAPOLLogoff OBJECT-TYPE
               SYNTAX      Integer32(-1..1000000)
               MAX-ACCESS  read-only
               STATUS      current
               DESCRIPTION
                   "The number of valid EAPOL Logoff frames that have been
                    received by the switch.
                    -1: no support."
               ::= {     sispm1040582lrtNASPortCounterEntry 6 }

    sispm1040582lrtNASReceiveEAPOLInvalidType OBJECT-TYPE
               SYNTAX      Integer32(-1..1000000)
               MAX-ACCESS  read-only
               STATUS      current
               DESCRIPTION
                   "The number of EAPOL frames that have been received by
                    the switch in which the frame type is not recognized.
                    -1: no support."
               ::= {     sispm1040582lrtNASPortCounterEntry 7 }

    sispm1040582lrtNASReceiveEAPOLInvalidLength OBJECT-TYPE
               SYNTAX      Integer32(-1..1000000)
               MAX-ACCESS  read-only
               STATUS      current
               DESCRIPTION
                   "The number of EAPOL frames that have been received
                    by the switch in which the Packet Body Length field
                    is invalid.
                    -1: no support."
               ::= {     sispm1040582lrtNASPortCounterEntry 8 }

    sispm1040582lrtNASTransmitEAPOLTotal OBJECT-TYPE
               SYNTAX      Integer32(-1..1000000)
               MAX-ACCESS  read-only
               STATUS      current
               DESCRIPTION
                   "The number of EAPOL frames of any type that have been
                    transmitted by the switch.
                    -1: no support."
               ::= {     sispm1040582lrtNASPortCounterEntry 9 }

    sispm1040582lrtNASTransmitEAPOLRequestID OBJECT-TYPE
               SYNTAX      Integer32(-1..1000000)
               MAX-ACCESS  read-only
               STATUS      current
               DESCRIPTION
                   "The number of EAPOL Request Identity frames that have
                    been transmitted by the switch.
                    -1: no support."
               ::= {     sispm1040582lrtNASPortCounterEntry 10 }

    sispm1040582lrtNASTransmitEAPOLRequests OBJECT-TYPE
               SYNTAX      Integer32(-1..1000000)
               MAX-ACCESS  read-only
               STATUS      current
               DESCRIPTION
                   "The number of valid EAPOL Request frames (other than
                    Request Identity frames) that have been transmitted
                    by the switch.
                    -1: no support."
               ::= {     sispm1040582lrtNASPortCounterEntry 11 }

    sispm1040582lrtNASPortReceiveBackendServerAccessChallenges OBJECT-TYPE
               SYNTAX      Integer32(-1..1000000)
               MAX-ACCESS  read-only
               STATUS      current
               DESCRIPTION
                   "802.1X-based: Counts the number of times that the switch
                    receives the first request from the backend server following
                    the first response from the supplicant. Indicates that the
                    backend server has communication with the switch.
                    MAC-based:Counts all Access Challenges received from the
                    backend server for this port (left-most table).
                    -1: no support."
               ::= {     sispm1040582lrtNASPortCounterEntry 12 }

    sispm1040582lrtNASPortReceiveBackendServerOtherRequests OBJECT-TYPE
               SYNTAX      Integer32(-1..1000000)
               MAX-ACCESS  read-only
               STATUS      current
               DESCRIPTION
                   "802.1X-based: Counts the number of times that the switch
                    sends an EAP Request packet following the first to the
                    supplicant. Indicates that the backend server chose an
                    EAP-method.
                    MAC-based: Not applicable.
                    -1: no support."
               ::= {     sispm1040582lrtNASPortCounterEntry 13 }

    sispm1040582lrtNASPortReceiveBackendServerAuthSuccesses OBJECT-TYPE
               SYNTAX      Integer32(-1..1000000)
               MAX-ACCESS  read-only
               STATUS      current
               DESCRIPTION
                   "802.1X- and MAC-based: Counts the number of times that
                    the switch receives a success indication.Indicates that
                    the supplicant has successfully authenticated to
                    the backend server.
                    -1: no support."
               ::= {     sispm1040582lrtNASPortCounterEntry 14 }

    sispm1040582lrtNASPortReceiveBackendServerAuthFailures OBJECT-TYPE
               SYNTAX      Integer32(-1..1000000)
               MAX-ACCESS  read-only
               STATUS      current
               DESCRIPTION
                   "802.1X- and MAC-based:Counts the number of times that the
                    switch receives a failure message.This indicates that the
                    supplicant has not authenticated to the backend
                    server.
                    -1: no support."
               ::= {     sispm1040582lrtNASPortCounterEntry 15 }

    sispm1040582lrtNASPortTransmitBackendServerResponses OBJECT-TYPE
               SYNTAX      Integer32(-1..1000000)
               MAX-ACCESS  read-only
               STATUS      current
               DESCRIPTION
                   "802.1X-based:Counts the number of times that the switch
                    attempts to send a supplicant's first response packet to
                    the backend server. Indicates the switch attempted
                    communication with the backend server. Possible
                    retransmissions are not counted.
                    MAC-based: Counts all the backend server packets sent from
                    the switch towards the backend server for a given port
                    (left-most table). Possible retransmissions are not
                    counted.
                    -1: no support."
               ::= {     sispm1040582lrtNASPortCounterEntry 16 }

    sispm1040582lrtNASSupplicantInfoMAC OBJECT-TYPE
               SYNTAX      DisplayString
               MAX-ACCESS  read-only
               STATUS      current
               DESCRIPTION
                   "The MAC address of the last supplicant. "
               ::= {     sispm1040582lrtNASPortCounterEntry 17 }

    sispm1040582lrtNASSupplicantInfoVlanID OBJECT-TYPE
               SYNTAX      Integer32(-1..1000000)
               MAX-ACCESS  read-only
               STATUS      current
               DESCRIPTION
                   "The VLAN ID on which the last frame from the last
                    supplicant was received.
                    -1: no support."
               ::= {     sispm1040582lrtNASPortCounterEntry 18 }

    sispm1040582lrtNASSupplicantInfoVersion OBJECT-TYPE
               SYNTAX      Integer32(-1..1000000)
               MAX-ACCESS  read-only
               STATUS      current
               DESCRIPTION
                   "802.1X-based:The protocol version number carried in
                    the most recently received EAPOL frame.
                    MAC-based: Not applicable.
                    -1: no support."
               ::= {     sispm1040582lrtNASPortCounterEntry 19 }

    sispm1040582lrtNASSupplicantInfoIdentity OBJECT-TYPE
               SYNTAX      DisplayString
               MAX-ACCESS  read-only
               STATUS      current
               DESCRIPTION
                   "802.1X-based:The user name (supplicant identity) carried
                    in the most recently received Response Identity EAPOL frame.
                    MAC-based: Not applicable. "
               ::= {     sispm1040582lrtNASPortCounterEntry 20 }

    sispm1040582lrtNASPortCounterClearCmd OBJECT-TYPE
               SYNTAX      ActivateCmd
               MAX-ACCESS  read-write
               STATUS      current
               DESCRIPTION
                   "Clear the counters for the selected port."
               ::= {     sispm1040582lrtNASPortCounterEntry 21 }


-- =======================================================================================================================
sispm1040582lrtMACConf 						OBJECT IDENTIFIER ::= { sispm1040582lrtConfiguration 17 }

    sispm1040582lrtMAC                                                    OBJECT IDENTIFIER   ::= { sispm1040582lrtMACConf 1 }

--
-- =======================================================================================================================
-- Start sispm1040582lrtMAC group
-- =======================================================================================================================
    sispm1040582lrtMACDisableAutomaticAging   OBJECT-TYPE
               SYNTAX       AdminMode
               MAX-ACCESS   read-write
               STATUS       current
               DESCRIPTION
                   "Disable the automatic aging of dynamic entries."
                ::= {     sispm1040582lrtMAC 1 }

    sispm1040582lrtMACAgingTime  OBJECT-TYPE
               SYNTAX       Integer32 (-1 | 10..1000000)
               MAX-ACCESS   read-write
               STATUS       current
               DESCRIPTION
                   "Configure aging time by entering a value here in seconds.
                   range: 10-1000000 seconds.
                   -1: Automatic Aging is disable."
                ::= {     sispm1040582lrtMAC 2 }

--sispm1040582lrtMACLearningTable
    sispm1040582lrtMACLearningTable OBJECT-TYPE
               SYNTAX      SEQUENCE OF     SISPM1040582LRTMACLearningEntry
               MAX-ACCESS  not-accessible
               STATUS      current
               DESCRIPTION
                   "The mac learning table.
                    INDEX for this table is ifIndex which is
                    equivalent to the panel port number."
               ::= {     sispm1040582lrtMAC 3 }

    sispm1040582lrtMACLearningEntry OBJECT-TYPE
               SYNTAX          SISPM1040582LRTMACLearningEntry
               MAX-ACCESS  not-accessible
               STATUS      current
               DESCRIPTION
                   "The mac learning entry."
               INDEX    {     ifIndex  }
               ::= {     sispm1040582lrtMACLearningTable 1 }

    SISPM1040582LRTMACLearningEntry             ::= SEQUENCE {
                sispm1040582lrtMACTableLearning     INTEGER
                }

    sispm1040582lrtMACTableLearning OBJECT-TYPE
               SYNTAX      INTEGER{ auto(0), disable(1), secure(2)}
               MAX-ACCESS  read-write
               STATUS      current
               DESCRIPTION
                   "auto(0)   : Learning is done automatically as soon as a
                                frame with unknown SMAC is received.
                    disable(1): Disable, No learning is done.
                    secure(2) : Secure, Only static MAC entries are learned,
                                all other frames are dropped."
               ::= {     sispm1040582lrtMACLearningEntry 2 }

--sispm1040582lrtMACStaticConfigTable
    sispm1040582lrtMACStaticConfigTable OBJECT-TYPE
               SYNTAX      SEQUENCE OF     SISPM1040582LRTMACStaticConfigEntry
               MAX-ACCESS  not-accessible
               STATUS      current
               DESCRIPTION
                   "The static Mac config table."
               ::= {     sispm1040582lrtMAC 4 }

    sispm1040582lrtMACStaticConfigEntry OBJECT-TYPE
               SYNTAX          SISPM1040582LRTMACStaticConfigEntry
               MAX-ACCESS  not-accessible
               STATUS      current
               DESCRIPTION
                   "The static Mac config entry."
               INDEX    {     sispm1040582lrtMACStaticConfigIndex  }
               ::= {     sispm1040582lrtMACStaticConfigTable 1 }

    SISPM1040582LRTMACStaticConfigEntry             ::= SEQUENCE {
                sispm1040582lrtMACStaticConfigSwitchIndex Integer32,
                sispm1040582lrtMACStaticConfigIndex       Integer32,
                sispm1040582lrtMACStaticConfigVID         Integer32,
                sispm1040582lrtMACStaticConfigMACaddress  DisplayString,
                sispm1040582lrtMACStaticConfigPortList    DisplayString,
                sispm1040582lrtMACStaticConfigRowStatus   RowStatus
                }

    sispm1040582lrtMACStaticConfigSwitchIndex OBJECT-TYPE
               SYNTAX      Integer32(1..16)
               MAX-ACCESS  not-accessible
               STATUS      current
               DESCRIPTION
                   "Switch Index."
               ::= {     sispm1040582lrtMACStaticConfigEntry 1 }



    sispm1040582lrtMACStaticConfigIndex OBJECT-TYPE
               SYNTAX      Integer32(1..64)
               MAX-ACCESS  not-accessible
               STATUS      current
               DESCRIPTION
                   "The static entries in the MAC table are shown in this table.
                    The static MAC table can contain 64 entries."
               ::= {     sispm1040582lrtMACStaticConfigEntry 2 }

    sispm1040582lrtMACStaticConfigVID OBJECT-TYPE
               SYNTAX      Integer32(1..4095)
               MAX-ACCESS  read-create
               STATUS      current
               DESCRIPTION
                   "The VLAN ID of the entry.
                    range: 1-4095."
               ::= {     sispm1040582lrtMACStaticConfigEntry 3 }

    sispm1040582lrtMACStaticConfigMACaddress OBJECT-TYPE
               SYNTAX      DisplayString
               MAX-ACCESS  read-create
               STATUS      current
               DESCRIPTION
                   "The MAC address of the entry."
               ::= {     sispm1040582lrtMACStaticConfigEntry 4 }

    sispm1040582lrtMACStaticConfigPortList OBJECT-TYPE
               SYNTAX      DisplayString
               MAX-ACCESS  read-create
               STATUS      current
               DESCRIPTION
                   "Checkmarks indicate which ports are members of the entry.
                    Check or uncheck as needed to
                    modify the entry."
               ::= {     sispm1040582lrtMACStaticConfigEntry 5 }

    sispm1040582lrtMACStaticConfigRowStatus OBJECT-TYPE
               SYNTAX      RowStatus
               MAX-ACCESS  read-create
               STATUS      current
               DESCRIPTION
                   "This object indicates the status of this entry,
                    and is used to create/delete entries. Any
                    object in an entry of this table may be modified
                    while the value of the corresponding instance
                    of this object is active(1).
                    createAndGo, notReady not supported."
               ::= {     sispm1040582lrtMACStaticConfigEntry 6 }


-- =======================================================================================================================
sispm1040582lrtSpanningTree 						OBJECT IDENTIFIER ::= { sispm1040582lrtConfiguration 18 }

sispm1040582lrtBridgeSettings                     OBJECT IDENTIFIER ::= { sispm1040582lrtSpanningTree 1 }

sispm1040582lrtSTPProtocolVersion    OBJECT-TYPE
               SYNTAX      Integer32
               MAX-ACCESS  read-write
               STATUS      current
               DESCRIPTION
                   "0:STP
				    2:RSTP
					3:MSTP"
               ::= {     sispm1040582lrtBridgeSettings 1 }

sispm1040582lrtBridgePriority    OBJECT-TYPE
               SYNTAX      Integer32
               MAX-ACCESS  read-write
               STATUS      current
               DESCRIPTION
                   "Bridge Priority, range: 0-61440, multiple of 4096."
               ::= {     sispm1040582lrtBridgeSettings 2 }

sispm1040582lrtBridgeForwardDelay    OBJECT-TYPE
               SYNTAX      Integer32
               MAX-ACCESS  read-write
               STATUS      current
               DESCRIPTION
                   "Bridge Forward Delay, range: 4-30 seconds."
               ::= {     sispm1040582lrtBridgeSettings 3 }

sispm1040582lrtBridgeMaxAge    OBJECT-TYPE
               SYNTAX      Integer32
               MAX-ACCESS  read-write
               STATUS      current
               DESCRIPTION
                   "Bridge MaxAge, range:6-40 seconds."
               ::= {     sispm1040582lrtBridgeSettings 4 }

sispm1040582lrtBridgeMaxHops    OBJECT-TYPE
               SYNTAX      Integer32
               MAX-ACCESS  read-write
               STATUS      current
               DESCRIPTION
                   "Bridge Max Hops, range:6-40 hops."
               ::= {     sispm1040582lrtBridgeSettings 5 }

sispm1040582lrtBridgetxHoldCount    OBJECT-TYPE
               SYNTAX      Integer32
               MAX-ACCESS  read-write
               STATUS      current
               DESCRIPTION
                   "Bridge Transmit Hold Count,range: 1-10 bpdu's per second. "
               ::= {     sispm1040582lrtBridgeSettings 6 }

sispm1040582lrtBridgeBPDUFilter    OBJECT-TYPE
               SYNTAX      Integer32
               MAX-ACCESS  read-write
               STATUS      current
               DESCRIPTION
                   "Bridge BPD UFilter
              		0:disable
                    1:enable					"
               ::= {     sispm1040582lrtBridgeSettings 7 }

sispm1040582lrtBridgeBPDUGuard    OBJECT-TYPE
               SYNTAX      Integer32
               MAX-ACCESS  read-write
               STATUS      current
               DESCRIPTION
                   "Bridge BPDU Guard
              		0:disable
                    1:enable					   "
               ::= {     sispm1040582lrtBridgeSettings 8 }

sispm1040582lrtBridgeerrorRecoveryDelay    OBJECT-TYPE
               SYNTAX      Integer32
               MAX-ACCESS  read-write
               STATUS      current
               DESCRIPTION
                   "Bridge error Recovery Delay
				   range:30-86400 seconds
				   0:disable
				   "
               ::= {     sispm1040582lrtBridgeSettings 9 }

sispm1040582lrtBridgeHelloTime    OBJECT-TYPE
               SYNTAX      Integer32
               MAX-ACCESS  read-write
               STATUS      current
               DESCRIPTION
                   "The interval between sending STP BPDU's. Valid values are in the range 1 to 10 seconds, 
				   default:2 seconds."
               ::= {     sispm1040582lrtBridgeSettings 10 }			   

sispm1040582lrtMSTIMapping                        OBJECT IDENTIFIER ::= { sispm1040582lrtSpanningTree 2 }
sispm1040582lrtConfigName    OBJECT-TYPE
               SYNTAX      DisplayString
               MAX-ACCESS  read-write
               STATUS      current
               DESCRIPTION
                   "Configuration Name, identify the VLAN to MSTI mapping"
               ::= {     sispm1040582lrtMSTIMapping 1 }

sispm1040582lrtConfigRevision    OBJECT-TYPE
               SYNTAX      Integer32
               MAX-ACCESS  read-write
               STATUS      current
               DESCRIPTION
                   "Configuration Revision. range:0-65535 "
               ::= {     sispm1040582lrtMSTIMapping 2 }

sispm1040582lrtMSTIMappingVLAN                    OBJECT IDENTIFIER ::= { sispm1040582lrtSpanningTree 3 }
sispm1040582lrtConfigMstiName1    OBJECT-TYPE
               SYNTAX      DisplayString
               MAX-ACCESS  read-write
               STATUS      current
               DESCRIPTION
                   "The list of VLANs mapped to the MSTI1.
				    The VLANs can be given as a single (xx, xx being between 1 and 4094) VLAN, or a range (xx-yy), each of which must be separated with comma and/or space. "
               ::= {     sispm1040582lrtMSTIMappingVLAN 1 }

sispm1040582lrtConfigMstiName2    OBJECT-TYPE
               SYNTAX      DisplayString
               MAX-ACCESS  read-write
               STATUS      current
               DESCRIPTION
                   "The list of VLANs mapped to the MSTI2.
				    The VLANs can be given as a single (xx, xx being between 1 and 4094) VLAN, or a range (xx-yy), each of which must be separated with comma and/or space.  "
               ::= {     sispm1040582lrtMSTIMappingVLAN 2 }

sispm1040582lrtConfigMstiName3    OBJECT-TYPE
               SYNTAX      DisplayString
               MAX-ACCESS  read-write
               STATUS      current
               DESCRIPTION
                   "The list of VLANs mapped to the MSTI3.
				    The VLANs can be given as a single (xx, xx being between 1 and 4094) VLAN, or a range (xx-yy), each of which must be separated with comma and/or space. "
               ::= {     sispm1040582lrtMSTIMappingVLAN 3 }

sispm1040582lrtConfigMstiName4    OBJECT-TYPE
               SYNTAX      DisplayString
               MAX-ACCESS  read-write
               STATUS      current
               DESCRIPTION
                   "The list of VLANs mapped to the MSTI4.
				    The VLANs can be given as a single (xx, xx being between 1 and 4094) VLAN, or a range (xx-yy), each of which must be separated with comma and/or space. "
               ::= {     sispm1040582lrtMSTIMappingVLAN 4 }

sispm1040582lrtConfigMstiName5    OBJECT-TYPE
               SYNTAX      DisplayString
               MAX-ACCESS  read-write
               STATUS      current
               DESCRIPTION
                   "The list of VLANs mapped to the MSTI5.
				    The VLANs can be given as a single (xx, xx being between 1 and 4094) VLAN, or a range (xx-yy), each of which must be separated with comma and/or space. "
               ::= {     sispm1040582lrtMSTIMappingVLAN 5 }

sispm1040582lrtConfigMstiName6    OBJECT-TYPE
               SYNTAX      DisplayString
               MAX-ACCESS  read-write
               STATUS      current
               DESCRIPTION
                   "The list of VLANs mapped to the MSTI6.
				    The VLANs can be given as a single (xx, xx being between 1 and 4094) VLAN, or a range (xx-yy), each of which must be separated with comma and/or space. "
               ::= {     sispm1040582lrtMSTIMappingVLAN 6 }

sispm1040582lrtConfigMstiName7    OBJECT-TYPE
               SYNTAX      DisplayString
               MAX-ACCESS  read-write
               STATUS      current
               DESCRIPTION
                   "The list of VLANs mapped to the MSTI7.
				    The VLANs can be given as a single (xx, xx being between 1 and 4094) VLAN, or a range (xx-yy), each of which must be separated with comma and/or space. "
               ::= {     sispm1040582lrtMSTIMappingVLAN 7 }

sispm1040582lrtMSTIPriorities                     OBJECT IDENTIFIER ::= { sispm1040582lrtSpanningTree 4 }

sispm1040582lrtCSTIPriority   OBJECT-TYPE
               SYNTAX      Integer32
               MAX-ACCESS  read-write
               STATUS      current
               DESCRIPTION
                   "CSTI Priority. range: 0-61440, multiple of 4096. Lower numeric values have better priority."
               ::= {     sispm1040582lrtMSTIPriorities 1 }

sispm1040582lrtMSTI1Priority   OBJECT-TYPE
               SYNTAX      Integer32
               MAX-ACCESS  read-write
               STATUS      current
               DESCRIPTION
                   "MSTI1 Priority. range: 0-61440, multiple of 4096. Lower numeric values have better priority."
               ::= {     sispm1040582lrtMSTIPriorities 2 }

sispm1040582lrtMSTI2Priority   OBJECT-TYPE
               SYNTAX      Integer32
               MAX-ACCESS  read-write
               STATUS      current
               DESCRIPTION
                   "MSTI2 Priority. range: 0-61440, multiple of 4096. Lower numeric values have better priority."
               ::= {     sispm1040582lrtMSTIPriorities 3 }

sispm1040582lrtMSTI3Priority   OBJECT-TYPE
               SYNTAX      Integer32
               MAX-ACCESS  read-write
               STATUS      current
               DESCRIPTION
                   "MSTI3 Priority. range: 0-61440, multiple of 4096. Lower numeric values have better priority."
               ::= {     sispm1040582lrtMSTIPriorities 4 }
sispm1040582lrtMSTI4Priority   OBJECT-TYPE
               SYNTAX      Integer32
               MAX-ACCESS  read-write
               STATUS      current
               DESCRIPTION
                   "MSTI4 Priority. range: 0-61440, multiple of 4096. Lower numeric values have better priority."
               ::= {     sispm1040582lrtMSTIPriorities 5 }
sispm1040582lrtMSTI5Priority   OBJECT-TYPE
               SYNTAX      Integer32
               MAX-ACCESS  read-write
               STATUS      current
               DESCRIPTION
                   "MSTI5 Priority. range: 0-61440, multiple of 4096. Lower numeric values have better priority."
               ::= {     sispm1040582lrtMSTIPriorities 6 }

sispm1040582lrtMSTI6Priority   OBJECT-TYPE
               SYNTAX      Integer32
               MAX-ACCESS  read-write
               STATUS      current
               DESCRIPTION
                   "MSTI6 Priority. range: 0-61440, multiple of 4096. Lower numeric values have better priority."
               ::= {     sispm1040582lrtMSTIPriorities 7 }
sispm1040582lrtMSTI7Priority   OBJECT-TYPE
               SYNTAX      Integer32
               MAX-ACCESS  read-write
               STATUS      current
               DESCRIPTION
                   "MSTI7 Priority. range: 0-61440, multiple of 4096. Lower numeric values have better priority."
               ::= {     sispm1040582lrtMSTIPriorities 8 }


sispm1040582lrtCISTPorts                          OBJECT IDENTIFIER ::= { sispm1040582lrtSpanningTree 5 }

sispm1040582lrtCISTAggregatedEnable   OBJECT-TYPE
               SYNTAX      Integer32 (0|1)
               MAX-ACCESS  read-write
               STATUS      current
               DESCRIPTION
                   "CIST Port Enable. range: 0-1.
				   0:disable
				   1:enable."
               ::= {     sispm1040582lrtCISTPorts 1 }

sispm1040582lrtCISTAggregatedPathCost   OBJECT-TYPE
               SYNTAX      Integer32 (0..200000000)
               MAX-ACCESS  read-write
               STATUS      current
               DESCRIPTION
                   "CIST Port Path Cost. range: 0-200000000. 0 is Auto."
               ::= {     sispm1040582lrtCISTPorts 2 }

sispm1040582lrtCISTAggregatedPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sispm1040582lrtCISTPorts 3 }

sispm1040582lrtCISTAggregatedAdminEdge   OBJECT-TYPE
               SYNTAX      Integer32 (0|1)
               MAX-ACCESS  read-write
               STATUS      current
               DESCRIPTION
                   "CIST Port Admin Edge. range: 0-1.
				   0:Non-Edge
				   1:Edge."
               ::= {     sispm1040582lrtCISTPorts 4 }

sispm1040582lrtCISTAggregatedAutoEdge   OBJECT-TYPE
               SYNTAX      Integer32 (0|1)
               MAX-ACCESS  read-write
               STATUS      current
               DESCRIPTION
                   "CIST Port Auto Edge. range: 0-1.
				   0:disable
				   1:enable."
               ::= {     sispm1040582lrtCISTPorts 5 }

sispm1040582lrtCISTAggregatedrestrictedRole   OBJECT-TYPE
               SYNTAX      Integer32 (0|1)
               MAX-ACCESS  read-write
               STATUS      current
               DESCRIPTION
                   "CIST Port restricted Role. range: 0-1.
				   0:disable
				   1:enable."
               ::= {     sispm1040582lrtCISTPorts 6 }

sispm1040582lrtCISTAggregatedrestrictedTcn   OBJECT-TYPE
               SYNTAX      Integer32 (0|1)
               MAX-ACCESS  read-write
               STATUS      current
               DESCRIPTION
                   "CIST Port restricted Tcn. range: 0-1.
				   0:disable
				   1:enable."
               ::= {     sispm1040582lrtCISTPorts 7 }

sispm1040582lrtCISTAggregatedbpduGuard   OBJECT-TYPE
               SYNTAX      Integer32 (0|1)
               MAX-ACCESS  read-write
               STATUS      current
               DESCRIPTION
                   "CIST Port bpdu Guard. range: 0-1.
				   0:disable
				   1:enable."
               ::= {     sispm1040582lrtCISTPorts 8 }

sispm1040582lrtCISTAggregatedPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sispm1040582lrtCISTPorts 9 }


sispm1040582lrtCISTPortsTable OBJECT-TYPE
   SYNTAX      SEQUENCE OF SISPM1040582LRTCISTPortsEntry
   MAX-ACCESS  not-accessible
   STATUS      current
   DESCRIPTION
        "CIST port table."
    ::= { sispm1040582lrtCISTPorts 10 }

sispm1040582lrtCISTPortsEntry OBJECT-TYPE
    SYNTAX        SISPM1040582LRTCISTPortsEntry
    MAX-ACCESS    not-accessible
    STATUS        current
    DESCRIPTION
        "An entry in the CIST Ports Table."
    INDEX        { sispm1040582lrtCISTPortIndex }
    ::= { sispm1040582lrtCISTPortsTable 1 }

SISPM1040582LRTCISTPortsEntry ::=
    SEQUENCE {
        sispm1040582lrtCISTPortIndex                 Integer32,
        sispm1040582lrtCISTPortEnable                Integer32,
        sispm1040582lrtCISTPortPathCost              Integer32,
        sispm1040582lrtCISTPortPortPriority          Integer32,
        sispm1040582lrtCISTPortAdminEdge             Integer32,
        sispm1040582lrtCISTPortAutoEdge              Integer32,
        sispm1040582lrtCISTPortrestrictedRole        Integer32,
        sispm1040582lrtCISTPortrestrictedTcn         Integer32,
        sispm1040582lrtCISTPortbpduGuard             Integer32,
        sispm1040582lrtCISTPortPointToPoint          Integer32
    }

sispm1040582lrtCISTPortIndex   OBJECT-TYPE
               SYNTAX      Integer32 (1..53)
               MAX-ACCESS  not-accessible
               STATUS      current
               DESCRIPTION
                   "CIST Port Index. range: 1-53. 53 is Aggregated Port Configuration."
               ::= {     sispm1040582lrtCISTPortsEntry 1 }

sispm1040582lrtCISTPortEnable   OBJECT-TYPE
               SYNTAX      Integer32 (0|1)
               MAX-ACCESS  read-write
               STATUS      current
               DESCRIPTION
                   "CIST Port Enable. range: 0-1.
				   0:disable
				   1:enable."
               ::= {     sispm1040582lrtCISTPortsEntry 2 }

sispm1040582lrtCISTPortPathCost   OBJECT-TYPE
               SYNTAX      Integer32 (0..200000000)
               MAX-ACCESS  read-write
               STATUS      current
               DESCRIPTION
                   "CIST Port Path Cost. range: 0-200000000. 0 is Auto."
               ::= {     sispm1040582lrtCISTPortsEntry 3 }

sispm1040582lrtCISTPortPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sispm1040582lrtCISTPortsEntry 4 }

sispm1040582lrtCISTPortAdminEdge   OBJECT-TYPE
               SYNTAX      Integer32 (0|1)
               MAX-ACCESS  read-write
               STATUS      current
               DESCRIPTION
                   "CIST Port Admin Edge. range: 0-1.
				   0:Non-Edge
				   1:Edge."
               ::= {     sispm1040582lrtCISTPortsEntry 5 }

sispm1040582lrtCISTPortAutoEdge   OBJECT-TYPE
               SYNTAX      Integer32 (0|1)
               MAX-ACCESS  read-write
               STATUS      current
               DESCRIPTION
                   "CIST Port Auto Edge. range: 0-1.
				   0:disable
				   1:enable."
               ::= {     sispm1040582lrtCISTPortsEntry 6 }

sispm1040582lrtCISTPortrestrictedRole   OBJECT-TYPE
               SYNTAX      Integer32 (0|1)
               MAX-ACCESS  read-write
               STATUS      current
               DESCRIPTION
                   "CIST Port restricted Role. range: 0-1.
				   0:disable
				   1:enable."
               ::= {     sispm1040582lrtCISTPortsEntry 7 }

sispm1040582lrtCISTPortrestrictedTcn   OBJECT-TYPE
               SYNTAX      Integer32 (0|1)
               MAX-ACCESS  read-write
               STATUS      current
               DESCRIPTION
                   "CIST Port restricted Tcn. range: 0-1.
				   0:disable
				   1:enable."
               ::= {     sispm1040582lrtCISTPortsEntry 8 }

sispm1040582lrtCISTPortbpduGuard   OBJECT-TYPE
               SYNTAX      Integer32 (0|1)
               MAX-ACCESS  read-write
               STATUS      current
               DESCRIPTION
                   "CIST Port bpdu Guard. range: 0-1.
				   0:disable
				   1:enable."
               ::= {     sispm1040582lrtCISTPortsEntry 9 }

sispm1040582lrtCISTPortPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sispm1040582lrtCISTPortsEntry 10 }

sispm1040582lrtMSTIPorts                          OBJECT IDENTIFIER ::= { sispm1040582lrtSpanningTree 6 }


sispm1040582lrtMSTIAggregatedPortsTable OBJECT-TYPE
   SYNTAX      SEQUENCE OF SISPM1040582LRTMSTIAggregatedPortsEntry
   MAX-ACCESS  not-accessible
   STATUS      current
   DESCRIPTION
       "A table of MSTI ports."
    ::= { sispm1040582lrtMSTIPorts 1 }

sispm1040582lrtMSTIAggregatedPortsEntry OBJECT-TYPE
    SYNTAX        SISPM1040582LRTMSTIAggregatedPortsEntry
    MAX-ACCESS    not-accessible
    STATUS        current
    DESCRIPTION
        "An entry in the MSTI ports Table."
    INDEX        { sispm1040582lrtMSTIAggregatedPortsMSTIndex }
    ::= { sispm1040582lrtMSTIAggregatedPortsTable 1 }

SISPM1040582LRTMSTIAggregatedPortsEntry ::=
    SEQUENCE {
        sispm1040582lrtMSTIAggregatedPortsMSTIndex                        Integer32,
        sispm1040582lrtMSTIAggregatedPortsPathCost                        Integer32,
        sispm1040582lrtMSTIAggregatedPortsPortPriority                    Integer32
    }

sispm1040582lrtMSTIAggregatedPortsMSTIndex OBJECT-TYPE
   SYNTAX      Integer32 (1..7)
   MAX-ACCESS  not-accessible
   STATUS      current
   DESCRIPTION
       "MST index, range:1-7"
   ::= {sispm1040582lrtMSTIAggregatedPortsEntry 1 }

sispm1040582lrtMSTIAggregatedPortsPathCost   OBJECT-TYPE
   SYNTAX      Integer32 (0..200000000)
   MAX-ACCESS  read-write
   STATUS      current
   DESCRIPTION
       "MST Path Cost. range: 0-200000000. 0 is Auto."
   ::= {sispm1040582lrtMSTIAggregatedPortsEntry 3 }

sispm1040582lrtMSTIAggregatedPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sispm1040582lrtMSTIAggregatedPortsEntry 4 }


sispm1040582lrtMSTIPortsTable OBJECT-TYPE
   SYNTAX      SEQUENCE OF SISPM1040582LRTMSTIPortsEntry
   MAX-ACCESS  not-accessible
   STATUS      current
   DESCRIPTION
       "A table of MSTI ports."
    ::= { sispm1040582lrtMSTIPorts 2 }

sispm1040582lrtMSTIPortsEntry OBJECT-TYPE
    SYNTAX        SISPM1040582LRTMSTIPortsEntry
    MAX-ACCESS    not-accessible
    STATUS        current
    DESCRIPTION
        "An entry in the MSTI ports Table."
    INDEX        { sispm1040582lrtMSTIPortsMSTIndex, sispm1040582lrtMSTIPortsPortIndex }
    ::= { sispm1040582lrtMSTIPortsTable 1 }

SISPM1040582LRTMSTIPortsEntry ::=
    SEQUENCE {
        sispm1040582lrtMSTIPortsMSTIndex                        Integer32,
        sispm1040582lrtMSTIPortsPortIndex                       Integer32,
        sispm1040582lrtMSTIPortsPathCost                        Integer32,
        sispm1040582lrtMSTIPortsPortPriority                    Integer32
    }

sispm1040582lrtMSTIPortsMSTIndex OBJECT-TYPE
   SYNTAX      Integer32 (1..7)
   MAX-ACCESS  not-accessible
   STATUS      current
   DESCRIPTION
       "MST index, range:1-7"
   ::= {sispm1040582lrtMSTIPortsEntry 1 }

sispm1040582lrtMSTIPortsPortIndex OBJECT-TYPE
   SYNTAX      Integer32 (1..53)
   MAX-ACCESS  not-accessible
   STATUS      current
   DESCRIPTION
       "Port index, range 1-53, 53 is Aggregated Ports Configuration."
   ::= {sispm1040582lrtMSTIPortsEntry 2 }

sispm1040582lrtMSTIPortsPathCost   OBJECT-TYPE
   SYNTAX      Integer32 (0..200000000)
   MAX-ACCESS  read-write
   STATUS      current
   DESCRIPTION
       "MST Path Cost. range: 0-200000000. 0 is Auto."
   ::= {sispm1040582lrtMSTIPortsEntry 3 }

sispm1040582lrtMSTIPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sispm1040582lrtMSTIPortsEntry 4 }

-- =======================================================================================================================
sispm1040582lrtPrivateVLANs 						OBJECT IDENTIFIER ::= { sispm1040582lrtConfiguration 19 }

sispm1040582lrtPVLANMembershipTable  OBJECT-TYPE
   SYNTAX      SEQUENCE OF SISPM1040582LRTPVLANMembershipEntry
   MAX-ACCESS  not-accessible
   STATUS      current
   DESCRIPTION
       "A table of Private VLAN Membership."
 ::= { sispm1040582lrtPrivateVLANs 1 }

sispm1040582lrtPVLANMembershipEntry OBJECT-TYPE
    SYNTAX        SISPM1040582LRTPVLANMembershipEntry
    MAX-ACCESS    not-accessible
    STATUS        current
    DESCRIPTION
        "An entry in the private VLAN table."
    INDEX        { sispm1040582lrtPVLANMembershipIndex }
    ::= { sispm1040582lrtPVLANMembershipTable 1 }

SISPM1040582LRTPVLANMembershipEntry ::=
    SEQUENCE {
        sispm1040582lrtPVLANMembershipIndex                    Integer32,
        sispm1040582lrtPVLANID                                 Integer32,
        sispm1040582lrtPVLANMembers                            DisplayString,
        sispm1040582lrtPVLANRowStatus                          RowStatus
    }

sispm1040582lrtPVLANMembershipIndex OBJECT-TYPE
   SYNTAX      Integer32 (1..28)
   MAX-ACCESS  not-accessible
   STATUS      current
   DESCRIPTION
       "PVLAN membership index. Range:1-28."
   ::= {sispm1040582lrtPVLANMembershipEntry 1 }

sispm1040582lrtPVLANID OBJECT-TYPE
   SYNTAX      Integer32 (1..28)
   MAX-ACCESS  read-create
   STATUS      current
   DESCRIPTION
       "PVLAN ID. Range:1-28."
   ::= {sispm1040582lrtPVLANMembershipEntry 2 }

sispm1040582lrtPVLANMembers OBJECT-TYPE
   SYNTAX      DisplayString
   MAX-ACCESS  read-create
   STATUS      current
   DESCRIPTION
       "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
   ::= {sispm1040582lrtPVLANMembershipEntry 3 }

sispm1040582lrtPVLANRowStatus OBJECT-TYPE
   SYNTAX      RowStatus
   MAX-ACCESS  read-create
   STATUS      current
   DESCRIPTION
       "PVLAN Row Status."
   ::= {sispm1040582lrtPVLANMembershipEntry 4 }

sispm1040582lrtPVLANPortIsolationTable  OBJECT-TYPE
   SYNTAX      SEQUENCE OF SISPM1040582LRTPVLANPortIsolationEntry
   MAX-ACCESS  not-accessible
   STATUS      current
   DESCRIPTION
       "A table of Private VLAN Port Isolation."
 ::= { sispm1040582lrtPrivateVLANs 2 }

sispm1040582lrtPVLANPortIsolationEntry OBJECT-TYPE
    SYNTAX        SISPM1040582LRTPVLANPortIsolationEntry
    MAX-ACCESS    not-accessible
    STATUS        current
    DESCRIPTION
        "An entry in the private VLAN table."
    INDEX        { sispm1040582lrtPVLANPortIsolationIndex }
    ::= { sispm1040582lrtPVLANPortIsolationTable 1 }

SISPM1040582LRTPVLANPortIsolationEntry ::=
    SEQUENCE {
        sispm1040582lrtPVLANPortIsolationIndex                 Integer32,
        sispm1040582lrtPVLANPortIsolationPortMembers           Integer32
    }

sispm1040582lrtPVLANPortIsolationIndex OBJECT-TYPE
   SYNTAX      Integer32 (1..28)
   MAX-ACCESS  not-accessible
   STATUS      current
   DESCRIPTION
       "PVLAN Port Isolation Index. Range:1-28."
   ::= {sispm1040582lrtPVLANPortIsolationEntry 1 }

sispm1040582lrtPVLANPortIsolationPortMembers OBJECT-TYPE
   SYNTAX      Integer32 (0|1)
   MAX-ACCESS  read-write
   STATUS      current
   DESCRIPTION
       "PVLAN Port Isolation Port Members enable/disable. Range:0-1.
	   1:Port Isolation enable  on that port.
	   0:Port Isolation disable on that port."
   ::= {sispm1040582lrtPVLANPortIsolationEntry 2 }

-- =======================================================================================================================


sispm1040582lrtsFlow 						OBJECT IDENTIFIER ::= { sispm1040582lrtConfiguration 20 }

      sispm1040582lrtsFlowVersion OBJECT-TYPE
              SYNTAX      SnmpAdminString
              MAX-ACCESS  read-only
              STATUS      current
              DESCRIPTION "Uniquely identifies the version and implementation of this MIB. The version string must have the following structure: <MIB Version>;<Organization>;<Software Revision> where: <MIB Version>  must be '1.3', the version of this MIB.
                    <Organization> the name of the organization responsible for the agent implementation. <Revision>     the specific software build of this agent.
                 As an example, the string '1.3;InMon Corp.;2.1.1' indicates that this agent implements version '1.2' of the SFLOW MIB, that
                 it was developed by 'InMon Corp.' and that the software build is '2.1.1'.
                 The MIB Version will change with each revision of the SFLOW MIB.
                 Management entities must check the MIB Version and not attempt to manage agents with MIB Versions greater than that for which
                 they were designed.
                 Note: The sFlow Datagram Format has an independent version number which may change independently from <MIB Version>.
                       <MIB Version> applies to the structure and semantics of the SFLOW MIB only." DEFVAL { "1.3;;" }
              ::= { sispm1040582lrtsFlow 1 }

      sispm1040582lrtsFlowAgentAddressType OBJECT-TYPE
              SYNTAX      InetAddressType
              MAX-ACCESS  read-only
              STATUS      current
              DESCRIPTION "The address type of the address associated with this agent. Only ipv4 and ipv6 types are supported. ipv4:1, ipv6:2."
              ::= { sispm1040582lrtsFlow 2 }

      sispm1040582lrtsFlowAgentAddress OBJECT-TYPE
              SYNTAX      IpAddress
              MAX-ACCESS  read-write
              STATUS      current
              DESCRIPTION "The IP address associated with this agent. In the case of a multi-homed agent, this should be the loopback address of the
                 agent. The sFlowAgent address must provide SNMP connectivity to the agent. The address should be an invariant that does not
                 change as interfaces are reconfigured, enabled, disabled, added or removed. A manager should be able to use the
                 sFlowAgentAddress as a unique key that will identify this agent over extended periods of time so that a history can
                 be maintained."
              ::= { sispm1040582lrtsFlow 3 }
      --
      -- Receiver Table
      --
      sispm1040582lrtsFlowRcvrTable OBJECT-TYPE
              SYNTAX      SEQUENCE OF SISPM1040582LRTSFlowRcvrEntry
              MAX-ACCESS  not-accessible
              STATUS      current
              DESCRIPTION "A table of the receivers of sFlow information."
              ::= { sispm1040582lrtsFlow 4 }

      sispm1040582lrtsFlowRcvrEntry OBJECT-TYPE
              SYNTAX SISPM1040582LRTSFlowRcvrEntry
              MAX-ACCESS  not-accessible
              STATUS      current
              DESCRIPTION "Attributes of an sFlow Receiver."
              INDEX { sispm1040582lrtsFlowRcvrIndex }
              ::= { sispm1040582lrtsFlowRcvrTable 1 }

      SISPM1040582LRTSFlowRcvrEntry ::= SEQUENCE {
              sispm1040582lrtsFlowRcvrIndex                    Integer32,
              sispm1040582lrtsFlowRcvrOwner                    OwnerString,
              sispm1040582lrtsFlowRcvrTimeout                  Integer32,
              sispm1040582lrtsFlowRcvrMaximumDatagramSize      Integer32,
              sispm1040582lrtsFlowRcvrAddressType              InetAddressType,
              sispm1040582lrtsFlowRcvrAddress                  IpAddress,
              sispm1040582lrtsFlowRcvrPort                     Integer32,
              sispm1040582lrtsFlowRcvrDatagramVersion          Integer32 }

      sispm1040582lrtsFlowRcvrIndex OBJECT-TYPE
              SYNTAX      Integer32 (1..65535)
              MAX-ACCESS  not-accessible
              STATUS      current
              DESCRIPTION "Index into sFlowReceiverTable."
              ::= { sispm1040582lrtsFlowRcvrEntry 1 }

      sispm1040582lrtsFlowRcvrOwner OBJECT-TYPE
              SYNTAX      OwnerString
              MAX-ACCESS  read-write
              STATUS      current
              DESCRIPTION "The entity making use of this sFlowRcvrTable entry. The empty string indicates that the entry is currently unclaimed.
                 An entity wishing to claim an sFlowRcvrTable entry must ensure that the entry is unclaimed before trying to claim it.
                 The entry is claimed by setting the owner string. The entry must be claimed before any changes can be made to other sampler
                 objects.
                 In order to avoid a race condition, the entity taking control of the sampler must set both the owner and a value for
                 sFlowRcvrTimeout in the same SNMP set request.
                 When a management entity is finished using the sampler, it should set the value of sFlowRcvrOwner back to unclaimed.
                 The agent must restore all other entities this row to their default values when the owner is set to unclaimed. It must
                 also free all other resources associated with this sFlowRcvrTable entry.
                 This mechanism provides no enforcement and relies on the cooperation of management entities in order to ensure that
                 competition for a receiver entry is fairly resolved." DEFVAL { "" }
              ::= { sispm1040582lrtsFlowRcvrEntry 2 }

      sispm1040582lrtsFlowRcvrTimeout OBJECT-TYPE
              SYNTAX      Integer32
              MAX-ACCESS  read-write
              STATUS      current
              DESCRIPTION "The time (in seconds) remaining before the sampler is released and stops sampling. When set, the owner establishes control
                 for the specified period. When read, the remaining time in the interval is returned.
                 A management entity wanting to maintain control of the sampler is responsible for setting a new value before the old one
                 expires.
                 When the interval expires, the agent is responsible for restoring all other entities in this row to their default
                 values. It must also free all other resources associated with this sFlowRcvrTable entry." DEFVAL { 0 }
              ::= { sispm1040582lrtsFlowRcvrEntry 3 }

      sispm1040582lrtsFlowRcvrMaximumDatagramSize OBJECT-TYPE
              SYNTAX      Integer32
              MAX-ACCESS  read-write
              STATUS      current
              DESCRIPTION "The maximum number of data bytes that can be sent in a single sample datagram. The manager should set this value to avoid fragmentation of the sFlow datagrams." DEFVAL { 1400 }
              ::= { sispm1040582lrtsFlowRcvrEntry 4 }

      sispm1040582lrtsFlowRcvrAddressType OBJECT-TYPE
              SYNTAX      InetAddressType
              MAX-ACCESS  read-write
              STATUS      current
              DESCRIPTION "The type of sFlowRcvrCollectorAddress." DEFVAL { ipv4 }
              ::= { sispm1040582lrtsFlowRcvrEntry 5 }

      sispm1040582lrtsFlowRcvrAddress OBJECT-TYPE
              SYNTAX      IpAddress
              MAX-ACCESS  read-write
              STATUS      current
              DESCRIPTION "The IP address of the sFlow collector. If set to 0.0.0.0 not sFlow datagrams will be sent." DEFVAL { '00000000'h }  -- 0.0.0.0
              ::= { sispm1040582lrtsFlowRcvrEntry 6 }

      sispm1040582lrtsFlowRcvrPort OBJECT-TYPE
              SYNTAX      Integer32
              MAX-ACCESS  read-write
              STATUS      current
              DESCRIPTION "The destination port for sFlow datagrams." DEFVAL { 6343 }
              ::= { sispm1040582lrtsFlowRcvrEntry 7 }

      sispm1040582lrtsFlowRcvrDatagramVersion OBJECT-TYPE
              SYNTAX      Integer32
              MAX-ACCESS  read-write
              STATUS      current
              DESCRIPTION "The version of sFlow datagrams that should be sent.
                 When set to a value not support by the agent, the agent should adjust the value to the highest supported value less than the
                 requested value, or return an SNMP bad value error if no such value exists." DEFVAL { 5 }
              ::= { sispm1040582lrtsFlowRcvrEntry 8 }

      --
      -- Flow Sampling Table
      --
      sispm1040582lrtsFlowFsTable OBJECT-TYPE
              SYNTAX      SEQUENCE OF SISPM1040582LRTSFlowFsEntry
              MAX-ACCESS  not-accessible
              STATUS      current
              DESCRIPTION "A table of the flow samplers within a device."
              ::= { sispm1040582lrtsFlow 5 }

      sispm1040582lrtsFlowFsEntry OBJECT-TYPE
              SYNTAX      SISPM1040582LRTSFlowFsEntry
              MAX-ACCESS  not-accessible
              STATUS      current
              DESCRIPTION "Attributes of a flow sampler."
              INDEX { sispm1040582lrtsFlowFsDataSource, sispm1040582lrtsFlowFsInstance }
              ::= { sispm1040582lrtsFlowFsTable 1 }

      SISPM1040582LRTSFlowFsEntry ::= SEQUENCE {
              sispm1040582lrtsFlowFsDataSource               OBJECT IDENTIFIER,
              sispm1040582lrtsFlowFsInstance                 Integer32,
              sispm1040582lrtsFlowFsReceiver                 Integer32,
              sispm1040582lrtsFlowFsPacketSamplingRate       Integer32,
              sispm1040582lrtsFlowFsMaximumHeaderSize        Integer32,
              sispm1040582lrtsFlowFsType                     Integer32
              }

      sispm1040582lrtsFlowFsDataSource OBJECT-TYPE
              SYNTAX      OBJECT IDENTIFIER
              MAX-ACCESS  not-accessible
              STATUS      current
              DESCRIPTION "sFlowDataSource for this flow sampler."
              ::= { sispm1040582lrtsFlowFsEntry 1 }

      sispm1040582lrtsFlowFsInstance OBJECT-TYPE
              SYNTAX      Integer32 (1..65535)
              MAX-ACCESS  not-accessible
              STATUS      current
              DESCRIPTION "The sFlow instance for this flow sampler."
              ::= { sispm1040582lrtsFlowFsEntry 2 }

      sispm1040582lrtsFlowFsReceiver OBJECT-TYPE
              SYNTAX      Integer32
              MAX-ACCESS  read-write
              STATUS      current
              DESCRIPTION "The SFlowReceiver for this flow sampler." DEFVAL { 0 }
              ::= { sispm1040582lrtsFlowFsEntry 3 }

      sispm1040582lrtsFlowFsPacketSamplingRate OBJECT-TYPE
              SYNTAX      Integer32
              MAX-ACCESS  read-write
              STATUS      current
              DESCRIPTION "The statistical sampling rate for packet sampling from this source.
                 Set to N to sample 1/Nth of the packets in the monitored flows. An agent should choose its own algorithm to introduce variance
                 into the sampling so that exactly every Nth packet is not counted. A sampling rate of 1 counts all packets. A sampling
                 rate of 0 disables sampling.
                 The agent is permitted to have minimum and maximum allowable values for the sampling rate. A minimum rate lets the agent
                 designer set an upper bound on the overhead associated with sampling, and a maximum rate may be the result of hardware
                 restrictions (such as counter size). In addition not all values between the maximum and minimum may be realizable as the
                 sampling rate (again because of implementation considerations).
                 When the sampling rate is set the agent is free to adjust the value so that it lies between the maximum and minimum values
                 and has the closest achievable value.
                 When read, the agent must return the actual sampling rate it will be using (after the adjustments previously described). The
                 sampling algorithm must converge so that over time the number of packets sampled approaches 1/Nth of the total number of
                 packets in the monitored flows." DEFVAL { 0 }
              ::= { sispm1040582lrtsFlowFsEntry 4 }

      sispm1040582lrtsFlowFsMaximumHeaderSize OBJECT-TYPE
              SYNTAX      Integer32
              MAX-ACCESS  read-write
              STATUS      current
              DESCRIPTION "The maximum number of bytes that should be copied from a sampled packet. The agent may have an internal maximum and
                 minimum permissible sizes. If an attempt is made to set this value outside the permissible range then the agent should
                 adjust the value to the closest permissible value." DEFVAL { 128 }
              ::= { sispm1040582lrtsFlowFsEntry 5 }

      sispm1040582lrtsFlowFsType OBJECT-TYPE
              SYNTAX      Integer32
              MAX-ACCESS  read-write
              STATUS      current
              DESCRIPTION "Flow Sample Type.
			  1:Rx
			  2:Tx
			  3:All."
			  DEFVAL { 2 }
              ::= { sispm1040582lrtsFlowFsEntry 6 }
      --
      -- Counter Polling Table
      --
      sispm1040582lrtsFlowCpTable OBJECT-TYPE
              SYNTAX      SEQUENCE OF SISPM1040582LRTSFlowCpEntry
              MAX-ACCESS  not-accessible
              STATUS      current
              DESCRIPTION "A table of the counter pollers within a device."
              ::= { sispm1040582lrtsFlow 6 }

      sispm1040582lrtsFlowCpEntry OBJECT-TYPE
              SYNTAX      SISPM1040582LRTSFlowCpEntry
              MAX-ACCESS  not-accessible
              STATUS      current
              DESCRIPTION "Attributes of a counter poller."
              INDEX { sispm1040582lrtsFlowCpDataSource, sispm1040582lrtsFlowCpInstance }
              ::= { sispm1040582lrtsFlowCpTable 1 }

      SISPM1040582LRTSFlowCpEntry ::= SEQUENCE {
              sispm1040582lrtsFlowCpDataSource               OBJECT IDENTIFIER,
              sispm1040582lrtsFlowCpInstance                 Integer32,
              sispm1040582lrtsFlowCpReceiver                 Integer32,
              sispm1040582lrtsFlowCpInterval                 Integer32
              }

      sispm1040582lrtsFlowCpDataSource OBJECT-TYPE
              SYNTAX      OBJECT IDENTIFIER
              MAX-ACCESS  not-accessible
              STATUS      current
              DESCRIPTION "Identifies the source of the data for the counter poller."
              ::= { sispm1040582lrtsFlowCpEntry 1 }

      sispm1040582lrtsFlowCpInstance OBJECT-TYPE
              SYNTAX      Integer32 (1..65535)
              MAX-ACCESS  not-accessible
              STATUS      current
              DESCRIPTION "The sFlowInstance for this counter poller."
              ::= { sispm1040582lrtsFlowCpEntry 2 }

      sispm1040582lrtsFlowCpReceiver OBJECT-TYPE
              SYNTAX      Integer32
              MAX-ACCESS  read-write
              STATUS      current
              DESCRIPTION "The SFlowReciever associated with this counter poller." DEFVAL { 0 }
              ::= { sispm1040582lrtsFlowCpEntry 3 }

      sispm1040582lrtsFlowCpInterval OBJECT-TYPE
              SYNTAX      Integer32
              MAX-ACCESS  read-write
              STATUS      current
              DESCRIPTION "The maximum number of seconds between successive samples of the counters associated with this data source. A sampling interval
                 of 0 disables counter sampling.
                 The agent is permitted to have minimum and maximum allowable values for the counter polling interval. A minimum interval
                 lets the agent designer set an upper bound on the overhead associated with polling, and a maximum interval may be the
                 result of implementation restrictions (such as counter size). In addition not all values between the maximum and minimum may
                 be realizable as the sampling interval (again because of implementation considerations).
                 When the sampling rate is set the agent is free to adjust the value so that it lies between the maximum and minimum values
                 and has the closest achievable value.
                 When read, the agent must return the actual sampling interval it will be using (after the adjustments previously described).
                 The sampling algorithm must converge so that over time the number of packets sampled approaches 1/Nth of the total number
                 of packets in the monitored flows." DEFVAL { 0 }
              ::= { sispm1040582lrtsFlowCpEntry 4 }

sispm1040582lrtLLDP                  OBJECT IDENTIFIER ::= { sispm1040582lrtConfiguration 21 }

    sispm1040582lrtLLDPConfTable OBJECT-TYPE
               SYNTAX      SEQUENCE OF     SISPM1040582LRTLLDPConfEntry
               MAX-ACCESS  not-accessible
               STATUS      current
               DESCRIPTION
                   " "
               ::= {     sispm1040582lrtLLDP 1 }

    sispm1040582lrtLLDPConfEntry OBJECT-TYPE
               SYNTAX          SISPM1040582LRTLLDPConfEntry
               MAX-ACCESS  not-accessible
               STATUS      current
               DESCRIPTION
                   " "
               INDEX    {    sispm1040582lrtLLDPIndex  }
               ::= {     sispm1040582lrtLLDPConfTable 1 }

    SISPM1040582LRTLLDPConfEntry             ::= SEQUENCE {
                 sispm1040582lrtLLDPIndex        Integer32,
                 sispm1040582lrtLLDPMode         Integer32,
                 sispm1040582lrtLLDPCDPAware     Integer32,
                 sispm1040582lrtLLDPPortDescr    Integer32,
		 sispm1040582lrtLLDPSysName      Integer32,
		 sispm1040582lrtLLDPSysDescr     Integer32,
		 sispm1040582lrtLLDPSysCapa      Integer32,
		 sispm1040582lrtLLDPMgmtAddr     Integer32
    }

    sispm1040582lrtLLDPIndex OBJECT-TYPE
               SYNTAX      Integer32
               MAX-ACCESS  read-write
               STATUS      current
               DESCRIPTION
                   "LLDP configuration index."
               ::= {     sispm1040582lrtLLDPConfEntry 1 }

    sispm1040582lrtLLDPMode OBJECT-TYPE
               SYNTAX      Integer32
               MAX-ACCESS  read-write
               STATUS      current
               DESCRIPTION
                   "0:Disable
		   1:Tx only
		   2:Rx only
		   3:Enabled"
               ::= {     sispm1040582lrtLLDPConfEntry 2 }

    sispm1040582lrtLLDPCDPAware OBJECT-TYPE
               SYNTAX      Integer32
               MAX-ACCESS  read-write
               STATUS      current
               DESCRIPTION
                   "0:Disable
		   1:Enable"
               ::= {     sispm1040582lrtLLDPConfEntry 3 }

    sispm1040582lrtLLDPPortDescr OBJECT-TYPE
               SYNTAX      Integer32
               MAX-ACCESS  read-write
               STATUS      current
               DESCRIPTION
                   "0:Disable
		   1:Enable"
               ::= {     sispm1040582lrtLLDPConfEntry 4 }

    sispm1040582lrtLLDPSysName OBJECT-TYPE
               SYNTAX      Integer32
               MAX-ACCESS  read-write
               STATUS      current
               DESCRIPTION
                   "0:Disable
		   1:Enable"
               ::= {     sispm1040582lrtLLDPConfEntry 5 }

    sispm1040582lrtLLDPSysDescr OBJECT-TYPE
               SYNTAX      Integer32
               MAX-ACCESS  read-write
               STATUS      current
               DESCRIPTION
                   "0:Disable
		   1:Enable"
               ::= {     sispm1040582lrtLLDPConfEntry 6 }

    sispm1040582lrtLLDPSysCapa OBJECT-TYPE
               SYNTAX      Integer32
               MAX-ACCESS  read-write
               STATUS      current
               DESCRIPTION
                   "0:Disable
		   1:Enable"
               ::= {     sispm1040582lrtLLDPConfEntry 7 }

    sispm1040582lrtLLDPMgmtAddr OBJECT-TYPE
               SYNTAX      Integer32
               MAX-ACCESS  read-write
               STATUS      current
               DESCRIPTION
                   "0:Disable
		   1:Enable"
               ::= {     sispm1040582lrtLLDPConfEntry 8 }

sispm1040582lrtLLDPMEDCoordinatesLocation                          OBJECT IDENTIFIER ::= { sispm1040582lrtLLDP 2 }   
			   
sispm1040582lrtLLDPMEDLatitude   OBJECT-TYPE
   SYNTAX      DisplayString
   MAX-ACCESS  read-write
   STATUS      current
   DESCRIPTION
	   "Latitude SHOULD be normalized to within 0-90 degrees with a maximum of 4 digits."
   ::= { sispm1040582lrtLLDPMEDCoordinatesLocation 2 }
			   
sispm1040582lrtLLDPMEDLatitudeDirection OBJECT-TYPE
   SYNTAX      Integer32(0|1)
   MAX-ACCESS  read-write
   STATUS      current
   DESCRIPTION
       "0:North 
	    1:South"
   ::= { sispm1040582lrtLLDPMEDCoordinatesLocation 3 }
			  
sispm1040582lrtLLDPMEDLongitude   OBJECT-TYPE
   SYNTAX      DisplayString
   MAX-ACCESS  read-write
   STATUS      current
   DESCRIPTION
	   "Longitude SHOULD be normalized to within 0-180 degrees with a maximum of 4 digits."
   ::= { sispm1040582lrtLLDPMEDCoordinatesLocation 4 }
			   
sispm1040582lrtLLDPMEDLongitudeDirection OBJECT-TYPE
   SYNTAX      Integer32(0|1)
   MAX-ACCESS  read-write
   STATUS      current
   DESCRIPTION
       "0:East 
	    1:West"
   ::= { sispm1040582lrtLLDPMEDCoordinatesLocation 5 }
			  
sispm1040582lrtLLDPMEDAltitude   OBJECT-TYPE
   SYNTAX      DisplayString
   MAX-ACCESS  read-write
   STATUS      current
   DESCRIPTION
	   "Altitude SHOULD be normalized to within -2097151.9 to 2097151.9 with a maximum of 1 digits."
   ::= { sispm1040582lrtLLDPMEDCoordinatesLocation 6 }
			   
sispm1040582lrtLLDPMEDAltitudeType OBJECT-TYPE
   SYNTAX      Integer32(1|2)
   MAX-ACCESS  read-write
   STATUS      current
   DESCRIPTION
       "1:Meters 
	    2:Floors"
   ::= { sispm1040582lrtLLDPMEDCoordinatesLocation 7 } 
   
sispm1040582lrtLLDPMEDMapDatum OBJECT-TYPE
   SYNTAX      Integer32(0..2)
   MAX-ACCESS  read-write
   STATUS      current
   DESCRIPTION
       "The Map Datum is used for the coordinates given in these options:
	    1:WGS84
	    2:NAD83/NAVD88 
	    3:NAD83/MLLW
		"
   ::= { sispm1040582lrtLLDPMEDCoordinatesLocation 8 }    

   
sispm1040582lrtLLDPMEDTransmitTLVsTable OBJECT-TYPE
   SYNTAX      SEQUENCE OF SISPM1040582LRTLLDPMEDTransmitTLVsEntry
   MAX-ACCESS  not-accessible
   STATUS      current
   DESCRIPTION
       " "
   ::= { sispm1040582lrtLLDP 3 }

sispm1040582lrtLLDPMEDTransmitTLVsEntry OBJECT-TYPE
   SYNTAX      SISPM1040582LRTLLDPMEDTransmitTLVsEntry
   MAX-ACCESS  not-accessible
   STATUS      current
   DESCRIPTION
       " "
   INDEX    { sispm1040582lrtLLDPMEDTransmitTLVsPort  }
   ::= { sispm1040582lrtLLDPMEDTransmitTLVsTable 1 }
  
SISPM1040582LRTLLDPMEDTransmitTLVsEntry ::= SEQUENCE {
   sispm1040582lrtLLDPMEDTransmitTLVsPort          Integer32,
   sispm1040582lrtLLDPMEDTransmitTLVsCapabilities  Integer32,
   sispm1040582lrtLLDPMEDTransmitTLVsPolicies      Integer32,
   sispm1040582lrtLLDPMEDTransmitTLVsLocation      Integer32,
   sispm1040582lrtLLDPMEDTransmitTLVsPoE           Integer32
}

sispm1040582lrtLLDPMEDTransmitTLVsPort OBJECT-TYPE
   SYNTAX      Integer32
   MAX-ACCESS  not-accessible
   STATUS      current
   DESCRIPTION
       "Index"
   ::= { sispm1040582lrtLLDPMEDTransmitTLVsEntry 1 }

sispm1040582lrtLLDPMEDTransmitTLVsCapabilities OBJECT-TYPE
   SYNTAX      Integer32 (0|1)
   MAX-ACCESS  read-write
   STATUS      current
   DESCRIPTION
       "0:Disable
	    1:Enable"
   ::= { sispm1040582lrtLLDPMEDTransmitTLVsEntry 2 }
			   
sispm1040582lrtLLDPMEDTransmitTLVsPolicies OBJECT-TYPE
   SYNTAX      Integer32 (0|1)
   MAX-ACCESS  read-write
   STATUS      current
   DESCRIPTION
       "0:Disable
	    1:Enable"
   ::= { sispm1040582lrtLLDPMEDTransmitTLVsEntry 3 }
   
sispm1040582lrtLLDPMEDTransmitTLVsLocation OBJECT-TYPE
   SYNTAX      Integer32 (0|1)
   MAX-ACCESS  read-write
   STATUS      current
   DESCRIPTION
       "0:Disable
	    1:Enable"
   ::= { sispm1040582lrtLLDPMEDTransmitTLVsEntry 4 }
   
sispm1040582lrtLLDPMEDTransmitTLVsPoE OBJECT-TYPE
   SYNTAX      Integer32 (0|1)
   MAX-ACCESS  read-write
   STATUS      current
   DESCRIPTION
       "0:Disable
	    1:Enable"
   ::= { sispm1040582lrtLLDPMEDTransmitTLVsEntry 5 }
   
sispm1040582lrtLLDPMEDCivicAddressLocation                          OBJECT IDENTIFIER ::= { sispm1040582lrtLLDP 4 }   

sispm1040582lrtLLDPMEDCivicAddressLocationCountryCode   OBJECT-TYPE
   SYNTAX      DisplayString
   MAX-ACCESS  read-write
   STATUS      current
   DESCRIPTION
	   " "
   ::= { sispm1040582lrtLLDPMEDCivicAddressLocation 2 }

sispm1040582lrtLLDPMEDCivicAddressLocationStateProvince   OBJECT-TYPE
   SYNTAX      DisplayString
   MAX-ACCESS  read-write
   STATUS      current
   DESCRIPTION
	   " "
   ::= { sispm1040582lrtLLDPMEDCivicAddressLocation 3 }
	
sispm1040582lrtLLDPMEDCivicAddressLocationCounty   OBJECT-TYPE
   SYNTAX      DisplayString
   MAX-ACCESS  read-write
   STATUS      current
   DESCRIPTION
	   " "
   ::= { sispm1040582lrtLLDPMEDCivicAddressLocation 4 }
   
sispm1040582lrtLLDPMEDCivicAddressLocationCity   OBJECT-TYPE
   SYNTAX      DisplayString
   MAX-ACCESS  read-write
   STATUS      current
   DESCRIPTION
	   " "
   ::= { sispm1040582lrtLLDPMEDCivicAddressLocation 5 }
   
sispm1040582lrtLLDPMEDCivicAddressLocationCityDistrict   OBJECT-TYPE
   SYNTAX      DisplayString
   MAX-ACCESS  read-write
   STATUS      current
   DESCRIPTION
	   " "
   ::= { sispm1040582lrtLLDPMEDCivicAddressLocation 6 }
   
sispm1040582lrtLLDPMEDCivicAddressLocationBlockNeighborhood   OBJECT-TYPE
   SYNTAX      DisplayString
   MAX-ACCESS  read-write
   STATUS      current
   DESCRIPTION
	   " "
   ::= { sispm1040582lrtLLDPMEDCivicAddressLocation 7 }
   
sispm1040582lrtLLDPMEDCivicAddressLocationStreet   OBJECT-TYPE
   SYNTAX      DisplayString
   MAX-ACCESS  read-write
   STATUS      current
   DESCRIPTION
	   " "
   ::= { sispm1040582lrtLLDPMEDCivicAddressLocation 8 }
   
sispm1040582lrtLLDPMEDCivicAddressLocationLeadingStreetDirection   OBJECT-TYPE
   SYNTAX      DisplayString
   MAX-ACCESS  read-write
   STATUS      current
   DESCRIPTION
	   " "
   ::= { sispm1040582lrtLLDPMEDCivicAddressLocation 9 }
   
sispm1040582lrtLLDPMEDCivicAddressLocationTrailingStreetSuffix   OBJECT-TYPE
   SYNTAX      DisplayString
   MAX-ACCESS  read-write
   STATUS      current
   DESCRIPTION
	   " "
   ::= { sispm1040582lrtLLDPMEDCivicAddressLocation 10 }
   
sispm1040582lrtLLDPMEDCivicAddressLocationStreetSuffix   OBJECT-TYPE
   SYNTAX      DisplayString
   MAX-ACCESS  read-write
   STATUS      current
   DESCRIPTION
	   " "
   ::= { sispm1040582lrtLLDPMEDCivicAddressLocation 11 }
   
sispm1040582lrtLLDPMEDCivicAddressLocationHouseNo   OBJECT-TYPE
   SYNTAX      DisplayString
   MAX-ACCESS  read-write
   STATUS      current
   DESCRIPTION
	   " "
   ::= { sispm1040582lrtLLDPMEDCivicAddressLocation 12 }
	
sispm1040582lrtLLDPMEDCivicAddressLocationHouseNoSuffix   OBJECT-TYPE
   SYNTAX      DisplayString
   MAX-ACCESS  read-write
   STATUS      current
   DESCRIPTION
	   " "
   ::= { sispm1040582lrtLLDPMEDCivicAddressLocation 13 }
	
sispm1040582lrtLLDPMEDCivicAddressLocationLandmark   OBJECT-TYPE
   SYNTAX      DisplayString
   MAX-ACCESS  read-write
   STATUS      current
   DESCRIPTION
	   " "
   ::= { sispm1040582lrtLLDPMEDCivicAddressLocation 14 }
   
sispm1040582lrtLLDPMEDCivicAddressLocationAdditionalLocationInfo   OBJECT-TYPE
   SYNTAX      DisplayString
   MAX-ACCESS  read-write
   STATUS      current
   DESCRIPTION
	   " "
   ::= { sispm1040582lrtLLDPMEDCivicAddressLocation 15 }
   
sispm1040582lrtLLDPMEDCivicAddressLocationName   OBJECT-TYPE
   SYNTAX      DisplayString
   MAX-ACCESS  read-write
   STATUS      current
   DESCRIPTION
	   " "
   ::= { sispm1040582lrtLLDPMEDCivicAddressLocation 16 }
   
sispm1040582lrtLLDPMEDCivicAddressLocationZipCode   OBJECT-TYPE
   SYNTAX      DisplayString
   MAX-ACCESS  read-write
   STATUS      current
   DESCRIPTION
	   " "
   ::= { sispm1040582lrtLLDPMEDCivicAddressLocation 17 }
	
sispm1040582lrtLLDPMEDCivicAddressLocationBuilding   OBJECT-TYPE
   SYNTAX      DisplayString
   MAX-ACCESS  read-write
   STATUS      current
   DESCRIPTION
	   " "
   ::= { sispm1040582lrtLLDPMEDCivicAddressLocation 18 }
   
sispm1040582lrtLLDPMEDCivicAddressLocationApartment   OBJECT-TYPE
   SYNTAX      DisplayString
   MAX-ACCESS  read-write
   STATUS      current
   DESCRIPTION
	   " "
   ::= { sispm1040582lrtLLDPMEDCivicAddressLocation 19 }   
   
sispm1040582lrtLLDPMEDCivicAddressLocationFloor   OBJECT-TYPE
   SYNTAX      DisplayString
   MAX-ACCESS  read-write
   STATUS      current
   DESCRIPTION
	   " "
   ::= { sispm1040582lrtLLDPMEDCivicAddressLocation 20 } 
   
sispm1040582lrtLLDPMEDCivicAddressLocationRoomNo   OBJECT-TYPE
   SYNTAX      DisplayString
   MAX-ACCESS  read-write
   STATUS      current
   DESCRIPTION
	   " "
   ::= { sispm1040582lrtLLDPMEDCivicAddressLocation 21 }    
   
sispm1040582lrtLLDPMEDCivicAddressLocationPlaceType   OBJECT-TYPE
   SYNTAX      DisplayString
   MAX-ACCESS  read-write
   STATUS      current
   DESCRIPTION
	   " "
   ::= { sispm1040582lrtLLDPMEDCivicAddressLocation 22 }     
   
sispm1040582lrtLLDPMEDCivicAddressLocationPostalCommunityName   OBJECT-TYPE
   SYNTAX      DisplayString
   MAX-ACCESS  read-write
   STATUS      current
   DESCRIPTION
	   " "
   ::= { sispm1040582lrtLLDPMEDCivicAddressLocation 23 }    

sispm1040582lrtLLDPMEDCivicAddressLocationPOBox   OBJECT-TYPE
   SYNTAX      DisplayString
   MAX-ACCESS  read-write
   STATUS      current
   DESCRIPTION
	   " "
   ::= { sispm1040582lrtLLDPMEDCivicAddressLocation 24 }     
   
sispm1040582lrtLLDPMEDCivicAddressLocationAdditionalCode   OBJECT-TYPE
   SYNTAX      DisplayString
   MAX-ACCESS  read-write
   STATUS      current
   DESCRIPTION
	   " "
   ::= { sispm1040582lrtLLDPMEDCivicAddressLocation 25 }

   
sispm1040582lrtLLDPMEDPoliciesTable OBJECT-TYPE
   SYNTAX      SEQUENCE OF SISPM1040582LRTLLDPMEDPoliciesEntry
   MAX-ACCESS  not-accessible
   STATUS      current
   DESCRIPTION
       " "
   ::= { sispm1040582lrtLLDP 5 }

sispm1040582lrtLLDPMEDPoliciesEntry OBJECT-TYPE
   SYNTAX      SISPM1040582LRTLLDPMEDPoliciesEntry
   MAX-ACCESS  not-accessible
   STATUS      current
   DESCRIPTION
       " "
   INDEX    { sispm1040582lrtLLDPMEDPoliciesIndex  }
   ::= { sispm1040582lrtLLDPMEDPoliciesTable 1 }
  
SISPM1040582LRTLLDPMEDPoliciesEntry ::= SEQUENCE {
   sispm1040582lrtLLDPMEDPoliciesIndex            Integer32,
   sispm1040582lrtLLDPMEDPoliciesPolicyID         Integer32,
   sispm1040582lrtLLDPMEDPoliciesApplicationType  Integer32,
   sispm1040582lrtLLDPMEDPoliciesTag              Integer32,
   sispm1040582lrtLLDPMEDPoliciesVLANID           Integer32,
   sispm1040582lrtLLDPMEDPoliciesL2Priority       Integer32,
   sispm1040582lrtLLDPMEDPoliciesDSCP             Integer32,
   sispm1040582lrtLLDPMEDPoliciesRowStatus        RowStatus
}

sispm1040582lrtLLDPMEDPoliciesIndex OBJECT-TYPE
   SYNTAX      Integer32
   MAX-ACCESS  not-accessible
   STATUS      current
   DESCRIPTION
       "Index"
   ::= { sispm1040582lrtLLDPMEDPoliciesEntry 1 }

sispm1040582lrtLLDPMEDPoliciesPolicyID OBJECT-TYPE
   SYNTAX      Integer32
   MAX-ACCESS  read-only
   STATUS      current
   DESCRIPTION
       " "
   ::= { sispm1040582lrtLLDPMEDPoliciesEntry 2 }
			   
sispm1040582lrtLLDPMEDPoliciesApplicationType OBJECT-TYPE
   SYNTAX      Integer32 (1..8)
   MAX-ACCESS  read-write
   STATUS      current
   DESCRIPTION
       "1:Voice
		2:Voice Signalling
		3:Guest Voice
		4:Guest Voice Signalling
		5:Softphone Voice
		6:Video Conferencing
		7:Streaming Video 
		8:Video Signalling"
   ::= { sispm1040582lrtLLDPMEDPoliciesEntry 3 }
   
sispm1040582lrtLLDPMEDPoliciesTag OBJECT-TYPE
   SYNTAX      Integer32 (0|1)
   MAX-ACCESS  read-write
   STATUS      current
   DESCRIPTION
       "0:Untagged
	    1:Tagged"
   ::= { sispm1040582lrtLLDPMEDPoliciesEntry 4 }
   
sispm1040582lrtLLDPMEDPoliciesVLANID OBJECT-TYPE
   SYNTAX      Integer32 (1..4095)
   MAX-ACCESS  read-write
   STATUS      current
   DESCRIPTION
       "Range:1-4095"
   ::= { sispm1040582lrtLLDPMEDPoliciesEntry 5 }

sispm1040582lrtLLDPMEDPoliciesL2Priority OBJECT-TYPE
   SYNTAX      Integer32 (0..7)
   MAX-ACCESS  read-write
   STATUS      current
   DESCRIPTION
       "Range:0-7"
   ::= { sispm1040582lrtLLDPMEDPoliciesEntry 6 }
   
sispm1040582lrtLLDPMEDPoliciesDSCP OBJECT-TYPE
   SYNTAX      Integer32 (0..63)
   MAX-ACCESS  read-write
   STATUS      current
   DESCRIPTION
       "Range:0-63"
   ::= { sispm1040582lrtLLDPMEDPoliciesEntry 7 }	
   
sispm1040582lrtLLDPMEDPoliciesRowStatus OBJECT-TYPE
   SYNTAX      RowStatus
   MAX-ACCESS  read-create
   STATUS      current
   DESCRIPTION
       "Row Status."
   ::= { sispm1040582lrtLLDPMEDPoliciesEntry 8 }
	
sispm1040582lrtLLDPMEDPolicyPortConfTable OBJECT-TYPE
   SYNTAX      SEQUENCE OF SISPM1040582LRTLLDPMEDPolicyPortConfEntry
   MAX-ACCESS  not-accessible
   STATUS      current
   DESCRIPTION
       " "
   ::= { sispm1040582lrtLLDP 6 }

sispm1040582lrtLLDPMEDPolicyPortConfEntry OBJECT-TYPE
   SYNTAX      SISPM1040582LRTLLDPMEDPolicyPortConfEntry
   MAX-ACCESS  not-accessible
   STATUS      current
   DESCRIPTION
       " "
   INDEX    { sispm1040582lrtLLDPMEDPolicyPortConfPort  }
   ::= { sispm1040582lrtLLDPMEDPolicyPortConfTable 1 }

SISPM1040582LRTLLDPMEDPolicyPortConfEntry ::= SEQUENCE {
   sispm1040582lrtLLDPMEDPolicyPortConfPort        Integer32,
   sispm1040582lrtLLDPMEDPolicyPortConf            Integer32
}
	
sispm1040582lrtLLDPMEDPolicyPortConfPort OBJECT-TYPE
   SYNTAX      Integer32
   MAX-ACCESS  not-accessible
   STATUS      current
   DESCRIPTION
       "Index"
   ::= { sispm1040582lrtLLDPMEDPolicyPortConfEntry 1 }

sispm1040582lrtLLDPMEDPolicyPortConf OBJECT-TYPE
   SYNTAX      Integer32 (0|1)
   MAX-ACCESS  read-write
   STATUS      current
   DESCRIPTION
       "0:Disable
	    1:Enable"
   ::= { sispm1040582lrtLLDPMEDPolicyPortConfEntry 2 }
	
sispm1040582lrtLLDPMEDFastStartRepeatCount OBJECT-TYPE
   SYNTAX      Integer32 (1..10)
   MAX-ACCESS  read-write
   STATUS      current
   DESCRIPTION
       "Range:1-10"
   ::= { sispm1040582lrtLLDP 7 }
	
sispm1040582lrtLLDPMEDEmergencyCallService OBJECT-TYPE
   SYNTAX      DisplayString
   MAX-ACCESS  read-write
   STATUS      current
   DESCRIPTION
       " "
   ::= { sispm1040582lrtLLDP 8 }

sispm1040582lrtUDLD    OBJECT IDENTIFIER ::= { sispm1040582lrtConfiguration 22 }

sispm1040582lrtUDLDPortConfigTable OBJECT-TYPE
   SYNTAX      SEQUENCE OF SISPM1040582LRTUDLDPortConfigEntry
   MAX-ACCESS  not-accessible
   STATUS      current
   DESCRIPTION
       " "
   ::= { sispm1040582lrtUDLD 1 }

sispm1040582lrtUDLDPortConfigEntry OBJECT-TYPE
   SYNTAX      SISPM1040582LRTUDLDPortConfigEntry
   MAX-ACCESS  not-accessible
   STATUS      current
   DESCRIPTION
       " "
   INDEX    { sispm1040582lrtUDLDPort  }
   ::= { sispm1040582lrtUDLDPortConfigTable 1 }

SISPM1040582LRTUDLDPortConfigEntry ::= SEQUENCE {
   sispm1040582lrtUDLDPort                       Integer32,
   sispm1040582lrtUDLDPortMode                   Integer32,
   sispm1040582lrtUDLDPortMessageInterval        Integer32
}

sispm1040582lrtUDLDPort OBJECT-TYPE
   SYNTAX      Integer32
   MAX-ACCESS  not-accessible
   STATUS      current
   DESCRIPTION
       " "
   ::= { sispm1040582lrtUDLDPortConfigEntry 1 }

sispm1040582lrtUDLDPortMode OBJECT-TYPE
   SYNTAX      Integer32 (0|1|2)
   MAX-ACCESS  read-write
   STATUS      current
   DESCRIPTION
       "default: 0
       0: disable
       1: Normal
	   2: Aggressive"
   ::= { sispm1040582lrtUDLDPortConfigEntry 2 }

sispm1040582lrtUDLDPortMessageInterval OBJECT-TYPE
   SYNTAX      Integer32(7..90)
   MAX-ACCESS  read-write
   STATUS      current
   DESCRIPTION
       "default: 7, range: 7-90"
   ::= { sispm1040582lrtUDLDPortConfigEntry 3 }


sispm1040582lrtUDLDPortStatusTable OBJECT-TYPE
   SYNTAX      SEQUENCE OF SISPM1040582LRTUDLDPortStatusEntry
   MAX-ACCESS  not-accessible
   STATUS      current
   DESCRIPTION
       " "
   ::= { sispm1040582lrtUDLD 2 }

sispm1040582lrtUDLDPortStatusEntry OBJECT-TYPE
   SYNTAX      SISPM1040582LRTUDLDPortStatusEntry
   MAX-ACCESS  not-accessible
   STATUS      current
   DESCRIPTION
       " "
   INDEX    { sispm1040582lrtUDLDPortStatusPort  }
   ::= { sispm1040582lrtUDLDPortStatusTable 1 }

SISPM1040582LRTUDLDPortStatusEntry ::= SEQUENCE {
   sispm1040582lrtUDLDPortStatusPort                   Integer32,
   sispm1040582lrtUDLDStatusAdminState                 Integer32,
   sispm1040582lrtUDLDStatusDeviceIDLocal          DisplayString,
   sispm1040582lrtUDLDStatusDeviceNameLocal        DisplayString,
   sispm1040582lrtUDLDStatusBidirectionalState     DisplayString
}

sispm1040582lrtUDLDPortStatusPort OBJECT-TYPE
   SYNTAX      Integer32
   MAX-ACCESS  not-accessible
   STATUS      current
   DESCRIPTION
       "Port index"
   ::= { sispm1040582lrtUDLDPortStatusEntry 1 }

sispm1040582lrtUDLDStatusAdminState OBJECT-TYPE
   SYNTAX      Integer32
   MAX-ACCESS  read-only
   STATUS      current
   DESCRIPTION
       "0:disable
	   1:enable"
   ::= { sispm1040582lrtUDLDPortStatusEntry 2 }

sispm1040582lrtUDLDStatusDeviceIDLocal OBJECT-TYPE
   SYNTAX      DisplayString
   MAX-ACCESS  read-only
   STATUS      current
   DESCRIPTION
       " "
   ::= { sispm1040582lrtUDLDPortStatusEntry 3 }

sispm1040582lrtUDLDStatusDeviceNameLocal OBJECT-TYPE
   SYNTAX      DisplayString
   MAX-ACCESS  read-only
   STATUS      current
   DESCRIPTION
       " "
   ::= { sispm1040582lrtUDLDPortStatusEntry 4 }

sispm1040582lrtUDLDStatusBidirectionalState OBJECT-TYPE
   SYNTAX      DisplayString
   MAX-ACCESS  read-only
   STATUS      current
   DESCRIPTION
       " "
   ::= { sispm1040582lrtUDLDPortStatusEntry 5 }


sispm1040582lrtUDLDStatusPort OBJECT-TYPE
   SYNTAX      Integer32
   MAX-ACCESS  read-write
   STATUS      current
   DESCRIPTION
       "Specify port number for check neighbour status"
   ::= { sispm1040582lrtUDLD 3 }

sispm1040582lrtUDLDPortNeighbourStatusTable OBJECT-TYPE
   SYNTAX      SEQUENCE OF SISPM1040582LRTUDLDPortNeighbourStatusEntry
   MAX-ACCESS  not-accessible
   STATUS      current
   DESCRIPTION
       " "
   ::= { sispm1040582lrtUDLD 4 }

sispm1040582lrtUDLDPortNeighbourStatusEntry OBJECT-TYPE
   SYNTAX      SISPM1040582LRTUDLDPortNeighbourStatusEntry
   MAX-ACCESS  not-accessible
   STATUS      current
   DESCRIPTION
       " "
   INDEX    { sispm1040582lrtUDLDNeighbourPort  }
   ::= { sispm1040582lrtUDLDPortNeighbourStatusTable 1 }

SISPM1040582LRTUDLDPortNeighbourStatusEntry ::= SEQUENCE {
   sispm1040582lrtUDLDNeighbourPort                 Integer32,
   sispm1040582lrtUDLDNeighbourStatusPort           DisplayString,
   sispm1040582lrtUDLDNeighbourStatusDeviceId       DisplayString,
   sispm1040582lrtUDLDNeighbourStatusLinkStatus     DisplayString,
   sispm1040582lrtUDLDNeighbourStatusDeviceName     DisplayString
}

sispm1040582lrtUDLDNeighbourPort OBJECT-TYPE
   SYNTAX      Integer32
   MAX-ACCESS  not-accessible
   STATUS      current
   DESCRIPTION
       "Index"
   ::= { sispm1040582lrtUDLDPortNeighbourStatusEntry 1 }

sispm1040582lrtUDLDNeighbourStatusPort OBJECT-TYPE
   SYNTAX      DisplayString
   MAX-ACCESS  read-only
   STATUS      current
   DESCRIPTION
       " "
   ::= { sispm1040582lrtUDLDPortNeighbourStatusEntry 2 }

sispm1040582lrtUDLDNeighbourStatusDeviceId OBJECT-TYPE
   SYNTAX      DisplayString
   MAX-ACCESS  read-only
   STATUS      current
   DESCRIPTION
       " "
   ::= { sispm1040582lrtUDLDPortNeighbourStatusEntry 3 }

sispm1040582lrtUDLDNeighbourStatusLinkStatus OBJECT-TYPE
   SYNTAX      DisplayString
   MAX-ACCESS  read-only
   STATUS      current
   DESCRIPTION
       " "
   ::= { sispm1040582lrtUDLDPortNeighbourStatusEntry 4 }

sispm1040582lrtUDLDNeighbourStatusDeviceName OBJECT-TYPE
   SYNTAX      DisplayString
   MAX-ACCESS  read-only
   STATUS      current
   DESCRIPTION
       " "
   ::= { sispm1040582lrtUDLDPortNeighbourStatusEntry 5 }

-- =======================================================================================================================
sispm1040582lrtEPS    OBJECT IDENTIFIER ::= { sispm1040582lrtConfiguration 23 }

sispm1040582lrtEPSTable  OBJECT-TYPE
   SYNTAX      SEQUENCE OF SISPM1040582LRTEPSEntry
   MAX-ACCESS  not-accessible
   STATUS      current
   DESCRIPTION
       "A table of EPS."
 ::= { sispm1040582lrtEPS 1 }

sispm1040582lrtEPSEntry OBJECT-TYPE
    SYNTAX        SISPM1040582LRTEPSEntry
    MAX-ACCESS    not-accessible
    STATUS        current
    DESCRIPTION
        ""
    INDEX        { sispm1040582lrtEPSIndex }
    ::= { sispm1040582lrtEPSTable 1 }

SISPM1040582LRTEPSEntry ::=
    SEQUENCE {
        sispm1040582lrtEPSIndex                                Integer32,
        sispm1040582lrtEpsID                                   Integer32,
		sispm1040582lrtEpsDomain                               Integer32,
        sispm1040582lrtEpsArchitecture                         Integer32,
        sispm1040582lrtEpsWFlow                                Integer32,
        sispm1040582lrtEpsPFlow                                Integer32,	
        sispm1040582lrtEpsWSFMEP                               Integer32,		
        sispm1040582lrtEpsPSFMEP                               Integer32,		
        sispm1040582lrtEpsAPSMEP                               Integer32,		
        sispm1040582lrtEpsAlarm                                Integer32,		
        sispm1040582lrtEpsRowStatus                            RowStatus
    }

sispm1040582lrtEPSIndex OBJECT-TYPE
   SYNTAX      Integer32
   MAX-ACCESS  not-accessible
   STATUS      current
   DESCRIPTION
       "Index"
   ::= { sispm1040582lrtEPSEntry 1 }

sispm1040582lrtEpsID OBJECT-TYPE
   SYNTAX      Integer32 (1..100)
   MAX-ACCESS  read-create
   STATUS      current
   DESCRIPTION
       "EPS ID. Range:1-100."
   ::= {sispm1040582lrtEPSEntry 2 }

sispm1040582lrtEpsDomain OBJECT-TYPE
   SYNTAX      Integer32
   MAX-ACCESS  read-create
   STATUS      current
   DESCRIPTION
       "EPS Domain. Range:0.
	   0:Domain is Port"
   ::= {sispm1040582lrtEPSEntry 3 }   
   
sispm1040582lrtEpsArchitecture OBJECT-TYPE
   SYNTAX      Integer32
   MAX-ACCESS  read-create
   STATUS      current
   DESCRIPTION
       "EPS Architecture. Range:0-1.
	   0:Architecture is 1+1
	   1:Architecture is 1:1"
   ::= {sispm1040582lrtEPSEntry 4 }   
   
sispm1040582lrtEpsWFlow OBJECT-TYPE
   SYNTAX      Integer32
   MAX-ACCESS  read-create
   STATUS      current
   DESCRIPTION
       "The working flow for the EPS."
   ::= {sispm1040582lrtEPSEntry 5 }  

sispm1040582lrtEpsPFlow OBJECT-TYPE
   SYNTAX      Integer32
   MAX-ACCESS  read-create
   STATUS      current
   DESCRIPTION
       "The protecting flow for the EPS"
   ::= {sispm1040582lrtEPSEntry 6 }    
   
sispm1040582lrtEpsWSFMEP OBJECT-TYPE
   SYNTAX      Integer32
   MAX-ACCESS  read-create
   STATUS      current
   DESCRIPTION
       "The working Signal Fail reporting MEP."
   ::= {sispm1040582lrtEPSEntry 7 }     
   
sispm1040582lrtEpsPSFMEP OBJECT-TYPE
   SYNTAX      Integer32
   MAX-ACCESS  read-create
   STATUS      current
   DESCRIPTION
       "The protecting Signal Fail reporting MEP."
   ::= {sispm1040582lrtEPSEntry 8 }        
   
sispm1040582lrtEpsAPSMEP OBJECT-TYPE
   SYNTAX      Integer32
   MAX-ACCESS  read-create
   STATUS      current
   DESCRIPTION
       "The APS PDU handling MEP."
   ::= {sispm1040582lrtEPSEntry 9 }
   
sispm1040582lrtEpsAlarm OBJECT-TYPE
   SYNTAX      Integer32
   MAX-ACCESS  read-only
   STATUS      current
   DESCRIPTION
       "There is an active alarm on the EPS."
   ::= {sispm1040582lrtEPSEntry 10 }  
   
sispm1040582lrtEpsRowStatus OBJECT-TYPE
   SYNTAX      RowStatus
   MAX-ACCESS  read-create
   STATUS      current
   DESCRIPTION
       "EPS Row Status."
   ::= {sispm1040582lrtEPSEntry 11 }
   
sispm1040582lrtEpsConfigInstanceEpsID   OBJECT-TYPE
   SYNTAX      Integer32
   MAX-ACCESS  read-write
   STATUS      current
   DESCRIPTION
	   "Specify EPS ID for table uesd."
   ::= {sispm1040582lrtEPS 2 }
   
   
sispm1040582lrtEPSConfigInstanceEntry    OBJECT IDENTIFIER ::= { sispm1040582lrtEPS 3 } 

sispm1040582lrtEpsConfigInstanceProtectionType OBJECT-TYPE
   SYNTAX      Integer32
   MAX-ACCESS  read-write
   STATUS      current
   DESCRIPTION
       "Range:0-1.
	   0:Unidirectional: EPS in the two ends can select traffic from different working/protecting flow. This is only possible in case of 1+1.
       1:Bidirectional: EPS in the two ends is selecting traffic from the same working/protecting flow. This requires APS enabled. This is mandatory for 1:1"
   ::= { sispm1040582lrtEPSConfigInstanceEntry 2 }

sispm1040582lrtEpsConfigInstanceAPS OBJECT-TYPE
   SYNTAX      Integer32
   MAX-ACCESS  read-write
   STATUS      current
   DESCRIPTION
       "Range:0-1.
	    0:disable
	    1:enable
	    The Automatic Protection Switching protocol can be enabled/disabled. This is mandatory for 1:1."
   ::= { sispm1040582lrtEPSConfigInstanceEntry 3 }

sispm1040582lrtEpsConfigInstanceRevertive OBJECT-TYPE
   SYNTAX      Integer32
   MAX-ACCESS  read-write
   STATUS      current
   DESCRIPTION
       "Range:0-1.
	    0:disable
	    1:enable
		The revertive switching to working flow can be enabled/disabled.
		"
   ::= { sispm1040582lrtEPSConfigInstanceEntry 4 }   
   
sispm1040582lrtEpsConfigInstanceWTRTime OBJECT-TYPE
   SYNTAX      Integer32
   MAX-ACCESS  read-write
   STATUS      current
   DESCRIPTION
       "The Wait To Restore timing value to be used in revertive switching. Range is 1 to 720 seconds.
		"
   ::= { sispm1040582lrtEPSConfigInstanceEntry 5 }      
   
sispm1040582lrtEpsConfigInstanceHoldOffTime OBJECT-TYPE
   SYNTAX      Integer32
   MAX-ACCESS  read-write
   STATUS      current
   DESCRIPTION
       "The timing value to be used to make persistent check on Signal Fail before switching. This is in 100 ms. and the max value is 100 (10 sec)."
   ::= { sispm1040582lrtEPSConfigInstanceEntry 6 }     
   
sispm1040582lrtEpsConfigInstanceCommand OBJECT-TYPE
   SYNTAX      Integer32
   MAX-ACCESS  read-write
   STATUS      current
   DESCRIPTION
       "0:None
	    1:Clear
		2:Lock Out
		3:Forced switch
		4:Manual switch P
		5:Manual switch W
		6:Exercise
		7:Freeze
		8:Lock Out Local
	   "
   ::= { sispm1040582lrtEPSConfigInstanceEntry 7 }     

sispm1040582lrtEpsStatusProtectionState OBJECT-TYPE
   SYNTAX      DisplayString
   MAX-ACCESS  read-only
   STATUS      current
   DESCRIPTION
       "EPS state according to State Transition Tables in G.8031.
	   "
   ::= { sispm1040582lrtEPSConfigInstanceEntry 8 }
   
sispm1040582lrtEpsStatusWorkingFlowState OBJECT-TYPE
   SYNTAX      DisplayString
   MAX-ACCESS  read-only
   STATUS      current
   DESCRIPTION
       "OK: State of working flow is ok
        SF: State of working flow is Signal Fail
		SD: State of working flow is Signal Degrade (for future use)
	   "
   ::= { sispm1040582lrtEPSConfigInstanceEntry 9 }   
   
sispm1040582lrtEpsStatusProtectingFlowState OBJECT-TYPE
   SYNTAX      DisplayString
   MAX-ACCESS  read-only
   STATUS      current
   DESCRIPTION
       "OK: State of protecting flow is ok
        SF: State of protecting flow is Signal Fail
        SD: State of protecting flow is Signal Degrade (for future use)
	   "
   ::= { sispm1040582lrtEPSConfigInstanceEntry 10 }     
   
sispm1040582lrtEpsStatusTransmittedApsRequest OBJECT-TYPE
   SYNTAX      DisplayString
   MAX-ACCESS  read-only
   STATUS      current
   DESCRIPTION
       "The transmitted APS according to State Transition Tables in G.8031.
	   "
   ::= { sispm1040582lrtEPSConfigInstanceEntry 11 }     
   
sispm1040582lrtEpsStatusTransmittedApsReSignal OBJECT-TYPE
   SYNTAX      Integer32
   MAX-ACCESS  read-only
   STATUS      current
   DESCRIPTION
       "The transmitted APS according to State Transition Tables in G.8031.
	   "
   ::= { sispm1040582lrtEPSConfigInstanceEntry 12 }    
   
sispm1040582lrtEpsStatusTransmittedApsBrSignal OBJECT-TYPE
   SYNTAX      Integer32
   MAX-ACCESS  read-only
   STATUS      current
   DESCRIPTION
       "The transmitted APS according to State Transition Tables in G.8031.
	   "
   ::= { sispm1040582lrtEPSConfigInstanceEntry 13 }
   
sispm1040582lrtEpsStatusReceivedApsRequest OBJECT-TYPE
   SYNTAX      DisplayString
   MAX-ACCESS  read-only
   STATUS      current
   DESCRIPTION
       "The received APS according to State Transition Tables in G.8031.
	   "
   ::= { sispm1040582lrtEPSConfigInstanceEntry 14 }   
   
sispm1040582lrtEpsStatusReceivedApsReSignal OBJECT-TYPE
   SYNTAX      Integer32
   MAX-ACCESS  read-only
   STATUS      current
   DESCRIPTION
       "The received APS according to State Transition Tables in G.8031.
	   "
   ::= { sispm1040582lrtEPSConfigInstanceEntry 15 }      
   
sispm1040582lrtEpsStatusReceivedApsBrSignal OBJECT-TYPE
   SYNTAX      Integer32
   MAX-ACCESS  read-only
   STATUS      current
   DESCRIPTION
       "The received APS according to State Transition Tables in G.8031.
	   "
   ::= { sispm1040582lrtEPSConfigInstanceEntry 16 }    

sispm1040582lrtEpsStatusArchitectureMismatch OBJECT-TYPE
   SYNTAX      DisplayString
   MAX-ACCESS  read-only
   STATUS      current
   DESCRIPTION
       "The architecture indicated in the received APS does not match the locally configured.
	   "
   ::= { sispm1040582lrtEPSConfigInstanceEntry 17 }    

sispm1040582lrtEpsStatusAPSOnWorking OBJECT-TYPE
   SYNTAX      DisplayString
   MAX-ACCESS  read-only
   STATUS      current
   DESCRIPTION
       "APS is received on the working flow.
	   "
   ::= { sispm1040582lrtEPSConfigInstanceEntry 18 }     
   
sispm1040582lrtEpsStatusSwitchingIncomplete OBJECT-TYPE
   SYNTAX      DisplayString
   MAX-ACCESS  read-only
   STATUS      current
   DESCRIPTION
       "Traffic is not selected from the same flow instance in the two ends.
	   "
   ::= { sispm1040582lrtEPSConfigInstanceEntry 19 }     
   
sispm1040582lrtEpsStatusNoApsReceived OBJECT-TYPE
   SYNTAX      DisplayString
   MAX-ACCESS  read-only
   STATUS      current
   DESCRIPTION
       "APS PDU is not received from the other end.
	   "
   ::= { sispm1040582lrtEPSConfigInstanceEntry 20 }      
   
-- =======================================================================================================================
 
sispm1040582lrtERPS    OBJECT IDENTIFIER ::= { sispm1040582lrtConfiguration 24 }

sispm1040582lrtERPSTable  OBJECT-TYPE
   SYNTAX      SEQUENCE OF SISPM1040582LRTERPSEntry
   MAX-ACCESS  not-accessible
   STATUS      current
   DESCRIPTION
       "A table of ERPS."
 ::= { sispm1040582lrtERPS 1 }

sispm1040582lrtERPSEntry OBJECT-TYPE
    SYNTAX        SISPM1040582LRTERPSEntry
    MAX-ACCESS    not-accessible
    STATUS        current
    DESCRIPTION
        ""
    INDEX        { sispm1040582lrtErpsIndex }
    ::= { sispm1040582lrtERPSTable 1 }

SISPM1040582LRTERPSEntry ::=
    SEQUENCE {
        sispm1040582lrtErpsIndex                                Integer32,
        sispm1040582lrtErpsID                                   Integer32,
		sispm1040582lrtErpsPort0                                Integer32,
		sispm1040582lrtErpsPort1                                Integer32,
		sispm1040582lrtErpsPort0APSMEP                          Integer32,		
        sispm1040582lrtErpsPort1APSMEP                          Integer32,
        sispm1040582lrtErpsPort0SFMEP                           Integer32,
        sispm1040582lrtErpsPort1SFMEP                           Integer32,	
        sispm1040582lrtErpsRingType                             Integer32,		
        sispm1040582lrtErpsInterconnectedNode                   Integer32,		
        sispm1040582lrtErpsVirtualChannel                       Integer32,		
        sispm1040582lrtErpsMajorRingID                          Integer32,	
        sispm1040582lrtErpsAlarm		                          Integer32,
        sispm1040582lrtErpsRowStatus                            RowStatus
    }

sispm1040582lrtErpsIndex OBJECT-TYPE
   SYNTAX      Integer32
   MAX-ACCESS  not-accessible
   STATUS      current
   DESCRIPTION
       "Index"
   ::= { sispm1040582lrtERPSEntry 1 }

sispm1040582lrtErpsID OBJECT-TYPE
   SYNTAX      Integer32 (1..64)
   MAX-ACCESS  read-create
   STATUS      current
   DESCRIPTION
       "ERPS ID. Range:1-64."
   ::= {sispm1040582lrtERPSEntry 2 }

sispm1040582lrtErpsPort0 OBJECT-TYPE
   SYNTAX      Integer32
   MAX-ACCESS  read-create
   STATUS      current
   DESCRIPTION
       "This will create a Port 0 of the switch in the ring."
   ::= {sispm1040582lrtERPSEntry 3 }   
   
sispm1040582lrtErpsPort1 OBJECT-TYPE
   SYNTAX      Integer32
   MAX-ACCESS  read-create
   STATUS      current
   DESCRIPTION
       "This will create Port 1 of the switch in the Ring. 
	   As interconnected sub-ring will have only one ring port, Port 1 is configured as 0 for interconnected sub-ring.
	   0 in this field indicates that no Port 1 is associated with this instance"
   ::= {sispm1040582lrtERPSEntry 4 }   
   
sispm1040582lrtErpsPort0APSMEP OBJECT-TYPE
   SYNTAX      Integer32
   MAX-ACCESS  read-create
   STATUS      current
   DESCRIPTION
       "The Port 0 APS PDU handling MEP.
	   Range: 1-100."
   ::= {sispm1040582lrtERPSEntry 5 }  
   
sispm1040582lrtErpsPort1APSMEP OBJECT-TYPE
   SYNTAX      Integer32
   MAX-ACCESS  read-create
   STATUS      current
   DESCRIPTION
       "The Port 1 APS PDU handling MEP.
	   Range: 1-100."
   ::= {sispm1040582lrtERPSEntry 6 }     

sispm1040582lrtErpsPort0SFMEP OBJECT-TYPE
   SYNTAX      Integer32
   MAX-ACCESS  read-create
   STATUS      current
   DESCRIPTION
       "The Port 0 Signal Fail reporting MEP.
	   Range: 1-100."
   ::= {sispm1040582lrtERPSEntry 7 }      
   
 sispm1040582lrtErpsPort1SFMEP OBJECT-TYPE
   SYNTAX      Integer32
   MAX-ACCESS  read-create
   STATUS      current
   DESCRIPTION
       "The Port 1 Signal Fail reporting MEP.
	   Range: 1-100."
   ::= {sispm1040582lrtERPSEntry 8 }      
   
sispm1040582lrtErpsRingType OBJECT-TYPE
   SYNTAX      Integer32
   MAX-ACCESS  read-create
   STATUS      current
   DESCRIPTION
       "Type of Protecting ring. It can be either major ring or sub-ring.
	   0:Major
	   1:Sub"
   ::= {sispm1040582lrtERPSEntry 9 }
   
sispm1040582lrtErpsInterconnectedNode OBJECT-TYPE
   SYNTAX      Integer32
   MAX-ACCESS  read-create
   STATUS      current
   DESCRIPTION
       "Interconnected Node indicates that the ring instance is interconnected. 
	   0: not interconnected
	   1: interconnected"
   ::= {sispm1040582lrtERPSEntry 10 }  
   
sispm1040582lrtErpsVirtualChannel OBJECT-TYPE
   SYNTAX      Integer32
   MAX-ACCESS  read-create
   STATUS      current
   DESCRIPTION
       "1: indicates it is a sub-ring with virtual channel. 
	    0: indicates, sub-ring doesn't have virtual channel."
   ::= {sispm1040582lrtERPSEntry 11 }
   
sispm1040582lrtErpsMajorRingID OBJECT-TYPE
   SYNTAX      Integer32
   MAX-ACCESS  read-create
   STATUS      current
   DESCRIPTION
       "Major ring group ID for the interconnected sub-ring.
	   Range:1-64"
   ::= {sispm1040582lrtERPSEntry 12 }   

sispm1040582lrtErpsAlarm OBJECT-TYPE
   SYNTAX      Integer32
   MAX-ACCESS  read-create
   STATUS      current
   DESCRIPTION
       "There is an active alarm on the ERPS."
   ::= {sispm1040582lrtERPSEntry 13 }  
   
sispm1040582lrtErpsRowStatus OBJECT-TYPE
   SYNTAX      RowStatus
   MAX-ACCESS  read-create
   STATUS      current
   DESCRIPTION
       "ERPS Row Status."
   ::= {sispm1040582lrtERPSEntry 14 }      
  
   
sispm1040582lrtErpsConfigInstanceErpsID   OBJECT-TYPE
   SYNTAX      Integer32
   MAX-ACCESS  read-write
   STATUS      current
   DESCRIPTION
	   "Specify ERPS ID for ERPSConfigInstanceEntry and ErpsConfigInstanceVLANConfigTable uesd."
   ::= {sispm1040582lrtERPS 2 }
   

sispm1040582lrtERPSConfigInstanceEntry    OBJECT IDENTIFIER ::= { sispm1040582lrtERPS 3 } 

sispm1040582lrtErpsConfigInstanceConfigured OBJECT-TYPE
   SYNTAX      DisplayString
   MAX-ACCESS  read-only
   STATUS      current
   DESCRIPTION
       "Down: This ERPS is only created and has not yet been configured - is not active.
        Up: This ERPS is configured - is active."
   ::= { sispm1040582lrtERPSConfigInstanceEntry 2 }

sispm1040582lrtErpsConfigInstanceGuardTime OBJECT-TYPE
   SYNTAX      Integer32
   MAX-ACCESS  read-write
   STATUS      current
   DESCRIPTION
       "The period of the guard timer can be configured in 10 ms steps between 10 ms and 2 seconds, with a default value of 500 ms.
	    Guard timeout value to be used to prevent ring nodes from receiving outdated R-APS messages."
   ::= { sispm1040582lrtERPSConfigInstanceEntry 3 }

sispm1040582lrtErpsConfigInstanceWTRTime OBJECT-TYPE
   SYNTAX      Integer32
   MAX-ACCESS  read-write
   STATUS      current
   DESCRIPTION
       "The Wait To Restore timing value to be used in revertive switching.
        The period of the WTR time can be configured by the operator in 1 minute steps between 5 and 12 minutes with a default value of 5 minutes.
		"
   ::= { sispm1040582lrtERPSConfigInstanceEntry 4 }   
   
sispm1040582lrtErpsConfigInstanceHoldOffTime OBJECT-TYPE
   SYNTAX      Integer32
   MAX-ACCESS  read-write
   STATUS      current
   DESCRIPTION
       "The timing value to be used to make persistent check on Signal Fail before switching.
        The range of the hold off timer is 0 to 10 seconds in steps of 100 ms
		"
   ::= { sispm1040582lrtERPSConfigInstanceEntry 5 }      
   
sispm1040582lrtErpsConfigInstanceVersion OBJECT-TYPE
   SYNTAX      Integer32
   MAX-ACCESS  read-write
   STATUS      current
   DESCRIPTION
       "ERPS Protocol Version - v1 or v2
	   1:v1
	   2:v2"
   ::= { sispm1040582lrtERPSConfigInstanceEntry 6 }     
   
sispm1040582lrtErpsConfigInstanceRevertive OBJECT-TYPE
   SYNTAX      Integer32
   MAX-ACCESS  read-write
   STATUS      current
   DESCRIPTION
       "1:Revertive mode
	    0:Non-Revertive mode"
   ::= { sispm1040582lrtERPSConfigInstanceEntry 7 }     

sispm1040582lrtErpsConfigInstanceRPLRole OBJECT-TYPE
   SYNTAX      Integer32
   MAX-ACCESS  read-write
   STATUS      current
   DESCRIPTION
       "It can be either RPL owner or RPL Neighbor.
	   0:None 
	   1:RPL owner
	   2:RPL Neighbor
	   Please set RPLPort first.
	   "
   ::= { sispm1040582lrtERPSConfigInstanceEntry 8 }
   
sispm1040582lrtErpsConfigInstanceRPLPort OBJECT-TYPE
   SYNTAX      Integer32
   MAX-ACCESS  read-write
   STATUS      current
   DESCRIPTION
       "This allows to select the east port or west port as the RPL block.
	   0:None
	   1:Port0
	   2:Port1
	   Please set RPLRole after specify RPLPort.
	   "
   ::= { sispm1040582lrtERPSConfigInstanceEntry 9 }   
   
sispm1040582lrtErpsConfigInstanceClear OBJECT-TYPE
   SYNTAX      Integer32
   MAX-ACCESS  read-write
   STATUS      current
   DESCRIPTION
       "If the owner has to be changed, then the clear check box allows to clear the RPL owner for that ERPS ring.
	   0: no clear
	   1: clear
	   "
   ::= { sispm1040582lrtERPSConfigInstanceEntry 10 }     
   
sispm1040582lrtErpsConfigInstanceTopologyChange OBJECT-TYPE
   SYNTAX      Integer32
   MAX-ACCESS  read-write
   STATUS      current
   DESCRIPTION
       "1: indicates that the topology changes in the sub-ring are propagated in the major ring.
	    0: indicates that the topology changes in the sub-ring are not propagated in the major ring.
	   "
   ::= { sispm1040582lrtERPSConfigInstanceEntry 11 }     
 
sispm1040582lrtErpsConfigInstanceCommand OBJECT-TYPE
   SYNTAX      Integer32
   MAX-ACCESS  read-write
   STATUS      current
   DESCRIPTION
       "0:None
	    1:Manual Switch
		2:Forced Switch
		3:Clear
		Please set InstancePort first.
	   "
   ::= { sispm1040582lrtERPSConfigInstanceEntry 12 }  
 
sispm1040582lrtErpsConfigInstancePort OBJECT-TYPE
   SYNTAX      Integer32
   MAX-ACCESS  read-write
   STATUS      current
   DESCRIPTION
       "0:None
	   1:Port0
	   2:Port1
	   Please set InstanceCommand after specify InstancePort.
	   "
   ::= { sispm1040582lrtERPSConfigInstanceEntry 13 }     
   
sispm1040582lrtErpsStatusProtectionState OBJECT-TYPE
   SYNTAX      DisplayString
   MAX-ACCESS  read-only
   STATUS      current
   DESCRIPTION
       "ERPS state according to State Transition Tables in G.8032.
	   "
   ::= { sispm1040582lrtERPSConfigInstanceEntry 14 }        
   
sispm1040582lrtErpsStatusPort0 OBJECT-TYPE
   SYNTAX      DisplayString
   MAX-ACCESS  read-only
   STATUS      current
   DESCRIPTION
       "OK: State of East port is ok
        SF: State of East port is Signal Fail
	   "
   ::= { sispm1040582lrtERPSConfigInstanceEntry 15 }        
   
sispm1040582lrtErpsStatusPort1 OBJECT-TYPE
   SYNTAX      DisplayString
   MAX-ACCESS  read-only
   STATUS      current
   DESCRIPTION
       "OK: State of West port is ok
        SF: State of West port is Signal Fail
	   "
   ::= { sispm1040582lrtERPSConfigInstanceEntry 16 }    
   
sispm1040582lrtErpsStatusTransmitAPS OBJECT-TYPE
   SYNTAX      DisplayString
   MAX-ACCESS  read-only
   STATUS      current
   DESCRIPTION
       "The transmitted APS according to State Transition Tables in G.8032.
	   "
   ::= { sispm1040582lrtERPSConfigInstanceEntry 17 }    

sispm1040582lrtErpsStatusPort0ReceiveAPS OBJECT-TYPE
   SYNTAX      DisplayString
   MAX-ACCESS  read-only
   STATUS      current
   DESCRIPTION
       "The received APS on Port 0 according to State Transition Tables in G.8032.
	   "
   ::= { sispm1040582lrtERPSConfigInstanceEntry 18 } 

sispm1040582lrtErpsStatusPort1ReceiveAPS OBJECT-TYPE
   SYNTAX      DisplayString
   MAX-ACCESS  read-only
   STATUS      current
   DESCRIPTION
       "The received APS on Port 1 according to State Transition Tables in G.8032.
	   "
   ::= { sispm1040582lrtERPSConfigInstanceEntry 19 }    
   
sispm1040582lrtErpsStatusWTRRemaining OBJECT-TYPE
   SYNTAX      Integer32
   MAX-ACCESS  read-only
   STATUS      current
   DESCRIPTION
       "Remaining WTR timeout in milliseconds.
	   "
   ::= { sispm1040582lrtERPSConfigInstanceEntry 20 }   
   
sispm1040582lrtErpsStatusRPLUnblocked OBJECT-TYPE
   SYNTAX      DisplayString
   MAX-ACCESS  read-only
   STATUS      current
   DESCRIPTION
       "APS is received on the working flow.
	   "
   ::= { sispm1040582lrtERPSConfigInstanceEntry 21 }      
   
sispm1040582lrtErpsStatusNoAPSReceived OBJECT-TYPE
   SYNTAX      DisplayString
   MAX-ACCESS  read-only
   STATUS      current
   DESCRIPTION
       "RAPS PDU is not received from the other end.
	   "
   ::= { sispm1040582lrtERPSConfigInstanceEntry 22 }   
   
sispm1040582lrtErpsStatusPort0BlockStatus OBJECT-TYPE
   SYNTAX      DisplayString
   MAX-ACCESS  read-only
   STATUS      current
   DESCRIPTION
       "Block status for Port 0 (Both traffic and R-APS block status). R-APS channel is never blocked on sub-rings without virtual channel.
	   "
   ::= { sispm1040582lrtERPSConfigInstanceEntry 23 }      
   
sispm1040582lrtErpsStatusPort1BlockStatus OBJECT-TYPE
   SYNTAX      DisplayString
   MAX-ACCESS  read-only
   STATUS      current
   DESCRIPTION
       "Block status for Port 1 (Both traffic and R-APS block status). R-APS channel is never blocked on sub-rings without virtual channel.
	   "
   ::= { sispm1040582lrtERPSConfigInstanceEntry 24 }       
   
sispm1040582lrtErpsStatusFOPAlarm OBJECT-TYPE
   SYNTAX      DisplayString
   MAX-ACCESS  read-only
   STATUS      current
   DESCRIPTION
       "Failure of Protocol Defect(FOP) status:
	   FOP is not detected
	   FOP is detected
	   "
   ::= { sispm1040582lrtERPSConfigInstanceEntry 25 }      
   
sispm1040582lrtErpsConfigInstanceVLANConfigTable  OBJECT-TYPE
   SYNTAX      SEQUENCE OF SISPM1040582LRTErpsConfigInstanceVLANConfigEntry
   MAX-ACCESS  not-accessible
   STATUS      current
   DESCRIPTION
       "A table of ERPS VLANConfig."
 ::= { sispm1040582lrtERPS 4 }

sispm1040582lrtErpsConfigInstanceVLANConfigEntry OBJECT-TYPE
    SYNTAX        SISPM1040582LRTErpsConfigInstanceVLANConfigEntry
    MAX-ACCESS    not-accessible
    STATUS        current
    DESCRIPTION
        ""
    INDEX        { sispm1040582lrtErpsConfigInstanceVLANConfigIndex }
    ::= { sispm1040582lrtErpsConfigInstanceVLANConfigTable 1 }

SISPM1040582LRTErpsConfigInstanceVLANConfigEntry ::=
    SEQUENCE {
        sispm1040582lrtErpsConfigInstanceVLANConfigIndex            Integer32,
        sispm1040582lrtErpsConfigInstanceVLANConfigVLANID           Integer32,
        sispm1040582lrtErpsConfigInstanceVLANConfigRowStatus        RowStatus
    }

sispm1040582lrtErpsConfigInstanceVLANConfigIndex OBJECT-TYPE
   SYNTAX      Integer32
   MAX-ACCESS  not-accessible
   STATUS      current
   DESCRIPTION
       "Index"
   ::= { sispm1040582lrtErpsConfigInstanceVLANConfigEntry 1 }

sispm1040582lrtErpsConfigInstanceVLANConfigVLANID OBJECT-TYPE
   SYNTAX      Integer32 (1..4095)
   MAX-ACCESS  read-create
   STATUS      current
   DESCRIPTION
       "ERPS VLAN Config ID. Range:1-4095."
   ::= {sispm1040582lrtErpsConfigInstanceVLANConfigEntry 2 }

sispm1040582lrtErpsConfigInstanceVLANConfigRowStatus OBJECT-TYPE
   SYNTAX      RowStatus
   MAX-ACCESS  read-create
   STATUS      current
   DESCRIPTION
       "ERPS VLAN Config Row Status."
   ::= {sispm1040582lrtErpsConfigInstanceVLANConfigEntry 3 }   
-- =======================================================================================================================

sispm1040582lrtVLANTranslation    OBJECT IDENTIFIER ::= { sispm1040582lrtConfiguration 25 }

sispm1040582lrtVLANTranslationPortTable  OBJECT-TYPE
   SYNTAX      SEQUENCE OF SISPM1040582LRTVLANTranslationPortEntry
   MAX-ACCESS  not-accessible
   STATUS      current
   DESCRIPTION
       "A table of VLANTranslationPort."
 ::= { sispm1040582lrtVLANTranslation 1 }

sispm1040582lrtVLANTranslationPortEntry OBJECT-TYPE
    SYNTAX        SISPM1040582LRTVLANTranslationPortEntry
    MAX-ACCESS    not-accessible
    STATUS        current
    DESCRIPTION
        "An entry in the VLANTranslationPort table."
    INDEX        { sispm1040582lrtVLANTranslationPortIndex }
    ::= { sispm1040582lrtVLANTranslationPortTable 1 }

SISPM1040582LRTVLANTranslationPortEntry ::=
    SEQUENCE {
        sispm1040582lrtVLANTranslationPortIndex                Integer32,
        sispm1040582lrtVLANTranslationPortDefault              Integer32,
        sispm1040582lrtVLANTranslationPortGroupID              Integer32
    }

sispm1040582lrtVLANTranslationPortIndex OBJECT-TYPE
   SYNTAX      Integer32
   MAX-ACCESS  not-accessible
   STATUS      current
   DESCRIPTION
       "VLANTranslationPort index."
   ::= {sispm1040582lrtVLANTranslationPortEntry 1 }

sispm1040582lrtVLANTranslationPortDefault OBJECT-TYPE
   SYNTAX      Integer32
   MAX-ACCESS  read-write
   STATUS      current
   DESCRIPTION
       "Set the switch port to use the default VLAN Translation Group.
	   1:set
	   0:not set"
   ::= {sispm1040582lrtVLANTranslationPortEntry 2 }

sispm1040582lrtVLANTranslationPortGroupID OBJECT-TYPE
   SYNTAX      Integer32
   MAX-ACCESS  read-write
   STATUS      current
   DESCRIPTION
       "The VLAN Translation mappings are organized into Groups, identified by the Group ID."
   ::= {sispm1040582lrtVLANTranslationPortEntry 3 }
   
   
   
sispm1040582lrtVLANTranslationMappingTable  OBJECT-TYPE
   SYNTAX      SEQUENCE OF SISPM1040582LRTVLANTranslationMappingEntry
   MAX-ACCESS  not-accessible
   STATUS      current
   DESCRIPTION
       "A table of VLANTranslationMapping."
 ::= { sispm1040582lrtVLANTranslation 2 }

sispm1040582lrtVLANTranslationMappingEntry OBJECT-TYPE
    SYNTAX        SISPM1040582LRTVLANTranslationMappingEntry
    MAX-ACCESS    not-accessible
    STATUS        current
    DESCRIPTION
        "An entry in the VLANTranslationMapping table."
    INDEX        { sispm1040582lrtVLANTranslationMappingIndex }
    ::= { sispm1040582lrtVLANTranslationMappingTable 1 }

SISPM1040582LRTVLANTranslationMappingEntry ::=
    SEQUENCE {
        sispm1040582lrtVLANTranslationMappingIndex                Integer32,
        sispm1040582lrtVLANTranslationMappingGroupID              Integer32,
        sispm1040582lrtVLANTranslationMappingVID                  Integer32,
		sispm1040582lrtVLANTranslationMappingTVID                 Integer32,
		sispm1040582lrtVLANTranslationMappingRowStatus            RowStatus
    }

sispm1040582lrtVLANTranslationMappingIndex OBJECT-TYPE
   SYNTAX      Integer32
   MAX-ACCESS  not-accessible
   STATUS      current
   DESCRIPTION
       "VLANTranslationMapping index."
   ::= {sispm1040582lrtVLANTranslationMappingEntry 1 }

sispm1040582lrtVLANTranslationMappingGroupID OBJECT-TYPE
   SYNTAX      Integer32
   MAX-ACCESS  read-create
   STATUS      current
   DESCRIPTION
       "The VLAN Translation mappings are organized into Groups, identified by the Group ID."
   ::= {sispm1040582lrtVLANTranslationMappingEntry 2 }

sispm1040582lrtVLANTranslationMappingVID OBJECT-TYPE
   SYNTAX      Integer32
   MAX-ACCESS  read-create
   STATUS      current
   DESCRIPTION
       "Range:1-4095"
   ::= {sispm1040582lrtVLANTranslationMappingEntry 3 }

sispm1040582lrtVLANTranslationMappingTVID OBJECT-TYPE
   SYNTAX      Integer32
   MAX-ACCESS  read-create
   STATUS      current
   DESCRIPTION
       "Range:1-4095"
   ::= {sispm1040582lrtVLANTranslationMappingEntry 4 }   
   
sispm1040582lrtVLANTranslationMappingRowStatus OBJECT-TYPE
   SYNTAX      RowStatus
   MAX-ACCESS  read-create
   STATUS      current
   DESCRIPTION
       "VLANTranslationMapping Row Status."
   ::= {sispm1040582lrtVLANTranslationMappingEntry 5 }
   
sispm1040582lrtMEP    OBJECT IDENTIFIER ::= { sispm1040582lrtConfiguration 26 }    

sispm1040582lrtMEPTable  OBJECT-TYPE
   SYNTAX      SEQUENCE OF SISPM1040582LRTMEPEntry
   MAX-ACCESS  not-accessible
   STATUS      current
   DESCRIPTION
       "A table of MEP."
 ::= { sispm1040582lrtMEP 1 }

sispm1040582lrtMEPEntry OBJECT-TYPE
    SYNTAX        SISPM1040582LRTMEPEntry
    MAX-ACCESS    not-accessible
    STATUS        current
    DESCRIPTION
        "An entry in the MEP table."
    INDEX        { sispm1040582lrtMEPIndex }
    ::= { sispm1040582lrtMEPTable 1 }

SISPM1040582LRTMEPEntry ::=
    SEQUENCE {
        sispm1040582lrtMEPIndex                         Integer32,
        sispm1040582lrtMepInstance                      Integer32,
        sispm1040582lrtMepDomain                        Integer32,
        sispm1040582lrtMepMode                          Integer32,
		sispm1040582lrtMepDirection                     Integer32,
		sispm1040582lrtMepResidencePort                 Integer32,
		sispm1040582lrtMepLevel                         Integer32,
		sispm1040582lrtMepFlowInstance                  Integer32,
		sispm1040582lrtMepTaggedVID                     Integer32,
		sispm1040582lrtMepEPSInstance                   DisplayString,
		sispm1040582lrtMepThisMAC                       DisplayString,
		sispm1040582lrtMepAlarm                         DisplayString,
        sispm1040582lrtMepRowStatus                     RowStatus
    }

sispm1040582lrtMEPIndex OBJECT-TYPE
   SYNTAX      Integer32
   MAX-ACCESS  not-accessible
   STATUS      current
   DESCRIPTION
       "MEP Table index."
   ::= {sispm1040582lrtMEPEntry 1 }

sispm1040582lrtMepInstance OBJECT-TYPE
   SYNTAX      Integer32
   MAX-ACCESS  read-create
   STATUS      current
   DESCRIPTION
       ""
   ::= {sispm1040582lrtMEPEntry 2 }

sispm1040582lrtMepDomain OBJECT-TYPE
   SYNTAX      Integer32
   MAX-ACCESS  read-create
   STATUS      current
   DESCRIPTION
       ""
   ::= {sispm1040582lrtMEPEntry 3 }  
   
sispm1040582lrtMepMode OBJECT-TYPE
   SYNTAX      Integer32
   MAX-ACCESS  read-create
   STATUS      current
   DESCRIPTION
       ""
   ::= {sispm1040582lrtMEPEntry 4 }    

sispm1040582lrtMepDirection OBJECT-TYPE
   SYNTAX      Integer32
   MAX-ACCESS  read-create
   STATUS      current
   DESCRIPTION
       ""
   ::= {sispm1040582lrtMEPEntry 5 }  

sispm1040582lrtMepResidencePort OBJECT-TYPE
   SYNTAX      Integer32
   MAX-ACCESS  read-create
   STATUS      current
   DESCRIPTION
       ""
   ::= {sispm1040582lrtMEPEntry 6 }  

sispm1040582lrtMepLevel OBJECT-TYPE
   SYNTAX      Integer32
   MAX-ACCESS  read-create
   STATUS      current
   DESCRIPTION
       ""
   ::= {sispm1040582lrtMEPEntry 7 }  

sispm1040582lrtMepFlowInstance OBJECT-TYPE
   SYNTAX      Integer32
   MAX-ACCESS  read-create
   STATUS      current
   DESCRIPTION
       ""
   ::= {sispm1040582lrtMEPEntry 8 }  

sispm1040582lrtMepTaggedVID OBJECT-TYPE
   SYNTAX      Integer32
   MAX-ACCESS  read-create
   STATUS      current
   DESCRIPTION
       ""
   ::= {sispm1040582lrtMEPEntry 9 }    

sispm1040582lrtMepEPSInstance OBJECT-TYPE
   SYNTAX      DisplayString
   MAX-ACCESS  read-only
   STATUS      current
   DESCRIPTION
       ""
   ::= {sispm1040582lrtMEPEntry 10 }     
   
sispm1040582lrtMepThisMAC OBJECT-TYPE
   SYNTAX      DisplayString
   MAX-ACCESS  read-only
   STATUS      current
   DESCRIPTION
       ""
   ::= {sispm1040582lrtMEPEntry 11 }

sispm1040582lrtMepAlarm OBJECT-TYPE
   SYNTAX      DisplayString
   MAX-ACCESS  read-only
   STATUS      current
   DESCRIPTION
       ""
   ::= {sispm1040582lrtMEPEntry 12 }  
   
sispm1040582lrtMepRowStatus OBJECT-TYPE
   SYNTAX      RowStatus
   MAX-ACCESS  read-create
   STATUS      current
   DESCRIPTION
       "MEP Row Status."
   ::= {sispm1040582lrtMEPEntry 13 }
 
sispm1040582lrtMepInstanceID   OBJECT-TYPE
   SYNTAX      Integer32
   MAX-ACCESS  read-write
   STATUS      current
   DESCRIPTION
	   "Specify MEP Instance ID for the following item and table uesd."
   ::= {sispm1040582lrtMEP 2 } 
 

sispm1040582lrtMepInstanceConfEntry    OBJECT IDENTIFIER ::= { sispm1040582lrtMEP 3 }

sispm1040582lrtMepInstanceConfLevel OBJECT-TYPE
   SYNTAX      Integer32
   MAX-ACCESS  read-write
   STATUS      current
   DESCRIPTION
       ""
   ::= {sispm1040582lrtMepInstanceConfEntry 2 }  

sispm1040582lrtMepInstanceConfFormat OBJECT-TYPE
   SYNTAX      Integer32
   MAX-ACCESS  read-write
   STATUS      current
   DESCRIPTION
       ""
   ::= {sispm1040582lrtMepInstanceConfEntry 3 }  

sispm1040582lrtMepInstanceConfDomainName OBJECT-TYPE
   SYNTAX      DisplayString
   MAX-ACCESS  read-write
   STATUS      current
   DESCRIPTION
       ""
   ::= {sispm1040582lrtMepInstanceConfEntry 4 }  

sispm1040582lrtMepInstanceConfMEGid OBJECT-TYPE
   SYNTAX      DisplayString
   MAX-ACCESS  read-write
   STATUS      current
   DESCRIPTION
       ""
   ::= {sispm1040582lrtMepInstanceConfEntry 5 } 

sispm1040582lrtMepInstanceConfMEPid OBJECT-TYPE
   SYNTAX      Integer32
   MAX-ACCESS  read-write
   STATUS      current
   DESCRIPTION
       ""
   ::= {sispm1040582lrtMepInstanceConfEntry 6 }   

sispm1040582lrtMepInstanceConfTaggedVID OBJECT-TYPE
   SYNTAX      Integer32
   MAX-ACCESS  read-write
   STATUS      current
   DESCRIPTION
       ""
   ::= {sispm1040582lrtMepInstanceConfEntry 7 }      
  
sispm1040582lrtMepInstanceConfSyslog OBJECT-TYPE
   SYNTAX      Integer32
   MAX-ACCESS  read-write
   STATUS      current
   DESCRIPTION
       ""
   ::= {sispm1040582lrtMepInstanceConfEntry 8 }  
  
sispm1040582lrtMepInstanceConfcLevel OBJECT-TYPE
   SYNTAX      DisplayString
   MAX-ACCESS  read-only
   STATUS      current
   DESCRIPTION
       ""
   ::= {sispm1040582lrtMepInstanceConfEntry 9 }  
 
sispm1040582lrtMepInstanceConfcMEG OBJECT-TYPE
   SYNTAX      DisplayString
   MAX-ACCESS  read-only
   STATUS      current
   DESCRIPTION
       ""
   ::= {sispm1040582lrtMepInstanceConfEntry 10 }   
 
sispm1040582lrtMepInstanceConfcMEP OBJECT-TYPE
   SYNTAX      DisplayString
   MAX-ACCESS  read-only
   STATUS      current
   DESCRIPTION
       ""
   ::= {sispm1040582lrtMepInstanceConfEntry 11 }   
 
sispm1040582lrtMepInstanceConfcAIS OBJECT-TYPE
   SYNTAX      DisplayString
   MAX-ACCESS  read-only
   STATUS      current
   DESCRIPTION
       ""
   ::= {sispm1040582lrtMepInstanceConfEntry 12 }   
   
sispm1040582lrtMepInstanceConfcLCK OBJECT-TYPE
   SYNTAX      DisplayString
   MAX-ACCESS  read-only
   STATUS      current
   DESCRIPTION
       ""
   ::= {sispm1040582lrtMepInstanceConfEntry 13 }   
 
sispm1040582lrtMepInstanceConfcLoop OBJECT-TYPE
   SYNTAX      DisplayString
   MAX-ACCESS  read-only
   STATUS      current
   DESCRIPTION
       ""
   ::= {sispm1040582lrtMepInstanceConfEntry 14 }  

sispm1040582lrtMepInstanceConfcConfig OBJECT-TYPE
   SYNTAX      DisplayString
   MAX-ACCESS  read-only
   STATUS      current
   DESCRIPTION
       ""
   ::= {sispm1040582lrtMepInstanceConfEntry 15 }  

sispm1040582lrtMepInstanceConfcDEG OBJECT-TYPE
   SYNTAX      DisplayString
   MAX-ACCESS  read-only
   STATUS      current
   DESCRIPTION
       ""
   ::= {sispm1040582lrtMepInstanceConfEntry 16 }  

sispm1040582lrtMepInstanceConfcSSF OBJECT-TYPE
   SYNTAX      DisplayString
   MAX-ACCESS  read-only
   STATUS      current
   DESCRIPTION
       ""
   ::= {sispm1040582lrtMepInstanceConfEntry 17 }  

sispm1040582lrtMepInstanceConfaBLK OBJECT-TYPE
   SYNTAX      DisplayString
   MAX-ACCESS  read-only
   STATUS      current
   DESCRIPTION
       ""
   ::= {sispm1040582lrtMepInstanceConfEntry 18 }  

sispm1040582lrtMepInstanceConfaTSD OBJECT-TYPE
   SYNTAX      DisplayString
   MAX-ACCESS  read-only
   STATUS      current
   DESCRIPTION
       ""
   ::= {sispm1040582lrtMepInstanceConfEntry 19 }  

sispm1040582lrtMepInstanceConfaTSF OBJECT-TYPE
   SYNTAX      DisplayString
   MAX-ACCESS  read-only
   STATUS      current
   DESCRIPTION
       ""
   ::= {sispm1040582lrtMepInstanceConfEntry 20 }     
 
 
sispm1040582lrtPeerMepConfTable  OBJECT-TYPE
   SYNTAX      SEQUENCE OF SISPM1040582LRTPeerMepConfEntry
   MAX-ACCESS  not-accessible
   STATUS      current
   DESCRIPTION
       "A table of MEP."
 ::= { sispm1040582lrtMEP 4 }

sispm1040582lrtPeerMepConfEntry OBJECT-TYPE
    SYNTAX        SISPM1040582LRTPeerMepConfEntry
    MAX-ACCESS    not-accessible
    STATUS        current
    DESCRIPTION
        ""
    INDEX        { sispm1040582lrtPeerMepConfIndex }
    ::= { sispm1040582lrtPeerMepConfTable 1 }

SISPM1040582LRTPeerMepConfEntry ::=
    SEQUENCE {
        sispm1040582lrtPeerMepConfIndex                       Integer32,
        sispm1040582lrtPeerMepConfPeerMEPID                   Integer32,
		sispm1040582lrtPeerMepConfUnicastPeerMAC              DisplayString,
        sispm1040582lrtPeerMepConfcLOC                        DisplayString,
        sispm1040582lrtPeerMepConfcRDI                        DisplayString,
        sispm1040582lrtPeerMepConfcPeriod                     DisplayString,	
        sispm1040582lrtPeerMepConfcPriority                   DisplayString,			
        sispm1040582lrtPeerMepConfRowStatus                   RowStatus
    }

sispm1040582lrtPeerMepConfIndex OBJECT-TYPE
   SYNTAX      Integer32
   MAX-ACCESS  not-accessible
   STATUS      current
   DESCRIPTION
       "Index"
   ::= { sispm1040582lrtPeerMepConfEntry 1 }

sispm1040582lrtPeerMepConfPeerMEPID OBJECT-TYPE
   SYNTAX      Integer32 
   MAX-ACCESS  read-create
   STATUS      current
   DESCRIPTION
       "Peer MEP ID"
   ::= {sispm1040582lrtPeerMepConfEntry 2 }

sispm1040582lrtPeerMepConfUnicastPeerMAC OBJECT-TYPE
   SYNTAX      DisplayString
   MAX-ACCESS  read-create
   STATUS      current
   DESCRIPTION
       ""
   ::= {sispm1040582lrtPeerMepConfEntry 3 }   
   
sispm1040582lrtPeerMepConfcLOC OBJECT-TYPE
   SYNTAX      DisplayString
   MAX-ACCESS  read-create
   STATUS      current
   DESCRIPTION
       ""
   ::= {sispm1040582lrtPeerMepConfEntry 4 }      
   
sispm1040582lrtPeerMepConfcRDI OBJECT-TYPE
   SYNTAX      DisplayString
   MAX-ACCESS  read-create
   STATUS      current
   DESCRIPTION
       ""
   ::= {sispm1040582lrtPeerMepConfEntry 5 }    
   
sispm1040582lrtPeerMepConfcPeriod OBJECT-TYPE
   SYNTAX      DisplayString
   MAX-ACCESS  read-create
   STATUS      current
   DESCRIPTION
       ""
   ::= {sispm1040582lrtPeerMepConfEntry 6 }  

sispm1040582lrtPeerMepConfcPriority OBJECT-TYPE
   SYNTAX      DisplayString
   MAX-ACCESS  read-create
   STATUS      current
   DESCRIPTION
       ""
   ::= {sispm1040582lrtPeerMepConfEntry 7 }  
   
sispm1040582lrtPeerMepConfRowStatus OBJECT-TYPE
   SYNTAX      RowStatus
   MAX-ACCESS  read-create
   STATUS      current
   DESCRIPTION
       "Peer Mep Conf Row Status."
   ::= {sispm1040582lrtPeerMepConfEntry 8 }
   
sispm1040582lrtFunctionalConf    OBJECT IDENTIFIER ::= { sispm1040582lrtMEP 5 }

sispm1040582lrtFunctionalConfContinuityCheckEnable OBJECT-TYPE
   SYNTAX      Integer32
   MAX-ACCESS  read-write
   STATUS      current
   DESCRIPTION
       "0:disable
	   1:enable"
   ::= {sispm1040582lrtFunctionalConf 2 } 
   
sispm1040582lrtFunctionalConfContinuityCheckPriority OBJECT-TYPE
   SYNTAX      Integer32
   MAX-ACCESS  read-write
   STATUS      current
   DESCRIPTION
       "range:0-7"
   ::= {sispm1040582lrtFunctionalConf 3 } 
   
sispm1040582lrtFunctionalConfContinuityCheckFrameRate OBJECT-TYPE
   SYNTAX      Integer32
   MAX-ACCESS  read-write
   STATUS      current
   DESCRIPTION
       "range:1-7
	   1: 300 f/sec
	   2: 100 f/sec
	   3: 10 f/sec
	   4: 1 f/sec
	   5: 6 f/min
	   6: 1 f/min
	   7: 6 f/hour"
   ::= {sispm1040582lrtFunctionalConf 4 }    

sispm1040582lrtFunctionalConfContinuityCheckTLV OBJECT-TYPE
   SYNTAX      Integer32
   MAX-ACCESS  read-write
   STATUS      current
   DESCRIPTION
       "0:disable
	   1:enable"
   ::= {sispm1040582lrtFunctionalConf 5 } 

sispm1040582lrtFunctionalConfAPSProtocolEnable OBJECT-TYPE
   SYNTAX      Integer32
   MAX-ACCESS  read-write
   STATUS      current
   DESCRIPTION
       "0:disable
	   1:enable"
   ::= {sispm1040582lrtFunctionalConf 6 }   

sispm1040582lrtFunctionalConfAPSProtocolPriority OBJECT-TYPE
   SYNTAX      Integer32
   MAX-ACCESS  read-write
   STATUS      current
   DESCRIPTION
       "range:0-7"
   ::= {sispm1040582lrtFunctionalConf 7 }   
   
sispm1040582lrtFunctionalConfAPSProtocolCast OBJECT-TYPE
   SYNTAX      Integer32
   MAX-ACCESS  read-write
   STATUS      current
   DESCRIPTION
       "0: Unicast destination address
	   1: Multicast destination address"
   ::= {sispm1040582lrtFunctionalConf 8 }     

sispm1040582lrtFunctionalConfAPSProtocolType OBJECT-TYPE
   SYNTAX      Integer32
   MAX-ACCESS  read-write
   STATUS      current
   DESCRIPTION
       "1: Linear protection APS
	   2: Ring protection APS"
   ::= {sispm1040582lrtFunctionalConf 9 }  

sispm1040582lrtFunctionalConfAPSProtocolLastOctet OBJECT-TYPE
   SYNTAX      Integer32
   MAX-ACCESS  read-write
   STATUS      current
   DESCRIPTION
       "range:0-255"
   ::= {sispm1040582lrtFunctionalConf 10 }    
   
sispm1040582lrtTLVConf    OBJECT IDENTIFIER ::= { sispm1040582lrtMEP 6 }   

sispm1040582lrtTLVConfOUIFirst OBJECT-TYPE
   SYNTAX      Integer32
   MAX-ACCESS  read-write
   STATUS      current
   DESCRIPTION
       "range:0-255"
   ::= {sispm1040582lrtTLVConf 2 } 
   
sispm1040582lrtTLVConfOUISecond OBJECT-TYPE
   SYNTAX      Integer32
   MAX-ACCESS  read-write
   STATUS      current
   DESCRIPTION
       "range:0-255"
   ::= {sispm1040582lrtTLVConf 3 } 
   
sispm1040582lrtTLVConfOUIThird OBJECT-TYPE
   SYNTAX      Integer32
   MAX-ACCESS  read-write
   STATUS      current
   DESCRIPTION
       "range:0-255"
   ::= {sispm1040582lrtTLVConf 4 } 
   
sispm1040582lrtTLVConfSubType OBJECT-TYPE
   SYNTAX      Integer32
   MAX-ACCESS  read-write
   STATUS      current
   DESCRIPTION
       "range:0-255"
   ::= {sispm1040582lrtTLVConf 5 }    
   
sispm1040582lrtTLVConfValue OBJECT-TYPE
   SYNTAX      Integer32
   MAX-ACCESS  read-write
   STATUS      current
   DESCRIPTION
       "range:0-255"
   ::= {sispm1040582lrtTLVConf 6 }  


sispm1040582lrtTLVConfStateTable OBJECT-TYPE
   SYNTAX      SEQUENCE OF SISPM1040582LRTTLVConfStateEntry
   MAX-ACCESS  not-accessible
   STATUS      current
   DESCRIPTION
       "TLV Conf State Table"
   ::= { sispm1040582lrtMEP 7 }

sispm1040582lrtTLVConfStateEntry OBJECT-TYPE
   SYNTAX      SISPM1040582LRTTLVConfStateEntry
   MAX-ACCESS  not-accessible
   STATUS      current
   DESCRIPTION
       "TLV Conf State Entry"
   INDEX    { sispm1040582lrtTLVConfStateIndex  }
   ::= { sispm1040582lrtTLVConfStateTable 1 }

SISPM1040582LRTTLVConfStateEntry ::= SEQUENCE {
   sispm1040582lrtTLVConfStateIndex                                Integer32,
   sispm1040582lrtTLVConfStatePeerMEPID                            Integer32,
   sispm1040582lrtTLVConfStateCCOrganizationSpecificOUIFirst       Integer32,
   sispm1040582lrtTLVConfStateCCOrganizationSpecificOUISecond      Integer32,
   sispm1040582lrtTLVConfStateCCOrganizationSpecificOUIThird       Integer32,  
   sispm1040582lrtTLVConfStateCCOrganizationSpecificSubType        Integer32,  
   sispm1040582lrtTLVConfStateCCOrganizationSpecificValue          Integer32,  
   sispm1040582lrtTLVConfStateCCOrganizationSpecificLastRX         DisplayString, 
   sispm1040582lrtTLVConfStateCCPortStatusValue                    Integer32,
   sispm1040582lrtTLVConfStateCCPortStatusLastRX                   DisplayString, 
   sispm1040582lrtTLVConfStateCCInterfaceStatusValue               Integer32,
   sispm1040582lrtTLVConfStateCCInterfaceStatusLastRX              DisplayString
}

sispm1040582lrtTLVConfStateIndex OBJECT-TYPE
   SYNTAX      Integer32
   MAX-ACCESS  not-accessible
   STATUS      current
   DESCRIPTION
       "Index"
   ::= { sispm1040582lrtTLVConfStateEntry 1 }
   
sispm1040582lrtTLVConfStatePeerMEPID OBJECT-TYPE
   SYNTAX      Integer32
   MAX-ACCESS  read-only
   STATUS      current
   DESCRIPTION
       "Peer MEP ID"
   ::= { sispm1040582lrtTLVConfStateEntry 2 }   
   
sispm1040582lrtTLVConfStateCCOrganizationSpecificOUIFirst OBJECT-TYPE
   SYNTAX      Integer32
   MAX-ACCESS  read-only
   STATUS      current
   DESCRIPTION
       "The last received first value in the OUI field."
   ::= { sispm1040582lrtTLVConfStateEntry 3 }      
   
sispm1040582lrtTLVConfStateCCOrganizationSpecificOUISecond OBJECT-TYPE
   SYNTAX      Integer32
   MAX-ACCESS  read-only
   STATUS      current
   DESCRIPTION
       "The last received second value in the OS TLV OUI field."
   ::= { sispm1040582lrtTLVConfStateEntry 4 }    
   
sispm1040582lrtTLVConfStateCCOrganizationSpecificOUIThird OBJECT-TYPE
   SYNTAX      Integer32
   MAX-ACCESS  read-only
   STATUS      current
   DESCRIPTION
       "The last received third value in the OS TLV OUI field."
   ::= { sispm1040582lrtTLVConfStateEntry 5 }  
   
sispm1040582lrtTLVConfStateCCOrganizationSpecificSubType OBJECT-TYPE
   SYNTAX      Integer32
   MAX-ACCESS  read-only
   STATUS      current
   DESCRIPTION
       "The last received value in the OS TLV Sub-Type field."
   ::= { sispm1040582lrtTLVConfStateEntry 6 }   

sispm1040582lrtTLVConfStateCCOrganizationSpecificValue OBJECT-TYPE
   SYNTAX      Integer32
   MAX-ACCESS  read-only
   STATUS      current
   DESCRIPTION
       "The last received value in the OS TLV Value field."
   ::= { sispm1040582lrtTLVConfStateEntry 7 }  

sispm1040582lrtTLVConfStateCCOrganizationSpecificLastRX OBJECT-TYPE
   SYNTAX      DisplayString
   MAX-ACCESS  read-only
   STATUS      current
   DESCRIPTION
       "OS TLV was received in the last received CCM PDU."
   ::= { sispm1040582lrtTLVConfStateEntry 8 }  

sispm1040582lrtTLVConfStateCCPortStatusValue OBJECT-TYPE
   SYNTAX      Integer32
   MAX-ACCESS  read-only
   STATUS      current
   DESCRIPTION
       "The last received value in the PS TLV Value field."
   ::= { sispm1040582lrtTLVConfStateEntry 9 }

sispm1040582lrtTLVConfStateCCPortStatusLastRX OBJECT-TYPE
   SYNTAX      DisplayString
   MAX-ACCESS  read-only
   STATUS      current
   DESCRIPTION
       "PS TLV was received in the last received CCM PDU."
   ::= { sispm1040582lrtTLVConfStateEntry 10 }  
   
sispm1040582lrtTLVConfStateCCInterfaceStatusValue OBJECT-TYPE
   SYNTAX      Integer32
   MAX-ACCESS  read-only
   STATUS      current
   DESCRIPTION
       "The last received value in the IS TLV Value field."
   ::= { sispm1040582lrtTLVConfStateEntry 11 }   
   
sispm1040582lrtTLVConfStateCCInterfaceStatusLastRX OBJECT-TYPE
   SYNTAX      DisplayString
   MAX-ACCESS  read-only
   STATUS      current
   DESCRIPTION
       "IS TLV was received in the last received CCM PDU."
   ::= { sispm1040582lrtTLVConfStateEntry 12 } 

sispm1040582lrtLinkStateTracking OBJECT-TYPE
   SYNTAX      Integer32
   MAX-ACCESS  read-write
   STATUS      current
   DESCRIPTION
       "0:disable
	   1:enable"
   ::= { sispm1040582lrtMEP 8 } 

   
sispm1040582lrtFaultManagement    OBJECT IDENTIFIER ::= { sispm1040582lrtMEP 9 }   

sispm1040582lrtFaultMgmtLoopBackConfEnable OBJECT-TYPE
   SYNTAX      Integer32
   MAX-ACCESS  read-write
   STATUS      current
   DESCRIPTION
       "0:disable
	   1:enable"
   ::= { sispm1040582lrtFaultManagement 2 } 

sispm1040582lrtFaultMgmtLoopBackConfDEI OBJECT-TYPE
   SYNTAX      Integer32
   MAX-ACCESS  read-write
   STATUS      current
   DESCRIPTION
       "0:disable
	   1:enable"
   ::= { sispm1040582lrtFaultManagement 3 } 
   
sispm1040582lrtFaultMgmtLoopBackConfPriority OBJECT-TYPE
   SYNTAX      Integer32
   MAX-ACCESS  read-write
   STATUS      current
   DESCRIPTION
       "range:0-7"
   ::= { sispm1040582lrtFaultManagement 4 } 
 
sispm1040582lrtFaultMgmtLoopBackConfCast OBJECT-TYPE
   SYNTAX      Integer32
   MAX-ACCESS  read-write
   STATUS      current
   DESCRIPTION
       "0:Unicast destination address
	   1:Multicast destination address"
   ::= { sispm1040582lrtFaultManagement 5 }  
 
sispm1040582lrtFaultMgmtLoopBackConfPeerMEP OBJECT-TYPE
   SYNTAX      Integer32
   MAX-ACCESS  read-write
   STATUS      current
   DESCRIPTION
       "This is only used if the 'Unicast MAC' is configured to all zero. 
	   The LBM unicast MAC will be taken from the 'Unicast Peer MAC' configuration of this peer."
   ::= { sispm1040582lrtFaultManagement 6 }  
 
sispm1040582lrtFaultMgmtLoopBackConfUnicastMAC OBJECT-TYPE
   SYNTAX      DisplayString
   MAX-ACCESS  read-write
   STATUS      current
   DESCRIPTION
       "This is only used if NOT configured to all zero. 
	   This will be used as the LBM PDU unicast MAC. 
	   This is the only way to configure Loop Back to-wards a MIP. "
   ::= { sispm1040582lrtFaultManagement 7 }  
   
sispm1040582lrtFaultMgmtLoopBackConfToSend OBJECT-TYPE
   SYNTAX      Integer32
   MAX-ACCESS  read-write
   STATUS      current
   DESCRIPTION
       "The number of LBM PDU to send in one loop test. 
	   The value 0 indicate infinite transmission (test behaviour). 
	   This is HW based LBM/LBR and Requires VOE."
   ::= { sispm1040582lrtFaultManagement 8 } 
   
sispm1040582lrtFaultMgmtLoopBackConfSize OBJECT-TYPE
   SYNTAX      Integer32
   MAX-ACCESS  read-write
   STATUS      current
   DESCRIPTION
       "The LBM frame size."
   ::= { sispm1040582lrtFaultManagement 9 } 
   
sispm1040582lrtFaultMgmtLoopBackConfInterval OBJECT-TYPE
   SYNTAX      Integer32
   MAX-ACCESS  read-write
   STATUS      current
   DESCRIPTION
       "The interval between transmitting LBM PDU."
   ::= { sispm1040582lrtFaultManagement 10 } 
   
   
sispm1040582lrtFaultManagementState    OBJECT IDENTIFIER ::= { sispm1040582lrtMEP 10 }  
   
   
sispm1040582lrtFaultMgmtStateTransactionID OBJECT-TYPE
   SYNTAX      Integer32
   MAX-ACCESS  read-only
   STATUS      current
   DESCRIPTION
       "The transaction id of the first LBM transmitted. 
	   For each LBM transmitted the transaction id in the PDU is incremented."
   ::= { sispm1040582lrtFaultManagementState 1 } 
   

sispm1040582lrtFaultMgmtStateTransmitted OBJECT-TYPE
   SYNTAX      Integer32
   MAX-ACCESS  read-only
   STATUS      current
   DESCRIPTION
       "The total number of LBM PDU transmitted."
   ::= { sispm1040582lrtFaultManagementState 2 } 
   
   
sispm1040582lrtFaultMgmtStateTable OBJECT-TYPE
   SYNTAX      SEQUENCE OF SISPM1040582LRTFaultMgmtStateEntry
   MAX-ACCESS  not-accessible
   STATUS      current
   DESCRIPTION
       " "
   ::= { sispm1040582lrtFaultManagementState 3 }

sispm1040582lrtFaultMgmtStateEntry OBJECT-TYPE
   SYNTAX      SISPM1040582LRTFaultMgmtStateEntry
   MAX-ACCESS  not-accessible
   STATUS      current
   DESCRIPTION
       " "
   INDEX    { sispm1040582lrtFaultMgmtStateIndex  }
   ::= { sispm1040582lrtFaultMgmtStateTable 1 }

SISPM1040582LRTFaultMgmtStateEntry ::= SEQUENCE {
   sispm1040582lrtFaultMgmtStateIndex               Integer32,
   sispm1040582lrtFaultMgmtStateReplyMAC            DisplayString,
   sispm1040582lrtFaultMgmtStateReceived            Integer32,
   sispm1040582lrtFaultMgmtStateOutOfOrder          Integer32
}

sispm1040582lrtFaultMgmtStateIndex OBJECT-TYPE
   SYNTAX      Integer32
   MAX-ACCESS  not-accessible
   STATUS      current
   DESCRIPTION
       "Index"
   ::= { sispm1040582lrtFaultMgmtStateEntry 1 }

sispm1040582lrtFaultMgmtStateReplyMAC OBJECT-TYPE
   SYNTAX      DisplayString
   MAX-ACCESS  read-only
   STATUS      current
   DESCRIPTION
       "The MAC of the replying MEP/MIP. 
	   In case of multi-cast LBM, replies can be received from all peer MEP in the group. 
	   This MAC is not shown in case of 'To Send' == 0."
   ::= { sispm1040582lrtFaultMgmtStateEntry 2 }

sispm1040582lrtFaultMgmtStateReceived OBJECT-TYPE
   SYNTAX      Integer32
   MAX-ACCESS  read-only
   STATUS      current
   DESCRIPTION
       "The total number of LBR PDU received from this 'Reply MAC'."
   ::= { sispm1040582lrtFaultMgmtStateEntry 3 }   
   
sispm1040582lrtFaultMgmtStateOutOfOrder OBJECT-TYPE
   SYNTAX      Integer32
   MAX-ACCESS  read-only
   STATUS      current
   DESCRIPTION
       "The number of LBR PDU received from this 'Reply MAC' with incorrect 'Transaction ID'."
   ::= { sispm1040582lrtFaultMgmtStateEntry 4 }  
   
sispm1040582lrtFaultMgmtTestSignal    OBJECT IDENTIFIER ::= { sispm1040582lrtMEP 11 }  

sispm1040582lrtFaultMgmtTestSignalTx OBJECT-TYPE
   SYNTAX      Integer32
   MAX-ACCESS  read-write
   STATUS      current
   DESCRIPTION
       "Test Signal based on transmitting TST PDU can be enabled/disabled.
	   0:disable
	   1:enable"
   ::= { sispm1040582lrtFaultMgmtTestSignal 2 }  
   
sispm1040582lrtFaultMgmtTestSignalRx OBJECT-TYPE
   SYNTAX      Integer32
   MAX-ACCESS  read-write
   STATUS      current
   DESCRIPTION
       "Test Signal based on transmitting TST PDU can be enabled/disabled.
	   0:disable
	   1:enable"
   ::= { sispm1040582lrtFaultMgmtTestSignal 3 }  
   
sispm1040582lrtFaultMgmtTestSignalDEI OBJECT-TYPE
   SYNTAX      Integer32
   MAX-ACCESS  read-write
   STATUS      current
   DESCRIPTION
       "The DEI to be inserted as PCP bits in TAG (if any).
	   0:disable
	   1:enable"
   ::= { sispm1040582lrtFaultMgmtTestSignal 4 }  

sispm1040582lrtFaultMgmtTestSignalPriority OBJECT-TYPE
   SYNTAX      Integer32
   MAX-ACCESS  read-write
   STATUS      current
   DESCRIPTION
       "The priority to be inserted as PCP bits in TAG (if any).
       Range:0-7"
   ::= { sispm1040582lrtFaultMgmtTestSignal 5 }    
   
sispm1040582lrtFaultMgmtTestSignalPeerMEP OBJECT-TYPE
   SYNTAX      Integer32
   MAX-ACCESS  read-write
   STATUS      current
   DESCRIPTION
       "The TST frame destination MAC will be taken from the 'Unicast Peer MAC' configuration of this peer."
   ::= { sispm1040582lrtFaultMgmtTestSignal 6 }    
   
sispm1040582lrtFaultMgmtTestSignalRate OBJECT-TYPE
   SYNTAX      Integer32
   MAX-ACCESS  read-write
   STATUS      current
   DESCRIPTION
       "The TST frame transmission bit rate - in Mega bits pr. second. 
	   Limit is 400 Mbps. This is the bit rate of a standard frame without any encapsulation. 
	   If 1 Mbps rate is selected in a EVC MEP, the added tag will give a higher bitrate on the wire."
   ::= { sispm1040582lrtFaultMgmtTestSignal 7 }  
   
sispm1040582lrtFaultMgmtTestSignalSize OBJECT-TYPE
   SYNTAX      Integer32
   MAX-ACCESS  read-write
   STATUS      current
   DESCRIPTION
       "The TST frame size. This is entered as the wanted size (in bytes) of a un-tagged frame containing TST OAM PDU - including CRC (four bytes)."
   ::= { sispm1040582lrtFaultMgmtTestSignal 8 }  
   
sispm1040582lrtFaultMgmtTestSignalPattern OBJECT-TYPE
   SYNTAX      Integer32
   MAX-ACCESS  read-write
   STATUS      current
   DESCRIPTION
       "The 'empty' TST PDU has the size of 12 bytes. 
	   In order to achieve the configured frame size a data TLV will be added with a pattern.
	   0:All Zero
	   1:All One
	   2:10101010"
   ::= { sispm1040582lrtFaultMgmtTestSignal 9 }  
   
sispm1040582lrtFaultMgmtTestSignalSequenceNumber OBJECT-TYPE
   SYNTAX      Integer32
   MAX-ACCESS  read-write
   STATUS      current
   DESCRIPTION
       "0:disable
	   1:enable"
   ::= { sispm1040582lrtFaultMgmtTestSignal 10 }  
   
sispm1040582lrtFaultMgmtTestSignalState    OBJECT IDENTIFIER ::= { sispm1040582lrtMEP 12 }  
   
sispm1040582lrtFaultMgmtTestSignalStateTXFrameCount OBJECT-TYPE
   SYNTAX      Integer32
   MAX-ACCESS  read-only
   STATUS      current
   DESCRIPTION
       "The number of transmitted TST frames since last 'Clear'."
   ::= { sispm1040582lrtFaultMgmtTestSignalState 2 }  
   
sispm1040582lrtFaultMgmtTestSignalStateRXFrameCount OBJECT-TYPE
   SYNTAX      Integer32
   MAX-ACCESS  read-only
   STATUS      current
   DESCRIPTION
       "The number of received TST frames since last 'Clear'."
   ::= { sispm1040582lrtFaultMgmtTestSignalState 3 }  
   
sispm1040582lrtFaultMgmtTestSignalStateRXRate OBJECT-TYPE
   SYNTAX      Integer32
   MAX-ACCESS  read-only
   STATUS      current
   DESCRIPTION
       "The current received TST frame bit rate in Kbps. 
	   This is calculated on a 1 s. basis, starting when first TST frame is received after 'Clear'. 
	   The frame size used for this calculation is the first received after 'Clear'"
   ::= { sispm1040582lrtFaultMgmtTestSignalState 4 }  
   
sispm1040582lrtFaultMgmtTestSignalStateTestTime OBJECT-TYPE
   SYNTAX      Integer32
   MAX-ACCESS  read-only
   STATUS      current
   DESCRIPTION
       "The number of seconds passed since first TST frame received after last 'Clear'."
   ::= { sispm1040582lrtFaultMgmtTestSignalState 5 }  
   
   
sispm1040582lrtFaultMgmtTestSignalStateClear OBJECT-TYPE
   SYNTAX      Integer32
   MAX-ACCESS  read-write
   STATUS      current
   DESCRIPTION
       "This will clear all Test Signal State. 
	   Transmission of TST frame will be restarted. 
	   Calculation of 'Rx frame count', 'RX rate' and 'Test time' will be started when receiving first TST frame."
   ::= { sispm1040582lrtFaultMgmtTestSignalState 6 }     
   
   
sispm1040582lrtFaultMgmtClientConfigFlow    OBJECT IDENTIFIER ::= { sispm1040582lrtMEP 13 }  

sispm1040582lrtFaultMgmtClientConfigFlowTable OBJECT-TYPE
   SYNTAX      SEQUENCE OF SISPM1040582LRTFaultMgmtClientConfigFlowEntry
   MAX-ACCESS  not-accessible
   STATUS      current
   DESCRIPTION
       " "
   ::= { sispm1040582lrtFaultMgmtClientConfigFlow 1 }

sispm1040582lrtFaultMgmtClientConfigFlowEntry OBJECT-TYPE
   SYNTAX      SISPM1040582LRTFaultMgmtClientConfigFlowEntry
   MAX-ACCESS  not-accessible
   STATUS      current
   DESCRIPTION
       " "
   INDEX    { sispm1040582lrtFaultMgmtClientConfigFlowIndex  }
   ::= { sispm1040582lrtFaultMgmtClientConfigFlowTable 1 }

SISPM1040582LRTFaultMgmtClientConfigFlowEntry ::= SEQUENCE {
   sispm1040582lrtFaultMgmtClientConfigFlowIndex     Integer32,
   sispm1040582lrtFaultMgmtClientConfigFlowDomain    Integer32,
   sispm1040582lrtFaultMgmtClientConfigFlowInstance  Integer32,
   sispm1040582lrtFaultMgmtClientConfigFlowLevel     Integer32,
   sispm1040582lrtFaultMgmtClientConfigFlowAISprio   Integer32,
   sispm1040582lrtFaultMgmtClientConfigFlowLCKprio   Integer32,
   sispm1040582lrtFaultMgmtClientConfigFlowRowStatus RowStatus
}

sispm1040582lrtFaultMgmtClientConfigFlowIndex OBJECT-TYPE
   SYNTAX      Integer32
   MAX-ACCESS  not-accessible
   STATUS      current
   DESCRIPTION
       "Index"
   ::= { sispm1040582lrtFaultMgmtClientConfigFlowEntry 1 }

sispm1040582lrtFaultMgmtClientConfigFlowDomain OBJECT-TYPE
   SYNTAX      Integer32
   MAX-ACCESS  read-create
   STATUS      current
   DESCRIPTION
       "The domain of the client layer flow.
	   Ranfew:0-6
	   0:Port
	   1:EVC
	   2:VLAN
	   3:MPLS_LINK
	   4:MPLS_TUNNEL
	   5:MPLS_PW
	   6:MPLS_LSP"
   ::= { sispm1040582lrtFaultMgmtClientConfigFlowEntry 2 }  

sispm1040582lrtFaultMgmtClientConfigFlowInstance OBJECT-TYPE
   SYNTAX      Integer32
   MAX-ACCESS  read-create
   STATUS      current
   DESCRIPTION
       "Client layer flow instance numbers."
   ::= { sispm1040582lrtFaultMgmtClientConfigFlowEntry 3 }  
   
sispm1040582lrtFaultMgmtClientConfigFlowLevel OBJECT-TYPE
   SYNTAX      Integer32
   MAX-ACCESS  read-create
   STATUS      current
   DESCRIPTION
       "Client layer level - AIS and LCK PDU transmitted in this client layer flow will be on this level."
   ::= { sispm1040582lrtFaultMgmtClientConfigFlowEntry 4 }  
   
sispm1040582lrtFaultMgmtClientConfigFlowAISprio OBJECT-TYPE
   SYNTAX      Integer32
   MAX-ACCESS  read-create
   STATUS      current
   DESCRIPTION
       "The priority to be used when transmitting AIS in each client flow. 
	   Priority resulting in highest possible PCP can be selected.
	   Range:0-7. 255 indicate highest possible is requested"
   ::= { sispm1040582lrtFaultMgmtClientConfigFlowEntry 5 }  
   
sispm1040582lrtFaultMgmtClientConfigFlowLCKprio OBJECT-TYPE
   SYNTAX      Integer32
   MAX-ACCESS  read-create
   STATUS      current
   DESCRIPTION
       "The priority to be used when transmitting LCK in each client flow. 
	   Priority resulting in highest possible PCP can be selected.
	   Range:0-7. 255 indicate highest possible is requested"
   ::= { sispm1040582lrtFaultMgmtClientConfigFlowEntry 6 }  
   
sispm1040582lrtFaultMgmtClientConfigFlowRowStatus OBJECT-TYPE
   SYNTAX      RowStatus
   MAX-ACCESS  read-create
   STATUS      current
   DESCRIPTION
       "FaultMgmtClientConfigFlow Row Status."
   ::= {sispm1040582lrtFaultMgmtClientConfigFlowEntry 7 }
   
   
sispm1040582lrtFaultMgmtAISLOCK    OBJECT IDENTIFIER ::= { sispm1040582lrtMEP 14 }  
   
sispm1040582lrtFaultMgmtAISEnable OBJECT-TYPE
   SYNTAX      Integer32
   MAX-ACCESS  read-write
   STATUS      current
   DESCRIPTION
       "Insertion of AIS signal (AIS PDU transmission) in client layer flows, can be enable/disabled.
	   0:disable
	   1:enable"
   ::= { sispm1040582lrtFaultMgmtAISLOCK 2 }  
   
sispm1040582lrtFaultMgmtAISFrameRate OBJECT-TYPE
   SYNTAX      Integer32
   MAX-ACCESS  read-write
   STATUS      current
   DESCRIPTION
       "Selecting the frame rate of AIS PDU. 
	   This is the inverse of transmission period as described in Y.1731.
       1: 300 frames per second
	   2: 100 frames per second
	   3: 10 frames per second
	   4: 1 frames per second
	   5: 6 frames per minute
	   6: 1 frames per minute
	   7: 6 frames per hour"
   ::= { sispm1040582lrtFaultMgmtAISLOCK 3 }  
   
sispm1040582lrtFaultMgmtAISProtection OBJECT-TYPE
   SYNTAX      Integer32
   MAX-ACCESS  read-write
   STATUS      current
   DESCRIPTION
       "Selecting this means that the first 3 AIS PDU is transmitted as fast as possible - in case of using this for protection in the end point.
	   0:disable
	   1:enable"
   ::= { sispm1040582lrtFaultMgmtAISLOCK 4 }     
   
   
sispm1040582lrtFaultMgmtLOCKEnable OBJECT-TYPE
   SYNTAX      Integer32
   MAX-ACCESS  read-write
   STATUS      current
   DESCRIPTION
       "Insertion of LOCK signal (LCK PDU transmission) in client layer flows, can be enable/disabled.
	   0:disable
	   1:enable"
   ::= { sispm1040582lrtFaultMgmtAISLOCK 5 }   
   
sispm1040582lrtFaultMgmtLOCKFrameRate OBJECT-TYPE
   SYNTAX      Integer32
   MAX-ACCESS  read-write
   STATUS      current
   DESCRIPTION
       "Selecting the frame rate of LCK PDU. This is the inverse of transmission period as described in Y.1731.
       1: 300 frames per second
	   2: 100 frames per second
	   3: 10 frames per second
	   4: 1 frames per second
	   5: 6 frames per minute
	   6: 1 frames per minute
	   7: 6 frames per hour"
   ::= { sispm1040582lrtFaultMgmtAISLOCK 6 }  

sispm1040582lrtPerformanceMonitor  OBJECT IDENTIFIER ::= { sispm1040582lrtMEP 15 }  

sispm1040582lrtPerformanceMonitorDataSetEnable OBJECT-TYPE
   SYNTAX      Integer32
   MAX-ACCESS  read-write
   STATUS      current
   DESCRIPTION
       "
	   When enabled this MEP instance will contribute to the 'PM Data Set' gathered by the PM Session.
	   0:disable
	   1:enable"
   ::= { sispm1040582lrtPerformanceMonitor 2 }   
   
sispm1040582lrtPerformanceMonitorLossMeasurementEnable OBJECT-TYPE
   SYNTAX      Integer32
   MAX-ACCESS  read-write
   STATUS      current
   DESCRIPTION
       "
	   Loss Measurement based on transmitting/receiving CCM or LMM/LMR PDU can be enabled/disabled - see 'Ended'. 
	   This is only valid with one Peer MEP configured.
	   0:disable
	   1:enable"
   ::= { sispm1040582lrtPerformanceMonitor 3 }     
   
sispm1040582lrtPerformanceMonitorLossMeasurementPriority OBJECT-TYPE
   SYNTAX      Integer32
   MAX-ACCESS  read-write
   STATUS      current
   DESCRIPTION
       "
	   The priority to be inserted as PCP bits in TAG (if any). 
	   In case of enable of Continuity Check and Loss Measurement both implemented on SW based CCM, 'Priority' has to be the same.
	   range:0-7"
   ::= { sispm1040582lrtPerformanceMonitor 4 } 
   
sispm1040582lrtPerformanceMonitorLossMeasurementFrameRate OBJECT-TYPE
   SYNTAX      Integer32
   MAX-ACCESS  read-write
   STATUS      current
   DESCRIPTION
       "
	   1: 300 frames per second
	   2: 100 frames per second
	   3: 10 frames per second
	   4: 1 frames per second
	   5: 6 frames per minute
	   6: 1 frames per minute
	   7: 6 frames per hour"
   ::= { sispm1040582lrtPerformanceMonitor 5 }   
   
sispm1040582lrtPerformanceMonitorLossMeasurementCast OBJECT-TYPE
   SYNTAX      Integer32
   MAX-ACCESS  read-write
   STATUS      current
   DESCRIPTION
       "
	   0: Unicast destination address
	   1: Multicast destination address 
	   "
   ::= { sispm1040582lrtPerformanceMonitor 6 }  
   
sispm1040582lrtPerformanceMonitorLossMeasurementEnded OBJECT-TYPE
   SYNTAX      Integer32
   MAX-ACCESS  read-write
   STATUS      current
   DESCRIPTION
       "
	   0: Single ended LM based on LMM/LMR or DM based on DMM/DMR 
	   1: Dual ended LM based on CCM or DM based on 1DM
	   "
   ::= { sispm1040582lrtPerformanceMonitor 7 }  
   
sispm1040582lrtPerformanceMonitorLossMeasurementFLRInterval OBJECT-TYPE
   SYNTAX      Integer32
   MAX-ACCESS  read-write
   STATUS      current
   DESCRIPTION
       "
       This is the interval in seconds where the Frame Loss Ratio is calculated.
	   "
   ::= { sispm1040582lrtPerformanceMonitor 8 }  
   
sispm1040582lrtPerformanceMonitorLossMeasurementLossThreshold OBJECT-TYPE
   SYNTAX      Integer32
   MAX-ACCESS  read-write
   STATUS      current
   DESCRIPTION
       "
       Far end loss threshold count is incremented if a loss measurement is above this threshold.
	   "
   ::= { sispm1040582lrtPerformanceMonitor 9 }   
    
sispm1040582lrtPerformanceMonitorLossMeasurementStateTx OBJECT-TYPE
   SYNTAX      Integer32
   MAX-ACCESS  read-only
   STATUS      current
   DESCRIPTION
       "
	   "
   ::= { sispm1040582lrtPerformanceMonitor 10 }     
    
sispm1040582lrtPerformanceMonitorLossMeasurementStateRx OBJECT-TYPE
   SYNTAX      Integer32
   MAX-ACCESS  read-only
   STATUS      current
   DESCRIPTION
       "
	   "
   ::= { sispm1040582lrtPerformanceMonitor 11 }
   
sispm1040582lrtPerformanceMonitorLossMeasurementStateNearEndLossCount OBJECT-TYPE
   SYNTAX      Integer32
   MAX-ACCESS  read-only
   STATUS      current
   DESCRIPTION
       "The accumulated near end frame loss count - since last 'clear'.
	   "
   ::= { sispm1040582lrtPerformanceMonitor 12 }
   
sispm1040582lrtPerformanceMonitorLossMeasurementStateFarEndLossCount OBJECT-TYPE
   SYNTAX      Integer32
   MAX-ACCESS  read-only
   STATUS      current
   DESCRIPTION
       "The accumulated far end frame loss count - since last 'clear'.
	   "
   ::= { sispm1040582lrtPerformanceMonitor 13 }
   
sispm1040582lrtPerformanceMonitorLossMeasurementStateNearEndLossRatio OBJECT-TYPE
   SYNTAX      Integer32
   MAX-ACCESS  read-only
   STATUS      current
   DESCRIPTION
       "The near end frame loss ratio calculated based on the near end frame loss count and far end frame transmitted - in the latest 'FLR Interval'. 
	   The result is given in percent.
	   "
   ::= { sispm1040582lrtPerformanceMonitor 14 }
   
sispm1040582lrtPerformanceMonitorLossMeasurementStateFarEndLossRatio OBJECT-TYPE
   SYNTAX      Integer32
   MAX-ACCESS  read-only
   STATUS      current
   DESCRIPTION
       "The far end frame loss ratio calculated based on the far end frame loss count and near end frame transmitted - in the latest 'FLR Interval'. 
	   The result is given in percent.
	   "
   ::= { sispm1040582lrtPerformanceMonitor 15 }
   
sispm1040582lrtPerformanceMonitorLossMeasurementStateClear OBJECT-TYPE
   SYNTAX      Integer32
   MAX-ACCESS  read-write
   STATUS      current
   DESCRIPTION
       "Set of this check and save will clear the accumulated counters and restart ratio calculation.
	   "
   ::= { sispm1040582lrtPerformanceMonitor 16 }
   
sispm1040582lrtPerformanceMonitorLossMeasurementAvailabilityEnable OBJECT-TYPE
   SYNTAX      Integer32
   MAX-ACCESS  read-write
   STATUS      current
   DESCRIPTION
       "Enable/disable of loss measurement availability.
	   0:disable
	   1:enable	   
	   "
   ::= { sispm1040582lrtPerformanceMonitor 17 }
   
sispm1040582lrtPerformanceMonitorLossMeasurementAvailabilityInterval OBJECT-TYPE
   SYNTAX      Integer32
   MAX-ACCESS  read-write
   STATUS      current
   DESCRIPTION
       "Availability interval - number of measurements with same availability in order to change availability state.
	   
	   "
   ::= { sispm1040582lrtPerformanceMonitor 18 }
   
sispm1040582lrtPerformanceMonitorLossMeasurementAvailabilityFLRThreshold OBJECT-TYPE
   SYNTAX      Integer32
   MAX-ACCESS  read-write
   STATUS      current
   DESCRIPTION
       "Availability frame loss ratio threshold in per mille.
	   "
   ::= { sispm1040582lrtPerformanceMonitor 19 }
   
sispm1040582lrtPerformanceMonitorLossMeasurementAvailabilityMaintenance OBJECT-TYPE
   SYNTAX      Integer32
   MAX-ACCESS  read-write
   STATUS      current
   DESCRIPTION
       "Enable/disable of loss measurement availability maintenance.
	   "
   ::= { sispm1040582lrtPerformanceMonitor 20 }  
   
   
sispm1040582lrtPerformanceMonitorLossMeasurementAvailabilityStateNearAvailabilityCount OBJECT-TYPE
   SYNTAX      Integer32
   MAX-ACCESS  read-only
   STATUS      current
   DESCRIPTION
       "Near end availability count.
	   "
   ::= { sispm1040582lrtPerformanceMonitor 21 }     
   
sispm1040582lrtPerformanceMonitorLossMeasurementAvailabilityStateFarAvailabilityCount OBJECT-TYPE
   SYNTAX      Integer32
   MAX-ACCESS  read-only
   STATUS      current
   DESCRIPTION
       "Far end availability count.
	   "
   ::= { sispm1040582lrtPerformanceMonitor 22 }  
   
sispm1040582lrtPerformanceMonitorLossMeasurementAvailabilityStateNearUnavailabilityCount OBJECT-TYPE
   SYNTAX      Integer32
   MAX-ACCESS  read-only
   STATUS      current
   DESCRIPTION
       "Near end unavailability count.
	   "
   ::= { sispm1040582lrtPerformanceMonitor 23 }  
   
sispm1040582lrtPerformanceMonitorLossMeasurementAvailabilityStateFarUnavailabilityCount OBJECT-TYPE
   SYNTAX      Integer32
   MAX-ACCESS  read-only
   STATUS      current
   DESCRIPTION
       "Far end unavailability count.
	   "
   ::= { sispm1040582lrtPerformanceMonitor 24 }  
   
sispm1040582lrtPerformanceMonitorLossMeasurementAvailabilityStateNearState OBJECT-TYPE
   SYNTAX      Integer32
   MAX-ACCESS  read-only
   STATUS      current
   DESCRIPTION
       "Near end availability state.
	   "
   ::= { sispm1040582lrtPerformanceMonitor 25 }  
   
sispm1040582lrtPerformanceMonitorLossMeasurementAvailabilityStateFarState OBJECT-TYPE
   SYNTAX      Integer32
   MAX-ACCESS  read-only
   STATUS      current
   DESCRIPTION
       "Far end availability state.
	   "
   ::= { sispm1040582lrtPerformanceMonitor 26 }  
   
sispm1040582lrtPerformanceMonitorLossMeasurementHighLossIntervalEnable OBJECT-TYPE
   SYNTAX      Integer32
   MAX-ACCESS  read-write
   STATUS      current
   DESCRIPTION
       "Enable/disable of loss measurement high loss interval.
	   0:disable
	   1:enable	 
	   "
   ::= { sispm1040582lrtPerformanceMonitor 27 }  
   
sispm1040582lrtPerformanceMonitorLossMeasurementHighLossIntervalFLRThreshold OBJECT-TYPE
   SYNTAX      Integer32
   MAX-ACCESS  read-write
   STATUS      current
   DESCRIPTION
       "High Loss Interval frame loss ratio threshold in per mille.
	   "
   ::= { sispm1040582lrtPerformanceMonitor 28 }  
   
sispm1040582lrtPerformanceMonitorLossMeasurementHighLossIntervalConsecutiveInterval OBJECT-TYPE
   SYNTAX      Integer32
   MAX-ACCESS  read-write
   STATUS      current
   DESCRIPTION
       "High Loss Interval consecutive interval (number of measurements).
	   "
   ::= { sispm1040582lrtPerformanceMonitor 29 }   
   
sispm1040582lrtPerformanceMonitorLossMeasurementHighLossIntervalStateNearCount OBJECT-TYPE
   SYNTAX      Integer32
   MAX-ACCESS  read-only
   STATUS      current
   DESCRIPTION
       "Near end high loss interval count (number of measurements where availability state is available and FLR is above high loss interval FLR threshold.
	   "
   ::= { sispm1040582lrtPerformanceMonitor 30 }   
   
sispm1040582lrtPerformanceMonitorLossMeasurementHighLossIntervalStateFarCount OBJECT-TYPE
   SYNTAX      Integer32
   MAX-ACCESS  read-only
   STATUS      current
   DESCRIPTION
       "Far end high loss interval count (number of measurements where availability state is available and FLR is above high loss interval FLR threshold.
	   "
   ::= { sispm1040582lrtPerformanceMonitor 31 }  
   
sispm1040582lrtPerformanceMonitorLossMeasurementHighLossIntervalStateNearConsecutiveCount OBJECT-TYPE
   SYNTAX      Integer32
   MAX-ACCESS  read-only
   STATUS      current
   DESCRIPTION
       "Near end high loss interval consecutive count.
	   "
   ::= { sispm1040582lrtPerformanceMonitor 32 }  
   
sispm1040582lrtPerformanceMonitorLossMeasurementHighLossIntervalStateFarConsecutiveCount OBJECT-TYPE
   SYNTAX      Integer32
   MAX-ACCESS  read-only
   STATUS      current
   DESCRIPTION
       "Far end high loss interval consecutive count.
	   "
   ::= { sispm1040582lrtPerformanceMonitor 33 } 
   
sispm1040582lrtPerformanceMonitorLossMeasurementSignalDegradeEnable OBJECT-TYPE
   SYNTAX      Integer32
   MAX-ACCESS  read-write
   STATUS      current
   DESCRIPTION
       "Enable/disable of loss measurement signal degrade.
	   0:disable
	   1:enable	 	   
	   "
   ::= { sispm1040582lrtPerformanceMonitor 34 } 
   
sispm1040582lrtPerformanceMonitorLossMeasurementSignalDegradeTXMinimum OBJECT-TYPE
   SYNTAX      Integer32
   MAX-ACCESS  read-write
   STATUS      current
   DESCRIPTION
       "Minimum number of frames that must be transmitted in a measurement before frame loss ratio is tested against loss ratio threshold.
 	   
	   "
   ::= { sispm1040582lrtPerformanceMonitor 35 } 
   
sispm1040582lrtPerformanceMonitorLossMeasurementSignalDegradeFLRThreshold OBJECT-TYPE
   SYNTAX      Integer32
   MAX-ACCESS  read-write
   STATUS      current
   DESCRIPTION
       "Signal Degraded frame loss ratio threshold in per mille.
	   "
   ::= { sispm1040582lrtPerformanceMonitor 36 } 
   
sispm1040582lrtPerformanceMonitorLossMeasurementSignalDegradeBadThreshold OBJECT-TYPE
   SYNTAX      Integer32
   MAX-ACCESS  read-write
   STATUS      current
   DESCRIPTION
       "Number of consecutive bad interval measurements required to set degrade state.
	   "
   ::= { sispm1040582lrtPerformanceMonitor 37 }    
   
sispm1040582lrtPerformanceMonitorLossMeasurementSignalDegradeGoodThreshold OBJECT-TYPE
   SYNTAX      Integer32
   MAX-ACCESS  read-write
   STATUS      current
   DESCRIPTION
       "Number of consecutive good interval measurements required to clear degrade state.
	   "
   ::= { sispm1040582lrtPerformanceMonitor 38 } 
   
sispm1040582lrtPerformanceMonitorDelayMeasurementEnable OBJECT-TYPE
   SYNTAX      Integer32
   MAX-ACCESS  read-write
   STATUS      current
   DESCRIPTION
       "Delay Measurement based on transmitting 1DM/DMM PDU can be enabled/disabled. 
	   Delay Measurement based on receiving and handling 1DM/DMR PDU is always enabled.
	   0:disable
	   1:enable		   
	   "
   ::= { sispm1040582lrtPerformanceMonitor 39 } 
   
sispm1040582lrtPerformanceMonitorDelayMeasurementPriority OBJECT-TYPE
   SYNTAX      Integer32
   MAX-ACCESS  read-write
   STATUS      current
   DESCRIPTION
       "The priority to be inserted as PCP bits in TAG (if any).
       Range:0-7	   
	   "
   ::= { sispm1040582lrtPerformanceMonitor 40 }  
   
sispm1040582lrtPerformanceMonitorDelayMeasurementCast OBJECT-TYPE
   SYNTAX      Integer32
   MAX-ACCESS  read-write
   STATUS      current
   DESCRIPTION
       "Selection of 1DM/DMM PDU transmitted unicast or multicast. 
	   The unicast MAC will be configured through 'Peer MEP'.   
	   0: Unicast destination address
	   1: Multicast destination address 	   
	   "
   ::= { sispm1040582lrtPerformanceMonitor 41 } 
   
sispm1040582lrtPerformanceMonitorDelayMeasurementPeerMEP OBJECT-TYPE
   SYNTAX      Integer32
   MAX-ACCESS  read-write
   STATUS      current
   DESCRIPTION
       "This is only used if the 'Cast' is configured to Uni. 
	   The 1DM/DMR unicast MAC will be taken from the 'Unicast Peer MAC' configuration of this peer. 
	   "
   ::= { sispm1040582lrtPerformanceMonitor 42 } 
   
sispm1040582lrtPerformanceMonitorDelayMeasurementEnded OBJECT-TYPE
   SYNTAX      Integer32
   MAX-ACCESS  read-write
   STATUS      current
   DESCRIPTION
       "0:One-Way: One-Way Delay Measurement implemented on 1DM.
        1:Two-Way: Two-Way Delay Measurement implemented on DMM/DMR.
	   "
   ::= { sispm1040582lrtPerformanceMonitor 43 } 
   
sispm1040582lrtPerformanceMonitorDelayMeasurementTxMode OBJECT-TYPE
   SYNTAX      Integer32
   MAX-ACCESS  read-write
   STATUS      current
   DESCRIPTION
       "0:Standardize: Y.1731 standardize way to transmit 1DM/DMR.
        1:Proprietary: Vitesse proprietary way with follow-up packets to transmit 1DM/DMR.
	   "
   ::= { sispm1040582lrtPerformanceMonitor 44 } 
   
sispm1040582lrtPerformanceMonitorDelayMeasurementCalc OBJECT-TYPE
   SYNTAX      Integer32
   MAX-ACCESS  read-write
   STATUS      current
   DESCRIPTION
       "This is only used if the 'Way' is configured to Two-way.
        0:Round trip: The frame delay calculated by the transmitting and receiving timestamps of initiators. 
		    Frame Delay = RxTimeb-TxTimeStampf
        1:Flow: The frame delay calculated by the transmitting and receiving timestamps of initiators and remotes. 
		    Frame Delay = (RxTimeb-TxTimeStampf)-(TxTimeStampb-RxTimeStampf)
	   "
   ::= { sispm1040582lrtPerformanceMonitor 45 } 
   
sispm1040582lrtPerformanceMonitorDelayMeasurementGap OBJECT-TYPE
   SYNTAX      Integer32
   MAX-ACCESS  read-write
   STATUS      current
   DESCRIPTION
       "The gap between transmitting 1DM/DMM PDU in 10ms. The range is 10 to 65535.
	   "
   ::= { sispm1040582lrtPerformanceMonitor 46 } 

sispm1040582lrtPerformanceMonitorDelayMeasurementCount OBJECT-TYPE
   SYNTAX      Integer32
   MAX-ACCESS  read-write
   STATUS      current
   DESCRIPTION
       "The number of last records to calculate. The range is 10 to 2000.
	   "
   ::= { sispm1040582lrtPerformanceMonitor 47 } 
   
sispm1040582lrtPerformanceMonitorDelayMeasurementUnit OBJECT-TYPE
   SYNTAX      Integer32
   MAX-ACCESS  read-write
   STATUS      current
   DESCRIPTION
       "The time resolution.
	   0:us
	   1:ns
	   "
   ::= { sispm1040582lrtPerformanceMonitor 48 }  
   
sispm1040582lrtPerformanceMonitorDelayMeasurementD2forD1 OBJECT-TYPE
   SYNTAX      Integer32
   MAX-ACCESS  read-write
   STATUS      current
   DESCRIPTION
       "Enable to use DMM/DMR packet to calculate one-way DM.
	   0:disable
	   1:enable	
	   "
   ::= { sispm1040582lrtPerformanceMonitor 49 }  
   
sispm1040582lrtPerformanceMonitorDelayMeasurementCounterOverflowAction OBJECT-TYPE
   SYNTAX      Integer32
   MAX-ACCESS  read-write
   STATUS      current
   DESCRIPTION
       "The action to counter when overflow happens.
	   0: Keep:When internal total delay counter overflow, DM is disabled automatically
	   1: Reset:When internal total delay counter overflow, counter is reset and DM continues running
	   "
   ::= { sispm1040582lrtPerformanceMonitor 50 }  
   
sispm1040582lrtPerformanceMonitorDelayMeasurementStateOnewayTx OBJECT-TYPE
   SYNTAX      DisplayString
   MAX-ACCESS  read-only
   STATUS      current
   DESCRIPTION
       "The accumulated transmit count - since last 'clear'.
	   "
   ::= { sispm1040582lrtPerformanceMonitor 51 } 
   
sispm1040582lrtPerformanceMonitorDelayMeasurementStateOnewayRx OBJECT-TYPE
   SYNTAX      DisplayString
   MAX-ACCESS  read-only
   STATUS      current
   DESCRIPTION
       "The accumulated receive count - since last 'clear'.
	   "
   ::= { sispm1040582lrtPerformanceMonitor 52 } 
   
sispm1040582lrtPerformanceMonitorDelayMeasurementStateOnewayRxTimeout OBJECT-TYPE
   SYNTAX      DisplayString
   MAX-ACCESS  read-only
   STATUS      current
   DESCRIPTION
       "The accumulated receive timeout count for two-way only - since last 'clear'.
	   "
   ::= { sispm1040582lrtPerformanceMonitor 53 } 
   
sispm1040582lrtPerformanceMonitorDelayMeasurementStateOnewayRxError OBJECT-TYPE
   SYNTAX      DisplayString
   MAX-ACCESS  read-only
   STATUS      current
   DESCRIPTION
       "The accumulated receive error count - since last 'clear'. 
	   This is counting if the frame delay is larger than 1 second or if far end residence time is larger than the round trip time.
	   "
   ::= { sispm1040582lrtPerformanceMonitor 54 }
   
sispm1040582lrtPerformanceMonitorDelayMeasurementStateOnewayAvDelayTot OBJECT-TYPE
   SYNTAX      DisplayString
   MAX-ACCESS  read-only
   STATUS      current
   DESCRIPTION
       "The average total delay - since last 'clear'.
	   "
   ::= { sispm1040582lrtPerformanceMonitor 55 }
   
sispm1040582lrtPerformanceMonitorDelayMeasurementStateOnewayAvDelaylastN OBJECT-TYPE
   SYNTAX      DisplayString
   MAX-ACCESS  read-only
   STATUS      current
   DESCRIPTION
       "The average delay of the last n packets - since last 'clear'.
	   "
   ::= { sispm1040582lrtPerformanceMonitor 56 }
   
sispm1040582lrtPerformanceMonitorDelayMeasurementStateOnewayDelayMin OBJECT-TYPE
   SYNTAX      DisplayString
   MAX-ACCESS  read-only
   STATUS      current
   DESCRIPTION
       "The minimum delay - since last 'clear'.
	   "
   ::= { sispm1040582lrtPerformanceMonitor 57 }
   
sispm1040582lrtPerformanceMonitorDelayMeasurementStateOnewayDelayMax OBJECT-TYPE
   SYNTAX      DisplayString
   MAX-ACCESS  read-only
   STATUS      current
   DESCRIPTION
       "The maximum delay - since last 'clear'.
	   "
   ::= { sispm1040582lrtPerformanceMonitor 58 }
   
sispm1040582lrtPerformanceMonitorDelayMeasurementStateOnewayAvDelayVarTot OBJECT-TYPE
   SYNTAX      DisplayString
   MAX-ACCESS  read-only
   STATUS      current
   DESCRIPTION
       "The average total delay variation - since last 'clear'.
	   "
   ::= { sispm1040582lrtPerformanceMonitor 59 }
   
sispm1040582lrtPerformanceMonitorDelayMeasurementStateOnewayAvDelayVarlastN OBJECT-TYPE
   SYNTAX      DisplayString
   MAX-ACCESS  read-only
   STATUS      current
   DESCRIPTION
       "The average delay variation of the last n packets - since last 'clear'.
	   "
   ::= { sispm1040582lrtPerformanceMonitor 60 }
   
sispm1040582lrtPerformanceMonitorDelayMeasurementStateOnewayDelayVarMin OBJECT-TYPE
   SYNTAX      DisplayString
   MAX-ACCESS  read-only
   STATUS      current
   DESCRIPTION
       "The minimum delay variation - since last 'clear'.
	   "
   ::= { sispm1040582lrtPerformanceMonitor 61 }
   
sispm1040582lrtPerformanceMonitorDelayMeasurementStateOnewayDelayVarMax OBJECT-TYPE
   SYNTAX      DisplayString
   MAX-ACCESS  read-only
   STATUS      current
   DESCRIPTION
       "The maximum delay variation - since last 'clear'.
	   "
   ::= { sispm1040582lrtPerformanceMonitor 62 }
   
sispm1040582lrtPerformanceMonitorDelayMeasurementStateOnewayOverflow OBJECT-TYPE
   SYNTAX      DisplayString
   MAX-ACCESS  read-only
   STATUS      current
   DESCRIPTION
       "The number of counter overflow - since last 'clear'.
	   "
   ::= { sispm1040582lrtPerformanceMonitor 63 }
   
sispm1040582lrtPerformanceMonitorDelayMeasurementStateFtoNTx OBJECT-TYPE
   SYNTAX      Integer32
   MAX-ACCESS  read-only
   STATUS      current
   DESCRIPTION
       "The accumulated transmit count - since last 'clear'.
	   "
   ::= { sispm1040582lrtPerformanceMonitor 64 } 
   
sispm1040582lrtPerformanceMonitorDelayMeasurementStateFtoNRx OBJECT-TYPE
   SYNTAX      Integer32
   MAX-ACCESS  read-only
   STATUS      current
   DESCRIPTION
       "The accumulated receive count - since last 'clear'.
	   "
   ::= { sispm1040582lrtPerformanceMonitor 65 } 
   
sispm1040582lrtPerformanceMonitorDelayMeasurementStateFtoNRxTimeout OBJECT-TYPE
   SYNTAX      Integer32
   MAX-ACCESS  read-only
   STATUS      current
   DESCRIPTION
       "The accumulated receive timeout count for two-way only - since last 'clear'.
	   "
   ::= { sispm1040582lrtPerformanceMonitor 66 } 
   
sispm1040582lrtPerformanceMonitorDelayMeasurementStateFtoNRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sispm1040582lrtPerformanceMonitor 67 }
   
sispm1040582lrtPerformanceMonitorDelayMeasurementStateFtoNAvDelayTot OBJECT-TYPE
   SYNTAX      Integer32
   MAX-ACCESS  read-only
   STATUS      current
   DESCRIPTION
       "The average total delay - since last 'clear'.
	   "
   ::= { sispm1040582lrtPerformanceMonitor 68 }
   
sispm1040582lrtPerformanceMonitorDelayMeasurementStateFtoNAvDelaylastN OBJECT-TYPE
   SYNTAX      Integer32
   MAX-ACCESS  read-only
   STATUS      current
   DESCRIPTION
       "The average delay of the last n packets - since last 'clear'.
	   "
   ::= { sispm1040582lrtPerformanceMonitor 69 }
   
sispm1040582lrtPerformanceMonitorDelayMeasurementStateFtoNDelayMin OBJECT-TYPE
   SYNTAX      Integer32
   MAX-ACCESS  read-only
   STATUS      current
   DESCRIPTION
       "The minimum delay - since last 'clear'.
	   "
   ::= { sispm1040582lrtPerformanceMonitor 70 }
   
sispm1040582lrtPerformanceMonitorDelayMeasurementStateFtoNDelayMax OBJECT-TYPE
   SYNTAX      Integer32
   MAX-ACCESS  read-only
   STATUS      current
   DESCRIPTION
       "The maximum delay - since last 'clear'.
	   "
   ::= { sispm1040582lrtPerformanceMonitor 71 }
   
sispm1040582lrtPerformanceMonitorDelayMeasurementStateFtoNAvDelayVarTot OBJECT-TYPE
   SYNTAX      Integer32
   MAX-ACCESS  read-only
   STATUS      current
   DESCRIPTION
       "The average total delay variation - since last 'clear'.
	   "
   ::= { sispm1040582lrtPerformanceMonitor 72 }
   
sispm1040582lrtPerformanceMonitorDelayMeasurementStateFtoNAvDelayVarlastN OBJECT-TYPE
   SYNTAX      Integer32
   MAX-ACCESS  read-only
   STATUS      current
   DESCRIPTION
       "The average delay variation of the last n packets - since last 'clear'.
	   "
   ::= { sispm1040582lrtPerformanceMonitor 73 }
   
sispm1040582lrtPerformanceMonitorDelayMeasurementStateFtoNDelayVarMin OBJECT-TYPE
   SYNTAX      Integer32
   MAX-ACCESS  read-only
   STATUS      current
   DESCRIPTION
       "The minimum delay variation - since last 'clear'.
	   "
   ::= { sispm1040582lrtPerformanceMonitor 74 }
   
sispm1040582lrtPerformanceMonitorDelayMeasurementStateFtoNDelayVarMax OBJECT-TYPE
   SYNTAX      Integer32
   MAX-ACCESS  read-only
   STATUS      current
   DESCRIPTION
       "The maximum delay variation - since last 'clear'.
	   "
   ::= { sispm1040582lrtPerformanceMonitor 75 }
   
sispm1040582lrtPerformanceMonitorDelayMeasurementStateFtoNOverflow OBJECT-TYPE
   SYNTAX      Integer32
   MAX-ACCESS  read-only
   STATUS      current
   DESCRIPTION
       "The number of counter overflow - since last 'clear'.
	   "
   ::= { sispm1040582lrtPerformanceMonitor 76 }
   
sispm1040582lrtPerformanceMonitorDelayMeasurementStateNtoFTx OBJECT-TYPE
   SYNTAX      Integer32
   MAX-ACCESS  read-only
   STATUS      current
   DESCRIPTION
       "The accumulated transmit count - since last 'clear'.
	   "
   ::= { sispm1040582lrtPerformanceMonitor 77 } 
   
sispm1040582lrtPerformanceMonitorDelayMeasurementStateNtoFRx OBJECT-TYPE
   SYNTAX      Integer32
   MAX-ACCESS  read-only
   STATUS      current
   DESCRIPTION
       "The accumulated receive count - since last 'clear'.
	   "
   ::= { sispm1040582lrtPerformanceMonitor 78 } 
   
sispm1040582lrtPerformanceMonitorDelayMeasurementStateNtoFRxTimeout OBJECT-TYPE
   SYNTAX      Integer32
   MAX-ACCESS  read-only
   STATUS      current
   DESCRIPTION
       "The accumulated receive timeout count for two-way only - since last 'clear'.
	   "
   ::= { sispm1040582lrtPerformanceMonitor 79 } 
   
sispm1040582lrtPerformanceMonitorDelayMeasurementStateNtoFRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sispm1040582lrtPerformanceMonitor 80 }
   
sispm1040582lrtPerformanceMonitorDelayMeasurementStateNtoFAvDelayTot OBJECT-TYPE
   SYNTAX      Integer32
   MAX-ACCESS  read-only
   STATUS      current
   DESCRIPTION
       "The average total delay - since last 'clear'.
	   "
   ::= { sispm1040582lrtPerformanceMonitor 81 }
   
sispm1040582lrtPerformanceMonitorDelayMeasurementStateNtoFAvDelaylastN OBJECT-TYPE
   SYNTAX      Integer32
   MAX-ACCESS  read-only
   STATUS      current
   DESCRIPTION
       "The average delay of the last n packets - since last 'clear'.
	   "
   ::= { sispm1040582lrtPerformanceMonitor 82 }
   
sispm1040582lrtPerformanceMonitorDelayMeasurementStateNtoFDelayMin OBJECT-TYPE
   SYNTAX      Integer32
   MAX-ACCESS  read-only
   STATUS      current
   DESCRIPTION
       "The minimum delay - since last 'clear'.
	   "
   ::= { sispm1040582lrtPerformanceMonitor 83 }
   
sispm1040582lrtPerformanceMonitorDelayMeasurementStateNtoFDelayMax OBJECT-TYPE
   SYNTAX      Integer32
   MAX-ACCESS  read-only
   STATUS      current
   DESCRIPTION
       "The maximum delay - since last 'clear'.
	   "
   ::= { sispm1040582lrtPerformanceMonitor 84 }
   
sispm1040582lrtPerformanceMonitorDelayMeasurementStateNtoFAvDelayVarTot OBJECT-TYPE
   SYNTAX      Integer32
   MAX-ACCESS  read-only
   STATUS      current
   DESCRIPTION
       "The average total delay variation - since last 'clear'.
	   "
   ::= { sispm1040582lrtPerformanceMonitor 85 }
   
sispm1040582lrtPerformanceMonitorDelayMeasurementStateNtoFAvDelayVarlastN OBJECT-TYPE
   SYNTAX      Integer32
   MAX-ACCESS  read-only
   STATUS      current
   DESCRIPTION
       "The average delay variation of the last n packets - since last 'clear'.
	   "
   ::= { sispm1040582lrtPerformanceMonitor 86 }
   
sispm1040582lrtPerformanceMonitorDelayMeasurementStateNtoFDelayVarMin OBJECT-TYPE
   SYNTAX      Integer32
   MAX-ACCESS  read-only
   STATUS      current
   DESCRIPTION
       "The minimum delay variation - since last 'clear'.
	   "
   ::= { sispm1040582lrtPerformanceMonitor 87 }
   
sispm1040582lrtPerformanceMonitorDelayMeasurementStateNtoFDelayVarMax OBJECT-TYPE
   SYNTAX      Integer32
   MAX-ACCESS  read-only
   STATUS      current
   DESCRIPTION
       "The maximum delay variation - since last 'clear'.
	   "
   ::= { sispm1040582lrtPerformanceMonitor 88 }
   
sispm1040582lrtPerformanceMonitorDelayMeasurementStateNtoFOverflow OBJECT-TYPE
   SYNTAX      Integer32
   MAX-ACCESS  read-only
   STATUS      current
   DESCRIPTION
       "The number of counter overflow - since last 'clear'.
	   "
   ::= { sispm1040582lrtPerformanceMonitor 89 }
   
sispm1040582lrtPerformanceMonitorDelayMeasurementStateTwowayTx OBJECT-TYPE
   SYNTAX      Integer32
   MAX-ACCESS  read-only
   STATUS      current
   DESCRIPTION
       "The accumulated transmit count - since last 'clear'.
	   "
   ::= { sispm1040582lrtPerformanceMonitor 90 } 
   
sispm1040582lrtPerformanceMonitorDelayMeasurementStateTwowayRx OBJECT-TYPE
   SYNTAX      Integer32
   MAX-ACCESS  read-only
   STATUS      current
   DESCRIPTION
       "The accumulated receive count - since last 'clear'.
	   "
   ::= { sispm1040582lrtPerformanceMonitor 91 } 
   
sispm1040582lrtPerformanceMonitorDelayMeasurementStateTwowayRxTimeout OBJECT-TYPE
   SYNTAX      Integer32
   MAX-ACCESS  read-only
   STATUS      current
   DESCRIPTION
       "The accumulated receive timeout count for two-way only - since last 'clear'.
	   "
   ::= { sispm1040582lrtPerformanceMonitor 92 } 
   
sispm1040582lrtPerformanceMonitorDelayMeasurementStateTwowayRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sispm1040582lrtPerformanceMonitor 93 }
   
sispm1040582lrtPerformanceMonitorDelayMeasurementStateTwowayAvDelayTot OBJECT-TYPE
   SYNTAX      Integer32
   MAX-ACCESS  read-only
   STATUS      current
   DESCRIPTION
       "The average total delay - since last 'clear'.
	   "
   ::= { sispm1040582lrtPerformanceMonitor 94 }
   
sispm1040582lrtPerformanceMonitorDelayMeasurementStateTwowayAvDelaylastN OBJECT-TYPE
   SYNTAX      Integer32
   MAX-ACCESS  read-only
   STATUS      current
   DESCRIPTION
       "The average delay of the last n packets - since last 'clear'.
	   "
   ::= { sispm1040582lrtPerformanceMonitor 95 }
   
sispm1040582lrtPerformanceMonitorDelayMeasurementStateTwowayDelayMin OBJECT-TYPE
   SYNTAX      Integer32
   MAX-ACCESS  read-only
   STATUS      current
   DESCRIPTION
       "The minimum delay - since last 'clear'.
	   "
   ::= { sispm1040582lrtPerformanceMonitor 96 }
   
sispm1040582lrtPerformanceMonitorDelayMeasurementStateTwowayDelayMax OBJECT-TYPE
   SYNTAX      Integer32
   MAX-ACCESS  read-only
   STATUS      current
   DESCRIPTION
       "The maximum delay - since last 'clear'.
	   "
   ::= { sispm1040582lrtPerformanceMonitor 97 }
   
sispm1040582lrtPerformanceMonitorDelayMeasurementStateTwowayAvDelayVarTot OBJECT-TYPE
   SYNTAX      Integer32
   MAX-ACCESS  read-only
   STATUS      current
   DESCRIPTION
       "The average total delay variation - since last 'clear'.
	   "
   ::= { sispm1040582lrtPerformanceMonitor 98 }
   
sispm1040582lrtPerformanceMonitorDelayMeasurementStateTwowayAvDelayVarlastN OBJECT-TYPE
   SYNTAX      Integer32
   MAX-ACCESS  read-only
   STATUS      current
   DESCRIPTION
       "The average delay variation of the last n packets - since last 'clear'.
	   "
   ::= { sispm1040582lrtPerformanceMonitor 99 }
   
sispm1040582lrtPerformanceMonitorDelayMeasurementStateTwowayDelayVarMin OBJECT-TYPE
   SYNTAX      Integer32
   MAX-ACCESS  read-only
   STATUS      current
   DESCRIPTION
       "The minimum delay variation - since last 'clear'.
	   "
   ::= { sispm1040582lrtPerformanceMonitor 100 }
   
sispm1040582lrtPerformanceMonitorDelayMeasurementStateTwowayDelayVarMax OBJECT-TYPE
   SYNTAX      Integer32
   MAX-ACCESS  read-only
   STATUS      current
   DESCRIPTION
       "The maximum delay variation - since last 'clear'.
	   "
   ::= { sispm1040582lrtPerformanceMonitor 101 }
   
sispm1040582lrtPerformanceMonitorDelayMeasurementStateTwowayOverflow OBJECT-TYPE
   SYNTAX      Integer32
   MAX-ACCESS  read-only
   STATUS      current
   DESCRIPTION
       "The number of counter overflow - since last 'clear'.
	   "
   ::= { sispm1040582lrtPerformanceMonitor 102 }
   
sispm1040582lrtPerformanceMonitorDelayMeasurementStateClear OBJECT-TYPE
   SYNTAX      Integer32
   MAX-ACCESS  read-write
   STATUS      current
   DESCRIPTION
       "Set of this check and save will clear the accumulated counters.
	   1:clear
	   "
   ::= { sispm1040582lrtPerformanceMonitor 103 }
   
sispm1040582lrtPerformanceMonitorDelayMeasurementBinsMeasurementBinsforFD OBJECT-TYPE
   SYNTAX      Integer32
   MAX-ACCESS  read-write
   STATUS      current
   DESCRIPTION
       "Configurable number of Frame Delay Measurement Bins per Measurement Interval.
	   range: 2-10
	   "
   ::= { sispm1040582lrtPerformanceMonitor 104 }
   
sispm1040582lrtPerformanceMonitorDelayMeasurementBinsMeasurementBinsforIFDV OBJECT-TYPE
   SYNTAX      Integer32
   MAX-ACCESS  read-write
   STATUS      current
   DESCRIPTION
       "Configurable number of Inter-Frame Delay Variation Measurement Bins per Measurement Interval.
	   range: 2-10
	   "
   ::= { sispm1040582lrtPerformanceMonitor 105 }
   
sispm1040582lrtPerformanceMonitorDelayMeasurementBinsMeasurementThreshold OBJECT-TYPE
   SYNTAX      Integer32
   MAX-ACCESS  read-write
   STATUS      current
   DESCRIPTION
       "Configurable the Measurement Threshold for each Measurement Bin.
	   "
   ::= { sispm1040582lrtPerformanceMonitor 106 }
   
   
   
   
sispm1040582lrtPerformanceMonitorDelayMeasurementBinsforFDTable OBJECT-TYPE
   SYNTAX      SEQUENCE OF SISPM1040582LRTPerformanceMonitorDelayMeasurementBinsforFDEntry
   MAX-ACCESS  not-accessible
   STATUS      current
   DESCRIPTION
       " "
   ::= { sispm1040582lrtMEP 16 }

sispm1040582lrtPerformanceMonitorDelayMeasurementBinsforFDEntry OBJECT-TYPE
   SYNTAX      SISPM1040582LRTPerformanceMonitorDelayMeasurementBinsforFDEntry
   MAX-ACCESS  not-accessible
   STATUS      current
   DESCRIPTION
       " "
   INDEX    { sispm1040582lrtPerformanceMonitorDelayMeasurementBinsforFDIndex  }
   ::= { sispm1040582lrtPerformanceMonitorDelayMeasurementBinsforFDTable 1 }

SISPM1040582LRTPerformanceMonitorDelayMeasurementBinsforFDEntry ::= SEQUENCE {
   sispm1040582lrtPerformanceMonitorDelayMeasurementBinsforFDIndex    Integer32,
   sispm1040582lrtPerformanceMonitorDelayMeasurementBinsforFDOneway   Integer32,
   sispm1040582lrtPerformanceMonitorDelayMeasurementBinsforFDFtoN     Integer32,
   sispm1040582lrtPerformanceMonitorDelayMeasurementBinsforFDNtoF     Integer32,
   sispm1040582lrtPerformanceMonitorDelayMeasurementBinsforFDTwoway   Integer32
   
}

sispm1040582lrtPerformanceMonitorDelayMeasurementBinsforFDIndex OBJECT-TYPE
   SYNTAX      Integer32
   MAX-ACCESS  not-accessible
   STATUS      current
   DESCRIPTION
       "Index"
   ::= { sispm1040582lrtPerformanceMonitorDelayMeasurementBinsforFDEntry 1 }

sispm1040582lrtPerformanceMonitorDelayMeasurementBinsforFDOneway OBJECT-TYPE
   SYNTAX      Integer32
   MAX-ACCESS  read-only
   STATUS      current
   DESCRIPTION
       " "
   ::= { sispm1040582lrtPerformanceMonitorDelayMeasurementBinsforFDEntry 2 }

sispm1040582lrtPerformanceMonitorDelayMeasurementBinsforFDFtoN OBJECT-TYPE
   SYNTAX      Integer32
   MAX-ACCESS  read-only
   STATUS      current
   DESCRIPTION
       " "
   ::= { sispm1040582lrtPerformanceMonitorDelayMeasurementBinsforFDEntry 3 }
   
sispm1040582lrtPerformanceMonitorDelayMeasurementBinsforFDNtoF OBJECT-TYPE
   SYNTAX      Integer32
   MAX-ACCESS  read-only
   STATUS      current
   DESCRIPTION
       " "
   ::= { sispm1040582lrtPerformanceMonitorDelayMeasurementBinsforFDEntry 4 }  
   
sispm1040582lrtPerformanceMonitorDelayMeasurementBinsforFDTwoway OBJECT-TYPE
   SYNTAX      Integer32
   MAX-ACCESS  read-only
   STATUS      current
   DESCRIPTION
       " "
   ::= { sispm1040582lrtPerformanceMonitorDelayMeasurementBinsforFDEntry 5 } 
   
   
   
   
sispm1040582lrtPerformanceMonitorDelayMeasurementBinsforIFDVTable OBJECT-TYPE
   SYNTAX      SEQUENCE OF SISPM1040582LRTPerformanceMonitorDelayMeasurementBinsforIFDVEntry
   MAX-ACCESS  not-accessible
   STATUS      current
   DESCRIPTION
       " "
   ::= { sispm1040582lrtMEP 17 }

sispm1040582lrtPerformanceMonitorDelayMeasurementBinsforIFDVEntry OBJECT-TYPE
   SYNTAX      SISPM1040582LRTPerformanceMonitorDelayMeasurementBinsforIFDVEntry
   MAX-ACCESS  not-accessible
   STATUS      current
   DESCRIPTION
       " "
   INDEX    { sispm1040582lrtPerformanceMonitorDelayMeasurementBinsforIFDVIndex  }
   ::= { sispm1040582lrtPerformanceMonitorDelayMeasurementBinsforIFDVTable 1 }

SISPM1040582LRTPerformanceMonitorDelayMeasurementBinsforIFDVEntry ::= SEQUENCE {
   sispm1040582lrtPerformanceMonitorDelayMeasurementBinsforIFDVIndex    Integer32,
   sispm1040582lrtPerformanceMonitorDelayMeasurementBinsforIFDVOneway   Integer32,
   sispm1040582lrtPerformanceMonitorDelayMeasurementBinsforIFDVFtoN     Integer32,
   sispm1040582lrtPerformanceMonitorDelayMeasurementBinsforIFDVNtoF     Integer32,
   sispm1040582lrtPerformanceMonitorDelayMeasurementBinsforIFDVTwoway   Integer32
   
}

sispm1040582lrtPerformanceMonitorDelayMeasurementBinsforIFDVIndex OBJECT-TYPE
   SYNTAX      Integer32
   MAX-ACCESS  not-accessible
   STATUS      current
   DESCRIPTION
       "Index"
   ::= { sispm1040582lrtPerformanceMonitorDelayMeasurementBinsforIFDVEntry 1 }

sispm1040582lrtPerformanceMonitorDelayMeasurementBinsforIFDVOneway OBJECT-TYPE
   SYNTAX      Integer32
   MAX-ACCESS  read-only
   STATUS      current
   DESCRIPTION
       " "
   ::= { sispm1040582lrtPerformanceMonitorDelayMeasurementBinsforIFDVEntry 2 }

sispm1040582lrtPerformanceMonitorDelayMeasurementBinsforIFDVFtoN OBJECT-TYPE
   SYNTAX      Integer32
   MAX-ACCESS  read-only
   STATUS      current
   DESCRIPTION
       " "
   ::= { sispm1040582lrtPerformanceMonitorDelayMeasurementBinsforIFDVEntry 3 }
   
sispm1040582lrtPerformanceMonitorDelayMeasurementBinsforIFDVNtoF OBJECT-TYPE
   SYNTAX      Integer32
   MAX-ACCESS  read-only
   STATUS      current
   DESCRIPTION
       " "
   ::= { sispm1040582lrtPerformanceMonitorDelayMeasurementBinsforIFDVEntry 4 }  
   
sispm1040582lrtPerformanceMonitorDelayMeasurementBinsforIFDVTwoway OBJECT-TYPE
   SYNTAX      Integer32
   MAX-ACCESS  read-only
   STATUS      current
   DESCRIPTION
       " "
   ::= { sispm1040582lrtPerformanceMonitorDelayMeasurementBinsforIFDVEntry 5 } 
   
sispm1040582lrtRRING    OBJECT IDENTIFIER ::= { sispm1040582lrtConfiguration 27 }   
   
sispm1040582lrtRRINGTable OBJECT-TYPE
   SYNTAX      SEQUENCE OF SISPM1040582LRTRRINGEntry
   MAX-ACCESS  not-accessible
   STATUS      current
   DESCRIPTION
       " "
   ::= { sispm1040582lrtRRING 1 }

sispm1040582lrtRRINGEntry OBJECT-TYPE
   SYNTAX      SISPM1040582LRTRRINGEntry
   MAX-ACCESS  not-accessible
   STATUS      current
   DESCRIPTION
       " "
   INDEX    { sispm1040582lrtRRINGIndex  }
   ::= { sispm1040582lrtRRINGTable 1 }

SISPM1040582LRTRRINGEntry ::= SEQUENCE {
   sispm1040582lrtRRINGIndex     Integer32,
   sispm1040582lrtRRINGRole      Integer32,
   sispm1040582lrtRRINGPort1     Integer32,
   sispm1040582lrtRRINGPort2     Integer32,
   sispm1040582lrtRRINGStatus1   DisplayString,
   sispm1040582lrtRRINGStatus2   DisplayString
}

sispm1040582lrtRRINGIndex OBJECT-TYPE
   SYNTAX      Integer32
   MAX-ACCESS  not-accessible
   STATUS      current
   DESCRIPTION
       "Index"
   ::= { sispm1040582lrtRRINGEntry 1 }

sispm1040582lrtRRINGRole OBJECT-TYPE
   SYNTAX      Integer32
   MAX-ACCESS  read-write
   STATUS      current
   DESCRIPTION
       "Set role value.
	   0:Disabled
	   1:Master
	   2:Member
	   3:Rapid-Chain
	   "
   ::= { sispm1040582lrtRRINGEntry 2 }

sispm1040582lrtRRINGPort1 OBJECT-TYPE
   SYNTAX      Integer32
   MAX-ACCESS  read-write
   STATUS      current
   DESCRIPTION
       "The switch port number of the port1 .
	   "
   ::= { sispm1040582lrtRRINGEntry 3 }
   
sispm1040582lrtRRINGPort2 OBJECT-TYPE
   SYNTAX      Integer32
   MAX-ACCESS  read-write
   STATUS      current
   DESCRIPTION
       "The switch port number of the port2 .
	   "
   ::= { sispm1040582lrtRRINGEntry 4 }  
   
sispm1040582lrtRRINGStatus1 OBJECT-TYPE
   SYNTAX      DisplayString
   MAX-ACCESS  read-only
   STATUS      current
   DESCRIPTION
       "The current Rapid Ring status of the port1. "
   ::= { sispm1040582lrtRRINGEntry 5 } 
   
sispm1040582lrtRRINGStatus2 OBJECT-TYPE
   SYNTAX      DisplayString
   MAX-ACCESS  read-only
   STATUS      current
   DESCRIPTION
       "The current Rapid Ring status of the port2. "
   ::= { sispm1040582lrtRRINGEntry 6 }    

sispm1040582lrtRINGtoRINGRole OBJECT-TYPE
   SYNTAX      Integer32
   MAX-ACCESS  read-write
   STATUS      current
   DESCRIPTION
       "Set ring-to-ring role value.
	   0:Disabled
	   1:Active
	   2:Backup
	   "
   ::= { sispm1040582lrtRRING 2 }

sispm1040582lrtRINGtoRINGPort OBJECT-TYPE
   SYNTAX      Integer32
   MAX-ACCESS  read-write
   STATUS      current
   DESCRIPTION
       "The switch port number of the ring-to-ring port.
	   "
   ::= { sispm1040582lrtRRING 3 }
   

sispm1040582lrtRINGtoRINGStatus OBJECT-TYPE
   SYNTAX      DisplayString
   MAX-ACCESS  read-only
   STATUS      current
   DESCRIPTION
       "The current ring-to-ring status of the port."
   ::= { sispm1040582lrtRRING 4 }
   
   
sispm1040582lrtPTP    OBJECT IDENTIFIER ::= { sispm1040582lrtConfiguration 28 }   

sispm1040582lrtPTPOnePPSMode OBJECT-TYPE
   SYNTAX      Integer32
   MAX-ACCESS  read-write
   STATUS      current
   DESCRIPTION
       "This Selection box will allow you to select the One_pps_mode configuration.
		The following values are possible:
		0:Disable
		1. Output
		2. Input
		3. Output Input
		"
   ::= { sispm1040582lrtPTP 1 }
   
sispm1040582lrtPTPExternalEnable OBJECT-TYPE
   SYNTAX      Integer32
   MAX-ACCESS  read-write
   STATUS      current
   DESCRIPTION
       "This Selection box will allow you to configure the External Clock output.
		The following values are possible:
		1. True : Enable the external clock output
		0. False : Disable the external clock output
		"
   ::= { sispm1040582lrtPTP 2 }   
   
sispm1040582lrtPTPAdjustMethod OBJECT-TYPE
   SYNTAX      Integer32
   MAX-ACCESS  read-write
   STATUS      current
   DESCRIPTION
       "This Selection box will allow you to configure the Frequency adjustment configuration.
		0: LTC frequency : Select Local Time Counter (LTC) frequency control
		1: SyncE-DPLL : Select SyncE DPLL frequency control, if allowed by SyncE
		2: Oscillator : Select an oscillator independent of SyncE for frequency control, if supported by the HW
		3: LTC phase : Select Local Time Counter (LTC) phase control (assumes that the frequency is locked by means of SyncE)
		"
   ::= { sispm1040582lrtPTP 3 }      
   
sispm1040582lrtPTPClockFrequency OBJECT-TYPE
   SYNTAX      Integer32
   MAX-ACCESS  read-write
   STATUS      current
   DESCRIPTION
       "This will allow to set the Clock Frequency.
        The possible range of values are 1 - 25000000 (1 - 25MHz)
	   "
   ::= { sispm1040582lrtPTP 4 }   
   


sispm1040582lrtPTPClockConfTable  OBJECT-TYPE
   SYNTAX      SEQUENCE OF SISPM1040582LRTPTPClockConfEntry
   MAX-ACCESS  not-accessible
   STATUS      current
   DESCRIPTION
       "A table of PTP Clock Conf."
 ::= { sispm1040582lrtPTP 5 }

sispm1040582lrtPTPClockConfEntry OBJECT-TYPE
    SYNTAX        SISPM1040582LRTPTPClockConfEntry
    MAX-ACCESS    not-accessible
    STATUS        current
    DESCRIPTION
        "An entry in the PTP Clock Conf table."
    INDEX        { sispm1040582lrtPTPClockConfIndex }
    ::= { sispm1040582lrtPTPClockConfTable 1 }

SISPM1040582LRTPTPClockConfEntry ::=
    SEQUENCE {
        sispm1040582lrtPTPClockConfIndex                    Integer32,
        sispm1040582lrtPTPClockConfClockInstance            Integer32,
        sispm1040582lrtPTPClockConfDeviceType               Integer32,
		sispm1040582lrtPTPClockConfProfile                  Integer32,
        sispm1040582lrtPTPClockConfRowStatus                RowStatus
    }

sispm1040582lrtPTPClockConfIndex OBJECT-TYPE
   SYNTAX      Integer32
   MAX-ACCESS  not-accessible
   STATUS      current
   DESCRIPTION
       "PTP Clock Conf index."
   ::= {sispm1040582lrtPTPClockConfEntry 1 }

sispm1040582lrtPTPClockConfClockInstance OBJECT-TYPE
   SYNTAX      Integer32
   MAX-ACCESS  read-create
   STATUS      current
   DESCRIPTION
       "Indicates the Instance of a particular Clock Instance [0..3]."
   ::= {sispm1040582lrtPTPClockConfEntry 2 }

sispm1040582lrtPTPClockConfDeviceType OBJECT-TYPE
   SYNTAX      Integer32
   MAX-ACCESS  read-create
   STATUS      current
   DESCRIPTION
       "Indicates the Type of the Clock Instance. There are five Device Types.
	    0: Inactive - passive clock instance
		1: Ord-Bound - clock's Device Type is Ordinary-Boundary Clock.
		2: P2p Transp - clock's Device Type is Peer to Peer Transparent Clock.
		3: E2e Transp - clock's Device Type is End to End Transparent Clock.
		4: Master Only - clock's Device Type is Master Only.
		5: Slave Only - clock's Device Type is Slave Only.
		6: Boundary Clock frontend clock instance, only 1-step, 1-way is supported."
   ::= {sispm1040582lrtPTPClockConfEntry 3 }
   
sispm1040582lrtPTPClockConfProfile OBJECT-TYPE
   SYNTAX      Integer32
   MAX-ACCESS  read-create
   STATUS      current
   DESCRIPTION
       "0:No profile
	   1:1588
	   2:G8265.1
	   3:G8275.1
	   "
   ::= {sispm1040582lrtPTPClockConfEntry 4 }   
   
sispm1040582lrtPTPClockConfRowStatus OBJECT-TYPE
   SYNTAX      RowStatus
   MAX-ACCESS  read-create
   STATUS      current
   DESCRIPTION
       "PTP Clock Conf Row Status."
   ::= {sispm1040582lrtPTPClockConfEntry 5 }
   
sispm1040582lrtPTPClockInstance OBJECT-TYPE
   SYNTAX      Integer32
   MAX-ACCESS  read-write
   STATUS      current
   DESCRIPTION
       "Specify the PTP clock instance for the following item used [0..3]."
   ::= {sispm1040582lrtPTP 6 }
   
   
sispm1040582lrtPTPClockConfAndStatus    OBJECT IDENTIFIER ::= { sispm1040582lrtPTP 7 }

sispm1040582lrtPTPClockConfEntryClockInstance OBJECT-TYPE
   SYNTAX      Integer32
   MAX-ACCESS  read-only
   STATUS      current
   DESCRIPTION
       ""
   ::= {sispm1040582lrtPTPClockConfAndStatus 2 }

sispm1040582lrtPTPClockConfEntryDeviceType OBJECT-TYPE
   SYNTAX      DisplayString
   MAX-ACCESS  read-only
   STATUS      current
   DESCRIPTION
       ""
   ::= {sispm1040582lrtPTPClockConfAndStatus 3 }   
   
sispm1040582lrtPTPClockConfEntryProfile OBJECT-TYPE
   SYNTAX      DisplayString
   MAX-ACCESS  read-only
   STATUS      current
   DESCRIPTION
       ""
   ::= {sispm1040582lrtPTPClockConfAndStatus 4 }    

sispm1040582lrtPTPClockConfEntryApplyProfileDefaults OBJECT-TYPE
   SYNTAX      Integer32
   MAX-ACCESS  read-write
   STATUS      current
   DESCRIPTION
       "-1:n/a
	   0:normal state
	   1:apply profile default"
   ::= {sispm1040582lrtPTPClockConfAndStatus 5 }   
   
sispm1040582lrtPTPClockConfEntryPTPTime OBJECT-TYPE
   SYNTAX      DisplayString
   MAX-ACCESS  read-only
   STATUS      current
   DESCRIPTION
       "Shows the actual PTP time with nanosecond resolution."
   ::= {sispm1040582lrtPTPClockConfAndStatus 6 }    
   
sispm1040582lrtPTPClockConfEntryClockAdjustmentMethod OBJECT-TYPE
   SYNTAX      DisplayString
   MAX-ACCESS  read-only
   STATUS      current
   DESCRIPTION
       "Shows the actual clock adjustment method. The method depends on the available hardware."
   ::= {sispm1040582lrtPTPClockConfAndStatus 7 }     
   
sispm1040582lrtPTPClockConfEntrySynchronizeToSystemClock OBJECT-TYPE
   SYNTAX      Integer32
   MAX-ACCESS  read-write
   STATUS      current
   DESCRIPTION
       "Activate this button to synchronize the System Clock to PTP Time.
	   1:Synchronize to system clock."
   ::= {sispm1040582lrtPTPClockConfAndStatus 8 }    

sispm1040582lrtPTPClockConfEntryClockCurrentDataSetstpRm OBJECT-TYPE
   SYNTAX      Integer32
   MAX-ACCESS  read-only
   STATUS      current
   DESCRIPTION
       "Steps Removed : It is the number of PTP clocks traversed from the grandmaster to the local slave clock."
   ::= {sispm1040582lrtPTPClockConfAndStatus 9 }   
   
sispm1040582lrtPTPClockConfEntryClockCurrentDataSetOffsetFromMaster OBJECT-TYPE
   SYNTAX      DisplayString
   MAX-ACCESS  read-only
   STATUS      current
   DESCRIPTION
       "Time difference between the master clock and the local slave clock, measured in ns."
   ::= {sispm1040582lrtPTPClockConfAndStatus 10 }      
  
sispm1040582lrtPTPClockConfEntryClockCurrentDataSetMeanPathDelay OBJECT-TYPE
   SYNTAX      DisplayString
   MAX-ACCESS  read-only
   STATUS      current
   DESCRIPTION
       "The mean propagation time for the link between the master and the local slave."
   ::= {sispm1040582lrtPTPClockConfAndStatus 11 }   
   
sispm1040582lrtPTPClockConfEntryClockCurrentDataSetSlavePort OBJECT-TYPE
   SYNTAX      Integer32
   MAX-ACCESS  read-only
   STATUS      current
   DESCRIPTION
       "Shows which port is in slave mode. The value is 0 if no ports are in slave mode."
   ::= {sispm1040582lrtPTPClockConfAndStatus 12 }  
   
sispm1040582lrtPTPClockConfEntryClockCurrentDataSetSlaveState OBJECT-TYPE
   SYNTAX      DisplayString
   MAX-ACCESS  read-only
   STATUS      current
   DESCRIPTION
       "Shows synchronization state of the slave."
   ::= {sispm1040582lrtPTPClockConfAndStatus 13 }  
   
sispm1040582lrtPTPClockConfEntryClockCurrentDataSetHoldover OBJECT-TYPE
   SYNTAX      DisplayString
   MAX-ACCESS  read-only
   STATUS      current
   DESCRIPTION
       "After the slave has been in Locked mode during the stabilization period, 
	   this value shows the actual clock offset between the freerun and the actual holdover frequency, 
	   the value is shown in parts pr billion (ppb). 
	   During the stabilization period, the value is shown as N.A. 
	   The stabilization period is 60 sec as default, it can be changed from the CLI interface."
   ::= {sispm1040582lrtPTPClockConfAndStatus 14 } 

sispm1040582lrtPTPClockConfEntryClockParentDataSetParentPortID OBJECT-TYPE
   SYNTAX      DisplayString
   MAX-ACCESS  read-only
   STATUS      current
   DESCRIPTION
       "Clock identity for the parent clock, if the local clock is not a slave, the value is the clocks own id."
   ::= {sispm1040582lrtPTPClockConfAndStatus 15 }     
  
sispm1040582lrtPTPClockConfEntryClockParentDataSetPort OBJECT-TYPE
   SYNTAX      Integer32
   MAX-ACCESS  read-only
   STATUS      current
   DESCRIPTION
       "Port Id for the parent master port"
   ::= {sispm1040582lrtPTPClockConfAndStatus 16 }

sispm1040582lrtPTPClockConfEntryClockParentDataSetPStat OBJECT-TYPE
   SYNTAX      DisplayString
   MAX-ACCESS  read-only
   STATUS      current
   DESCRIPTION
       "Parents Stats (always false)."
   ::= {sispm1040582lrtPTPClockConfAndStatus 17 }     
   
sispm1040582lrtPTPClockConfEntryClockParentDataSetVar OBJECT-TYPE
   SYNTAX      Integer32
   MAX-ACCESS  read-only
   STATUS      current
   DESCRIPTION
       "It is observed parent offset scaled log variance"
   ::= {sispm1040582lrtPTPClockConfAndStatus 18 }    
   
sispm1040582lrtPTPClockConfEntryClockParentDataSetRate OBJECT-TYPE
   SYNTAX      Integer32
   MAX-ACCESS  read-only
   STATUS      current
   DESCRIPTION
       "Observed Parent Clock Phase Change Rate. i.e. the slave clocks rate offset compared to the master. 
	   (unit = ns per s)."
   ::= {sispm1040582lrtPTPClockConfAndStatus 19 }  

sispm1040582lrtPTPClockConfEntryClockParentDataSetGrandMasterID OBJECT-TYPE
   SYNTAX      DisplayString
   MAX-ACCESS  read-only
   STATUS      current
   DESCRIPTION
       "Clock identity for the grand master clock, if the local clock is not a slave, the value is the clocks own id."
   ::= {sispm1040582lrtPTPClockConfAndStatus 20 }   

sispm1040582lrtPTPClockConfEntryClockParentDataSetGrandMasterClockQuality OBJECT-TYPE
   SYNTAX      DisplayString
   MAX-ACCESS  read-only
   STATUS      current
   DESCRIPTION
       "The clock quality announced by the grand master (See description of Clock Default DataSet:Clock Quality)"
   ::= {sispm1040582lrtPTPClockConfAndStatus 21 }     
   
sispm1040582lrtPTPClockConfEntryClockParentDataSetPri1 OBJECT-TYPE
   SYNTAX      Integer32
   MAX-ACCESS  read-only
   STATUS      current
   DESCRIPTION
       "Clock priority 1 announced by the grand master"
   ::= {sispm1040582lrtPTPClockConfAndStatus 22 }   

sispm1040582lrtPTPClockConfEntryClockParentDataSetPri2 OBJECT-TYPE
   SYNTAX      Integer32
   MAX-ACCESS  read-only
   STATUS      current
   DESCRIPTION
       "Clock priority 2 announced by the grand master."
   ::= {sispm1040582lrtPTPClockConfAndStatus 23 }      
   
sispm1040582lrtPTPClockConfEntryClockDefaultDataSetClockID OBJECT-TYPE
   SYNTAX      Integer32
   MAX-ACCESS  read-only
   STATUS      current
   DESCRIPTION
       "An internal instance id (0..3)"
   ::= {sispm1040582lrtPTPClockConfAndStatus 24 }     
   
sispm1040582lrtPTPClockConfEntryClockDefaultDataSetDeviceType OBJECT-TYPE
   SYNTAX      DisplayString
   MAX-ACCESS  read-only
   STATUS      current
   DESCRIPTION
       "Indicates the Type of the Clock Instance. There are five Device Types.
		1. Ord-Bound - Clock's Device Type is Ordinary-Boundary Clock.
		2. P2p Transp - Clock's Device Type is Peer to Peer Transparent Clock.
		3. E2e Transp - Clock's Device Type is End to End Transparent Clock.
		4. Master Only - Clock's Device Type is Master Only.
		5. Slave Only - Clock's Device Type is Slave Only."
   ::= {sispm1040582lrtPTPClockConfAndStatus 25 }    

sispm1040582lrtPTPClockConfEntryClockDefaultDataSet2StepFlag OBJECT-TYPE
   SYNTAX      Integer32
   MAX-ACCESS  read-write
   STATUS      current
   DESCRIPTION
       "True if two-step Sync events and Pdelay_Resp events are used
	   0:false
	   1:true"
   ::= {sispm1040582lrtPTPClockConfAndStatus 26 }   
   
sispm1040582lrtPTPClockConfEntryClockDefaultDataSetPorts OBJECT-TYPE
   SYNTAX      Integer32
   MAX-ACCESS  read-only
   STATUS      current
   DESCRIPTION
       "The total number of physical ports in the node"
   ::= {sispm1040582lrtPTPClockConfAndStatus 27 }     
   
sispm1040582lrtPTPClockConfEntryClockDefaultDataSetClockIdentity OBJECT-TYPE
   SYNTAX      DisplayString
   MAX-ACCESS  read-only
   STATUS      current
   DESCRIPTION
       "It shows unique clock identifier"
   ::= {sispm1040582lrtPTPClockConfAndStatus 28 }    

sispm1040582lrtPTPClockConfEntryClockDefaultDataSetDom OBJECT-TYPE
   SYNTAX      Integer32
   MAX-ACCESS  read-write
   STATUS      current
   DESCRIPTION
       "Clock domain [0..127]."
   ::= {sispm1040582lrtPTPClockConfAndStatus 29 }     
   
sispm1040582lrtPTPClockConfEntryClockDefaultDataSetClockQuality OBJECT-TYPE
   SYNTAX      DisplayString
   MAX-ACCESS  read-only
   STATUS      current
   DESCRIPTION
       "The clock quality is determined by the system, and holds 3 parts: Clock Class, Clock Accuracy and OffsetScaledLog Variance as defined in IEEE1588.
The Clock Accuracy values are defined in IEEE1588 table 6 (Currently the clock Accuracy is set to 'Unknown' as default)."
   ::= {sispm1040582lrtPTPClockConfAndStatus 30 }  
   
sispm1040582lrtPTPClockConfEntryClockDefaultDataSetPri1 OBJECT-TYPE
   SYNTAX      Integer32
   MAX-ACCESS  read-write
   STATUS      current
   DESCRIPTION
       "Clock priority 1 [0..255] used by the BMC master select algorithm."
   ::= {sispm1040582lrtPTPClockConfAndStatus 31 }
   
sispm1040582lrtPTPClockConfEntryClockDefaultDataSetPri2 OBJECT-TYPE
   SYNTAX      Integer32
   MAX-ACCESS  read-write
   STATUS      current
   DESCRIPTION
       "Clock priority 2 [0..255] used by the BMC master select algorithm."
   ::= {sispm1040582lrtPTPClockConfAndStatus 32 }   
   
sispm1040582lrtPTPClockConfEntryClockDefaultDataSetProtocol OBJECT-TYPE
   SYNTAX      Integer32
   MAX-ACCESS  read-write
   STATUS      current
   DESCRIPTION
       "0:Ethernet
	   1:Ethernet Mixed
	   2:IP4Multi
	   3:IP4Mixed
	   4:IP4Uni
	   5:OAM
	   6:OnePPS"
   ::= {sispm1040582lrtPTPClockConfAndStatus 33 }     
   
sispm1040582lrtPTPClockConfEntryClockDefaultDataSetOneWay OBJECT-TYPE
   SYNTAX      Integer32
   MAX-ACCESS  read-write
   STATUS      current
   DESCRIPTION
       "If true, one way measurements are used. 
	   This parameter applies only to a slave. 
	   In one-way mode no delay measurements are performed, i.e. this is applicable only if frequency synchronization is needed. 
	   The master always responds to delay requests.
	   0:false
	   1:true"
   ::= {sispm1040582lrtPTPClockConfAndStatus 34 }     
   
sispm1040582lrtPTPClockConfEntryClockDefaultDataSetVLANTagEnable OBJECT-TYPE
   SYNTAX      Integer32
   MAX-ACCESS  read-write
   STATUS      current
   DESCRIPTION
       "The VLAN Tag Enable parameter is ignored, because the tagging is controlled by the VLAN configuration.
	   0:false
	   1:true"
   ::= {sispm1040582lrtPTPClockConfAndStatus 35 }   

sispm1040582lrtPTPClockConfEntryClockDefaultDataSetVID OBJECT-TYPE
   SYNTAX      Integer32
   MAX-ACCESS  read-write
   STATUS      current
   DESCRIPTION
       "TVLAN Identifier used for tagging the VLAN packets.
	   range:1-4095"
   ::= {sispm1040582lrtPTPClockConfAndStatus 36 }    

sispm1040582lrtPTPClockConfEntryClockDefaultDataSetPCP OBJECT-TYPE
   SYNTAX      Integer32
   MAX-ACCESS  read-write
   STATUS      current
   DESCRIPTION
       "Priority Code Point value used for PTP frames. range:0-7"
   ::= {sispm1040582lrtPTPClockConfAndStatus 37 }     
   
sispm1040582lrtPTPClockConfEntryClockDefaultDataSetDSCP OBJECT-TYPE
   SYNTAX      Integer32
   MAX-ACCESS  read-write
   STATUS      current
   DESCRIPTION
       ""
   ::= {sispm1040582lrtPTPClockConfAndStatus 38 }  
   
sispm1040582lrtPTPClockConfEntryClockTimePropertiesDataSetUtcOffset OBJECT-TYPE
   SYNTAX      Integer32
   MAX-ACCESS  read-write
   STATUS      current
   DESCRIPTION
       "range: 0-10000"
   ::= {sispm1040582lrtPTPClockConfAndStatus 39 }     
 
sispm1040582lrtPTPClockConfEntryClockTimePropertiesDataSetValid OBJECT-TYPE
   SYNTAX      Integer32
   MAX-ACCESS  read-write
   STATUS      current
   DESCRIPTION
       "0:false
	   1:true"
   ::= {sispm1040582lrtPTPClockConfAndStatus 40 }     
   
sispm1040582lrtPTPClockConfEntryClockTimePropertiesDataSetLeap59 OBJECT-TYPE
   SYNTAX      Integer32
   MAX-ACCESS  read-write
   STATUS      current
   DESCRIPTION
       "0:false
	   1:true"
   ::= {sispm1040582lrtPTPClockConfAndStatus 41 }   
   
sispm1040582lrtPTPClockConfEntryClockTimePropertiesDataSetLeap61 OBJECT-TYPE
   SYNTAX      Integer32
   MAX-ACCESS  read-write
   STATUS      current
   DESCRIPTION
       "0:false
	   1:true"
   ::= {sispm1040582lrtPTPClockConfAndStatus 42 }    
   
sispm1040582lrtPTPClockConfEntryClockTimePropertiesDataSetTimeTrac OBJECT-TYPE
   SYNTAX      Integer32
   MAX-ACCESS  read-write
   STATUS      current
   DESCRIPTION
       "0:false
	   1:true"
   ::= {sispm1040582lrtPTPClockConfAndStatus 43 }           
   
sispm1040582lrtPTPClockConfEntryClockTimePropertiesDataSetFreqTrac OBJECT-TYPE
   SYNTAX      Integer32
   MAX-ACCESS  read-write
   STATUS      current
   DESCRIPTION
       "0:false
	   1:true"
   ::= {sispm1040582lrtPTPClockConfAndStatus 44 }    
   
sispm1040582lrtPTPClockConfEntryClockTimePropertiesDataSetPTPTimeScale OBJECT-TYPE
   SYNTAX      Integer32
   MAX-ACCESS  read-write
   STATUS      current
   DESCRIPTION
       "0:false
	   1:true"
   ::= {sispm1040582lrtPTPClockConfAndStatus 45 }    
   
sispm1040582lrtPTPClockConfEntryClockTimePropertiesDataSetTimeSource OBJECT-TYPE
   SYNTAX      Integer32
   MAX-ACCESS  read-write
   STATUS      current
   DESCRIPTION
       "range: 0-255"
   ::= {sispm1040582lrtPTPClockConfAndStatus 46 }      
   
sispm1040582lrtPTPClockConfEntryFilterParametersFilterType OBJECT-TYPE
   SYNTAX      Integer32
   MAX-ACCESS  read-write
   STATUS      current
   DESCRIPTION
       "Shows the filter type used which can be either the basic filter or an advanced filter that can be configured to use only a fraction of the packets received 
	   (i.e. the packets that have experienced the least latency).
	   0:BASIC"
   ::= {sispm1040582lrtPTPClockConfAndStatus 47 }  
   
sispm1040582lrtPTPClockConfEntryFilterParametersDelayFilter OBJECT-TYPE
   SYNTAX      Integer32
   MAX-ACCESS  read-write
   STATUS      current
   DESCRIPTION
       "range:0-6"
   ::= {sispm1040582lrtPTPClockConfAndStatus 48 }   
   
sispm1040582lrtPTPClockConfEntryFilterParametersPeriod OBJECT-TYPE
   SYNTAX      Integer32
   MAX-ACCESS  read-write
   STATUS      current
   DESCRIPTION
       "range:1-10000"
   ::= {sispm1040582lrtPTPClockConfAndStatus 49 }    

sispm1040582lrtPTPClockConfEntryFilterParametersDist OBJECT-TYPE
   SYNTAX      Integer32
   MAX-ACCESS  read-write
   STATUS      current
   DESCRIPTION
       "range:1-10"
   ::= {sispm1040582lrtPTPClockConfAndStatus 50 }     

sispm1040582lrtPTPClockConfEntryServoParametersDisplay OBJECT-TYPE
   SYNTAX      Integer32
   MAX-ACCESS  read-write
   STATUS      current
   DESCRIPTION
       "If true then Offset From Master, MeanPathDelay and clockAdjustment are logged on the debug terminal
	   0:false
	   1:true"
   ::= {sispm1040582lrtPTPClockConfAndStatus 51 }    

sispm1040582lrtPTPClockConfEntryServoParametersPEnable OBJECT-TYPE
   SYNTAX      Integer32
   MAX-ACCESS  read-write
   STATUS      current
   DESCRIPTION
       "If true the P part of the algorithm is included
	   0:false
	   1:true"
   ::= {sispm1040582lrtPTPClockConfAndStatus 52 }    
   
sispm1040582lrtPTPClockConfEntryServoParametersIEnable OBJECT-TYPE
   SYNTAX      Integer32
   MAX-ACCESS  read-write
   STATUS      current
   DESCRIPTION
       "If true the I part of the algorithm is included
	   0:false
	   1:true"
   ::= {sispm1040582lrtPTPClockConfAndStatus 53 }       
   
sispm1040582lrtPTPClockConfEntryServoParametersDEnable OBJECT-TYPE
   SYNTAX      Integer32
   MAX-ACCESS  read-write
   STATUS      current
   DESCRIPTION
       "If true the D part of the algorithm is included
	   0:false
	   1:true"
   ::= {sispm1040582lrtPTPClockConfAndStatus 54 }          
   
sispm1040582lrtPTPClockConfEntryServoParametersPConstant OBJECT-TYPE
   SYNTAX      Integer32
   MAX-ACCESS  read-write
   STATUS      current
   DESCRIPTION
       "range:0-1000"
   ::= {sispm1040582lrtPTPClockConfAndStatus 55 }      
   
sispm1040582lrtPTPClockConfEntryServoParametersIConstant OBJECT-TYPE
   SYNTAX      Integer32
   MAX-ACCESS  read-write
   STATUS      current
   DESCRIPTION
       "range:0-10000"
   ::= {sispm1040582lrtPTPClockConfAndStatus 56 }     

sispm1040582lrtPTPClockConfEntryServoParametersDConstant OBJECT-TYPE
   SYNTAX      Integer32
   MAX-ACCESS  read-write
   STATUS      current
   DESCRIPTION
       "range:0-1000"
   ::= {sispm1040582lrtPTPClockConfAndStatus 57 }     

   
sispm1040582lrtPTPClockPortDataSetConfTable OBJECT-TYPE
   SYNTAX      SEQUENCE OF SISPM1040582LRTPTPClockPortDataSetConfEntry
   MAX-ACCESS  not-accessible
   STATUS      current
   DESCRIPTION
       " "
   ::= { sispm1040582lrtPTP 8 }

sispm1040582lrtPTPClockPortDataSetConfEntry OBJECT-TYPE
   SYNTAX      SISPM1040582LRTPTPClockPortDataSetConfEntry
   MAX-ACCESS  not-accessible
   STATUS      current
   DESCRIPTION
       " "
   INDEX    { sispm1040582lrtPTPClockPortDataSetConfPort  }
   ::= { sispm1040582lrtPTPClockPortDataSetConfTable 1 }

SISPM1040582LRTPTPClockPortDataSetConfEntry ::= SEQUENCE {
   sispm1040582lrtPTPClockPortDataSetConfPort               Integer32,
   sispm1040582lrtPTPClockConfEntryPortConfEnable           Integer32,
   sispm1040582lrtPTPClockConfEntryPortConfStat             DisplayString,
   sispm1040582lrtPTPClockConfEntryPortConfMDR              Integer32,
   sispm1040582lrtPTPClockConfEntryPortConfPeerMeanPathDel  DisplayString,
   sispm1040582lrtPTPClockConfEntryPortConfAnv              Integer32,
   sispm1040582lrtPTPClockConfEntryPortConfATo              Integer32,
   sispm1040582lrtPTPClockConfEntryPortConfSyv              Integer32,
   sispm1040582lrtPTPClockConfEntryPortConfDlm              Integer32,
   sispm1040582lrtPTPClockConfEntryPortConfMPR              Integer32,
   sispm1040582lrtPTPClockConfEntryPortConfDelayAsymmetry   Integer32,
   sispm1040582lrtPTPClockConfEntryPortConfIngressLatency   Integer32,
   sispm1040582lrtPTPClockConfEntryPortConfEgressLatency    Integer32,
   sispm1040582lrtPTPClockConfEntryPortConfVersion          Integer32
}

sispm1040582lrtPTPClockPortDataSetConfPort OBJECT-TYPE
   SYNTAX      Integer32
   MAX-ACCESS  not-accessible
   STATUS      current
   DESCRIPTION
       "Index"
   ::= { sispm1040582lrtPTPClockPortDataSetConfEntry 1 }

sispm1040582lrtPTPClockConfEntryPortConfEnable OBJECT-TYPE
   SYNTAX      Integer32
   MAX-ACCESS  read-write
   STATUS      current
   DESCRIPTION
       "0:false
	   1:true"
   ::= { sispm1040582lrtPTPClockPortDataSetConfEntry 2 }
   
sispm1040582lrtPTPClockConfEntryPortConfStat OBJECT-TYPE
   SYNTAX      DisplayString
   MAX-ACCESS  read-only
   STATUS      current
   DESCRIPTION
       "Dynamic member portState: Current state of the port."
   ::= { sispm1040582lrtPTPClockPortDataSetConfEntry 3 }   
   
sispm1040582lrtPTPClockConfEntryPortConfMDR OBJECT-TYPE
   SYNTAX      Integer32
   MAX-ACCESS  read-only
   STATUS      current
   DESCRIPTION
       "Dynamic member log Min Delay Req Interval: The delay request interval announced by the master."
   ::= { sispm1040582lrtPTPClockPortDataSetConfEntry 4 }      

sispm1040582lrtPTPClockConfEntryPortConfPeerMeanPathDel OBJECT-TYPE
   SYNTAX      DisplayString
   MAX-ACCESS  read-only
   STATUS      current
   DESCRIPTION
       "The path delay measured by the port in P2P mode. In E2E mode this value is 0"
   ::= { sispm1040582lrtPTPClockPortDataSetConfEntry 5 }  
   

   
sispm1040582lrtPTPClockConfEntryPortConfAnv OBJECT-TYPE
   SYNTAX      Integer32
   MAX-ACCESS  read-write
   STATUS      current
   DESCRIPTION
       "The interval for issuing announce messages in master state. Range is -3 to 4."
   ::= { sispm1040582lrtPTPClockPortDataSetConfEntry 6 }     
   
sispm1040582lrtPTPClockConfEntryPortConfATo OBJECT-TYPE
   SYNTAX      Integer32
   MAX-ACCESS  read-write
   STATUS      current
   DESCRIPTION
       "The timeout for receiving announce messages on the port. Range is 1 to 10."
   ::= { sispm1040582lrtPTPClockPortDataSetConfEntry 7 }    
   
sispm1040582lrtPTPClockConfEntryPortConfSyv OBJECT-TYPE
   SYNTAX      Integer32
   MAX-ACCESS  read-write
   STATUS      current
   DESCRIPTION
       "The interval for issuing sync messages in master. Range is -7 to 4."
   ::= { sispm1040582lrtPTPClockPortDataSetConfEntry 8 }     

sispm1040582lrtPTPClockConfEntryPortConfDlm OBJECT-TYPE
   SYNTAX      Integer32
   MAX-ACCESS  read-write
   STATUS      current
   DESCRIPTION
       "Configurable member delayMechanism: The delay mechanism used for the port:
		e2e	End to end delay measurement
		p2p	Peer to peer delay measurement.
		Can be defined per port in an Ordinary/Boundary clock.
		In a transparent clock all ports use the same delay mechanism, determined by the clock type.
		1:e2e
		2:p2p"
   ::= { sispm1040582lrtPTPClockPortDataSetConfEntry 9 }    

sispm1040582lrtPTPClockConfEntryPortConfMPR OBJECT-TYPE
   SYNTAX      Integer32
   MAX-ACCESS  read-write
   STATUS      current
   DESCRIPTION
       "The interval for issuing Delay_Req messages for the port in E2e mode. This value is announced from the master to the slave in an announce message. The value is reflected in the MDR field in the Slave
The interval for issuing Pdelay_Req messages for the port in P2P mode
Note: The interpretation of this parameter has changed from release 2.40. In earlier versions the value was interpreted relative to the Sync interval, this was a violation of the standard, so now the value is interpreted as an interval. I.e. MPR = 0 => 1 Delay_Req pr sec, independent of the Sync rate.
Range is -7 to 5."
   ::= { sispm1040582lrtPTPClockPortDataSetConfEntry 10 }    

sispm1040582lrtPTPClockConfEntryPortConfDelayAsymmetry OBJECT-TYPE
   SYNTAX      Integer32
   MAX-ACCESS  read-write
   STATUS      current
   DESCRIPTION
       "If the transmission delay for a link in not symmetric, the asymmetry can be configured here, see IEEE 1588 Section 7.4.2 Communication path asymmetry
Range is -100000 to 100000."
   ::= { sispm1040582lrtPTPClockPortDataSetConfEntry 11 }    
   
sispm1040582lrtPTPClockConfEntryPortConfIngressLatency OBJECT-TYPE
   SYNTAX      Integer32
   MAX-ACCESS  read-write
   STATUS      current
   DESCRIPTION
       "Ingress latency measured in ns, as defined in IEEE 1588 Section 7.3.4.2.
Range is -100000 to 100000."
   ::= { sispm1040582lrtPTPClockPortDataSetConfEntry 12 }     
   
sispm1040582lrtPTPClockConfEntryPortConfEgressLatency OBJECT-TYPE
   SYNTAX      Integer32
   MAX-ACCESS  read-write
   STATUS      current
   DESCRIPTION
       "Egress latency measured in ns, as defined in IEEE 1588 Section 7.3.4.2.
Range is -100000 to 100000."
   ::= { sispm1040582lrtPTPClockPortDataSetConfEntry 13 }     
   
sispm1040582lrtPTPClockConfEntryPortConfVersion OBJECT-TYPE
   SYNTAX      Integer32
   MAX-ACCESS  read-only
   STATUS      current
   DESCRIPTION
       "The current implementation only supports PTP version 2"
   ::= { sispm1040582lrtPTPClockPortDataSetConfEntry 14 }    
   
  
sispm1040582lrtPTPClockUnicastSlaveConfTable OBJECT-TYPE
   SYNTAX      SEQUENCE OF SISPM1040582LRTPTPClockUnicastSlaveConfEntry
   MAX-ACCESS  not-accessible
   STATUS      current
   DESCRIPTION
       " "
   ::= { sispm1040582lrtPTP 9 }

sispm1040582lrtPTPClockUnicastSlaveConfEntry OBJECT-TYPE
   SYNTAX      SISPM1040582LRTPTPClockUnicastSlaveConfEntry
   MAX-ACCESS  not-accessible
   STATUS      current
   DESCRIPTION
       " "
   INDEX    { sispm1040582lrtPTPClockConfEntryUnicastSlaveConfIndex  }
   ::= { sispm1040582lrtPTPClockUnicastSlaveConfTable 1 }

SISPM1040582LRTPTPClockUnicastSlaveConfEntry ::= SEQUENCE {
   sispm1040582lrtPTPClockConfEntryUnicastSlaveConfIndex              Integer32,
   sispm1040582lrtPTPClockConfEntryUnicastSlaveConfDuration           Integer32,
   sispm1040582lrtPTPClockConfEntryUnicastSlaveConfIPAddress          IpAddress,
   sispm1040582lrtPTPClockConfEntryUnicastSlaveConfGrant              Integer32,
   sispm1040582lrtPTPClockConfEntryUnicastSlaveConfCommState          DisplayString
}

sispm1040582lrtPTPClockConfEntryUnicastSlaveConfIndex OBJECT-TYPE
   SYNTAX      Integer32
   MAX-ACCESS  not-accessible
   STATUS      current
   DESCRIPTION
       "Index"
   ::= { sispm1040582lrtPTPClockUnicastSlaveConfEntry 1 }

sispm1040582lrtPTPClockConfEntryUnicastSlaveConfDuration OBJECT-TYPE
   SYNTAX      Integer32
   MAX-ACCESS  read-write
   STATUS      current
   DESCRIPTION
       "The number of seconds a master is requested to send Announce/Sync messages. 
	   The request is repeated from the slave each Duration/4 seconds.
	   range:10-1000"
   ::= { sispm1040582lrtPTPClockUnicastSlaveConfEntry 2 }
      
sispm1040582lrtPTPClockConfEntryUnicastSlaveConfIPAddress OBJECT-TYPE
   SYNTAX      IpAddress
   MAX-ACCESS  read-write
   STATUS      current
   DESCRIPTION
       "IPv4 Address of the Master clock"
   ::= { sispm1040582lrtPTPClockUnicastSlaveConfEntry 3 }
   
sispm1040582lrtPTPClockConfEntryUnicastSlaveConfGrant OBJECT-TYPE
   SYNTAX      Integer32
   MAX-ACCESS  read-only
   STATUS      current
   DESCRIPTION
       "The granted repetition period for the sync message"
   ::= { sispm1040582lrtPTPClockUnicastSlaveConfEntry 4 }   
   
sispm1040582lrtPTPClockConfEntryUnicastSlaveConfCommState OBJECT-TYPE
   SYNTAX      DisplayString
   MAX-ACCESS  read-only
   STATUS      current
   DESCRIPTION
       "The state of the communication with the master, possible values are:
		IDLE : The entry is not in use.
		INIT : Announce is sent to the master (Waiting for a response).
		CONN : The master has responded.
		SELL : The assigned master is selected as current master.
		SYNC : The master is sending Sync messages."
   ::= { sispm1040582lrtPTPClockUnicastSlaveConfEntry 5 }   

sispm1040582lrtETHLINKOAM    OBJECT IDENTIFIER ::= { sispm1040582lrtConfiguration 29 } 

sispm1040582lrtEthLinkOAMPortConfTable OBJECT-TYPE
   SYNTAX      SEQUENCE OF SISPM1040582LRTEthLinkOAMPortConfEntry
   MAX-ACCESS  not-accessible
   STATUS      current
   DESCRIPTION
       " "
   ::= { sispm1040582lrtETHLINKOAM 1 }

sispm1040582lrtEthLinkOAMPortConfEntry OBJECT-TYPE
   SYNTAX      SISPM1040582LRTEthLinkOAMPortConfEntry
   MAX-ACCESS  not-accessible
   STATUS      current
   DESCRIPTION
       " "
   INDEX    { sispm1040582lrtEthLinkOAMPortConfIndex  }
   ::= { sispm1040582lrtEthLinkOAMPortConfTable 1 }

SISPM1040582LRTEthLinkOAMPortConfEntry ::= SEQUENCE {
   sispm1040582lrtEthLinkOAMPortConfIndex               Integer32,
   sispm1040582lrtEthLinkOAMPortConfOAMEnable           Integer32,
   sispm1040582lrtEthLinkOAMPortConfOAMMode             Integer32,
   sispm1040582lrtEthLinkOAMPortConfLoopbackSupport     Integer32,
   sispm1040582lrtEthLinkOAMPortConfLinkMonitorSupport  Integer32,
   sispm1040582lrtEthLinkOAMPortConfMIBRetrievalSupport Integer32,
   sispm1040582lrtEthLinkOAMPortConfLoopbackOperation   Integer32
}

sispm1040582lrtEthLinkOAMPortConfIndex OBJECT-TYPE
   SYNTAX      Integer32
   MAX-ACCESS  not-accessible
   STATUS      current
   DESCRIPTION
       "Index"
   ::= { sispm1040582lrtEthLinkOAMPortConfEntry 1 }

sispm1040582lrtEthLinkOAMPortConfOAMEnable OBJECT-TYPE
   SYNTAX      Integer32
   MAX-ACCESS  read-write
   STATUS      current
   DESCRIPTION
       "Controls whether Link OAM is enabled on this switch port. 
	   Enabling Link OAM provides the network operators the ability to monitor the health of the network and 
	   quickly determine the location of failing links or fault conditions.
	   0:disable
	   1:enable"
   ::= { sispm1040582lrtEthLinkOAMPortConfEntry 2 }
   
sispm1040582lrtEthLinkOAMPortConfOAMMode OBJECT-TYPE
   SYNTAX      Integer32
   MAX-ACCESS  read-write
   STATUS      current
   DESCRIPTION
       "Configures the OAM Mode as Active or Passive. The default mode is Passive.
	   0:Passive mode
	   1:Active mode"
   ::= { sispm1040582lrtEthLinkOAMPortConfEntry 3 }   
   
sispm1040582lrtEthLinkOAMPortConfLoopbackSupport OBJECT-TYPE
   SYNTAX      Integer32
   MAX-ACCESS  read-write
   STATUS      current
   DESCRIPTION
       "Controls whether the loopback support is enabled for the switch port. 
	   0:disable
	   1:enable"
   ::= { sispm1040582lrtEthLinkOAMPortConfEntry 4 }     
   
sispm1040582lrtEthLinkOAMPortConfLinkMonitorSupport OBJECT-TYPE
   SYNTAX      Integer32
   MAX-ACCESS  read-write
   STATUS      current
   DESCRIPTION
       "Controls whether the Link Monitor support is enabled for the switch port.
	   0:disable
	   1:enable"
   ::= { sispm1040582lrtEthLinkOAMPortConfEntry 5 }

sispm1040582lrtEthLinkOAMPortConfMIBRetrievalSupport OBJECT-TYPE
   SYNTAX      Integer32
   MAX-ACCESS  read-write
   STATUS      current
   DESCRIPTION
       "Controls whether the MIB Retrieval Support is enabled for the switch port. 
	   0:disable
	   1:enable"
   ::= { sispm1040582lrtEthLinkOAMPortConfEntry 6 }    
   
sispm1040582lrtEthLinkOAMPortConfLoopbackOperation OBJECT-TYPE
   SYNTAX      Integer32
   MAX-ACCESS  read-write
   STATUS      current
   DESCRIPTION
       "If the Loopback support is enabled, enabling this field will start a loopback operation for the port.
	   0:disable
	   1:enable"
   ::= { sispm1040582lrtEthLinkOAMPortConfEntry 7 }       
   
   
   
sispm1040582lrtEthLinkOAMPortDetailStatusTable OBJECT-TYPE
   SYNTAX      SEQUENCE OF SISPM1040582LRTEthLinkOAMPortDetailStatusEntry
   MAX-ACCESS  not-accessible
   STATUS      current
   DESCRIPTION
       "Eth Link OAM Port Detail Status table"
   ::= { sispm1040582lrtETHLINKOAM 2 }

sispm1040582lrtEthLinkOAMPortDetailStatusEntry OBJECT-TYPE
   SYNTAX      SISPM1040582LRTEthLinkOAMPortDetailStatusEntry
   MAX-ACCESS  not-accessible
   STATUS      current
   DESCRIPTION
       "Eth Link OAM Port Detail Status entry"
   INDEX    { sispm1040582lrtEthLinkOAMPortDetailStatusIndex  }
   ::= { sispm1040582lrtEthLinkOAMPortDetailStatusTable 1 }

SISPM1040582LRTEthLinkOAMPortDetailStatusEntry ::= SEQUENCE {
   sispm1040582lrtEthLinkOAMPortDetailStatusIndex                       Integer32,
   sispm1040582lrtEthLinkOAMPortPDUPermission                           DisplayString,
   sispm1040582lrtEthLinkOAMPortDiscoveryState                          DisplayString,
   sispm1040582lrtEthLinkOAMPortPeerMACAddress                          DisplayString,
   sispm1040582lrtEthLinkOAMPortLocalMode                               DisplayString,
   sispm1040582lrtEthLinkOAMPortLocalUnidirectionalOperationSupport     DisplayString,
   sispm1040582lrtEthLinkOAMPortLocalRemoteLoopbackSupport              DisplayString,
   sispm1040582lrtEthLinkOAMPortLocalLinkMonitoringSupport              DisplayString,
   sispm1040582lrtEthLinkOAMPortLocalMIBRetrievalSupport                DisplayString,
   sispm1040582lrtEthLinkOAMPortLocalMTUSize                            Integer32,  
   sispm1040582lrtEthLinkOAMPortLocalMultiplexerState                   DisplayString,  
   sispm1040582lrtEthLinkOAMPortLocalParserState                        DisplayString,  
   sispm1040582lrtEthLinkOAMPortLocalOrganizationalUniqueIdentification DisplayString,  
   sispm1040582lrtEthLinkOAMPortLocalPDURevision                        Integer32,  
   sispm1040582lrtEthLinkOAMPortPeerMode                                DisplayString,  
   sispm1040582lrtEthLinkOAMPortPeerUnidirectionalOperationSupport      DisplayString,  
   sispm1040582lrtEthLinkOAMPortPeerRemoteLoopbackSupport               DisplayString,  
   sispm1040582lrtEthLinkOAMPortPeerLinkMonitoringSupport               DisplayString,  
   sispm1040582lrtEthLinkOAMPortPeerMIBRetrievalSupport                 DisplayString,  
   sispm1040582lrtEthLinkOAMPortPeerMTUSize                             DisplayString,  
   sispm1040582lrtEthLinkOAMPortPeerMultiplexerState                    DisplayString,  
   sispm1040582lrtEthLinkOAMPortPeerParserState                         DisplayString,  
   sispm1040582lrtEthLinkOAMPortPeerOrganizationalUniqueIdentification  DisplayString,  
   sispm1040582lrtEthLinkOAMPortPDURevision                             DisplayString     
}

sispm1040582lrtEthLinkOAMPortDetailStatusIndex OBJECT-TYPE
   SYNTAX      Integer32
   MAX-ACCESS  not-accessible
   STATUS      current
   DESCRIPTION
       "Index"
   ::= { sispm1040582lrtEthLinkOAMPortDetailStatusEntry 1 }

sispm1040582lrtEthLinkOAMPortPDUPermission OBJECT-TYPE
   SYNTAX      DisplayString
   MAX-ACCESS  read-only
   STATUS      current
   DESCRIPTION
       "This field is available only for the Local DTE. 
	   It displays the current permission rules set for the local DTE. 
	   Possible values are Link fault, Receive only, Information exchange only, ANY."
   ::= { sispm1040582lrtEthLinkOAMPortDetailStatusEntry 2 }
   
sispm1040582lrtEthLinkOAMPortDiscoveryState OBJECT-TYPE
   SYNTAX      DisplayString
   MAX-ACCESS  read-only
   STATUS      current
   DESCRIPTION
       "Displays the current state of the discovery process. 
	   Possible states are Fault state, Active state, Passive state, 
	   SEND_LOCAL_REMOTE_STATE, SEND_LOCAL_REMOTE_OK_STATE, SEND_ANY_STATE."
   ::= { sispm1040582lrtEthLinkOAMPortDetailStatusEntry 3 }   
   
sispm1040582lrtEthLinkOAMPortPeerMACAddress OBJECT-TYPE
   SYNTAX      DisplayString
   MAX-ACCESS  read-only
   STATUS      current
   DESCRIPTION
       " "
   ::= { sispm1040582lrtEthLinkOAMPortDetailStatusEntry 4 }     
   
sispm1040582lrtEthLinkOAMPortLocalMode OBJECT-TYPE
   SYNTAX      DisplayString
   MAX-ACCESS  read-only
   STATUS      current
   DESCRIPTION
       "The Mode in which the Link OAM is operating, Active or Passive."
   ::= { sispm1040582lrtEthLinkOAMPortDetailStatusEntry 5 }

sispm1040582lrtEthLinkOAMPortLocalUnidirectionalOperationSupport OBJECT-TYPE
   SYNTAX      DisplayString
   MAX-ACCESS  read-only
   STATUS      current
   DESCRIPTION
       "This feature is not available to be configured by the user. The status of this configuration is retrieved from the PHY."
   ::= { sispm1040582lrtEthLinkOAMPortDetailStatusEntry 6 }    
   
sispm1040582lrtEthLinkOAMPortLocalRemoteLoopbackSupport OBJECT-TYPE
   SYNTAX      DisplayString
   MAX-ACCESS  read-only
   STATUS      current
   DESCRIPTION
       "If status is enabled, DTE is capable of OAM remote loopback mode."
   ::= { sispm1040582lrtEthLinkOAMPortDetailStatusEntry 7 }       
   
sispm1040582lrtEthLinkOAMPortLocalLinkMonitoringSupport OBJECT-TYPE
   SYNTAX      DisplayString
   MAX-ACCESS  read-only
   STATUS      current
   DESCRIPTION
       "If status is enabled, DTE supports interpreting Link Events."
   ::= { sispm1040582lrtEthLinkOAMPortDetailStatusEntry 8 }   

sispm1040582lrtEthLinkOAMPortLocalMIBRetrievalSupport OBJECT-TYPE
   SYNTAX      DisplayString
   MAX-ACCESS  read-only
   STATUS      current
   DESCRIPTION
       "If status ie enabled DTE supports sending Variable Response OAMPDUs."
   ::= { sispm1040582lrtEthLinkOAMPortDetailStatusEntry 9 }   

sispm1040582lrtEthLinkOAMPortLocalMTUSize OBJECT-TYPE
   SYNTAX      Integer32
   MAX-ACCESS  read-only
   STATUS      current
   DESCRIPTION
       "It represents the largest OAMPDU, in octets, supported by the DTE. 
	   This value is compared to the remotes Maximum PDU Size and the smaller of the two is used."
   ::= { sispm1040582lrtEthLinkOAMPortDetailStatusEntry 10 }   
   
sispm1040582lrtEthLinkOAMPortLocalMultiplexerState OBJECT-TYPE
   SYNTAX      DisplayString
   MAX-ACCESS  read-only
   STATUS      current
   DESCRIPTION
       "When in forwarding state, the Device is forwarding non-OAMPDUs to the lower sublayer. 
	   Incase of discarding, the device discards all the non-OAMPDU's."
   ::= { sispm1040582lrtEthLinkOAMPortDetailStatusEntry 11 }  
   
sispm1040582lrtEthLinkOAMPortLocalParserState OBJECT-TYPE
   SYNTAX      DisplayString
   MAX-ACCESS  read-only
   STATUS      current
   DESCRIPTION
       "When in forwarding state, Device is forwarding non-OAMPDUs to higher sublayer. 
	   When in loopback, Device is looping back non-OAMPDUs to the lower sublayer. 
	   When in discarding state, Device is discarding non-OAMPDUs."
   ::= { sispm1040582lrtEthLinkOAMPortDetailStatusEntry 12 }  
   
sispm1040582lrtEthLinkOAMPortLocalOrganizationalUniqueIdentification OBJECT-TYPE
   SYNTAX      DisplayString
   MAX-ACCESS  read-only
   STATUS      current
   DESCRIPTION
       "24-bit Organizationally Unique Identifier of the vendor."
   ::= { sispm1040582lrtEthLinkOAMPortDetailStatusEntry 13 }   
   
sispm1040582lrtEthLinkOAMPortLocalPDURevision OBJECT-TYPE
   SYNTAX      Integer32
   MAX-ACCESS  read-only
   STATUS      current
   DESCRIPTION
       "It indicates the current revision of the Information TLV. 
	   The value of this field shall start at zero and be incremented each time something in the Information TLV changes. 
	   Upon reception of an Information TLV from a peer, an OAM client may use this field to decide if it needs to be processed 
	   (an Information TLV that is identical to the previous Information TLV doesn't need to be parsed as nothing in it has changed)."
   ::= { sispm1040582lrtEthLinkOAMPortDetailStatusEntry 14 } 
   
sispm1040582lrtEthLinkOAMPortPeerMode OBJECT-TYPE
   SYNTAX      DisplayString
   MAX-ACCESS  read-only
   STATUS      current
   DESCRIPTION
       "The Mode in which the Link OAM is operating, Active or Passive."
   ::= { sispm1040582lrtEthLinkOAMPortDetailStatusEntry 15 }  
   
sispm1040582lrtEthLinkOAMPortPeerUnidirectionalOperationSupport OBJECT-TYPE
   SYNTAX      DisplayString
   MAX-ACCESS  read-only
   STATUS      current
   DESCRIPTION
       "This feature is not available to be configured by the user. 
	   The status of this configuration is retrieved from the PHY."
   ::= { sispm1040582lrtEthLinkOAMPortDetailStatusEntry 16 } 
   
sispm1040582lrtEthLinkOAMPortPeerRemoteLoopbackSupport OBJECT-TYPE
   SYNTAX      DisplayString
   MAX-ACCESS  read-only
   STATUS      current
   DESCRIPTION
       "If status is enabled, DTE is capable of OAM remote loopback mode."
   ::= { sispm1040582lrtEthLinkOAMPortDetailStatusEntry 17 } 
   
sispm1040582lrtEthLinkOAMPortPeerLinkMonitoringSupport OBJECT-TYPE
   SYNTAX      DisplayString
   MAX-ACCESS  read-only
   STATUS      current
   DESCRIPTION
       "If status is enabled, DTE supports interpreting Link Events."
   ::= { sispm1040582lrtEthLinkOAMPortDetailStatusEntry 18 } 
   
sispm1040582lrtEthLinkOAMPortPeerMIBRetrievalSupport OBJECT-TYPE
   SYNTAX      DisplayString
   MAX-ACCESS  read-only
   STATUS      current
   DESCRIPTION
       "If status ie enabled DTE supports sending Variable Response OAMPDUs."
   ::= { sispm1040582lrtEthLinkOAMPortDetailStatusEntry 19 } 
   
sispm1040582lrtEthLinkOAMPortPeerMTUSize OBJECT-TYPE
   SYNTAX      DisplayString
   MAX-ACCESS  read-only
   STATUS      current
   DESCRIPTION
       "It represents the largest OAMPDU, in octets, supported by the DTE. 
	   This value is compared to the remotes Maximum PDU Size and the smaller of the two is used."
   ::= { sispm1040582lrtEthLinkOAMPortDetailStatusEntry 20 } 
   
sispm1040582lrtEthLinkOAMPortPeerMultiplexerState OBJECT-TYPE
   SYNTAX      DisplayString
   MAX-ACCESS  read-only
   STATUS      current
   DESCRIPTION
       "When in forwarding state, the Device is forwarding non-OAMPDUs to the lower sublayer. 
	   Incase of discarding, the device discards all the non-OAMPDU's."
   ::= { sispm1040582lrtEthLinkOAMPortDetailStatusEntry 21 } 
   
sispm1040582lrtEthLinkOAMPortPeerParserState OBJECT-TYPE
   SYNTAX      DisplayString
   MAX-ACCESS  read-only
   STATUS      current
   DESCRIPTION
       "When in forwarding state, Device is forwarding non-OAMPDUs to higher sublayer. 
	   When in loopback, Device is looping back non-OAMPDUs to the lower sublayer. 
	   When in discarding state, Device is discarding non-OAMPDUs."
   ::= { sispm1040582lrtEthLinkOAMPortDetailStatusEntry 22 } 
   
sispm1040582lrtEthLinkOAMPortPeerOrganizationalUniqueIdentification OBJECT-TYPE
   SYNTAX      DisplayString
   MAX-ACCESS  read-only
   STATUS      current
   DESCRIPTION
       "24-bit Organizationally Unique Identifier of the vendor."
   ::= { sispm1040582lrtEthLinkOAMPortDetailStatusEntry 23 }      
   
sispm1040582lrtEthLinkOAMPortPDURevision                              OBJECT-TYPE
   SYNTAX      DisplayString
   MAX-ACCESS  read-only
   STATUS      current
   DESCRIPTION
       "It indicates the current revision of the Information TLV. 
	   The value of this field shall start at zero and be incremented each time something in the Information TLV changes. 
	   Upon reception of an Information TLV from a peer, an OAM client may use this field to decide if it needs to be processed 
	   (an Information TLV that is identical to the previous Information TLV doesn't need to be parsed as nothing in it has changed)."
   ::= { sispm1040582lrtEthLinkOAMPortDetailStatusEntry 24 }   


sispm1040582lrtEthLinkOAMPortLinkEventConfTable OBJECT-TYPE
   SYNTAX      SEQUENCE OF SISPM1040582LRTEthLinkOAMPortLinkEventConfEntry
   MAX-ACCESS  not-accessible
   STATUS      current
   DESCRIPTION
       "Eth Link OAM Port Link Event Conf Table"
   ::= { sispm1040582lrtETHLINKOAM 3 }

sispm1040582lrtEthLinkOAMPortLinkEventConfEntry OBJECT-TYPE
   SYNTAX      SISPM1040582LRTEthLinkOAMPortLinkEventConfEntry
   MAX-ACCESS  not-accessible
   STATUS      current
   DESCRIPTION
       "Eth Link OAM Port Link Event Conf Entry"
   INDEX    { sispm1040582lrtEthLinkOAMPortLinkEventConfIndex  }
   ::= { sispm1040582lrtEthLinkOAMPortLinkEventConfTable 1 }

SISPM1040582LRTEthLinkOAMPortLinkEventConfEntry ::= SEQUENCE {
   sispm1040582lrtEthLinkOAMPortLinkEventConfIndex                                 Integer32,
   sispm1040582lrtEthLinkOAMPortLinkEventConfErrorFrameEventErrorWindow            Integer32,
   sispm1040582lrtEthLinkOAMPortLinkEventConfErrorFrameEventErrorThreshold         Integer32,
   sispm1040582lrtEthLinkOAMPortLinkEventConfSymbolPeriodErrorEventErrorWindow     Integer32,
   sispm1040582lrtEthLinkOAMPortLinkEventConfSymbolPeriodErrorEventErrorThreshold  Integer32,
   sispm1040582lrtEthLinkOAMPortLinkEventConfSecondsSummaryEventErrorWindow        Integer32,
   sispm1040582lrtEthLinkOAMPortLinkEventConfSecondsSummaryEventErrorThreshold     Integer32
}

sispm1040582lrtEthLinkOAMPortLinkEventConfIndex OBJECT-TYPE
   SYNTAX      Integer32
   MAX-ACCESS  not-accessible
   STATUS      current
   DESCRIPTION
       "Index"
   ::= { sispm1040582lrtEthLinkOAMPortLinkEventConfEntry 1 }

sispm1040582lrtEthLinkOAMPortLinkEventConfErrorFrameEventErrorWindow OBJECT-TYPE
   SYNTAX      Integer32
   MAX-ACCESS  read-write
   STATUS      current
   DESCRIPTION
       "The Errored Frame Event counts the number of errored frames detected during the specified period. 
	   Represents the window period in the order of 1 sec for the observation of various link events.
	   range: 1-60"
   ::= { sispm1040582lrtEthLinkOAMPortLinkEventConfEntry 2 }
   
sispm1040582lrtEthLinkOAMPortLinkEventConfErrorFrameEventErrorThreshold OBJECT-TYPE
   SYNTAX      Integer32
   MAX-ACCESS  read-write
   STATUS      current
   DESCRIPTION
       "The Errored Frame Event counts the number of errored frames detected during the specified period. 
	   Represents the threshold value for the window period for the appropriate Link event so as to notify the peer of this error.
	   range:0-0xffffffff"
   ::= { sispm1040582lrtEthLinkOAMPortLinkEventConfEntry 3 }
   
sispm1040582lrtEthLinkOAMPortLinkEventConfSymbolPeriodErrorEventErrorWindow OBJECT-TYPE
   SYNTAX      Integer32
   MAX-ACCESS  read-write
   STATUS      current
   DESCRIPTION
       "The Errored Symbol Period Event counts the number of symbol errors that occurred during the specified period.
	   Represents the window period in the order of 1 sec for the observation of various link events.
	   range: 1-60"
   ::= { sispm1040582lrtEthLinkOAMPortLinkEventConfEntry 4 }

sispm1040582lrtEthLinkOAMPortLinkEventConfSymbolPeriodErrorEventErrorThreshold OBJECT-TYPE
   SYNTAX      Integer32
   MAX-ACCESS  read-write
   STATUS      current
   DESCRIPTION
       "The Errored Symbol Period Event counts the number of symbol errors that occurred during the specified period.
	   Represents the threshold value for the window period for the appropriate Link event so as to notify the peer of this error.
	   range:0-0xffffffff"
   ::= { sispm1040582lrtEthLinkOAMPortLinkEventConfEntry 5 }

sispm1040582lrtEthLinkOAMPortLinkEventConfSecondsSummaryEventErrorWindow OBJECT-TYPE
   SYNTAX      Integer32
   MAX-ACCESS  read-write
   STATUS      current
   DESCRIPTION
       "The Errored Frame Seconds Summary Event TLV counts the number of errored frame seconds that occurred during the specified period. 
	   Represents the window period in the order of 1 sec for the observation of various link events.
	   range: 10-900"
   ::= { sispm1040582lrtEthLinkOAMPortLinkEventConfEntry 6 }   
   
sispm1040582lrtEthLinkOAMPortLinkEventConfSecondsSummaryEventErrorThreshold OBJECT-TYPE
   SYNTAX      Integer32
   MAX-ACCESS  read-write
   STATUS      current
   DESCRIPTION
       "The Errored Frame Seconds Summary Event TLV counts the number of errored frame seconds that occurred during the specified period. 
	   Represents the threshold value for the window period for the appropriate Link event so as to notify the peer of this error.
	   range:0-0xffff"
   ::= { sispm1040582lrtEthLinkOAMPortLinkEventConfEntry 7 } 




sispm1040582lrtEthLinkOAMPortDetailedStatisticsTable OBJECT-TYPE
   SYNTAX      SEQUENCE OF SISPM1040582LRTEthLinkOAMPortDetailedStatisticsEntry
   MAX-ACCESS  not-accessible
   STATUS      current
   DESCRIPTION
       "Eth Link OAM Port Detailed Statistics Table"
   ::= { sispm1040582lrtETHLINKOAM 4 }

sispm1040582lrtEthLinkOAMPortDetailedStatisticsEntry OBJECT-TYPE
   SYNTAX      SISPM1040582LRTEthLinkOAMPortDetailedStatisticsEntry
   MAX-ACCESS  not-accessible
   STATUS      current
   DESCRIPTION
       "Eth Link OAM Port Detailed Statistics Entry"
   INDEX    { sispm1040582lrtEthLinkOAMPortDetailedStatisticsIndex  }
   ::= { sispm1040582lrtEthLinkOAMPortDetailedStatisticsTable 1 }

SISPM1040582LRTEthLinkOAMPortDetailedStatisticsEntry ::= SEQUENCE {
   sispm1040582lrtEthLinkOAMPortDetailedStatisticsIndex                             Integer32,
   sispm1040582lrtEthLinkOAMPortDetailedStatisticsRxOAMInformationPDUs              Integer32,
   sispm1040582lrtEthLinkOAMPortDetailedStatisticsRxUniqueErrorEventNotification    Integer32,
   sispm1040582lrtEthLinkOAMPortDetailedStatisticsRxDuplicateErrorEventNotification Integer32,
   sispm1040582lrtEthLinkOAMPortDetailedStatisticsRxLoopbackControl                 Integer32,
   sispm1040582lrtEthLinkOAMPortDetailedStatisticsRxVariableRequest                 Integer32,
   sispm1040582lrtEthLinkOAMPortDetailedStatisticsRxVariableResponse                Integer32,
   sispm1040582lrtEthLinkOAMPortDetailedStatisticsRxOrgSpecificPDUs                 Integer32,
   sispm1040582lrtEthLinkOAMPortDetailedStatisticsRxUnsupportedCodes                Integer32,
   sispm1040582lrtEthLinkOAMPortDetailedStatisticsRxLinkFaultPDUs                   Integer32,
   sispm1040582lrtEthLinkOAMPortDetailedStatisticsRxDyingGasp                       Integer32,
   sispm1040582lrtEthLinkOAMPortDetailedStatisticsRxCriticalEventPDUs               Integer32,
   sispm1040582lrtEthLinkOAMPortDetailedStatisticsTxOAMInformationPDUs              Integer32,
   sispm1040582lrtEthLinkOAMPortDetailedStatisticsTxUniqueErrorEventNotification    Integer32,
   sispm1040582lrtEthLinkOAMPortDetailedStatisticsTxDuplicateErrorEventNotification Integer32,
   sispm1040582lrtEthLinkOAMPortDetailedStatisticsTxLoopbackControl                 Integer32,
   sispm1040582lrtEthLinkOAMPortDetailedStatisticsTxVariableRequest                 Integer32,
   sispm1040582lrtEthLinkOAMPortDetailedStatisticsTxVariableResponse                Integer32,
   sispm1040582lrtEthLinkOAMPortDetailedStatisticsTxOrgSpecificPDUs                 Integer32,
   sispm1040582lrtEthLinkOAMPortDetailedStatisticsTxUnsupportedCodes                Integer32,
   sispm1040582lrtEthLinkOAMPortDetailedStatisticsTxLinkFaultPDUs                   Integer32,
   sispm1040582lrtEthLinkOAMPortDetailedStatisticsTxDyingGasp                       Integer32,
   sispm1040582lrtEthLinkOAMPortDetailedStatisticsTxCriticalEventPDUs               Integer32,
   sispm1040582lrtEthLinkOAMPortDetailedStatisticsClear                             Integer32
}

sispm1040582lrtEthLinkOAMPortDetailedStatisticsIndex OBJECT-TYPE
   SYNTAX      Integer32
   MAX-ACCESS  not-accessible
   STATUS      current
   DESCRIPTION
       "Index"
   ::= { sispm1040582lrtEthLinkOAMPortDetailedStatisticsEntry 1 }

sispm1040582lrtEthLinkOAMPortDetailedStatisticsRxOAMInformationPDUs OBJECT-TYPE
   SYNTAX      Integer32
   MAX-ACCESS  read-only
   STATUS      current
   DESCRIPTION
       "The number of received and transmitted OAM Information PDU's. 
	   Discontinuities of this counter can occur at re-initialization of the management system."
   ::= { sispm1040582lrtEthLinkOAMPortDetailedStatisticsEntry 2 }
   
sispm1040582lrtEthLinkOAMPortDetailedStatisticsRxUniqueErrorEventNotification OBJECT-TYPE
   SYNTAX      Integer32
   MAX-ACCESS  read-only
   STATUS      current
   DESCRIPTION
       "A count of the number of unique Event OAMPDUs received and transmitted on this interface. 
	   Event Notifications may be sent in duplicate to increase the probability of successfully being received, 
	   given the possibility that a frame may be lost in transit. 
	   Duplicate Event Notification transmissions are counted by 
	   Duplicate Event Notification counters for Tx and Rx respectively. 
	   A unique Event Notification OAMPDU is indicated as an Event Notification OAMPDU with
	   a Sequence Number field that is distinct from the previously transmitted Event Notification OAMPDU Sequence Number."
   ::= { sispm1040582lrtEthLinkOAMPortDetailedStatisticsEntry 3 }
   
sispm1040582lrtEthLinkOAMPortDetailedStatisticsRxDuplicateErrorEventNotification OBJECT-TYPE
   SYNTAX      Integer32
   MAX-ACCESS  read-only
   STATUS      current
   DESCRIPTION
       "A count of the number of duplicate Event OAMPDUs received and transmitted on this interface. 
	   Event Notification OAMPDUs may be sent in duplicate to increase the probability of successfully being received, 
	   given the possibility that a frame may be lost in transit. 
	   A duplicate Event Notification OAMPDU is indicated as an Event Notification OAMPDU with
	   a Sequence Number field that is identical to the previously transmitted Event Notification OAMPDU Sequence Number."
   ::= { sispm1040582lrtEthLinkOAMPortDetailedStatisticsEntry 4 }
   
sispm1040582lrtEthLinkOAMPortDetailedStatisticsRxLoopbackControl OBJECT-TYPE
   SYNTAX      Integer32
   MAX-ACCESS  read-only
   STATUS      current
   DESCRIPTION
       "A count of the number of Loopback Control OAMPDUs received and transmitted on this interface."
   ::= { sispm1040582lrtEthLinkOAMPortDetailedStatisticsEntry 5 }
   
sispm1040582lrtEthLinkOAMPortDetailedStatisticsRxVariableRequest OBJECT-TYPE
   SYNTAX      Integer32
   MAX-ACCESS  read-only
   STATUS      current
   DESCRIPTION
       "A count of the number of Variable Request OAMPDUs received and transmitted on this interface."
   ::= { sispm1040582lrtEthLinkOAMPortDetailedStatisticsEntry 6 }
   
sispm1040582lrtEthLinkOAMPortDetailedStatisticsRxVariableResponse OBJECT-TYPE
   SYNTAX      Integer32
   MAX-ACCESS  read-only
   STATUS      current
   DESCRIPTION
       "A count of the number of Variable Response OAMPDUs received and transmitted on this interface."
   ::= { sispm1040582lrtEthLinkOAMPortDetailedStatisticsEntry 7 }
   
sispm1040582lrtEthLinkOAMPortDetailedStatisticsRxOrgSpecificPDUs OBJECT-TYPE
   SYNTAX      Integer32
   MAX-ACCESS  read-only
   STATUS      current
   DESCRIPTION
       "A count of the number of Organization Specific OAMPDUs transmitted on this interface."
   ::= { sispm1040582lrtEthLinkOAMPortDetailedStatisticsEntry 8 }
   
sispm1040582lrtEthLinkOAMPortDetailedStatisticsRxUnsupportedCodes OBJECT-TYPE
   SYNTAX      Integer32
   MAX-ACCESS  read-only
   STATUS      current
   DESCRIPTION
       "A count of the number of OAMPDUs transmitted on this interface with an unsupported op-code."
   ::= { sispm1040582lrtEthLinkOAMPortDetailedStatisticsEntry 9 }
   
sispm1040582lrtEthLinkOAMPortDetailedStatisticsRxLinkFaultPDUs OBJECT-TYPE
   SYNTAX      Integer32
   MAX-ACCESS  read-only
   STATUS      current
   DESCRIPTION
       "A count of the number of Link fault PDU's received and transmitted on this interface."
   ::= { sispm1040582lrtEthLinkOAMPortDetailedStatisticsEntry 10 }
   
sispm1040582lrtEthLinkOAMPortDetailedStatisticsRxDyingGasp OBJECT-TYPE
   SYNTAX      Integer32
   MAX-ACCESS  read-only
   STATUS      current
   DESCRIPTION
       "A count of the number of Dying Gasp events received and transmitted on this interface."
   ::= { sispm1040582lrtEthLinkOAMPortDetailedStatisticsEntry 11 }
   
sispm1040582lrtEthLinkOAMPortDetailedStatisticsRxCriticalEventPDUs OBJECT-TYPE
   SYNTAX      Integer32
   MAX-ACCESS  read-only
   STATUS      current
   DESCRIPTION
       "A count of the number of Critical event PDU's received and transmitted on this interface."
   ::= { sispm1040582lrtEthLinkOAMPortDetailedStatisticsEntry 12 }
   
sispm1040582lrtEthLinkOAMPortDetailedStatisticsTxOAMInformationPDUs OBJECT-TYPE
   SYNTAX      Integer32
   MAX-ACCESS  read-only
   STATUS      current
   DESCRIPTION
       "The number of received and transmitted OAM Information PDU's. 
	   Discontinuities of this counter can occur at re-initialization of the management system."
   ::= { sispm1040582lrtEthLinkOAMPortDetailedStatisticsEntry 13 }
   
sispm1040582lrtEthLinkOAMPortDetailedStatisticsTxUniqueErrorEventNotification OBJECT-TYPE
   SYNTAX      Integer32
   MAX-ACCESS  read-only
   STATUS      current
   DESCRIPTION
       "A count of the number of unique Event OAMPDUs received and transmitted on this interface. 
	   Event Notifications may be sent in duplicate to increase the probability of successfully being received, 
	   given the possibility that a frame may be lost in transit. 
	   Duplicate Event Notification transmissions are counted by 
	   Duplicate Event Notification counters for Tx and Rx respectively. 
	   A unique Event Notification OAMPDU is indicated as an Event Notification OAMPDU with
	   a Sequence Number field that is distinct from the previously transmitted Event Notification OAMPDU Sequence Number."
   ::= { sispm1040582lrtEthLinkOAMPortDetailedStatisticsEntry 14 }
   
sispm1040582lrtEthLinkOAMPortDetailedStatisticsTxDuplicateErrorEventNotification OBJECT-TYPE
   SYNTAX      Integer32
   MAX-ACCESS  read-only
   STATUS      current
   DESCRIPTION
       "A count of the number of duplicate Event OAMPDUs received and transmitted on this interface. 
	   Event Notification OAMPDUs may be sent in duplicate to increase the probability of successfully being received, 
	   given the possibility that a frame may be lost in transit. 
	   A duplicate Event Notification OAMPDU is indicated as an Event Notification OAMPDU with
	   a Sequence Number field that is identical to the previously transmitted Event Notification OAMPDU Sequence Number."
   ::= { sispm1040582lrtEthLinkOAMPortDetailedStatisticsEntry 15 }
   
sispm1040582lrtEthLinkOAMPortDetailedStatisticsTxLoopbackControl OBJECT-TYPE
   SYNTAX      Integer32
   MAX-ACCESS  read-only
   STATUS      current
   DESCRIPTION
       "A count of the number of Loopback Control OAMPDUs received and transmitted on this interface."
   ::= { sispm1040582lrtEthLinkOAMPortDetailedStatisticsEntry 16 }
   
sispm1040582lrtEthLinkOAMPortDetailedStatisticsTxVariableRequest OBJECT-TYPE
   SYNTAX      Integer32
   MAX-ACCESS  read-only
   STATUS      current
   DESCRIPTION
       "A count of the number of Variable Request OAMPDUs received and transmitted on this interface."
   ::= { sispm1040582lrtEthLinkOAMPortDetailedStatisticsEntry 17 }
   
sispm1040582lrtEthLinkOAMPortDetailedStatisticsTxVariableResponse OBJECT-TYPE
   SYNTAX      Integer32
   MAX-ACCESS  read-only
   STATUS      current
   DESCRIPTION
       "A count of the number of Variable Response OAMPDUs received and transmitted on this interface."
   ::= { sispm1040582lrtEthLinkOAMPortDetailedStatisticsEntry 18 }
   
sispm1040582lrtEthLinkOAMPortDetailedStatisticsTxOrgSpecificPDUs OBJECT-TYPE
   SYNTAX      Integer32
   MAX-ACCESS  read-only
   STATUS      current
   DESCRIPTION
       "A count of the number of Organization Specific OAMPDUs transmitted on this interface."
   ::= { sispm1040582lrtEthLinkOAMPortDetailedStatisticsEntry 19 }
   
sispm1040582lrtEthLinkOAMPortDetailedStatisticsTxUnsupportedCodes OBJECT-TYPE
   SYNTAX      Integer32
   MAX-ACCESS  read-only
   STATUS      current
   DESCRIPTION
       "A count of the number of OAMPDUs transmitted on this interface with an unsupported op-code."
   ::= { sispm1040582lrtEthLinkOAMPortDetailedStatisticsEntry 20 }
   
sispm1040582lrtEthLinkOAMPortDetailedStatisticsTxLinkFaultPDUs OBJECT-TYPE
   SYNTAX      Integer32
   MAX-ACCESS  read-only
   STATUS      current
   DESCRIPTION
       "A count of the number of Link fault PDU's received and transmitted on this interface."
   ::= { sispm1040582lrtEthLinkOAMPortDetailedStatisticsEntry 21 }
   
sispm1040582lrtEthLinkOAMPortDetailedStatisticsTxDyingGasp OBJECT-TYPE
   SYNTAX      Integer32
   MAX-ACCESS  read-only
   STATUS      current
   DESCRIPTION
       "A count of the number of Dying Gasp events received and transmitted on this interface."
   ::= { sispm1040582lrtEthLinkOAMPortDetailedStatisticsEntry 22 }
   
sispm1040582lrtEthLinkOAMPortDetailedStatisticsTxCriticalEventPDUs OBJECT-TYPE
   SYNTAX      Integer32
   MAX-ACCESS  read-only
   STATUS      current
   DESCRIPTION
       "A count of the number of Critical event PDU's received and transmitted on this interface."
   ::= { sispm1040582lrtEthLinkOAMPortDetailedStatisticsEntry 23 }
   
sispm1040582lrtEthLinkOAMPortDetailedStatisticsClear OBJECT-TYPE
   SYNTAX      Integer32
   MAX-ACCESS  read-write
   STATUS      current
   DESCRIPTION
       "Clears the counters for the selected port."
   ::= { sispm1040582lrtEthLinkOAMPortDetailedStatisticsEntry 24 }
   
   
sispm1040582lrtEthLinkOAMPortEventDetailedStatisticsTable OBJECT-TYPE
   SYNTAX      SEQUENCE OF SISPM1040582LRTEthLinkOAMPortEventDetailedStatisticsEntry
   MAX-ACCESS  not-accessible
   STATUS      current
   DESCRIPTION
       "Eth Link OAM Port Event Detailed Statistics Table"
   ::= { sispm1040582lrtETHLINKOAM 5 }

sispm1040582lrtEthLinkOAMPortEventDetailedStatisticsEntry OBJECT-TYPE
   SYNTAX      SISPM1040582LRTEthLinkOAMPortEventDetailedStatisticsEntry
   MAX-ACCESS  not-accessible
   STATUS      current
   DESCRIPTION
       "Eth Link OAM Port Event Detailed Statistics Entry"
   INDEX    { sispm1040582lrtEthLinkOAMPortEventDetailedStatisticsIndex  }
   ::= { sispm1040582lrtEthLinkOAMPortEventDetailedStatisticsTable 1 }

SISPM1040582LRTEthLinkOAMPortEventDetailedStatisticsEntry ::= SEQUENCE {
   sispm1040582lrtEthLinkOAMPortEventDetailedStatisticsIndex                                  Integer32,
   sispm1040582lrtEthLinkOAMPortEventDetailedStatisticsLocalSequenceNumber                    Integer32,
   sispm1040582lrtEthLinkOAMPortEventDetailedStatisticsLocalFrameErrorEventTimestamp          Integer32,
   sispm1040582lrtEthLinkOAMPortEventDetailedStatisticsLocalFrameErrorEventWindow             Integer32,
   sispm1040582lrtEthLinkOAMPortEventDetailedStatisticsLocalFrameErrorEventThreshold          Integer32,
   sispm1040582lrtEthLinkOAMPortEventDetailedStatisticsLocalFrameErrors                       Integer32,
   sispm1040582lrtEthLinkOAMPortEventDetailedStatisticsLocalTotalFrameErrors                  Counter64,
   sispm1040582lrtEthLinkOAMPortEventDetailedStatisticsLocalTotalFrameErrorEvents             Integer32,
   sispm1040582lrtEthLinkOAMPortEventDetailedStatisticsLocalFramePeriodErrorEventTimestamp    Integer32,
   sispm1040582lrtEthLinkOAMPortEventDetailedStatisticsLocalFramePeriodErrorEventWindow       Integer32,
   sispm1040582lrtEthLinkOAMPortEventDetailedStatisticsLocalFramePeriodErrorEventThreshold    Integer32,
   sispm1040582lrtEthLinkOAMPortEventDetailedStatisticsLocalFramePeriodErrors                 Integer32,
   sispm1040582lrtEthLinkOAMPortEventDetailedStatisticsLocalTotalFramePeriodErrors            Counter64,
   sispm1040582lrtEthLinkOAMPortEventDetailedStatisticsLocalTotalFramePeriodErrorEvents       Integer32,
   sispm1040582lrtEthLinkOAMPortEventDetailedStatisticsLocalSymbolPeriodErrorEventTimestamp   Integer32,
   sispm1040582lrtEthLinkOAMPortEventDetailedStatisticsLocalSymbolPeriodErrorEventWindow      Counter64,
   sispm1040582lrtEthLinkOAMPortEventDetailedStatisticsLocalSymbolPeriodErrorEventThreshold   Counter64,
   sispm1040582lrtEthLinkOAMPortEventDetailedStatisticsLocalSymbolPeriodErrors                Counter64,
   sispm1040582lrtEthLinkOAMPortEventDetailedStatisticsLocalSymbolFramePeriodErrors           Counter64,
   sispm1040582lrtEthLinkOAMPortEventDetailedStatisticsLocalSymbolFramePeriodErrorEvents      Integer32,
   sispm1040582lrtEthLinkOAMPortEventDetailedStatisticsLocalEventSecondsSummaryTimeStamp      Integer32,
   sispm1040582lrtEthLinkOAMPortEventDetailedStatisticsLocalEventSecondsSummaryWindow         Integer32,
   sispm1040582lrtEthLinkOAMPortEventDetailedStatisticsLocalEventSecondsSummaryThreshold      Integer32,
   sispm1040582lrtEthLinkOAMPortEventDetailedStatisticsLocalEventSecondsSummaryEvents         Integer32,
   sispm1040582lrtEthLinkOAMPortEventDetailedStatisticsLocalEventSecondsSummaryErrorTotal     Integer32,
   sispm1040582lrtEthLinkOAMPortEventDetailedStatisticsLocalEventSecondsSummaryEventTotal     Integer32,
   sispm1040582lrtEthLinkOAMPortEventDetailedStatisticsRemoteFrameErrorEventTimestamp         Integer32,
   sispm1040582lrtEthLinkOAMPortEventDetailedStatisticsRemoteFrameErrorEventWindow            Integer32,
   sispm1040582lrtEthLinkOAMPortEventDetailedStatisticsRemoteFrameErrorEventThreshold         Integer32,
   sispm1040582lrtEthLinkOAMPortEventDetailedStatisticsRemoteFrameErrors                      Integer32,
   sispm1040582lrtEthLinkOAMPortEventDetailedStatisticsRemoteTotalFrameErrors                 Counter64,
   sispm1040582lrtEthLinkOAMPortEventDetailedStatisticsRemoteTotalFrameErrorEvents            Integer32,
   sispm1040582lrtEthLinkOAMPortEventDetailedStatisticsRemoteFramePeriodErrorEventTimestamp   Integer32,
   sispm1040582lrtEthLinkOAMPortEventDetailedStatisticsRemoteFramePeriodErrorEventWindow      Integer32,
   sispm1040582lrtEthLinkOAMPortEventDetailedStatisticsRemoteFramePeriodErrorEventThreshold   Integer32,
   sispm1040582lrtEthLinkOAMPortEventDetailedStatisticsRemoteFramePeriodErrors                Integer32,
   sispm1040582lrtEthLinkOAMPortEventDetailedStatisticsRemoteTotalFramePeriodErrors           Counter64,
   sispm1040582lrtEthLinkOAMPortEventDetailedStatisticsRemoteTotalFramePeriodErrorEvents      Integer32,
   sispm1040582lrtEthLinkOAMPortEventDetailedStatisticsRemoteSymbolPeriodErrorEventTimestamp  Integer32,
   sispm1040582lrtEthLinkOAMPortEventDetailedStatisticsRemoteSymbolPeriodErrorEventWindow     Counter64,
   sispm1040582lrtEthLinkOAMPortEventDetailedStatisticsRemoteSymbolPeriodErrorEventThreshold  Counter64,
   sispm1040582lrtEthLinkOAMPortEventDetailedStatisticsRemoteSymbolPeriodErrors               Counter64,
   sispm1040582lrtEthLinkOAMPortEventDetailedStatisticsRemoteSymbolFramePeriodErrors          Counter64,
   sispm1040582lrtEthLinkOAMPortEventDetailedStatisticsRemoteSymbolFramePeriodErrorEvents     Integer32,
   sispm1040582lrtEthLinkOAMPortEventDetailedStatisticsRemoteEventSecondsSummaryTimeStamp     Integer32,
   sispm1040582lrtEthLinkOAMPortEventDetailedStatisticsRemoteEventSecondsSummaryWindow        Integer32,
   sispm1040582lrtEthLinkOAMPortEventDetailedStatisticsRemoteEventSecondsSummaryThreshold     Integer32,   
   sispm1040582lrtEthLinkOAMPortEventDetailedStatisticsRemoteEventSecondsSummaryEvents        Integer32,
   sispm1040582lrtEthLinkOAMPortEventDetailedStatisticsRemoteEventSecondsSummaryErrorTotal    Integer32,
   sispm1040582lrtEthLinkOAMPortEventDetailedStatisticsRemoteEventSecondsSummaryEventTotal    Integer32   
}

sispm1040582lrtEthLinkOAMPortEventDetailedStatisticsIndex OBJECT-TYPE
   SYNTAX      Integer32
   MAX-ACCESS  not-accessible
   STATUS      current
   DESCRIPTION
       "Index"
   ::= { sispm1040582lrtEthLinkOAMPortEventDetailedStatisticsEntry 1 }

sispm1040582lrtEthLinkOAMPortEventDetailedStatisticsLocalSequenceNumber OBJECT-TYPE
   SYNTAX      Integer32
   MAX-ACCESS  read-only
   STATUS      current
   DESCRIPTION
       "This two-octet field indicates the total number of events occurred at the remote end."   
   ::= { sispm1040582lrtEthLinkOAMPortEventDetailedStatisticsEntry 2 }
   
sispm1040582lrtEthLinkOAMPortEventDetailedStatisticsLocalFrameErrorEventTimestamp OBJECT-TYPE
   SYNTAX      Integer32
   MAX-ACCESS  read-only
   STATUS      current
   DESCRIPTION
       "This two-octet field indicates the time reference when the event was generated, in terms of 100 ms intervals."   
   ::= { sispm1040582lrtEthLinkOAMPortEventDetailedStatisticsEntry 3 }

sispm1040582lrtEthLinkOAMPortEventDetailedStatisticsLocalFrameErrorEventWindow OBJECT-TYPE
   SYNTAX      Integer32
   MAX-ACCESS  read-only
   STATUS      current
   DESCRIPTION
       "This two-octet field indicates the duration of the period in terms of 100 ms intervals. 1) 
	   The default value is one second. 2) The lower bound is one second. 3) 
	   The upper bound is one minute."   
   ::= { sispm1040582lrtEthLinkOAMPortEventDetailedStatisticsEntry 4 }

sispm1040582lrtEthLinkOAMPortEventDetailedStatisticsLocalFrameErrorEventThreshold OBJECT-TYPE
   SYNTAX      Integer32
   MAX-ACCESS  read-only
   STATUS      current
   DESCRIPTION
       "This four-octet field indicates the number of detected errored frames in the period is required
	   to be equal to or greater than in order for the event to be generated. 1) 
	   The default value is one frame error. 2) 
	   The lower bound is zero frame errors. 3) 
	   The upper bound is unspecified."   
   ::= { sispm1040582lrtEthLinkOAMPortEventDetailedStatisticsEntry 5 }

sispm1040582lrtEthLinkOAMPortEventDetailedStatisticsLocalFrameErrors OBJECT-TYPE
   SYNTAX      Integer32
   MAX-ACCESS  read-only
   STATUS      current
   DESCRIPTION
       "This four-octet field indicates the number of detected errored frames in the period."   
   ::= { sispm1040582lrtEthLinkOAMPortEventDetailedStatisticsEntry 6 }

sispm1040582lrtEthLinkOAMPortEventDetailedStatisticsLocalTotalFrameErrors OBJECT-TYPE
   SYNTAX      Counter64
   MAX-ACCESS  read-only
   STATUS      current
   DESCRIPTION
       "This eight-octet field indicates the sum of errored frames that have been detected since the OAM sublayer was reset."   
   ::= { sispm1040582lrtEthLinkOAMPortEventDetailedStatisticsEntry 7 }

sispm1040582lrtEthLinkOAMPortEventDetailedStatisticsLocalTotalFrameErrorEvents OBJECT-TYPE
   SYNTAX      Integer32
   MAX-ACCESS  read-only
   STATUS      current
   DESCRIPTION
       "This four-octet field indicates the number of Errored Frame Event TLVs that 
	   have been generated since the OAM sublayer was reset."   
   ::= { sispm1040582lrtEthLinkOAMPortEventDetailedStatisticsEntry 8 }

sispm1040582lrtEthLinkOAMPortEventDetailedStatisticsLocalFramePeriodErrorEventTimestamp OBJECT-TYPE
   SYNTAX      Integer32
   MAX-ACCESS  read-only
   STATUS      current
   DESCRIPTION
       "This two-octet field indicates the time reference when the event was generated, in terms of 100 ms intervals."   
   ::= { sispm1040582lrtEthLinkOAMPortEventDetailedStatisticsEntry 9 }

sispm1040582lrtEthLinkOAMPortEventDetailedStatisticsLocalFramePeriodErrorEventWindow OBJECT-TYPE
   SYNTAX      Integer32
   MAX-ACCESS  read-only
   STATUS      current
   DESCRIPTION
       "This four-octet field indicates the duration of period in terms of frames."   
   ::= { sispm1040582lrtEthLinkOAMPortEventDetailedStatisticsEntry 10 }

sispm1040582lrtEthLinkOAMPortEventDetailedStatisticsLocalFramePeriodErrorEventThreshold OBJECT-TYPE
   SYNTAX      Integer32
   MAX-ACCESS  read-only
   STATUS      current
   DESCRIPTION
       "This four-octet field indicates the number of errored frames in the period is required
	   to be equal to or greater than in order for the event to be generated."   
   ::= { sispm1040582lrtEthLinkOAMPortEventDetailedStatisticsEntry 11 }

sispm1040582lrtEthLinkOAMPortEventDetailedStatisticsLocalFramePeriodErrors OBJECT-TYPE
   SYNTAX      Integer32
   MAX-ACCESS  read-only
   STATUS      current
   DESCRIPTION
       "This four-octet field indicates the number of frame errors in the period."   
   ::= { sispm1040582lrtEthLinkOAMPortEventDetailedStatisticsEntry 12 }

sispm1040582lrtEthLinkOAMPortEventDetailedStatisticsLocalTotalFramePeriodErrors OBJECT-TYPE
   SYNTAX      Counter64
   MAX-ACCESS  read-only
   STATUS      current
   DESCRIPTION
       "This eight-octet field indicates the sum of frame errors that have been detected since the OAM sublayer was reset."   
   ::= { sispm1040582lrtEthLinkOAMPortEventDetailedStatisticsEntry 13 }

sispm1040582lrtEthLinkOAMPortEventDetailedStatisticsLocalTotalFramePeriodErrorEvents OBJECT-TYPE
   SYNTAX      Integer32
   MAX-ACCESS  read-only
   STATUS      current
   DESCRIPTION
       "This four-octet field indicates the number of Errored Frame Period Event TLVs 
	   that have been generated since the OAM sublayer was reset."   
   ::= { sispm1040582lrtEthLinkOAMPortEventDetailedStatisticsEntry 14 }

sispm1040582lrtEthLinkOAMPortEventDetailedStatisticsLocalSymbolPeriodErrorEventTimestamp OBJECT-TYPE
   SYNTAX      Integer32
   MAX-ACCESS  read-only
   STATUS      current
   DESCRIPTION
       "This two-octet field indicates the time reference when the event was generated, in terms of 100 ms intervals."   
   ::= { sispm1040582lrtEthLinkOAMPortEventDetailedStatisticsEntry 15 }

sispm1040582lrtEthLinkOAMPortEventDetailedStatisticsLocalSymbolPeriodErrorEventWindow OBJECT-TYPE
   SYNTAX      Counter64
   MAX-ACCESS  read-only
   STATUS      current
   DESCRIPTION
       "This eight-octet field indicates the number of symbols in the period."   
   ::= { sispm1040582lrtEthLinkOAMPortEventDetailedStatisticsEntry 16 }

sispm1040582lrtEthLinkOAMPortEventDetailedStatisticsLocalSymbolPeriodErrorEventThreshold OBJECT-TYPE
   SYNTAX      Counter64
   MAX-ACCESS  read-only
   STATUS      current
   DESCRIPTION
       "This eight-octet field indicates the number of errored symbols in the period is required to
	   be equal to or greater than in order for the event to be generated."   
   ::= { sispm1040582lrtEthLinkOAMPortEventDetailedStatisticsEntry 17 }

sispm1040582lrtEthLinkOAMPortEventDetailedStatisticsLocalSymbolPeriodErrors OBJECT-TYPE
   SYNTAX      Counter64
   MAX-ACCESS  read-only
   STATUS      current
   DESCRIPTION
       "This eight-octet field indicates the number of symbol errors in the period."   
   ::= { sispm1040582lrtEthLinkOAMPortEventDetailedStatisticsEntry 18 }

sispm1040582lrtEthLinkOAMPortEventDetailedStatisticsLocalSymbolFramePeriodErrors OBJECT-TYPE
   SYNTAX      Counter64
   MAX-ACCESS  read-only
   STATUS      current
   DESCRIPTION
       "This eight-octet field indicates the sum of symbol errors since the OAM sublayer was reset."   
   ::= { sispm1040582lrtEthLinkOAMPortEventDetailedStatisticsEntry 19 }

sispm1040582lrtEthLinkOAMPortEventDetailedStatisticsLocalSymbolFramePeriodErrorEvents OBJECT-TYPE
   SYNTAX      Integer32
   MAX-ACCESS  read-only
   STATUS      current
   DESCRIPTION
       "This four-octet field indicates the number of Errored Symbol Period Event TLVs that
	   have been generated since the OAM sublayer was reset."   
   ::= { sispm1040582lrtEthLinkOAMPortEventDetailedStatisticsEntry 20 }

sispm1040582lrtEthLinkOAMPortEventDetailedStatisticsLocalEventSecondsSummaryTimeStamp OBJECT-TYPE
   SYNTAX      Integer32
   MAX-ACCESS  read-only
   STATUS      current
   DESCRIPTION
       "This two-octet field indicates the time reference when the event was generated, 
	   in terms of 100 ms intervals, encoded as a 16-bit unsigned integer."   
   ::= { sispm1040582lrtEthLinkOAMPortEventDetailedStatisticsEntry 21 }

sispm1040582lrtEthLinkOAMPortEventDetailedStatisticsLocalEventSecondsSummaryWindow OBJECT-TYPE
   SYNTAX      Integer32
   MAX-ACCESS  read-only
   STATUS      current
   DESCRIPTION
       "This two-octet field indicates the duration of the period in terms of 100 ms intervals, encoded as a 16-bit unsigned integer."   
   ::= { sispm1040582lrtEthLinkOAMPortEventDetailedStatisticsEntry 22 }

sispm1040582lrtEthLinkOAMPortEventDetailedStatisticsLocalEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."   
   ::= { sispm1040582lrtEthLinkOAMPortEventDetailedStatisticsEntry 23 }

sispm1040582lrtEthLinkOAMPortEventDetailedStatisticsLocalEventSecondsSummaryEvents OBJECT-TYPE
   SYNTAX      Integer32
   MAX-ACCESS  read-only
   STATUS      current
   DESCRIPTION
       "This two-octet field indicates the number of errored frame seconds in the period, encoded as a 16-bit unsigned integer."   
   ::= { sispm1040582lrtEthLinkOAMPortEventDetailedStatisticsEntry 24 }

sispm1040582lrtEthLinkOAMPortEventDetailedStatisticsLocalEventSecondsSummaryErrorTotal OBJECT-TYPE
   SYNTAX      Integer32
   MAX-ACCESS  read-only
   STATUS      current
   DESCRIPTION
       "This four-octet field indicates the sum of errored frame seconds that have been detected since the OAM sublayer was reset."   
   ::= { sispm1040582lrtEthLinkOAMPortEventDetailedStatisticsEntry 25 }

sispm1040582lrtEthLinkOAMPortEventDetailedStatisticsLocalEventSecondsSummaryEventTotal OBJECT-TYPE
   SYNTAX      Integer32
   MAX-ACCESS  read-only
   STATUS      current
   DESCRIPTION
       "This four-octet field indicates the number of Errored Frame Seconds Summary Event TLVs that 
	   have been generated since the OAM sublayer was reset, encoded as a 32bit unsigned integer."   
   ::= { sispm1040582lrtEthLinkOAMPortEventDetailedStatisticsEntry 26 }

sispm1040582lrtEthLinkOAMPortEventDetailedStatisticsRemoteFrameErrorEventTimestamp OBJECT-TYPE
   SYNTAX      Integer32
   MAX-ACCESS  read-only
   STATUS      current
   DESCRIPTION
       "This two-octet field indicates the time reference when the event was generated, in terms of 100 ms intervals."   
   ::= { sispm1040582lrtEthLinkOAMPortEventDetailedStatisticsEntry 27 }
   
sispm1040582lrtEthLinkOAMPortEventDetailedStatisticsRemoteFrameErrorEventWindow OBJECT-TYPE
   SYNTAX      Integer32
   MAX-ACCESS  read-only
   STATUS      current
   DESCRIPTION
       "This two-octet field indicates the duration of the period in terms of 100 ms intervals. 1) 
	   The default value is one second. 2) The lower bound is one second. 3) 
	   The upper bound is one minute."   
   ::= { sispm1040582lrtEthLinkOAMPortEventDetailedStatisticsEntry 28 }   
   
sispm1040582lrtEthLinkOAMPortEventDetailedStatisticsRemoteFrameErrorEventThreshold OBJECT-TYPE
   SYNTAX      Integer32
   MAX-ACCESS  read-only
   STATUS      current
   DESCRIPTION
       "This four-octet field indicates the number of detected errored frames in the period is required
	   to be equal to or greater than in order for the event to be generated. 1) 
	   The default value is one frame error. 2) 
	   The lower bound is zero frame errors. 3) 
	   The upper bound is unspecified."   
   ::= { sispm1040582lrtEthLinkOAMPortEventDetailedStatisticsEntry 29 }

sispm1040582lrtEthLinkOAMPortEventDetailedStatisticsRemoteFrameErrors OBJECT-TYPE
   SYNTAX      Integer32
   MAX-ACCESS  read-only
   STATUS      current
   DESCRIPTION
       "This four-octet field indicates the number of detected errored frames in the period."   
   ::= { sispm1040582lrtEthLinkOAMPortEventDetailedStatisticsEntry 30 }
   
sispm1040582lrtEthLinkOAMPortEventDetailedStatisticsRemoteTotalFrameErrors OBJECT-TYPE
   SYNTAX      Counter64
   MAX-ACCESS  read-only
   STATUS      current
   DESCRIPTION
       "This eight-octet field indicates the sum of errored frames that have been detected since the OAM sublayer was reset."   
   ::= { sispm1040582lrtEthLinkOAMPortEventDetailedStatisticsEntry 31 }
   
sispm1040582lrtEthLinkOAMPortEventDetailedStatisticsRemoteTotalFrameErrorEvents OBJECT-TYPE
   SYNTAX      Integer32
   MAX-ACCESS  read-only
   STATUS      current
   DESCRIPTION
       "This four-octet field indicates the number of Errored Frame Event TLVs that 
	   have been generated since the OAM sublayer was reset."   
   ::= { sispm1040582lrtEthLinkOAMPortEventDetailedStatisticsEntry 32 }
   
sispm1040582lrtEthLinkOAMPortEventDetailedStatisticsRemoteFramePeriodErrorEventTimestamp OBJECT-TYPE
   SYNTAX      Integer32
   MAX-ACCESS  read-only
   STATUS      current
   DESCRIPTION
       "This two-octet field indicates the time reference when the event was generated, in terms of 100 ms intervals."   
   ::= { sispm1040582lrtEthLinkOAMPortEventDetailedStatisticsEntry 33 }
   
sispm1040582lrtEthLinkOAMPortEventDetailedStatisticsRemoteFramePeriodErrorEventWindow OBJECT-TYPE
   SYNTAX      Integer32
   MAX-ACCESS  read-only
   STATUS      current
   DESCRIPTION
       "This four-octet field indicates the duration of period in terms of frames."   
   ::= { sispm1040582lrtEthLinkOAMPortEventDetailedStatisticsEntry 34 }
   
sispm1040582lrtEthLinkOAMPortEventDetailedStatisticsRemoteFramePeriodErrorEventThreshold OBJECT-TYPE
   SYNTAX      Integer32
   MAX-ACCESS  read-only
   STATUS      current
   DESCRIPTION
       "This four-octet field indicates the number of errored frames in the period is required
	   to be equal to or greater than in order for the event to be generated."   
   ::= { sispm1040582lrtEthLinkOAMPortEventDetailedStatisticsEntry 35 }
   
sispm1040582lrtEthLinkOAMPortEventDetailedStatisticsRemoteFramePeriodErrors OBJECT-TYPE
   SYNTAX      Integer32
   MAX-ACCESS  read-only
   STATUS      current
   DESCRIPTION
       "This four-octet field indicates the number of frame errors in the period."   
   ::= { sispm1040582lrtEthLinkOAMPortEventDetailedStatisticsEntry 36 }
   
sispm1040582lrtEthLinkOAMPortEventDetailedStatisticsRemoteTotalFramePeriodErrors OBJECT-TYPE
   SYNTAX      Counter64
   MAX-ACCESS  read-only
   STATUS      current
   DESCRIPTION
       "This eight-octet field indicates the sum of frame errors that have been detected since the OAM sublayer was reset."   
   ::= { sispm1040582lrtEthLinkOAMPortEventDetailedStatisticsEntry 37 }
   
sispm1040582lrtEthLinkOAMPortEventDetailedStatisticsRemoteTotalFramePeriodErrorEvents OBJECT-TYPE
   SYNTAX      Integer32
   MAX-ACCESS  read-only
   STATUS      current
   DESCRIPTION
       "This four-octet field indicates the number of Errored Frame Period Event TLVs 
	   that have been generated since the OAM sublayer was reset."   
   ::= { sispm1040582lrtEthLinkOAMPortEventDetailedStatisticsEntry 38 }
   
sispm1040582lrtEthLinkOAMPortEventDetailedStatisticsRemoteSymbolPeriodErrorEventTimestamp OBJECT-TYPE
   SYNTAX      Integer32
   MAX-ACCESS  read-only
   STATUS      current
   DESCRIPTION
       "This two-octet field indicates the time reference when the event was generated, in terms of 100 ms intervals."   
   ::= { sispm1040582lrtEthLinkOAMPortEventDetailedStatisticsEntry 39 }
   
sispm1040582lrtEthLinkOAMPortEventDetailedStatisticsRemoteSymbolPeriodErrorEventWindow OBJECT-TYPE
   SYNTAX      Counter64
   MAX-ACCESS  read-only
   STATUS      current
   DESCRIPTION
       "This eight-octet field indicates the number of symbols in the period."   
   ::= { sispm1040582lrtEthLinkOAMPortEventDetailedStatisticsEntry 40 }
   
sispm1040582lrtEthLinkOAMPortEventDetailedStatisticsRemoteSymbolPeriodErrorEventThreshold OBJECT-TYPE
   SYNTAX      Counter64
   MAX-ACCESS  read-only
   STATUS      current
   DESCRIPTION
       "This eight-octet field indicates the number of errored symbols in the period is required to
	   be equal to or greater than in order for the event to be generated."   
   ::= { sispm1040582lrtEthLinkOAMPortEventDetailedStatisticsEntry 41 }
   
sispm1040582lrtEthLinkOAMPortEventDetailedStatisticsRemoteSymbolPeriodErrors OBJECT-TYPE
   SYNTAX      Counter64
   MAX-ACCESS  read-only
   STATUS      current
   DESCRIPTION
       "This eight-octet field indicates the number of symbol errors in the period."   
   ::= { sispm1040582lrtEthLinkOAMPortEventDetailedStatisticsEntry 42 }
   
sispm1040582lrtEthLinkOAMPortEventDetailedStatisticsRemoteSymbolFramePeriodErrors OBJECT-TYPE
   SYNTAX      Counter64
   MAX-ACCESS  read-only
   STATUS      current
   DESCRIPTION
       "This eight-octet field indicates the sum of symbol errors since the OAM sublayer was reset."   
   ::= { sispm1040582lrtEthLinkOAMPortEventDetailedStatisticsEntry 43 }
   
sispm1040582lrtEthLinkOAMPortEventDetailedStatisticsRemoteSymbolFramePeriodErrorEvents OBJECT-TYPE
   SYNTAX      Integer32
   MAX-ACCESS  read-only
   STATUS      current
   DESCRIPTION
       "This four-octet field indicates the number of Errored Symbol Period Event TLVs that
	   have been generated since the OAM sublayer was reset."   
   ::= { sispm1040582lrtEthLinkOAMPortEventDetailedStatisticsEntry 44 }
   
sispm1040582lrtEthLinkOAMPortEventDetailedStatisticsRemoteEventSecondsSummaryTimeStamp OBJECT-TYPE
   SYNTAX      Integer32
   MAX-ACCESS  read-only
   STATUS      current
   DESCRIPTION
       "This two-octet field indicates the time reference when the event was generated, 
	   in terms of 100 ms intervals, encoded as a 16-bit unsigned integer."   
   ::= { sispm1040582lrtEthLinkOAMPortEventDetailedStatisticsEntry 45 }
   
sispm1040582lrtEthLinkOAMPortEventDetailedStatisticsRemoteEventSecondsSummaryWindow OBJECT-TYPE
   SYNTAX      Integer32
   MAX-ACCESS  read-only
   STATUS      current
   DESCRIPTION
       "This two-octet field indicates the duration of the period in terms of 100 ms intervals, encoded as a 16-bit unsigned integer."   
   ::= { sispm1040582lrtEthLinkOAMPortEventDetailedStatisticsEntry 46 }
   
sispm1040582lrtEthLinkOAMPortEventDetailedStatisticsRemoteEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."   
   ::= { sispm1040582lrtEthLinkOAMPortEventDetailedStatisticsEntry 47 }
   
sispm1040582lrtEthLinkOAMPortEventDetailedStatisticsRemoteEventSecondsSummaryEvents OBJECT-TYPE
   SYNTAX      Integer32
   MAX-ACCESS  read-only
   STATUS      current
   DESCRIPTION
       "This two-octet field indicates the number of errored frame seconds in the period, encoded as a 16-bit unsigned integer."   
   ::= { sispm1040582lrtEthLinkOAMPortEventDetailedStatisticsEntry 48 }
   
sispm1040582lrtEthLinkOAMPortEventDetailedStatisticsRemoteEventSecondsSummaryErrorTotal OBJECT-TYPE
   SYNTAX      Integer32
   MAX-ACCESS  read-only
   STATUS      current
   DESCRIPTION
       "This four-octet field indicates the sum of errored frame seconds that have been detected since the OAM sublayer was reset."   
   ::= { sispm1040582lrtEthLinkOAMPortEventDetailedStatisticsEntry 49 }
   
sispm1040582lrtEthLinkOAMPortEventDetailedStatisticsRemoteEventSecondsSummaryEventTotal OBJECT-TYPE
   SYNTAX      Integer32
   MAX-ACCESS  read-only
   STATUS      current
   DESCRIPTION
       "This four-octet field indicates the number of Errored Frame Seconds Summary Event TLVs that 
	   have been generated since the OAM sublayer was reset, encoded as a 32bit unsigned integer."   
   ::= { sispm1040582lrtEthLinkOAMPortEventDetailedStatisticsEntry 50 }
   
   
   
sispm1040582lrtEVC    OBJECT IDENTIFIER ::= { sispm1040582lrtConfiguration 30 } 

sispm1040582lrtEVCPortConfTable OBJECT-TYPE
   SYNTAX      SEQUENCE OF SISPM1040582LRTEVCPortConfEntry
   MAX-ACCESS  not-accessible
   STATUS      current
   DESCRIPTION
       " "
   ::= { sispm1040582lrtEVC 1 }

sispm1040582lrtEVCPortConfEntry OBJECT-TYPE
   SYNTAX      SISPM1040582LRTEVCPortConfEntry
   MAX-ACCESS  not-accessible
   STATUS      current
   DESCRIPTION
       " "
   INDEX    { sispm1040582lrtEVCPortConfIndex  }
   ::= { sispm1040582lrtEVCPortConfTable 1 }

SISPM1040582LRTEVCPortConfEntry ::= SEQUENCE {
   sispm1040582lrtEVCPortConfIndex           Integer32,
   sispm1040582lrtEVCPortConfDEIMode         Integer32,
   sispm1040582lrtEVCPortConfTagMode         Integer32,
   sispm1040582lrtEVCPortConfAddressMode     Integer32
}

sispm1040582lrtEVCPortConfIndex OBJECT-TYPE
   SYNTAX      Integer32
   MAX-ACCESS  not-accessible
   STATUS      current
   DESCRIPTION
       "Index"
   ::= { sispm1040582lrtEVCPortConfEntry 1 }

sispm1040582lrtEVCPortConfDEIMode OBJECT-TYPE
   SYNTAX      Integer32
   MAX-ACCESS  read-write
   STATUS      current
   DESCRIPTION
       "The DEI mode for an NNI port determines whether frames transmitted on the port 
	   will have the DEI field in the outer tag marked based on the colour of the frame. 
	   The allowed values are: 
	   0:Fixed: The DEI value is determined by ECE rules.
       1:Coloured: The DEI is 1 for yellow frames and 0 for green frames. 
       "
   ::= { sispm1040582lrtEVCPortConfEntry 2 }

sispm1040582lrtEVCPortConfTagMode OBJECT-TYPE
   SYNTAX      Integer32
   MAX-ACCESS  read-write
   STATUS      current
   DESCRIPTION
       "The tag mode specifying whether the EVC classification must be based on the outer or inner tag. 
	   This can be used on NNI ports connected to another service provider, 
	   where an outer tunnel tag is added together with the inner tag identifying the EVC. 
	   The allowed values are: 
		0:Inner: Enable inner tag in EVC classification. 
		1:Outer: Enable outer tag in EVC classification."
   ::= { sispm1040582lrtEVCPortConfEntry 3 }
   
sispm1040582lrtEVCPortConfAddressMode OBJECT-TYPE
   SYNTAX      Integer32
   MAX-ACCESS  read-write
   STATUS      current
   DESCRIPTION
       "The IP/MAC address mode specifying whether the EVC classification must be based on source (SMAC/SIP) or 
	   destination (DMAC/DIP) addresses. 
	   The allowed values are: 
	   0:Source: Enable SMAC/SIP matching. 
	   1:Destination: Enable DMAC/DIP matching."
   ::= { sispm1040582lrtEVCPortConfEntry 4 }

   
   
sispm1040582lrtEVCBandwidthProfilesConfTable OBJECT-TYPE
   SYNTAX      SEQUENCE OF SISPM1040582LRTEVCBandwidthProfilesConfEntry
   MAX-ACCESS  not-accessible
   STATUS      current
   DESCRIPTION
       " "
   ::= { sispm1040582lrtEVC 2 }

sispm1040582lrtEVCBandwidthProfilesConfEntry OBJECT-TYPE
   SYNTAX      SISPM1040582LRTEVCBandwidthProfilesConfEntry
   MAX-ACCESS  not-accessible
   STATUS      current
   DESCRIPTION
       " "
   INDEX    { sispm1040582lrtEVCBandwidthProfilesConfIndex  }
   ::= { sispm1040582lrtEVCBandwidthProfilesConfTable 1 }

SISPM1040582LRTEVCBandwidthProfilesConfEntry ::= SEQUENCE {
   sispm1040582lrtEVCBandwidthProfilesConfIndex           Integer32,
   sispm1040582lrtEVCBandwidthProfilesConfState           Integer32,
   sispm1040582lrtEVCBandwidthProfilesConfType            Integer32,
   sispm1040582lrtEVCBandwidthProfilesConfPolicerMode     Integer32,
   sispm1040582lrtEVCBandwidthProfilesConfRateType        Integer32,
   sispm1040582lrtEVCBandwidthProfilesConfCIRkbps         Integer32,
   sispm1040582lrtEVCBandwidthProfilesConfCBSbytes        Integer32,
   sispm1040582lrtEVCBandwidthProfilesConfEIRkbps         Integer32,  
   sispm1040582lrtEVCBandwidthProfilesConfEBSbytes        Integer32   
}

sispm1040582lrtEVCBandwidthProfilesConfIndex OBJECT-TYPE
   SYNTAX      Integer32
   MAX-ACCESS  not-accessible
   STATUS      current
   DESCRIPTION
       "Index"
   ::= { sispm1040582lrtEVCBandwidthProfilesConfEntry 1 }

sispm1040582lrtEVCBandwidthProfilesConfState OBJECT-TYPE
   SYNTAX      Integer32
   MAX-ACCESS  read-write
   STATUS      current
   DESCRIPTION
       "The administrative state of the bandwidth profile. The allowed values are: 
		1:Enabled: The bandwidth profile enabled. 
		0:Disabled: The bandwidth profile is disabled.
       "
   ::= { sispm1040582lrtEVCBandwidthProfilesConfEntry 2 }

sispm1040582lrtEVCBandwidthProfilesConfType OBJECT-TYPE
   SYNTAX      Integer32
   MAX-ACCESS  read-write
   STATUS      current
   DESCRIPTION
       "The policer type of the bandwidth profile. The allowed values are: 
		0:MEF: MEF ingress bandwidth profile. 
		1:Single: Single bucket policer."
   ::= { sispm1040582lrtEVCBandwidthProfilesConfEntry 3 }
   
sispm1040582lrtEVCBandwidthProfilesConfPolicerMode OBJECT-TYPE
   SYNTAX      Integer32
   MAX-ACCESS  read-write
   STATUS      current
   DESCRIPTION
       "The colour mode of the bandwidth profile. The allowed values are: 
		0:Coupled: Colour-aware mode with coupling enabled. 
		1:Aware: Colour-aware mode with coupling disabled."
   ::= { sispm1040582lrtEVCBandwidthProfilesConfEntry 4 }
   
sispm1040582lrtEVCBandwidthProfilesConfRateType OBJECT-TYPE
   SYNTAX      Integer32
   MAX-ACCESS  read-write
   STATUS      current
   DESCRIPTION
       "The rate type of the bandwidth profile. The allowed values are: 
		0:Data: Specify that this bandwidth profile operates on data rate. 
		1:Line: Specify that this bandwidth profile operates on line rate."
   ::= { sispm1040582lrtEVCBandwidthProfilesConfEntry 5 }

sispm1040582lrtEVCBandwidthProfilesConfCIRkbps OBJECT-TYPE
   SYNTAX      Integer32
   MAX-ACCESS  read-write
   STATUS      current
   DESCRIPTION
       "The Committed Information Rate of the bandwidth profile. 
	   The allowed range is from 0 through 10000000 kilobit per second."
   ::= { sispm1040582lrtEVCBandwidthProfilesConfEntry 6 }

sispm1040582lrtEVCBandwidthProfilesConfCBSbytes OBJECT-TYPE
   SYNTAX      Integer32
   MAX-ACCESS  read-write
   STATUS      current
   DESCRIPTION
       "The Committed Burst Size of the bandwidth profile. 
	   The allowed range is from 0 through 100000 bytes."
   ::= { sispm1040582lrtEVCBandwidthProfilesConfEntry 7 }

sispm1040582lrtEVCBandwidthProfilesConfEIRkbps OBJECT-TYPE
   SYNTAX      Integer32
   MAX-ACCESS  read-write
   STATUS      current
   DESCRIPTION
       "The Excess Information Rate for MEF type bandwidth profile. 
	   The allowed range is from 0 through 10000000 kilobit per second."
   ::= { sispm1040582lrtEVCBandwidthProfilesConfEntry 8 }

sispm1040582lrtEVCBandwidthProfilesConfEBSbytes OBJECT-TYPE
   SYNTAX      Integer32
   MAX-ACCESS  read-write
   STATUS      current
   DESCRIPTION
       "The Excess Burst Size for MEF type bandwidth profile. 
	   The allowed range is from 0 through 100000 bytes."
   ::= { sispm1040582lrtEVCBandwidthProfilesConfEntry 9 }   


   
sispm1040582lrtEVCControlListConfTable  OBJECT-TYPE
   SYNTAX      SEQUENCE OF SISPM1040582LRTEVCControlListConfEntry
   MAX-ACCESS  not-accessible
   STATUS      current
   DESCRIPTION
       "A table of EVC Control List Conf."
   ::= { sispm1040582lrtEVC 3 }

sispm1040582lrtEVCControlListConfEntry OBJECT-TYPE
    SYNTAX        SISPM1040582LRTEVCControlListConfEntry
    MAX-ACCESS    not-accessible
    STATUS        current
    DESCRIPTION
        "An entry of EVC Control List Conf table."
    INDEX        { sispm1040582lrtEVCControlListConfIndex }
    ::= { sispm1040582lrtEVCControlListConfTable 1 }

SISPM1040582LRTEVCControlListConfEntry ::=
    SEQUENCE {
        sispm1040582lrtEVCControlListConfIndex                       Integer32,
        sispm1040582lrtEVCControlListConfEVCID                       Integer32,
        sispm1040582lrtEVCControlListConfVID                         Integer32,
        sispm1040582lrtEVCControlListConfIVID                        Integer32,
        sispm1040582lrtEVCControlListConfLearning                    Integer32,
        sispm1040582lrtEVCControlListConfPolicerIDFilter             Integer32,
        sispm1040582lrtEVCControlListConfPolicerID                   Integer32,
        sispm1040582lrtEVCControlListConfInnerTagType                Integer32,
        sispm1040582lrtEVCControlListConfInnerTagVIDMode             Integer32,
        sispm1040582lrtEVCControlListConfInnerTagVLANID              Integer32,
        sispm1040582lrtEVCControlListConfInnerTagPCPDEIPreservation  Integer32,
        sispm1040582lrtEVCControlListConfInnerTagPCP                 Integer32,
        sispm1040582lrtEVCControlListConfInnerTagDEI                 Integer32,        
		sispm1040582lrtEVCControlListConfOuterTagVLANID              Integer32,
        sispm1040582lrtEVCControlListConfNNIPorts                    DisplayString,
		sispm1040582lrtEVCControlListConfLeafVID                     Integer32,
        sispm1040582lrtEVCControlListConfLeafIVID                    Integer32,
		sispm1040582lrtEVCControlListConfLeafPorts                   DisplayString,
        sispm1040582lrtEVCControlListConfRowStatus                   RowStatus
    }

sispm1040582lrtEVCControlListConfIndex OBJECT-TYPE
   SYNTAX      Integer32
   MAX-ACCESS  not-accessible
   STATUS      current
   DESCRIPTION
       "index"
   ::= {sispm1040582lrtEVCControlListConfEntry 1 }

sispm1040582lrtEVCControlListConfEVCID OBJECT-TYPE
   SYNTAX      Integer32
   MAX-ACCESS  read-create
   STATUS      current
   DESCRIPTION
       "The EVC ID identifies the EVC. The allowed range is from 1 through 256."
   ::= {sispm1040582lrtEVCControlListConfEntry 2 }

sispm1040582lrtEVCControlListConfVID OBJECT-TYPE
   SYNTAX      Integer32
   MAX-ACCESS  read-create
   STATUS      current
   DESCRIPTION
       "The VLAN ID in the PB network. It may be inserted in a C-tag, S-tag or S-custom tag 
	   depending on the NNI port VLAN configuration. 
	   The allowed range is from 1 through 4095."
   ::= {sispm1040582lrtEVCControlListConfEntry 3 }
   
sispm1040582lrtEVCControlListConfIVID OBJECT-TYPE
   SYNTAX      Integer32
   MAX-ACCESS  read-create
   STATUS      current
   DESCRIPTION
       "The Internal/classified VLAN ID in the PB network. 
	   The allowed range is from 1 through 4095."
   ::= {sispm1040582lrtEVCControlListConfEntry 4 }
   
sispm1040582lrtEVCControlListConfLearning OBJECT-TYPE
   SYNTAX      Integer32
   MAX-ACCESS  read-create
   STATUS      current
   DESCRIPTION
       "The learning mode for the EVC controls whether source MAC addresses are learned for frames matching the EVC. 
	   Learning may be disabled if the EVC only includes two UNI/NNI ports. The possible values are: 
		1:Enabled: Learning is enabled (MAC addresses are learned). 
		0:Disabled: Learning is disabled (MAC addresses are not learned)."
   ::= {sispm1040582lrtEVCControlListConfEntry 5 }
   
sispm1040582lrtEVCControlListConfPolicerIDFilter OBJECT-TYPE
   SYNTAX      Integer32
   MAX-ACCESS  read-create
   STATUS      current
   DESCRIPTION
       "The ingress bandwidth profile mode for the EVC. The possible values are:
	   0:Specific.
	   1:Discard: All received frames are discarded for the EVC.
	   2:None: None bandwidth profile for the EVC.
	   "
   ::= {sispm1040582lrtEVCControlListConfEntry 6 }   
   
sispm1040582lrtEVCControlListConfPolicerID OBJECT-TYPE
   SYNTAX      Integer32
   MAX-ACCESS  read-create
   STATUS      current
   DESCRIPTION
       "The ingress bandwidth profile ID for the EVC."
   ::= {sispm1040582lrtEVCControlListConfEntry 7 }    
   
sispm1040582lrtEVCControlListConfInnerTagType OBJECT-TYPE
   SYNTAX      Integer32
   MAX-ACCESS  read-create
   STATUS      current
   DESCRIPTION
       "The inner tag type is used to determine whether an inner tag is inserted in frames forwarded to NNI ports. The possible values are: 
		0:None: An inner tag is not inserted. 
		1:C-tag: An inner C-tag is inserted. 
		2:S-tag: An inner S-tag is inserted. 
		3:S-custom-tag: An inner tag is inserted and the tag type is determined by the VLAN port configuration of the NNI."
   ::= {sispm1040582lrtEVCControlListConfEntry 8 }     
   
sispm1040582lrtEVCControlListConfInnerTagVIDMode OBJECT-TYPE
   SYNTAX      Integer32
   MAX-ACCESS  read-create
   STATUS      current
   DESCRIPTION
       "The inner VID Mode affects the VID in the inner and outer tag. 
	   The possible values are: 
		0:Normal: The VID of the two outer tags aren't swapped. 
		1:Tunnel: The VID of the two outer tags are swapped, 
		so that the VID of the outer tag is taken from the Inner Tag configuration and the VID of the inner tag is the EVC VID. 
		In this mode, the NNI ports are normally configured to do EVC classification based on the inner tag."
   ::= {sispm1040582lrtEVCControlListConfEntry 9 }   

sispm1040582lrtEVCControlListConfInnerTagVLANID OBJECT-TYPE
   SYNTAX      Integer32
   MAX-ACCESS  read-create
   STATUS      current
   DESCRIPTION
       "The Inner tag VLAN ID. The allowed range is from 1 through 4095."
   ::= {sispm1040582lrtEVCControlListConfEntry 10 }    

 sispm1040582lrtEVCControlListConfInnerTagPCPDEIPreservation OBJECT-TYPE
   SYNTAX      Integer32
   MAX-ACCESS  read-create
   STATUS      current
   DESCRIPTION
       "The inner tag PCP and DEI preservation. The possible values are: 
		1:Preserved: The inner tag PCP and DEI is preserved. 
		0:Fixed: The inner tag PCP and DEI is fixed."
   ::= {sispm1040582lrtEVCControlListConfEntry 11 }  
   
sispm1040582lrtEVCControlListConfInnerTagPCP OBJECT-TYPE
   SYNTAX      Integer32
   MAX-ACCESS  read-create
   STATUS      current
   DESCRIPTION
       "The inner tag PCP value. The allowed range is from 0 through 7."
   ::= {sispm1040582lrtEVCControlListConfEntry 12 }     
   
sispm1040582lrtEVCControlListConfInnerTagDEI OBJECT-TYPE
   SYNTAX      Integer32
   MAX-ACCESS  read-create
   STATUS      current
   DESCRIPTION
       "The inner tag DEI value. The allowed value is 0 or 1."
   ::= {sispm1040582lrtEVCControlListConfEntry 13 }     

sispm1040582lrtEVCControlListConfOuterTagVLANID OBJECT-TYPE
   SYNTAX      Integer32
   MAX-ACCESS  read-create
   STATUS      current
   DESCRIPTION
       "The EVC outer tag VID for UNI ports. The allowed range is from 1 through 4095."
   ::= {sispm1040582lrtEVCControlListConfEntry 14 }    

sispm1040582lrtEVCControlListConfNNIPorts OBJECT-TYPE
   SYNTAX      DisplayString
   MAX-ACCESS  read-create
   STATUS      current
   DESCRIPTION
       "The list of Network to Network Interfaces for the EVC."
   ::= {sispm1040582lrtEVCControlListConfEntry 15 }     
   
sispm1040582lrtEVCControlListConfLeafVID OBJECT-TYPE
   SYNTAX      Integer32
   MAX-ACCESS  read-create
   STATUS      current
   DESCRIPTION
       " The leaf VLAN ID used in the outer tag for the EVC. range:1-4095"
   ::= {sispm1040582lrtEVCControlListConfEntry 16 }  

sispm1040582lrtEVCControlListConfLeafIVID OBJECT-TYPE
   SYNTAX      Integer32
   MAX-ACCESS  read-create
   STATUS      current
   DESCRIPTION
       "The leaf internal classified VLAN ID for the EVC. range:1-4095"
   ::= {sispm1040582lrtEVCControlListConfEntry 17 }      
   
sispm1040582lrtEVCControlListConfLeafPorts OBJECT-TYPE
   SYNTAX      DisplayString
   MAX-ACCESS  read-create
   STATUS      current
   DESCRIPTION
       " The list of leaf ports for the EVC."
   ::= {sispm1040582lrtEVCControlListConfEntry 18 }    

sispm1040582lrtEVCControlListConfRowStatus OBJECT-TYPE
   SYNTAX      RowStatus
   MAX-ACCESS  read-create
   STATUS      current
   DESCRIPTION
       "EVC Control List Conf Row Status."
   ::= {sispm1040582lrtEVCControlListConfEntry 19 }

   
   
sispm1040582lrtECEControlListConfTable  OBJECT-TYPE
   SYNTAX      SEQUENCE OF SISPM1040582LRTECEControlListConfEntry
   MAX-ACCESS  not-accessible
   STATUS      current
   DESCRIPTION
       "A table of ECE Control List Conf."
   ::= { sispm1040582lrtEVC 4 }

sispm1040582lrtECEControlListConfEntry OBJECT-TYPE
    SYNTAX        SISPM1040582LRTECEControlListConfEntry
    MAX-ACCESS    not-accessible
    STATUS        current
    DESCRIPTION
        "An entry of ECE Control List Conf table."
    INDEX        { sispm1040582lrtECEControlListConfIndex }
    ::= { sispm1040582lrtECEControlListConfTable 1 }

SISPM1040582LRTECEControlListConfEntry ::=
    SEQUENCE {
        sispm1040582lrtECEControlListConfIndex                               Integer32,
        sispm1040582lrtECEControlListConfECEID                               Integer32,
        sispm1040582lrtECEControlListConfUNIPorts                            DisplayString,
        sispm1040582lrtECEControlListConfIngressMatchingTagType              Integer32,
        sispm1040582lrtECEControlListConfIngressMatchingVLANIDFilter         Integer32,
        sispm1040582lrtECEControlListConfIngressMatchingVLANIDRangeLow       Integer32,
        sispm1040582lrtECEControlListConfIngressMatchingVLANIDRangeHigh      Integer32,
        sispm1040582lrtECEControlListConfIngressMatchingPCP                  Integer32,
        sispm1040582lrtECEControlListConfIngressMatchingDEI                  Integer32,
        sispm1040582lrtECEControlListConfIngressMatchingFrameType            Integer32,
        sispm1040582lrtECEControlListConfActionsDirection                    Integer32,
        sispm1040582lrtECEControlListConfActionsEVCIDFilter                  Integer32,
        sispm1040582lrtECEControlListConfActionsEVCIDValue                   Integer32,        
		sispm1040582lrtECEControlListConfActionsTagPopCount                  Integer32,
        sispm1040582lrtECEControlListConfActionsPolicyID                     Integer32,
		sispm1040582lrtECEControlListConfActionsClass                        Integer32,
        sispm1040582lrtECEControlListConfMACParametersDMACType               Integer32,
		sispm1040582lrtECEControlListConfMACParametersSMACFilter             Integer32,
		sispm1040582lrtECEControlListConfMACParametersSMACValue              DisplayString,
		sispm1040582lrtECEControlListConfIPv4Protocol                        Integer32,
		sispm1040582lrtECEControlListConfIPv4ProtocolValue                   Integer32,
		sispm1040582lrtECEControlListConfIPv4SIPDIPFilter                    Integer32,
		sispm1040582lrtECEControlListConfIPv4SIPDIPAddress                   IpAddress,
		sispm1040582lrtECEControlListConfIPv4SIPDIPMask                      IpAddress,
		sispm1040582lrtECEControlListConfIPv4DSCPFilter                      Integer32,
		sispm1040582lrtECEControlListConfIPv4DSCPRangeLow                    Integer32,
		sispm1040582lrtECEControlListConfIPv4DSCPRangeHigh                   Integer32,
		sispm1040582lrtECEControlListConfIPv4Fragment                        Integer32,
		sispm1040582lrtECEControlListConfIPv4SourcePortFilter                Integer32,
		sispm1040582lrtECEControlListConfIPv4SourceRangeLow                  Integer32,
		sispm1040582lrtECEControlListConfIPv4SourceRangeHigh                 Integer32,
		sispm1040582lrtECEControlListConfIPv4DestPortFilter                  Integer32,
		sispm1040582lrtECEControlListConfIPv4DestRangeLow                    Integer32,
		sispm1040582lrtECEControlListConfIPv4DestRangeHigh                   Integer32,
		sispm1040582lrtECEControlListConfIPv6Protocol                        Integer32,
		sispm1040582lrtECEControlListConfIPv6ProtocolValue                   Integer32,
		sispm1040582lrtECEControlListConfIPv6SIPDIPFilter                    Integer32,
		sispm1040582lrtECEControlListConfIPv6SIPDIPAddress                   IpAddress,
		sispm1040582lrtECEControlListConfIPv6SIPDIPMask                      IpAddress,
		sispm1040582lrtECEControlListConfIPv6DSCPFilter                      Integer32,
		sispm1040582lrtECEControlListConfIPv6DSCPRangeLow                    Integer32,
		sispm1040582lrtECEControlListConfIPv6DSCPRangeHigh                   Integer32,
		sispm1040582lrtECEControlListConfIPv6SourcePortFilter                Integer32,
		sispm1040582lrtECEControlListConfIPv6SourceRangeLow                  Integer32,
		sispm1040582lrtECEControlListConfIPv6SourceRangeHigh                 Integer32,
		sispm1040582lrtECEControlListConfIPv6DestPortFilter                  Integer32,
		sispm1040582lrtECEControlListConfIPv6DestRangeLow                    Integer32,
		sispm1040582lrtECEControlListConfIPv6DestRangeHigh                   Integer32,
		sispm1040582lrtECEControlListConfEgressOuterTagMode                  Integer32,
		sispm1040582lrtECEControlListConfEgressOuterTagPCPDEIPreservation    Integer32,
		sispm1040582lrtECEControlListConfEgressOuterTagPCP                   Integer32,
		sispm1040582lrtECEControlListConfEgressOuterTagDEI                   Integer32,
		sispm1040582lrtECEControlListConfConflict                            Integer32,
        sispm1040582lrtECEControlListConfRowStatus                           RowStatus
    }

sispm1040582lrtECEControlListConfIndex OBJECT-TYPE
   SYNTAX      Integer32
   MAX-ACCESS  not-accessible
   STATUS      current
   DESCRIPTION
       "index"
   ::= {sispm1040582lrtECEControlListConfEntry 1 }

sispm1040582lrtECEControlListConfECEID OBJECT-TYPE
   SYNTAX      Integer32
   MAX-ACCESS  read-create
   STATUS      current
   DESCRIPTION
       "The ECE ID identifies the ECE. Unique ECE IDs are automatically assigned to ECEs added. 
	   The possible range is from 1 through 256."
   ::= {sispm1040582lrtECEControlListConfEntry 2 }  
   
sispm1040582lrtECEControlListConfUNIPorts OBJECT-TYPE
   SYNTAX      DisplayString
   MAX-ACCESS  read-create
   STATUS      current
   DESCRIPTION
       "The list of User Network Interfaces for the ECE. Ex:1,2 1-5"
   ::= {sispm1040582lrtECEControlListConfEntry 3 }  

sispm1040582lrtECEControlListConfIngressMatchingTagType OBJECT-TYPE
   SYNTAX      Integer32
   MAX-ACCESS  read-create
   STATUS      current
   DESCRIPTION
       "The tag type for the ECE. The possible values are: 
		0:Any: The ECE will match both tagged and untagged frames. 
		1:Untagged: The ECE will match untagged frames only. 
		2:C-Tagged: The ECE will match custom tagged frames only. 
		3:S-Tagged: The ECE will match service tagged frames only. 
		4:Tagged: The ECE will match tagged frames only."
   ::= {sispm1040582lrtECEControlListConfEntry 4 }  

sispm1040582lrtECEControlListConfIngressMatchingVLANIDFilter OBJECT-TYPE
   SYNTAX      Integer32
   MAX-ACCESS  read-create
   STATUS      current
   DESCRIPTION
       "The VLAN ID filter for matching the ECE. It only significant if tag type 'Tagged' is selected. The possible values are: 
		0:Any: No VLAN ID filter is specified. (VLAN ID filter status is don't-care.) 
		1:Specific: If you want to filter a specific VLAN ID value with this ECE, choose this value. A field for entering a specific value appears. 
		2:Range: If you want to filter a specific VLAN ID range filter with this ECE, choose this value. A field for entering a range appears."
   ::= {sispm1040582lrtECEControlListConfEntry 5 }  
   
sispm1040582lrtECEControlListConfIngressMatchingVLANIDRangeLow OBJECT-TYPE
   SYNTAX      Integer32
   MAX-ACCESS  read-create
   STATUS      current
   DESCRIPTION
       "When Specific is selected for the VLAN ID filter, you can enter a specific value. 
	   The allowed value is from 0 through 4095."
   ::= {sispm1040582lrtECEControlListConfEntry 6 }     
   
sispm1040582lrtECEControlListConfIngressMatchingVLANIDRangeHigh OBJECT-TYPE
   SYNTAX      Integer32
   MAX-ACCESS  read-create
   STATUS      current
   DESCRIPTION
       "When Specific is selected for the VLAN ID filter, you can enter a specific value. 
	   The allowed value is from 0 through 4095."
   ::= {sispm1040582lrtECEControlListConfEntry 7 }     
   
sispm1040582lrtECEControlListConfIngressMatchingPCP OBJECT-TYPE
   SYNTAX      Integer32
   MAX-ACCESS  read-create
   STATUS      current
   DESCRIPTION
       "The PCP value for matching the ECE. It only significant if tag type 'Tagged' is selected. The possible values are: 
        14:Any: The ECE will match any PCP value. 
		0-7:Specific: The ECE will match a specific PCP in the range 0 through 7. 
		8-13:Range: The ECE will match PCP values in the selected range 0-1, 2-3, 4-5, 6-7, 0-3 or 4-7."
   ::= {sispm1040582lrtECEControlListConfEntry 8 }    
   
sispm1040582lrtECEControlListConfIngressMatchingDEI OBJECT-TYPE
   SYNTAX      Integer32
   MAX-ACCESS  read-create
   STATUS      current
   DESCRIPTION
       "The DEI value for matching the ECE. It only significant if tag type 'Tagged' is selected. 
	   The allowed value is: 
	   0:Any
	   1:0
	   2:1"
   ::= {sispm1040582lrtECEControlListConfEntry 9 }    
   
sispm1040582lrtECEControlListConfIngressMatchingFrameType OBJECT-TYPE
   SYNTAX      Integer32
   MAX-ACCESS  read-create
   STATUS      current
   DESCRIPTION
       "The frame type for the ECE. The possible values are: 
		0:Any: The ECE will match any frame type. 
		1:IPv4: The ECE will match IPv4 frames only. 
		2:IPv6: The ECE will match IPv6 frames only."
   ::= {sispm1040582lrtECEControlListConfEntry 16 }  
   
sispm1040582lrtECEControlListConfActionsDirection OBJECT-TYPE
   SYNTAX      Integer32
   MAX-ACCESS  read-create
   STATUS      current
   DESCRIPTION
       "The EVCs and ECEs are used to setup flows in one or both directions as determined by the ECE Direction parameter. 
	   If the ECE is bidirectional, the ingress rules of the NNI ports will be setup to match the traffic being forwarded to NNI ports. 
	   The possible values are: 
		0:Both: Bidirectional. 
		1:UNI-to-NNI: Unidirectional from UNI to NNI. 
		2:NNI-to-UNI: Unidirectional from NNI to UNI."
   ::= {sispm1040582lrtECEControlListConfEntry 17 }  
   
sispm1040582lrtECEControlListConfActionsEVCIDFilter OBJECT-TYPE
   SYNTAX      Integer32
   MAX-ACCESS  read-create
   STATUS      current
   DESCRIPTION
       "The EVC ID for the ECE. 
	   The ECE is only active when mapping to an existing EVC. 
	   The possible values are: 
		0:None: No EVC ID filter is specified. (EVC ID filter status is don't-care.) 
		1:Specific: If you want to filter a specific EVC ID with this ECE, choose this value. A field for entering a specific value appears."
   ::= {sispm1040582lrtECEControlListConfEntry 18 }     
   
sispm1040582lrtECEControlListConfActionsEVCIDValue OBJECT-TYPE
   SYNTAX      Integer32
   MAX-ACCESS  read-create
   STATUS      current
   DESCRIPTION
       "When Specific is selected for the VLAN ID filter, you can enter a specific value. 
	   The allowed value is from 1 through 256."
   ::= {sispm1040582lrtECEControlListConfEntry 19 }      
   
sispm1040582lrtECEControlListConfActionsTagPopCount OBJECT-TYPE
   SYNTAX      Integer32
   MAX-ACCESS  read-create
   STATUS      current
   DESCRIPTION
       "The ingress tag pop count for the ECE. The allowed range is from 0 through 2."
   ::= {sispm1040582lrtECEControlListConfEntry 22 }   

sispm1040582lrtECEControlListConfActionsPolicyID OBJECT-TYPE
   SYNTAX      Integer32
   MAX-ACCESS  read-create
   STATUS      current
   DESCRIPTION
       "The ACL Policy ID for the ECE for matching ACL rules. 
	   The allowed range is from 0 through 255."
   ::= {sispm1040582lrtECEControlListConfEntry 23 }     
   
sispm1040582lrtECEControlListConfActionsClass OBJECT-TYPE
   SYNTAX      Integer32
   MAX-ACCESS  read-create
   STATUS      current
   DESCRIPTION
       "The traffic class for the ECE. The allowed range is from 0 through 7 or disabled(8)."
   ::= {sispm1040582lrtECEControlListConfEntry 24 }   

sispm1040582lrtECEControlListConfMACParametersDMACType OBJECT-TYPE
   SYNTAX      Integer32
   MAX-ACCESS  read-create
   STATUS      current
   DESCRIPTION
       "The destination MAC address type for matching the ECE. The possible values are: 
		0:Any: No DMAC tyoe is specified. (DMAC filter status is don't-care.) 
		1:Unicast: Frame must be unicast. 
		2:Multicast: Frame must be multicast. 
		3:Broadcast: Frame must be broadcast."
   ::= {sispm1040582lrtECEControlListConfEntry 25 }      
   
sispm1040582lrtECEControlListConfMACParametersSMACFilter OBJECT-TYPE
   SYNTAX      Integer32
   MAX-ACCESS  read-create
   STATUS      current
   DESCRIPTION
       "The source MAC address for matching the ECE. The possible values are: 
		0:Any: No SMAC filter is specified. (SMAC filter status is don't-care.) 
		1:Specific: If you want to filter a specific SMAC value with this ECE, choose this value. A field for entering a specific value appears."
   ::= {sispm1040582lrtECEControlListConfEntry 28 }    
   
sispm1040582lrtECEControlListConfMACParametersSMACValue OBJECT-TYPE
   SYNTAX      DisplayString
   MAX-ACCESS  read-create
   STATUS      current
   DESCRIPTION
       "When Specific is selected for the SMAC filter, you can enter a specific value. 
	   The legal format is xx-xx-xx-xx-xx-xx (x is a hexadecimal digit)."
   ::= {sispm1040582lrtECEControlListConfEntry 29 }     
   
sispm1040582lrtECEControlListConfIPv4Protocol OBJECT-TYPE
   SYNTAX      Integer32
   MAX-ACCESS  read-create
   STATUS      current
   DESCRIPTION
       "The IP protocol for matching the ECE. The possible values are: 
		0:Any: No protocol filter is specified. (Protocol filter status is don't-care.) 
		1:UDP: Specify the UDP for matching the ECE. 
		2:TCP: Specify the TCP for matching the ECE. 
		3:Specific: If you want to filter a specific protocol value with this ECE, choose this value. A field for entering a specific value appears."
   ::= {sispm1040582lrtECEControlListConfEntry 30 }
   
sispm1040582lrtECEControlListConfIPv4ProtocolValue OBJECT-TYPE
   SYNTAX      Integer32
   MAX-ACCESS  read-create
   STATUS      current
   DESCRIPTION
       "When Specific is selected for the protocol filter, you can enter a specific value. 
	   The allowed value is from 0 through 255."
   ::= {sispm1040582lrtECEControlListConfEntry 31 }   
   
sispm1040582lrtECEControlListConfIPv4SIPDIPFilter OBJECT-TYPE
   SYNTAX      Integer32
   MAX-ACCESS  read-create
   STATUS      current
   DESCRIPTION
       "The source/destination IP address for matching the ECE. 
	   It depend on by the port address mode, when port address mode is set to 'Source' then the field is used for source address. 
	   Similarly when port address mode is set to 'Destination' then the field is used for destination address. 
	   The possible values are: 
		0:Any: No SIP/DIP filter is specified. (SIP/DIP filter status is don't-care.) 
		1:Host: When IPv4 is selected for the Frame Type, if you want to filter a specific host address with this ECE, choose this value. A field for entering a host address appears. 
		2:Network: When IPv4 is selected for the Frame Type, if you want to filter a specific network address with this ECE, choose this value. Two fields for entering a specific network address and network mask appears. "
   ::= {sispm1040582lrtECEControlListConfEntry 32 }    
   
sispm1040582lrtECEControlListConfIPv4SIPDIPAddress OBJECT-TYPE
   SYNTAX      IpAddress
   MAX-ACCESS  read-create
   STATUS      current
   DESCRIPTION
       "When IPv4 is selected for the Frame Type and Host or Network is selected for the SIP/DIP filter, 
	   you can enter a specific host or network address. 
	   "
   ::= {sispm1040582lrtECEControlListConfEntry 33 }    
   
sispm1040582lrtECEControlListConfIPv4SIPDIPMask OBJECT-TYPE
   SYNTAX      IpAddress
   MAX-ACCESS  read-create
   STATUS      current
   DESCRIPTION
       "When IPv4 is selected for the Frame Type and Host or Network is selected for the SIP/DIP filter, 
	   you can enter a specific network mask. "
   ::= {sispm1040582lrtECEControlListConfEntry 34 }     
   
sispm1040582lrtECEControlListConfIPv4DSCPFilter OBJECT-TYPE
   SYNTAX      Integer32
   MAX-ACCESS  read-create
   STATUS      current
   DESCRIPTION
       "The DSCP filter for matching the ECE. The possible values are: 
		0:Any: No DSCP filter is specified. (DSCP filter status is don't-care.) 
		1:Specific: If you want to filter a specific DSCP value with this ECE, choose this value. A field for entering a specific value appears. 
		2:Range: If you want to filter a specific DSCP range filter with this ECE, choose this value. A field for entering a range appears."
   ::= {sispm1040582lrtECEControlListConfEntry 35 }    
   
sispm1040582lrtECEControlListConfIPv4DSCPRangeLow OBJECT-TYPE
   SYNTAX      Integer32
   MAX-ACCESS  read-create
   STATUS      current
   DESCRIPTION
       "When Specific is selected for the DSCP filter, you can enter a specific value. 
	   The allowed value is from 0 through 63."
   ::= {sispm1040582lrtECEControlListConfEntry 36 }    

sispm1040582lrtECEControlListConfIPv4DSCPRangeHigh OBJECT-TYPE
   SYNTAX      Integer32
   MAX-ACCESS  read-create
   STATUS      current
   DESCRIPTION
       "When Range is selected for the DSCP filter, you can enter a specific range. 
	   The allowed range is from 0 through 63."
   ::= {sispm1040582lrtECEControlListConfEntry 37 }   

sispm1040582lrtECEControlListConfIPv4Fragment OBJECT-TYPE
   SYNTAX      Integer32
   MAX-ACCESS  read-create
   STATUS      current
   DESCRIPTION
       "The IPv4 Fragment for matching the ECE. 
	   This involves the settings for the More Fragments (MF) bit and the Fragment Offset (FRAG OFFSET) field for an IPv4 frame. 
	   The possible values are: 
		0:Any: The ECE will match any MF bit. 
		1:Non-Fragment: IPv4 frames where the MF bit is set or the FRAG OFFSET field is greater than zero must not be able to match this entry. 
		2:Fragment: IPv4 frames where the MF bit is set or the FRAG OFFSET field is greater than zero must be able to match this entry."
   ::= {sispm1040582lrtECEControlListConfEntry 38 }    

sispm1040582lrtECEControlListConfIPv4SourcePortFilter OBJECT-TYPE
   SYNTAX      Integer32
   MAX-ACCESS  read-create
   STATUS      current
   DESCRIPTION
       "The TCP/UDP source port for matching the ECE. 
	   It only significant if protocol filter 'UDP' or 'TCP' is selected. 
	   The possible values are: 
		0:Any: No TCP/UDP source port filter is specified. (Source port filter status is don't-care.) 
		1:Specific: If you want to filter a specific TCP/UDP source port No. with this ECE, choose this value. A field for entering a specific No. appears. 
		2:Range: If you want to filter a specific TCP/UDP source port range filter with this ECE, choose this value. A field for entering a range appears."
   ::= {sispm1040582lrtECEControlListConfEntry 39 }     
   
sispm1040582lrtECEControlListConfIPv4SourceRangeLow OBJECT-TYPE
   SYNTAX      Integer32
   MAX-ACCESS  read-create
   STATUS      current
   DESCRIPTION
       "When Range is selected for the source port filter, you can enter a specific range. 
	   The allowed range is from 0 through 65535."
   ::= {sispm1040582lrtECEControlListConfEntry 40 }    
   
sispm1040582lrtECEControlListConfIPv4SourceRangeHigh OBJECT-TYPE
   SYNTAX      Integer32
   MAX-ACCESS  read-create
   STATUS      current
   DESCRIPTION
       "When Range is selected for the source port filter, you can enter a specific range. 
	   The allowed range is from 0 through 65535."
   ::= {sispm1040582lrtECEControlListConfEntry 41 }    
   
sispm1040582lrtECEControlListConfIPv4DestPortFilter OBJECT-TYPE
   SYNTAX      Integer32
   MAX-ACCESS  read-create
   STATUS      current
   DESCRIPTION
       "The TCP/UDP destination port for matching the ECE. It only significant if protocol filter 'UDP' or 'TCP' is selected. The possible values are: 
		0:Any: No TCP/UDP destination port filter is specified. (Destination port filter status is don't-care.) 
		1:Specific: If you want to filter a specific TCP/UDP destination port No. with this ECE, choose this value. A field for entering a specific No. appears. 
		2:Range: If you want to filter a specific TCP/UDP destination port range filter with this ECE, choose this value. A field for entering a range appears."
   ::= {sispm1040582lrtECEControlListConfEntry 42 }    

sispm1040582lrtECEControlListConfIPv4DestRangeLow OBJECT-TYPE
   SYNTAX      Integer32
   MAX-ACCESS  read-create
   STATUS      current
   DESCRIPTION
       "When Range is selected for the destination port filter, you can enter a specific range. 
	   The allowed range is from 0 through 65535."
   ::= {sispm1040582lrtECEControlListConfEntry 43 }    

sispm1040582lrtECEControlListConfIPv4DestRangeHigh OBJECT-TYPE
   SYNTAX      Integer32
   MAX-ACCESS  read-create
   STATUS      current
   DESCRIPTION
       "When Range is selected for the destination port filter, you can enter a specific range. 
	   The allowed range is from 0 through 65535."
   ::= {sispm1040582lrtECEControlListConfEntry 44 }  

sispm1040582lrtECEControlListConfIPv6Protocol OBJECT-TYPE
   SYNTAX      Integer32
   MAX-ACCESS  read-create
   STATUS      current
   DESCRIPTION
       "The IP protocol for matching the ECE. The possible values are: 
		0:Any: No protocol filter is specified. (Protocol filter status is don't-care.) 
		1:UDP: Specify the UDP for matching the ECE. 
		2:TCP: Specify the TCP for matching the ECE. 
		3:Specific: If you want to filter a specific protocol value with this ECE, choose this value. A field for entering a specific value appears."
   ::= {sispm1040582lrtECEControlListConfEntry 45 }     
   
sispm1040582lrtECEControlListConfIPv6ProtocolValue OBJECT-TYPE
   SYNTAX      Integer32
   MAX-ACCESS  read-create
   STATUS      current
   DESCRIPTION
       "When Specific is selected for the protocol filter, you can enter a specific value. 
	   The allowed value is from 0 through 255."
   ::= {sispm1040582lrtECEControlListConfEntry 46 }     
   
sispm1040582lrtECEControlListConfIPv6SIPDIPFilter OBJECT-TYPE
   SYNTAX      Integer32
   MAX-ACCESS  read-create
   STATUS      current
   DESCRIPTION
       "The source/destination IP address for matching the ECE. 
	   It depend on by the port address mode, when port address mode is set to 'Source' then the field is used for source address. Similarly when port address mode is set to 'Destination' then the field is used for destination address. 
	   The possible values are: 
		0:Any: No SIP/DIP filter is specified. (SIP/DIP filter status is don't-care.) 
		1:Specific: When IPv6 is selected for the Frame Type, if you want to filter a specific network address with this ECE, choose this value. Two fields for entering a specific network address and network mask appears."
   ::= {sispm1040582lrtECEControlListConfEntry 47 } 

sispm1040582lrtECEControlListConfIPv6SIPDIPAddress OBJECT-TYPE
   SYNTAX      IpAddress
   MAX-ACCESS  read-create
   STATUS      current
   DESCRIPTION
	   "When IPv6 is selected for the Frame Type, the field only supported 32 bits for IPv6 address."
   ::= {sispm1040582lrtECEControlListConfEntry 48 }    

sispm1040582lrtECEControlListConfIPv6SIPDIPMask OBJECT-TYPE
   SYNTAX      IpAddress
   MAX-ACCESS  read-create
   STATUS      current
   DESCRIPTION
	   "When IPv6 is selected for the Frame Type, the field only supported 32 bits for IPv6 mask."
   ::= {sispm1040582lrtECEControlListConfEntry 49 }   

sispm1040582lrtECEControlListConfIPv6DSCPFilter OBJECT-TYPE
   SYNTAX      Integer32
   MAX-ACCESS  read-create
   STATUS      current
   DESCRIPTION
       "The DSCP filter for matching the ECE. The possible values are: 
		0:Any: No DSCP filter is specified. (DSCP filter status is don't-care.) 
		1:Specific: If you want to filter a specific DSCP value with this ECE, choose this value. A field for entering a specific value appears. 
		2:Range: If you want to filter a specific DSCP range filter with this ECE, choose this value. A field for entering a range appears."
   ::= {sispm1040582lrtECEControlListConfEntry 50 }    
   
sispm1040582lrtECEControlListConfIPv6DSCPRangeLow OBJECT-TYPE
   SYNTAX      Integer32
   MAX-ACCESS  read-create
   STATUS      current
   DESCRIPTION
       "When Range is selected for the DSCP filter, you can enter a specific range. The allowed range is from 0 through 63."
   ::= {sispm1040582lrtECEControlListConfEntry 51 }     
   
sispm1040582lrtECEControlListConfIPv6DSCPRangeHigh OBJECT-TYPE
   SYNTAX      Integer32
   MAX-ACCESS  read-create
   STATUS      current
   DESCRIPTION
       "When Range is selected for the DSCP filter, you can enter a specific range. The allowed range is from 0 through 63."
   ::= {sispm1040582lrtECEControlListConfEntry 52 }      
   
sispm1040582lrtECEControlListConfIPv6SourcePortFilter OBJECT-TYPE
   SYNTAX      Integer32
   MAX-ACCESS  read-create
   STATUS      current
   DESCRIPTION
       "The TCP/UDP source port for matching the ECE. 
	   It only significant if protocol filter 'UDP' or 'TCP' is selected. The possible values are: 
		0:Any: No TCP/UDP source port filter is specified. (Source port filter status is don't-care.) 
		1:Specific: If you want to filter a specific TCP/UDP source port No. with this ECE, choose this value. A field for entering a specific No. appears. 
		2:Range: If you want to filter a specific TCP/UDP source port range filter with this ECE, choose this value. A field for entering a range appears."
   ::= {sispm1040582lrtECEControlListConfEntry 53 }    

sispm1040582lrtECEControlListConfIPv6SourceRangeLow OBJECT-TYPE
   SYNTAX      Integer32
   MAX-ACCESS  read-create
   STATUS      current
   DESCRIPTION
       "When Range is selected for the source port filter, you can enter a specific range. 
	   The allowed range is from 0 through 65535."
   ::= {sispm1040582lrtECEControlListConfEntry 54 }    

sispm1040582lrtECEControlListConfIPv6SourceRangeHigh OBJECT-TYPE
   SYNTAX      Integer32
   MAX-ACCESS  read-create
   STATUS      current
   DESCRIPTION
       "When Range is selected for the source port filter, you can enter a specific range. 
	   The allowed range is from 0 through 65535."
   ::= {sispm1040582lrtECEControlListConfEntry 55 }    
   
sispm1040582lrtECEControlListConfIPv6DestPortFilter OBJECT-TYPE
   SYNTAX      Integer32
   MAX-ACCESS  read-create
   STATUS      current
   DESCRIPTION
       "The TCP/UDP destination port for matching the ECE. 
	   It only significant if protocol filter 'UDP' or 'TCP' is selected. 
	   The possible values are: 
		0:Any: No TCP/UDP destination port filter is specified. (Destination port filter status is don't-care.) 
		1:Specific: If you want to filter a specific TCP/UDP destination port No. with this ECE, choose this value. A field for entering a specific No. appears. 
		2:Range: If you want to filter a specific TCP/UDP destination port range filter with this ECE, choose this value. A field for entering a range appears."
   ::= {sispm1040582lrtECEControlListConfEntry 56 }   
   
sispm1040582lrtECEControlListConfIPv6DestRangeLow OBJECT-TYPE
   SYNTAX      Integer32
   MAX-ACCESS  read-create
   STATUS      current
   DESCRIPTION
       "When Range is selected for the destination port filter, you can enter a specific range. 
	   The allowed range is from 0 through 65535."
   ::= {sispm1040582lrtECEControlListConfEntry 57 }    
   
sispm1040582lrtECEControlListConfIPv6DestRangeHigh OBJECT-TYPE
   SYNTAX      Integer32
   MAX-ACCESS  read-create
   STATUS      current
   DESCRIPTION
       "When Range is selected for the destination port filter, you can enter a specific range. 
	   The allowed range is from 0 through 65535."
   ::= {sispm1040582lrtECEControlListConfEntry 58 }    
   
sispm1040582lrtECEControlListConfEgressOuterTagMode OBJECT-TYPE
   SYNTAX      Integer32
   MAX-ACCESS  read-create
   STATUS      current
   DESCRIPTION
       "The outer tag for nni-to-uni direction for the ECE. The possible values are: 
		1:Enable: Enable outer tag for nni-to-uni direction for the ECE. 
		0:Disable: Disable outer tag for nni-to-uni direction for the ECE."
   ::= {sispm1040582lrtECEControlListConfEntry 59 }    
   
sispm1040582lrtECEControlListConfEgressOuterTagPCPDEIPreservation OBJECT-TYPE
   SYNTAX      Integer32
   MAX-ACCESS  read-create
   STATUS      current
   DESCRIPTION
       "The outer tag PCP and DEI preservation for the ECE. The possible values are: 
		1:Preserved: The outer tag PCP and DEI is preserved. 
		0:Fixed: The outer tag PCP and DEI is fixed."
   ::= {sispm1040582lrtECEControlListConfEntry 61 }    
   
sispm1040582lrtECEControlListConfEgressOuterTagPCP OBJECT-TYPE
   SYNTAX      Integer32
   MAX-ACCESS  read-create
   STATUS      current
   DESCRIPTION
       "The outer tag PCP value for the ECE. The allowed range is from 0 through 7."
   ::= {sispm1040582lrtECEControlListConfEntry 62 }      

sispm1040582lrtECEControlListConfEgressOuterTagDEI OBJECT-TYPE
   SYNTAX      Integer32
   MAX-ACCESS  read-create
   STATUS      current
   DESCRIPTION
       "The outer tag DEI value for the ECE. The allowed value is 0 or 1."
   ::= {sispm1040582lrtECEControlListConfEntry 63 }   

sispm1040582lrtECEControlListConfConflict OBJECT-TYPE
   SYNTAX      Integer32
   MAX-ACCESS  read-only
   STATUS      current
   DESCRIPTION
       "Indicates the hardware status of the specific ECE. 
	   The specific ECE is not applied to the hardware due to hardware limitations.
	   0:No
	   1:Yes"
   ::= {sispm1040582lrtECEControlListConfEntry 69 }      
   
sispm1040582lrtECEControlListConfRowStatus OBJECT-TYPE
   SYNTAX      RowStatus
   MAX-ACCESS  read-create
   STATUS      current
   DESCRIPTION
       "ECE Control List Conf Row Status."
   ::= {sispm1040582lrtECEControlListConfEntry 70 }
   
   
sispm1040582lrtEVCStatisticsTable  OBJECT-TYPE
   SYNTAX      SEQUENCE OF SISPM1040582LRTEVCStatisticsEntry
   MAX-ACCESS  not-accessible
   STATUS      current
   DESCRIPTION
       "A table of EVC Statistics."
   ::= { sispm1040582lrtEVC 5 }

sispm1040582lrtEVCStatisticsEntry OBJECT-TYPE
    SYNTAX        SISPM1040582LRTEVCStatisticsEntry
    MAX-ACCESS    not-accessible
    STATUS        current
    DESCRIPTION
        "An entry of EVC Statistics table."
    INDEX        { sispm1040582lrtEVCStatisticsPort, sispm1040582lrtEVCStatisticsClass}
    ::= { sispm1040582lrtEVCStatisticsTable 1 }

SISPM1040582LRTEVCStatisticsEntry ::=
    SEQUENCE {
        sispm1040582lrtEVCStatisticsPort                                     Integer32,
		sispm1040582lrtEVCStatisticsClass                                    Integer32,
        sispm1040582lrtEVCStatisticsGreenFramesRx                            Integer32,
		sispm1040582lrtEVCStatisticsGreenFramesTx                            Integer32,
		sispm1040582lrtEVCStatisticsYellowFramesRx                           Integer32,
		sispm1040582lrtEVCStatisticsYellowFramesTx                           Integer32,
		sispm1040582lrtEVCStatisticsRedFramesRx                              Integer32,
		sispm1040582lrtEVCStatisticsDiscardedFramesGreen                     Integer32,
		sispm1040582lrtEVCStatisticsDiscardedFramesYellow                    Integer32
    }

sispm1040582lrtEVCStatisticsPort OBJECT-TYPE
   SYNTAX      Integer32
   MAX-ACCESS  not-accessible
   STATUS      current
   DESCRIPTION
       "Port Index"
   ::= {sispm1040582lrtEVCStatisticsEntry 1 }
   
sispm1040582lrtEVCStatisticsClass OBJECT-TYPE
   SYNTAX      Integer32
   MAX-ACCESS  not-accessible
   STATUS      current
   DESCRIPTION
       "Class Index, from 1-8"
   ::= {sispm1040582lrtEVCStatisticsEntry 2 }

sispm1040582lrtEVCStatisticsGreenFramesRx OBJECT-TYPE
   SYNTAX      Integer32
   MAX-ACCESS  read-only
   STATUS      current
   DESCRIPTION
       "The number of green received."
   ::= {sispm1040582lrtEVCStatisticsEntry 3 }  
   
sispm1040582lrtEVCStatisticsGreenFramesTx OBJECT-TYPE
   SYNTAX      Integer32
   MAX-ACCESS  read-only
   STATUS      current
   DESCRIPTION
       "The number of green transmitted."
   ::= {sispm1040582lrtEVCStatisticsEntry 4 }   

sispm1040582lrtEVCStatisticsYellowFramesRx OBJECT-TYPE
   SYNTAX      Integer32
   MAX-ACCESS  read-only
   STATUS      current
   DESCRIPTION
       "The number of yellow received."
   ::= {sispm1040582lrtEVCStatisticsEntry 5 }    
   
sispm1040582lrtEVCStatisticsYellowFramesTx OBJECT-TYPE
   SYNTAX      Integer32
   MAX-ACCESS  read-only
   STATUS      current
   DESCRIPTION
       "The number of yellow transmitted."
   ::= {sispm1040582lrtEVCStatisticsEntry 6 }     
   
sispm1040582lrtEVCStatisticsRedFramesRx OBJECT-TYPE
   SYNTAX      Integer32
   MAX-ACCESS  read-only
   STATUS      current
   DESCRIPTION
       "The number of red received."
   ::= {sispm1040582lrtEVCStatisticsEntry 7 }    
   
sispm1040582lrtEVCStatisticsDiscardedFramesGreen OBJECT-TYPE
   SYNTAX      Integer32
   MAX-ACCESS  read-only
   STATUS      current
   DESCRIPTION
       "The number of discarded in the green color."
   ::= {sispm1040582lrtEVCStatisticsEntry 8 }    
  
sispm1040582lrtEVCStatisticsDiscardedFramesYellow OBJECT-TYPE
   SYNTAX      Integer32
   MAX-ACCESS  read-only
   STATUS      current
   DESCRIPTION
       "The number of discarded in the yellow color."
   ::= {sispm1040582lrtEVCStatisticsEntry 9 }    
   
   
sispm1040582lrtEVCStatisticsClearTable  OBJECT-TYPE
   SYNTAX      SEQUENCE OF SISPM1040582LRTEVCStatisticsClearEntry
   MAX-ACCESS  not-accessible
   STATUS      current
   DESCRIPTION
       "A table of EVC Statistics Clear."
   ::= { sispm1040582lrtEVC 6 }

sispm1040582lrtEVCStatisticsClearEntry OBJECT-TYPE
    SYNTAX        SISPM1040582LRTEVCStatisticsClearEntry
    MAX-ACCESS    not-accessible
    STATUS        current
    DESCRIPTION
        "An entry of EVC Statistics Clear table."
    INDEX        { sispm1040582lrtEVCStatisticsClearPort}
    ::= { sispm1040582lrtEVCStatisticsClearTable 1 }

SISPM1040582LRTEVCStatisticsClearEntry ::=
    SEQUENCE {
        sispm1040582lrtEVCStatisticsClearPort                Integer32,
		sispm1040582lrtEVCStatisticsClear                    Integer32
    }


sispm1040582lrtEVCStatisticsClearPort OBJECT-TYPE
   SYNTAX      Integer32
   MAX-ACCESS  not-accessible
   STATUS      current
   DESCRIPTION
       "Port Index"
   ::= {sispm1040582lrtEVCStatisticsClearEntry 1 }
   
sispm1040582lrtEVCStatisticsClear OBJECT-TYPE
   SYNTAX      Integer32
   MAX-ACCESS  read-write
   STATUS      current
   DESCRIPTION
       "Clears the counters for selected ports."
   ::= {sispm1040582lrtEVCStatisticsClearEntry 2 }

-- =======================================================================================================================

sispm1040582lrtAggregation    OBJECT IDENTIFIER ::= { sispm1040582lrtConfiguration 31 } 
    
sispm1040582lrtAggregationStatic    OBJECT IDENTIFIER ::= { sispm1040582lrtAggregation 1 } 

sispm1040582lrtAggrSourceMACAddress   OBJECT-TYPE
               SYNTAX      Integer32 (0|1)
               MAX-ACCESS  read-write
               STATUS      current
               DESCRIPTION
                   "Source MAC Address"
               ::= { sispm1040582lrtAggregationStatic 2 }

sispm1040582lrtAggrDestinationMACAddress   OBJECT-TYPE
               SYNTAX      Integer32 (0|1)
               MAX-ACCESS  read-write
               STATUS      current
               DESCRIPTION
                   "Destination MAC Address"
               ::= { sispm1040582lrtAggregationStatic 3 }
               
sispm1040582lrtAggrIPAddress   OBJECT-TYPE
               SYNTAX      Integer32 (0|1)
               MAX-ACCESS  read-write
               STATUS      current
               DESCRIPTION
                   "IP Address"
               ::= { sispm1040582lrtAggregationStatic 4 }

sispm1040582lrtAggrTCPUDPPortNumber   OBJECT-TYPE
               SYNTAX      Integer32 (0|1)
               MAX-ACCESS  read-write
               STATUS      current
               DESCRIPTION
                   "TCP/UDP Port Number"
               ::= { sispm1040582lrtAggregationStatic 5 }
               
               
sispm1040582lrtAggrGroupConfigTable OBJECT-TYPE
   SYNTAX      SEQUENCE OF SISPM1040582LRTAggrGroupConfigEntry
   MAX-ACCESS  not-accessible
   STATUS      current
   DESCRIPTION
       " "
   ::= { sispm1040582lrtAggregationStatic 6 }

sispm1040582lrtAggrGroupConfigEntry OBJECT-TYPE
   SYNTAX      SISPM1040582LRTAggrGroupConfigEntry
   MAX-ACCESS  not-accessible
   STATUS      current
   DESCRIPTION
       " "
   INDEX    { sispm1040582lrtAggrGroupConfigPort  }
   ::= { sispm1040582lrtAggrGroupConfigTable 1 }

SISPM1040582LRTAggrGroupConfigEntry ::= SEQUENCE {
   sispm1040582lrtAggrGroupConfigPort                 Integer32,
   sispm1040582lrtAggrGroupConfigGroup                Integer32,
   sispm1040582lrtAggrGroupConfig                     Integer32
}

sispm1040582lrtAggrGroupConfigPort OBJECT-TYPE
   SYNTAX      Integer32
   MAX-ACCESS  not-accessible
   STATUS      current
   DESCRIPTION
       "port index"
   ::= { sispm1040582lrtAggrGroupConfigEntry 1 }
      
sispm1040582lrtAggrGroupConfigGroup OBJECT-TYPE
   SYNTAX      Integer32
   MAX-ACCESS  not-accessible
   STATUS      current
   DESCRIPTION
       "group index"
   ::= { sispm1040582lrtAggrGroupConfigEntry 2 }   

sispm1040582lrtAggrGroupConfig OBJECT-TYPE
   SYNTAX      Integer32 (0|1)
   MAX-ACCESS  read-write
   STATUS      current
   DESCRIPTION
       "Aggregation Group Configuration"
   ::= { sispm1040582lrtAggrGroupConfigEntry 3 }
   
   
sispm1040582lrtAggrGroupStateTable OBJECT-TYPE
   SYNTAX      SEQUENCE OF SISPM1040582LRTAggrGroupStateEntry
   MAX-ACCESS  not-accessible
   STATUS      current
   DESCRIPTION
       " "
   ::= { sispm1040582lrtAggregation 2 }

sispm1040582lrtAggrGroupStateEntry OBJECT-TYPE
   SYNTAX      SISPM1040582LRTAggrGroupStateEntry
   MAX-ACCESS  not-accessible
   STATUS      current
   DESCRIPTION
       " "
   INDEX    { sispm1040582lrtAggrGroupStateIndex  }
   ::= { sispm1040582lrtAggrGroupStateTable 1 }

SISPM1040582LRTAggrGroupStateEntry ::= SEQUENCE {
   sispm1040582lrtAggrGroupStateIndex             Integer32,
   sispm1040582lrtAggrGroupStateAggrID            DisplayString,
   sispm1040582lrtAggrGroupStateName              DisplayString,
   sispm1040582lrtAggrGroupStateType              DisplayString,
   sispm1040582lrtAggrGroupStateSpeed             DisplayString,   
   sispm1040582lrtAggrGroupStateConfiguredPorts   DisplayString,
   sispm1040582lrtAggrGroupStateAggregatedPorts   DisplayString,
   sispm1040582lrtAggrGroupStateAggregatedBandwidth   DisplayString 
}

sispm1040582lrtAggrGroupStateIndex OBJECT-TYPE
   SYNTAX      Integer32
   MAX-ACCESS  not-accessible
   STATUS      current
   DESCRIPTION
       "index"
   ::= { sispm1040582lrtAggrGroupStateEntry 1 }
   
sispm1040582lrtAggrGroupStateAggrID OBJECT-TYPE
   SYNTAX      DisplayString
   MAX-ACCESS  read-only
   STATUS      current
   DESCRIPTION
       "AggrID"
   ::= { sispm1040582lrtAggrGroupStateEntry 2 }

sispm1040582lrtAggrGroupStateName OBJECT-TYPE
   SYNTAX      DisplayString
   MAX-ACCESS  read-only
   STATUS      current
   DESCRIPTION
       "Name"
   ::= { sispm1040582lrtAggrGroupStateEntry 3 }
   
sispm1040582lrtAggrGroupStateType OBJECT-TYPE
   SYNTAX      DisplayString
   MAX-ACCESS  read-only
   STATUS      current
   DESCRIPTION
       "Type"
   ::= { sispm1040582lrtAggrGroupStateEntry 4 }   
   
sispm1040582lrtAggrGroupStateSpeed OBJECT-TYPE
   SYNTAX      DisplayString
   MAX-ACCESS  read-only
   STATUS      current
   DESCRIPTION
       "Speed"
   ::= { sispm1040582lrtAggrGroupStateEntry 5 }
   
sispm1040582lrtAggrGroupStateConfiguredPorts OBJECT-TYPE
   SYNTAX      DisplayString
   MAX-ACCESS  read-only
   STATUS      current
   DESCRIPTION
       "Configured Ports"
   ::= { sispm1040582lrtAggrGroupStateEntry 6 }

sispm1040582lrtAggrGroupStateAggregatedPorts OBJECT-TYPE
   SYNTAX      DisplayString
   MAX-ACCESS  read-only
   STATUS      current
   DESCRIPTION
       "Aggregated Ports"
   ::= { sispm1040582lrtAggrGroupStateEntry 7 }   
   
sispm1040582lrtAggrGroupStateAggregatedBandwidth OBJECT-TYPE
   SYNTAX      DisplayString
   MAX-ACCESS  read-only
   STATUS      current
   DESCRIPTION
       "Aggregated Bandwidth"
   ::= { sispm1040582lrtAggrGroupStateEntry 8 }   
   

-- =======================================================================================================================
sispm1040582lrtSecurity                                              OBJECT IDENTIFIER ::= { sispm1040582lrtProductId 3 }

sispm1040582lrtIPSourceGuard                                         OBJECT IDENTIFIER ::= { sispm1040582lrtSecurity 1 }

sispm1040582lrtIPSourceGuardConf                                     OBJECT IDENTIFIER ::= { sispm1040582lrtIPSourceGuard 1 }

-- RowStatus Info:  createAndGo, notReady not supported.
-- =======================================================================================================================
-- Textual Conventions for the SISPM1040582LRT IP Source Guard Mib
-- =======================================================================================================================
--
--    sispm1040582lrtIPSourceGuard        OBJECT IDENTIFIER  ::= { sispm1040582lrtIPSourceGuardMIB 1 }
--    sispm1040582lrtIPSourceGuardConf    OBJECT IDENTIFIER  ::= { sispm1040582lrtIPSourceGuard 1 }

--
-- =======================================================================================================================
-- Start sispm1040582lrtIPSourceGuard group
-- =======================================================================================================================
--sispm1040582lrtIPSourceGuardConf

    sispm1040582lrtIPSourceGuardMode OBJECT-TYPE
               SYNTAX      AdminMode
               MAX-ACCESS  read-write
               STATUS      current
               DESCRIPTION
                   "Enable the Global IP Source Guard or disable the
                    Global IP Source Guard."
               ::= {     sispm1040582lrtIPSourceGuardConf 1 }

    sispm1040582lrtIPSourceGuardDynamicToStaticCmd OBJECT-TYPE
               SYNTAX      ActivateCmd
               MAX-ACCESS  read-write
               STATUS      current
               DESCRIPTION
                   "Translate all dynamic entries to static entries."
               DEFVAL  { noAction }
               ::= {     sispm1040582lrtIPSourceGuardConf 2 }

--sispm1040582lrtIPSourceGuardPortConfigTable

    sispm1040582lrtIPSourceGuardPortConfigTable OBJECT-TYPE
               SYNTAX      SEQUENCE OF     SISPM1040582LRTIPSourceGuardPortConfigEntry
               MAX-ACCESS  not-accessible
               STATUS      current
               DESCRIPTION
                   "The IP Source Guard Port Configuration Table.
                    INDEX for this table is ifIndex which is
                    equivalent to the panel port number."
               ::= {     sispm1040582lrtIPSourceGuardConf 3 }

    sispm1040582lrtIPSourceGuardPortConfigEntry OBJECT-TYPE
               SYNTAX          SISPM1040582LRTIPSourceGuardPortConfigEntry
               MAX-ACCESS  not-accessible
               STATUS      current
               DESCRIPTION
                   "The IP Source Guard Port Configuration Entry."
               INDEX    {    ifIndex  }
               ::= {     sispm1040582lrtIPSourceGuardPortConfigTable 1 }

    SISPM1040582LRTIPSourceGuardPortConfigEntry             ::= SEQUENCE {
                 sispm1040582lrtIPSourceGuardPortConfigMode            AdminMode,
                 sispm1040582lrtIPSourceGuardPortMaxDynamicClients     Integer32
                 }

    sispm1040582lrtIPSourceGuardPortConfigMode OBJECT-TYPE
               SYNTAX      AdminMode
               MAX-ACCESS  read-write
               STATUS      current
               DESCRIPTION
                   "Specify IP Source Guard is enabled on which ports."
               ::= {     sispm1040582lrtIPSourceGuardPortConfigEntry 2 }

    sispm1040582lrtIPSourceGuardPortMaxDynamicClients OBJECT-TYPE
               SYNTAX      Integer32(0..2|99)
               MAX-ACCESS  read-write
               STATUS      current
               DESCRIPTION
                   "Specify the maximum number of dynamic clients that can
                    be learned on given port.
                    default: 99
                    0~2: Max Dynamic clients
                    99:Unlimited "
               ::= {     sispm1040582lrtIPSourceGuardPortConfigEntry 3 }

--sispm1040582lrtIPSourceGuardStaticTable

    sispm1040582lrtIPSourceGuardStaticTable OBJECT-TYPE
               SYNTAX      SEQUENCE OF     SISPM1040582LRTIPSourceGuardStaticEntry
               MAX-ACCESS  not-accessible
               STATUS      current
               DESCRIPTION
                   "The IP Source Guard Static Table."
               ::= {     sispm1040582lrtIPSourceGuard 2 }

    sispm1040582lrtIPSourceGuardStaticEntry OBJECT-TYPE
               SYNTAX          SISPM1040582LRTIPSourceGuardStaticEntry
               MAX-ACCESS  not-accessible
               STATUS      current
               DESCRIPTION
                   "The IP Source Guard Static Entry."
               INDEX    {    sispm1040582lrtIPSourceGuardStaticIndex  }
               ::= {     sispm1040582lrtIPSourceGuardStaticTable 1 }

    SISPM1040582LRTIPSourceGuardStaticEntry             ::= SEQUENCE {
                 sispm1040582lrtIPSourceGuardStaticSwitchIndex   Integer32,
                 sispm1040582lrtIPSourceGuardStaticIndex         Integer32,
                 sispm1040582lrtIPSourceGuardStaticPort          Integer32,
                 sispm1040582lrtIPSourceGuardStaticVLANId        Integer32,
                 sispm1040582lrtIPSourceGuardStaticIPAddress     IpAddress,
                 sispm1040582lrtIPSourceGuardStaticIPMask        IpAddress,
                 sispm1040582lrtIPSourceGuardStaticMACAddress    DisplayString,
                 sispm1040582lrtIPSourceGuardStaticRowStatus     RowStatus
                 }

    sispm1040582lrtIPSourceGuardStaticSwitchIndex OBJECT-TYPE
               SYNTAX      Integer32(1..16)
               MAX-ACCESS  not-accessible
               STATUS      current
               DESCRIPTION
                   "Switch Index."
               ::= {     sispm1040582lrtIPSourceGuardStaticEntry 1 }

    sispm1040582lrtIPSourceGuardStaticIndex OBJECT-TYPE
               SYNTAX      Integer32(1..28)
               MAX-ACCESS  not-accessible
               STATUS      current
               DESCRIPTION
                   "The entry of table."
               ::= {     sispm1040582lrtIPSourceGuardStaticEntry 2 }

    sispm1040582lrtIPSourceGuardStaticPort OBJECT-TYPE
               SYNTAX      Integer32(1..255)
               MAX-ACCESS  read-create
               STATUS      current
               DESCRIPTION
                   "The port number of table.
                    range: 1 - port number."
               ::= {     sispm1040582lrtIPSourceGuardStaticEntry 3 }

    sispm1040582lrtIPSourceGuardStaticVLANId OBJECT-TYPE
               SYNTAX      Integer32(1..4095)
               MAX-ACCESS  read-create
               STATUS      current
               DESCRIPTION
                   "VLAN ID, range: 1 - 4095."
               ::= {     sispm1040582lrtIPSourceGuardStaticEntry 4 }

    sispm1040582lrtIPSourceGuardStaticIPAddress OBJECT-TYPE
               SYNTAX      IpAddress
               MAX-ACCESS  read-create
               STATUS      current
               DESCRIPTION
                   "IP address allowed for doing IP source guard."
               ::= {     sispm1040582lrtIPSourceGuardStaticEntry 5 }

    sispm1040582lrtIPSourceGuardStaticIPMask OBJECT-TYPE
               SYNTAX      IpAddress
               MAX-ACCESS  read-create
               STATUS      current
               DESCRIPTION
                   "IP Mask allowed for doing IP source guard."
               ::= {     sispm1040582lrtIPSourceGuardStaticEntry 6 }

    sispm1040582lrtIPSourceGuardStaticMACAddress OBJECT-TYPE
               SYNTAX      DisplayString
               MAX-ACCESS  read-create
               STATUS      current
               DESCRIPTION
                   "Allowed Source MAC address, format: 0a 1b 2c 3d 4e 5f."
               ::= {     sispm1040582lrtIPSourceGuardStaticEntry 7 }

    sispm1040582lrtIPSourceGuardStaticRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm1040582lrtIPSourceGuardStaticEntry 8 }

--sispm1040582lrtIPSourceGuardDynamicTable

    sispm1040582lrtIPSourceGuardDynamicTable OBJECT-TYPE
               SYNTAX      SEQUENCE OF     SISPM1040582LRTIPSourceGuardDynamicEntry
               MAX-ACCESS  not-accessible
               STATUS      current
               DESCRIPTION
                   "The IP Source Guard Dynamic Table."
               ::= {     sispm1040582lrtIPSourceGuard 3 }

    sispm1040582lrtIPSourceGuardDynamicEntry OBJECT-TYPE
               SYNTAX          SISPM1040582LRTIPSourceGuardDynamicEntry
               MAX-ACCESS  not-accessible
               STATUS      current
               DESCRIPTION
                   "The IP Source Guard Dynamic Entry."
               INDEX    {    sispm1040582lrtIPSourceGuardDynamicIndex  }
               ::= {     sispm1040582lrtIPSourceGuardDynamicTable 1 }

    SISPM1040582LRTIPSourceGuardDynamicEntry             ::= SEQUENCE {
                 sispm1040582lrtIPSourceGuardDynamicSwitchIndex    Integer32,
                 sispm1040582lrtIPSourceGuardDynamicIndex          Integer32,
                 sispm1040582lrtIPSourceGuardDynamicPort           Integer32,
                 sispm1040582lrtIPSourceGuardDynamicVLANId         Integer32,
                 sispm1040582lrtIPSourceGuardDynamicIPAddress      IpAddress,
                 sispm1040582lrtIPSourceGuardDynamicMACAddress     DisplayString
                 }

    sispm1040582lrtIPSourceGuardDynamicSwitchIndex OBJECT-TYPE
               SYNTAX      Integer32(1..16)
               MAX-ACCESS  not-accessible
               STATUS      current
               DESCRIPTION
                   "Switch Index."
               ::= {     sispm1040582lrtIPSourceGuardDynamicEntry 1 }

    sispm1040582lrtIPSourceGuardDynamicIndex OBJECT-TYPE
               SYNTAX      Integer32(1..4095)
               MAX-ACCESS  not-accessible
               STATUS      current
               DESCRIPTION
                   "The entry of table."
               ::= {     sispm1040582lrtIPSourceGuardDynamicEntry 2 }

    sispm1040582lrtIPSourceGuardDynamicPort OBJECT-TYPE
               SYNTAX      Integer32(1..255)
               MAX-ACCESS  read-only
               STATUS      current
               DESCRIPTION
                   "The logical port for the settings."
               ::= {     sispm1040582lrtIPSourceGuardDynamicEntry 3 }

    sispm1040582lrtIPSourceGuardDynamicVLANId OBJECT-TYPE
               SYNTAX      Integer32(1..4094)
               MAX-ACCESS  read-only
               STATUS      current
               DESCRIPTION
                   "The vlan id for the settings."
               ::= {     sispm1040582lrtIPSourceGuardDynamicEntry 4 }

    sispm1040582lrtIPSourceGuardDynamicIPAddress OBJECT-TYPE
               SYNTAX      IpAddress
               MAX-ACCESS  read-only
               STATUS      current
               DESCRIPTION
                   "Allowed Source IP address."
               ::= {     sispm1040582lrtIPSourceGuardDynamicEntry 5 }

    sispm1040582lrtIPSourceGuardDynamicMACAddress OBJECT-TYPE
               SYNTAX      DisplayString
               MAX-ACCESS  read-only
               STATUS      current
               DESCRIPTION
                   "Allowed Source MAC address."
               ::= {     sispm1040582lrtIPSourceGuardDynamicEntry 6 }
-- =======================================================================================================================
sispm1040582lrtARPInspection                                          OBJECT IDENTIFIER ::= { sispm1040582lrtSecurity 2 }
-- RowStatus Info:  createAndGo, notReady not supported.
-- =======================================================================================================================
-- Textual Conventions for the sispm1040582lrt Arp Mib
-- =======================================================================================================================
--
    sispm1040582lrtARP                  OBJECT IDENTIFIER  ::= { sispm1040582lrtARPInspection 1 }
    sispm1040582lrtARPConfig            OBJECT IDENTIFIER  ::= { sispm1040582lrtARP 1 }

--
-- =======================================================================================================================
-- Start sispm1040582lrtARP group
-- =======================================================================================================================
--sispm1040582lrtARPConfig

    sispm1040582lrtARPConfMode OBJECT-TYPE
               SYNTAX      AdminMode
               MAX-ACCESS  read-write
               STATUS      current
               DESCRIPTION
                   "Enable the Global ARP Inspection or disable the Global
                    ARP Inspection."
               ::= {     sispm1040582lrtARPConfig 1 }

--sispm1040582lrtARPPortConfTable

    sispm1040582lrtARPPortConfTable OBJECT-TYPE
               SYNTAX      SEQUENCE OF     SISPM1040582LRTARPPortConfEntry
               MAX-ACCESS  not-accessible
               STATUS      current
               DESCRIPTION
                   "The ARP Port Configuration Table."
               ::= {     sispm1040582lrtARPConfig 3 }

    sispm1040582lrtARPPortConfEntry OBJECT-TYPE
               SYNTAX          SISPM1040582LRTARPPortConfEntry
               MAX-ACCESS  not-accessible
               STATUS      current
               DESCRIPTION
                   "The ARP Port Configuration Entry."
               INDEX    {    sispm1040582lrtARPPortConfPort  }
               ::= {     sispm1040582lrtARPPortConfTable 1 }

    SISPM1040582LRTARPPortConfEntry             ::= SEQUENCE {
                 sispm1040582lrtARPPortConfPort            Integer32,
                 sispm1040582lrtARPPortConfMode            AdminMode,
                 sispm1040582lrtARPPortConfCheckVLAN       AdminMode,
                 sispm1040582lrtARPPortConfLogType         INTEGER
                 }

    sispm1040582lrtARPPortConfPort OBJECT-TYPE
               SYNTAX      Integer32(1..255)
               MAX-ACCESS  not-accessible
               STATUS      current
               DESCRIPTION
                   "The port number for which the configuration below applies.
                    range: 1 - port number."
               ::= {     sispm1040582lrtARPPortConfEntry 1 }

    sispm1040582lrtARPPortConfMode OBJECT-TYPE
               SYNTAX      AdminMode
               MAX-ACCESS  read-write
               STATUS      current
               DESCRIPTION
                   "Specify ARP Inspection is enabled on which ports."
               ::= {     sispm1040582lrtARPPortConfEntry 2 }

    sispm1040582lrtARPPortConfCheckVLAN OBJECT-TYPE
               SYNTAX      AdminMode
               MAX-ACCESS  read-write
               STATUS      current
               DESCRIPTION
                   "When the setting of 'Check VLAN' is disabled, the log
                   type of ARP Inspection will refer to the port setting.
                   And the setting of 'Check VLAN' is enabled, the log type
                   of ARP Inspection will refer to the VLAN setting."
               ::= {     sispm1040582lrtARPPortConfEntry 3 }

    sispm1040582lrtARPPortConfLogType OBJECT-TYPE
               SYNTAX      INTEGER{none(0),deny(1),permit(2),all(3)}
               MAX-ACCESS  read-write
               STATUS      current
               DESCRIPTION
                   "The log type of ARP Inspection will refer to the
                    port setting.
                    0: none,
                    1: deny,
                    2: permit,
                    3: all,
                    range: 0-3."
               ::= {     sispm1040582lrtARPPortConfEntry 4 }

--sispm1040582lrtARPVlanConfig

    sispm1040582lrtARPVlanConfigTable OBJECT-TYPE
               SYNTAX      SEQUENCE OF     SISPM1040582LRTARPVlanConfigEntry
               MAX-ACCESS  not-accessible
               STATUS      current
               DESCRIPTION
                   "The ARP Vlan Configuration Table."
               ::= {     sispm1040582lrtARP 2 }

    sispm1040582lrtARPVlanConfigEntry OBJECT-TYPE
               SYNTAX          SISPM1040582LRTARPVlanConfigEntry
               MAX-ACCESS  not-accessible
               STATUS      current
               DESCRIPTION
                   "The ARP Vlan Configuration Entry."
               INDEX    {    sispm1040582lrtARPVlanConfigVlan  }
               ::= {     sispm1040582lrtARPVlanConfigTable 1 }

    SISPM1040582LRTARPVlanConfigEntry             ::= SEQUENCE {
                 sispm1040582lrtARPVlanConfigVlan       Integer32,
                 sispm1040582lrtARPVlanConfigLogType    INTEGER,
                 sispm1040582lrtARPVlanConfigRowStatus  RowStatus
                 }

    sispm1040582lrtARPVlanConfigVlan OBJECT-TYPE
               SYNTAX      Integer32(1..4095)
               MAX-ACCESS  not-accessible
               STATUS      current
               DESCRIPTION
                   "Specify ARP Inspection is enabled on which VLANs.
                    range: 1 - 4095."
               ::= {     sispm1040582lrtARPVlanConfigEntry 1 }

    sispm1040582lrtARPVlanConfigLogType OBJECT-TYPE
               SYNTAX      INTEGER{none(0),deny(1),permit(2),all(3)}
               MAX-ACCESS  read-create
               STATUS      current
               DESCRIPTION
                   "The log type also can be configured on per VLAN setting.
                    0: none,
                    1: deny,
                    2: permit,
                    3: all,
                    range: 0-3."
               ::= {     sispm1040582lrtARPVlanConfigEntry 2 }

    sispm1040582lrtARPVlanConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm1040582lrtARPVlanConfigEntry 3 }

--sispm1040582lrtARPStaticTable

    sispm1040582lrtARPStaticTable OBJECT-TYPE
               SYNTAX      SEQUENCE OF     SISPM1040582LRTARPStaticEntry
               MAX-ACCESS  not-accessible
               STATUS      current
               DESCRIPTION
                   "The ARP Static Table."
               ::= {     sispm1040582lrtARP 3 }

    sispm1040582lrtARPStaticEntry OBJECT-TYPE
               SYNTAX          SISPM1040582LRTARPStaticEntry
               MAX-ACCESS  not-accessible
               STATUS      current
               DESCRIPTION
                   "The ARP Static Entry."
               INDEX    {    sispm1040582lrtARPStaticIndex  }
               ::= {     sispm1040582lrtARPStaticTable 1 }

    SISPM1040582LRTARPStaticEntry             ::= SEQUENCE {
                 sispm1040582lrtARPStaticSwitchIndex   Integer32,
                 sispm1040582lrtARPStaticIndex         Integer32,
                 sispm1040582lrtARPStaticPort          Integer32,
                 sispm1040582lrtARPStaticVlanID        Integer32,
                 sispm1040582lrtARPStaticMACAddress    DisplayString,
                 sispm1040582lrtARPStaticIPAddress     IpAddress,
                 sispm1040582lrtARPStaticRowStatus     RowStatus
                 }


    sispm1040582lrtARPStaticSwitchIndex OBJECT-TYPE
               SYNTAX      Integer32(1..16)
               MAX-ACCESS  not-accessible
               STATUS      current
               DESCRIPTION
                   "Switch Index."
               ::= {     sispm1040582lrtARPStaticEntry 1 }

    sispm1040582lrtARPStaticIndex OBJECT-TYPE
               SYNTAX      Integer32(1..255)
               MAX-ACCESS  not-accessible
               STATUS      current
               DESCRIPTION
                   "The entry of table."
               ::= {     sispm1040582lrtARPStaticEntry 2 }

    sispm1040582lrtARPStaticPort OBJECT-TYPE
               SYNTAX      Integer32(1..255)
               MAX-ACCESS  read-create
               STATUS      current
               DESCRIPTION
                   "The logical port for the settings.
                    range: 1 - port number."
               ::= {     sispm1040582lrtARPStaticEntry 3 }

    sispm1040582lrtARPStaticVlanID OBJECT-TYPE
               SYNTAX      Integer32(1..4095)
               MAX-ACCESS  read-create
               STATUS      current
               DESCRIPTION
                   "The vlan id for the settings.
                    range: 1-4095."
               ::= {     sispm1040582lrtARPStaticEntry 4 }

    sispm1040582lrtARPStaticMACAddress OBJECT-TYPE
               SYNTAX      DisplayString
               MAX-ACCESS  read-create
               STATUS      current
               DESCRIPTION
                   "Allowed Source MAC address in ARP request packets."
               ::= {     sispm1040582lrtARPStaticEntry 5 }

    sispm1040582lrtARPStaticIPAddress OBJECT-TYPE
               SYNTAX      IpAddress
               MAX-ACCESS  read-create
               STATUS      current
               DESCRIPTION
                   "Allowed Source IP address in ARP request packets."
               ::= {     sispm1040582lrtARPStaticEntry 6 }

    sispm1040582lrtARPStaticRowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sispm1040582lrtARPStaticEntry 7 }

--sispm1040582lrtARPDynamicTable

    sispm1040582lrtARPDynamicTable OBJECT-TYPE
               SYNTAX      SEQUENCE OF     SISPM1040582LRTARPDynamicEntry
               MAX-ACCESS  not-accessible
               STATUS      current
               DESCRIPTION
                   "The ARP Dynamic Table."
               ::= {    sispm1040582lrtARP 4 }

    sispm1040582lrtARPDynamicEntry OBJECT-TYPE
               SYNTAX          SISPM1040582LRTARPDynamicEntry
               MAX-ACCESS  not-accessible
               STATUS      current
               DESCRIPTION
                   "The ARP Dynamic Entry."
               INDEX    {   sispm1040582lrtARPDynamicIndex  }
               ::= {    sispm1040582lrtARPDynamicTable 1 }

    SISPM1040582LRTARPDynamicEntry             ::= SEQUENCE {
                 sispm1040582lrtARPDynamicIndex          Integer32,
                 sispm1040582lrtARPDynamicPort           Integer32,
                 sispm1040582lrtARPDynamicVLANId         Integer32,
                 sispm1040582lrtARPDynamicMACAddress     MacAddress,
                 sispm1040582lrtARPDynamicIPAddress      IpAddress,
                 sispm1040582lrtARPDynamicToStaticCmd    INTEGER
                 }

    sispm1040582lrtARPDynamicIndex OBJECT-TYPE
               SYNTAX      Integer32(1..4095)
               MAX-ACCESS  not-accessible
               STATUS      current
               DESCRIPTION
                   "The entry of table."
               ::= {    sispm1040582lrtARPDynamicEntry 1 }

    sispm1040582lrtARPDynamicPort OBJECT-TYPE
               SYNTAX      Integer32(1..255)
               MAX-ACCESS  read-only
               STATUS      current
               DESCRIPTION
                   "Switch Port Number for which the entries are displayed."
               ::= {    sispm1040582lrtARPDynamicEntry 2 }

    sispm1040582lrtARPDynamicVLANId OBJECT-TYPE
               SYNTAX      Integer32(1..4095)
               MAX-ACCESS  read-only
               STATUS      current
               DESCRIPTION
                   "VLAN-ID in which the ARP traffic is permitted."
               ::= {    sispm1040582lrtARPDynamicEntry 3 }

    sispm1040582lrtARPDynamicMACAddress OBJECT-TYPE
               SYNTAX      MacAddress
               MAX-ACCESS  read-only
               STATUS      current
               DESCRIPTION
                   "User MAC address of the entry."
               ::= {    sispm1040582lrtARPDynamicEntry 4 }

    sispm1040582lrtARPDynamicIPAddress OBJECT-TYPE
               SYNTAX      IpAddress
               MAX-ACCESS  read-only
               STATUS      current
               DESCRIPTION
                   "User IP address of the entry."
               ::= {    sispm1040582lrtARPDynamicEntry 5 }

    sispm1040582lrtARPDynamicToStaticCmd OBJECT-TYPE
               SYNTAX      ActivateCmd
               MAX-ACCESS  read-write
               STATUS      current
               DESCRIPTION
                   "Enable the Global ARP Inspection or disable the Global
                    ARP Inspection."
               ::= {     sispm1040582lrtARPDynamicEntry 6 }


-- =======================================================================================================================
-- sispm1040582lrtARPConformance
-- =======================================================================================================================
sispm1040582lrtARPConformance OBJECT IDENTIFIER ::= { sispm1040582lrtARPInspection 200 }

sispm1040582lrtARPCompliances OBJECT IDENTIFIER ::= { sispm1040582lrtARPConformance 1 }

sispm1040582lrtARPGroups      OBJECT IDENTIFIER ::= { sispm1040582lrtARPConformance 2 }

sispm1040582lrtARPGroup OBJECT-GROUP
    OBJECTS {
                -- sispm1040582lrtARPConfig
                sispm1040582lrtARPConfMode,

                --sispm1040582lrtARPPortConfTable
                sispm1040582lrtARPPortConfMode,
                sispm1040582lrtARPPortConfCheckVLAN,
                sispm1040582lrtARPPortConfLogType,

                --sispm1040582lrtARPVlanConfig
                sispm1040582lrtARPVlanConfigLogType,
                sispm1040582lrtARPVlanConfigRowStatus,

                --sispm1040582lrtARPStaticTable
                sispm1040582lrtARPStaticPort,
                sispm1040582lrtARPStaticVlanID,
                sispm1040582lrtARPStaticMACAddress,
                sispm1040582lrtARPStaticIPAddress,
                sispm1040582lrtARPStaticRowStatus,

                --sispm1040582lrtARPDynamicTable
                sispm1040582lrtARPDynamicPort,
                sispm1040582lrtARPDynamicVLANId,
                sispm1040582lrtARPDynamicMACAddress,
                sispm1040582lrtARPDynamicIPAddress,
                sispm1040582lrtARPDynamicToStaticCmd
            }
     STATUS  current
     DESCRIPTION
            "The collection of objects which are used to indicate
            sispm1040582lrt ARP information."
    ::= { sispm1040582lrtARPGroups 1 }

-- =======================================================================================================================
sispm1040582lrtDHCPSnooping                                          OBJECT IDENTIFIER ::= { sispm1040582lrtSecurity 3 }

sispm1040582lrtDHCPSnoopingConf                                          OBJECT IDENTIFIER ::= { sispm1040582lrtDHCPSnooping 1 }

sispm1040582lrtDHCPSnoopingMode OBJECT-TYPE
   SYNTAX      Integer32(0|1)
   MAX-ACCESS  read-write
   STATUS      current
   DESCRIPTION
       "default: 0
       0: disable
       1: enable"
   ::= { sispm1040582lrtDHCPSnoopingConf 1 }

sispm1040582lrtDHCPSnoopingPortModeConfigurationTable OBJECT-TYPE
   SYNTAX      SEQUENCE OF SISPM1040582LRTDHCPSnoopingPortModeConfigurationEntry
   MAX-ACCESS  not-accessible
   STATUS      current
   DESCRIPTION
       " "
   ::= { sispm1040582lrtDHCPSnoopingConf 2 }

sispm1040582lrtDHCPSnoopingPortModeConfigurationEntry OBJECT-TYPE
   SYNTAX      SISPM1040582LRTDHCPSnoopingPortModeConfigurationEntry
   MAX-ACCESS  not-accessible
   STATUS      current
   DESCRIPTION
       " "
   INDEX    { sispm1040582lrtDHCPSnoopingPortModeConfigurationPort  }
   ::= { sispm1040582lrtDHCPSnoopingPortModeConfigurationTable 1 }

SISPM1040582LRTDHCPSnoopingPortModeConfigurationEntry ::= SEQUENCE {
   sispm1040582lrtDHCPSnoopingPortModeConfigurationPort	Integer32,
   sispm1040582lrtDHCPSnoopingPortModeConfigurationMode	Integer32
}

sispm1040582lrtDHCPSnoopingPortModeConfigurationPort OBJECT-TYPE
   SYNTAX      Integer32(1..4095)
   MAX-ACCESS  not-accessible
   STATUS      current
   DESCRIPTION
       " "
   ::= { sispm1040582lrtDHCPSnoopingPortModeConfigurationEntry 1 }

sispm1040582lrtDHCPSnoopingPortModeConfigurationMode OBJECT-TYPE
   SYNTAX      Integer32 (0|1)
   MAX-ACCESS  read-write
   STATUS      current
   DESCRIPTION
       "default: 1
       0: trust port mode
       1: untrust port mode"
   ::= { sispm1040582lrtDHCPSnoopingPortModeConfigurationEntry 2 }

sispm1040582lrtDHCPSnoopingStatisticsTable OBJECT-TYPE
   SYNTAX      SEQUENCE OF SISPM1040582LRTDHCPSnoopingStatisticsEntry
   MAX-ACCESS  not-accessible
   STATUS      current
   DESCRIPTION
       " "
   ::= { sispm1040582lrtDHCPSnooping 2 }

sispm1040582lrtDHCPSnoopingStatisticsEntry OBJECT-TYPE
   SYNTAX      SISPM1040582LRTDHCPSnoopingStatisticsEntry
   MAX-ACCESS  not-accessible
   STATUS      current
   DESCRIPTION
       " "
   INDEX    { sispm1040582lrtDHCPSnoopingStatisticsPort  }
   ::= { sispm1040582lrtDHCPSnoopingStatisticsTable 1 }

SISPM1040582LRTDHCPSnoopingStatisticsEntry ::= SEQUENCE {
   sispm1040582lrtDHCPSnoopingStatisticsPort         Integer32,
   sispm1040582lrtDHCPSnoopingStatisticsClear        Integer32,
   sispm1040582lrtDHCPSnoopingRxDiscover             Counter32,
   sispm1040582lrtDHCPSnoopingRxOffer                Counter32,
   sispm1040582lrtDHCPSnoopingRxRequest              Counter32,
   sispm1040582lrtDHCPSnoopingRxDecline              Counter32,
   sispm1040582lrtDHCPSnoopingRxACK                  Counter32,
   sispm1040582lrtDHCPSnoopingRxNAK                  Counter32,
   sispm1040582lrtDHCPSnoopingRxRelease              Counter32,
   sispm1040582lrtDHCPSnoopingRxInform               Counter32,
   sispm1040582lrtDHCPSnoopingRxLeaseQuery           Counter32,
   sispm1040582lrtDHCPSnoopingRxLeaseUnassigned      Counter32,
   sispm1040582lrtDHCPSnoopingRxLeaseUnknown         Counter32,
   sispm1040582lrtDHCPSnoopingRxLeaseActive          Counter32,
   sispm1040582lrtDHCPSnoopingTxDiscover             Counter32,
   sispm1040582lrtDHCPSnoopingTxOffer                Counter32,
   sispm1040582lrtDHCPSnoopingTxRequest              Counter32,
   sispm1040582lrtDHCPSnoopingTxDecline              Counter32,
   sispm1040582lrtDHCPSnoopingTxACK                  Counter32,
   sispm1040582lrtDHCPSnoopingTxNAK                  Counter32,
   sispm1040582lrtDHCPSnoopingTxRelease              Counter32,
   sispm1040582lrtDHCPSnoopingTxInform               Counter32,
   sispm1040582lrtDHCPSnoopingTxLeaseQuery           Counter32,
   sispm1040582lrtDHCPSnoopingTxLeaseUnassigned      Counter32,
   sispm1040582lrtDHCPSnoopingTxLeaseUnknown         Counter32,
   sispm1040582lrtDHCPSnoopingTxLeaseActive          Counter32,
   sispm1040582lrtDHCPSnoopingRxDiscardedChecksumError  Counter32,
   sispm1040582lrtDHCPSnoopingRxDiscardedFromUntrusted  Counter32
}

sispm1040582lrtDHCPSnoopingStatisticsPort OBJECT-TYPE
   SYNTAX      Integer32(1..4095)
   MAX-ACCESS  not-accessible
   STATUS      current
   DESCRIPTION
       " "
   ::= { sispm1040582lrtDHCPSnoopingStatisticsEntry 1 }

sispm1040582lrtDHCPSnoopingStatisticsClear OBJECT-TYPE
   SYNTAX      Integer32 (0|1)
   MAX-ACCESS  read-write
   STATUS      current
   DESCRIPTION
       "default: 0
       0: none
       1: clear"
   ::= { sispm1040582lrtDHCPSnoopingStatisticsEntry 2 }

sispm1040582lrtDHCPSnoopingRxDiscover OBJECT-TYPE
   SYNTAX      Counter32
   MAX-ACCESS  read-only
   STATUS      current
   DESCRIPTION
       " "
   ::= { sispm1040582lrtDHCPSnoopingStatisticsEntry 3 }

sispm1040582lrtDHCPSnoopingRxOffer OBJECT-TYPE
   SYNTAX      Counter32
   MAX-ACCESS  read-only
   STATUS      current
   DESCRIPTION
       " "
   ::= { sispm1040582lrtDHCPSnoopingStatisticsEntry 4 }

sispm1040582lrtDHCPSnoopingRxRequest OBJECT-TYPE
   SYNTAX      Counter32
   MAX-ACCESS  read-only
   STATUS      current
   DESCRIPTION
       " "
   ::= { sispm1040582lrtDHCPSnoopingStatisticsEntry 5 }

sispm1040582lrtDHCPSnoopingRxDecline OBJECT-TYPE
   SYNTAX      Counter32
   MAX-ACCESS  read-only
   STATUS      current
   DESCRIPTION
       " "
   ::= { sispm1040582lrtDHCPSnoopingStatisticsEntry 6 }

sispm1040582lrtDHCPSnoopingRxACK OBJECT-TYPE
   SYNTAX      Counter32
   MAX-ACCESS  read-only
   STATUS      current
   DESCRIPTION
       " "
   ::= { sispm1040582lrtDHCPSnoopingStatisticsEntry 7 }

sispm1040582lrtDHCPSnoopingRxNAK OBJECT-TYPE
   SYNTAX      Counter32
   MAX-ACCESS  read-only
   STATUS      current
   DESCRIPTION
       " "
   ::= { sispm1040582lrtDHCPSnoopingStatisticsEntry 8 }

sispm1040582lrtDHCPSnoopingRxRelease OBJECT-TYPE
   SYNTAX      Counter32
   MAX-ACCESS  read-only
   STATUS      current
   DESCRIPTION
       " "
   ::= { sispm1040582lrtDHCPSnoopingStatisticsEntry 9 }

sispm1040582lrtDHCPSnoopingRxInform OBJECT-TYPE
   SYNTAX      Counter32
   MAX-ACCESS  read-only
   STATUS      current
   DESCRIPTION
       " "
   ::= { sispm1040582lrtDHCPSnoopingStatisticsEntry 10 }

sispm1040582lrtDHCPSnoopingRxLeaseQuery OBJECT-TYPE
   SYNTAX      Counter32
   MAX-ACCESS  read-only
   STATUS      current
   DESCRIPTION
       " "
   ::= { sispm1040582lrtDHCPSnoopingStatisticsEntry 11 }

sispm1040582lrtDHCPSnoopingRxLeaseUnassigned OBJECT-TYPE
   SYNTAX      Counter32
   MAX-ACCESS  read-only
   STATUS      current
   DESCRIPTION
       " "
   ::= { sispm1040582lrtDHCPSnoopingStatisticsEntry 12 }

sispm1040582lrtDHCPSnoopingRxLeaseUnknown OBJECT-TYPE
   SYNTAX      Counter32
   MAX-ACCESS  read-only
   STATUS      current
   DESCRIPTION
       " "
   ::= { sispm1040582lrtDHCPSnoopingStatisticsEntry 13 }

sispm1040582lrtDHCPSnoopingRxLeaseActive OBJECT-TYPE
   SYNTAX      Counter32
   MAX-ACCESS  read-only
   STATUS      current
   DESCRIPTION
       " "
   ::= { sispm1040582lrtDHCPSnoopingStatisticsEntry 14 }

sispm1040582lrtDHCPSnoopingTxDiscover OBJECT-TYPE
   SYNTAX      Counter32
   MAX-ACCESS  read-only
   STATUS      current
   DESCRIPTION
       " "
   ::= { sispm1040582lrtDHCPSnoopingStatisticsEntry 15 }

sispm1040582lrtDHCPSnoopingTxOffer OBJECT-TYPE
   SYNTAX      Counter32
   MAX-ACCESS  read-only
   STATUS      current
   DESCRIPTION
       " "
   ::= { sispm1040582lrtDHCPSnoopingStatisticsEntry 16 }

sispm1040582lrtDHCPSnoopingTxRequest OBJECT-TYPE
   SYNTAX      Counter32
   MAX-ACCESS  read-only
   STATUS      current
   DESCRIPTION
       " "
   ::= { sispm1040582lrtDHCPSnoopingStatisticsEntry 17 }

sispm1040582lrtDHCPSnoopingTxDecline OBJECT-TYPE
   SYNTAX      Counter32
   MAX-ACCESS  read-only
   STATUS      current
   DESCRIPTION
       " "
   ::= { sispm1040582lrtDHCPSnoopingStatisticsEntry 18 }

sispm1040582lrtDHCPSnoopingTxACK OBJECT-TYPE
   SYNTAX      Counter32
   MAX-ACCESS  read-only
   STATUS      current
   DESCRIPTION
       " "
   ::= { sispm1040582lrtDHCPSnoopingStatisticsEntry 19 }

sispm1040582lrtDHCPSnoopingTxNAK OBJECT-TYPE
   SYNTAX      Counter32
   MAX-ACCESS  read-only
   STATUS      current
   DESCRIPTION
       " "
   ::= { sispm1040582lrtDHCPSnoopingStatisticsEntry 20 }

sispm1040582lrtDHCPSnoopingTxRelease OBJECT-TYPE
   SYNTAX      Counter32
   MAX-ACCESS  read-only
   STATUS      current
   DESCRIPTION
       " "
   ::= { sispm1040582lrtDHCPSnoopingStatisticsEntry 21 }

sispm1040582lrtDHCPSnoopingTxInform OBJECT-TYPE
   SYNTAX      Counter32
   MAX-ACCESS  read-only
   STATUS      current
   DESCRIPTION
       " "
   ::= { sispm1040582lrtDHCPSnoopingStatisticsEntry 22 }

sispm1040582lrtDHCPSnoopingTxLeaseQuery OBJECT-TYPE
   SYNTAX      Counter32
   MAX-ACCESS  read-only
   STATUS      current
   DESCRIPTION
       " "
   ::= { sispm1040582lrtDHCPSnoopingStatisticsEntry 23 }

sispm1040582lrtDHCPSnoopingTxLeaseUnassigned OBJECT-TYPE
   SYNTAX      Counter32
   MAX-ACCESS  read-only
   STATUS      current
   DESCRIPTION
       " "
   ::= { sispm1040582lrtDHCPSnoopingStatisticsEntry 24 }

sispm1040582lrtDHCPSnoopingTxLeaseUnknown OBJECT-TYPE
   SYNTAX      Counter32
   MAX-ACCESS  read-only
   STATUS      current
   DESCRIPTION
       " "
   ::= { sispm1040582lrtDHCPSnoopingStatisticsEntry 25 }

sispm1040582lrtDHCPSnoopingTxLeaseActive OBJECT-TYPE
   SYNTAX      Counter32
   MAX-ACCESS  read-only
   STATUS      current
   DESCRIPTION
       " "
   ::= { sispm1040582lrtDHCPSnoopingStatisticsEntry 26 }

sispm1040582lrtDHCPSnoopingRxDiscardedChecksumError OBJECT-TYPE
   SYNTAX      Counter32
   MAX-ACCESS  read-only
   STATUS      current
   DESCRIPTION
       " "
   ::= { sispm1040582lrtDHCPSnoopingStatisticsEntry 27 }

sispm1040582lrtDHCPSnoopingRxDiscardedFromUntrusted OBJECT-TYPE
   SYNTAX      Counter32
   MAX-ACCESS  read-only
   STATUS      current
   DESCRIPTION
       " "
   ::= { sispm1040582lrtDHCPSnoopingStatisticsEntry 28 }

sispm1040582lrtDHCPRelay                                             OBJECT IDENTIFIER ::= { sispm1040582lrtSecurity 4 }

sispm1040582lrtDHCPRelayConfiguration                                         OBJECT IDENTIFIER ::= { sispm1040582lrtDHCPRelay 1 }

sispm1040582lrtDHCPRelayMode OBJECT-TYPE
   SYNTAX      Integer32(0|1)
   MAX-ACCESS  read-write
   STATUS      current
   DESCRIPTION
       "default: 0
       0: disable
       1: enable
       We need at least one server"
   ::= { sispm1040582lrtDHCPRelayConfiguration 1 }

sispm1040582lrtDHCPRelayServer OBJECT-TYPE
   SYNTAX      IpAddress
   MAX-ACCESS  read-write
   STATUS      current
   DESCRIPTION
       " "
   ::= { sispm1040582lrtDHCPRelayConfiguration 2 }

sispm1040582lrtDHCPRelayInformationMode OBJECT-TYPE
   SYNTAX      Integer32(0|1)
   MAX-ACCESS  read-write
   STATUS      current
   DESCRIPTION
       "default: 0
       0: disable
       1: enable "
   ::= { sispm1040582lrtDHCPRelayConfiguration 3 }

sispm1040582lrtDHCPRelayInformationPolicy OBJECT-TYPE
   SYNTAX      Integer32(0..2)
   MAX-ACCESS  read-write
   STATUS      current
   DESCRIPTION
       "default: 0
       0: replace
       1: keep
       2: drop "
   ::= { sispm1040582lrtDHCPRelayConfiguration 4 }

sispm1040582lrtDHCPRelayStatistics                                   OBJECT IDENTIFIER ::= { sispm1040582lrtDHCPRelay 2 }

sispm1040582lrtDHCPRelayServerStatistics                                   OBJECT IDENTIFIER ::= { sispm1040582lrtDHCPRelayStatistics 1 }

sispm1040582lrtServerStatTransmitToServer OBJECT-TYPE
   SYNTAX      Counter32
   MAX-ACCESS  read-only
   STATUS      current
   DESCRIPTION
       " "
   ::= { sispm1040582lrtDHCPRelayServerStatistics 1 }

sispm1040582lrtServerStatTransmitError OBJECT-TYPE
   SYNTAX      Counter32
   MAX-ACCESS  read-only
   STATUS      current
   DESCRIPTION
       " "
   ::= { sispm1040582lrtDHCPRelayServerStatistics 2 }

sispm1040582lrtServerStatReceiveFromServer OBJECT-TYPE
   SYNTAX      Counter32
   MAX-ACCESS  read-only
   STATUS      current
   DESCRIPTION
       " "
   ::= { sispm1040582lrtDHCPRelayServerStatistics 3 }

sispm1040582lrtServerStatReceiveMissingAgentOption OBJECT-TYPE
   SYNTAX      Counter32
   MAX-ACCESS  read-only
   STATUS      current
   DESCRIPTION
       " "
   ::= { sispm1040582lrtDHCPRelayServerStatistics 4 }

sispm1040582lrtServerStatReceiveMissingCircuitID OBJECT-TYPE
   SYNTAX      Counter32
   MAX-ACCESS  read-only
   STATUS      current
   DESCRIPTION
       " "
   ::= { sispm1040582lrtDHCPRelayServerStatistics 5 }

sispm1040582lrtServerStatReceiveMissingRemoteID OBJECT-TYPE
   SYNTAX      Counter32
   MAX-ACCESS  read-only
   STATUS      current
   DESCRIPTION
       " "
   ::= { sispm1040582lrtDHCPRelayServerStatistics 6 }

sispm1040582lrtServerStatReceiveBadCircuitID OBJECT-TYPE
   SYNTAX      Counter32
   MAX-ACCESS  read-only
   STATUS      current
   DESCRIPTION
       " "
   ::= { sispm1040582lrtDHCPRelayServerStatistics 7 }

sispm1040582lrtServerStatReceiveBadRemoteID OBJECT-TYPE
   SYNTAX      Counter32
   MAX-ACCESS  read-only
   STATUS      current
   DESCRIPTION
       " "
   ::= { sispm1040582lrtDHCPRelayServerStatistics 8 }

sispm1040582lrtDHCPRelayClientStatistics                                   OBJECT IDENTIFIER ::= { sispm1040582lrtDHCPRelayStatistics 2 }

sispm1040582lrtClientStatTransmitToClient OBJECT-TYPE
   SYNTAX      Counter32
   MAX-ACCESS  read-only
   STATUS      current
   DESCRIPTION
       " "
   ::= { sispm1040582lrtDHCPRelayClientStatistics 1 }

sispm1040582lrtClientStatTransmitError OBJECT-TYPE
   SYNTAX      Counter32
   MAX-ACCESS  read-only
   STATUS      current
   DESCRIPTION
       " "
   ::= { sispm1040582lrtDHCPRelayClientStatistics 2 }

sispm1040582lrtClientStatReceivefromClient OBJECT-TYPE
   SYNTAX      Counter32
   MAX-ACCESS  read-only
   STATUS      current
   DESCRIPTION
       " "
   ::= { sispm1040582lrtDHCPRelayClientStatistics 3 }

sispm1040582lrtClientStatReceiveAgentOption OBJECT-TYPE
   SYNTAX      Counter32
   MAX-ACCESS  read-only
   STATUS      current
   DESCRIPTION
       " "
   ::= { sispm1040582lrtDHCPRelayClientStatistics 4 }

sispm1040582lrtClientStatReplaceAgentOption OBJECT-TYPE
   SYNTAX      Counter32
   MAX-ACCESS  read-only
   STATUS      current
   DESCRIPTION
       " "
   ::= { sispm1040582lrtDHCPRelayClientStatistics 5 }

sispm1040582lrtClientStatKeepAgentOption OBJECT-TYPE
   SYNTAX      Counter32
   MAX-ACCESS  read-only
   STATUS      current
   DESCRIPTION
       " "
   ::= { sispm1040582lrtDHCPRelayClientStatistics 6 }

sispm1040582lrtClientStatDropAgentOption OBJECT-TYPE
   SYNTAX      Counter32
   MAX-ACCESS  read-only
   STATUS      current
   DESCRIPTION
       " "
   ::= { sispm1040582lrtDHCPRelayClientStatistics 7 }

sispm1040582lrtPortSecurity                                          OBJECT IDENTIFIER ::= { sispm1040582lrtSecurity 5 }

sispm1040582lrtPortSecLimitCtrl                                      OBJECT IDENTIFIER ::= { sispm1040582lrtPortSecurity 1 }

sispm1040582lrtPortSecLimitCtrlSystemConf                                      OBJECT IDENTIFIER ::= { sispm1040582lrtPortSecLimitCtrl 1 }

sispm1040582lrtPortSecurityMode OBJECT-TYPE
   SYNTAX      Integer32(0|1)
   MAX-ACCESS  read-write
   STATUS      current
   DESCRIPTION
       "default: 0
       0: disable
       1: enable "
   ::= { sispm1040582lrtPortSecLimitCtrlSystemConf 1 }

sispm1040582lrtPortSecurityAging OBJECT-TYPE
   SYNTAX      Integer32(0|1)
   MAX-ACCESS  read-write
   STATUS      current
   DESCRIPTION
       "default: 0
       0: disable
       1: enable "
   ::= { sispm1040582lrtPortSecLimitCtrlSystemConf 2 }

sispm1040582lrtPortSecurityAgingPeriod OBJECT-TYPE
   SYNTAX      Integer32(10..10000000)
   MAX-ACCESS  read-write
   STATUS      current
   DESCRIPTION
       "default: 3600, range: 10-10000000 "
   ::= { sispm1040582lrtPortSecLimitCtrlSystemConf 3 }

sispm1040582lrtPortSecLimitCtrlTable OBJECT-TYPE
   SYNTAX      SEQUENCE OF SISPM1040582LRTPortSecLimitCtrlEntry
   MAX-ACCESS  not-accessible
   STATUS      current
   DESCRIPTION
       " "
   ::= { sispm1040582lrtPortSecLimitCtrl 2 }

sispm1040582lrtPortSecLimitCtrlEntry OBJECT-TYPE
   SYNTAX      SISPM1040582LRTPortSecLimitCtrlEntry
   MAX-ACCESS  not-accessible
   STATUS      current
   DESCRIPTION
       " "
   INDEX    { sispm1040582lrtPortSecLimitCtrlPort  }
   ::= { sispm1040582lrtPortSecLimitCtrlTable 1 }

SISPM1040582LRTPortSecLimitCtrlEntry ::= SEQUENCE {
   sispm1040582lrtPortSecLimitCtrlPort           Integer32,
   sispm1040582lrtPortSecLimitCtrlPortMode       Integer32,
   sispm1040582lrtPortSecLimitCtrlPortLimit      Integer32,
   sispm1040582lrtPortSecLimitCtrlPortAction     Integer32,
   sispm1040582lrtPortSecLimitCtrlPortState      DisplayString,
   sispm1040582lrtPortSecLimitCtrlPortReOpen     Integer32,
   sispm1040582lrtPortSecLimitCtrlPortSticky     Integer32,
   sispm1040582lrtPortSecLimitCtrlPortClear      Integer32
}

sispm1040582lrtPortSecLimitCtrlPort OBJECT-TYPE
   SYNTAX      Integer32 (1..4095)
   MAX-ACCESS  not-accessible
   STATUS      current
   DESCRIPTION
       " "
   ::= { sispm1040582lrtPortSecLimitCtrlEntry 1 }

sispm1040582lrtPortSecLimitCtrlPortMode OBJECT-TYPE
   SYNTAX      Integer32 (0|1)
   MAX-ACCESS  read-write
   STATUS      current
   DESCRIPTION
       "default: 0
       0: disable
       1: enable"
   ::= { sispm1040582lrtPortSecLimitCtrlEntry 2 }

sispm1040582lrtPortSecLimitCtrlPortLimit OBJECT-TYPE
   SYNTAX      Integer32(1..1024)
   MAX-ACCESS  read-write
   STATUS      current
   DESCRIPTION
       "default: 4, range: 1-1024"
   ::= { sispm1040582lrtPortSecLimitCtrlEntry 3 }

sispm1040582lrtPortSecLimitCtrlPortAction OBJECT-TYPE
   SYNTAX      Integer32(0..3)
   MAX-ACCESS  read-write
   STATUS      current
   DESCRIPTION
       "default: 0
       0: none
       1: trap
       2: shutdown
       3: trap&shutdown"
   ::= { sispm1040582lrtPortSecLimitCtrlEntry 4 }

sispm1040582lrtPortSecLimitCtrlPortState OBJECT-TYPE
   SYNTAX      DisplayString
   MAX-ACCESS  read-only
   STATUS      current
   DESCRIPTION
       " "
   ::= { sispm1040582lrtPortSecLimitCtrlEntry 5 }

sispm1040582lrtPortSecLimitCtrlPortReOpen OBJECT-TYPE
   SYNTAX      Integer32 (0|1)
   MAX-ACCESS  read-write
   STATUS      current
   DESCRIPTION
       "default: 0
       0: none
       1: reopen"
   ::= { sispm1040582lrtPortSecLimitCtrlEntry 6 }

sispm1040582lrtPortSecLimitCtrlPortSticky OBJECT-TYPE
   SYNTAX      Integer32 (0|1)
   MAX-ACCESS  read-write
   STATUS      current
   DESCRIPTION
       "default: 0
       0: disable
       1: enable"
   ::= { sispm1040582lrtPortSecLimitCtrlEntry 7 }

sispm1040582lrtPortSecLimitCtrlPortClear OBJECT-TYPE
   SYNTAX      Integer32 (0|1)
   MAX-ACCESS  read-write
   STATUS      current
   DESCRIPTION
       "default: 0
       1: clear"
   ::= { sispm1040582lrtPortSecLimitCtrlEntry 8 }
   
sispm1040582lrtPortSecSwitchStatusTable OBJECT-TYPE
   SYNTAX      SEQUENCE OF SISPM1040582LRTPortSecSwitchStatusEntry
   MAX-ACCESS  not-accessible
   STATUS      current
   DESCRIPTION
       " "
   ::= { sispm1040582lrtPortSecurity 2 }

sispm1040582lrtPortSecSwitchStatusEntry OBJECT-TYPE
   SYNTAX      SISPM1040582LRTPortSecSwitchStatusEntry
   MAX-ACCESS  not-accessible
   STATUS      current
   DESCRIPTION
       " "
   INDEX    { sispm1040582lrtPortSecSwitchStatusPort  }
   ::= { sispm1040582lrtPortSecSwitchStatusTable 1 }

SISPM1040582LRTPortSecSwitchStatusEntry ::= SEQUENCE {
   sispm1040582lrtPortSecSwitchStatusPort                Integer32,
   sispm1040582lrtPortSecSwitchStatusUsers               DisplayString,
   sispm1040582lrtPortSecSwitchStatusState               DisplayString,
   sispm1040582lrtPortSecSwitchStatusMACCountCurrent     Integer32,
   sispm1040582lrtPortSecSwitchStatusMACCountLimit       Integer32
}

sispm1040582lrtPortSecSwitchStatusPort OBJECT-TYPE
   SYNTAX      Integer32 (1..4095)
   MAX-ACCESS  not-accessible
   STATUS      current
   DESCRIPTION
       " "
   ::= { sispm1040582lrtPortSecSwitchStatusEntry 1 }

sispm1040582lrtPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { sispm1040582lrtPortSecSwitchStatusEntry 2 }

sispm1040582lrtPortSecSwitchStatusState OBJECT-TYPE
   SYNTAX      DisplayString
   MAX-ACCESS  read-only
   STATUS      current
   DESCRIPTION
       " Shows the current state of the port : Disabled, Ready, Limit Reached, Shutdown. "
   ::= { sispm1040582lrtPortSecSwitchStatusEntry 3 }

sispm1040582lrtPortSecSwitchStatusMACCountCurrent OBJECT-TYPE
   SYNTAX      Integer32 (1..4095)
   MAX-ACCESS  read-only
   STATUS      current
   DESCRIPTION
       " "
   ::= { sispm1040582lrtPortSecSwitchStatusEntry 4 }

sispm1040582lrtPortSecSwitchStatusMACCountLimit OBJECT-TYPE
   SYNTAX      Integer32(1..4095)
   MAX-ACCESS  read-only
   STATUS      current
   DESCRIPTION
       " "
   ::= { sispm1040582lrtPortSecSwitchStatusEntry 5 }

sispm1040582lrtPortSecPortStatus                                      OBJECT IDENTIFIER ::= { sispm1040582lrtPortSecurity 3 }

sispm1040582lrtPortSecPortStatusPort OBJECT-TYPE
   SYNTAX       Integer32 (1..4095)
   MAX-ACCESS   read-write
   STATUS       current
   DESCRIPTION
       "port number
        default: 1
        range: 1 - port number."
   ::= { sispm1040582lrtPortSecPortStatus 1 }

sispm1040582lrtPortSecPortStatusTable OBJECT-TYPE
   SYNTAX      SEQUENCE OF SISPM1040582LRTPortSecPortStatusEntry
   MAX-ACCESS  not-accessible
   STATUS      current
   DESCRIPTION
      " "
   ::= { sispm1040582lrtPortSecPortStatus 2 }

sispm1040582lrtPortSecPortStatusEntry OBJECT-TYPE
   SYNTAX      SISPM1040582LRTPortSecPortStatusEntry
   MAX-ACCESS  not-accessible
   STATUS      current
   DESCRIPTION
       " "
   INDEX    { sispm1040582lrtPortSecPortStatusIndex  }
   ::= { sispm1040582lrtPortSecPortStatusTable 1 }

SISPM1040582LRTPortSecPortStatusEntry ::= SEQUENCE {
   sispm1040582lrtPortSecPortStatusIndex              Integer32,
   sispm1040582lrtPortSecPortStatusMACAddress         MacAddress,
   sispm1040582lrtPortSecPortStatusVLANId             Integer32,
   sispm1040582lrtPortSecPortStatusState              DisplayString,
   sispm1040582lrtPortSecPortStatusTimeOfAddition     DisplayString,
   sispm1040582lrtPortSecPortStatusAgeAndHold         DisplayString
}

sispm1040582lrtPortSecPortStatusIndex OBJECT-TYPE
   SYNTAX      Integer32(1..4095)
   MAX-ACCESS  not-accessible
   STATUS      current
   DESCRIPTION
       " "
   ::= { sispm1040582lrtPortSecPortStatusEntry 1 }

sispm1040582lrtPortSecPortStatusMACAddress OBJECT-TYPE
   SYNTAX      MacAddress
   MAX-ACCESS  read-only
   STATUS      current
   DESCRIPTION
       " "
   ::= { sispm1040582lrtPortSecPortStatusEntry 2 }

sispm1040582lrtPortSecPortStatusVLANId OBJECT-TYPE
   SYNTAX      Integer32(1..4094)
   MAX-ACCESS  read-only
   STATUS      current
   DESCRIPTION
       " "
   ::= { sispm1040582lrtPortSecPortStatusEntry 3 }

sispm1040582lrtPortSecPortStatusState OBJECT-TYPE
   SYNTAX      DisplayString
   MAX-ACCESS  read-only
   STATUS      current
   DESCRIPTION
       "Blocked / Forwarding "
   ::= { sispm1040582lrtPortSecPortStatusEntry 4 }

sispm1040582lrtPortSecPortStatusTimeOfAddition OBJECT-TYPE
   SYNTAX      DisplayString
   MAX-ACCESS  read-only
   STATUS      current
   DESCRIPTION
       " "
   ::= { sispm1040582lrtPortSecPortStatusEntry 5 }

sispm1040582lrtPortSecPortStatusAgeAndHold OBJECT-TYPE
   SYNTAX      DisplayString
   MAX-ACCESS  read-only
   STATUS      current
   DESCRIPTION
       " "
   ::= { sispm1040582lrtPortSecPortStatusEntry 6 }


sispm1040582lrtAccessManagement                                      OBJECT IDENTIFIER ::= { sispm1040582lrtSecurity 6 }

sispm1040582lrtAccessMgmtConf                                         OBJECT IDENTIFIER ::= { sispm1040582lrtAccessManagement 1 }

sispm1040582lrtAccessMgmtStatistics                                   OBJECT IDENTIFIER ::= { sispm1040582lrtAccessManagement 2 }
--
-- =======================================================================================================================
-- Start sispm1040582lrtAccessManagement group
-- =======================================================================================================================
--sispm1040582lrtAccessMgmtConf

    sispm1040582lrtAccessMgmtConfMode OBJECT-TYPE
               SYNTAX      AdminMode
               MAX-ACCESS  read-write
               STATUS      current
               DESCRIPTION
                   "Indicates the access management mode operation."
               DEFVAL  { disable }
               ::= {     sispm1040582lrtAccessMgmtConf 1 }

--sispm1040582lrtAccessMgmtConfTable

    sispm1040582lrtAccessMgmtConfTable OBJECT-TYPE
               SYNTAX      SEQUENCE OF     SISPM1040582LRTAccessMgmtConfEntry
               MAX-ACCESS  not-accessible
               STATUS      current
               DESCRIPTION
                   "The Access Mgmt Conf Table. "
               ::= {     sispm1040582lrtAccessMgmtConf 2 }

    sispm1040582lrtAccessMgmtConfEntry OBJECT-TYPE
               SYNTAX          SISPM1040582LRTAccessMgmtConfEntry
               MAX-ACCESS  not-accessible
               STATUS      current
               DESCRIPTION
                   "The Access Mgmt Conf Entry "
               INDEX    {    sispm1040582lrtAccessMgmtIndex  }
               ::= {     sispm1040582lrtAccessMgmtConfTable 1 }

    SISPM1040582LRTAccessMgmtConfEntry             ::= SEQUENCE {
                 sispm1040582lrtAccessMgmtIndex            Integer32,
                 sispm1040582lrtAccessMgmtVlanID           Integer32,
                 sispm1040582lrtAccessMgmtStartIpAddress   IpAddress,
                 sispm1040582lrtAccessMgmtEndIpAddress     IpAddress,
                 sispm1040582lrtAccessMgmtHttpHttps        AdminMode,
                 sispm1040582lrtAccessMgmtSNMP             AdminMode,
                 sispm1040582lrtAccessMgmtTelnetSSH        AdminMode,
                 sispm1040582lrtAccessMgmtRowStatus        RowStatus
                 }

    sispm1040582lrtAccessMgmtIndex OBJECT-TYPE
               SYNTAX      Integer32(1..16)
               MAX-ACCESS  not-accessible
               STATUS      current
               DESCRIPTION
                   "The Access Management config index.
                    range : 1-16."
               ::= {     sispm1040582lrtAccessMgmtConfEntry 1 }

    sispm1040582lrtAccessMgmtVlanID OBJECT-TYPE
               SYNTAX      Integer32 (1..4095)
               MAX-ACCESS  read-create
               STATUS      current
               DESCRIPTION
                   "The VLAN ID for the access management entry.
                    range: 1-4095."
               ::= {     sispm1040582lrtAccessMgmtConfEntry 2 }

    sispm1040582lrtAccessMgmtStartIpAddress OBJECT-TYPE
               SYNTAX      IpAddress
               MAX-ACCESS  read-create
               STATUS      current
               DESCRIPTION
                   "The start IP address for the access management
                    entry."
               ::= {     sispm1040582lrtAccessMgmtConfEntry 3 }

    sispm1040582lrtAccessMgmtEndIpAddress OBJECT-TYPE
               SYNTAX      IpAddress
               MAX-ACCESS  read-create
               STATUS      current
               DESCRIPTION
                   "The end IP address for the access management
                    entry. "
               ::= {     sispm1040582lrtAccessMgmtConfEntry 4 }

    sispm1040582lrtAccessMgmtHttpHttps OBJECT-TYPE
               SYNTAX      AdminMode
               MAX-ACCESS  read-create
               STATUS      current
               DESCRIPTION
                   "Indicates that the host can access the switch from
                    HTTP/HTTPS interface if the host IP address matches the IP
                    address range provided in the entry."
               DEFVAL  { disable }
               ::= {     sispm1040582lrtAccessMgmtConfEntry 5 }

    sispm1040582lrtAccessMgmtSNMP OBJECT-TYPE
               SYNTAX      AdminMode
               MAX-ACCESS  read-create
               STATUS      current
               DESCRIPTION
                   "Indicates that the host can access the switch from SNMP
                    interface if the host IP address matches the IP address
                    range provided in the entry."
               DEFVAL  { disable }
               ::= {     sispm1040582lrtAccessMgmtConfEntry 6 }

    sispm1040582lrtAccessMgmtTelnetSSH OBJECT-TYPE
               SYNTAX      AdminMode
               MAX-ACCESS  read-create
               STATUS      current
               DESCRIPTION
                   "Indicates that the host can access the switch from
                    TELNET/SSH interface if the host IP address matches
                    the IP address range provided in the entry."
               DEFVAL  { disable }
               ::= {     sispm1040582lrtAccessMgmtConfEntry 7 }

    sispm1040582lrtAccessMgmtRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sispm1040582lrtAccessMgmtConfEntry 8 }

--sispm1040582lrtAccessMgmtStatistics

    sispm1040582lrtAccessMgmtStatisticsClear OBJECT-TYPE
               SYNTAX      ActivateCmd
               MAX-ACCESS  read-write
               STATUS      current
               DESCRIPTION
                   "Clear all statistics."
               ::= {     sispm1040582lrtAccessMgmtStatistics 1 }

--sispm1040582lrtAccessMgmtStatisticsTable

    sispm1040582lrtAccessMgmtStatisticsTable OBJECT-TYPE
               SYNTAX      SEQUENCE OF     SISPM1040582LRTAccessMgmtStatisticsEntry
               MAX-ACCESS  not-accessible
               STATUS      current
               DESCRIPTION
                   "The Access Mgmt Statistics Table. "
               ::= {     sispm1040582lrtAccessMgmtStatistics 2 }

    sispm1040582lrtAccessMgmtStatisticsEntry OBJECT-TYPE
               SYNTAX          SISPM1040582LRTAccessMgmtStatisticsEntry
               MAX-ACCESS  not-accessible
               STATUS      current
               DESCRIPTION
                   "The Access Mgmt Statistics Entry. "
               INDEX    {    sispm1040582lrtAccessMgmtStatisticsInterface  }
               ::= {     sispm1040582lrtAccessMgmtStatisticsTable 1 }

    SISPM1040582LRTAccessMgmtStatisticsEntry ::= SEQUENCE {
                 sispm1040582lrtAccessMgmtStatisticsInterface         INTEGER,
                 sispm1040582lrtAccessMgmtStatisticsReceivedPackets   Integer32,
                 sispm1040582lrtAccessMgmtStatisticsAllowedPackets    Integer32,
                 sispm1040582lrtAccessMgmtStatisticsDiscardedPackets  Integer32
                 }

    sispm1040582lrtAccessMgmtStatisticsInterface OBJECT-TYPE
               SYNTAX      INTEGER { http(1), https(2), snmp(3), telnet(4), ssh (5) }
               MAX-ACCESS  not-accessible
               STATUS      current
               DESCRIPTION
                   "The interface type through which the remote host can
                    access the switch.
                    1: HTTP,
                    2: HTTPs,
                    3: SNMP,
                    4: TELNET,
                    5: SSH"
               ::= {     sispm1040582lrtAccessMgmtStatisticsEntry 1 }

    sispm1040582lrtAccessMgmtStatisticsReceivedPackets OBJECT-TYPE
               SYNTAX      Integer32(1..10000000)
               MAX-ACCESS  read-only
               STATUS      current
               DESCRIPTION
                   "Number of received packets from the interface when
                    access management mode is enabled. "
               ::= {     sispm1040582lrtAccessMgmtStatisticsEntry 2 }

    sispm1040582lrtAccessMgmtStatisticsAllowedPackets OBJECT-TYPE
               SYNTAX      Integer32(1..10000000)
               MAX-ACCESS  read-only
               STATUS      current
               DESCRIPTION
                   "Number of allowed packets from the interface when
                    access management mode is enabled. "
               ::= {     sispm1040582lrtAccessMgmtStatisticsEntry 3 }

    sispm1040582lrtAccessMgmtStatisticsDiscardedPackets OBJECT-TYPE
               SYNTAX      Integer32(1..10000000)
               MAX-ACCESS  read-only
               STATUS      current
               DESCRIPTION
                   "Number of discarded packets from the interface when
                    access management mode is enabled. "
               ::= {     sispm1040582lrtAccessMgmtStatisticsEntry 4 }

-- =======================================================================================================================

--sispm1040582lrtSSH                                                   OBJECT IDENTIFIER ::= { sispm1040582lrtSecurity 7 }
--
--sispm1040582lrtSSHMode OBJECT-TYPE
--   SYNTAX      Integer32(0|1)
--   MAX-ACCESS  read-write
--   STATUS      current
--   DESCRIPTION
--       "default: 1
--        0: disable
--        1: enable"
--   ::= { sispm1040582lrtSSH 1 }
--
--sispm1040582lrtSSHPort OBJECT-TYPE
--   SYNTAX      Integer32(1..65534)
--   MAX-ACCESS  read-write
--   STATUS      current
--   DESCRIPTION
--       "SSH service port number.
--        range : 1-65534, default : 22."
--   ::= { sispm1040582lrtSSH 2 }

sispm1040582lrtHTTPS                                                 OBJECT IDENTIFIER ::= { sispm1040582lrtSecurity 8 }

--sispm1040582lrtHTTPSMode OBJECT-TYPE
--   SYNTAX      Integer32(0|1)
--   MAX-ACCESS  read-write
--   STATUS      current
--   DESCRIPTION
--       "default: 1
--        0: disable
--        1: enable"
--   ::= { sispm1040582lrtHTTPS 1 }
--
--sispm1040582lrtHTTPSAutoRedirect OBJECT-TYPE
--   SYNTAX      Integer32(0|1)
--   MAX-ACCESS  read-write
--   STATUS      current
--   DESCRIPTION
--       "default: 0
--        0: disable
--        1: enable"
--   ::= { sispm1040582lrtHTTPS 2 }
--
--sispm1040582lrtHTTPSPort OBJECT-TYPE
--   SYNTAX      Integer32(1..65534)
--   MAX-ACCESS  read-write
--   STATUS      current
--   DESCRIPTION
--       "HTTPS service port number.
--        range : 1-65534, default : 443."
--   ::= { sispm1040582lrtHTTPS 3 }

sispm1040582lrtHTTPSCertificateMaintain OBJECT-TYPE
   SYNTAX      Integer32(2..3)
   MAX-ACCESS  read-write
   STATUS      current
   DESCRIPTION
       "2: Upload
		3: Generate"
   ::= { sispm1040582lrtHTTPS 4 }

sispm1040582lrtHTTPSCertificatePassPhrase OBJECT-TYPE
   SYNTAX      DisplayString
   MAX-ACCESS  read-write
   STATUS      current
   DESCRIPTION
       "Enter the pass phrase in this field if your uploading certificate is protected by a specific passphrase."
   ::= { sispm1040582lrtHTTPS 5 }
   
sispm1040582lrtHTTPSCertificateUpload OBJECT-TYPE
   SYNTAX      Integer32(0|1)
   MAX-ACCESS  read-write
   STATUS      current
   DESCRIPTION
       "default: 0
        0: TFTP
        1: URL"
   ::= { sispm1040582lrtHTTPS 6 }
   
sispm1040582lrtHTTPSFileUploadFileURL OBJECT-TYPE
   SYNTAX      DisplayString
   MAX-ACCESS  read-write
   STATUS      current
   DESCRIPTION
       "TFTP: filename
	    URL: URL"
   ::= { sispm1040582lrtHTTPS 7 }
   
sispm1040582lrtHTTPSFileUploadTFTPServer OBJECT-TYPE
   SYNTAX       IpAddress
   MAX-ACCESS   read-write
   STATUS       current
   DESCRIPTION
		"TFTP server IP address"
   ::= { sispm1040582lrtHTTPS 8 }
   
sispm1040582lrtHTTPSApply OBJECT-TYPE
   SYNTAX      Integer32(0|1)
   MAX-ACCESS  read-write
   STATUS      current
   DESCRIPTION
       "1: apply the above https settings"
   ::= { sispm1040582lrtHTTPS 9 }
   
sispm1040582lrtHTTPSCertificateStatus OBJECT-TYPE
   SYNTAX      DisplayString
   MAX-ACCESS  read-only
   STATUS      current
   DESCRIPTION
       "Display the current status of certificate on the switch."
   ::= { sispm1040582lrtHTTPS 10 }   

sispm1040582lrtAuthMethod                                            OBJECT IDENTIFIER ::= { sispm1040582lrtSecurity 9 }

--
-- =======================================================================================================================
-- Start sispm1040582lrtAuthMethodConfig group
-- =======================================================================================================================
--sispm1040582lrtAuthMethodConfigTable

    sispm1040582lrtAuthMethodConfigTable OBJECT-TYPE
               SYNTAX      SEQUENCE OF     SISPM1040582LRTAuthMethodConfigEntry
               MAX-ACCESS  not-accessible
               STATUS      current
               DESCRIPTION
                   "The Auth Method Config Table."
               ::= {     sispm1040582lrtAuthMethod 1 }

    sispm1040582lrtAuthMethodConfigEntry OBJECT-TYPE
               SYNTAX          SISPM1040582LRTAuthMethodConfigEntry
               MAX-ACCESS  not-accessible
               STATUS      current
               DESCRIPTION
                   "The Auth Method Config Entry."
               INDEX    {    sispm1040582lrtAuthMethodConfigClient  }
               ::= {     sispm1040582lrtAuthMethodConfigTable 1 }

    SISPM1040582LRTAuthMethodConfigEntry             ::= SEQUENCE {
                 sispm1040582lrtAuthMethodConfigClient        INTEGER,
                 sispm1040582lrtAuthMethodConfigMethod1       INTEGER,
                 sispm1040582lrtAuthMethodConfigMethod2       INTEGER,
                 sispm1040582lrtAuthMethodConfigMethod3       INTEGER,
                 sispm1040582lrtAuthMethodConfigMethod4       INTEGER,
                 sispm1040582lrtAuthMethodConfigServicePort   Integer32,
                 sispm1040582lrtAuthMethodConfigFallback      Integer32
                 }

    sispm1040582lrtAuthMethodConfigClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sispm1040582lrtAuthMethodConfigEntry 1 }

    sispm1040582lrtAuthMethodConfigMethod1 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm1040582lrtAuthMethodConfigEntry 2 }

    sispm1040582lrtAuthMethodConfigMethod2 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm1040582lrtAuthMethodConfigEntry 3 }

    sispm1040582lrtAuthMethodConfigMethod3 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm1040582lrtAuthMethodConfigEntry 4 }

    sispm1040582lrtAuthMethodConfigMethod4 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm1040582lrtAuthMethodConfigEntry 5 }
               
    sispm1040582lrtAuthMethodConfigServicePort OBJECT-TYPE
               SYNTAX      Integer32 (1..65535)
               MAX-ACCESS  read-write
               STATUS      current
               DESCRIPTION
                   "The network port number this client bound to provide service."
               ::= {     sispm1040582lrtAuthMethodConfigEntry 6 }   

    sispm1040582lrtAuthMethodConfigFallback OBJECT-TYPE
               SYNTAX      Integer32 (0..1)
               MAX-ACCESS  read-write
               STATUS      current
               DESCRIPTION
                   "Enable/Disable fallback to local authentication
                   0:Disable
                   1:Enable"
               ::= {     sispm1040582lrtAuthMethodConfigEntry 7 }                 

               
    sispm1040582lrtCommandAuthorizationMethodTable OBJECT-TYPE
               SYNTAX      SEQUENCE OF     SISPM1040582LRTCommandAuthorizationMethodEntry
               MAX-ACCESS  not-accessible
               STATUS      current
               DESCRIPTION
                   "The Command Authorized Method Config Table."
               ::= {     sispm1040582lrtAuthMethod 2 }

    sispm1040582lrtCommandAuthorizationMethodEntry OBJECT-TYPE
               SYNTAX          SISPM1040582LRTCommandAuthorizationMethodEntry
               MAX-ACCESS  not-accessible
               STATUS      current
               DESCRIPTION
                   "The Command Authorized Method Config Entry."
               INDEX    {    sispm1040582lrtCommandAuthorizationMethodClient  }
               ::= {     sispm1040582lrtCommandAuthorizationMethodTable 1 }

    SISPM1040582LRTCommandAuthorizationMethodEntry             ::= SEQUENCE {
                 sispm1040582lrtCommandAuthorizationMethodClient       INTEGER,
                 sispm1040582lrtCommandAuthorizationMethodMethod       Integer32,
                 sispm1040582lrtCommandAuthorizationMethodCmdLvl       Integer32,
                 sispm1040582lrtCommandAuthorizationMethodCfgCmd       Integer32,
                 sispm1040582lrtCommandAuthorizationMethodFallback     Integer32
                 }

    sispm1040582lrtCommandAuthorizationMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sispm1040582lrtCommandAuthorizationMethodEntry 1 }

    sispm1040582lrtCommandAuthorizationMethodMethod OBJECT-TYPE
               SYNTAX      Integer32
               MAX-ACCESS  read-write
               STATUS      current
               DESCRIPTION
                   "Method can be set to one of the following values:
                    0:no: Command authorization is disabled. 
					  User is granted access to CLI commands according to his privilege level.
                    3:tacacs: Use remote TACACS+ server(s) for command authorization. 
					  If all remote servers are offline, the user is granted access to CLI commands
					  according to his privilege level."
               ::= {     sispm1040582lrtCommandAuthorizationMethodEntry 2 }

    sispm1040582lrtCommandAuthorizationMethodCmdLvl OBJECT-TYPE
               SYNTAX      Integer32
               MAX-ACCESS  read-write
               STATUS      current
               DESCRIPTION
                   "Authorize all commands with a privilege level higher than or equal to this level.
                    Valid values are in the range 0 to 15."
               ::= {     sispm1040582lrtCommandAuthorizationMethodEntry 3 }

    sispm1040582lrtCommandAuthorizationMethodCfgCmd OBJECT-TYPE
               SYNTAX      Integer32
               MAX-ACCESS  read-write
               STATUS      current
               DESCRIPTION
                   "Also authorize configuration commands.
				   0:Disable
				   1:Enable"
               ::= {     sispm1040582lrtCommandAuthorizationMethodEntry 4 }

    sispm1040582lrtCommandAuthorizationMethodFallback OBJECT-TYPE
               SYNTAX      Integer32
               MAX-ACCESS  read-write
               STATUS      current
               DESCRIPTION
                   "This function is an auxiliary function of Authorization.
				   0:Disable
				   1:Enable"
               ::= {     sispm1040582lrtCommandAuthorizationMethodEntry 5 }		   
               
    sispm1040582lrtAccountingMethodTable OBJECT-TYPE
               SYNTAX      SEQUENCE OF     SISPM1040582LRTAccountingMethodEntry
               MAX-ACCESS  not-accessible
               STATUS      current
               DESCRIPTION
                   "The Accounting Method Config Table."
               ::= {     sispm1040582lrtAuthMethod 3 }

    sispm1040582lrtAccountingMethodEntry OBJECT-TYPE
               SYNTAX          SISPM1040582LRTAccountingMethodEntry
               MAX-ACCESS  not-accessible
               STATUS      current
               DESCRIPTION
                   "The Accounting Method Config Entry."
               INDEX    {    sispm1040582lrtAccountingMethodClient  }
               ::= {     sispm1040582lrtAccountingMethodTable 1 }

    SISPM1040582LRTAccountingMethodEntry             ::= SEQUENCE {
                 sispm1040582lrtAccountingMethodClient       INTEGER,
                 sispm1040582lrtAccountingMethodMethod       Integer32,
                 sispm1040582lrtAccountingMethodCmdLvl       Integer32,
                 sispm1040582lrtAccountingMethodCfgCmd       Integer32
                 }

    sispm1040582lrtAccountingMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sispm1040582lrtAccountingMethodEntry 1 }

    sispm1040582lrtAccountingMethodMethod OBJECT-TYPE
               SYNTAX      Integer32
               MAX-ACCESS  read-write
               STATUS      current
               DESCRIPTION
                   "Method can be set to one of the following values:
                    0:no: Accounting is disabled.
                    3:tacacs: Use remote TACACS+ server(s) for accounting."
               ::= {     sispm1040582lrtAccountingMethodEntry 2 }

    sispm1040582lrtAccountingMethodCmdLvl OBJECT-TYPE
               SYNTAX      Integer32
               MAX-ACCESS  read-write
               STATUS      current
               DESCRIPTION
                   "Enable accounting of all commands with a privilege level higher than or equal to this level.
                    Valid values are in the range 0 to 15. Leave the field empty to disable command accounting."
               ::= {     sispm1040582lrtAccountingMethodEntry 3 }

    sispm1040582lrtAccountingMethodCfgCmd OBJECT-TYPE
               SYNTAX      Integer32
               MAX-ACCESS  read-write
               STATUS      current
               DESCRIPTION
                   "Enable exec (login) accounting.
				   0:Disable
				   1:Enable"
               ::= {     sispm1040582lrtAccountingMethodEntry 4 }			          

--sispm1040582lrtTELNET                                                 OBJECT IDENTIFIER ::= { sispm1040582lrtSecurity 10 }
--
--sispm1040582lrtTELNETPort OBJECT-TYPE
--   SYNTAX      Integer32(1..65534)
--   MAX-ACCESS  read-write
--   STATUS      current
--   DESCRIPTION
--       "TELNET service port number.
--        range : 1-65534, default : 23."
--   ::= { sispm1040582lrtTELNET 1 }
--
--sispm1040582lrtHTTP                                                   OBJECT IDENTIFIER ::= { sispm1040582lrtSecurity 11 }
--
--sispm1040582lrtHTTPPort OBJECT-TYPE
--   SYNTAX      Integer32(1..65534)
--   MAX-ACCESS  read-write
--   STATUS      current
--   DESCRIPTION
--       "HTTP service port number.
--        range : 1-65534, default : 80."
--   ::= { sispm1040582lrtHTTP 1 }

-- =======================================================================================================================
sispm1040582lrtMaintenance                                           OBJECT IDENTIFIER ::= { sispm1040582lrtProductId 4 }

sispm1040582lrtSoftware                      OBJECT IDENTIFIER   ::= {  sispm1040582lrtMaintenance 3 }
sispm1040582lrtConfig                        OBJECT IDENTIFIER   ::= {  sispm1040582lrtMaintenance 4 }

--
-- =======================================================================================================================
-- Objects in the sispm1040582lrtMaintenance Group
-- =======================================================================================================================
    sispm1040582lrtRestartDevice OBJECT-TYPE
               SYNTAX      ActivateCmd
               MAX-ACCESS  read-write
               STATUS      current
               DESCRIPTION
                   "Command to restart the device."
               DEFVAL  { noAction }
               ::= {     sispm1040582lrtMaintenance 1 }

    sispm1040582lrtFactoryDefaults OBJECT-TYPE
               SYNTAX      ActivateCmd
               MAX-ACCESS  read-write
               STATUS      current
               DESCRIPTION
                   "Reset the configuration to Factory Defaults keep-ip."
               DEFVAL  { noAction }
               ::= {     sispm1040582lrtMaintenance 2 }

--sispm1040582lrtSoftware

    sispm1040582lrtSoftwareUsername OBJECT-TYPE
               SYNTAX       DisplayString
               MAX-ACCESS   read-write
               STATUS       current
               DESCRIPTION
                    "Get/Set the username for 'tftp' firmware upgrading."
               ::= {     sispm1040582lrtSoftware 1 }

    sispm1040582lrtSoftwarePassword OBJECT-TYPE
               SYNTAX       DisplayString
               MAX-ACCESS   read-write
               STATUS       current
               DESCRIPTION
                    "Get/Set the password for 'tftp' firmware upgrading."
               ::= {     sispm1040582lrtSoftware 2 }

    sispm1040582lrtSoftwareIpAddress OBJECT-TYPE
               SYNTAX       IpAddress
               MAX-ACCESS   read-write
               STATUS       current
               DESCRIPTION
                    "Get/Set the firmware tftp server."
               ::= {     sispm1040582lrtSoftware 3 }

    sispm1040582lrtSoftwareFileName OBJECT-TYPE
               SYNTAX       DisplayString
               MAX-ACCESS   read-write
               STATUS       current
               DESCRIPTION
                    "Get/Set the path and filename for firmware upgrading."
               ::= {     sispm1040582lrtSoftware 4 }

    sispm1040582lrtSoftwareUpgradeCmd OBJECT-TYPE
               SYNTAX       INTEGER  {  noAction ( 0 ),
                                        tftpUpgrade ( 1 ),
                                        ftpUpgrade ( 2 )
                                     }
               MAX-ACCESS   read-write
               STATUS       current
               DESCRIPTION
                    "Firmware upgrade command.
                     noAction(0) - do nothing   (read only).
                     tftpUpgrade(1) - activate 'tftp' firmware upgrade
                     ftpUpgrade(2) - activate 'ftp' firmware upgrade"

               DEFVAL  { noAction }
               ::= {     sispm1040582lrtSoftware 5 }

    sispm1040582lrtSoftwareImageSelectionCmd OBJECT-TYPE
               SYNTAX       ActivateCmd
               MAX-ACCESS   read-write
               STATUS       current
               DESCRIPTION
                    "Activate firmware image selection.
                     noAction(0) - do nothing - returned upon get.
                     activate(1) - activate firmware image selection."
               DEFVAL  { noAction }
               ::= {     sispm1040582lrtSoftware 6 }

    sispm1040582lrtSaveStartCmd OBJECT-TYPE
               SYNTAX      ActivateCmd
               MAX-ACCESS  read-write
               STATUS      current
               DESCRIPTION
                   "This copies running-config to startup-config,
                   thereby ensuring that the currently active
                   configuration will be used at the next reboot. "
               DEFVAL  { noAction }
               ::= {     sispm1040582lrtConfig 1 }

    sispm1040582lrtConfigUsername OBJECT-TYPE
               SYNTAX       DisplayString
               MAX-ACCESS   read-write
               STATUS       current
               DESCRIPTION
                    "Get/Set the username for 'tftp' 'upload config' or 'download config'."
               ::= {     sispm1040582lrtConfig 2 }

    sispm1040582lrtConfigPassword OBJECT-TYPE
               SYNTAX       DisplayString
               MAX-ACCESS   read-write
               STATUS       current
               DESCRIPTION
                    "Get/Set the password for 'tftp' 'upload config' or 'download config'."
               ::= {     sispm1040582lrtConfig 3 }

    sispm1040582lrtConfigIpAddress OBJECT-TYPE
               SYNTAX       IpAddress
               MAX-ACCESS   read-write
               STATUS       current
               DESCRIPTION
                    "Get/Set the IP address for 'tftp' 'upload config'
                    or 'download config'."
               ::= {     sispm1040582lrtConfig 4 }

    sispm1040582lrtConfigFilename OBJECT-TYPE
               SYNTAX       DisplayString
               MAX-ACCESS   read-write
               STATUS       current
               DESCRIPTION
                    "Get/Set the filename in switch for 'tftp'
                    'upload config' or 'download config'."
               ::= {     sispm1040582lrtConfig 5 }

    sispm1040582lrtConfigFileTable OBJECT-TYPE
               SYNTAX      SEQUENCE OF     SISPM1040582LRTConfigFileEntry
               MAX-ACCESS  not-accessible
               STATUS      current
               DESCRIPTION
                   "The config file tabe."
               ::= {     sispm1040582lrtConfig 6 }

    sispm1040582lrtConfigFileEntry OBJECT-TYPE
               SYNTAX          SISPM1040582LRTConfigFileEntry
               MAX-ACCESS  not-accessible
               STATUS      current
               DESCRIPTION
                   "an entry in the config file tabe."
               INDEX    {     sispm1040582lrtConfigFileIndex }
               ::= {     sispm1040582lrtConfigFileTable 1 }

    SISPM1040582LRTConfigFileEntry             ::= SEQUENCE {
                sispm1040582lrtConfigFileIndex         Integer32,
                sispm1040582lrtShowConfigFileName      DisplayString,
                sispm1040582lrtActivateConfigCmd       ActivateCmd,
                sispm1040582lrtDeleteConfigCmd         ActivateCmd,
                sispm1040582lrtUploadConfigCmd         INTEGER,
                sispm1040582lrtDownloadConfigCmd       INTEGER
                }

    sispm1040582lrtConfigFileIndex OBJECT-TYPE
               SYNTAX      Integer32(1..255)
               MAX-ACCESS  not-accessible
               STATUS      current
               DESCRIPTION
                   "The config file index."
               ::= {     sispm1040582lrtConfigFileEntry 1 }

    sispm1040582lrtShowConfigFileName OBJECT-TYPE
               SYNTAX      DisplayString
               MAX-ACCESS  read-write
               STATUS      current
               DESCRIPTION
                   "Shows the config file name. Without config filename:'NewConfig'
                   is temp file when 'activate upload
                   config' can 'create new file' and 'change create filename'."
               ::= {     sispm1040582lrtConfigFileEntry 2 }

    sispm1040582lrtActivateConfigCmd OBJECT-TYPE
               SYNTAX       ActivateCmd
               MAX-ACCESS   read-write
               STATUS       current
               DESCRIPTION
                    "Activate config command.
                     noAction(0) : do nothing  (read only).
                     activate(1) : activate the config"
               DEFVAL  { noAction }
               ::= {     sispm1040582lrtConfigFileEntry 3 }

    sispm1040582lrtDeleteConfigCmd OBJECT-TYPE
               SYNTAX       ActivateCmd
               MAX-ACCESS   read-write
               STATUS       current
               DESCRIPTION
                    "Delete config command.
                     noAction(0) : do nothing  (read only).
                     activate(1) : delete the config"
               DEFVAL  { noAction }
               ::= {     sispm1040582lrtConfigFileEntry 4 }

    sispm1040582lrtDownloadConfigCmd OBJECT-TYPE
               SYNTAX       INTEGER  {  noAction ( 0 ),
                                        tftpDownload ( 1 )
                                        --ftpDownload ( 2 )
                                     }
               MAX-ACCESS   read-write
               STATUS       current
               DESCRIPTION
                    "Download config command.
                     noAction   (0) - do nothing   (read only).
                     tftpDownload (1) - activate 'tftp' config download."
               DEFVAL  { noAction }
               ::= {     sispm1040582lrtConfigFileEntry 5 }

    sispm1040582lrtUploadConfigCmd OBJECT-TYPE
               SYNTAX       INTEGER  {  noAction ( 0 ),
                                        tftpUpload ( 1 )
                                        --ftpUpload ( 2 )
                                     }
               MAX-ACCESS   read-write
               STATUS       current
               DESCRIPTION
                    "Upload config command.
                     noAction   (0) - do nothing   (read only).
                     tftpUpload (1) - activate 'tftp' config upload.
					 For merge/replace running-config:
					 1:merge
					 3:replace"
               DEFVAL  { noAction }
               ::= {     sispm1040582lrtConfigFileEntry 6 }

-- =======================================================================================================================
sispm1040582lrtDiagnostics                                           OBJECT IDENTIFIER ::= { sispm1040582lrtMaintenance 5 }

sispm1040582lrtPingIpAddress OBJECT-TYPE
   SYNTAX      IpAddress
   MAX-ACCESS  read-write
   STATUS      current
   DESCRIPTION
       " The destination IP Address. "
   ::= { sispm1040582lrtDiagnostics 1 }

sispm1040582lrtPingSize OBJECT-TYPE
   SYNTAX      Integer32(60..1400)
   MAX-ACCESS  read-write
   STATUS      current
   DESCRIPTION
       " Size of ICMP echo packet.
         range : 60-1400, default : 64. "
   ::= { sispm1040582lrtDiagnostics 2 }

sispm1040582lrtDoPingConfig OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sispm1040582lrtDiagnostics 3 }

sispm1040582lrtPingResult OBJECT-TYPE
   SYNTAX      DisplayString
   MAX-ACCESS  read-only
   STATUS      current
   DESCRIPTION
       " Show ping result. "
   ::= { sispm1040582lrtDiagnostics 4 }

sispm1040582lrtPing6IpAddress OBJECT-TYPE
   SYNTAX      DisplayString
   MAX-ACCESS  read-write
   STATUS      current
   DESCRIPTION
       " The destination IPv6 Address. "
   ::= { sispm1040582lrtDiagnostics 5 }

sispm1040582lrtPing6Size OBJECT-TYPE
   SYNTAX      Integer32(60..1400)
   MAX-ACCESS  read-write
   STATUS      current
   DESCRIPTION
       " Size of ICMP echo packet.
         range : 60-1400. "
   ::= { sispm1040582lrtDiagnostics 6 }

sispm1040582lrtPing6EgressInterface OBJECT-TYPE
   SYNTAX      Integer32(1..4095)
   MAX-ACCESS  read-write
   STATUS      current
   DESCRIPTION
       "The VLAN ID (VID) of the specific egress IPv6 interface which ICMP packet goes."
   ::= { sispm1040582lrtDiagnostics 7 }
   
sispm1040582lrtDoPing6Config OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sispm1040582lrtDiagnostics 8 }

sispm1040582lrtPing6Result OBJECT-TYPE
   SYNTAX      DisplayString
   MAX-ACCESS  read-only
   STATUS      current
   DESCRIPTION
       " Show ping result. "
   ::= { sispm1040582lrtDiagnostics 9 }

sispm1040582lrttracerouteIpAddress OBJECT-TYPE
   SYNTAX      DisplayString
   MAX-ACCESS  read-write
   STATUS      current
   DESCRIPTION
       " The destination IP Address. "
   ::= { sispm1040582lrtDiagnostics 10 }

sispm1040582lrttracerouteProtocol OBJECT-TYPE
   SYNTAX      Integer32(0..2)
   MAX-ACCESS  read-write
   STATUS      current
   DESCRIPTION
       " Specify protocol including icmp=0, udp=1 and tcp=2.
         range : 0-2, default : 0. "
   ::= { sispm1040582lrtDiagnostics 11 }

sispm1040582lrttracerouteWaittime OBJECT-TYPE
   SYNTAX      Integer32(1..60)
   MAX-ACCESS  read-write
   STATUS      current
   DESCRIPTION
       " Specify wait time for waiting probe packets come back.
         range : 1-60(sec), default : 5(sec). "
   ::= { sispm1040582lrtDiagnostics 12 }

sispm1040582lrttracerouteMaxTTL OBJECT-TYPE
   SYNTAX      Integer32(1..255)
   MAX-ACCESS  read-write
   STATUS      current
   DESCRIPTION
       " Specify max TTL.
         range : 1-255, default : 30. "
   ::= { sispm1040582lrtDiagnostics 13 }

sispm1040582lrttracerouteNqueries OBJECT-TYPE
   SYNTAX      Integer32(1..10)
   MAX-ACCESS  read-write
   STATUS      current
   DESCRIPTION
       " Specify number of probe packets.
         range : 1-10, default : 3. "
   ::= { sispm1040582lrtDiagnostics 14 }

sispm1040582lrtDotracerouteConfig OBJECT-TYPE
   SYNTAX      Integer32(1)
   MAX-ACCESS  read-write
   STATUS      current
   DESCRIPTION
       "Do traceroute-config.
         Get this OID always return zero.
         1 - ping. Uses the traceroute program to get
         ip address of the middle gateway. "
   ::= { sispm1040582lrtDiagnostics 15 }

sispm1040582lrttracerouteResult OBJECT-TYPE
   SYNTAX      DisplayString
   MAX-ACCESS  read-only
   STATUS      current
   DESCRIPTION
       " Show traceroute result. "
   ::= { sispm1040582lrtDiagnostics 16 }

sispm1040582lrtCableDiagnostics                                           OBJECT IDENTIFIER ::= { sispm1040582lrtDiagnostics 17 }

sispm1040582lrtCableDiagnosticsTest OBJECT-TYPE
   SYNTAX      Integer32
   MAX-ACCESS  read-write
   STATUS      current
   DESCRIPTION
       "Run Cable Diagnostics.
        port, range : 1 - port number."
   ::= { sispm1040582lrtCableDiagnostics 1 }

sispm1040582lrtCableDiagnosticsTable OBJECT-TYPE
   SYNTAX      SEQUENCE OF SISPM1040582LRTCableDiagnosticsEntry
   MAX-ACCESS  not-accessible
   STATUS      current
   DESCRIPTION
       " "
   ::= { sispm1040582lrtCableDiagnostics 2 }

sispm1040582lrtCableDiagnosticsEntry OBJECT-TYPE
   SYNTAX      SISPM1040582LRTCableDiagnosticsEntry
   MAX-ACCESS  not-accessible
   STATUS      current
   DESCRIPTION
       " "
   INDEX    { sispm1040582lrtCableDiagnosticsPort  }
   ::= { sispm1040582lrtCableDiagnosticsTable 1 }

SISPM1040582LRTCableDiagnosticsEntry ::= SEQUENCE {
   sispm1040582lrtCableDiagnosticsPort        Integer32,
   sispm1040582lrtCableDiagnosticsLinkStatus  DisplayString,
   sispm1040582lrtCableDiagnosticsTestResult  DisplayString,
   sispm1040582lrtCableDiagnosticsLength      DisplayString
}

sispm1040582lrtCableDiagnosticsPort OBJECT-TYPE
   SYNTAX      Integer32
   MAX-ACCESS  not-accessible
   STATUS      current
   DESCRIPTION
       "port index"
   ::= { sispm1040582lrtCableDiagnosticsEntry 1 }

sispm1040582lrtCableDiagnosticsLinkStatus OBJECT-TYPE
   SYNTAX      DisplayString
   MAX-ACCESS  read-only
   STATUS      current
   DESCRIPTION
       "The status of the cable."
   ::= { sispm1040582lrtCableDiagnosticsEntry 2 }

sispm1040582lrtCableDiagnosticsTestResult OBJECT-TYPE
   SYNTAX      DisplayString
   MAX-ACCESS  read-only
   STATUS      current
   DESCRIPTION
       "Test Result of the cable."
   ::= { sispm1040582lrtCableDiagnosticsEntry 3 }

sispm1040582lrtCableDiagnosticsLength OBJECT-TYPE
   SYNTAX      DisplayString
   MAX-ACCESS  read-only
   STATUS      current
   DESCRIPTION
       "The length (in meters) of the cable."
   ::= { sispm1040582lrtCableDiagnosticsEntry 4 }

sispm1040582lrtSwitchRebootSchedule OBJECT IDENTIFIER ::= { sispm1040582lrtMaintenance 6 }   

sispm1040582lrtSwitchRebootMode OBJECT-TYPE
   SYNTAX      Integer32
   MAX-ACCESS  read-write
   STATUS      current
   DESCRIPTION
       "Switch Reboot Mode.
	    0:disable
		1:enable"
   ::= { sispm1040582lrtSwitchRebootSchedule 1 }

sispm1040582lrtSwitchRebootTimeTable OBJECT-TYPE
   SYNTAX      SEQUENCE OF SISPM1040582LRTSwitchRebootTimeEntry
   MAX-ACCESS  not-accessible
   STATUS      current
   DESCRIPTION
       " Configure the Switch reboot time. "
   ::= { sispm1040582lrtSwitchRebootSchedule 2 }

sispm1040582lrtSwitchRebootTimeEntry OBJECT-TYPE
   SYNTAX      SISPM1040582LRTSwitchRebootTimeEntry
   MAX-ACCESS  not-accessible
   STATUS      current
   DESCRIPTION
       " "
   INDEX    { sispm1040582lrtSwitchRebootWeekIndex  }
   ::= { sispm1040582lrtSwitchRebootTimeTable 1 }

SISPM1040582LRTSwitchRebootTimeEntry ::= SEQUENCE {
   sispm1040582lrtSwitchRebootWeekIndex	       Integer32,
   sispm1040582lrtSwitchRebootTimeHour           Integer32,
   sispm1040582lrtSwitchRebootTimeMinute         Integer32
}

sispm1040582lrtSwitchRebootWeekIndex OBJECT-TYPE
   SYNTAX      Integer32 (1..7)
   MAX-ACCESS  not-accessible
   STATUS      current
   DESCRIPTION
       "Switch reboot week index.
	   1: Sun, 2: Mon, 3:Tue, 4: Wed, 5: Thu, 6: Fri, 7: Sat"
   ::= { sispm1040582lrtSwitchRebootTimeEntry 1 }

sispm1040582lrtSwitchRebootTimeHour OBJECT-TYPE
   SYNTAX      Integer32 (-1..23)
   MAX-ACCESS  read-write
   STATUS      current
   DESCRIPTION
       "Switch Reboot Time (Hour). Range: 0-23. 
	   -1:disable"
   ::= { sispm1040582lrtSwitchRebootTimeEntry 2 }

sispm1040582lrtSwitchRebootTimeMinute OBJECT-TYPE
   SYNTAX      Integer32 (-1..55)
   MAX-ACCESS  read-write
   STATUS      current
   DESCRIPTION
       "Switch Reboot Time (Minute). Range:0,5,10,...,55. 
	   -1:disable"
   ::= { sispm1040582lrtSwitchRebootTimeEntry 3 }    

-- =======================================================================================================================
sispm1040582lrtTrap                                                  OBJECT IDENTIFIER ::= { sispm1040582lrtProductId 5 }

sispm1040582lrtTrapEvent                                             OBJECT IDENTIFIER ::= { sispm1040582lrtTrap 1 }

sispm1040582lrtTrapEventNotifications                                OBJECT IDENTIFIER ::= { sispm1040582lrtTrapEvent 0 }

sispm1040582lrtEmergency NOTIFICATION-TYPE
  OBJECTS   { sispm1040582lrtInformation }
  STATUS        current
    DESCRIPTION
        "The severity level is Emergency. Emergency conditions."
    ::= { sispm1040582lrtTrapEventNotifications 1 }

sispm1040582lrtAlert NOTIFICATION-TYPE
  OBJECTS   { sispm1040582lrtInformation }
  STATUS        current
    DESCRIPTION
        "The severity level is Alert. Alert conditions."
    ::= { sispm1040582lrtTrapEventNotifications 2 }

sispm1040582lrtCritical NOTIFICATION-TYPE
  OBJECTS   { sispm1040582lrtInformation }
  STATUS        current
    DESCRIPTION
        "The severity level is Critical. Critical conditions."
    ::= { sispm1040582lrtTrapEventNotifications 3 }

sispm1040582lrtError NOTIFICATION-TYPE
  OBJECTS   { sispm1040582lrtInformation }
  STATUS        current
    DESCRIPTION
        "The severity level is Error. Error conditions."
    ::= { sispm1040582lrtTrapEventNotifications 4 }

sispm1040582lrtWarning NOTIFICATION-TYPE
  OBJECTS   { sispm1040582lrtInformation }
  STATUS        current
    DESCRIPTION
        "The severity level is Warning. Warning conditions."
    ::= { sispm1040582lrtTrapEventNotifications 5 }

sispm1040582lrtNotice NOTIFICATION-TYPE
  OBJECTS   { sispm1040582lrtInformation }
  STATUS        current
    DESCRIPTION
        "The severity level is Notice. Notice conditions."
    ::= { sispm1040582lrtTrapEventNotifications 6 }

sispm1040582lrtInformational NOTIFICATION-TYPE
  OBJECTS   { sispm1040582lrtInformation }
  STATUS        current
    DESCRIPTION
        "The severity level is Informational. Informational conditions."
    ::= { sispm1040582lrtTrapEventNotifications 7 }

sispm1040582lrtDebug NOTIFICATION-TYPE
  OBJECTS   { sispm1040582lrtInformation }
  STATUS        current
    DESCRIPTION
        "The severity level is Debug. Debug conditions."
    ::= { sispm1040582lrtTrapEventNotifications 8 }

sispm1040582lrtTrapVariable                                          OBJECT IDENTIFIER ::= { sispm1040582lrtTrap 2 }

sispm1040582lrtInformation OBJECT-TYPE
    SYNTAX      DisplayString
    MAX-ACCESS  read-only
    STATUS      current
    DESCRIPTION
        "Trap information."
    ::= { sispm1040582lrtTrapVariable 1 }

sispm1040582lrtZTPTrap                                             OBJECT IDENTIFIER ::= { sispm1040582lrtTrap 3 }

sispm1040582lrtZTPTrapEvent                                        OBJECT IDENTIFIER ::= { sispm1040582lrtZTPTrap 0 }

sispm1040582lrtZTPOnboardTrap NOTIFICATION-TYPE
  OBJECTS   { sysObjectID, ipgs-2710atSnmpSystemVersion, ipgs-2710atSnmpSystemReadCommunity,
              ipgs-2710atSnmpSystemWriteCommunity, ipgs-2710atSystemInfoSerialNumber, 
              ipgs-2710atSystemInfoHostMACAddress, ipgs-2710atIPInterfacesIPv4Address }
  STATUS        current
    DESCRIPTION
        "The switch information."
    ::= { sispm1040582lrtZTPTrapEvent 1 }

END
