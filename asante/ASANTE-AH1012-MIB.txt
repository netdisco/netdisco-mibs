-- Title:	AsanteHub 1012 MIB

-- Date:	January 18, 1993 (Latest Revision)

-- Version:	2.1E



-- Information in this document is subject to change without notice

-- and does not represent a commitment on the part of

-- Asante Technologies, Inc.  No part of this document, or any

-- associated software, product design or design concept,

-- may be copied, reproduced or stored, in whole or in part, in any

-- form or by any means mechanical, electronic, optical, photocopying,

-- recording or otherwise, including translation to another language

-- or format, except for your own internal use, without the express

-- written consent of Asante Technologies, Inc.



-- The AsanteHub 1012 MIB is supplied "AS IS", and Asante Technologies,

-- Inc. makes no warranty, either express of implied, as to the use,

-- operation, condition, or performance of the AsanteHub 1012 MIB.



-- Copyright 1992 by Asante Technologies, Inc.  All rights reserved.











		ASANTE-AH1012-MIB

		DEFINITIONS ::= BEGIN

		IMPORTS                                                      

			private, NetworkAddress,                             
			IpAddress, Counter, Gauge, TimeTicks

			    FROM RFC1155-SMI                                 

			OBJECT-TYPE

			    FROM RFC-1212                                    

			TRAP-TYPE

			    FROM RFC-1215;

									     

		asante          OBJECT IDENTIFIER ::= { enterprises 298}

		DisplayString ::=                                            

			OCTET STRING

		-- This data type is used to model textual information       

		-- taken from the NVT ASCII character set.  By 

		-- convention, objects                                       

		-- with this syntax are declared as having                   

		--                                                           

		-- SIZE (0..255)

									     

		PhysAddress ::=                                              

			OCTET STRING                                         

		-- This data type is used to model media addresses.  For     

		-- many types of media, this will be in a binary             

		-- representation. For example, an ethernet address          

		-- would be represented as a string of 6 octets.

									     

	-- Asante Enterprise Specific Objects                                

	--


	products        OBJECT IDENTIFIER ::= { asante 1 }                   

	productId       OBJECT IDENTIFIER ::= { asante 2 }

	snmpAgent       OBJECT IDENTIFIER ::= { products 1 }                 

	adaptCard       OBJECT IDENTIFIER ::= { products 2 }                 

	concentrator    OBJECT IDENTIFIER ::= { products 3 }

	agentSw         OBJECT IDENTIFIER ::= { snmpAgent 1 }                

	agentFw         OBJECT IDENTIFIER ::= { snmpAgent 2 }                

	agentHw         OBJECT IDENTIFIER ::= { snmpAgent 3 }

	agentNetProtocol        OBJECT IDENTIFIER ::= { snmpAgent 5 }

	ipagentProtocol         OBJECT IDENTIFIER ::= { agentNetProtocol 1 } 

	concChassis             OBJECT IDENTIFIER ::= { concentrator 1 }     

	concConfiguration       OBJECT IDENTIFIER ::= { concentrator 2 }     

	concStatistics          OBJECT IDENTIFIER ::= { concentrator 3 }     

	concStateCtrl           OBJECT IDENTIFIER ::= { concentrator 4 }     

	concNodeMgt             OBJECT IDENTIFIER ::= { concentrator 5 }     

	concAlarmMgt            OBJECT IDENTIFIER ::= { concentrator 6 }     

	concBasicGrp            OBJECT IDENTIFIER ::= { concChassis 1 }      

	eSmartHubConfig         OBJECT IDENTIFIER ::= { concConfiguration 1 }

	eStatistics             OBJECT IDENTIFIER ::= { concStatistics 1 }   

	eStateCtrl              OBJECT IDENTIFIER ::= { concStateCtrl 1 }    

	eGlobalStatistics       OBJECT IDENTIFIER ::= { eStatistics 1 }      


	-- the agent network protocol stack capability map                   

									     

	agentNetProtoStkCapMap OBJECT-TYPE                                   

		SYNTAX  OCTET STRING(SIZE(1..4))                             

		ACCESS  read-only                                            

		STATUS  mandatory                                            

		DESCRIPTION                                                  

			"This octet string represents the current	     

			protocol stack configuration supported               

			by the agent, encoded as a bit string.               

			Each protocol stack is represented                   

			by a single bit. When the value of a                 

			bit = 1, it indicates that the protocol              

			stack on the agent represented by that               

			bit is supported; when zero, the protocol            

			stack is not supported.  The number of               

			octets in the string is always integer               

			multiple of the octet. The first protocol            

			stack will encode in the least significant           

			bit of the first octet.  Current, only               

			IP Stack(bit 0) and IPX Stack(bit 1) were            

			defined, all other bits should be zero."       

		::= { snmpAgent 4 }


	-- the agent Sw group                                                
									     

	agentRunTimeImageMajorVer OBJECT-TYPE                                

		SYNTAX  INTEGER                                              

		ACCESS  read-only                                            

		STATUS  mandatory                                            

		DESCRIPTION                                                  

			"The major software version number of the agent      

			run time image."     

		::= { agentSw 1 }                                            

									     

	agentRunTimeImageMinorVer OBJECT-TYPE                                

		SYNTAX  INTEGER                                              

		ACCESS  read-only                                            

		STATUS  mandatory                                            

		DESCRIPTION                                                  

			"The minor software version number of the agent      

			run time image."     

		::= { agentSw 2 }                                            

									     

	agentImageLoadMode OBJECT-TYPE                                       

		SYNTAX  INTEGER {                                            

			other(1),       -- Unknown                           

			localBoot(2),   -- Load image from local flash EEPROM

			netBoot(3)      -- Load image remotely from network  

			}                                                    

		ACCESS  read-write                                           

		STATUS  mandatory                                            

		DESCRIPTION                                                  

			"Tells hub whether the software image is to be      

			loaded from the FLASH EPROM or from over the network."

		::= { agentSw 3 }                                            

									     

	agentRemoteBootInfo OBJECT-TYPE                                      

		SYNTAX  INTEGER {                                            

			other(1),               -- use boot protocol         

			eepromBootInfo(2)       -- use EEPROM boot parameters

			}                                                    

		ACCESS  read-only                                            

		STATUS  mandatory                                            

		DESCRIPTION                                                  

			"The method for getting boot parameter information." 

		::= { agentSw 4 }

									     

	agentRemoteBootProtocol OBJECT-TYPE                                  

		SYNTAX  INTEGER {                                            

			other(1),       -- Unknown boot protocol             

			bootp-tftp(2),  -- use bootp-tftp protocol           

			tftp-only(3)    -- use tftp protocol                 

			}                                                    

		ACCESS  read-write                                           

		STATUS  mandatory                                            

		DESCRIPTION                                                  

			"The netboot protocol that used to load the     

			agent software."     

		::= { agentSw 5 }

									     

	agentRemoteBootFile OBJECT-TYPE                                      

		SYNTAX  OCTET STRING (SIZE(0..64))                           

		ACCESS  read-write                                           

		STATUS  mandatory                                            

		DESCRIPTION                                                  

			"The boot file name that is sent to the boot file    

			server by agent boot code during boot time."      

		::= { agentSw 6 }

									     

	agentOutBandDialString OBJECT-TYPE                                   

		SYNTAX  OCTET STRING (SIZE(0..64))                           

		ACCESS  read-write                                           

		STATUS  mandatory                                            

		DESCRIPTION                                                  

			"This is the initialization string used by the      

			Network Management station to establish the          

			out-of-band connection for modem only."      

		::= { agentSw 7 }                                            

									     

	agentOutBandBaudRate OBJECT-TYPE                                     

		SYNTAX  INTEGER {                                            

			other(1),       -- Unknown baud rate                 

			b1200(2),       -- 1200 baud rate                    

			b2400(3),       -- 2400 baud rate                    

			b4800(4),       -- 4800 baud rate                    

			b9600(5)        -- 9600 baud rate                    

			}                                                    

		ACCESS  read-write                                           

		STATUS  mandatory                                            

		DESCRIPTION                                                  

			"The baud rate setting for the out-of-band     

			port."     

		::= { agentSw 8 }

									     

	agentReset OBJECT-TYPE                                               

		SYNTAX  INTEGER {                                            

			other(1),       -- Unknown                           

			reset(2),       -- system reset                      

			not-reset(3)    -- normal operation                  

			}                                                    

		ACCESS  read-write                                           

		STATUS  mandatory                                            

		DESCRIPTION                                                  

			"The object to allow software to perform     

			 'push_button' system reset."     

		::= { agentSw 9 }

									     

	-- the agent Hw group

									     

	agentHwReVer OBJECT-TYPE                                             

		SYNTAX  INTEGER                                              

		ACCESS  read-only                                            

		STATUS  mandatory                                            

		DESCRIPTION                                                  

			"The hardware reversion number of the network     

			management module."     

		::= { agentHw 1 }

									     

	agentHwVer OBJECT-TYPE                                               

		SYNTAX  INTEGER                                              

		ACCESS  read-only                                            

		STATUS  mandatory                                            

		DESCRIPTION                                                  

			"The hardware model number of the network     

			management module"     

		::= { agentHw 2 }

									     

	-- the agent Fw group

									     

	agentFwMajorVer OBJECT-TYPE                                          

		SYNTAX  INTEGER                                              

		ACCESS  read-only                                            

		STATUS  mandatory                                            

		DESCRIPTION                                                  

			"The major firmware version number of the agent      

			prom code."     

		::= { agentFw 1 }

									     

	agentFwMinorVer OBJECT-TYPE                                          

		SYNTAX  INTEGER                                              

		ACCESS  read-only                                            

		STATUS  mandatory                                            

		DESCRIPTION                                                  

			"The minor firmware version number of the agent      

			 prom code."     

		::= { agentFw 2 }

									     

	-- the ipagent protocol group

									     

	ipagentIpAddr OBJECT-TYPE                                            

		SYNTAX  IpAddress                                            

		ACCESS  read-write                                           

		STATUS  mandatory                                            

		DESCRIPTION                                                  

			"The ipagent's administrative IP address.  The     

			current operational IP address can be obtained       

			from the ipAdEntAddr in the ipAddrTable.  This       

			parameter will take effect only after reset hub.     

			This parameter will always be updated in the         

			EEPROM."     

		::= { ipagentProtocol 1 }

									     

	ipagentIpNetMask OBJECT-TYPE                                         

		SYNTAX  IpAddress                                            

		ACCESS  read-write                                           

		STATUS  mandatory                                            

		DESCRIPTION                                                  

			"The ipagent's administrative IP subnet mask.  The   

			current operational IP subnet mask can be obtained   

			from the ipAdEntMask in the ipAddrTable.  This       

			parameter will take effect only after reset hub.     

			This parameter will always be updated in the         

			EEPROM."     

		::= { ipagentProtocol 2 }

									     

	ipagentDefaultGateway OBJECT-TYPE                                    

		SYNTAX  IpAddress                                            

		ACCESS  read-write                                           

		STATUS  mandatory                                            

		DESCRIPTION                                                  

			"The ipagent's administrative default gateway IP     

			address.  The current operational IP default         

			gateway IP address can be obtained from the          

			ipRouteDest in the ipRouteTable.  This parameter     

			will take effect only after reset hub.  This         

			parameter will always be updated in the EEPROM."     

		::= { ipagentProtocol 3 }

									     

	ipagentBootServerAddr OBJECT-TYPE                                    

		SYNTAX  IpAddress                                            

		ACCESS  read-write                                           

		STATUS  mandatory                                            

		DESCRIPTION                                                  

			"The IP address of the boot server that was used     

			for booting this ipagent. This parameter will        

			always be updated in the EEPROM."     

		::= { ipagentProtocol 4 }                                    

									     

	ipagentUnAuthIP OBJECT-TYPE                                          

		SYNTAX  IpAddress                                            

		ACCESS  read-only                                            

		STATUS  mandatory                                            

		DESCRIPTION                                                  

			"The IP address of the last station that tried to    

			access this ipagent with an invalid community        

			string."     

		::= { ipagentProtocol 5 }                                    

									     

	ipagentUnAuthComm OBJECT-TYPE                                        

		SYNTAX  OCTET STRING                                         

		ACCESS  read-only                                            

		STATUS  mandatory                                            

		DESCRIPTION                                                  

			"The community string of the last station that tried 

			to access this ipagent with an invalid community     

			string."     

		::= { ipagentProtocol 6 }                                    

									     

	-- the ipagent trap receive table group                              

									     

	ipagentTrapRcvrTable OBJECT-TYPE                                     

		SYNTAX  SEQUENCE OF IpagentTrapRcvrEntry                     

		ACCESS  not-accessible                                       

		STATUS  mandatory                                            

		DESCRIPTION                                                  

			"Table consisting of the list of Network Management  

			Stations that are to receive traps generated by this 

			agent."     

		::= { agentNetProtocol 2 }                                   

									     

	ipagentTrapRcvrEntry OBJECT-TYPE                                     

		SYNTAX  IpagentTrapRcvrEntry                                 

		ACCESS  not-accessible                                       

		STATUS  mandatory                                            

		DESCRIPTION                                                  

			"Destination IP address and community string for     

			a particular trap server. "     

		INDEX { ipagentTrapRcvrIpAddr }                              

		::= { ipagentTrapRcvrTable 1 }                               

									     

	IpagentTrapRcvrEntry ::= SEQUENCE {                                  

		ipagentTrapRcvrIpAddr                                        

			IpAddress,                                           

		ipagentTrapRcvrStatus                                        

			INTEGER,                                             

		ipagentTrapRcvrComm                                          

			OCTET STRING                                         

		}                                                            

									     

	ipagentTrapRcvrIpAddr OBJECT-TYPE                                    

		SYNTAX  IpAddress                                            

		ACCESS  read-only                                            

		STATUS  mandatory                                            

		DESCRIPTION                                                  

			"IP address for trap server receiving trap. "        

		::= { ipagentTrapRcvrEntry 1 }                                       

									     

	ipagentTrapRcvrStatus OBJECT-TYPE                                    

		SYNTAX  INTEGER {                                            

			other(1),                                            

			valid(2),                                            

			invalid(3)                                           

			}                                                    

		ACCESS  read-write                                           

		STATUS  mandatory                                            

		DESCRIPTION                                                  

			"Validation of individual trap receiver.  If value	     

		 	of this object is set to invalid(3), then that              

		 	particular entry is deemed invalid, meaning that            

		 	the address for that entry is no longer valid               

		 	because the entry has been removed from the table."     

		::= { ipagentTrapRcvrEntry 2 }

									     

	ipagentTrapRcvrComm OBJECT-TYPE                                      

		SYNTAX  OCTET STRING                                         

		ACCESS  read-write                                           

		STATUS  mandatory                                            

		DESCRIPTION                                                  

			"Community string for traps sent to this trap     

			receiver."     

		::= { ipagentTrapRcvrEntry 3 }

									     

	-- the concChassis group

									     

	concChassisType OBJECT-TYPE                                          

		SYNTAX  INTEGER {                                            

			other(1),                                            

			aH1012(2)   

			}                                                    

		ACCESS  read-only                                            

		STATUS  mandatory                                            

		DESCRIPTION                                                  

			"The concentrator's chassis type."                   

		::= { concBasicGrp 1 }

									     

	concChassisBkplType OBJECT-TYPE                                      

		SYNTAX  INTEGER {                                            

			other(1),                                            

			no-backplane(2)                                      

			}                                                    

		ACCESS  read-only                                            

		STATUS  mandatory                                            

		DESCRIPTION                                                  

			"The concentrator's chassis backplane type."         

		::= { concBasicGrp 2 }

									     

	concChassisBkplRev OBJECT-TYPE                                       

		SYNTAX  INTEGER                                              

		ACCESS  read-only                                            

		STATUS  mandatory                                            

		DESCRIPTION                                                  

			"The concentrator's chassis backplane      

			revision number."     

		::= { concBasicGrp 3 }

									     

	-- chassis power supply table group

									     

	concChassisPsTable OBJECT-TYPE                                       

		SYNTAX  SEQUENCE OF ConcChassisPsEntry                       

		ACCESS  not-accessible                                       

		STATUS  mandatory                                            

		DESCRIPTION                                                  

			"This table contains concentrator's power supply     

			information."      

		::= { concBasicGrp 4 }

									     

	concChassisPsEntry OBJECT-TYPE                                       

		SYNTAX  ConcChassisPsEntry                                   

		ACCESS  not-accessible                                       

		STATUS  mandatory                                            

		DESCRIPTION                                                  

			"The entry in the table containing the information   

			about a single power supply."     

		INDEX { concChassisPsIndex }                                 

		::= { concChassisPsTable 1 }

									     

	ConcChassisPsEntry ::= SEQUENCE {                                    

		concChassisPsIndex                                           

			INTEGER,                                             

		concChassisPsModuleType                                      

			INTEGER,                                             

		concChassisPsStatus                                          

			INTEGER                                              

		}

									     

	concChassisPsIndex OBJECT-TYPE                                       

		SYNTAX  INTEGER                                              

		ACCESS  read-only                                            

		STATUS  mandatory                                            

		DESCRIPTION                                                  

			"The value of this object identifies the     

			power supply table for which this entry              

			contains power supply type and status."      

		::= { concChassisPsEntry 1 }

									     

	concChassisPsModuleType OBJECT-TYPE                                  

		SYNTAX  INTEGER {                                            

			other(1)                                             

			}                                                    

		ACCESS  read-only                                            

		STATUS  mandatory                                            

		DESCRIPTION                                                  

			"The value of this object identifies the     

			power supply module type."     

		::= { concChassisPsEntry 2 }

									     

	concChassisPsStatus OBJECT-TYPE                                

		SYNTAX  INTEGER {                                            

			other(1),       -- unknown                           

			good(2),        -- power supply in good cond.        

			bad(3)          -- power supply in failed cond.      

			}                                                    

		ACCESS  read-only                                            

		STATUS  mandatory                                            

		DESCRIPTION                                                  

			"The value of this object identifies the     

			power supply module status." 

		::= { concChassisPsEntry 3 }

									     

	-- chassis fan

									     

	concChassisFanStatus OBJECT-TYPE                                     

		SYNTAX  INTEGER {                                            

			other(1),       -- unknown                           

			no-fan(2),      -- no fan is found at this model     

			good(3),        -- fan in good cond.                 

			bad(4)          -- fan in failed cond.               

			}                                                    

		ACCESS  read-only                                            

		STATUS  mandatory                                            

		DESCRIPTION                                                  

			"The value of this object identifies the     

			fan status."   

		::= { concBasicGrp 5 }

									     

	-- chassis group capacity

									     

	concChassisGroupCapacity OBJECT-TYPE                                 

		SYNTAX  INTEGER                                              

		ACCESS  read-only                                            

		STATUS  mandatory                                            

		DESCRIPTION                                                  

			"The number of groups that can be contained within   

			the concentrator. "     

		::= { concBasicGrp 6 }

									     

	concChassisGroupMap OBJECT-TYPE                                      

		SYNTAX  OCTET STRING                                         

		ACCESS  read-only                                            

		STATUS  mandatory                                            

		DESCRIPTION                                                  

			"This octet string represents the current     

			configuration of groups, encoded as a bit string,    

			each group is represented by a single bit."     

		::= { concBasicGrp 7 }

									     

	concChassisGrpTable OBJECT-TYPE                                      

		SYNTAX  SEQUENCE OF ConcChassisGrpEntry                      

		ACCESS  not-accessible                                       

		STATUS  mandatory                                            

		DESCRIPTION                                                  

			"A table that contains information about the     

			group/slot in this chassis."      

		::= { concBasicGrp 8 }

									     

	concChassisGrpEntry OBJECT-TYPE                                      

		SYNTAX  ConcChassisGrpEntry                                  

		ACCESS  not-accessible                                       

		STATUS  mandatory                                            

		DESCRIPTION                                                  

			"A list of information for each slot in this chassis."

		INDEX { concChassisGrpIndex }                                

		::= { concChassisGrpTable 1 }

									     

	ConcChassisGrpEntry ::= SEQUENCE {                                   

		concChassisGrpIndex                                          

			INTEGER,                                             

		concChassisGrpNumberPort                                     

			INTEGER,                                             

		concChassisGrpType                                           

			INTEGER,                                             

		concChassisGrpDescr                                          

			DisplayString,                                       

		concChassisGrpHwRev                                          

			INTEGER                                              

	}

									     

	concChassisGrpIndex OBJECT-TYPE                                      

		SYNTAX  INTEGER                                              

		ACCESS  read-only                                            

		STATUS  mandatory                                            

		DESCRIPTION                                                  

			"The value of this object identifies the    

			chassis group table for which this entry             

			contains group related information."     

		::= { concChassisGrpEntry 1 }

									     

	concChassisGrpNumberPort OBJECT-TYPE                                 

		SYNTAX  INTEGER                                              

		ACCESS  read-only                                            

		STATUS  mandatory                                            

		DESCRIPTION                                                  

			"The number of port is available for up/down link    

			within this group."     

		::= { concChassisGrpEntry 2 }

									     

	concChassisGrpType OBJECT-TYPE                                       

		SYNTAX  INTEGER                                              

		ACCESS  read-only                                            

		STATUS  mandatory                                            

		DESCRIPTION                                                  

			"The value represents the function of this group."   

		::= { concChassisGrpEntry 3 }

									     

	concChassisGrpDescr OBJECT-TYPE                                      

		SYNTAX  DisplayString                                        

		ACCESS  read-only                                            

		STATUS  mandatory                                            

		DESCRIPTION                                                  

			"A description of this group device."                

		::= { concChassisGrpEntry 4 }

									     

	concChassisGrpHwRev OBJECT-TYPE                                      

		SYNTAX  INTEGER                                              

		ACCESS  read-only                                            

		STATUS  mandatory                                            

		DESCRIPTION                                                  

			"The hardware revision number of this particular     

			group."     

		::= { concChassisGrpEntry 5 }

									     

	-- ConcConfiguration Group

									     

	eSmartHubId OBJECT-TYPE                                              

		SYNTAX  PhysAddress                                          

		ACCESS  read-only                                            

		STATUS  mandatory                                            

		DESCRIPTION                                                  

			"Hub MAC address (octet string) found from prom     

			chip in hub."     

		::= { eSmartHubConfig 1 }

									     

	eSmartHubAssignedId OBJECT-TYPE                                      

		SYNTAX  INTEGER                                              

		ACCESS  read-only                                            

		STATUS  mandatory                                            

		DESCRIPTION                                                  

			"Assigned hub ID for Out-of-Band."                   

		::= { eSmartHubConfig 2 }

									     

	eSmartHubTerSwitch OBJECT-TYPE                                       

		SYNTAX  INTEGER {                                            

			other(1),       -- unknown                           

			terminal(2),    -- switch is on terminal mode        

			pc-modem(3)     -- switch is on pc/modem mode        

			}                                                    

		ACCESS  read-only                                            

		STATUS  mandatory                                            

		DESCRIPTION                                                  

			"Status of position of PC/terminal switch located on 

			rear panel of hub.  Switches between serial and      

			parallel communications for modem/PC or terminal     

			connection to RS-232 Port.  Up (off) for PC,         

			down (on) for terminal.  If position of switch is    

			changed, there will be no change in this status      

			until hub is reset."     

		::= { eSmartHubConfig 3 }

									     

	-- Currently, this object does not allow user                        

	-- to set new value.

									     

	eSmartHubHwLoadPatStatus OBJECT-TYPE                                 

		SYNTAX  INTEGER                                              

		ACCESS  read-write                                           

		STATUS  mandatory                                            

		DESCRIPTION                                                  

			"Which logic configuration pattern is loaded into the

			Programmable Logic Device PLD."     

		::= { eSmartHubConfig 4 }

									     

	eSmartHubHwLoadPatCapacity OBJECT-TYPE                               

		SYNTAX  OCTET STRING                                         

		ACCESS  read-only                                            

		STATUS  mandatory                                            

		DESCRIPTION                                                  

			"What kind of function the PLD can perform."         

		::= { eSmartHubConfig 5 }

									     

	eSmartHubNodeAgeTimer OBJECT-TYPE                                    

		SYNTAX  INTEGER                                              

		ACCESS  read-write                                           

		STATUS  mandatory                                            

		DESCRIPTION                                                  

			"How long to keep node entry in node summary     

			table, measured in sec.  The maximum is 11 hours."     

		::= { eSmartHubConfig 6 }

									     

	eSmartHub3in1LnConStatus OBJECT-TYPE                                 

		SYNTAX  INTEGER {                                            

		      other(1),       -- BNC is connected or no connection 

		      uTP(2),         -- 10BASE-T port is connected        

		      aUI(3),         -- AUI port is connected             

		      uTP-and-AUI(4)  -- both 10-T and AUI ports are connected

									  

		}                                                            

		ACCESS  read-only                                            

		STATUS  mandatory                                            

		DESCRIPTION                                                  

			"Status of 3In1 Uplink which is located on rear     

			panel of hub.  Describes the physical link type      

			or types currently connected."     

		::= { eSmartHubConfig 7 }

									     

	eSmartHub3in1StateCtrl OBJECT-TYPE                                   

		SYNTAX  INTEGER {                                            

			other(1),       -- unknown                           

			uTP(2),         -- 10BASE-T port is selected         

			bNC(3),         -- BNC port is selected              

			aUI(4),         -- AUI port is selected              

			auto(5)         -- automatically switched            

		}                                                            

		ACCESS  read-write                                           

		STATUS  mandatory                                            

		DESCRIPTION                                                  

			"Whether using Auto-sense or manually selected a     

			particular media type for the uplink connection.  If 

			using Auto-sense it first tries AUI.  If             

			AUI is not present then 10T.  If neither AUI nor     

			10T is present, then it defaults to BNC."     

		::= { eSmartHubConfig 8 }

									     

	-- enet concStatictics Global group

									     

	eGlobalHubReadableFrames OBJECT-TYPE                                 

		SYNTAX  Counter                                              

		ACCESS  read-only                                            

		STATUS  mandatory                                            

		DESCRIPTION                                                  

			"Global counter of good or readable frames for this  

			hub.  Frame is between 64 and 1518 bytes in          

			length and has SFD and good FCS."     

		::= { eGlobalStatistics 1 }

									     

	eGlobalHubMcastFrames OBJECT-TYPE                                    

		SYNTAX  Counter                                              

		ACCESS  read-only                                            

		STATUS  mandatory                                            

		DESCRIPTION                                                  

			"Global counter of number of multicast frames for    

			this hub.  1st bit in highest ordered bytes of       

			destination address is set to 1. Broadcast packets   

			are not included."     

		::= { eGlobalStatistics 2 }

									     

	eGlobalHubBcastFrames OBJECT-TYPE                                    

		SYNTAX  Counter                                              

		ACCESS  read-only                                            

		STATUS  mandatory                                            

		DESCRIPTION                                                  

			"Global counter of number of broadcast frames for    

			his hub.  All 1s in network destination address.     

			Multicast packets are not included."     

		::= { eGlobalStatistics 3 }

									     

	eGlobalHubFrameTooLongs OBJECT-TYPE                                  

		SYNTAX  Counter                                              

		ACCESS  read-only                                            

		STATUS  mandatory                                            

		DESCRIPTION                                                  

			"Global counter, for this hub, of data frames      

			longer than 1518 bytes, with a SFD and good FCS."    

		::= { eGlobalStatistics 4 }

									     

	eGlobalHubRunts OBJECT-TYPE                                          

		SYNTAX  Counter                                              

		ACCESS  read-only                                            

		STATUS  mandatory                                            

		DESCRIPTION                                                  

			"Global counter, for this hub, of data frames with   

			size less than 64 bytes, with no CRC or alignment    

			errors. "     

		::= { eGlobalStatistics 5 }

									     

	eGlobalHubAlignmentErrors OBJECT-TYPE                                

		SYNTAX  Counter                                              

		ACCESS  read-only                                            

		STATUS  mandatory                                            

		DESCRIPTION                                                  

			"Global counter, for this hub, of frames which      

			are not integer multiples of 1 byte."     

		::= { eGlobalStatistics 6 }

									     

	eGlobalHubFragmentErrors OBJECT-TYPE                                 

		SYNTAX  Counter                                              

		ACCESS  read-only                                            

		STATUS  mandatory                                            

		DESCRIPTION                                                  

			"Global counter, for this hub, of frames greater than

			2 bytes and less than 64 bytes, with SFD and bad     

			FCS (CRC error)."     

		::= { eGlobalStatistics 7 }

									     

	eGlobalHubFCSErrors OBJECT-TYPE

		SYNTAX  Counter                                              

		ACCESS  read-only                                            

		STATUS  mandatory                                            

		DESCRIPTION                                                  

			"Global counter, for this hub, of frames that      

			failed Cyclic Redundancy Check (CRC)."     

		::= { eGlobalStatistics 8 }

									     

	eGlobalHubIFGErrors OBJECT-TYPE                                      

		SYNTAX  Counter                                              

		ACCESS  read-only                                            

		STATUS  mandatory                                            

		DESCRIPTION                                                  

			"Global counter, for this hub, of occurrences of     

			Interframe Gap Errors where time period between      

			data frames is less than 5.5 micro seconds."     

		::= { eGlobalStatistics 9 }

									     

	eGlobalHubDataRateMismatchs OBJECT-TYPE                               

		SYNTAX  Counter                                              

		ACCESS  read-only                                            

		STATUS  mandatory                                            

		DESCRIPTION                                                  

			"Global counter, for this hub, of errors where     

			incoming data rate is not with in the tolerance      

			level of 10MHZ + or - 0.01%."     

		::= { eGlobalStatistics 10 }

									     

	eGlobalHubShortEvents OBJECT-TYPE                                    

		SYNTAX  Counter                                              

		ACCESS  read-only                                            

		STATUS  mandatory                                            

		DESCRIPTION                                                  

			"Global counter, for this hub, of data burst where   

			data is less than 10 bytes in length, with no        

			SFD."     

		::= { eGlobalStatistics 11 }

									     

	eGlobalHubCollisions OBJECT-TYPE                                     

		SYNTAX  Counter                                              

		ACCESS  read-only                                            

		STATUS  mandatory                                            

		DESCRIPTION                                                  

			"Global counter of collision flags, for this hub."   

		::= { eGlobalStatistics 12 }

									     

	eGlobalHubLateCollisions OBJECT-TYPE                                 

		SYNTAX  Counter                                              

		ACCESS  read-only                                            

		STATUS  mandatory                                            

		DESCRIPTION                                                  

			"Global counter, for this hub, of collisions   

			occurring after the 64 byte collision window."     

		::= { eGlobalStatistics 13 }

									     

	eGlobalHubMJLPs OBJECT-TYPE                                          

		SYNTAX  Counter                                              

		ACCESS  read-only                                            

		STATUS  mandatory                                            

		DESCRIPTION                                                  

			"Global counter of MAU jabber lockup protection      

			where hub repeater chip goes into lockup state."     

		::= { eGlobalStatistics 14 }

									     

	eGlobalHubAutoPartitions OBJECT-TYPE                                 

		SYNTAX  Counter                                              

		ACCESS  read-only                                            

		STATUS  mandatory                                            

		DESCRIPTION                                                  

			"Global counter, for this hub, of all ports including

			3in1 port being partitioned from network in          

			response to 31 or more continuous collisions."     

		::= { eGlobalStatistics 15 }

									     

	eGlobalHubSFDMissings OBJECT-TYPE                                     

		SYNTAX  Counter                                              

		ACCESS  read-only                                            

		STATUS  mandatory                                            

		DESCRIPTION                                                  

			"Global counter, for this hub, of a burst of data    

			greater than or equal to 10 bytes in length with     

			no SFD."     

		::= { eGlobalStatistics 16 }

									     

	eGlobalHubBadFrames OBJECT-TYPE                                      

		SYNTAX  Counter                                              

		ACCESS  read-only                                            

		STATUS  mandatory                                            

		DESCRIPTION                                                  

			"Global counter, for this hub, of total errored frame

			including toolong, runts, misaligned, or bad FCS."   

		::= { eGlobalStatistics 17 }

									     

	-- eGroupStatistics group 

									     

	eGrpStatisticsTable OBJECT-TYPE                                      

		SYNTAX  SEQUENCE OF EnetGrpStatisticsEntry                   

		ACCESS  not-accessible                                       

		STATUS  mandatory                                            

		DESCRIPTION                                                  

			"Table of statistical information for each group."   

		::= { eStatistics 3 }

									     

	eGrpStatisticsEntry OBJECT-TYPE                                      

		SYNTAX  EnetGrpStatisticsEntry                               

		ACCESS  not-accessible                                       

		STATUS  mandatory                                            

		DESCRIPTION                                                  

			"Entry for individual group in table."               

		INDEX { eGrpStatIndex }                                      

		::= { eGrpStatisticsTable 1 }

									     

	EnetGrpStatisticsEntry ::= SEQUENCE {                                

		eGrpStatIndex                                                

			INTEGER,                                             

		eGrpStatReadableFrames                                       

			Counter,                                             

		eGrpStatMcastFrames                                          

			Counter,                                             

		eGrpStatBcastFrames                                          

			Counter,                                             

		eGrpStatFrameTooLongs                                        

			Counter,                                             

		eGrpStatRunts                                                

			Counter,                                             

		eGrpStatAlignmentErrors                                      

			Counter,                                             

		eGrpStatFragmentErrors                                       

			Counter,                                             

		eGrpStatFCSErrors                                            

			Counter,                                             

		eGrpStatIFGErrors                                            

			Counter,                                             

		eGrpStatDataRateMismatchs

			Counter,                                             

		eGrpStatShortEvents                                          

			Counter,                                             

		eGrpStatCollisions                                           

			Counter,                                             

		eGrpStatLateCollisions                                       

			Counter,                                             

		eGrpStatMJLPs                                                

			Counter,                                             

		eGrpStatAutoPartitions                                       

			Counter,                                             

		eGrpStatSFDMissings

			Counter,                                             

		eGrpStatBadFrames                                            

			Counter                                              

	}

									     

	eGrpStatIndex OBJECT-TYPE                                            

		SYNTAX  INTEGER                                              

		ACCESS  read-only                                            

		STATUS  mandatory                                            

		DESCRIPTION                                                  

			"The value of this object identifies the group     

			for which this entry contains group statistical      

			information."     

		::= { eGrpStatisticsEntry 1 }

									     

	eGrpStatReadableFrames OBJECT-TYPE                                   

		SYNTAX  Counter                                              

		ACCESS  read-only                                            

		STATUS  mandatory                                            

		DESCRIPTION                                                  

			"Group counter of 'good' or readable frames.  Frame  

			is between 64 and 1518 bytes in length and           

			has SFD and good FCS."     

		::= { eGrpStatisticsEntry 2 }                                

									     

	eGrpStatMcastFrames OBJECT-TYPE                                      

		SYNTAX  Counter                                              

		ACCESS  read-only                                            

		STATUS  mandatory                                            

		DESCRIPTION                                                  

			"Group counter of number of muliticast frames.     

			1st bit in highest ordered bytes of destination      

			address is set to 1.  Broadcast packets are not      

			included."     

		::= { eGrpStatisticsEntry 3 }

									     

	eGrpStatBcastFrames OBJECT-TYPE                                      

		SYNTAX  Counter                                              

		ACCESS  read-only                                            

		STATUS  mandatory                                            

		DESCRIPTION                                                  

			"Group counter of number of broadcast frames. All    

			1s in network destination address.  Multicast        

			packets are not included."     

		::= { eGrpStatisticsEntry 4 }

									     

	eGrpStatFrameTooLongs OBJECT-TYPE                                    

		SYNTAX  Counter                                              

		ACCESS  read-only                                            

		STATUS  mandatory                                            

		DESCRIPTION                                                  

			"Group counter for data frames longer than 1518      

			bytes, with a SFD and good FCS. "     

		::= { eGrpStatisticsEntry 5 }

									     

	eGrpStatRunts OBJECT-TYPE                                            

		SYNTAX  Counter                                              

		ACCESS  read-only                                            

		STATUS  mandatory                                            

		DESCRIPTION                                                  

			"Group counter for data frames with size less than   

			64 bytes, with no CRC or alignment errors."     

		::= { eGrpStatisticsEntry 6 }

									     

	eGrpStatAlignmentErrors OBJECT-TYPE                                  

		SYNTAX  Counter                                              

		ACCESS  read-only                                            

		STATUS  mandatory                                            

		DESCRIPTION                                                  

			"Group counter of frames which are not integer      

			multiples of 1 byte ."     

		::= { eGrpStatisticsEntry 7 }

									     

	eGrpStatFragmentErrors OBJECT-TYPE                                   

		SYNTAX  Counter                                              

		ACCESS  read-only                                            

		STATUS  mandatory                                            

		DESCRIPTION                                                  

			"Group counter of frames greater than 2 bytes and    

			less than 64 bytes, with SFD and bad FCS             

			(CRC error)."     

		::= { eGrpStatisticsEntry 8 }

									     

	eGrpStatFCSErrors OBJECT-TYPE                                        

		SYNTAX  Counter                                              

		ACCESS  read-only                                            

		STATUS  mandatory                                            

		DESCRIPTION                                                  

			"Group counter frames that failed Cyclic      

			Redundancy Check (CRC)."     

		::= { eGrpStatisticsEntry 9 }                                

									     

	eGrpStatIFGErrors OBJECT-TYPE                                        

		SYNTAX  Counter                                              

		ACCESS  read-only                                            

		STATUS  mandatory                                            

		DESCRIPTION                                                  

			"Group counter of Interframe Gap Errors     

			where time period between data frames is less than   

			5.5 micro seconds."     

		::= { eGrpStatisticsEntry 10 }

									     

	eGrpStatDataRateMismatchs OBJECT-TYPE                                 

		SYNTAX  Counter                                              

		ACCESS  read-only                                            

		STATUS  mandatory                                            

		DESCRIPTION                                                  

			"Group counter of errors where incoming data rate    

			is not with in the tolerance level of                

			10 MHZ + or - 0.01%."     

		::= { eGrpStatisticsEntry 11 }

									     

	eGrpStatShortEvents OBJECT-TYPE                                      

		SYNTAX  Counter                                              

		ACCESS  read-only                                            

		STATUS  mandatory                                            

		DESCRIPTION                                                  

			"Group counter of data burst where data is less than 

			10 bytes in length, with no SFD."     

		::= { eGrpStatisticsEntry 12 }                               

									     

	eGrpStatCollisions OBJECT-TYPE                                       

		SYNTAX  Counter                                              

		ACCESS  read-only                                            

		STATUS  mandatory                                            

		DESCRIPTION                                                  

			"Group counter of collision flags."                  

		::= { eGrpStatisticsEntry 13 }

									     

	eGrpStatLateCollisions OBJECT-TYPE                                   

		SYNTAX  Counter                                              

		ACCESS  read-only                                            

		STATUS  mandatory                                            

		DESCRIPTION                                                  

			"Group counter of collisions occurring after the 64  

			byte collision window."     

		::= { eGrpStatisticsEntry 14 }

									     

	eGrpStatMJLPs OBJECT-TYPE                                            

		SYNTAX  Counter                                              

		ACCESS  read-only                                            

		STATUS  mandatory                                            

		DESCRIPTION                                                  

			"Group counter of MAU jabber lockup protection      

			where hub repeater chip goes into lockup state."     

		::= { eGrpStatisticsEntry 15 }

									     

	eGrpStatAutoPartitions OBJECT-TYPE                                   

		SYNTAX  Counter                                              

		ACCESS  read-only                                            

		STATUS  mandatory                                            

		DESCRIPTION                                                  

			"Group counter of ports in group autopartitioned in  

			response to 31 or more continuous collisions."     

		::= { eGrpStatisticsEntry 16 }

									     

	eGrpStatSFDMissings OBJECT-TYPE                                       

		SYNTAX  Counter                                              

		ACCESS  read-only                                            

		STATUS  mandatory                                            

		DESCRIPTION                                                  

			"Group counter of a burst of data greater than or    

			equal to 10 bytes in length with no SFD."     

		::= { eGrpStatisticsEntry 17 }

									     

	eGrpStatBadFrames OBJECT-TYPE                                        

		SYNTAX  Counter                                              

		ACCESS  read-only                                            

		STATUS  mandatory                                            

		DESCRIPTION                                                  

			"Group counter of total errored frames including     

			toolong, runts, misaligned, or bad FCS."     

		::= { eGrpStatisticsEntry 18 }

									     

	-- ePortStatistics group 

									     

	ePortStatisticsTable OBJECT-TYPE                                     

		SYNTAX  SEQUENCE OF EnetPortStatisticsEntry                  

		ACCESS  not-accessible                                       

		STATUS  mandatory                                            

		DESCRIPTION                                                  

			"Table for port specific network statistics."        

		::= { eStatistics 4 }                                        

									     

	ePortStatisticsEntry OBJECT-TYPE                                     

		SYNTAX  EnetPortStatisticsEntry                              

		ACCESS  not-accessible                                       

		STATUS  mandatory                                            

		DESCRIPTION                                                  

			"Entry for individual port in table."                

		INDEX { ePortGrpIndex, ePortIndex }                          

		::= { ePortStatisticsTable 1 }

									     

	EnetPortStatisticsEntry ::= SEQUENCE {                               

		ePortGrpIndex                                                

			INTEGER,                                             

		ePortIndex                                                   

			INTEGER,                                             

		ePortStatReadableFrames                                      

			Counter,                                             

		ePortStatMcastFrames                                         

			Counter,                                             

		ePortStatBcastFrames                                         

			Counter,                                             

		ePortStatFrameTooLongs                                       

			Counter,                                             

		ePortStatRunts                                               

			Counter,                                             

		ePortStatAlignmentErrors                                     

			Counter,                                             

		ePortStatFragmentErrors                                      

			Counter,                                             

		ePortStatFCSErrors                                           

			Counter,                                             

		ePortStatIFGErrors                                           

			Counter,                                             

		ePortStatDataRateMismatchs

			Counter,                                             

		ePortStatShortEvents                                         

			Counter,                                             

		ePortStatCollisions                                          

			Counter,                                             

		ePortStatLateCollisions                                      

			Counter,                                             

		ePortStatMJLPs                                               

			Counter,                                             

		ePortStatAutoPartitions                                      

			Counter,                                             

		ePortStatSFDMissings

			Counter,                                             

		ePortStatBadFrames                                           

			Counter                                              

	}                                                                    

									     

	ePortGrpIndex OBJECT-TYPE                                            

		SYNTAX  INTEGER                                              

		ACCESS  read-only                                            

		STATUS  mandatory                                            

		DESCRIPTION                                                  

			"The value of this object identifies the group for   

			which this entry contains port statistical           

			information."     

		::= { ePortStatisticsEntry 1 }

									     

	ePortIndex OBJECT-TYPE                                               

		SYNTAX  INTEGER                                              

		ACCESS  read-only                                            

		STATUS  mandatory                                            

		DESCRIPTION                                                  

			"The value of this object identifies the port for    

			which this entry contains port statistical           

			information."     

		::= { ePortStatisticsEntry 2 }

									     

	ePortStatReadableFrames OBJECT-TYPE                                  

		SYNTAX  Counter                                              

		ACCESS  read-only                                            

		STATUS  mandatory                                            

		DESCRIPTION                                                  

			"Port counter of good or readable frames.  Frame is  

			between 64 and 1518 bytes in length and              

			has SFD and good FCS."     

		::= { ePortStatisticsEntry 3 }                               

									     

	ePortStatMcastFrames OBJECT-TYPE                                     

		SYNTAX  Counter                                              

		ACCESS  read-only                                            

		STATUS  mandatory                                            

		DESCRIPTION                                                  

			"Port counter of number of muliticast frames.  1st   

			bit in highest ordered bytes of destination address  

			is set to 1. Broadcast packets are not included."    

		::= { ePortStatisticsEntry 4 }                               

									     

	ePortStatBcastFrames OBJECT-TYPE                                     

		SYNTAX  Counter                                              

		ACCESS  read-only                                            

		STATUS  mandatory                                            

		DESCRIPTION                                                  

			"Port counter of number of broadcast frames.  All    

			1s in network destination address.  Multicast        

			packets are not included."     

		::= { ePortStatisticsEntry 5 }                               

									     

	ePortStatFrameTooLongs OBJECT-TYPE                                   

		SYNTAX  Counter                                              

		ACCESS  read-only                                            

		STATUS  mandatory                                            

		DESCRIPTION                                                  

			"Port counter for data frames longer than 1518      

			bytes,  with a SFD and good FCS."     

		::= { ePortStatisticsEntry 6 }

									     

	ePortStatRunts OBJECT-TYPE                                           

		SYNTAX  Counter                                              

		ACCESS  read-only                                            

		STATUS  mandatory                                            

		DESCRIPTION                                                  

			"Port counter for data frames with size less than    

			64 bytes, with no CRC or alignment errors."     

		::= { ePortStatisticsEntry 7 }

									     

	ePortStatAlignmentErrors OBJECT-TYPE                                 

		SYNTAX  Counter                                              

		ACCESS  read-only                                            

		STATUS  mandatory                                            

		DESCRIPTION                                                  

			"Port counter of frames which are not integer     

			multiples of 1 byte."     

		::= { ePortStatisticsEntry 8 }

									     

	ePortStatFragmentErrors OBJECT-TYPE                                  

		SYNTAX  Counter                                              

		ACCESS  read-only                                            

		STATUS  mandatory                                            

		DESCRIPTION                                                  

			"Port counter of frames greater than 2 bytes and     

			less than 64 bytes, with SFD and bad                 

			FCS (CRC error)."     

		::= { ePortStatisticsEntry 9 }

									     

	ePortStatFCSErrors OBJECT-TYPE                                       

		SYNTAX  Counter                                              

		ACCESS  read-only                                            

		STATUS  mandatory                                            

		DESCRIPTION                                                  

			"Port counter of frames that failed Cyclic      

			Redundancy Check (CRC)."     

		::= { ePortStatisticsEntry 10 }                              

									     

	ePortStatIFGErrors OBJECT-TYPE                                       

		SYNTAX  Counter                                              

		ACCESS  read-only                                            

		STATUS  mandatory                                            

		DESCRIPTION                                                  

			"Port counter of Interframe Gap Errors where	     

			time period between data frames is less than 5.5     

			micro seconds."     

		::= { ePortStatisticsEntry 11 }

									     

	ePortStatDataRateMismatchs OBJECT-TYPE                                

		SYNTAX  Counter                                              

		ACCESS  read-only                                            

		STATUS  mandatory                                            

		DESCRIPTION                                                  

			"Port counter of errors where incoming data rate     

			is not with in the tolerance level of                

			10 MHZ + or - 0.01%."     

		::= { ePortStatisticsEntry 12 }

									     

	ePortStatShortEvents OBJECT-TYPE                                     

		SYNTAX  Counter                                              

		ACCESS  read-only                                            

		STATUS  mandatory                                            

		DESCRIPTION                                                  

			"Port counter of data burst where data is less than  

			10 bytes in length, with no SFD."     

		::= { ePortStatisticsEntry 13 }

									     

	ePortStatCollisions OBJECT-TYPE                                      

		SYNTAX  Counter                                              

		ACCESS  read-only                                            

		STATUS  mandatory                                            

		DESCRIPTION                                                  

			"Port counter of collision flags."                   

		::= { ePortStatisticsEntry 14 }

									     

	ePortStatLateCollisions OBJECT-TYPE                                  

		SYNTAX  Counter                                              

		ACCESS  read-only                                            

		STATUS  mandatory                                            

		DESCRIPTION                                                  

			"Port counter of collisions occurring after the 64   

			byte collision window."     

		::= { ePortStatisticsEntry 15 }

									     

	ePortStatMJLPs OBJECT-TYPE                                           

		SYNTAX  Counter                                              

		ACCESS  read-only                                            

		STATUS  mandatory                                            

		DESCRIPTION                                                  

			"Port counter of MAU jabber lockup protection      

			where hub repeater chip goes into lockup state."     

		::= { ePortStatisticsEntry 16 }                              

									     

	ePortStatAutoPartitions OBJECT-TYPE                                  

		SYNTAX  Counter                                              

		ACCESS  read-only                                            

		STATUS  mandatory                                            

		DESCRIPTION                                                  

			"Port counter of number of times port was      

			autopartitioned in response to 31 or more            

			continuous collisions."     

		::= { ePortStatisticsEntry 17 }

									     

	ePortStatSFDMissings OBJECT-TYPE                                      

		SYNTAX  Counter                                              

		ACCESS  read-only                                            

		STATUS  mandatory                                            

		DESCRIPTION                                                  

			"Port counter of a burst of data greater than or     

			equal to 10 bytes in length with no SFD."    

		::= { ePortStatisticsEntry 18 }

									     

	ePortStatBadFrames OBJECT-TYPE                                       

		SYNTAX  Counter                                              

		ACCESS  read-only                                            

		STATUS  mandatory                                            

		DESCRIPTION                                                  

			"Port counter of total errored frames including     

			toolong, runts, misaligned, or bad FCS."     

		::= { ePortStatisticsEntry 19 }

									     

	-- Ethernet traffic matrix group

									     

	eTrafficMatrixTable OBJECT-TYPE                                      

		SYNTAX  SEQUENCE OF EnetTrafficMatrixEntry                   

		ACCESS  not-accessible                                       

		STATUS  mandatory                                            

		DESCRIPTION                                                  

			"Table to analyze the number of packets received     

			through network traffic by the size of each packet." 

		::= { eStatistics 5 }

									     

	eTrafficMatrixEntry OBJECT-TYPE                                      

		SYNTAX  EnetTrafficMatrixEntry                               

		ACCESS  not-accessible                                       

		STATUS  mandatory                                            

		DESCRIPTION                                                  

			"Individual entry in matrix of packet lengths table."

		INDEX { eTrafficMatrixLength  }                              

		::= { eTrafficMatrixTable 1 }

									     

	EnetTrafficMatrixEntry ::= SEQUENCE {                                

		eTrafficMatrixLength                                         

			INTEGER,                                             

		eTrafficMatrixRange                                          

			INTEGER,                                             

		eTrafficMatrixFramesCounts

			Counter                                              

		}

									     

	eTrafficMatrixLength OBJECT-TYPE                                     

		SYNTAX  INTEGER                                              

		ACCESS  read-only                                            

		STATUS  mandatory                                            

		DESCRIPTION                                                  

			"Starting length for each range in table."           

		::= { eTrafficMatrixEntry 1 }

									     

	eTrafficMatrixRange OBJECT-TYPE                                      

		SYNTAX  INTEGER {                                            

		   other(1),                       -- Unknown           

		   from-1-to-63-bytes(2),          -- 1-63 bytes range  

		   from-64-to-127-bytes(3),        -- 64-127 bytes range

		   from-128-to-255-bytes(4),       -- 128-255 bytes range

		   from-256-to-511-bytes(5),       -- 256-511 bytes range

		   from-512-to-767-bytes(6),       -- 512-767 bytes range

		   from-768-to-1023-bytes(7),      -- 768-1023 bytes range

		   from-1024-to-1518-bytes(8),     -- 1024-1518 bytes range

		   from-512-to-1023-bytes(9),      -- 512-1023 bytes range

		   from-65-to-511-bytes(10),       -- 65-511 bytes range

		   exact-64-bytes(11),             -- exact 64 bytes    

		   over-1518-bytes(12)             -- over 1518 bytes   

		}                                                            

		ACCESS  read-only                                            

		STATUS  mandatory                                            

		DESCRIPTION                                                  

			"Range of packet sizes to be scanned for in network  

			traffic."     

		::= { eTrafficMatrixEntry 2 }

									     

	eTrafficMatrixFramesCounts OBJECT-TYPE                                

		SYNTAX  Counter                                              

		ACCESS  read-only                                            

		STATUS  mandatory                                            

		DESCRIPTION                                                  

			"Counter for number of frames received for     

			particular range specified by the MatrixRange. "     

		::= { eTrafficMatrixEntry 3 }

									     

	-- eSmartSpecific Group                                              

	eSpecific       OBJECT IDENTIFIER ::= { eStatistics 6 }              

	eSmartHubSpec   OBJECT IDENTIFIER ::= { eSpecific 1 }                


	eColGraphBar OBJECT-TYPE                                             

		SYNTAX  INTEGER                                              

		ACCESS  read-only                                            

		STATUS  mandatory                                            

		DESCRIPTION                                                  

			"Information on hardware LED collision graph bar."   

		::= { eSmartHubSpec 1 }

									     

	eUtilGraphBar OBJECT-TYPE                                            

		SYNTAX  INTEGER                                              

		ACCESS  read-only                                            

		STATUS  mandatory                                            

		DESCRIPTION                                                  

			"Information on hardware LED for utilization      

			graph bar."     

		::= { eSmartHubSpec 2 }

									     

									     

	-- ePort packet rate table 

									     

	ePortRateTable OBJECT-TYPE                                           

		SYNTAX  SEQUENCE OF EnetPortRateEntry                        

		ACCESS  not-accessible                                       

		STATUS  optional                                             

		DESCRIPTION                                                  

			"Network statistics for individual ports measured    

			in Rate/Second."      

		::= { eSmartHubSpec 6 }                                      

									     

	ePortRateEntry OBJECT-TYPE                                           

		SYNTAX  EnetPortRateEntry                                    

		ACCESS  not-accessible                                       

		STATUS  optional                                             

		DESCRIPTION                                                  

			"Individual entry in port rate table."               

		INDEX { ePortRateGrpIndex, ePortRatePortIndex }              

		::= { ePortRateTable 1 }

									     

	EnetPortRateEntry ::= SEQUENCE {                                     

		ePortRateGrpIndex                                            

			INTEGER,                                             

		ePortRatePortIndex                                           

			INTEGER,                                             

		ePortRateReadableFrames                                      

			INTEGER,                                             

		ePortRateMcastFrames                                         

			INTEGER,                                             

		ePortRateBcastFrames                                         

			INTEGER,                                             

		ePortRateFrameTooLongs                                       

			INTEGER,                                             

		ePortRateRunts                                               

			INTEGER,                                             

		ePortRateAlignmentErrors                                     

			INTEGER,                                             

		ePortRateFragmentErrors                                      

			INTEGER,                                             

		ePortRateFCSErrors                                           

			INTEGER,                                             

		ePortRateIFGErrors                                           

			INTEGER,                                             

		ePortRateDataRateMismatch                                    

			INTEGER,                                             

		ePortRateShortEvents                                         

			INTEGER,                                             

		ePortRateCollisions                                          

			INTEGER,                                             

		ePortRateLateCollisions                                      

			INTEGER,                                             

		ePortRateMJLPs                                               

			INTEGER,                                             

		ePortRateAutoPartitions                                      

			INTEGER,                                             

		ePortRateSFDMissings                                          

			INTEGER,                                             

		ePortRateBadFrames                                           

			INTEGER                                              

	}                                                                    

									     

	ePortRateGrpIndex OBJECT-TYPE                                        

		SYNTAX  INTEGER                                              

		ACCESS  read-only                                            

		STATUS  optional                                             

		DESCRIPTION                                                  

			"The value of this object identifies the group for   

			which this entry contains port statistical           

			information."     

		::= { ePortRateEntry 1 }

									     

	ePortRatePortIndex OBJECT-TYPE                                       

		SYNTAX  INTEGER                                              

		ACCESS  read-only                                            

		STATUS  optional                                             

		DESCRIPTION                                                  

			"This value identifies the port for which     

			this entry contains port statistical information."   

		::= { ePortRateEntry 2 }                                     

									     

	ePortRateReadableFrames OBJECT-TYPE                                  

		SYNTAX  INTEGER                                              

		ACCESS  read-only                                            

		STATUS  optional                                             

		DESCRIPTION                                                  

			"Rate of occurrence of good or readable frames."     

		::= { ePortRateEntry 3 }                                     

									     

	ePortRateMcastFrames OBJECT-TYPE                                     

		SYNTAX  INTEGER                                              

		ACCESS  read-only                                            

		STATUS  optional                                             

		DESCRIPTION                                                  

			"Rate of occurrence of number of muliticast frames.  

			1st bit in highest ordered bytes of destination      

			address is set to 1. Broadcast packets are           

			not included."     

		::= { ePortRateEntry 4 }                                     

									     

	ePortRateBcastFrames OBJECT-TYPE                                     

		SYNTAX  INTEGER                                              

		ACCESS  read-only                                            

		STATUS  optional                                             

		DESCRIPTION                                                  

			"Rate of occurrence of number of broadcast frames.   

			All 1s in network destination address.  Multicast    

			packets are not included."     

		::= { ePortRateEntry 5 }                                     

									     

	ePortRateFrameTooLongs OBJECT-TYPE                                   

		SYNTAX  INTEGER                                              

		ACCESS  read-only                                            

		STATUS  optional                                             

		DESCRIPTION                                                  

			"Rate of occurrence of data frames longer than 1518  

			bytes, with a SFD and good FCS."     

		::= { ePortRateEntry 6 }

									     

	ePortRateRunts OBJECT-TYPE                                           

		SYNTAX  INTEGER                                              

		ACCESS  read-only                                            

		STATUS  optional                                             

		DESCRIPTION                                                  

			"Rate of occurrence of data frames with size less    

			than 64 bytes, with no CRC or alignment errors."     

		::= { ePortRateEntry 7 }

									     

	ePortRateAlignmentErrors OBJECT-TYPE                                 

		SYNTAX  INTEGER                                              

		ACCESS  read-only                                            

		STATUS  optional                                             

		DESCRIPTION                                                  

			"Rate of occurrence of frames which are not integer  

			multiples of 1 byte."     

		::= { ePortRateEntry 8 }

									     

	ePortRateFragmentErrors OBJECT-TYPE                                  

		SYNTAX  INTEGER                                              

		ACCESS  read-only                                            

		STATUS  optional                                             

		DESCRIPTION                                                  

			"Rate of occurrence of frames greater than 2 bytes   

			and less than 64 bytes, with SFD and bad             

			FCS (CRC error)."     

		::= { ePortRateEntry 9 }

									     

	ePortRateFCSErrors OBJECT-TYPE                                       

		SYNTAX  INTEGER                                              

		ACCESS  read-only                                            

		STATUS  optional                                             

		DESCRIPTION                                                  

			"Rate of occurrence of frames that failed Cyclic     

			Redundancy Check (CRC)."     

		::= { ePortRateEntry 10 }                                    

									     

	ePortRateIFGErrors OBJECT-TYPE                                       

		SYNTAX  INTEGER                                              

		ACCESS  read-only                                            

		STATUS  optional                                             

		DESCRIPTION                                                  

			"Rate of occurrence of interframe Gap Errors where   

			time period between data frames is less than 5.5     

			micro seconds."     

		::= { ePortRateEntry 11 }

									     

	ePortRateDataRateMismatch OBJECT-TYPE                                

		SYNTAX  INTEGER                                              

		ACCESS  read-only                                            

		STATUS  optional                                             

		DESCRIPTION                                                  

			"Rate of occurrence of errors where incoming data    

			rate is not with in the tolerance level of           

			10 MHz + or - 0.01%."     

		::= { ePortRateEntry 12 }

									     

	ePortRateShortEvents OBJECT-TYPE                                     

		SYNTAX  INTEGER                                              

		ACCESS  read-only                                            

		STATUS  optional                                             

		DESCRIPTION                                                  

			"Rate of occurrence of data burst where data is less 

			than 10 bytes in length, with no SFD."     

		::= { ePortRateEntry 13 }

									     

	ePortRateCollisions OBJECT-TYPE                                      

		SYNTAX  INTEGER                                              

		ACCESS  read-only                                            

		STATUS  optional                                             

		DESCRIPTION                                                  

			"Rate of occurrence of collision flags."             

		::= { ePortRateEntry 14 }

									     

	ePortRateLateCollisions OBJECT-TYPE                                  

		SYNTAX  INTEGER                                              

		ACCESS  read-only                                            

		STATUS  optional                                             

		DESCRIPTION                                                  

			"Rate of occurrence of collisions occurring after the

			64 byte collision window."     

		::= { ePortRateEntry 15 }

									     

	ePortRateMJLPs OBJECT-TYPE                                           

		SYNTAX  INTEGER                                              

		ACCESS  read-only                                            

		STATUS  optional                                             

		DESCRIPTION                                                  

			"Rate of occurrence of MAU jabber lockup     

			protection where hub repeater chip goes into         

			lockup state."     

		::= { ePortRateEntry 16 }                                    

									     

	ePortRateAutoPartitions OBJECT-TYPE                                  

		SYNTAX  INTEGER                                              

		ACCESS  read-only                                            

		STATUS  optional                                             

		DESCRIPTION                                                  

			"Rate of occurrence of times port was      

			autopartitioned in response to 31 or                 

			more continuous collisions."     

		::= { ePortRateEntry 17 }

									     

	ePortRateSFDMissings OBJECT-TYPE                                      

		SYNTAX  INTEGER                                              

		ACCESS  read-only                                            

		STATUS  optional                                             

		DESCRIPTION                                                  

			"Rate of occurrence of a burst of data greater than  

			or equal to 10 bytes in length with no SFD."     

		::= { ePortRateEntry 18 }

									     

	ePortRateBadFrames OBJECT-TYPE                                       

		SYNTAX  INTEGER                                              

		ACCESS  read-only                                            

		STATUS  optional                                             

		DESCRIPTION                                                  

			"Rate of occurrence of total errored frames      

			including toolong, runts, misaligned, or bad FCS."   

		::= { ePortRateEntry 19 }

									     

	-- eStateCtrl Group

									     

	ePortStateCtrlTable OBJECT-TYPE                                      

		SYNTAX  SEQUENCE OF EPortStateCtrlEntry                      

		ACCESS  not-accessible                                       

		STATUS  mandatory                                            

		DESCRIPTION                                                  

			"Table for port control parameters."                 

		::= { eStateCtrl 1 }

									     

	ePortStateCtrlEntry OBJECT-TYPE                                      

		SYNTAX  EPortStateCtrlEntry                                  

		ACCESS  not-accessible                                       

		STATUS  mandatory                                            

		DESCRIPTION                                                  

			"Individual entry of port control in table."         

		INDEX { ePortStateGrpIndex, ePortStatePortIndex }            

		::= { ePortStateCtrlTable 1 }

									     

	EPortStateCtrlEntry ::= SEQUENCE {                                   

		ePortStateGrpIndex                                           

			INTEGER,                                             

		ePortStatePortIndex                                          

			INTEGER,                                             

		ePortStateType                                               

			INTEGER,                                             

		ePortStateLinkStatus                                         

			INTEGER,                                             

		ePortStateLinkIntegTest                                      

			INTEGER,                                             

		ePortStateAutoPartStatus                                     

			INTEGER,                                             

		ePortStateJabberStatus                                       

			INTEGER,                                             

		ePortStateJabberState                                        

			INTEGER,                                             

		ePortStateAdminState                                         

			INTEGER,                                             

		ePortStateRDTState                        

			INTEGER,                                             

		ePortStatePolarityStatus                                     

			INTEGER,                                             

		ePortStatePolarityState                                      

			INTEGER                                              

		}

									     

	ePortStateGrpIndex OBJECT-TYPE                                       

		SYNTAX  INTEGER                                              

		ACCESS  read-only                                            

		STATUS  mandatory                                            

		DESCRIPTION                                                  

			"The value of this object identifies the group for   

			which this entry contains port control information." 

		::= { ePortStateCtrlEntry 1 }

									     

	ePortStatePortIndex OBJECT-TYPE                                      

		SYNTAX  INTEGER                                              

		ACCESS  read-only                                            

		STATUS  mandatory                                            

		DESCRIPTION                                                  

			"This value identifies the port for which this     

			entry contains port control information."     

		::= { ePortStateCtrlEntry 2 }

									     

	ePortStateType OBJECT-TYPE                                           

		SYNTAX  INTEGER {                                            

			other(1),       -- unknown                           

			bNC(2),         -- BNC port                          

			aUI(3),         -- aui port                          

			rJ45(4),        -- 10 baset port                     

			foil(5),        -- fiber optics                      

			three-in-one(6) -- three in one port                 

		}                                                            

		ACCESS  read-only                                            

		STATUS  mandatory                                            

		DESCRIPTION                                                  

			"Type of cabling physically connected to port."      

		::= { ePortStateCtrlEntry 3 }

									     

	ePortStateLinkStatus OBJECT-TYPE                                     

		SYNTAX  INTEGER {                                            

			others(1),     -- unknown                            

			linkon(2),     -- link on                            

			linkoff(3)     -- link off                           

		}                                                            

		ACCESS  read-only                                            

		STATUS  mandatory                                            

		DESCRIPTION                                                  

			"Link status for particular port.  On=physical link  

			if link test enabled.  Off=no physical link          

			exists or link test is disabled."     

		::= { ePortStateCtrlEntry 4 }

									     

	ePortStateLinkIntegTest OBJECT-TYPE                                  

		SYNTAX  INTEGER {                                            

			others(1),              -- unknown                   

			linkTestEnable(2),      -- link int test enable      

			linkTestDisable(3)      -- link int test disable     

		}                                                            

		ACCESS  read-write                                           

		STATUS  mandatory                                            

		DESCRIPTION                                                  

			"Set can  enable or disabled link integrity test.    

			Get will say if link integrity test is enabled (2)   

			or disabled (3)."     

		::= { ePortStateCtrlEntry 5 }

									     

	ePortStateAutoPartStatus OBJECT-TYPE                                 

		SYNTAX  INTEGER {                                            

			others(1),              -- unknown                   

			autopartitioned(2),                                  

			notautopartitioned(3)                                

		}                                                            

		ACCESS  read-only                                            

		STATUS  mandatory                                            

		DESCRIPTION                                                  

			"Whether port has been autopartitioned (2) or not    

			autopartitioned (3)."     

		::= { ePortStateCtrlEntry 6 }

									     

	ePortStateJabberStatus OBJECT-TYPE                                   

		SYNTAX  INTEGER {                                            

			others(1),      -- unknown                           

			on(2),          -- port jabbering                    

			off(3)          -- port not jabbering                

		}                                                            

		ACCESS  read-only                                            

		STATUS  mandatory                                            

		DESCRIPTION                                                  

			"Jabber detection for port.  If On(2), then     

			jabber occurred on this port.  Off(3), then no jabber

			occurred or jabber detection has been manually       

			disabled."     

		::= { ePortStateCtrlEntry 7 }

									     

	ePortStateJabberState OBJECT-TYPE                                    

		SYNTAX  INTEGER {                                            

			others(1),      -- unknown                           

			enabled(2),     -- enabled                           

			disabled(3)     -- disabled                          

		}                                                            

		ACCESS  read-write                                           

		STATUS  mandatory                                            

		DESCRIPTION                                                  

			"Set can enable or disable jabber detection test. Get

			will say if jabber detection test is enabled (2)     

			or disabled (3)."     

		::= { ePortStateCtrlEntry 8 }

									     

	ePortStateAdminState OBJECT-TYPE                                     

		SYNTAX  INTEGER {                                            

			others(1),      -- unknown                           

			enabled(2),     -- enabled                           

			disabled(3)     -- disabled                          

		}                                                            

		ACCESS  read-write                                           

		STATUS  mandatory                                            

		DESCRIPTION                                                  

			"Set will manually enable or disable any port.  Get  

			will say if port has been enabled (2) or             

			disabled (3)."     

		::= { ePortStateCtrlEntry 9 }

									     

	ePortStateRDTState OBJECT-TYPE                                       

		SYNTAX  INTEGER {                                            

			others(1),      -- unknown                           

			unreduce(2),    -- normal operation                  

			reduce(3)       -- reduced threshold                 

		}                                                            

		ACCESS  read-write                                           

		STATUS  mandatory                                            

		DESCRIPTION                                                  

			"Whether RecvThreshold has been enabled or      

			disabled. Can use this to lower noise threshold      

			(tolerance) so that longer twisted pair links        

			can be used."     

		::= { ePortStateCtrlEntry 10 }

									     

	ePortStatePolarityStatus OBJECT-TYPE                                 

		SYNTAX  INTEGER {                                            

			others(1),     -- unknown                            

			normal(2),                                           

			reversed(3)                                          

		}                                                            

		ACCESS  read-only                                            

		STATUS  mandatory                                            

		DESCRIPTION                                                  

			"Polarity is correct (2) or not for this port."      

		::= { ePortStateCtrlEntry 11 }

									     

	ePortStatePolarityState OBJECT-TYPE                                  

		SYNTAX  INTEGER {                                            

			others(1),      -- unknown                           

			enabled(2),     -- enabled                           

			disabled(3)     -- disabled                          

		}                                                            

		ACCESS  read-write                                           

		STATUS  mandatory                                            

		DESCRIPTION                                                  

			"Autopolarity correction enabled or disabled.      

			Allows hub to make electrical corrections            

			automatically if cable does not reverse polarity     

			within wire pairs.  If do not want this correction to

			take place, autocorrection can be disabled."     

		::= { ePortStateCtrlEntry 12 }

									     

									     

	-- Node Summary Group ( Node Traffic Matrix Table )

									     

	nodeSummaryTable OBJECT-TYPE                                         

		SYNTAX  SEQUENCE OF NodeSummaryEntry                         

		ACCESS  not-accessible                                       

		STATUS  mandatory                                            

		DESCRIPTION                                                  

			"Node summary of all traffic through hub."           

		::= { concNodeMgt 1 }

									     

	nodeSummaryEntry OBJECT-TYPE                                         

		SYNTAX  NodeSummaryEntry                                     

		ACCESS  not-accessible                                       

		STATUS  mandatory                                            

		DESCRIPTION                                                  

			"Individual entry in node summary table. "           

		INDEX { nodeSummaryGrpIndex, nodeSummaryPortIndex,           

			nodeSummarySrcMacAddr, nodeSummaryDestMacAddr }      

		::= { nodeSummaryTable 1 }

									     

	NodeSummaryEntry ::= SEQUENCE {                                      

		nodeSummaryGrpIndex                                          

			INTEGER,                                             

		nodeSummaryPortIndex                                         

			INTEGER,                                             

		nodeSummarySrcMacAddr                                        

			PhysAddress,                                         

		nodeSummaryDestMacAddr                                       

			PhysAddress,                                         

		nodeSummaryEtherType                                         

			INTEGER,                                             

		nodeSummaryIpAddrPair                                        

			OCTET STRING,

		nodeSummaryTimeStamp

			TimeTicks

		}

									     

	nodeSummaryGrpIndex OBJECT-TYPE                                      

		SYNTAX  INTEGER                                              

		ACCESS  read-only                                            

		STATUS  mandatory                                            

		DESCRIPTION                                                  

			"Group Id for identifying the group     

			where node activity is detected."     

		::= { nodeSummaryEntry 1 }

									     

	nodeSummaryPortIndex OBJECT-TYPE                                     

		SYNTAX  INTEGER                                              

		ACCESS  read-only                                            

		STATUS  mandatory                                            

		DESCRIPTION                                                  

			"Port Id for identifying the port where     

			node activity is detected."     

		::= { nodeSummaryEntry 2 }

									     

	nodeSummarySrcMacAddr OBJECT-TYPE                                    

		SYNTAX  PhysAddress                                          

		ACCESS  read-only                                            

		STATUS  mandatory                                            

		DESCRIPTION                                                  

			"The source MAC address of the node     

			that is transmitting frames                          

			received by this port."     

		::= { nodeSummaryEntry 3 }

									     

	nodeSummaryDestMacAddr OBJECT-TYPE                                   

		SYNTAX  PhysAddress                                          

		ACCESS  read-only                                            

		STATUS  mandatory                                            

		DESCRIPTION                                                  

			"The destination MAC address of the     

			node to which frames are being                       

			received by this port. "     

		::= { nodeSummaryEntry 4 }

									     

	nodeSummaryEtherType OBJECT-TYPE                                     

		SYNTAX  INTEGER                                              

		ACCESS  read-only                                            

		STATUS  mandatory                                            

		DESCRIPTION                                                  

			"The 2 bytes after the source (src) address     

			in packet."     

		::= { nodeSummaryEntry 5 }

									     

	nodeSummaryIpAddrPair OBJECT-TYPE                                    

		SYNTAX  OCTET STRING                                         

		ACCESS  read-only                                            

		STATUS  mandatory                                            

		DESCRIPTION                                                  

			"Destination and source IP address if packet is     

			an Ethernet IP packet.  It the packet is not an      

			Ethernet IP packet, then the information may         

			not be accurate."     

		::= { nodeSummaryEntry 6 }


	nodeSummaryTimeStamp OBJECT-TYPE

		SYNTAX  TimeTicks

		ACCESS  read-only

		STATUS  mandatory

		DESCRIPTION

			"nodeSummary entry time stamp (in hundredths of a 

			second) since the network management portion of the 

			system was last re-initialized."

		::= { nodeSummaryEntry 7 }

									     

	-- Node Security Table Level One

									     

	nodeSecurity    OBJECT IDENTIFIER ::= { concNodeMgt 2 }

									     

	nodeSecuLev1Table OBJECT-TYPE                                        

		SYNTAX  SEQUENCE OF NodeSecuLev1Entry                        

		ACCESS  not-accessible                                       

		STATUS  mandatory                                            

		DESCRIPTION                                                  

			"Table of nodes which have access to particular      

			ports.  Nodes are identified by MAC address."      

		::= { nodeSecurity 1 }

									     

	nodeSecuLev1Entry OBJECT-TYPE                                        

		SYNTAX  NodeSecuLev1Entry                                    

		ACCESS  not-accessible                                       

		STATUS  mandatory                                            

		DESCRIPTION                                                  

			"Individual entry for node security table."          

		INDEX { nodeSecuLev1GrpIndex, nodeSecuLev1PortIndex }        

		::= { nodeSecuLev1Table 1 }

									     

	NodeSecuLev1Entry ::= SEQUENCE {                                     

		nodeSecuLev1GrpIndex                                         

			INTEGER,                                             

		nodeSecuLev1PortIndex                                        

			INTEGER,                                             

		nodeSecuLev1Status                                           

			INTEGER,                                             

		nodeSecuLev1AllowedAddr                                      

			PhysAddress,                                         

		nodeSecuLev1Action                                           

			INTEGER                                              

		}

									     

	nodeSecuLev1GrpIndex OBJECT-TYPE                                     

		SYNTAX  INTEGER                                              

		ACCESS  read-only                                            

		STATUS  mandatory                                            

		DESCRIPTION                                                  

			"Group ID for port which verifying node access."     

		::= { nodeSecuLev1Entry 1 }

									     

	nodeSecuLev1PortIndex OBJECT-TYPE                                    

		SYNTAX  INTEGER                                              

		ACCESS  read-only                                            

		STATUS  mandatory                                            

		DESCRIPTION                                                  

			"Specific port for which verifying node access."     

		::= { nodeSecuLev1Entry 2 }

									     

	nodeSecuLev1Status OBJECT-TYPE                                      

		SYNTAX  INTEGER {                                            

			other(1),                                            

			valid(2),                                            

			invalid(3)                                           

		}                                                            

		ACCESS  read-write                                           

		STATUS  mandatory                                            

		DESCRIPTION                                                  

			"Address is valid or invalid."                       

		::= { nodeSecuLev1Entry 3 }

									     

	nodeSecuLev1AllowedAddr OBJECT-TYPE                                  

		SYNTAX  PhysAddress                                          

		ACCESS  read-write                                           

		STATUS  mandatory                                            

		DESCRIPTION                                                  

			"MAC address of nodes allowed for particular port."  

		::= { nodeSecuLev1Entry 4 }

									     

	nodeSecuLev1Action OBJECT-TYPE                                       

		SYNTAX  INTEGER {                                            

			other(1),                                            

			partition-port(2),                                   

			send-trap(3),                                        

			partition-port-and-send-trap(4),                     

			send-trap-and-request-page(5),                       

			partition-port-and-send-trap-and-request-page(6)     

		}                                                            

		ACCESS  read-write                                           

		STATUS  mandatory                                            

		DESCRIPTION                                                  

			"Set action for node intrusion violation."           

		::= { nodeSecuLev1Entry 5 }

									     

	-- Concentrator Alarm

									     

	thresholdAlarm OBJECT IDENTIFIER ::= { concAlarmMgt 1 }

									     

	-- (Basic) Threshold table

									     

	thresholdLev1Table OBJECT-TYPE                                       

		SYNTAX  SEQUENCE OF ThresholdLev1Entry                       

		ACCESS  not-accessible                                       

		STATUS  optional                                             

		DESCRIPTION                                                  

			"Threshold/trap table."                              

		::= { thresholdAlarm 1 }                                     

									     

	thresholdLev1Entry OBJECT-TYPE                                       

		SYNTAX  ThresholdLev1Entry                                   

		ACCESS  not-accessible                                       

		STATUS  optional                                             

		DESCRIPTION                                                  

			"Individual entry in threshold trap table."          

		INDEX { thresholdLev1Index }                                 

		::= { thresholdLev1Table 1 }

									     

	ThresholdLev1Entry ::= SEQUENCE {                                    

		thresholdLev1Index                                           

			INTEGER,                                             

		thresholdLev1Status                                          

			INTEGER,                                             

		thresholdLev1Target                                          

			INTEGER,                                             

		thresholdLev1GroupIndex                                      

			INTEGER,                                             

		thresholdLev1PortIndex                                       

			INTEGER,                                             

		thresholdLev1Subject                                         

			INTEGER,                                             

		thresholdLev1SampleType                                      

			INTEGER,                                             

		thresholdLev1StartupAlarm                                    

			INTEGER,                                             

		thresholdLev1WaterMark                                       

			INTEGER,                                             

		thresholdLev1DetectedValue                                   

			INTEGER,                                             

		thresholdLev1RisingEvent                                     

			INTEGER,                                             

		thresholdLev1FallingEvent                                    

			INTEGER,                                             

		thresholdLev1Interval                                        

			INTEGER,                                             

		thresholdLev1OwnerString                                     

			OCTET STRING                                         

	}                                                                    

									     

	thresholdLev1Index OBJECT-TYPE                                       

		SYNTAX  INTEGER                                              

		ACCESS  read-only                                            

		STATUS  optional                                             

		DESCRIPTION                                                  

			"An index that uniquely identifies an entry in the   

			alarm table."     

		::= { thresholdLev1Entry 1 }                                 

									     

	thresholdLev1Status OBJECT-TYPE                                      

		SYNTAX  INTEGER {                                            

			other(1),                                            

			valid(2),                                            

			invalid(3)                                           

		}                                                            

		ACCESS  read-write                                           

		STATUS  optional                                             

		DESCRIPTION                                                  

			"Status of entry in threshold/trap table."           

		::= { thresholdLev1Entry 2 }                                 

									     

	thresholdLev1Target OBJECT-TYPE                                      

		SYNTAX  INTEGER {                                            

			other(1),                                            

			hub(2),                                              

			port(3)                                              

		}                                                            

		ACCESS  read-write                                           

		STATUS  optional                                             

		DESCRIPTION                                                  

			"Set target for threshold definition.  Either whole  

			hub(2) or particular port (3)."     

		::= { thresholdLev1Entry 3 }                                 

									     

	thresholdLev1GroupIndex OBJECT-TYPE                                  

		SYNTAX  INTEGER                                              

		ACCESS  read-write                                           

		STATUS  optional                                             

		DESCRIPTION                                                  

			"Group ID for trap set. One note--if the	     

			target is selected as hub, the group index           

			will be ignored."     

		::= { thresholdLev1Entry 4 }                                 

									     

	thresholdLev1PortIndex OBJECT-TYPE                                   

		SYNTAX  INTEGER                                              

		ACCESS  read-write                                           

		STATUS  optional                                             

		DESCRIPTION                                                  

			"Port number for trap set. One note--if the     

			target is selected as hub, the port index            

			will be ignored."     

		::= { thresholdLev1Entry 5 }                                 

									     

	thresholdLev1Subject OBJECT-TYPE                                     

		SYNTAX  INTEGER {                                            

			other(1),                                            

			readable-frames(2),                                  

			mcast-frames(3),                                     

			bcast-frames(4),                                     

			frame-too-longs(5),                                  

			runts(6),                                            

			alignment-errors(7),                                 

			fragment-errors(8),                                  

			fCS-errors(9),                                       

			iFG-errors(10),                                      

			data-rate-mismatch(11),                              

			short-events(12),                                    

			collisions(13),                                      

			late-collisions(14),                                 

			auto-partitions(15),                                 

			sfd-missing(16),                                     

			bad-frames(17)                                       

		}                                                            

		ACCESS  read-write                                           

		STATUS  optional                                             

		DESCRIPTION                                                  

			"Variable checking for in trap.  These are the type  

			of frames that a trap will be verified against."     

		::= { thresholdLev1Entry 6 }                                 

									     

	thresholdLev1SampleType OBJECT-TYPE                                  

		SYNTAX  INTEGER {                                            

			other(1),                                            

			event-per-second(2)                                  

		}                                                            

		ACCESS  read-write                                           

		STATUS  optional                                             

		DESCRIPTION                                                  

			"The method of sampling the selected variable     

			and calculating the value to be compared             

			against the threshold."     

		::= { thresholdLev1Entry 7 }                                 

									     

	thresholdLev1StartupAlarm OBJECT-TYPE                                

		SYNTAX  INTEGER {                                            

			other(1),                                            

			rising(2),                                           

			falling(3),                                                  
			rising-or-falling(4)                                 

		}                                                            

		ACCESS  read-write                                           

		STATUS  optional                                             

		DESCRIPTION                                                  

			"When the trap is triggered in relation to value set.

			When goes above (2), below (3), or changes at        

			all from (4)."     

		::= { thresholdLev1Entry 8 }                                 

									     

	thresholdLev1WaterMark OBJECT-TYPE                                   

		SYNTAX  INTEGER                                              

		ACCESS  read-write                                           

		STATUS  optional                                             

		DESCRIPTION                                                  

			"Counter of threshold."                              

		::= { thresholdLev1Entry 9 }                                 

									     

	thresholdLev1DetectedValue OBJECT-TYPE                               

		SYNTAX  INTEGER                                              

		ACCESS  read-only                                            

		STATUS  optional                                             

		DESCRIPTION                                                  

			"The value of the statistic for the last      

			sampling period."     

		::= { thresholdLev1Entry 10 }                                

									     

	thresholdLev1RisingEvent OBJECT-TYPE                                 

		SYNTAX  INTEGER {                                            

			other(1),                                            

			partition-port(2),                                   

			send-trap(3),                                        

			partition-port-and-send-trap(4),                     

			send-trap-and-request-page(5),                       

			partition-port-and-send-trap-and-request-page(6)     

		}                                                            

		ACCESS  read-write                                           

		STATUS  optional                                             

		DESCRIPTION                                                  

			"How to respond to a triggered event for a      

			rising event."     

		::= { thresholdLev1Entry 11 }

									     

	thresholdLev1FallingEvent OBJECT-TYPE                                

		SYNTAX  INTEGER {                                            

			other(1),                                            

			partition-port(2),                                   

			send-trap(3),                                        

			partition-port-and-send-trap(4),                     

			send-trap-and-request-page(5),                       

			partition-port-and-send-trap-and-request-page(6)     

		}                                                            

		ACCESS  read-write                                           

		STATUS  optional                                             

		DESCRIPTION                                                  

			"How to respond to a triggered event for a      

			falling event."     

		::= { thresholdLev1Entry 12 }

									     

	thresholdLev1Interval OBJECT-TYPE                                    

		SYNTAX  INTEGER                                              

		ACCESS  read-write                                           

		STATUS  optional                                             

		DESCRIPTION                                                  

			"The interval in seconds over which the data is      

			sampled."     

		::= { thresholdLev1Entry 13 }

									     

	thresholdLev1OwnerString OBJECT-TYPE                                 

		SYNTAX  OCTET STRING (SIZE(8))                               

		ACCESS  read-write                                           

		STATUS  optional                                             

		DESCRIPTION                                                  

			"8-byte octet reserved for the owner who      

			defined this entry."     

		::= { thresholdLev1Entry 14 }

									     

	adapterProductId        OBJECT IDENTIFIER ::= { productId 1 }        

	concProductId           OBJECT IDENTIFIER ::= { productId 2 }        

	hub1012                 OBJECT IDENTIFIER ::= { concProductId 1 }

	hub1012-bridge		OBJECT IDENTIFIER ::= { concProductId 2 }
									     

	-- Traps for use by Asante products                                  

	-- Traps are defined using the conventions in RFC1215.

									     

	-- threshold trap

									     

	thresholdLev1 TRAP-TYPE                                              

		ENTERPRISE hub1012

		VARIABLES {                                                  

			thresholdLev1Target,                                 

			thresholdLev1GroupIndex,                             

			thresholdLev1PortIndex,                              

			thresholdLev1Subject,                                

			thresholdLev1SampleType,                             

			thresholdLev1WaterMark,                              

			thresholdLev1DetectedValue,                          

			thresholdLev1OwnerString,                            

			thresholdLev1RisingEvent,                            

			thresholdLev1FallingEvent }                          

		DESCRIPTION                                                  

		"The SNMP trap that is generated when an alarm     

		entry crosses its rising threshold or falling threshold, and 

		generates an event that is configured for sending SNMP       

		traps."     

		::= 1

									     

	-- node intrusion trap

									     

	nodeSecuLevel1 TRAP-TYPE                                             

		ENTERPRISE hub1012

	--	VARIABLES {                                                  

	--		nodeSecuLev1GrpIndex,                                

	--		nodeSecuLev1PortIndex,                               

	--		rptrAddrLastSourceAddress,                           

	--		nodeSecuLev1Action }                                 

		DESCRIPTION                                                  

		"The SNMP trap that is generated when the MAC layer     

		address of the incoming frame from a particular port         

		does not match the pre-assigned address with that port,      

		and generates an event that is configured for sending        

		SNMP traps."     

		::= 2

									     

		END
