--
--    Generic Bridge Database Control MIB
-- --------------------------------------------------------------------
-- Copyright (c) 3Com Corporation. All Rights Reserved.
-- --------------------------------------------------------------------

A3COM0039-GENERIC-BRIDGE DEFINITIONS ::= BEGIN


   IMPORTS
      OBJECT-TYPE FROM RFC-1212
      bridgeMgmt FROM A3COM0004-GENERIC
      TRAP-TYPE FROM RFC-1215
      ;

brControlPackage  OBJECT IDENTIFIER ::= {bridgeMgmt 1}
brClearCounters OBJECT-TYPE
      SYNTAX      INTEGER  {
                  no-action (1),
                  clear (2)
      }
      ACCESS      read-write
      STATUS      mandatory
      DESCRIPTION "Clears all the counters associated with the 
        bridgeing function for all bridge ports. A read will 
        always return a value of no-action(1), a write of no-acti
        on(1) will have no effect, while a write of clear(2) 
        will clear all the counters."
      ::= {brControlPackage 1}

brSTAPMode OBJECT-TYPE
      SYNTAX      INTEGER  {
                  off (1),
                  on (2),
                  single (3)
      }
      ACCESS      read-write
      STATUS      mandatory
      DESCRIPTION "Determines whether the STAP algorithm is on or off. 
         The value on(2) provides STAP per Vlan while the value single(3) provides a 
         single STAP domain which runs under the Vlans."
      ::= {brControlPackage 2}

brLearnMode OBJECT-TYPE
      SYNTAX      INTEGER  {
                  off (1),
                  on (2)
      }
      ACCESS      read-write
      STATUS      mandatory
      DESCRIPTION "Determines whether the bridge is not learning 
        addresses
        (off), or learning addresses as permanent, deleteOnReset 
        or
        deleteOnTimeout."
      ::= {brControlPackage 3}

brAgingMode OBJECT-TYPE
      SYNTAX      INTEGER  {
                  on (1),
                  off (2)
      }
      ACCESS      read-write
      STATUS      mandatory
      DESCRIPTION "Determines whether the bridge will age out 
        entries in its filtering database or not."
      ::= {brControlPackage 7}

brMonitorPackage  OBJECT IDENTIFIER ::= {bridgeMgmt 2}
brDataBase        OBJECT IDENTIFIER ::= {bridgeMgmt 4}
brDummyPackage    OBJECT IDENTIFIER ::= {bridgeMgmt 5}
--
--       Dummy variables
--
brDatabaseType OBJECT-TYPE
      SYNTAX      INTEGER  {
                  filtering (1),
                  permanent (2),
                  atmCam (3)
      }
      ACCESS      read-only
      STATUS      mandatory
      DESCRIPTION "This dummy object enables the database full 
        trap to differentiate between the filtering database, 
        the permanent database and the ATM CAM."
      ::= {brDummyPackage 1}

brDatabaseLevel OBJECT-TYPE
      SYNTAX      INTEGER  {
                  ninetyPercent (90),
                  oneHundredPercent (100)
      }
      ACCESS      read-only
      STATUS      mandatory
      DESCRIPTION "This dummy object enables the database full 
        trap to differentiate between the database being 90% and 
        100% full."
      ::= {brDummyPackage 2}

END
