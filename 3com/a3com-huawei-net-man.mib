-- ==========================================================================
-- Copyright (C) 2008 by Hangzhou H3C Technologies Co., Ltd. All rights reserved.
--
-- Description: The purpose of this MIB file is to provide object definition
--              of network management parameters.
-- Reference:
-- Version: V1.0
-- History:
-- V1.0 2008-04-16 Initial version, created by Longyin
-- ==========================================================================
A3COM-HUAWEI-NET-MAN-MIB DEFINITIONS ::= BEGIN

IMPORTS
        OBJECT-TYPE, MODULE-IDENTITY, NOTIFICATION-TYPE
    FROM SNMPv2-SMI
        OBJECT-GROUP, MODULE-COMPLIANCE, NOTIFICATION-GROUP
    FROM SNMPv2-CONF
        InetAddressType, InetAddress
    FROM INET-ADDRESS-MIB
        h3cCommon
    FROM A3COM-HUAWEI-OID-MIB;

h3cNetMan MODULE-IDENTITY
    LAST-UPDATED "200804161700Z"
    ORGANIZATION
        "Hangzhou H3C Technologies Co., Ltd."
    CONTACT-INFO
        "Platform Team H3C Technologies Co., Ltd.
         Hai-Dian District Beijing P.R. China
         Http://www.h3c.com
         Zip: 100085"
    DESCRIPTION
        "This MIB file is to provide the object definition of the network
        management parameters.  These parameters are used to identify devices.
        It is useful for devices management in a dynamic address assignment
        network."
    REVISION "200804161700Z"
    DESCRIPTION
        "The initial version of this MIB file."
    ::= { h3cCommon 90 }

--
-- Object definitions
--
h3cNMConfigObjects OBJECT IDENTIFIER ::= { h3cNetMan 1 }

h3cNMMonitorObjects OBJECT IDENTIFIER ::= { h3cNetMan 2 }

h3cNMNotify OBJECT IDENTIFIER ::= { h3cNetMan 3 }

-- Scalar Objects for Notify
h3cNMNotifyScalarObjects OBJECT IDENTIFIER ::= { h3cNMNotify 1 }

h3cNMIpAddressType OBJECT-TYPE
    SYNTAX      InetAddressType
    MAX-ACCESS  accessible-for-notify
    STATUS      current
    DESCRIPTION
        "The IP address type of specified interface on the device."
    ::= { h3cNMNotifyScalarObjects 1 }

h3cNMIpAddress OBJECT-TYPE
    SYNTAX      InetAddress
    MAX-ACCESS  accessible-for-notify
    STATUS      current
    DESCRIPTION
        "The IP address of specified interface on the device."
    ::= { h3cNMNotifyScalarObjects 2 }

h3cNMCustomBuildInfo OBJECT-TYPE
    SYNTAX      OCTET STRING(SIZE(0..64))
    MAX-ACCESS  read-only
    STATUS      current
    DESCRIPTION
        "The customer-required information of devices, for example,
        OUI (Organizational Unique Identifier)."
    ::= { h3cNMNotifyScalarObjects 3 }

h3cNMSerialNum OBJECT-TYPE
    SYNTAX      OCTET STRING(SIZE(0..64))
    MAX-ACCESS  accessible-for-notify
    STATUS      current
    DESCRIPTION
        "The serial number used by NMS (Network Management Station) for
        mapping IP address and device."
    ::= { h3cNMNotifyScalarObjects 4 }

-- Notification Objects
h3cNMNotifyObjects OBJECT IDENTIFIER ::= { h3cNMNotify 2 }

h3cNMNotifyObjectsPrefix OBJECT IDENTIFIER ::= { h3cNMNotifyObjects 0 }

h3cIpAddrChangeNotify NOTIFICATION-TYPE
    OBJECTS
        {
            h3cNMIpAddressType,
            h3cNMIpAddress,
            h3cNMCustomBuildInfo,
            h3cNMSerialNum
        }
    STATUS      current
    DESCRIPTION
        "This notification will be generated when the IP address of active
        management interface is changed.  The change maybe originate from NMS,
        DHCP server or administrator.

        The management interfaces are the interfaces that assigned by
        administrator, which can be used to manage device, but may be inactive
        for link fault or IP address (IPv4 or IPv6) missing.

        The active management interface means an active interface, the IP
        address of which can be used for network management.

        This notification announces useful management IP address change.  So it
        is triggered by significative IP address change.

        Suppose that two management interfaces on a device, Interface-A and
        Interface-B.  Initially both interfaces are down and assigned no IP
        address. Configure Interface-A as the primary monitored interface,
        Interface-B as the secondary.

        Significative IP address change in following cases:
        1. If Interface-A is assigned an IP address primarily, and it is linking
        up, then Interface-B will be ignored.  A notification will be triggered,
        appending IP address of Interface-A.

        2. If Interface-B is assigned an IP address primarily, and it is linking
        up, then Interface-A will be ignored.  A notification will be triggered,
        appending IP address of Interface-B.

        3. If IP address of that interface, which had its IP address announced
        to NMS, is changed since last notification triggered, then another
        notification will be sent to NMS.

        4. Suppore that Interface-A was linked up and assigned an IP address
        primarily.  If for some unknown reason, Interface-A is down or loses IP
        address, and Interface-B is assigned an IP address which is different
        with that announced to NMS before, then a notification will be
        triggered, appending the new IP address that Interface-B assigned.

        5. A notification appending new IP address that Interface-A assigned
        will be triggered, if 4 occurs to Interface-B."

    ::= { h3cNMNotifyObjectsPrefix 1 }

-- Compliances Objects
h3cNetManConformance OBJECT IDENTIFIER ::= { h3cNetMan 4 }

h3cNetManCompliances OBJECT IDENTIFIER ::= { h3cNetManConformance 1 }

h3cNetManCompliance MODULE-COMPLIANCE
    STATUS      current
    DESCRIPTION
        "The statement of compliance for those implementing
        the network management MIB."
    MODULE
        MANDATORY-GROUPS
        {
            h3cNMMonitorGroup,
            h3cNMNotificationGroup
        }
    ::= { h3cNetManCompliances 1 }

h3cNetManGroups OBJECT IDENTIFIER ::= { h3cNetManConformance 2 }

h3cNMMonitorGroup OBJECT-GROUP
    OBJECTS
        {
            h3cNMIpAddressType,
            h3cNMIpAddress,
            h3cNMCustomBuildInfo,
            h3cNMSerialNum
        }
    STATUS current
    DESCRIPTION
        "A collection of objects in net management monitor group."
    ::= { h3cNetManGroups 1 }

h3cNMNotificationGroup NOTIFICATION-GROUP
    NOTIFICATIONS
        {
            h3cIpAddrChangeNotify
        }
    STATUS      current
    DESCRIPTION
         "A collection of objects in net management notification group."
    ::= { h3cNetManGroups 2 }

END
