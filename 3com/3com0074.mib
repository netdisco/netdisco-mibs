-- ------------------------------------------------------------------
-- Copyright (c) 3Com Corporation. All Rights Reserved.
-- ------------------------------------------------------------------
--
-- SMA Vlan Support MIB.
--
-- This module provides internal, private information to be shared
-- between units in the stack. A MIB definition is used to share this
-- information so that the existing SMA distributed SNMP stack can do 
-- most of the work.
--
A3COM0074-SMA-VLAN-SUPPORT DEFINITIONS ::= BEGIN


	IMPORTS
		smaVlanSupport FROM A3COM0004-GENERIC
		a3ComVlanIfIndex FROM GENERIC-3COM-VLAN-MIB-1-0-7
		OBJECT-TYPE FROM RFC-1212
		;

--
-- a3ComVlanPrivateIfTable
-- Private VLAN Information Table. To be used only by the agent and NOT to be 
-- published outside 3Com PDD.
--
a3ComVlanPrivateIfTable OBJECT-TYPE
      SYNTAX      SEQUENCE OF A3ComVlanIPrivatefEntry
      ACCESS      not-accessible
      STATUS      mandatory
      DESCRIPTION "Private VLAN information table for internal agent operations."
      ::= {smaVlanSupport 1}

a3ComVlanPrivateIfEntry OBJECT-TYPE
      SYNTAX      A3ComVlanIPrivatefEntry
      ACCESS      not-accessible
      STATUS      mandatory
      DESCRIPTION "An individual VLAN interface entry.  When an NMS wishes to 
        create a new entry in this table, it must obtain a non-zero index from 
        the a3ComNextAvailableVirtIfIndex object. Row creation in this table 
        will fail if the chosen index value does not match the current value 
        returned from the a3ComNextAvailableVirtIfIndex object."
      INDEX       {a3ComVlanIfIndex}
      ::= {a3ComVlanPrivateIfTable 1}

A3ComVlanIPrivatefEntry ::= SEQUENCE {
                  a3ComVlanCreateType             INTEGER,
                  a3ComVlanMembers                INTEGER
                  }

a3ComVlanCreateType OBJECT-TYPE
      SYNTAX      INTEGER  {
                  automatic (1),
                  dynamic (2),
                  manual (3)
      }
      ACCESS      read-write
      STATUS      mandatory
      DESCRIPTION "The reason this Vlan has been created. The possible values 
        are:
        automatic (1) -
            This VLAN was created on this unit due to replication across
            a stack of units.
        dynamic (2) -
            VLAN created internally by some automatic mechanism, for
            example GVRP.
        manual (3) -
            VLAN created by some external management application.
        NOTE - This MIB object may only be set by the agent. It is illegal
        and serves no purpose for this object to be set for some other
        application."
      ::= {a3ComVlanPrivateIfEntry 1}

a3ComVlanMembers OBJECT-TYPE
      SYNTAX      INTEGER 
      ACCESS      read-only
      STATUS      mandatory
      DESCRIPTION "Total number of members of this VLAN across the entire stack.
         If the value of this MIB object is zero then the VLAN is not currently 
        in use on any device in the stack."
      ::= {a3ComVlanPrivateIfEntry 2}



END
