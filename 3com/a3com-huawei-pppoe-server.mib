-- =================================================================
-- Copyright (c) 2004-2009 Hangzhou H3C Tech. Co., Ltd. All rights reserved.
--
-- Description: PPPoE server MIB
-- Reference:
-- Version:     V1.1
-- History:
-- V1.0 Initial version by y04444
-- V1.1 2009-09-07 Modify by yuhaibo
--      Add PPPoE server trap
-- =================================================================
A3COM-HUAWEI-PPPOE-SERVER-MIB DEFINITIONS ::= BEGIN
IMPORTS
    h3cCommon
        FROM A3COM-HUAWEI-OID-MIB
    OBJECT-TYPE, MODULE-IDENTITY, Integer32, Counter32, NOTIFICATION-TYPE
        FROM SNMPv2-SMI;

h3cPPPoEServer MODULE-IDENTITY
    LAST-UPDATED "200905060000Z"            -- May 06th, 2009 at 00:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "The MIB module is used for PPPoE server."
    REVISION    "200905060000Z"
    DESCRIPTION
        "Initial version"
    ::= { h3cCommon 102 }

h3cPPPoEServerObject OBJECT IDENTIFIER ::= { h3cPPPoEServer 1 }

--
-- PPPOE SERVER MAXIMUM SESSIONS SUPPORT
--

h3cPPPoEServerMaxSessions OBJECT-TYPE
    SYNTAX      Integer32
    MAX-ACCESS  read-only
    STATUS      current
    DESCRIPTION
        "The maximum sessions supported by PPPoE server."
    ::= { h3cPPPoEServerObject 1 }

--
-- PPPOE SERVER CURRENT SESSION NUMBERS
--

h3cPPPoEServerCurrSessions OBJECT-TYPE
    SYNTAX      Integer32
    MAX-ACCESS  read-only
    STATUS      current
    DESCRIPTION
        "The number of current sessions on the PPPoE server."
    ::= { h3cPPPoEServerObject 2 }

--
-- PPPOE SERVER AUTHENTICATION REQUEST NUMBERS
--

h3cPPPoEServerAuthRequests OBJECT-TYPE
    SYNTAX      Counter32
    MAX-ACCESS  read-only
    STATUS      current
    DESCRIPTION
        "The number of authentication requests."
    ::= { h3cPPPoEServerObject 3 }

--
-- PPPOE SERVER AUTHENTICATION SUCCESS NUMBERS
--

h3cPPPoEServerAuthSuccesses OBJECT-TYPE
    SYNTAX      Counter32
    MAX-ACCESS  read-only
    STATUS      current
    DESCRIPTION
        "The number of authentication succeses."
    ::= { h3cPPPoEServerObject 4 }

--
-- PPPOE SERVER AUTHENTICATION FAIL NUMBERS
--

h3cPPPoEServerAuthFailures OBJECT-TYPE
    SYNTAX      Counter32
    MAX-ACCESS  read-only
    STATUS      current
    DESCRIPTION
        "The number of authentication failure."
    ::= { h3cPPPoEServerObject 5 }

--
-- PPPOE SERVER ABNORMAL OFFLINE COUNT THRESHOLD
--

h3cPPPoESAbnormOffsThreshold OBJECT-TYPE
    SYNTAX      Integer32 (0..65535)
    MAX-ACCESS  read-write
    STATUS      current
    DESCRIPTION
        "The threshold of abnormal offline count."
    ::= { h3cPPPoEServerObject 6 }

--
-- PPPOE SERVER ABNORMAL OFFLINE PERCENT THRESHOLD
--

h3cPPPoESAbnormOffPerThreshold OBJECT-TYPE
    SYNTAX      Integer32 (0..100)
    MAX-ACCESS  read-write
    STATUS      current
    DESCRIPTION
        "The threshold of abnormal offline percent."
    ::= { h3cPPPoEServerObject 7 }

--
-- PPPOE SERVER NORMAL OFFLINE PERCENT THRESHOLD
--

h3cPPPoESNormOffPerThreshold OBJECT-TYPE
    SYNTAX      Integer32 (0..100)
    MAX-ACCESS  read-write
    STATUS      current
    DESCRIPTION
        "The threshold of normal offline percent."
    ::= { h3cPPPoEServerObject 8 }

--
-- Define the PPPoE Server Traps.
--
    h3cPPPoEServerTraps OBJECT IDENTIFIER ::= { h3cPPPoEServer 2 }

    h3cPPPoeServerTrapPrefix OBJECT IDENTIFIER ::= { h3cPPPoEServerTraps 0 }

    h3cPPPoESAbnormOffsAlarm NOTIFICATION-TYPE
        STATUS      current
        DESCRIPTION
            "This trap is generated when the PPPoE server abnormal
            offline counts over threshold in five minutes."
        ::= { h3cPPPoeServerTrapPrefix 1 }

    h3cPPPoESAbnormOffPerAlarm NOTIFICATION-TYPE
        STATUS      current
        DESCRIPTION
            "This trap is generated when the PPPoE server abnormal
            offline percent over threshold in five minutes."
        ::= { h3cPPPoeServerTrapPrefix 2 }

    h3cPPPoESNormOffPerAlarm NOTIFICATION-TYPE
        STATUS      current
        DESCRIPTION
            "This trap is generated when the PPPoE server normal
            offline percent under threshold in five minutes."
        ::= { h3cPPPoeServerTrapPrefix 3 }

END
