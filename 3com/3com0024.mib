-- ----------------------------------------------------------------------
-- Copyright (c) 3Com Corporation. All Rights Reserved.
-- ----------------------------------------------------------------------

A3COM0024-EVENT-EXTENSION DEFINITIONS ::= BEGIN


   IMPORTS
      eventExtensions FROM A3COM0027-RMON-EXTENSIONS
      DisplayString, eventDescription, eventIndex FROM RMON-MIB
      OBJECT-TYPE FROM RFC-1212
      TRAP-TYPE FROM RFC-1215
      ;

extEventTable OBJECT-TYPE
      SYNTAX      SEQUENCE OF ExtEventEntry
      ACCESS      not-accessible
      STATUS      mandatory
      DESCRIPTION "A list of events to be generated."
      ::= {eventExtensions 1}

extEventEntry OBJECT-TYPE
      SYNTAX      ExtEventEntry
      ACCESS      not-accessible
      STATUS      mandatory
      DESCRIPTION "A set of parameters that describe an event to be generated 
      when certain conditions are met."
      INDEX       {eventIndex}
      ::= {extEventTable 1}

ExtEventEntry ::= SEQUENCE {
                  eventAction                DisplayString (SIZE(0..127))
                  }

eventAction OBJECT-TYPE
      SYNTAX      DisplayString (SIZE(0..127))
      ACCESS      read-write
      STATUS      mandatory
      DESCRIPTION ""
      ::= {extEventEntry 1}

END
