-- ------------------------------------------------------------------------------
-- Copyright (c) 3Com Corporation. All Rights Reserved.
-- ------------------------------------------------------------------------------

A3COM0028-ALARM-PEAK DEFINITIONS ::= BEGIN


   IMPORTS
      OBJECT-TYPE FROM RFC-1212
      alarmExtensions FROM A3COM0027-RMON-EXTENSIONS
      alarmIndex FROM RMON-MIB
      ;

alarmExtTable OBJECT-TYPE
      SYNTAX      SEQUENCE OF AlarmExtEntry
      ACCESS      not-accessible
      STATUS      mandatory
      DESCRIPTION "This table augments the RMON alarm table defined in RFC1757. 
        The table does not define its own indices, but rather shares those 
        defined for the RMON alarm table. For each entry in the RMON alarm 
        table there will be a row in this table. The columns in this table can 
        be considered as additions to the standard MIB."
      ::= {alarmExtensions 1}

alarmExtEntry OBJECT-TYPE
      SYNTAX      AlarmExtEntry
      ACCESS      not-accessible
      STATUS      mandatory
      DESCRIPTION ""
      INDEX       {alarmIndex}
      ::= {alarmExtTable 1}

AlarmExtEntry ::= SEQUENCE {
                  alarmPeakValue             INTEGER
                  }

alarmPeakValue OBJECT-TYPE
      SYNTAX      INTEGER 
      ACCESS      read-only
      STATUS      mandatory
      DESCRIPTION "This value reports the maximum calculated value of
        'alarmValue' since the alarm was last activiated.This value can be used 
        by
        auto-calibrate applications."
      ::= {alarmExtEntry 1}



END
