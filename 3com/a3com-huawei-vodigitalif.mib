-- ==========================================================================
-- Copyright (C) 2004 by Huawei 3Com Technologies. All rights reserved.
--
-- Description: The purpose of this MIB file is to provide the the definition 
--              of the general digital voice interface configuration.
-- Reference:
-- Version: V1.0
-- History:
-- V1.0 2005-03-22 Initial version, created by Yang Youku
-- ==========================================================================
A3COM-HUAWEI-VODIGITALIF-MIB DEFINITIONS ::= BEGIN
        IMPORTS
            OBJECT-TYPE, MODULE-IDENTITY, Integer32
                FROM SNMPv2-SMI
        h3cVoice
                FROM A3COM-HUAWEI-OID-MIB;
    
        
        h3cVoiceDigitalInterface  MODULE-IDENTITY 
            LAST-UPDATED "200503150000Z"
            ORGANIZATION 
                "Huawei-3COM Technologies Co., Ltd."
            CONTACT-INFO 
                "PLAT Team Huawei 3Com Technologies co.,Ltd.                                
                Shang-Di Information Industry Base,
                Hai-Dian District Beijing P.R. China
                http://www.huawei-3com.com
                Zip:100085"
            DESCRIPTION 
                "The MIB file is to provide the definition of the
                general digital voice interface configuration."
            REVISION "200503150000Z"
            DESCRIPTION 
                "The initial version of this MIB file."
            ::= { h3cVoice 4 }

        
        h3cVoDigitalIfCommonObjects OBJECT IDENTIFIER ::= 
                                        { h3cVoiceDigitalInterface 1 }


--==========================================================================
--                      h3cVoDigitalIfCommonCfgTable
--
--==========================================================================
        h3cVoDigitalIfCommonCfgTable OBJECT-TYPE
            SYNTAX SEQUENCE OF H3CVoDigitalIfCommonCfgEntry
            MAX-ACCESS not-accessible
            STATUS current
            DESCRIPTION
                "This table contains the information about configurable 
                parameters for a digital voice interface."
            ::= { h3cVoDigitalIfCommonObjects 1 }

        
        h3cVoDigitalIfCommonCfgEntry OBJECT-TYPE
            SYNTAX H3CVoDigitalIfCommonCfgEntry
            MAX-ACCESS not-accessible
            STATUS current
            DESCRIPTION
                "The entry of h3cVoDigitalIfCommonCfgTable, which is 
                automatically created when a digital voice module has 
                been found."
            INDEX { h3cVoDIfCfgPort, h3cVoDIfCfgGroup }
            ::= { h3cVoDigitalIfCommonCfgTable 1 }

        
        H3CVoDigitalIfCommonCfgEntry ::=
            SEQUENCE { 
                h3cVoDIfCfgPort
                    Integer32,
                h3cVoDIfCfgGroup
                    Integer32,
                h3cVoDIfCfgBoardType
                    INTEGER,
                h3cVoDIfCfgSignalType
                    INTEGER,
                h3cVoDIfCfgTsInformation
                    OCTET STRING,
                h3cVoDIfCfgPortSubLine
                    OCTET STRING
             }

        h3cVoDIfCfgPort OBJECT-TYPE
            SYNTAX Integer32
            MAX-ACCESS not-accessible
            STATUS current
            DESCRIPTION
                "This object indicates the port of a voice digital module."
            ::= { h3cVoDigitalIfCommonCfgEntry 1 }


        h3cVoDIfCfgGroup OBJECT-TYPE
            SYNTAX Integer32
            MAX-ACCESS not-accessible
            STATUS current
            DESCRIPTION
                "This object indicates the group number of a voice digital 
                module."
            ::= { h3cVoDigitalIfCommonCfgEntry 2 }

        
        h3cVoDIfCfgBoardType OBJECT-TYPE
            SYNTAX INTEGER
                {
                e1vi(1),
                t1vi(2)
                }
            MAX-ACCESS read-only
            STATUS current
            DESCRIPTION
                "This object indicates the type of board."
            ::= { h3cVoDigitalIfCommonCfgEntry 3 }

        
        h3cVoDIfCfgSignalType OBJECT-TYPE
            SYNTAX INTEGER
                {
                r2(1),
                pri(2),
                emImmediateStart(3),
                emDelayStart(4),
                emWinkStart(5)
                }
            MAX-ACCESS read-only
            STATUS current
            DESCRIPTION
                "This object indicates the signal type of a group."
            ::= { h3cVoDigitalIfCommonCfgEntry 4 }

        
        h3cVoDIfCfgTsInformation OBJECT-TYPE
            SYNTAX OCTET STRING
            MAX-ACCESS read-only
            STATUS current
            DESCRIPTION
                "This object indicates the availability of every single timeslot 
                for voice services. 
                '1' indicates the timeslot is available for voice services.
                '0' indicates the timeslot is not available for voice services." 
            ::= { h3cVoDigitalIfCommonCfgEntry 5 }

        h3cVoDIfCfgPortSubLine OBJECT-TYPE
            SYNTAX OCTET STRING
            MAX-ACCESS read-only
            STATUS current
            DESCRIPTION
                "This object indicates the port subscriber line name."
            ::= { h3cVoDigitalIfCommonCfgEntry 6 }

        

        h3cVoDigitalIfEMObjects OBJECT IDENTIFIER ::= 
                                            { h3cVoiceDigitalInterface 2 }

--==========================================================================
--                      h3cVoDigitalIfEMCfgTable
--
--==========================================================================
        h3cVoDigitalIfEMCfgTable OBJECT-TYPE
            SYNTAX SEQUENCE OF H3CVoDigitalIfEMCfgEntry
            MAX-ACCESS not-accessible
            STATUS current
            DESCRIPTION
                "This table contains the information about configurable 
                parameters for a digital EM voice interface."
            ::= { h3cVoDigitalIfEMObjects 1 }

        
        h3cVoDigitalIfEMCfgEntry OBJECT-TYPE
            SYNTAX H3CVoDigitalIfEMCfgEntry
            MAX-ACCESS not-accessible
            STATUS current
            DESCRIPTION
                "The entry of h3cVoDigitalIfEMCfgTable."
            INDEX { h3cVoDIfEMCfgPort, h3cVoDIfEMCfgGroup }
            ::= { h3cVoDigitalIfEMCfgTable 1 }

        
        H3CVoDigitalIfEMCfgEntry ::=
            SEQUENCE { 
                h3cVoDIfEMCfgPort
                    Integer32,
                h3cVoDIfEMCfgGroup
                    Integer32,
                h3cVoDIfEMCfgTimeoutInterDigit
                    Integer32,
                h3cVoDIfEMCfgTimeoutRinging
                    Integer32,
                h3cVoDIfEMCfgTimeoutWaitDigit
                    Integer32,
                h3cVoDIfEMCfgPortSubLine
                    OCTET STRING
             }

        h3cVoDIfEMCfgPort OBJECT-TYPE
            SYNTAX Integer32
            MAX-ACCESS not-accessible
            STATUS current
            DESCRIPTION
                "This object indicates the port of a voice digital module."
            ::= { h3cVoDigitalIfEMCfgEntry 1 }

        
        h3cVoDIfEMCfgGroup OBJECT-TYPE
            SYNTAX Integer32
            MAX-ACCESS not-accessible
            STATUS current
            DESCRIPTION
                "This object indicates the group number of a voice digital 
                module."
            ::= { h3cVoDigitalIfEMCfgEntry 2 }

        
        h3cVoDIfEMCfgTimeoutInterDigit OBJECT-TYPE
            SYNTAX Integer32
            MAX-ACCESS read-write
            STATUS current
            DESCRIPTION
                "The maximum seconds, to wait for two DTMF (Dual Tone 
                Multi-Frequency) number."
            ::= { h3cVoDigitalIfEMCfgEntry 3 }

        
        h3cVoDIfEMCfgTimeoutRinging OBJECT-TYPE
            SYNTAX Integer32
            MAX-ACCESS read-write
            STATUS current
            DESCRIPTION
                "The maximum seconds, to wait for the ring back on the
                EM interface."
            ::= { h3cVoDigitalIfEMCfgEntry 4 }

        
        h3cVoDIfEMCfgTimeoutWaitDigit OBJECT-TYPE
            SYNTAX Integer32
            MAX-ACCESS read-write
            STATUS current
            DESCRIPTION
                "The maximum seconds, to wait for called number of called side."
            ::= { h3cVoDigitalIfEMCfgEntry 5 }

        h3cVoDIfEMCfgPortSubLine OBJECT-TYPE
            SYNTAX OCTET STRING
            MAX-ACCESS read-only
            STATUS current
            DESCRIPTION
                "This object indicates the port subscriber line name."
            ::= { h3cVoDigitalIfEMCfgEntry 6 }


--==========================================================================
--                      h3cVoDigitalIfEMABCDCfgTable
--
--==========================================================================
        h3cVoDigitalIfEMABCDCfgTable OBJECT-TYPE
            SYNTAX SEQUENCE OF H3CVoDigitalIfEMABCDCfgEntry
            MAX-ACCESS not-accessible
            STATUS current
            DESCRIPTION
                "This table contains the information about ABCD bits
                 parameters for a digital EM voice interface."
            ::= { h3cVoDigitalIfEMObjects 2 }

        
        h3cVoDigitalIfEMABCDCfgEntry OBJECT-TYPE
            SYNTAX H3CVoDigitalIfEMABCDCfgEntry
            MAX-ACCESS not-accessible
            STATUS current
            DESCRIPTION
                "The entry of h3cVoDigitalIfEMABCDCfgTable." 
            INDEX { h3cVoDIfEMABCDCfgPort, h3cVoDIfEMABCDCfgGroup }
            ::= { h3cVoDigitalIfEMABCDCfgTable 1 }

        
        H3CVoDigitalIfEMABCDCfgEntry ::=
            SEQUENCE { 
                h3cVoDIfEMABCDCfgPort
                    Integer32,
                h3cVoDIfEMABCDCfgGroup
                    Integer32,
                h3cVoDIfEMABCDRxIdle
                    OCTET STRING,
                h3cVoDIfEMABCDRxSeizure
                    OCTET STRING,
                h3cVoDIfEMABCDTxIdle
                    OCTET STRING,
                h3cVoDIfEMABCDTxSeizure
                    OCTET STRING,
                h3cVoDIFEMABCDSubLine
                    OCTET STRING
             }

        h3cVoDIfEMABCDCfgPort OBJECT-TYPE
            SYNTAX Integer32
            MAX-ACCESS not-accessible
            STATUS current
            DESCRIPTION
                "This object indicates the port of a voice digital module." 
            ::= { h3cVoDigitalIfEMABCDCfgEntry 1 }

        
        h3cVoDIfEMABCDCfgGroup OBJECT-TYPE
            SYNTAX Integer32
            MAX-ACCESS not-accessible
            STATUS current
            DESCRIPTION
                "This object indicates the group number of a voice digital 
                module."
            ::= { h3cVoDigitalIfEMABCDCfgEntry 2 }

        
        h3cVoDIfEMABCDRxIdle OBJECT-TYPE
            SYNTAX OCTET STRING (SIZE (4))
            MAX-ACCESS read-write
            STATUS current
            DESCRIPTION
                "This object indicates the ABCD bits of receiving idle 
                signal."
            ::= { h3cVoDigitalIfEMABCDCfgEntry 3 }

        
        h3cVoDIfEMABCDRxSeizure OBJECT-TYPE
            SYNTAX OCTET STRING (SIZE (4))
            MAX-ACCESS read-write
            STATUS current
            DESCRIPTION
                "This object indicates the ABCD bits of receiving seizure 
                signal."
            ::= { h3cVoDigitalIfEMABCDCfgEntry 4 }

        
        h3cVoDIfEMABCDTxIdle OBJECT-TYPE
            SYNTAX OCTET STRING (SIZE (4))
            MAX-ACCESS read-write
            STATUS current
            DESCRIPTION
                "This object indicates the ABCD bits of sending idle 
                signal."
            ::= { h3cVoDigitalIfEMABCDCfgEntry 5 }

        
        h3cVoDIfEMABCDTxSeizure OBJECT-TYPE
            SYNTAX OCTET STRING (SIZE (4))
            MAX-ACCESS read-write
            STATUS current
            DESCRIPTION
                "This object indicates the ABCD bits of sending seizure 
                signal."
            ::= { h3cVoDigitalIfEMABCDCfgEntry 6 }

        h3cVoDIFEMABCDSubLine OBJECT-TYPE
            SYNTAX OCTET STRING
            MAX-ACCESS read-only
            STATUS current
            DESCRIPTION
                "This object indicates the port subscriber line name."
            ::= { h3cVoDigitalIfEMABCDCfgEntry 7 }
            

--==========================================================================
--                      h3cVoDigitalIfEMTimerTable
--
--==========================================================================
        h3cVoDigitalIfEMTimerTable OBJECT-TYPE
            SYNTAX SEQUENCE OF H3CVoDigitalIfEMTimerEntry
            MAX-ACCESS not-accessible
            STATUS current
            DESCRIPTION
                "This table contains the timer parameters for a digital 
                EM voice interface."
        ::= { h3cVoDigitalIfEMObjects 4 }

        
        h3cVoDigitalIfEMTimerEntry OBJECT-TYPE
            SYNTAX H3CVoDigitalIfEMTimerEntry
            MAX-ACCESS not-accessible
            STATUS current
            DESCRIPTION
                "The entry of h3cVoDigitalIfEMTimerTable." 
            INDEX { h3cVoDIfEMTimerPort, h3cVoDIfEMTimerGroup }
            ::= { h3cVoDigitalIfEMTimerTable 1 }

        
        H3CVoDigitalIfEMTimerEntry ::=
            SEQUENCE { 
                h3cVoDIfEMTimerPort
                    Integer32,
                h3cVoDIfEMTimerGroup
                    Integer32,
                h3cVoDIfEMTimerSendWink
                    Integer32,
                h3cVoDIfEMTimerWinkRising
                    Integer32,
                h3cVoDIfEMTimerWinkHold
                    Integer32,
                h3cVoDIfEMTimerDialoutDelay
                    Integer32,
                h3cVoDIfEMTimerDelayRising
                    Integer32,
                h3cVoDIfEMTimerDelayHold
                    Integer32,
                h3cVoDIfEMTimerDtmf
                    Integer32,
                h3cVoDIfEMTimerDtmfInterval
                    Integer32,
                h3cVoDIfEMTimerPortSubLine
                    OCTET STRING
             }

        h3cVoDIfEMTimerPort OBJECT-TYPE
            SYNTAX Integer32
            MAX-ACCESS not-accessible
            STATUS current
            DESCRIPTION
                "This object indicates the port of a voice digital module." 
            ::= { h3cVoDigitalIfEMTimerEntry 1 }

        
        h3cVoDIfEMTimerGroup OBJECT-TYPE
            SYNTAX Integer32
            MAX-ACCESS not-accessible
            STATUS current
            DESCRIPTION
                "This object indicates the group number of a voice digital 
                module."
            ::= { h3cVoDigitalIfEMTimerEntry 2 }

        
        h3cVoDIfEMTimerSendWink OBJECT-TYPE
            SYNTAX Integer32
            MAX-ACCESS read-write
            STATUS current
            DESCRIPTION
                "This object indicates the maximum time in milliseconds
                between receiving seizure signal and sending wink signal. 
                This object can only take effect when h3cVoDIfCfgSignalType 
                is set to 'emWinkStart'."           
            DEFVAL { 200 }
            ::= { h3cVoDigitalIfEMTimerEntry 4 }

        
        h3cVoDIfEMTimerWinkRising OBJECT-TYPE
            SYNTAX Integer32
            MAX-ACCESS read-write
            STATUS current
            DESCRIPTION
                "This object indicates the maximum time in milliseconds
                between sending seizure signal and receiving wink signal. 
                This object can only take effect when h3cVoDIfCfgSignalType 
                is set to 'emWinkStart'." 
            ::= { h3cVoDigitalIfEMTimerEntry 5 }

        
        h3cVoDIfEMTimerWinkHold OBJECT-TYPE
            SYNTAX Integer32
            MAX-ACCESS read-write
            STATUS current
            DESCRIPTION
                "This object indicates the maximum duration in milliseconds
                for sending wink signal. This object can only take effect 
                when h3cVoDIfCfgSignalType is set to 'emWinkStart'."
            ::= { h3cVoDigitalIfEMTimerEntry 6 }

        
        h3cVoDIfEMTimerDialoutDelay OBJECT-TYPE
            SYNTAX Integer32
            MAX-ACCESS read-write
            STATUS current
            DESCRIPTION
                "This object indicates the maximum duration in milliseconds
                for sending called digits. This object can only take effect 
                when h3cVoDIfCfgSignalType is set to 'emImmediateStart'." 
            ::= { h3cVoDigitalIfEMTimerEntry 7 }

        
        h3cVoDIfEMTimerDelayRising OBJECT-TYPE
            SYNTAX Integer32
            MAX-ACCESS read-write
            STATUS current
            DESCRIPTION
                "This object indicates the maximum duration in milliseconds
                between receiveing seizure signal and sending delay signal. 
                This object can only take effect when h3cVoDIfCfgSignalType 
                is set to 'emDelayStart'." 
            ::= { h3cVoDigitalIfEMTimerEntry 8 }

        
        h3cVoDIfEMTimerDelayHold OBJECT-TYPE
            SYNTAX Integer32
            MAX-ACCESS read-write
            STATUS current
            DESCRIPTION
                "This object indicates the maximum duration in milliseconds 
                for sending delay signal. This object can only take effect when 
                h3cVoDIfCfgSignalType is set to 'emDelayStart'."
            ::= { h3cVoDigitalIfEMTimerEntry 9 }

        
        h3cVoDIfEMTimerDtmf OBJECT-TYPE
            SYNTAX Integer32
            MAX-ACCESS read-write
            STATUS current
            DESCRIPTION
                "This object indicates DTMF sending duration in milliseconds." 
            ::= { h3cVoDigitalIfEMTimerEntry 10 }

        
        h3cVoDIfEMTimerDtmfInterval OBJECT-TYPE
            SYNTAX Integer32
            MAX-ACCESS read-write
            STATUS current
            DESCRIPTION
                "This object indicates DTMF sending interval in milliseconds."
            ::= { h3cVoDigitalIfEMTimerEntry 11 }

        h3cVoDIfEMTimerPortSubLine OBJECT-TYPE
            SYNTAX OCTET STRING
            MAX-ACCESS read-only
            STATUS current
            DESCRIPTION
                "This object indicates the port subscriber line name."
            ::= { h3cVoDigitalIfEMTimerEntry 12 }
        


        h3cVoDigitalIfR2Objects OBJECT IDENTIFIER ::= 
                                            { h3cVoiceDigitalInterface 3 }

--==========================================================================
--                      h3cVoDigitalIfR2CfgTable
--
--==========================================================================
        h3cVoDigitalIfR2CfgTable OBJECT-TYPE
            SYNTAX SEQUENCE OF H3CVoDigitalIfR2CfgEntry
            MAX-ACCESS not-accessible
            STATUS current
            DESCRIPTION
                "This table contains information about general configurable 
                parameters for digital r2 voice interface."
            ::= { h3cVoDigitalIfR2Objects 1 }

        
        h3cVoDigitalIfR2CfgEntry OBJECT-TYPE
            SYNTAX H3CVoDigitalIfR2CfgEntry
            MAX-ACCESS not-accessible
            STATUS current
            DESCRIPTION
                "The entry of h3cVoDigitalIfR2CfgTable." 
            INDEX { h3cVoDIfR2CfgPort, h3cVoDIfR2CfgGroup }
            ::= { h3cVoDigitalIfR2CfgTable 1 }

        
        H3CVoDigitalIfR2CfgEntry ::=
            SEQUENCE { 
                h3cVoDIfR2CfgPort
                    Integer32,
                h3cVoDIfR2CfgGroup
                    Integer32,
                h3cVoDIfR2CfgCountryMode
                    INTEGER,
                h3cVoDIfR2CfgSpecialChar
                    INTEGER,
                h3cVoDIfR2CfgSpecialSignal
                    Integer32,      
                h3cVoDIfR2CfgSelectMode
                    INTEGER,
                h3cVoDIFR2CfgSubLine
                    OCTET STRING
             }

        h3cVoDIfR2CfgPort OBJECT-TYPE
            SYNTAX Integer32
            MAX-ACCESS not-accessible
            STATUS current
            DESCRIPTION
                "This object indicates the port of a voice digital module." 
            ::= { h3cVoDigitalIfR2CfgEntry 1 }

        
        h3cVoDIfR2CfgGroup OBJECT-TYPE
            SYNTAX Integer32
            MAX-ACCESS not-accessible
            STATUS current
            DESCRIPTION
                "This object indicates the group number of a voice digital 
                module."
            ::= { h3cVoDigitalIfR2CfgEntry 2 }


        h3cVoDIfR2CfgCountryMode OBJECT-TYPE
            SYNTAX INTEGER 
                {
                customer (1),
                argentina (2),
                australia (3),
                bengal (4),
                brazil (5),
                china (6),
                hongkong (7),
                india (8),
                indonesia (9),
                itut (10),
                korea (11),
                malaysia (12),
                mexico (13),
                newzealand (14),
                singapore (15),
                thailand (16)
                }
            MAX-ACCESS read-write
            STATUS current
            DESCRIPTION
                "This object indicates the value of country mode."
            ::= { h3cVoDigitalIfR2CfgEntry 3 }
            
            
        h3cVoDIfR2CfgSpecialChar OBJECT-TYPE
            SYNTAX INTEGER 
                {
                null (0),
                a (65),
                b (66),
                c (67),
                d (68),
                pound (35),
                asterisk (42)
                }
            MAX-ACCESS read-write
            STATUS current
            DESCRIPTION
                "This object indicates the special character(A,B,C,D,#,*)."
            ::= { h3cVoDigitalIfR2CfgEntry 4 }


        h3cVoDIfR2CfgSpecialSignal OBJECT-TYPE
            SYNTAX Integer32 (11..16)
            MAX-ACCESS read-write
            STATUS current
            DESCRIPTION
                "This object indicates the signal of special character."
            DEFVAL {16}
            ::= { h3cVoDigitalIfR2CfgEntry 5 }


        h3cVoDIfR2CfgSelectMode OBJECT-TYPE
            SYNTAX INTEGER
                {
                min(1),
                max(2),
                minpoll(3),
                maxpoll(4)
                }
            MAX-ACCESS read-write
            STATUS current
            DESCRIPTION
                "This object indicates the trunk mode to be selected:
                min            set selected trunk mode to min-mode.
                max            set selected trunk mode to max-mode.
                minpoll        set selected trunk mode to min-poll-mode.  
                maxpoll        set selected trunk mode to max-poll-mode.
                "
            ::= { h3cVoDigitalIfR2CfgEntry 6 }

        h3cVoDIFR2CfgSubLine OBJECT-TYPE
            SYNTAX OCTET STRING
            MAX-ACCESS read-only
            STATUS current
            DESCRIPTION
                "This object indicates the port subscriber line name."
            ::= { h3cVoDigitalIfR2CfgEntry 7 }
            

--==========================================================================
--                      h3cVoDigitalIfR2ABCDCfgTable
--
--==========================================================================
        h3cVoDigitalIfR2ABCDCfgTable OBJECT-TYPE
            SYNTAX SEQUENCE OF H3CVoDigitalIfR2ABCDCfgEntry
            MAX-ACCESS not-accessible
            STATUS current
            DESCRIPTION
                "This table contains the information about ABCD bits
                 parameters for a digital r2 voice interface."
            ::= { h3cVoDigitalIfR2Objects 2 }

        
        h3cVoDigitalIfR2ABCDCfgEntry OBJECT-TYPE
            SYNTAX H3CVoDigitalIfR2ABCDCfgEntry
            MAX-ACCESS not-accessible
            STATUS current
            DESCRIPTION
                "The entry of h3cVoDigitalIfR2ABCDCfgTable." 
            INDEX { h3cVoDIfR2ABCDCfgPort, h3cVoDIfR2ABCDCfgGroup }
            ::= { h3cVoDigitalIfR2ABCDCfgTable 1 }

        
        H3CVoDigitalIfR2ABCDCfgEntry ::=
            SEQUENCE { 
                h3cVoDIfR2ABCDCfgPort
                    Integer32,
                h3cVoDIfR2ABCDCfgGroup
                    Integer32,
                h3cVoDIfR2ABCDReverseABCD
                    OCTET STRING,
                h3cVoDIfR2ABCDRenewABCD
                    OCTET STRING,
                h3cVoDIfR2ABCDRxIdle
                    OCTET STRING,
                h3cVoDIfR2ABCDTxIdle
                    OCTET STRING,
                h3cVoDIfR2ABCDRxSeizure
                    OCTET STRING,
                h3cVoDIfR2ABCDTxSeizure
                    OCTET STRING,
                h3cVoDIfR2ABCDRxSeizureAck
                    OCTET STRING,
                h3cVoDIfR2ABCDTxSeizureAck
                    OCTET STRING,
                h3cVoDIfR2ABCDRxAnswer
                    OCTET STRING,
                h3cVoDIfR2ABCDTxAnswer
                    OCTET STRING,
                h3cVoDIfR2ABCDRxClearForward
                    OCTET STRING,
                h3cVoDIfR2ABCDTxClearForward
                    OCTET STRING,
                h3cVoDIfR2ABCDRxClearBack
                    OCTET STRING,
                h3cVoDIfR2ABCDTxClearBack
                    OCTET STRING,
                h3cVoDIfR2ABCDRxReleaseGuard
                    OCTET STRING,
                h3cVoDIfR2ABCDTxReleaseGuard
                    OCTET STRING,
                h3cVoDIfR2ABCDRxBlocking
                    OCTET STRING,
                h3cVoDIfR2ABCDTxBlocking
                    OCTET STRING,
                h3cVoDIfR2ABCDSubLine
                    OCTET STRING            
             }

        h3cVoDIfR2ABCDCfgPort OBJECT-TYPE
            SYNTAX Integer32
            MAX-ACCESS not-accessible
            STATUS current
            DESCRIPTION
                "This object indicates the port of a voice digital module."  
            ::= { h3cVoDigitalIfR2ABCDCfgEntry 1 }

        
        h3cVoDIfR2ABCDCfgGroup OBJECT-TYPE
            SYNTAX Integer32
            MAX-ACCESS not-accessible
            STATUS current
            DESCRIPTION
                "This object indicates the group number of a voice digital 
                module."
            ::= { h3cVoDigitalIfR2ABCDCfgEntry 2 }

        
        h3cVoDIfR2ABCDReverseABCD OBJECT-TYPE
            SYNTAX OCTET STRING (SIZE (4))
            MAX-ACCESS read-write
            STATUS current
            DESCRIPTION
                "This object indicates whether the ABCD bits should be inverted.
                '0' : disable invertion.
                '1' : enable invertion.
                "
            ::= { h3cVoDigitalIfR2ABCDCfgEntry 3 }

        
        h3cVoDIfR2ABCDRenewABCD OBJECT-TYPE
            SYNTAX OCTET STRING (SIZE (4))
            MAX-ACCESS read-write
            STATUS current
            DESCRIPTION
                "This object indicates the unused ABCD bits to be sent."
            ::= { h3cVoDigitalIfR2ABCDCfgEntry 4 }


        h3cVoDIfR2ABCDRxIdle OBJECT-TYPE
            SYNTAX OCTET STRING (SIZE (4))
            MAX-ACCESS read-write
            STATUS current
            DESCRIPTION
                "This object indicates the IDLE line signaling to be received."
            ::= { h3cVoDigitalIfR2ABCDCfgEntry 5 }


        h3cVoDIfR2ABCDTxIdle OBJECT-TYPE
            SYNTAX OCTET STRING (SIZE (4))
            MAX-ACCESS read-write
            STATUS current
            DESCRIPTION
                "This object indicates the IDLE line signaling to be sent."
            ::= { h3cVoDigitalIfR2ABCDCfgEntry 6 }

        
        h3cVoDIfR2ABCDRxSeizure OBJECT-TYPE
            SYNTAX OCTET STRING (SIZE (4))
            MAX-ACCESS read-write
            STATUS current
            DESCRIPTION
                "This object indicates the SEIZURE line signaling to be received."
            ::= { h3cVoDigitalIfR2ABCDCfgEntry 7 }


        h3cVoDIfR2ABCDTxSeizure OBJECT-TYPE
            SYNTAX OCTET STRING (SIZE (4))
            MAX-ACCESS read-write
            STATUS current
            DESCRIPTION
                "This object indicates the SEIZURE line signaling to be sent."
            ::= { h3cVoDigitalIfR2ABCDCfgEntry 8 }
    

        h3cVoDIfR2ABCDRxSeizureAck OBJECT-TYPE
            SYNTAX OCTET STRING (SIZE (4))
            MAX-ACCESS read-write
            STATUS current
            DESCRIPTION
                "This object indicates the SEIZURE_ACK line signaling to be
                received."
            ::= { h3cVoDigitalIfR2ABCDCfgEntry 9 }


        h3cVoDIfR2ABCDTxSeizureAck OBJECT-TYPE
            SYNTAX OCTET STRING (SIZE (4))
            MAX-ACCESS read-write
            STATUS current
            DESCRIPTION
                "This object indicates the SEIZURE_ACK line signaling to be sent."
            ::= { h3cVoDigitalIfR2ABCDCfgEntry 10 }


        h3cVoDIfR2ABCDRxAnswer OBJECT-TYPE
            SYNTAX OCTET STRING (SIZE (4))
            MAX-ACCESS read-write
            STATUS current
            DESCRIPTION
                "This object indicates the ANSWER line signaling to be received."
            ::= { h3cVoDigitalIfR2ABCDCfgEntry 11 }


        h3cVoDIfR2ABCDTxAnswer OBJECT-TYPE
            SYNTAX OCTET STRING (SIZE (4))
            MAX-ACCESS read-write
            STATUS current
            DESCRIPTION
                "This object indicates the ANSWER line signaling to be sent."
            ::= { h3cVoDigitalIfR2ABCDCfgEntry 12 }


        h3cVoDIfR2ABCDRxClearForward OBJECT-TYPE
            SYNTAX OCTET STRING (SIZE (4))
            MAX-ACCESS read-write
            STATUS current
            DESCRIPTION
                "This object indicates the CLEAR_FORWARD line signaling to be
                received."
            ::= { h3cVoDigitalIfR2ABCDCfgEntry 13 }


        h3cVoDIfR2ABCDTxClearForward OBJECT-TYPE
            SYNTAX OCTET STRING (SIZE (4))
            MAX-ACCESS read-write
            STATUS current
            DESCRIPTION
                "This object indicates the CLEAR_FORWARD line signaling to 
                be sent." 
            ::= { h3cVoDigitalIfR2ABCDCfgEntry 14 }


        h3cVoDIfR2ABCDRxClearBack OBJECT-TYPE
            SYNTAX OCTET STRING (SIZE (4))
            MAX-ACCESS read-write
            STATUS current
            DESCRIPTION
                "This object indicates the CLEAR_BACKWARD line signaling to
                be received."
            ::= { h3cVoDigitalIfR2ABCDCfgEntry 15 }


        h3cVoDIfR2ABCDTxClearBack OBJECT-TYPE
            SYNTAX OCTET STRING (SIZE (4))
            MAX-ACCESS read-write
            STATUS current
            DESCRIPTION
                "This object indicates the CLEAR_BACKWARD line signaling to
                be sent."
            ::= { h3cVoDigitalIfR2ABCDCfgEntry 16 }


        h3cVoDIfR2ABCDRxReleaseGuard OBJECT-TYPE
            SYNTAX OCTET STRING (SIZE (4))
            MAX-ACCESS read-write
            STATUS current
            DESCRIPTION
                "This object indicates the RELEASE_GUARD line signaling 
                to be received."
            ::= { h3cVoDigitalIfR2ABCDCfgEntry 17 }


        h3cVoDIfR2ABCDTxReleaseGuard OBJECT-TYPE
            SYNTAX OCTET STRING (SIZE (4))
            MAX-ACCESS read-write
            STATUS current
            DESCRIPTION
                "This object indicates the RELEASE_GUARD line signaling
                to be sent."
            ::= { h3cVoDigitalIfR2ABCDCfgEntry 18 }

            
        h3cVoDIfR2ABCDRxBlocking OBJECT-TYPE
            SYNTAX OCTET STRING (SIZE (4))
            MAX-ACCESS read-write
            STATUS current
            DESCRIPTION
                "This object indicates the BLOCKING line signaling to be 
                received."
            ::= { h3cVoDigitalIfR2ABCDCfgEntry 19 }


        h3cVoDIfR2ABCDTxBlocking OBJECT-TYPE
            SYNTAX OCTET STRING (SIZE (4))
            MAX-ACCESS read-write
            STATUS current
            DESCRIPTION
                "This object indicates the BLOCKING line signaling to be
                sent."
            ::= { h3cVoDigitalIfR2ABCDCfgEntry 20}


        h3cVoDIfR2ABCDSubLine OBJECT-TYPE
            SYNTAX OCTET STRING
            MAX-ACCESS read-only
            STATUS current
            DESCRIPTION
                "This object indicates the port subscriber line name."
            ::= { h3cVoDigitalIfR2ABCDCfgEntry 21 }


--==========================================================================
--                      h3cVoDigitalIfR2MfcCfgTable
--
--==========================================================================
        h3cVoDigitalIfR2MfcCfgTable OBJECT-TYPE
            SYNTAX SEQUENCE OF H3CVoDigitalIfR2MfcCfgEntry
            MAX-ACCESS not-accessible
            STATUS current
            DESCRIPTION
                "This table contains information about MFC(Multi-Frequency  
                Control) configurable parameters for digital r2 voice 
                interface."
            ::= { h3cVoDigitalIfR2Objects 3 }

        
        h3cVoDigitalIfR2MfcCfgEntry OBJECT-TYPE
            SYNTAX H3CVoDigitalIfR2MfcCfgEntry
            MAX-ACCESS not-accessible
            STATUS current
            DESCRIPTION
                "The entry of h3cVoDigitalIfR2MfcCfgTable." 
            INDEX { h3cVoDIfR2MfcCfgPort, h3cVoDIfR2MfcCfgGroup }
            ::= { h3cVoDigitalIfR2MfcCfgTable 1 }

        
        H3CVoDigitalIfR2MfcCfgEntry ::=
            SEQUENCE { 
                h3cVoDIfR2MfcCfgPort
                    Integer32,
                h3cVoDIfR2MfcCfgGroup
                    Integer32,
                h3cVoDIfR2BillingCategory
                    Integer32,
                h3cVoDIfR2CallingCategory
                    Integer32,      
                h3cVoDIfR2Congestion
                    Integer32,  
                h3cVoDIfR2DemandRefused
                    Integer32,                                          
                h3cVoDIfR2DigitEnd
                    Integer32,  
                h3cVoDIfR2Nullnum
                    Integer32,  
                h3cVoDIfR2ReqBillingCategory
                    Integer32,
                h3cVoDIfR2ReqCallingCategory
                    Integer32,
                h3cVoDIfR2ReqCurrentdigit
                    Integer32,
                h3cVoDIfR2ReqFirstCallingnum
                    Integer32,
                h3cVoDIfR2ReqFirstDigit
                    Integer32,
                h3cVoDIfR2ReqNextCallednum
                    Integer32,
                h3cVoDIfR2ReqNextCallingnum
                    Integer32,
                h3cVoDIfR2ReqLastFirstDigit
                    Integer32,
                h3cVoDIfR2ReqLastSecondDigit
                    Integer32,
                h3cVoDIfR2ReqLastThirdDigit
                    Integer32,
                h3cVoDIfR2ReqSwitchGroupB
                    Integer32,
                h3cVoDIfR2SubscriberIdle
                    Integer32,
                h3cVoDIfR2SubscriberBusy
                    Integer32,
                h3cVoDIfR2ReqCallingnumOffset
                    Integer32,
                h3cVoDIfR2CallCreateInA
                    Integer32,
                h3cVoDIfR2ReqFirstCalledNumInC
                    Integer32,
                h3cVoDIfR2ReqCurCalledNumInC
                    Integer32,
                h3cVoDIfR2ReqCalledNumSwitchA
                    Integer32,
                h3cVoDIfR2ReqSpecialSignal
                    Integer32,
                h3cVoDIfR2SubscriberCharge
                    Integer32,
                h3cVoDIfR2SubscriberAbnormal
                    Integer32,
                h3cVoDIfR2Ani
                    INTEGER,
                h3cVoDIfR2SubLine
                    OCTET STRING
             }

        h3cVoDIfR2MfcCfgPort OBJECT-TYPE
            SYNTAX Integer32
            MAX-ACCESS not-accessible
            STATUS current
            DESCRIPTION
                "This object indicates the port of a voice digital module."  
            ::= { h3cVoDigitalIfR2MfcCfgEntry 1 }

        
        h3cVoDIfR2MfcCfgGroup OBJECT-TYPE
            SYNTAX Integer32
            MAX-ACCESS not-accessible
            STATUS current
            DESCRIPTION
                "This object indicates the group number of a voice digital 
                module."
            ::= { h3cVoDigitalIfR2MfcCfgEntry 2 }

        h3cVoDIfR2BillingCategory OBJECT-TYPE
            SYNTAX Integer32 (1..16)
            MAX-ACCESS read-write
            STATUS current
            DESCRIPTION
                "This object indicates the value of BILLING CATEGORY during
                the MFC procedure."
            ::= { h3cVoDigitalIfR2MfcCfgEntry 3 }           
            
                            
        h3cVoDIfR2CallingCategory OBJECT-TYPE
            SYNTAX Integer32 (1..16)
            MAX-ACCESS read-write
            STATUS current
            DESCRIPTION
                "This object indicates the value of CALLING CATEGORY during 
                the MFC procedure."
            ::= { h3cVoDigitalIfR2MfcCfgEntry 4 }
        
        
        h3cVoDIfR2Congestion OBJECT-TYPE
            SYNTAX Integer32 (1..16)
            MAX-ACCESS read-write
            STATUS current
            DESCRIPTION
                "This object indicates the value of CONGESTION during 
                the MFC procedure. "
            ::= { h3cVoDigitalIfR2MfcCfgEntry 5 }


        h3cVoDIfR2DemandRefused OBJECT-TYPE
            SYNTAX Integer32 (1..16)
            MAX-ACCESS read-write
            STATUS current
            DESCRIPTION
                "This object indicates the value of DEMAND REFUSED during 
                the MFC procedure."
            ::= { h3cVoDigitalIfR2MfcCfgEntry 6 }


        h3cVoDIfR2DigitEnd OBJECT-TYPE
            SYNTAX Integer32 (1..16)
            MAX-ACCESS read-write
            STATUS current
            DESCRIPTION
                "This object indicates the value of DIGIT END during 
                the MFC procedure."
            ::= { h3cVoDigitalIfR2MfcCfgEntry 7 }


        h3cVoDIfR2Nullnum OBJECT-TYPE
            SYNTAX Integer32 (1..16)
            MAX-ACCESS read-write
            STATUS current
            DESCRIPTION
                "This object indicates the value of NULL NUMBER during 
                the MFC procedure."
            ::= { h3cVoDigitalIfR2MfcCfgEntry 8 }


        h3cVoDIfR2ReqBillingCategory OBJECT-TYPE
            SYNTAX Integer32 (1..16)
            MAX-ACCESS read-write
            STATUS current
            DESCRIPTION
                "This object indicates the value of REQUESTING BILLING 
                category during the MFC procedure."
            ::= { h3cVoDigitalIfR2MfcCfgEntry 9 }


        h3cVoDIfR2ReqCallingCategory OBJECT-TYPE
            SYNTAX Integer32 (1..16)
            MAX-ACCESS read-write
            STATUS current
            DESCRIPTION
                "This object indicates the value of REQUESTING CALLING CATEGORY 
                during the MFC procedure."
            ::= { h3cVoDigitalIfR2MfcCfgEntry 10 }


        h3cVoDIfR2ReqCurrentdigit OBJECT-TYPE
            SYNTAX Integer32 (1..16)
            MAX-ACCESS read-write
            STATUS current
            DESCRIPTION
                "This object indicates the value of REQUESTING CURRENT DIGIT 
                during the MFC procedure."
            ::= { h3cVoDigitalIfR2MfcCfgEntry 11 }


        h3cVoDIfR2ReqFirstCallingnum OBJECT-TYPE
            SYNTAX Integer32 (1..16)
            MAX-ACCESS read-write
            STATUS current
            DESCRIPTION
                "This object indicates the value of REQUESTING FIRST CALLING 
                NUMBER during the MFC procedure."
            ::= { h3cVoDigitalIfR2MfcCfgEntry 12 }


        h3cVoDIfR2ReqFirstDigit OBJECT-TYPE
            SYNTAX Integer32 (1..16)
            MAX-ACCESS read-write
            STATUS current
            DESCRIPTION
                "This object indicates the value of REQUESTING FIRST DIGIT 
                during the MFC procedure."
            ::= { h3cVoDigitalIfR2MfcCfgEntry 13 }


        h3cVoDIfR2ReqNextCallednum OBJECT-TYPE
            SYNTAX Integer32 (1..16)
            MAX-ACCESS read-write
            STATUS current
            DESCRIPTION
                "This object indicates the value of REQUESTING NEXT CALLED 
                NUMBER during the MFC procedure."
            ::= { h3cVoDigitalIfR2MfcCfgEntry 14 }

        h3cVoDIfR2ReqNextCallingnum OBJECT-TYPE
            SYNTAX Integer32 (1..16)
            MAX-ACCESS read-write
            STATUS current
            DESCRIPTION
                "This object indicates the value of REQUESTING NEXT CALLING 
                NUMBER during the MFC procedure."
            ::= { h3cVoDigitalIfR2MfcCfgEntry 15 }

        h3cVoDIfR2ReqLastFirstDigit OBJECT-TYPE
            SYNTAX Integer32 (1..16)
            MAX-ACCESS read-write
            STATUS current
            DESCRIPTION
                "This object indicates the value of REQUESTING LAST FIRST 
                DIGIT during the MFC procedure."
            ::= { h3cVoDigitalIfR2MfcCfgEntry 16 }

        h3cVoDIfR2ReqLastSecondDigit OBJECT-TYPE
            SYNTAX Integer32 (1..16)
            MAX-ACCESS read-write
            STATUS current
            DESCRIPTION
                "This object indicates the value of REQUESTING LAST SECOND DIIGT 
                during the MFC procedure."
            ::= { h3cVoDigitalIfR2MfcCfgEntry 17 }

        h3cVoDIfR2ReqLastThirdDigit OBJECT-TYPE
            SYNTAX Integer32 (1..16)
            MAX-ACCESS read-write
            STATUS current
            DESCRIPTION
                "This object indicates the value of REQUESTING LAST LAST THIRD 
                DIGIT during the MFC procedure."
            ::= { h3cVoDigitalIfR2MfcCfgEntry 18 }

        h3cVoDIfR2ReqSwitchGroupB OBJECT-TYPE
            SYNTAX Integer32 (1..16)
            MAX-ACCESS read-write
            STATUS current
            DESCRIPTION
                "This object indicates the value of REQUESTING SWITCH GROUP B 
                during the MFC procedure."
            ::= { h3cVoDigitalIfR2MfcCfgEntry 19 }

        h3cVoDIfR2SubscriberIdle OBJECT-TYPE
            SYNTAX Integer32 (1..16)
            MAX-ACCESS read-write
            STATUS current
            DESCRIPTION
                "This object indicates the value of SUSCRIBER IDLE during the 
                MFC procedure."
            ::= { h3cVoDigitalIfR2MfcCfgEntry 20 }

        h3cVoDIfR2SubscriberBusy OBJECT-TYPE
            SYNTAX Integer32 (1..16)
            MAX-ACCESS read-write
            STATUS current
            DESCRIPTION
                "This object indicates the value of SUBSCRIBER BUSY."
            ::= { h3cVoDigitalIfR2MfcCfgEntry 21 }

        h3cVoDIfR2ReqCallingnumOffset OBJECT-TYPE
            SYNTAX Integer32 (1..10)
            MAX-ACCESS read-write
            STATUS current
            DESCRIPTION
                "This object indicates the value of CALLING NUMBER OFFSET 
                during the MFC procedure."
            ::= { h3cVoDigitalIfR2MfcCfgEntry 22 }
            
        h3cVoDIfR2CallCreateInA OBJECT-TYPE
            SYNTAX Integer32 (1..16)
            MAX-ACCESS read-write
            STATUS current
            DESCRIPTION
                "This object indicates the value of CALLCREATE IN GROUP A during 
                the MFC procedure.
                "
        DEFVAL {6}
            ::= { h3cVoDigitalIfR2MfcCfgEntry 23 }

        h3cVoDIfR2ReqFirstCalledNumInC OBJECT-TYPE
            SYNTAX Integer32 (1..16)
            MAX-ACCESS read-write
            STATUS current
            DESCRIPTION
                "This object indicates the value of FIRST CALLED NUMBER IN GROUP C 
                during the MFC procedure."
            ::= { h3cVoDigitalIfR2MfcCfgEntry 24 }
            
        h3cVoDIfR2ReqCurCalledNumInC OBJECT-TYPE
            SYNTAX Integer32 (1..16)
            MAX-ACCESS read-write
            STATUS current
            DESCRIPTION
                "This object indicates the value of CURRENT CALLED NUMBER IN GROUP 
                C during the MFC procedure."
            ::= { h3cVoDigitalIfR2MfcCfgEntry 25 }
            
        h3cVoDIfR2ReqCalledNumSwitchA OBJECT-TYPE
            SYNTAX Integer32 (1..16)
            MAX-ACCESS read-write
            STATUS current
            DESCRIPTION
                "This object indicates the value of REQUEST CALLED NUMBER AND 
                SWITCH TO GROUP A during the MFC procedure."
            ::= { h3cVoDigitalIfR2MfcCfgEntry 26 }
            
        h3cVoDIfR2ReqSpecialSignal OBJECT-TYPE
            SYNTAX Integer32 (1..16)
            MAX-ACCESS read-write
            STATUS current
            DESCRIPTION
                "This object indicates the value of SPECIAL SIGNAL during the 
                MFC procedure."
            ::= { h3cVoDigitalIfR2MfcCfgEntry 27 }
        
        h3cVoDIfR2SubscriberCharge OBJECT-TYPE
            SYNTAX Integer32 (1..16)
            MAX-ACCESS read-write
            STATUS current
            DESCRIPTION
                "This object indicates the value of SUBSCRIBER CHARGE during the 
                MFC procedure."
            ::= { h3cVoDigitalIfR2MfcCfgEntry 28 }

        h3cVoDIfR2SubscriberAbnormal OBJECT-TYPE
            SYNTAX Integer32 (1..16)
            MAX-ACCESS read-write
            STATUS current
            DESCRIPTION
                "This object indicates the value of SUBSCRIBER ABNORMAL during 
                the MFC procedure."
            ::= { h3cVoDigitalIfR2MfcCfgEntry 29 }
            
        h3cVoDIfR2Ani OBJECT-TYPE
            SYNTAX INTEGER
                {
                disable(1),
                all(2),
                ka(3)
                }
            MAX-ACCESS read-write
            STATUS current
            DESCRIPTION
                "This object indicates whether to return the calling category and 
                the call number during the MFC procedure." 
            ::= { h3cVoDigitalIfR2MfcCfgEntry 30 }
            
        h3cVoDIfR2SubLine OBJECT-TYPE
            SYNTAX OCTET STRING 
            MAX-ACCESS read-only
            STATUS current
            DESCRIPTION
                "This object indicates the port subscriber line name."
            ::= { h3cVoDigitalIfR2MfcCfgEntry 31 }



--==========================================================================
--                      h3cVoDigitalIfR2TimerCfgTable
--
--==========================================================================
        h3cVoDigitalIfR2TimerCfgTable OBJECT-TYPE
            SYNTAX SEQUENCE OF H3CVoDigitalIfR2TimerCfgEntry
            MAX-ACCESS not-accessible
            STATUS current
            DESCRIPTION
                "This table contains information about time parameters
                for digital r2 voice interface."
            ::= { h3cVoDigitalIfR2Objects 4 }

        
        h3cVoDigitalIfR2TimerCfgEntry OBJECT-TYPE
            SYNTAX H3CVoDigitalIfR2TimerCfgEntry
            MAX-ACCESS not-accessible
            STATUS current
            DESCRIPTION
                "The entry of h3cVoDigitalIfR2TimeCfgTable." 
            INDEX { h3cVoDIfR2TimeCfgPort, h3cVoDIfR2TimeCfgGroup }
            ::= { h3cVoDigitalIfR2TimerCfgTable 1 }

        
        H3CVoDigitalIfR2TimerCfgEntry ::=
            SEQUENCE { 
                h3cVoDIfR2TimeCfgPort
                    Integer32,
                h3cVoDIfR2TimeCfgGroup
                    Integer32,
                h3cVoDIfR2CfgDebounceTime
                    Integer32,      
                h3cVoDIfR2CfgSendringBackTime
                    Integer32,  
                h3cVoDIfR2CfgSendringBusyTime
                    Integer32,                                                                  
                h3cVoDIfR2PulseSignalPersistT
                    Integer32,
                h3cVoDIfR2CfgDlAnswerTime
                    Integer32,
                h3cVoDIfR2CfgDlClearBackTime
                    Integer32,
                h3cVoDIfR2CfgDlClearForwardT
                    Integer32,
                h3cVoDIfR2CfgDlSeizureTime
                    Integer32,
                h3cVoDIfR2CfgDlReanswerTime
                    Integer32,
                h3cVoDIfR2CfgDlRelGuardTime
                    Integer32,
                h3cVoDIfR2CfgMfcGroupBTime
                    Integer32,
                h3cVoDIfR2CfgDTMFTime
                    Integer32,
                h3cVoDIfR2TimeCfgSubLine
                    OCTET STRING
             }

        h3cVoDIfR2TimeCfgPort OBJECT-TYPE
            SYNTAX Integer32
            MAX-ACCESS not-accessible
            STATUS current
            DESCRIPTION
                "This object indicates the port of a voice digital module."  
            ::= { h3cVoDigitalIfR2TimerCfgEntry 1 }
                  
        
        h3cVoDIfR2TimeCfgGroup OBJECT-TYPE
            SYNTAX Integer32
            MAX-ACCESS not-accessible
            STATUS current
            DESCRIPTION
                "This object indicates the group number of a voice digital 
                module."
            ::= { h3cVoDigitalIfR2TimerCfgEntry 2 }

        h3cVoDIfR2CfgDebounceTime OBJECT-TYPE
            SYNTAX Integer32
            MAX-ACCESS read-write
            STATUS current
            DESCRIPTION
                "This object indicates the minimum duration which is the line 
                signal going to persist."
            ::= { h3cVoDigitalIfR2TimerCfgEntry 3 }
            
            
        h3cVoDIfR2CfgSendringBackTime OBJECT-TYPE
            SYNTAX Integer32
            MAX-ACCESS read-write
            STATUS current
            DESCRIPTION
                "This object indicates the minimum duration which is the ring 
                back going to persist."
            ::= { h3cVoDigitalIfR2TimerCfgEntry 4 }
            
            
        h3cVoDIfR2CfgSendringBusyTime OBJECT-TYPE
            SYNTAX Integer32
            MAX-ACCESS read-write
            STATUS current
            DESCRIPTION
                "This object indicates the minimum duration which is the ring 
                busy going to persist."
            ::= { h3cVoDigitalIfR2TimerCfgEntry 5 }
        
        
        h3cVoDIfR2PulseSignalPersistT OBJECT-TYPE
            SYNTAX Integer32
            MAX-ACCESS read-write
            STATUS current
            DESCRIPTION
                "This object indicates the value of pulse signal persistence 
                timer."
            ::= { h3cVoDigitalIfR2TimerCfgEntry 6 }

        h3cVoDIfR2CfgDlAnswerTime OBJECT-TYPE
            SYNTAX Integer32
            MAX-ACCESS read-write
            STATUS current
            DESCRIPTION
                "This object indicates the value of answer timer."
            ::= { h3cVoDigitalIfR2TimerCfgEntry 7 }

        h3cVoDIfR2CfgDlClearBackTime OBJECT-TYPE
            SYNTAX Integer32
            MAX-ACCESS read-write
            STATUS current
            DESCRIPTION
                "This object indicates the value of clear back timer."
            ::= { h3cVoDigitalIfR2TimerCfgEntry 8 }

        h3cVoDIfR2CfgDlClearForwardT OBJECT-TYPE
            SYNTAX Integer32
            MAX-ACCESS read-write
            STATUS current
            DESCRIPTION
                "This object indicates the value of clear forward timer."
            ::= { h3cVoDigitalIfR2TimerCfgEntry 9 }

        h3cVoDIfR2CfgDlSeizureTime OBJECT-TYPE
            SYNTAX Integer32
            MAX-ACCESS read-write
            STATUS current
            DESCRIPTION
                "This object indicates the value of seizure timer."
            ::= { h3cVoDigitalIfR2TimerCfgEntry 10 }

        h3cVoDIfR2CfgDlReanswerTime OBJECT-TYPE
            SYNTAX Integer32
            MAX-ACCESS read-write
            STATUS current
            DESCRIPTION
                "This object indicates the value of reanswer timer."
            ::= { h3cVoDigitalIfR2TimerCfgEntry 11 }

        h3cVoDIfR2CfgDlRelGuardTime OBJECT-TYPE
            SYNTAX Integer32
            MAX-ACCESS read-write
            STATUS current
            DESCRIPTION
                "This object indicates the value of release guard timer."
            ::= { h3cVoDigitalIfR2TimerCfgEntry 12 }

        h3cVoDIfR2CfgMfcGroupBTime OBJECT-TYPE
            SYNTAX Integer32
            MAX-ACCESS read-write
            STATUS current
            DESCRIPTION
                "This object indicates the value of group B timer."
            ::= { h3cVoDigitalIfR2TimerCfgEntry 13 }

        h3cVoDIfR2CfgDTMFTime OBJECT-TYPE
            SYNTAX Integer32
            MAX-ACCESS read-write
            STATUS current
            DESCRIPTION
                "This object indicates the value of DTMF(Dual Tone 
                Multi-Frequency) timer."
            ::= { h3cVoDigitalIfR2TimerCfgEntry 14 }

        h3cVoDIfR2TimeCfgSubLine OBJECT-TYPE
            SYNTAX OCTET STRING 
            MAX-ACCESS read-only
            STATUS current
            DESCRIPTION
                "This object indicates the port subscriber line name."
            ::= { h3cVoDigitalIfR2TimerCfgEntry 15 }


--==========================================================================
--                      h3cVoDIfR2CapabilityCfgTable
--
--==========================================================================
        h3cVoDIfR2CapabilityCfgTable OBJECT-TYPE
            SYNTAX SEQUENCE OF H3CVoDIfR2CapabilityCfgEntry
            MAX-ACCESS not-accessible
            STATUS current
            DESCRIPTION
                "This table contains information about capability parameters
                for digital r2 voice interface."
            ::= { h3cVoDigitalIfR2Objects 5 }

        
        h3cVoDIfR2CapabilityCfgEntry OBJECT-TYPE
            SYNTAX H3CVoDIfR2CapabilityCfgEntry
            MAX-ACCESS not-accessible
            STATUS current
            DESCRIPTION
                "The entry of h3cVoDIfR2CapabilityCfgTable." 
            INDEX { h3cVoDIfR2CapCfgPort, h3cVoDIfR2CapCfgGroup }
            ::= { h3cVoDIfR2CapabilityCfgTable 1 }

        
        H3CVoDIfR2CapabilityCfgEntry ::=
            SEQUENCE { 
                h3cVoDIfR2CapCfgPort
                    Integer32,
                h3cVoDIfR2CapCfgGroup
                    Integer32,
                h3cVoDIfR2CfgGroupB
                    INTEGER,
                h3cVoDIfR2CfgClearForwardAck
                    INTEGER,
                h3cVoDIfR2CfgDlSeizureAck
                    INTEGER,    
                h3cVoDIfR2CfgDTMF
                    INTEGER,
                h3cVoDIfR2CfgAnswer
                    INTEGER,
                h3cVoDIfR2CfgReanswer
                    INTEGER,    
                h3cVoDIfR2CfgFinalCallnum
                    INTEGER,
                h3cVoDIfR2CfgForceMetering
                    INTEGER,
                h3cVoDIfR2CfgSendRingBack
                    INTEGER,
                h3cVoDIfR2CfgSendRingBusy
                    INTEGER,
                h3cVoDIfR2CapCfgSubLine
                    OCTET STRING
             }

        h3cVoDIfR2CapCfgPort OBJECT-TYPE
            SYNTAX Integer32
            MAX-ACCESS not-accessible
            STATUS current
            DESCRIPTION
                "This object indicates the port of a voice digital module."  
            ::= { h3cVoDIfR2CapabilityCfgEntry 1 }
        
        h3cVoDIfR2CapCfgGroup OBJECT-TYPE
            SYNTAX Integer32
            MAX-ACCESS not-accessible
            STATUS current
            DESCRIPTION
                "This object indicates the group number of a voice digital module."
            ::= { h3cVoDIfR2CapabilityCfgEntry 2 }

        h3cVoDIfR2CfgGroupB OBJECT-TYPE
            SYNTAX INTEGER
                {
                enable(1),
                disable(2)
                }
            MAX-ACCESS read-write
            STATUS current
            DESCRIPTION
                "This object indicates whether the group B process is enabled."
            ::= { h3cVoDIfR2CapabilityCfgEntry 3 }

        h3cVoDIfR2CfgClearForwardAck OBJECT-TYPE
            SYNTAX INTEGER
                {
                enable(1),
                disable(2)
                }
            MAX-ACCESS read-write
            STATUS current
            DESCRIPTION
                "This object indicates whether the CLEAR_FORWARD_ACK signal is 
                enabled."
            ::= { h3cVoDIfR2CapabilityCfgEntry 4 }

        h3cVoDIfR2CfgDlSeizureAck OBJECT-TYPE
            SYNTAX INTEGER
                {
                enable(1),
                disable(2)
                }
            MAX-ACCESS read-write
            STATUS current
            DESCRIPTION
                "This object indicates whether the SEIZURE_ACK signal is enabled."
            ::= { h3cVoDIfR2CapabilityCfgEntry 5 }

        h3cVoDIfR2CfgDTMF OBJECT-TYPE
            SYNTAX INTEGER
                {
                enable(1),
                disable(2)
                }
            MAX-ACCESS read-write
            STATUS current
            DESCRIPTION
                "This object indicates whether the DTMF(Dual Tone Multi-Frequency) 
                is enabled."
            ::= { h3cVoDIfR2CapabilityCfgEntry 6 }

        h3cVoDIfR2CfgAnswer OBJECT-TYPE
            SYNTAX INTEGER
                {
                enable(1),
                disable(2)
                }
            MAX-ACCESS read-write
            STATUS current
            DESCRIPTION
                "This object indicates whether the ANSWER signal is enabled."
            ::= { h3cVoDIfR2CapabilityCfgEntry 7 }

        h3cVoDIfR2CfgReanswer OBJECT-TYPE
            SYNTAX INTEGER
                {
                enable(1),
                disable(2)
                }
            MAX-ACCESS read-write
            STATUS current
            DESCRIPTION
                "This object indicates whether the REANSWER signal is enabled."
            ::= { h3cVoDIfR2CapabilityCfgEntry 8 } 

        h3cVoDIfR2CfgFinalCallnum OBJECT-TYPE
            SYNTAX INTEGER
                {
                enable(1),
                disable(2)
                }
            MAX-ACCESS read-write
            STATUS current
            DESCRIPTION
                "This object indicates whether the FINAL_CALL_NUMBER signal 
                is enabled."
            ::= { h3cVoDIfR2CapabilityCfgEntry 9 }

        h3cVoDIfR2CfgForceMetering OBJECT-TYPE
            SYNTAX INTEGER
                {
                enable(1),
                disable(2)
                }
            MAX-ACCESS read-write
            STATUS current
            DESCRIPTION
                "This object indicates whether the METERING signal is enabled."
            ::= { h3cVoDIfR2CapabilityCfgEntry 10 }

        h3cVoDIfR2CfgSendRingBack OBJECT-TYPE
            SYNTAX INTEGER
                {
                enable(1),
                disable(2)
                }
            MAX-ACCESS read-write
            STATUS current
            DESCRIPTION
                "This object indicates whether to send the ring back tone."
            ::= { h3cVoDIfR2CapabilityCfgEntry 11 }

        h3cVoDIfR2CfgSendRingBusy OBJECT-TYPE
            SYNTAX INTEGER
                {
                enable(1),
                disable(2)
                }
            MAX-ACCESS read-write
            STATUS current
            DESCRIPTION
                "This object indicates whether to send the busy tone."
            ::= { h3cVoDIfR2CapabilityCfgEntry 12 }

        h3cVoDIfR2CapCfgSubLine OBJECT-TYPE
            SYNTAX OCTET STRING 
            MAX-ACCESS read-only
            STATUS current
            DESCRIPTION
                "This object indicates the port subscriber line name."
            ::= { h3cVoDIfR2CapabilityCfgEntry 15 }

    END
