-- ==========================================================================
-- Copyright (C) 2004 by Hangzhou H3C Technologies Co., Ltd. All rights reserved.
--
-- Description: The purpose of this MIB file is to provide the definition of
--              the voice interface general configuration.
-- Reference:
-- Version: V1.0
-- History:
-- V1.0 2007-12-10 Initial version, created by Qu Pingping
-- ==========================================================================
A3COM-HUAWEI-VOICE-IF-MIB DEFINITIONS ::= BEGIN

IMPORTS
        OBJECT-TYPE, MODULE-IDENTITY, Integer32
    FROM SNMPv2-SMI
        DisplayString
    FROM SNMPv2-TC
        ifIndex
    FROM IF-MIB
        h3cVoice
    FROM A3COM-HUAWEI-OID-MIB;

h3cVoiceInterface MODULE-IDENTITY
    LAST-UPDATED "200712101700Z"
    ORGANIZATION
        "Hangzhou H3C Technologies Co., Ltd."
    CONTACT-INFO
        "Platform Team H3C Technologies Co., Ltd.
         Hai-Dian District Beijing P.R. China
         Http://www.h3c.com
         Zip:100085"
    DESCRIPTION
        "This MIB file is to provide the definition of the voice
        interface general configuration."
    REVISION "200712101700Z"
    DESCRIPTION
        "The initial version of this MIB file."
    ::= { h3cVoice 13 }

h3cVoiceIfObjects OBJECT IDENTIFIER ::= { h3cVoiceInterface 1 }

--===========================================================================
--                            h3cVoiceIfConfigTable
--
--===========================================================================
h3cVoiceIfConfigTable OBJECT-TYPE
    SYNTAX      SEQUENCE OF H3CVoiceIfConfigEntry
    MAX-ACCESS  not-accessible
    STATUS      current
    DESCRIPTION
        "The table contains configurable parameters for both analog
        voice interface and digital voice interface."
    ::= { h3cVoiceIfObjects 1 }

h3cVoiceIfConfigEntry OBJECT-TYPE
    SYNTAX      H3CVoiceIfConfigEntry
    MAX-ACCESS  not-accessible
    STATUS      current
    DESCRIPTION
        "The entry of voice interface table."
    INDEX
        {
            ifIndex
        }
    ::= { h3cVoiceIfConfigTable 1 }

H3CVoiceIfConfigEntry ::= SEQUENCE
    {
        h3cVoiceIfCfgCngOn                INTEGER,
        h3cVoiceIfCfgNonLinearSwitch      INTEGER,
        h3cVoiceIfCfgInputGain            Integer32,
        h3cVoiceIfCfgOutputGain           Integer32,
        h3cVoiceIfCfgEchoCancelSwitch     INTEGER,
        h3cVoiceIfCfgEchoCancelDelay      Integer32,
        h3cVoiceIfCfgTimerDialInterval    Integer32,
        h3cVoiceIfCfgTimerFirstDial       Integer32,
        h3cVoiceIfCfgPrivateline          DisplayString,
        h3cVoiceIfCfgRegTone              OCTET STRING
    }

h3cVoiceIfCfgCngOn OBJECT-TYPE
    SYNTAX      INTEGER
        {
            enable(1),
            disable(2)
        }
    MAX-ACCESS  read-write
    STATUS      current
    DESCRIPTION
        "This object indicates whether the silence gaps should be
        filled with background noise. It is applicable to FXO, FXS,
        E&M subscriber lines and E1/T1 voice subscriber line."
    DEFVAL { enable }
    ::= { h3cVoiceIfConfigEntry 1 }

h3cVoiceIfCfgNonLinearSwitch OBJECT-TYPE
    SYNTAX      INTEGER
        {
            enable(1),
            disable(2)
        }
    MAX-ACCESS  read-write
    STATUS      current
    DESCRIPTION
        "This object expresses the nonlinear processing is enable
        or disable for the voice interface. It is applicable to FXO,
        FXS, E&M subscriber lines and E1/T1 voice subscriber line.
        Currently, only digital voice subscriber lines can be set
        disabled."
    DEFVAL { enable }
    ::= { h3cVoiceIfConfigEntry 2 }

h3cVoiceIfCfgInputGain OBJECT-TYPE
    SYNTAX      Integer32(-140..139)
    MAX-ACCESS  read-write
    STATUS      current
    DESCRIPTION
        "This object indicates the amount of gain added to the receiver
        side of the voice interface. Unit is 0.1 db. It is applicable to
        FXO, FXS, E&M subscriber lines and E1/T1 voice subscriber line."
    DEFVAL { 0 }
    ::= { h3cVoiceIfConfigEntry 3 }

h3cVoiceIfCfgOutputGain OBJECT-TYPE
    SYNTAX      Integer32(-140..139)
    MAX-ACCESS  read-write
    STATUS      current
    DESCRIPTION
        "This object indicates the amount of gain added to the send side
        of the voice interface. Unit is 0.1 db. It is applicable to FXO,
        FXS, E&M subscriber lines and E1/T1 voice subscriber line."
    DEFVAL { 0 }
    ::= { h3cVoiceIfConfigEntry 4 }

h3cVoiceIfCfgEchoCancelSwitch OBJECT-TYPE
    SYNTAX      INTEGER
        {
            enable(1),
            disable(2)
        }
    MAX-ACCESS  read-write
    STATUS      current
    DESCRIPTION
        "This object indicates whether the echo cancellation is enabled.
        It is applicable to FXO, FXS, E&M subscriber lines and E1/T1 voice
        subscriber line."
    DEFVAL { enable }
    ::= { h3cVoiceIfConfigEntry 5 }

h3cVoiceIfCfgEchoCancelDelay OBJECT-TYPE
    SYNTAX      Integer32(0..64)
    MAX-ACCESS  read-write
    STATUS      current
    DESCRIPTION
        "This object indicates the delay of the echo cancellation for
        the voice interface. This value couldn't be modified unless
        h3cVoiceIfCfgEchoCancelSwitch is enable. Unit is milliseconds.
        It is applicable to FXO, FXS, E&M subscriber lines and E1/T1
        voice subscriber line. The default value of this object is 32."
    ::= { h3cVoiceIfConfigEntry 6 }

h3cVoiceIfCfgTimerDialInterval OBJECT-TYPE
    SYNTAX      Integer32(1..300)
    MAX-ACCESS  read-write
    STATUS      current
    DESCRIPTION
        "The interval, in seconds, between two dialing numbers.
        The default value of this object is 10 seconds. It is
        applicable to FXO, FXS, E&M subscriber lines and E1/T1 with
        loop-start or ground-start protocol voice subscriber line."
    ::= { h3cVoiceIfConfigEntry 7 }

h3cVoiceIfCfgTimerFirstDial OBJECT-TYPE
    SYNTAX      Integer32(1..300)
    MAX-ACCESS  read-write
    STATUS      current
    DESCRIPTION
        "The period of time, in seconds, before dialing the first
        number. The default value of this object is 10 seconds. It
        is applicable to FXO, FXS subscriber lines and E1/T1 with
        loop-start or ground-start protocol voice subscriber line."
    ::= { h3cVoiceIfConfigEntry 8 }

h3cVoiceIfCfgPrivateline OBJECT-TYPE
    SYNTAX      DisplayString(SIZE(0..31))
    MAX-ACCESS  read-write
    STATUS      current
    DESCRIPTION
        "This object indicates the E.164 phone number for plar mode.
        It is applicable to FXO, FXS, E&M subscriber lines and E1/T1
        voice subscriber line."
    ::= { h3cVoiceIfConfigEntry 9 }

h3cVoiceIfCfgRegTone OBJECT-TYPE
    SYNTAX      OCTET STRING(SIZE(0|2..3))
    MAX-ACCESS  read-write
    STATUS      current
    DESCRIPTION
        "This object uses 2 or 3 letter country code specify voice
        parameters of different countrys. This value will take effect
        on all voice interfaces of all cards on the device."
    ::= { h3cVoiceIfConfigEntry 10 }

END
