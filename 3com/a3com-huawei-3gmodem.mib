-- =============================================================
-- Copyright (c) 2004-2011 by H3C Technologies. All rights reserved.
--
-- Description:
-- Reference:
-- Version: V1.2
-- History:
--   V1.0 2009-04-30 Initial Version by jinyi
--   V1.1 2009-12-30 Added h3cAccessMediaChanged by jinyi
--   V1.2 2011-07-22 Added h3cWirelessCardInterfaceIndex,
--                   h3cWirelessCardModemStatus, h3cWirelessCardCurServiceStatus,
--                   h3cWirelessCardCurRoamingStatus and in h3cWirelessCardTable.
--                   Added h3c3GCdma1xRttTable, h3c3GCdmaEvDoTable, h3c3GGsmInfoTable
--                   h3c3GCurrentService, h3c3GCurrentRssiBind, h3c3GImsiBind,
--                   h3c3GRssiStrongSignalTrap, h3c3GRssiMediumSignalTrap and
--                   h3c3GRssiWeakSignalTrap.
--                   Changed MAX-ACCESS of h3cWirelessCardIndex by songhao
-- =============================================================
A3COM-HUAWEI-3GMODEM-MIB DEFINITIONS ::= BEGIN
    IMPORTS
        MODULE-IDENTITY, OBJECT-TYPE, NOTIFICATION-TYPE,
        Integer32, Unsigned32
            FROM SNMPv2-SMI
        TEXTUAL-CONVENTION
            FROM SNMPv2-TC
        SnmpAdminString
            FROM SNMP-FRAMEWORK-MIB
        InterfaceIndex
            FROM IF-MIB
        h3cCommon
            FROM A3COM-HUAWEI-OID-MIB;

h3c3GModem MODULE-IDENTITY
    LAST-UPDATED    "200904301200Z"
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The information about the wireless card and the UIM
         (User Identification Module)."
    REVISION        "200904301200Z"
    DESCRIPTION
        "Initial version of this MIB module."
    ::= { h3cCommon 98 }

H3cUIMStatusType ::= TEXTUAL-CONVENTION
    STATUS      current
    DESCRIPTION
        "The status of the UIM."
    SYNTAX      INTEGER
        {
            absent(1),      -- the UIM is absent
            initial(2),     -- the UIM is initial
            fault(3),       -- something wrong in UIM
            unprotected(4), -- the UIM is not protected with PIN
                            -- (Personal Identification Number) and can be
                            -- used normally
            protected(5),   -- the UIM is protected with PIN and can be
                            -- used normally
            pinLocked(6),   -- the UIM is locked, and need be unlocked with PIN
            pukLocked(7),   -- the UIM is locked, and need be unlocked with PUK
                            -- (PIN Unblocking Key)
            selfDestruct(8) -- the UIM is destruct by itself
        }

h3c3GModemObjects     OBJECT IDENTIFIER ::= { h3c3GModem 1 }

h3cWirelessCard OBJECT IDENTIFIER ::= { h3c3GModemObjects 1 }
h3cUIM OBJECT IDENTIFIER ::= { h3c3GModemObjects 2 }
h3c3GCdma OBJECT IDENTIFIER ::= { h3c3GModemObjects 3 }
h3c3GGsm OBJECT IDENTIFIER ::= { h3c3GModemObjects 4 }


-- The wireless card table
h3cWirelessCardTable OBJECT-TYPE
    SYNTAX      SEQUENCE OF H3cWirelessCardEntry
    MAX-ACCESS  not-accessible
    STATUS      current
    DESCRIPTION
        "This table contains one row per wireless card."
    ::= { h3cWirelessCard 1 }

h3cWirelessCardEntry OBJECT-TYPE
    SYNTAX      H3cWirelessCardEntry
    MAX-ACCESS  not-accessible
    STATUS      current
    DESCRIPTION
        "Information about a particular wireless card."
    INDEX { h3cWirelessCardIndex }
    ::= { h3cWirelessCardTable 1 }

H3cWirelessCardEntry ::= SEQUENCE
    {
        h3cWirelessCardIndex                Integer32,
        h3cWirelessCardModelName            SnmpAdminString,
        h3cWirelessCardMfgName              SnmpAdminString,
        h3cWirelessCardDescription          SnmpAdminString,
        h3cWirelessCardSerialNumber         SnmpAdminString,
        h3cWirelessCardCMIIID               SnmpAdminString,
        h3cWirelessCardHardwareVersion      SnmpAdminString,
        h3cWirelessCardFirmwareVersion      SnmpAdminString,
        h3cWirelessCardPRLVersion           SnmpAdminString,
        h3cWirelessCardInterfaceIndex       InterfaceIndex,
        h3cWirelessCardModemStatus          INTEGER,
        h3cWirelessCardCurServiceStatus     INTEGER,
        h3cWirelessCardCurRoamingStatus     INTEGER
    }

h3cWirelessCardIndex OBJECT-TYPE
    SYNTAX      Integer32 (1..2147483647)
    MAX-ACCESS  read-only
    STATUS      current
    DESCRIPTION
        "The index for this entry."
    ::= { h3cWirelessCardEntry 1 }

h3cWirelessCardModelName OBJECT-TYPE
    SYNTAX      SnmpAdminString (SIZE (0..255))
    MAX-ACCESS  read-only
    STATUS      current
    DESCRIPTION
        "The model name of this card."
    ::= { h3cWirelessCardEntry 2 }

h3cWirelessCardMfgName OBJECT-TYPE
    SYNTAX      SnmpAdminString (SIZE (0..255))
    MAX-ACCESS  read-only
    STATUS      current
    DESCRIPTION
        "The name of the manufacturer of this card."
    ::= { h3cWirelessCardEntry 3 }

h3cWirelessCardDescription OBJECT-TYPE
    SYNTAX      SnmpAdminString (SIZE (0..255))
    MAX-ACCESS  read-only
    STATUS      current
    DESCRIPTION
        "The textual description of this card."
    ::= { h3cWirelessCardEntry 4 }

h3cWirelessCardSerialNumber OBJECT-TYPE
    SYNTAX      SnmpAdminString (SIZE (0..32))
    MAX-ACCESS  read-only
    STATUS      current
    DESCRIPTION
        "The vendor-specific serial number string for this card."
    ::= { h3cWirelessCardEntry 5 }

h3cWirelessCardCMIIID OBJECT-TYPE
    SYNTAX      SnmpAdminString (SIZE (0..32))
    MAX-ACCESS  read-only
    STATUS      current
    DESCRIPTION
        "The card ID of CMII (Ministry of Information Industry of China)."
    ::= { h3cWirelessCardEntry 6 }

h3cWirelessCardHardwareVersion OBJECT-TYPE
    SYNTAX      SnmpAdminString (SIZE (0..255))
    MAX-ACCESS  read-only
    STATUS      current
    DESCRIPTION
        "The vendor-specific hardware version string for this card."
    ::= { h3cWirelessCardEntry 7 }

h3cWirelessCardFirmwareVersion OBJECT-TYPE
    SYNTAX      SnmpAdminString (SIZE (0..255))
    MAX-ACCESS  read-only
    STATUS      current
    DESCRIPTION
        "The vendor-specific firmware version string for this card."
    ::= { h3cWirelessCardEntry 8 }

h3cWirelessCardPRLVersion OBJECT-TYPE
    SYNTAX      SnmpAdminString (SIZE (0..255))
    MAX-ACCESS  read-only
    STATUS      current
    DESCRIPTION
        "The preferred roaming list version for this card."
    ::= { h3cWirelessCardEntry 9 }

h3cWirelessCardInterfaceIndex OBJECT-TYPE
    SYNTAX      InterfaceIndex
    MAX-ACCESS  read-only
    STATUS      current
    DESCRIPTION
        "The interface index in IF-MIB of this card."
    ::= { h3cWirelessCardEntry 10 }

h3cWirelessCardModemStatus OBJECT-TYPE
    SYNTAX      INTEGER {
                        unknown(1),
                        onLine(2),
                        offLine(3)
                }
    MAX-ACCESS  read-only
    STATUS      current
    DESCRIPTION
        "The status of modem."
    ::= { h3cWirelessCardEntry 11 }

h3cWirelessCardCurServiceStatus OBJECT-TYPE
    SYNTAX      INTEGER {
                        unknown(1),
                        available(2),
                        emergency(3),
                        lowPower(4),
                        noService(5)
                }
    MAX-ACCESS  read-only
    STATUS      current
    DESCRIPTION
        "The status of service."

    ::= { h3cWirelessCardEntry 12 }

h3cWirelessCardCurRoamingStatus OBJECT-TYPE
    SYNTAX      INTEGER {
                        unknown(1),
                        roaming(2),
                        home(3)
                }
    MAX-ACCESS  read-only
    STATUS      current
    DESCRIPTION
        "The status of roaming."
    ::= { h3cWirelessCardEntry 13 }


-- The UIM information table
h3cUIMInfoTable OBJECT-TYPE
    SYNTAX      SEQUENCE OF H3cUIMInfoEntry
    MAX-ACCESS  not-accessible
    STATUS      current
    DESCRIPTION
        "This table contains one row per UIM."
    ::= { h3cUIM 1 }

h3cUIMInfoEntry OBJECT-TYPE
    SYNTAX      H3cUIMInfoEntry
    MAX-ACCESS  not-accessible
    STATUS      current
    DESCRIPTION
        "The information about the UIM."
    INDEX { h3cWirelessCardIndex, h3cUIMIndex }
    ::= { h3cUIMInfoTable 1 }

H3cUIMInfoEntry ::= SEQUENCE
    {
        h3cUIMIndex          Integer32,
        h3cUIMStatus         H3cUIMStatusType,
        h3cUIMImsi           SnmpAdminString,
        h3cUIMPin            SnmpAdminString,
        h3cUIMVoltage        Unsigned32,
        h3cUIMProvider       SnmpAdminString,
        h3cUIMSignal         Integer32,
        h3cUIMTryPinPukTimes Unsigned32,
        h3cUIMOldPin         SnmpAdminString
    }

h3cUIMIndex OBJECT-TYPE
    SYNTAX      Integer32 (0..2147483647)
    MAX-ACCESS  not-accessible
    STATUS      current
    DESCRIPTION
        "The index for this entry."
    ::= { h3cUIMInfoEntry 1 }

h3cUIMStatus OBJECT-TYPE
    SYNTAX      H3cUIMStatusType
    MAX-ACCESS  read-only
    STATUS      current
    DESCRIPTION
        "The status about this UIM."
    ::= { h3cUIMInfoEntry 2 }

h3cUIMImsi OBJECT-TYPE
    SYNTAX      SnmpAdminString (SIZE (0..32))
    MAX-ACCESS  read-only
    STATUS      current
    DESCRIPTION
        "The IMSI (International Mobile Subscriber Identification Number) about
        this UIM.  If this information is unknown to the agent, then this object
        will be returned a zero-length string."
    ::= { h3cUIMInfoEntry 3 }

h3cUIMPin OBJECT-TYPE
    SYNTAX      SnmpAdminString (SIZE (0..9))
    MAX-ACCESS  read-only
    STATUS      current
    DESCRIPTION
        "The PIN about this UIM.  If this information is unknown to the agent,
        then this object will be returned a zero-length string."
    ::= { h3cUIMInfoEntry 4 }

h3cUIMVoltage OBJECT-TYPE
    SYNTAX      Unsigned32(0..4294967295)
    UNITS       "milli-volt"
    MAX-ACCESS  read-only
    STATUS      current
    DESCRIPTION
        "The voltage about this UIM.  If this information is unknown to the
        agent, then this object will be returned 4294967295."
    ::= { h3cUIMInfoEntry 5 }

h3cUIMProvider OBJECT-TYPE
    SYNTAX      SnmpAdminString (SIZE (0..32))
    MAX-ACCESS  read-only
    STATUS      current
    DESCRIPTION
        "The provider of mobile network.  If this information is unknown to the
        agent, then this object will be returned a zero-length string."
    ::= { h3cUIMInfoEntry 6 }

h3cUIMSignal OBJECT-TYPE
    SYNTAX      Integer32(0..31 | 99)
    MAX-ACCESS  read-only
    STATUS      current
    DESCRIPTION
        "The intensity of the signal about this UIM.
        A value of '99' means no signal."
    ::= { h3cUIMInfoEntry 7 }

h3cUIMTryPinPukTimes OBJECT-TYPE
    SYNTAX      Unsigned32(0..4294967295)
    MAX-ACCESS  read-only
    STATUS      current
    DESCRIPTION
        "The number of remaining times for unlocking PIN or PUK.
        The value is associated the same instance of h3cUIMStatus.  If this
        information is unknown to the agent, then this object will be
        returned 4294967295."
    ::= { h3cUIMInfoEntry 8 }

h3cUIMOldPin OBJECT-TYPE
    SYNTAX      SnmpAdminString (SIZE (0..9))
    MAX-ACCESS  accessible-for-notify
    STATUS      current
    DESCRIPTION
            "The old PIN for this UIM."
    ::= { h3cUIMInfoEntry 9 }


-- The CDMA information table of 1xRTT
h3c3GCdma1xRttTable OBJECT-TYPE
    SYNTAX      SEQUENCE OF H3c3GCdma1xRttEntry
    MAX-ACCESS  not-accessible
    STATUS      current
    DESCRIPTION
        "CDMA 1xRTT table."
    ::= { h3c3GCdma 1 }

h3c3GCdma1xRttEntry OBJECT-TYPE
    SYNTAX      H3c3GCdma1xRttEntry
    MAX-ACCESS  not-accessible
    STATUS      current
    DESCRIPTION
        "An entry of h3c3GCdma1xRttTable."
    INDEX { h3cWirelessCardIndex }
    ::= { h3c3GCdma1xRttTable 1 }

H3c3GCdma1xRttEntry ::= SEQUENCE
    {
        h3c3GCdma1xRttCurrentRssi           Integer32,
        h3c3GCdma1xRttRssiMediumThreshold   Integer32,
        h3c3GCdma1xRttRssiWeakThreshold     Integer32
    }

h3c3GCdma1xRttCurrentRssi OBJECT-TYPE
    SYNTAX      Integer32 (-150..0)
    UNITS       "dBm"
    MAX-ACCESS  read-only
    STATUS      current
    DESCRIPTION
        "The Received Signal Strength Indicator(RSSI) of CDMA 1xRTT."
    ::= { h3c3GCdma1xRttEntry 1 }

h3c3GCdma1xRttRssiMediumThreshold OBJECT-TYPE
    SYNTAX      Integer32 (-150..0)
    UNITS       "dBm"
    MAX-ACCESS  read-write
    STATUS      current
    DESCRIPTION
        "The medium signal threshold of CMDA 1xRTT RSSI. The absolute 
        value of h3c3GCdma1xRttRssiMediumThreshold should be less than 
        or equal to the absolute value of h3c3GCdma1xRttRssiWeakThreshold.
        (|h3c3GCdma1xRttRssiMediumThreshold| <= |h3c3GCdma1xRttRssiWeakThreshold|)."
    DEFVAL      { 0 }
    ::= { h3c3GCdma1xRttEntry 2 }

h3c3GCdma1xRttRssiWeakThreshold OBJECT-TYPE
    SYNTAX      Integer32 (-150..0)
    UNITS       "dBm"
    MAX-ACCESS  read-write
    STATUS      current
    DESCRIPTION
        "The weak signal threshold of CMDA 1xRTT RSSI. The absolute 
        value of h3c3GCdma1xRttRssiMediumThreshold should be less than 
        or equal to the absolute value of h3c3GCdma1xRttRssiWeakThreshold.
        (|h3c3GCdma1xRttRssiMediumThreshold| <= |h3c3GCdma1xRttRssiWeakThreshold|)."
    DEFVAL      { -150 }
    ::= { h3c3GCdma1xRttEntry 3 }


-- The CDMA information table of EvDo
h3c3GCdmaEvDoTable OBJECT-TYPE
    SYNTAX      SEQUENCE OF H3c3GCdmaEvDoEntry
    MAX-ACCESS  not-accessible
    STATUS      current
    DESCRIPTION
        "CDMA EvDo table."
    ::= { h3c3GCdma 2 }

h3c3GCdmaEvDoEntry OBJECT-TYPE
    SYNTAX      H3c3GCdmaEvDoEntry
    MAX-ACCESS  not-accessible
    STATUS      current
    DESCRIPTION
        "An entry of h3c3GCdmaEvDoTable."
    INDEX { h3cWirelessCardIndex }
    ::= { h3c3GCdmaEvDoTable 1 }

H3c3GCdmaEvDoEntry ::= SEQUENCE
    {
        h3c3GCdmaEvDoCurrentRssi           Integer32,
        h3c3GCdmaEvDoRssiMediumThreshold   Integer32,
        h3c3GCdmaEvDoRssiWeakThreshold     Integer32
    }

h3c3GCdmaEvDoCurrentRssi OBJECT-TYPE
    SYNTAX      Integer32 (-150..0)
    UNITS       "dBm"
    MAX-ACCESS  read-only
    STATUS      current
    DESCRIPTION
        "The Received Signal Strength Indicator(RSSI) of CDMA EvDo."
    ::= { h3c3GCdmaEvDoEntry 1 }

h3c3GCdmaEvDoRssiMediumThreshold OBJECT-TYPE
    SYNTAX      Integer32 (-150..0)
    UNITS       "dBm"
    MAX-ACCESS  read-write
    STATUS      current
    DESCRIPTION
        "The medium signal threshold of CMDA EvDo RSSI. The absolute 
        value of h3c3GCdmaEvDoRssiMediumThreshold should be less than 
        or equal to the absolute value of h3c3GCdmaEvDoRssiWeakThreshold.
        (|h3c3GCdmaEvDoRssiMediumThreshold| <= |h3c3GCdmaEvDoRssiWeakThreshold|)."
    DEFVAL      { 0 }
    ::= { h3c3GCdmaEvDoEntry 2 }

h3c3GCdmaEvDoRssiWeakThreshold OBJECT-TYPE
    SYNTAX      Integer32 (-150..0)
    UNITS       "dBm"
    MAX-ACCESS  read-write
    STATUS      current
    DESCRIPTION
        "The weak signal threshold of CMDA EvDo RSSI. The absolute 
        value of h3c3GCdmaEvDoRssiMediumThreshold should be less than 
        or equal to the absolute value of h3c3GCdmaEvDoRssiWeakThreshold.
        (|h3c3GCdmaEvDoRssiMediumThreshold| <= |h3c3GCdmaEvDoRssiWeakThreshold|)."
    DEFVAL      { -150 }
    ::= { h3c3GCdmaEvDoEntry 3 }


-- The GSM information table
h3c3GGsmInfoTable OBJECT-TYPE
    SYNTAX      SEQUENCE OF H3c3GGsmInfoEntry
    MAX-ACCESS  not-accessible
    STATUS      current
    DESCRIPTION
        "GSM information table."
    ::= { h3c3GGsm 1 }

h3c3GGsmInfoEntry OBJECT-TYPE
    SYNTAX      H3c3GGsmInfoEntry
    MAX-ACCESS  not-accessible
    STATUS      current
    DESCRIPTION
        "An entry of h3c3GGsmInfoTable."
    INDEX { h3cWirelessCardIndex }
    ::= { h3c3GGsmInfoTable 1 }

H3c3GGsmInfoEntry ::= SEQUENCE
    {
        h3c3GGsmCurrentRssi             Integer32,
        h3c3GGsmRssiMediumThreshold     Integer32,
        h3c3GGsmRssiWeakThreshold       Integer32,
        h3c3GGsmImsi                    SnmpAdminString,
        h3c3GGsmImei                    SnmpAdminString,
        h3c3GGsmApn                     SnmpAdminString,
        h3c3GGsmPacketSessionStatus     INTEGER,
        h3c3GGsmNetworkSelectionMode    INTEGER,
        h3c3GGsmMobileNetworkName       SnmpAdminString,
        h3c3GGsmLac                     SnmpAdminString,
        h3c3GGsmCellId                  SnmpAdminString,
        h3c3GGsmSimStatus               INTEGER
    }

h3c3GGsmCurrentRssi OBJECT-TYPE
    SYNTAX      Integer32 (-150..0)
    UNITS       "dBm"
    MAX-ACCESS  read-only
    STATUS      current
    DESCRIPTION
        "The Received Signal Strength Indicator(RSSI) of GSM."
    ::= { h3c3GGsmInfoEntry 1 }

h3c3GGsmRssiMediumThreshold OBJECT-TYPE
    SYNTAX      Integer32 (-150..0)
    UNITS       "dBm"
    MAX-ACCESS  read-write
    STATUS      current
    DESCRIPTION
        "The medium signal threshold of GSM RSSI. The absolute 
        value of h3c3GGsmRssiMediumThreshold should be less than 
        or equal to the absolute value of h3c3GGsmRssiWeakThreshold.
        (|h3c3GGsmRssiMediumThreshold| <= |h3c3GGsmRssiWeakThreshold|)."
    DEFVAL      { 0 }
    ::= { h3c3GGsmInfoEntry 2 }

h3c3GGsmRssiWeakThreshold OBJECT-TYPE
    SYNTAX      Integer32 (-150..0)
    UNITS       "dBm"
    MAX-ACCESS  read-write
    STATUS      current
    DESCRIPTION
        "The weak signal threshold of GSM RSSI. The absolute 
        value of h3c3GGsmRssiMediumThreshold should be less than 
        or equal to the absolute value of h3c3GGsmRssiWeakThreshold.
        (|h3c3GGsmRssiMediumThreshold| <= |h3c3GGsmRssiWeakThreshold|)."
    DEFVAL      { -150 }
    ::= { h3c3GGsmInfoEntry 3 }

h3c3GGsmImsi OBJECT-TYPE
    SYNTAX      SnmpAdminString (SIZE (0..255))
    MAX-ACCESS  read-only
    STATUS      current
    DESCRIPTION
        "The International Mobile Subscriber Identity(IMSI) of GSM."
    ::= { h3c3GGsmInfoEntry 4 }

h3c3GGsmImei OBJECT-TYPE
    SYNTAX      SnmpAdminString (SIZE (0..255))
    MAX-ACCESS  read-only
    STATUS      current
    DESCRIPTION
        "The International Mobile Equipment Identity(IMEI) of GSM."
    ::= { h3c3GGsmInfoEntry 5 }

h3c3GGsmApn OBJECT-TYPE
    SYNTAX      SnmpAdminString (SIZE (0..100))
    MAX-ACCESS  read-write
    STATUS      current
    DESCRIPTION
        "The Access Point Name(APN) of GSM."
    ::= { h3c3GGsmInfoEntry 6 }

h3c3GGsmPacketSessionStatus OBJECT-TYPE
    SYNTAX      INTEGER {
                        unknown(1),
                        active(2),
                        inactive(3)
                }
    MAX-ACCESS  read-only
    STATUS      current
    DESCRIPTION
        "The packet session status of GSM."
    ::= { h3c3GGsmInfoEntry 7 }

h3c3GGsmNetworkSelectionMode    OBJECT-TYPE
    SYNTAX      INTEGER {
                        unknown(1),
                        automatic(2),
                        manual(3)
                }
    MAX-ACCESS  read-only
    STATUS      current
    DESCRIPTION
        "The network selection mode of GSM."
    ::= { h3c3GGsmInfoEntry 8 }

h3c3GGsmMobileNetworkName OBJECT-TYPE
    SYNTAX      SnmpAdminString (SIZE (0..255))
    MAX-ACCESS  read-only
    STATUS      current
    DESCRIPTION
        "The mobile network name of GSM."
    ::= { h3c3GGsmInfoEntry 9 }

h3c3GGsmLac OBJECT-TYPE
    SYNTAX      SnmpAdminString (SIZE (0..255))
    MAX-ACCESS  read-only
    STATUS      current
    DESCRIPTION
        "The Location Area Code(LAC) of GSM."
    ::= { h3c3GGsmInfoEntry 10 }

h3c3GGsmCellId OBJECT-TYPE
    SYNTAX      SnmpAdminString (SIZE (0..255))
    MAX-ACCESS  read-only
    STATUS      current
    DESCRIPTION
        "The ID of cell."
    ::= { h3c3GGsmInfoEntry 11 }

h3c3GGsmSimStatus OBJECT-TYPE
    SYNTAX      INTEGER {
                        unknown(1),
                        ok(2),
                        notInsert(3),
                        networkReject(4),
                        blocked(5)
                }
    MAX-ACCESS  read-only
    STATUS      current
    DESCRIPTION
        "The status of SIM."
    ::= { h3c3GGsmInfoEntry 12 }


-- MIB trap definitions
h3c3GModemTrap       OBJECT IDENTIFIER ::= { h3c3GModem 2 }
h3c3GModemTraps       OBJECT IDENTIFIER ::= { h3c3GModem 3 }
h3c3GModemTrapPrefix  OBJECT IDENTIFIER ::= { h3c3GModemTraps 0 }

h3cDevSerialNumber OBJECT-TYPE
    SYNTAX      SnmpAdminString (SIZE (0..32))
    MAX-ACCESS  accessible-for-notify
    STATUS      current
    DESCRIPTION
            "The serial number of the current device."
    ::= { h3c3GModemTrap 1 }

h3cDeviceOUI OBJECT-TYPE
    SYNTAX      SnmpAdminString (SIZE (0..64))
    MAX-ACCESS  accessible-for-notify
    STATUS      current
    DESCRIPTION
            "The OUI (Organizational Unique Identifier) of the current device."
    ::= { h3c3GModemTrap 2 }

h3cAccessMedia OBJECT-TYPE
    SYNTAX      INTEGER
        {
            unknown(1),
            air(2),
            cable(3)
        }
    MAX-ACCESS  accessible-for-notify
    STATUS      current
    DESCRIPTION
            "The current access media."
    ::= { h3c3GModemTrap 3 }

h3c3GCurrentService OBJECT-TYPE
    SYNTAX      INTEGER
        {
            unknown(1),
            oneXRtt(2),
            evDo(3),
            gsm(4)
        }
    MAX-ACCESS  accessible-for-notify
    STATUS      current
    DESCRIPTION
            "The current service type which binded in the notifications."
    ::= { h3c3GModemTrap 4 }

h3c3GCurrentRssiBind OBJECT-TYPE
    SYNTAX      Integer32 (-150..0)
    UNITS       "dBm"
    MAX-ACCESS  accessible-for-notify
    STATUS      current
    DESCRIPTION
            "The current RSSI which binded in the notifications."
    ::= { h3c3GModemTrap 5 }

h3c3GImsiBind OBJECT-TYPE
    SYNTAX      SnmpAdminString (SIZE (0..32))
    MAX-ACCESS  accessible-for-notify
    STATUS      current
    DESCRIPTION
            "The IMSI which binded in the notifications."
    ::= { h3c3GModemTrap 6 }

h3cWirelessCardInserted NOTIFICATION-TYPE
    OBJECTS
        {
            h3cDeviceOUI,
            h3cDevSerialNumber,
            h3cWirelessCardSerialNumber,
            h3cUIMImsi
        }
    STATUS      current
    DESCRIPTION
        "A h3cWirelessCardInserted notification is generated when a wireless
        card is inserted."
   ::= { h3c3GModemTrapPrefix 1 }

h3cWirelessCardPulledOut NOTIFICATION-TYPE
    OBJECTS
        {
            h3cDeviceOUI,
            h3cDevSerialNumber,
            h3cWirelessCardSerialNumber,
            h3cUIMImsi
        }
    STATUS      current
    DESCRIPTION
        "A h3cWirelessCardPulledOut notification is generated when a wireless
        card is pulled out."
   ::= { h3c3GModemTrapPrefix 2 }

h3cUIMPinInvalid NOTIFICATION-TYPE
    OBJECTS
        {
            h3cDeviceOUI,
            h3cDevSerialNumber,
            h3cWirelessCardSerialNumber,
            h3cUIMImsi
        }
    STATUS      current
    DESCRIPTION
        "A h3cUIMPinInvalid notification is generated when UIM PIN is invalid."
   ::= { h3c3GModemTrapPrefix 3 }

h3cUIMPinChanged NOTIFICATION-TYPE
    OBJECTS
        {
            h3cDeviceOUI,
            h3cDevSerialNumber,
            h3cWirelessCardSerialNumber,
            h3cUIMImsi,
            h3cUIMOldPin,
            h3cUIMPin
        }
    STATUS      current
    DESCRIPTION
        "A h3cUIMPinInvalid notification is generated when UIM PIN is changed."
   ::= { h3c3GModemTrapPrefix 4 }

h3cAccessMediaChanged NOTIFICATION-TYPE
    OBJECTS
        {
            h3cDeviceOUI,
            h3cDevSerialNumber,
            h3cWirelessCardSerialNumber,
            h3cUIMImsi,
            h3cAccessMedia
        }
    STATUS      current
    DESCRIPTION
        "A h3cAccessMediaChanged notification is generated when access media
         is changed."
   ::= { h3c3GModemTrapPrefix 5 }

h3c3GRssiStrongSignalTrap NOTIFICATION-TYPE
    OBJECTS
        {
            h3cWirelessCardIndex,
            h3cDeviceOUI,
            h3cDevSerialNumber,
            h3cWirelessCardSerialNumber,
            h3c3GCurrentService,
            h3c3GCurrentRssiBind,
            h3c3GImsiBind
        }
    STATUS      current
    DESCRIPTION
        "A h3c3GRssiStrongSignalTrap notification is generated when current RSSI
        exceeds the medium signal threshold."
   ::= { h3c3GModemTrapPrefix 6 }

h3c3GRssiMediumSignalTrap NOTIFICATION-TYPE
    OBJECTS
        {
            h3cWirelessCardIndex,
            h3cDeviceOUI,
            h3cDevSerialNumber,
            h3cWirelessCardSerialNumber,
            h3c3GCurrentService,
            h3c3GCurrentRssiBind,
            h3c3GImsiBind
        }
    STATUS      current
    DESCRIPTION
        "A h3c3GRssiMediumSignalTrap notification is generated when the current RSSI
        falls or rises to a value between the medium and weak signal thresholds."
   ::= { h3c3GModemTrapPrefix 7 }

h3c3GRssiWeakSignalTrap NOTIFICATION-TYPE
    OBJECTS
        {
            h3cWirelessCardIndex,
            h3cDeviceOUI,
            h3cDevSerialNumber,
            h3cWirelessCardSerialNumber,
            h3c3GCurrentService,
            h3c3GCurrentRssiBind,
            h3c3GImsiBind
        }
    STATUS      current
    DESCRIPTION
        "A h3c3GRssiWeakSignalTrap notification is generated when current RSSI
        falls below the weak signal threshold."
   ::= { h3c3GModemTrapPrefix 8 }

END
