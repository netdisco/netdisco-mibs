-- =================================================================
-- Copyright (c) 2004-2009 Hangzhou H3C Tech. Co., Ltd. All rights reserved.
--
-- Description: This file describes the h3c MIB implementation of l2 isolation
-- Reference:   H3C Enterprise MIB
-- Version:     V1.0 Created by y04444 Initial version
-- History:
-- V1.0 Initial version
-- =================================================================
A3COM-HUAWEI-L2ISOLATE-MIB DEFINITIONS ::= BEGIN

IMPORTS
    TruthValue,
    MacAddress,
    RowStatus
        FROM SNMPv2-TC
    h3cCommon
        FROM A3COM-HUAWEI-OID-MIB
    OBJECT-TYPE, MODULE-IDENTITY, Integer32
        FROM SNMPv2-SMI;

h3cL2Isolate MODULE-IDENTITY
    LAST-UPDATED "200905060000Z"            -- May 06th, 2009 at 00:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "The MIB module is used for l2 isolation."
    REVISION    "200905060000Z"
    DESCRIPTION
        "Initial version"
    ::= { h3cCommon 103 }

h3cL2IsolateObject OBJECT IDENTIFIER ::= { h3cL2Isolate 1 }

-- =================================================================
--  1st Table of h3cL2Isolate: h3cL2IsolateEnableTable
-- =================================================================
h3cL2IsolateEnableTable OBJECT-TYPE
    SYNTAX      SEQUENCE OF H3cL2IsolateEnableEntry
    MAX-ACCESS  not-accessible
    STATUS      current
    DESCRIPTION
        "A table for enabling/disabling layer-2-isolate for VLAN."
    ::= { h3cL2IsolateObject 1 }

h3cL2IsolateEnableEntry OBJECT-TYPE
    SYNTAX      H3cL2IsolateEnableEntry
    MAX-ACCESS  not-accessible
    STATUS      current
    DESCRIPTION
        "An entry for enabling/disabling layer-2-isolate for VLAN."
    INDEX
        {
            h3cL2IsolateVLANIndex
        }
    ::= { h3cL2IsolateEnableTable 1 }

H3cL2IsolateEnableEntry ::= SEQUENCE
    {
        h3cL2IsolateVLANIndex        Integer32,
        h3cL2IsolateEnable           TruthValue
    }

h3cL2IsolateVLANIndex OBJECT-TYPE
    SYNTAX      Integer32 (1..4094)
    MAX-ACCESS  not-accessible
    STATUS      current
    DESCRIPTION
        "Represents index of VLAN for layer-2-isolate."
    ::= { h3cL2IsolateEnableEntry 1 }

h3cL2IsolateEnable OBJECT-TYPE
    SYNTAX      TruthValue
    MAX-ACCESS  read-write
    STATUS      current
    DESCRIPTION
        "Represents the layer-2-isolate status of VLAN."
    ::= { h3cL2IsolateEnableEntry 2 }

-- =================================================================
--   2nd Table of h3cL2Isolate: h3cL2IsolatePermitMACTable
-- =================================================================
h3cL2IsolatePermitMACTable OBJECT-TYPE
    SYNTAX      SEQUENCE OF H3cL2IsolatePermitMACEntry
    MAX-ACCESS  not-accessible
    STATUS      current
    DESCRIPTION
        "A table represents the permitting MAC address for the specific VLAN."
    ::= { h3cL2IsolateObject 2 }

h3cL2IsolatePermitMACEntry OBJECT-TYPE
    SYNTAX      H3cL2IsolatePermitMACEntry
    MAX-ACCESS  not-accessible
    STATUS      current
    DESCRIPTION
        "Each entry represents the permitting MAC address for the specific VLAN."
    INDEX
        {
            h3cL2IsolateVLANIndex,
            h3cL2IsoLatePermitMAC
        }
    ::= { h3cL2IsolatePermitMACTable 1 }

H3cL2IsolatePermitMACEntry ::= SEQUENCE
    {
        h3cL2IsoLatePermitMAC            MacAddress,
        h3cL2IsoLatePermitMACRowStatus   RowStatus
    }

h3cL2IsoLatePermitMAC OBJECT-TYPE
    SYNTAX      MacAddress
    MAX-ACCESS  not-accessible
    STATUS      current
    DESCRIPTION
        "Represents the MAC address permitted in the VLAN."
    ::= { h3cL2IsolatePermitMACEntry 1 }

h3cL2IsoLatePermitMACRowStatus OBJECT-TYPE
    SYNTAX      RowStatus
    MAX-ACCESS  read-create
    STATUS      current
    DESCRIPTION
        "RowStatus. Three actions are used: active, CreateAndGo, destroy."
    ::= { h3cL2IsolatePermitMACEntry 2 }

END
