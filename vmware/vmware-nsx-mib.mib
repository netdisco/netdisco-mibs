-- **********************************************************
-- Copyright 2019 VMware, Inc.  All rights reserved.
-- **********************************************************

VMWARE-NSX-MIB DEFINITIONS ::= BEGIN

IMPORTS
    MODULE-IDENTITY, OBJECT-IDENTITY, OBJECT-TYPE, NOTIFICATION-TYPE
        FROM SNMPv2-SMI
    MODULE-COMPLIANCE, OBJECT-GROUP, NOTIFICATION-GROUP
        FROM SNMPv2-CONF
    TEXTUAL-CONVENTION, DateAndTime
        FROM SNMPv2-TC
    vmwNSXsys
        FROM VMWARE-ROOT-MIB;

    vmwNSXsysMIB MODULE-IDENTITY
    LAST-UPDATED "202006290000Z"
    ORGANIZATION "VMware, Inc"
    CONTACT-INFO
        "VMware, Inc
        3401 Hillview Ave
        Palo Alto, CA 94304
        Tel: 1-877-486-9273 or 650-427-5000
        Fax: 650-427-5001
        Web: http://kb.vmware.com/kb/1013445
        "

    DESCRIPTION
        "In much the same way that server virtualization programmatically
        creates, snapshots, deletes, and restores software-based virtual
        machines (VMs), NSX-T Data Center network virtualization
        programmatically creates, deletes, and restores software-based
        virtual networks.

        With network virtualization, the functional equivalent of a network
        hypervisor reproduces the complete set of Layer 2 through Layer 7
        networking services (for example, switching, routing, access control,
        firewalling, QoS) in software. As a result, these services can be
        programmatically assembled in any arbitrary combination, to produce
        unique, isolated virtual networks in a matter of seconds.

        For more information about NSX-T Data Center, please visit:
        https://docs.vmware.com/en/VMware-NSX-T-Data-Center/
        "

    REVISION "202006290000Z"
    DESCRIPTION
        "This revision adds 12 new notifications for NSX-T Data Center 3.0.1"

    REVISION "202003240000Z"
    DESCRIPTION
        "Initial revision of NSX-T Data Center SNMP event notifications."

   ::= { vmwNSXsys 1 }

-- **********************************************************
-- Top-level MIB groups
-- **********************************************************

vmwNsxTDataCenterNotifications OBJECT-IDENTITY
    STATUS current
    DESCRIPTION
    "All event notifications from NSX-T Data Center fall under this oid."
    ::= { vmwNSXsysMIB 0 }

vmwNsxTDataCenterData OBJECT-IDENTITY
    STATUS current
    DESCRIPTION
    "All variables that are sent in NSX-T Data Center event notifications
    fall under this oid."
    ::= { vmwNSXsysMIB 1 }

-- **********************************************************
-- Type definitions
-- **********************************************************

VmwNsxTDataCenterFeatureIdType ::= TEXTUAL-CONVENTION
    STATUS       current
    DESCRIPTION
        "The NSX-T Data Center feature ID associated with the event.
        For example, this value identifies the feature is managerHealth,
        edgeHealth, loadBalancer, etc."
    SYNTAX INTEGER {
        managerHealth(1),
        edgeHealth(2),
        certificates(3),
        passwordManagement(4),
        licenses(5),
        intelligenceHealth(6),
        infrastructureCommunication(7),
        intelligenceCommunication(9),
        cniHealth(10),
        ncpHealth(11),
        nodeAgentsHealth(12),
        endpointProtection(13),
        vpn(15),
        alarmManagement(16),
        loadBalancer(17),
        transportNodeHealth(18),
        infrastructureService(19),
        dhcp(20),
        highAvailability(21),
        routing(28),
        dns(30),
        distributedFirewall(31),
        federation(32)
    }

VmwNsxTDataCenterEventTypeType ::= TEXTUAL-CONVENTION
    DISPLAY-HINT "256a"
    STATUS       current
    DESCRIPTION
        "The name of the NSX-T Data Center event. The complete set of events
        are reported by the NSX API GET /api/v1/events."
    SYNTAX OCTET STRING (SIZE (0..256))

VmwNsxTDataCenterSeverityType ::= TEXTUAL-CONVENTION
    STATUS current
    DESCRIPTION
        "The severity of the NSX-T Data Center event. Currently only the
        critical(2), error(3), warning(4) and informational(6) levels
        are used, but the other levels may be used in future releases."
    SYNTAX INTEGER {
        emergency(0),
        alert(1),
        critical(2),
        error(3),
        warning(4),
        notice(5),
        informational(6),
        debug(7)
    }

VmwNsxTDataCenterNodeIdType ::= TEXTUAL-CONVENTION
    DISPLAY-HINT "256a"
    STATUS       current
    DESCRIPTION
        "The node ID from where a NSX-T Data Center event was emitted. A
        node ID can be for a cluster node as reported by the NSX API
        GET /api/v1/cluster. Or a node ID can be for a transport node
        as reported by the NSX API GET /api/v1/transport-nodes."
    SYNTAX OCTET STRING (SIZE (0..256))

VmwNsxTDataCenterNodeTypeType ::= TEXTUAL-CONVENTION
    STATUS       current
    DESCRIPTION
        "The type of node from where a NSX-T Data Center event was emitted."
    SYNTAX INTEGER {
        manager(0),
        edge(1),
        esx(2),
        kvm(3),
        publiccloudgateway(4),
        intelligence(5),
        autonomousedge(6),
        globalmanager(7)
    }

VmwNsxTDataCenterEntityIdType ::= TEXTUAL-CONVENTION
    DISPLAY-HINT "256a"
    STATUS       current
    DESCRIPTION
        "The ID of a NSX-T Data Center entity an event pertains to. The event
        description field provides additional details of the entity. For
        example the ID can be for a specific Load Balancer rule as reported by
        the NSX API GET /api/v1/loadbalancer/rules or a specific certificate
        as reported by the NSX API GET /api/v1/trust-management/certificates."
    SYNTAX OCTET STRING (SIZE (0..256))

VmwNsxTDataCenterSystemResourceUsageType ::= TEXTUAL-CONVENTION
    DISPLAY-HINT "256a"
    STATUS       current
    DESCRIPTION
        "The CPU, memory, or disk usage percentage of an NSX-T appliance. The
        value is an integer between 0 and 100."
    SYNTAX OCTET STRING (SIZE (0..256))

VmwNsxTDataCenterDiskPartitionNameType ::= TEXTUAL-CONVENTION
    DISPLAY-HINT "256a"
    STATUS       current
    DESCRIPTION
        "The name of a disk partition in an NSX-T appliance. For example, the
        name for the /tmp partition is '/tmp'."
    SYNTAX OCTET STRING (SIZE (0..256))

VmwNsxTDataCenterLicenseEditionTypeType ::= TEXTUAL-CONVENTION
    DISPLAY-HINT "256a"
    STATUS       current
    DESCRIPTION
        "The edition type of an NSX-T license. For example, the type for an NSX-T
        evaluation license is 'NSX Data Center Evaluation'."
    SYNTAX OCTET STRING (SIZE (0..256))

VmwNsxTDataCenterApplianceAddressType ::= TEXTUAL-CONVENTION
    DISPLAY-HINT "256a"
    STATUS       current
    DESCRIPTION
        "The NSX appliance's IP address. The value is an IPv4 address."
    SYNTAX OCTET STRING (SIZE (0..256))

VmwNsxTDataCenterCurrentGatewayStateType ::= TEXTUAL-CONVENTION
    DISPLAY-HINT "256a"
    STATUS       current
    DESCRIPTION
        "The current gateway state. The value could be active/standby/admin down."
    SYNTAX OCTET STRING (SIZE (0..256))

VmwNsxTDataCenterCurrentServiceStateType ::= TEXTUAL-CONVENTION
    DISPLAY-HINT "256a"
    STATUS       current
    DESCRIPTION
        "The current service state. The value could be start/stop/restart/crashed."
    SYNTAX OCTET STRING (SIZE (0..256))

VmwNsxTDataCenterDatapathResourceUsageType ::= TEXTUAL-CONVENTION
    DISPLAY-HINT "256a"
    STATUS       current
    DESCRIPTION
        "The CPU, memory, or disk usage percentage of the datapath on a NSX-T appliance.
        The value is an integer between 0 and 100."
    SYNTAX OCTET STRING (SIZE (0..256))

VmwNsxTDataCenterDHCPPoolUsageType ::= TEXTUAL-CONVENTION
    DISPLAY-HINT "256a"
    STATUS       current
    DESCRIPTION
        "The usage of a DHCP pool. The value is an integer between 0 and 100."
    SYNTAX OCTET STRING (SIZE (0..256))

VmwNsxTDataCenterEdgeServiceNameType ::= TEXTUAL-CONVENTION
    DISPLAY-HINT "256a"
    STATUS       current
    DESCRIPTION
        "The name of the service running on the Edge node."
    SYNTAX OCTET STRING (SIZE (0..256))

VmwNsxTDataCenterFailureReasonType ::= TEXTUAL-CONVENTION
    DISPLAY-HINT "256a"
    STATUS       current
    DESCRIPTION
        "The detailed reason of any module failure like BGP down, IKE down, etc."
    SYNTAX OCTET STRING (SIZE (0..256))

VmwNsxTDataCenterPreviousGatewayStateType ::= TEXTUAL-CONVENTION
    DISPLAY-HINT "256a"
    STATUS       current
    DESCRIPTION
        "The previous gateway state. The value could be active/standby/admin down."
    SYNTAX OCTET STRING (SIZE (0..256))

VmwNsxTDataCenterPreviousServiceStateType ::= TEXTUAL-CONVENTION
    DISPLAY-HINT "256a"
    STATUS       current
    DESCRIPTION
        "The previous service state. The value could be start/stop/restart/crashed."
    SYNTAX OCTET STRING (SIZE (0..256))

VmwNsxTDataCenterSystemUsageThresholdType ::= TEXTUAL-CONVENTION
    DISPLAY-HINT "256a"
    STATUS       current
    DESCRIPTION
        "The configured threshold value for the CPU, memory, or disk usage
        percentage of an NSX-T appliance. The value is an integer between 0 and
        100."
    SYNTAX OCTET STRING (SIZE (0..256))

VmwNsxTDataCenterUsernameType ::= TEXTUAL-CONVENTION
    DISPLAY-HINT "256a"
    STATUS       current
    DESCRIPTION
        "The name of a user in an NSX-T appliance."
    SYNTAX OCTET STRING (SIZE (0..256))

VmwNsxTDataCenterDHCPServerIdType ::= TEXTUAL-CONVENTION
    DISPLAY-HINT "256a"
    STATUS       current
    DESCRIPTION
        "The UUID of a DHCP server."
    SYNTAX OCTET STRING (SIZE (0..256))

VmwNsxTDataCenterServiceNameType ::= TEXTUAL-CONVENTION
    DISPLAY-HINT "256a"
    STATUS       current
    DESCRIPTION
        "The name of the service running in an NSX-T appliance."
    SYNTAX OCTET STRING (SIZE (0..256))

VmwNsxTDataCenterIntelligenceNodeIdType ::= TEXTUAL-CONVENTION
    DISPLAY-HINT "256a"
    STATUS       current
    DESCRIPTION
        "The node ID of NSX-T intelligence node."
    SYNTAX OCTET STRING (SIZE (0..256))

VmwNsxTDataCenterEventIdType ::= TEXTUAL-CONVENTION
    DISPLAY-HINT "256a"
    STATUS       current
    DESCRIPTION
        "The event identifier."
    SYNTAX OCTET STRING (SIZE (0..256))

VmwNsxTDataCenterSessionDownReasonType ::= TEXTUAL-CONVENTION
    DISPLAY-HINT "256a"
    STATUS       current
    DESCRIPTION
        "Down reason of the IPsec VPN session."
    SYNTAX OCTET STRING (SIZE (0..256))

VmwNsxTDataCenterTunnelDownReasonType ::= TEXTUAL-CONVENTION
    DISPLAY-HINT "256a"
    STATUS       current
    DESCRIPTION
        "Down reason of the IPsec VPN tunnel."
    SYNTAX OCTET STRING (SIZE (0..256))

VmwNsxTDataCenterHeapTypeType ::= TEXTUAL-CONVENTION
    DISPLAY-HINT "256a"
    STATUS       current
    DESCRIPTION
        "Heap type information for DFW memory usage like vsip-attr, vsip-flow, vsip-fqdni, etc."
    SYNTAX OCTET STRING (SIZE (0..256))

VmwNsxTDataCenterMempoolNameType ::= TEXTUAL-CONVENTION
    DISPLAY-HINT "256a"
    STATUS       current
    DESCRIPTION
        "Name of a memory pool."
    SYNTAX OCTET STRING (SIZE (0..256))

VmwNsxTDataCenterPasswordExpirationDaysType ::= TEXTUAL-CONVENTION
    DISPLAY-HINT "256a"
    STATUS       current
    DESCRIPTION
        "The number of days left before expiration of the password of an NSX-T
        appliance user. The value is an integer greater than 0."
    SYNTAX OCTET STRING (SIZE (0..256))

VmwNsxTDataCenterBGPNeighborIPType ::= TEXTUAL-CONVENTION
    DISPLAY-HINT "256a"
    STATUS       current
    DESCRIPTION
        "IP address of BGP Neighbor. This could be either IPv4 or IPv6 address."
    SYNTAX OCTET STRING (SIZE (0..256))

VmwNsxTDataCenterPeerAddressType ::= TEXTUAL-CONVENTION
    DISPLAY-HINT "256a"
    STATUS       current
    DESCRIPTION
        "IP address of BFD peer."
    SYNTAX OCTET STRING (SIZE (0..256))

VmwNsxTDataCenterStaticAddressType ::= TEXTUAL-CONVENTION
    DISPLAY-HINT "256a"
    STATUS       current
    DESCRIPTION
        "A Static IP address."
    SYNTAX OCTET STRING (SIZE (0..256))

VmwNsxTDataCenterDuplicateIPAddressType ::= TEXTUAL-CONVENTION
    DISPLAY-HINT "256a"
    STATUS       current
    DESCRIPTION
        "Duplicate IP address."
    SYNTAX OCTET STRING (SIZE (0..256))

VmwNsxTDataCenterEdgeNICNameType ::= TEXTUAL-CONVENTION
    DISPLAY-HINT "256a"
    STATUS       current
    DESCRIPTION
        "The name of the NIC whose link is down or which faced tx/rx ring buffer overflow."
    SYNTAX OCTET STRING (SIZE (0..256))

VmwNsxTDataCenterRxRingBufferOverflowPercentageType ::= TEXTUAL-CONVENTION
    DISPLAY-HINT "256a"
    STATUS       current
    DESCRIPTION
        "The NIC's receive descriptor ring buffer on a NSX-T Edge or Gateway node has no space left
        to accomodate new incoming packets and there is a significant drop due to it.
        The value is a float between 0 to 100 describing the overflow percentage due to the packet drops."
    SYNTAX OCTET STRING (SIZE (0..256))

VmwNsxTDataCenterTxRingBufferOverflowPercentageType ::= TEXTUAL-CONVENTION
    DISPLAY-HINT "256a"
    STATUS       current
    DESCRIPTION
        "The NIC's transmit descriptor ring buffer on a NSX-T Edge or Gateway node has no space left
        to accomodate new outgoing packets and there is a significant drop due to it.
        The value is a float between 0 to 100 describing the overflow percentage due to the packet drops."
    SYNTAX OCTET STRING (SIZE (0..256))

VmwNsxTDataCenterSrIdType ::= TEXTUAL-CONVENTION
    DISPLAY-HINT "256a"
    STATUS       current
    DESCRIPTION
        "Service Router UUID."
    SYNTAX OCTET STRING (SIZE (0..256))

VmwNsxTDataCenterRemoteSiteNameType ::= TEXTUAL-CONVENTION
    DISPLAY-HINT "256a"
    STATUS       current
    DESCRIPTION
        "Name of a remote site in federation. For more information on remote
        sites and an overview of the federation feature, please refer to:
        https://docs.vmware.com/en/VMware-NSX-T-Data-Center/3.0/administration/GUID-D5B6DC79-6733-44A7-8072-50221CF2122A.html"
    SYNTAX OCTET STRING (SIZE (0..256))

VmwNsxTDataCenterBGPSourceIPType ::= TEXTUAL-CONVENTION
    DISPLAY-HINT "256a"
    STATUS       current
    DESCRIPTION
        "Source IP address of BGP session. This could be either an IPv4 address
         in dotted-decimal format or an IPv6 address in IPv6 address format."
    SYNTAX OCTET STRING (SIZE (0..256))

VmwNsxTDataCenterRemoteSiteIdType ::= TEXTUAL-CONVENTION
    DISPLAY-HINT "256a"
    STATUS       current
    DESCRIPTION
        "The identifier for a remote site."
    SYNTAX OCTET STRING (SIZE (0..256))

VmwNsxTDataCenterSiteIdType ::= TEXTUAL-CONVENTION
    DISPLAY-HINT "256a"
    STATUS       current
    DESCRIPTION
        "The identifier for a local site."
    SYNTAX OCTET STRING (SIZE (0..256))

VmwNsxTDataCenterSiteNameType ::= TEXTUAL-CONVENTION
    DISPLAY-HINT "256a"
    STATUS       current
    DESCRIPTION
        "Name of a local site in federation. For more information on local
        sites and an overview of the federation feature, please refer to:
        https://docs.vmware.com/en/VMware-NSX-T-Data-Center/3.0/administration/GUID-D5B6DC79-6733-44A7-8072-50221CF2122A.html"
    SYNTAX OCTET STRING (SIZE (0..256))

vmwNsxTDataCenterTimestamp OBJECT-TYPE
    SYNTAX      DateAndTime
    MAX-ACCESS  accessible-for-notify
    STATUS      current
    DESCRIPTION
        "The timestamp when the NSX-T Data Center event occurred."
    ::= { vmwNsxTDataCenterData 1 }

vmwNsxTDataCenterFeatureName OBJECT-TYPE
    SYNTAX      VmwNsxTDataCenterFeatureIdType
    MAX-ACCESS  accessible-for-notify
    STATUS      current
    DESCRIPTION
        "The NSX-T Data Center feature ID associated with the event."
    ::= { vmwNsxTDataCenterData 2 }

vmwNsxTDataCenterEventType OBJECT-TYPE
    SYNTAX      VmwNsxTDataCenterEventTypeType
    MAX-ACCESS  accessible-for-notify
    STATUS      current
    DESCRIPTION
        "The name of the NSX-T Data Center event."
    ::= { vmwNsxTDataCenterData 3 }

vmwNsxTDataCenterEventSeverity OBJECT-TYPE
    SYNTAX      VmwNsxTDataCenterSeverityType
    MAX-ACCESS  accessible-for-notify
    STATUS      current
    DESCRIPTION
        "The severity of the NSX-T Data Center event."
    ::= { vmwNsxTDataCenterData 4 }

vmwNsxTDataCenterNodeId OBJECT-TYPE
    SYNTAX      VmwNsxTDataCenterNodeIdType
    MAX-ACCESS  accessible-for-notify
    STATUS      current
    DESCRIPTION
        "The node ID from where a NSX-T Data Center event was emitted."
    ::= { vmwNsxTDataCenterData 5 }

vmwNsxTDataCenterNodeType OBJECT-TYPE
    SYNTAX      VmwNsxTDataCenterNodeTypeType
    MAX-ACCESS  accessible-for-notify
    STATUS      current
    DESCRIPTION
        "The type of node from where a NSX-T Data Center event was emitted."
    ::= { vmwNsxTDataCenterData 6 }

vmwNsxTDataCenterEntityId OBJECT-TYPE
    SYNTAX      VmwNsxTDataCenterEntityIdType
    MAX-ACCESS  accessible-for-notify
    STATUS      current
    DESCRIPTION
        "The ID of a NSX-T Data Center entity an event pertains to. The event
        description field provides additional details of the entity. For
        example the ID can be for a specific Load Balancer rule as reported by
        the NSX API GET /api/v1/loadbalancer/rules or a specific certificate
        as reported by the NSX API GET /api/v1/trust-management/certificates."
    ::= { vmwNsxTDataCenterData 21 }

vmwNsxTDataCenterSystemResourceUsage OBJECT-TYPE
    SYNTAX      VmwNsxTDataCenterSystemResourceUsageType
    MAX-ACCESS  accessible-for-notify
    STATUS      current
    DESCRIPTION
        "The CPU, memory, or disk usage percentage of an NSX-T appliance. The
        value is an integer between 0 and 100."
    ::= { vmwNsxTDataCenterData 22 }

vmwNsxTDataCenterDiskPartitionName OBJECT-TYPE
    SYNTAX      VmwNsxTDataCenterDiskPartitionNameType
    MAX-ACCESS  accessible-for-notify
    STATUS      current
    DESCRIPTION
        "The name of a disk partition in an NSX-T appliance. For example, the
        name for the /tmp partition is '/tmp'."
    ::= { vmwNsxTDataCenterData 23 }

vmwNsxTDataCenterLicenseEditionType OBJECT-TYPE
    SYNTAX      VmwNsxTDataCenterLicenseEditionTypeType
    MAX-ACCESS  accessible-for-notify
    STATUS      current
    DESCRIPTION
        "The edition type of an NSX-T license. For example, the type for an NSX-T
        evaluation license is 'NSX Data Center Evaluation'."
    ::= { vmwNsxTDataCenterData 24 }

vmwNsxTDataCenterApplianceAddress OBJECT-TYPE
    SYNTAX      VmwNsxTDataCenterApplianceAddressType
    MAX-ACCESS  accessible-for-notify
    STATUS      current
    DESCRIPTION
        "The NSX appliance's IP address. The value is an IPv4 address."
    ::= { vmwNsxTDataCenterData 25 }

vmwNsxTDataCenterCurrentGatewayState OBJECT-TYPE
    SYNTAX      VmwNsxTDataCenterCurrentGatewayStateType
    MAX-ACCESS  accessible-for-notify
    STATUS      current
    DESCRIPTION
        "The current gateway state. The value could be active/standby/admin down."
    ::= { vmwNsxTDataCenterData 26 }

vmwNsxTDataCenterCurrentServiceState OBJECT-TYPE
    SYNTAX      VmwNsxTDataCenterCurrentServiceStateType
    MAX-ACCESS  accessible-for-notify
    STATUS      current
    DESCRIPTION
        "The current service state. The value could be start/stop/restart/crashed."
    ::= { vmwNsxTDataCenterData 27 }

vmwNsxTDataCenterDatapathResourceUsage OBJECT-TYPE
    SYNTAX      VmwNsxTDataCenterDatapathResourceUsageType
    MAX-ACCESS  accessible-for-notify
    STATUS      current
    DESCRIPTION
        "The CPU, memory, or disk usage percentage of the datapath on a NSX-T appliance.
        The value is an integer between 0 and 100."
    ::= { vmwNsxTDataCenterData 28 }

vmwNsxTDataCenterDHCPPoolUsage OBJECT-TYPE
    SYNTAX      VmwNsxTDataCenterDHCPPoolUsageType
    MAX-ACCESS  accessible-for-notify
    STATUS      current
    DESCRIPTION
        "The usage of a DHCP pool. The value is an integer between 0 and 100."
    ::= { vmwNsxTDataCenterData 29 }

vmwNsxTDataCenterEdgeServiceName OBJECT-TYPE
    SYNTAX      VmwNsxTDataCenterEdgeServiceNameType
    MAX-ACCESS  accessible-for-notify
    STATUS      current
    DESCRIPTION
        "The name of the service running on the Edge node."
    ::= { vmwNsxTDataCenterData 30 }

vmwNsxTDataCenterFailureReason OBJECT-TYPE
    SYNTAX      VmwNsxTDataCenterFailureReasonType
    MAX-ACCESS  accessible-for-notify
    STATUS      current
    DESCRIPTION
        "The detailed reason of any module failure like BGP down, IKE down, etc."
    ::= { vmwNsxTDataCenterData 31 }

vmwNsxTDataCenterPreviousGatewayState OBJECT-TYPE
    SYNTAX      VmwNsxTDataCenterPreviousGatewayStateType
    MAX-ACCESS  accessible-for-notify
    STATUS      current
    DESCRIPTION
        "The previous gateway state. The value could be active/standby/admin down."
    ::= { vmwNsxTDataCenterData 32 }

vmwNsxTDataCenterPreviousServiceState OBJECT-TYPE
    SYNTAX      VmwNsxTDataCenterPreviousServiceStateType
    MAX-ACCESS  accessible-for-notify
    STATUS      current
    DESCRIPTION
        "The previous service state. The value could be start/stop/restart/crashed."
    ::= { vmwNsxTDataCenterData 33 }

vmwNsxTDataCenterSystemUsageThreshold OBJECT-TYPE
    SYNTAX      VmwNsxTDataCenterSystemUsageThresholdType
    MAX-ACCESS  accessible-for-notify
    STATUS      current
    DESCRIPTION
        "The configured threshold value for the CPU, memory, or disk usage
        percentage of an NSX-T appliance. The value is an integer between 0 and
        100."
    ::= { vmwNsxTDataCenterData 34 }

vmwNsxTDataCenterUsername OBJECT-TYPE
    SYNTAX      VmwNsxTDataCenterUsernameType
    MAX-ACCESS  accessible-for-notify
    STATUS      current
    DESCRIPTION
        "The name of a user in an NSX-T appliance."
    ::= { vmwNsxTDataCenterData 35 }

vmwNsxTDataCenterDHCPServerId OBJECT-TYPE
    SYNTAX      VmwNsxTDataCenterDHCPServerIdType
    MAX-ACCESS  accessible-for-notify
    STATUS      current
    DESCRIPTION
        "The UUID of a DHCP server."
    ::= { vmwNsxTDataCenterData 36 }

vmwNsxTDataCenterServiceName OBJECT-TYPE
    SYNTAX      VmwNsxTDataCenterServiceNameType
    MAX-ACCESS  accessible-for-notify
    STATUS      current
    DESCRIPTION
        "The name of the service running in an NSX-T appliance."
    ::= { vmwNsxTDataCenterData 37 }

vmwNsxTDataCenterIntelligenceNodeId OBJECT-TYPE
    SYNTAX      VmwNsxTDataCenterIntelligenceNodeIdType
    MAX-ACCESS  accessible-for-notify
    STATUS      current
    DESCRIPTION
        "The node ID of NSX-T intelligence node."
    ::= { vmwNsxTDataCenterData 38 }

vmwNsxTDataCenterEventId OBJECT-TYPE
    SYNTAX      VmwNsxTDataCenterEventIdType
    MAX-ACCESS  accessible-for-notify
    STATUS      current
    DESCRIPTION
        "The event identifier."
    ::= { vmwNsxTDataCenterData 40 }

vmwNsxTDataCenterSessionDownReason OBJECT-TYPE
    SYNTAX      VmwNsxTDataCenterSessionDownReasonType
    MAX-ACCESS  accessible-for-notify
    STATUS      current
    DESCRIPTION
        "Down reason of the IPsec VPN session."
    ::= { vmwNsxTDataCenterData 43 }

vmwNsxTDataCenterTunnelDownReason OBJECT-TYPE
    SYNTAX      VmwNsxTDataCenterTunnelDownReasonType
    MAX-ACCESS  accessible-for-notify
    STATUS      current
    DESCRIPTION
        "Down reason of the IPsec VPN tunnel."
    ::= { vmwNsxTDataCenterData 48 }

vmwNsxTDataCenterHeapType OBJECT-TYPE
    SYNTAX      VmwNsxTDataCenterHeapTypeType
    MAX-ACCESS  accessible-for-notify
    STATUS      current
    DESCRIPTION
        "Heap type information for DFW memory usage like vsip-attr, vsip-flow, vsip-fqdni, etc."
    ::= { vmwNsxTDataCenterData 49 }

vmwNsxTDataCenterMempoolName OBJECT-TYPE
    SYNTAX      VmwNsxTDataCenterMempoolNameType
    MAX-ACCESS  accessible-for-notify
    STATUS      current
    DESCRIPTION
        "Name of a memory pool."
    ::= { vmwNsxTDataCenterData 50 }

vmwNsxTDataCenterPasswordExpirationDays OBJECT-TYPE
    SYNTAX      VmwNsxTDataCenterPasswordExpirationDaysType
    MAX-ACCESS  accessible-for-notify
    STATUS      current
    DESCRIPTION
        "The number of days left before expiration of the password of an NSX-T
        appliance user. The value is an integer greater than 0."
    ::= { vmwNsxTDataCenterData 51 }

vmwNsxTDataCenterBGPNeighborIP OBJECT-TYPE
    SYNTAX      VmwNsxTDataCenterBGPNeighborIPType
    MAX-ACCESS  accessible-for-notify
    STATUS      current
    DESCRIPTION
        "IP address of BGP Neighbor. This could be either IPv4 or IPv6 address."
    ::= { vmwNsxTDataCenterData 52 }

vmwNsxTDataCenterPeerAddress OBJECT-TYPE
    SYNTAX      VmwNsxTDataCenterPeerAddressType
    MAX-ACCESS  accessible-for-notify
    STATUS      current
    DESCRIPTION
        "IP address of BFD peer."
    ::= { vmwNsxTDataCenterData 54 }

vmwNsxTDataCenterStaticAddress OBJECT-TYPE
    SYNTAX      VmwNsxTDataCenterStaticAddressType
    MAX-ACCESS  accessible-for-notify
    STATUS      current
    DESCRIPTION
        "A Static IP address."
    ::= { vmwNsxTDataCenterData 56 }

vmwNsxTDataCenterDuplicateIPAddress OBJECT-TYPE
    SYNTAX      VmwNsxTDataCenterDuplicateIPAddressType
    MAX-ACCESS  accessible-for-notify
    STATUS      current
    DESCRIPTION
        "Duplicate IP address."
    ::= { vmwNsxTDataCenterData 57 }

vmwNsxTDataCenterEdgeNICName OBJECT-TYPE
    SYNTAX      VmwNsxTDataCenterEdgeNICNameType
    MAX-ACCESS  accessible-for-notify
    STATUS      current
    DESCRIPTION
        "The name of the NIC whose link is down or which faced tx/rx ring buffer overflow."
    ::= { vmwNsxTDataCenterData 60 }

vmwNsxTDataCenterRxRingBufferOverflowPercentage OBJECT-TYPE
    SYNTAX      VmwNsxTDataCenterRxRingBufferOverflowPercentageType
    MAX-ACCESS  accessible-for-notify
    STATUS      current
    DESCRIPTION
        "The NIC's receive descriptor ring buffer on a NSX-T Edge or Gateway node has no space left
        to accomodate new incoming packets and there is a significant drop due to it.
        The value is a float between 0 to 100 describing the overflow percentage due to the packet drops."
    ::= { vmwNsxTDataCenterData 61 }

vmwNsxTDataCenterTxRingBufferOverflowPercentage OBJECT-TYPE
    SYNTAX      VmwNsxTDataCenterTxRingBufferOverflowPercentageType
    MAX-ACCESS  accessible-for-notify
    STATUS      current
    DESCRIPTION
        "The NIC's transmit descriptor ring buffer on a NSX-T Edge or Gateway node has no space left
        to accomodate new outgoing packets and there is a significant drop due to it.
        The value is a float between 0 to 100 describing the overflow percentage due to the packet drops."
    ::= { vmwNsxTDataCenterData 62 }

vmwNsxTDataCenterSrId OBJECT-TYPE
    SYNTAX      VmwNsxTDataCenterSrIdType
    MAX-ACCESS  accessible-for-notify
    STATUS      current
    DESCRIPTION
        "Service Router UUID."
    ::= { vmwNsxTDataCenterData 63 }

vmwNsxTDataCenterRemoteSiteName OBJECT-TYPE
    SYNTAX      VmwNsxTDataCenterRemoteSiteNameType
    MAX-ACCESS  accessible-for-notify
    STATUS      current
    DESCRIPTION
        "This value is not expected to be empty."
    ::= { vmwNsxTDataCenterData 65 }

vmwNsxTDataCenterBGPSourceIP OBJECT-TYPE
    SYNTAX      VmwNsxTDataCenterBGPSourceIPType
    MAX-ACCESS  accessible-for-notify
    STATUS      current
    DESCRIPTION
        "This value is not expected to be empty."
    ::= { vmwNsxTDataCenterData 66 }

vmwNsxTDataCenterRemoteSiteId OBJECT-TYPE
    SYNTAX      VmwNsxTDataCenterRemoteSiteIdType
    MAX-ACCESS  accessible-for-notify
    STATUS      current
    DESCRIPTION
        "This value is not expected to be empty."
    ::= { vmwNsxTDataCenterData 67 }

vmwNsxTDataCenterSiteId OBJECT-TYPE
    SYNTAX      VmwNsxTDataCenterSiteIdType
    MAX-ACCESS  accessible-for-notify
    STATUS      current
    DESCRIPTION
        "This value is not expected to be empty."
    ::= { vmwNsxTDataCenterData 68 }

vmwNsxTDataCenterSiteName OBJECT-TYPE
    SYNTAX      VmwNsxTDataCenterSiteNameType
    MAX-ACCESS  accessible-for-notify
    STATUS      current
    DESCRIPTION
        "This value is not expected to be empty."
    ::= { vmwNsxTDataCenterData 69 }

-- **********************************************************
-- AlarmManagement feature event notifications
-- **********************************************************

vmwNsxTAlarmManagementFeaturePrefix OBJECT-IDENTITY
    STATUS current
    DESCRIPTION
        "Notifications applicable to the AlarmManagement feature have this OID prefix."
    ::= { vmwNsxTDataCenterNotifications 16 }

vmwNsxTAlarmManagementFeature OBJECT-IDENTITY
    STATUS current
    DESCRIPTION
        "Sub-identifier added to ensure the next-to-last sub-identifier is zero
        for AlarmManagement feature notifications.
        "
    ::= { vmwNsxTAlarmManagementFeaturePrefix 0 }

vmwNsxTAlarmManagementAlarmServiceOverloaded NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Due to heavy volume of alarms reported, the alarm service is temporarily
        overloaded. The NSX UI and GET /api/v1/alarms NSX API have stopped
        reporting new alarms; however, syslog entries and SNMP traps (if enabled)
        are still being emitted reporting the underlying event details. When the
        underlying issues causing the heavy volume of alarms are addressed, the
        alarm service will start reporting new alarms again.

        Action required:
        Review all active alarms using the Alarms page in the NSX UI or using the
        GET /api/v1/alarms?status=OPEN,ACKNOWLEDGED,SUPPRESSED NSX API. For each
        active alarm investigate the root cause by following the recommended action
        for the alarm. When sufficient alarms are resolved, the alarm service will
        start reporting new alarms again.
        "
    ::= { vmwNsxTAlarmManagementFeature 1 }

vmwNsxTAlarmManagementAlarmServiceOverloadedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The heavy volume of alarms has subsided and new alarms are being reported
        again.

        Action required:
        None, receipt of this notification indicates event cleared.
        "
    ::= { vmwNsxTAlarmManagementFeature 2 }

vmwNsxTAlarmManagementHeavyVolumeOfAlarms NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEventId
    }
    STATUS current
    DESCRIPTION
        "Due to heavy volume of vmwNsxTDataCenterEventId alarms, the alarm service has
        temporarily stopped reporting alarms of this type. The NSX UI and
        GET /api/v1/alarms NSX API are not reporting new instances of these
        alarms; however, syslog entries and SNMP traps (if enabled) are
        still being emitted reporting the underlying event details. When the
        underlying issues causing the heavy volume of vmwNsxTDataCenterEventId alarms are
        addressed, the alarm service will start reporting new vmwNsxTDataCenterEventId
        alarms when new issues are detected again.

        Action required:
        Review all active alarms of type vmwNsxTDataCenterEventId using the
        Alarms page in the NSX UI or using the NSX API GET
        /api/v1/alarms?status=OPEN,ACKNOWLEDGED,SUPPRESSED. For each active
        alarm investigate the root cause by following the recommended action
        for the alarm. When sufficient alarms are resolved, the alarm service
        will start reporting new vmwNsxTDataCenterEventId alarms again.
        "
    ::= { vmwNsxTAlarmManagementFeature 3 }

vmwNsxTAlarmManagementHeavyVolumeOfAlarmsClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEventId
    }
    STATUS current
    DESCRIPTION
        "The heavy volume of vmwNsxTDataCenterEventId alarms has subsided and new alarms of
        this type are being reported again.

        Action required:
        None, receipt of this notification indicates event cleared.
        "
    ::= { vmwNsxTAlarmManagementFeature 4 }

-- **********************************************************
-- Certificates feature event notifications
-- **********************************************************

vmwNsxTCertificatesFeaturePrefix OBJECT-IDENTITY
    STATUS current
    DESCRIPTION
        "Notifications applicable to the Certificates feature have this OID prefix."
    ::= { vmwNsxTDataCenterNotifications 3 }

vmwNsxTCertificatesFeature OBJECT-IDENTITY
    STATUS current
    DESCRIPTION
        "Sub-identifier added to ensure the next-to-last sub-identifier is zero
        for Certificates feature notifications.
        "
    ::= { vmwNsxTCertificatesFeaturePrefix 0 }

vmwNsxTCertificatesCertificateExpirationApproaching NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Certificate vmwNsxTDataCenterEntityId is approaching expiration.

        Action required:
        Ensure services that are currently using the certificate are updated
        to use a new, non-expiring certificate. For example, to apply a new
        certificate to the HTTP service, invoke the following NSX API POST
        /api/v1/node/services/http?action=apply_certificate&certificate_id=<cert-id>
        where <cert-id> is the ID of a valid certificate reported by the
        GET /api/v1/trust-management/certificates NSX API. Once the expiring
        certificate is no longer in use, it should be deleted by invoking the
        DELETE /api/v1/trust-management/certificates/vmwNsxTDataCenterEntityId NSX API.
        "
    ::= { vmwNsxTCertificatesFeature 1 }

vmwNsxTCertificatesCertificateExpirationApproachingClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The expiring certificate vmwNsxTDataCenterEntityId has been removed or is no longer
        approaching expiration.

        Action required:
        None, receipt of this notification indicates event cleared.
        "
    ::= { vmwNsxTCertificatesFeature 2 }

vmwNsxTCertificatesCertificateExpired NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Certificate vmwNsxTDataCenterEntityId has expired.

        Action required:
        Ensure services that are currently using the certificate are updated
        to use a new, non-expired certificate. For example, to apply a new
        certificate to the HTTP service, invoke the NSX API POST
        /api/v1/node/services/http?action=apply_certificate&certificate_id=<cert-id>
        where <cert-id> is the ID of a valid certificate reported by the
        GET /api/v1/trust-management/certificates NSX API. Once the expired
        certificate is no longer in use, it should be deleted by invoking the
        DELETE /api/v1/trust-management/certificates/vmwNsxTDataCenterEntityId NSX API.
        "
    ::= { vmwNsxTCertificatesFeature 3 }

vmwNsxTCertificatesCertificateExpiredClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The expired certificate vmwNsxTDataCenterEntityId has been removed or is no longer
        expired.

        Action required:
        None, receipt of this notification indicates event cleared.
        "
    ::= { vmwNsxTCertificatesFeature 4 }

vmwNsxTCertificatesCertificateIsAboutToExpire NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Certificate vmwNsxTDataCenterEntityId is about to expire.

        Action required:
        Ensure services that are currently using the certificate are updated
        to use a new, non-expiring certificate. For example, to apply a new
        certificate to the HTTP service, invoke the following NSX API POST
        /api/v1/node/services/http?action=apply_certificate&certificate_id=<cert-id>
        where <cert-id> is the ID of a valid certificate reported by the
        GET /api/v1/trust-management/certificates NSX API. Once the expiring
        certificate is no longer in use, it should be deleted by invoking the
        DELETE /api/v1/trust-management/certificates/vmwNsxTDataCenterEntityId NSX API.
        "
    ::= { vmwNsxTCertificatesFeature 5 }

vmwNsxTCertificatesCertificateIsAboutToExpireClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The expiring certificate vmwNsxTDataCenterEntityId has been removed or is no longer
        about to expire.

        Action required:
        None, receipt of this notification indicates event cleared.
        "
    ::= { vmwNsxTCertificatesFeature 6 }

-- **********************************************************
-- CniHealth feature event notifications
-- **********************************************************

vmwNsxTCniHealthFeaturePrefix OBJECT-IDENTITY
    STATUS current
    DESCRIPTION
        "Notifications applicable to the CniHealth feature have this OID prefix."
    ::= { vmwNsxTDataCenterNotifications 10 }

vmwNsxTCniHealthFeature OBJECT-IDENTITY
    STATUS current
    DESCRIPTION
        "Sub-identifier added to ensure the next-to-last sub-identifier is zero
        for CniHealth feature notifications.
        "
    ::= { vmwNsxTCniHealthFeaturePrefix 0 }

vmwNsxTCniHealthHyperbusManagerConnectionDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Hyperbus cannot communicate with the Manager node.

        Action required:
        The hyperbus vmkernel interface (vmk50) may be missing. Please refer to
        Knowledge Base article https://kb.vmware.com/s/article/67432.
        "
    ::= { vmwNsxTCniHealthFeature 3 }

vmwNsxTCniHealthHyperbusManagerConnectionDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Hyperbus can communicate with the Manager node.

        Action required:
        None, receipt of this notification indicates event cleared.
        "
    ::= { vmwNsxTCniHealthFeature 4 }

-- **********************************************************
-- DHCP feature event notifications
-- **********************************************************

vmwNsxTDHCPFeaturePrefix OBJECT-IDENTITY
    STATUS current
    DESCRIPTION
        "Notifications applicable to the DHCP feature have this OID prefix."
    ::= { vmwNsxTDataCenterNotifications 20 }

vmwNsxTDHCPFeature OBJECT-IDENTITY
    STATUS current
    DESCRIPTION
        "Sub-identifier added to ensure the next-to-last sub-identifier is zero
        for DHCP feature notifications.
        "
    ::= { vmwNsxTDHCPFeaturePrefix 0 }

vmwNsxTDHCPPoolLeaseAllocationFailed NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDHCPServerId
    }
    STATUS current
    DESCRIPTION
        "The addresses in IP Pool vmwNsxTDataCenterEntityId of DHCP Server vmwNsxTDataCenterDHCPServerId have
        been exhausted. The last DHCP request has failed and future requests will
        fail.

        Action required:
        Review the DHCP pool configuration in the NSX UI or on the Edge node where
        the DHCP server is running by invoking the NSX CLI command `get dhcp ip-pool`.
        Also review the current active leases on the Edge node by invoking the NSX
        CLI command `get dhcp lease`.  Compare the leases to the number of active
        VMs. Consider reducing the lease time on the DHCP server configuration if
        the number of VMs are low compared to the number of active leases. Also
        consider expanding the pool range for the DHCP server by visiting the
        Networking | Segments | Segment page in the NSX UI.
        "
    ::= { vmwNsxTDHCPFeature 1 }

vmwNsxTDHCPPoolLeaseAllocationFailedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDHCPServerId
    }
    STATUS current
    DESCRIPTION
        "IP Pool vmwNsxTDataCenterEntityId of DHCP Server vmwNsxTDataCenterDHCPServerId is no longer exhausted.
        A lease is successfully allocated to the last DHCP request.

        Action required:
        None, receipt of this notification indicates event cleared.
        "
    ::= { vmwNsxTDHCPFeature 2 }

vmwNsxTDHCPPoolOverloaded NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDHCPServerId,
        vmwNsxTDataCenterDHCPPoolUsage
    }
    STATUS current
    DESCRIPTION
        "The DHCP Server vmwNsxTDataCenterDHCPServerId IP Pool vmwNsxTDataCenterEntityId usage is approaching
        exhaustion with vmwNsxTDataCenterDHCPPoolUsage% IPs allocated.

        Action required:
        Review the DHCP pool configuration in the NSX UI or on the Edge node where
        the DHCP server is running by invoking the NSX CLI command `get dhcp ip-pool`.
        Also review the current active leases on the Edge node by invoking the NSX
        CLI command `get dhcp lease`.  Compare the leases to the number of active
        VMs. Consider reducing the lease time on the DHCP server configuration if
        the number of VMs are low compared to the number of active leases. Also
        consider expanding the pool range for the DHCP server by visiting the
        Networking | Segments | Segment page in the NSX UI.
        "
    ::= { vmwNsxTDHCPFeature 3 }

vmwNsxTDHCPPoolOverloadedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDHCPServerId
    }
    STATUS current
    DESCRIPTION
        "The DHCP Server vmwNsxTDataCenterDHCPServerId IP Pool vmwNsxTDataCenterEntityId has fallen below the
        high usage threshold.

        Action required:
        None, receipt of this notification indicates event cleared.
        "
    ::= { vmwNsxTDHCPFeature 4 }

-- **********************************************************
-- DistributedFirewall feature event notifications
-- **********************************************************

vmwNsxTDistributedFirewallFeaturePrefix OBJECT-IDENTITY
    STATUS current
    DESCRIPTION
        "Notifications applicable to the DistributedFirewall feature have this OID prefix."
    ::= { vmwNsxTDataCenterNotifications 31 }

vmwNsxTDistributedFirewallFeature OBJECT-IDENTITY
    STATUS current
    DESCRIPTION
        "Sub-identifier added to ensure the next-to-last sub-identifier is zero
        for DistributedFirewall feature notifications.
        "
    ::= { vmwNsxTDistributedFirewallFeaturePrefix 0 }

vmwNsxTDistributedFirewallDFWCPUUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The DFW CPU usage on Transport node vmwNsxTDataCenterEntityId has reached
        vmwNsxTDataCenterSystemResourceUsage% which is at or above the very high
        threshold value of vmwNsxTDataCenterSystemUsageThreshold%.

        Action required:
        Consider re-balancing the VM workloads on this host to other hosts.  Please
        review the security design for optimization. For example, use the apply-to
        configuration if the rules are not applicable to the entire datacenter.
        "
    ::= { vmwNsxTDistributedFirewallFeature 1 }

vmwNsxTDistributedFirewallDFWCPUUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The DFW CPU usage on Transport node vmwNsxTDataCenterEntityId has reached
        vmwNsxTDataCenterSystemResourceUsage% which is below the very high
        threshold value of vmwNsxTDataCenterSystemUsageThreshold%.

        Action required:
        None, receipt of this notification indicates event cleared.
        "
    ::= { vmwNsxTDistributedFirewallFeature 2 }

vmwNsxTDistributedFirewallDFWMemoryUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterHeapType,
        vmwNsxTDataCenterSystemResourceUsage,
        vmwNsxTDataCenterSystemUsageThreshold
    }
    STATUS current
    DESCRIPTION
        "The DFW Memory usage vmwNsxTDataCenterHeapType on Transport node
        vmwNsxTDataCenterEntityId has reached vmwNsxTDataCenterSystemResourceUsage% which
        is at or above the very high threshold value of vmwNsxTDataCenterSystemUsageThreshold%.

        Action required:
        View the current DFW memory usage by invoking the NSX CLI command
        `get firewall thresholds` on the host. Consider re-balancing the
        workloads on this host to other hosts.
        "
    ::= { vmwNsxTDistributedFirewallFeature 3 }

vmwNsxTDistributedFirewallDFWMemoryUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterHeapType,
        vmwNsxTDataCenterSystemResourceUsage,
        vmwNsxTDataCenterSystemUsageThreshold
    }
    STATUS current
    DESCRIPTION
        "The DFW Memory usage vmwNsxTDataCenterHeapType on Transport node
        vmwNsxTDataCenterEntityId has reached vmwNsxTDataCenterSystemResourceUsage% which
        is below the very high threshold value of vmwNsxTDataCenterSystemUsageThreshold%.

        Action required:
        None, receipt of this notification indicates event cleared.
        "
    ::= { vmwNsxTDistributedFirewallFeature 4 }

-- **********************************************************
-- DNS feature event notifications
-- **********************************************************

vmwNsxTDNSFeaturePrefix OBJECT-IDENTITY
    STATUS current
    DESCRIPTION
        "Notifications applicable to the DNS feature have this OID prefix."
    ::= { vmwNsxTDataCenterNotifications 30 }

vmwNsxTDNSFeature OBJECT-IDENTITY
    STATUS current
    DESCRIPTION
        "Sub-identifier added to ensure the next-to-last sub-identifier is zero
        for DNS feature notifications.
        "
    ::= { vmwNsxTDNSFeaturePrefix 0 }

vmwNsxTDNSForwarderDisabled NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "DNS forwarder vmwNsxTDataCenterEntityId is disabled.

        Action required:
        1. Invoke the NSX CLI command `get dns-forwarders status` to verify
        if the DNS forwarder is in the disabled state.
        2. Use NSX Policy API or Manager API to enable the DNS forwarder it
        should not be in the disabled state.
        "
    ::= { vmwNsxTDNSFeature 1 }

vmwNsxTDNSForwarderDisabledClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "DNS forwarder vmwNsxTDataCenterEntityId is enabled.

        Action required:
        None, receipt of this notification indicates event cleared.
        "
    ::= { vmwNsxTDNSFeature 2 }

vmwNsxTDNSForwarderDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "DNS forwarder vmwNsxTDataCenterEntityId is not running. This is impacting all
        configured DNS Forwarders that are currently enabled.

        Action required:
        1. Invoke the NSX CLI command `get dns-forwarders status` to verify
        if the DNS forwarder is in down state.
        2. Check /var/log/syslog to see if there are errors reported.
        3. Collect a support bundle and contact the NSX support team.
        "
    ::= { vmwNsxTDNSFeature 3 }

vmwNsxTDNSForwarderDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "DNS forwarder vmwNsxTDataCenterEntityId is running again.

        Action required:
        None, receipt of this notification indicates event cleared.
        "
    ::= { vmwNsxTDNSFeature 4 }

-- **********************************************************
-- EdgeHealth feature event notifications
-- **********************************************************

vmwNsxTEdgeHealthFeaturePrefix OBJECT-IDENTITY
    STATUS current
    DESCRIPTION
        "Notifications applicable to the EdgeHealth feature have this OID prefix."
    ::= { vmwNsxTDataCenterNotifications 2 }

vmwNsxTEdgeHealthFeature OBJECT-IDENTITY
    STATUS current
    DESCRIPTION
        "Sub-identifier added to ensure the next-to-last sub-identifier is zero
        for EdgeHealth feature notifications.
        "
    ::= { vmwNsxTEdgeHealthFeaturePrefix 0 }

vmwNsxTEdgeHealthEdgeCPUUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Edge node vmwNsxTDataCenterEntityId has reached
        vmwNsxTDataCenterSystemResourceUsage% which is at or above the high threshold
        value of vmwNsxTDataCenterSystemUsageThreshold%.

        Action required:
        Please review the configuration, running services and sizing of this Edge
        node. Consider adjusting the Edge appliance form factor size or rebalancing
        services to other Edge nodes for the applicable workload.
        "
    ::= { vmwNsxTEdgeHealthFeature 1 }

vmwNsxTEdgeHealthEdgeCPUUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Edge node vmwNsxTDataCenterEntityId has reached
        vmwNsxTDataCenterSystemResourceUsage% which is below the high threshold
        value of vmwNsxTDataCenterSystemUsageThreshold%.

        Action required:
        None, receipt of this notification indicates event cleared.
        "
    ::= { vmwNsxTEdgeHealthFeature 2 }

vmwNsxTEdgeHealthEdgeCPUUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Edge node vmwNsxTDataCenterEntityId has reached
        vmwNsxTDataCenterSystemResourceUsage% which is at or above the very high
        threshold value of vmwNsxTDataCenterSystemUsageThreshold%.

        Action required:
        Please review the configuration, running services and sizing of this Edge
        node. Consider adjusting the Edge appliance form factor size or rebalancing
        services to other Edge nodes for the applicable workload.
        "
    ::= { vmwNsxTEdgeHealthFeature 3 }

vmwNsxTEdgeHealthEdgeCPUUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Edge node vmwNsxTDataCenterEntityId has reached
        vmwNsxTDataCenterSystemResourceUsage% which is below the very high threshold
        value of vmwNsxTDataCenterSystemUsageThreshold%.

        Action required:
        None, receipt of this notification indicates event cleared.
        "
    ::= { vmwNsxTEdgeHealthFeature 4 }

vmwNsxTEdgeHealthEdgeDatapathConfigurationFailure NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Failed to enable the datapath on the Edge node after three attempts.

        Action required:
        Ensure the Edge node's connectivity to the Manager node is healthy.  From
        the Edge node's NSX CLI, invoke the command `get services` to check the
        health of services. If the dataplane service is stopped, invoke the
        command `start service dataplane` to start it.
        "
    ::= { vmwNsxTEdgeHealthFeature 21 }

vmwNsxTEdgeHealthEdgeDatapathConfigurationFailureClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Datapath on the Edge node has been successfully enabled.

        Action required:
        None, receipt of this notification indicates event cleared.
        "
    ::= { vmwNsxTEdgeHealthFeature 22 }

vmwNsxTEdgeHealthEdgeDatapathCPUHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDatapathResourceUsage
    }
    STATUS current
    DESCRIPTION
        "The datapath CPU usage on Edge node vmwNsxTDataCenterEntityId has reached
        vmwNsxTDataCenterDatapathResourceUsage% which is at or above the high
        threshold for at least two minutes.

        Action required:
        Review the CPU statistics on the Edge node by invoking the NSX CLI command
        `get dataplane cpu stats` to show packet rates per CPU core.  Higher CPU
        usage is expected with higher packet rates. Consider increasing the Edge
        appliance form factor size and rebalancing services on this Edge node to
        other Edge nodes in the same cluster or other Edge clusters.
        "
    ::= { vmwNsxTEdgeHealthFeature 17 }

vmwNsxTEdgeHealthEdgeDatapathCPUHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The CPU usage on Edge node vmwNsxTDataCenterEntityId has reached below the
        high threshold.

        Action required:
        None, receipt of this notification indicates event cleared.
        "
    ::= { vmwNsxTEdgeHealthFeature 18 }

vmwNsxTEdgeHealthEdgeDatapathCPUVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDatapathResourceUsage
    }
    STATUS current
    DESCRIPTION
        "The datapath CPU usage on Edge node vmwNsxTDataCenterEntityId has reached
        vmwNsxTDataCenterDatapathResourceUsage% which is at or above the very high
        threshold for at least two minutes.

        Action required:
        Review the CPU statistics on the Edge node by invoking the NSX CLI command
        `get dataplane cpu stats` to show packet rates per CPU core.  Higher CPU
        usage is expected with higher packet rates. Consider increasing the Edge
        appliance form factor size and rebalancing services on this Edge node to
        other Edge nodes in the same cluster or other Edge clusters.
        "
    ::= { vmwNsxTEdgeHealthFeature 19 }

vmwNsxTEdgeHealthEdgeDatapathCPUVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The CPU usage on Edge node vmwNsxTDataCenterEntityId has reached below the
        very high threshold.

        Action required:
        None, receipt of this notification indicates event cleared.
        "
    ::= { vmwNsxTEdgeHealthFeature 20 }

vmwNsxTEdgeHealthEdgeDatapathCryptodrvDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Edge node crypto driver is down.

        Action required:
        Upgrade the Edge node as needed.
        "
    ::= { vmwNsxTEdgeHealthFeature 23 }

vmwNsxTEdgeHealthEdgeDatapathCryptodrvDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Edge node crypto driver is up.

        Action required:
        None, receipt of this notification indicates event cleared.
        "
    ::= { vmwNsxTEdgeHealthFeature 24 }

vmwNsxTEdgeHealthEdgeDatapathMempoolHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterMempoolName,
        vmwNsxTDataCenterSystemResourceUsage,
        vmwNsxTDataCenterSystemUsageThreshold
    }
    STATUS current
    DESCRIPTION
        "The datapath mempool usage for vmwNsxTDataCenterMempoolName on Edge node
        vmwNsxTDataCenterEntityId has reached vmwNsxTDataCenterSystemResourceUsage% which
        is at or above the high threshold value of vmwNsxTDataCenterSystemUsageThreshold%.

        Action required:
        Log in as the root user and invoke the command
        `edge-appctl -t /var/run/vmware/edge/dpd.ctl mempool/show` and
        `edge-appctl -t /var/run/vmware/edge/dpd.ctl memory/show malloc_heap` to
        check DPDK memory usage.
        "
    ::= { vmwNsxTEdgeHealthFeature 25 }

vmwNsxTEdgeHealthEdgeDatapathMempoolHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterMempoolName,
        vmwNsxTDataCenterSystemResourceUsage,
        vmwNsxTDataCenterSystemUsageThreshold
    }
    STATUS current
    DESCRIPTION
        "The datapath mempool usage for vmwNsxTDataCenterMempoolName on Edge node
        vmwNsxTDataCenterEntityId has reached vmwNsxTDataCenterSystemResourceUsage% which
        is below the high threshold value of vmwNsxTDataCenterSystemUsageThreshold%.

        Action required:
        None, receipt of this notification indicates event cleared.
        "
    ::= { vmwNsxTEdgeHealthFeature 26 }

vmwNsxTEdgeHealthEdgeDiskUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Edge node disk partition vmwNsxTDataCenterDiskPartitionName
        has reached vmwNsxTDataCenterSystemResourceUsage% which is at or above
        the high threshold value of vmwNsxTDataCenterSystemUsageThreshold%.

        Action required:
        Examine the partition with high usage and see if there are any
        unexpected large files that can be removed.
        "
    ::= { vmwNsxTEdgeHealthFeature 9 }

vmwNsxTEdgeHealthEdgeDiskUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Edge node disk partition vmwNsxTDataCenterDiskPartitionName
        has reached vmwNsxTDataCenterSystemResourceUsage% which is below the high
        threshold value of vmwNsxTDataCenterSystemUsageThreshold%.

        Action required:
        None, receipt of this notification indicates event cleared.
        "
    ::= { vmwNsxTEdgeHealthFeature 10 }

vmwNsxTEdgeHealthEdgeDiskUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Edge node disk partition vmwNsxTDataCenterDiskPartitionName
        has reached vmwNsxTDataCenterSystemResourceUsage% which is at or above
        the very high threshold value of vmwNsxTDataCenterSystemUsageThreshold%.

        Action required:
        Examine the partition with high usage and see if there are any
        unexpected large files that can be removed.
        "
    ::= { vmwNsxTEdgeHealthFeature 11 }

vmwNsxTEdgeHealthEdgeDiskUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Edge node disk partition vmwNsxTDataCenterDiskPartitionName
        has reached vmwNsxTDataCenterSystemResourceUsage% which is below the
        very high threshold value of vmwNsxTDataCenterSystemUsageThreshold%.

        Action required:
        None, receipt of this notification indicates event cleared.
        "
    ::= { vmwNsxTEdgeHealthFeature 12 }

vmwNsxTEdgeHealthEdgeGlobalARPTableUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDatapathResourceUsage
    }
    STATUS current
    DESCRIPTION
        "Global ARP table usage on Edge node vmwNsxTDataCenterEntityId has reached
        vmwNsxTDataCenterDatapathResourceUsage% which is above the high threshold
        for over two minutes.

        Action required:
        Log in as the root user and invoke the command
        `edge-appctl -t /var/run/vmware/edge/dpd.ctl neigh/show` and check
        if neigh cache usage is normal. If it is normal, invoke the command
        `edge-appctl -t /var/run/vmware/edge/dpd.ctl neigh/set_param max_entries`
        to increase the ARP table size.
        "
    ::= { vmwNsxTEdgeHealthFeature 27 }

vmwNsxTEdgeHealthEdgeGlobalARPTableUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Global arp table usage on Edge node vmwNsxTDataCenterEntityId has reached
        below the high threshold.

        Action required:
        None, receipt of this notification indicates event cleared.
        "
    ::= { vmwNsxTEdgeHealthFeature 28 }

vmwNsxTEdgeHealthEdgeMemoryUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Edge node vmwNsxTDataCenterEntityId has reached
        vmwNsxTDataCenterSystemResourceUsage% which is at or above the high
        threshold value of vmwNsxTDataCenterSystemUsageThreshold%.

        Action required:
        Please review the configuration, running services and sizing of this Edge
        node. Consider adjusting the Edge appliance form factor size or rebalancing
        services to other Edge nodes for the applicable workload.
        "
    ::= { vmwNsxTEdgeHealthFeature 5 }

vmwNsxTEdgeHealthEdgeMemoryUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Edge node vmwNsxTDataCenterEntityId has reached
        vmwNsxTDataCenterSystemResourceUsage% which is below the high threshold
        value of vmwNsxTDataCenterSystemUsageThreshold%.

        Action required:
        None, receipt of this notification indicates event cleared.
        "
    ::= { vmwNsxTEdgeHealthFeature 6 }

vmwNsxTEdgeHealthEdgeMemoryUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Edge node vmwNsxTDataCenterEntityId has reached
        vmwNsxTDataCenterSystemResourceUsage% which is at or above the very
        high threshold value of vmwNsxTDataCenterSystemUsageThreshold%.

        Action required:
        Please review the configuration, running services and sizing of this Edge
        node. Consider adjusting the Edge appliance form factor size or rebalancing
        services to other Edge nodes for the applicable workload.
        "
    ::= { vmwNsxTEdgeHealthFeature 7 }

vmwNsxTEdgeHealthEdgeMemoryUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Edge node vmwNsxTDataCenterEntityId has reached
        vmwNsxTDataCenterSystemResourceUsage% which is below the very high
        threshold value of vmwNsxTDataCenterSystemUsageThreshold%.

        Action required:
        None, receipt of this notification indicates event cleared.
        "
    ::= { vmwNsxTEdgeHealthFeature 8 }

vmwNsxTEdgeHealthEdgeNICLinkStatusDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeNICName
    }
    STATUS current
    DESCRIPTION
        "Edge node NIC vmwNsxTDataCenterEdgeNICName link is down.

        Action required:
        On the Edge node confirm if the NIC link is physically down by invoking
        the NSX CLI command `get interfaces`. If it is down, verify the cable
        connection.
        "
    ::= { vmwNsxTEdgeHealthFeature 29 }

vmwNsxTEdgeHealthEdgeNICLinkStatusDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeNICName
    }
    STATUS current
    DESCRIPTION
        "Edge node NIC vmwNsxTDataCenterEdgeNICName link is up.

        Action required:
        None, receipt of this notification indicates event cleared.
        "
    ::= { vmwNsxTEdgeHealthFeature 30 }

vmwNsxTEdgeHealthEdgeNICOutOfReceiveBuffer NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeNICName,
        vmwNsxTDataCenterRxRingBufferOverflowPercentage
    }
    STATUS current
    DESCRIPTION
        "Edge NIC vmwNsxTDataCenterEdgeNICName receive ring buffer has overflowed by
        vmwNsxTDataCenterRxRingBufferOverflowPercentage% on Edge node vmwNsxTDataCenterEntityId.

        Action required:
        Invoke the NSX CLI command `get dataplane`, and check
        1. if pps and cpu usage is high and check rx ring size using
        `get dataplane ring-size rx`.
        2. If pps and cpu is high and rx ring size is low, invoke
        `set dataplane ring-size rx <ring-size>` i,e set <ring-size>
        to a high value to accommodate incoming packets.
        3. If the above condition is not satisfied, i.e. ring size is
        high and yet CPU usage is high, then this could be due to
        dataplane processing overhead delay.
        "
    ::= { vmwNsxTEdgeHealthFeature 31 }

vmwNsxTEdgeHealthEdgeNICOutOfReceiveBufferClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeNICName
    }
    STATUS current
    DESCRIPTION
        "Edge NIC vmwNsxTDataCenterEdgeNICName receive ring buffer usage on Edge node
        vmwNsxTDataCenterEntityId is no longer overflowing.

        Action required:
        None, receipt of this notification indicates event cleared.
        "
    ::= { vmwNsxTEdgeHealthFeature 32 }

vmwNsxTEdgeHealthEdgeNICOutOfTransmitBuffer NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeNICName,
        vmwNsxTDataCenterTxRingBufferOverflowPercentage
    }
    STATUS current
    DESCRIPTION
        "Edge NIC vmwNsxTDataCenterEdgeNICName transmit ring buffer has overflowed by
        vmwNsxTDataCenterTxRingBufferOverflowPercentage% on Edge node vmwNsxTDataCenterEntityId.

        Action required:
        Invoke the NSX CLI command `get dataplane`, and check
        1. if pps and cpu usage high and check tx ring size using
        `get dataplane ring-size tx`.
        2. If pps and cpu is high and tx ring size is low, invoke
        `set dataplane ring-size tx <ring-size>`, i.e. set <ring-size>
        to a high value to accommodate outgoing packets.
        3. If the above condition is not satisfied, i.e. ring size is
        high and CPU usage is low/nominal, then it could be due to
        the hypervisor's corresponding transmit ring size being low.
        "
    ::= { vmwNsxTEdgeHealthFeature 33 }

vmwNsxTEdgeHealthEdgeNICOutOfTransmitBufferClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeNICName
    }
    STATUS current
    DESCRIPTION
        "Edge NIC vmwNsxTDataCenterEdgeNICName transmit ring buffer usage on Edge node
        vmwNsxTDataCenterEntityId is no longer overflowing.

        Action required:
        None, receipt of this notification indicates event cleared.
        "
    ::= { vmwNsxTEdgeHealthFeature 34 }

vmwNsxTEdgeHealthStorageError NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName
    }
    STATUS current
    DESCRIPTION
        "The following disk partitions on the Edge node are in
        read-only mode: vmwNsxTDataCenterDiskPartitionName

        Action required:
        Examine the read-only partition to see if reboot resolves the issue
        or the disk needs to be replaced. Refer to KB article
        https://kb.vmware.com/s/article/2146870.
        "
    ::= { vmwNsxTEdgeHealthFeature 37 }

vmwNsxTEdgeHealthStorageErrorClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName
    }
    STATUS current
    DESCRIPTION
        "The following disk partitions on the Edge node have recovered from
        read-only mode: vmwNsxTDataCenterDiskPartitionName

        Action required:
        None, receipt of this notification indicates event cleared.
        "
    ::= { vmwNsxTEdgeHealthFeature 38 }

-- **********************************************************
-- EndpointProtection feature event notifications
-- **********************************************************

vmwNsxTEndpointProtectionFeaturePrefix OBJECT-IDENTITY
    STATUS current
    DESCRIPTION
        "Notifications applicable to the EndpointProtection feature have this OID prefix."
    ::= { vmwNsxTDataCenterNotifications 13 }

vmwNsxTEndpointProtectionFeature OBJECT-IDENTITY
    STATUS current
    DESCRIPTION
        "Sub-identifier added to ensure the next-to-last sub-identifier is zero
        for EndpointProtection feature notifications.
        "
    ::= { vmwNsxTEndpointProtectionFeaturePrefix 0 }

vmwNsxTEndpointProtectionEAMStatusDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "ESX Agent Manager (EAM) service on compute manager vmwNsxTDataCenterEntityId is down.

        Action required:
        Start the ESX Agent Manager (EAM) service. SSH into vCenter and invoke
        the command `service vmware-eam start`.
        "
    ::= { vmwNsxTEndpointProtectionFeature 1 }

vmwNsxTEndpointProtectionEAMStatusDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "ESX Agent Manager (EAM) service on compute manager vmwNsxTDataCenterEntityId is either up
        or compute manager vmwNsxTDataCenterEntityId has been removed.

        Action required:
        None, receipt of this notification indicates event cleared.
        "
    ::= { vmwNsxTEndpointProtectionFeature 2 }

vmwNsxTEndpointProtectionPartnerChannelDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The connection between host module and Partner SVM vmwNsxTDataCenterEntityId
        is down.

        Action required:
        Refer to https://kb.vmware.com/s/article/2148821 and make sure
        that Partner SVM vmwNsxTDataCenterEntityId is re-connected to the host module.
        "
    ::= { vmwNsxTEndpointProtectionFeature 3 }

vmwNsxTEndpointProtectionPartnerChannelDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The connection between host module and Partner SVM vmwNsxTDataCenterEntityId
        is up.

        Action required:
        None, receipt of this notification indicates event cleared.
        "
    ::= { vmwNsxTEndpointProtectionFeature 4 }

-- **********************************************************
-- Federation feature event notifications
-- **********************************************************

vmwNsxTFederationFeaturePrefix OBJECT-IDENTITY
    STATUS current
    DESCRIPTION
        "Notifications applicable to the Federation feature have this OID prefix."
    ::= { vmwNsxTDataCenterNotifications 32 }

vmwNsxTFederationFeature OBJECT-IDENTITY
    STATUS current
    DESCRIPTION
        "Sub-identifier added to ensure the next-to-last sub-identifier is zero
        for Federation feature notifications.
        "
    ::= { vmwNsxTFederationFeaturePrefix 0 }

vmwNsxTFederationLmToLmSynchronizationError NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSiteName,
        vmwNsxTDataCenterSiteId,
        vmwNsxTDataCenterRemoteSiteName,
        vmwNsxTDataCenterRemoteSiteId
    }
    STATUS current
    DESCRIPTION
        "The synchronization between vmwNsxTDataCenterSiteName(vmwNsxTDataCenterSiteId) and vmwNsxTDataCenterRemoteSiteName(vmwNsxTDataCenterRemoteSiteId)
        failed for more than 5 minutes.

        Action required:
        1. Invoke the NSX CLI command `get site-replicator remote-sites` to get connection
           state between the remote locations. If a remote location is connected but not synchronized,
           it is possible that the location is still in the process of master resolution. In
           this case, wait for around 10 seconds and try invoking the CLI again to
           check for the state of the remote location. If a location is disconnected, try the next
           step.
        2. Check the connectivity from Local Manager (LM) in location vmwNsxTDataCenterSiteName(vmwNsxTDataCenterSiteId) to the LMs
           in location vmwNsxTDataCenterRemoteSiteName(vmwNsxTDataCenterRemoteSiteId) via ping. If they are not pingable,
           check for flakiness in WAN connectivity. If there are no physical network
           connectivity issues, try the next step.
        3. Check the /var/log/cloudnet/nsx-ccp.log file on the Manager nodes in the local cluster in
           location vmwNsxTDataCenterSiteName(vmwNsxTDataCenterSiteId) that triggered the alarm to see if there are any cross-site
           communication errors. In addition, also look for errors being logged by the
           nsx-appl-proxy subcomponent within /var/log/syslog.
        "
    ::= { vmwNsxTFederationFeature 3 }

vmwNsxTFederationLmToLmSynchronizationErrorClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSiteName,
        vmwNsxTDataCenterSiteId,
        vmwNsxTDataCenterRemoteSiteName,
        vmwNsxTDataCenterRemoteSiteId
    }
    STATUS current
    DESCRIPTION
        "Remote sites vmwNsxTDataCenterSiteName(vmwNsxTDataCenterSiteId) and vmwNsxTDataCenterRemoteSiteName(vmwNsxTDataCenterRemoteSiteId) are now synchronized.

        Action required:
        None, receipt of this notification indicates event cleared.
        "
    ::= { vmwNsxTFederationFeature 4 }

vmwNsxTFederationLmToLmSynchronizationWarning NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSiteName,
        vmwNsxTDataCenterSiteId,
        vmwNsxTDataCenterRemoteSiteName,
        vmwNsxTDataCenterRemoteSiteId
    }
    STATUS current
    DESCRIPTION
        "The synchronization between vmwNsxTDataCenterSiteName(vmwNsxTDataCenterSiteId) and vmwNsxTDataCenterRemoteSiteName(vmwNsxTDataCenterRemoteSiteId) failed.

        Action required:
        1. Invoke the NSX CLI command `get site-replicator remote-sites` to get connection
           state between the remote locations. If a remote location is connected but not synchronized,
           it is possible that the location is still in the process of master resolution. In
           this case, wait for around 10 seconds and try invoking the CLI again to
           check for the state of the remote location. If a location is disconnected, try the next
           step.
        2. Check the connectivity from Local Manager (LM) in location vmwNsxTDataCenterSiteName(vmwNsxTDataCenterSiteId) to the LMs
           in location vmwNsxTDataCenterRemoteSiteName(vmwNsxTDataCenterRemoteSiteId) via ping. If they are not pingable,
           check for flakiness in WAN connectivity. If there are no physical network
           connectivity issues, try the next step.
        3. Check the /var/log/cloudnet/nsx-ccp.log file on the Manager nodes in the local cluster in
           location vmwNsxTDataCenterSiteName(vmwNsxTDataCenterSiteId) that triggered the alarm to see if there are any cross-site
           communication errors. In addition, also look for errors being logged by the
           nsx-appl-proxy subcomponent within /var/log/syslog.
        "
    ::= { vmwNsxTFederationFeature 5 }

vmwNsxTFederationLmToLmSynchronizationWarningClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSiteName,
        vmwNsxTDataCenterSiteId,
        vmwNsxTDataCenterRemoteSiteName,
        vmwNsxTDataCenterRemoteSiteId
    }
    STATUS current
    DESCRIPTION
        "Remote locations vmwNsxTDataCenterSiteName(vmwNsxTDataCenterSiteId) and vmwNsxTDataCenterRemoteSiteName(vmwNsxTDataCenterRemoteSiteId) are now synchronized.

        Action required:
        None, receipt of this notification indicates event cleared.
        "
    ::= { vmwNsxTFederationFeature 6 }

vmwNsxTFederationRtepBGPDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterBGPSourceIP,
        vmwNsxTDataCenterRemoteSiteName,
        vmwNsxTDataCenterBGPNeighborIP,
        vmwNsxTDataCenterFailureReason
    }
    STATUS current
    DESCRIPTION
        "RTEP (Remote Tunnel Endpoint) BGP session from source IP vmwNsxTDataCenterBGPSourceIP
        to remote location vmwNsxTDataCenterRemoteSiteName neighbor IP vmwNsxTDataCenterBGPNeighborIP is down.
        Reason: vmwNsxTDataCenterFailureReason.

        Action required:
        1. Invoke the NSX CLI command 'get logical-routers' on affected edge node.
        2. Switch to remote tunnel vrf context.
        3. Invoke the NSX CLI command 'get bgp neighbor summary' to check the BGP neighbor status.
        4. Check RTEP connectivity and see /var/log/syslog for any errors related to BGP.
        "
    ::= { vmwNsxTFederationFeature 1 }

vmwNsxTFederationRtepBGPDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterBGPSourceIP,
        vmwNsxTDataCenterRemoteSiteName,
        vmwNsxTDataCenterBGPNeighborIP
    }
    STATUS current
    DESCRIPTION
        "RTEP (Remote Tunnel Endpoint) BGP session from source IP vmwNsxTDataCenterBGPSourceIP
        to remote location vmwNsxTDataCenterRemoteSiteName neighbor IP vmwNsxTDataCenterBGPNeighborIP is established.

        Action required:
        None, receipt of this notification indicates event cleared.
        "
    ::= { vmwNsxTFederationFeature 2 }

-- **********************************************************
-- HighAvailability feature event notifications
-- **********************************************************

vmwNsxTHighAvailabilityFeaturePrefix OBJECT-IDENTITY
    STATUS current
    DESCRIPTION
        "Notifications applicable to the HighAvailability feature have this OID prefix."
    ::= { vmwNsxTDataCenterNotifications 21 }

vmwNsxTHighAvailabilityFeature OBJECT-IDENTITY
    STATUS current
    DESCRIPTION
        "Sub-identifier added to ensure the next-to-last sub-identifier is zero
        for HighAvailability feature notifications.
        "
    ::= { vmwNsxTHighAvailabilityFeaturePrefix 0 }

vmwNsxTHighAvailabilityTier0GatewayFailover NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterPreviousGatewayState,
        vmwNsxTDataCenterCurrentGatewayState
    }
    STATUS current
    DESCRIPTION
        "The tier0 gateway vmwNsxTDataCenterEntityId failover from vmwNsxTDataCenterPreviousGatewayState
        to vmwNsxTDataCenterCurrentGatewayState.

        Action required:
        Invoke the NSX CLI command `get logical-routers` to identify the tier0
        vrf ID. Switch to the vrf context by invoking `vrf <vrf-id>` then invoke
        `get high-availability status` to determine the service that is down.
        "
    ::= { vmwNsxTHighAvailabilityFeature 9 }

vmwNsxTHighAvailabilityTier0GatewayFailoverClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The tier0 gateway vmwNsxTDataCenterEntityId is now up.

        Action required:
        None, receipt of this notification indicates event cleared.
        "
    ::= { vmwNsxTHighAvailabilityFeature 10 }

vmwNsxTHighAvailabilityTier1GatewayFailover NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterPreviousGatewayState,
        vmwNsxTDataCenterCurrentGatewayState
    }
    STATUS current
    DESCRIPTION
        "The tier1 gateway vmwNsxTDataCenterEntityId failover from vmwNsxTDataCenterPreviousGatewayState
        to vmwNsxTDataCenterCurrentGatewayState.

        Action required:
        Invoke the NSX CLI command `get logical-routers` to identify the tier1
        vrf ID. Switch to the vrf context by invoking `vrf <vrf-id>` then invoke
        `get high-availability status` to determine the service that is down.
        "
    ::= { vmwNsxTHighAvailabilityFeature 11 }

vmwNsxTHighAvailabilityTier1GatewayFailoverClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The tier1 gateway vmwNsxTDataCenterEntityId is now up.

        Action required:
        None, receipt of this notification indicates event cleared.
        "
    ::= { vmwNsxTHighAvailabilityFeature 12 }

-- **********************************************************
-- InfrastructureCommunication feature event notifications
-- **********************************************************

vmwNsxTInfrastructureCommunicationFeaturePrefix OBJECT-IDENTITY
    STATUS current
    DESCRIPTION
        "Notifications applicable to the InfrastructureCommunication feature have this OID prefix."
    ::= { vmwNsxTDataCenterNotifications 7 }

vmwNsxTInfrastructureCommunicationFeature OBJECT-IDENTITY
    STATUS current
    DESCRIPTION
        "Sub-identifier added to ensure the next-to-last sub-identifier is zero
        for InfrastructureCommunication feature notifications.
        "
    ::= { vmwNsxTInfrastructureCommunicationFeaturePrefix 0 }

vmwNsxTInfrastructureCommunicationEdgeTunnelsDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The overall tunnel status of Edge node vmwNsxTDataCenterEntityId is down.

        Action required:
        Invoke the NSX CLI command `get tunnel-ports` to get all tunnel ports,
        then check each tunnel's stats by invoking NSX CLI command
        `get tunnel-port <UUID> stats` to check if there are any drops. Also
        check /var/log/syslog if there are tunnel related errors.
        "
    ::= { vmwNsxTInfrastructureCommunicationFeature 17 }

vmwNsxTInfrastructureCommunicationEdgeTunnelsDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The tunnels of Edge node vmwNsxTDataCenterEntityId have been restored.

        Action required:
        None, receipt of this notification indicates event cleared.
        "
    ::= { vmwNsxTInfrastructureCommunicationFeature 18 }

-- **********************************************************
-- InfrastructureService feature event notifications
-- **********************************************************

vmwNsxTInfrastructureServiceFeaturePrefix OBJECT-IDENTITY
    STATUS current
    DESCRIPTION
        "Notifications applicable to the InfrastructureService feature have this OID prefix."
    ::= { vmwNsxTDataCenterNotifications 19 }

vmwNsxTInfrastructureServiceFeature OBJECT-IDENTITY
    STATUS current
    DESCRIPTION
        "Sub-identifier added to ensure the next-to-last sub-identifier is zero
        for InfrastructureService feature notifications.
        "
    ::= { vmwNsxTInfrastructureServiceFeaturePrefix 0 }

vmwNsxTInfrastructureServiceEdgeServiceStatusChanged NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeServiceName,
        vmwNsxTDataCenterPreviousServiceState,
        vmwNsxTDataCenterCurrentServiceState
    }
    STATUS current
    DESCRIPTION
        "The service vmwNsxTDataCenterEdgeServiceName changed from vmwNsxTDataCenterPreviousServiceState
        to vmwNsxTDataCenterCurrentServiceState.

        Action required:
        On the Edge node, verify the service hasn't exited due to an error by
        looking for core files in the /var/log/core directory. In addition,
        invoke the NSX CLI command `get services` to confirm whether the service
        is stopped. If so, invoke `start service <service-name>` to restart the
        service.
        "
    ::= { vmwNsxTInfrastructureServiceFeature 1 }

vmwNsxTInfrastructureServiceEdgeServiceStatusChangedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeServiceName,
        vmwNsxTDataCenterPreviousServiceState,
        vmwNsxTDataCenterCurrentServiceState
    }
    STATUS current
    DESCRIPTION
        "The service vmwNsxTDataCenterEdgeServiceName changed from vmwNsxTDataCenterPreviousServiceState
        to vmwNsxTDataCenterCurrentServiceState.

        Action required:
        None, receipt of this notification indicates event cleared.
        "
    ::= { vmwNsxTInfrastructureServiceFeature 2 }

vmwNsxTInfrastructureServiceEdgeServiceStatusDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeServiceName
    }
    STATUS current
    DESCRIPTION
        "The service vmwNsxTDataCenterEdgeServiceName is down for at least one minute.

        Action required:
        On the Edge node, verify the service hasn't exited due to an error by
        looking for core files in the /var/log/core directory. In addition,
        invoke the NSX CLI command `get services` to confirm whether the service
        is stopped. If so, invoke `start service <service-name>` to restart the
        service.
        "
    ::= { vmwNsxTInfrastructureServiceFeature 3 }

vmwNsxTInfrastructureServiceEdgeServiceStatusDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterEdgeServiceName
    }
    STATUS current
    DESCRIPTION
        "The service vmwNsxTDataCenterEdgeServiceName is up.

        Action required:
        None, receipt of this notification indicates event cleared.
        "
    ::= { vmwNsxTInfrastructureServiceFeature 4 }

-- **********************************************************
-- IntelligenceCommunication feature event notifications
-- **********************************************************

vmwNsxTIntelligenceCommunicationFeaturePrefix OBJECT-IDENTITY
    STATUS current
    DESCRIPTION
        "Notifications applicable to the IntelligenceCommunication feature have this OID prefix."
    ::= { vmwNsxTDataCenterNotifications 9 }

vmwNsxTIntelligenceCommunicationFeature OBJECT-IDENTITY
    STATUS current
    DESCRIPTION
        "Sub-identifier added to ensure the next-to-last sub-identifier is zero
        for IntelligenceCommunication feature notifications.
        "
    ::= { vmwNsxTIntelligenceCommunicationFeaturePrefix 0 }

vmwNsxTIntelligenceCommunicationTNFlowExporterDisconnected NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The flow exporter on Transport node vmwNsxTDataCenterEntityId is disconnected from
        the Intelligence node's messaging broker. Data collection is affected.

        Action required:
        Restart the messaging service if it is not running in the Intelligence
        node. Resolve the network connection failure between the Transport node
        flow exporter and the Intelligence node.
        "
    ::= { vmwNsxTIntelligenceCommunicationFeature 7 }

vmwNsxTIntelligenceCommunicationTNFlowExporterDisconnectedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The flow exporter on Transport node vmwNsxTDataCenterEntityId has reconnected to
        the Intelligence node's messaging broker.

        Action required:
        None, receipt of this notification indicates event cleared.
        "
    ::= { vmwNsxTIntelligenceCommunicationFeature 8 }

-- **********************************************************
-- IntelligenceHealth feature event notifications
-- **********************************************************

vmwNsxTIntelligenceHealthFeaturePrefix OBJECT-IDENTITY
    STATUS current
    DESCRIPTION
        "Notifications applicable to the IntelligenceHealth feature have this OID prefix."
    ::= { vmwNsxTDataCenterNotifications 6 }

vmwNsxTIntelligenceHealthFeature OBJECT-IDENTITY
    STATUS current
    DESCRIPTION
        "Sub-identifier added to ensure the next-to-last sub-identifier is zero
        for IntelligenceHealth feature notifications.
        "
    ::= { vmwNsxTIntelligenceHealthFeaturePrefix 0 }

vmwNsxTIntelligenceHealthCPUUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The CPU usage on Intelligence node vmwNsxTDataCenterIntelligenceNodeId
        is above the high threshold value of vmwNsxTDataCenterSystemUsageThreshold%.

        Action required:
        Use the top command to check which processes have the most CPU usages, and
        then check /var/log/syslog and these processes' local logs to see if there
        are any outstanding errors to be resolved.
        "
    ::= { vmwNsxTIntelligenceHealthFeature 41 }

vmwNsxTIntelligenceHealthCPUUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The CPU usage on Intelligence node vmwNsxTDataCenterIntelligenceNodeId
        is below the high threshold value of vmwNsxTDataCenterSystemUsageThreshold%.

        Action required:
        None, receipt of this notification indicates event cleared.
        "
    ::= { vmwNsxTIntelligenceHealthFeature 42 }

vmwNsxTIntelligenceHealthCPUUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The CPU usage on Intelligence node vmwNsxTDataCenterIntelligenceNodeId
        is above the very high threshold value of vmwNsxTDataCenterSystemUsageThreshold%.

        Action required:
        Use the top command to check which processes have the most CPU usages, and
        then check /var/log/syslog and these processes' local logs to see if there
        are any outstanding errors to be resolved.
        "
    ::= { vmwNsxTIntelligenceHealthFeature 43 }

vmwNsxTIntelligenceHealthCPUUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The CPU usage on Intelligence node vmwNsxTDataCenterIntelligenceNodeId
        is below the very high threshold value of vmwNsxTDataCenterSystemUsageThreshold%.

        Action required:
        None, receipt of this notification indicates event cleared.
        "
    ::= { vmwNsxTIntelligenceHealthFeature 44 }

vmwNsxTIntelligenceHealthDataDiskPartitionUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The disk usage of disk partition /data on Intelligence node
        vmwNsxTDataCenterIntelligenceNodeId is above the high threshold value
        of vmwNsxTDataCenterSystemUsageThreshold%.

        Action required:
        Stop NSX intelligence data collection until the disk usage is below
        the threshold. Examine disk partition /data and see if there are any
        unexpected large files that can be removed.
        "
    ::= { vmwNsxTIntelligenceHealthFeature 45 }

vmwNsxTIntelligenceHealthDataDiskPartitionUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The disk usage of disk partition /data on Intelligence node
        vmwNsxTDataCenterIntelligenceNodeId is below the high threshold value
        of vmwNsxTDataCenterSystemUsageThreshold%.

        Action required:
        None, receipt of this notification indicates event cleared.
        "
    ::= { vmwNsxTIntelligenceHealthFeature 46 }

vmwNsxTIntelligenceHealthDataDiskPartitionUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The disk usage of disk partition /data on Intelligence node
        vmwNsxTDataCenterIntelligenceNodeId is above the very high threshold value
        of vmwNsxTDataCenterSystemUsageThreshold%.

        Action required:
        Stop NSX intelligence data collection until the disk usage is below
        the threshold. In the NSX UI, navigate to System | Appliances | NSX
        Intelligence Appliance. Then click ACTONS, Stop Collecting Data.
        "
    ::= { vmwNsxTIntelligenceHealthFeature 47 }

vmwNsxTIntelligenceHealthDataDiskPartitionUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The disk usage of disk partition /data on Intelligence node
        vmwNsxTDataCenterIntelligenceNodeId is below the very high threshold value
        of vmwNsxTDataCenterSystemUsageThreshold%.

        Action required:
        None, receipt of this notification indicates event cleared.
        "
    ::= { vmwNsxTIntelligenceHealthFeature 48 }

vmwNsxTIntelligenceHealthDiskUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterIntelligenceNodeId,
        vmwNsxTDataCenterSystemUsageThreshold
    }
    STATUS current
    DESCRIPTION
        "The disk usage of disk partition vmwNsxTDataCenterDiskPartitionName on
        Intelligence node vmwNsxTDataCenterIntelligenceNodeId is above
        the high threshold value of vmwNsxTDataCenterSystemUsageThreshold%.

        Action required:
        Examine disk partition vmwNsxTDataCenterDiskPartitionName and see if there are any
        unexpected large files that can be removed.
        "
    ::= { vmwNsxTIntelligenceHealthFeature 49 }

vmwNsxTIntelligenceHealthDiskUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterIntelligenceNodeId,
        vmwNsxTDataCenterSystemUsageThreshold
    }
    STATUS current
    DESCRIPTION
        "The disk usage of disk partition vmwNsxTDataCenterDiskPartitionName on
        Intelligence node vmwNsxTDataCenterIntelligenceNodeId is below
        the high threshold value of vmwNsxTDataCenterSystemUsageThreshold%.

        Action required:
        None, receipt of this notification indicates event cleared.
        "
    ::= { vmwNsxTIntelligenceHealthFeature 50 }

vmwNsxTIntelligenceHealthDiskUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterIntelligenceNodeId,
        vmwNsxTDataCenterSystemUsageThreshold
    }
    STATUS current
    DESCRIPTION
        "The disk usage of disk partition vmwNsxTDataCenterDiskPartitionName on
        Intelligence node vmwNsxTDataCenterIntelligenceNodeId is above
        the very high threshold value of vmwNsxTDataCenterSystemUsageThreshold%.

        Action required:
        Examine disk partition vmwNsxTDataCenterDiskPartitionName and see if there are any
        unexpected large files that can be removed.
        "
    ::= { vmwNsxTIntelligenceHealthFeature 51 }

vmwNsxTIntelligenceHealthDiskUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterIntelligenceNodeId,
        vmwNsxTDataCenterSystemUsageThreshold
    }
    STATUS current
    DESCRIPTION
        "The disk usage of disk partition vmwNsxTDataCenterDiskPartitionName on
        Intelligence node vmwNsxTDataCenterIntelligenceNodeId is below
        the very high threshold value of vmwNsxTDataCenterSystemUsageThreshold%.

        Action required:
        None, receipt of this notification indicates event cleared.
        "
    ::= { vmwNsxTIntelligenceHealthFeature 52 }

vmwNsxTIntelligenceHealthMemoryUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The memory usage on Intelligence node vmwNsxTDataCenterIntelligenceNodeId
        is above the high threshold value of vmwNsxTDataCenterSystemUsageThreshold%.

        Action required:
        Use the top command to check which processes have the most memory usages,
        and then check /var/log/syslog and these processes' local logs to see if
        there are any outstanding errors to be resolved.
        "
    ::= { vmwNsxTIntelligenceHealthFeature 53 }

vmwNsxTIntelligenceHealthMemoryUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The memory usage on Intelligence node vmwNsxTDataCenterIntelligenceNodeId
        is below the high threshold value of vmwNsxTDataCenterSystemUsageThreshold%.

        Action required:
        None, receipt of this notification indicates event cleared.
        "
    ::= { vmwNsxTIntelligenceHealthFeature 54 }

vmwNsxTIntelligenceHealthMemoryUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The memory usage on Intelligence node vmwNsxTDataCenterIntelligenceNodeId
        is above the very high threshold value of vmwNsxTDataCenterSystemUsageThreshold%.

        Action required:
        Use the top command to check which processes have the most memory usages,
        and then check /var/log/syslog and these processes' local logs to see if
        there are any outstanding errors to be resolved.
        "
    ::= { vmwNsxTIntelligenceHealthFeature 55 }

vmwNsxTIntelligenceHealthMemoryUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterIntelligenceNodeId,
        vmwNsxTDataCenterSystemUsageThreshold
    }
    STATUS current
    DESCRIPTION
        "The memory usage on Intelligence node vmwNsxTDataCenterIntelligenceNodeId
        is below the very high threshold value of vmwNsxTDataCenterSystemUsageThreshold%.

        Action required:
        None, receipt of this notification indicates event cleared.
        "
    ::= { vmwNsxTIntelligenceHealthFeature 56 }

vmwNsxTIntelligenceHealthNodeStatusDegraded NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterServiceName,
        vmwNsxTDataCenterIntelligenceNodeId
    }
    STATUS current
    DESCRIPTION
        "Service vmwNsxTDataCenterServiceName on Intelligence node
        vmwNsxTDataCenterIntelligenceNodeId is not running.

        Action required:
        Examine the service status and health information by invoking the
        NSX CLI command `get services` on the Intelligence node. Restart
        unexpected stopped services on the Intelligence node by invoking
        the NSX CLI command `restart service <service-name>`.
        "
    ::= { vmwNsxTIntelligenceHealthFeature 57 }

vmwNsxTIntelligenceHealthNodeStatusDegradedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterServiceName,
        vmwNsxTDataCenterIntelligenceNodeId
    }
    STATUS current
    DESCRIPTION
        "Service vmwNsxTDataCenterServiceName on Intelligence node
        vmwNsxTDataCenterIntelligenceNodeId is running properly.

        Action required:
        None, receipt of this notification indicates event cleared.
        "
    ::= { vmwNsxTIntelligenceHealthFeature 58 }

-- **********************************************************
-- Licenses feature event notifications
-- **********************************************************

vmwNsxTLicensesFeaturePrefix OBJECT-IDENTITY
    STATUS current
    DESCRIPTION
        "Notifications applicable to the Licenses feature have this OID prefix."
    ::= { vmwNsxTDataCenterNotifications 5 }

vmwNsxTLicensesFeature OBJECT-IDENTITY
    STATUS current
    DESCRIPTION
        "Sub-identifier added to ensure the next-to-last sub-identifier is zero
        for Licenses feature notifications.
        "
    ::= { vmwNsxTLicensesFeaturePrefix 0 }

vmwNsxTLicensesLicenseExpired NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterLicenseEditionType
    }
    STATUS current
    DESCRIPTION
        "The license of type vmwNsxTDataCenterLicenseEditionType has expired.

        Action required:
        Add a new, non-expired license using the NSX UI by navigating to
        System | Licenses then click ADD and specify the key of the new
        license. The expired license should be deleted by checking the
        checkbox of the license, then click UNASSIGN.
        "
    ::= { vmwNsxTLicensesFeature 1 }

vmwNsxTLicensesLicenseExpiredClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterLicenseEditionType
    }
    STATUS current
    DESCRIPTION
        "The expired license of type vmwNsxTDataCenterLicenseEditionType has been removed,
        updated or is no longer expired.

        Action required:
        None, receipt of this notification indicates event cleared.
        "
    ::= { vmwNsxTLicensesFeature 2 }

vmwNsxTLicensesLicenseIsAboutToExpire NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterLicenseEditionType
    }
    STATUS current
    DESCRIPTION
        "The license of type vmwNsxTDataCenterLicenseEditionType is about to expire.

        Action required:
        Add a new, non-expiring license using the NSX UI by navigating to
        System | Licenses then click ADD and specify the key of the new
        license. The expired license should be deleted by checking the
        checkbox of the license, then click UNASSIGN.
        "
    ::= { vmwNsxTLicensesFeature 3 }

vmwNsxTLicensesLicenseIsAboutToExpireClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterLicenseEditionType
    }
    STATUS current
    DESCRIPTION
        "The expiring license of type vmwNsxTDataCenterLicenseEditionType has been removed,
        updated or is no longer about to expire.

        Action required:
        None, receipt of this notification indicates event cleared.
        "
    ::= { vmwNsxTLicensesFeature 4 }

-- **********************************************************
-- LoadBalancer feature event notifications
-- **********************************************************

vmwNsxTLoadBalancerFeaturePrefix OBJECT-IDENTITY
    STATUS current
    DESCRIPTION
        "Notifications applicable to the LoadBalancer feature have this OID prefix."
    ::= { vmwNsxTDataCenterNotifications 17 }

vmwNsxTLoadBalancerFeature OBJECT-IDENTITY
    STATUS current
    DESCRIPTION
        "Sub-identifier added to ensure the next-to-last sub-identifier is zero
        for LoadBalancer feature notifications.
        "
    ::= { vmwNsxTLoadBalancerFeaturePrefix 0 }

vmwNsxTLoadBalancerLBCPUVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage of load balancer vmwNsxTDataCenterEntityId is vmwNsxTDataCenterSystemResourceUsage%
        which is higher than the very high threshold of vmwNsxTDataCenterSystemUsageThreshold%.

        Action required:
        If the load balancer CPU utilization is higher than vmwNsxTDataCenterSystemUsageThreshold%,
        the workload is too high for this load balancer. Rescale the load balancer
        service by changing the load balancer size from small to medium or from
        medium to large. If the CPU utilization of this load balancer is still high,
        consider adjusting the Edge appliance form factor size or moving load
        balancer services to other Edge nodes for the applicable workload.
        "
    ::= { vmwNsxTLoadBalancerFeature 1 }

vmwNsxTLoadBalancerLBCPUVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU utilization of load balancer vmwNsxTDataCenterEntityId is vmwNsxTDataCenterSystemResourceUsage%
        which is lower than the very high threshold of vmwNsxTDataCenterSystemUsageThreshold%.

        Action required:
        None, receipt of this notification indicates event cleared.
        "
    ::= { vmwNsxTLoadBalancerFeature 2 }

vmwNsxTLoadBalancerLBStatusDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The load balancer service vmwNsxTDataCenterEntityId is down.

        Action required:
        Verify whether the load balancer service in the Edge node is running.
        If the status of load balancer service is not ready, make the Edge
        node enter maintenance mode, then exit maintenance mode. If the status
        of load balancer is still not recovered, please check whether there
        are any error log in /var/log/syslog.
        "
    ::= { vmwNsxTLoadBalancerFeature 7 }

vmwNsxTLoadBalancerLBStatusDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The noad balancer service vmwNsxTDataCenterEntityId is up.

        Action required:
        None, receipt of this notification indicates event cleared.
        "
    ::= { vmwNsxTLoadBalancerFeature 8 }

vmwNsxTLoadBalancerPoolStatusDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The load balancer pool vmwNsxTDataCenterEntityId status is down.

        Action required:
        Consult the load balancer pool to determine which members are down. Check
        network connectivity from the load balancer to the impacted pool members.
        Validate application health of each pool member. Also validate the health
        of each pool member using the configured monitor. When the health of the
        member is established, the pool member status is updated to healthy based
        on the 'Rise Count' configuration in the monitor.
        "
    ::= { vmwNsxTLoadBalancerFeature 9 }

vmwNsxTLoadBalancerPoolStatusDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The load balancer pool vmwNsxTDataCenterEntityId status is up

        Action required:
        None, receipt of this notification indicates event cleared.
        "
    ::= { vmwNsxTLoadBalancerFeature 10 }

vmwNsxTLoadBalancerVirtualServerStatusDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The load balancer virtual server vmwNsxTDataCenterEntityId is down.

        Action required:
        Consult the load balancer pool to determine its status and verify its
        configuration. If incorrectly configured, reconfigure it and remove the
        load balancer pool from the virtual server then re-add it to the
        virtual server again.
        "
    ::= { vmwNsxTLoadBalancerFeature 11 }

vmwNsxTLoadBalancerVirtualServerStatusDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The load balancer virtual server vmwNsxTDataCenterEntityId is up.

        Action required:
        None, receipt of this notification indicates event cleared.
        "
    ::= { vmwNsxTLoadBalancerFeature 12 }

-- **********************************************************
-- ManagerHealth feature event notifications
-- **********************************************************

vmwNsxTManagerHealthFeaturePrefix OBJECT-IDENTITY
    STATUS current
    DESCRIPTION
        "Notifications applicable to the ManagerHealth feature have this OID prefix."
    ::= { vmwNsxTDataCenterNotifications 1 }

vmwNsxTManagerHealthFeature OBJECT-IDENTITY
    STATUS current
    DESCRIPTION
        "Sub-identifier added to ensure the next-to-last sub-identifier is zero
        for ManagerHealth feature notifications.
        "
    ::= { vmwNsxTManagerHealthFeaturePrefix 0 }

vmwNsxTManagerHealthDuplicateIPAddress NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDuplicateIPAddress
    }
    STATUS current
    DESCRIPTION
        "Manager node vmwNsxTDataCenterEntityId IP address vmwNsxTDataCenterDuplicateIPAddress is
        currently being used by another device in the network.

        Action required:
        1. Determine which device is using the Manager's IP address
        and assign the device a new IP address. Note, reconfiguring
        the Manager to use a new IP address is not supported.
        2. Ensure the static IP address pool/DHCP server is configured correctly.
        3. Correct the IP address of the device if it is manually assigned.
        "
    ::= { vmwNsxTManagerHealthFeature 17 }

vmwNsxTManagerHealthDuplicateIPAddressClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDuplicateIPAddress
    }
    STATUS current
    DESCRIPTION
        "The device using the IP address assigned to Manager node
        vmwNsxTDataCenterEntityId appears to no longer be using vmwNsxTDataCenterDuplicateIPAddress.

        Action required:
        None, receipt of this notification indicates event cleared.
        "
    ::= { vmwNsxTManagerHealthFeature 18 }

vmwNsxTManagerHealthManagerConfigDiskUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /config has reached
        vmwNsxTDataCenterSystemResourceUsage% which is at or above the high threshold value of
        vmwNsxTDataCenterSystemUsageThreshold%. This can be an indication of rising disk
        usage by the NSX Datastore service under the /config/corfu directory.

        Action required:
        Please run the following tool and contact GSS if any issues are reported
        /opt/vmware/tools/support/inspect_checkpoint_issues.py
        "
    ::= { vmwNsxTManagerHealthFeature 13 }

vmwNsxTManagerHealthManagerConfigDiskUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /config has reached
        vmwNsxTDataCenterSystemResourceUsage% which is below the high threshold value of
        vmwNsxTDataCenterSystemUsageThreshold%.

        Action required:
        None, receipt of this notification indicates event cleared.
        "
    ::= { vmwNsxTManagerHealthFeature 14 }

vmwNsxTManagerHealthManagerConfigDiskUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /config has reached
        vmwNsxTDataCenterSystemResourceUsage% which is at or above the very high threshold value
        of vmwNsxTDataCenterSystemUsageThreshold%. This can be an indication of high disk usage
        by the NSX Datastore service under the /config/corfu directory.

        Action required:
        Please run the following tool and contact GSS if any issues are reported
        /opt/vmware/tools/support/inspect_checkpoint_issues.py
        "
    ::= { vmwNsxTManagerHealthFeature 15 }

vmwNsxTManagerHealthManagerConfigDiskUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /config has reached
        vmwNsxTDataCenterSystemResourceUsage% which is below the very high threshold value of
        vmwNsxTDataCenterSystemUsageThreshold%.

        Action required:
        None, receipt of this notification indicates event cleared.
        "
    ::= { vmwNsxTManagerHealthFeature 16 }

vmwNsxTManagerHealthManagerCPUUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Manager node vmwNsxTDataCenterEntityId has reached
        vmwNsxTDataCenterSystemResourceUsage% which is at or above the high
        threshold value of vmwNsxTDataCenterSystemUsageThreshold%.

        Action required:
        Please review the configuration, running services and sizing of this
        Manager node. Consider adjusting the Manager appliance form factor size.
        "
    ::= { vmwNsxTManagerHealthFeature 1 }

vmwNsxTManagerHealthManagerCPUUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Manager node vmwNsxTDataCenterEntityId has reached
        vmwNsxTDataCenterSystemResourceUsage% which is below the high
        threshold value of vmwNsxTDataCenterSystemUsageThreshold%.

        Action required:
        None, receipt of this notification indicates event cleared.
        "
    ::= { vmwNsxTManagerHealthFeature 2 }

vmwNsxTManagerHealthManagerCPUUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Manager node vmwNsxTDataCenterEntityId has reached
        vmwNsxTDataCenterSystemResourceUsage% which is at or above the very high
        threshold value of vmwNsxTDataCenterSystemUsageThreshold%.

        Action required:
        Please review the configuration, running services and sizing of this
        Manager node. Consider adjusting the Manager appliance form factor size.
        "
    ::= { vmwNsxTManagerHealthFeature 3 }

vmwNsxTManagerHealthManagerCPUUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The CPU usage on Manager node vmwNsxTDataCenterEntityId has reached
        vmwNsxTDataCenterSystemResourceUsage% which is below the very high
        threshold value of vmwNsxTDataCenterSystemUsageThreshold%.

        Action required:
        None, receipt of this notification indicates event cleared.
        "
    ::= { vmwNsxTManagerHealthFeature 4 }

vmwNsxTManagerHealthManagerDiskUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Manager node disk partition vmwNsxTDataCenterDiskPartitionName
        has reached vmwNsxTDataCenterSystemResourceUsage% which is at or above the high
        threshold value of vmwNsxTDataCenterSystemUsageThreshold%.

        Action required:
        Examine the partition with high usage and see if there are any
        unexpected large files that can be removed.
        "
    ::= { vmwNsxTManagerHealthFeature 9 }

vmwNsxTManagerHealthManagerDiskUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Manager node disk partition vmwNsxTDataCenterDiskPartitionName
        has reached vmwNsxTDataCenterSystemResourceUsage% which is below the high threshold
        value of vmwNsxTDataCenterSystemUsageThreshold%.

        Action required:
        None, receipt of this notification indicates event cleared.
        "
    ::= { vmwNsxTManagerHealthFeature 10 }

vmwNsxTManagerHealthManagerDiskUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Manager node disk partition vmwNsxTDataCenterDiskPartitionName
        has reached vmwNsxTDataCenterSystemResourceUsage% which is at or above the very high
        threshold value of vmwNsxTDataCenterSystemUsageThreshold%.

        Action required:
        Examine the partition with high usage and see if there are any
        unexpected large files that can be removed.
        "
    ::= { vmwNsxTManagerHealthFeature 11 }

vmwNsxTManagerHealthManagerDiskUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterDiskPartitionName,
        vmwNsxTDataCenterSystemResourceUsage,
        vmwNsxTDataCenterSystemUsageThreshold
    }
    STATUS current
    DESCRIPTION
        "The disk usage for the Manager node disk partition vmwNsxTDataCenterDiskPartitionName
        has reached vmwNsxTDataCenterSystemResourceUsage% which is below the very high
        threshold value of vmwNsxTDataCenterSystemUsageThreshold%.

        Action required:
        None, receipt of this notification indicates event cleared.
        "
    ::= { vmwNsxTManagerHealthFeature 12 }

vmwNsxTManagerHealthManagerMemoryUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Manager node vmwNsxTDataCenterEntityId has reached
        vmwNsxTDataCenterSystemResourceUsage% which is at or above the high
        threshold value of vmwNsxTDataCenterSystemUsageThreshold%.

        Action required:
        Please review the configuration, running services and sizing of this
        Manager node. Consider adjusting the Manager appliance form factor size.
        "
    ::= { vmwNsxTManagerHealthFeature 5 }

vmwNsxTManagerHealthManagerMemoryUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Manager node vmwNsxTDataCenterEntityId has reached
        vmwNsxTDataCenterSystemResourceUsage% which is below the high
        threshold value of vmwNsxTDataCenterSystemUsageThreshold%.

        Action required:
        None, receipt of this notification indicates event cleared.
        "
    ::= { vmwNsxTManagerHealthFeature 6 }

vmwNsxTManagerHealthManagerMemoryUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Manager node vmwNsxTDataCenterEntityId has reached
        vmwNsxTDataCenterSystemResourceUsage% which is at or above the very
        high threshold value of vmwNsxTDataCenterSystemUsageThreshold%.

        Action required:
        Please review the configuration, running services and sizing of this
        Manager node. Consider adjusting the Manager appliance form factor size.
        "
    ::= { vmwNsxTManagerHealthFeature 7 }

vmwNsxTManagerHealthManagerMemoryUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The memory usage on Manager node vmwNsxTDataCenterEntityId has reached
        vmwNsxTDataCenterSystemResourceUsage% which is below the very high
        threshold value of vmwNsxTDataCenterSystemUsageThreshold%.

        Action required:
        None, receipt of this notification indicates event cleared.
        "
    ::= { vmwNsxTManagerHealthFeature 8 }

vmwNsxTManagerHealthOperationsDbDiskUsageHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /nonconfig has reached
        vmwNsxTDataCenterSystemResourceUsage% which is at or above the high threshold value of
        vmwNsxTDataCenterSystemUsageThreshold%. This can be an indication of rising disk
        usage by the NSX Datastore service under the /nonconfig/corfu directory.

        Action required:
        Please run the following tool and contact GSS if any issues are reported
        /opt/vmware/tools/support/inspect_checkpoint_issues.py --nonconfig
        "
    ::= { vmwNsxTManagerHealthFeature 19 }

vmwNsxTManagerHealthOperationsDbDiskUsageHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /nonconfig has reached
        vmwNsxTDataCenterSystemResourceUsage% which is below the high threshold value of
        vmwNsxTDataCenterSystemUsageThreshold%.

        Action required:
        None, receipt of this notification indicates event cleared.
        "
    ::= { vmwNsxTManagerHealthFeature 20 }

vmwNsxTManagerHealthOperationsDbDiskUsageVeryHigh NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /nonconfig has reached
        vmwNsxTDataCenterSystemResourceUsage% which is at or above the very high threshold value
        of vmwNsxTDataCenterSystemUsageThreshold%. This can be an indication of high disk usage
        by the NSX Datastore service under the /nonconfig/corfu directory.

        Action required:
        Please run the following tool and contact GSS if any issues are reported
        /opt/vmware/tools/support/inspect_checkpoint_issues.py --nonconfig
        "
    ::= { vmwNsxTManagerHealthFeature 21 }

vmwNsxTManagerHealthOperationsDbDiskUsageVeryHighClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSystemResourceUsage,
        vmwNsxTDataCenterSystemUsageThreshold
    }
    STATUS current
    DESCRIPTION
        "The disk usage for the Manager node disk partition /nonconfig has reached
        vmwNsxTDataCenterSystemResourceUsage% which is below the very high threshold value of
        vmwNsxTDataCenterSystemUsageThreshold%.

        Action required:
        None, receipt of this notification indicates event cleared.
        "
    ::= { vmwNsxTManagerHealthFeature 22 }

-- **********************************************************
-- NCPHealth feature event notifications
-- **********************************************************

vmwNsxTNCPHealthFeaturePrefix OBJECT-IDENTITY
    STATUS current
    DESCRIPTION
        "Notifications applicable to the NCPHealth feature have this OID prefix."
    ::= { vmwNsxTDataCenterNotifications 11 }

vmwNsxTNCPHealthFeature OBJECT-IDENTITY
    STATUS current
    DESCRIPTION
        "Sub-identifier added to ensure the next-to-last sub-identifier is zero
        for NCPHealth feature notifications.
        "
    ::= { vmwNsxTNCPHealthFeaturePrefix 0 }

vmwNsxTNCPHealthNCPPluginDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Manager Node has detected the NCP is down or unhealthy.

        Action required:
        To find the clusters which are having issues, invoke the NSX API GET
        /api/v1/systemhealth/container-cluster/ncp/status to fetch all cluster
        statuses and determine the name of any clusters that report DOWN or
        UNKNOWN. Then on the NSX UI Inventory | Container | Clusters page find
        the names of clusters that reported DOWN or UNKNOWN status and click
        the Nodes tab which lists all Kubernetes and PAS cluster members.
        For Kubernetes cluster: 
        1. Check NCP Pod liveness by finding the K8s master node from all the
        cluster members and log onto the master node. Then invoke the kubectl
        command `kubectl get pods --all-namespaces`. If there is an issue with
        the NCP Pod, please use kubectl logs command to check the issue and fix
        the error.
        2. Check the connection between NCP and Kubernetes API server. The
        NSX CLI can be used inside the NCP Pod to check this connection status
        by invoking the following commands from the master VM.
        `kubectl exec -it <NCP-Pod-Name> -n nsx-system bash`
        `nsxcli`
        `get ncp-k8s-api-server status`
        If there is an issue with the connection, please check both the network
        and NCP configurations.
        3. Check the connection between NCP and NSX Manager. The NSX CLI can be
        used inside the NCP Pod to check this connection status by invoking the
        following command from the master VM.
        `kubectl exec -it <NCP-Pod-Name> -n nsx-system bash`
        `nsxcli`
        `get ncp-nsx status`
        If there is an issue with the connection, please check both the network
        and NCP configurations.
        For PAS cluster:
        1. Check the network connections between virtual machines and fix any
        network issues.
        2. Check the status of both nodes and services and fix crashed nodes
        or services. Invoke the command `bosh vms` and `bosh instances -p` to
        check the status of nodes and services.
        "
    ::= { vmwNsxTNCPHealthFeature 3 }

vmwNsxTNCPHealthNCPPluginDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Manager Node has detected the NCP is up or healthy again.

        Action required:
        None, receipt of this notification indicates event cleared.
        "
    ::= { vmwNsxTNCPHealthFeature 4 }

-- **********************************************************
-- NodeAgentsHealth feature event notifications
-- **********************************************************

vmwNsxTNodeAgentsHealthFeaturePrefix OBJECT-IDENTITY
    STATUS current
    DESCRIPTION
        "Notifications applicable to the NodeAgentsHealth feature have this OID prefix."
    ::= { vmwNsxTDataCenterNotifications 12 }

vmwNsxTNodeAgentsHealthFeature OBJECT-IDENTITY
    STATUS current
    DESCRIPTION
        "Sub-identifier added to ensure the next-to-last sub-identifier is zero
        for NodeAgentsHealth feature notifications.
        "
    ::= { vmwNsxTNodeAgentsHealthFeaturePrefix 0 }

vmwNsxTNodeAgentsHealthNodeAgentsDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The agents running inside the Node VM appear to be down.

        Action required:
        For ESX:
        1. If Vmk50 is missing, refer to this Knowledge Base article
         https://kb.vmware.com/s/article/67432.
        2. If Hyperbus 4094 is missing, restarting nsx-cfgagent or restarting the
        container host VM may help.
        3. If container host VIF is blocked, check the connection to the Controller
        to make sure all configurations are sent down.
        4. If nsx-cfg-agent has stopped, restart nsx-cfgagent.
        For KVM:
        1. If Hyperbus namespace is missing, restarting the  nsx-opsagent may help
        recreate the namespace.
        2. If Hyperbus interface is missing inside the hyperbus namespace,
        restarting the nsx-opsagent may help.
        3. If nsx-agent has stopped, restart nsx-agent.
        For Both ESX and KVM:
        1. If the node-agent package is missing, check whether node-agent package
        has been successfully installed in the container host vm.
        2. If the interface for node-agent in container host vm is down, check the
        eth1 interface status inside the container host vm.
        "
    ::= { vmwNsxTNodeAgentsHealthFeature 3 }

vmwNsxTNodeAgentsHealthNodeAgentsDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The agents inside the Node VM are running.

        Action required:
        None, receipt of this notification indicates event cleared.
        "
    ::= { vmwNsxTNodeAgentsHealthFeature 4 }

-- **********************************************************
-- PasswordManagement feature event notifications
-- **********************************************************

vmwNsxTPasswordManagementFeaturePrefix OBJECT-IDENTITY
    STATUS current
    DESCRIPTION
        "Notifications applicable to the PasswordManagement feature have this OID prefix."
    ::= { vmwNsxTDataCenterNotifications 4 }

vmwNsxTPasswordManagementFeature OBJECT-IDENTITY
    STATUS current
    DESCRIPTION
        "Sub-identifier added to ensure the next-to-last sub-identifier is zero
        for PasswordManagement feature notifications.
        "
    ::= { vmwNsxTPasswordManagementFeaturePrefix 0 }

vmwNsxTPasswordManagementPasswordExpirationApproaching NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterUsername,
        vmwNsxTDataCenterPasswordExpirationDays
    }
    STATUS current
    DESCRIPTION
        "The password for user vmwNsxTDataCenterUsername is approaching expiration in
        vmwNsxTDataCenterPasswordExpirationDays days.

        Action required:
        The password for the user vmwNsxTDataCenterUsername needs to be changed soon. For example,
        to apply a new password to a user, invoke the following NSX API with a valid
        password in the request body: PUT /api/v1/node/users/<userid> where <userid>
        is the ID of the user.
        "
    ::= { vmwNsxTPasswordManagementFeature 1 }

vmwNsxTPasswordManagementPasswordExpirationApproachingClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterUsername
    }
    STATUS current
    DESCRIPTION
        "The password for the user vmwNsxTDataCenterUsername has been changed successfully or
        is no longer expired.

        Action required:
        None, receipt of this notification indicates event cleared.
        "
    ::= { vmwNsxTPasswordManagementFeature 2 }

vmwNsxTPasswordManagementPasswordExpired NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterUsername
    }
    STATUS current
    DESCRIPTION
        "The password for user vmwNsxTDataCenterUsername has expired.

        Action required:
        The password for user vmwNsxTDataCenterUsername must be changed now to access the
        system. For example, to apply a new password to a user, invoke the
        following NSX API with a valid password in the request body: PUT
        /api/v1/node/users/<userid> where <userid> is the ID of the user. If the
        admin user (with <userid> 10000) password has expired, admin must login to
        the system via SSH (if enabled) or console in order to change the password.
        Upon entering the current expired password, admin will be prompted to enter
        a new password.
        "
    ::= { vmwNsxTPasswordManagementFeature 3 }

vmwNsxTPasswordManagementPasswordExpiredClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterUsername
    }
    STATUS current
    DESCRIPTION
        "The password for user vmwNsxTDataCenterUsername has been changed successfully or
        is no longer expired.

        Action required:
        None, receipt of this notification indicates event cleared.
        "
    ::= { vmwNsxTPasswordManagementFeature 4 }

vmwNsxTPasswordManagementPasswordIsAboutToExpire NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterUsername,
        vmwNsxTDataCenterPasswordExpirationDays
    }
    STATUS current
    DESCRIPTION
        "The password for user vmwNsxTDataCenterUsername is about to expire in
        vmwNsxTDataCenterPasswordExpirationDays days.

        Action required:
        Ensure the password for the user vmwNsxTDataCenterUsername is changed immediately. For
        example, to apply a new password to a user, invoke the following NSX API
        with a valid password in the request body: PUT /api/v1/node/users/<userid>
        where <userid> is the ID of the user.
        "
    ::= { vmwNsxTPasswordManagementFeature 5 }

vmwNsxTPasswordManagementPasswordIsAboutToExpireClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterUsername
    }
    STATUS current
    DESCRIPTION
        "The password for the user vmwNsxTDataCenterUsername has been changed successfully or
        is no longer expired.

        Action required:
        None, receipt of this notification indicates event cleared.
        "
    ::= { vmwNsxTPasswordManagementFeature 6 }

-- **********************************************************
-- Routing feature event notifications
-- **********************************************************

vmwNsxTRoutingFeaturePrefix OBJECT-IDENTITY
    STATUS current
    DESCRIPTION
        "Notifications applicable to the Routing feature have this OID prefix."
    ::= { vmwNsxTDataCenterNotifications 28 }

vmwNsxTRoutingFeature OBJECT-IDENTITY
    STATUS current
    DESCRIPTION
        "Sub-identifier added to ensure the next-to-last sub-identifier is zero
        for Routing feature notifications.
        "
    ::= { vmwNsxTRoutingFeaturePrefix 0 }

vmwNsxTRoutingBFDDownOnExternalInterface NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterPeerAddress,
        vmwNsxTDataCenterSrId
    }
    STATUS current
    DESCRIPTION
        "In router vmwNsxTDataCenterEntityId, BFD session for peer vmwNsxTDataCenterPeerAddress is down.

        Action required:
        1. Invoke the NSX CLI command `get logical-routers`.
        2. Switch to the service router vmwNsxTDataCenterSrId
        3. Invoke the NSX CLI command `ping vmwNsxTDataCenterPeerAddress` to verify the
        connectivity.
        "
    ::= { vmwNsxTRoutingFeature 7 }

vmwNsxTRoutingBFDDownOnExternalInterfaceClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterPeerAddress
    }
    STATUS current
    DESCRIPTION
        "In router vmwNsxTDataCenterEntityId, BFD session for peer vmwNsxTDataCenterPeerAddress is up.

        Action required:
        None, receipt of this notification indicates event cleared.
        "
    ::= { vmwNsxTRoutingFeature 8 }

vmwNsxTRoutingBGPDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterBGPNeighborIP,
        vmwNsxTDataCenterFailureReason,
        vmwNsxTDataCenterSrId
    }
    STATUS current
    DESCRIPTION
        "In Router vmwNsxTDataCenterEntityId, BGP neighbor vmwNsxTDataCenterBGPNeighborIP is down,
        reason: vmwNsxTDataCenterFailureReason.

        Action required:
        1. Invoke the NSX CLI command `get logical-routers`.
        2. Switch to service-router vmwNsxTDataCenterSrId.
        3. Invoke the NSX CLI command `get bgp neighbor summary` to check the
        BGP neighbor status.
        4. Check /var/log/syslog to see if there are any errors related to BGP
        connectivity.
        "
    ::= { vmwNsxTRoutingFeature 1 }

vmwNsxTRoutingBGPDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterBGPNeighborIP
    }
    STATUS current
    DESCRIPTION
        "In Router vmwNsxTDataCenterEntityId, BGP neighbor vmwNsxTDataCenterBGPNeighborIP is up.

        Action required:
        None, receipt of this notification indicates event cleared.
        "
    ::= { vmwNsxTRoutingFeature 2 }

vmwNsxTRoutingRoutingDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "All BGP/BFD sessions are down.

        Action required:
        Invoke the NSX CLI command `get logical-routers` to get the tier0 service router
        and switch to this vrf, then invoke the following NSX CLI commands.
        1. `ping <BFD peer IP address>` to verifyconnectivity.
        2. `get bfd-config` and `get bfd-sessions` to check if BFD is running well.
        3. `get bgp neighbor summary` to check if BGP is running well.
        Also check /var/log/syslog to see if there are any errors related to BGP
        connectivity.
        "
    ::= { vmwNsxTRoutingFeature 9 }

vmwNsxTRoutingRoutingDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "At least one BGP/BFD session up.

        Action required:
        None, receipt of this notification indicates event cleared.
        "
    ::= { vmwNsxTRoutingFeature 10 }

vmwNsxTRoutingStaticRoutingRemoved NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterStaticAddress,
        vmwNsxTDataCenterSrId
    }
    STATUS current
    DESCRIPTION
        "In router vmwNsxTDataCenterEntityId, static route vmwNsxTDataCenterStaticAddress was removed because
        BFD was down.

        Action required:
        The static routing entry was removed because the BFD session was down.
        1. Invoke the NSX CLI command `get logical-routers`.
        2. Switch to the service-router vmwNsxTDataCenterSrId.
        3. Invoke the NSX CLI command `ping <BFD peer IP address>` to verify the
        connectivity.
        Also, verify the configuration in both NSX and the BFD peer to ensure that
        timers have not been changed.
        "
    ::= { vmwNsxTRoutingFeature 5 }

vmwNsxTRoutingStaticRoutingRemovedClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterStaticAddress
    }
    STATUS current
    DESCRIPTION
        "In router vmwNsxTDataCenterEntityId, static route vmwNsxTDataCenterStaticAddress was re-added as BFD
        recovered.

        Action required:
        None, receipt of this notification indicates event cleared.
        "
    ::= { vmwNsxTRoutingFeature 6 }

-- **********************************************************
-- TransportNodeHealth feature event notifications
-- **********************************************************

vmwNsxTTransportNodeHealthFeaturePrefix OBJECT-IDENTITY
    STATUS current
    DESCRIPTION
        "Notifications applicable to the TransportNodeHealth feature have this OID prefix."
    ::= { vmwNsxTDataCenterNotifications 18 }

vmwNsxTTransportNodeHealthFeature OBJECT-IDENTITY
    STATUS current
    DESCRIPTION
        "Sub-identifier added to ensure the next-to-last sub-identifier is zero
        for TransportNodeHealth feature notifications.
        "
    ::= { vmwNsxTTransportNodeHealthFeaturePrefix 0 }

vmwNsxTTransportNodeHealthLAGMemberDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "LACP reporting member down.

        Action required:
        Check the connection status of LAG members on hosts.
        1. In the NSX UI navigate to Fabric | Nodes | Transport Nodes |
        Host Transport Nodes.
        2. In the Host Transport Nodes list, check the Node Status column. Find the
        Transport node with the degraded or down Node Status.
        3. Select <transport node> | Monitor.  Find the bond(uplink) which is
        reporting degraded or down.
        4. Check the LACP member status details by logging into the failed host and
        invoking `esxcli network vswitch dvs vmware lacp status get` on an ESXi
        host or `ovs-appctl bond/show` and `ovs-appctl lacp/show` on a KVM host.
        "
    ::= { vmwNsxTTransportNodeHealthFeature 5 }

vmwNsxTTransportNodeHealthLAGMemberDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "LACP reporting member up.

        Action required:
        None, receipt of this notification indicates event cleared.
        "
    ::= { vmwNsxTTransportNodeHealthFeature 6 }

vmwNsxTTransportNodeHealthNVDSUplinkDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Uplink is going down.

        Action required:
        Check the physical NICs' status of uplinks on hosts.
        1. In the NSX UI navigate to Fabric | Nodes | Transport Nodes |
        Host Transport Nodes.
        2. In the Host Transport Nodes list, check the Node Status column. Find the
        Transport node with the degraded or down Node Status.
        3. Select <transport node> | Monitor. Check the status details of the
        bond(uplink) which is reporting degraded or down. To avoid a degraded state,
        ensure all uplink interfaces are connected and up regardless of whether they
        are in use or not.
        "
    ::= { vmwNsxTTransportNodeHealthFeature 3 }

vmwNsxTTransportNodeHealthNVDSUplinkDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "Uplink is going up.

        Action required:
        None, receipt of this notification indicates event cleared.
        "
    ::= { vmwNsxTTransportNodeHealthFeature 4 }

-- **********************************************************
-- VPN feature event notifications
-- **********************************************************

vmwNsxTVPNFeaturePrefix OBJECT-IDENTITY
    STATUS current
    DESCRIPTION
        "Notifications applicable to the VPN feature have this OID prefix."
    ::= { vmwNsxTDataCenterNotifications 15 }

vmwNsxTVPNFeature OBJECT-IDENTITY
    STATUS current
    DESCRIPTION
        "Sub-identifier added to ensure the next-to-last sub-identifier is zero
        for VPN feature notifications.
        "
    ::= { vmwNsxTVPNFeaturePrefix 0 }

vmwNsxTVPNIPsecPolicyBasedSessionDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSessionDownReason
    }
    STATUS current
    DESCRIPTION
        "The policy based IPsec VPN session vmwNsxTDataCenterEntityId is down.
        Reason: vmwNsxTDataCenterSessionDownReason.

        Action required:
        Check IPsec VPN session configuration and resolve errors based on the
        session down reason.
        "
    ::= { vmwNsxTVPNFeature 7 }

vmwNsxTVPNIPsecPolicyBasedSessionDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The policy based IPsec VPN session vmwNsxTDataCenterEntityId is up.

        Action required:
        None, receipt of this notification indicates event cleared.
        "
    ::= { vmwNsxTVPNFeature 8 }

vmwNsxTVPNIPsecPolicyBasedTunnelDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "One or more policy based IPsec VPN tunnels in session vmwNsxTDataCenterEntityId are down.

        Action required:
        Check IPsec VPN session configuration and resolve errors based on the
        tunnel down reason.
        "
    ::= { vmwNsxTVPNFeature 9 }

vmwNsxTVPNIPsecPolicyBasedTunnelDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "All policy based IPsec VPN tunnels in session vmwNsxTDataCenterEntityId are up.

        Action required:
        None, receipt of this notification indicates event cleared.
        "
    ::= { vmwNsxTVPNFeature 10 }

vmwNsxTVPNIPsecRouteBasedSessionDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterSessionDownReason
    }
    STATUS current
    DESCRIPTION
        "The route based IPsec VPN session vmwNsxTDataCenterEntityId is down.
        Reason: vmwNsxTDataCenterSessionDownReason.

        Action required:
        Check IPsec VPN session configuration and resolve errors based on the
        session down reason.
        "
    ::= { vmwNsxTVPNFeature 11 }

vmwNsxTVPNIPsecRouteBasedSessionDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The route based IPsec VPN session vmwNsxTDataCenterEntityId is up.

        Action required:
        None, receipt of this notification indicates event cleared.
        "
    ::= { vmwNsxTVPNFeature 12 }

vmwNsxTVPNIPsecRouteBasedTunnelDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId,
        vmwNsxTDataCenterTunnelDownReason
    }
    STATUS current
    DESCRIPTION
        "The route based IPsec VPN tunnel in session vmwNsxTDataCenterEntityId is down.
        Reason: vmwNsxTDataCenterTunnelDownReason.

        Action required:
        Check IPsec VPN session configuration and resolve errors based on the
        tunnel down reason.
        "
    ::= { vmwNsxTVPNFeature 13 }

vmwNsxTVPNIPsecRouteBasedTunnelDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The route based IPsec VPN tunnel in session vmwNsxTDataCenterEntityId is up.

        Action required:
        None, receipt of this notification indicates event cleared.
        "
    ::= { vmwNsxTVPNFeature 14 }

vmwNsxTVPNL2VpnSessionDown NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The L2VPN session vmwNsxTDataCenterEntityId is down.

        Action required:
        Check L2VPN session status for session down reason and resolve errors based
        on the reason.
        "
    ::= { vmwNsxTVPNFeature 15 }

vmwNsxTVPNL2VpnSessionDownClear NOTIFICATION-TYPE
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterEntityId
    }
    STATUS current
    DESCRIPTION
        "The L2VPN session vmwNsxTDataCenterEntityId is up.

        Action required:
        None, receipt of this notification indicates event cleared.
        "
    ::= { vmwNsxTVPNFeature 16 }

-- **********************************************************
-- Conformance information
-- **********************************************************

vmwNsxTDataCenterConformance OBJECT IDENTIFIER ::= { vmwNSXsysMIB 2 }
vmwNsxTDataCenterCompliances OBJECT IDENTIFIER ::= { vmwNsxTDataCenterConformance 1 }
vmwNsxTDataCenterSMIBGroups OBJECT IDENTIFIER ::= { vmwNsxTDataCenterConformance 2 }

-- **********************************************************
-- Compliance statements
-- **********************************************************

vmwNsxTDataCenterBasicCompliance MODULE-COMPLIANCE
    STATUS deprecated
    DESCRIPTION
        "The compliance statement for entities which implement VMWARE-NSX-MIB."
    MODULE -- this module
    MANDATORY-GROUPS { vmwNsxTDataCenterNotificationInfoGroup, vmwNsxTDataCenterNotificationGroup }
    ::= { vmwNsxTDataCenterCompliances 1 }

vmwNsxTDataCenterNotificationInfoGroup OBJECT-GROUP
    OBJECTS {
        vmwNsxTDataCenterTimestamp,
        vmwNsxTDataCenterFeatureName,
        vmwNsxTDataCenterEventType,
        vmwNsxTDataCenterEventSeverity,
        vmwNsxTDataCenterNodeId,
        vmwNsxTDataCenterNodeType,
        vmwNsxTDataCenterApplianceAddress,
        vmwNsxTDataCenterBGPNeighborIP,
        vmwNsxTDataCenterCurrentGatewayState,
        vmwNsxTDataCenterCurrentServiceState,
        vmwNsxTDataCenterDHCPPoolUsage,
        vmwNsxTDataCenterDHCPServerId,
        vmwNsxTDataCenterDatapathResourceUsage,
        vmwNsxTDataCenterDiskPartitionName,
        vmwNsxTDataCenterDuplicateIPAddress,
        vmwNsxTDataCenterEdgeNICName,
        vmwNsxTDataCenterEdgeServiceName,
        vmwNsxTDataCenterEntityId,
        vmwNsxTDataCenterEventId,
        vmwNsxTDataCenterFailureReason,
        vmwNsxTDataCenterHeapType,
        vmwNsxTDataCenterIntelligenceNodeId,
        vmwNsxTDataCenterLicenseEditionType,
        vmwNsxTDataCenterMempoolName,
        vmwNsxTDataCenterPasswordExpirationDays,
        vmwNsxTDataCenterPeerAddress,
        vmwNsxTDataCenterPreviousGatewayState,
        vmwNsxTDataCenterPreviousServiceState,
        vmwNsxTDataCenterRxRingBufferOverflowPercentage,
        vmwNsxTDataCenterServiceName,
        vmwNsxTDataCenterSessionDownReason,
        vmwNsxTDataCenterSrId,
        vmwNsxTDataCenterStaticAddress,
        vmwNsxTDataCenterSystemResourceUsage,
        vmwNsxTDataCenterSystemUsageThreshold,
        vmwNsxTDataCenterTunnelDownReason,
        vmwNsxTDataCenterTxRingBufferOverflowPercentage,
        vmwNsxTDataCenterUsername
    }
    STATUS current
    DESCRIPTION
        "These objects provide details in NSX-T Data Center event notifications."
    ::= { vmwNsxTDataCenterSMIBGroups 1 }

vmwNsxTDataCenterNotificationGroup NOTIFICATION-GROUP
    NOTIFICATIONS {
        vmwNsxTAlarmManagementAlarmServiceOverloaded,
        vmwNsxTAlarmManagementAlarmServiceOverloadedClear,
        vmwNsxTAlarmManagementHeavyVolumeOfAlarms,
        vmwNsxTAlarmManagementHeavyVolumeOfAlarmsClear,
        vmwNsxTCertificatesCertificateExpirationApproaching,
        vmwNsxTCertificatesCertificateExpirationApproachingClear,
        vmwNsxTCertificatesCertificateExpired,
        vmwNsxTCertificatesCertificateExpiredClear,
        vmwNsxTCertificatesCertificateIsAboutToExpire,
        vmwNsxTCertificatesCertificateIsAboutToExpireClear,
        vmwNsxTCniHealthHyperbusManagerConnectionDown,
        vmwNsxTCniHealthHyperbusManagerConnectionDownClear,
        vmwNsxTDHCPPoolLeaseAllocationFailed,
        vmwNsxTDHCPPoolLeaseAllocationFailedClear,
        vmwNsxTDHCPPoolOverloaded,
        vmwNsxTDHCPPoolOverloadedClear,
        vmwNsxTDistributedFirewallDFWCPUUsageVeryHigh,
        vmwNsxTDistributedFirewallDFWCPUUsageVeryHighClear,
        vmwNsxTDistributedFirewallDFWMemoryUsageVeryHigh,
        vmwNsxTDistributedFirewallDFWMemoryUsageVeryHighClear,
        vmwNsxTDNSForwarderDisabled,
        vmwNsxTDNSForwarderDisabledClear,
        vmwNsxTDNSForwarderDown,
        vmwNsxTDNSForwarderDownClear,
        vmwNsxTEdgeHealthEdgeCPUUsageHigh,
        vmwNsxTEdgeHealthEdgeCPUUsageHighClear,
        vmwNsxTEdgeHealthEdgeCPUUsageVeryHigh,
        vmwNsxTEdgeHealthEdgeCPUUsageVeryHighClear,
        vmwNsxTEdgeHealthEdgeDatapathConfigurationFailure,
        vmwNsxTEdgeHealthEdgeDatapathConfigurationFailureClear,
        vmwNsxTEdgeHealthEdgeDatapathCPUHigh,
        vmwNsxTEdgeHealthEdgeDatapathCPUHighClear,
        vmwNsxTEdgeHealthEdgeDatapathCPUVeryHigh,
        vmwNsxTEdgeHealthEdgeDatapathCPUVeryHighClear,
        vmwNsxTEdgeHealthEdgeDatapathCryptodrvDown,
        vmwNsxTEdgeHealthEdgeDatapathCryptodrvDownClear,
        vmwNsxTEdgeHealthEdgeDatapathMempoolHigh,
        vmwNsxTEdgeHealthEdgeDatapathMempoolHighClear,
        vmwNsxTEdgeHealthEdgeDiskUsageHigh,
        vmwNsxTEdgeHealthEdgeDiskUsageHighClear,
        vmwNsxTEdgeHealthEdgeDiskUsageVeryHigh,
        vmwNsxTEdgeHealthEdgeDiskUsageVeryHighClear,
        vmwNsxTEdgeHealthEdgeGlobalARPTableUsageHigh,
        vmwNsxTEdgeHealthEdgeGlobalARPTableUsageHighClear,
        vmwNsxTEdgeHealthEdgeMemoryUsageHigh,
        vmwNsxTEdgeHealthEdgeMemoryUsageHighClear,
        vmwNsxTEdgeHealthEdgeMemoryUsageVeryHigh,
        vmwNsxTEdgeHealthEdgeMemoryUsageVeryHighClear,
        vmwNsxTEdgeHealthEdgeNICLinkStatusDown,
        vmwNsxTEdgeHealthEdgeNICLinkStatusDownClear,
        vmwNsxTEdgeHealthEdgeNICOutOfReceiveBuffer,
        vmwNsxTEdgeHealthEdgeNICOutOfReceiveBufferClear,
        vmwNsxTEdgeHealthEdgeNICOutOfTransmitBuffer,
        vmwNsxTEdgeHealthEdgeNICOutOfTransmitBufferClear,
        vmwNsxTEndpointProtectionEAMStatusDown,
        vmwNsxTEndpointProtectionEAMStatusDownClear,
        vmwNsxTEndpointProtectionPartnerChannelDown,
        vmwNsxTEndpointProtectionPartnerChannelDownClear,
        vmwNsxTHighAvailabilityTier0GatewayFailover,
        vmwNsxTHighAvailabilityTier0GatewayFailoverClear,
        vmwNsxTHighAvailabilityTier1GatewayFailover,
        vmwNsxTHighAvailabilityTier1GatewayFailoverClear,
        vmwNsxTInfrastructureCommunicationEdgeTunnelsDown,
        vmwNsxTInfrastructureCommunicationEdgeTunnelsDownClear,
        vmwNsxTInfrastructureServiceEdgeServiceStatusChanged,
        vmwNsxTInfrastructureServiceEdgeServiceStatusChangedClear,
        vmwNsxTInfrastructureServiceEdgeServiceStatusDown,
        vmwNsxTInfrastructureServiceEdgeServiceStatusDownClear,
        vmwNsxTIntelligenceCommunicationTNFlowExporterDisconnected,
        vmwNsxTIntelligenceCommunicationTNFlowExporterDisconnectedClear,
        vmwNsxTIntelligenceHealthCPUUsageHigh,
        vmwNsxTIntelligenceHealthCPUUsageHighClear,
        vmwNsxTIntelligenceHealthCPUUsageVeryHigh,
        vmwNsxTIntelligenceHealthCPUUsageVeryHighClear,
        vmwNsxTIntelligenceHealthDataDiskPartitionUsageHigh,
        vmwNsxTIntelligenceHealthDataDiskPartitionUsageHighClear,
        vmwNsxTIntelligenceHealthDataDiskPartitionUsageVeryHigh,
        vmwNsxTIntelligenceHealthDataDiskPartitionUsageVeryHighClear,
        vmwNsxTIntelligenceHealthDiskUsageHigh,
        vmwNsxTIntelligenceHealthDiskUsageHighClear,
        vmwNsxTIntelligenceHealthDiskUsageVeryHigh,
        vmwNsxTIntelligenceHealthDiskUsageVeryHighClear,
        vmwNsxTIntelligenceHealthMemoryUsageHigh,
        vmwNsxTIntelligenceHealthMemoryUsageHighClear,
        vmwNsxTIntelligenceHealthMemoryUsageVeryHigh,
        vmwNsxTIntelligenceHealthMemoryUsageVeryHighClear,
        vmwNsxTIntelligenceHealthNodeStatusDegraded,
        vmwNsxTIntelligenceHealthNodeStatusDegradedClear,
        vmwNsxTLicensesLicenseExpired,
        vmwNsxTLicensesLicenseExpiredClear,
        vmwNsxTLicensesLicenseIsAboutToExpire,
        vmwNsxTLicensesLicenseIsAboutToExpireClear,
        vmwNsxTLoadBalancerLBCPUVeryHigh,
        vmwNsxTLoadBalancerLBCPUVeryHighClear,
        vmwNsxTLoadBalancerLBStatusDown,
        vmwNsxTLoadBalancerLBStatusDownClear,
        vmwNsxTLoadBalancerPoolStatusDown,
        vmwNsxTLoadBalancerPoolStatusDownClear,
        vmwNsxTLoadBalancerVirtualServerStatusDown,
        vmwNsxTLoadBalancerVirtualServerStatusDownClear,
        vmwNsxTManagerHealthDuplicateIPAddress,
        vmwNsxTManagerHealthDuplicateIPAddressClear,
        vmwNsxTManagerHealthManagerConfigDiskUsageHigh,
        vmwNsxTManagerHealthManagerConfigDiskUsageHighClear,
        vmwNsxTManagerHealthManagerConfigDiskUsageVeryHigh,
        vmwNsxTManagerHealthManagerConfigDiskUsageVeryHighClear,
        vmwNsxTManagerHealthManagerCPUUsageHigh,
        vmwNsxTManagerHealthManagerCPUUsageHighClear,
        vmwNsxTManagerHealthManagerCPUUsageVeryHigh,
        vmwNsxTManagerHealthManagerCPUUsageVeryHighClear,
        vmwNsxTManagerHealthManagerDiskUsageHigh,
        vmwNsxTManagerHealthManagerDiskUsageHighClear,
        vmwNsxTManagerHealthManagerDiskUsageVeryHigh,
        vmwNsxTManagerHealthManagerDiskUsageVeryHighClear,
        vmwNsxTManagerHealthManagerMemoryUsageHigh,
        vmwNsxTManagerHealthManagerMemoryUsageHighClear,
        vmwNsxTManagerHealthManagerMemoryUsageVeryHigh,
        vmwNsxTManagerHealthManagerMemoryUsageVeryHighClear,
        vmwNsxTNCPHealthNCPPluginDown,
        vmwNsxTNCPHealthNCPPluginDownClear,
        vmwNsxTNodeAgentsHealthNodeAgentsDown,
        vmwNsxTNodeAgentsHealthNodeAgentsDownClear,
        vmwNsxTPasswordManagementPasswordExpirationApproaching,
        vmwNsxTPasswordManagementPasswordExpirationApproachingClear,
        vmwNsxTPasswordManagementPasswordExpired,
        vmwNsxTPasswordManagementPasswordExpiredClear,
        vmwNsxTPasswordManagementPasswordIsAboutToExpire,
        vmwNsxTPasswordManagementPasswordIsAboutToExpireClear,
        vmwNsxTRoutingBFDDownOnExternalInterface,
        vmwNsxTRoutingBFDDownOnExternalInterfaceClear,
        vmwNsxTRoutingBGPDown,
        vmwNsxTRoutingBGPDownClear,
        vmwNsxTRoutingRoutingDown,
        vmwNsxTRoutingRoutingDownClear,
        vmwNsxTRoutingStaticRoutingRemoved,
        vmwNsxTRoutingStaticRoutingRemovedClear,
        vmwNsxTTransportNodeHealthLAGMemberDown,
        vmwNsxTTransportNodeHealthLAGMemberDownClear,
        vmwNsxTTransportNodeHealthNVDSUplinkDown,
        vmwNsxTTransportNodeHealthNVDSUplinkDownClear,
        vmwNsxTVPNIPsecPolicyBasedSessionDown,
        vmwNsxTVPNIPsecPolicyBasedSessionDownClear,
        vmwNsxTVPNIPsecPolicyBasedTunnelDown,
        vmwNsxTVPNIPsecPolicyBasedTunnelDownClear,
        vmwNsxTVPNIPsecRouteBasedSessionDown,
        vmwNsxTVPNIPsecRouteBasedSessionDownClear,
        vmwNsxTVPNIPsecRouteBasedTunnelDown,
        vmwNsxTVPNIPsecRouteBasedTunnelDownClear,
        vmwNsxTVPNL2VpnSessionDown,
        vmwNsxTVPNL2VpnSessionDownClear
    }
    STATUS current
    DESCRIPTION
        "Group of objects describing event notifications emitted by
        NSX-T Data Center.
        "
    ::= { vmwNsxTDataCenterSMIBGroups 2 }

vmwNsxTDataCenterBasicCompliance2 MODULE-COMPLIANCE
    STATUS current
    DESCRIPTION
        "The compliance statement for entities which implement VMWARE-NSX-MIB."
    MODULE -- this module
    MANDATORY-GROUPS {
        vmwNsxTDataCenterNotificationInfoGroup,
        vmwNsxTDataCenterNotificationInfoGroup2,
        vmwNsxTDataCenterNotificationGroup,
        vmwNsxTDataCenterNotificationGroup2
    }
    ::= { vmwNsxTDataCenterCompliances 2 }

vmwNsxTDataCenterNotificationInfoGroup2 OBJECT-GROUP
    OBJECTS {
        vmwNsxTDataCenterBGPSourceIP,
        vmwNsxTDataCenterRemoteSiteId,
        vmwNsxTDataCenterRemoteSiteName,
        vmwNsxTDataCenterSiteId,
        vmwNsxTDataCenterSiteName
    }
    STATUS current
    DESCRIPTION
        "These objects provide details in NSX-T Data Center event notifications."
    ::= { vmwNsxTDataCenterSMIBGroups 3 }

vmwNsxTDataCenterNotificationGroup2 NOTIFICATION-GROUP
    NOTIFICATIONS {
        vmwNsxTEdgeHealthStorageError,
        vmwNsxTEdgeHealthStorageErrorClear,
        vmwNsxTFederationLmToLmSynchronizationError,
        vmwNsxTFederationLmToLmSynchronizationErrorClear,
        vmwNsxTFederationLmToLmSynchronizationWarning,
        vmwNsxTFederationLmToLmSynchronizationWarningClear,
        vmwNsxTFederationRtepBGPDown,
        vmwNsxTFederationRtepBGPDownClear,
        vmwNsxTManagerHealthOperationsDbDiskUsageHigh,
        vmwNsxTManagerHealthOperationsDbDiskUsageHighClear,
        vmwNsxTManagerHealthOperationsDbDiskUsageVeryHigh,
        vmwNsxTManagerHealthOperationsDbDiskUsageVeryHighClear
    }
    STATUS current
    DESCRIPTION
        "Group of objects describing event notifications emitted by
        NSX-T Data Center.
        "
    ::= { vmwNsxTDataCenterSMIBGroups 4 }

END
