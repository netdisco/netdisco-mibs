FDRY-IPV6-IP-MIB DEFINITIONS ::= BEGIN

IMPORTS
    MODULE-IDENTITY, OBJECT-TYPE, Unsigned32      
      FROM SNMPv2-SMI       -- [RFC2578]
    RtrStatus
      FROM FOUNDRY-SN-IP-MIB  --[snrouteru.mib]
    fdryIpv6
      FROM FOUNDRY-SN-ROOT-MIB -- [snrootu.mib]
   ;

fdryIpv6MIB MODULE-IDENTITY
	LAST-UPDATED "201007260000Z" -- July 26, 2010
	ORGANIZATION "Brocade Communications Systems, Inc."
	CONTACT-INFO
		"Technical Support Center
              130 Holger Way,
              San Jose, CA  95134
              Email:  ipsupport@brocade.com
              Phone: 1-800-752-8061
              URL:  www.brocade.com"
    DESCRIPTION
        "The Brocade proprietary MIB module for IPv6. 

         Copyright 1996-2010 Brocade Communications Systems, Inc.  
  		All rights reserved.
  		This Brocade Communications Systems SNMP Management Information Base Specification
 		embodies Brocade Communications Systems' confidential and proprietary
 		intellectual property. Brocade Communications Systems retains all
  		title and ownership in the Specification, including any revisions.

 		This Specification is supplied AS IS, and Brocade Communications Systems makes
 		no warranty, either express or implied, as to the use,
 		operation, condition, or performance of the specification, and any unintended 
 		consequence it may on the user environment."

 	REVISION        "201007260000Z" -- July 26, 2010
 	DESCRIPTION  
 		"Changed the ORGANIZATION, CONTACT-INFO and DESCRIPTION fields."

	REVISION	 "201005060000Z"  -- 06 May 2010
	DESCRIPTION  ""

   ::= { fdryIpv6 1 }


--
-- Top level components of this MIB.
--

fdryIpv6GlobalObjects   		OBJECT IDENTIFIER ::= { fdryIpv6MIB 1 }


--
-- Ipv6 global Scalar Object
--

fdryIpv6LoadShare         OBJECT-TYPE
	SYNTAX  RtrStatus
	MAX-ACCESS  read-write
	STATUS  current
	DESCRIPTION
		"If more than one ipv6 route available,
		use them to share load."
	::= { fdryIpv6GlobalObjects 1}

fdryIpv6LoadShareNumOfPaths	OBJECT-TYPE
	SYNTAX Unsigned32
	MAX-ACCESS  read-write
	STATUS  current
	DESCRIPTION
		"Number of ipv6 routes are used to share load."
	::= { fdryIpv6GlobalObjects 2 }

END
