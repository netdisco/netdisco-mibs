RUCKUS-DHCPCLIENT-MIB DEFINITIONS ::= BEGIN

IMPORTS
    OBJECT-TYPE, NOTIFICATION-TYPE, MODULE-IDENTITY, IpAddress, Integer32,
    TimeTicks, Counter32
        FROM SNMPv2-SMI
    snSwitch
        FROM FOUNDRY-SN-SWITCH-GROUP-MIB
    RowStatus, MacAddress
        FROM SNMPv2-TC
    InterfaceIndexOrZero
        FROM IF-MIB;

ruckusDhcpClientMIB MODULE-IDENTITY
    LAST-UPDATED "202007290000Z" -- Jul 29, 2020
    ORGANIZATION "Ruckus Wireless, Inc."
    CONTACT-INFO
            "
            Technical Support Center, Ruckus Wireless, Inc,
            350 West Java Drive,
            Sunnyvale, CA 94089, USA
            Support URL: https://support.ruckuswireless.com
            Phone: +1-855-782-5871
            ROW TF Numbers: https://support.ruckuswireless.com/contact-us"
    DESCRIPTION
            "
            Copyright 2020 Ruckus Wireless, Inc..
            All rights reserved.
            This Ruckus Wireless, Inc SNMP Management Information Base Specification
            embodies Ruckus Wireless, Inc' confidential and proprietary
            intellectual property. Ruckus Wireless, Inc retains all
            title and ownership in the Specification, including any
            revisions.

            This Specification is supplied AS IS, and Ruckus Wireless, Inc makes
            no warranty, either express or implied, as to the use,
            operation, condition, or performance of the Specification.
            "
    REVISION     "202007290000Z" -- Jul 29, 2020
    DESCRIPTION
                 "Initial Version"
   ::= { snSwitch 46 }

--
-- Define the DHCP Client Tables.
--
    ruckusDhcpClientGlobalObjects OBJECT IDENTIFIER ::= { ruckusDhcpClientMIB 1 }
    
-- =================================================================
-- DHCPv4 Client Global Scalar Object Section
-- =================================================================

ruckusDhcpClientGlobalConfigState OBJECT-TYPE
	SYNTAX  INTEGER { disabled(0), enabled(1) }
	MAX-ACCESS      read-write
	STATUS  current
	DESCRIPTION
		"Configure state for DHCP client on the global level.
			enabled(1) - DHCPv4 client is enabled.
			disabled(0) - DHCPv4 client is disabled.
		Note: DHCPv4 server should be disabled when enabling DHCP client."
	DEFVAL { enabled }
	::= {ruckusDhcpClientGlobalObjects  1}

ruckusDhcpClientGlobalAutoUpdateConfigState OBJECT-TYPE
	SYNTAX  INTEGER { disabled(0), enabled(1) }
	MAX-ACCESS      read-write
	STATUS  current
	DESCRIPTION
		"Configure state for DHCP client auto-update on the global level.
			enabled(1) - DHCPv4 client auto-update is enabled.
			disabled(0) - DHCPv4 client auto-update is disabled."
	DEFVAL { enabled }
	::= {ruckusDhcpClientGlobalObjects  2}

ruckusDhcpClientSpecificVEPort OBJECT-TYPE
    SYNTAX     InterfaceIndexOrZero
    MAX-ACCESS read-write
    STATUS     current
    DESCRIPTION
		 "Configure state of DHCP client on specific VE at the global level.
			 If DHCP client is configured at specific VE, ifIndex of the DHCP 
			 client enabled VE port is returned.
			 If DHCP Client is not configured on VE port, zero is returned.
		 	 Note: DHCPv4 client should be enabled globally when enabling DHCP
			 client on specific VE. In switch, the feature is not supported 
			 and zero value will be returned for this OID."

     DEFVAL { 0 }
     ::= {ruckusDhcpClientGlobalObjects  3}

END
