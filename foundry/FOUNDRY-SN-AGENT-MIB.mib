FOUNDRY-SN-AGENT-MIB DEFINITIONS ::= BEGIN

IMPORTS
	MODULE-IDENTITY, OBJECT-TYPE,TimeTicks, IpAddress, Counter32, Gauge32,Unsigned32,Integer32
		FROM SNMPv2-SMI
	TEXTUAL-CONVENTION, RowStatus
		FROM SNMPv2-TC
	InterfaceIndex
		FROM IF-MIB
	InetAddressType, InetAddress		
		FROM INET-ADDRESS-MIB		-- [RFC 4001]
	CounterBasedGauge64
		FROM HCNUM-TC
	EnabledStatus
		FROM P-BRIDGE-MIB
	snChassis, snAgentSys, snStack
		FROM FOUNDRY-SN-ROOT-MIB
    Ipv6Address
        FROM IPV6-TC;


snAgent MODULE-IDENTITY
	LAST-UPDATED "201708070000Z" -- Aug 7, 2017
	ORGANIZATION "Ruckus Wireless, Inc."
	CONTACT-INFO
			"
			Technical Support Center, Ruckus Wireless, Inc,
			350 West Java Drive,
			Sunnyvale, CA 94089, USA
			Support URL: https://support.ruckuswireless.com
			Phone: +1-855-782-5871
			ROW TF Numbers: https://support.ruckuswireless.com/contact-us"
	DESCRIPTION
			"
			Copyright 1996-2017 Ruckus Wireless, Inc..
			All rights reserved.
			This Ruckus Wireless, Inc SNMP Management Information Base Specification
			embodies Ruckus Wireless, Inc' confidential and proprietary
			intellectual property. Ruckus Wireless, Inc retains all
			title and ownership in the Specification, including any
			revisions.
			
			This Specification is supplied AS IS, and Ruckus Wireless, Inc makes
			no warranty, either express or implied, as to the use,
			operation, condition, or performance of the Specification.			
			"        	
	REVISION     "200909300000Z" -- September 30, 2009
	DESCRIPTION
			"convert from SMIv1 to SMIv2"
	REVISION     "201708070000Z" -- Aug 7, 2017
	DESCRIPTION
        	     "Modified contact Info, Organization and Decscription"
	REVISION     "202407260000Z" -- July 26, 2024
	DESCRIPTION
        	     "Modified the length of Displaystring for snAgImgFname MIB from existing 32 characters to 256 characters"
	REVISION     "202408060000Z" -- Aug 06, 2024
	DESCRIPTION
        	     "Modified the Description of snAgentTempTable and snAgentTemp2Table"
   ::= { iso(1) org(3) dod(6) internet(1) private(4) enterprises(1) foundry(1991) 4}

		-- textual conventions

	MacAddress ::= TEXTUAL-CONVENTION
		DISPLAY-HINT "1x:"
		STATUS	  current
		DESCRIPTION
			"
			   This data type is used to model media addresses.  For many
			   types of media, this will be in a binary representation.
			   For example, an ethernet address would be represented as
			   a string of 6 octets.			
			"
		SYNTAX	OCTET STRING (SIZE(6))        
		
	DisplayString ::= TEXTUAL-CONVENTION
		STATUS	  current
		DESCRIPTION
			"This data type is used to model textual information taken
			 from the NVT ASCII character set.  By convention, objects
			 with this syntax are declared as having
				SIZE (0..255)"
		SYNTAX	OCTET STRING        

-- Groups

snChasGen	OBJECT IDENTIFIER ::= { snChassis 1 }
snChasPwr	OBJECT IDENTIFIER ::= { snChassis 2 }
snChasFan	OBJECT IDENTIFIER ::= { snChassis 3 }
snChasUnit	OBJECT IDENTIFIER ::= { snChassis 4 }


-- SECTION 2: MIB Objects


-- General Chassis Information

snChasType OBJECT-TYPE
	SYNTAX DisplayString (SIZE(0..128))
	MAX-ACCESS	read-only
	STATUS	current
	DESCRIPTION
		"The chassis type represents the type 
		of Ruckus Wireless product being managed. "
	::= { snChasGen 1 }



snChasSerNum OBJECT-TYPE
	SYNTAX	DisplayString (SIZE(0..128))
	MAX-ACCESS	read-only
	STATUS	current
	DESCRIPTION
		"The serial number of the chassis. If the
		serial number is unknown or unavailable then
		the value should be a zero length string."
	::= { snChasGen 2 }



-- Power Supply Status


snChasPwrSupplyStatus OBJECT-TYPE
	SYNTAX	Integer32
	MAX-ACCESS	read-only
	STATUS	deprecated
	DESCRIPTION
		"This object is being deprecated, please use snChasPwrSupplyTable instead.
	
		A bit array that contains the value of the
		Chassis Power Supplies. This is a packed bit string;
		the 2 power supplies status are encoded into 4 bits
		(a nibble). 

		There are multiple power supplies per chassis in this release.
		The following shows the meaning of each bit:
		(bit 0 is the least significant bit).

		  bit position   meaning
		  ------------   -------
			  20-31  reserved
			  19     Power  Supply 8 DC (0=bad, 1=good).
			  18     Power  Supply 7 DC (0=bad, 1=good).
			  17     Power  Supply 8 present status (0=present, 1=not-present).
			  16     Power  Supply 7 present status (0=present, 1=not-present).
			  15     Power  Supply 6 DC (0=bad, 1=good).
			  14     Power  Supply 5 DC (0=bad, 1=good).
			  13     Power  Supply 6 present status (0=present, 1=not-present).
			  12     Power  Supply 5 present status (0=present, 1=not-present).
			  11     Power  Supply 4 DC (0=bad, 1=good).
			  10     Power  Supply 3 DC (0=bad, 1=good).
			  9      Power  Supply 4 present status (0=present, 1=not-present).
			  8      Power  Supply 3 present status (0=present, 1=not-present).
			  4-7    reserved
			  3      Power  Supply 2 DC (0=bad, 1=good).
			  2      Power  Supply 1 DC (0=bad, 1=good).
			  1      Power  Supply 2 present status (0=present, 1=not-present).
			  0      Power  Supply 1 present status (0=present, 1=not-present)."
	::= { snChasGen 3 }


-- Fan Status


snChasFanStatus OBJECT-TYPE
	SYNTAX	Integer32
	MAX-ACCESS	read-only
	STATUS	deprecated
	DESCRIPTION
		"This object is being deprecated, please use snChasFanTable instead.
	
		A bit array that contains the value of the
		fan status. This is a packed bit string. The
		status of each fan is encoded into one bit.

		  bit value    meaning
		  ---------    -------
			  0         fan failure.
			  1         fan good.

		There are two fans per VLAN Switch chassis in this release.
		The following shows the meaning of each bit:
		(bit 0 is the least significant bit).

		  bit position   meaning
		  ------------   -------
			  6-31       reserved
			  5          fan6 status
			  4          fan5 status
			  3          fan4 status
			  2          fan3 status
			  1          fan2 status
			  0          fan1 status"
	::= { snChasGen 4 }




snChasMainBrdDescription OBJECT-TYPE
	SYNTAX DisplayString (SIZE(0..128))
	MAX-ACCESS read-only
	STATUS current
	DESCRIPTION
		"The main board description string. (It is obsoleted for Chassis Product)"
	::= { snChasGen 5 }


snChasMainPortTotal OBJECT-TYPE
	SYNTAX INTEGER (1..24)
	MAX-ACCESS read-only
	STATUS current
	DESCRIPTION
		"The total number of ports for the main board. (It is obsoleted for Chassis Product)"
	::= { snChasGen 6 }


snChasExpBrdDescription OBJECT-TYPE
	SYNTAX DisplayString (SIZE(0..128))
	MAX-ACCESS read-only
	STATUS current
	DESCRIPTION
		"The expansion board description string. Expansion
		board are those boards attaching on the main board.
		(It is obsoleted for Chassis Product)"
	::= { snChasGen 7 }


snChasExpPortTotal OBJECT-TYPE
	SYNTAX INTEGER (1..24)
	MAX-ACCESS read-only
	STATUS current
	DESCRIPTION
		"The total number of ports for the expansion board.
		(It is obsoleted for Chassis Product)"
	::= { snChasGen 8 }


snChasStatusLeds OBJECT-TYPE
	SYNTAX	Integer32
	MAX-ACCESS	read-only
	STATUS	current
	DESCRIPTION
		"A bit array that contains the value of the
		front panel status LEDs. This is a bit-map; 
		each LED is encoded into 1 bit for each switch
		port.  The maximum number of ports in one chassis 
		is 24 that means 24 Ports Status LEDs. The expansion port 
		number always begins from the last main port number.  
		The following shows the meaning of each bit for each 
		switch port:

		  bit value  meaning
		  --------   ---------  
			 0         off (Link off)
			 1         on  (Link on)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snChasGen 9 }


snChasTrafficLeds OBJECT-TYPE
	SYNTAX	Integer32
	MAX-ACCESS	read-only
	STATUS	current
	DESCRIPTION
		"A bit array that contains the value of the
		front panel traffic LEDs. This is a packed bit string; 
		each LED is encoded into 1 bit for each switch
		port.  The maximum number of ports in one chassis 
		is 24 that means 24 Ports Traffic LEDs. The expansion port 
		number always begins from the last main port number.  
		The following shows the meaning of each bit for each 
		switch port:

		  bit value  meaning
		  --------   ---------  
			 0         off (no traffic)
			 1         on  (traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snChasGen 10 }


snChasMediaLeds OBJECT-TYPE
	SYNTAX	Integer32
	MAX-ACCESS	read-only
	STATUS	current
	DESCRIPTION
		"A bit array that contains the value of the
		front panel media LEDs. This is a packed bit string; 
		each LED is encoded into 1 bit for each switch port.  
		The maximum number of ports in one chassis is 24 
		that means 24 Ports Media LEDs.  The expansion port 
		number always begins from the last main port number. 
		The following shows the meaning of each bit for each 
		switch port:

		bit value  meaning   
		---------  -------
		  0        half duplex
		  1        full duplex

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snChasGen 11 }


snChasEnablePwrSupplyTrap OBJECT-TYPE
	SYNTAX	INTEGER { disabled(0), enabled(1) }
	MAX-ACCESS	read-write
	STATUS	current
	DESCRIPTION
		"Indicates whether the SNMP agent process is
		permitted to generate power supply failure traps."
	DEFVAL { enabled }
	::= { snChasGen 12 }

snChasMainBrdId OBJECT-TYPE
	SYNTAX OCTET STRING
	MAX-ACCESS read-only
	STATUS current
	DESCRIPTION
		"The main board identifier, which can uniquely identify a board
		type. It is an encoded octet string with the following meaning:
		  octet 0  - octet string format version, which identifies the
					 format of this string.

		If format version octet has the value 1, the octets after the
		version octet have the following meaning:
		  octet 1  - product type, FIWG=0x57, FIBB=0x42, FIMLS=0x4D
					 NI=0x4E, TI=0x54, TIRT=0x52
		  octet 2  - board type, POWERPC=1, ALPHA=2
		  The length of the octet string is 27.

		If format version octet has the value 2, the octets after the
		version octet have the following meaning:
		  octet 1  - product type: 
						BI_WG					0x57
						BI_BB					0x42
						BI_NI					0x4E
						NI_M4					0x4D
						BI_SLB					0x53
		  octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G		0xC5
						SLAVE_JC_8G				0xC6	
						SLAVE_JC_B16GF			0xC8	
						MASTER_JC_B2404			0xC9	
						SLAVE_JC_B16GC			0xCA	

		  The length of the octet string is 28.

		  Both format version 1 and 2:
		  octet 3  - processor type, PVR_M603=3, PVR_M604=4, PVR_M603E=6,
					 PVR_M603EV=7, PVR_M750=8, PVR_M604E=9, PVR_M8245=81
		  octet 4 to
		  octet 5  - processor speed in MHz
		  octet 6  - MAC type:
						MAC_NONE=0
						MAC_SEEQ_10_100=1, 
						MAC_DEC_10_100=2,
						MAC_3COM_10_100=3,
						MAC_X10GMAC_10000=4,
						MAC_SEEQ_1000=5, 
						MAC_GMAC_1000=6,
						MAC_VLSI_1000=7
		  octet 7  - PHY type, PHY_NONE=0, PHY_QSI=1, PHY_BROADCOM=2,
					 PHY_ICS=3, PHY_NATIONAL=4, PHY_LEVEL1=6,
					 PHY_BROADCOM_10_100=7, PHY_LEVEL24=8,
					 PHY_BROADCOM_10000=9 (for 10G),
					 PHY_3COM_10_100=9 (for others)
		  octet 8  - port type, COPPER=0, FIBER=1
		  octet 9  - fiber port type, NONFIBER=0, SX_FIBER=1,
					 LX_FIBER=2, LHX_FIBER=3, LX_SX_FIBER=4,
					 LHB_FIBER=5
		  octet 10 to
		  octet 13 - DRAM size in KBytes
		  octet 14 to
		  octet 17 - boot flash size in KBytes
		  octet 18 to
		  octet 21 - code flash size in KBytes
		  octet 22 to
		  octet 27 - serial number.

		  Format version 1 only:
		  octet 28 - chassis backplane type. 
			chassis4000	= 	0x00
			chassis8000	=	0x02
			chassis15000	=	0x01
			chassisFISX	=	0x04
			Turbo8			=	0x07 (stack2)
			FastIron2		=	0x06 (stack1)"
	::= { snChasGen 13 }


snChasExpBrdId OBJECT-TYPE
	SYNTAX OCTET STRING
	MAX-ACCESS read-only
	STATUS current
	DESCRIPTION
		"The expansion board identifier. Expansion board are those
		boards attaching on the main board. It is an encoded octet
		string with the following meaning:
		  octet 0  - octet string format version, which identifies
					 the format of this string.
		If format version octet has the value 1, the octets after
		the version octet have the following meaning:
		  octet 1  - expansion board type, HUNDRED_MEG_1PORT=1,
					 HUNDRED_MEG_2PORT=2, HUNDRED_MEG_1PORT_COPPER=3,
					 HUNDRED_MEG_2PORT_COPPER=4, HUNDRED_MEG_2PORT_LX=5,
					 GIGA_1PORT=8, GIGA_2PORT=9
		  octet 2  - fiber port type, NONFIBER=0, SX_FIBER=1,
					 LX_FIBER=2, LHX_FIBER=3, LX_SX_FIBER=4
		(It is obsoleted for Chassis Product)"
	::= { snChasGen 14 }


snChasSpeedLeds OBJECT-TYPE
	SYNTAX	Integer32
	MAX-ACCESS	read-only
	STATUS	current
	DESCRIPTION
		"A bit array that contains the value of the
		front panel media LEDs. This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
		  0        10 MBit
		  1        100 MBit

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snChasGen 15 }


snChasEnableFanTrap OBJECT-TYPE
	SYNTAX	INTEGER { disabled(0), enabled(1) }
	MAX-ACCESS	read-write
	STATUS	current
	DESCRIPTION
		"Indicates whether the SNMP agent process is
		permitted to generate fan failure traps."
	DEFVAL { enabled }
	::= { snChasGen 16 }


snChasIdNumber OBJECT-TYPE
	SYNTAX  DisplayString (SIZE (0..64))
	MAX-ACCESS  read-write
	STATUS  current
	DESCRIPTION
		"An administratively-assigned chassis identity number,
		used by inventory control."
	::= { snChasGen 17 }


snChasActualTemperature OBJECT-TYPE
	SYNTAX  INTEGER (-110..250)
	MAX-ACCESS	read-only
	STATUS	current
	DESCRIPTION
		"Temperature of the chassis. Each unit is 0.5 degrees Celcius.
		Only management module built with temperature sensor hardware
		is applicable. For those non-applicable management module, it
		returns no-such-name."
	::= { snChasGen 18 }


snChasWarningTemperature OBJECT-TYPE
	SYNTAX  INTEGER (0..250)
	MAX-ACCESS	read-write
	STATUS	current
	DESCRIPTION
		"Actual temperature higher than this threshold value will trigger
		the switch to send a temperature warning trap. Each unit is 0.5
		degrees Celcius. Only management module built with temperature
		sensor hardware is applicable. For those non-applicable management
		module, it returns no-such-name."
	::= { snChasGen 19 }


snChasShutdownTemperature OBJECT-TYPE
	SYNTAX  INTEGER (0..250)
	MAX-ACCESS	read-write
	STATUS	current
	DESCRIPTION
		"Actual temperature higher than this threshold value will shutdown
		a partial of the switch hardware to cool down the system. Each unit
		is 0.5 degrees Celcius. Only management module built with temperature
		sensor hardware is applicable. For those non-applicable management
		module, it returns no-such-name."
	::= { snChasGen 20 }

snChasEnableTempWarnTrap OBJECT-TYPE
	SYNTAX	INTEGER { disabled(0), enabled(1) }
	MAX-ACCESS	read-write
	STATUS	current
	DESCRIPTION
		"Indicates whether the SNMP agent process is
		permitted to generate temperature warning traps."
	DEFVAL { enabled }
	::= { snChasGen 21 }

-- Flash Card

snChasFlashCard OBJECT-TYPE
	SYNTAX	Integer32
	MAX-ACCESS	read-only
	STATUS	current
	DESCRIPTION
		"A bit array that contains the value of the
		flash card status. This is a packed bit string. The
		status of each flash card is encoded into one bit.

		  bit value    meaning
		  ---------    -------
			  0         flash card absent.
			  1         flash card present.

		There are up to two flash cards in this release.
		This object is valid if M4 management module is present.
		The following shows the meaning of each bit:
		(bit 0 is the least significant bit).

		  bit position   meaning
		  ------------   -------
			  2-31       reserved
			  1          flash card 2 status
			  0          flash card 1 status"
	::= { snChasGen 22 }


snChasFlashCardLeds OBJECT-TYPE
	SYNTAX   Integer32
	MAX-ACCESS	read-only
	STATUS	current
	DESCRIPTION
		"A bit array that contains the value of the
		flash card LEDs. This is a packed bit string; 
		each LED is encoded into 1 bit for each flash card.

		  bit value  meaning
		  --------   ---------  
			 0         off 
			 1         on 
		"	  
	::= { snChasGen 23 }


snChasNumSlots OBJECT-TYPE
	SYNTAX   Integer32
	MAX-ACCESS	read-only
	STATUS	current
	DESCRIPTION
		"Number of slots of the chassis."
	::= { snChasGen 24 }


snChasArchitectureType OBJECT-TYPE
	SYNTAX		INTEGER {
					stackable(1), -- old stackable
					bigIron(2),
					terathon(3), -- MG-8, NI-40G, IMR
					fifthGen(4) -- XMR, MLX, RX
				}
	MAX-ACCESS	read-only
	STATUS	current
	DESCRIPTION
		"Architecture type."
	::= { snChasGen 25 }


snChasProductType OBJECT-TYPE
	SYNTAX		INTEGER {
		invalid(0),
		mg8(1),
		ni40G(2),
		imr(3),
		biRx800(4),
		niXmr16000(5),
		biRx400(6),
		niXmr8000(7),
		biRx200(8),
		niXmr4000(9),
		niMlx16(10),
		niMlx8(11),
		niMlx4(12),
		niMlx32(13),
		niXmr32000(14),
		biRx32(15),
		niCES2000Series(16),
		niCER2000Series(17),
		biNI2(50),
		biBB(66),
		biM4(77),
		biNI(78),
		biSLB(83),
		biWG(87)
	}
	MAX-ACCESS	read-only
	STATUS	current
	DESCRIPTION
		"Product type."
	::= { snChasGen 26 }

snChasGlobalIgnoreShutdownTemperature OBJECT-TYPE
    SYNTAX  INTEGER { disabled(0), enabled(1) }
    MAX-ACCESS  read-write
    STATUS  current
    DESCRIPTION
         "Enable/Disable the temperature threshold shutdown (Battleshort mode) feature at global level.
        Able to fetch the temperature threshold shutdown (Battleshort mode) feature status enabled (1)/disabled (0) at global level
        The set operation is allowed at global level.
        Set to 1 to enable the temperature threshold shutdown (Battleshort mode) feature at global level.
        Set to 0 to disable the temperature threshold shutdown (Battleshort mode) feature at global level.
        The default status is disabled."

    DEFVAL { disabled }
    ::= { snChasGen 30 }

-- Power Supply Table


snChasPwrSupplyTable OBJECT-TYPE
	SYNTAX	SEQUENCE OF SnChasPwrSupplyEntry
	MAX-ACCESS	not-accessible
	STATUS	current
	DESCRIPTION
		"A table of each power supply information. Only installed
		power supply appears in a table row."
	::= { snChasPwr 1 }

snChasPwrSupplyEntry OBJECT-TYPE
	SYNTAX	SnChasPwrSupplyEntry
	MAX-ACCESS	not-accessible
	STATUS	current
	DESCRIPTION
		"A row in the power supply table."
	INDEX	{ snChasPwrSupplyIndex }
	::= { snChasPwrSupplyTable 1 }

SnChasPwrSupplyEntry ::= SEQUENCE {
	snChasPwrSupplyIndex
		Integer32,
	snChasPwrSupplyDescription
		DisplayString,
	snChasPwrSupplyOperStatus
		INTEGER
	}

snChasPwrSupplyIndex OBJECT-TYPE
	SYNTAX	Integer32
	MAX-ACCESS	read-only
	STATUS	current
	DESCRIPTION
		"The index to power supply table."
	::= { snChasPwrSupplyEntry 1 }

snChasPwrSupplyDescription OBJECT-TYPE
	SYNTAX DisplayString (SIZE(0..128))
	MAX-ACCESS read-only
	STATUS current
	DESCRIPTION
		"The power supply description string."
	::= { snChasPwrSupplyEntry 2 }

snChasPwrSupplyOperStatus OBJECT-TYPE
	SYNTAX  INTEGER {
		other(1),
		normal(2),
		failure(3)
		}
	MAX-ACCESS  read-only
	STATUS  current
	DESCRIPTION
		"The power supply operation status."
	::= { snChasPwrSupplyEntry 3 }


-- Stacking Power Supply Table


snChasPwrSupply2Table OBJECT-TYPE
	SYNTAX	SEQUENCE OF SnChasPwrSupply2Entry
	MAX-ACCESS	not-accessible
	STATUS	current
	DESCRIPTION
		"A table of each power supply information for each unit. Only installed
		power supply appears in a table row."
	::= { snChasPwr 2 }

snChasPwrSupply2Entry OBJECT-TYPE
	SYNTAX	SnChasPwrSupply2Entry
	MAX-ACCESS	not-accessible
	STATUS	current
	DESCRIPTION
		"A row in the power supply table."
	INDEX	{ snChasPwrSupply2Unit, snChasPwrSupply2Index }
	::= { snChasPwrSupply2Table 1 }

SnChasPwrSupply2Entry ::= SEQUENCE {
	snChasPwrSupply2Unit
		Integer32,
	snChasPwrSupply2Index
	Integer32	,
	snChasPwrSupply2Description
		DisplayString,
	snChasPwrSupply2OperStatus
		INTEGER
	}

snChasPwrSupply2Unit OBJECT-TYPE
	SYNTAX	Integer32
	MAX-ACCESS	read-only
	STATUS	current
	DESCRIPTION
		"The index to power supply table."
	::= { snChasPwrSupply2Entry 1 }

snChasPwrSupply2Index OBJECT-TYPE
	SYNTAX	Integer32
	MAX-ACCESS	read-only
	STATUS	current
	DESCRIPTION
		"The index to power supply table."
	::= { snChasPwrSupply2Entry 2}

snChasPwrSupply2Description OBJECT-TYPE
	SYNTAX DisplayString (SIZE(0..128))
	MAX-ACCESS read-only
	STATUS current
	DESCRIPTION
		"The power supply description string."
	::= { snChasPwrSupply2Entry 3 }

snChasPwrSupply2OperStatus OBJECT-TYPE
	SYNTAX  INTEGER {
		other(1),
		normal(2),
		failure(3)
		}
	MAX-ACCESS  read-only
	STATUS  current
	DESCRIPTION
		"The power supply operation status."
	::= { snChasPwrSupply2Entry 4 }


-- Fan Table


snChasFanTable OBJECT-TYPE
	SYNTAX	SEQUENCE OF SnChasFanEntry
	MAX-ACCESS	not-accessible
	STATUS	current
	DESCRIPTION
		"A table of each fan information. Only installed
		fan appears in a table row."
	::= { snChasFan 1 }

snChasFanEntry OBJECT-TYPE
	SYNTAX	SnChasFanEntry
	MAX-ACCESS	not-accessible
	STATUS	current
	DESCRIPTION
		"A row in the fan table."
	INDEX	{ snChasFanIndex }
	::= { snChasFanTable 1 }

SnChasFanEntry ::= SEQUENCE {
	snChasFanIndex
		Integer32,
	snChasFanDescription
		DisplayString,
	snChasFanOperStatus
		INTEGER
	}

snChasFanIndex OBJECT-TYPE
	SYNTAX	Integer32
	MAX-ACCESS	read-only
	STATUS	current
	DESCRIPTION
		"The index to fan table."
	::= { snChasFanEntry 1 }

snChasFanDescription OBJECT-TYPE
	SYNTAX DisplayString (SIZE(0..128))
	MAX-ACCESS read-only
	STATUS current
	DESCRIPTION
		"The fan description string."
	::= { snChasFanEntry 2 }

snChasFanOperStatus OBJECT-TYPE
	SYNTAX  INTEGER {
		other(1),
		normal(2),
		failure(3)
		}
	MAX-ACCESS  read-only
	STATUS  current
	DESCRIPTION
		"The fan operation status."
	::= { snChasFanEntry 3 }


-- Stacking Fan Table

snChasFan2Table OBJECT-TYPE
	SYNTAX	SEQUENCE OF SnChasFan2Entry
	MAX-ACCESS	not-accessible
	STATUS	current
	DESCRIPTION
		"A table of each fan information for each unit. Only installed
		fan appears in a table row."
	::= { snChasFan 2 }

snChasFan2Entry OBJECT-TYPE
	SYNTAX	SnChasFan2Entry
	MAX-ACCESS	not-accessible
	STATUS	current
	DESCRIPTION
		"A row in the fan table."
	INDEX	{ snChasFan2Unit, snChasFan2Index }
	::= { snChasFan2Table 1 }

SnChasFan2Entry ::= SEQUENCE {
	snChasFan2Unit
		Integer32,
	snChasFan2Index
		Integer32,
	snChasFan2Description
		DisplayString,
	snChasFan2OperStatus
		INTEGER
	}

snChasFan2Unit OBJECT-TYPE
	SYNTAX	Integer32
	MAX-ACCESS	read-only
	STATUS	current
	DESCRIPTION
		"The index to fan table."
	::= { snChasFan2Entry 1 }
	
snChasFan2Index OBJECT-TYPE
	SYNTAX	Integer32
	MAX-ACCESS	read-only
	STATUS	current
	DESCRIPTION
		"The index to fan table."
	::= { snChasFan2Entry 2 }

snChasFan2Description OBJECT-TYPE
	SYNTAX DisplayString (SIZE(0..128))
	MAX-ACCESS read-only
	STATUS current
	DESCRIPTION
		"The fan description string."
	::= { snChasFan2Entry 3 }

snChasFan2OperStatus OBJECT-TYPE
	SYNTAX  INTEGER {
		other(1),
		normal(2),
		failure(3)
		}
	MAX-ACCESS  read-only
	STATUS  current
	DESCRIPTION
		"The fan operation status."
	::= { snChasFan2Entry 4 }


-- Stacking Chassis unit Information

snChasUnitTable OBJECT-TYPE
	SYNTAX	SEQUENCE OF SnChasUnitEntry
	MAX-ACCESS	not-accessible
	STATUS	current
	DESCRIPTION
		"A table of chassis  information for each unit. Only active
		chassis appears in a table row."
	::= { snChasUnit 1 }

snChasUnitEntry OBJECT-TYPE
	SYNTAX	SnChasUnitEntry
	MAX-ACCESS	not-accessible
	STATUS	current
	DESCRIPTION
		"A row in the chassis table."
	INDEX	{ snChasUnitIndex }
	::= { snChasUnitTable 1 }

SnChasUnitEntry ::= SEQUENCE {
	snChasUnitIndex
		Integer32,
	snChasUnitSerNum
		DisplayString,
	snChasUnitNumSlots
		Integer32,
	snChasUnitActualTemperature
		INTEGER,
	snChasUnitWarningTemperature
		INTEGER,
	snChasUnitShutdownTemperature
		INTEGER,
	snChasUnitPartNum
		DisplayString,
    snChasUnitIgnoreShutdownTemperature
        INTEGER,
	snChasUnitFanless
		INTEGER
	}

snChasUnitIndex OBJECT-TYPE
	SYNTAX	Integer32
	MAX-ACCESS	read-only
	STATUS	current
	DESCRIPTION
		"The index to chassis table."
	::= { snChasUnitEntry 1 }

snChasUnitSerNum OBJECT-TYPE
	SYNTAX	DisplayString (SIZE(0..128))
	MAX-ACCESS	read-only
	STATUS	current
	DESCRIPTION
		"The serial number of the chassis for each unit. If the
		serial number is unknown or unavailable then
		the value should be a zero length string."
	::= { snChasUnitEntry 2 }

snChasUnitNumSlots OBJECT-TYPE
	SYNTAX	Integer32
	MAX-ACCESS	read-only
	STATUS	current
	DESCRIPTION
		"Number of slots of the chassis for each unit."
	::= { snChasUnitEntry 3 }

	
snChasUnitActualTemperature OBJECT-TYPE
	SYNTAX  INTEGER (-110..250)
	MAX-ACCESS	read-only
	STATUS	current
	DESCRIPTION
		"Temperature of the chassis. Each unit is 0.5 degrees Celcius.
		Only management module built with temperature sensor hardware
		is applicable. For those non-applicable management module, it
		returns no-such-name."
	::= { snChasUnitEntry 4 }


snChasUnitWarningTemperature OBJECT-TYPE
	SYNTAX  INTEGER (0..250)
	MAX-ACCESS	read-write
	STATUS	current
	DESCRIPTION
		"Actual temperature higher than this threshold value will trigger
		the switch to send a temperature warning trap. Each unit is 0.5
		degrees Celcius. Only management module built with temperature
		sensor hardware is applicable. For those non-applicable management
		module, it returns no-such-name."
	::= { snChasUnitEntry 5 }


snChasUnitShutdownTemperature OBJECT-TYPE
	SYNTAX  INTEGER (0..250)
	MAX-ACCESS	read-only
	STATUS	current
	DESCRIPTION
		"Actual temperature higher than this threshold value will shutdown
		a partial of the switch hardware to cool down the system. Each unit
		is 0.5 degrees Celcius. Only management module built with temperature
		sensor hardware is applicable. For those non-applicable management
		module, it returns no-such-name."
	::= { snChasUnitEntry 6 }

snChasUnitPartNum OBJECT-TYPE
	SYNTAX	DisplayString
	MAX-ACCESS	read-only
	STATUS	current
	DESCRIPTION
		"The part number of the chassis for each unit. If the
		part number is unknown or unavailable then
		the value should be a zero length string."
	::= { snChasUnitEntry 7 }

snChasUnitIgnoreShutdownTemperature OBJECT-TYPE
    SYNTAX  INTEGER { disabled(0), enabled(1) }
    MAX-ACCESS  read-write
    STATUS  current
    DESCRIPTION
        "Enable/Disable the temperature threshold shutdown (Battleshort mode) feature on the unit specific.
        Able to fetch the temperature threshold shutdown (Battleshort mode) feature status enabled (1)/disabled (0) on the unit specific
        The set operation is allowed at unit specific.
        Set to 1 to enable the temperature threshold shutdown (Battleshort mode) feature on the unit specific.
        Set to 0 to disable the temperature threshold shutdown (Battleshort mode) feature on the unit specific.
        The default status is disabled."
    DEFVAL { disabled }
    ::= { snChasUnitEntry 8 }

snChasUnitFanless OBJECT-TYPE
	SYNTAX  INTEGER {
		 none(0),
		 enabled(1), 
		 disabled(2)
		 }
    MAX-ACCESS  read-write
    STATUS  current
    DESCRIPTION
	"Fanless mode can be enabled or disabled on certain FI devices.
	none (0): not applicable to the device.
	enabled(1): fanless mode is enabled on the device
	disabled(2): fanless mode is disabled on the device.
	The default value is disabled (2) .
	Note: that Fanless mode can be applicable to ICX7150-24P and ICX7150-48P only"
	DEFVAL { disabled }
	::= { snChasUnitEntry 9 }

-- Agent Groups

snAgentGbl				OBJECT IDENTIFIER ::= { snAgentSys 1 }
snAgentBrd				OBJECT IDENTIFIER ::= { snAgentSys 2 }
snAgentTrp 				OBJECT IDENTIFIER ::= { snAgentSys 3 }
snAgentBoot				OBJECT IDENTIFIER ::= { snAgentSys 4 }
snAgCfgEos				OBJECT IDENTIFIER ::= { snAgentSys 5 }
snAgentLog				OBJECT IDENTIFIER ::= { snAgentSys 6 }
snAgentSysParaConfig	OBJECT IDENTIFIER ::= { snAgentSys 7 }
snAgentConfigModule		OBJECT IDENTIFIER ::= { snAgentSys 8 }
snAgentUser				OBJECT IDENTIFIER ::= { snAgentSys 9 }
snAgentRedundant		OBJECT IDENTIFIER ::= { snAgentSys 10 }
snAgentCpu			    OBJECT IDENTIFIER ::= { snAgentSys 11 }
snAgentHw			    OBJECT IDENTIFIER ::= { snAgentSys 12 }
snAgentTemp			    OBJECT IDENTIFIER ::= { snAgentSys 13 }
--snAgentPoe			OBJECT IDENTIFIER ::= { snAgentSys 14 } this change due to the duplicate OID issue (FI-247705)
snAgentLicense			OBJECT IDENTIFIER ::= { snAgentSys 15 }
  


-- SECTION 2: MIB Objects


-- Agent's Global Group
	
snAgReload OBJECT-TYPE
	SYNTAX	INTEGER {
		other(1),
		running(2),
		reset(3),
		busy(4)
		}
	MAX-ACCESS	read-write
	STATUS	current
	DESCRIPTION
		"Action object to reboot the agent.
		The following values can only be read:
		  other(1).....agent in unknown or other state
		  running(2)...agent running
		  busy(4).......reload not allowed at this time, flash is busy

		The following value can be written:
		  reset(3).....do a hard reset

		The agent will return a
		response before the action occurs."
	::= { snAgentGbl 1 }

snAgEraseNVRAM OBJECT-TYPE
	SYNTAX	INTEGER {
		normal(1),
		error(2),
		erase(3),
		erasing(4),		
		busy(5)
		}
	MAX-ACCESS	read-write
	STATUS   	deprecated
	DESCRIPTION
		"This object is not supported from FI9010, please use snAgEraseConfig
		 Action object to erase NVRAM of the agent.
		The following values can only be read:
		  normal(1)
		  error(2)... operation failed or bad flash
		  erasing(4)...agent is erasing NVRAM flash
		  busy(5).......operation not allowed at this time, flash is busy

		The following value can be written:
		  erase(3).....do erase 

		The agent will return a response even before the erase is done.
		And the read value will be erasing until erase is done.
		And the erase request will be rejected until error or normal."
	::= { snAgentGbl 2 }

snAgWriteNVRAM OBJECT-TYPE
	SYNTAX	INTEGER {
		normal(1),
		error(2),
		write(3),
		writing(4),		
		busy(5)
		}
	MAX-ACCESS	read-write
	STATUS 		deprecated	
	DESCRIPTION
		"This object is not supported from FI9010, please use snAgSaveConfig
		Action object to save all configuration info to
		 NVRAM of the agent.
		The following values can only be read:
		  normal(1)
		  error(2)... operation failed or bad flash
		  writing(4)...agent is writing NVRAM flash
		  busy(5).......operation not allowed at this time, flash is busy

		The following value can be written:
		  write(3).....do write 

		The agent will return a response even before the write is done.
		And the read value will be writing until write is done.
		And the write request will be rejected until error or normal."
	::= { snAgentGbl 3 }

snAgConfigFromNVRAM OBJECT-TYPE
	SYNTAX	INTEGER {
		normal(1),
		error(2),
		config(3),
		configing(4),
		busy(5)
	}
	MAX-ACCESS	not-accessible
	STATUS		deprecated	
	DESCRIPTION
		"This object is not supported from FI9010,
		Action object to config the switch from NVRAM of the agent.
		The following values can only be read:
		  normal(1)
		  error(2)... operation failed or bad flash
		  configing(4)...configing from NVRAM flash is in process.
		  busy(5).......operation not allowed at this time, flash is busy
		The following value can be written:
		  config(3).....do config 

		The agent will return a response after config is done."
	::= { snAgentGbl 4 }

--  image and config file down/up load 

-- snAgTftpServerIp object is deprecated, and added following 2 new objects.
-- 1. "snAgTftpServerAddrType" represents Ipv4 and Ipv6 address types
-- 2. "snAgTftpServerAddr" reprasents Ipv4 and Ipv6 addresses

snAgTftpServerIp OBJECT-TYPE
	SYNTAX	IpAddress
	MAX-ACCESS	read-write
	STATUS	deprecated
	DESCRIPTION
		"The tftp server address, this will be used for both download/upload
		 image file and config file."
	::= { snAgentGbl 5 }

snAgImgFname OBJECT-TYPE
	SYNTAX	DisplayString (SIZE (0..256))
	MAX-ACCESS	read-write
	STATUS	current
	DESCRIPTION
		"Name of the image file including path currently associated
		with the system. When the object is not used, the value is a
		zero length string."
	::= { snAgentGbl 6 }


snAgImgLoad OBJECT-TYPE
	SYNTAX	INTEGER {
		normal(1),
		flashPrepareReadFailure(2),
		flashReadError(3),
		flashPrepareWriteFailure(4),
		flashWriteError(5),
		tftpTimeoutError(6),
		tftpOutOfBufferSpace(7),
		tftpBusy(8),
		tftpRemoteOtherErrors(9), 
		tftpRemoteNoFile(10), 
		tftpRemoteBadAccess(11), 
		tftpRemoteDiskFull(12), 
		tftpRemoteBadOperation(13), 
		tftpRemoteBadId(14), 
		tftpRemoteFileExists(15), 
		tftpRemoteNoUser(16), 
		operationError(17),
		loading(18),
		uploadMPPrimary(19),
		downloadMPPrimary(20),
		uploadMPSecondary(21),
		downloadMPSecondary(22),
		tftpWrongFileType(23),
		downloadSPPrimary(24),
		downloadSPSecondary(25),
		uploadMPBootROM(26),
		downloadMPBootROM(27),
		uploadMPBootTFTP(28),
		downloadMPBootTFTP(29),
		uploadMPMonitor(30),
		downloadMPMonitor(31),
		downloadSPBootROM(32),
		downloadUfiPrimary(34),
        downloadUfiSecondary(35)
		}
	MAX-ACCESS	read-write
	STATUS	current
	DESCRIPTION
		"Action object to down/up load a new image
		to the agent. The following values:
		Error values: from normal(1) to operationError(17) and tftpWrongFileType(23).
		  loading(18) .. operation is in process.

		The following values are used for set :
		  uploadMPPrimary(19)..upload the Primary image from MP flash to tftp server.
		  downloadMPPrimary(20)..download the Primary image from tftp server to MP flash.
		  uploadMPSecondary(21)..upload the Secondary image from MP flash to tftp server.
		  downloadMPSecondary(22)..download the Secondary image from tftp server to MP flash.
		  downloadSPPrimary(24)..download the Primary image from tftp server to SP flash.
		  downloadSPSecondary(25)..download the Secondary image from tftp server to SP flash.
		  uploadMPBootROM(26)..upload the Boot from flash image from MP flash to tftp server.
		  downloadMPBootROM(27)..download the Boot from flash image from tftp server to MP flash.
		  uploadMPBootTFTP(28)..upload the Boot from TFTP image from MP flash to tftp server.
		  downloadMPBootTFTP(29)..download the Boot from TFTP image from tftp server to MP flash.
		  uploadMPMonitor(30)..upload the Monitor image from MP flash to tftp server.
		  downloadMPMonitor(31)..download the Monitor image from tftp server to MP flash.
		  downloadSPBootROM(32)..download the Boot image from tftp server to SP flash.
		  downloadUfiPrimary(34)..download the Primary UFI image from tftp server to flash.
          downloadUfiSecondary(35)..download the Secondary UFI image from tftp server to flash.
	
		MP is the management processor, SP is the switch processor.

		The image filename is defined in
		snAgImgFname. The tftp server address is defined in snAgTftpServerIp.
		Atomic set of snAgImgLoad, snAgImgFname and  
		snAgTftpServerIp is required to allow down/up load to happen. 
		And the write request will be rejected during loading until error 
		or normal."
	::= { snAgentGbl 7 }

snAgCfgFname OBJECT-TYPE
	SYNTAX	DisplayString (SIZE (0..32))
	MAX-ACCESS	read-write
	STATUS	current
	DESCRIPTION
		"Name of the config file(s) including path currently associated
		with the system. Some agents in special
		situations may support a value which contains
		multiple file names instead of a single file
		name. Multiple names are specified as a list
		of file names separated by semicolons (;).
		When the object is not used, the value is a
		zero length string."
	::= { snAgentGbl 8 }

snAgCfgLoad OBJECT-TYPE
	SYNTAX	INTEGER {
		normal(1),
		flashPrepareReadFailure(2),
		flashReadError(3),
		flashPrepareWriteFailure(4),
		flashWriteError(5),
		tftpTimeoutError(6),
		tftpOutOfBufferSpace(7),
		tftpBusy(8),
		tftpRemoteOtherErrors(9), 
		tftpRemoteNoFile(10), 
		tftpRemoteBadAccess(11), 
		tftpRemoteDiskFull(12), 
		tftpRemoteBadOperation(13), 
		tftpRemoteBadId(14), 
		tftpRemoteFileExists(15), 
		tftpRemoteNoUser(16), 
		operationError(17),
		loading(18),
		uploadFromFlashToServer(20),
		downloadToFlashFromServer(21),
		uploadFromDramToServer(22),
		downloadToDramFromServer(23),
		uploadFromFlashToNMS(24),
		downloadToFlashFromNMS(25),
		uploadFromDramToNMS(26),
		downloadToDramFromNMS(27),
		operationDoneWithNMS(28),
		tftpWrongFileType(29),
		downloadToDramFromServerOverwrite(30)
		}
	MAX-ACCESS	read-write
	STATUS	current
	DESCRIPTION
		"Action object to down/up load a config image
		to the agent. The following values can be
		read :
		Error values: from normal(1) to operationError(17) and tftpWrongFileType(29).
		  loading(18) .. operation is in process.


		The following value can be used to set:
		  uploadFromFlashToServer(20)..upload the config from flash
											  to tftp server. 
		  downloadToFlashFromServer(21)..download the config to flash
												from tftp server.
		  uploadFromDramToServer(22)..upload the config from DRAM 
											 to tftp server.
		  downloadToDramFromServer(23)..download the config to DRAM
											   from tftp server.
		  downloadToDramFromServerOverwrite(30)..download the config to DRAM
											   from tftp server, clear the running-config,
											   and overwrite with the new config.

		The following value can be used to set:
		  uploadFromFlashToNMS(24)..upload the config from flash to NMS. 
		  downloadToFlashFromNMS(25)..download the config to flash from NMS.
		  uploadFromDramToNMS(26)..upload the config from DRAM to NMS.
		  downloadToDramFromNMS(27)..download the config to DRAM from NMS.

		The config filename is defined in
		snAgCfgFname. The tftp server address is defined in snAgTftpServerIp.
		Atomic set of snAgCfgLoad, snAgCfgFname and  snAgTftpServerIp is
		required to allow down/up load to happen. And the write request 
		will be rejected during loading until error or normal.
		For those NMS commands from (24) to (27), The snAgCfgEosTable MIB must
		be sent along in one PDU.  A seperate write memory cli or set 
		snAgWriteNVRAM is required to save the config to NVRAM."
	::= { snAgentGbl 9 }

-- default gateway ip address

snAgDefGwayIp OBJECT-TYPE
	SYNTAX	IpAddress
	MAX-ACCESS	read-write
	STATUS	current
	DESCRIPTION
		"The default gateway (router) address." 	
	::= { snAgentGbl 10 }


-- image version

snAgImgVer OBJECT-TYPE
	SYNTAX	DisplayString (SIZE(0..32))
	MAX-ACCESS	read-only
	STATUS	current
	DESCRIPTION
		"The version of the running software in the form
		'major.minor.maintenance[letters]'."
	::= { snAgentGbl 11 }

snAgFlashImgVer OBJECT-TYPE
	SYNTAX	DisplayString (SIZE(0..32))
	MAX-ACCESS	read-only
	STATUS	current
	DESCRIPTION
		"The version of the software image saved in local
		storage such as flash memory in the form
		'major.minor.maintenance[letters]'. If not
		known or not available, then the value is
		a zero length string."
	::= { snAgentGbl 12 }

snAgGblIfIpAddr OBJECT-TYPE
	SYNTAX	IpAddress
	MAX-ACCESS	read-write
	STATUS	current
	DESCRIPTION
		"The interface ip address."
	::= { snAgentGbl 13 }

snAgGblIfIpMask OBJECT-TYPE
	SYNTAX	IpAddress
	MAX-ACCESS	read-write
	STATUS	current
	DESCRIPTION
		"The interface ip address mask."
	::= { snAgentGbl 14 }

snAgGblPassword OBJECT-TYPE
	SYNTAX	DisplayString (SIZE (0..97))
	MAX-ACCESS	read-write
	STATUS  deprecated
	DESCRIPTION
		"System Security Access Password and this is only 
		 allowed to use for setting but not for reading.
		   An SNMP-Get will get an null string.
		   By default, this object needs to be in the same PDU while
		 doing Set operation some critical SNMP objects.
		   If command 'no snmp-server pw-check' is configured on
		the device, then this object is not needed in the PDU.
		   The value of this object depends on the authentication
		 method configured for SNMP.
		   If there's no AAA authentication configuration for SNMP,
		this object will have the enable superuser password. 
		   If the AAA authentication for SNMP is configured and has 
		leading method as enable or line, this object will have 
		the corresponding enable or line password.
		   If the switch has AAA authentication for SNMP operation,
		and the method specified is one of local, TACACS+, or RADIUS,
		this object will have format '<username> <password>' 
		(note one space character in between).
		  The max size allows concatenation of max 48 octets of 
		 username and 48 octets of password, with one blank character"
	::= { snAgentGbl 15 }

snAgTrpRcvrCurEntry OBJECT-TYPE
	SYNTAX	INTEGER (0..255)
	MAX-ACCESS	read-only
	STATUS	current
	DESCRIPTION
		"The current total entries of the Trap 
		Receiver Table are created."
	::= { snAgentGbl 16 }

snAgGblDataRetrieveMode OBJECT-TYPE
	SYNTAX  INTEGER {
		nextbootCfg(0),             
		operationalData(1)
		}
	MAX-ACCESS  read-write
	STATUS  current
	DESCRIPTION
		"By default, this mode is set to nextbootCfg(0).
		 The VLAN Table and Port-STP Table data will be retrieved
		 according to this mode.
		 nextbootCfg(0).........the nextboot configuration data are retrieved
		 operationalData(1)..........the current running data are retrieved"  
	::= { snAgentGbl 19 }


snAgSystemLog OBJECT-TYPE
	SYNTAX	OCTET STRING (SIZE(5))	
	MAX-ACCESS	read-write
	STATUS	current
	DESCRIPTION
		"The system log object to indicate whether any Network
		 Management Station(NMS) has login.  The first byte
		 of the octet string is the value decribed below and 
		 followed by 4 bytes of secret code.
		  login(1)..... a value for a NMS to login.
		  heartbeat(2)... a value for the login NMS periodically to 
						checkin; Otherwise, the Agent will automatically
						set this object to logout(3) after a timeout 
						period. 
		  logout(3).... a value for a NMS to logout.
		  changePassword(4).... a value for the login NMS to change
						password, only if snAgGblPasswordChangeMode
						was configured to 'anyMgmtEntity'.
		  changeReadOnlyCommunity(5).... a value for the login NMS
						to change the read-only community string,
						only if snAgGblPasswordChangeMode was
						configured to 'anyMgmtEntity'.
		  changeReadWriteCommunity(6).... a value for the login NMS
						to change the read-write community string,
						only if snAgGblPasswordChangeMode was
						configured to 'anyMgmtEntity'."
	::= { snAgentGbl 20 }


snAgGblEnableColdStartTrap OBJECT-TYPE
	SYNTAX	INTEGER { disabled(0), enabled(1) }
	MAX-ACCESS	read-write
	STATUS	current
	DESCRIPTION
		"Indicates whether the SNMP agent process is
		permitted to generate cold start traps."
	DEFVAL { enabled }
	::= { snAgentGbl 21 }


snAgGblEnableLinkUpTrap OBJECT-TYPE
	SYNTAX	INTEGER { disabled(0), enabled(1) }
	MAX-ACCESS	read-write
	STATUS	current
	DESCRIPTION
		"Indicates whether the SNMP agent process is
		permitted to generate link up traps."
	DEFVAL { enabled }
	::= { snAgentGbl 22 }


snAgGblEnableLinkDownTrap OBJECT-TYPE
	SYNTAX	INTEGER { disabled(0), enabled(1) }
	MAX-ACCESS	read-write
	STATUS	current
	DESCRIPTION
		"Indicates whether the SNMP agent process is
		permitted to generate link down traps."
	DEFVAL { enabled }
	::= { snAgentGbl 23 }

snAgGblPasswordChangeMode OBJECT-TYPE
	SYNTAX	INTEGER {
			  anyMgmtEntity(1),
			  consoleAndTelnet(2),
			  consoleOnly(3),
			  telnetOnly(4) }
	MAX-ACCESS	read-only
	STATUS	current
	DESCRIPTION
		"Specify which management entity is allowed to change
		the password. 'anyMgmtEntity' management entities are
		SNMP management station, console command line interface,
		and telnet command line interface. For security reason,
		this object can only be modified by console command line
		interface or telnet command line interface. The default
		value is 'consoleAndTelnet', of which both console and
		telnet command line interfaces are allowed to change
		the password."
	::= { snAgentGbl 24 }

snAgGblReadOnlyCommunity OBJECT-TYPE
	SYNTAX	DisplayString (SIZE (0..32))
	MAX-ACCESS	read-write
	STATUS	current
	DESCRIPTION
		"SNMP read community string and this is only allowed
		to use for setting but not for reading. An SNMP-Get
		will get an zero length string.
		  Set operation on this object is allowed only if command
		'password-change any' is configured on the target device."
	::= { snAgentGbl 25 }

snAgGblReadWriteCommunity OBJECT-TYPE
	SYNTAX	DisplayString (SIZE (0..32))
	MAX-ACCESS	read-write
	STATUS	current
	DESCRIPTION
		"SNMP read-write community string and this is only
		allowed to use for setting but not for reading. An
		SNMP-Get will get an zero length string.
		  Set operation on this object is allowed only if command
		'password-change any' is configured on the target device."
	::= { snAgentGbl 26 }

snAgGblCurrentSecurityLevel OBJECT-TYPE
	SYNTAX	INTEGER (0..5)
	MAX-ACCESS	read-only
	STATUS	current
	DESCRIPTION
		"This represnts the current log-in security level.
		Each level of security requires a password to permit
		user for different system configurations."
	::= { snAgentGbl 27 }

snAgGblSecurityLevelSet OBJECT-TYPE
	SYNTAX	INTEGER (0..5)
	MAX-ACCESS	read-write
	STATUS	current
	DESCRIPTION
		"This shows which the security level password to be set."
	::= { snAgentGbl 28 }

snAgGblLevelPasswordsMask OBJECT-TYPE
	SYNTAX   Integer32 
	MAX-ACCESS	read-only
	STATUS	current
	DESCRIPTION
		"This shows the bitmap of level passwords which successfully assigned to the system."
	::= { snAgentGbl 29 }

snAgGblQueueOverflow OBJECT-TYPE
	SYNTAX	INTEGER	{ false(0), true(1) } 
	MAX-ACCESS	read-only
	STATUS	current
	DESCRIPTION
		"false - The device queues are not overflow.
		 true  - The device queues are overflow."
	::= { snAgentGbl 30 }

snAgGblBufferShortage OBJECT-TYPE
	SYNTAX	INTEGER	{ false(0), true(1) } 
	MAX-ACCESS	read-only
	STATUS	current
	DESCRIPTION
		"false - The device buffers are adequate.
		 true  - The device buffers are in shortage."
	::= { snAgentGbl 31 }

snAgGblDmaFailure OBJECT-TYPE
	SYNTAX	INTEGER	{ false(0), true(1) } 
	MAX-ACCESS	read-only
	STATUS	current
	DESCRIPTION
		"false - The device DMAs are in good condition.
		 true  - One of the DMAs in the device fails."
	::= { snAgentGbl 32 }

snAgGblResourceLowWarning OBJECT-TYPE
	SYNTAX	INTEGER	{ false(0), true(1) } 
	MAX-ACCESS	read-only
	STATUS	current
	DESCRIPTION
		"false - No, the device does not have resource-low-warning.
		 true  - Yes, the device does have resource-low-warning."
	::= { snAgentGbl 33 }

snAgGblExcessiveErrorWarning OBJECT-TYPE
	SYNTAX	INTEGER	{ false(0), true(1) } 
	MAX-ACCESS	read-only
	STATUS	current
	DESCRIPTION
		"false - No, the device does not have any excessive collision, FCS errors, alignment warning etc.
		 true  - Yes, the device does have."
	::= { snAgentGbl 34 }

snAgGblCpuUtilData OBJECT-TYPE
	SYNTAX	Gauge32
	MAX-ACCESS	read-only
	STATUS	current
	DESCRIPTION
		"The statistics collection of utilization of the CPU in the device. Reading this object resets all the counters.  Therefore, a user need not set snAgGblUtilCollect."
	::= { snAgentGbl 35 }

snAgGblCpuUtilCollect OBJECT-TYPE
	SYNTAX	INTEGER { disabled(0), enabled(1) }
	MAX-ACCESS	read-write
	STATUS	deprecated
	DESCRIPTION
		"enable(1)  - The beginning of statistics collection of utilization of the CPU in the device.
		 disable(0) - The end of statistics collection of utilization of the CPU in the device.
			   This object is deprecated. User need not set this object. User can read snAgGblCpuUtilData to reset all the counters. "
	::= { snAgentGbl 36 }

snAgGblTelnetTimeout OBJECT-TYPE
	SYNTAX	INTEGER (0..240)
	MAX-ACCESS	read-write
	STATUS	current
	DESCRIPTION
		"Telnet session idling timeout value. Writing value 0 to
		this object never timeouts any telnet sessions. Each value
		unit is one minute."
	::= { snAgentGbl 37 }

snAgGblEnableWebMgmt OBJECT-TYPE
	SYNTAX	INTEGER { disabled(0), enabled(1) }
	MAX-ACCESS	read-write
	STATUS	current
	DESCRIPTION
		"Enable/disable web management."
	DEFVAL { enabled }
	::= { snAgentGbl 38 }

snAgGblSecurityLevelBinding OBJECT-TYPE
	SYNTAX   Integer32
	MAX-ACCESS	read-only
	STATUS	current
	DESCRIPTION
		"This represnts the binding of a given password to which
		security level. A value of 255 indicates an invalid
		binding."
	::= { snAgentGbl 39 }

snAgGblEnableSLB OBJECT-TYPE
	SYNTAX	INTEGER { disabled(0), enabled(1) }
	MAX-ACCESS	read-only
	STATUS	current
	DESCRIPTION
		"Enable/disable Server Load Balancing."
	::= { snAgentGbl 40 }

snAgSoftwareFeature OBJECT-TYPE
	SYNTAX  OCTET STRING
	MAX-ACCESS	read-only
	STATUS	current
	DESCRIPTION
		"A bit string representing the software feature of the running
		switch/router image. These features were conditional compiled
		to different product images. For each bit, exist feature has
		a value of 1, but non-exist feature has a value of 0.
		  octet 0, bit 0 - RMON
		  octet 0, bit 1 - ipx switching
		  octet 0, bit 2 - server load balancing
		  octet 0, bit 3 - layer 3 filter in switch
		  octet 0, bit 4 - ipx routing
		  octet 0, bit 5 - appletalk routing
		  octet 0, bit 6 - ip multicast routing
		  octet 0, bit 7 - local access control
		  octet 1, bit 0 - BGP routing
		  octet 1, bit 1 - loopback interface
		  octet 1, bit 2 - BigIron multi-management module
		  octet 1, bit 3 - BigIron SYSIF II
		  octet 1, bit 4 - BigIron POS support
		  octet 1, bit 5 - appletalk cable vlan
		  octet 1, bit 6 - 64 subnet
		  octet 1, bit 7 - multi-slot trunk
		  octet 2, bit 0 - TACACS
		  octet 2, bit 1 - Gigabit Ethernet port auto-negotiation mode
		  octet 2, bit 2 - FSRP
		  octet 2, bit 3 - Exodus requested OSPF enhancement
		  octet 2, bit 4 - OSPF NSSA
		  octet 2, bit 5 - POS
		  octet 2, bit 6 - QOS
		  octet 2, bit 7 - Single Span
		  octet 3, bit 0 - Fast Span
		  octet 3, bit 1 - Base L3
		  octet 3, bit 2 - static log buffer
		  octet 3, bit 3 - L2 POS
		  octet 3, bit 4 - BI15K
		  octet 3, bit 5 - L2 ATM
		  octet 3, bit 6 - ATM
		  octet 3, bit 7 - NETFLOW
		  octet 4, bit 0 - SFLOW
		  octet 4, bit 1 - GVRP
		  octet 4, bit 2 - GARP
		  octet 4, bit 3 - dynamic trunk
		  octet 4, bit 4 - IGC 8G
		  octet 4, bit 5 - rate limit
		  octet 4, bit 6 - IPC rate limit
		  octet 4, bit 7 - MPLS
		  octet 5, bit 0 - ISIS
		  octet 5, bit 1 - link aggregation
		  octet 5, bit 2 - port dual mode
		  octet 5, bit 3 - private vlan
		  octet 5, bit 4 - MBGP
		  octet 5, bit 5 - ipv6 protocol vlan
		  octet 5, bit 6 - X10G
		  octet 5, bit 7 - fastiron edge switch/router (gridiron)
		  octet 6, bit 0 - FDP
		  octet 6, bit 1 - port tag type
		  octet 6, bit 2 - wireless capable
		  octet 6, bit 3 - snSwPortVlanId object has changed from read-only to read-write
		  octet 6, bit 4 - LLDP
		Bit 0 is the least significant bit of an octet, and
		bit 7 is the most significant bit of an octet."
	::= { snAgentGbl 41 }

snAgGblEnableModuleInsertedTrap OBJECT-TYPE
	SYNTAX	INTEGER { disabled(0), enabled(1) }
	MAX-ACCESS	read-write
	STATUS	current
	DESCRIPTION
		"Indicates whether the SNMP agent process is permitted to
		generate hardware module inserted to chassis traps."
	DEFVAL { enabled }
	::= { snAgentGbl 42 }

snAgGblEnableModuleRemovedTrap OBJECT-TYPE
	SYNTAX	INTEGER { disabled(0), enabled(1) }
	MAX-ACCESS	read-write
	STATUS	current
	DESCRIPTION
		"Indicates whether the SNMP agent process is permitted to
		generate hardware module removed from chassis traps."
	DEFVAL { enabled }
	::= { snAgentGbl 43 }

snAgGblTrapMessage OBJECT-TYPE
	SYNTAX  DisplayString
	MAX-ACCESS	read-only
	STATUS	current
	DESCRIPTION
		"A generic trap message string."
	::= { snAgentGbl 44 }

snAgGblEnableTelnetServer OBJECT-TYPE
	SYNTAX	INTEGER { disabled(0), enabled(1) }
	MAX-ACCESS	read-write
	STATUS	current
	DESCRIPTION
		"Enable or disable telnet server in device."
	DEFVAL { enabled }
	::= { snAgentGbl 45 }

snAgGblTelnetPassword OBJECT-TYPE
	SYNTAX	DisplayString (SIZE (0..48))
	MAX-ACCESS	read-write
	STATUS	current
	DESCRIPTION
		"Telnet Access Password and this is only 
		 useful for write operation. A read operation
		 get a null string.
		  Set operation on this object is allowed only if command
		'password-change any' is configured on the target device.
		  Another configuration affecting this is
		'no snmp-server pw-check'. If its configured on the device,
		there's no need to pass another varbind snAgGblPassword.
		By default, 'snmp-server pw-check' is true, and thus needs
		to have snAgGblPassword along with this object.
		in the same Set PDU."
	::= { snAgentGbl 46 }

snAgBuildDate OBJECT-TYPE
	SYNTAX	DisplayString (SIZE(0..32))
	MAX-ACCESS	read-only
	STATUS	current
	DESCRIPTION
		"The date of the built software."
	::= { snAgentGbl 47 }

snAgBuildtime OBJECT-TYPE
	SYNTAX	DisplayString (SIZE(0..32))
	MAX-ACCESS	read-only
	STATUS	current
	DESCRIPTION
		"The time of the built software."
	::= { snAgentGbl 48 }

snAgBuildVer OBJECT-TYPE
	SYNTAX	DisplayString (SIZE(0..32))
	MAX-ACCESS	read-only
	STATUS	current
	DESCRIPTION
		"The version of the built software in the form
		'major.minor.maintenance[letters]'."
	::= { snAgentGbl 49 }

snAgGblCpuUtil1SecAvg OBJECT-TYPE
	SYNTAX	Gauge32
	MAX-ACCESS	read-only
	STATUS	current
	DESCRIPTION
		"The statistics collection of 1 second CPU utilization."
	::= { snAgentGbl 50 }

snAgGblCpuUtil5SecAvg OBJECT-TYPE
	SYNTAX	Gauge32
	MAX-ACCESS	read-only
	STATUS	current
	DESCRIPTION
		"The statistics collection of 5 second CPU utilization."
	::= { snAgentGbl 51 }

snAgGblCpuUtil1MinAvg OBJECT-TYPE
	SYNTAX	Gauge32
	MAX-ACCESS	read-only
	STATUS	current
	DESCRIPTION
		"The statistics collection of 1 minute CPU utilization."
	::= { snAgentGbl 52 }

snAgGblDynMemUtil OBJECT-TYPE
	SYNTAX	Gauge32
	MAX-ACCESS	read-only
	STATUS  deprecated
	DESCRIPTION
		"The system dynamic memory utilization, in unit of percentage.
		Deprecated: Refer to snAgSystemDRAMUtil"
	::= { snAgentGbl 53 }

snAgGblDynMemTotal OBJECT-TYPE
	SYNTAX   Gauge32
	MAX-ACCESS	read-only
	STATUS  deprecated
	DESCRIPTION
		"The total amount of system dynamic memory, in number of bytes.
		Deprecated: Refer to snAgSystemDRAMTotal"
	::= { snAgentGbl 54 }

snAgGblDynMemFree OBJECT-TYPE
	SYNTAX		Gauge32
	MAX-ACCESS	read-only
	STATUS  deprecated
	DESCRIPTION
		"The free amount of system dynamic memory, in number of bytes.
		Deprecated: Refer to snAgSystemDRAMFree"
	::= { snAgentGbl 55 }

snAgImgLoadSPModuleType OBJECT-TYPE
	SYNTAX	INTEGER {
		other(1),
		vm1(2),
		pos12(3),
		pos48(4),
		atm(5),
		gignpa(6),
		lp(7)
		}
	MAX-ACCESS	read-write
	STATUS	current
	DESCRIPTION
		"The switch processor module type of which that receives
		the downloaded image."
	::= { snAgentGbl 56 }

snAgImgLoadSPModuleNumber OBJECT-TYPE
	SYNTAX   Integer32
	MAX-ACCESS	read-write
	STATUS	current
	DESCRIPTION
		"The slot numner of a switch processor module that receives
		the downloaded image. Setting value 0 applies to all SP
		modules."
	::= { snAgentGbl 57 }

snAgTrapHoldTime OBJECT-TYPE
	SYNTAX	INTEGER (1..600)
	MAX-ACCESS	read-write
	STATUS	current
	DESCRIPTION
		"The time in seconds for which traps will be witheld
		during system initialization."
	::= { snAgentGbl 58 }

snAgSFlowSourceInterface OBJECT-TYPE
	SYNTAX   InterfaceIndex
	MAX-ACCESS   read-write
	STATUS   current
	DESCRIPTION
		"Use the ifIndex value here to specify the
		source interface to be used for sFlow packets.
		The interface should have IP address configured
		on it. Value of 0 indicates that source interface
		has not been configured for sFlow. Port 65534
		is used to specify a null port."
	::= { snAgentGbl 59 }

snAgGblTelnetLoginTimeout OBJECT-TYPE
	SYNTAX	INTEGER (1..10)
	MAX-ACCESS	read-write
	STATUS	current
	DESCRIPTION
		"Telnet session login timeout value in minutes. Default is 2 minutes."
	::= { snAgentGbl 60 }

snAgGblBannerExec OBJECT-TYPE
	SYNTAX	DisplayString
	MAX-ACCESS	read-write
	STATUS	current
	DESCRIPTION
		"EXEC process creation banner. Insert newlines using '\n' within the string."
	::= { snAgentGbl 61 }

snAgGblBannerIncoming OBJECT-TYPE
	SYNTAX	DisplayString
	MAX-ACCESS	read-write
	STATUS	current
	DESCRIPTION
		"Incoming terminal line banner. Insert newlines using '\n' within the string."
	::= { snAgentGbl 62 }

snAgGblBannerMotd OBJECT-TYPE
	SYNTAX	DisplayString
	MAX-ACCESS	read-write
	STATUS	current
	DESCRIPTION
		"Message-of-the-day banner. Insert newlines using '\n' within the string."
	::= { snAgentGbl 63 }

snAgWebMgmtServerTcpPort OBJECT-TYPE
	SYNTAX	INTEGER (1..65535)
	MAX-ACCESS	read-write
	STATUS	current
	DESCRIPTION
		"The TCP port number of web management interface."
	::= { snAgentGbl 64 }

--  image and config file down/up load 

snAgTftpServerAddrType			 OBJECT-TYPE
	SYNTAX	InetAddressType
	MAX-ACCESS	read-write
	STATUS	current
	DESCRIPTION
		  "TFTP server IP address Type. Supported address types are ipv4(1) and ipv6(2)"
	DEFVAL	{ ipv4 }
	::= { snAgentGbl 65 }

snAgTftpServerAddr			 OBJECT-TYPE
	SYNTAX	InetAddress
	MAX-ACCESS	read-write
	STATUS	current
	DESCRIPTION
		  "TFTP server IP address."
	::= { snAgentGbl 66 }

snAgGblPasswordCheckMode OBJECT-TYPE
	SYNTAX	EnabledStatus
	MAX-ACCESS	read-only
	STATUS	current
	DESCRIPTION
		"enabled(1)  - The password checking for SNMP set requests is enabled. The default value is enable.
		 disabled(2) -  The password checking for SNMP set requests is disabled. 
		When enabled all image/file related MIB object set requests  PDU must include the password using the snAgGblPassword."
	DEFVAL { enabled }
	::= { snAgentGbl 68 }

snAgGblEnableTelnetAuthentication OBJECT-TYPE
	SYNTAX	INTEGER { disabled(0), enabled(1) }
	MAX-ACCESS	read-write
	STATUS	current
	DESCRIPTION
		"Enable or disable telnet authentication in device."
	DEFVAL { disabled }
	::= { snAgentGbl 69 }

snAgGblManager2FactorAuthentication OBJECT-TYPE
	SYNTAX  INTEGER { disabled(0), enabled(1) }
	MAX-ACCESS      read-write
	STATUS  current
	DESCRIPTION
		"enabled(1) - The manager two-factor authentication is enabled. Only revSSH access through SZ is allowed
		and all incoming SSH sessions to device are closed when two-factor authentication is enabled.
		disabled(0) - The manager two-factor authentication is disabled. SSH access to device from sources
		other than SZ is allowed after manager two-factor authentication is disabled"
	DEFVAL { disabled }
	::= { snAgentGbl 70 }

-- default gateway ipv6 address

snAgDefGwayIpv6 OBJECT-TYPE
	SYNTAX	Ipv6Address
	MAX-ACCESS	read-only
	STATUS	current
	DESCRIPTION
		"The default ipv6 gateway (router) address." 	
	::= { snAgentGbl 71 }

snAgEraseConfig OBJECT-TYPE
        SYNTAX  INTEGER {
                normal(1),
                error(2),
                erase(3),
                erasing(4),
                busy(5)
                }
        MAX-ACCESS      read-write
        STATUS          current
        DESCRIPTION
                "Action object to erase start-up config from flash  on the device.
				The following values can only be read:
                  normal(1)
                  error(2)... operation failed or bad flash
                  erasing(4)...agent is erasing from flash
                  busy(5).......operation not allowed at this time, flash is busy

                The following value can be written:
                  erase(3).....do erase

                The agent will return a response even before the erase is done.
                And the read value will be erasing until erase is done.
                And the erase request will be rejected until error or normal."
        ::= { snAgentGbl 72 }
		

snAgSaveConfig OBJECT-TYPE
        SYNTAX  INTEGER {
                normal(1),
                error(2),
                write(3),
                writing(4),
                busy(5)
                }
        MAX-ACCESS      read-write
        STATUS          current
        DESCRIPTION
                "Action object to save all configuration info to flash on the device.
                The following values can only be read:
                  normal(1)
                  error(2)... operation failed or bad flash
                  writing(4)...agent is writing into flash
                  busy(5).......operation not allowed at this time, flash is busy

                The following value can be written:
                  write(3).....do write

                The agent will return a response even before the write is done.
                And the read value will be writing until write is done.
                And the write request will be rejected until error or normal."
        ::= { snAgentGbl 73 }

snAgGblFirmWareDownLoadState OBJECT-TYPE
    SYNTAX INTEGER {
        start(0),
        validateParameters(1),
        downloading(2),
        validatingImage(3),
        syncingToRemote(4),
        writingToFlash(5),
        complete(6),
        failed(7)
   }
   MAX-ACCESS read-only
   STATUS current
   DESCRIPTION
       "The firmware download status represents the current state
        of a firmware download operation."
   DEFVAL  { start }
   ::= { snAgentGbl 74 }


-- Agent Board Table


snAgentBrdTable OBJECT-TYPE
	SYNTAX	SEQUENCE OF SnAgentBrdEntry
	MAX-ACCESS	not-accessible
	STATUS	current
	DESCRIPTION
		"A table of each physical board information."
	::= { snAgentBrd 1 }

snAgentBrdEntry OBJECT-TYPE
	SYNTAX	SnAgentBrdEntry
	MAX-ACCESS	not-accessible
	STATUS	current
	DESCRIPTION
		"A row in the Agent Board table."
	INDEX	{ snAgentBrdIndex }
	::= { snAgentBrdTable 1 }

SnAgentBrdEntry ::= SEQUENCE {
	snAgentBrdIndex
		Integer32,
	snAgentBrdMainBrdDescription
		DisplayString,
	snAgentBrdMainBrdId
		OCTET STRING,
	snAgentBrdMainPortTotal
		Integer32,
	snAgentBrdExpBrdDescription
		DisplayString,
	snAgentBrdExpBrdId
		OCTET STRING,
	snAgentBrdExpPortTotal
		INTEGER,
	snAgentBrdStatusLeds 
		Integer32,
	snAgentBrdTrafficLeds 
		Integer32,
	snAgentBrdMediaLeds 
		Integer32,
	snAgentBrdSpeedLeds 
		Integer32,
	snAgentBrdModuleStatus
		INTEGER,
	snAgentBrdRedundantStatus
		INTEGER,
	snAgentBrdAlarmLeds 
		Integer32,
	snAgentBrdTxTrafficLeds 
		Integer32,
	snAgentBrdRxTrafficLeds 
		Integer32,
	snAgentBrdStatusLedString
		OCTET STRING,
	snAgentBrdTrafficLedString
		OCTET STRING,
	snAgentBrdMediaLedString
		OCTET STRING,
	snAgentBrdSpeedLedString
		OCTET STRING,
	snAgentBrdAlarmLedString
		OCTET STRING,
	snAgentBrdTxTrafficLedString
		OCTET STRING,
	snAgentBrdRxTrafficLedString
		OCTET STRING,
	snAgentBrdMemoryTotal
		CounterBasedGauge64,
	snAgentBrdMemoryAvailable
		CounterBasedGauge64,
	snAgentBrdSerialNumber
		DisplayString,
	snAgentBrdPartNumber
		DisplayString
	}

snAgentBrdIndex OBJECT-TYPE
	SYNTAX	Integer32 
	MAX-ACCESS	read-only
	STATUS	current
	DESCRIPTION
		"The index to the Agent Interface Table."
	::= { snAgentBrdEntry 1 }

snAgentBrdMainBrdDescription OBJECT-TYPE
	SYNTAX DisplayString (SIZE(0..128))
	MAX-ACCESS read-only
	STATUS current
	DESCRIPTION
		"The main board description string."
	::= { snAgentBrdEntry 2 }

snAgentBrdMainBrdId OBJECT-TYPE
	SYNTAX OCTET STRING
	MAX-ACCESS read-only
	STATUS current
	DESCRIPTION
		"The main board identifier, which can uniquely identify a board
		type. It is an encoded octet string with the following meaning:
		  octet 0  - octet string format version, which identifies the
					 format of this string.
		If format version octet has the value 2, the octets after the
		version octet have the following meaning:
		  octet 1  - product type: 
						BI_WG					0x57
						BI_BB					0x42
						BI_NI					0x4E
						BI_NI2					0x32
						NI_M4					0x4D
						BI_SLB					0x53
		  octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G			0xC5	
						SLAVE_JC_8G				0xC6	
						SLAVE_JC_B16GF			0xC8	
						MASTER_JC_B2404			0xC9	
						SLAVE_JC_B16GC			0xCA
						SLAVE_JC_B24FX			0xCE
		  octet 3  - processor type, PVR_M603=3, PVR_M604=4, PVR_M603E=6,
					 PVR_M603EV=7, PVR_M750=8, PVR_M604E=9, PVR_M8245=81
		  octet 4 to
		  octet 5  - processor speed in MHz
		  octet 6  - MAC type:
						MAC_NONE=0
						MAC_SEEQ_10_100=1, 
						MAC_DEC_10_100=2,
						MAC_3COM_10_100=3,
						MAC_X10GMAC_10000=4,
						MAC_SEEQ_1000=5, 
						MAC_GMAC_1000=6,
						MAC_VLSI_1000=7
		  octet 7  - PHY type, PHY_NONE=0, PHY_QSI=1, PHY_BROADCOM=2,
					 PHY_ICS=3, PHY_NATIONAL=4, PHY_LEVEL1=6,
					 PHY_BROADCOM_10_100=7, PHY_LEVEL24=8,
					 PHY_BROADCOM_10000=9 (for 10G),
					 PHY_3COM_10_100=9 (for others)
		  octet 8  - port type, COPPER=0, FIBER=1
		  octet 9  - fiber port type, NONFIBER=0, SX_FIBER=1,
					 LX_FIBER=2, LHX_FIBER=3, LX_SX_FIBER=4,
					 LHB_FIBER=5
		  octet 10 to
		  octet 13 - DRAM size in KBytes
		  octet 14 to
		  octet 17 - boot flash size in KBytes
		  octet 18 to
		  octet 21 - code flash size in KBytes
		  octet 22 to
		  octet 27 - serial number.
		  octet 28 - chassis backplane type. 
			chassis4000	= 	0x00
			chassis8000	=	0x02
			chassis15000	=	0x01
			chassisFISX	=	0x04
			Turbo8		=	0x07 (stack2)
			FastIron2	=	0x06 (stack1)"
	::= { snAgentBrdEntry 3 }


snAgentBrdMainPortTotal OBJECT-TYPE
	SYNTAX Integer32
	MAX-ACCESS read-only
	STATUS current
	DESCRIPTION
		"The total number of ports for the main board."
	::= { snAgentBrdEntry 4 }


snAgentBrdExpBrdDescription OBJECT-TYPE
	SYNTAX DisplayString (SIZE(0..128))
	MAX-ACCESS read-only
	STATUS current
	DESCRIPTION
		"The expansion board description string. Expansion
		board are those boards attaching on the main board."
	::= { snAgentBrdEntry 5 }


snAgentBrdExpBrdId OBJECT-TYPE
	SYNTAX OCTET STRING
	MAX-ACCESS read-only
	STATUS current
	DESCRIPTION
		"The expansion board identifier. Expansion board are those
		boards attaching on the main board. It is an encoded octet
		string with the following meaning:
		  octet 0  - octet string format version, which identifies
					 the format of this string.
		If format version octet has the value 1, the octets after
		the version octet have the following meaning:
		  octet 1  - expansion board type, HUNDRED_MEG_1PORT=1,
					 HUNDRED_MEG_2PORT=2, HUNDRED_MEG_1PORT_COPPER=3,
					 HUNDRED_MEG_2PORT_COPPER=4, HUNDRED_MEG_2PORT_LX=5,
					 GIGA_1PORT=8, GIGA_2PORT=9
		  octet 2  - fiber port type, NONFIBER=0, SX_FIBER=1,
					 LX_FIBER=2, LHX_FIBER=3, LX_SX_FIBER=4, LHB_FIBER=5"
	::= { snAgentBrdEntry 6 }


snAgentBrdExpPortTotal OBJECT-TYPE
	SYNTAX INTEGER (0..24)
	MAX-ACCESS read-only
	STATUS current
	DESCRIPTION
		"The total number of ports for the expansion board."
	::= { snAgentBrdEntry 7 }


snAgentBrdStatusLeds OBJECT-TYPE
	SYNTAX	Integer32
	MAX-ACCESS	read-only
	STATUS  deprecated
	DESCRIPTION
		"A bit array that contains the value of the
		front panel status LEDs. This is a bit-map; 
		each LED is encoded into 1 bit for each switch
		port.  The maximum number of ports in one chassis 
		is 32 that means 32 Ports Status LEDs. The expansion port 
		number always begins from the last main port number.  
		The following shows the meaning of each bit for each 
		switch port:

		  bit value  meaning
		  --------   ---------  
			 0         off (Link off)
			 1         on  (Link on)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdStatusLedString)"
	::= { snAgentBrdEntry 8 }


snAgentBrdTrafficLeds OBJECT-TYPE
	SYNTAX	Integer32
	MAX-ACCESS	read-only
	STATUS  deprecated
	DESCRIPTION
		"A bit array that contains the value of the
		front panel traffic LEDs. This is a packed bit string; 
		each LED is encoded into 1 bit for each switch
		port.  The maximum number of ports in one chassis 
		is 24 that means 24 Ports Traffic LEDs. The expansion port 
		number always begins from the last main port number.  
		The following shows the meaning of each bit for each 
		switch port:

		  bit value  meaning
		  --------   ---------  
			 0         off (no traffic)
			 1         on  (traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdTrafficLedString)"
	::= { snAgentBrdEntry 9 }


snAgentBrdMediaLeds OBJECT-TYPE
	SYNTAX	Integer32
	MAX-ACCESS	read-only
	STATUS  deprecated
	DESCRIPTION
		"A bit array that contains the value of the
		front panel media LEDs. This is a packed bit string; 
		each LED is encoded into 1 bit for each switch port.  
		The maximum number of ports in one chassis is 24 
		that means 24 Ports Media LEDs.  The expansion port 
		number always begins from the last main port number. 
		The following shows the meaning of each bit for each 
		switch port:

		bit value  meaning   
		---------  -------
		  0        half duplex
		  1        full duplex

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdMediaLedString)"
	::= { snAgentBrdEntry 10 }



snAgentBrdSpeedLeds OBJECT-TYPE
	SYNTAX	Integer32
	MAX-ACCESS	read-only
	STATUS  deprecated
	DESCRIPTION
		"A bit array that contains the value of the
		front panel media LEDs. This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
		  0        10 MBit
		  1        100 MBit

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdSpeedLedString)"
	::= { snAgentBrdEntry 11 }

snAgentBrdModuleStatus OBJECT-TYPE
	SYNTAX  INTEGER {
		moduleEmpty(0),             
		moduleGoingDown(2),
		moduleRejected(3),
		moduleBad(4),
		moduleConfigured(8),
		moduleComingUp(9),
		moduleRunning(10)
		}
	MAX-ACCESS  read-only
	STATUS  current
	DESCRIPTION
		"By default, this mode is set to notActivated(0).
		moduleEmpty(0) ......... The slot of the chassis is empty.
		moduleGoingDown(2) ..... The module is going down.
		moduleRejected(3) ...... The module is being rejected due to wrong configuration.
		moduleBad(4) ........... The module Hardware is bad.
		moduleConfigured(8) ...... The module is configured (stacking)
		moduleComingUp(9) ...... The module is in power-up cycle.
		moduleRunning(10) ....... The module is running."
	::= { snAgentBrdEntry 12 }

snAgentBrdRedundantStatus OBJECT-TYPE
	SYNTAX  INTEGER {
		other(1),
		active(2),             
		standby(3),
		crashed(4),
		comingUp(5)
		}
	MAX-ACCESS  read-only
	STATUS  current
	DESCRIPTION
		"The redundant status of a module. Non-management module always
		returns other(1). Management module returns the rest of the
		states."
	::= { snAgentBrdEntry 13 }

snAgentBrdAlarmLeds OBJECT-TYPE
	SYNTAX   Integer32
	MAX-ACCESS	read-only
	STATUS  deprecated
	DESCRIPTION
		"A bit array that contains the value of the
		front panel media LEDs (for POS Module Only). This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
		  0        no alarm
		  1        alarm

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdAlarmLedString)"
	::= { snAgentBrdEntry 14 }


snAgentBrdTxTrafficLeds OBJECT-TYPE
	SYNTAX	Integer32
	MAX-ACCESS	read-only
	STATUS  deprecated
	DESCRIPTION
		"A bit array that contains the value of the
		front panel transmit traffic LEDs (for POS Module Only). This is a packed bit string; 
		each LED is encoded into 1 bit for each switch
		port.  The maximum number of ports in one chassis 
		is 24 that means 24 Ports Transmit Traffic LEDs. The expansion port 
		number always begins from the last main port number.  
		The following shows the meaning of each bit for each 
		switch port:

		  bit value  meaning
		  --------   ---------  
			 0         off (no transmit traffic)
			 1         on  (transmit traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdTxTrafficLedString)"
	::= { snAgentBrdEntry 15 }

snAgentBrdRxTrafficLeds OBJECT-TYPE
	SYNTAX   Integer32
	MAX-ACCESS	read-only
	STATUS  deprecated
	DESCRIPTION
		"A bit array that contains the value of the
		front panel receive traffic LEDs (for POS Module Only). This is a packed bit string; 
		each LED is encoded into 1 bit for each switch
		port.  The maximum number of ports in one chassis 
		is 24 that means 24 Ports Receive Traffic LEDs. The expansion port 
		number always begins from the last main port number.  
		The following shows the meaning of each bit for each 
		switch port:

		  bit value  meaning
		  --------   ---------  
			 0         off (no receive traffic)
			 1         on  (receive traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdRxTrafficLedString)"
	::= { snAgentBrdEntry 16 }

snAgentBrdStatusLedString OBJECT-TYPE
	SYNTAX	OCTET STRING
	MAX-ACCESS	read-only
	STATUS	current
	DESCRIPTION
		"A bit array that contains the value of the
		front panel status LEDs. This is a bit-map; 
		each LED is encoded into 1 bit for each switch
		port. The following shows the meaning of each
		bit for each switch port:

		  bit value  meaning
		  --------   ---------  
			 0         off (Link off)
			 1         on  (Link on)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 17 }

snAgentBrdTrafficLedString OBJECT-TYPE
	SYNTAX	OCTET STRING
	MAX-ACCESS	read-only
	STATUS	current
	DESCRIPTION
		"A bit array that contains the value of the
		front panel traffic LEDs. This is a packed bit string; 
		each LED is encoded into 1 bit for each switch
		port. The following shows the meaning of each
		bit for each switch port:

		  bit value  meaning
		  --------   ---------  
			 0         off (no traffic)
			 1         on  (traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 18 }

snAgentBrdMediaLedString OBJECT-TYPE
	SYNTAX	OCTET STRING
	MAX-ACCESS	read-only
	STATUS	current
	DESCRIPTION
		"A bit array that contains the value of the
		front panel media LEDs. This is a packed bit string;
		each LED is encoded into 1 bit for each switch port.
		The following shows the meaning of each bit for each
		switch port:

		bit value  meaning   
		---------  -------
		  0        half duplex
		  1        full duplex

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snAgentBrdEntry 19 }

snAgentBrdSpeedLedString OBJECT-TYPE
	SYNTAX	OCTET STRING
	MAX-ACCESS	read-only
	STATUS	current
	DESCRIPTION
		"A bit array that contains the value of the
		front panel media LEDs. This is a packed bit string;
		each LED is encoded into 1 bit for each switch port.
		The following shows the meaning of each bit for each
		switch port:

		bit value  meaning   
		---------  -------
		  0        10 MBit
		  1        100 MBit

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snAgentBrdEntry 20 }

snAgentBrdAlarmLedString OBJECT-TYPE
	SYNTAX	OCTET STRING
	MAX-ACCESS	read-only
	STATUS	current
	DESCRIPTION
		"A bit array that contains the value of the
		front panel media LEDs (for POS Module Only).
		This is a packed bit string; each LED is encoded
		into 1 bit for each switch port. The following
		shows the meaning of each bit for each switch port:

		bit value  meaning   
		---------  -------
		  0        no alarm
		  1        alarm

		The bitmap of LEDs are as following: 
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		---------"
	::= { snAgentBrdEntry 21 }

snAgentBrdTxTrafficLedString OBJECT-TYPE
	SYNTAX	OCTET STRING
	MAX-ACCESS	read-only
	STATUS	current
	DESCRIPTION
		"A bit array that contains the value of the
		front panel transmit traffic LEDs (for POS Module Only).
		This is a packed bit string; each LED is encoded into
		1 bit for each switch port. The following shows the
		meaning of each bit for each switch port:

		  bit value  meaning
		  --------   ---------  
			 0         off (no transmit traffic)
			 1         on  (transmit traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 22 }

snAgentBrdRxTrafficLedString OBJECT-TYPE
	SYNTAX	OCTET STRING
	MAX-ACCESS	read-only
	STATUS	current
	DESCRIPTION
		"A bit array that contains the value of the
		front panel receive traffic LEDs (for POS Module Only).
		This is a packed bit string; each LED is encoded into
		1 bit for each switch port. The following shows the
		meaning of each bit for each switch port:

		  bit value  meaning
		  --------   ---------  
			 0         off (no receive traffic)
			 1         on  (receive traffic)

		The bitmap of LEDs are as following: 
			  
				 (Port1)            (Port4)                    (Port8)
		Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		--------"
	::= { snAgentBrdEntry 23 }

snAgentBrdMemoryTotal  OBJECT-TYPE
	SYNTAX		CounterBasedGauge64
	MAX-ACCESS		read-only
	STATUS		current
	DESCRIPTION
		"The total memory in bytes within this module."
	::= { snAgentBrdEntry 24 }

snAgentBrdMemoryAvailable  OBJECT-TYPE
	SYNTAX		CounterBasedGauge64
	MAX-ACCESS		read-only
	STATUS		current
	DESCRIPTION
		"The total memory in bytes available for use within this module."
	::= { snAgentBrdEntry 25 }

snAgentBrdSerialNumber  OBJECT-TYPE
	SYNTAX		DisplayString
	MAX-ACCESS		read-only
	STATUS		current
	DESCRIPTION
		"The Board Serial number. Zero length string indicates that
		module serial number has not been programmed within 
		EEPROM or the module does not support serial number within EEPROM."
	::= { snAgentBrdEntry 26 }

snAgentBrdPartNumber  OBJECT-TYPE
	SYNTAX		DisplayString 
	MAX-ACCESS		read-only
	STATUS		current
	DESCRIPTION
		"The Board Part number. Zero length string indicates that
		module part number has not been programmed within 
		EEPROM or the module does not support part number within EEPROM."
	::= { snAgentBrdEntry 27 }


-- Agent Stacking Board Table


snAgentBrd2Table OBJECT-TYPE
	SYNTAX	SEQUENCE OF SnAgentBrd2Entry
	MAX-ACCESS	not-accessible
	STATUS	current
	DESCRIPTION
		"A table of each physical board information for each unit."
	::= { snAgentBrd 2 }

snAgentBrd2Entry OBJECT-TYPE
	SYNTAX	SnAgentBrd2Entry
	MAX-ACCESS	not-accessible
	STATUS	current
	DESCRIPTION
		"A row in the Agent Board table."
	INDEX	{ snAgentBrd2Unit,  snAgentBrd2Slot }
	::= { snAgentBrd2Table 1 }

SnAgentBrd2Entry ::= SEQUENCE {
	snAgentBrd2Unit
		Integer32,
	snAgentBrd2Slot
		Integer32,
	snAgentBrd2MainBrdDescription
		DisplayString,
	snAgentBrd2MainBrdId
		OCTET STRING,
	snAgentBrd2MainPortTotal
		Integer32,	
	snAgentBrd2ModuleStatus
		INTEGER,
	snAgentBrd2RedundantStatus
		INTEGER
	}

snAgentBrd2Unit OBJECT-TYPE
	SYNTAX   Integer32 
	MAX-ACCESS	read-only
	STATUS	current
	DESCRIPTION
		"The index to the Agent module Table."
	::= { snAgentBrd2Entry 1 }

snAgentBrd2Slot OBJECT-TYPE
	SYNTAX   Integer32
	MAX-ACCESS	read-only
	STATUS	current
	DESCRIPTION
		"The index to the Agent module Table."
	::= { snAgentBrd2Entry 2 }

snAgentBrd2MainBrdDescription OBJECT-TYPE
	SYNTAX DisplayString (SIZE(0..128))
	MAX-ACCESS read-only
	STATUS current
	DESCRIPTION
		"The main board description string."
	::= { snAgentBrd2Entry 3}

snAgentBrd2MainBrdId OBJECT-TYPE
	SYNTAX OCTET STRING
	MAX-ACCESS read-only
	STATUS current
	DESCRIPTION
		"The main board identifier, which can uniquely identify a board
		type. It is an encoded octet string with the following meaning:
		  octet 0  - octet string format version, which identifies the
					 format of this string.
		If format version octet has the value 2, the octets after the
		version octet have the following meaning:
		  octet 1  - product type: 
						BI_WG					0x57
						BI_BB					0x42
						BI_NI					0x4E
						BI_NI2					0x32
						NI_M4					0x4D
						BI_SLB					0x53
		  octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G			0xC5	
						SLAVE_JC_8G				0xC6	
						SLAVE_JC_B16GF			0xC8	
						MASTER_JC_B2404			0xC9	
						SLAVE_JC_B16GC			0xCA	
		  octet 3  - processor type, PVR_M603=3, PVR_M604=4, PVR_M603E=6,
					 PVR_M603EV=7, PVR_M750=8, PVR_M604E=9, PVR_M8245=81
		  octet 4 to
		  octet 5  - processor speed in MHz
		  octet 6  - MAC type:
						MAC_NONE=0
						MAC_SEEQ_10_100=1, 
						MAC_DEC_10_100=2,
						MAC_3COM_10_100=3,
						MAC_X10GMAC_10000=4,
						MAC_SEEQ_1000=5, 
						MAC_GMAC_1000=6,
						MAC_VLSI_1000=7
		  octet 7  - PHY type, PHY_NONE=0, PHY_QSI=1, PHY_BROADCOM=2,
					 PHY_ICS=3, PHY_NATIONAL=4, PHY_LEVEL1=6,
					 PHY_BROADCOM_10_100=7, PHY_LEVEL24=8,
					 PHY_BROADCOM_10000=9 (for 10G),
					 PHY_3COM_10_100=9 (for others)
		  octet 8  - port type, COPPER=0, FIBER=1
		  octet 9  - fiber port type, NONFIBER=0, SX_FIBER=1,
					 LX_FIBER=2, LHX_FIBER=3, LX_SX_FIBER=4,
					 LHB_FIBER=5
		  octet 10 to
		  octet 13 - DRAM size in KBytes
		  octet 14 to
		  octet 17 - boot flash size in KBytes
		  octet 18 to
		  octet 21 - code flash size in KBytes
		  octet 22 to
		  octet 27 - serial number.
		  octet 28 - chassis backplane type. 
			chassis4000	= 	0x00
			chassis8000	=	0x02
			chassis15000	=	0x01
			chassisFISX	=	0x04
			Turbo8		=	0x07 (stack2)
			FastIron2	=	0x06 (stack1)"
	::= { snAgentBrd2Entry 4 }


snAgentBrd2MainPortTotal OBJECT-TYPE
	SYNTAX Integer32
	MAX-ACCESS read-only
	STATUS current
	DESCRIPTION
		"The total number of ports for the main board."
	::= { snAgentBrd2Entry 5 }

snAgentBrd2ModuleStatus OBJECT-TYPE
	SYNTAX  INTEGER {
		moduleEmpty(0),             
		moduleGoingDown(2),
		moduleRejected(3),
		moduleBad(4),
		moduleConfigured(8),
		moduleComingUp(9),
		moduleRunning(10)
		}
	MAX-ACCESS  read-only
	STATUS  current
	DESCRIPTION
		"By default, this mode is set to notActivated(0).
		moduleEmpty(0) ......... The slot of the chassis is empty.
		moduleGoingDown(2) ..... The module is going down.
		moduleRejected(3) ...... The module is being rejected due to wrong configuration.
		moduleBad(4) ........... The module Hardware is bad.
		moduleConfigured(8) ...... The module is configured (stacking)
		moduleComingUp(9) ...... The module is in power-up cycle.
		moduleRunning(10) ....... The module is running."
	::= { snAgentBrd2Entry 6 }

snAgentBrd2RedundantStatus OBJECT-TYPE
	SYNTAX  INTEGER {
		other(1),
		active(2),             
		standby(3),
		crashed(4),
		comingUp(5)
		}
	MAX-ACCESS  read-only
	STATUS  current
	DESCRIPTION
		"The redundant status of a module. Non-management module always
		returns other(1). Management module returns the rest of the
		states."
	::= { snAgentBrd2Entry 7}

-- Trap Receiver Table


-- Trap Receiver Table
-- snAgTrpRcvrTable is deprecated, replaced by fdryTrapReceiverTable.
-- The new table "fdryTrapReceiverTable" combines Ipv4 and Ipv6 configuration of 
-- trap Receiver/managers which to send traps.

snAgTrpRcvrTable OBJECT-TYPE
	SYNTAX	SEQUENCE OF SnAgTrpRcvrEntry
	MAX-ACCESS	not-accessible
	STATUS	deprecated
	DESCRIPTION
		"A table of managers which to send traps."
	::= { snAgentTrp 1 }

snAgTrpRcvrEntry OBJECT-TYPE
	SYNTAX	SnAgTrpRcvrEntry
	MAX-ACCESS	not-accessible
	STATUS	deprecated
	DESCRIPTION
		"A row in the trap receiver table.
		The column snAgTrpRcvrStatus is used to create
		and delete rows in the table. Creation requires
		a SET PDU with objects snAgTrpRcvrIndex,
		snAgTrpRcvrIpAddr, snAgTrpRcvrComm and 
		snAgTrpRcvrStatus."
	INDEX	{ snAgTrpRcvrIndex }
	::= { snAgTrpRcvrTable 1 }

SnAgTrpRcvrEntry ::= SEQUENCE {
	snAgTrpRcvrIndex
		Integer32,
	snAgTrpRcvrIpAddr
		IpAddress,
	snAgTrpRcvrCommunityOrSecurityName
		OCTET STRING,
	snAgTrpRcvrStatus
		INTEGER,
	snAgTrpRcvrUDPPort
		INTEGER,
	snAgTrpRcvrSecurityModel
		INTEGER,
	snAgTrpRcvrSecurityLevel
		INTEGER
	}

snAgTrpRcvrIndex OBJECT-TYPE
	SYNTAX   Integer32
	MAX-ACCESS	read-only
	STATUS	deprecated
	DESCRIPTION
		"The index to the Trap Receiver Table."
	::= { snAgTrpRcvrEntry 1 }

snAgTrpRcvrIpAddr OBJECT-TYPE
	SYNTAX	IpAddress
	MAX-ACCESS	read-write
	STATUS	deprecated
	DESCRIPTION
		"The ip address for
		SNMP manager that is to receive the trap."
	::= { snAgTrpRcvrEntry 2 }

snAgTrpRcvrCommunityOrSecurityName OBJECT-TYPE
	SYNTAX	OCTET STRING (SIZE(0..32))
	MAX-ACCESS	read-write
	STATUS	deprecated
	DESCRIPTION
		"Community string to use. In case of USM (SNMPv3) security model,
		this object is used to provide the security name."
	::= { snAgTrpRcvrEntry 3 }


snAgTrpRcvrStatus OBJECT-TYPE
	SYNTAX	INTEGER {
		other(1),
		valid(2),
		delete(3),
		create(4),
		ignore(5)
		}
	MAX-ACCESS	read-write
	STATUS	deprecated
	DESCRIPTION
		"This object is used to create and
		delete rows in the table and control
		if they are used. The values
		that can be written are:
		  ignore(5)...don't use this entry to
						send traps to at this time
		  delete(3)...deletes the row
		  create(4)...creates a new row

		If the row exists, then a SET with
		value of create(5) returns error
		'badValue'. Deleted rows go away
		immediately. The following values
		can be returned on reads:
		  other(1)....some other case
		  valid(2)....the row exists and is valid
		  ignore(5)...don't use this entry to
						send traps to at this time"
	::= { snAgTrpRcvrEntry 4 }

snAgTrpRcvrUDPPort       OBJECT-TYPE
	SYNTAX	INTEGER	 (0..65535)
	MAX-ACCESS  read-write
	STATUS	deprecated
	DESCRIPTION
		"UDP port number of the trap receiver."
	DEFVAL { 162 }
	::= { snAgTrpRcvrEntry 5 }

snAgTrpRcvrSecurityModel       OBJECT-TYPE
	SYNTAX	INTEGER {
		v1(1),
		v2c(2),
		usm(3)
		}
	MAX-ACCESS  read-write
	STATUS	deprecated
	DESCRIPTION
		"Version of trap format to be used."
	DEFVAL { 1 }
	::= { snAgTrpRcvrEntry 6 }

snAgTrpRcvrSecurityLevel       OBJECT-TYPE
	SYNTAX	INTEGER {
		noAuth(1),
		auth(2),
		authPriv(3)
		}
	MAX-ACCESS  read-write
	STATUS	deprecated
	DESCRIPTION
		"Used for USM (SNMPv3) security model to specify the level of security.
		The security name is provided by snAgTrpRcvrCommunityOrSecurityName."
	DEFVAL { 1 }
	::= { snAgTrpRcvrEntry 7 }


-- Boot Sequence Table


snAgBootSeqTable OBJECT-TYPE
	SYNTAX	SEQUENCE OF SnAgBootSeqEntry
	MAX-ACCESS	not-accessible
	STATUS	current
	DESCRIPTION
		"A table of image load sequnce instructions to the boot code.
		Boot code will start from instruction of the first valid entry
		to load the image. If failed, it will use the second valid
		entry and so on, until a succesful load has completed. Each
		entry must have an unique instruction, duplicate instructions
		will be rejected."
	::= { snAgentBoot 1 }

snAgBootSeqEntry OBJECT-TYPE
	SYNTAX	SnAgBootSeqEntry
	MAX-ACCESS	not-accessible
	STATUS	current
	DESCRIPTION
		"A row in the boot sequence table."
	INDEX	{ snAgBootSeqIndex }
	::= { snAgBootSeqTable 1 }

SnAgBootSeqEntry ::= SEQUENCE {
	snAgBootSeqIndex
		INTEGER,
	snAgBootSeqInstruction
		INTEGER,
	snAgBootSeqIpAddr
		IpAddress,
	snAgBootSeqFilename
		DisplayString,
	snAgBootSeqRowStatus
		INTEGER
	}

snAgBootSeqIndex OBJECT-TYPE
	SYNTAX	INTEGER (1..6)
	MAX-ACCESS	read-only
	STATUS	current
	DESCRIPTION
		"The index to the boot sequence table."
	::= { snAgBootSeqEntry 1 }

snAgBootSeqInstruction OBJECT-TYPE
	SYNTAX	INTEGER {
		fromPrimaryFlash(1),
		fromSecondaryFlash(2),
		fromTftpServer(3),
		fromBootpServer(4),
		fromPcmciaCard1(5),
		fromPcmciaCard2(6) }
	MAX-ACCESS	read-write
	STATUS	current
	DESCRIPTION
		"The instruction for the boot code."
	::= { snAgBootSeqEntry 2 }

snAgBootSeqIpAddr OBJECT-TYPE
	SYNTAX	IpAddress
	MAX-ACCESS	read-write
	STATUS	current
	DESCRIPTION
		"The ip address of the TFTP server if snAgBootSeqInstruction
		was set to 'fromTftpServer'; otherwise, this object is not
		used in any other boot instruction."
	::= { snAgBootSeqEntry 3 }

snAgBootSeqFilename OBJECT-TYPE
	SYNTAX	DisplayString (SIZE (0..32))
	MAX-ACCESS	read-write
	STATUS	current
	DESCRIPTION
		"The image filename on the TFTP server if snAgBootSeqInstruction
		was set to 'fromTftpServer'; otherwise, this object is not
		used in any other boot instruction."
	::= { snAgBootSeqEntry 4 }

snAgBootSeqRowStatus OBJECT-TYPE
	SYNTAX	INTEGER	{
		other(1),
		valid(2),
		delete(3),
		create(4) }
	MAX-ACCESS	read-write
	STATUS	current
	DESCRIPTION
		"To create or delete a boot sequence table entry."
	::= { snAgBootSeqEntry 5 }


-- SP Boot Sequence Table

snAgSpBootSeqTable OBJECT-TYPE
	SYNTAX	SEQUENCE OF SnAgSpBootSeqEntry
	MAX-ACCESS	not-accessible
	STATUS	current
	DESCRIPTION
		"A table of image load sequnce instructions to the boot code for
		the slave (line) modules. Boot code will start from instruction of
		the first valid entry to load the image. If failed, it will use
		the second valid entry and so on, until a succesful load has
		completed. Each entry must have an unique instruction, duplicate
		instructions will be rejected."
	::= { snAgentBoot 2 }

snAgSpBootSeqEntry OBJECT-TYPE
	SYNTAX	SnAgSpBootSeqEntry
	MAX-ACCESS	not-accessible
	STATUS	current
	DESCRIPTION
		"A row in the slave module boot sequence table."
	INDEX	{ snAgSpBootSeqSpNumber, snAgSpBootSeqIndex }
	::= { snAgSpBootSeqTable 1 }

SnAgSpBootSeqEntry ::= SEQUENCE {
	snAgSpBootSeqSpNumber
		INTEGER,
	snAgSpBootSeqIndex
		Integer32,
	snAgSpBootSeqInstruction
		INTEGER,
	snAgSpBootSeqIpAddr
		IpAddress,
	snAgSpBootSeqFilename
		DisplayString,
	snAgSpBootSeqRowStatus
		INTEGER
	}

snAgSpBootSeqSpNumber OBJECT-TYPE
	SYNTAX	INTEGER (0..32)
	MAX-ACCESS  not-accessible
	STATUS	current
	DESCRIPTION
		"The slot numner of a slave/witch processor module for which 
		this boot sequence applies. Setting value 0 applies to all SP
		modules. Index 0 is valid only for setting to simplify the set
		operation for all the modules."
	::= { snAgSpBootSeqEntry 1 }
	
snAgSpBootSeqIndex OBJECT-TYPE
	SYNTAX	Integer32
	MAX-ACCESS  not-accessible
	STATUS	current
	DESCRIPTION
		"The index to the boot sequence table."
	::= { snAgSpBootSeqEntry 2 }

snAgSpBootSeqInstruction OBJECT-TYPE
	SYNTAX	INTEGER {
					fromSpPrimaryFlash(1),
					fromSpSecondaryFlash(2),
					fromMpPrimaryFlash(3),
					fromMpSecondaryFlash(4),
					fromPcmciaCard1(5),
					fromPcmciaCard2(6),
					fromTftpServer(7),
					interactively(8)
				}
	MAX-ACCESS	read-write
	STATUS	current
	DESCRIPTION
		"The instruction for the boot code."
	::= { snAgSpBootSeqEntry 3 }

snAgSpBootSeqIpAddr OBJECT-TYPE
	SYNTAX	IpAddress
	MAX-ACCESS	read-write
	STATUS	current
	DESCRIPTION
		"The ip address of the TFTP server if snAgBootSeqInstruction
		was set to 'fromTftpServer'; otherwise, this object is not
		used in any other boot instruction."
	::= { snAgSpBootSeqEntry 4 }

snAgSpBootSeqFilename OBJECT-TYPE
	SYNTAX	DisplayString (SIZE (0..32))
	MAX-ACCESS	read-write
	STATUS	current
	DESCRIPTION
		"The image filename on the TFTP server if snAgBootSeqInstruction
		was set to 'fromTftpServer'; otherwise, this object is not
		used in any other boot instruction."
	::= { snAgSpBootSeqEntry 5 }

snAgSpBootSeqRowStatus OBJECT-TYPE
	SYNTAX	INTEGER	{
					valid(1),
					delete(2),
					create(3)
				}
	MAX-ACCESS	read-write
	STATUS	current
	DESCRIPTION
		"To create or delete a boot sequence table entry."
	::= { snAgSpBootSeqEntry 6 }

--- Encoded Octet Strings for the Configuration File Transfer


snAgCfgEosTable OBJECT-TYPE
	SYNTAX	SEQUENCE OF SnAgCfgEosEntry
	MAX-ACCESS	not-accessible
	STATUS	deprecated
	DESCRIPTION
		"This table represents the fragmented Configuration File data packet 
		with checksum include in each rows of this table.  A SNMP-SET
		represents configuration file download, and a SNMP-GET represents
		configuration file upload.  This action is only if the SNMP-SET of
		snAgCfgLoad command is sent along with this table consecutively.  The 
		applicable snAgCfgLoad command value is as followings:
		uploadFromFlashToNMS(23),
		downloadToFlashFromNMS(24),
		uploadFromDramToNMS(25),
		downloadToDramFromNMS(26)." 
	::= { snAgCfgEos 1 }


snAgCfgEosEntry OBJECT-TYPE
	SYNTAX	SnAgCfgEosEntry	
	MAX-ACCESS	not-accessible
	STATUS	deprecated
	DESCRIPTION
		"An EOS row in the table of encoded octet strings for table 
		snAgCfgEosTable. "
	INDEX  { snAgCfgEosIndex }
	::= { snAgCfgEosTable 1 }



SnAgCfgEosEntry ::= 
	SEQUENCE {
	snAgCfgEosIndex
		Integer32,
	snAgCfgEosPacket 
		OCTET STRING,
	snAgCfgEosChkSum
		Integer32
	}


snAgCfgEosIndex OBJECT-TYPE
	SYNTAX  Integer32
	MAX-ACCESS  read-only
	STATUS  deprecated
	DESCRIPTION
		 "Each VLAN EOS Buffer Identifier have a multiple 
		 VLAN table entries."
	::= { snAgCfgEosEntry 1 }

snAgCfgEosPacket OBJECT-TYPE
	SYNTAX	OCTET STRING (SIZE(0..1000))
	MAX-ACCESS	read-write
	STATUS	deprecated
	DESCRIPTION
		"An encoded octet string. On reads it contains an integral 
		number of configuration file data packets. The size 
		of each encoded octet string is less than or equal to 1400
		bytes."
	::= { snAgCfgEosEntry 2 }


snAgCfgEosChkSum OBJECT-TYPE
	SYNTAX Integer32
	MAX-ACCESS  read-write
	STATUS  deprecated
	DESCRIPTION
		 "A checksum of each configuration file data packet." 
	::= { snAgCfgEosEntry 3 }


-- Stackable Management Group

snStackGen				OBJECT IDENTIFIER ::= { snStack 1 }
snStackSecSwitchInfo	OBJECT IDENTIFIER ::= { snStack 2 }

-- MIB Objects


-- General Stackable Management Information

snStackPriSwitchMode OBJECT-TYPE
	SYNTAX  INTEGER {
		disabled(0),             
		enabled(1)
		}
	MAX-ACCESS  read-write
	STATUS  current
	DESCRIPTION
		"The Stackable Management Primary Switch mode
		 either enabled or disabled and the default is 
		 disabled mode.
		 enabled(1)...........primary switch enabled
		 disabled(0)..........primary switch disabled"  
	::= { snStackGen 1 }

snStackMaxSecSwitch OBJECT-TYPE
	SYNTAX Integer32
	MAX-ACCESS  read-only
	STATUS  current
	DESCRIPTION
		"The Maximum Secondary Switches are allowed in the
		 Stackable Management Group."
	::= { snStackGen 2 }

snStackTotalSecSwitch OBJECT-TYPE
	SYNTAX Integer32
	MAX-ACCESS  read-only
	STATUS  current
	DESCRIPTION
		"The Total Secondary Switches currently connected to the
		 Stackable Management Group."
	::= { snStackGen 3 }

snStackSyncAllSecSwitch OBJECT-TYPE
	SYNTAX  INTEGER {
		normal(0),
		invalid(1),
		device(2),
		global(3),
		local(4)
		}
	MAX-ACCESS  read-write
	STATUS  current
	DESCRIPTION
		"Synchronize all the secondary switches in the
		 Stackable Management Group with the following commands.
		 device(2)...........device related parameters.
		 global(3)...........global parameters.  
		 local(4)............local parameters.
		 The return result of the above commands are either
		 normal(0)...........normal condition.
		 invalid(1)...........invalid result."  
	::= { snStackGen 4 }

snStackSmSlotIndex OBJECT-TYPE
	SYNTAX	INTEGER (0..8)
	MAX-ACCESS	read-write
	STATUS	current
	DESCRIPTION
		"The Slot 0 is the Master slot and Slot 1-8 are slaves. 
		 All the slot-based MIB data can be retrieved with respect to 
		 this slot index such as snChassis global MIB. "
	::= { snStackGen 5 }

snStackFmpSetProcess OBJECT-TYPE
	SYNTAX	INTEGER { 
						normal(0), 
						pending(1), 
						failure(2)
					}
	MAX-ACCESS	read-only
	STATUS	current
	DESCRIPTION
		"normal(0)  - The set process is either in an idle state or FMP-SET-SUCCESS state.
		 pending(1) - The pending process is waiting for the result of an FMP-SET.
		 failure(2) - The failure result of an FMP-SET."
	::= { snStackGen 6 }




-- Stackable Management Secondary Switch Information Table


snStackSecSwitchTable OBJECT-TYPE
	SYNTAX  SEQUENCE OF SnStackSecSwitchEntry
	MAX-ACCESS  not-accessible
	STATUS  current
	DESCRIPTION
		"If snSwGroupOperMode is configured as basic mode
		 which is VLAN by Port, Layer2 switching,
		 then this table is valid.  Each VLAN switch port
		 could have a number of VLAN IDs."
	::= { snStackSecSwitchInfo 1 }


snStackSecSwitchEntry OBJECT-TYPE
	SYNTAX  SnStackSecSwitchEntry
	MAX-ACCESS  not-accessible
	STATUS  current
	DESCRIPTION
		"An entry in the Stackable Management Secondary Switch 
		 Information table."
	INDEX   { 
		snStackSecSwitchIndex
	}
	::= { snStackSecSwitchTable 1 }


SnStackSecSwitchEntry ::= SEQUENCE {
	snStackSecSwitchIndex
		INTEGER,
	snStackSecSwitchSlotId
		INTEGER,
	snStackSecSwitchPortCnts
		INTEGER,
	snStackSecSwitchEnabled
		INTEGER,
	snStackSecSwitchAck
		INTEGER,
	snStackSecSwitchMacAddr
		MacAddress,
	snStackSecSwitchSyncCmd
		INTEGER, 
	snStackSecSwitchIpAddr
		IpAddress,
	snStackSecSwitchSubnetMask
		IpAddress,
	snStackSecSwitchCfgCmd
		INTEGER 
	}

snStackSecSwitchIndex OBJECT-TYPE
	SYNTAX  INTEGER (1..26)
	MAX-ACCESS  read-only
	STATUS  current
	DESCRIPTION
		"The secondary switch index must not be greater than the snStackMaxSecSwitch."
	::= { snStackSecSwitchEntry 1 }


snStackSecSwitchSlotId OBJECT-TYPE
	SYNTAX  INTEGER (1..26)
	MAX-ACCESS  read-write
	STATUS  current
	DESCRIPTION
		"The secondary switch slot ID must be set before the Configuration 
		 command sent from the primary switch to the secondary switch 
		 either manually or automatically - snStackSecSwitchCfgCmd."
	::= { snStackSecSwitchEntry 2 }

snStackSecSwitchPortCnts OBJECT-TYPE
	SYNTAX  INTEGER (1..26)
	MAX-ACCESS  read-only
	STATUS  current
	DESCRIPTION
		"The number of ports in this secondary switch."
	::= { snStackSecSwitchEntry 3 }

snStackSecSwitchEnabled OBJECT-TYPE
	SYNTAX  INTEGER {
		disabled(0),             
		enabled(1)
		}
	MAX-ACCESS  read-write
	STATUS  current
	DESCRIPTION
		"The secondary switch has been selected to Stackable Management Group."
	::= { snStackSecSwitchEntry 4 }

snStackSecSwitchAck OBJECT-TYPE
	SYNTAX  INTEGER {
		disabled(0),             
		enabled(1)
		}
	MAX-ACCESS  read-only
	STATUS  current
	DESCRIPTION
		"The secondary switch has sent reponse to the primary switch."
	::= { snStackSecSwitchEntry 5 }

snStackSecSwitchMacAddr OBJECT-TYPE
	SYNTAX  MacAddress
	MAX-ACCESS  read-only
	STATUS  current
	DESCRIPTION
		"The secondary switch physical address. The physical address 
		represents a MAC Station."
	::= { snStackSecSwitchEntry 6 }

snStackSecSwitchSyncCmd OBJECT-TYPE
	SYNTAX  INTEGER {
		normal(0),
		invalid(1),
		device(2),
		global(3),
		local(4)
		}
	MAX-ACCESS  read-write
	STATUS  current
	DESCRIPTION
		"Synchronize the secondary switches in the
		 Stackable Management Group with the following commands.
		 device(2)...........device related parameters.
		 global(3)...........global parameters.  
		 local(4)............local parameters.
		 The return result of the above commands are either
		 normal(0)...........normal condition.
		 invalid(1)...........invalid result."  
	::= { snStackSecSwitchEntry 7 }

snStackSecSwitchIpAddr OBJECT-TYPE
	SYNTAX	IpAddress
	MAX-ACCESS  read-write
	STATUS  current
	DESCRIPTION
		"The secondary switch IP Address and is used for 
		 manual-command of snStackSecSwitchCfgCmd."
	::= { snStackSecSwitchEntry 8 }

snStackSecSwitchSubnetMask OBJECT-TYPE
	SYNTAX	IpAddress
	MAX-ACCESS  read-write
	STATUS  current
	DESCRIPTION
		"The secondary switch IP Subnet Mask and is used for 
		 manual-command of snStackSecSwitchCfgCmd."
	::= { snStackSecSwitchEntry 9 }

snStackSecSwitchCfgCmd OBJECT-TYPE
	SYNTAX  INTEGER {
		normal(0),
		invalid(1),
		auto(2),
		manual(3)
		}
	MAX-ACCESS  read-write
	STATUS  current
	DESCRIPTION
		"snStackSecSwitchSlotId must be set before the Configuration 
		 command sent from the primary switch to the secondary switch 
		 either manually or automatically.
		 auto(2)...........auto-configuration command sent.
		 manual(3).........manual-configuration command sent.
						   if manual-mode is used, snStackSecSwitchIpAddr
						   and snStackSecSwitchSubnetMask must be
						   first set before this command is sent.
		 The return result of the above commands are either
		 normal(0)...........normal condition.
		 invalid(1)..........invalid result."  
	::= { snStackSecSwitchEntry 10 }

-- System Logging Group

snAgSysLogGbl	OBJECT IDENTIFIER ::= { snAgentLog 1 }

snAgSysLogGblEnable OBJECT-TYPE
	SYNTAX	INTEGER { disabled(0), enabled(1) }
	MAX-ACCESS	read-write
	STATUS	current
	DESCRIPTION
		"Enable/disable system logging."
	DEFVAL { enabled }
	::= { snAgSysLogGbl 1 }

snAgSysLogGblBufferSize OBJECT-TYPE
	SYNTAX   Integer32
	MAX-ACCESS	read-write
	STATUS	current
	DESCRIPTION
		"The number of dynamic system logging entries."
	DEFVAL { 50 }
	::= { snAgSysLogGbl 2 }

snAgSysLogGblClear OBJECT-TYPE
	SYNTAX	INTEGER { normal(0), clearAll(1), clearDynamic(2), clearStatic(3) }
	MAX-ACCESS	read-write
	STATUS	current
	DESCRIPTION
		"Clear dynamic and/or static system logging buffers."
	::= { snAgSysLogGbl 3 }

snAgSysLogGblCriticalLevel OBJECT-TYPE
	SYNTAX   Integer32
	MAX-ACCESS	read-write
	STATUS	current
	DESCRIPTION
		"Filter events going to the logging buffer. This is a packed
		bit string object of which each bit has the following meaning:
		(bit 0 is the least significant bit).

		  bit position   meaning
		  ------------   -------
			  8-31	 reserved
			  7		 Warning (warning conditions)
			  6		 Notification (normal but significant conditions)
			  5		 Informational (informational messages)
			  4		 Error (error conditions)
			  3		 Emergency (system is unusable)
			  2		 Debugging (debugging messages)
			  1		 Critical (critical conditions)
			  0		 Alert (immediate action needed)

		Setting a critical level bit to 1 makes the logging buffer
		accept the corresponding event. Resetting a critical level
		bit to 0 makes the logging buffer reject the corresponding
		event."
	DEFVAL { 255 }
	::= { snAgSysLogGbl 4 }

snAgSysLogGblLoggedCount OBJECT-TYPE
	SYNTAX	Counter32
	MAX-ACCESS	read-only
	STATUS	current
	DESCRIPTION
		"The number events logged in the system logging buffer."
	::= { snAgSysLogGbl 5 }

snAgSysLogGblDroppedCount OBJECT-TYPE
	SYNTAX	Counter32
	MAX-ACCESS	read-only
	STATUS	current
	DESCRIPTION
		"The number of events dropped."
	::= { snAgSysLogGbl 6 }

snAgSysLogGblFlushedCount OBJECT-TYPE
	SYNTAX	Counter32
	MAX-ACCESS	read-only
	STATUS	current
	DESCRIPTION
		"The number of times that the system logging buffer was cleared."
	::= { snAgSysLogGbl 7 }

snAgSysLogGblOverrunCount OBJECT-TYPE
	SYNTAX	Counter32
	MAX-ACCESS	read-only
	STATUS	current
	DESCRIPTION
		"The number of times that the system logging buffer was wrapped
		around."
	::= { snAgSysLogGbl 8 }

snAgSysLogGblServer OBJECT-TYPE
	SYNTAX  IpAddress
	MAX-ACCESS	read-write
	STATUS	deprecated
	DESCRIPTION
		"IP address of syslog server."
	::= { snAgSysLogGbl 9 }

snAgSysLogGblFacility OBJECT-TYPE
	SYNTAX  INTEGER {
		kern(1),
		user(2),
		mail(3),
		daemon(4),
		auth(5),
		syslog(6),
		lpr(7),
		news(8),
		uucp(9),
		sys9(10),
		sys10(11),
		sys11(12),
		sys12(13),
		sys13(14),
		sys14(15),
		cron(16),
		local0(17),
		local1(18),
		local2(19),
		local3(20),
		local4(21),
		local5(22),
		local6(23),
		local7(24)
		}
	MAX-ACCESS	read-write
	STATUS	current
	DESCRIPTION
		"Facility code."
	DEFVAL { user }
	::= { snAgSysLogGbl 10 }

snAgSysLogGblPersistenceEnable OBJECT-TYPE
	SYNTAX	INTEGER { disabled(0), enabled(1) }
	MAX-ACCESS	read-write
	STATUS	current
	DESCRIPTION
		"Enable/disable system logging persistence."
	DEFVAL { enabled }
	::= { snAgSysLogGbl 11 }

-- Dynamic System Logging Buffer Table

snAgSysLogBufferTable OBJECT-TYPE
	SYNTAX	SEQUENCE OF SnAgSysLogBufferEntry
	MAX-ACCESS	not-accessible
	STATUS	current
	DESCRIPTION
		"Dynamic system logging buffer table."
	::= { snAgentLog 2 }

snAgSysLogBufferEntry OBJECT-TYPE
	SYNTAX	SnAgSysLogBufferEntry
	MAX-ACCESS	not-accessible
	STATUS	current
	DESCRIPTION
		"A row in the dynamic system logging buffer table."
	INDEX	{ snAgSysLogBufferIndex }
	::= { snAgSysLogBufferTable 1 }

SnAgSysLogBufferEntry ::= SEQUENCE {
	snAgSysLogBufferIndex
		Integer32,
	snAgSysLogBufferTimeStamp
		TimeTicks,
	snAgSysLogBufferCriticalLevel
		INTEGER,
	snAgSysLogBufferMessage
		DisplayString,
	snAgSysLogBufferCalTimeStamp
		DisplayString
	}

snAgSysLogBufferIndex OBJECT-TYPE
	SYNTAX   Integer32
	MAX-ACCESS	read-only
	STATUS	current
	DESCRIPTION
		"The index to the dynamic system logging buffer table."
	::= { snAgSysLogBufferEntry 1 }

snAgSysLogBufferTimeStamp OBJECT-TYPE
	SYNTAX	TimeTicks
	MAX-ACCESS	read-only
	STATUS	current
	DESCRIPTION
		"A time stamp when the event is logged."
	::= { snAgSysLogBufferEntry 2 }

snAgSysLogBufferCriticalLevel OBJECT-TYPE
	SYNTAX	INTEGER {
		other(1),
		alert(2),
		critical(3),
		debugging(4),
		emergency(5),
		error(6),
		informational(7),
		notification(8),
		warning(9) }
	MAX-ACCESS	read-only
	STATUS	current
	DESCRIPTION
		"The critical level of this event."
	::= { snAgSysLogBufferEntry 3 }

snAgSysLogBufferMessage OBJECT-TYPE
	SYNTAX	DisplayString
	MAX-ACCESS	read-only
	STATUS	current
	DESCRIPTION
		"The system logging message."
	::= { snAgSysLogBufferEntry 4 }

snAgSysLogBufferCalTimeStamp OBJECT-TYPE
	SYNTAX	DisplayString
	MAX-ACCESS	read-only
	STATUS	current
	DESCRIPTION
		"A time stamp when the event is logged. This object returns
		a NULL terminated time stamp string if the system calendar
		time was set. It returns a zero length string if the system
		calendar time was not set."
	::= { snAgSysLogBufferEntry 5 }


-- Static System Logging Buffer Table

snAgStaticSysLogBufferTable OBJECT-TYPE
	SYNTAX	SEQUENCE OF SnAgStaticSysLogBufferEntry
	MAX-ACCESS	not-accessible
	STATUS	current
	DESCRIPTION
		"Static system logging buffer table."
	::= { snAgentLog 3 }

snAgStaticSysLogBufferEntry OBJECT-TYPE
	SYNTAX	SnAgStaticSysLogBufferEntry
	MAX-ACCESS	not-accessible
	STATUS	current
	DESCRIPTION
		"A row in the static system logging buffer table."
	INDEX	{ snAgStaticSysLogBufferIndex }
	::= { snAgStaticSysLogBufferTable 1 }

SnAgStaticSysLogBufferEntry ::= SEQUENCE {
	snAgStaticSysLogBufferIndex
		INTEGER,
	snAgStaticSysLogBufferTimeStamp
		TimeTicks,
	snAgStaticSysLogBufferCriticalLevel
		INTEGER,
	snAgStaticSysLogBufferMessage
		DisplayString,
	snAgStaticSysLogBufferCalTimeStamp
		DisplayString
	}

snAgStaticSysLogBufferIndex OBJECT-TYPE
	SYNTAX	INTEGER (1..100)
	MAX-ACCESS	read-only
	STATUS	current
	DESCRIPTION
		"The index to the static system logging buffer table."
	::= { snAgStaticSysLogBufferEntry 1 }

snAgStaticSysLogBufferTimeStamp OBJECT-TYPE
	SYNTAX	TimeTicks
	MAX-ACCESS	read-only
	STATUS	current
	DESCRIPTION
		"A time stamp when the event is logged."
	::= { snAgStaticSysLogBufferEntry 2 }

snAgStaticSysLogBufferCriticalLevel OBJECT-TYPE
	SYNTAX	INTEGER {
		other(1),
		alert(2),
		critical(3),
		debugging(4),
		emergency(5),
		error(6),
		informational(7),
		notification(8),
		warning(9) }
	MAX-ACCESS	read-only
	STATUS	current
	DESCRIPTION
		"The critical level of this event."
	::= { snAgStaticSysLogBufferEntry 3 }

snAgStaticSysLogBufferMessage OBJECT-TYPE
	SYNTAX	DisplayString
	MAX-ACCESS	read-only
	STATUS	current
	DESCRIPTION
		"The system logging message."
	::= { snAgStaticSysLogBufferEntry 4 }

snAgStaticSysLogBufferCalTimeStamp OBJECT-TYPE
	SYNTAX	DisplayString
	MAX-ACCESS	read-only
	STATUS	current
	DESCRIPTION
		"A time stamp when the event is logged. This object returns
		a NULL terminated time stamp string if the system calendar
		time was set. It returns a zero length string if the system
		calendar time was not set."
	::= { snAgStaticSysLogBufferEntry 5 }

-- SysLog Server Table

snAgSysLogServerTable OBJECT-TYPE
	SYNTAX	SEQUENCE OF SnAgSysLogServerEntry
	MAX-ACCESS	not-accessible
	STATUS	current
	DESCRIPTION
		"System Log Server table."
	::= { snAgentLog 4 }

snAgSysLogServerEntry OBJECT-TYPE
	SYNTAX	SnAgSysLogServerEntry
	MAX-ACCESS	not-accessible
	STATUS	current
	DESCRIPTION
		"A row in the SysLog Server table."
	INDEX	{snAgSysLogServerIP, snAgSysLogServerUDPPort}
	::= { snAgSysLogServerTable 1 }

SnAgSysLogServerEntry ::= SEQUENCE {
	snAgSysLogServerIP
		IpAddress,
	snAgSysLogServerUDPPort
		INTEGER,
	snAgSysLogServerRowStatus
		INTEGER
	}

snAgSysLogServerIP OBJECT-TYPE
	SYNTAX  IpAddress
	MAX-ACCESS	read-only
	STATUS	current
	DESCRIPTION
		"IP address of syslog server."
	::= { snAgSysLogServerEntry 1 }

snAgSysLogServerUDPPort       OBJECT-TYPE
	SYNTAX	INTEGER	 (0..65535)
	MAX-ACCESS	read-only
	STATUS  current
	DESCRIPTION
		"UDP port number of syslog server."
	::= { snAgSysLogServerEntry 2 }

snAgSysLogServerRowStatus OBJECT-TYPE
	SYNTAX  INTEGER {
		other(1),
		valid(2),
		delete(3),
		create(4)
		}
	MAX-ACCESS  read-write
	STATUS  current
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  other(1)....some other case
		  valid(2)....the row exists and is valid"
	::= { snAgSysLogServerEntry 3 }

-- Agent System Parameters Configuration Table


snAgentSysParaConfigTable OBJECT-TYPE
	SYNTAX	SEQUENCE OF SnAgentSysParaConfigEntry
	MAX-ACCESS	not-accessible
	STATUS	current
	DESCRIPTION
		"A table of Agent of each board."
	::= { snAgentSysParaConfig 1 }

snAgentSysParaConfigEntry OBJECT-TYPE
	SYNTAX	SnAgentSysParaConfigEntry
	MAX-ACCESS	not-accessible
	STATUS	current
	DESCRIPTION
		"A row in the Agent System Parameters Configuation table."
	INDEX	{ snAgentSysParaConfigIndex }
	::= { snAgentSysParaConfigTable 1 }

SnAgentSysParaConfigEntry ::= SEQUENCE {
	snAgentSysParaConfigIndex
		Integer32,
	snAgentSysParaConfigDescription
		DisplayString,
	snAgentSysParaConfigMin
		Integer32,
	snAgentSysParaConfigMax 
		Integer32,
	snAgentSysParaConfigDefault 
		Integer32,
	snAgentSysParaConfigCurrent
		Integer32
	}

snAgentSysParaConfigIndex OBJECT-TYPE
	SYNTAX  Integer32
	MAX-ACCESS	read-only
	STATUS	current
	DESCRIPTION
		"The index to the Agent System Parameters Configuation Table."
	::= { snAgentSysParaConfigEntry 1 }

snAgentSysParaConfigDescription OBJECT-TYPE
	SYNTAX DisplayString (SIZE(0..32))
	MAX-ACCESS read-only
	STATUS current
	DESCRIPTION
		"The main board description string."
	::= { snAgentSysParaConfigEntry 2 }

snAgentSysParaConfigMin OBJECT-TYPE
	SYNTAX   Integer32
	MAX-ACCESS	read-only
	STATUS	current
	DESCRIPTION
		"The minimum value of this Agent System Parameter."
	::= { snAgentSysParaConfigEntry 3 }

snAgentSysParaConfigMax OBJECT-TYPE
	SYNTAX   Integer32
	MAX-ACCESS	read-only
	STATUS	current
	DESCRIPTION
		"The maximum value of this Agent System Parameter."
	::= { snAgentSysParaConfigEntry 4 }

snAgentSysParaConfigDefault OBJECT-TYPE
	SYNTAX   Integer32
	MAX-ACCESS	read-only
	STATUS	current
	DESCRIPTION
		"The default value of this Agent System Parameter."
	::= { snAgentSysParaConfigEntry 5 }

snAgentSysParaConfigCurrent OBJECT-TYPE
	SYNTAX   Integer32
	MAX-ACCESS	read-write
	STATUS	current
	DESCRIPTION
		"The current configurated value of this Agent System Parameter."
	::= { snAgentSysParaConfigEntry 6 }


-- Agent Configured Module Table


snAgentConfigModuleTable OBJECT-TYPE
	SYNTAX	SEQUENCE OF SnAgentConfigModuleEntry
	MAX-ACCESS	not-accessible
	STATUS	current
	DESCRIPTION
		"A table of each configured module information."
	::= { snAgentConfigModule 1 }

snAgentConfigModuleEntry OBJECT-TYPE
	SYNTAX	SnAgentConfigModuleEntry
	MAX-ACCESS	not-accessible
	STATUS	current
	DESCRIPTION
		"A row in the Agent Configured Module table."
	INDEX	{ snAgentConfigModuleIndex }
	::= { snAgentConfigModuleTable 1 }

SnAgentConfigModuleEntry ::= SEQUENCE {
	snAgentConfigModuleIndex
		Integer32,
	snAgentConfigModuleType
		INTEGER,
	snAgentConfigModuleRowStatus
		INTEGER,
	snAgentConfigModuleDescription
		DisplayString,
	snAgentConfigModuleOperStatus
		DisplayString,
	snAgentConfigModuleSerialNumber
		DisplayString,
	snAgentConfigModuleNumberOfPorts
		Integer32,
	snAgentConfigModuleMgmtModuleType
		INTEGER,
	snAgentConfigModuleNumberOfCpus
		Integer32
	}

snAgentConfigModuleIndex OBJECT-TYPE
	SYNTAX   Integer32
	MAX-ACCESS	read-only
	STATUS	current
	DESCRIPTION
		"The index to the Agent Configured Module Table."
	::= { snAgentConfigModuleEntry 1 }

snAgentConfigModuleType OBJECT-TYPE
	SYNTAX	INTEGER	{
		bi8PortGigManagementModule(0),
		bi4PortGigManagementModule(1),
		bi16PortCopperManagementModule(2),
		bi4PortGigModule(3),
		fi2PortGigManagementModule(4),
		fi4PortGigManagementModule(5),
		bi8PortGigCopperManagementModule(6),
		fi8PortGigManagementModule(7),
		bi8PortGigModule(8),
		bi12PortGigCopper2PortGigFiberManagement(9),
		bi24PortCopperModule(10),
		fi24PortCopperModule(11),
		bi16Port100FXModule(12),
		bi8Port100FXModule(13),
		bi8PortGigCopperModule(14),
		bi12PortGigCopper2PortGigFiber(15),
		bi2PortGigManagementModule(18),
		bi24Port100FXModule(19),
		bi0PortManagementModule(20),
		pos622MbsModule(21),
		pos155MbsModule(22),
		bi2PortGigModule(23),
		bi2PortGigCopperModule(24),
		fi2PortGigModule(25),
		fi4PortGigModule(26),
		fi8PortGigModule(27),
		fi8PortGigCopperModule(28),
		fi8PortGigCopperManagementModule(29),
		pos155Mbs2PModule(30),
		fi4PortGigCopperManagementModule(31),
		fi2PortGigCopperManagementModule(32),
		bi4PortGigCopperManagementModule(33),
		bi2PortGigCopperManagementModule(34),
		bi8PortGigM4ManagementModule(35),
		bi4PortGigM4ManagementModule(36),
		bi2PortGigM4ManagementModule(37),
		bi0PortGigM4ManagementModule(38),
		bi0PortWSMManagementModule(39),
		biPos2Port2488MbsModule(40),
		bi0PortWSMModule(41),
		niPos2Port2488MbsModule(42),
		ni4802(43),
		bi4PortGigNPAModule(44),
		biAtm2Port155MbsModule(45),
		biAtm4Port155MbsModule(46),
		bi1Port10GigModule(47),
		fes4802Module(48),
		fes2402Module(49),
		fes9604Module(50),
		fes12GigCopperAndGigFiberModule(51),
		fesx24GigModule(52),
		fesx24Gig2TenGigModule(53),
		fesx24Gig1TenGigModule(54),
		fesx48GigModule(55),
		fesx48Gig2TenGigModule(56),
		fesx48Gig1TenGigModule(57),
		bi40PortGigCopperHVModule(58), --unused
		bi60PortGigCopperHVModule(59), --unused
		bi8Port10GigModule(60), --unused
		bi10PortGigHVModule(61), --unused
		bi20PortGigHVModule(62), --unused
		bi24PortGigModule(63), --unused
		bi24PortGigCopperModule(64), --unused
		bi48PortGigCopperModule(65), --unused
		bi24PortGigFiberModule(66), --unused
		ni4Port10GigSPModule(75), --unused
		ni40PortGigSPModule(76), --unused
		ni40PortGigCopperSPModule(77), --unused
		ni2Port10GigSPModule(78), --unused
		ni10PortGigSPModule(79), --unused
		ni20PortGigSPModule(80), --unused
		xmr4Port10GigSPModule(81), --unused
		xmr20PortGigSPModule(82), --unused
		xmr2Port10GigSPModule(83), --unused
		xmr20PortGigCopperSPModule(84), --unused
		xmr20PortGigFXSPModule(85), --unused
		niImrMrManagementModule(86), --unused
		niXmrMrManagementModule(87), --unused
		xer4Port10GigSPModule(88), --unused
		xer2Port10GigSPModule(89), --unused
		xer20PortGigCopperSPModule(90), --unused
		xer20PortGigFXSPModule(91), --unused
		mlx4Port10GigSPModule(92), --unused
		mlx2Port10GigSPModule(93), --unused
		mlx20PortGigCopperSPModule(94), --unused
		mlx20PortGigFXSPModule(95), --unused
		mlx48PortGigMrj21SPModule(103), --unused		
		fesx24GigFiberGigCopperModule(112),
		fesx24GigFiber2TenGigModule(113),
		fesx24GigFiber1TenGigModule(114),

		-- Modules for FGS/FLS family
		fgs24PortManagementModule(144),  
		fgs48PortManagementModule(145),   
		fgsXfp2Port10gModule(152),  
		fgsCx42Port10gModule(153), 
		fgsXfp1Cx41Port10gModule(154),  
		fgsXpf1Port10gModule(155),    
		fls24PortCopperBaseModule(160),   
		fls48PortCopperBaseModule(161),   
		flsXfp1Port10gModule(168),   
		flsCx41Port10gModule(169),  

		--Modules for FCX family
		fcx624SBaseModule(176),   
		fcx648SBaseModule(177),   
		fcx624SPoeBaseModule(180),   
		fcx648SPoeBaseModule(181),   
		fcxXfp2Port10gModule(184),    
		fcxCx42Port16gModule(185),   
		fcx624SFBaseModule(192),   

		biFiJc48ePort100fxIpcModule(195),
		biFiJc48tPort100fxIpcModule(196),
		biFiJc8PortGigM4ManagementModule(197),
		biFiJc8PortGigIgcModule(198),
		biFiJc16PortGigIgcModule(200),
		biJc24PortCopperIpc4GigIgcModule(201),
		biJc16PortGigCopperIgcModule(202),
		biFiJc24Port100fxIpcModule(206),
		bi2Port10GigModule(207),
		biJc48tPortRJ21OmpModule(208),
		biJc48ePortRJ45OmpModule(209),
		biJc24PortIpcRJ45PoeModule(212),
		biJc2PortGigIgcM4ManagementModule(214),

		--Modules for MG-8, RX, XMR, MLX
		
		fdryBi4Port10GigModule(1048), --
		fdryBi40PortGigModule(1049), --
		fdryBi1Port100FXManagementModule(1050),
		fdryBi2Port10GigModule(1051), --
		fdryBi40PortGigCopperModule(1052), --
		fdryBi60PortGigCopperModule(1053), --
		fdryBi4Port10GigHVModule(1054), --
		fdryBi2Port10GigHVModule(1055), --
		fdryBi8Port10GigHVModule(1056), --
		fdryBi40PortGigHVModule(1057), --
		fdryBi40PortGigCopperHVModule(1058), --
		fdryBi60PortGigCopperHVModule(1059), --
		fdryBi8Port10GigModule(1060), --
		fdryBi10PortGigHVModule(1061), --
		fdryBi20PortGigHVModule(1062), --
		fdryBi24PortGigModule(1063), --
		fdryBi24PortGigCopperModule(1064), --
		fdryBi48PortGigCopperModule(1065),
		fdryBi24PortGigFiberModule(1066),
		fdryBi16Port10GigModule(1067),
		fdryNi4Port10GigSPModule(1075),
		fdryNi40PortGigSPModule(1076),
		fdryNi40PortGigCopperSPModule(1077),
		fdryNi2Port10GigSPModule(1078),
		fdryNi10PortGigSPModule(1079),
		fdryNi20PortGigSPModule(1080),
		fdryXmr4Port10GigSPModule(1081), --
		fdryXmr20PortGigSPModule(1082), --
		fdryXmr2Port10GigSPModule(1083), --
		fdryXmr20PortGigCopperSPModule(1084), --
		fdryXmr20PortGigFXSPModule(1085), --
		fdryNiImrMrManagementModule(1086),
		fdryNiXmrMrManagementModule(1087),
		fdryMlx4Port10GigSPModule(1088), --
		fdryMlx2Port10GigSPModule(1089), --
		fdryMlx20PortGigCopperSPModule(1090), --
		fdryMlx20PortGigFXSPModule(1091), --
		niMlx8Port10GigSPModule (1092),
		niCes24PortFiberModule(1096),
		niCes24PortCopperModule(1097),
		niCes2Port10GigModule(1098),
		niCes48PortFiberModule(1099),
		niCes48PortCopperModule(1100),
		niCes48PortFiberWith2Port10GModule(1101),
		niCes48PortCopperWith2Port10GModule(1102),		
		fdryMlx48PortGigMrj21SPModule(1103), --
		fdryXmr2PortOC192SPModule(1104), --
		fdryXmr1PortOC192SPModule(1105), --
		fdryXmr8PortOC48SPModule(1106), --
		fdryXmr4PortOC48SPModule(1107), --
		fdryXmr2PortOC48SPModule(1108), --
		fdryNiMlxMrManagementModule(1109),--
		
		--Modules for FastIron Superx, SXR8, SXR16, V4 and V6 Modules (unused after FI8.0.50)

		--fdryFiV4Sx12ComboPortManagementModule(2064),
		--fdryFiV4Sx2Port10gModule(2065),
		--fdryFiV4Sx24PortGigCopperModule(2066),
		--fdryFiV4Sx24PortGigFiberModule(2067),
		--fdryFiV4Sx2Port10gLanWanModule(2068),		
		--fdryFiV4Sx24Port100m1gFiberModule(2069),		
		--fdryFiV4Sx12ComboPortManagement2Module(2074),
		--fdryFiV4Sx210gPortManagementModule(2080),
		--fdryFiSx0PortManagementModule(2081),
		--fdryFiV4Sx4g4fPortManagementModule(2083),
		--fdryFiV6Sx12ComboPortManagementModule(2096),
		--fdryFiV6Sx24PortGigCopperModule(2098),
		--fdryFiV6Sx2Port10gModule(2100),
		--fdryFiV6Sx24Port100m1gFiberModule(2101),
		--fdryFiV6Sx210gPortManagementModule(2102),
		--fdryFiV6Sx48PortGigCopperPoeModule(2103),
		--fdryFiV6Sx4g4fPortManagementModule(2104),
		--fdryFiV6Sx12ComboPortManagement2Module(2105),		
		--fdryFiV6Sx48PortGigCopperModule(2106),
		--fdryFiV6SxXl0PortManagementModule(2112),
		--fdryFiV6SxXl210gPortManagementModule(2113),

		-- Modules for FWS family (unused after FI8.0.20)
		--fdryFws24PortCopperBaseModule(2224),  
		--fdryFws48PortCopperBaseModule(2225),   
		--fdryFws24GPortCopperBaseModule(2226),  
		--fdryFws48GPortCopperBaseModule(2227),  

		--Modules for FCX family  (unused after FI8.0.95)
		--fdryFcx624BaseModule(2208),
		--fdryFcx648BaseModule(2209),
		--fdryFcxSfpPlus4Port10gModule(2220),

		--Modules for ICX6610 family
		fdryIcx6610624BaseModule(2240),
		fdryIcx6610648BaseModule(2241),
		fdryIcx6610624PoeBaseModule(2244),
		fdryIcx6610648PoeBaseModule(2245),
		fdryIcx6610624FBaseModule(2246),
		fdryIcx6610DualMode8PortModule(2248),
		fdryIcx6610Qsfp10Port160gModule(2249),

		--Modules for ICX6430 family
		fdryIcx6430624BaseModule(2016),
		fdryIcx6430648BaseModule(2017),
		fdryIcx6430624PoeBaseModule(2020),
		fdryIcx6430648PoeBaseModule(2021),
		fdryIcx6430sfp4Port4gModule(2024),
		-- fdryIcx6430612CBaseModule(2137),
		fdryIcx6430Copper2Port2gModule(2138),
		fdryIcx6430sfp2Port2gModule(2139),
	
		--Modules for ICX6450 family
		fdryIcx6450624BaseModule(2032),
		fdryIcx6450648BaseModule(2033),
		fdryIcx6450624PoeBaseModule(2036),
		fdryIcx6450648PoeBaseModule(2037),
		fdryIcx6450sfp4Port40gModule(2040),
		fdryIcx6450612CPDBaseModule(2140),
		fdryIcx6450Copper2Port2gModule(2141),
		fdryIcx6450sfp2Port2gModule(2142),

		--Modules for ICX6650 family
		fdryIcx665056BaseModule(2055),
		fdryIcx6650sfp4Port40gModule(2056),
		fdryIcx6650sfp8Port10gModule(2057),

		--Modules for ICX7750 family
		fdryIcx775048CBaseModule(2134),
		fdryIcx775048FBaseModule(2133),
		fdryIcx775026QBaseModule(2132),
		fdryIcx7750QSFP6port40gModule(2136),
		fdryIcx77506Q6port40gModule(2137),

		--Modules for ICX7450 family
		fdryIcx7450624BaseModule(2224),
		fdryIcx7450648BaseModule(2225),
		fdryIcx7450648FBaseModule(2227),
		fdryIcx7450624PoeBaseModule(2228),
		fdryIcx7450648PoeBaseModule(2229),
		fdryIcx7450632ZPBaseModule(2230),
		fdryIcx7400ServiceModule(2232),
		fdryIcx7400sfpplus4Port40gModule(2233),
		fdryIcx7400copper4Port40gModule(2234),
		fdryIcx7400sfp4Port4gModule(2235),
		fdryIcx7400qsfpplus1Port40gModule(2236),
		
		--Modules for ICX7250 family
		fdryIcx7250624BaseModule(2162),
		fdryIcx7250648BaseModule(2163),
		fdryIcx7250624GBaseModule(2160),
		fdryIcx7250624PoeBaseModule(2164),
		fdryIcx7250648PoeBaseModule(2165),
		fdryIcx7250sfpplus8Port80gModule(2169),
		fdryIcx7250sfpplus4Port4gModule(2168),

		--Modules for ICX7150 family
		fdryIcx7150624BaseModule(2064),
		fdryIcx7150648BaseModule(2065),
		fdryIcx7150648ZPBaseModule(2066),
		fdryIcx7150612CPoeBaseModule(2068),
		fdryIcx7150624PoeBaseModule(2069),
		fdryIcx7150648PoeBaseModule(2070),
		fdryIcx7150648PoeFBaseModule(2071),
		fdryIcx7150gc2Port2gModule(2072),
		fdryIcx7150sfpplus4Port40gModule(2073),
		fdryIcx7150sfpplus2Port20gModule(2074),
		fdryIcx7150sfpplus8Port80gModule(2075),
		fdryIcx7150C08PBaseModule(2176),
		fdryIcx7150C10ZPBaseModule(2177),
		fdryIcx7150624FBaseModule(2178),
        fdryIcx7150C08PTBaseModule(2179),
		fdryIcx7150sfp2Port2gModule(2184),
		fdryIcx7150gc2Port20gModule(2185),


		--Modules for ICX7650 family
		fdryIcx7650648FBaseModule(2144),
		fdryIcx7650648ZPBaseModule(2148),
		fdryIcx7650648PBaseModule(2149),
		fdryIcx76001Port100gModule(2152),
		fdryIcx76002Port80gModule(2153),
		fdryIcx76004Port40gModule(2154),
		fdryIcx76504Port160gModule(2155),
		fdryIcx76502Port200gModule(2156),
		fdryIcx76502Port80gModule(2157),

		--Modules for ICX7850 family
		fdryIcx7850632QBaseModule(2192),
		fdryIcx7850648FBaseModule(2193),
		fdryIcx7850648FSBaseModule(2194),
		fdryIcx7850648CBaseModule(2195),
		fdryIcx780012Port1200gModule(2200),
		fdryIcx78008Port800gModule(2201),

	    --Modules for ICX7550 family
		fdryIcx7550624BaseModule(2208),
		fdryIcx7550648BaseModule(2209),
		fdryIcx7550624FBaseModule(2210),
		fdryIcx7550648FBaseModule(2211),
		fdryIcx7550624PBaseModule(2212),
		fdryIcx7550648PBaseModule(2213),
		fdryIcx7550624ZPBaseModule(2214),
		fdryIcx7550648ZPBaseModule(2215),
	    fdryIcx75502Port200gModule(2216),
		fdryIcx75502Port80gModule(2217),
		fdryIcx755076004Port40gModule(2218),
		fdryIcx755076002Port80gModule(2219),
		fdryIcx755076001Port100gModule(2220),

		--Modules for ICX8200 family
		fdryIcx8200624BaseModule(2080),
		fdryIcx8200624PBaseModule(2081),
		fdryIcx8200648BaseModule(2082),
		fdryIcx8200648PBaseModule(2083),
		fdryIcx8200648PFBaseModule(2084),
		fdryIcx8200648PF2BaseModule(2085),
		fdryIcx8200624ZPBaseModule(2086),
		fdryIcx8200648ZP2BaseModule(2087),
		fdryIcx8200624FXBaseModule(2096),
		fdryIcx8200624FBaseModule(2097),
		fdryIcx8200648FBaseModule(2098),
		fdryIcx8200C08PBaseModule(2099),
		fdryIcx8200C08PTBaseModule(2100),
		fdryIcx8200C08PDCBaseModule(2101),
		fdryIcx8200C08PFBaseModule(2102),
		fdryIcx8200C08ZPBaseModule(2103),
		fdryIcx82004Port100gModule(2088),
		fdryIcx82008Port200gModule(2089),
		fdryIcx82002Port2gModule(2090),
		fdryIcx82002Port20gModule(2091),
		fdryIcx82002Port50gModule(2092),
		fdryIcx82002Port20gcfModule(2093)

		}	
	MAX-ACCESS read-write
	STATUS current
	DESCRIPTION
		"The Configured Module Type."
	::= { snAgentConfigModuleEntry 2 }


snAgentConfigModuleRowStatus OBJECT-TYPE
	SYNTAX	INTEGER	{
		other(1),
		valid(2),
		delete(3),
		create(4) }
	MAX-ACCESS	read-write
	STATUS	current
	DESCRIPTION
		"To create or delete a configured module table entry."
	::= { snAgentConfigModuleEntry 3 }


snAgentConfigModuleDescription OBJECT-TYPE
	SYNTAX	DisplayString
	MAX-ACCESS	read-only
	STATUS	current
	DESCRIPTION
		"A description of the configured module."
	::= { snAgentConfigModuleEntry 4 }


snAgentConfigModuleOperStatus OBJECT-TYPE
	SYNTAX	DisplayString
	MAX-ACCESS	read-only
	STATUS	current
	DESCRIPTION
		"Module operational status. Zero length string indicates
		that physical module has not been inserted to the chassis."
	::= { snAgentConfigModuleEntry 5 }


snAgentConfigModuleSerialNumber OBJECT-TYPE
	SYNTAX	DisplayString
	MAX-ACCESS	read-only
	STATUS	current
	DESCRIPTION
		"Module serial number. Zero length string indicates that
		module serial number EEPROM has not been programmed or
		the module does not support serial number EEPROM."
	::= { snAgentConfigModuleEntry 6 }


snAgentConfigModuleNumberOfPorts OBJECT-TYPE
	SYNTAX   Integer32
	MAX-ACCESS	read-only
	STATUS	current
	DESCRIPTION
		"The number of ports of module."
	::= { snAgentConfigModuleEntry 7 }


snAgentConfigModuleMgmtModuleType OBJECT-TYPE
	SYNTAX	INTEGER	{
		other(1),
		nonManagementModule(2),
		unknownManagementModule(3),
		m1ManagementModule(4),
		m2ManagementModule(5),
		m3ManagementModule(6),
		m4ManagementModule(7),
		m5ManagementModule(8),
		jetcoreStackManagementModule(9), 
		muchoManagementModule(10),
		rottWeilerManagementModule(11),
		fesXStackManagementModule(12),
		fgsStackManagementModule(13),
		niCesManagementModule(14),
		fastIronSuperXManagementModule(15),
		fastIronSXRManagementModule(16),
		fastIronV6SuperXManagementModule(17),
		fastIronV6SXRManagementModule(18),
		icxStackManagementModule(19),
		icxManagementModule(20)
		}	
	MAX-ACCESS	read-only
	STATUS	current
	DESCRIPTION
		"Management module type."
	::= { snAgentConfigModuleEntry 8 }


snAgentConfigModuleNumberOfCpus OBJECT-TYPE
	SYNTAX   Integer32
	MAX-ACCESS	read-only
	STATUS	current
	DESCRIPTION
		"The number of module CPUs."
	::= { snAgentConfigModuleEntry 9 }


-- Agent System Parameters stacking Configuration Table

snAgentConfigModule2Table OBJECT-TYPE
	SYNTAX	SEQUENCE OF SnAgentConfigModule2Entry
	MAX-ACCESS	not-accessible
	STATUS	current
	DESCRIPTION
		"A table of each configured stacking module information."
	::= { snAgentConfigModule 2 }

snAgentConfigModule2Entry OBJECT-TYPE
	SYNTAX	SnAgentConfigModule2Entry
	MAX-ACCESS	not-accessible
	STATUS	current
	DESCRIPTION
		"A row in the Agent Configured Stacking Module table."
	INDEX	{ snAgentConfigModule2Unit, 
					 snAgentConfigModule2Slot 
	}
	::= { snAgentConfigModule2Table 1 }

SnAgentConfigModule2Entry ::= SEQUENCE {
	snAgentConfigModule2Unit
		Integer32,
	snAgentConfigModule2Slot
		Integer32,
	snAgentConfigModule2Type
		INTEGER,
	snAgentConfigModule2RowStatus
		INTEGER,
	snAgentConfigModule2Description
		DisplayString,
	snAgentConfigModule2OperStatus
		DisplayString,
	snAgentConfigModule2SerialNumber
		DisplayString,
	snAgentConfigModule2NumberOfPorts
		Integer32,
	snAgentConfigModule2MgmtModuleType
		INTEGER,
	snAgentConfigModule2NumberOfCpus
		Integer32
	}

snAgentConfigModule2Unit OBJECT-TYPE
	SYNTAX   Integer32
	MAX-ACCESS	read-only
	STATUS	current
	DESCRIPTION
		"The index to the Agent Configured Module Table."
	::= { snAgentConfigModule2Entry 1 }
	
snAgentConfigModule2Slot OBJECT-TYPE
	SYNTAX   Integer32
	MAX-ACCESS	read-only
	STATUS	current
	DESCRIPTION
		"The index to the Agent Configured Module Table."
	::= { snAgentConfigModule2Entry 2 }

snAgentConfigModule2Type OBJECT-TYPE
	SYNTAX	INTEGER	{
		fgs24PortManagementModule(144),     
		fgs48PortManagementModule(145),   
		fgsXfp2Port10gModule(152),  
		fgsCx42Port10gModule(153),  
		fgsXfp1Cx41Port10gModule(154),  
		fgsXpf1Port10gModule(155),   
		fls24PortCopperBaseModule(160),   
		fls48PortCopperBaseModule(161),   
		flsXfp1Port10gModule(168),   
		flsCx41Port10gModule(169),  
		fcx624SBaseModule(176),   
		fcx648SBaseModule(177),   
		fcx624SPoeBaseModule(180),   
		fcx648SPoeBaseModule(181),   
		fcxXfp2Port10gModule(184),   
		fcxCx42Port16gModule(185),   
		fcx624SFBaseModule(192), 
		
		-- Modules for FWS family (unused after FI8.0.20)
		--fdryFws24PortCopperBaseModule(2224),   
		--fdryFws48PortCopperBaseModule(2225),  
		--fdryFws24GPortCopperBaseModule(2226),  
		--fdryFws48GPortCopperBaseModule(2227), 
		
		--Modules for FCX family  (unused after FI8.0.95)
		--fdryFcx624BaseModule(2208),
		--fdryFcx648BaseModule(2209),
		--fdryFcxSfpPlus4Port10gModule(2220),
		
		--Modules for ICX6610 family
		fdryIcx6610624BaseModule(2240),
		fdryIcx6610648BaseModule(2241),
		fdryIcx6610624PoeBaseModule(2244),
		fdryIcx6610648PoeBaseModule(2245),
		fdryIcx6610624FBaseModule(2246),
		fdryIcx6610DualMode8PortModule(2248),
		fdryIcx6610Qsfp10Port160gModule(2249),

		--Modules for ICX6430 family
		fdryIcx6430624BaseModule(2016),
		fdryIcx6430648BaseModule(2017),
		fdryIcx6430624PoeBaseModule(2020),
		fdryIcx6430648PoeBaseModule(2021),
		fdryIcx6430sfp4Port4gModule(2024),
		-- fdryIcx6430612CBaseModule(2137),
		fdryIcx6430Copper2Port2gModule(2138),
		fdryIcx6430sfp2Port2gModule(2139),
	
		--Modules for ICX6450 family
		fdryIcx6450624BaseModule(2032),
		fdryIcx6450648BaseModule(2033),
		fdryIcx6450624PoeBaseModule(2036),
		fdryIcx6450648PoeBaseModule(2037),
		fdryIcx6450sfp4Port40gModule(2040),
		fdryIcx6450612CPDBaseModule(2140),
		fdryIcx6450Copper2Port2gModule(2141),
		fdryIcx6450sfp2Port2gModule(2142),

		--Modules for ICX6650 family
		fdryIcx665056BaseModule(2055),
		fdryIcx6650sfp4Port40gModule(2056),
		fdryIcx6650sfp8Port10gModule(2057),

		--Modules for ICX7750 family
		fdryIcx775048CBaseModule(2134),
		fdryIcx775048FBaseModule(2133),
		fdryIcx775026QBaseModule(2132),
		fdryIcx7750QSFP6port40gModule(2136),
		fdryIcx77506Q6port40gModule(2137),

		--Modules for ICX7450 family
		fdryIcx7450624BaseModule(2224),
		fdryIcx7450648BaseModule(2225),
		fdryIcx7450648FBaseModule(2227),
		fdryIcx7450624PoeBaseModule(2228),
		fdryIcx7450648PoeBaseModule(2229),
		fdryIcx7450632ZPBaseModule(2230),
		fdryIcx7400ServiceModule(2232),
		fdryIcx7400sfpplus4Port40gModule(2233),
		fdryIcx7400copper4Port40gModule(2234),
		fdryIcx7400sfp4Port4gModule(2235),
		fdryIcx7400qsfpplus1Port40gModule(2236),

		--Modules for ICX7250 family
		fdryIcx7250624BaseModule(2162),
		fdryIcx7250648BaseModule(2163),
		fdryIcx7250624GBaseModule(2160),
		fdryIcx7250624PoeBaseModule(2164),
		fdryIcx7250648PoeBaseModule(2165),
		fdryIcx7250sfpplus8Port80gModule(2169),
		fdryIcx7250sfpplus4Port4gModule(2168),

		--Modules for ICX7150 family
		fdryIcx7150624BaseModule(2064),
		fdryIcx7150648BaseModule(2065),
		fdryIcx7150648ZPBaseModule(2066),
		fdryIcx7150612CPoeBaseModule(2068),
		fdryIcx7150624PoeBaseModule(2069),
		fdryIcx7150648PoeBaseModule(2070),
		fdryIcx7150648PoeFBaseModule(2071),
		fdryIcx7150gc2Port2gModule(2072),
		fdryIcx7150sfpplus4Port40gModule(2073),
		fdryIcx7150sfpplus2Port20gModule(2074),
		fdryIcx7150sfpplus8Port80gModule(2075),
		fdryIcx7150C08PBaseModule(2176),
		fdryIcx7150C10ZPBaseModule(2177),
		fdryIcx7150624FBaseModule(2178),
		fdryIcx7150C08PTBaseModule(2179),
		fdryIcx7150sfp2Port2gModule(2184),
		fdryIcx7150gc2Port20gModule(2185),

		--Modules for ICX7650 family
		fdryIcx7650648FBaseModule(2144),
		fdryIcx7650648ZPBaseModule(2148),
		fdryIcx7650648PBaseModule(2149),
		fdryIcx76001Port100gModule(2152),
		fdryIcx76002Port80gModule(2153),
		fdryIcx76004Port40gModule(2154),
		fdryIcx76504Port160gModule(2155),
		fdryIcx76502Port200gModule(2156),
		fdryIcx76502Port80gModule(2157),

		--Modules for ICX7850 family
		fdryIcx7850632QBaseModule(2192),
		fdryIcx7850648FBaseModule(2193),
		fdryIcx7850648FSBaseModule(2194),
		fdryIcx7850648CBaseModule(2195),
		fdryIcx780012Port1200gModule(2200),
		fdryIcx78008Port800gModule(2201),

		--Modules for ICX7550 family
		fdryIcx7550624BaseModule(2208),
		fdryIcx7550648BaseModule(2209),
		fdryIcx7550624FBaseModule(2210),
		fdryIcx7550648FBaseModule(2211),
		fdryIcx7550624PBaseModule(2212),
		fdryIcx7550648PBaseModule(2213),
		fdryIcx7550624ZPBaseModule(2214),
		fdryIcx7550648ZPBaseModule(2215),
	    fdryIcx75502Port200gModule(2216),
		fdryIcx75502Port80gModule(2217),
		fdryIcx755076004Port40gModule(2218),
		fdryIcx755076002Port80gModule(2219),
		fdryIcx755076001Port100gModule(2220),

		--Modules for ICX8200 family
		fdryIcx8200624BaseModule(2080),
		fdryIcx8200624PBaseModule(2081),
		fdryIcx8200648BaseModule(2082),
		fdryIcx8200648PBaseModule(2083),
		fdryIcx8200648PFBaseModule(2084),
		fdryIcx8200648PF2BaseModule(2085),
		fdryIcx8200624ZPBaseModule(2086),
		fdryIcx8200648ZP2BaseModule(2087),
		fdryIcx8200624FXBaseModule(2096),
		fdryIcx8200624FBaseModule(2097),
		fdryIcx8200648FBaseModule(2098),
		fdryIcx8200C08PBaseModule(2099),
		fdryIcx8200C08PTBaseModule(2100),
		fdryIcx8200C08PDCBaseModule(2101),
		fdryIcx8200C08PFBaseModule(2102),
		fdryIcx8200C08ZPBaseModule(2103),
		fdryIcx82004Port100gModule(2088),
		fdryIcx82008Port200gModule(2089),
		fdryIcx82002Port2gModule(2090),
		fdryIcx82002Port20gModule(2091),
		fdryIcx82002Port50gModule(2092),
		fdryIcx82002Port20gcfModule(2093)

		}	
	MAX-ACCESS read-write
	STATUS current
	DESCRIPTION
		"The Configured Module Type."
	::= { snAgentConfigModule2Entry 3 }


snAgentConfigModule2RowStatus OBJECT-TYPE
	SYNTAX	INTEGER	{
		other(1),
		valid(2),
		delete(3),
		create(4) }
	MAX-ACCESS	read-write
	STATUS	current
	DESCRIPTION
		"To create or delete a configured module table entry."
	::= { snAgentConfigModule2Entry 4 }


snAgentConfigModule2Description OBJECT-TYPE
	SYNTAX	DisplayString
	MAX-ACCESS	read-only
	STATUS	current
	DESCRIPTION
		"A description of the configured module."
	::= { snAgentConfigModule2Entry 5 }


snAgentConfigModule2OperStatus OBJECT-TYPE
	SYNTAX	DisplayString
	MAX-ACCESS	read-only
	STATUS	current
	DESCRIPTION
		"Module operational status. Zero length string indicates
		that physical module has not been inserted to the chassis."
	::= { snAgentConfigModule2Entry 6 }


snAgentConfigModule2SerialNumber OBJECT-TYPE
	SYNTAX	DisplayString
	MAX-ACCESS	read-only
	STATUS	current
	DESCRIPTION
		"Module serial number. Zero length string indicates that
		module serial number EEPROM has not been programmed or
		the module does not support serial number EEPROM."
	::= { snAgentConfigModule2Entry 7 }


snAgentConfigModule2NumberOfPorts OBJECT-TYPE
	SYNTAX   Integer32
	MAX-ACCESS	read-only
	STATUS	current
	DESCRIPTION
		"The number of ports of module."
	::= { snAgentConfigModule2Entry 8 }


snAgentConfigModule2MgmtModuleType OBJECT-TYPE
	SYNTAX	INTEGER	{
		other(1),
		nonManagementModule(2),
		unknownManagementModule(3),
		m1ManagementModule(4),
		m2ManagementModule(5),
		m3ManagementModule(6),
		m4ManagementModule(7),
		m5ManagementModule(8),
		jetcoreStackManagementModule(9),
		muchoManagementModule(10),
		rottWeilerManagementModule(11),
		fesXStackManagementModule(12),
		fgsStackManagementModule(13),
		icxStackManagementModule(19),
		icxManagementModule(20)
		}
	MAX-ACCESS	read-only
	STATUS	current
	DESCRIPTION
		"Management module type."
	::= { snAgentConfigModule2Entry 9 }


snAgentConfigModule2NumberOfCpus OBJECT-TYPE
	SYNTAX   Integer32
	MAX-ACCESS	read-only
	STATUS	current
	DESCRIPTION
		"The number of module CPUs."
	::= { snAgentConfigModule2Entry 10 }


-- Agent User Access Group


snAgentUserGbl OBJECT IDENTIFIER ::= { snAgentUser 1 }

snAgentUserMaxAccnt         OBJECT-TYPE
	SYNTAX   Integer32
	MAX-ACCESS	read-only
	STATUS	current
	DESCRIPTION
		"Maximum number of user account entries can be configured."
	::= { snAgentUserGbl 1 }


-- Agent User Account Table


snAgentUserAccntTable       OBJECT-TYPE
	SYNTAX	SEQUENCE OF SnAgentUserAccntEntry
	MAX-ACCESS	not-accessible
	STATUS	current
	DESCRIPTION
		"A table of user account information."
	::= { snAgentUser 2 }

snAgentUserAccntEntry       OBJECT-TYPE
	SYNTAX	SnAgentUserAccntEntry
	MAX-ACCESS	not-accessible
	STATUS	current
	DESCRIPTION
		"A row in the Agent User table."
	INDEX	{ snAgentUserAccntName }
	::= { snAgentUserAccntTable 1 }

SnAgentUserAccntEntry ::= SEQUENCE {
	snAgentUserAccntName
		DisplayString,
	snAgentUserAccntPassword
		DisplayString,
	snAgentUserAccntEncryptCode
		Integer32,
	snAgentUserAccntPrivilege
		Integer32,
	snAgentUserAccntRowStatus
		INTEGER
	}

snAgentUserAccntName        OBJECT-TYPE
	SYNTAX  DisplayString (SIZE (1..48))
	MAX-ACCESS	read-only
	STATUS	current
	DESCRIPTION
		"The user name."
	::= { snAgentUserAccntEntry 1 }

snAgentUserAccntPassword    OBJECT-TYPE
	SYNTAX	DisplayString (SIZE (0..48))
	MAX-ACCESS	read-write
	STATUS	current
	DESCRIPTION
		"The user password."
	::= { snAgentUserAccntEntry 2 }

snAgentUserAccntEncryptCode OBJECT-TYPE
	SYNTAX   Integer32
	MAX-ACCESS	read-write
	STATUS	current
	DESCRIPTION
		"The password encryption method code."
	::= { snAgentUserAccntEntry 3 }

snAgentUserAccntPrivilege   OBJECT-TYPE
	SYNTAX   Integer32
	MAX-ACCESS	read-write
	STATUS	current
	DESCRIPTION
		"The user privilege."
	::= { snAgentUserAccntEntry 4 }

snAgentUserAccntRowStatus   OBJECT-TYPE
	SYNTAX	INTEGER	{
		other(1),
		valid(2),
		delete(3),
		create(4),
		modify(5) }
	MAX-ACCESS	read-write
	STATUS	current
	DESCRIPTION
		"To create or delete a user account table entry."
	::= { snAgentUserAccntEntry 5 }

-- Agent Redundant Group


snAgentRedunGbl OBJECT IDENTIFIER ::= { snAgentRedundant 1 }

snAgentRedunActiveMgmtMod      OBJECT-TYPE
	SYNTAX   Integer32
	MAX-ACCESS	read-write
	STATUS	current
	DESCRIPTION
		"Slot number of the active management module. Setting
		this object does not take effect immediately. Saving
		configuration data to flash storage and reboot the
		system are required to take effect. Setting a value of 0
		requests the system to auto-select an active management
		module after power up."
	DEFVAL { 0 }
	::= { snAgentRedunGbl 1 }

snAgentRedunSyncConfig         OBJECT-TYPE
	SYNTAX   Integer32
	MAX-ACCESS	read-write
	STATUS	current
	DESCRIPTION
		"Frequency of the backup management module copying the
		configuration data from the active management module.
		Each unit is 1 second. Setting a value 0 will disable
		the synchronization copy. Setting a negative value will
		initiate the synchronization copy once immediately."
	::= { snAgentRedunGbl 2 }

snAgentRedunBkupCopyBootCode   OBJECT-TYPE
	SYNTAX	INTEGER { disabled(0), enabled(1) }
	MAX-ACCESS	read-write
	STATUS	current
	DESCRIPTION
		"If enabled(1), the backup management module copies the boot code
		from the active management module to its boot code flash storage
		after power up, and whenever the active management module's boot
		code is updated. The backup management module does not copy if
		both boot codes were identical."
	DEFVAL { disabled }
	::= { snAgentRedunGbl 3 }

snAgentEnableMgmtModRedunStateChangeTrap OBJECT-TYPE
	SYNTAX	INTEGER { disabled(0), enabled(1) }
	MAX-ACCESS	read-write
	STATUS	current
	DESCRIPTION
		"Indicates whether the SNMP agent process is permitted to
		generate management module redundancy state change traps."
	DEFVAL { enabled }
	::= { snAgentRedunGbl 4 }

snAgentRedunBkupBootLoad       OBJECT-TYPE
	SYNTAX	INTEGER {
		normal(1),
		operationError(17),
		downloadBackup(20)
		}
	MAX-ACCESS	read-write
	STATUS	current
	DESCRIPTION
		"Action object to down load a new boot code from boot flash storage
		of the active management module to the backup management module.
		The following are returned values from get operation:
		  normal(1)............no operation
		  operationError(17)...error codes

		The following are input values from set operation:
		  downloadBackup(20)...download the boot code from the active
							   management module to the backup management
							   module

		Any set operation is rejected during loading until error
		or normal state is reached."
	::= { snAgentRedunGbl 5 }

snAgentRedunSwitchOver         OBJECT-TYPE
	SYNTAX	INTEGER {
		other(1),
		reset(2)
		}
	MAX-ACCESS	read-write
	STATUS	current
	DESCRIPTION
		"To force a switch-over from standby to active state
		if the backup management module exists in a chassis."
	::= { snAgentRedunGbl 6 }

-- System CPU Utilization Table.

snAgentCpuUtilTable     OBJECT-TYPE
	SYNTAX	SEQUENCE OF SnAgentCpuUtilEntry
	MAX-ACCESS	not-accessible
	STATUS	current
	DESCRIPTION
		"Table to list utilization for all CPUs in the device."
	::= { snAgentCpu 1 }

snAgentCpuUtilEntry	OBJECT-TYPE
	SYNTAX	SnAgentCpuUtilEntry
	MAX-ACCESS	not-accessible
	STATUS	current
	DESCRIPTION
		"A row in the CPU utilization table."
	INDEX	{ 
		snAgentCpuUtilSlotNum,
		snAgentCpuUtilCpuId,
		snAgentCpuUtilInterval
	}
	::= { snAgentCpuUtilTable 1 }

SnAgentCpuUtilEntry ::= SEQUENCE {
	snAgentCpuUtilSlotNum
		Integer32,
	snAgentCpuUtilCpuId
		Integer32,
	snAgentCpuUtilInterval
		Integer32,
	snAgentCpuUtilValue
		Gauge32,
	snAgentCpuUtilPercent
		Gauge32,
	snAgentCpuUtil100thPercent
		Gauge32
	}

snAgentCpuUtilSlotNum	OBJECT-TYPE
	SYNTAX Integer32
	MAX-ACCESS	read-only
	STATUS	current
	DESCRIPTION
		"The slot number of module which contains the cpu."
	::= { snAgentCpuUtilEntry 1 }

snAgentCpuUtilCpuId  OBJECT-TYPE
	SYNTAX   Integer32
	MAX-ACCESS	read-only
	STATUS	current
	DESCRIPTION
		"The id of cpu. For non-VM1/WSM management module, there is one CPU.
		For VM1/WSM there's one management CPU and three slave CPUs.
		The management CPU could be turned off. For POS and ATM
		there's no management CPU but  two slave CPUs.
		Id for management cpu is 1. Value of 2 or greater are for slave CPUs. "
	::= { snAgentCpuUtilEntry 2 }

snAgentCpuUtilInterval  OBJECT-TYPE
	SYNTAX   Integer32
	MAX-ACCESS	read-only
	STATUS	current
	DESCRIPTION
		"The value, in seconds, for this utilization. For both management and slave CPU, we display
		utilization for 1 sec, 5 sec, 60 sec and 300 sec interval."
	::= { snAgentCpuUtilEntry 3 }

snAgentCpuUtilValue OBJECT-TYPE
	SYNTAX	Gauge32
	MAX-ACCESS	read-only
	STATUS	deprecated
	DESCRIPTION
		"The statistical CPU utilization in units of one-hundredth
		 of a percent. This value is deprecated. Users are recommended
		 to use snAgentCpuUtilPercent or snAgentCpuUtil100thPercent
		 instead."
	::= { snAgentCpuUtilEntry 4 }

snAgentCpuUtilPercent OBJECT-TYPE
	SYNTAX	Gauge32
	MAX-ACCESS	read-only
	STATUS	current
	DESCRIPTION
		"The statistical CPU utilization in units of a percent."
	::= { snAgentCpuUtilEntry 5 }

snAgentCpuUtil100thPercent OBJECT-TYPE
	SYNTAX	Gauge32
	MAX-ACCESS	read-only
	STATUS	current
	DESCRIPTION
		"The statistical CPU utilization in units of one-hundredth
		 of a percent."
	::= { snAgentCpuUtilEntry 6 }

-- System Process Utilization Table.

snCpuProcessTable     OBJECT-TYPE
	SYNTAX	SEQUENCE OF SnCpuProcessEntry
	MAX-ACCESS	not-accessible
	STATUS	current
	DESCRIPTION
		"Table to list utilization and runtime for all CPU processes in the device."
	::= { snAgentCpu 2 }

snCpuProcessEntry	OBJECT-TYPE
	SYNTAX	SnCpuProcessEntry
	MAX-ACCESS	not-accessible
	STATUS	current
	DESCRIPTION
		"A row in the CPU process table."
	INDEX	{ 
		snCpuProcessName
	}
	::= { snCpuProcessTable 1 }

SnCpuProcessEntry ::= SEQUENCE {
	snCpuProcessName
		DisplayString,
	snCpuProcess5SecUtil
		Gauge32,
	snCpuProcess1MinUtil
		Gauge32,
	snCpuProcess5MinUtil
		Gauge32,
	snCpuProcess15MinUtil
		Gauge32,
	snCpuProcessRuntime
		Counter32
	}

snCpuProcessName        OBJECT-TYPE
	SYNTAX  DisplayString (SIZE (1..48))
	MAX-ACCESS	read-only
	STATUS	current
	DESCRIPTION
		"The process name."
	::= { snCpuProcessEntry 1 }

snCpuProcess5SecUtil OBJECT-TYPE
	SYNTAX	Gauge32
	MAX-ACCESS	read-only
	STATUS	current
	DESCRIPTION
		"The statistics collection of last 5 second process utilization."
	::= { snCpuProcessEntry 2 }

snCpuProcess1MinUtil OBJECT-TYPE
	SYNTAX	Gauge32
	MAX-ACCESS	read-only
	STATUS	current
	DESCRIPTION
		"The statistics collection of last 1 minute process utilization."
	::= { snCpuProcessEntry 3 }

snCpuProcess5MinUtil OBJECT-TYPE
	SYNTAX	Gauge32
	MAX-ACCESS	read-only
	STATUS	current
	DESCRIPTION
		"The statistics collection of last 5 minute process utilization."
	::= { snCpuProcessEntry 4 }

snCpuProcess15MinUtil OBJECT-TYPE
	SYNTAX	Gauge32
	MAX-ACCESS	read-only
	STATUS	current
	DESCRIPTION
		"The statistics collection of last 15 minute process utilization."
	::= { snCpuProcessEntry 5 }

snCpuProcessRuntime OBJECT-TYPE
	SYNTAX	Counter32
	MAX-ACCESS	read-only
	STATUS	current
	DESCRIPTION
		"Process runtime in milliseconds."
	::= { snCpuProcessEntry 6 }

-- Hardware ICBM (Integrated Central Buffer Manager) Counter Table.

snAgentHwICBMCounterTable     OBJECT-TYPE
	SYNTAX	SEQUENCE OF SnAgentHwICBMCounterEntry
	MAX-ACCESS	not-accessible
	STATUS	current
	DESCRIPTION
		"Table to list the ICBM counter values.
		This table is not supported on 10G module."
	::= { snAgentHw 1 }

snAgentHwICBMCounterEntry	OBJECT-TYPE
	SYNTAX	SnAgentHwICBMCounterEntry
	MAX-ACCESS	not-accessible
	STATUS	current
	DESCRIPTION
		"A row representing ICBM counter values for that slot."
	INDEX	{ 
		snAgentHwICBMCounterSlot,
		snAgentHwICBMCounterDMA
	}
	::= { snAgentHwICBMCounterTable 1 }

SnAgentHwICBMCounterEntry ::= SEQUENCE {
	snAgentHwICBMCounterSlot
		Unsigned32,
	snAgentHwICBMCounterDMA
		Unsigned32,
	snAgentHwICBMCounterFreeDepth
		Gauge32,
	snAgentHwICBMCounterWriteDrop
		Counter32,
	snAgentHwICBMCounterWriteInput
		Counter32,
	snAgentHwICBMCounterWriteOutput
		Counter32,
	snAgentHwICBMCounterReadInput
		Counter32,
	snAgentHwICBMCounterReadOutput
		Counter32
	}

snAgentHwICBMCounterSlot  OBJECT-TYPE
	SYNTAX	Unsigned32
	MAX-ACCESS	read-only
	STATUS	current
	DESCRIPTION
		"Slot number where ICBM resides."
	::= { snAgentHwICBMCounterEntry 1 }

snAgentHwICBMCounterDMA  OBJECT-TYPE
	SYNTAX	Unsigned32
	MAX-ACCESS	read-only
	STATUS	current
	DESCRIPTION
		"DMA Id within a slot where ICBM resides. Valid only for Jetcore modules.
		For non-Jetcore modules, this index is ignored by the agent. In this case, value
		0 will be returned by the agent."
	::= { snAgentHwICBMCounterEntry 2 }

snAgentHwICBMCounterFreeDepth  OBJECT-TYPE
	SYNTAX	Gauge32
	MAX-ACCESS	read-only
	STATUS	current
	DESCRIPTION
		"Current depth of the free queue for this ICBM."
	::= { snAgentHwICBMCounterEntry 3 }

snAgentHwICBMCounterWriteDrop  OBJECT-TYPE
	SYNTAX	Counter32
	MAX-ACCESS	read-only
	STATUS	current
	DESCRIPTION
		"Write sequencer drop count for this ICBM."
	::= { snAgentHwICBMCounterEntry 4 }

snAgentHwICBMCounterWriteInput  OBJECT-TYPE
	SYNTAX	Counter32
	MAX-ACCESS	read-only
	STATUS	current
	DESCRIPTION
		"Write sequencer input counter for this ICBM."
	::= { snAgentHwICBMCounterEntry 5 }

snAgentHwICBMCounterWriteOutput  OBJECT-TYPE
	SYNTAX	Counter32
	MAX-ACCESS	read-only
	STATUS	current
	DESCRIPTION
		"Write sequencer output counter for this ICBM."
	::= { snAgentHwICBMCounterEntry 6 }

snAgentHwICBMCounterReadInput  OBJECT-TYPE
	SYNTAX	Counter32
	MAX-ACCESS	read-only
	STATUS	current
	DESCRIPTION
		"Read sequencer input counter for this ICBM."
	::= { snAgentHwICBMCounterEntry 7 }

snAgentHwICBMCounterReadOutput  OBJECT-TYPE
	SYNTAX	Counter32
	MAX-ACCESS	read-only
	STATUS	current
	DESCRIPTION
		"Read sequencer output counter for this ICBM."
	::= { snAgentHwICBMCounterEntry 8 }

-- IP CAM Statistics Table.

snCAMIpStatTable     OBJECT-TYPE
	SYNTAX	SEQUENCE OF SnCAMIpStatEntry
	MAX-ACCESS	not-accessible
	STATUS	current
	DESCRIPTION
		"Table to list the IP CAM statistics.
		"
	::= { snAgentHw 2 }

snCAMIpStatEntry	OBJECT-TYPE
	SYNTAX	SnCAMIpStatEntry
	MAX-ACCESS	not-accessible
	STATUS	current
	DESCRIPTION
		"A row representing IP CAM statistics for a given interface and level."
	INDEX	{ 
		snCAMIpStatIfIndex,
		snCAMIpStatLevel
	}
	::= { snCAMIpStatTable 1 }

SnCAMIpStatEntry ::= SEQUENCE {
	snCAMIpStatIfIndex         Unsigned32,
	snCAMIpStatLevel           Unsigned32,
	snCAMIpStatFreeEntries   Unsigned32,
	snCAMIpStatTotalEntries  Unsigned32
}

snCAMIpStatIfIndex OBJECT-TYPE
	SYNTAX     Unsigned32
	MAX-ACCESS     read-only
	STATUS     current
	DESCRIPTION
			"ifIndex value of the local interface."
	::= { snCAMIpStatEntry 1 }

snCAMIpStatLevel OBJECT-TYPE
	SYNTAX     Unsigned32
	MAX-ACCESS     read-only
	STATUS     current
	DESCRIPTION
			"Level of CAM entry for that interface."
	::= { snCAMIpStatEntry 2 }

snCAMIpStatFreeEntries OBJECT-TYPE
	SYNTAX     Unsigned32
	MAX-ACCESS     read-only
	STATUS     current
	DESCRIPTION
			"Free entries in the IP CAM for that interface and level."
	::= { snCAMIpStatEntry 3 }

snCAMIpStatTotalEntries OBJECT-TYPE
	SYNTAX     Unsigned32
	MAX-ACCESS     read-only
	STATUS     current
	DESCRIPTION
			"Total entries in the IP CAM for that interface and level."
	::= { snCAMIpStatEntry 4 }

-- CAM Statistics Table.

snCAMStatTable     OBJECT-TYPE
	SYNTAX	SEQUENCE OF SnCAMStatEntry
	MAX-ACCESS	not-accessible
	STATUS	current
	DESCRIPTION
		"Table to list the CAM statistics.
		"
	::= { snAgentHw 3 }

snCAMStatEntry	OBJECT-TYPE
	SYNTAX	SnCAMStatEntry
	MAX-ACCESS	not-accessible
	STATUS	current
	DESCRIPTION
		"A row representing CAM statistics for a given DMA Id number."
	INDEX	{ 
		snCamStatDMAIdNumber
	}
	::= { snCAMStatTable 1 }

SnCAMStatEntry ::= SEQUENCE {
	snCamStatDMAIdNumber              Unsigned32,
	snCamStatDMAMasterNumber         Unsigned32,
	snCamStatFreePool0Entries            Unsigned32,
	snCamStatFreePool1Entries            Unsigned32,
	snCamStatFreePool2Entries            Unsigned32,
	snCamStatFreePool3Entries            Unsigned32,
	snCamStatFreeL2Entries                Unsigned32,
	snCamStatFreeL2LowestSection     Unsigned32,
	snCamStatHostLookupCount           Counter32,
	snCamStatRouteLookupCount         Counter32,
	snCamStatLevel1                         Unsigned32,
	snCamStatLevel2                         Unsigned32,
	snCamStatLevel3                         Unsigned32,
	snCamStatMacFailCount                Counter32,
	snCamStatIPRouteFailCount           Counter32,
	snCamStatIPSessionFailCount         Counter32,
	snCamStatIPMCastFailCount           Counter32,
	snCamStatL2SessionFailCount         Counter32,
	snCamStatAddMACCount               Counter32,
	snCamStatAddVLANCount              Counter32,
	snCamStatAddIPHostCount            Counter32,
	snCamStatAddIPRouteCount           Counter32,
	snCamStatAddIPSessionCount        Counter32,
	snCamStatAddIPMCastCount          Counter32,
	snCamStatAddL2SessionCount        Counter32,
	snCamStatAddIPXCount                Counter32,
	snCamStatDeleteDMACamCount      Counter32
}

snCamStatDMAIdNumber OBJECT-TYPE
	SYNTAX     Unsigned32
	MAX-ACCESS     read-only
	STATUS     current
	DESCRIPTION
			"DMA Id number."
	::= { snCAMStatEntry 1 }

snCamStatDMAMasterNumber OBJECT-TYPE
	SYNTAX     Unsigned32
	MAX-ACCESS     read-only
	STATUS     current
	DESCRIPTION
			"DMA Master for that DMA Id."
	::= { snCAMStatEntry 2 }

snCamStatFreePool0Entries OBJECT-TYPE
	SYNTAX     Unsigned32
	MAX-ACCESS     read-only
	STATUS     current
	DESCRIPTION
			"CAM free pool0 entries."
	::= { snCAMStatEntry 3 }

snCamStatFreePool1Entries OBJECT-TYPE
	SYNTAX     Unsigned32
	MAX-ACCESS     read-only
	STATUS     current
	DESCRIPTION
			"CAM free pool1 entries."
	::= { snCAMStatEntry 4 }

snCamStatFreePool2Entries OBJECT-TYPE
	SYNTAX     Unsigned32
	MAX-ACCESS     read-only
	STATUS     current
	DESCRIPTION
			"CAM free pool2 entries."
	::= { snCAMStatEntry 5 }

snCamStatFreePool3Entries OBJECT-TYPE
	SYNTAX     Unsigned32
	MAX-ACCESS     read-only
	STATUS     current
	DESCRIPTION
			"CAM free pool3 entries."
	::= { snCAMStatEntry 6 }

snCamStatFreeL2Entries OBJECT-TYPE
	SYNTAX     Unsigned32
	MAX-ACCESS     read-only
	STATUS     current
	DESCRIPTION
			"CAM Free L2 entries."
	::= { snCAMStatEntry 7 }

snCamStatFreeL2LowestSection OBJECT-TYPE
	SYNTAX     Unsigned32
	MAX-ACCESS     read-only
	STATUS     current
	DESCRIPTION
			"CAM Free L2 lowest section entries."
	::= { snCAMStatEntry 8 }

snCamStatHostLookupCount OBJECT-TYPE
	SYNTAX     Counter32
	MAX-ACCESS     read-only
	STATUS     current
	DESCRIPTION
			"CAM host lookup count for router."
	::= { snCAMStatEntry 9 }

snCamStatRouteLookupCount OBJECT-TYPE
	SYNTAX     Counter32
	MAX-ACCESS     read-only
	STATUS     current
	DESCRIPTION
			"CAM route lookup count for router."
	::= { snCAMStatEntry 10 }

snCamStatLevel1 OBJECT-TYPE
	SYNTAX     Unsigned32
	MAX-ACCESS     read-only
	STATUS     current
	DESCRIPTION
			"CAM stat level1 entries for router."
	::= { snCAMStatEntry 11 }

snCamStatLevel2 OBJECT-TYPE
	SYNTAX     Unsigned32
	MAX-ACCESS     read-only
	STATUS     current
	DESCRIPTION
			"CAM stat level2 entries for router."
	::= { snCAMStatEntry 12 }

snCamStatLevel3 OBJECT-TYPE
	SYNTAX     Unsigned32
	MAX-ACCESS     read-only
	STATUS     current
	DESCRIPTION
			"CAM stat level3 entries for router."
	::= { snCAMStatEntry 13 }

snCamStatMacFailCount OBJECT-TYPE
	SYNTAX     Counter32
	MAX-ACCESS     read-only
	STATUS     current
	DESCRIPTION
			"CAM MAC fail count."
	::= { snCAMStatEntry 14 }

snCamStatIPRouteFailCount OBJECT-TYPE
	SYNTAX     Counter32
	MAX-ACCESS     read-only
	STATUS     current
	DESCRIPTION
			"CAM IP route fail count."
	::= { snCAMStatEntry 15 }

snCamStatIPSessionFailCount OBJECT-TYPE
	SYNTAX     Counter32
	MAX-ACCESS     read-only
	STATUS     current
	DESCRIPTION
			"CAM IP session fail count."
	::= { snCAMStatEntry 16 }

snCamStatIPMCastFailCount OBJECT-TYPE
	SYNTAX     Counter32
	MAX-ACCESS     read-only
	STATUS     current
	DESCRIPTION
			"CAM IP multicast fail count."
	::= { snCAMStatEntry 17 }

snCamStatL2SessionFailCount OBJECT-TYPE
	SYNTAX     Counter32
	MAX-ACCESS     read-only
	STATUS     current
	DESCRIPTION
			"CAM L2 session fail count."
	::= { snCAMStatEntry 18 }

snCamStatAddMACCount OBJECT-TYPE
	SYNTAX     Counter32
	MAX-ACCESS     read-only
	STATUS     current
	DESCRIPTION
			"CAM add MAC count."
	::= { snCAMStatEntry 19 }

snCamStatAddVLANCount OBJECT-TYPE
	SYNTAX     Counter32
	MAX-ACCESS     read-only
	STATUS     current
	DESCRIPTION
			"CAM add VLAN count."
	::= { snCAMStatEntry 20 }

snCamStatAddIPHostCount OBJECT-TYPE
	SYNTAX     Counter32
	MAX-ACCESS     read-only
	STATUS     current
	DESCRIPTION
			"CAM add IP host count."
	::= { snCAMStatEntry 21 }

snCamStatAddIPRouteCount OBJECT-TYPE
	SYNTAX     Counter32
	MAX-ACCESS     read-only
	STATUS     current
	DESCRIPTION
			"CAM add IP route count."
	::= { snCAMStatEntry 22 }

snCamStatAddIPSessionCount OBJECT-TYPE
	SYNTAX     Counter32
	MAX-ACCESS     read-only
	STATUS     current
	DESCRIPTION
			"CAM add IP session count."
	::= { snCAMStatEntry 23 }

snCamStatAddIPMCastCount OBJECT-TYPE
	SYNTAX     Counter32
	MAX-ACCESS     read-only
	STATUS     current
	DESCRIPTION
			"CAM add IP multicast count."
	::= { snCAMStatEntry 24 }

snCamStatAddL2SessionCount OBJECT-TYPE
	SYNTAX     Counter32
	MAX-ACCESS     read-only
	STATUS     current
	DESCRIPTION
			"CAM add L2 session count."
	::= { snCAMStatEntry 25 }

snCamStatAddIPXCount OBJECT-TYPE
	SYNTAX     Counter32
	MAX-ACCESS     read-only
	STATUS     current
	DESCRIPTION
			"CAM add IPX count."
	::= { snCAMStatEntry 26 }

snCamStatDeleteDMACamCount OBJECT-TYPE
	SYNTAX     Counter32
	MAX-ACCESS     read-only
	STATUS     current
	DESCRIPTION
			"CAM delete DMA CAM count."
	::= { snCAMStatEntry 27 }

-- System DRAM info Group. 
snAgSystemDRAM       OBJECT IDENTIFIER ::= { snAgentHw 4 }

snAgSystemDRAMUtil OBJECT-TYPE
	SYNTAX	Gauge32
	MAX-ACCESS	read-only
	STATUS	current
	DESCRIPTION
		"The system dynamic memory utilization, in unit of percentage."
	::= { snAgSystemDRAM 1 }

snAgSystemDRAMTotal OBJECT-TYPE
	SYNTAX   Integer32
	MAX-ACCESS	read-only
	STATUS	current
	DESCRIPTION
		"The total amount of system dynamic memory, in number of bytes."
	::= { snAgSystemDRAM 2 }

snAgSystemDRAMFree OBJECT-TYPE
	SYNTAX   Integer32
	MAX-ACCESS	read-only
	STATUS	current
	DESCRIPTION
		"The free amount of system dynamic memory, in number of bytes."
	::= { snAgSystemDRAM 3 }

snAgSystemDRAMForBGP OBJECT-TYPE
	SYNTAX   Integer32
	MAX-ACCESS	read-only
	STATUS	current
	DESCRIPTION
		"The free amount of system dynamic memory used by BGP, in number of bytes."
	::= { snAgSystemDRAM 4 }

snAgSystemDRAMForOSPF OBJECT-TYPE
	SYNTAX   Integer32
	MAX-ACCESS	read-only
	STATUS	current
	DESCRIPTION
		"The free amount of system dynamic memory used by OSPF, in number of bytes."
	::= { snAgSystemDRAM 5 }

-- System Debug Group. You would see output of "de" command here.
snAgSystemDebug       OBJECT IDENTIFIER ::= { snAgentHw 5 }

snAgSystemDebugTotalIn OBJECT-TYPE
	SYNTAX Integer32
	MAX-ACCESS     read-only
	STATUS     current
	DESCRIPTION
			"Total incoming packet count. Sum of Buffer Manager and CPU read count."
	::= { snAgSystemDebug 1 }

snAgSystemDebugTotalOut OBJECT-TYPE
	SYNTAX Integer32
	MAX-ACCESS     read-only
	STATUS     current
	DESCRIPTION
			"Total outgoing packet count."
	::= { snAgSystemDebug 2 }

snAgSystemDebugCpuQueueRead OBJECT-TYPE
	SYNTAX Integer32
	MAX-ACCESS     read-only
	STATUS     current
	DESCRIPTION
			"CPU Queue read count."
	::= { snAgSystemDebug 3 }

snAgSystemDebugDRAMBuffer OBJECT-TYPE
	SYNTAX Integer32
	MAX-ACCESS     read-only
	STATUS     current
	DESCRIPTION
			"DRAM buffer count."
	::= { snAgSystemDebug 4 }

snAgSystemDebugBMBuffer OBJECT-TYPE
	SYNTAX Integer32
	MAX-ACCESS     read-only
	STATUS     current
	DESCRIPTION
			"BM buffer count."
	::= { snAgSystemDebug 5 }

snAgSystemDebugBMFreeBuffer OBJECT-TYPE
	SYNTAX Integer32
	MAX-ACCESS     read-only
	STATUS     current
	DESCRIPTION
			"BM free buffer count."
	::= { snAgSystemDebug 6 }

snAgSystemDebugBMFreeBufferMgmt OBJECT-TYPE
	SYNTAX Integer32
	MAX-ACCESS     read-only
	STATUS     current
	DESCRIPTION
			"BM free buffer management count."
	::= { snAgSystemDebug 7 }

snAgSystemDebugIpcGigLock OBJECT-TYPE
	SYNTAX Integer32
	MAX-ACCESS     read-only
	STATUS     current
	DESCRIPTION
			"IPC GIG lock count."
	::= { snAgSystemDebug 8 }

snAgSystemDebugDRAMGetError OBJECT-TYPE
	SYNTAX Integer32
	MAX-ACCESS     read-only
	STATUS     current
	DESCRIPTION
			"DRAM get error count."
	::= { snAgSystemDebug 9 }

snAgSystemDebugDRAMToBMCopyFail OBJECT-TYPE
	SYNTAX Integer32
	MAX-ACCESS     read-only
	STATUS     current
	DESCRIPTION
			"DRAM to Buffer Manager copy fail count."
	::= { snAgSystemDebug 10 }

-- System Temperature Table.

snAgentTempTable     OBJECT-TYPE
	SYNTAX		SEQUENCE OF SnAgentTempEntry
	MAX-ACCESS	not-accessible
	STATUS		current
	DESCRIPTION
		"Table to list temperatures of all the modules in the device. This
		 table is applicable to only those modules with temperature sensors.
		 This table is applicable for standalone setup only."
	::= { snAgentTemp 1 }

snAgentTempEntry	OBJECT-TYPE
	SYNTAX		SnAgentTempEntry
	MAX-ACCESS	not-accessible
	STATUS		current
	DESCRIPTION
		"A row in the module temperature table."
	INDEX	{ snAgentTempSlotNum, snAgentTempSensorId }
	::= { snAgentTempTable 1 }

SnAgentTempEntry ::= SEQUENCE {
	snAgentTempSlotNum
		Integer32,
	snAgentTempSensorId
		Integer32,
	snAgentTempSensorDescr
		DisplayString,
	snAgentTempValue
		INTEGER
	}

snAgentTempSlotNum	OBJECT-TYPE
	SYNTAX		Integer32
	MAX-ACCESS	not-accessible
	STATUS		current
	DESCRIPTION
		"The slot number of module which contains the temperature sensor
		 represented by this row."
	::= { snAgentTempEntry 1 }

snAgentTempSensorId  OBJECT-TYPE
	SYNTAX		Integer32
	MAX-ACCESS	not-accessible
	STATUS		current
	DESCRIPTION
		"The temperature sensor identifier of Slave module whose temperature is
		 represented by this row, for management module: sensor#1 -  Intake Side Temperature
		 sensor# 2 - Exhaust Side Temperature."
	::= { snAgentTempEntry 2 }

snAgentTempSensorDescr  OBJECT-TYPE
	SYNTAX		DisplayString (SIZE (0..128))
	MAX-ACCESS	read-only
	STATUS		current
	DESCRIPTION
		"Describes the temperature sensor in a human readable form. This
		 is the same as snAgentTempSensorId, which is numeric and used to
		 traverse the temperature sensor table. The description provides
		 the meaning and purpose of this senor."
	::= { snAgentTempEntry 3 }

snAgentTempValue OBJECT-TYPE
	SYNTAX		INTEGER (-110..250)
	MAX-ACCESS	read-only
	STATUS		current
	DESCRIPTION
		"Temperature of the the sensor represented by this row. Each unit
		 is 0.5 degrees Celcius."
	::= { snAgentTempEntry 4 }


-- System Temperature Threshold Table.

snAgentTempThresholdTable     OBJECT-TYPE
	SYNTAX	SEQUENCE OF SnAgentTempThresholdEntry
	MAX-ACCESS	not-accessible
	STATUS	current
	DESCRIPTION
		"Table to list temperature threshold levels for 4 speeds of fan settings.
		 Depending on the temperature level, the fans run at diffrent speeds of RPM.
		 There are 4 levels of temperature settings for 4 fan speeds (low, medium,
		 medium-high, high). This table is applicable to only those modules with
		 temperature sensors. For each row, there are 2 temperature threshold values.
		 The high value, if reached causes the fan to run at next high level speed
		 and when it reduces the below the low value, the fan runs at next low spped."
	::= { snAgentTemp 2 }

snAgentTempThresholdEntry	OBJECT-TYPE
	SYNTAX	SnAgentTempThresholdEntry
	MAX-ACCESS	not-accessible
	STATUS	current
	DESCRIPTION
		"A row in the module temperature threshold table."
	INDEX	{ snAgentTempThresholdModule, snAgentTempThresholdLevel }
	::= { snAgentTempThresholdTable 1 }

SnAgentTempThresholdEntry ::= SEQUENCE {
	snAgentTempThresholdModule
		INTEGER,
	snAgentTempThresholdLevel
		INTEGER,
	snAgentTempThresholdHighValue
		INTEGER,
	snAgentTempThresholdLowValue
		INTEGER
	}

snAgentTempThresholdModule	OBJECT-TYPE
	SYNTAX	INTEGER {
					mgmtModule(1),			-- management module
					slaveModule(2),			-- slave/line module
					switchFabricModule(3)	-- switch fabric module
				}
	MAX-ACCESS	not-accessible
	STATUS	current
	DESCRIPTION
		"The module in the system for which threshold levels represented by this
		 row are applicable."
	::= { snAgentTempThresholdEntry 1 }

snAgentTempThresholdLevel OBJECT-TYPE
	SYNTAX	INTEGER {
					low(1),
					medium(2),
					mediumHhigh(3),
					high(4)
				}
	MAX-ACCESS	not-accessible
	STATUS	current
	DESCRIPTION
		"The temperature threshold level of the module for which threshold levels
		 represented by this row are applicable."
	::= { snAgentTempThresholdEntry 2 }

snAgentTempThresholdHighValue OBJECT-TYPE
	SYNTAX	INTEGER (-110..250)
	MAX-ACCESS	read-write
	STATUS	current
	DESCRIPTION
		"The high value for the temperature threshold, above which the fans would
		 need to operate at the next higher speed. If it reaches more than the
		 high threshold value for 'high' level, the module will be shutdown."
	::= { snAgentTempThresholdEntry 3 }

snAgentTempThresholdLowValue OBJECT-TYPE
	SYNTAX	INTEGER (-110..250)
	MAX-ACCESS	read-write
	STATUS	current
	DESCRIPTION
		"The low value for the temperature threshold, below which the fans would
		 need to operate at the next lower speed. This value is not applicable for
		 the 'low' level, as there is no more lower speeds than that."
	::= { snAgentTempThresholdEntry 4 }

-- System Stacking Temperature Table.

snAgentTemp2Table     OBJECT-TYPE
	SYNTAX		SEQUENCE OF SnAgentTemp2Entry
	MAX-ACCESS	not-accessible
	STATUS		current
	DESCRIPTION
		"Table to list temperatures of the modules in the device for each unit. This
		 table is applicable to only those modules with temperature sensors.
		 This table is applicable for stack setup."
	::= { snAgentTemp 3 }

snAgentTemp2Entry	OBJECT-TYPE
	SYNTAX		SnAgentTemp2Entry
	MAX-ACCESS	not-accessible
	STATUS		current
	DESCRIPTION
		"A row in the module temperature table."
	INDEX	{ snAgentTemp2UnitNum, snAgentTemp2SlotNum, snAgentTemp2SensorId }
	::= { snAgentTemp2Table 1 }

SnAgentTemp2Entry ::= SEQUENCE {
	snAgentTemp2UnitNum
		Integer32,
	snAgentTemp2SlotNum
		Integer32,
	snAgentTemp2SensorId
		Integer32,
	snAgentTemp2SensorDescr
		DisplayString,
	snAgentTemp2Value
		INTEGER
	}

snAgentTemp2UnitNum	OBJECT-TYPE
	SYNTAX		Integer32
	MAX-ACCESS	not-accessible
	STATUS		current
	DESCRIPTION
		"The unit number of module which contains the temperature sensor
		 represented by this row."
	::= { snAgentTemp2Entry 1 }

snAgentTemp2SlotNum	OBJECT-TYPE
	SYNTAX		Integer32
	MAX-ACCESS	not-accessible
	STATUS		current
	DESCRIPTION
		"The slot number of module which contains the temperature sensor
		 represented by this row."
	::= { snAgentTemp2Entry 2 }

snAgentTemp2SensorId  OBJECT-TYPE
	SYNTAX		Integer32
	MAX-ACCESS	not-accessible
	STATUS		current
	DESCRIPTION
		"The temperature sensor identifier of Slave module whose temperature is
		 represented by this row, for management module: sensor#1 -  Intake Side Temperature
		 sensor# 2 - Exhaust Side Temperature."
	::= { snAgentTemp2Entry 3 }

snAgentTemp2SensorDescr  OBJECT-TYPE
	SYNTAX		DisplayString (SIZE (0..128))
	MAX-ACCESS	read-only
	STATUS		current
	DESCRIPTION
		"Describes the temperature sensor in a human readable form. This
		 is the same as snAgentTempSensorId, which is numeric and used to
		 traverse the temperature sensor table. The description provides
		 the meaning and purpose of this senor."
	::= { snAgentTemp2Entry 4 }

snAgentTemp2Value OBJECT-TYPE
	SYNTAX		INTEGER (-110..250)
	MAX-ACCESS	read-only
	STATUS		current
	DESCRIPTION
		"Temperature of the sensor represented by this row. Each unit
		 is 0.5 degrees Celsius."
	::= { snAgentTemp2Entry 5 }

snAgentTempThreshold2Table     OBJECT-TYPE
    SYNTAX  SEQUENCE OF SnAgentTempThreshold2Entry
    MAX-ACCESS  not-accessible
    STATUS  current
    DESCRIPTION
        "Table to list temperature threshold levels for 3 speeds of fan settings,
		 threshold and warning temperature . Depending on the temperature level,
		 the fans run at diffrent speeds of RPM. There are 3 levels of temperature 
		 settings for 3 fan speeds (low, high, shutdown). This table is
		 applicable to only those modules with temperature sensors. For each row,
		 there are 3 temperature threshold values. The high value, if reached 
		 causes the fan to run at next high level speed and when it reduces the 
		 below the low value, the fan runs at next low speed."
    ::= { snAgentTemp 4 }

snAgentTempThreshold2Entry   OBJECT-TYPE
    SYNTAX  SnAgentTempThreshold2Entry
    MAX-ACCESS  not-accessible
    STATUS  current
    DESCRIPTION
        "A row in the module temperature threshold table."
    INDEX   { snAgentTempThreshold2UnitNum, snAgentTempThreshold2Rule }
    ::= { snAgentTempThreshold2Table 1 }

SnAgentTempThreshold2Entry ::= SEQUENCE {
    snAgentTempThreshold2UnitNum
        INTEGER,
	snAgentTempThreshold2Rule
		INTEGER,
	snAgentTempThreshold2LowValue
		INTEGER,
    snAgentTempThreshold2HighValue
        INTEGER,
    snAgentTempThreshold2ShutdownValue
        INTEGER
    }

snAgentTempThreshold2UnitNum OBJECT-TYPE
    SYNTAX      INTEGER
    MAX-ACCESS  not-accessible
    STATUS      current
    DESCRIPTION
        "The unit number in the system for which threshold levels represented by this
         row are applicable."
    ::= { snAgentTempThreshold2Entry 1 }

snAgentTempThreshold2Rule OBJECT-TYPE
    SYNTAX      INTEGER
    MAX-ACCESS  not-accessible
    STATUS      current
    DESCRIPTION
        "The Rule number in the system for which threshold levels represented by this
         row are applicable."
    ::= { snAgentTempThreshold2Entry 2 }

snAgentTempThreshold2LowValue OBJECT-TYPE
    SYNTAX  INTEGER 
    MAX-ACCESS  read-only
    STATUS  current
    DESCRIPTION
		"The low value for the temperature threshold, below which the fans would
		 need to operate at the next lower speed. Each unit is degrees Celcius.
		 This value is not applicable for the 'low' level, as there is no more
		 lower speeds than that."
    ::= { snAgentTempThreshold2Entry 3 }

snAgentTempThreshold2HighValue OBJECT-TYPE
    SYNTAX  INTEGER
    MAX-ACCESS  read-only
    STATUS  current
    DESCRIPTION
        "The high value for the temperature threshold, above which the fans would
         need to operate at the next higher speed. If it reaches more than the
         high threshold value for 'high' level, the module will be shutdown.
		 Each unit is degrees Celcius."
    ::= { snAgentTempThreshold2Entry 4 }

snAgentTempThreshold2ShutdownValue  OBJECT-TYPE
    SYNTAX  INTEGER
    MAX-ACCESS  read-only
    STATUS  current
    DESCRIPTION
	    "Actual temperature higher than this threshold value will shutdown
		 a partial of the switch hardware to cool down the system. Each unit
  		 is degrees Celcius. Only management module built with temperature
		 sensor hardware is applicable. For those non-applicable management
		 module, it returns no-such-name."
    ::= { snAgentTempThreshold2Entry 5 }

-- Deprecated table fdryLicenseTable (The XML license is not supported) 
fdryLicenseTable OBJECT-TYPE
	SYNTAX  SEQUENCE OF FdryLicenseEntry
	MAX-ACCESS  not-accessible
	STATUS  deprecated
	DESCRIPTION
        "A list of licenses maintained by license sub-system."
	::= { snAgentLicense 1 }

fdryLicenseEntry OBJECT-TYPE
    SYNTAX      FdryLicenseEntry
    MAX-ACCESS  not-accessible
    STATUS      deprecated
    DESCRIPTION
        "An entry in a license table."
    INDEX	{fdryLicensePackageName, fdryLicenseLid, fdryLicenseHash}
    ::= { fdryLicenseTable 1 }

FdryLicenseEntry ::= SEQUENCE {
	fdryLicensePackageName
		DisplayString,
	fdryLicenseLid
		DisplayString,
	fdryLicenseHash
		DisplayString,
	fdryLicenseType
		INTEGER,
	fdryLicensePrecedence
		Unsigned32,
	fdryLicenseTrialDays
		Unsigned32,
	fdryLicenseTrialTimeElapsed
		Unsigned32,
	fdryLicenseTrialTimeLeft
		Unsigned32,
	fdryLicenseTrialState
		INTEGER,
	fdryLicenseVendorInfo
		DisplayString,
	fdryLicenseSlot
		Integer32,
	fdryLicenseMode	
		INTEGER,
	fdryLicenseSerialNumber	
		DisplayString,
	fdryLicenseCapacity
		Integer32
    }

fdryLicensePackageName OBJECT-TYPE
	SYNTAX		DisplayString (SIZE(1..24))
	MAX-ACCESS	not-accessible
	STATUS		deprecated
	DESCRIPTION
		"Name of the package, whose license information, this entry displays."
	::= { fdryLicenseEntry 1 }
	
fdryLicenseLid OBJECT-TYPE
	SYNTAX		DisplayString (SIZE(1..11))
	MAX-ACCESS	not-accessible
	STATUS		deprecated
	DESCRIPTION
		"License Id (LID) of the license from the package. For the node locked license, 
		this LID is same as LID of the device. For the non-node locked license, this LID 
		is set as 2.0. This entry displays license information."
	::= { fdryLicenseEntry 2 }
	
fdryLicenseHash OBJECT-TYPE
	SYNTAX		DisplayString (SIZE(1..17))
	MAX-ACCESS	not-accessible
	STATUS		deprecated
	DESCRIPTION
		"A unique hash for identifying a license entry in the system. This helps
		 traverse through the entries with same package name and LID."
	::= { fdryLicenseEntry 3 }
	
fdryLicenseType OBJECT-TYPE
	SYNTAX		INTEGER {
					normal(1),
					trial(2)
				}
	MAX-ACCESS	read-only
	STATUS		deprecated
	DESCRIPTION
		"The type of the license, which can be either normal or trial."
	::= { fdryLicenseEntry 4 }

fdryLicensePrecedence OBJECT-TYPE
	SYNTAX		Unsigned32 (0..65535)
	MAX-ACCESS	read-only
	STATUS		deprecated
	DESCRIPTION
		"Defines the priority of a particular trial license among those having
		 the same package and LID. This is primarily used for determining which
		 license to use, when there are many trial and normal licenses with same
		 package name and LID."
	::= { fdryLicenseEntry 5 }
	
fdryLicenseTrialDays OBJECT-TYPE
	SYNTAX		Unsigned32 (0..65535)
	MAX-ACCESS	read-only
	STATUS		deprecated
	DESCRIPTION
		"The number of trial days for the license, if it's a trial license.
		 Otherwise, the value has no meaning for normal licenses and read
		 as 0 on Get operation."
	::= { fdryLicenseEntry 6 }

fdryLicenseTrialTimeElapsed OBJECT-TYPE
	SYNTAX		Unsigned32 (0..65535)
	MAX-ACCESS	read-only
	STATUS		deprecated
	DESCRIPTION
		"The cumulative number of hours used for this trial license. This
		 counts all the usages of the trial license. For a normal license,
		 this is 0."
	::= { fdryLicenseEntry 7 }
	
fdryLicenseTrialTimeLeft OBJECT-TYPE
	SYNTAX		Unsigned32 (0..65535)
	MAX-ACCESS	read-only
	STATUS		deprecated
	DESCRIPTION
		"The number of hours left for the trial license. This is derived
		 from the total number of hours and the cumulative number of hours
		 used. For a normal license, this is 0."
	::= { fdryLicenseEntry 8 }

fdryLicenseTrialState OBJECT-TYPE
	SYNTAX		INTEGER {
					invalid(1),
					unused(2),
					active(3),
					expired(4),
					duplicated (5)
				}
	MAX-ACCESS	read-only
	STATUS		deprecated
	DESCRIPTION
		"This indicates the state of the trial license. Invalid means the 
		 license is not valid for this box, unused means the license is
		 never used, avtive means it has been used at least once and expired
		 means it has expired and can't be used any more. Duplicated means 
		 the license has same package name with other license and but both 
		 serial numbers are different in the same device, this is only for 
		 the non-node locked license"
	::= { fdryLicenseEntry 9 }

fdryLicenseVendorInfo OBJECT-TYPE
	SYNTAX		DisplayString
	MAX-ACCESS	read-only
	STATUS		deprecated
	DESCRIPTION
		"This is the Ruckus Wireless specific package data which is an octet string.
		 This contains encoded information of license specific information
		 such as package bit mask, number of ports, etc."
	::= { fdryLicenseEntry 10 }

fdryLicenseSlot OBJECT-TYPE
	SYNTAX		Integer32
	MAX-ACCESS	read-only
	STATUS		deprecated
	DESCRIPTION
		"This indicates the slot number of the module, the license belongs to.
		 There is a one to one mapping between LID and slot number, as each
		 module has unique LID and can be present only in one slot."
	::= { fdryLicenseEntry 11 }
	
fdryLicenseMode OBJECT-TYPE
	SYNTAX		INTEGER {
					nodeLocked(1),
					nonNodeLocked(2)
				}
	MAX-ACCESS	read-only
	STATUS		deprecated
	DESCRIPTION
		"The mode of the license, which can be either node locked or non-node locked mode."
	::= { fdryLicenseEntry 12 }

fdryLicenseSerialNumber OBJECT-TYPE
	SYNTAX		DisplayString
	MAX-ACCESS	read-only
	STATUS		deprecated
	DESCRIPTION
		"This is the serial number of the license. This is only for the non-node locked license"
	::= { fdryLicenseEntry 13 }

fdryLicenseCapacity OBJECT-TYPE
	SYNTAX		Integer32
	MAX-ACCESS	read-only
	STATUS		deprecated
	DESCRIPTION
		"The capacity of the license. For POD license, this is the number of ports.
		For premium or advance license, it is 1"
	::= { fdryLicenseEntry 14 }


-- the port table contains the port which requirs the port license

brcdPortLicenseTable OBJECT-TYPE
	SYNTAX  SEQUENCE OF BrcdPortLicenseEntry
	MAX-ACCESS  not-accessible
	STATUS  current
	DESCRIPTION
        "A list of ports which require the port license."
	::= { snAgentLicense 3 }

brcdPortLicenseEntry OBJECT-TYPE
    SYNTAX      BrcdPortLicenseEntry
    MAX-ACCESS  not-accessible
    STATUS      current
    DESCRIPTION
        "An entry in a licensed port table."
    INDEX	{ brcdPortLicenseIndex }
    ::= { brcdPortLicenseTable 1 }

BrcdPortLicenseEntry ::= SEQUENCE {
	brcdPortLicenseIndex
		InterfaceIndex,
	brcdPortLicenseStatus
		INTEGER
    }

brcdPortLicenseIndex OBJECT-TYPE
	SYNTAX	InterfaceIndex
	MAX-ACCESS  not-accessible
	STATUS	current
	DESCRIPTION
		"The port/interface index (ifindex)."
	::= { brcdPortLicenseEntry 1 }

brcdPortLicenseStatus OBJECT-TYPE
	SYNTAX  INTEGER {
				validLic(1),       
				noLic(2)  
			}
	MAX-ACCESS  read-only
	STATUS  current
	DESCRIPTION
		"The current license state of the port.
		 validLic(1)  ............ the port requires port license, and has valid license      
		 noLic(2)      ........... the port requires port license, and doesn't have valid license "
	::= { brcdPortLicenseEntry 2 }


-- SAU license unit table

snSAULicenseUnitTable OBJECT-TYPE
	SYNTAX  SEQUENCE OF SnSAULicenseUnitEntry
	MAX-ACCESS  not-accessible
	STATUS  current
	DESCRIPTION
        "A list of SAU licenses maintained by each unit."
	::= { snAgentLicense 4 }

snSAULicenseUnitEntry OBJECT-TYPE
    SYNTAX      SnSAULicenseUnitEntry
    MAX-ACCESS  not-accessible
    STATUS      current
    DESCRIPTION
        "An entry in SAU license table."
    INDEX	{snSAULicenseUnitIndex }
    ::= { snSAULicenseUnitTable 1 }

SnSAULicenseUnitEntry ::= SEQUENCE {
	snSAULicenseUnitIndex		      Integer32,	
	snSAULicensePackageName	          DisplayString,
	snSAUIsPremLicensePresent	      INTEGER,
	snSAUIsPoDLicensePresent	      INTEGER,
	snSAUPoDLicensedSpeed		      INTEGER,
	snSAUPoDLicensedPorts		      Integer32,
	snSAUIsMACSecLicensePresent	      INTEGER,
	snSAUPremSerialNumber	          DisplayString,
    snSAUPoDSerialNumber	          DisplayString,
    snSAUMACsecSerialNumber           DisplayString,
	snSAUICX7150SerialNumber          DisplayString,
	snSAUICX8200SerialNumber          DisplayString 
}
    
snSAULicenseUnitIndex OBJECT-TYPE
	SYNTAX Integer32
	MAX-ACCESS not-accessible
	STATUS     current
	DESCRIPTION
		"The stacking unit Id"
	::= { snSAULicenseUnitEntry 1 }

snSAULicensePackageName OBJECT-TYPE
	SYNTAX		DisplayString 
	MAX-ACCESS	read-only
	STATUS		current
	DESCRIPTION
		"Name of the license package."
	::= { snSAULicenseUnitEntry 2 }

 snSAUIsPremLicensePresent OBJECT-TYPE
	SYNTAX INTEGER {
			none (0),
			yes (1),
			no (2)
	}
	MAX-ACCESS read-only
	STATUS     current
	DESCRIPTION
		"The present state of L3 premium license.
		 none means the license is not applicable to this device"
	::= { snSAULicenseUnitEntry 3 }

snSAUIsPoDLicensePresent OBJECT-TYPE
	SYNTAX INTEGER {
			none (0),
			yes (1),
			no (2)
	}
	MAX-ACCESS read-only
	STATUS     current
	DESCRIPTION
		"The present state of PoD license.
		none means the license is not applicable to this device"
	::= { snSAULicenseUnitEntry 4 }

snSAUPoDLicensedSpeed OBJECT-TYPE
	SYNTAX INTEGER {
			none (0),
			speed10G (1),
			speed25G (2)
	}
	MAX-ACCESS read-only
	STATUS     current
	DESCRIPTION
		"The port speed of PoD license.
		 none means the license is not applicable to this device"
	::= { snSAULicenseUnitEntry 5 }

snSAUPoDLicensedPorts OBJECT-TYPE
	SYNTAX Integer32 
	MAX-ACCESS read-only
	STATUS     current
	DESCRIPTION
		"The number of licensed ports. The capacity of PoD License.
		 Zero means no PoD license or the license is not applicable to this device"
	::= { snSAULicenseUnitEntry 6 }

snSAUIsMACSecLicensePresent OBJECT-TYPE
	SYNTAX INTEGER {
			none (0),
			yes (1),
			no (2)
	}
	MAX-ACCESS read-only
	STATUS     current
	DESCRIPTION
		"The present state of MACSec license.
		none means the license is not applicable to this device"
	::= { snSAULicenseUnitEntry 7 }

snSAUPremSerialNumber OBJECT-TYPE
	SYNTAX		DisplayString
	MAX-ACCESS	read-only
	STATUS		current
	DESCRIPTION
		"This is the serial number of CoE L3 premium license."
	::= { snSAULicenseUnitEntry 8 }

snSAUPoDSerialNumber OBJECT-TYPE
	SYNTAX		DisplayString
	MAX-ACCESS	read-only
	STATUS		current
	DESCRIPTION
		"This is the serial number of CoE PoD license."
	::= { snSAULicenseUnitEntry 9 }

snSAUMACsecSerialNumber OBJECT-TYPE
	SYNTAX		DisplayString
	MAX-ACCESS	read-only
	STATUS		current
	DESCRIPTION
		"This is the serial number of CoE MACsec license."
	::= { snSAULicenseUnitEntry 10 }

snSAUICX7150SerialNumber OBJECT-TYPE
	SYNTAX		DisplayString
	MAX-ACCESS	read-only
	STATUS		deprecated
	DESCRIPTION
		"This is the serial number of CoE ICX7150 license. 
		FOR ICX7150 platform, only one SAU license option can be installed. e.g. 4x10gr,
		It is combination of l3 premium and PoD license, thus there is only a license serial number at one time"
	::= { snSAULicenseUnitEntry 11 }

snSAUICX8200SerialNumber OBJECT-TYPE
	SYNTAX		DisplayString
	MAX-ACCESS	read-only
	STATUS		current
	DESCRIPTION
		"This is the serial number of CoE ICX8200 license. 
		FOR ICX8200 platform, only one SAU license option can be installed. e.g. 4x25gr,
		It is combination of l3 premium and PoD license, thus there is only a license serial number at one time"
	::= { snSAULicenseUnitEntry 12 }

END
