RUCKUS-VXLAN-MIB DEFINITIONS ::= BEGIN

IMPORTS
    MODULE-IDENTITY, OBJECT-TYPE, Unsigned32, Integer32, IpAddress, Counter64
       FROM SNMPv2-SMI
    TruthValue
        FROM SNMPv2-TC
 snSwitch
 FROM FOUNDRY-SN-SWITCH-GROUP-MIB
    DisplayString
       FROM FOUNDRY-SN-AGENT-MIB;

ruckusVxlanMIB MODULE-IDENTITY
    LAST-UPDATED "202110290000Z" -- Oct 29, 2021
    ORGANIZATION "Ruckus Wireless, Inc."
    CONTACT-INFO
        "Technical Support Center
              350 West Java Drive,
              Sunnyvale, CA 94089, USA
              Support URL: https://support.ruckuswireless.com
              Phone: +1-855-782-5871
              ROW TF Numbers: https://support.ruckuswireless.com/contact-us"
    DESCRIPTION
        "Management Information for configuration of VxLAN feature.
        VxLAN is a Layer 3 feature which helps to extend a Local Area Network
        over devices which are separated over different subnets.

        Copyright 1996-2021 Ruckus Wireless, Inc.
        All rights reserved.
        This Ruckus Wireless, Inc SNMP Management Information Base Specification
        embodies Ruckus Wireless, Inc' confidential and proprietary
        intellectual property. Ruckus Wireless, Inc retains all
        title and ownership in the Specification, including any revisions.

        This Specification is supplied AS IS, and Ruckus Wireless, Inc makes
        no warranty, either express or implied, as to the use,
        operation, condition, or performance of the specification, and any unintended
        consequence it may on the user environment."

  REVISION     "202110290000Z" -- Oct 29, 2021
  DESCRIPTION
 "initial version to support Vxlan feature in FI9010"

    ::= { snSwitch 49}

ruckusVxlanObjects        OBJECT IDENTIFIER  ::=  { ruckusVxlanMIB 1 }

ruckusVxlanOverlayGateway  OBJECT IDENTIFIER ::= { ruckusVxlanObjects 1 }

-- Table for Overlay Gateway Config and Show Attributes

ruckusVxlanOverlayGatewayTable OBJECT-TYPE
    SYNTAX  SEQUENCE OF RuckusVxlanOverlayGatewayEntry
    MAX-ACCESS  not-accessible
    STATUS  current
    DESCRIPTION
       "This table provides the general configuration details
        related to an overlay gateway. When a new overlay Gateway
        is created a new entry will be added in this table"
    ::= { ruckusVxlanOverlayGateway 1 }

ruckusVxlanOverlayGatewayEntry OBJECT-TYPE
    SYNTAX  RuckusVxlanOverlayGatewayEntry
    MAX-ACCESS  not-accessible
    STATUS  current
    DESCRIPTION
         "An row instance of the Overlay Gateway table."
    INDEX   { ruckusVxlanOverlayGatewayName }
    ::= { ruckusVxlanOverlayGatewayTable 1 }

RuckusVxlanOverlayGatewayEntry ::= SEQUENCE {
       ruckusVxlanOverlayGatewayName
           DisplayString,
       ruckusVxlanOverlayGatewayType
           INTEGER,
       ruckusVxlanOverlayGatewayLoopbackId
           Integer32,
       ruckusVxlanOverlayGatewayMappedVlans
           Integer32,
       ruckusVxlanOverlayGatewayExtendedSites
           Integer32,
       ruckusVxlanOverlayGatewayRowStatus
           INTEGER
   }

ruckusVxlanOverlayGatewayName OBJECT-TYPE
    SYNTAX  DisplayString (SIZE(0..64))
    MAX-ACCESS  read-only
    STATUS  current
    DESCRIPTION
       "VxLAN Overlay Gateway Name"
    ::= { ruckusVxlanOverlayGatewayEntry 1 }

ruckusVxlanOverlayGatewayType OBJECT-TYPE
    SYNTAX  INTEGER {
           none(0),
    l2Extension(1)
    }
    MAX-ACCESS  read-write
    STATUS  current
    DESCRIPTION
       "VxLAN Overlay Gateway Name Type
        Only Type Supported is:
        1 - Layer2-Extension           "
    ::= { ruckusVxlanOverlayGatewayEntry 2 }

ruckusVxlanOverlayGatewayLoopbackId OBJECT-TYPE
    SYNTAX  Integer32
    MAX-ACCESS  read-write
    STATUS  current
    DESCRIPTION
       "VxLAN Overlay Gateway Loopback ID"
    ::= { ruckusVxlanOverlayGatewayEntry 3 }

ruckusVxlanOverlayGatewayMappedVlans OBJECT-TYPE
    SYNTAX Integer32
    MAX-ACCESS  read-only
    STATUS  current
    DESCRIPTION
       "VxLAN Overlay Gateway Number of Mapped Vlans"
    ::= { ruckusVxlanOverlayGatewayEntry 4 }

ruckusVxlanOverlayGatewayExtendedSites OBJECT-TYPE
    SYNTAX Integer32
    MAX-ACCESS  read-only
    STATUS  current
    DESCRIPTION
       "VxLAN Overlay Gateway Number of Extended Sites"
    ::= { ruckusVxlanOverlayGatewayEntry 5 }

ruckusVxlanOverlayGatewayRowStatus OBJECT-TYPE
    SYNTAX   INTEGER {
        invalid(1),
        valid(2),
        delete(3),
        create(4)
        }
     MAX-ACCESS   read-write
     STATUS   current
     DESCRIPTION
     "This object is used to create and
      delete row in the table and control
      if they are used. The values
      that can be written are:
      delete(3)...deletes the row
      create(4)...creates a new row

      If the row exists, then a SET with
      value of create(4) returns error
      'badValue'. Deleted rows go away
      immediately. The following values
      can be returned on reads:
      noSuch(0)...no such row
      invalid(1)...Setting it to 'invalid' has the effect of
                  rendering it inoperative..
      valid(2)....the row exists and is valid"
    ::= { ruckusVxlanOverlayGatewayEntry 6 }

-- Table for defining VLAN - VNI Mapping Attributes in an Overlay-Gateway

ruckusVxlanOverlayGatewayVlanMapTable OBJECT-TYPE
    SYNTAX  SEQUENCE OF RuckusVxlanOverlayGatewayVlanMapEntry
    MAX-ACCESS  not-accessible
    STATUS  current
    DESCRIPTION
       "This table provides the information related to the
       vlan - vni mapping which is included in an overlay gateway
       If a new vlan- vni mapping is introduced in an overlay gateway
       then a new entry will be added to the table."
    ::= { ruckusVxlanOverlayGateway 2 }

ruckusVxlanOverlayGatewayVlanMapEntry OBJECT-TYPE
    SYNTAX  RuckusVxlanOverlayGatewayVlanMapEntry
    MAX-ACCESS  not-accessible
    STATUS  current
    DESCRIPTION
           "An row instance of the Overlay Gateway Vlan Map table."
    INDEX   { ruckusVxlanOverlayGatewayName,
              ruckusVxlanOverlayGatewayVlanMapVlanId }
    ::= { ruckusVxlanOverlayGatewayVlanMapTable 1 }

RuckusVxlanOverlayGatewayVlanMapEntry ::= SEQUENCE {
        ruckusVxlanOverlayGatewayVlanMapVlanId
            Integer32,
        ruckusVxlanOverlayGatewayVlanMapVniId
            Integer32,
        ruckusVxlanOverlayGatewayVlanMapVfiId
            Integer32,
        ruckusVxlanOverlayGatewayVlanMapCrossConnect
            INTEGER,
        ruckusVxlanOverlayGatewayVlanMapStatistics
            INTEGER,
        ruckusVxlanOverlayGatewayVlanMapAccessPortCount
            Integer32,
        ruckusVxlanOverlayGatewayVlanMapExtendedSite
            Integer32,
        ruckusVxlanOverlayGatewayVlanMapRowStatus
            INTEGER,
        ruckusVxlanOverlayGatewayVlanMapInUnicastPackets
            Counter64,
        ruckusVxlanOverlayGatewayVlanMapInUnicastBytes
            Counter64,
        ruckusVxlanOverlayGatewayVlanMapInMulticastPackets
            Counter64,
        ruckusVxlanOverlayGatewayVlanMapInMutlticastBytes
            Counter64,
        ruckusVxlanOverlayGatewayVlanMapInBroadcastPackets
            Counter64,
        ruckusVxlanOverlayGatewayVlanMapInBroadcastBytes
            Counter64,
        ruckusVxlanOverlayGatewayVlanMapOutPackets
            Counter64,
        ruckusVxlanOverlayGatewayVlanMapOutBytes
            Counter64
    }

ruckusVxlanOverlayGatewayVlanMapVlanId OBJECT-TYPE
    SYNTAX Integer32
    MAX-ACCESS  read-only
    STATUS  current
    DESCRIPTION
        "Vlan Index of the VLAN - VNI Mapping"
    ::= { ruckusVxlanOverlayGatewayVlanMapEntry 1 }

ruckusVxlanOverlayGatewayVlanMapVniId OBJECT-TYPE
    SYNTAX Integer32
    MAX-ACCESS  read-write
    STATUS  current
    DESCRIPTION
        "VNI Index of the VLAN - VNI Mapping"
    ::= { ruckusVxlanOverlayGatewayVlanMapEntry 2 }

ruckusVxlanOverlayGatewayVlanMapVfiId OBJECT-TYPE
    SYNTAX Integer32
    MAX-ACCESS  read-only
    STATUS  current
    DESCRIPTION
        "VFI Index of the VLAN - VNI Mapping"
    ::= { ruckusVxlanOverlayGatewayVlanMapEntry 3 }

ruckusVxlanOverlayGatewayVlanMapCrossConnect OBJECT-TYPE
    SYNTAX INTEGER {
     disabled(0),
      enabled(1)
     }
    MAX-ACCESS  read-only
    STATUS  current
    DESCRIPTION
        "The Cross-Connect Setting for a VLAN-VNI Mapping
           0 -  If Cross-Connect Setting is Disabled
           1 -  If Cross-Connect Setting is Enabled    "
    ::= { ruckusVxlanOverlayGatewayVlanMapEntry 4 }

ruckusVxlanOverlayGatewayVlanMapStatistics OBJECT-TYPE
    SYNTAX INTEGER {
     disabled(0),
      enabled(1)
     }
    MAX-ACCESS  read-only
    STATUS  current
    DESCRIPTION
        "The VXLAN Statistics for a VLAN-VNI Mapping
           0 -  If Setting is Disabled
           1 -  If Setting is Enabled    "
    ::= { ruckusVxlanOverlayGatewayVlanMapEntry 5 }

ruckusVxlanOverlayGatewayVlanMapAccessPortCount OBJECT-TYPE
    SYNTAX Integer32
    MAX-ACCESS  read-only
    STATUS  current
    DESCRIPTION
        "Number of Access Ports Added to the VLAN"
    ::= { ruckusVxlanOverlayGatewayVlanMapEntry 6 }

ruckusVxlanOverlayGatewayVlanMapExtendedSite OBJECT-TYPE
    SYNTAX Integer32
    MAX-ACCESS  read-only
    STATUS  current
    DESCRIPTION
        "Number of Sites the VLAN - VNI Mapping is extended to"
    ::= { ruckusVxlanOverlayGatewayVlanMapEntry 7 }

ruckusVxlanOverlayGatewayVlanMapRowStatus OBJECT-TYPE
    SYNTAX   INTEGER {
         invalid(1),
         valid(2),
         delete(3),
         create(4)
     }
     MAX-ACCESS   read-write
     STATUS   current
     DESCRIPTION
     "This object is used to create and
      delete row in the table and control
      if they are used. The values
      that can be written are:
      delete(3)...deletes the row
      create(4)...creates a new row

      If the row exists, then a SET with
      value of create(4) returns error
      'badValue'. Deleted rows go away
      immediately. The following values
      can be returned on reads:
      noSuch(0)...no such row
      invalid(1)...Setting it to 'invalid' has the effect of
                   rendering it inoperative..
      valid(2)....the row exists and is valid"
    ::= { ruckusVxlanOverlayGatewayVlanMapEntry 8 }

ruckusVxlanOverlayGatewayVlanMapInUnicastPackets OBJECT-TYPE
    SYNTAX Counter64
    MAX-ACCESS  read-only
    STATUS  current
    DESCRIPTION
        "Number of incoming unicast packets on the VNI"
    ::= { ruckusVxlanOverlayGatewayVlanMapEntry 9 }

ruckusVxlanOverlayGatewayVlanMapInUnicastBytes OBJECT-TYPE
    SYNTAX Counter64
    MAX-ACCESS  read-only
    STATUS  current
    DESCRIPTION
        "Number of incoming unicast bytes on the VNI"
    ::= { ruckusVxlanOverlayGatewayVlanMapEntry 10 }

ruckusVxlanOverlayGatewayVlanMapInMulticastPackets OBJECT-TYPE
    SYNTAX Counter64
    MAX-ACCESS  read-only
    STATUS  current
    DESCRIPTION
        "Number of incoming multicast packets on the VNI"
    ::= { ruckusVxlanOverlayGatewayVlanMapEntry 11 }

ruckusVxlanOverlayGatewayVlanMapInMutlticastBytes OBJECT-TYPE
    SYNTAX Counter64
    MAX-ACCESS  read-only
    STATUS  current
    DESCRIPTION
        "Number of incoming multicast bytes on the VNI"
    ::= { ruckusVxlanOverlayGatewayVlanMapEntry 12 }

ruckusVxlanOverlayGatewayVlanMapInBroadcastPackets OBJECT-TYPE
    SYNTAX Counter64
    MAX-ACCESS  read-only
    STATUS  current
    DESCRIPTION
        "Number of incoming broadcast packets on the VNI"
    ::= { ruckusVxlanOverlayGatewayVlanMapEntry 13 }

ruckusVxlanOverlayGatewayVlanMapInBroadcastBytes OBJECT-TYPE
    SYNTAX Counter64
    MAX-ACCESS  read-only
    STATUS  current
    DESCRIPTION
        "Number of incoming broadcast bytes on the VNI"
    ::= { ruckusVxlanOverlayGatewayVlanMapEntry 14 }

ruckusVxlanOverlayGatewayVlanMapOutPackets OBJECT-TYPE
    SYNTAX Counter64
    MAX-ACCESS  read-only
    STATUS  current
    DESCRIPTION
        "Number of outgoing packets on the VNI"
    ::= { ruckusVxlanOverlayGatewayVlanMapEntry 15 }

ruckusVxlanOverlayGatewayVlanMapOutBytes OBJECT-TYPE
    SYNTAX Counter64
    MAX-ACCESS  read-only
    STATUS  current
    DESCRIPTION
        "Number of outgoing bytes on the VNI"
    ::= { ruckusVxlanOverlayGatewayVlanMapEntry 16 }

-- Table for handling config and show details for a site extended in an overlay gateway

ruckusVxlanOverlayGatewaySiteTable OBJECT-TYPE
    SYNTAX  SEQUENCE OF RuckusVxlanOverlayGatewaySiteEntry
    MAX-ACCESS  not-accessible
    STATUS  current
    DESCRIPTION
         "This table provides the information related to the
         external site which is extended by an overlay-gateway
         If a new site is extended by an overlay gateway
         then a new entry will be added to the table."
    ::= { ruckusVxlanOverlayGateway 3 }

ruckusVxlanOverlayGatewaySiteEntry OBJECT-TYPE
         SYNTAX  RuckusVxlanOverlayGatewaySiteEntry
         MAX-ACCESS  not-accessible
         STATUS  current
         DESCRIPTION
             "An row instance of the Overlay Gateway Site table."
         INDEX   { ruckusVxlanOverlayGatewayName,
                   ruckusVxlanOverlayGatewaySiteName }
         ::= { ruckusVxlanOverlayGatewaySiteTable 1 }

RuckusVxlanOverlayGatewaySiteEntry ::= SEQUENCE {
         ruckusVxlanOverlayGatewaySiteName
             DisplayString,
         ruckusVxlanOverlayGatewaySiteIpAddress
             IpAddress,
         ruckusVxlanOverlayGatewaySiteStatus
             TruthValue,
         ruckusVxlanOverlayGatewaySiteRowStatus
             INTEGER,
         ruckusVxlanOverlayGatewaySiteInUnicastPackets
             Counter64,
         ruckusVxlanOverlayGatewaySiteInUnicastBytes
             Counter64,
         ruckusVxlanOverlayGatewaySiteInMulticastPackets
             Counter64,
         ruckusVxlanOverlayGatewaySiteInMutlticastBytes
             Counter64,
         ruckusVxlanOverlayGatewaySiteInBroadcastPackets
             Counter64,
         ruckusVxlanOverlayGatewaySiteInBroadcastBytes
             Counter64,
         ruckusVxlanOverlayGatewaySiteOutPackets
             Counter64,
         ruckusVxlanOverlayGatewaySiteOutBytes
             Counter64,
         ruckusVxlanOverlayGatewaySiteMonitoring
             TruthValue,
         ruckusVxlanOverlayGatewaySiteKeepAlive
             Integer32,
         ruckusVxlanOverlayGatewaySiteRetry
             Integer32
     }

ruckusVxlanOverlayGatewaySiteName OBJECT-TYPE
    SYNTAX  DisplayString (SIZE(0..64))
    MAX-ACCESS  read-only
    STATUS  current
    DESCRIPTION
         "VxLAN Extended Site Name"
    ::= { ruckusVxlanOverlayGatewaySiteEntry 1 }

ruckusVxlanOverlayGatewaySiteIpAddress OBJECT-TYPE
    SYNTAX  IpAddress
    MAX-ACCESS  read-write
    STATUS  current
    DESCRIPTION
         "VxLAN Extended Site's IP Address"
    ::= { ruckusVxlanOverlayGatewaySiteEntry 2 }

ruckusVxlanOverlayGatewaySiteStatus OBJECT-TYPE
    SYNTAX TruthValue
    MAX-ACCESS  read-only
    STATUS  current
    DESCRIPTION
         "VxLAN Extended Site's Status
          True -  If Site is up
          False - If Site is Down      "
    ::= { ruckusVxlanOverlayGatewaySiteEntry 3 }

ruckusVxlanOverlayGatewaySiteRowStatus OBJECT-TYPE
    SYNTAX   INTEGER {
          invalid(1),
          valid(2),
          delete(3),
          create(4)
      }
     MAX-ACCESS   read-write
     STATUS   current
     DESCRIPTION
      "This object is used to create and
       delete row in the table and control
       if they are used. The values
       that can be written are:
       delete(3)...deletes the row
       create(4)...creates a new row

       If the row exists, then a SET with
       value of create(4) returns error
       'badValue'. Deleted rows go away
       immediately. The following values
       can be returned on reads:
       noSuch(0)...no such row
       invalid(1)...Setting it to 'invalid' has the effect of
                    rendering it inoperative..
       valid(2)....the row exists and is valid"
    ::= { ruckusVxlanOverlayGatewaySiteEntry 4 }

ruckusVxlanOverlayGatewaySiteInUnicastPackets OBJECT-TYPE
    SYNTAX Counter64
    MAX-ACCESS  read-only
    STATUS  current
    DESCRIPTION
         "Number of incoming unicast packets on the site's Network Virtual Port"
    ::= { ruckusVxlanOverlayGatewaySiteEntry 5 }

ruckusVxlanOverlayGatewaySiteInUnicastBytes OBJECT-TYPE
    SYNTAX Counter64
    MAX-ACCESS  read-only
    STATUS  current
    DESCRIPTION
         "Number of incoming unicast bytes on the site's Network Virtual Port"
    ::= { ruckusVxlanOverlayGatewaySiteEntry 6 }

ruckusVxlanOverlayGatewaySiteInMulticastPackets OBJECT-TYPE
    SYNTAX Counter64
    MAX-ACCESS  read-only
    STATUS  current
    DESCRIPTION
         "Number of incoming multicast packets on the site's Network Virtual Port"
    ::= { ruckusVxlanOverlayGatewaySiteEntry 7 }

ruckusVxlanOverlayGatewaySiteInMutlticastBytes OBJECT-TYPE
    SYNTAX Counter64
    MAX-ACCESS  read-only
    STATUS  current
    DESCRIPTION
         "Number of incoming multicast bytes on the site's Network Virtual Port"
    ::= { ruckusVxlanOverlayGatewaySiteEntry 8 }

ruckusVxlanOverlayGatewaySiteInBroadcastPackets OBJECT-TYPE
    SYNTAX Counter64
    MAX-ACCESS  read-only
    STATUS  current
    DESCRIPTION
         "Number of incoming broadcast packets on the site's Network Virtual Port"
    ::= { ruckusVxlanOverlayGatewaySiteEntry 9 }

ruckusVxlanOverlayGatewaySiteInBroadcastBytes OBJECT-TYPE
    SYNTAX Counter64
    MAX-ACCESS  read-only
    STATUS  current
    DESCRIPTION
         "Number of incoming broadcast bytes on the site's Network Virtual Port"
    ::= { ruckusVxlanOverlayGatewaySiteEntry 10 }

ruckusVxlanOverlayGatewaySiteOutPackets OBJECT-TYPE
    SYNTAX Counter64
    MAX-ACCESS  read-only
    STATUS  current
    DESCRIPTION
         "Number of outgoing packets on the site's Network Virtual Port"
    ::= { ruckusVxlanOverlayGatewaySiteEntry 11 }

ruckusVxlanOverlayGatewaySiteOutBytes OBJECT-TYPE
    SYNTAX Counter64
    MAX-ACCESS  read-only
    STATUS  current
    DESCRIPTION
         "Number of outgoing bytes on the site's Network Virtual Port"
    ::= { ruckusVxlanOverlayGatewaySiteEntry 12 }

ruckusVxlanOverlayGatewaySiteMonitoring OBJECT-TYPE
    SYNTAX TruthValue
    MAX-ACCESS  read-only
    STATUS  current
    DESCRIPTION
        "VxLAN Extended Site's Monitoring Status
         True  - If Monitoring is Enabled
         False - If Monitoring is Disabled      "
    ::= { ruckusVxlanOverlayGatewaySiteEntry 13 }

ruckusVxlanOverlayGatewaySiteKeepAlive OBJECT-TYPE
    SYNTAX Integer32
    MAX-ACCESS  read-write
    STATUS  current
    DESCRIPTION
         "VxLAN Extended Site's Monitoring Mechanism
          Keep-Alive Value
          The Interval after which an ICMP Ping is sent"
    ::= { ruckusVxlanOverlayGatewaySiteEntry 14 }

ruckusVxlanOverlayGatewaySiteRetry OBJECT-TYPE
    SYNTAX Integer32
    MAX-ACCESS  read-write
    STATUS  current
    DESCRIPTION
         "VxLAN Extended Site's Monitoring Mechanism
          Retry Value
          The Number of times the ICMP Pings will be sent
          to the extended site IP. If a response is not received
          after these many retries the remote IP is considered
          unreachable                                         "
    ::= { ruckusVxlanOverlayGatewaySiteEntry 15 }

-- Table for defining Extended Vlans in a Site

ruckusVxlanOverlayGatewaySiteExtVlanTable OBJECT-TYPE
    SYNTAX  SEQUENCE OF RuckusVxlanOverlayGatewaySiteExtVlanEntry
    MAX-ACCESS  not-accessible
    STATUS  current
    DESCRIPTION
         "This table provides the information related to the
         vlans which are extended to an external site which
         is extended by an overlay-gateway
         If a new vlan is extended to site in an overlay gateway
         then a new entry will be added to the table."
    ::= { ruckusVxlanOverlayGateway 4 }

ruckusVxlanOverlayGatewaySiteExtVlanEntry OBJECT-TYPE
    SYNTAX  RuckusVxlanOverlayGatewaySiteExtVlanEntry
    MAX-ACCESS  not-accessible
    STATUS  current
    DESCRIPTION
         "An row instance of the Overlay Gateway Extended Site Vlan table."
    INDEX   { ruckusVxlanOverlayGatewayName,
              ruckusVxlanOverlayGatewaySiteName,
              ruckusVxlanOverlayGatewaySiteExtVlanId }
    ::= { ruckusVxlanOverlayGatewaySiteExtVlanTable 1 }

RuckusVxlanOverlayGatewaySiteExtVlanEntry ::= SEQUENCE {
          ruckusVxlanOverlayGatewaySiteExtVlanId
              Integer32,
          ruckusVxlanOverlayGatewaySiteExtVlanRowStatus
              INTEGER
      }

ruckusVxlanOverlayGatewaySiteExtVlanId OBJECT-TYPE
     SYNTAX Integer32
     MAX-ACCESS  read-only
     STATUS  current
     DESCRIPTION
          "Vlan Index extended to the site"
     ::= { ruckusVxlanOverlayGatewaySiteExtVlanEntry 1 }

ruckusVxlanOverlayGatewaySiteExtVlanRowStatus OBJECT-TYPE
    SYNTAX   INTEGER {
           invalid(1),
           valid(2),
           delete(3),
           create(4)
           }
    MAX-ACCESS   read-write
    STATUS   current
    DESCRIPTION
       "This object is used to create and
        delete row in the table and control
        if they are used. The values
        that can be written are:
        delete(3)...deletes the row
        create(4)...creates a new row

        If the row exists, then a SET with
        value of create(4) returns error
        'badValue'. Deleted rows go away
        immediately. The following values
        can be returned on reads:
        noSuch(0)...no such row
        invalid(1)...Setting it to 'invalid' has the effect of
                     rendering it inoperative..
        valid(2)....the row exists and is valid"
    ::= { ruckusVxlanOverlayGatewaySiteExtVlanEntry 2 }

-- Table for defining the List of IPs in the Site

ruckusVxlanOverlayGatewaySiteIpListTable OBJECT-TYPE
    SYNTAX  SEQUENCE OF RuckusVxlanOverlayGatewaySiteIpListEntry
    MAX-ACCESS  not-accessible
    STATUS  current
    DESCRIPTION
         "This table provides the information related to the
         IPs which are added to the IP List in the site which
         is extended by an overlay-gateway. The IP List includes
         Primary IP and all the secondary IPs with the index
         If a new IP is added to the IP List in an extended site
         then a new entry will be added to the table."
    ::= { ruckusVxlanOverlayGateway 5 }

ruckusVxlanOverlayGatewaySiteIpListEntry OBJECT-TYPE
    SYNTAX  RuckusVxlanOverlayGatewaySiteIpListEntry
    MAX-ACCESS  not-accessible
    STATUS  current
    DESCRIPTION
         "An row instance of the Overlay Gateway Site IP List table."
    INDEX   { ruckusVxlanOverlayGatewayName,
              ruckusVxlanOverlayGatewaySiteName,
              ruckusVxlanOverlayGatewaySiteIpListIpIndex }
    ::= { ruckusVxlanOverlayGatewaySiteIpListTable 1 }

RuckusVxlanOverlayGatewaySiteIpListEntry ::= SEQUENCE {
          ruckusVxlanOverlayGatewaySiteIpListIpIndex
              Integer32,
          ruckusVxlanOverlayGatewaySiteIpListIpAddress
              IpAddress,
          ruckusVxlanOverlayGatewaySiteIpListRowStatus
              INTEGER
      }

ruckusVxlanOverlayGatewaySiteIpListIpIndex OBJECT-TYPE
     SYNTAX Integer32
     MAX-ACCESS  read-only
     STATUS  current
     DESCRIPTION
          "Index at which the IP is assigned in the IP List"
     ::= { ruckusVxlanOverlayGatewaySiteIpListEntry 1 }

ruckusVxlanOverlayGatewaySiteIpListIpAddress OBJECT-TYPE
     SYNTAX IpAddress
     MAX-ACCESS  read-write
     STATUS  current
     DESCRIPTION
          "IP Address added to the IP List of the Site"
     ::= { ruckusVxlanOverlayGatewaySiteIpListEntry 2 }

ruckusVxlanOverlayGatewaySiteIpListRowStatus OBJECT-TYPE
    SYNTAX   INTEGER {
           invalid(1),
           valid(2),
           delete(3),
           create(4)
           }
    MAX-ACCESS   read-write
    STATUS   current
    DESCRIPTION
       "This object is used to create and
        delete row in the table and control
        if they are used. The values
        that can be written are:
        delete(3)...deletes the row
        create(4)...creates a new row

        If the row exists, then a SET with
        value of create(4) returns error
        'badValue'. Deleted rows go away
        immediately. The following values
        can be returned on reads:
        noSuch(0)...no such row
        invalid(1)...Setting it to 'invalid' has the effect of
                     rendering it inoperative..
        valid(2)....the row exists and is valid"
    ::= { ruckusVxlanOverlayGatewaySiteIpListEntry 3 }

END
