-- =============================================================================
-- Copyright (c) 2004-2009 Hangzhou H3C Tech. Co., Ltd. All rights reserved.
--
-- Description:
--   The file defines a MIB to provide AP object information such as
--   performance statistic and notification events.
-- Reference:
-- Version: V2.0
-- History:
--   V1.0 2006-05-10 Initial version, created by shiyang (Richard)
--   V1.1 2007-02-01 modified by xingjichen(Daniel)
--        Changed DESCRIPTION of h3cDot11APRxStatisTable,
--        h3cDot11APTxStatisTable,h3cDot11APMtRadioFailTrap,
--        h3cDot11APMtRadioFailRecoverTrap.
--   V1.2 2007-04-27 modified by shiyang(Richard)
--        Add new nodes of h3cDot11APChannelChgMode and h3cDot11APChgWorkMode.
--        Split h3cDot11APObjectTable table into h3cDot11APObjectStatusTable
--        and h3cDot11APObjectTable.
--        Rename h3cDot11APRadioRelationTable as h3cDot11APRadioTable.
--        Rename h3cDot11APBSSRelationTable as h3cDot11APBSSTable.
--   V1.3 2007-06-19 modified by Banasree
--        Add new table of h3cDot11APIfTable for h3cDot11APObjectGroup.
--        Add new table of h3cDot11APAssocStatisTable for h3cDot11APStatisGroup.
--        Add new node of h3cDot11CurrAPName, h3cDot11CurrAPModelName,
--        h3cDot11CurrAPImageName, h3cDot11CurrAPSoftwareVersion,
--        h3cDot11CurrAPIPNetMask, h3cDot11CurrRadioModeSupport for
--        h3cDot11APObjectTable.
--        Add new node of h3cDot11Channel, h3cDot11TxPowerLevel,
--        h3cDot11APRadioIfIndex, h3cDot11AntennaGain for h3cDot11APRadioTable.
--        Add new node of h3cDot11APManufacturer, h3cDot11APCPUType,
--        h3cDot11APCPUClockSpeed, h3cDot11APMemoryType, h3cDot11APMemorySize,
--        h3cDot11APFlashType, h3cDot11APFlashSize for h3cDot11APModelTable
--        Add h3cDot11APReset node to the h3cDot11APObjectStatusTable.
--        Add h3cDot11RxFrameErrorRatio to the h3cDot11APRxStatisTable.
--        Add_h3cDot11TxFrameRetryRatio to the h3cDot11APTxStatisTable.
--   V1.4 2007-12-21 modified by wanghao (Kumar)
--        Add h3cDot11BSSRxStatisTable, h3cDot11BSSTxStatisTable,
--        h3cDot11BSSAssocStatisTable for BSS statistics.
--        Add h3cDot11APCpuUsage to h3cDot11APObjectStatusTable.
--        Add h3cDot11MaxBandwidth to h3cDot11APRadioTable.
--        Add h3cDot11RxPhyErrorCnt, h3cDot11RxMICErrorCnt,
--        h3cDot11RxDataFrameBytes to h3cDot11APRxStatisTable.
--        Add h3cDot11TxDataFrameCnt, h3cDot11TxDataFrameBytes to
--        h3cDot11APTxStatisTable.
--        Add h3cDot11ApStationExDeAuthenSum, h3cDot11ApStationCurAssocSum to
--        h3cDot11APAssocStatisTable.
--   V1.5 2008-02-25 modified by wanghao (Kumar)
--        Add h3cDot11ResourceUseRatio to h3cDot11APRadioTable.
--   V1.6 2008-07-09 modified by ChangHuifeng
--        Add h3cDot11APConnectionType to h3cDot11APObjectStatusTable.
--   V1.7 2008-11-07 modified by Wang Lu and Li Yugang
--        Add h3cDot11APLinkStatisTable and h3cDot11RadioAssocStatisTable.
--        Add h3cDot11CurrIfNumber to h3cDot11APObjectTable.
--        Add h3cDot11RadioModeSupport, h3cDot11TxPowerLevel2 and
--        h3cDot11PowerMgmtStatus to h3cDot11APRadioTable.
--        Add h3cDot11SSID to h3cDot11APBSSTable.
--        Add h3cDot11APIfSpeed, h3cDot11APIfInDataRate and
--        h3cDot11APIfOutDataRate to h3cDot11APIfTable
--        Add h3cDot11RadioRxAverSnr to h3cDot11APRxStatisTable.
--        Add h3cDot11APMtTimeSynFail, h3cDot11APMtChlIntfDetected,
--        h3cDot11APMtIntfAPDetected, h3cDot11APMtIntfStaDetected,
--        h3cDot11APMtIPChange, h3cDot11APFlashWriteFailure,
--        h3cDot11APSysReboot, h3cDot11APMtAvailChlTooLow and
--        h3cDot11APImgDwldSuccess to h3cDot11APMtTraps.
--        Add h3cDot11APIntfDevMACAddress and h3cDot11APMtTrapOldIPAddr to
--        h3cDot11APMtTrapVarObjects.
--        Add h3cDot11ChannelSwitchTimes to h3cDot11APRadioTable.
--        Add h3cDot11RxPayloadBytes, h3cDot11RxTrafficSpeed to
--        h3cDot11APRxStatisTable.
--        Add h3cDot11TxMSDUCnt, h3cDot11TxDiscardMSDUCnt,
--        h3cDot11RetryMSDUCnt, h3cDot11TxPayloadBytes,
--        h3cDot11TxTrafficSpeed to h3cDot11APTxStatisTable.
--        Add h3cDot11ApStaCurAuthSuccSum, h3cDot11AllStationUpSumTime,
--        h3cDot11ApStationAssocReqSum to h3cDot11APAssocStatisTable.
--        Add h3cDot11BSSRxFrameErrorRatio, h3cDot11BSSRxPayloadBytes to
--        h3cDot11BSSRxStatisTable.
--        Add h3cDot11BSSTxPayloadBytes to h3cDot11BSSTxStatisTable.
--        Add h3cDot11BSSStationAssocReqSum to h3cDot11BSSAssocStatisTable.
--        Add new tables h3cDot11RadioMngFrameStatisTable,
--        h3cDot11APAuthFailStatisTable, h3cDot11APAssocFailStatisTable,
--        h3cDot11APReassocStatisTable, h3cDot11APUserAuthStatisTable,
--        h3cDot11APDeauthStatisTable, h3cDot11APDeassocStatisTable to
--        h3cDot11APStatisGroup.
--   V1.8 2009-04-17 modified by WangChunsheng
--        Add h3cDot11AntennaType to h3cDot11APRadioTable.
--   V1.9 2009-05-07 modified by Li Yugang, Wang Shaojie, Jin Yi
--        Add h3cDot11CurrAPElementID to h3cDot11APObjectTable.
--        Add h3cDot11DiversitySelectionRx, h3cDot11MaxTxPwrLvl,
--        h3cDot11PwrAttRange, h3cDot11AvgRxSignalStrength,
--        h3cDot11HighestRxSignalStrength, h3cDot11LowestRxSignalStrength
--        h3cDot11RadioIfUpdownTimes, h3cDot11RadioIfLastChange
--        to h3cDot11APRadioTable.
--        Add h3cDot11CurrSSIDResourceUseRatio to h3cDot11APBSSTable.
--        Add new table h3cDot11APSSIDObjectTable, h3cDot11APSysInfoTable
--        to h3cDot11APObjectGroup.
--        Add h3cDot11TxErrFrameRatio, h3cDot11TxFrameRate
--        to h3cDot11APTxStatisTable.
--        Add h3cDot11BSSRxUniFrameCnt, h3cDot11BSSRxNonUniFrameCnt,
--        h3cDot11BSSRxAuthenFrameCnt to h3cDot11BSSRxStatisTable.
--        Add h3cDot11BSSTxRetryCnt, h3cDot11BSSTxUniFrameCnt,
--        h3cDot11BSSTxNonUniFrameCnt, h3cDot11BSSTxAuthenFrameCnt
--        to h3cDot11BSSTxStatisTable.
--        Add new table h3cDot11APAssocFailStatis2Table, h3cDot11APIfStatisTable
--        to h3cDot11APStatisGroup.
--        Add h3cDot11APInterfDetectedTrap,
--        h3cDot11APInterfClearTrap, h3cDot11StaInterfDetectedTrap,
--        h3cDot11StaInterfClearTrap, h3cDot11OtherDevIntDetectedTrap,
--        h3cDot11OtherDevIntClearTrap, h3cDot11APModuleTroubleTrap,
--        h3cDot11APModuleTroubleClearTrap, h3cDot11APRadioDownTrap,
--        h3cDot11APRadioDownRecovTrap, h3cDot11APStaFullTrap,
--        h3cDot11APStaFullRecoverTrap, h3cDot11DFSFreeCntBelowThrRecov,
--        h3cDot11APCpuUsageHigh, h3cDot11APCpuUsageHighRecover,
--        h3cDot11APMemUsageHigh, h3cDot11APMemUsageHighRecover
--        to h3cDot11APMtTraps.
--        Add h3cDot11CurrInterfDetectedNum, h3cDot11StaFullReason,
--        h3cDot11StaLimitNumber, h3cDot11APRadioDownReason,
--        h3cDot11InterfMacList to h3cDot11APMtTrapVarObjects.
--        Add h3cDot11APLastImgDownloadTime to h3cDot11APObjectStatusTable.
--   V2.0 2009-07-29 modified by Heziqi
--        Add new node h3cDot11CurrAPMode for h3cDot11APObjectTable.
--        Add new node h3cDot11APEssVlanId and h3cDot11APBSSResourceUseRatio
--        for h3cDot11APBSSTable.
--        Add new node h3cDot11APTrapUserCnt and h3cDot11APTrapUserThreshold
--        for h3cDot11APMtTrapVarObjects.
--        Add h3cDot11APUserCntOverFlow for h3cDot11APMtNotifyGroup.
--        Add new node h3cDot11TxDiscardFrameRatio, h3cDot11TxFrameRate,
--        h3cDot11TxMgtFrameCnt and h3cDot11TxCtrlFrameCnt
--        for h3cDot11APTxStatisTable.
--        Add new node h3cDot11APIPv6Address for h3cDot11APObjectStatusTable.
--        Add new node h3cDot11CurrAPIPv6Address for h3cDot11APObjectTable.
--        Add h3cDot11RadioMngFrmStatisTable.
-- =============================================================================
H3C-DOT11-APMT-MIB DEFINITIONS ::= BEGIN

IMPORTS
        MODULE-IDENTITY,
        OBJECT-TYPE,
        NOTIFICATION-TYPE,
        Integer32,
        Counter32,
        IpAddress,
        Unsigned32
    FROM SNMPv2-SMI
        TimeTicks
    FROM RFC1155-SMI
        MacAddress,
        TruthValue,
        DateAndTime
    FROM SNMPv2-TC
        h3cDot11,
        H3cDot11ObjectIDType,
        H3cDot11MACModeType,
        H3cDot11RadioScopeType,
        H3cDot11NotifyReasonType,
        H3cDot11ChannelScopeType,
        H3cDot11ServicePolicyIDType,
        H3cDot11RFModeType,
        H3cDot11TxPwrLevelScopeType,
        H3cDot11RadioElementIndex,
        h3cDot11APElementIndex,
        H3cDot11SSIDStringType
    FROM H3C-DOT11-REF-MIB;

h3cDot11APMT MODULE-IDENTITY
    LAST-UPDATED "200907291800Z"        -- Jul 29, 2009 at 18:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB provides AP information which includes AP current object
        information, AP statistic data.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable STA invocation
        of the distribution system services.
        (Wireless clients attempt to connect to
        access points.)

        Basic Rate
        A data rate that is mandatory for client
        devices to support in order for them to achieve
        successful association."

    REVISION "200907291800Z"        -- Jul 29, 2009 at 18:00 GMT
    DESCRIPTION
        "Modified to add new nodes."
    REVISION "200905072000Z"        -- May 7, 2009 at 20:00 GMT
    DESCRIPTION
        "Modified to add new tables and new nodes."
    REVISION "200811071000Z"        -- Nov 07, 2008 at 10:00 GMT
    DESCRIPTION
        "Modified to add new tables and new nodes."
    REVISION "200807091800Z"        -- July 09, 2008 at 18:00 GMT
    DESCRIPTION
        "Modified to add new nodes."
    REVISION "200802251800Z"        -- Feb 25, 2008 at 18:00 GMT
    DESCRIPTION
        "Modified to add new nodes."
    REVISION "200712211800Z"        -- Dec 21, 2007 at 18:00 GMT
    DESCRIPTION
        "Modified to add new tables and new nodes."
    REVISION "200706191800Z"        -- June 19, 2007 at 18:00 GMT
    DESCRIPTION
        "Modified for new requirements and fix some issue."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { h3cDot11 2 }

-- *****************************************************************************
-- *  Major sections
-- *****************************************************************************
--  AP Object Group
--  DEFINED AS "The group to provide the basic information for APs.
--  In order to support fit and fat AP, it uses tables to keep
--  information. For fat AP, if it is needful, it could add more
--  tables to keep information."
h3cDot11APObjectGroup OBJECT IDENTIFIER   ::= { h3cDot11APMT 1 }

--  AP Object Group has the following children:
--  h3cDot11APObjectStatusTable           ::= { h3cDot11APObjectGroup 1 }
--  h3cDot11APObjectTable                 ::= { h3cDot11APObjectGroup 2 }
--  h3cDot11APRadioTable                  ::= { h3cDot11APObjectGroup 3 }
--  h3cDot11APBSSTable                    ::= { h3cDot11APObjectGroup 4 }
--  h3cDot11APModelTable                  ::= { h3cDot11APObjectGroup 5 }
--  h3cDot11APIfTable                     ::= { h3cDot11APObjectGroup 6 }
--  h3cDot11APSSIDObjectTable             ::= { h3cDot11APObjectGroup 7 }
--  h3cDot11APSysInfoTable                ::= { h3cDot11APObjectGroup 8 }

--  AP Statistic Group
--  DEFINED AS "The group to provide the statistic information of Rx
--  and Tx for AP."
h3cDot11APStatisGroup OBJECT IDENTIFIER   ::= { h3cDot11APMT 2 }

--  AP Statistic Group has the following children:
--  h3cDot11APRxStatisTable               ::= { h3cDot11APStatisGroup 1 }
--  h3cDot11APTxStatisTable               ::= { h3cDot11APStatisGroup 2 }
--  h3cDot11APAssocStatisTable            ::= { h3cDot11APStatisGroup 3 }
--  h3cDot11BSSRxStatisTable              ::= { h3cDot11APStatisGroup 4 }
--  h3cDot11BSSTxStatisTable              ::= { h3cDot11APStatisGroup 5 }
--  h3cDot11BSSAssocStatisTable           ::= { h3cDot11APStatisGroup 6 }
--  h3cDot11APLinkStatisTable             ::= { h3cDot11APStatisGroup 7 }
--  h3cDot11RadioAssocStatisTable         ::= { h3cDot11APStatisGroup 8 }
--  h3cDot11RadioMngFrameStatisTable      ::= { h3cDot11APStatisGroup 9 }
--  h3cDot11APAuthFailStatisTable         ::= { h3cDot11APStatisGroup 10 }
--  h3cDot11APAssocFailStatisTable        ::= { h3cDot11APStatisGroup 11 }
--  h3cDot11APReassocStatisTable          ::= { h3cDot11APStatisGroup 12 }
--  h3cDot11APUserAuthStatisTable         ::= { h3cDot11APStatisGroup 13 }
--  h3cDot11APDeauthStatisTable           ::= { h3cDot11APStatisGroup 14 }
--  h3cDot11APDeassocStatisTable          ::= { h3cDot11APStatisGroup 15 }
--  h3cDot11APAssocFailStatis2Table       ::= { h3cDot11APStatisGroup 16 }
--  h3cDot11APIfStatisTable               ::= { h3cDot11APStatisGroup 17 }
--  h3cDot11RadioMngFrmStatisTable        ::= { h3cDot11APStatisGroup 18 }

--  AP Event Notification
--  DEFINED AS " The group to provide AP management notification."
h3cDot11APMtNotifyGroup OBJECT IDENTIFIER ::= { h3cDot11APMT 3 }

-- *****************************************************************************
-- *  h3cDot11APObjectStatusTable Definition
-- *****************************************************************************
h3cDot11APObjectStatusTable OBJECT-TYPE
    SYNTAX      SEQUENCE OF H3cDot11APObjectStatusEntry
    MAX-ACCESS  not-accessible
    STATUS      current
    DESCRIPTION
        "The table will provide the general information about APs in
        different status."
    ::= { h3cDot11APObjectGroup 1 }

h3cDot11APObjectStatusEntry OBJECT-TYPE
    SYNTAX      H3cDot11APObjectStatusEntry
    MAX-ACCESS  not-accessible
    STATUS      current
    DESCRIPTION
        "Each entry contains the general information of an AP."
    INDEX
        {
            h3cDot11APID
        }
    ::= { h3cDot11APObjectStatusTable 1 }

H3cDot11APObjectStatusEntry ::= SEQUENCE
    {
        h3cDot11APID                  H3cDot11ObjectIDType,
        h3cDot11APIPAddress           IpAddress,
        h3cDot11APMacAddress          MacAddress,
        h3cDot11APOperationStatus     INTEGER,
        h3cDot11APTemplateNameOfAP    OCTET STRING,
        h3cDot11APReset               TruthValue,
        h3cDot11APCpuUsage            Integer32,
        h3cDot11APConnectionType      INTEGER,
        h3cDot11APLastImgDownloadTime DateAndTime,
        h3cDot11APIPv6Address         OCTET STRING
    }

h3cDot11APID OBJECT-TYPE
    SYNTAX      H3cDot11ObjectIDType
    MAX-ACCESS  accessible-for-notify
    STATUS      current
    DESCRIPTION
        "To uniquely identify each AP, and relation-ship between h3cDot11APID
        and AP device will be static."
    ::= { h3cDot11APObjectStatusEntry 1 }

h3cDot11APIPAddress OBJECT-TYPE
    SYNTAX      IpAddress
    MAX-ACCESS  read-only
    STATUS      current
    DESCRIPTION
        "Represents the IP address of an AP."
    ::= { h3cDot11APObjectStatusEntry 2 }

h3cDot11APMacAddress OBJECT-TYPE
    SYNTAX      MacAddress
    MAX-ACCESS  read-only
    STATUS      current
    DESCRIPTION
        "Represents the MAC address of an AP."
    ::= { h3cDot11APObjectStatusEntry 3 }

h3cDot11APOperationStatus OBJECT-TYPE
    SYNTAX      INTEGER
        {
            join(1),
            joinConfirm(2),
            download(3),
            config(4),
            run(5)
        }
    MAX-ACCESS  read-only
    STATUS      current
    DESCRIPTION
        "Represents operational status of AP.
        The following values are supported:
        join(1)         - AP is joining to AC.
        joinConfirm(2)  - AC confirm whether permit AP to join.
        download(3)     - AP is downloading software from AC.
        config(4)       - AP and AC exchange configuration before AP
        - provide WLAN service.
        run(5)          - The WLAN service is ready.
        "
    ::= { h3cDot11APObjectStatusEntry 4 }

h3cDot11APTemplateNameOfAP OBJECT-TYPE
    SYNTAX      OCTET STRING
    MAX-ACCESS  read-only
    STATUS      current
    DESCRIPTION
        "Represents the name of current AP template configured for AP."
    ::= { h3cDot11APObjectStatusEntry 5 }

h3cDot11APReset OBJECT-TYPE
    SYNTAX      TruthValue
    MAX-ACCESS  read-write
    STATUS      current
    DESCRIPTION
        "When read the value from the node
        2: Represents the AP can not be reseted.
        1: Represents the AP can be reseted.
        When write the value to the node
        1: Represents reseting the AP. Other values are not supported"
    ::= { h3cDot11APObjectStatusEntry 6 }

h3cDot11APCpuUsage OBJECT-TYPE
    SYNTAX      Integer32(0..100)
    UNITS       "onepercent"
    MAX-ACCESS  read-only
    STATUS      current
    DESCRIPTION
        "Represents the current CPU usage for AP."
    ::= { h3cDot11APObjectStatusEntry 7 }

h3cDot11APConnectionType OBJECT-TYPE
    SYNTAX      INTEGER
        {
            master(1),
            slave(2),
            notAvailable(3)
        }
    MAX-ACCESS  read-only
    STATUS      current
    DESCRIPTION
        "Represents the current connection type."
    ::= { h3cDot11APObjectStatusEntry 8 }
h3cDot11APLastImgDownloadTime OBJECT-TYPE
    SYNTAX      DateAndTime
    MAX-ACCESS  read-only
    STATUS      current
    DESCRIPTION
        "Represents the time at which the device last downloaded image."
    ::= { h3cDot11APObjectStatusEntry 9 }

h3cDot11APIPv6Address OBJECT-TYPE
    SYNTAX      OCTET STRING
    MAX-ACCESS  read-only
    STATUS      current
    DESCRIPTION
        "Represents the IPv6 address of AP."
    ::= { h3cDot11APObjectStatusEntry 10 }
-- *****************************************************************************
-- *  End of H3cDot11APObjectStatusTable Definition
-- *****************************************************************************

-- *****************************************************************************
-- *  h3cDot11APObjectTable Definition
-- *****************************************************************************
h3cDot11APObjectTable OBJECT-TYPE
    SYNTAX      SEQUENCE OF H3cDot11APObjectEntry
    MAX-ACCESS  not-accessible
    STATUS      current
    DESCRIPTION
        "The table will provide information for APs in the running status."
    ::= { h3cDot11APObjectGroup 2 }

h3cDot11APObjectEntry OBJECT-TYPE
    SYNTAX      H3cDot11APObjectEntry
    MAX-ACCESS  not-accessible
    STATUS      current
    DESCRIPTION
        "Each entry contains information of an AP in run status."
    INDEX
        {
            h3cDot11APObjID
        }
    ::= { h3cDot11APObjectTable 1 }

H3cDot11APObjectEntry ::= SEQUENCE
    {
        h3cDot11APObjID                    H3cDot11ObjectIDType,
        h3cDot11CurrAPIPAddress            IpAddress,
        h3cDot11CurrAPMacAddress           MacAddress,
        h3cDot11CurrACPortIndex            Integer32,
        h3cDot11CurrAPMACMode              H3cDot11MACModeType,
        h3cDot11CurrAPTemplateName         OCTET STRING,
        h3cDot11CurrAPStationAssocCount    Integer32,
        h3cDot11CurrAPName                 OCTET STRING,
        h3cDot11CurrAPModelName            OCTET STRING,
        h3cDot11CurrAPImageName            OCTET STRING,
        h3cDot11CurrAPSoftwareVersion      OCTET STRING,
        h3cDot11CurrAPIPNetMask            IpAddress,
        h3cDot11CurrRadioModeSupport       Integer32,
        h3cDot11CurrIfNumber               Integer32,
        h3cDot11CurrAPElementID            Integer32,
        h3cDot11CurrAPMode                 INTEGER,
        h3cDot11CurrAPIPv6Address          OCTET STRING
    }

h3cDot11APObjID OBJECT-TYPE
    SYNTAX      H3cDot11ObjectIDType
    MAX-ACCESS  not-accessible
    STATUS      current
    DESCRIPTION
        "To uniquely identify each AP, and relation-ship between h3cDot11APObjID
        and AP device will be static."
    ::= { h3cDot11APObjectEntry 1 }

h3cDot11CurrAPIPAddress OBJECT-TYPE
    SYNTAX      IpAddress
    MAX-ACCESS  read-only
    STATUS      current
    DESCRIPTION
        "Represents the IP address of an AP."
    ::= { h3cDot11APObjectEntry 2 }

h3cDot11CurrAPMacAddress OBJECT-TYPE
    SYNTAX      MacAddress
    MAX-ACCESS  read-only
    STATUS      current
    DESCRIPTION
        "Represents the MAC address of an AP."
    ::= { h3cDot11APObjectEntry 3 }

h3cDot11CurrACPortIndex OBJECT-TYPE
    SYNTAX      Integer32
    MAX-ACCESS  read-only
    STATUS      current
    DESCRIPTION
        "Represents the port on the AC, by which the traffic of this AP comes
        through. NMS could refer it to access information kept in the
        MIB-2."
    ::= { h3cDot11APObjectEntry 4 }

h3cDot11CurrAPMACMode OBJECT-TYPE
    SYNTAX      H3cDot11MACModeType
    MAX-ACCESS  read-only
    STATUS      current
    DESCRIPTION
        "Represents what MAC mode defined in the CAPWAP is applied.
        For fat AP, the value will be fatap."
    ::= { h3cDot11APObjectEntry 5 }

h3cDot11CurrAPTemplateName OBJECT-TYPE
    SYNTAX      OCTET STRING
    MAX-ACCESS  read-only
    STATUS      current
    DESCRIPTION
        "Represents the name of current AP template."
    ::= { h3cDot11APObjectEntry 6 }

h3cDot11CurrAPStationAssocCount OBJECT-TYPE
    SYNTAX      Integer32
    MAX-ACCESS  read-only
    STATUS      current
    DESCRIPTION
        "Represents the total number of stations which are associating
        to AP."
    ::= { h3cDot11APObjectEntry 7 }

h3cDot11CurrAPName OBJECT-TYPE
    SYNTAX      OCTET STRING
    MAX-ACCESS  read-only
    STATUS      current
    DESCRIPTION
        "Represents the name of AP."
    ::= { h3cDot11APObjectEntry 8 }

h3cDot11CurrAPModelName OBJECT-TYPE
    SYNTAX      OCTET STRING
    MAX-ACCESS  read-only
    STATUS      current
    DESCRIPTION
        "Represents index of WTP model,with it to get AP model information."
    ::= { h3cDot11APObjectEntry 9 }

h3cDot11CurrAPImageName OBJECT-TYPE
    SYNTAX      OCTET STRING
    MAX-ACCESS  read-only
    STATUS      current
    DESCRIPTION
        "Represents the image file name of AP."
    ::= { h3cDot11APObjectEntry 10 }

h3cDot11CurrAPSoftwareVersion OBJECT-TYPE
    SYNTAX      OCTET STRING
    MAX-ACCESS  read-only
    STATUS      current
    DESCRIPTION
        "Represents the software version of AP."
    ::= { h3cDot11APObjectEntry 11 }

h3cDot11CurrAPIPNetMask OBJECT-TYPE
    SYNTAX      IpAddress
    MAX-ACCESS  read-only
    STATUS      current
    DESCRIPTION
        "Represents the IP netmask of AP."
    ::= { h3cDot11APObjectEntry 12 }

h3cDot11CurrRadioModeSupport OBJECT-TYPE
    SYNTAX      Integer32
    MAX-ACCESS  read-only
    STATUS      current
    DESCRIPTION
        "Represents which radio type supported by the AP.
        The WLAN system support the following possible radio type.
        dot11a(1),
        dot11b(2),
        dot11g(4),
        dot11n(8)
        For a AP,it could support multiple radio types at
        the same time.So the value of object could combine multiple value
        of radio type above.
        For example:
        For one AP which support both b and g mode radio, when getting the value
        from the node, the value is 6(2 + 4)."
    ::= { h3cDot11APObjectEntry 13 }

h3cDot11CurrIfNumber OBJECT-TYPE
    SYNTAX      Integer32
    MAX-ACCESS  read-only
    STATUS      current
    DESCRIPTION
        "Represents number of interface of the AP."
    ::= { h3cDot11APObjectEntry 14 }

h3cDot11CurrAPElementID OBJECT-TYPE
    SYNTAX      Integer32
    MAX-ACCESS  read-only
    STATUS      current
    DESCRIPTION
    "Represents the AP element ID."
    ::= { h3cDot11APObjectEntry 15 }

h3cDot11CurrAPMode OBJECT-TYPE
    SYNTAX      INTEGER
        {
            bridge(1),
            route(2)
        }
    MAX-ACCESS  read-only
    STATUS      current
    DESCRIPTION
        "Represents the forward mode of the AP."
    ::= { h3cDot11APObjectEntry 16 }

h3cDot11CurrAPIPv6Address OBJECT-TYPE
    SYNTAX      OCTET STRING
    MAX-ACCESS  read-only
    STATUS      current
    DESCRIPTION
        "Represents the IPv6 address of AP."
    ::= { h3cDot11APObjectEntry 17 }
-- *****************************************************************************
-- *  End of h3cDot11APObjectTable Definition
-- *****************************************************************************

-- *****************************************************************************
-- *  h3cDot11APRadioTable Definition
-- *****************************************************************************
h3cDot11APRadioTable OBJECT-TYPE
    SYNTAX      SEQUENCE OF H3cDot11APRadioEntry
    MAX-ACCESS  not-accessible
    STATUS      current
    DESCRIPTION
        "The table will describe the radio information of AP. The AP here will
        be in running status."
    ::= { h3cDot11APObjectGroup 3 }

h3cDot11APRadioEntry OBJECT-TYPE
    SYNTAX      H3cDot11APRadioEntry
    MAX-ACCESS  not-accessible
    STATUS      current
    DESCRIPTION
        "Each entry contains the information of each radio of a specific AP."
    INDEX
        {
            h3cDot11CurAPID,
            h3cDot11RadioID
        }
    ::= { h3cDot11APRadioTable 1 }

H3cDot11APRadioEntry ::= SEQUENCE
    {
        h3cDot11CurAPID            H3cDot11ObjectIDType,
        h3cDot11RadioID            H3cDot11RadioScopeType,
        h3cDot11AdminStatus        TruthValue,
        h3cDot11OperStatus         TruthValue,
        h3cDot11Channel            H3cDot11ChannelScopeType,
        h3cDot11TxPowerLevel       H3cDot11TxPwrLevelScopeType,
        h3cDot11APRadioIfIndex     Integer32,
        h3cDot11AntennaGain        Integer32,
        h3cDot11MaxBandwidth       Integer32,
        h3cDot11ResourceUseRatio   Integer32,
        h3cDot11RadioModeSupport   Unsigned32,
        h3cDot11TxPowerLevel2      INTEGER,
        h3cDot11PowerMgmtStatus    TruthValue,
        h3cDot11ChannelSwitchTimes Counter32,
        h3cDot11AntennaType        OCTET STRING,
        h3cDot11DiversitySelectionRx     TruthValue,
        h3cDot11MaxTxPwrLvl              OCTET STRING,
        h3cDot11PwrAttRange              Integer32,
        h3cDot11AvgRxSignalStrength      Integer32,
        h3cDot11HighestRxSignalStrength  Integer32,
        h3cDot11LowestRxSignalStrength   Integer32,
        h3cDot11RadioIfUpdownTimes       Counter32,
        h3cDot11RadioIfLastChange        TimeTicks
    }

h3cDot11CurAPID OBJECT-TYPE
    SYNTAX      H3cDot11ObjectIDType
    MAX-ACCESS  not-accessible
    STATUS      current
    DESCRIPTION
        "To uniquely identify a AP in running status."
    ::= { h3cDot11APRadioEntry 1 }

h3cDot11RadioID OBJECT-TYPE
    SYNTAX      H3cDot11RadioScopeType
    MAX-ACCESS  accessible-for-notify
    STATUS      current
    DESCRIPTION
        "Represents each radio."
    ::= { h3cDot11APRadioEntry 2 }

h3cDot11AdminStatus OBJECT-TYPE
    SYNTAX      TruthValue
    MAX-ACCESS  read-only
    STATUS      current
    DESCRIPTION
        "Represents the administrator status of radio."
    ::= { h3cDot11APRadioEntry 3 }

h3cDot11OperStatus OBJECT-TYPE
    SYNTAX      TruthValue
    MAX-ACCESS  read-only
    STATUS      current
    DESCRIPTION
        "Represents the operational status of radio."
    ::= { h3cDot11APRadioEntry 4 }

h3cDot11Channel OBJECT-TYPE
    SYNTAX      H3cDot11ChannelScopeType
    MAX-ACCESS  read-only
    STATUS      current
    DESCRIPTION
        "Represents the current channel allocation for radio."
    ::= { h3cDot11APRadioEntry 5 }

h3cDot11TxPowerLevel OBJECT-TYPE
    SYNTAX      H3cDot11TxPwrLevelScopeType
    UNITS       "dbm"
    MAX-ACCESS  read-only
    STATUS      current
    DESCRIPTION
        "Represents the current transmit power level for radio."
    ::= { h3cDot11APRadioEntry 6 }

h3cDot11APRadioIfIndex OBJECT-TYPE
    SYNTAX      Integer32
    MAX-ACCESS  read-only
    STATUS      current
    DESCRIPTION
        "Represents the interface index for the radio."
    ::= { h3cDot11APRadioEntry 7 }

h3cDot11AntennaGain OBJECT-TYPE
    SYNTAX      Integer32
    UNITS       "dBi"
    MAX-ACCESS  read-only
    STATUS      current
    DESCRIPTION
        "Represents the current gain for antenna."
    ::= { h3cDot11APRadioEntry 8 }

h3cDot11MaxBandwidth OBJECT-TYPE
    SYNTAX      Integer32
    UNITS       "Mbps"
    MAX-ACCESS  read-only
    STATUS      current
    DESCRIPTION
        "Represents the maximum bandwidth for the radio."
    ::= { h3cDot11APRadioEntry 9 }

h3cDot11ResourceUseRatio OBJECT-TYPE
    SYNTAX      Integer32
    UNITS       "onepercent"
    MAX-ACCESS  read-only
    STATUS      current
    DESCRIPTION
        "Represents the ratio of radio resource usage."
    ::= { h3cDot11APRadioEntry 10 }

h3cDot11RadioModeSupport OBJECT-TYPE
    SYNTAX      Unsigned32
    MAX-ACCESS  read-only
    STATUS      current
    DESCRIPTION
        "Represents radio type supported by the radio.
        The WLAN system supports the following possible radio type:
        dot11a(1),
        dot11b(2),
        dot11g(4),
        dot11gn(16),
        dot11an(32).
        For the radio, it could support multiple radio types at
        the same time.  So the value of this object could combine multiple
        values of radio type above.
        For example:
        For one radio which supports both dot11b and dot11g mode, when get
        value from the object, the value is 5(1 + 4)."
    ::= { h3cDot11APRadioEntry 11 }

h3cDot11TxPowerLevel2 OBJECT-TYPE
    SYNTAX      INTEGER(1..8)
    MAX-ACCESS  read-only
    STATUS      current
    DESCRIPTION
        "The TxPowerLevel N currently being used to transmit data."
    ::= { h3cDot11APRadioEntry 12 }

h3cDot11PowerMgmtStatus OBJECT-TYPE
    SYNTAX      TruthValue
    MAX-ACCESS  read-only
    STATUS      current
    DESCRIPTION
        "Represents status of power management of the radio."
    ::= { h3cDot11APRadioEntry 13 }

h3cDot11ChannelSwitchTimes OBJECT-TYPE
    SYNTAX      Counter32
    MAX-ACCESS  read-only
    STATUS      current
    DESCRIPTION
        "Represents the channel switch times."
    ::= { h3cDot11APRadioEntry 14 }

h3cDot11AntennaType OBJECT-TYPE
    SYNTAX      OCTET STRING
    MAX-ACCESS  read-only
    STATUS      current
    DESCRIPTION
        "Represents type of the antenna which radio used."
    ::= { h3cDot11APRadioEntry 15 }

h3cDot11DiversitySelectionRx OBJECT-TYPE
    SYNTAX      TruthValue
    MAX-ACCESS  read-only
    STATUS      current
    DESCRIPTION
        "Represents the diversity selection received."
    ::= { h3cDot11APRadioEntry 16 }

h3cDot11MaxTxPwrLvl OBJECT-TYPE
    SYNTAX      OCTET STRING
    MAX-ACCESS  read-only
    STATUS      current
    DESCRIPTION
        "Represents the maximum transmit power."
    ::= { h3cDot11APRadioEntry 17 }

h3cDot11PwrAttRange OBJECT-TYPE
    SYNTAX      Integer32
    MAX-ACCESS  read-only
    STATUS      current
    DESCRIPTION
        "Represents the range of power attenuation."
    ::= { h3cDot11APRadioEntry 18 }

h3cDot11AvgRxSignalStrength OBJECT-TYPE
    SYNTAX      Integer32
    UNITS       "dBm"
    MAX-ACCESS  read-only
    STATUS      current
    DESCRIPTION
        "Represents the average received signal strength."
    ::= { h3cDot11APRadioEntry 19 }

h3cDot11HighestRxSignalStrength OBJECT-TYPE
    SYNTAX      Integer32
    UNITS       "dBm"
    MAX-ACCESS  read-only
    STATUS      current
    DESCRIPTION
        "Represents the highest received signal strength."
    ::= { h3cDot11APRadioEntry 20 }

h3cDot11LowestRxSignalStrength OBJECT-TYPE
    SYNTAX      Integer32
    UNITS       "dBm"
    MAX-ACCESS  read-only
    STATUS      current
    DESCRIPTION
        "Represents the lowest received signal strength."
    ::= { h3cDot11APRadioEntry 21 }

h3cDot11RadioIfUpdownTimes OBJECT-TYPE
    SYNTAX      Counter32
    MAX-ACCESS  read-only
    STATUS      current
    DESCRIPTION
        "Represents the up/down times on radio interface."
    ::= { h3cDot11APRadioEntry 22 }

h3cDot11RadioIfLastChange OBJECT-TYPE
    SYNTAX      TimeTicks
    MAX-ACCESS  read-only
    STATUS      current
    DESCRIPTION
        "Represents time at last change that occurred on radio interface."
    ::= { h3cDot11APRadioEntry 23 }


-- *****************************************************************************
-- *  End of h3cDot11APRadioTable Definition
-- *****************************************************************************

-- *****************************************************************************
-- *  h3cDot11APBSSTable Definition
-- *****************************************************************************
h3cDot11APBSSTable OBJECT-TYPE
    SYNTAX      SEQUENCE OF H3cDot11APBSSEntry
    MAX-ACCESS  not-accessible
    STATUS      current
    DESCRIPTION
        "After AP connect to AC and get AP template configuration,
        it will create BSS data structure for each radio.
        The table will describe BSS information of AP and service
        policy as per BSS."
    ::= { h3cDot11APObjectGroup 4 }

h3cDot11APBSSEntry OBJECT-TYPE
    SYNTAX      H3cDot11APBSSEntry
    MAX-ACCESS  not-accessible
    STATUS      current
    DESCRIPTION
        "Each entry contains information of each BSS for specific radio."
    INDEX
        {
            h3cDot11CurAPID,
            h3cDot11RadioID,
            h3cDot11WlanID
        }
    ::= { h3cDot11APBSSTable 1 }

H3cDot11APBSSEntry ::= SEQUENCE
    {
        h3cDot11WlanID             Integer32,
        h3cDot11BSSID              MacAddress,
        h3cDot11CurrSvcPolicyID    H3cDot11ServicePolicyIDType,
        h3cDot11SSID               OCTET STRING,
        h3cDot11CurrSSIDResourceUseRatio             Integer32,
        h3cDot11APEssVlanId                          Integer32
    }

h3cDot11WlanID OBJECT-TYPE
    SYNTAX      Integer32
    MAX-ACCESS  not-accessible
    STATUS      current
    DESCRIPTION
        "Represents ID of a specific ESS."
    ::= { h3cDot11APBSSEntry 1 }

h3cDot11BSSID OBJECT-TYPE
    SYNTAX      MacAddress
    MAX-ACCESS  read-only
    STATUS      current
    DESCRIPTION
        "As MAC Address format, it is to identify BSS."
    ::= { h3cDot11APBSSEntry 2 }

h3cDot11CurrSvcPolicyID OBJECT-TYPE
    SYNTAX      H3cDot11ServicePolicyIDType
    MAX-ACCESS  read-only
    STATUS      current
    DESCRIPTION
        "Represents the ID of each service policy used by the AP."
    ::= { h3cDot11APBSSEntry 3 }

h3cDot11SSID OBJECT-TYPE
    SYNTAX      OCTET STRING
    MAX-ACCESS  read-only
    STATUS      current
    DESCRIPTION
        "This object represents the SSID corresponding to this BSS."
    ::= { h3cDot11APBSSEntry 4 }

h3cDot11CurrSSIDResourceUseRatio OBJECT-TYPE
    SYNTAX      Integer32
    MAX-ACCESS  read-only
    STATUS      current
    DESCRIPTION
        "Represents the ratio of resource usage of curr SSID"
    ::= { h3cDot11APBSSEntry 5 }

h3cDot11APEssVlanId OBJECT-TYPE
    SYNTAX      Integer32
    MAX-ACCESS  read-only
    STATUS      current
    DESCRIPTION
        "This object represents the VlanID of the interface ESS
        corresponding to this BSS."
    ::= { h3cDot11APBSSEntry 6 }
-- *****************************************************************************
-- *  End of h3cDot11APBSSTable Definition
-- *****************************************************************************

-- *****************************************************************************
-- *  h3cDot11APModelTable Definition
-- *****************************************************************************
h3cDot11APModelTable OBJECT-TYPE
    SYNTAX      SEQUENCE OF H3cDot11APModelEntry
    MAX-ACCESS  not-accessible
    STATUS      current
    DESCRIPTION
        "The table defines the capability information for a specific
        kind of AP."
    ::= { h3cDot11APObjectGroup 5 }

h3cDot11APModelEntry OBJECT-TYPE
    SYNTAX      H3cDot11APModelEntry
    MAX-ACCESS  not-accessible
    STATUS      current
    DESCRIPTION
        "Each entry contains capability information for a specific kind
        of AP."
    INDEX
        {
            IMPLIED h3cDot11APModelAlias
        }
    ::= { h3cDot11APModelTable 1 }

H3cDot11APModelEntry ::= SEQUENCE
    {
        h3cDot11APModelAlias         OCTET STRING,
        h3cDot11APModelName          OCTET STRING,
        h3cDot11RadioNumSupport      H3cDot11RadioScopeType,
        h3cDot11StationNumSupport    Integer32,
        h3cDot11MACModeSupport       H3cDot11MACModeType,
        h3cDot11APManufacturer       OCTET STRING,
        h3cDot11APCPUType            OCTET STRING,
        h3cDot11APCPUClockSpeed      Unsigned32,
        h3cDot11APMemoryType         OCTET STRING,
        h3cDot11APMemorySize         Unsigned32,
        h3cDot11APFlashType          OCTET STRING,
        h3cDot11APFlashSize          Unsigned32
    }

h3cDot11APModelAlias OBJECT-TYPE
    SYNTAX      OCTET STRING(SIZE(0..127))
    MAX-ACCESS  not-accessible
    STATUS      current
    DESCRIPTION
        "Represents alias of AP model name."
    ::= { h3cDot11APModelEntry 1 }

h3cDot11APModelName OBJECT-TYPE
    SYNTAX      OCTET STRING
    MAX-ACCESS  read-only
    STATUS      current
    DESCRIPTION
        "Represents AP model name(like WA2100)."
    ::= { h3cDot11APModelEntry 2 }

h3cDot11RadioNumSupport OBJECT-TYPE
    SYNTAX      H3cDot11RadioScopeType
    MAX-ACCESS  read-only
    STATUS      current
    DESCRIPTION
        "Represents how many radios the specific AP model
        could support."
    ::= { h3cDot11APModelEntry 3 }

h3cDot11StationNumSupport OBJECT-TYPE
    SYNTAX      Integer32
    MAX-ACCESS  read-only
    STATUS      current
    DESCRIPTION
        "Represents how many station could be supported by a specific
        AP model."
    ::= { h3cDot11APModelEntry 4 }

h3cDot11MACModeSupport OBJECT-TYPE
    SYNTAX      H3cDot11MACModeType
    MAX-ACCESS  read-only
    STATUS      current
    DESCRIPTION
        "Represents the MAC mode type could be supported by a specific
        AP model."
    DEFVAL      { split }
    ::= { h3cDot11APModelEntry 5 }

h3cDot11APManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { h3cDot11APModelEntry 6 }

h3cDot11APCPUType OBJECT-TYPE
    SYNTAX      OCTET STRING
    MAX-ACCESS  read-only
    STATUS      current
    DESCRIPTION
        "Represents the CPU type of AP"
    ::= { h3cDot11APModelEntry 7 }

h3cDot11APCPUClockSpeed OBJECT-TYPE
    SYNTAX      Unsigned32
    UNITS       "Hz"
    MAX-ACCESS  read-only
    STATUS      current
    DESCRIPTION
        "Represents the clock speed of CPU."
    ::= { h3cDot11APModelEntry 8 }

h3cDot11APMemoryType OBJECT-TYPE
    SYNTAX      OCTET STRING
    MAX-ACCESS  read-only
    STATUS      current
    DESCRIPTION
        "Represents the memory card type of AP"
    ::= { h3cDot11APModelEntry 9 }

h3cDot11APMemorySize OBJECT-TYPE
    SYNTAX      Unsigned32
    UNITS       "kbytes"
    MAX-ACCESS  read-only
    STATUS      current
    DESCRIPTION
        "Represents the size of AP memory card."
    ::= { h3cDot11APModelEntry 20 }

h3cDot11APFlashType OBJECT-TYPE
    SYNTAX      OCTET STRING
    MAX-ACCESS  read-only
    STATUS      current
    DESCRIPTION
        "Represents the flash card type of AP"
    ::= { h3cDot11APModelEntry 11 }

h3cDot11APFlashSize OBJECT-TYPE
    SYNTAX      Unsigned32
    UNITS       "kbytes"
    MAX-ACCESS  read-only
    STATUS      current
    DESCRIPTION
        "Represents the size of AP flash card."
    ::= { h3cDot11APModelEntry 12 }
-- *****************************************************************************
-- *  End of h3cDot11APModelTable Definition
-- *****************************************************************************

-- *****************************************************************************
-- *  h3cDot11APIfTable Definition
-- *****************************************************************************
h3cDot11APIfTable OBJECT-TYPE
    SYNTAX      SEQUENCE OF H3cDot11APIfEntry
    MAX-ACCESS  not-accessible
    STATUS      current
    DESCRIPTION
        "This table represents the AP interface informations."
    ::= { h3cDot11APObjectGroup 6 }

h3cDot11APIfEntry OBJECT-TYPE
    SYNTAX      H3cDot11APIfEntry
    MAX-ACCESS  not-accessible
    STATUS      current
    DESCRIPTION
        "Each entry of the table will provide data for the interface of AP."
    INDEX
        {
            h3cDot11APObjID,
            h3cDot11APIfIndex
        }
    ::= { h3cDot11APIfTable 1 }

H3cDot11APIfEntry ::= SEQUENCE
    {
        h3cDot11APIfIndex         Integer32,
        h3cDot11APIfDescr         OCTET STRING,
        h3cDot11APIfType          Integer32,
        h3cDot11APIfMtu           Integer32,
        h3cDot11APIfPHYAddress    OCTET STRING,
        h3cDot11APIfSpeed         Integer32,
        h3cDot11APIfInDataRate    Integer32,
        h3cDot11APIfOutDataRate   Integer32
    }

h3cDot11APIfIndex OBJECT-TYPE
    SYNTAX      Integer32
    MAX-ACCESS  not-accessible
    STATUS      current
    DESCRIPTION
        "Represents the index for a interface."
    ::= { h3cDot11APIfEntry 1 }

h3cDot11APIfDescr OBJECT-TYPE
    SYNTAX      OCTET STRING
    MAX-ACCESS  read-only
    STATUS      current
    DESCRIPTION
        "Represents the interface description for a interface."
    ::= { h3cDot11APIfEntry 2 }

h3cDot11APIfType OBJECT-TYPE
    SYNTAX      Integer32
    MAX-ACCESS  read-only
    STATUS      current
    DESCRIPTION
        "Represents the interface type for a interface."
    ::= { h3cDot11APIfEntry 3 }

h3cDot11APIfMtu OBJECT-TYPE
    SYNTAX      Integer32
    MAX-ACCESS  read-only
    STATUS      current
    DESCRIPTION
        "Represents size of the largest datagram which can
        be sent/received on the interface, specified in octets."
    ::= { h3cDot11APIfEntry 4 }

h3cDot11APIfPHYAddress OBJECT-TYPE
    SYNTAX      OCTET STRING
    MAX-ACCESS  read-only
    STATUS      current
    DESCRIPTION
        "Represents the PHY address of interface."
    ::= { h3cDot11APIfEntry 5 }

h3cDot11APIfSpeed OBJECT-TYPE
    SYNTAX      Integer32
    UNITS       "Mbps"
    MAX-ACCESS  read-only
    STATUS      current
    DESCRIPTION
        "Represents maximum bandwidth of this interface."
    ::= { h3cDot11APIfEntry 6 }

h3cDot11APIfInDataRate OBJECT-TYPE
    SYNTAX      Integer32
    UNITS       "Kbps"
    MAX-ACCESS  read-only
    STATUS      current
    DESCRIPTION
        "Represents the average input data rate of this interface in
        latest 300 seconds."
    ::= { h3cDot11APIfEntry 7 }

h3cDot11APIfOutDataRate OBJECT-TYPE
    SYNTAX      Integer32
    UNITS       "Kbps"
    MAX-ACCESS  read-only
    STATUS      current
    DESCRIPTION
        "Represents the average output data rate of this interface in
        latest 300 seconds."
    ::= { h3cDot11APIfEntry 8 }

-- *****************************************************************************
-- *  End of h3cDot11APIfTable Definition
-- *****************************************************************************

-- *****************************************************************************
-- *  h3cDot11APSSIDObjectTable Definition
-- *****************************************************************************
h3cDot11APSSIDObjectTable OBJECT-TYPE
    SYNTAX      SEQUENCE OF H3cDot11APSSIDObjectEntry
    MAX-ACCESS  not-accessible
    STATUS      current
    DESCRIPTION
        "This table provides BSSID number configuration information
         based on SSID."
    ::= { h3cDot11APObjectGroup 7 }

h3cDot11APSSIDObjectEntry OBJECT-TYPE
    SYNTAX      H3cDot11APSSIDObjectEntry
    MAX-ACCESS  not-accessible
    STATUS      current
    DESCRIPTION
        "Each entry provides BSSID number configuration information
         of a SSID."
    INDEX
        {
            h3cDot11APConfigSPID
        }
    ::= { h3cDot11APSSIDObjectTable 1 }

H3cDot11APSSIDObjectEntry ::= SEQUENCE
    {
        h3cDot11APConfigSPID              H3cDot11ServicePolicyIDType,
        h3cDot11APConfigSSIDName          H3cDot11SSIDStringType,
        h3cDot11APConfigBSSIDNum          Integer32
    }

h3cDot11APConfigSPID OBJECT-TYPE
    SYNTAX      H3cDot11ServicePolicyIDType
    MAX-ACCESS  not-accessible
    STATUS      current
    DESCRIPTION
        "Represents the service policy ID."
    ::= { h3cDot11APSSIDObjectEntry 1 }

h3cDot11APConfigSSIDName OBJECT-TYPE
    SYNTAX      H3cDot11SSIDStringType
    MAX-ACCESS  read-only
    STATUS      current
    DESCRIPTION
        "Represents the SSID name of this service policy."
    ::= { h3cDot11APSSIDObjectEntry 2 }

h3cDot11APConfigBSSIDNum OBJECT-TYPE
    SYNTAX      Integer32
    MAX-ACCESS  read-only
    STATUS      current
    DESCRIPTION
        "Represents the number of BSSID that be configured
         with current SSID."
    ::= { h3cDot11APSSIDObjectEntry 3 }

-- *****************************************************************************
-- *  End of h3cDot11APSSIDObjectTable Definition
-- *****************************************************************************

-- *****************************************************************************
-- *  h3cDot11APSysInfoTable Definition
-- *****************************************************************************
h3cDot11APSysInfoTable OBJECT-TYPE
    SYNTAX      SEQUENCE OF H3cDot11APSysInfoEntry
    MAX-ACCESS  not-accessible
    STATUS      current
    DESCRIPTION
        "The table provides the system information of the AP."
    ::= { h3cDot11APObjectGroup 8 }

h3cDot11APSysInfoEntry OBJECT-TYPE
    SYNTAX      H3cDot11APSysInfoEntry
    MAX-ACCESS  not-accessible
    STATUS      current
    DESCRIPTION
        "Each entry provides system information of an AP."
    INDEX
        {
            h3cDot11APElementIndex
        }
    ::= { h3cDot11APSysInfoTable 1 }

H3cDot11APSysInfoEntry ::= SEQUENCE
    {
        h3cDot11APSysUpTime           TimeTicks,
        h3cDot11APCPURTUsage          Integer32,
        h3cDot11APCPUAvgUsage         Integer32,
        h3cDot11APMemRTUsage          Integer32,
        h3cDot11APMemAvgUsage         Integer32,
        h3cDot11APIPAddressGateway    IpAddress,
        h3cDot11APACAssociateStatus   INTEGER,
        h3cDot11APManuBuildInfo       OCTET STRING,
        h3cDot11APFlashFreeSize       Unsigned32,
        h3cDot11APTemperature         INTEGER
    }

h3cDot11APSysUpTime OBJECT-TYPE
    SYNTAX      TimeTicks
    MAX-ACCESS  read-only
    STATUS      current
    DESCRIPTION
        "Represents how long AP has been powered on."
    ::= { h3cDot11APSysInfoEntry 1 }

h3cDot11APCPURTUsage OBJECT-TYPE
    SYNTAX      Integer32(0..100)
    UNITS       "onepercent"
    MAX-ACCESS  read-only
    STATUS      current
    DESCRIPTION
        "Represents the CPU real time usage for AP."
    ::= { h3cDot11APSysInfoEntry 2 }

h3cDot11APCPUAvgUsage OBJECT-TYPE
    SYNTAX      Integer32(0..100)
    UNITS       "onepercent"
    MAX-ACCESS  read-only
    STATUS      current
    DESCRIPTION
        "Represents the CPU average usage for AP."
    ::= { h3cDot11APSysInfoEntry 3 }

h3cDot11APMemRTUsage OBJECT-TYPE
    SYNTAX      Integer32(0..100)
    UNITS       "onepercent"
    MAX-ACCESS  read-only
    STATUS      current
    DESCRIPTION
        "Represents the memory real time usage for AP."
    ::= { h3cDot11APSysInfoEntry 4 }

h3cDot11APMemAvgUsage OBJECT-TYPE
    SYNTAX      Integer32(0..100)
    UNITS       "onepercent"
    MAX-ACCESS  read-only
    STATUS      current
    DESCRIPTION
        "Represents the average memory usage for AP."
    ::= { h3cDot11APSysInfoEntry 5 }

h3cDot11APIPAddressGateway OBJECT-TYPE
    SYNTAX      IpAddress
    MAX-ACCESS  read-only
    STATUS      current
    DESCRIPTION
        "Represents the IP address gateway for AP."
    ::= { h3cDot11APSysInfoEntry 6 }

h3cDot11APACAssociateStatus OBJECT-TYPE
    SYNTAX      INTEGER
        {
            associated(1),
            deassociated(2),
            downloadingImage(3)
        }
    MAX-ACCESS  read-only
    STATUS      current
    DESCRIPTION
        "Represents associate status of AP and AC."
    ::= { h3cDot11APSysInfoEntry 7 }

h3cDot11APManuBuildInfo OBJECT-TYPE
    SYNTAX      OCTET STRING(SIZE(0..255))
    MAX-ACCESS  read-only
    STATUS      current
    DESCRIPTION
        "Represents the device version information for AP."
    ::= { h3cDot11APSysInfoEntry 8 }

h3cDot11APFlashFreeSize OBJECT-TYPE
    SYNTAX      Unsigned32
    UNITS       "bytes"
    MAX-ACCESS  read-only
    STATUS      current
    DESCRIPTION
        "Represents the free size of AP flash card."
    ::= { h3cDot11APSysInfoEntry 9 }

h3cDot11APTemperature OBJECT-TYPE
    SYNTAX      INTEGER
    MAX-ACCESS  read-only
    STATUS      current
    DESCRIPTION
        "Represents the device temperature information for AP."
    ::= { h3cDot11APSysInfoEntry 10 }

-- *****************************************************************************
-- *  End of h3cDot11APSysInfoTable Definition
-- *****************************************************************************

-- *****************************************************************************
-- *  h3cDot11APRxStatisTable Definition
-- *****************************************************************************
h3cDot11APRxStatisTable OBJECT-TYPE
    SYNTAX      SEQUENCE OF H3cDot11APRxStatisEntry
    MAX-ACCESS  not-accessible
    STATUS      current
    DESCRIPTION
        "The table will provide the receiving statistic for a specific
        radio of AP."
    ::= { h3cDot11APStatisGroup 1 }

h3cDot11APRxStatisEntry OBJECT-TYPE
    SYNTAX      H3cDot11APRxStatisEntry
    MAX-ACCESS  not-accessible
    STATUS      current
    DESCRIPTION
        "Each entry of the table will provide the statistic data for
        each radio of a specific AP."
    INDEX
        {
            h3cDot11CurAPID,
            h3cDot11RadioID
        }
    ::= { h3cDot11APRxStatisTable 1 }

H3cDot11APRxStatisEntry ::= SEQUENCE
    {
        h3cDot11RxFrameDupCnt          Counter32,
        h3cDot11RxFrameCnt             Counter32,
        h3cDot11RxUcastFrameCnt        Counter32,
        h3cDot11RxBcastFrameCnt        Counter32,
        h3cDot11RxMcastFrameCnt        Counter32,
        h3cDot11RxDiscardFrameCnt      Counter32,
        h3cDot11RxFragCnt              Counter32,
        h3cDot11RxFcsErrCnt            Counter32,
        h3cDot11RxFrameBytes           Counter32,
        h3cDot11RxUcastFrameBytes      Counter32,
        h3cDot11RxBcastFrameBytes      Counter32,
        h3cDot11RxMcastFrameBytes      Counter32,
        h3cDot11RxDiscardFrameBytes    Counter32,
        h3cDot11RxMgmtFrameCnt         Counter32,
        h3cDot11RxCtrlFrameCnt         Counter32,
        h3cDot11RxDataFrameCnt         Counter32,
        h3cDot11RxDecryptErrorCnt      Counter32,
        h3cDot11RxAuthenFrameCnt       Counter32,
        h3cDot11RxAssociateFrameCnt    Counter32,
        h3cDot11RxFrameErrorRatio      Integer32,
        h3cDot11RxPhyErrorCnt          Counter32,
        h3cDot11RxMICErrorCnt          Counter32,
        h3cDot11RxDataFrameBytes       Counter32,
        h3cDot11RadioRxAverSnr         Integer32,
        h3cDot11RxPayloadBytes         Counter32,
        h3cDot11RxTrafficSpeed         Integer32
    }

h3cDot11RxFrameDupCnt OBJECT-TYPE
    SYNTAX      Counter32
    MAX-ACCESS  read-only
    STATUS      current
    DESCRIPTION
        "Represents the number of duplicate frames reception."
    ::= { h3cDot11APRxStatisEntry 1 }

h3cDot11RxFrameCnt OBJECT-TYPE
    SYNTAX      Counter32
    MAX-ACCESS  read-only
    STATUS      current
    DESCRIPTION
        "Represents the number of frames reception."
    ::= { h3cDot11APRxStatisEntry 2 }

h3cDot11RxUcastFrameCnt OBJECT-TYPE
    SYNTAX      Counter32
    MAX-ACCESS  read-only
    STATUS      current
    DESCRIPTION
        "Represents the number of unicast frames reception."
    ::= { h3cDot11APRxStatisEntry 3 }

h3cDot11RxBcastFrameCnt OBJECT-TYPE
    SYNTAX      Counter32
    MAX-ACCESS  read-only
    STATUS      current
    DESCRIPTION
        "Represents the number of broadcast frames reception."
    ::= { h3cDot11APRxStatisEntry 4 }

h3cDot11RxMcastFrameCnt OBJECT-TYPE
    SYNTAX      Counter32
    MAX-ACCESS  read-only
    STATUS      current
    DESCRIPTION
        "Represents the number of multicast frames reception."
    ::= { h3cDot11APRxStatisEntry 5 }

h3cDot11RxDiscardFrameCnt OBJECT-TYPE
    SYNTAX      Counter32
    MAX-ACCESS  read-only
    STATUS      current
    DESCRIPTION
        "Represents the number of frames discarded by AP."
    ::= { h3cDot11APRxStatisEntry 6 }

h3cDot11RxFragCnt OBJECT-TYPE
    SYNTAX      Counter32
    MAX-ACCESS  read-only
    STATUS      current
    DESCRIPTION
        "Represents the number of frame fragments reception."
    ::= { h3cDot11APRxStatisEntry 7 }

h3cDot11RxFcsErrCnt OBJECT-TYPE
    SYNTAX      Counter32
    MAX-ACCESS  read-only
    STATUS      current
    DESCRIPTION
        "Represents the number of FCS error frames reception."
    ::= { h3cDot11APRxStatisEntry 8 }

h3cDot11RxFrameBytes OBJECT-TYPE
    SYNTAX      Counter32
    MAX-ACCESS  read-only
    STATUS      current
    DESCRIPTION
        "Represents the bytes of frames reception."
    ::= { h3cDot11APRxStatisEntry 9 }

h3cDot11RxUcastFrameBytes OBJECT-TYPE
    SYNTAX      Counter32
    MAX-ACCESS  read-only
    STATUS      current
    DESCRIPTION
        "Represents the bytes of unicast frames reception."
    ::= { h3cDot11APRxStatisEntry 10 }

h3cDot11RxBcastFrameBytes OBJECT-TYPE
    SYNTAX      Counter32
    MAX-ACCESS  read-only
    STATUS      current
    DESCRIPTION
        "Represents the bytes of broadcast frames reception."
    ::= { h3cDot11APRxStatisEntry 11 }

h3cDot11RxMcastFrameBytes OBJECT-TYPE
    SYNTAX      Counter32
    MAX-ACCESS  read-only
    STATUS      current
    DESCRIPTION
        "Represents the bytes of multicast frames reception."
    ::= { h3cDot11APRxStatisEntry 12 }

h3cDot11RxDiscardFrameBytes OBJECT-TYPE
    SYNTAX      Counter32
    MAX-ACCESS  read-only
    STATUS      current
    DESCRIPTION
        "Represents the bytes of frames discarded by AP."
    ::= { h3cDot11APRxStatisEntry 13 }

h3cDot11RxMgmtFrameCnt OBJECT-TYPE
    SYNTAX      Counter32
    MAX-ACCESS  read-only
    STATUS      current
    DESCRIPTION
        "Represents the number of management frames reception."
    ::= { h3cDot11APRxStatisEntry 14 }

h3cDot11RxCtrlFrameCnt OBJECT-TYPE
    SYNTAX      Counter32
    MAX-ACCESS  read-only
    STATUS      current
    DESCRIPTION
        "Represents the number of control frames reception."
    ::= { h3cDot11APRxStatisEntry 15 }

h3cDot11RxDataFrameCnt OBJECT-TYPE
    SYNTAX      Counter32
    MAX-ACCESS  read-only
    STATUS      current
    DESCRIPTION
        "Represents the number of data frames reception."
    ::= { h3cDot11APRxStatisEntry 16 }

h3cDot11RxDecryptErrorCnt OBJECT-TYPE
    SYNTAX      Counter32
    MAX-ACCESS  read-only
    STATUS      current
    DESCRIPTION
        "Represents the number of decryption error."
    ::= { h3cDot11APRxStatisEntry 17 }

h3cDot11RxAuthenFrameCnt OBJECT-TYPE
    SYNTAX      Counter32
    MAX-ACCESS  read-only
    STATUS      current
    DESCRIPTION
        "Represents the number of authentication frame reception."
    ::= { h3cDot11APRxStatisEntry 18 }

h3cDot11RxAssociateFrameCnt OBJECT-TYPE
    SYNTAX      Counter32
    MAX-ACCESS  read-only
    STATUS      current
    DESCRIPTION
        "Represents the number of associate frame reception."
    ::= { h3cDot11APRxStatisEntry 19 }

h3cDot11RxFrameErrorRatio OBJECT-TYPE
    SYNTAX      Integer32
    UNITS       "onepercent"
    MAX-ACCESS  read-only
    STATUS      current
    DESCRIPTION
        "Represents the ratio of error frame."
    ::= { h3cDot11APRxStatisEntry 20 }

h3cDot11RxPhyErrorCnt OBJECT-TYPE
    SYNTAX      Counter32
    MAX-ACCESS  read-only
    STATUS      current
    DESCRIPTION
        "Represents the number of physical reception error."
    ::= { h3cDot11APRxStatisEntry 21 }

h3cDot11RxMICErrorCnt OBJECT-TYPE
    SYNTAX      Counter32
    MAX-ACCESS  read-only
    STATUS      current
    DESCRIPTION
        "Represents the number of MIC verification error."
    ::= { h3cDot11APRxStatisEntry 22 }

h3cDot11RxDataFrameBytes OBJECT-TYPE
    SYNTAX      Counter32
    MAX-ACCESS  read-only
    STATUS      current
    DESCRIPTION
        "Represents the bytes of data frames reception."
    ::= { h3cDot11APRxStatisEntry 23 }

h3cDot11RadioRxAverSnr OBJECT-TYPE
    SYNTAX      Integer32
    MAX-ACCESS  read-only
    STATUS      current
    DESCRIPTION
        "Represents the average signal noise rate of this radio."
    ::= { h3cDot11APRxStatisEntry 24 }

h3cDot11RxPayloadBytes OBJECT-TYPE
    SYNTAX      Counter32
    MAX-ACCESS  read-only
    STATUS      current
    DESCRIPTION
        "Represents the payload bytes of data frames reception."
    ::= { h3cDot11APRxStatisEntry 25 }

h3cDot11RxTrafficSpeed OBJECT-TYPE
    SYNTAX      Integer32
    UNITS       "byte/s"
    MAX-ACCESS  read-only
    STATUS      current
    DESCRIPTION
        "Represents the bytes of frames reception per second."
    ::= { h3cDot11APRxStatisEntry 26 }
-- *****************************************************************************
-- *  End of h3cDot11APRxStatisTable Definition
-- *****************************************************************************

-- *****************************************************************************
-- *  h3cDot11APTxStatisTable Definition
-- *****************************************************************************
h3cDot11APTxStatisTable OBJECT-TYPE
    SYNTAX      SEQUENCE OF H3cDot11APTxStatisEntry
    MAX-ACCESS  not-accessible
    STATUS      current
    DESCRIPTION
        "The table will provide the transmission statistic for a
        specific radio of AP."
    ::= { h3cDot11APStatisGroup 2 }

h3cDot11APTxStatisEntry OBJECT-TYPE
    SYNTAX      H3cDot11APTxStatisEntry
    MAX-ACCESS  not-accessible
    STATUS      current
    DESCRIPTION
        "Each entry of the table will provide the statistic data for
        each radio of a specific AP."
    INDEX
        {
            h3cDot11CurAPID,
            h3cDot11RadioID
        }
    ::= { h3cDot11APTxStatisTable 1 }

H3cDot11APTxStatisEntry ::= SEQUENCE
    {
        h3cDot11TxFragCnt              Counter32,
        h3cDot11FailedCnt              Counter32,
        h3cDot11RetryCnt               Counter32,
        h3cDot11MultiRetryCnt          Counter32,
        h3cDot11RtsSuccessCnt          Counter32,
        h3cDot11RtsFailCnt             Counter32,
        h3cDot11AckFailCnt             Counter32,
        h3cDot11TxFrameCnt             Counter32,
        h3cDot11TxUcastFrameCnt        Counter32,
        h3cDot11TxBcastFrameCnt        Counter32,
        h3cDot11TxMcastFrameCnt        Counter32,
        h3cDot11TxDiscardFrameCnt      Counter32,
        h3cDot11TxFrameBytes           Counter32,
        h3cDot11TxUcastFrameBytes      Counter32,
        h3cDot11TxBcastFrameBytes      Counter32,
        h3cDot11TxMcastFrameBytes      Counter32,
        h3cDot11TxDiscardFrameBytes    Counter32,
        h3cDot11TxAuthenFrameCnt       Counter32,
        h3cDot11TxAssociateFrameCnt    Counter32,
        h3cDot11TxFrameRetryRatio      Integer32,
        h3cDot11TxDataFrameCnt         Counter32,
        h3cDot11TxDataFrameBytes       Counter32,
        h3cDot11TxMSDUCnt              Counter32,
        h3cDot11TxDiscardMSDUCnt       Counter32,
        h3cDot11RetryMSDUCnt           Counter32,
        h3cDot11TxPayloadBytes         Counter32,
        h3cDot11TxTrafficSpeed         Integer32,
        h3cDot11TxErrFrameRatio        Integer32,
        h3cDot11TxFrameRate            Integer32,
        h3cDot11TxMgtFrameCnt          Counter32,
        h3cDot11TxCtrlFrameCnt         Counter32
    }

h3cDot11TxFragCnt OBJECT-TYPE
    SYNTAX      Counter32
    MAX-ACCESS  read-only
    STATUS      current
    DESCRIPTION
        "Represents the number of fragmented frames transmission."
    ::= { h3cDot11APTxStatisEntry 1 }

h3cDot11FailedCnt OBJECT-TYPE
    SYNTAX      Counter32
    MAX-ACCESS  read-only
    STATUS      current
    DESCRIPTION
        "Represents the number of transmission failures."
    ::= { h3cDot11APTxStatisEntry 2 }

h3cDot11RetryCnt OBJECT-TYPE
    SYNTAX      Counter32
    MAX-ACCESS  read-only
    STATUS      current
    DESCRIPTION
        "Represents the number of transmit retries."
    ::= { h3cDot11APTxStatisEntry 3 }

h3cDot11MultiRetryCnt OBJECT-TYPE
    SYNTAX      Counter32
    MAX-ACCESS  read-only
    STATUS      current
    DESCRIPTION
        "Represents the number of transmits that required more than
        one retry."
    ::= { h3cDot11APTxStatisEntry 4 }

h3cDot11RtsSuccessCnt OBJECT-TYPE
    SYNTAX      Counter32
    MAX-ACCESS  read-only
    STATUS      current
    DESCRIPTION
        "Represents the number of successful RTS (Request to send)
        transmission."
    ::= { h3cDot11APTxStatisEntry 5 }

h3cDot11RtsFailCnt OBJECT-TYPE
    SYNTAX      Counter32
    MAX-ACCESS  read-only
    STATUS      current
    DESCRIPTION
        "Represents the number of RTS transmission failures."
    ::= { h3cDot11APTxStatisEntry 6 }

h3cDot11AckFailCnt OBJECT-TYPE
    SYNTAX      Counter32
    MAX-ACCESS  read-only
    STATUS      current
    DESCRIPTION
        "Represents the number of acknowledgement failures."
    ::= { h3cDot11APTxStatisEntry 7 }

h3cDot11TxFrameCnt OBJECT-TYPE
    SYNTAX      Counter32
    MAX-ACCESS  read-only
    STATUS      current
    DESCRIPTION
        "Represents the total number of frames transmission."
    ::= { h3cDot11APTxStatisEntry 8 }

h3cDot11TxUcastFrameCnt OBJECT-TYPE
    SYNTAX      Counter32
    MAX-ACCESS  read-only
    STATUS      current
    DESCRIPTION
        "Represents the number of unicast frames transmission."
    ::= { h3cDot11APTxStatisEntry 9 }

h3cDot11TxBcastFrameCnt OBJECT-TYPE
    SYNTAX      Counter32
    MAX-ACCESS  read-only
    STATUS      current
    DESCRIPTION
        "Represents the number of broadcast frames transmission."
    ::= { h3cDot11APTxStatisEntry 10 }

h3cDot11TxMcastFrameCnt OBJECT-TYPE
    SYNTAX      Counter32
    MAX-ACCESS  read-only
    STATUS      current
    DESCRIPTION
        "Represents the number of multicast frames transmission."
    ::= { h3cDot11APTxStatisEntry 11 }

h3cDot11TxDiscardFrameCnt OBJECT-TYPE
    SYNTAX      Counter32
    MAX-ACCESS  read-only
    STATUS      current
    DESCRIPTION
        "Represents the number of frames discarded by AP."
    ::= { h3cDot11APTxStatisEntry 12 }

h3cDot11TxFrameBytes OBJECT-TYPE
    SYNTAX      Counter32
    MAX-ACCESS  read-only
    STATUS      current
    DESCRIPTION
        "Represents the total bytes of frames transmission."
    ::= { h3cDot11APTxStatisEntry 13 }

h3cDot11TxUcastFrameBytes OBJECT-TYPE
    SYNTAX      Counter32
    MAX-ACCESS  read-only
    STATUS      current
    DESCRIPTION
        "Represents the bytes of unicast frames transmission."
    ::= { h3cDot11APTxStatisEntry 14 }

h3cDot11TxBcastFrameBytes OBJECT-TYPE
    SYNTAX      Counter32
    MAX-ACCESS  read-only
    STATUS      current
    DESCRIPTION
        "Represents the bytes of broadcast frames transmission."
    ::= { h3cDot11APTxStatisEntry 15 }

h3cDot11TxMcastFrameBytes OBJECT-TYPE
    SYNTAX      Counter32
    MAX-ACCESS  read-only
    STATUS      current
    DESCRIPTION
        "Represents the bytes of multicast frames transmission."
    ::= { h3cDot11APTxStatisEntry 16 }

h3cDot11TxDiscardFrameBytes OBJECT-TYPE
    SYNTAX      Counter32
    MAX-ACCESS  read-only
    STATUS      current
    DESCRIPTION
        "Represents the bytes of multicast frames transmission."
    ::= { h3cDot11APTxStatisEntry 17 }

h3cDot11TxAuthenFrameCnt OBJECT-TYPE
    SYNTAX      Counter32
    MAX-ACCESS  read-only
    STATUS      current
    DESCRIPTION
        "Represents the number of authentication frame transmission."
    ::= { h3cDot11APTxStatisEntry 18 }

h3cDot11TxAssociateFrameCnt OBJECT-TYPE
    SYNTAX      Counter32
    MAX-ACCESS  read-only
    STATUS      current
    DESCRIPTION
        "Represents the number of associate frame transmission."
    ::= { h3cDot11APTxStatisEntry 19 }

h3cDot11TxFrameRetryRatio OBJECT-TYPE
    SYNTAX      Integer32
    UNITS       "onepercent"
    MAX-ACCESS  read-only
    STATUS      current
    DESCRIPTION
        "Represents the ratio of retry frame."
    ::= { h3cDot11APTxStatisEntry 20 }

h3cDot11TxDataFrameCnt OBJECT-TYPE
    SYNTAX      Counter32
    MAX-ACCESS  read-only
    STATUS      current
    DESCRIPTION
        "Represents the number of data frame transmission."
    ::= { h3cDot11APTxStatisEntry 21 }

h3cDot11TxDataFrameBytes OBJECT-TYPE
    SYNTAX      Counter32
    MAX-ACCESS  read-only
    STATUS      current
    DESCRIPTION
        "Represents the bytes of data frame transmission."
    ::= { h3cDot11APTxStatisEntry 22 }

h3cDot11TxMSDUCnt OBJECT-TYPE
    SYNTAX      Counter32
    MAX-ACCESS  read-only
    STATUS      current
    DESCRIPTION
        "Represents the total number of MSDU transmission."
    ::= { h3cDot11APTxStatisEntry 23 }

h3cDot11TxDiscardMSDUCnt OBJECT-TYPE
    SYNTAX      Counter32
    MAX-ACCESS  read-only
    STATUS      current
    DESCRIPTION
        "Represents the number of discarded MSDU transmission."
    ::= { h3cDot11APTxStatisEntry 24 }

h3cDot11RetryMSDUCnt OBJECT-TYPE
    SYNTAX      Counter32
    MAX-ACCESS  read-only
    STATUS      current
    DESCRIPTION
        "Represents the number of retransfer MSDU."
    ::= { h3cDot11APTxStatisEntry 25 }

h3cDot11TxPayloadBytes OBJECT-TYPE
    SYNTAX      Counter32
    MAX-ACCESS  read-only
    STATUS      current
    DESCRIPTION
        "Represents the payload bytes of data frames transmission."
    ::= { h3cDot11APTxStatisEntry 26 }

h3cDot11TxTrafficSpeed OBJECT-TYPE
    SYNTAX      Integer32
    UNITS       "byte/s"
    MAX-ACCESS  read-only
    STATUS      current
    DESCRIPTION
        "Represents the bytes of frames transmission per second."
    ::= { h3cDot11APTxStatisEntry 27 }

h3cDot11TxErrFrameRatio OBJECT-TYPE
    SYNTAX      Integer32
    UNITS       "onepercent"
    MAX-ACCESS  read-only
    STATUS      current
    DESCRIPTION
        "Represents the ratio of error frame."
    ::= { h3cDot11APTxStatisEntry 28 }

h3cDot11TxFrameRate OBJECT-TYPE
    SYNTAX      Integer32
    MAX-ACCESS  read-only
    STATUS      current
    DESCRIPTION
        "Represents the count of frames transmission per second."
    ::= { h3cDot11APTxStatisEntry 29 }

h3cDot11TxMgtFrameCnt OBJECT-TYPE
    SYNTAX      Counter32
    MAX-ACCESS  read-only
    STATUS      current
    DESCRIPTION
        "Represents the number of transmitted management frames."
    ::= { h3cDot11APTxStatisEntry 30 }

h3cDot11TxCtrlFrameCnt OBJECT-TYPE
    SYNTAX      Counter32
    MAX-ACCESS  read-only
    STATUS      current
    DESCRIPTION
        "Represents the number of transmission control frames."
    ::= { h3cDot11APTxStatisEntry 31 }
-- *****************************************************************************
-- *  End of h3cDot11APTxStatisTable Definition
-- *****************************************************************************

-- *****************************************************************************
-- *  h3cDot11APAssocStatisTable Definition
-- *****************************************************************************
h3cDot11APAssocStatisTable OBJECT-TYPE
    SYNTAX      SEQUENCE OF H3cDot11APAssocStatisEntry
    MAX-ACCESS  not-accessible
    STATUS      current
    DESCRIPTION
        "The table will provide the station association statistic for AP."
    ::= { h3cDot11APStatisGroup 3 }

h3cDot11APAssocStatisEntry OBJECT-TYPE
    SYNTAX      H3cDot11APAssocStatisEntry
    MAX-ACCESS  not-accessible
    STATUS      current
    DESCRIPTION
        "Each entry of the table will provide the statistic data of station
        association for AP."
    INDEX
        {
            h3cDot11CurAPID
        }
    ::= { h3cDot11APAssocStatisTable 1 }

H3cDot11APAssocStatisEntry ::= SEQUENCE
    {
        h3cDot11ApStationAssocSum          Counter32,
        h3cDot11ApStationAssocFailSum      Counter32,
        h3cDot11ApStationReassocSum        Counter32,
        h3cDot11ApStationAssocRejectSum    Counter32,
        h3cDot11ApStationExDeAuthenSum     Counter32,
        h3cDot11ApStationCurAssocSum       Integer32,
        h3cDot11ApStaCurAuthSuccSum        Integer32,
        h3cDot11AllStationUpSumTime        Counter32,
        h3cDot11ApStationAssocReqSum       Counter32
    }

h3cDot11ApStationAssocSum OBJECT-TYPE
    SYNTAX      Counter32
    MAX-ACCESS  read-only
    STATUS      current
    DESCRIPTION
        "Represents the total number of station association
        with this AP."
    ::= { h3cDot11APAssocStatisEntry 1 }

h3cDot11ApStationAssocFailSum OBJECT-TYPE
    SYNTAX      Counter32
    MAX-ACCESS  read-only
    STATUS      current
    DESCRIPTION
        "Represents the total number of station
        association failure with this AP."
    ::= { h3cDot11APAssocStatisEntry 2 }

h3cDot11ApStationReassocSum OBJECT-TYPE
    SYNTAX      Counter32
    MAX-ACCESS  read-only
    STATUS      current
    DESCRIPTION
        "Represents the total number of station reassociation with this AP."
    ::= { h3cDot11APAssocStatisEntry 3 }

h3cDot11ApStationAssocRejectSum OBJECT-TYPE
    SYNTAX      Counter32
    MAX-ACCESS  read-only
    STATUS      current
    DESCRIPTION
        "Represents the total number of station association rejected
        on account of resource limit with this AP."
    ::= { h3cDot11APAssocStatisEntry 4 }

h3cDot11ApStationExDeAuthenSum OBJECT-TYPE
    SYNTAX      Counter32
    MAX-ACCESS  read-only
    STATUS      current
    DESCRIPTION
        "Represents the total number of exceptional station deauthentication
        (Without sending a deauthentication to AP) with this AP."
    ::= { h3cDot11APAssocStatisEntry 5 }

h3cDot11ApStationCurAssocSum OBJECT-TYPE
    SYNTAX      Integer32
    MAX-ACCESS  read-only
    STATUS      current
    DESCRIPTION
        "Represents the total number of current associated stations
        with this AP."
    ::= { h3cDot11APAssocStatisEntry 6 }

h3cDot11ApStaCurAuthSuccSum OBJECT-TYPE
    SYNTAX      Integer32
    MAX-ACCESS  read-only
    STATUS      current
    DESCRIPTION
        "Represents the successful number of station authentication
        with this AP."
    ::= { h3cDot11APAssocStatisEntry 7 }

h3cDot11AllStationUpSumTime OBJECT-TYPE
    SYNTAX      Counter32
    UNITS       "minute"
    MAX-ACCESS  read-only
    STATUS      current
    DESCRIPTION
        "Represents the sum of duration of all stations which associate with
         this AP."
    ::= { h3cDot11APAssocStatisEntry 8 }

h3cDot11ApStationAssocReqSum OBJECT-TYPE
    SYNTAX      Counter32
    MAX-ACCESS  read-only
    STATUS      current
    DESCRIPTION
        "Represents the number of station association request with this AP."
    ::= { h3cDot11APAssocStatisEntry 9 }
-- *****************************************************************************
-- *  End of h3cDot11APAssocStatisTable Definition
-- *****************************************************************************

-- *****************************************************************************
-- *  h3cDot11BSSRxStatisTable Definition
-- *****************************************************************************
h3cDot11BSSRxStatisTable OBJECT-TYPE
    SYNTAX      SEQUENCE OF H3cDot11BSSRxStatisEntry
    MAX-ACCESS  not-accessible
    STATUS      current
    DESCRIPTION
        "The table will provide the reception statistic for a
        specific BSS on a radio."
    ::= { h3cDot11APStatisGroup 4 }

h3cDot11BSSRxStatisEntry OBJECT-TYPE
    SYNTAX      H3cDot11BSSRxStatisEntry
    MAX-ACCESS  not-accessible
    STATUS      current
    DESCRIPTION
        "Each entry of the table will provide the statistic data for
        each BSS on a specific radio."
    INDEX
        {
            h3cDot11CurAPID,
            h3cDot11RadioID,
            h3cDot11WlanID
        }
    ::= { h3cDot11BSSRxStatisTable 1 }

H3cDot11BSSRxStatisEntry ::= SEQUENCE
    {
        h3cDot11BSSRxFrameCnt             Counter32,
        h3cDot11BSSRxFrameBytes           Counter32,
        h3cDot11BSSRxDataFrameCnt         Counter32,
        h3cDot11BSSRxDataFrameBytes       Counter32,
        h3cDot11BSSRxAssociateFrameCnt    Counter32,
        h3cDot11BSSRxFrameErrorRatio      Integer32,
        h3cDot11BSSRxPayloadBytes         Counter32,
        h3cDot11BSSRxUniFrameCnt          Counter32,
        h3cDot11BSSRxNonUniFrameCnt       Integer32,
        h3cDot11BSSRxAuthenFrameCnt       Counter32
    }

h3cDot11BSSRxFrameCnt OBJECT-TYPE
    SYNTAX      Counter32
    MAX-ACCESS  read-only
    STATUS      current
    DESCRIPTION
        "Represents the number of frames reception with this BSS."
    ::= { h3cDot11BSSRxStatisEntry 1 }

h3cDot11BSSRxFrameBytes OBJECT-TYPE
    SYNTAX      Counter32
    MAX-ACCESS  read-only
    STATUS      current
    DESCRIPTION
        "Represents the bytes of frames reception with this BSS."
    ::= { h3cDot11BSSRxStatisEntry 2 }

h3cDot11BSSRxDataFrameCnt OBJECT-TYPE
    SYNTAX      Counter32
    MAX-ACCESS  read-only
    STATUS      current
    DESCRIPTION
        "Represents the number of data frames reception with this BSS."
    ::= { h3cDot11BSSRxStatisEntry 3 }

h3cDot11BSSRxDataFrameBytes OBJECT-TYPE
    SYNTAX      Counter32
    MAX-ACCESS  read-only
    STATUS      current
    DESCRIPTION
        "Represents the bytes of data frames reception with this BSS."
    ::= { h3cDot11BSSRxStatisEntry 4 }

h3cDot11BSSRxAssociateFrameCnt OBJECT-TYPE
    SYNTAX      Counter32
    MAX-ACCESS  read-only
    STATUS      current
    DESCRIPTION
        "Represents the number of associate frames reception with this BSS."
    ::= { h3cDot11BSSRxStatisEntry 5 }

h3cDot11BSSRxFrameErrorRatio OBJECT-TYPE
    SYNTAX      Integer32
    UNITS       "percent"
    MAX-ACCESS  read-only
    STATUS      current
    DESCRIPTION
        "Represents the ratio of error frames reception with this BSS."
    ::= { h3cDot11BSSRxStatisEntry 6 }

h3cDot11BSSRxPayloadBytes OBJECT-TYPE
    SYNTAX      Counter32
    MAX-ACCESS  read-only
    STATUS      current
    DESCRIPTION
        "Represents the payload bytes of data frames reception with this BSS."
    ::= { h3cDot11BSSRxStatisEntry 7 }

h3cDot11BSSRxUniFrameCnt OBJECT-TYPE
    SYNTAX      Counter32
    MAX-ACCESS  read-only
    STATUS      current
    DESCRIPTION
        "Represents the count of unicast frames received."
    ::= { h3cDot11BSSRxStatisEntry 8 }

h3cDot11BSSRxNonUniFrameCnt  OBJECT-TYPE
    SYNTAX      Integer32
    MAX-ACCESS  read-only
    STATUS      current
    DESCRIPTION
        "Represents the count of non-unicast frames received."
    ::= { h3cDot11BSSRxStatisEntry 9 }

h3cDot11BSSRxAuthenFrameCnt OBJECT-TYPE
    SYNTAX      Counter32
    MAX-ACCESS  read-only
    STATUS      current
    DESCRIPTION
        "Represents the count of authentication frames received."
    ::= { h3cDot11BSSRxStatisEntry 10 }

-- *****************************************************************************
-- *  End of h3cDot11BSSRxStatisTable Definition
-- *****************************************************************************

-- *****************************************************************************
-- *  h3cDot11BSSTxStatisTable Definition
-- *****************************************************************************
h3cDot11BSSTxStatisTable OBJECT-TYPE
    SYNTAX      SEQUENCE OF H3cDot11BSSTxStatisEntry
    MAX-ACCESS  not-accessible
    STATUS      current
    DESCRIPTION
        "The table will provide the transmission statistic for a
        specific BSS on a radio."
    ::= { h3cDot11APStatisGroup 5 }

h3cDot11BSSTxStatisEntry OBJECT-TYPE
    SYNTAX      H3cDot11BSSTxStatisEntry
    MAX-ACCESS  not-accessible
    STATUS      current
    DESCRIPTION
        "Each entry of the table will provide the statistic data for
        each BSS on a specific radio."
    INDEX
        {
            h3cDot11CurAPID,
            h3cDot11RadioID,
            h3cDot11WlanID
        }
    ::= { h3cDot11BSSTxStatisTable 1 }

H3cDot11BSSTxStatisEntry ::= SEQUENCE
    {
        h3cDot11BSSTxFrameCnt             Counter32,
        h3cDot11BSSTxFrameBytes           Counter32,
        h3cDot11BSSTxDataFrameCnt         Counter32,
        h3cDot11BSSTxDataFrameBytes       Counter32,
        h3cDot11BSSTxAssociateFrameCnt    Counter32,
        h3cDot11BSSTxPayloadBytes         Counter32,
        h3cDot11BSSTxRetryCnt             Counter32,
        h3cDot11BSSTxUniFrameCnt          Counter32,
        h3cDot11BSSTxNonUniFrameCnt       Integer32,
        h3cDot11BSSTxAuthenFrameCnt       Counter32
    }

h3cDot11BSSTxFrameCnt OBJECT-TYPE
    SYNTAX      Counter32
    MAX-ACCESS  read-only
    STATUS      current
    DESCRIPTION
        "Represents the total number of frames transmission with this BSS."
    ::= { h3cDot11BSSTxStatisEntry 1 }

h3cDot11BSSTxFrameBytes OBJECT-TYPE
    SYNTAX      Counter32
    MAX-ACCESS  read-only
    STATUS      current
    DESCRIPTION
        "Represents the total number of bytes transmission with this BSS."
    ::= { h3cDot11BSSTxStatisEntry 2 }

h3cDot11BSSTxDataFrameCnt OBJECT-TYPE
    SYNTAX      Counter32
    MAX-ACCESS  read-only
    STATUS      current
    DESCRIPTION
        "Represents the number of data frame transmission with this BSS."
    ::= { h3cDot11BSSTxStatisEntry 3 }

h3cDot11BSSTxDataFrameBytes OBJECT-TYPE
    SYNTAX      Counter32
    MAX-ACCESS  read-only
    STATUS      current
    DESCRIPTION
        "Represents the bytes of data frame transmission with this BSS."
    ::= { h3cDot11BSSTxStatisEntry 4 }

h3cDot11BSSTxAssociateFrameCnt OBJECT-TYPE
    SYNTAX      Counter32
    MAX-ACCESS  read-only
    STATUS      current
    DESCRIPTION
        "Represents the number of associate frame transmission with this BSS."
    ::= { h3cDot11BSSTxStatisEntry 5 }

h3cDot11BSSTxPayloadBytes OBJECT-TYPE
    SYNTAX      Counter32
    MAX-ACCESS  read-only
    STATUS      current
    DESCRIPTION
        "Represents the payload bytes of data frame transmission with this BSS."
    ::= { h3cDot11BSSTxStatisEntry 6 }

h3cDot11BSSTxRetryCnt   OBJECT-TYPE
    SYNTAX      Counter32
    MAX-ACCESS  read-only
    STATUS      current
    DESCRIPTION
        "Represents the count of bytes retransmitted with this BSS."
    ::= { h3cDot11BSSTxStatisEntry 7 }

h3cDot11BSSTxUniFrameCnt OBJECT-TYPE
    SYNTAX      Counter32
    MAX-ACCESS  read-only
    STATUS      current
    DESCRIPTION
        "Represents the count of unicast frames transmission with this BSS."
    ::= { h3cDot11BSSTxStatisEntry 8 }

h3cDot11BSSTxNonUniFrameCnt OBJECT-TYPE
    SYNTAX      Integer32
    MAX-ACCESS  read-only
    STATUS      current
    DESCRIPTION
        "Represents the number of non-unicast frames transmission with this BSS."
    ::= { h3cDot11BSSTxStatisEntry 9 }

h3cDot11BSSTxAuthenFrameCnt OBJECT-TYPE
    SYNTAX      Counter32
    MAX-ACCESS  read-only
    STATUS      current
    DESCRIPTION
        "Represents the count of authentication frames transmission with this BSS."
    ::= { h3cDot11BSSTxStatisEntry 10 }

-- *****************************************************************************
-- *  End of h3cDot11BSSTxStatisTable Definition
-- *****************************************************************************

-- *****************************************************************************
-- *  h3cDot11BSSAssocStatisTable Definition
-- *****************************************************************************
h3cDot11BSSAssocStatisTable OBJECT-TYPE
    SYNTAX      SEQUENCE OF H3cDot11BSSAssocStatisEntry
    MAX-ACCESS  not-accessible
    STATUS      current
    DESCRIPTION
        "The table will provide the station association statistic for BSS."
    ::= { h3cDot11APStatisGroup 6 }

h3cDot11BSSAssocStatisEntry OBJECT-TYPE
    SYNTAX      H3cDot11BSSAssocStatisEntry
    MAX-ACCESS  not-accessible
    STATUS      current
    DESCRIPTION
        "Each entry of the table will provide the statistic data of station
        association for BSS."
    INDEX
        {
            h3cDot11CurAPID,
            h3cDot11RadioID,
            h3cDot11WlanID
        }
    ::= { h3cDot11BSSAssocStatisTable 1 }

H3cDot11BSSAssocStatisEntry ::= SEQUENCE
    {
        h3cDot11BSSStationAssocSum          Counter32,
        h3cDot11BSSStationAssocFailSum      Counter32,
        h3cDot11BSSStationReassocSum        Counter32,
        h3cDot11BSSStationAssocRejectSum    Counter32,
        h3cDot11BSSStationExDeAssocSum      Counter32,
        h3cDot11BSSStationCurAssocSum       Integer32,
        h3cDot11BSSStationAssocReqSum       Counter32
    }

h3cDot11BSSStationAssocSum OBJECT-TYPE
    SYNTAX      Counter32
    MAX-ACCESS  read-only
    STATUS      current
    DESCRIPTION
        "Represents the total number of station association
        with this BSS."
    ::= { h3cDot11BSSAssocStatisEntry 1 }

h3cDot11BSSStationAssocFailSum OBJECT-TYPE
    SYNTAX      Counter32
    MAX-ACCESS  read-only
    STATUS      current
    DESCRIPTION
        "Represents the total number of station
        association failure with this BSS."
    ::= { h3cDot11BSSAssocStatisEntry 2 }

h3cDot11BSSStationReassocSum OBJECT-TYPE
    SYNTAX      Counter32
    MAX-ACCESS  read-only
    STATUS      current
    DESCRIPTION
        "Represents the total number of station reassociation
        with this BSS."
    ::= { h3cDot11BSSAssocStatisEntry 3 }

h3cDot11BSSStationAssocRejectSum OBJECT-TYPE
    SYNTAX      Counter32
    MAX-ACCESS  read-only
    STATUS      current
    DESCRIPTION
        "Represents the total number of station association rejected
        on account of resource limit with this BSS."
    ::= { h3cDot11BSSAssocStatisEntry 4 }

h3cDot11BSSStationExDeAssocSum OBJECT-TYPE
    SYNTAX      Counter32
    MAX-ACCESS  read-only
    STATUS      current
    DESCRIPTION
        "Represents the total number of exceptional station deauthentication
        (Without sending a deauthentication to AP) with this BSS."
    ::= { h3cDot11BSSAssocStatisEntry 5 }

h3cDot11BSSStationCurAssocSum OBJECT-TYPE
    SYNTAX      Integer32
    MAX-ACCESS  read-only
    STATUS      current
    DESCRIPTION
        "Represents the total number of current associated stations
        with this BSS."
    ::= { h3cDot11BSSAssocStatisEntry 6 }

h3cDot11BSSStationAssocReqSum OBJECT-TYPE
    SYNTAX      Counter32
    MAX-ACCESS  read-only
    STATUS      current
    DESCRIPTION
        "Represents the total number of station association request with
         this BSS."
    ::= { h3cDot11BSSAssocStatisEntry 7 }
-- *****************************************************************************
-- *  End of h3cDot11BSSAssocStatisTable Definition
-- *****************************************************************************

-- *****************************************************************************
-- *  h3cDot11APLinkStatisTable Definition
-- *****************************************************************************
h3cDot11APLinkStatisTable OBJECT-TYPE
    SYNTAX      SEQUENCE OF H3cDot11APLinkStatisEntry
    MAX-ACCESS  not-accessible
    STATUS      current
    DESCRIPTION
        "The table will provide the link statistic for AP."
    ::= { h3cDot11APStatisGroup 7 }

h3cDot11APLinkStatisEntry OBJECT-TYPE
    SYNTAX      H3cDot11APLinkStatisEntry
    MAX-ACCESS  not-accessible
    STATUS      current
    DESCRIPTION
        "Each entry provides the link statistic of the AP."
    INDEX
        {
            h3cDot11CurAPID
        }
    ::= { h3cDot11APLinkStatisTable 1 }

H3cDot11APLinkStatisEntry ::= SEQUENCE
    {
        h3cDot11UpLinkUpDownTimes          Counter32,
        h3cDot11DownLinkUpDownTimes        Counter32
    }

h3cDot11UpLinkUpDownTimes OBJECT-TYPE
    SYNTAX      Counter32
    MAX-ACCESS  read-only
    STATUS      current
    DESCRIPTION
        "Represents up/down times of uplink interface of the AP."
    ::= { h3cDot11APLinkStatisEntry 1 }

h3cDot11DownLinkUpDownTimes OBJECT-TYPE
    SYNTAX      Counter32
    MAX-ACCESS  read-only
    STATUS      current
    DESCRIPTION
        "Represents up/down times of downlink interface of the AP."
    ::= { h3cDot11APLinkStatisEntry 2 }
-- *****************************************************************************
-- *  End of h3cDot11APLinkStatisTable Definition
-- *****************************************************************************

-- *****************************************************************************
-- *  h3cDot11RadioAssocStatisTable Definition
-- *****************************************************************************
h3cDot11RadioAssocStatisTable OBJECT-TYPE
    SYNTAX      SEQUENCE OF H3cDot11RadioAssocStatisEntry
    MAX-ACCESS  not-accessible
    STATUS      current
    DESCRIPTION
        "The table will provide the station association statistic for radio."
    ::= { h3cDot11APStatisGroup 8 }

h3cDot11RadioAssocStatisEntry OBJECT-TYPE
    SYNTAX      H3cDot11RadioAssocStatisEntry
    MAX-ACCESS  not-accessible
    STATUS      current
    DESCRIPTION
        "Each entry of the table will provide the statistic data of station
        association for radio."
    INDEX
        {
            h3cDot11CurAPID,
            h3cDot11RadioID
        }
    ::= { h3cDot11RadioAssocStatisTable 1 }

H3cDot11RadioAssocStatisEntry ::= SEQUENCE
    {
        h3cDot11RadioStaAssocSum          Counter32,
        h3cDot11RadioStaAssocFailSum      Counter32,
        h3cDot11RadioStaReassocSum        Counter32,
        h3cDot11RadioStaAssocRejectSum    Counter32,
        h3cDot11RadioStaExDeAssocSum      Counter32,
        h3cDot11RadioStaCurAssocSum       Integer32
    }

h3cDot11RadioStaAssocSum OBJECT-TYPE
    SYNTAX      Counter32
    MAX-ACCESS  read-only
    STATUS      current
    DESCRIPTION
        "Represents the total number of station association
        with this radio."
    ::= { h3cDot11RadioAssocStatisEntry 1 }

h3cDot11RadioStaAssocFailSum OBJECT-TYPE
    SYNTAX      Counter32
    MAX-ACCESS  read-only
    STATUS      current
    DESCRIPTION
        "Represents the total number of station
        association failure with this radio."
    ::= { h3cDot11RadioAssocStatisEntry 2 }

h3cDot11RadioStaReassocSum OBJECT-TYPE
    SYNTAX      Counter32
    MAX-ACCESS  read-only
    STATUS      current
    DESCRIPTION
        "Represents the total number of station re-association
        with this radio."
    ::= { h3cDot11RadioAssocStatisEntry 3 }

h3cDot11RadioStaAssocRejectSum OBJECT-TYPE
    SYNTAX      Counter32
    MAX-ACCESS  read-only
    STATUS      current
    DESCRIPTION
        "Represents the total number of station association rejected
        on account of resource limit with this radio."
    ::= { h3cDot11RadioAssocStatisEntry 4 }

h3cDot11RadioStaExDeAssocSum OBJECT-TYPE
    SYNTAX      Counter32
    MAX-ACCESS  read-only
    STATUS      current
    DESCRIPTION
        "Represents the total number of exceptional station de-authentication
        (Without sending a de-authentication to AP) with this radio."
    ::= { h3cDot11RadioAssocStatisEntry 5 }

h3cDot11RadioStaCurAssocSum OBJECT-TYPE
    SYNTAX      Integer32
    MAX-ACCESS  read-only
    STATUS      current
    DESCRIPTION
        "Represents the total number of current associated stations
        with this radio."
    ::= { h3cDot11RadioAssocStatisEntry 6 }
-- *****************************************************************************
-- *  End of h3cDot11RadioAssocStatisTable Definition
-- *****************************************************************************

-- *****************************************************************************
-- *  h3cDot11RadioMngFrameStatisTable Definition
-- *****************************************************************************
h3cDot11RadioMngFrameStatisTable OBJECT-TYPE
    SYNTAX      SEQUENCE OF H3cDot11RadioMngFrameStatisEntry
    MAX-ACCESS  not-accessible
    STATUS      current
    DESCRIPTION
        "The table will provide the management frame statistic for this radio."
    ::= { h3cDot11APStatisGroup 9 }

h3cDot11RadioMngFrameStatisEntry OBJECT-TYPE
    SYNTAX      H3cDot11RadioMngFrameStatisEntry
    MAX-ACCESS  not-accessible
    STATUS      current
    DESCRIPTION
        "Each entry of the table will provide the management
        frame statistic for this radio."
    INDEX
        {
            h3cDot11RadioStatisIndex,
            h3cDot11MngFrameType
        }
    ::= { h3cDot11RadioMngFrameStatisTable 1 }

H3cDot11RadioMngFrameStatisEntry ::= SEQUENCE
    {
        h3cDot11RadioStatisIndex            H3cDot11RadioElementIndex,
        h3cDot11MngFrameType                INTEGER,
        h3cDot11MngFrameCnt                 Counter32
    }

h3cDot11RadioStatisIndex OBJECT-TYPE
    SYNTAX      H3cDot11RadioElementIndex
    MAX-ACCESS  not-accessible
    STATUS      current
    DESCRIPTION
        "Represents index of radio."
    ::= { h3cDot11RadioMngFrameStatisEntry 1 }

h3cDot11MngFrameType   OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { h3cDot11RadioMngFrameStatisEntry 2 }

h3cDot11MngFrameCnt OBJECT-TYPE
    SYNTAX      Counter32
    MAX-ACCESS  read-only
    STATUS      current
    DESCRIPTION
        "Represents the total number of each type for management frame on this
        radio."
    ::= { h3cDot11RadioMngFrameStatisEntry 3 }

-- *****************************************************************************
-- *  End of h3cDot11RadioMngFrameStatisTable Definition
-- *****************************************************************************

-- *****************************************************************************
-- *  h3cDot11APAuthFailStatisTable Definition
-- *****************************************************************************
h3cDot11APAuthFailStatisTable OBJECT-TYPE
    SYNTAX      SEQUENCE OF H3cDot11APAuthFailStatisEntry
    MAX-ACCESS  not-accessible
    STATUS      current
    DESCRIPTION
        "The table will provide the authentication failure statistic for this
         AP."
    ::= { h3cDot11APStatisGroup 10 }

h3cDot11APAuthFailStatisEntry OBJECT-TYPE
    SYNTAX      H3cDot11APAuthFailStatisEntry
    MAX-ACCESS  not-accessible
    STATUS      current
    DESCRIPTION
        "Each entry of the table will provide the authentication failure
         statistic for this AP."
    INDEX
        {
            h3cDot11CurAPID,
            h3cDot11APAuthFailStatisType
        }
    ::= { h3cDot11APAuthFailStatisTable 1 }

H3cDot11APAuthFailStatisEntry ::= SEQUENCE
    {
        h3cDot11APAuthFailStatisType                 INTEGER,
        h3cDot11APAuthFailStatisCnt                  Counter32
    }

h3cDot11APAuthFailStatisType OBJECT-TYPE
    SYNTAX      INTEGER
        {
            invalidation(1),
            overtime(2),
            rejected(3),
            other(4)
        }
    MAX-ACCESS  not-accessible
    STATUS      current
    DESCRIPTION
        "Represents the type of authentication
        failure with this AP."
    ::= { h3cDot11APAuthFailStatisEntry 1 }

h3cDot11APAuthFailStatisCnt   OBJECT-TYPE
    SYNTAX      Counter32
    MAX-ACCESS  read-only
    STATUS      current
    DESCRIPTION
        "Represents the total number of each type for authentication
        failure on this AP."
    ::= { h3cDot11APAuthFailStatisEntry 2 }

-- *****************************************************************************
-- *  End of h3cDot11APAuthFailStatisTable Definition
-- *****************************************************************************

-- *****************************************************************************
-- *  h3cDot11APAssocFailStatisTable Definition
-- *****************************************************************************
h3cDot11APAssocFailStatisTable OBJECT-TYPE
    SYNTAX      SEQUENCE OF H3cDot11APAssocFailStatisEntry
    MAX-ACCESS  not-accessible
    STATUS      current
    DESCRIPTION
        "The table will provide the association failure statistic for
        this AP."
    ::= { h3cDot11APStatisGroup 11 }

h3cDot11APAssocFailStatisEntry OBJECT-TYPE
    SYNTAX      H3cDot11APAssocFailStatisEntry
    MAX-ACCESS  not-accessible
    STATUS      current
    DESCRIPTION
        "Each entry of the table will provide the association failure statistic
         for this AP."
    INDEX
        {
            h3cDot11CurAPID,
            h3cDot11APAssocFailStatisType
        }
    ::= { h3cDot11APAssocFailStatisTable 1 }

H3cDot11APAssocFailStatisEntry ::= SEQUENCE
    {
        h3cDot11APAssocFailStatisType                 INTEGER,
        h3cDot11APAssocFailStatisCnt                  Counter32
    }

h3cDot11APAssocFailStatisType OBJECT-TYPE
    SYNTAX      INTEGER
        {
            invalidation(1),
            overtime(2),
            rejected(3),
            other(4)
        }
    MAX-ACCESS  not-accessible
    STATUS      current
    DESCRIPTION
        "Represents the type of association failure
        with this AP."
    ::= { h3cDot11APAssocFailStatisEntry 1 }

h3cDot11APAssocFailStatisCnt   OBJECT-TYPE
    SYNTAX      Counter32
    MAX-ACCESS  read-only
    STATUS      current
    DESCRIPTION
        "Represents the total number of each type for
        association failure on this AP."
    ::= { h3cDot11APAssocFailStatisEntry 2 }

-- *****************************************************************************
-- *  End of h3cDot11APAssocFailStatisTable Definition
-- *****************************************************************************

-- *****************************************************************************
-- *  h3cDot11APReassocStatisTable Definition
-- *****************************************************************************
h3cDot11APReassocStatisTable OBJECT-TYPE
    SYNTAX      SEQUENCE OF H3cDot11APReassocStatisEntry
    MAX-ACCESS  not-accessible
    STATUS      current
    DESCRIPTION
        "The table will provide the re-association statistic for this AP."
    ::= { h3cDot11APStatisGroup 12 }

h3cDot11APReassocStatisEntry OBJECT-TYPE
    SYNTAX      H3cDot11APReassocStatisEntry
    MAX-ACCESS  not-accessible
    STATUS      current
    DESCRIPTION
        "Each entry of the table will provide the re-association statistic
        for this AP."
    INDEX
        {
            h3cDot11CurAPID,
            h3cDot11APReassocStatisType
        }
    ::= { h3cDot11APReassocStatisTable 1 }

H3cDot11APReassocStatisEntry ::= SEQUENCE
    {
        h3cDot11APReassocStatisType                 INTEGER,
        h3cDot11APReassocStatisCnt                  Counter32
    }

h3cDot11APReassocStatisType OBJECT-TYPE
    SYNTAX      INTEGER
        {
            total(1),
            success(2),
            invalidation(3),
            overtime(4),
            rejected(5),
            other(6)
        }
    MAX-ACCESS  not-accessible
    STATUS      current
    DESCRIPTION
        "Represents the type of re-association with this AP."
    ::= { h3cDot11APReassocStatisEntry 1 }

h3cDot11APReassocStatisCnt   OBJECT-TYPE
    SYNTAX      Counter32
    MAX-ACCESS  read-only
    STATUS      current
    DESCRIPTION
        "Represents the total number of each type for re-association with
        this AP."
    ::= { h3cDot11APReassocStatisEntry 2 }

-- *****************************************************************************
-- *  End of h3cDot11APReassocStatisTable Definition
-- *****************************************************************************

-- *****************************************************************************
-- *  h3cDot11APUserAuthStatisTable Definition
-- *****************************************************************************
h3cDot11APUserAuthStatisTable OBJECT-TYPE
    SYNTAX      SEQUENCE OF H3cDot11APUserAuthStatisEntry
    MAX-ACCESS  not-accessible
    STATUS      current
    DESCRIPTION
        "The table will provide the user authentication statistic for this AP."
    ::= { h3cDot11APStatisGroup 13 }

h3cDot11APUserAuthStatisEntry OBJECT-TYPE
    SYNTAX      H3cDot11APUserAuthStatisEntry
    MAX-ACCESS  not-accessible
    STATUS      current
    DESCRIPTION
        "Each entry of the table will provide the user authentication statistic
        for this AP."
    INDEX
        {
            h3cDot11CurAPID,
            h3cDot11UserAuthStatisType
        }
    ::= { h3cDot11APUserAuthStatisTable 1 }

H3cDot11APUserAuthStatisEntry ::= SEQUENCE
    {
        h3cDot11UserAuthStatisType                 INTEGER,
        h3cDot11UserAuthStatisCnt                  Counter32
    }

h3cDot11UserAuthStatisType OBJECT-TYPE
    SYNTAX      INTEGER
        {
            total(1),
            success(2),
            keyError(3),
            invalidation(4),
            overtime(5),
            rejected(6),
            other(7)
        }
    MAX-ACCESS  not-accessible
    STATUS      current
    DESCRIPTION
        "Represents the type of user authentication with this AP."
    ::= { h3cDot11APUserAuthStatisEntry 1 }

h3cDot11UserAuthStatisCnt   OBJECT-TYPE
    SYNTAX      Counter32
    MAX-ACCESS  read-only
    STATUS      current
    DESCRIPTION
        "Represents the total number of each type for user authentication with
        this AP."
    ::= { h3cDot11APUserAuthStatisEntry 2 }

-- *****************************************************************************
-- *  End of h3cDot11APUserAuthStatisTable Definition
-- *****************************************************************************

-- *****************************************************************************
-- *  h3cDot11APDeauthStatisTable Definition
-- *****************************************************************************
h3cDot11APDeauthStatisTable OBJECT-TYPE
    SYNTAX      SEQUENCE OF H3cDot11APDeauthStatisEntry
    MAX-ACCESS  not-accessible
    STATUS      current
    DESCRIPTION
        "The table will provide the de-authentication statistic for this AP."
    ::= { h3cDot11APStatisGroup 14 }

h3cDot11APDeauthStatisEntry OBJECT-TYPE
    SYNTAX      H3cDot11APDeauthStatisEntry
    MAX-ACCESS  not-accessible
    STATUS      current
    DESCRIPTION
        "Each entry of the table will provide the de-authentication statistic
         for this AP."
    INDEX
        {
            h3cDot11CurAPID,
            h3cDot11APDeauthStatisType
        }
    ::= { h3cDot11APDeauthStatisTable 1 }

H3cDot11APDeauthStatisEntry ::= SEQUENCE
    {
        h3cDot11APDeauthStatisType                 INTEGER,
        h3cDot11APDeauthStatisCnt                  Counter32
    }

h3cDot11APDeauthStatisType OBJECT-TYPE
    SYNTAX      INTEGER
        {
            total(1),
            stationLeaving(2),
            shortResource(3),
            exception(4),
            other(5)
        }
    MAX-ACCESS  not-accessible
    STATUS      current
    DESCRIPTION
        "Represents the type of de-authentication for this AP."
    ::= { h3cDot11APDeauthStatisEntry 1 }

h3cDot11APDeauthStatisCnt   OBJECT-TYPE
    SYNTAX      Counter32
    MAX-ACCESS  read-only
    STATUS      current
    DESCRIPTION
        "Represents the total number of each type for de-authentication
         with this AP."
    ::= { h3cDot11APDeauthStatisEntry 2 }

-- *****************************************************************************
-- *  End of h3cDot11APDeauthStatisTable Definition
-- *****************************************************************************

-- *****************************************************************************
-- *  h3cDot11APDeassocStatisTable Definition
-- *****************************************************************************
h3cDot11APDeassocStatisTable OBJECT-TYPE
    SYNTAX      SEQUENCE OF H3cDot11APDeassocStatisEntry
    MAX-ACCESS  not-accessible
    STATUS      current
    DESCRIPTION
        "The table will provide the de-association statistic for this AP."
    ::= { h3cDot11APStatisGroup 15 }

h3cDot11APDeassocStatisEntry OBJECT-TYPE
    SYNTAX      H3cDot11APDeassocStatisEntry
    MAX-ACCESS  not-accessible
    STATUS      current
    DESCRIPTION
        "Each entry of the table will provide the de-association statistic
         for this AP."
    INDEX
        {
            h3cDot11CurAPID,
            h3cDot11APDeassocStatisType
        }
    ::= { h3cDot11APDeassocStatisTable 1 }

H3cDot11APDeassocStatisEntry ::= SEQUENCE
    {
        h3cDot11APDeassocStatisType                 INTEGER,
        h3cDot11APDeassocStatisCnt                  Counter32
    }

h3cDot11APDeassocStatisType OBJECT-TYPE
    SYNTAX      INTEGER
        {
            total(1),
            stationLeaving(2),
            shortResource(3),
            exception(4),
            other(5)
        }
    MAX-ACCESS  not-accessible
    STATUS      current
    DESCRIPTION
        "Represents the type of de-association with this AP."
    ::= { h3cDot11APDeassocStatisEntry 1 }

h3cDot11APDeassocStatisCnt   OBJECT-TYPE
    SYNTAX      Counter32
    MAX-ACCESS  read-only
    STATUS      current
    DESCRIPTION
        "Represents the total number of each type for de-association
         with this AP."
    ::= { h3cDot11APDeassocStatisEntry 2 }

-- *****************************************************************************
-- *  End of h3cDot11APDeassocStatisTable Definition
-- *****************************************************************************
-- *****************************************************************************
-- *  h3cDot11APAssocFailStatis2Table Definition
-- *****************************************************************************
h3cDot11APAssocFailStatis2Table OBJECT-TYPE
    SYNTAX      SEQUENCE OF H3cDot11APAssocFailStatis2Entry
    MAX-ACCESS  not-accessible
    STATUS      current
    DESCRIPTION
        "This table will provide statistic of association fails for each ap."
    ::= { h3cDot11APStatisGroup 16 }

h3cDot11APAssocFailStatis2Entry OBJECT-TYPE
    SYNTAX      H3cDot11APAssocFailStatis2Entry
    MAX-ACCESS  not-accessible
    STATUS      current
    DESCRIPTION
        "Each entry will provide statistic of association fails for this ap."
    INDEX
        {
            h3cDot11CurAPID,
            h3cDot11APAssocFailStatis2Type
        }
    ::= { h3cDot11APAssocFailStatis2Table 1 }

H3cDot11APAssocFailStatis2Entry ::= SEQUENCE
    {
        h3cDot11APAssocFailStatis2Type                 INTEGER,
        h3cDot11APAssocFailStatis2Cnt                  Counter32
    }

h3cDot11APAssocFailStatis2Type OBJECT-TYPE
    SYNTAX      INTEGER
        {
            shortResource(1),
            notSupportRateSet(2),
            unknownReasonCode(3),
            other(4)
        }
    MAX-ACCESS  not-accessible
    STATUS      current
    DESCRIPTION
        "Represents the type of association fails for this AP"
    ::= { h3cDot11APAssocFailStatis2Entry 1 }

h3cDot11APAssocFailStatis2Cnt   OBJECT-TYPE
    SYNTAX      Counter32
    MAX-ACCESS  read-only
    STATUS      current
    DESCRIPTION
        "Represents the total count of association fails for this AP."
    ::= { h3cDot11APAssocFailStatis2Entry 2 }

-- *****************************************************************************
-- *  End of h3cDot11APAssocFailStatis2Table Definition
-- *****************************************************************************
-- *****************************************************************************
-- *  h3cDot11APIfStatisTable Definition
-- *****************************************************************************
h3cDot11APIfStatisTable OBJECT-TYPE
    SYNTAX      SEQUENCE OF H3cDot11APIfStatisEntry
    MAX-ACCESS  not-accessible
    STATUS      current
    DESCRIPTION
        "The table will provide the statistics on the interface of the AP."
    ::= { h3cDot11APStatisGroup 17 }

h3cDot11APIfStatisEntry OBJECT-TYPE
    SYNTAX      H3cDot11APIfStatisEntry
    MAX-ACCESS  not-accessible
    STATUS      current
    DESCRIPTION
        "Each entry of the table will provide statistics on the interface of the AP."
    INDEX
        {
            h3cDot11APElementIndex,
            h3cDot11APIfIndex
        }
    ::= { h3cDot11APIfStatisTable 1 }

H3cDot11APIfStatisEntry ::= SEQUENCE
    {
        h3cDot11APIfInPkts              Counter32,
        h3cDot11APIfInNormalPkts        Counter32,
        h3cDot11APIfInErrorPkts         Counter32,
        h3cDot11APIfOutPkts             Counter32,
        h3cDot11APIfInOctets            Counter32,
        h3cDot11APIfOutOctets           Counter32,
        h3cDot11APIfFlowOut             Unsigned32,
        h3cDot11APIfFlowIN              Unsigned32,
        h3cDot11APIfInUcastPkts         Counter32,
        h3cDot11APIfInNUcastPkts        Counter32,
        h3cDot11APIfInDiscardPkts       Counter32,
        h3cDot11APIfOutUcastPkts        Counter32,
        h3cDot11APIfOutNUcastPkts       Counter32,
        h3cDot11APIfOutDiscardPkts      Counter32,
        h3cDot11APIfOutErrorPkts        Counter32,
        h3cDot11APIfUpdownTimes         Counter32,
        h3cDot11APIfLastChange          TimeTicks,
        h3cDot11APIfOperStatus          INTEGER
    }

h3cDot11APIfInPkts OBJECT-TYPE
    SYNTAX      Counter32
    MAX-ACCESS  read-only
    STATUS      current
    DESCRIPTION
        "Represents the total number of packets received
         on the interface."
    ::= { h3cDot11APIfStatisEntry 1 }

h3cDot11APIfInNormalPkts OBJECT-TYPE
    SYNTAX      Counter32
    MAX-ACCESS  read-only
    STATUS      current
    DESCRIPTION
        "Represents the total number of correct
         packets received on the interface."
    ::= { h3cDot11APIfStatisEntry 2 }

h3cDot11APIfInErrorPkts OBJECT-TYPE
    SYNTAX      Counter32
    MAX-ACCESS  read-only
    STATUS      current
    DESCRIPTION
        "Represents the total number of error
         packets received on the interface."
    ::= { h3cDot11APIfStatisEntry 3 }

h3cDot11APIfOutPkts OBJECT-TYPE
    SYNTAX      Counter32
    MAX-ACCESS  read-only
    STATUS      current
    DESCRIPTION
        "Represents the total number of packets
         sent from the interface."
    ::= { h3cDot11APIfStatisEntry 4 }

h3cDot11APIfInOctets OBJECT-TYPE
    SYNTAX      Counter32
    MAX-ACCESS  read-only
    STATUS      current
    DESCRIPTION
        "Represents the total number of octets
         received on the interface."
    ::= { h3cDot11APIfStatisEntry 5 }

h3cDot11APIfOutOctets OBJECT-TYPE
    SYNTAX      Counter32
    MAX-ACCESS  read-only
    STATUS      current
    DESCRIPTION
        "Represents the total number of octets
         sent from the interface."
    ::= { h3cDot11APIfStatisEntry 6 }

h3cDot11APIfFlowOut OBJECT-TYPE
    SYNTAX      Unsigned32
    MAX-ACCESS  read-only
    STATUS      current
    DESCRIPTION
        "Represents the traffic rate (byte/s) on the uplink interface
         during a sampling period."
    ::= { h3cDot11APIfStatisEntry 7 }

h3cDot11APIfFlowIN OBJECT-TYPE
    SYNTAX      Unsigned32
    MAX-ACCESS  read-only
    STATUS      current
    DESCRIPTION
        "Represents the traffic rate (byte/s) on the downlink interface
         during a sampling period."
    ::= { h3cDot11APIfStatisEntry 8 }

h3cDot11APIfInUcastPkts OBJECT-TYPE
    SYNTAX      Counter32
    MAX-ACCESS  read-only
    STATUS      current
    DESCRIPTION
        "Represents the number of unicast packets received on the interface."
    ::= { h3cDot11APIfStatisEntry 9 }

h3cDot11APIfInNUcastPkts OBJECT-TYPE
    SYNTAX      Counter32
    MAX-ACCESS  read-only
    STATUS      current
    DESCRIPTION
        "Represents the number of non-unicast packets received on the wired
         interface."
    ::= { h3cDot11APIfStatisEntry 10 }

h3cDot11APIfInDiscardPkts OBJECT-TYPE
    SYNTAX      Counter32
    MAX-ACCESS  read-only
    STATUS      current
    DESCRIPTION
        "Represents the number of unicast packets discarded on the interface."
    ::= { h3cDot11APIfStatisEntry 11 }

h3cDot11APIfOutUcastPkts OBJECT-TYPE
    SYNTAX      Counter32
    MAX-ACCESS  read-only
    STATUS      current
    DESCRIPTION
        "Represents the number of unicast packets send on the interface."
    ::= { h3cDot11APIfStatisEntry 12 }

h3cDot11APIfOutNUcastPkts OBJECT-TYPE
    SYNTAX      Counter32
    MAX-ACCESS  read-only
    STATUS      current
    DESCRIPTION
        "Represents the number of non-unicast packets send on the interface."
    ::= { h3cDot11APIfStatisEntry 13 }

h3cDot11APIfOutDiscardPkts OBJECT-TYPE
    SYNTAX      Counter32
    MAX-ACCESS  read-only
    STATUS      current
    DESCRIPTION
        "Represents the number of discarded packets send on the interface."
    ::= { h3cDot11APIfStatisEntry 14 }

h3cDot11APIfOutErrorPkts OBJECT-TYPE
    SYNTAX      Counter32
    MAX-ACCESS  read-only
    STATUS      current
    DESCRIPTION
        "Represents the number of error packets send on the interface."
    ::= { h3cDot11APIfStatisEntry 15 }

h3cDot11APIfUpdownTimes OBJECT-TYPE
    SYNTAX      Counter32
    MAX-ACCESS  read-only
    STATUS      current
    DESCRIPTION
        "Represents the up/down times on the interface."
    ::= { h3cDot11APIfStatisEntry 16 }

h3cDot11APIfLastChange OBJECT-TYPE
    SYNTAX      TimeTicks
    MAX-ACCESS  read-only
    STATUS      current
    DESCRIPTION
        "Represents the last change time on the interface."
    ::= { h3cDot11APIfStatisEntry 17 }

h3cDot11APIfOperStatus OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { h3cDot11APIfStatisEntry 18 }

-- *****************************************************************************
-- *  End of h3cDot11APIfStatisTable Definition
-- *****************************************************************************

-- *****************************************************************************
-- *  h3cDot11RadioMngFrmStatisTable Definition
-- *****************************************************************************
h3cDot11RadioMngFrmStatisTable OBJECT-TYPE
    SYNTAX      SEQUENCE OF H3cDot11RadioMngFrmStatisEntry
    MAX-ACCESS  not-accessible
    STATUS      current
    DESCRIPTION
        "The table will provide the management frame statistic of this radio."
    ::= { h3cDot11APStatisGroup 18 }

h3cDot11RadioMngFrmStatisEntry OBJECT-TYPE
    SYNTAX      H3cDot11RadioMngFrmStatisEntry
    MAX-ACCESS  not-accessible
    STATUS      current
    DESCRIPTION
        "Each entry of the table will provide the management
         frame statistic of this radio."
    INDEX
        {
            h3cDot11CurAPID,
            h3cDot11RadioID,
            h3cDot11MngFrmType
        }
    ::= { h3cDot11RadioMngFrmStatisTable 1 }

H3cDot11RadioMngFrmStatisEntry ::= SEQUENCE
    {
        h3cDot11MngFrmType                 INTEGER,
        h3cDot11MngFrmCnt                  Counter32
    }

h3cDot11MngFrmType  OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { h3cDot11RadioMngFrmStatisEntry 1 }

h3cDot11MngFrmCnt  OBJECT-TYPE
    SYNTAX      Counter32
    MAX-ACCESS  read-only
    STATUS      current
    DESCRIPTION
        "Represents the total number of each type of management frame on this
         radio."
    ::= { h3cDot11RadioMngFrmStatisEntry 2 }
-- *****************************************************************************
-- *  End of h3cDot11RadioMngFrmStatisTable Definition
-- *****************************************************************************

-- *****************************************************************************
-- *  AP Management Notifications Definition
-- *****************************************************************************
-- AP Management Notification

        h3cDot11APMtTraps OBJECT IDENTIFIER
    ::= { h3cDot11APMtNotifyGroup 0 }

h3cDot11APMtWorkModeChgTrap NOTIFICATION-TYPE
    OBJECTS
        {
            h3cDot11APID,
            h3cDot11APChgWorkMode
        }
    STATUS      current
    DESCRIPTION
        "The notification will represent AP changs the work mode, and
        h3cDot11APWorkMode suggests which work mode will be used by AP."
    ::= { h3cDot11APMtTraps 1 }

h3cDot11APMtCfgErrorTrap NOTIFICATION-TYPE
    OBJECTS
        {
            h3cDot11APID,
            h3cDot11RadioID,
            h3cDot11APMtTrapCfgErrReason
        }
    STATUS      current
    DESCRIPTION
        "The notification will represent errors caused by the
        configuration operation of AP."
    ::= { h3cDot11APMtTraps 2 }

h3cDot11APMtRadioFailTrap NOTIFICATION-TYPE
    OBJECTS
        {
            h3cDot11APID,
            h3cDot11RadioID,
            h3cDot11APMtTrapRadioFailReason
        }
    STATUS      current
    DESCRIPTION
        "The notification will notify which the operational status
        of radio becomes down."
    ::= { h3cDot11APMtTraps 3 }

h3cDot11APMtRadioFailRecoverTrap NOTIFICATION-TYPE
    OBJECTS
        {
            h3cDot11APID,
            h3cDot11RadioID
        }
    STATUS      current
    DESCRIPTION
        "The notification will notify the operational status of which radio
        becomes up again."
    ::= { h3cDot11APMtTraps 4 }

h3cDot11APMtRdoChanlChgTrap NOTIFICATION-TYPE
    OBJECTS
        {
            h3cDot11APID,
            h3cDot11RadioID,
            h3cDot11APChannelChgMode,
            h3cDot11APMtTrapOldChannel,
            h3cDot11APMtTrapNewChannel
        }
    STATUS      current
    DESCRIPTION
        "The notification will represent which radio changes the channel."
    ::= { h3cDot11APMtTraps 5 }

h3cDot11APMtTimeSynFail NOTIFICATION-TYPE
    OBJECTS
        {
            h3cDot11APID
        }
    STATUS      current
    DESCRIPTION
        "The notification will be sent when AC and AP failed to
        synchronize their time."
    ::= { h3cDot11APMtTraps 6 }

h3cDot11APMtChlIntfDetected NOTIFICATION-TYPE
    OBJECTS
        {
            h3cDot11Channel
        }
    STATUS      current
    DESCRIPTION
        "The notification will be sent when some ambient device interferes with
        current channel."
    ::= { h3cDot11APMtTraps 7 }

h3cDot11APMtIntfAPDetected NOTIFICATION-TYPE
    OBJECTS
        {
            h3cDot11Channel,
            h3cDot11APIntfDevMACAddress
        }
    STATUS current
    DESCRIPTION
        "The notification will be sent when some ambient AP interferes with
        current channel."
    ::= { h3cDot11APMtTraps 8 }

h3cDot11APMtIntfStaDetected NOTIFICATION-TYPE
    OBJECTS
        {
            h3cDot11Channel,
            h3cDot11APIntfDevMACAddress
        }
    STATUS current
    DESCRIPTION
        "The notification will be sent when some ambient station interferes with
        current channel."
    ::= { h3cDot11APMtTraps 9 }

h3cDot11APMtIPChange NOTIFICATION-TYPE
    OBJECTS
        {
            h3cDot11APIPAddress,
            h3cDot11APMtTrapOldIPAddr
        }
    STATUS current
    DESCRIPTION
        "The notification will be sent when IP address of the AP changes."
    ::= { h3cDot11APMtTraps 10 }

h3cDot11APFlashWriteFailure NOTIFICATION-TYPE
    OBJECTS
        {
            h3cDot11APID
        }
    STATUS      current
    DESCRIPTION
        "The notification will be sent when AP failed to write data
        into flash."
    ::= { h3cDot11APMtTraps 11 }

h3cDot11APSysReboot NOTIFICATION-TYPE
    OBJECTS
        {
            h3cDot11APID
        }
    STATUS current
    DESCRIPTION
        "The notification will be sent when AP reboots."
    ::= { h3cDot11APMtTraps 12 }

h3cDot11APMtAvailChlTooLow NOTIFICATION-TYPE
    OBJECTS
        {
            h3cDot11RadioID
        }
    STATUS current
    DESCRIPTION
        "The notification will be sent when number of available channels is
         too low.
        "
    ::= { h3cDot11APMtTraps 13 }

h3cDot11APImgDwldSuccess NOTIFICATION-TYPE
    OBJECTS
        {
            h3cDot11CurrAPName,
            h3cDot11CurrAPIPAddress,
            h3cDot11CurrAPSoftwareVersion
        }
    STATUS current
    DESCRIPTION
        "The notification will be sent when AP succeeds to download image from
        AC.
        "
    ::= { h3cDot11APMtTraps 14 }

h3cDot11APInterfDetectedTrap NOTIFICATION-TYPE
    OBJECTS
        {
            h3cDot11Channel,
            h3cDot11CurrInterfDetectedNum,
            h3cDot11InterfMacList
        }
    STATUS current
    DESCRIPTION
        "This notification will be sent when some ambient AP interferes with
         current channel."
    ::= { h3cDot11APMtTraps 15 }

h3cDot11APInterfClearTrap NOTIFICATION-TYPE
    OBJECTS
        {
            h3cDot11Channel
        }
    STATUS current
    DESCRIPTION
        "This notification will be sent when interference caused by ambient
         APs on the current channel disappears."
    ::= { h3cDot11APMtTraps 16 }

h3cDot11StaInterfDetectedTrap NOTIFICATION-TYPE
    OBJECTS
        {
            h3cDot11Channel,
            h3cDot11CurrInterfDetectedNum,
            h3cDot11InterfMacList
        }
    STATUS current
    DESCRIPTION
        "This notification will be sent when interference caused by ambient
         STAs on the current channel disappears."
    ::= { h3cDot11APMtTraps 17 }

h3cDot11StaInterfClearTrap NOTIFICATION-TYPE
    OBJECTS
        {
            h3cDot11Channel
        }
    STATUS current
    DESCRIPTION
        "This notification will be sent when interference caused by ambient
         devices on the current channel happens."
    ::= { h3cDot11APMtTraps 18 }

h3cDot11OtherDevIntDetectedTrap NOTIFICATION-TYPE
    OBJECTS
        {
            h3cDot11Channel
        }
    STATUS      current
    DESCRIPTION
        "This notification will be sent when interference caused by ambient
         devices on the current channel disappears."
    ::= { h3cDot11APMtTraps 19 }

h3cDot11OtherDevIntClearTrap NOTIFICATION-TYPE
    OBJECTS
        {
            h3cDot11Channel
        }
    STATUS      current
    DESCRIPTION
        "This notification will be sent when previous ambient device disappeared with
         the same channel."
    ::= { h3cDot11APMtTraps 20 }

h3cDot11APModuleTroubleTrap NOTIFICATION-TYPE
    OBJECTS
        {
            h3cDot11RadioID
        }
    STATUS current
    DESCRIPTION
        "This notification will be sent when WLAN module failed."
    ::= { h3cDot11APMtTraps 21 }

h3cDot11APModuleTroubleClearTrap NOTIFICATION-TYPE
    OBJECTS
        {
            h3cDot11RadioID
        }
    STATUS current
    DESCRIPTION
        "The notification will be sent when WLAN module recovered."
    ::= { h3cDot11APMtTraps 22 }

h3cDot11APRadioDownTrap NOTIFICATION-TYPE
    OBJECTS
        {
            h3cDot11RadioID,
            h3cDot11APRadioDownReason
        }
    STATUS current
    DESCRIPTION
        "This notification will be sent when WLAN links interrupted."
    ::= { h3cDot11APMtTraps 23 }

h3cDot11APRadioDownRecovTrap NOTIFICATION-TYPE
    OBJECTS
        {
            h3cDot11RadioID
        }
    STATUS current
    DESCRIPTION
        "This notification will be sent when WLAN links recover."
    ::= { h3cDot11APMtTraps 24 }

h3cDot11APStaFullTrap NOTIFICATION-TYPE
    OBJECTS
        {
            h3cDot11APID,
            h3cDot11StaLimitNumber,
            h3cDot11StaFullReason
        }
    STATUS current
    DESCRIPTION
        "This notification will be sent when STA number reach limit number."
    ::= { h3cDot11APMtTraps 25 }

h3cDot11APStaFullRecoverTrap NOTIFICATION-TYPE
    OBJECTS
        {
            h3cDot11APID,
            h3cDot11StaLimitNumber,
            h3cDot11StaFullReason
        }
    STATUS current
    DESCRIPTION
        "This notification will be sent when STA number recover enough level."
    ::= { h3cDot11APMtTraps 26 }

h3cDot11DFSFreeCntBelowThrRecov NOTIFICATION-TYPE
    OBJECTS
        {
            h3cDot11RadioID
        }
    STATUS current
    DESCRIPTION
        "This notification will be sent when available channels number
        recover enough level."
    ::= { h3cDot11APMtTraps 27 }

h3cDot11APCpuUsageHigh NOTIFICATION-TYPE
    OBJECTS
        {
            h3cDot11APID,
            h3cDot11APCPURTUsage
        }
    STATUS current
    DESCRIPTION
        "The notification will be sent when the AP CPU usage exceeds the
         threshold.
        "
    ::= { h3cDot11APMtTraps 28 }

h3cDot11APCpuUsageHighRecover NOTIFICATION-TYPE
    OBJECTS
        {
            h3cDot11APID,
            h3cDot11APCPURTUsage
        }
    STATUS current
    DESCRIPTION
        "The notification will be sent when the AP CPU usage descends the
         threshold.
        "
    ::= { h3cDot11APMtTraps 29 }

h3cDot11APMemUsageHigh NOTIFICATION-TYPE
    OBJECTS
        {
            h3cDot11APID,
            h3cDot11APMemRTUsage
        }
    STATUS current
    DESCRIPTION
        "The notification will be sent when the AP memory usage exceeds the
         threshold.
        "
    ::= { h3cDot11APMtTraps 30 }

h3cDot11APMemUsageHighRecover NOTIFICATION-TYPE
    OBJECTS
        {
            h3cDot11APID,
            h3cDot11APMemRTUsage
        }
    STATUS current
    DESCRIPTION
        "The notification will be sent when the AP memory usage descends the
         threshold.
         "
    ::= { h3cDot11APMtTraps 31 }

h3cDot11APTrapUserCntExceedThre NOTIFICATION-TYPE
    OBJECTS
        {
            h3cDot11APID,
            h3cDot11APTrapUserCnt,
            h3cDot11APTrapUserThreshold
        }
    STATUS      current
    DESCRIPTION
        "The notification will be sent when the online user counter exceeds
        the threshold."
    ::= { h3cDot11APMtTraps 32 }
-- AP Management Notification variable object

        h3cDot11APMtTrapVarObjects OBJECT IDENTIFIER
    ::= { h3cDot11APMtNotifyGroup 1 }

h3cDot11APMtTrapCfgErrReason OBJECT-TYPE
    SYNTAX      H3cDot11NotifyReasonType
    MAX-ACCESS  accessible-for-notify
    STATUS      current
    DESCRIPTION
        "Represents errors caused by configuration operation."
    ::= { h3cDot11APMtTrapVarObjects 1 }

h3cDot11APMtTrapRadioFailReason OBJECT-TYPE
    SYNTAX      INTEGER
        {
            config(1),
            hwerror(2),
            swerror(3),
            radar(4),
            unknown(8)
        }
    MAX-ACCESS  accessible-for-notify
    STATUS      current
    DESCRIPTION
        "Represents errors caused by configuration operation.
        The following values are supported:
        config(1)   - Configuration error
        hwerror(2)  - Hardware error
        swerror(3)  - Software error
        radar(4)    - Radar Detection
        unknown(8)  - Unknown reason
        "
    ::= { h3cDot11APMtTrapVarObjects 2 }

h3cDot11APMtTrapOldChannel OBJECT-TYPE
    SYNTAX      H3cDot11ChannelScopeType
    MAX-ACCESS  accessible-for-notify
    STATUS      current
    DESCRIPTION
        "Represents which channel the radio used to use."
    ::= { h3cDot11APMtTrapVarObjects 3 }

h3cDot11APMtTrapNewChannel OBJECT-TYPE
    SYNTAX      H3cDot11ChannelScopeType
    MAX-ACCESS  accessible-for-notify
    STATUS      current
    DESCRIPTION
        "Represents which channel the radio will use."
    ::= { h3cDot11APMtTrapVarObjects 4 }

h3cDot11APChannelChgMode OBJECT-TYPE
    SYNTAX      H3cDot11RFModeType
    MAX-ACCESS  accessible-for-notify
    STATUS      current
    DESCRIPTION
        "Represents the channel change mode for a radio."
    ::= { h3cDot11APMtTrapVarObjects 5 }

h3cDot11APChgWorkMode OBJECT-TYPE
    SYNTAX      INTEGER
        {
            normal(1),
            monitor(2)
        }
    MAX-ACCESS  accessible-for-notify
    STATUS      current
    DESCRIPTION
        "Represents what work mode for AP.
        The following values are supported:
        normal(1),  - AP will supply WLAN service.
        monitor(2)  - AP will be a monitor to find attack."
    ::= { h3cDot11APMtTrapVarObjects 6 }

h3cDot11APIntfDevMACAddress OBJECT-TYPE
    SYNTAX      MacAddress
    MAX-ACCESS  accessible-for-notify
    STATUS      current
    DESCRIPTION
        "Represents MAC address of the device which triggers the notification."
    ::= { h3cDot11APMtTrapVarObjects 7 }

h3cDot11APMtTrapOldIPAddr OBJECT-TYPE
    SYNTAX      IpAddress
    MAX-ACCESS  accessible-for-notify
    STATUS      current
    DESCRIPTION
        "Represents the IP address of AP."
    ::= { h3cDot11APMtTrapVarObjects 8 }

h3cDot11CurrInterfDetectedNum OBJECT-TYPE
    SYNTAX      Integer32
    MAX-ACCESS  accessible-for-notify
    STATUS      current
    DESCRIPTION
        "Represents the number of interfere detected."
    ::= { h3cDot11APMtTrapVarObjects 9 }

h3cDot11StaFullReason OBJECT-TYPE
    SYNTAX      INTEGER
        {
            ap(1),
            bss(2),
            radio(3),
            radioConcur(4),
            radiopolicy(5),
            ac(6),
            acConcur(7),
            aid(8)
        }
    MAX-ACCESS  accessible-for-notify
    STATUS      current
    DESCRIPTION
        "Reports which kind maximum number of STA
         is reached. New STA is not able to associate."
    ::= { h3cDot11APMtTrapVarObjects 10 }

h3cDot11StaLimitNumber OBJECT-TYPE
    SYNTAX      Integer32
    MAX-ACCESS  accessible-for-notify
    STATUS      current
    DESCRIPTION
        "Represents the limit number of STA."
    ::= { h3cDot11APMtTrapVarObjects 11 }

h3cDot11APRadioDownReason OBJECT-TYPE
    SYNTAX  INTEGER
        {
            phyicalUnusable(1),
            configDisable(2),
            operatinUnusable(3),
            apTunnelDown(4)
        }
    MAX-ACCESS  accessible-for-notify
    STATUS      current
    DESCRIPTION
        "Reports the reason why WLAN links is interrupted."
    ::= { h3cDot11APMtTrapVarObjects 12 }

h3cDot11InterfMacList OBJECT-TYPE
    SYNTAX      OCTET STRING
    MAX-ACCESS  accessible-for-notify
    STATUS      current
    DESCRIPTION
        "Represents MAC address list of interfere detected."
    ::= { h3cDot11APMtTrapVarObjects 13 }

h3cDot11APTrapUserCnt OBJECT-TYPE
    SYNTAX      Integer32
    MAX-ACCESS  accessible-for-notify
    STATUS      current
    DESCRIPTION
        "Represents the online user counter of AP."
    ::= { h3cDot11APMtTrapVarObjects 14 }

h3cDot11APTrapUserThreshold OBJECT-TYPE
    SYNTAX      Integer32
    MAX-ACCESS  accessible-for-notify
    STATUS      current
    DESCRIPTION
        "Represents threshold of AP's online user counter."
    ::= { h3cDot11APMtTrapVarObjects 15 }
-- *****************************************************************************
-- *  End of AP Management Notification  Definition
-- *****************************************************************************
END
