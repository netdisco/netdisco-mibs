--
-- HUAWEI-HQOS-MIB.my
-- MIB generated by MG-SOFT Visual MIB Builder Version 3.0 Build 253
-- Tuesday, June 03, 2014 at 14:55:30
--
--  ==================================================================
-- Copyright (C) 2016 by  HUAWEI TECHNOLOGIES. All rights reserved.
-- 
-- Description: HUAWEI Hierarchy Quality Of Service MIB
-- Reference:
-- Version: V2.33
-- History:
-- <author>,  <date>,  <contents>
-- CaiLi,LiuJun   2006-05-13
-- Liguoshuang      2007-08-23    for BT HQoS alarm
-- ==================================================================
-- ==================================================================
-- 
-- Variables and types are imported
-- 
-- ==================================================================

	HUAWEI-HQOS-MIB DEFINITIONS ::= BEGIN
 
		IMPORTS
			entPhysicalIndex, entPhysicalName			
				FROM ENTITY-MIB			
			hwDatacomm			
				FROM HUAWEI-MIB			
			InterfaceIndex			
				FROM IF-MIB			
			OBJECT-GROUP, MODULE-COMPLIANCE, NOTIFICATION-GROUP			
				FROM SNMPv2-CONF			
			TimeTicks, Integer32, Unsigned32, Counter64, OBJECT-TYPE, 
			MODULE-IDENTITY, NOTIFICATION-TYPE			
				FROM SNMPv2-SMI			
			RowStatus, TEXTUAL-CONVENTION			
				FROM SNMPv2-TC;
	

		hwHQOS MODULE-IDENTITY 
                                                     LAST-UPDATED "201610121400Z"        -- August 17, 2016 at 20:00:30
			ORGANIZATION 
				"Huawei Technologies Co.,Ltd."
			CONTACT-INFO 
				"Huawei Industrial Base
				Bantian, Longgang
				 Shenzhen 518129
				 People's Republic of China
				 Website: http://www.huawei.com
				 Email: support@huawei.com
				"
			DESCRIPTION 
				"mib of Hierarchy Quality Of Service module
				the huawei-hqos-mib is only defined about statistic information now. "
     REVISION "201610121400Z"
      DESCRIPTION
     "MOD hwHQoSPwifScheduleTreeCreateFailAlarm"
     REVISION "201608171400Z"
      DESCRIPTION
     "MOD hwhqoSIfProfileUserQueueStatisticsInterval"
     REVISION "201607221400Z"
      DESCRIPTION
     "MOD hwhqoSIfProfileUserQueueStatisticsIntervalTable"
     REVISION "201607211400Z"
      DESCRIPTION
     "ADD hwhqoSIfProfileUserQueueStatisticsIntervalTable"
      REVISION "201606071400Z"
      DESCRIPTION
      "MOD hwhqosBandwidthEntry"
      REVISION "201605231400Z"
      DESCRIPTION
      "MOD hwhqosBandwidthEntry"
      REVISION"201602021400Z"
      DESCRIPTION
      "ADD ALARM NODE"     
      REVISION"201511281126Z"
      DESCRIPTION
      "ADD ALARM NODE"     
      REVISION "201408041558Z"
      DESCRIPTION
      "MOD hwhqosUserQueueShapeAllTrafficEntry"				
      REVISION "201407231558Z"
      DESCRIPTION
      "ADD TABLE"
      REVISION "201406031455Z"        -- June 03, 2014 at 14:55:30
      DESCRIPTION
     "DELETE hwhqosFlowQueueCfgWeightPercentageValue OF hwhqosFlowQueueCfgEntry"
      REVISION "201405061915Z"                -- May 06, 2014 at 19:15:34
      DESCRIPTION
      "DELETE CIR LEAF OF HQOS CONFIG NODE"
      REVISION "201304241443Z"
      DESCRIPTION
      "MOD hwhqosProfileName NODE"
      REVISION "201403251433Z"		-- March 25, 2014 at 14:33 GMT
      DESCRIPTION
      "ADD IF USER QUEUE NODE"
      REVISION "201311201443Z"
      DESCRIPTION
      "MOD VALUE-RANGE"
      REVISION "201309301443Z"
      DESCRIPTION
      "ADD ALARM NODE"
      REVISION "201309161609Z"
      DESCRIPTION
      "ADD ALARM NODE"
      REVISION "201307291443Z"
      DESCRIPTION
      "ADD ALARM TABLE"
      REVISION "201304101443Z"
      DESCRIPTION
      "ADD ALARM NODE"
      REVISION"201408041558Z"
      DESCRIPTION
      "ADD ALARM NODE"
      REVISION"201412221558Z"
      DESCRIPTION
      "ADD ALARM NODE"
      REVISION"201603021558Z"
      DESCRIPTION
      "MOD ALARM NODE"



			::= { hwDatacomm 132 }
--
-- Textual conventions
--
-- type definitions in the interface queue
-- 
-- COS Type
		CosType ::= TEXTUAL-CONVENTION
			STATUS current
			DESCRIPTION 
				"
				BE(1)
				AF1(2)
				AF2(3)
				AF3(4)
				AF4(5)
				EF(6)
				CS6(7)
				CS7(8)
				"
			SYNTAX INTEGER
				{
				be(1),
				af1(2),
				af2(3),
				af3(4),
				af4(5),
				ef(6),
				cs6(7),
				cs7(8)
				}
	
-- 
-- Node definitions
-- 

-- 1.3.6.1.4.1.2011.5.25.132.1
		hwhqosStat OBJECT IDENTIFIER ::= { hwHQOS 1 }
		
-- 1.3.6.1.4.1.2011.5.25.132.1.1
		hwhqosIfStatTable OBJECT-TYPE
			SYNTAX SEQUENCE OF HwhqosIfStatEntry
			MAX-ACCESS not-accessible
			STATUS current
			DESCRIPTION
				"Table of Hierarchy QoS's statistic information."
			::= { hwhqosStat 1 }
		
-- 1.3.6.1.4.1.2011.5.25.132.1.1.1
		hwhqosIfStatEntry OBJECT-TYPE
			SYNTAX HwhqosIfStatEntry
			MAX-ACCESS not-accessible
			STATUS current
			DESCRIPTION
				"The table have multilevel index
				if don't have some or other index. please fill the MAX value 2147483647
				for example : MA52 don't have statistic of user's queue, but have statistic of user.
				              please set QueueIndex the MAX value 2147483647.
				"
			INDEX { hwhqosIfIndex, hwhqosDirection, hwhqosUserLayer1, hwhqosUserLayer2, hwhqosQueueIndex
				 }
			::= { hwhqosIfStatTable 1 }
		
		HwhqosIfStatEntry ::=
			SEQUENCE { 
				hwhqosIfIndex
					Integer32,
				hwhqosDirection
					INTEGER,
				hwhqosUserLayer1
					Integer32,
				hwhqosUserLayer2
					Integer32,
				hwhqosQueueIndex
					Integer32,
				hwhqosQueueForwardPackets
					Counter64,
				hwhqosQueueForwardBytes
					Counter64,
				hwhqosQueueDropPackets
					Counter64,
				hwhqosQueueDropBytes
					Counter64,
				hwhqosQueueRemarkPackets
					Counter64,
				hwhqosQueueRemarkBytes
					Counter64,
				hwhqosSetZero
					INTEGER,
				hwhqosQueueForwardPacketRate
					Counter64,
				hwhqosQueueForwardByteRate
					Counter64,
				hwhqosQueueDropPacketRate
					Counter64,
				hwhqosQueueDropByteRate
					Counter64
			 }

-- 1.3.6.1.4.1.2011.5.25.132.1.1.1.1
		hwhqosIfIndex OBJECT-TYPE
			SYNTAX Integer32 (0..2147483647)
			MAX-ACCESS not-accessible
			STATUS current
			DESCRIPTION
				"The value of this object identifies the index of an interface. The interface can be a physical interface or a logical interface.
				"
			::= { hwhqosIfStatEntry 1 }
		
-- 1.3.6.1.4.1.2011.5.25.132.1.1.1.2
		hwhqosDirection OBJECT-TYPE
			SYNTAX INTEGER
				{
				inbound(1),
				outbound(2),
				absent(255)
				}
			MAX-ACCESS not-accessible
			STATUS current
			DESCRIPTION
				"The value of this object identifies the incoming and outgoing directions. The object can be set to 0 when the direction is not specified.
				"
			::= { hwhqosIfStatEntry 2 }
		
-- 1.3.6.1.4.1.2011.5.25.132.1.1.1.3
		hwhqosUserLayer1 OBJECT-TYPE
			SYNTAX Integer32 (0..2147483647)
			MAX-ACCESS not-accessible
			STATUS current
			DESCRIPTION
				"The value of this object identifies the outer identifier of a user group.
				"
			::= { hwhqosIfStatEntry 3 }
		
-- 1.3.6.1.4.1.2011.5.25.132.1.1.1.4
		hwhqosUserLayer2 OBJECT-TYPE
			SYNTAX Integer32 (0..2147483647)
			MAX-ACCESS not-accessible
			STATUS current
			DESCRIPTION
				"The value of this object identifies the outer identifier of a user.
				"
			::= { hwhqosIfStatEntry 4 }
		
-- 1.3.6.1.4.1.2011.5.25.132.1.1.1.5
		hwhqosQueueIndex OBJECT-TYPE
			SYNTAX Integer32 (0..2147483647)
			MAX-ACCESS not-accessible
			STATUS current
			DESCRIPTION
				"The value of this object identifies the queue index of a user. Each user has multiple queues and the index indicates the queues for each user.
				Each user of the NE40E has eight queues.
				If this object does not exist, you can set it to 0.
				                "
			::= { hwhqosIfStatEntry 5 }
		
-- 1.3.6.1.4.1.2011.5.25.132.1.1.1.6
		hwhqosQueueForwardPackets OBJECT-TYPE
			SYNTAX Counter64
			MAX-ACCESS read-only
			STATUS current
			DESCRIPTION
				"The value of this object identifies the packets forwarded in the queue. If this object is not supported, fill 0.
				"
			::= { hwhqosIfStatEntry 6 }
		
-- 1.3.6.1.4.1.2011.5.25.132.1.1.1.7
		hwhqosQueueForwardBytes OBJECT-TYPE
			SYNTAX Counter64
			MAX-ACCESS read-only
			STATUS current
			DESCRIPTION
				"The value of this object identifies the bytes forwarded in the queue. If this object is not supported, fill 0.
				"
			::= { hwhqosIfStatEntry 7 }
		
-- 1.3.6.1.4.1.2011.5.25.132.1.1.1.8
		hwhqosQueueDropPackets OBJECT-TYPE
			SYNTAX Counter64
			MAX-ACCESS read-only
			STATUS current
			DESCRIPTION
				"This object indicates the number of packets discarded from the queue. If this object is not supported, fill 0.
				"
			::= { hwhqosIfStatEntry 8 }
		
-- 1.3.6.1.4.1.2011.5.25.132.1.1.1.9
		hwhqosQueueDropBytes OBJECT-TYPE
			SYNTAX Counter64
			MAX-ACCESS read-only
			STATUS current
			DESCRIPTION
				"This object indicates the number of bytes discarded from the queue. If this object is not supported, fill 0.
				"
			::= { hwhqosIfStatEntry 9 }
		
-- 1.3.6.1.4.1.2011.5.25.132.1.1.1.10
		hwhqosQueueRemarkPackets OBJECT-TYPE
			SYNTAX Counter64
			MAX-ACCESS read-only
			STATUS current
			DESCRIPTION
				"RemarkPackets number of queue.
				if not support, please fill 0.
				"
			::= { hwhqosIfStatEntry 10 }
		
-- 1.3.6.1.4.1.2011.5.25.132.1.1.1.11
		hwhqosQueueRemarkBytes OBJECT-TYPE
			SYNTAX Counter64
			MAX-ACCESS read-only
			STATUS current
			DESCRIPTION
				"RemarkBytes number of queue.
				if not support, please fill 0.
				"
			::= { hwhqosIfStatEntry 11 }
		
-- 1.3.6.1.4.1.2011.5.25.132.1.1.1.12
		hwhqosSetZero OBJECT-TYPE
			SYNTAX INTEGER { setZero(1) }
			MAX-ACCESS read-write
			STATUS current
			DESCRIPTION
				"This object indicates that the statistics are cleared."
			::= { hwhqosIfStatEntry 12 }
		
-- 1.3.6.1.4.1.2011.5.25.132.1.1.1.13
		hwhqosQueueForwardPacketRate OBJECT-TYPE
			SYNTAX Counter64
			MAX-ACCESS read-only
			STATUS current
			DESCRIPTION
				"This object indicates the packet forwarding rate in the queue, in pps."
			::= { hwhqosIfStatEntry 13 }
		
-- 1.3.6.1.4.1.2011.5.25.132.1.1.1.14
		hwhqosQueueForwardByteRate OBJECT-TYPE
			SYNTAX Counter64
			MAX-ACCESS read-only
			STATUS current
			DESCRIPTION
				"This object indicates the byte forwarding rate in the queue, in bps."
			::= { hwhqosIfStatEntry 14 }
		
-- 1.3.6.1.4.1.2011.5.25.132.1.1.1.15
		hwhqosQueueDropPacketRate OBJECT-TYPE
			SYNTAX Counter64
			MAX-ACCESS read-only
			STATUS current
			DESCRIPTION
				"This object indicates the packet discarding rate in the queue, in pps."
			::= { hwhqosIfStatEntry 15 }
		
-- 1.3.6.1.4.1.2011.5.25.132.1.1.1.16
		hwhqosQueueDropByteRate OBJECT-TYPE
			SYNTAX Counter64
			MAX-ACCESS read-only
			STATUS current
			DESCRIPTION
				"This object indicates the byte discarding rate in the queue, in bps."
			::= { hwhqosIfStatEntry 16 }
		
--                 ATM PVC table
-- 1.3.6.1.4.1.2011.5.25.132.1.2
		hwhqosAtmPvcStatTable OBJECT-TYPE
			SYNTAX SEQUENCE OF HwhqosAtmPvcStatEntry
			MAX-ACCESS not-accessible
			STATUS current
			DESCRIPTION
				"Table of Hierarchy QoS's statistic information."
			::= { hwhqosStat 2 }
		
-- 1.3.6.1.4.1.2011.5.25.132.1.2.1
		hwhqosAtmPvcStatEntry OBJECT-TYPE
			SYNTAX HwhqosAtmPvcStatEntry
			MAX-ACCESS not-accessible
			STATUS current
			DESCRIPTION
				"The table have multilevel index
				if don't have some or other index. please fill the MAX value 2147483647
				for example : MA52 don't have statistic of user's queue, but have statistic of user.
				              please set QueueIndex the MAX value 2147483647.
				"
			INDEX { hwhqosAtmPvcIfIndex, hwhqosAtmPvcVPI, hwhqosAtmPvcVCI, hwhqosAtmPvcDirection, hwhqosAtmPvcUserLayer1, 
				hwhqosAtmPvcUserLayer2, hwhqosAtmPvcQueueIndex }
			::= { hwhqosAtmPvcStatTable 1 }
		
		HwhqosAtmPvcStatEntry ::=
			SEQUENCE { 
				hwhqosAtmPvcIfIndex
					Integer32,
				hwhqosAtmPvcVPI
					Integer32,
				hwhqosAtmPvcVCI
					Integer32,
				hwhqosAtmPvcDirection
					INTEGER,
				hwhqosAtmPvcUserLayer1
					Integer32,
				hwhqosAtmPvcUserLayer2
					Integer32,
				hwhqosAtmPvcQueueIndex
					Integer32,
				hwhqosAtmPvcQueueForwardPackets
					Counter64,
				hwhqosAtmPvcQueueForwardBytes
					Counter64,
				hwhqosAtmPvcQueueDropPackets
					Counter64,
				hwhqosAtmPvcQueueDropBytes
					Counter64,
				hwhqosAtmPvcQueueRemarkPackets
					Counter64,
				hwhqosAtmPvcQueueRemarkBytes
					Counter64
			 }

-- 1.3.6.1.4.1.2011.5.25.132.1.2.1.1
		hwhqosAtmPvcIfIndex OBJECT-TYPE
			SYNTAX Integer32 (0..2147483647)
			MAX-ACCESS not-accessible
			STATUS current
			DESCRIPTION
				"ATM interfaceindex.
				"
			::= { hwhqosAtmPvcStatEntry 1 }
		
-- 1.3.6.1.4.1.2011.5.25.132.1.2.1.2
		hwhqosAtmPvcVPI OBJECT-TYPE
			SYNTAX Integer32 (0..2147483647)
			MAX-ACCESS not-accessible
			STATUS current
			DESCRIPTION
				"VPI NUMBER.
				"
			::= { hwhqosAtmPvcStatEntry 2 }
		
-- 1.3.6.1.4.1.2011.5.25.132.1.2.1.3
		hwhqosAtmPvcVCI OBJECT-TYPE
			SYNTAX Integer32 (0..2147483647)
			MAX-ACCESS not-accessible
			STATUS current
			DESCRIPTION
				"VCI NUMBER.
				"
			::= { hwhqosAtmPvcStatEntry 3 }
		
-- 1.3.6.1.4.1.2011.5.25.132.1.2.1.4
		hwhqosAtmPvcDirection OBJECT-TYPE
			SYNTAX INTEGER
				{
				inbound(1),
				outbound(2),
				absent(255)
				}
			MAX-ACCESS not-accessible
			STATUS current
			DESCRIPTION
				"Direction: inbound;outbound.
				if don't have, please fill 255.
				"
			::= { hwhqosAtmPvcStatEntry 4 }
		
-- 1.3.6.1.4.1.2011.5.25.132.1.2.1.5
		hwhqosAtmPvcUserLayer1 OBJECT-TYPE
			SYNTAX Integer32 (0..2147483647)
			MAX-ACCESS not-accessible
			STATUS current
			DESCRIPTION
				"Usergroupid: just the Usergroup's configure sequence
				Usergroupname is identifier in Hierarchy QoS.
				"
			::= { hwhqosAtmPvcStatEntry 5 }
		
-- 1.3.6.1.4.1.2011.5.25.132.1.2.1.6
		hwhqosAtmPvcUserLayer2 OBJECT-TYPE
			SYNTAX Integer32 (0..2147483647)
			MAX-ACCESS not-accessible
			STATUS current
			DESCRIPTION
				"Userid: just the User's configure sequence
				Username is identifier in Hierarchy QoS.
				"
			::= { hwhqosAtmPvcStatEntry 6 }
		
-- 1.3.6.1.4.1.2011.5.25.132.1.2.1.7
		hwhqosAtmPvcQueueIndex OBJECT-TYPE
			SYNTAX Integer32 (0..2147483647)
			MAX-ACCESS not-accessible
			STATUS current
			DESCRIPTION
				"index of user's queue.
				8031: everyuser have 4 queues
				MA52: everyuser have 8 queues
				8090: everyuser have 8 queues
				
				if don't have, please fill 0.
				"
			::= { hwhqosAtmPvcStatEntry 7 }
		
-- 1.3.6.1.4.1.2011.5.25.132.1.2.1.8
		hwhqosAtmPvcQueueForwardPackets OBJECT-TYPE
			SYNTAX Counter64
			MAX-ACCESS read-only
			STATUS current
			DESCRIPTION
				"ForwardPackets number of queue.
				if not support, please fill 0.
				"
			::= { hwhqosAtmPvcStatEntry 8 }
		
-- 1.3.6.1.4.1.2011.5.25.132.1.2.1.9
		hwhqosAtmPvcQueueForwardBytes OBJECT-TYPE
			SYNTAX Counter64
			MAX-ACCESS read-only
			STATUS current
			DESCRIPTION
				"ForwardBytes number of queue.
				if not support, please fill 0.
				"
			::= { hwhqosAtmPvcStatEntry 9 }
		
-- 1.3.6.1.4.1.2011.5.25.132.1.2.1.10
		hwhqosAtmPvcQueueDropPackets OBJECT-TYPE
			SYNTAX Counter64
			MAX-ACCESS read-only
			STATUS current
			DESCRIPTION
				"DropPackets number of queue.
				if not support, please fill 0.
				"
			::= { hwhqosAtmPvcStatEntry 10 }
		
-- 1.3.6.1.4.1.2011.5.25.132.1.2.1.11
		hwhqosAtmPvcQueueDropBytes OBJECT-TYPE
			SYNTAX Counter64
			MAX-ACCESS read-only
			STATUS current
			DESCRIPTION
				"DropBytes number of queue.
				if not support, please fill 0.
				"
			::= { hwhqosAtmPvcStatEntry 11 }
		
-- 1.3.6.1.4.1.2011.5.25.132.1.2.1.12
		hwhqosAtmPvcQueueRemarkPackets OBJECT-TYPE
			SYNTAX Counter64
			MAX-ACCESS read-only
			STATUS current
			DESCRIPTION
				"RemarkPackets number of queue.
				if not support, please fill 0.
				"
			::= { hwhqosAtmPvcStatEntry 12 }
		
-- 1.3.6.1.4.1.2011.5.25.132.1.2.1.13
		hwhqosAtmPvcQueueRemarkBytes OBJECT-TYPE
			SYNTAX Counter64
			MAX-ACCESS read-only
			STATUS current
			DESCRIPTION
				"RemarkBytes number of queue.
				if not support, please fill 0.
				"
			::= { hwhqosAtmPvcStatEntry 13 }
		
-- 1.3.6.1.4.1.2011.5.25.132.1.3
		hwhqosPortQueueTable OBJECT-TYPE
			SYNTAX SEQUENCE OF HwhqosPortQueueEntry
			MAX-ACCESS not-accessible
			STATUS current
			DESCRIPTION
				"Table of configuration about a port-queue."
			::= { hwhqosStat 3 }
		
-- 1.3.6.1.4.1.2011.5.25.132.1.3.1
		hwhqosPortQueueEntry OBJECT-TYPE
			SYNTAX HwhqosPortQueueEntry
			MAX-ACCESS not-accessible
			STATUS current
			DESCRIPTION
				"Information about configuration of an interface cos-queue."
			INDEX { hwhqosPortQueueIfIndex, hwhqosPortQueueCosValue }
			::= { hwhqosPortQueueTable 1 }
		
		HwhqosPortQueueEntry ::=
			SEQUENCE { 
				hwhqosPortQueueIfIndex
					Integer32,
				hwhqosPortQueueCosValue
					INTEGER,
				hwhqosPortQueueArithmetic
					INTEGER,
				hwhqosPortQueueWeightValue
					Integer32,
				hwhqosPortQueueShaValue
					Unsigned32,              
				hwhqosPortQueueShaPercent
					Integer32,
				hwhqosPortQueueWredName
					OCTET STRING,
				hwhqosPortQueuePbsValue
					Integer32,
				hwhqosPortQueueRowStatus
					RowStatus
			 }

-- 1.3.6.1.4.1.2011.5.25.132.1.3.1.1
		hwhqosPortQueueIfIndex OBJECT-TYPE
			SYNTAX Integer32 (0..2147483647)
			MAX-ACCESS read-only
			STATUS current
			DESCRIPTION
				"The value of this object identifies the index of a physical port.The value ranges from 0 to 2147483647."
			::= { hwhqosPortQueueEntry 1 }
		
-- 1.3.6.1.4.1.2011.5.25.132.1.3.1.2
		hwhqosPortQueueCosValue OBJECT-TYPE
			SYNTAX INTEGER
				{
				portqueueBE(1),
				portqueueAF1(2),
				portqueueAF2(3),
				portqueueAF3(4),
				portqueueAF4(5),
				portqueueEF(6),
				portqueueCS6(7),
				portqueueCS7(8)
				}
			MAX-ACCESS read-only
			STATUS current
			DESCRIPTION
				"The value of this object identifies the queue type.The value can be any of the following:
				portqueueBE(1)
				portqueueAF1(2)
				portqueueAF2(3)
				portqueueAF3(4)
				portqueueAF4(5)
				portqueueEF(6)
				portqueueCS6(7)
				portqueueCS7(8)
				"
			::= { hwhqosPortQueueEntry 2 }
		
-- 1.3.6.1.4.1.2011.5.25.132.1.3.1.11
		hwhqosPortQueueArithmetic OBJECT-TYPE
			SYNTAX INTEGER
				{
				portqueuePQ(1),
				portqueueWFQ(2),
				portqueueLPQ(3)
				}
			MAX-ACCESS read-create
			STATUS current
			DESCRIPTION
				"The value of this object identifies the queue scheduling arithmetic.
				The value can be any of the following:
				portqueuePQ(1)
				portqueueWFQ(2)
				portqueueLPQ(3)"
			::= { hwhqosPortQueueEntry 11 }
		
-- 1.3.6.1.4.1.2011.5.25.132.1.3.1.12
		hwhqosPortQueueWeightValue OBJECT-TYPE
			SYNTAX Integer32
			MAX-ACCESS read-create
			STATUS current
			DESCRIPTION
				"The value of this object identifies the weight of the Weighted Fair Queuing (WFQ) scheduling arithmetic."
			::= { hwhqosPortQueueEntry 12 }
		
-- 1.3.6.1.4.1.2011.5.25.132.1.3.1.13
		hwhqosPortQueueShaValue OBJECT-TYPE
	                                           SYNTAX Unsigned32            
			MAX-ACCESS read-create
			STATUS current
			DESCRIPTION
				"The value of this object identifies the bandwidth allocated to the queue."
			::= { hwhqosPortQueueEntry 13 }
		
-- 1.3.6.1.4.1.2011.5.25.132.1.3.1.14
		hwhqosPortQueueShaPercent OBJECT-TYPE
			SYNTAX Integer32
			MAX-ACCESS read-create
			STATUS current
			DESCRIPTION
				"The value of this object identifies the proportion of the queue bandwidth to the bandwidth of the port."
			::= { hwhqosPortQueueEntry 14 }
		
-- 1.3.6.1.4.1.2011.5.25.132.1.3.1.15
		hwhqosPortQueueWredName OBJECT-TYPE
			SYNTAX OCTET STRING (SIZE (1..31))
			MAX-ACCESS read-create
			STATUS current
			DESCRIPTION
				"This object indicates the name of the Weighted Random Early Detection (WRED) template.
				The object is a string of 1 to 31 characters."
			::= { hwhqosPortQueueEntry 15 }
		
-- 1.3.6.1.4.1.2011.5.25.132.1.3.1.16
		hwhqosPortQueuePbsValue OBJECT-TYPE
			SYNTAX Integer32 (1..262144)
			MAX-ACCESS read-create
			STATUS current
			DESCRIPTION
				"The object specifies the value of the port-queue specific queue pbs."
			::= { hwhqosPortQueueEntry 16 }
		
-- 1.3.6.1.4.1.2011.5.25.132.1.3.1.51
		hwhqosPortQueueRowStatus OBJECT-TYPE
			SYNTAX RowStatus
			MAX-ACCESS read-create
			STATUS current
			DESCRIPTION
				"This object indicates the row status."
			::= { hwhqosPortQueueEntry 51 }
		
-- 1.3.6.1.4.1.2011.5.25.132.1.4
		hwhqosWredTable OBJECT-TYPE
			SYNTAX SEQUENCE OF HwhqosWredEntry
			MAX-ACCESS not-accessible
			STATUS current
			DESCRIPTION
				"Table of configuration about a wred template."
			::= { hwhqosStat 4 }
		
-- 1.3.6.1.4.1.2011.5.25.132.1.4.1
		hwhqosWredEntry OBJECT-TYPE
			SYNTAX HwhqosWredEntry
			MAX-ACCESS not-accessible
			STATUS current
			DESCRIPTION
				"Information about configuration of the value of wred color ."
			INDEX { hwhqosWredName }
			::= { hwhqosWredTable 1 }
		
		HwhqosWredEntry ::=
			SEQUENCE { 
				hwhqosWredName
					OCTET STRING,
				hwhqosWredGreenLowLimit
					Integer32,
				hwhqosWredGreenHighLimit
					Integer32,
				hwhqosWredGreenDiscardPercent
					Integer32,
				hwhqosWredYellowLowLimit
					Integer32,
				hwhqosWredYellowHighLimit
					Integer32,
				hwhqosWredYellowDiscardPercent
					Integer32,
				hwhqosWredRedLowLimit
					Integer32,
				hwhqosWredRedHighLimit
					Integer32,
				hwhqosWredRedDiscardPercent
					Integer32,
				hwhqosWredRowStatus
					RowStatus
			 }

-- 1.3.6.1.4.1.2011.5.25.132.1.4.1.1
		hwhqosWredName OBJECT-TYPE
			SYNTAX OCTET STRING (SIZE (1..31))
			MAX-ACCESS not-accessible
			STATUS current
			DESCRIPTION
				"The value of this object identifies the name of the WRED template.
				The object is a string of 1 to 31 characters."
			::= { hwhqosWredEntry 1 }
		
-- 1.3.6.1.4.1.2011.5.25.132.1.4.1.11
		hwhqosWredGreenLowLimit OBJECT-TYPE
			SYNTAX Integer32
			MAX-ACCESS read-create
			STATUS current
			DESCRIPTION
				"The value of this object identifies the lower threshold of the green port queue."
			::= { hwhqosWredEntry 11 }
		
-- 1.3.6.1.4.1.2011.5.25.132.1.4.1.12
		hwhqosWredGreenHighLimit OBJECT-TYPE
			SYNTAX Integer32
			MAX-ACCESS read-create
			STATUS current
			DESCRIPTION
				"The value of this object identifies the upper threshold of the green port queue."
			::= { hwhqosWredEntry 12 }
		
-- 1.3.6.1.4.1.2011.5.25.132.1.4.1.13
		hwhqosWredGreenDiscardPercent OBJECT-TYPE
			SYNTAX Integer32
			MAX-ACCESS read-create
			STATUS current
			DESCRIPTION
				"The value of this object identifies the packet loss ratio between the upper threshold and the lower threshold of the green port queue."
			::= { hwhqosWredEntry 13 }
		
-- 1.3.6.1.4.1.2011.5.25.132.1.4.1.14
		hwhqosWredYellowLowLimit OBJECT-TYPE
			SYNTAX Integer32
			MAX-ACCESS read-create
			STATUS current
			DESCRIPTION
				"The value of this object identifies the lower threshold of the yellow port queue."
			::= { hwhqosWredEntry 14 }
		
-- 1.3.6.1.4.1.2011.5.25.132.1.4.1.15
		hwhqosWredYellowHighLimit OBJECT-TYPE
			SYNTAX Integer32
			MAX-ACCESS read-create
			STATUS current
			DESCRIPTION
				"The value of this object identifies the upper threshold of the yellow port queue."
			::= { hwhqosWredEntry 15 }
		
-- 1.3.6.1.4.1.2011.5.25.132.1.4.1.16
		hwhqosWredYellowDiscardPercent OBJECT-TYPE
			SYNTAX Integer32
			MAX-ACCESS read-create
			STATUS current
			DESCRIPTION
				"The value of this object identifies the packet loss ratio between the upper threshold and the lower threshold of the yellow port queue."
			::= { hwhqosWredEntry 16 }
		
-- 1.3.6.1.4.1.2011.5.25.132.1.4.1.17
		hwhqosWredRedLowLimit OBJECT-TYPE
			SYNTAX Integer32
			MAX-ACCESS read-create
			STATUS current
			DESCRIPTION
				"The value of this object identifies the lower threshold of the red port queue."
			::= { hwhqosWredEntry 17 }
		
-- 1.3.6.1.4.1.2011.5.25.132.1.4.1.18
		hwhqosWredRedHighLimit OBJECT-TYPE
			SYNTAX Integer32
			MAX-ACCESS read-create
			STATUS current
			DESCRIPTION
				"The value of this object identifies the upper threshold of the red port queue."
			::= { hwhqosWredEntry 18 }
		
-- 1.3.6.1.4.1.2011.5.25.132.1.4.1.19
		hwhqosWredRedDiscardPercent OBJECT-TYPE
			SYNTAX Integer32
			MAX-ACCESS read-create
			STATUS current
			DESCRIPTION
				"The value of this object identifies the packet loss ratio between the upper threshold and the lower threshold of the red port queue."
			::= { hwhqosWredEntry 19 }
		
-- 1.3.6.1.4.1.2011.5.25.132.1.4.1.51
		hwhqosWredRowStatus OBJECT-TYPE
			SYNTAX RowStatus
			MAX-ACCESS read-create
			STATUS current
			DESCRIPTION
				"This object indicates the row status."
			::= { hwhqosWredEntry 51 }
		
-- 1.3.6.1.4.1.2011.5.25.132.1.5
		hwhqosIfQueueStatTable OBJECT-TYPE
			SYNTAX SEQUENCE OF HwhqosIfQueueStatEntry
			MAX-ACCESS not-accessible
			STATUS current
			DESCRIPTION
				"Interface queue statistic table."
			::= { hwhqosStat 5 }
		
-- 1.3.6.1.4.1.2011.5.25.132.1.5.1
		hwhqosIfQueueStatEntry OBJECT-TYPE
			SYNTAX HwhqosIfQueueStatEntry
			MAX-ACCESS not-accessible
			STATUS current
			DESCRIPTION
				"Interface Queue statistic table entry."
			INDEX { hwhqosIfQueueStatIfIndex, hwhqosIfQueueStatQueueIndex, hwhqosIfQueueStatDirection }
			::= { hwhqosIfQueueStatTable 1 }
		
		HwhqosIfQueueStatEntry ::=
			SEQUENCE { 
				hwhqosIfQueueStatIfIndex
					InterfaceIndex,
				hwhqosIfQueueStatQueueIndex
					INTEGER,
				hwhqosIfQueueStatDirection
					INTEGER,
				hwhqosIfQueueStatForwardPackets
					Counter64,
				hwhqosIfQueueStatForwardBytes
					Counter64,
				hwhqosIfQueueStatDropPackets
					Counter64,
				hwhqosIfQueueStatDropBytes
					Counter64
			 }

-- 1.3.6.1.4.1.2011.5.25.132.1.5.1.1
		hwhqosIfQueueStatIfIndex OBJECT-TYPE
			SYNTAX InterfaceIndex
			MAX-ACCESS not-accessible
			STATUS current
			DESCRIPTION
				"Interface index.    "
			::= { hwhqosIfQueueStatEntry 1 }
		
-- 1.3.6.1.4.1.2011.5.25.132.1.5.1.2
		hwhqosIfQueueStatQueueIndex OBJECT-TYPE
			SYNTAX INTEGER
				{
				be(1),
				af1(2),
				af2(3),
				af3(4),
				af4(5),
				ef(6),
				cs6(7),
				cs7(8)
				}
			MAX-ACCESS not-accessible
			STATUS current
			DESCRIPTION
				"Index number of queues with priority.
				The values and meanings are as follows:
				                1 be
				                2 af1
				                3 af2
				                4 af3
				                5 af4
				                6 ef
				                7 cs6
				                8 cs7
				                "
			::= { hwhqosIfQueueStatEntry 2 }
		
-- 1.3.6.1.4.1.2011.5.25.132.1.5.1.3
		hwhqosIfQueueStatDirection OBJECT-TYPE
			SYNTAX INTEGER
				{
				inbound(1),
				outbound(2)
				}
			MAX-ACCESS not-accessible
			STATUS current
			DESCRIPTION
				"Direction: inbound 1,outbound 2"
			::= { hwhqosIfQueueStatEntry 3 }
		
-- 1.3.6.1.4.1.2011.5.25.132.1.5.1.4
		hwhqosIfQueueStatForwardPackets OBJECT-TYPE
			SYNTAX Counter64
			MAX-ACCESS read-only
			STATUS current
			DESCRIPTION
				"Number of forwarded packets."
			::= { hwhqosIfQueueStatEntry 4 }
		
-- 1.3.6.1.4.1.2011.5.25.132.1.5.1.5
		hwhqosIfQueueStatForwardBytes OBJECT-TYPE
			SYNTAX Counter64
			MAX-ACCESS read-only
			STATUS current
			DESCRIPTION
				"Number of forwarded bytes."
			::= { hwhqosIfQueueStatEntry 5 }
		
-- 1.3.6.1.4.1.2011.5.25.132.1.5.1.6
		hwhqosIfQueueStatDropPackets OBJECT-TYPE
			SYNTAX Counter64
			MAX-ACCESS read-only
			STATUS current
			DESCRIPTION
				"Number of discarded packets."
			::= { hwhqosIfQueueStatEntry 6 }
		
-- 1.3.6.1.4.1.2011.5.25.132.1.5.1.7
		hwhqosIfQueueStatDropBytes OBJECT-TYPE
			SYNTAX Counter64
			MAX-ACCESS read-only
			STATUS current
			DESCRIPTION
				"Number of discarded bytes."
			::= { hwhqosIfQueueStatEntry 7 }
		
-- 1.3.6.1.4.1.2011.5.25.132.1.6
		hwhqosUserQueueStatTable OBJECT-TYPE
			SYNTAX SEQUENCE OF HwhqosUserQueueStatEntry
			MAX-ACCESS not-accessible
			STATUS current
			DESCRIPTION
				"User queue statistic table."
			::= { hwhqosStat 6 }
		
-- 1.3.6.1.4.1.2011.5.25.132.1.6.1
		hwhqosUserQueueStatEntry OBJECT-TYPE
			SYNTAX HwhqosUserQueueStatEntry
			MAX-ACCESS not-accessible
			STATUS current
			DESCRIPTION
				"User Queue statistic table entry"
			INDEX { hwhqosUserQueueStatType, hwhqosUserQueueStatNameString, hwhqosUserQueueStatDirection, hwhqosUserQueueStatQueueIndex }
			::= { hwhqosUserQueueStatTable 1 }
		
		HwhqosUserQueueStatEntry ::=
			SEQUENCE { 
				hwhqosUserQueueStatType
					INTEGER,
				hwhqosUserQueueStatNameString
					OCTET STRING,
				hwhqosUserQueueStatDirection
					INTEGER,
				hwhqosUserQueueStatQueueIndex
					INTEGER,
				hwhqosUserQueueStatForwardPackets
					Counter64,
				hwhqosUserQueueStatForwardBytes
					Counter64,
				hwhqosUserQueueStatDropPackets
					Counter64,
				hwhqosUserQueueStatDropBytes
					Counter64,
				hwhqosUserQueueStatReset
					INTEGER,
				hwhqosUserQueueStatLastResetTime
					TimeTicks,
				hwhqosUserQueueStatPerDropPackets
					Counter64
			 }

-- 1.3.6.1.4.1.2011.5.25.132.1.6.1.1
		hwhqosUserQueueStatType OBJECT-TYPE
			SYNTAX INTEGER
				{
				interface(1),
				mactunel(2),
				userclassifier(3)
				}
			MAX-ACCESS not-accessible
			STATUS current
			DESCRIPTION
				"Types of statistic:
				interface(1),
				mactunel(2),
				userclassifier(3)
				"
			::= { hwhqosUserQueueStatEntry 1 }
		
-- 1.3.6.1.4.1.2011.5.25.132.1.6.1.2
		hwhqosUserQueueStatNameString OBJECT-TYPE
			SYNTAX OCTET STRING
			MAX-ACCESS not-accessible
			STATUS current
			DESCRIPTION
				"Name character string: If the statistic is based on mac-tunnel,
				this field is the name of the mac-tunnel. If the statistic is based
				on user classification, this field is the name of the user
				classification. If the statistic is based on an interface,
				this field is the name of the interface.
				"
			::= { hwhqosUserQueueStatEntry 2 }
		
-- 1.3.6.1.4.1.2011.5.25.132.1.6.1.3
		hwhqosUserQueueStatDirection OBJECT-TYPE
			SYNTAX INTEGER
				{
				inbound(1),
				outbound(2)
				}
			MAX-ACCESS not-accessible
			STATUS current
			DESCRIPTION
				"Direction: If the statistic is based on user classification,
				the direction is divided to upstream (1) and downstream (2). If the
				Statistic is based on mac-tunnel, the direction is applied only on
				the downstream (2)."
			::= { hwhqosUserQueueStatEntry 3 }
		
-- 1.3.6.1.4.1.2011.5.25.132.1.6.1.4
		hwhqosUserQueueStatQueueIndex OBJECT-TYPE
			SYNTAX INTEGER
				{
				be(1),
				af1(2),
				af2(3),
				af3(4),
				af4(5),
				ef(6),
				cs6(7),
				cs7(8),
				total(9)
				}
			MAX-ACCESS not-accessible
			STATUS current
			DESCRIPTION
				"Index number of the queues. The values and meanings are as follows:
				1 be
				2 af1
				3 af2
				4 af3
				5 af4
				6 ef
				7 cs6
				8 cs7
				9 total
				
				"
			::= { hwhqosUserQueueStatEntry 4 }
		
-- 1.3.6.1.4.1.2011.5.25.132.1.6.1.5
		hwhqosUserQueueStatForwardPackets OBJECT-TYPE
			SYNTAX Counter64
			MAX-ACCESS read-only
			STATUS current
			DESCRIPTION
				"The number of packets that pass through."
			::= { hwhqosUserQueueStatEntry 5 }
		
-- 1.3.6.1.4.1.2011.5.25.132.1.6.1.6
		hwhqosUserQueueStatForwardBytes OBJECT-TYPE
			SYNTAX Counter64
			MAX-ACCESS read-only
			STATUS current
			DESCRIPTION
				"The number of bytes that pass through."
			::= { hwhqosUserQueueStatEntry 6 }
		
-- 1.3.6.1.4.1.2011.5.25.132.1.6.1.7
		hwhqosUserQueueStatDropPackets OBJECT-TYPE
			SYNTAX Counter64
			MAX-ACCESS read-only
			STATUS current
			DESCRIPTION
				"The number of discarded packets."
			::= { hwhqosUserQueueStatEntry 7 }
		
-- 1.3.6.1.4.1.2011.5.25.132.1.6.1.8
		hwhqosUserQueueStatDropBytes OBJECT-TYPE
			SYNTAX Counter64
			MAX-ACCESS read-only
			STATUS current
			DESCRIPTION
				"The number of discarded bytes."
			::= { hwhqosUserQueueStatEntry 8 }
		
-- 1.3.6.1.4.1.2011.5.25.132.1.6.1.9
		hwhqosUserQueueStatReset OBJECT-TYPE
			SYNTAX INTEGER { reset(1) }
			MAX-ACCESS read-write
			STATUS current
			DESCRIPTION
				"Counter resetting. If the value is 1, the object resets
				the statistics through the set operation. It is no of use to
				access the value of this object.
				"
			::= { hwhqosUserQueueStatEntry 9 }
		
-- 1.3.6.1.4.1.2011.5.25.132.1.6.1.10
		hwhqosUserQueueStatLastResetTime OBJECT-TYPE
			SYNTAX TimeTicks
			MAX-ACCESS read-only
			STATUS current
			DESCRIPTION
				"The time stamp that the counter is reset last."
			::= { hwhqosUserQueueStatEntry 10 }
		
-- 1.3.6.1.4.1.2011.5.25.132.1.6.1.11
		hwhqosUserQueueStatPerDropPackets OBJECT-TYPE
			SYNTAX Counter64
			MAX-ACCESS read-only
			STATUS current
			DESCRIPTION
				"The number of discarded packets in a certain period."
			::= { hwhqosUserQueueStatEntry 11 }
		
-- 1.3.6.1.4.1.2011.5.25.132.1.7
		hwhqosUserGroupQueueStatTable OBJECT-TYPE
			SYNTAX SEQUENCE OF HwhqosUserGroupQueueStatEntry
			MAX-ACCESS not-accessible
			STATUS current
			DESCRIPTION
				"User group queue statistic table."
			::= { hwhqosStat 7 }
		
-- 1.3.6.1.4.1.2011.5.25.132.1.7.1
		hwhqosUserGroupQueueStatEntry OBJECT-TYPE
			SYNTAX HwhqosUserGroupQueueStatEntry
			MAX-ACCESS not-accessible
			STATUS current
			DESCRIPTION
				"user group queue statistic table entry"
			INDEX { hwhqosUserGroupQueueStatGroupName, hwhqosUserGroupQueueStatDirection }
			::= { hwhqosUserGroupQueueStatTable 1 }
		
		HwhqosUserGroupQueueStatEntry ::=
			SEQUENCE { 
				hwhqosUserGroupQueueStatGroupName
					OCTET STRING,
				hwhqosUserGroupQueueStatDirection
					INTEGER,
				hwhqosUserGroupQueueForwardPackets
					Counter64,
				hwhqosUserGroupQueueForwardBytes
					Counter64,
				hwhqosUserGroupQueueDropPackets
					Counter64,
				hwhqosUserGroupQueueDropBytes
					Counter64,
				hwhqosUserGroupQueueStatReset
					INTEGER,
				hwhqosUserGroupQueueStatLastResetTime
					TimeTicks
			 }

-- 1.3.6.1.4.1.2011.5.25.132.1.7.1.1
		hwhqosUserGroupQueueStatGroupName OBJECT-TYPE
			SYNTAX OCTET STRING
			MAX-ACCESS not-accessible
			STATUS current
			DESCRIPTION
				"User group name.
				"
			::= { hwhqosUserGroupQueueStatEntry 1 }
		
-- 1.3.6.1.4.1.2011.5.25.132.1.7.1.2
		hwhqosUserGroupQueueStatDirection OBJECT-TYPE
			SYNTAX INTEGER
				{
				inbount(1),
				outbound(2)
				}
			MAX-ACCESS not-accessible
			STATUS current
			DESCRIPTION
				"Direction: upstream (1), downstream (2);"
			::= { hwhqosUserGroupQueueStatEntry 2 }
		
-- 1.3.6.1.4.1.2011.5.25.132.1.7.1.3
		hwhqosUserGroupQueueForwardPackets OBJECT-TYPE
			SYNTAX Counter64
			MAX-ACCESS read-only
			STATUS current
			DESCRIPTION
				"The number of packets that pass through."
			::= { hwhqosUserGroupQueueStatEntry 3 }
		
-- 1.3.6.1.4.1.2011.5.25.132.1.7.1.4
		hwhqosUserGroupQueueForwardBytes OBJECT-TYPE
			SYNTAX Counter64
			MAX-ACCESS read-only
			STATUS current
			DESCRIPTION
				"The number of bytes that pass through."
			::= { hwhqosUserGroupQueueStatEntry 4 }
		
-- 1.3.6.1.4.1.2011.5.25.132.1.7.1.5
		hwhqosUserGroupQueueDropPackets OBJECT-TYPE
			SYNTAX Counter64
			MAX-ACCESS read-only
			STATUS current
			DESCRIPTION
				"The number of discarded packets."
			::= { hwhqosUserGroupQueueStatEntry 5 }
		
-- 1.3.6.1.4.1.2011.5.25.132.1.7.1.6
		hwhqosUserGroupQueueDropBytes OBJECT-TYPE
			SYNTAX Counter64
			MAX-ACCESS read-only
			STATUS current
			DESCRIPTION
				"The number of discarded bytes."
			::= { hwhqosUserGroupQueueStatEntry 6 }
		
-- 1.3.6.1.4.1.2011.5.25.132.1.7.1.7
		hwhqosUserGroupQueueStatReset OBJECT-TYPE
			SYNTAX INTEGER { reset(1) }
			MAX-ACCESS read-write
			STATUS current
			DESCRIPTION
				"Counter resetting. If the value is reset(1), the object resets
				the statistics through the set operation. It is no of use to
				access the value of this object."
			::= { hwhqosUserGroupQueueStatEntry 7 }
		
-- 1.3.6.1.4.1.2011.5.25.132.1.7.1.8
		hwhqosUserGroupQueueStatLastResetTime OBJECT-TYPE
			SYNTAX TimeTicks
			MAX-ACCESS read-only
			STATUS current
			DESCRIPTION
				"The time stamp that the counter is reset last."
			::= { hwhqosUserGroupQueueStatEntry 8 }
		
-- 1.3.6.1.4.1.2011.5.25.132.1.8
		hwVPNHQoSTunnelStatisticsTable OBJECT-TYPE
			SYNTAX SEQUENCE OF HwVPNHQoSTunnelStatisticsEntry
			MAX-ACCESS not-accessible
			STATUS current
			DESCRIPTION
				"VPN qos tunnel statistic table."
			::= { hwhqosStat 8 }
		
-- 1.3.6.1.4.1.2011.5.25.132.1.8.1
		hwVPNHQoSTunnelStatisticsEntry OBJECT-TYPE
			SYNTAX HwVPNHQoSTunnelStatisticsEntry
			MAX-ACCESS not-accessible
			STATUS current
			DESCRIPTION
				"VPN qos tunnel statistic table entry: L3VPN,VPLS and VLL are all supported. "
			INDEX { hwVPNHQoSTunnelIfIndex, hwVPNHQoSVPNType, hwVPNHQoSVPNValue }
			::= { hwVPNHQoSTunnelStatisticsTable 1 }
		
		HwVPNHQoSTunnelStatisticsEntry ::=
			SEQUENCE { 
				hwVPNHQoSTunnelIfIndex
					Integer32,
				hwVPNHQoSVPNType
					Integer32,
				hwVPNHQoSVPNValue
					OCTET STRING,
				hwVPNHQoSPassBytes
					Counter64,
				hwVPNHQoSPassPackets
					Counter64,
				hwVPNHQoSDropPackets
					Counter64,
				hwVPNHQoSDropBytes
					Counter64
			 }

-- 1.3.6.1.4.1.2011.5.25.132.1.8.1.1
		hwVPNHQoSTunnelIfIndex OBJECT-TYPE
			SYNTAX Integer32
			MAX-ACCESS read-only
			STATUS current
			DESCRIPTION
				"VPN Tunnel interface index."
			::= { hwVPNHQoSTunnelStatisticsEntry 1 }
		
-- 1.3.6.1.4.1.2011.5.25.132.1.8.1.2
		hwVPNHQoSVPNType OBJECT-TYPE
			SYNTAX Integer32 (0..3)
			MAX-ACCESS read-only
			STATUS current
			DESCRIPTION
				"VPN Type: Tunnel (0), L3VPN (1), VPLS (2), VLL(3);"
			::= { hwVPNHQoSTunnelStatisticsEntry 2 }
		
-- 1.3.6.1.4.1.2011.5.25.132.1.8.1.3
		hwVPNHQoSVPNValue OBJECT-TYPE
			SYNTAX OCTET STRING
			MAX-ACCESS read-only
			STATUS current
			DESCRIPTION
				"Name of VPN Instance."
			::= { hwVPNHQoSTunnelStatisticsEntry 3 }
		
-- 1.3.6.1.4.1.2011.5.25.132.1.8.1.4
		hwVPNHQoSPassBytes OBJECT-TYPE
			SYNTAX Counter64
			MAX-ACCESS read-only
			STATUS current
			DESCRIPTION
				"The number of bytes that pass through."
			::= { hwVPNHQoSTunnelStatisticsEntry 4 }
		
-- 1.3.6.1.4.1.2011.5.25.132.1.8.1.5
		hwVPNHQoSPassPackets OBJECT-TYPE
			SYNTAX Counter64
			MAX-ACCESS read-only
			STATUS current
			DESCRIPTION
				"The number of packets that pass through."
			::= { hwVPNHQoSTunnelStatisticsEntry 5 }
		
-- 1.3.6.1.4.1.2011.5.25.132.1.8.1.6
		hwVPNHQoSDropPackets OBJECT-TYPE
			SYNTAX Counter64
			MAX-ACCESS read-only
			STATUS current
			DESCRIPTION
				"The number of discarded packets."
			::= { hwVPNHQoSTunnelStatisticsEntry 6 }
		
-- 1.3.6.1.4.1.2011.5.25.132.1.8.1.7
		hwVPNHQoSDropBytes OBJECT-TYPE
			SYNTAX Counter64
			MAX-ACCESS read-only
			STATUS current
			DESCRIPTION
				" The number of discarded bytes."
			::= { hwVPNHQoSTunnelStatisticsEntry 7 }
		
-- 1.3.6.1.4.1.2011.5.25.132.1.9
		hwhqosTunnelStatisticsTable OBJECT-TYPE
			SYNTAX SEQUENCE OF HwhqosTunnelStatisticsEntry
			MAX-ACCESS not-accessible
			STATUS current
			DESCRIPTION
				"Tunnel statistic table."
			::= { hwhqosStat 9 }
		
-- 1.3.6.1.4.1.2011.5.25.132.1.9.1
		hwhqosTunnelStatisticsEntry OBJECT-TYPE
			SYNTAX HwhqosTunnelStatisticsEntry
			MAX-ACCESS not-accessible
			STATUS current
			DESCRIPTION
				"Tunnel statistic table entry: L3VPN,VPLS and VLL are all supported. "
			INDEX { hwhqosTunnelIfIndex, hwhqosTunnelCosType, hwhqosTunnelVPNType, hwhqosTunnelVPNName }
			::= { hwhqosTunnelStatisticsTable 1 }
		
		HwhqosTunnelStatisticsEntry ::=
			SEQUENCE { 
				hwhqosTunnelIfIndex
					Integer32,
				hwhqosTunnelCosType
					CosType,
				hwhqosTunnelVPNType
					Integer32,
				hwhqosTunnelVPNName
					OCTET STRING,
				hwhqosTunnelPassBytes
					Counter64,
				hwhqosTunnelPassPackets
					Counter64,
				hwhqosTunnelDropBytes
					Counter64,
				hwhqosTunnelDropPackets
					Counter64,
				hwhqosTunnelPassedByteRate
					Counter64,
				hwhqosTunnelPassPacketRate
					Counter64
			 }

-- 1.3.6.1.4.1.2011.5.25.132.1.9.1.1
		hwhqosTunnelIfIndex OBJECT-TYPE
			SYNTAX Integer32
			MAX-ACCESS read-only
			STATUS current
			DESCRIPTION
				"Tunnel interface index."
			::= { hwhqosTunnelStatisticsEntry 1 }
		
-- 1.3.6.1.4.1.2011.5.25.132.1.9.1.2
		hwhqosTunnelCosType OBJECT-TYPE
			SYNTAX CosType
			MAX-ACCESS read-only
			STATUS current
			DESCRIPTION
				"BE(1) AF1(2) AF2(3) AF3(4) AF4(5) EF(6) CS6(7) CS7(8)"
			::= { hwhqosTunnelStatisticsEntry 2 }
		
-- 1.3.6.1.4.1.2011.5.25.132.1.9.1.3
		hwhqosTunnelVPNType OBJECT-TYPE
			SYNTAX Integer32 (0..3)
			MAX-ACCESS read-only
			STATUS current
			DESCRIPTION
				"VPN Type: Tunnel (0), L3VPN (1), VPLS (2), VLL(3);"
			::= { hwhqosTunnelStatisticsEntry 3 }
		
-- 1.3.6.1.4.1.2011.5.25.132.1.9.1.4
		hwhqosTunnelVPNName OBJECT-TYPE
			SYNTAX OCTET STRING (SIZE (0..31))
			MAX-ACCESS read-only
			STATUS current
			DESCRIPTION
				"Name of VPN Instance."
			::= { hwhqosTunnelStatisticsEntry 4 }
		
-- 1.3.6.1.4.1.2011.5.25.132.1.9.1.5
		hwhqosTunnelPassBytes OBJECT-TYPE
			SYNTAX Counter64
			MAX-ACCESS read-only
			STATUS current
			DESCRIPTION
				"The number of bytes that pass through."
			::= { hwhqosTunnelStatisticsEntry 5 }
		
-- 1.3.6.1.4.1.2011.5.25.132.1.9.1.6
		hwhqosTunnelPassPackets OBJECT-TYPE
			SYNTAX Counter64
			MAX-ACCESS read-only
			STATUS current
			DESCRIPTION
				"The number of packets that pass through."
			::= { hwhqosTunnelStatisticsEntry 6 }
		
-- 1.3.6.1.4.1.2011.5.25.132.1.9.1.7
		hwhqosTunnelDropBytes OBJECT-TYPE
			SYNTAX Counter64
			MAX-ACCESS read-only
			STATUS current
			DESCRIPTION
				" The number of discarded bytes."
			::= { hwhqosTunnelStatisticsEntry 7 }
		
-- 1.3.6.1.4.1.2011.5.25.132.1.9.1.8
		hwhqosTunnelDropPackets OBJECT-TYPE
			SYNTAX Counter64
			MAX-ACCESS read-only
			STATUS current
			DESCRIPTION
				"The number of discarded packets."
			::= { hwhqosTunnelStatisticsEntry 8 }
		
-- 1.3.6.1.4.1.2011.5.25.132.1.9.1.9
		hwhqosTunnelPassedByteRate OBJECT-TYPE
			SYNTAX Counter64
			MAX-ACCESS read-only
			STATUS current
			DESCRIPTION
				"Rate of bytes passed of enqueue. Unit: Bps"
			::= { hwhqosTunnelStatisticsEntry 9 }
		
-- 1.3.6.1.4.1.2011.5.25.132.1.9.1.10
		hwhqosTunnelPassPacketRate OBJECT-TYPE
			SYNTAX Counter64
			MAX-ACCESS read-only
			STATUS current
			DESCRIPTION
				"Rate of packets passed of enqueue. Unit: pps"
			::= { hwhqosTunnelStatisticsEntry 10 }
		
--******************************************************************
-- 
-- hwhqosProfileTable
-- 
-- ******************************************************************
-- 1.3.6.1.4.1.2011.5.25.132.1.10
		hwhqosProfileTable OBJECT-TYPE
			SYNTAX SEQUENCE OF HwhqosProfileEntry
			MAX-ACCESS not-accessible
			STATUS current
			DESCRIPTION
				" hwhqosProfileTable "
			::= { hwhqosStat 10 }
		
-- 1.3.6.1.4.1.2011.5.25.132.1.10.1
		hwhqosProfileEntry OBJECT-TYPE
			SYNTAX HwhqosProfileEntry
			MAX-ACCESS not-accessible
			STATUS current
			DESCRIPTION
				" hwhqosProfileEntry "
			INDEX { hwhqosProfileName }
			::= { hwhqosProfileTable 1 }
		
		HwhqosProfileEntry ::=
			SEQUENCE { 
				hwhqosProfileName
					OCTET STRING,
				hwhqosProfileDescription
					OCTET STRING,
				hwhqosProfileRowStatus
					RowStatus
			 }

-- 1.3.6.1.4.1.2011.5.25.132.1.10.1.1
-- BEGIN: mod by l00248629, 2014/03/21
		hwhqosProfileName OBJECT-TYPE
                        SYNTAX OCTET STRING (SIZE (1..63))
			MAX-ACCESS read-only
			STATUS current
			DESCRIPTION
				"The value of this object identifies the name of a QoS profile."
			::= { hwhqosProfileEntry 1 }
-- END: mod by l00248629, 2014/03/21
-- 1.3.6.1.4.1.2011.5.25.132.1.10.1.2
		hwhqosProfileDescription OBJECT-TYPE
			SYNTAX OCTET STRING (SIZE (1..63))
			MAX-ACCESS read-create
			STATUS current
			DESCRIPTION
				" hwhqosProfileDescription "
			::= { hwhqosProfileEntry 2 }
		
-- 1.3.6.1.4.1.2011.5.25.132.1.10.1.50
		hwhqosProfileRowStatus OBJECT-TYPE
			SYNTAX RowStatus
			MAX-ACCESS read-create
			STATUS current
			DESCRIPTION
				"This object indicates the row status."
			::= { hwhqosProfileEntry 50 }
		
--******************************************************************
-- 
-- hwhqosProfileSuppressionTable
-- 
-- ******************************************************************
-- 1.3.6.1.4.1.2011.5.25.132.1.11
		hwhqosProfileSuppressionTable OBJECT-TYPE
			SYNTAX SEQUENCE OF HwhqosProfileSuppressionEntry
			MAX-ACCESS not-accessible
			STATUS current
			DESCRIPTION
				" hwhqosProfileSuppressionTable "
			::= { hwhqosStat 11 }
		
-- 1.3.6.1.4.1.2011.5.25.132.1.11.1
		hwhqosProfileSuppressionEntry OBJECT-TYPE
			SYNTAX HwhqosProfileSuppressionEntry
			MAX-ACCESS not-accessible
			STATUS current
			DESCRIPTION
				" hwhqosProfileSuppressionEntry "
			INDEX { hwhqosProfileName, hwhqosSuppressionDirection, hwhqosSuppressionType }
			::= { hwhqosProfileSuppressionTable 1 }
		
		HwhqosProfileSuppressionEntry ::=
			SEQUENCE { 
				hwhqosSuppressionDirection
					INTEGER,
				hwhqosSuppressionType
					INTEGER,
				hwhqosSuppressionCirValue
					Integer32,
				hwhqosSuppressionCbsValue
					Integer32,
				hwhqosSuppressionRowStatus
					RowStatus
			 }

-- 1.3.6.1.4.1.2011.5.25.132.1.11.1.1
		hwhqosSuppressionDirection OBJECT-TYPE
			SYNTAX INTEGER
				{
				inbound(1),
				outbound(2),
				inout(3)
				}
			MAX-ACCESS read-only
			STATUS current
			DESCRIPTION
				"This object indicates the direction where packets are suppressed."
			::= { hwhqosProfileSuppressionEntry 1 }
		
-- 1.3.6.1.4.1.2011.5.25.132.1.11.1.2
		hwhqosSuppressionType OBJECT-TYPE
			SYNTAX INTEGER
				{
				broadcast(1),
				multicast(2),
				unkonwnUnicast(3)
				}
			MAX-ACCESS read-only
			STATUS current
			DESCRIPTION
				"This object indicates the suppression type."
			::= { hwhqosProfileSuppressionEntry 2 }
		
-- 1.3.6.1.4.1.2011.5.25.132.1.11.1.3
		hwhqosSuppressionCirValue OBJECT-TYPE
			SYNTAX Integer32 (100..10000000)
			MAX-ACCESS read-create
			STATUS current
			DESCRIPTION
				"The value of this object identifies the CIR."
			::= { hwhqosProfileSuppressionEntry 3 }
		
-- 1.3.6.1.4.1.2011.5.25.132.1.11.1.4
		hwhqosSuppressionCbsValue OBJECT-TYPE
			SYNTAX Integer32 (100..33554432)
			MAX-ACCESS read-create
			STATUS current
			DESCRIPTION
				"The value of this object identifies the CBS."
			::= { hwhqosProfileSuppressionEntry 4 }
		
-- 1.3.6.1.4.1.2011.5.25.132.1.11.1.50
		hwhqosSuppressionRowStatus OBJECT-TYPE
			SYNTAX RowStatus
			MAX-ACCESS read-create
			STATUS current
			DESCRIPTION
				"This object indicates the row status.
				Currently, three row statuses are supported: Active, CreateAndGo, and Destroy."
			::= { hwhqosProfileSuppressionEntry 50 }
		
--******************************************************************
-- 
-- hwhqosProfileCarTable
-- 
-- ******************************************************************
-- 1.3.6.1.4.1.2011.5.25.132.1.12
		hwhqosProfileCarTable OBJECT-TYPE
			SYNTAX SEQUENCE OF HwhqosProfileCarEntry
			MAX-ACCESS not-accessible
			STATUS current
			DESCRIPTION
				" hwhqosProfileCarTable "
			::= { hwhqosStat 12 }
		
-- 1.3.6.1.4.1.2011.5.25.132.1.12.1
		hwhqosProfileCarEntry OBJECT-TYPE
			SYNTAX HwhqosProfileCarEntry
			MAX-ACCESS not-accessible
			STATUS current
			DESCRIPTION
				" hwhqosProfileCarEntry "
			INDEX { hwhqosProfileName, hwhqosProfileCarDirection }
			::= { hwhqosProfileCarTable 1 }
		
		HwhqosProfileCarEntry ::=
			SEQUENCE { 
				hwhqosProfileCarDirection
					INTEGER,
				hwhqosProfileCarCirValue
					Unsigned32,
				hwhqosProfileCarPirValue
					Unsigned32,
				hwhqosProfileCarCbsValue
					Unsigned32,
				hwhqosProfileCarPbsValue
					Unsigned32,
				hwhqosProfileCarGreenAction
					INTEGER,
				hwhqosProfileCarYellowAction
					INTEGER,
				hwhqosProfileCarRedAction
					INTEGER,
				hwhqosProfileCarRowStatus
					RowStatus
			 }

-- 1.3.6.1.4.1.2011.5.25.132.1.12.1.1
		hwhqosProfileCarDirection OBJECT-TYPE
			SYNTAX INTEGER
				{
				inbound(1),
				outbound(2),
				inout(3)
				}
			MAX-ACCESS read-only
			STATUS current
			DESCRIPTION
				"This object indicates the direction where traffic is policed."
			::= { hwhqosProfileCarEntry 1 }
		
-- 1.3.6.1.4.1.2011.5.25.132.1.12.1.2
		hwhqosProfileCarCirValue OBJECT-TYPE
			SYNTAX Unsigned32 (0..4294967295)
			MAX-ACCESS read-create
			STATUS current
			DESCRIPTION
				"The value of this object identifies the CIR."
			::= { hwhqosProfileCarEntry 2 }
		
-- 1.3.6.1.4.1.2011.5.25.132.1.12.1.3
		hwhqosProfileCarPirValue OBJECT-TYPE
			SYNTAX Unsigned32 (0..4294967295)
			MAX-ACCESS read-create
			STATUS current
			DESCRIPTION
				"The value of this object identifies the PIR."
			::= { hwhqosProfileCarEntry 3 }
		
-- 1.3.6.1.4.1.2011.5.25.132.1.12.1.4
		hwhqosProfileCarCbsValue OBJECT-TYPE
			SYNTAX Unsigned32 (0..4294967295)
			MAX-ACCESS read-create
			STATUS current
			DESCRIPTION
				"The value of this object identifies the CBS."
			::= { hwhqosProfileCarEntry 4 }
		
-- 1.3.6.1.4.1.2011.5.25.132.1.12.1.5
		hwhqosProfileCarPbsValue OBJECT-TYPE
			SYNTAX Unsigned32 (0..4294967295)
			MAX-ACCESS read-create
			STATUS current
			DESCRIPTION
				"The value of this object identifies the PBS."
			::= { hwhqosProfileCarEntry 5 }
		
-- 1.3.6.1.4.1.2011.5.25.132.1.12.1.6
		hwhqosProfileCarGreenAction OBJECT-TYPE
			SYNTAX INTEGER
				{
				pass(1),
				discard(2)
				}
			MAX-ACCESS read-create
			STATUS current
			DESCRIPTION
				"This object indicates the actions (pass and discard) taken on the packets marked in green."
			DEFVAL { 1 }
			::= { hwhqosProfileCarEntry 6 }
		
-- 1.3.6.1.4.1.2011.5.25.132.1.12.1.7
		hwhqosProfileCarYellowAction OBJECT-TYPE
			SYNTAX INTEGER
				{
				pass(1),
				discard(2)
				}
			MAX-ACCESS read-create
			STATUS current
			DESCRIPTION
				"This object indicates the actions (pass and discard) taken on the packets marked in yellow."
			DEFVAL { 1 }
			::= { hwhqosProfileCarEntry 7 }
		
-- 1.3.6.1.4.1.2011.5.25.132.1.12.1.8
		hwhqosProfileCarRedAction OBJECT-TYPE
			SYNTAX INTEGER
				{
				pass(1),
				discard(2)
				}
			MAX-ACCESS read-create
			STATUS current
			DESCRIPTION
				"This object indicates the actions (pass and discard) taken on the packets marked in red."
			DEFVAL { 2 }
			::= { hwhqosProfileCarEntry 8 }
		
-- 1.3.6.1.4.1.2011.5.25.132.1.12.1.50
		hwhqosProfileCarRowStatus OBJECT-TYPE
			SYNTAX RowStatus
			MAX-ACCESS read-create
			STATUS current
			DESCRIPTION
				"This object indicates the row status.
				Currently, three row statuses are supported: Active, CreateAndGo, and Destroy."
			::= { hwhqosProfileCarEntry 50 }
		
--******************************************************************
-- 
-- hwhqosProfileUserQueueTable
-- 
-- ******************************************************************
-- 1.3.6.1.4.1.2011.5.25.132.1.13
		hwhqosProfileUserQueueTable OBJECT-TYPE
			SYNTAX SEQUENCE OF HwhqosProfileUserQueueEntry
			MAX-ACCESS not-accessible
			STATUS current
			DESCRIPTION
				" hwhqosProfileUserQueueTable "
			::= { hwhqosStat 13 }
		
-- 1.3.6.1.4.1.2011.5.25.132.1.13.1
		hwhqosProfileUserQueueEntry OBJECT-TYPE
			SYNTAX HwhqosProfileUserQueueEntry
			MAX-ACCESS not-accessible
			STATUS current
			DESCRIPTION
				" hwhqosProfileUserQueueEntry "
			INDEX { hwhqosProfileName, hwhqosProfileUserQueueDirection }
			::= { hwhqosProfileUserQueueTable 1 }
		
		HwhqosProfileUserQueueEntry ::=
			SEQUENCE { 
				hwhqosProfileUserQueueDirection
					INTEGER,
				hwhqosProfileUserQueueCirValue
					Integer32,
				hwhqosProfileUserQueuePirValue
					Integer32,
				hwhqosProfileUserQueueFlowQueueName
					OCTET STRING,
				hwhqosProfileUserQueueMappingName
					OCTET STRING,
				hwhqosProfileUserQueueGroupName
					OCTET STRING,
				hwhqosProfileUserQueueServiceTemplateName
					OCTET STRING,
				hwhqosProfileUserQueueRowStatus
					RowStatus
			 }

-- 1.3.6.1.4.1.2011.5.25.132.1.13.1.1
		hwhqosProfileUserQueueDirection OBJECT-TYPE
			SYNTAX INTEGER
				{
				inbound(1),
				outbound(2),
				inout(3)
				}
			MAX-ACCESS read-only
			STATUS current
			DESCRIPTION
				"This object indicates the direction where a user queue is scheduled."
			::= { hwhqosProfileUserQueueEntry 1 }
		
-- 1.3.6.1.4.1.2011.5.25.132.1.13.1.2
		hwhqosProfileUserQueueCirValue OBJECT-TYPE
			SYNTAX Integer32 (-1 | 0 | 16..10000000)
			MAX-ACCESS read-create
			STATUS current
			DESCRIPTION
				"The value of this object identifies the guaranteed bandwidth of a user queue."
			::= { hwhqosProfileUserQueueEntry 2 }
		
-- 1.3.6.1.4.1.2011.5.25.132.1.13.1.3
		hwhqosProfileUserQueuePirValue OBJECT-TYPE
			SYNTAX Integer32 (-1 | 0 | 16..10000000)
			MAX-ACCESS read-create
			STATUS current
			DESCRIPTION
				"The value of this object identifies the PIR of a user queue."
			::= { hwhqosProfileUserQueueEntry 3 }
		
-- 1.3.6.1.4.1.2011.5.25.132.1.13.1.4
		hwhqosProfileUserQueueFlowQueueName OBJECT-TYPE
			SYNTAX OCTET STRING (SIZE (1..31))
			MAX-ACCESS read-create
			STATUS current
			DESCRIPTION
				"The value of this object identifies the name of a flow queue template."
			::= { hwhqosProfileUserQueueEntry 4 }
		
-- 1.3.6.1.4.1.2011.5.25.132.1.13.1.5
		hwhqosProfileUserQueueMappingName OBJECT-TYPE
			SYNTAX OCTET STRING (SIZE (1..31))
			MAX-ACCESS read-create
			STATUS current
			DESCRIPTION
				"The value of this object identifies the name of a flow queue mapping object."
			::= { hwhqosProfileUserQueueEntry 5 }
		
-- 1.3.6.1.4.1.2011.5.25.132.1.13.1.6
		hwhqosProfileUserQueueGroupName OBJECT-TYPE
			SYNTAX OCTET STRING (SIZE (1..31))
			MAX-ACCESS read-create
			STATUS current
			DESCRIPTION
				"The value of this object identifies the name of a user group queue."
			::= { hwhqosProfileUserQueueEntry 6 }
		
-- 1.3.6.1.4.1.2011.5.25.132.1.13.1.7
		hwhqosProfileUserQueueServiceTemplateName OBJECT-TYPE
			SYNTAX OCTET STRING (SIZE (1..31))
			MAX-ACCESS read-create
			STATUS current
			DESCRIPTION
				"The value of this object identifies the name of a user-defined service template."
			::= { hwhqosProfileUserQueueEntry 7 }
		
-- 1.3.6.1.4.1.2011.5.25.132.1.13.1.50
		hwhqosProfileUserQueueRowStatus OBJECT-TYPE
			SYNTAX RowStatus
			MAX-ACCESS read-create
			STATUS current
			DESCRIPTION
				"This object indicates the row status.
				Currently, three row statuses are supported: Active, CreateAndGo, and Destroy."
			::= { hwhqosProfileUserQueueEntry 50 }
		
--  ******************************************************************
-- 
-- hwhqosProfileApplyTable
-- 
-- ******************************************************************
-- 1.3.6.1.4.1.2011.5.25.132.1.14
		hwhqosProfileApplyTable OBJECT-TYPE
			SYNTAX SEQUENCE OF HwhqosProfileApplyEntry
			MAX-ACCESS not-accessible
			STATUS current
			DESCRIPTION
				" hwhqosProfileApplyTable "
			::= { hwhqosStat 14 }
		
-- 1.3.6.1.4.1.2011.5.25.132.1.14.1
		hwhqosProfileApplyEntry OBJECT-TYPE
			SYNTAX HwhqosProfileApplyEntry
			MAX-ACCESS not-accessible
			STATUS current
			DESCRIPTION
				" hwhqosProfileApplyEntry "
			INDEX { hwhqosProfileInterfaceIndex, hwhqosProfileApplyDirection, hwhqosProfileApplyPevid, hwhqosProfileApplyCevid }
			::= { hwhqosProfileApplyTable 1 }
		
		HwhqosProfileApplyEntry ::=
			SEQUENCE { 
				hwhqosProfileInterfaceIndex
					InterfaceIndex,
				hwhqosProfileApplyDirection
					INTEGER,
				hwhqosProfileApplyPevid
					Integer32,
				hwhqosProfileApplyCevid
					Integer32,
				hwhqosProfileApplyName
					OCTET STRING,
				hwhqosProfileApplyIdentifier
					INTEGER,
				hwhqosGroupName
					OCTET STRING,
				hwhqosProfileApplyRowStatus
					RowStatus
			 }

-- 1.3.6.1.4.1.2011.5.25.132.1.14.1.1
		hwhqosProfileInterfaceIndex OBJECT-TYPE
			SYNTAX InterfaceIndex
			MAX-ACCESS read-only
			STATUS current
			DESCRIPTION
				"This object indicates the interface index."
			::= { hwhqosProfileApplyEntry 1 }
		
-- 1.3.6.1.4.1.2011.5.25.132.1.14.1.2
		hwhqosProfileApplyDirection OBJECT-TYPE
			SYNTAX INTEGER
				{
				inbound(1),
				outbound(2)
				}
			MAX-ACCESS read-only
			STATUS current
			DESCRIPTION
				"This object indicates the direction where a QoS profile is applied."
			::= { hwhqosProfileApplyEntry 2 }
		
-- 1.3.6.1.4.1.2011.5.25.132.1.14.1.3
		hwhqosProfileApplyPevid OBJECT-TYPE
			SYNTAX Integer32 (0..4094)
			MAX-ACCESS read-only
			STATUS current
			DESCRIPTION
				"The value of this object identifies the VLAN ID of a specified PE."
			::= { hwhqosProfileApplyEntry 3 }
		
-- 1.3.6.1.4.1.2011.5.25.132.1.14.1.4
		hwhqosProfileApplyCevid OBJECT-TYPE
			SYNTAX Integer32 (0..4094)
			MAX-ACCESS read-only
			STATUS current
			DESCRIPTION
				"The value of this object identifies the VLAN ID of a specified CE."
			::= { hwhqosProfileApplyEntry 4 }
		
-- 1.3.6.1.4.1.2011.5.25.132.1.14.1.5
-- BEGIN: mod by l00248629, 2014/03/21
		hwhqosProfileApplyName OBJECT-TYPE
			SYNTAX OCTET STRING (SIZE (1..63))
			MAX-ACCESS read-create
			STATUS current
			DESCRIPTION
				"The value of this object identifies the name of a QoS profile."
			::= { hwhqosProfileApplyEntry 5 }
 -- END: mod by l00248629, 2014/03/21
		
-- 1.3.6.1.4.1.2011.5.25.132.1.14.1.6
		hwhqosProfileApplyIdentifier OBJECT-TYPE
			SYNTAX INTEGER
				{
				none(1),
				vlanId(2),
				ceVid(3),
				peVid(4),
				peCeVid(5)
				}
			MAX-ACCESS read-create
			STATUS current
			DESCRIPTION
				"This object indicates the queue where packets enter."
			DEFVAL { 1 }
			::= { hwhqosProfileApplyEntry 6 }
		
-- 1.3.6.1.4.1.2011.5.25.132.1.14.1.7
		hwhqosGroupName OBJECT-TYPE
			SYNTAX OCTET STRING (SIZE (1..31))
			MAX-ACCESS read-create
			STATUS current
			DESCRIPTION
				"The value of this object identifies the name of a shared group of QoS profile instances."
			::= { hwhqosProfileApplyEntry 7 }
		
-- 1.3.6.1.4.1.2011.5.25.132.1.14.1.50
		hwhqosProfileApplyRowStatus OBJECT-TYPE
			SYNTAX RowStatus
			MAX-ACCESS read-create
			STATUS current
			DESCRIPTION
				"This object indicates the row status.
				Currently, three row statuses are supported: Active, CreateAndGo, and Destroy."
			::= { hwhqosProfileApplyEntry 50 }
		
-- ******************************************************************
-- 
-- hwhqosFlowMappingTable
-- 
-- ******************************************************************
-- 1.3.6.1.4.1.2011.5.25.132.1.15
		hwhqosFlowMappingTable OBJECT-TYPE
			SYNTAX SEQUENCE OF HwhqosFlowMappingEntry
			MAX-ACCESS not-accessible
			STATUS current
			DESCRIPTION
				" hwhqosFlowMappingTable "
			::= { hwhqosStat 15 }
		
-- 1.3.6.1.4.1.2011.5.25.132.1.15.1
		hwhqosFlowMappingEntry OBJECT-TYPE
			SYNTAX HwhqosFlowMappingEntry
			MAX-ACCESS not-accessible
			STATUS current
			DESCRIPTION
				" hwhqosFlowMappingEntry "
			INDEX { hwhqosFlowMappingName }
			::= { hwhqosFlowMappingTable 1 }
		
		HwhqosFlowMappingEntry ::=
			SEQUENCE { 
				hwhqosFlowMappingName
					OCTET STRING,
				hwhqosFlowMappingRowStatus
					RowStatus
			 }

-- 1.3.6.1.4.1.2011.5.25.132.1.15.1.1
		hwhqosFlowMappingName OBJECT-TYPE
			SYNTAX OCTET STRING (SIZE (1..31))
			MAX-ACCESS read-only
			STATUS current
			DESCRIPTION
				"The value of this object identifies the name of a flow queue mapping object."
			::= { hwhqosFlowMappingEntry 1 }
		
-- 1.3.6.1.4.1.2011.5.25.132.1.15.1.50
		hwhqosFlowMappingRowStatus OBJECT-TYPE
			SYNTAX RowStatus
			MAX-ACCESS read-create
			STATUS current
			DESCRIPTION
				"This object indicates the row status.
				Currently, three row statuses are supported: Active, CreateAndGo, and Destroy."
			::= { hwhqosFlowMappingEntry 50 }
		
-- ******************************************************************
-- 
-- hwhqosFlowMappingCfgTable
-- 
-- ******************************************************************
-- 1.3.6.1.4.1.2011.5.25.132.1.16
		hwhqosFlowMappingCfgTable OBJECT-TYPE
			SYNTAX SEQUENCE OF HwhqosFlowMappingCfgEntry
			MAX-ACCESS not-accessible
			STATUS current
			DESCRIPTION
				" hwhqosFlowMappingCfgTable "
			::= { hwhqosStat 16 }
		
-- 1.3.6.1.4.1.2011.5.25.132.1.16.1
		hwhqosFlowMappingCfgEntry OBJECT-TYPE
			SYNTAX HwhqosFlowMappingCfgEntry
			MAX-ACCESS not-accessible
			STATUS current
			DESCRIPTION
				" hwhqosFlowMappingCfgEntry "
			INDEX { hwhqosFlowMappingName, hwhqosFolwMappingCfgQueueCosValue }
			::= { hwhqosFlowMappingCfgTable 1 }
		
		HwhqosFlowMappingCfgEntry ::=
			SEQUENCE { 
				hwhqosFolwMappingCfgQueueCosValue
					INTEGER,
				hwhqosFlowMappingCfgPortQueueCosValue
					INTEGER,
				hwhqosFlowMappingCfgRowStatus
					RowStatus
			 }

-- 1.3.6.1.4.1.2011.5.25.132.1.16.1.1
		hwhqosFolwMappingCfgQueueCosValue OBJECT-TYPE
			SYNTAX INTEGER
				{
				be(1),
				af1(2),
				af2(3),
				af3(4),
				af4(5),
				ef(6),
				cs6(7),
				cs7(8)
				}
			MAX-ACCESS read-only
			STATUS current
			DESCRIPTION
				"This object indicates the service type of a class queue."
			::= { hwhqosFlowMappingCfgEntry 1 }
		
-- 1.3.6.1.4.1.2011.5.25.132.1.16.1.2
		hwhqosFlowMappingCfgPortQueueCosValue OBJECT-TYPE
			SYNTAX INTEGER
				{
				be(1),
				af1(2),
				af2(3),
				af3(4),
				af4(5),
				ef(6),
				cs6(7),
				cs7(8)
				}
			MAX-ACCESS read-create
			STATUS current
			DESCRIPTION
				"This object indicates the service type of a port queue."
			::= { hwhqosFlowMappingCfgEntry 2 }
		
-- 1.3.6.1.4.1.2011.5.25.132.1.16.1.50
		hwhqosFlowMappingCfgRowStatus OBJECT-TYPE
			SYNTAX RowStatus
			MAX-ACCESS read-create
			STATUS current
			DESCRIPTION
				"This object indicates the row status.
				Currently, three row statuses are supported: Active, CreateAndGo, and Destroy."
			::= { hwhqosFlowMappingCfgEntry 50 }
		
-- ******************************************************************
-- 
-- hwhqosFlowQueueTable
-- 
-- ******************************************************************
-- 1.3.6.1.4.1.2011.5.25.132.1.17
		hwhqosFlowQueueTable OBJECT-TYPE
			SYNTAX SEQUENCE OF HwhqosFlowQueueEntry
			MAX-ACCESS not-accessible
			STATUS current
			DESCRIPTION
				" hwhqosFlowQueueTable "
			::= { hwhqosStat 17 }
		
-- 1.3.6.1.4.1.2011.5.25.132.1.17.1
		hwhqosFlowQueueEntry OBJECT-TYPE
			SYNTAX HwhqosFlowQueueEntry
			MAX-ACCESS not-accessible
			STATUS current
			DESCRIPTION
				" hwhqosFlowQueueEntry "
			INDEX { hwhqosFlowQueueName }
			::= { hwhqosFlowQueueTable 1 }
		
		HwhqosFlowQueueEntry ::=
			SEQUENCE { 
				hwhqosFlowQueueName
					OCTET STRING,
				hwhqosFlowQueueRowStatus
					RowStatus
			 }

-- 1.3.6.1.4.1.2011.5.25.132.1.17.1.1
		hwhqosFlowQueueName OBJECT-TYPE
			SYNTAX OCTET STRING (SIZE (1..31))
			MAX-ACCESS read-only
			STATUS current
			DESCRIPTION
				"The value of this object identifies the name of a flow queue template."
			::= { hwhqosFlowQueueEntry 1 }
		
-- 1.3.6.1.4.1.2011.5.25.132.1.17.1.50
		hwhqosFlowQueueRowStatus OBJECT-TYPE
			SYNTAX RowStatus
			MAX-ACCESS read-create
			STATUS current
			DESCRIPTION
				"This object indicates the row status.
				Currently, three row statuses are supported: Active, CreateAndGo, and Destroy."
			::= { hwhqosFlowQueueEntry 50 }
		
-- ******************************************************************
-- 
-- hwhqosFlowQueueCfgTable
-- 
-- ******************************************************************
-- 1.3.6.1.4.1.2011.5.25.132.1.18
		hwhqosFlowQueueCfgTable OBJECT-TYPE
			SYNTAX SEQUENCE OF HwhqosFlowQueueCfgEntry
			MAX-ACCESS not-accessible
			STATUS current
			DESCRIPTION
				" hwhqosFlowQueueCfgTable "
			::= { hwhqosStat 18 }
		
-- 1.3.6.1.4.1.2011.5.25.132.1.18.1
		hwhqosFlowQueueCfgEntry OBJECT-TYPE
			SYNTAX HwhqosFlowQueueCfgEntry
			MAX-ACCESS not-accessible
			STATUS current
			DESCRIPTION
				" hwhqosFlowQueueCfgEntry "
			INDEX { hwhqosFlowQueueName, hwhqosFlowQueueCfgCosValue }
			::= { hwhqosFlowQueueCfgTable 1 }
		
		HwhqosFlowQueueCfgEntry ::=
			SEQUENCE { 
				hwhqosFlowQueueCfgCosValue
					INTEGER,
				hwhqosFlowQueueCfgType
					INTEGER,
				hwhqosFlowQueueCfgWeightValue
					Integer32,
				hwhqosFlowQueueCfgShapingValue
					Unsigned32,	
				hwhqosFlowQueueCfgShapingPercentageValue
					Integer32,
				hwhqosFlowQueueCfgWredName
					OCTET STRING,
				hwhqosFlowQueueCfgPbsValue
					Integer32,
				hwhqosFlowQueueCfgRowStatus
					RowStatus
			 }

-- 1.3.6.1.4.1.2011.5.25.132.1.18.1.1
		hwhqosFlowQueueCfgCosValue OBJECT-TYPE
			SYNTAX INTEGER
				{
				be(1),
				af1(2),
				af2(3),
				af3(4),
				af4(5),
				ef(6),
				cs6(7),
				cs7(8)
				}
			MAX-ACCESS read-create
			STATUS current
			DESCRIPTION
				"This object indicates the configured priority of a flow queue."
			::= { hwhqosFlowQueueCfgEntry 1 }
		
-- 1.3.6.1.4.1.2011.5.25.132.1.18.1.2
		hwhqosFlowQueueCfgType OBJECT-TYPE
			SYNTAX INTEGER
				{
				pq(1),
				wfq(2),
				lpq(3)
				}
			MAX-ACCESS read-create
			STATUS current
			DESCRIPTION
				"This object indicates the scheduling mode of a flow queue."
			::= { hwhqosFlowQueueCfgEntry 2 }
		
-- 1.3.6.1.4.1.2011.5.25.132.1.18.1.3
		hwhqosFlowQueueCfgWeightValue OBJECT-TYPE
			SYNTAX Integer32 (1..100 | 2147483647)
			MAX-ACCESS read-create
			STATUS current
			DESCRIPTION
				"The value of this object identifies the WFQ scheduling weight."
			::= { hwhqosFlowQueueCfgEntry 3 }
		
-- 1.3.6.1.4.1.2011.5.25.132.1.18.1.4
		hwhqosFlowQueueCfgShapingValue OBJECT-TYPE
			SYNTAX Unsigned32 (8..4294967295)            
			MAX-ACCESS read-create
			STATUS current
			DESCRIPTION
				"The value of this object identifies the shaping rate, namely, the configured interface bandwidth. The value of this object is equal to the PIR value."
			::= { hwhqosFlowQueueCfgEntry 4 }
		
-- 1.3.6.1.4.1.2011.5.25.132.1.18.1.5
		hwhqosFlowQueueCfgShapingPercentageValue OBJECT-TYPE
			SYNTAX Integer32 (0..100 | 2147483647)
			MAX-ACCESS read-create
			STATUS current
			DESCRIPTION
				"The value of this object identifies the percentage of the shaping rate, that is, the percentage of the traffic-shaping bandwidth to the interface bandwidth."
			::= { hwhqosFlowQueueCfgEntry 5 }
		
-- 1.3.6.1.4.1.2011.5.25.132.1.18.1.6
		hwhqosFlowQueueCfgWredName OBJECT-TYPE
			SYNTAX OCTET STRING (SIZE (1..31))
			MAX-ACCESS read-create
			STATUS current
			DESCRIPTION
				"The value of this object identifies the WRED object used by a flow queue."
			::= { hwhqosFlowQueueCfgEntry 6 }
		
-- 1.3.6.1.4.1.2011.5.25.132.1.18.1.7
		hwhqosFlowQueueCfgPbsValue OBJECT-TYPE
			SYNTAX Integer32 (1..4194304)
			MAX-ACCESS read-create
			STATUS current
			DESCRIPTION
				"The object specifies the value of the flow-queue specific queue pbs."
			::= { hwhqosFlowQueueCfgEntry 7 }		
		
-- 1.3.6.1.4.1.2011.5.25.132.1.18.1.50
		hwhqosFlowQueueCfgRowStatus OBJECT-TYPE
			SYNTAX RowStatus
			MAX-ACCESS read-create
			STATUS current
			DESCRIPTION
				"This object indicates the row status.
				Currently, three row statuses are supported: Active, CreateAndGo, and Destroy."
			::= { hwhqosFlowQueueCfgEntry 50 }
		
-- ******************************************************************
-- 
-- hwhqosFlowWredTable
-- 
-- ******************************************************************
-- 1.3.6.1.4.1.2011.5.25.132.1.19
		hwhqosFlowWredTable OBJECT-TYPE
			SYNTAX SEQUENCE OF HwhqosFlowWredEntry
			MAX-ACCESS not-accessible
			STATUS current
			DESCRIPTION
				" hwhqosFlowWredTable "
			::= { hwhqosStat 19 }
		
-- 1.3.6.1.4.1.2011.5.25.132.1.19.1
		hwhqosFlowWredEntry OBJECT-TYPE
			SYNTAX HwhqosFlowWredEntry
			MAX-ACCESS not-accessible
			STATUS current
			DESCRIPTION
				" hwhqosFlowQueueEntry "
			INDEX { hwhqosFlowWredName }
			::= { hwhqosFlowWredTable 1 }
		
		HwhqosFlowWredEntry ::=
			SEQUENCE { 
				hwhqosFlowWredName
					OCTET STRING,
				hwhqosFlowWredRowStatus
					RowStatus
			 }

-- 1.3.6.1.4.1.2011.5.25.132.1.19.1.1
		hwhqosFlowWredName OBJECT-TYPE
			SYNTAX OCTET STRING (SIZE (1..31))
			MAX-ACCESS read-only
			STATUS current
			DESCRIPTION
				"The value of this object identifies the name of a flow queue template."
			::= { hwhqosFlowWredEntry 1 }
		
-- 1.3.6.1.4.1.2011.5.25.132.1.19.1.50
		hwhqosFlowWredRowStatus OBJECT-TYPE
			SYNTAX RowStatus
			MAX-ACCESS read-create
			STATUS current
			DESCRIPTION
				"This object indicates the row status.
				Currently, three row statuses are supported: Active, CreateAndGo, and Destroy."
			::= { hwhqosFlowWredEntry 50 }
		
-- ******************************************************************
-- 
-- hwhqosFlowWredColorTable
-- 
-- ******************************************************************
-- 1.3.6.1.4.1.2011.5.25.132.1.20
		hwhqosFlowWredColorTable OBJECT-TYPE
			SYNTAX SEQUENCE OF HwhqosFlowWredColorEntry
			MAX-ACCESS not-accessible
			STATUS current
			DESCRIPTION
				" hwhqosFlowWredColorTable "
			::= { hwhqosStat 20 }
		
-- 1.3.6.1.4.1.2011.5.25.132.1.20.1
		hwhqosFlowWredColorEntry OBJECT-TYPE
			SYNTAX HwhqosFlowWredColorEntry
			MAX-ACCESS not-accessible
			STATUS current
			DESCRIPTION
				" hwhqosFlowWredColorEntry "
			INDEX { hwhqosFlowWredName, hwhqosFlowWredColor }
			::= { hwhqosFlowWredColorTable 1 }
		
		HwhqosFlowWredColorEntry ::=
			SEQUENCE { 
				hwhqosFlowWredColor
					INTEGER,
				hwhqosFlowWredColorLowlimitPercentage
					Integer32,
				hwhqosFlowWredColorHighlimitPercentage
					Integer32,
				hwhqosFlowWredColorDiscardPercentage
					Integer32,
				hwhqosFlowWredColorRowStatus
					RowStatus
			 }

-- 1.3.6.1.4.1.2011.5.25.132.1.20.1.1
		hwhqosFlowWredColor OBJECT-TYPE
			SYNTAX INTEGER
				{
				green(1),
				yellow(2),
				red(3)
				}
			MAX-ACCESS read-only
			STATUS current
			DESCRIPTION
				"This object indicates the color for marking packets."
			::= { hwhqosFlowWredColorEntry 1 }
		
-- 1.3.6.1.4.1.2011.5.25.132.1.20.1.2
		hwhqosFlowWredColorLowlimitPercentage OBJECT-TYPE
			SYNTAX Integer32 (0..100)
			MAX-ACCESS read-create
			STATUS current
			DESCRIPTION
				"The value of this object identifies the percentage of the WRED lower threshold, that is, the percentage of the WRED lower threshold to the flow queue length. When the average queue length reaches this number, packets are discarded."
			DEFVAL { 100 }
			::= { hwhqosFlowWredColorEntry 2 }
		
-- 1.3.6.1.4.1.2011.5.25.132.1.20.1.3
		hwhqosFlowWredColorHighlimitPercentage OBJECT-TYPE
			SYNTAX Integer32 (0..100)
			MAX-ACCESS read-create
			STATUS current
			DESCRIPTION
				"The value of this object identifies the percentage of the WRED upper threshold, that is, the percentage of the WRED upper threshold to the flow queue length. When the average queue length reaches this number, packets are discarded."
			DEFVAL { 100 }
			::= { hwhqosFlowWredColorEntry 3 }
		
-- 1.3.6.1.4.1.2011.5.25.132.1.20.1.4
		hwhqosFlowWredColorDiscardPercentage OBJECT-TYPE
			SYNTAX Integer32 (1..100)
			MAX-ACCESS read-create
			STATUS current
			DESCRIPTION
				"The value of this object identifies the percentage of the packets that are discarded by WRED."
			DEFVAL { 100 }
			::= { hwhqosFlowWredColorEntry 4 }
		
-- 1.3.6.1.4.1.2011.5.25.132.1.20.1.50
		hwhqosFlowWredColorRowStatus OBJECT-TYPE
			SYNTAX RowStatus
			MAX-ACCESS read-create
			STATUS current
			DESCRIPTION
				"This object indicates the row status.
				Currently, three row statuses are supported: Active, CreateAndGo, and Destroy."
			::= { hwhqosFlowWredColorEntry 50 }
		
-- ******************************************************************
-- 
-- hwhqosUserGroupQueueTable
-- 
-- ******************************************************************
-- 1.3.6.1.4.1.2011.5.25.132.1.21
		hwhqosUserGroupQueueTable OBJECT-TYPE
			SYNTAX SEQUENCE OF HwhqosUserGroupQueueEntry
			MAX-ACCESS not-accessible
			STATUS current
			DESCRIPTION
				" hwhqosUserGroupQueueTable "
			::= { hwhqosStat 21 }
		
-- 1.3.6.1.4.1.2011.5.25.132.1.21.1
		hwhqosUserGroupQueueEntry OBJECT-TYPE
			SYNTAX HwhqosUserGroupQueueEntry
			MAX-ACCESS not-accessible
			STATUS current
			DESCRIPTION
				" hwhqosUserGroupQueueEntry "
			INDEX { hwhqosUserGroupQueueName }
			::= { hwhqosUserGroupQueueTable 1 }
		
		HwhqosUserGroupQueueEntry ::=
			SEQUENCE { 
				hwhqosUserGroupQueueName
					OCTET STRING,
				hwhqosUserGroupQueueSlotNumber
					Integer32,
				hwhqosUserGroupQueueRowStatus
					RowStatus
			 }

-- 1.3.6.1.4.1.2011.5.25.132.1.21.1.1
		hwhqosUserGroupQueueName OBJECT-TYPE
			SYNTAX OCTET STRING (SIZE (1..31))
			MAX-ACCESS read-only
			STATUS current
			DESCRIPTION
				"The value of this object identifies the name of a user group queue."
			::= { hwhqosUserGroupQueueEntry 1 }
		
-- 1.3.6.1.4.1.2011.5.25.132.1.21.1.2
		hwhqosUserGroupQueueSlotNumber OBJECT-TYPE
			SYNTAX Integer32 (0 | 1..8)
			MAX-ACCESS read-create
			STATUS current
			DESCRIPTION
				"The value of this object identifies the number of the slot where a user group queue object is located."
			DEFVAL { 0 }
			::= { hwhqosUserGroupQueueEntry 2 }
		
-- 1.3.6.1.4.1.2011.5.25.132.1.21.1.50
		hwhqosUserGroupQueueRowStatus OBJECT-TYPE
			SYNTAX RowStatus
			MAX-ACCESS read-create
			STATUS current
			DESCRIPTION
				"This object indicates the row status.
				Currently, three row statuses are supported: Active, CreateAndGo, and Destroy."
			::= { hwhqosUserGroupQueueEntry 50 }
		
-- ******************************************************************
-- 
-- hwhqosUserGroupQueueShapingTable
-- 
-- ******************************************************************
-- 1.3.6.1.4.1.2011.5.25.132.1.22
		hwhqosUserGroupQueueShapingTable OBJECT-TYPE
			SYNTAX SEQUENCE OF HwhqosUserGroupQueueShapingEntry
			MAX-ACCESS not-accessible
			STATUS current
			DESCRIPTION
				" hwhqosUserGroupQueueShapingTable "
			::= { hwhqosStat 22 }
		
-- 1.3.6.1.4.1.2011.5.25.132.1.22.1
		hwhqosUserGroupQueueShapingEntry OBJECT-TYPE
			SYNTAX HwhqosUserGroupQueueShapingEntry
			MAX-ACCESS not-accessible
			STATUS current
			DESCRIPTION
				" hwhqosUserGroupQueueShapingEntry "
			INDEX { hwhqosUserGroupQueueName, hwhqosUserGroupQueueShapingDirection }
			::= { hwhqosUserGroupQueueShapingTable 1 }
		
		HwhqosUserGroupQueueShapingEntry ::=
			SEQUENCE { 
				hwhqosUserGroupQueueShapingDirection
					INTEGER,
				hwhqosUserGroupQueueShapingValue
					Integer32,
				hwhqosUserGroupQueuePbsValue
					Integer32,
				hwhqosUserGroupQueueShapingRowStatus
					RowStatus
			 }

-- 1.3.6.1.4.1.2011.5.25.132.1.22.1.1
		hwhqosUserGroupQueueShapingDirection OBJECT-TYPE
			SYNTAX INTEGER
				{
				inbound(1),
				outbound(2)
				}
			MAX-ACCESS read-only
			STATUS current
			DESCRIPTION
				"This object indicates the direction where a user group queue is scheduled."
			::= { hwhqosUserGroupQueueShapingEntry 1 }
		
-- 1.3.6.1.4.1.2011.5.25.132.1.22.1.2
		hwhqosUserGroupQueueShapingValue OBJECT-TYPE
			SYNTAX Integer32 (66..10000000)
			UNITS "Kbps"
			MAX-ACCESS read-create
			STATUS current
			DESCRIPTION
				"The value of this object identifies the PIR of a user group queue."
			::= { hwhqosUserGroupQueueShapingEntry 2 }
		
-- 1.3.6.1.4.1.2011.5.25.132.1.22.1.3
		hwhqosUserGroupQueuePbsValue OBJECT-TYPE
			SYNTAX Integer32 (64..2097152)
			UNITS "bytes"
			MAX-ACCESS read-create
			STATUS current
			DESCRIPTION
				" The object specifies the value of the user group queue pbs. "
			::= { hwhqosUserGroupQueueShapingEntry 3 }
		
-- 1.3.6.1.4.1.2011.5.25.132.1.22.1.50
		hwhqosUserGroupQueueShapingRowStatus OBJECT-TYPE
			SYNTAX RowStatus
			MAX-ACCESS read-create
			STATUS current
			DESCRIPTION
				"This object indicates the row status.
				Currently, three row statuses are supported: Active, CreateAndGo, and Destroy."
			::= { hwhqosUserGroupQueueShapingEntry 50 }
		
-- ******************************************************************
-- 
-- hwhqosUserQueueTable
-- 
-- ******************************************************************
-- 1.3.6.1.4.1.2011.5.25.132.1.23
		hwhqosUserQueueTable OBJECT-TYPE
			SYNTAX SEQUENCE OF HwhqosUserQueueEntry
			MAX-ACCESS not-accessible
			STATUS current
			DESCRIPTION
				" hwhqosUserQueueTable "
			::= { hwhqosStat 23 }
		
-- 1.3.6.1.4.1.2011.5.25.132.1.23.1
		hwhqosUserQueueEntry OBJECT-TYPE
			SYNTAX HwhqosUserQueueEntry
			MAX-ACCESS not-accessible
			STATUS current
			DESCRIPTION
				" hwhqosUserQueueEntry "
			INDEX { hwhqosUserQueueInterfaceIndex, hwhqosUserQueueDirection }
			::= { hwhqosUserQueueTable 1 }
		
		HwhqosUserQueueEntry ::=
			SEQUENCE { 
				hwhqosUserQueueInterfaceIndex
					InterfaceIndex,
				hwhqosUserQueueDirection
					INTEGER,
				hwhqosUserQueueCirValue
					Integer32,
				hwhqosUserQueuePirValue
					Integer32,
				hwhqosUserQueueFlowQueueName
					OCTET STRING,
				hwhqosUserQueueFlowMappingName
					OCTET STRING,
				hwhqosUserQueueGroupName
					OCTET STRING,
				hwhqosUserQueueServiceTemplateName
					OCTET STRING,
				hwhqosUserQueueRowStatus
					RowStatus
			 }

-- 1.3.6.1.4.1.2011.5.25.132.1.23.1.1
		hwhqosUserQueueInterfaceIndex OBJECT-TYPE
			SYNTAX InterfaceIndex
			MAX-ACCESS read-only
			STATUS current
			DESCRIPTION
				"This object indicates the interface index."
			::= { hwhqosUserQueueEntry 1 }
		
-- 1.3.6.1.4.1.2011.5.25.132.1.23.1.2
		hwhqosUserQueueDirection OBJECT-TYPE
			SYNTAX INTEGER
				{
				inbound(1),
				outbound(2)
				}
			MAX-ACCESS read-only
			STATUS current
			DESCRIPTION
				"This object indicates the direction where a user queue is scheduled."
			::= { hwhqosUserQueueEntry 2 }
		
-- 1.3.6.1.4.1.2011.5.25.132.1.23.1.3
		hwhqosUserQueueCirValue OBJECT-TYPE
			SYNTAX Integer32 (0 | 16..1000000)
			UNITS "Kbps"
			MAX-ACCESS read-create
			STATUS current
			DESCRIPTION
				"The value of this object identifies the guaranteed bandwidth of a user queue."
			::= { hwhqosUserQueueEntry 3 }
		
-- 1.3.6.1.4.1.2011.5.25.132.1.23.1.4
		hwhqosUserQueuePirValue OBJECT-TYPE
			SYNTAX Integer32 (0 | 16..1000000)
			UNITS "Kbps"
			MAX-ACCESS read-create
			STATUS current
			DESCRIPTION
				"The value of this object identifies the PIR of a user queue."
			::= { hwhqosUserQueueEntry 4 }
		
-- 1.3.6.1.4.1.2011.5.25.132.1.23.1.5
		hwhqosUserQueueFlowQueueName OBJECT-TYPE
			SYNTAX OCTET STRING (SIZE (1..31))
			MAX-ACCESS read-create
			STATUS current
			DESCRIPTION
				"The value of this object identifies the flow queue template that is applied."
			::= { hwhqosUserQueueEntry 5 }
		
-- 1.3.6.1.4.1.2011.5.25.132.1.23.1.6
		hwhqosUserQueueFlowMappingName OBJECT-TYPE
			SYNTAX OCTET STRING (SIZE (1..31))
			MAX-ACCESS read-create
			STATUS current
			DESCRIPTION
				"The value of this object identifies the flow queue mapping object that is applied."
			::= { hwhqosUserQueueEntry 6 }
		
-- 1.3.6.1.4.1.2011.5.25.132.1.23.1.7
		hwhqosUserQueueGroupName OBJECT-TYPE
			SYNTAX OCTET STRING (SIZE (1..31))
			MAX-ACCESS read-create
			STATUS current
			DESCRIPTION
				"The value of this object identifies the name of the user group queue that is applied."
			::= { hwhqosUserQueueEntry 7 }
		
-- 1.3.6.1.4.1.2011.5.25.132.1.23.1.8
		hwhqosUserQueueServiceTemplateName OBJECT-TYPE
			SYNTAX OCTET STRING (SIZE (1..31))
			MAX-ACCESS read-create
			STATUS current
			DESCRIPTION
				"The value of this object identifies the name of the service template that is applied."
			::= { hwhqosUserQueueEntry 8 }
		
-- 1.3.6.1.4.1.2011.5.25.132.1.23.1.50
		hwhqosUserQueueRowStatus OBJECT-TYPE
			SYNTAX RowStatus
			MAX-ACCESS read-create
			STATUS current
			DESCRIPTION
				"This object indicates the row status.
				Currently, three row statuses are supported: Active, CreateAndGo, and Destroy."
			::= { hwhqosUserQueueEntry 50 }
		
-- ******************************************************************
-- 
-- hwhqosBehaviorUserQueueTable
-- 
-- ******************************************************************
-- 1.3.6.1.4.1.2011.5.25.132.1.24
		hwhqosBehaviorUserQueueTable OBJECT-TYPE
			SYNTAX SEQUENCE OF HwhqosBehaviorUserQueueEntry
			MAX-ACCESS not-accessible
			STATUS current
			DESCRIPTION
				" hwBehaviorhqosUserQueueTable "
			::= { hwhqosStat 24 }
		
-- 1.3.6.1.4.1.2011.5.25.132.1.24.1
		hwhqosBehaviorUserQueueEntry OBJECT-TYPE
			SYNTAX HwhqosBehaviorUserQueueEntry
			MAX-ACCESS not-accessible
			STATUS current
			DESCRIPTION
				" hwhqosBehaviorUserQueueEntry "
			INDEX { hwhqosBehaviorName }
			::= { hwhqosBehaviorUserQueueTable 1 }
		
		HwhqosBehaviorUserQueueEntry ::=
			SEQUENCE { 
				hwhqosBehaviorName
					OCTET STRING,
				hwhqosBehaviorCirValue
					Integer32,
				hwhqosBehaviorPirValue
					Integer32,
				hwhqosBehaviorFlowQueueName
					OCTET STRING,
				hwhqosBehaviorFlowMappingName
					OCTET STRING,
				hwhqosBehaviorGroupName
					OCTET STRING,
				hwhqosBehaviorServiceTemplateName
					OCTET STRING,
				hwhqosBehaviorUserQueueRowStatus
					RowStatus
			 }

-- 1.3.6.1.4.1.2011.5.25.132.1.24.1.1
		hwhqosBehaviorName OBJECT-TYPE
			SYNTAX OCTET STRING (SIZE (1..31))
			MAX-ACCESS read-only
			STATUS current
			DESCRIPTION
				"The value of this object identifies the name of a flow behavior."
			::= { hwhqosBehaviorUserQueueEntry 1 }
		
-- 1.3.6.1.4.1.2011.5.25.132.1.24.1.2
		hwhqosBehaviorCirValue OBJECT-TYPE
			SYNTAX Integer32 (0 | 16..10000000)
			UNITS "Kbps"
			MAX-ACCESS read-create
			STATUS current
			DESCRIPTION
				"The value of this object identifies the guaranteed bandwidth of a flow user queue."
			::= { hwhqosBehaviorUserQueueEntry 2 }
		
-- 1.3.6.1.4.1.2011.5.25.132.1.24.1.3
		hwhqosBehaviorPirValue OBJECT-TYPE
			SYNTAX Integer32 (0 | 16..10000000)
			UNITS "Kbps"
			MAX-ACCESS read-create
			STATUS current
			DESCRIPTION
				"The value of this object identifies the PIR of a flow user queue."
			::= { hwhqosBehaviorUserQueueEntry 3 }
		
-- 1.3.6.1.4.1.2011.5.25.132.1.24.1.4
		hwhqosBehaviorFlowQueueName OBJECT-TYPE
			SYNTAX OCTET STRING (SIZE (1..31))
			MAX-ACCESS read-create
			STATUS current
			DESCRIPTION
				"The value of this object identifies the flow queue template that is applied."
			::= { hwhqosBehaviorUserQueueEntry 4 }
		
-- 1.3.6.1.4.1.2011.5.25.132.1.24.1.5
		hwhqosBehaviorFlowMappingName OBJECT-TYPE
			SYNTAX OCTET STRING (SIZE (1..31))
			MAX-ACCESS read-create
			STATUS current
			DESCRIPTION
				"The value of this object identifies the flow queue mapping object that is applied."
			::= { hwhqosBehaviorUserQueueEntry 5 }
		
-- 1.3.6.1.4.1.2011.5.25.132.1.24.1.6
		hwhqosBehaviorGroupName OBJECT-TYPE
			SYNTAX OCTET STRING (SIZE (1..31))
			MAX-ACCESS read-create
			STATUS current
			DESCRIPTION
				"The value of this object identifies the name of the user group queue that is applied."
			::= { hwhqosBehaviorUserQueueEntry 6 }
		
-- 1.3.6.1.4.1.2011.5.25.132.1.24.1.7
		hwhqosBehaviorServiceTemplateName OBJECT-TYPE
			SYNTAX OCTET STRING (SIZE (1..31))
			MAX-ACCESS read-create
			STATUS current
			DESCRIPTION
				"The value of this object identifies the name of the service template that is applied."
			::= { hwhqosBehaviorUserQueueEntry 7 }
		
-- 1.3.6.1.4.1.2011.5.25.132.1.24.1.50
		hwhqosBehaviorUserQueueRowStatus OBJECT-TYPE
			SYNTAX RowStatus
			MAX-ACCESS read-create
			STATUS current
			DESCRIPTION
				"This object indicates the row status.
				Currently, three row statuses are supported: Active, CreateAndGo, and Destroy."
			::= { hwhqosBehaviorUserQueueEntry 50 }
		
-- ******************************************************************
-- 
-- hwhqosBandwidthTable
-- 
-- ******************************************************************
-- 1.3.6.1.4.1.2011.5.25.132.1.25
		hwhqosBandwidthTable OBJECT-TYPE
			SYNTAX SEQUENCE OF HwhqosBandwidthEntry
			MAX-ACCESS not-accessible
			STATUS current
			DESCRIPTION
				" hwhqosBandwidthTable "
			::= { hwhqosStat 25 }
		
-- 1.3.6.1.4.1.2011.5.25.132.1.25.1
		hwhqosBandwidthEntry OBJECT-TYPE
			SYNTAX HwhqosBandwidthEntry
			MAX-ACCESS not-accessible
			STATUS current
			DESCRIPTION
				" hwhqosBandwidthEntry "
			INDEX { hwhqosBandwidthInterfaceIndex }
			::= { hwhqosBandwidthTable 1 }
		
		HwhqosBandwidthEntry ::=
			SEQUENCE { 
				hwhqosBandwidthInterfaceIndex
					InterfaceIndex,
				hwhqosBandwidthValue
					Integer32,
				hwhqosBandwidthRowStatus
					RowStatus
			 }

-- 1.3.6.1.4.1.2011.5.25.132.1.25.1.1
		hwhqosBandwidthInterfaceIndex OBJECT-TYPE
			SYNTAX InterfaceIndex
			MAX-ACCESS read-only
			STATUS current
			DESCRIPTION
				"This object indicates the name of a trunk interface."
			::= { hwhqosBandwidthEntry 1 }
		
-- 1.3.6.1.4.1.2011.5.25.132.1.25.1.2
		hwhqosBandwidthValue OBJECT-TYPE
			SYNTAX Integer32 (0..2147483647)
			UNITS "Mbps"
			MAX-ACCESS read-create
			STATUS current
			DESCRIPTION
				"The value of this object identifies the bandwidth of a trunk interface."
			DEFVAL { 1000 }
			::= { hwhqosBandwidthEntry 2 }
		
-- 1.3.6.1.4.1.2011.5.25.132.1.25.1.50
		hwhqosBandwidthRowStatus OBJECT-TYPE
			SYNTAX RowStatus
			MAX-ACCESS read-create
			STATUS current
			DESCRIPTION
				"This object indicates the row status.
				Currently, three row statuses are supported: Active, CreateAndGo, and Destroy."
			::= { hwhqosBandwidthEntry 50 }
		
--  ******************************************************************
-- 
-- hwhqosServiceTemplateTable
-- 
-- ******************************************************************
-- 1.3.6.1.4.1.2011.5.25.132.1.26
		hwhqosServiceTemplateTable OBJECT-TYPE
			SYNTAX SEQUENCE OF HwhqosServiceTemplateEntry
			MAX-ACCESS not-accessible
			STATUS current
			DESCRIPTION
				" hwhqosServiceTemplateTable "
			::= { hwhqosStat 26 }
		
-- 1.3.6.1.4.1.2011.5.25.132.1.26.1
		hwhqosServiceTemplateEntry OBJECT-TYPE
			SYNTAX HwhqosServiceTemplateEntry
			MAX-ACCESS not-accessible
			STATUS current
			DESCRIPTION
				" hwhqosServiceTemplateEntry "
			INDEX { hwhqosServiceTemplateName }
			::= { hwhqosServiceTemplateTable 1 }
		
		HwhqosServiceTemplateEntry ::=
			SEQUENCE { 
				hwhqosServiceTemplateName
					OCTET STRING,
				hwhqosSlotNumber
					Integer32,
				hwhqosServiceTemplateRowStatus
					RowStatus
			 }

-- 1.3.6.1.4.1.2011.5.25.132.1.26.1.1
		hwhqosServiceTemplateName OBJECT-TYPE
			SYNTAX OCTET STRING (SIZE (1..31))
			MAX-ACCESS read-only
			STATUS current
			DESCRIPTION
				"The value of this object identifies the name of a user-defined service template."
			::= { hwhqosServiceTemplateEntry 1 }
		
-- 1.3.6.1.4.1.2011.5.25.132.1.26.1.2
		hwhqosSlotNumber OBJECT-TYPE
			SYNTAX Integer32 (1..8)
			MAX-ACCESS read-create
			STATUS current
			DESCRIPTION
				"The value of this object identifies the number of the slot where a user-defined service template is located."
			::= { hwhqosServiceTemplateEntry 2 }
		
-- 1.3.6.1.4.1.2011.5.25.132.1.26.1.50
		hwhqosServiceTemplateRowStatus OBJECT-TYPE
			SYNTAX RowStatus
			MAX-ACCESS read-create
			STATUS current
			DESCRIPTION
				"This object indicates the row status.
				Currently, three row statuses are supported: Active, CreateAndGo, and Destroy."
			::= { hwhqosServiceTemplateEntry 50 }
		
--  ******************************************************************
-- 
-- hwhqosNetworkHeaderLengthTable
-- 
-- ******************************************************************
-- 1.3.6.1.4.1.2011.5.25.132.1.27
		hwhqosNetworkHeaderLengthTable OBJECT-TYPE
			SYNTAX SEQUENCE OF HwhqosNetworkHeaderLengthEntry
			MAX-ACCESS not-accessible
			STATUS current
			DESCRIPTION
				" hwhqosNetworkHeaderLengthTable "
			::= { hwhqosStat 27 }
		
-- 1.3.6.1.4.1.2011.5.25.132.1.27.1
		hwhqosNetworkHeaderLengthEntry OBJECT-TYPE
			SYNTAX HwhqosNetworkHeaderLengthEntry
			MAX-ACCESS not-accessible
			STATUS current
			DESCRIPTION
				" hwhqosNetworkHeaderLengthEntry "
			INDEX { hwhqosServiceTemplateName, hwhqosNetworkHeaderLengthDirection }
			::= { hwhqosNetworkHeaderLengthTable 1 }
		
		HwhqosNetworkHeaderLengthEntry ::=
			SEQUENCE { 
				hwhqosNetworkHeaderLengthDirection
					INTEGER,
				hwhqosNetWorkHeaderLengthValue
					Integer32,
				hwhqosNetWorkHeaderLengthRowStatus
					RowStatus
			 }

-- 1.3.6.1.4.1.2011.5.25.132.1.27.1.1
		hwhqosNetworkHeaderLengthDirection OBJECT-TYPE
			SYNTAX INTEGER
				{
				inbound(1),
				outbound(2)
				}
			MAX-ACCESS read-only
			STATUS current
			DESCRIPTION
				"This object indicates the direction where the packet loss compensation of a service template is configured."
			::= { hwhqosNetworkHeaderLengthEntry 1 }
		
-- 1.3.6.1.4.1.2011.5.25.132.1.27.1.2
		hwhqosNetWorkHeaderLengthValue OBJECT-TYPE
			SYNTAX Integer32 (-63..63)
			MAX-ACCESS read-create
			STATUS current
			DESCRIPTION
				"The value of this object identifies the accuracy of the length for the packet loss compensation of a service template."
			::= { hwhqosNetworkHeaderLengthEntry 2 }
		
-- 1.3.6.1.4.1.2011.5.25.132.1.27.1.50
		hwhqosNetWorkHeaderLengthRowStatus OBJECT-TYPE
			SYNTAX RowStatus
			MAX-ACCESS read-create
			STATUS current
			DESCRIPTION
				"This object indicates the row status.
				Currently, three row statuses are supported: Active, CreateAndGo, and Destroy."
			::= { hwhqosNetworkHeaderLengthEntry 50 }
		
--  ******************************************************************
-- 
-- hwhqosServiceTemplateApplyTable
-- 
-- ******************************************************************
-- 1.3.6.1.4.1.2011.5.25.132.1.28
		hwhqosServiceTemplateApplyTable OBJECT-TYPE
			SYNTAX SEQUENCE OF HwhqosServiceTemplateApplyEntry
			MAX-ACCESS not-accessible
			STATUS current
			DESCRIPTION
				" hwhqosServiceTemplateApplyTable "
			::= { hwhqosStat 28 }
		
-- 1.3.6.1.4.1.2011.5.25.132.1.28.1
		hwhqosServiceTemplateApplyEntry OBJECT-TYPE
			SYNTAX HwhqosServiceTemplateApplyEntry
			MAX-ACCESS not-accessible
			STATUS current
			DESCRIPTION
				" hwhqosServiceTemplateApplyEntry "
			INDEX { hwhqosServiceTemplateApplyInterfaceIndex }
			::= { hwhqosServiceTemplateApplyTable 1 }
		
		HwhqosServiceTemplateApplyEntry ::=
			SEQUENCE { 
				hwhqosServiceTemplateApplyInterfaceIndex
					InterfaceIndex,
				hwhqosApplyServiceTemplateName
					OCTET STRING,
				hwhqosServiceTemplateApplyRowStatus
					RowStatus
			 }

-- 1.3.6.1.4.1.2011.5.25.132.1.28.1.1
		hwhqosServiceTemplateApplyInterfaceIndex OBJECT-TYPE
			SYNTAX InterfaceIndex
			MAX-ACCESS read-only
			STATUS current
			DESCRIPTION
				"This object indicates the name of the interface."
			::= { hwhqosServiceTemplateApplyEntry 1 }
		
-- 1.3.6.1.4.1.2011.5.25.132.1.28.1.2
		hwhqosApplyServiceTemplateName OBJECT-TYPE
			SYNTAX OCTET STRING (SIZE (1..31))
			MAX-ACCESS read-create
			STATUS current
			DESCRIPTION
				"The value of this object identifies the name of a user-defined service template."
			::= { hwhqosServiceTemplateApplyEntry 2 }
		
-- 1.3.6.1.4.1.2011.5.25.132.1.28.1.50
		hwhqosServiceTemplateApplyRowStatus OBJECT-TYPE
			SYNTAX RowStatus
			MAX-ACCESS read-create
			STATUS current
			DESCRIPTION
				"This object indicates the row status.
				Currently, three row statuses are supported: Active, CreateAndGo, and Destroy."
			::= { hwhqosServiceTemplateApplyEntry 50 }
		
-- ******************************************************************
-- 
-- hwhqosProfileUserQueueStatisticsTable
-- 
-- ******************************************************************
-- 1.3.6.1.4.1.2011.5.25.132.1.29
		hwhqosProfileUserQueueStatisticsTable OBJECT-TYPE
			SYNTAX SEQUENCE OF HwhqosProfileUserQueueStatisticsEntry
			MAX-ACCESS not-accessible
			STATUS current
			DESCRIPTION
				" hwhqosProfileUserQueueStatisticsTable "
			::= { hwhqosStat 29 }
		
-- 1.3.6.1.4.1.2011.5.25.132.1.29.1
		hwhqosProfileUserQueueStatisticsEntry OBJECT-TYPE
			SYNTAX HwhqosProfileUserQueueStatisticsEntry
			MAX-ACCESS not-accessible
			STATUS current
			DESCRIPTION
				" hwhqosProfileUserQueueStatisticsEntry "
			INDEX { hwhqosProfileUserQueueStatisticsInterfaceIndex, hwhqosProfileUserQueueStatisticsDirection, hwhqosProfileUserQueueStatisticsPevid, hwhqosProfileUserQueueStatisticsCevid, hwhqosProfileUserQueueStatisticsSlotNumber, 
				hwhqosProfileUserQueueStatisticsQueueIndex }
			::= { hwhqosProfileUserQueueStatisticsTable 1 }
		
		HwhqosProfileUserQueueStatisticsEntry ::=
			SEQUENCE { 
				hwhqosProfileUserQueueStatisticsInterfaceIndex
					InterfaceIndex,
				hwhqosProfileUserQueueStatisticsDirection
					INTEGER,
				hwhqosProfileUserQueueStatisticsPevid
					Integer32,
				hwhqosProfileUserQueueStatisticsCevid
					Integer32,
				hwhqosProfileUserQueueStatisticsSlotNumber
					Integer32,
				hwhqosProfileUserQueueStatisticsQueueIndex
					INTEGER,
				hwhqosProfileUserQueueStatisticsReset
					INTEGER,
				hwhqosProfileUserQueueStatisticsPassPackets
					Counter64,
				hwhqosProfileUserQueueStatisticsPassBytes
					Counter64,
				hwhqosProfileUserQueueStatisticsDropPackets
					Counter64,
				hwhqosProfileUserQueueStatisticsDropBytes
					Counter64,
				hwhqosProfileUserQueueStatisticsPassPacketsRate
					Counter64,
				hwhqosProfileUserQueueStatisticsPassBytesRate
					Counter64,
				hwhqosProfileUserQueueStatisticsDropPacketsRate
					Counter64,
				hwhqosProfileUserQueueStatisticsDropBytesRate
					Counter64,
				hwhqosProfileUserQueueStatisticsTrafficTowardsThisInterface
					Counter64,
				hwhqosProfileUserQueueStatisticsConfiguredCir
					Unsigned32,     
				hwhqosProfileUserQueueStatisticsConfiguredPir
					Unsigned32
			 }

-- 1.3.6.1.4.1.2011.5.25.132.1.29.1.1
		hwhqosProfileUserQueueStatisticsInterfaceIndex OBJECT-TYPE
			SYNTAX InterfaceIndex
			MAX-ACCESS read-only
			STATUS current
			DESCRIPTION
				"This object indicates the interface index."
			::= { hwhqosProfileUserQueueStatisticsEntry 1 }
		
-- 1.3.6.1.4.1.2011.5.25.132.1.29.1.2
		hwhqosProfileUserQueueStatisticsDirection OBJECT-TYPE
			SYNTAX INTEGER
				{
				inbound(1),
				outbound(2)
				}
			MAX-ACCESS read-only
			STATUS current
			DESCRIPTION
				"This object indicates the direction where a QoS profile is applied."
			::= { hwhqosProfileUserQueueStatisticsEntry 2 }
		
-- 1.3.6.1.4.1.2011.5.25.132.1.29.1.3
		hwhqosProfileUserQueueStatisticsPevid OBJECT-TYPE
			SYNTAX Integer32 (0..4094)
			MAX-ACCESS read-only
			STATUS current
			DESCRIPTION
				"The value of this object identifies the PE VID (outer tag value) of a QoS profile."
			::= { hwhqosProfileUserQueueStatisticsEntry 3 }
		
-- 1.3.6.1.4.1.2011.5.25.132.1.29.1.4
		hwhqosProfileUserQueueStatisticsCevid OBJECT-TYPE
			SYNTAX Integer32 (0..4094)
			MAX-ACCESS read-only
			STATUS current
			DESCRIPTION
				"The value of this object identifies the CE VID (inner tag value) or the VLAN ID of a QoS profile."
			::= { hwhqosProfileUserQueueStatisticsEntry 4 }
		
-- 1.3.6.1.4.1.2011.5.25.132.1.29.1.5
		hwhqosProfileUserQueueStatisticsSlotNumber OBJECT-TYPE
			SYNTAX Integer32 (0..128)
			MAX-ACCESS read-only
			STATUS current
			DESCRIPTION
				"The value of this object identifies the number of the slot where the interface for applying a QoS profile is located."
			::= { hwhqosProfileUserQueueStatisticsEntry 5 }
		
-- 1.3.6.1.4.1.2011.5.25.132.1.29.1.6
		hwhqosProfileUserQueueStatisticsQueueIndex OBJECT-TYPE
			SYNTAX INTEGER
				{
				be(1),
				af1(2),
				af2(3),
				af3(4),
				af4(5),
				ef(6),
				cs6(7),
				cs7(8),
				total(9)
				}
			MAX-ACCESS read-only
			STATUS current
			DESCRIPTION
				"This object indicates the priority of the user queue whose statistics are queried."
			::= { hwhqosProfileUserQueueStatisticsEntry 6 }
		
-- 1.3.6.1.4.1.2011.5.25.132.1.29.1.7
		hwhqosProfileUserQueueStatisticsReset OBJECT-TYPE
			SYNTAX INTEGER { reset(1) }
			MAX-ACCESS read-create
			STATUS current
			DESCRIPTION
				"This object indicates the resetting of statistics."
			::= { hwhqosProfileUserQueueStatisticsEntry 7 }
		
-- 1.3.6.1.4.1.2011.5.25.132.1.29.1.8
		hwhqosProfileUserQueueStatisticsPassPackets OBJECT-TYPE
			SYNTAX Counter64
			UNITS "packets"
			MAX-ACCESS read-only
			STATUS current
			DESCRIPTION
				"This object indicates the number of passed packets."
			::= { hwhqosProfileUserQueueStatisticsEntry 8 }
		
-- 1.3.6.1.4.1.2011.5.25.132.1.29.1.9
		hwhqosProfileUserQueueStatisticsPassBytes OBJECT-TYPE
			SYNTAX Counter64
			UNITS "bytes"
			MAX-ACCESS read-only
			STATUS current
			DESCRIPTION
				"This object indicates the number of passed bytes."
			::= { hwhqosProfileUserQueueStatisticsEntry 9 }
		
-- 1.3.6.1.4.1.2011.5.25.132.1.29.1.10
		hwhqosProfileUserQueueStatisticsDropPackets OBJECT-TYPE
			SYNTAX Counter64
			UNITS "packets"
			MAX-ACCESS read-only
			STATUS current
			DESCRIPTION
				"This object indicates the number of discarded packets."
			::= { hwhqosProfileUserQueueStatisticsEntry 10 }
		
-- 1.3.6.1.4.1.2011.5.25.132.1.29.1.11
		hwhqosProfileUserQueueStatisticsDropBytes OBJECT-TYPE
			SYNTAX Counter64
			UNITS "bytes"
			MAX-ACCESS read-only
			STATUS current
			DESCRIPTION
				"This object indicates the number of discarded bytes."
			::= { hwhqosProfileUserQueueStatisticsEntry 11 }
		
-- 1.3.6.1.4.1.2011.5.25.132.1.29.1.12
		hwhqosProfileUserQueueStatisticsPassPacketsRate OBJECT-TYPE
			SYNTAX Counter64
			UNITS "pps"
			MAX-ACCESS read-only
			STATUS current
			DESCRIPTION
				"This object indicates the packet pass rate."
			::= { hwhqosProfileUserQueueStatisticsEntry 12 }
		
-- 1.3.6.1.4.1.2011.5.25.132.1.29.1.13
		hwhqosProfileUserQueueStatisticsPassBytesRate OBJECT-TYPE
			SYNTAX Counter64
			UNITS "bps"
			MAX-ACCESS read-only
			STATUS current
			DESCRIPTION
				"This object indicates the byte pass rate."
			::= { hwhqosProfileUserQueueStatisticsEntry 13 }
		
-- 1.3.6.1.4.1.2011.5.25.132.1.29.1.14
		hwhqosProfileUserQueueStatisticsDropPacketsRate OBJECT-TYPE
			SYNTAX Counter64
			UNITS "pps"
			MAX-ACCESS read-only
			STATUS current
			DESCRIPTION
				"This object indicates the packet discarding rate."
			::= { hwhqosProfileUserQueueStatisticsEntry 14 }
		
-- 1.3.6.1.4.1.2011.5.25.132.1.29.1.15
		hwhqosProfileUserQueueStatisticsDropBytesRate OBJECT-TYPE
			SYNTAX Counter64
			UNITS "bps"
			MAX-ACCESS read-only
			STATUS current
			DESCRIPTION
				"This object indicates the byte discarding rate."
			::= { hwhqosProfileUserQueueStatisticsEntry 15 }
		
-- 1.3.6.1.4.1.2011.5.25.132.1.29.1.16
		hwhqosProfileUserQueueStatisticsTrafficTowardsThisInterface OBJECT-TYPE
			SYNTAX Counter64
			UNITS "bps"
			MAX-ACCESS read-only
			STATUS current
			DESCRIPTION
				"This object indicates the traffic which towards this interface."
			::= { hwhqosProfileUserQueueStatisticsEntry 16 }
		
-- 1.3.6.1.4.1.2011.5.25.132.1.29.1.17
		hwhqosProfileUserQueueStatisticsConfiguredCir OBJECT-TYPE
			SYNTAX Unsigned32 (0 | 16..4294967294)   
			UNITS "kbps"
			MAX-ACCESS read-only
			STATUS current
			DESCRIPTION
				"This object indicates the configured CIR."
			::= { hwhqosProfileUserQueueStatisticsEntry 17 }
		
-- 1.3.6.1.4.1.2011.5.25.132.1.29.1.18
		hwhqosProfileUserQueueStatisticsConfiguredPir OBJECT-TYPE
			SYNTAX Unsigned32 (0 | 16..4294967294)   
			UNITS "kbps"
			MAX-ACCESS read-only
			STATUS current
			DESCRIPTION
				"This object indicates the configured PIR."
			::= { hwhqosProfileUserQueueStatisticsEntry 18 }
		
-- ******************************************************************
-- 
-- 1.4.29  hwhqosProfileCarStatisticsTable
-- 
-- ******************************************************************
-- 1.3.6.1.4.1.2011.5.25.132.1.30
		hwhqosProfileCarStatisticsTable OBJECT-TYPE
			SYNTAX SEQUENCE OF HwhqosProfileCarStatisticsEntry
			MAX-ACCESS not-accessible
			STATUS current
			DESCRIPTION
				" hwhqosProfileCarStatisticsTable "
			::= { hwhqosStat 30 }
		
-- 1.3.6.1.4.1.2011.5.25.132.1.30.1
		hwhqosProfileCarStatisticsEntry OBJECT-TYPE
			SYNTAX HwhqosProfileCarStatisticsEntry
			MAX-ACCESS not-accessible
			STATUS current
			DESCRIPTION
				" hwhqosProfileCarStatisticsEntry "
			INDEX { hwhqosProfileCarStatisticsInterfaceIndex, hwhqosProfileCarStatisticsDirection, hwhqosProfileCarStatisticsPevid, hwhqosProfileCarStatisticsCevid, hwhqosProfileCarStatisticsType, 
				hwhqosProfileCarStatisticsSlotNumber }
			::= { hwhqosProfileCarStatisticsTable 1 }
		
		HwhqosProfileCarStatisticsEntry ::=
			SEQUENCE { 
				hwhqosProfileCarStatisticsInterfaceIndex
					InterfaceIndex,
				hwhqosProfileCarStatisticsDirection
					INTEGER,
				hwhqosProfileCarStatisticsPevid
					Integer32,
				hwhqosProfileCarStatisticsCevid
					Integer32,
				hwhqosProfileCarStatisticsType
					INTEGER,
				hwhqosProfileCarStatisticsSlotNumber
					Integer32,
				hwhqosProfileCarStatisticsReset
					INTEGER,
				hwhqosProfileCarStatisticsPassPackets
					Counter64,
				hwhqosProfileCarStatisticsPassBytes
					Counter64,
				hwhqosProfileCarStatisticsDropPackets
					Counter64,
				hwhqosProfileCarStatisticsDropBytes
					Counter64,
				hwhqosProfileCarStatisticsPassPacketsRate
					Counter64,
				hwhqosProfileCarStatisticsPassBytesRate
					Counter64,
				hwhqosProfileCarStatisticsDropPacketsRate
					Counter64,
				hwhqosProfileCarStatisticsDropBytesRate
					Counter64
			 }

-- 1.3.6.1.4.1.2011.5.25.132.1.30.1.1
		hwhqosProfileCarStatisticsInterfaceIndex OBJECT-TYPE
			SYNTAX InterfaceIndex
			MAX-ACCESS read-only
			STATUS current
			DESCRIPTION
				"This object indicates the interface index."
			::= { hwhqosProfileCarStatisticsEntry 1 }
		
-- 1.3.6.1.4.1.2011.5.25.132.1.30.1.2
		hwhqosProfileCarStatisticsDirection OBJECT-TYPE
			SYNTAX INTEGER
				{
				inbound(1),
				outbound(2)
				}
			MAX-ACCESS read-only
			STATUS current
			DESCRIPTION
				"This object indicates the direction where a QoS profile is applied."
			::= { hwhqosProfileCarStatisticsEntry 2 }
		
-- 1.3.6.1.4.1.2011.5.25.132.1.30.1.3
		hwhqosProfileCarStatisticsPevid OBJECT-TYPE
			SYNTAX Integer32 (0..4094)
			MAX-ACCESS read-only
			STATUS current
			DESCRIPTION
				"The value of this object identifies the PE VID (outer tag value) of a QoS profile."
			::= { hwhqosProfileCarStatisticsEntry 3 }
		
-- 1.3.6.1.4.1.2011.5.25.132.1.30.1.4
		hwhqosProfileCarStatisticsCevid OBJECT-TYPE
			SYNTAX Integer32 (0..4094)
			MAX-ACCESS read-only
			STATUS current
			DESCRIPTION
				"The value of this object identifies the CE VID (inner tag value) or the VLAN ID of a QoS profile."
			::= { hwhqosProfileCarStatisticsEntry 4 }
		
-- 1.3.6.1.4.1.2011.5.25.132.1.30.1.5
		hwhqosProfileCarStatisticsType OBJECT-TYPE
			SYNTAX INTEGER
				{
				car(1),
				broadcastSuppression(2),
				multicastSuppression(3),
				unknownUnicastSuppression(4)
				}
			MAX-ACCESS read-only
			STATUS current
			DESCRIPTION
				"This object indicates the type of the statistics on the CAR or suppression to be queried."
			::= { hwhqosProfileCarStatisticsEntry 5 }
		
-- 1.3.6.1.4.1.2011.5.25.132.1.30.1.6
		hwhqosProfileCarStatisticsSlotNumber OBJECT-TYPE
			SYNTAX Integer32 (0..128)
			MAX-ACCESS read-only
			STATUS current
			DESCRIPTION
				"The value of this object identifies the number of the slot where the interface for applying a QoS profile is located."
			::= { hwhqosProfileCarStatisticsEntry 6 }
		
-- 1.3.6.1.4.1.2011.5.25.132.1.30.1.7
		hwhqosProfileCarStatisticsReset OBJECT-TYPE
			SYNTAX INTEGER { reset(1) }
			MAX-ACCESS read-create
			STATUS current
			DESCRIPTION
				"This object indicates the resetting of statistics."
			::= { hwhqosProfileCarStatisticsEntry 7 }
		
-- 1.3.6.1.4.1.2011.5.25.132.1.30.1.8
		hwhqosProfileCarStatisticsPassPackets OBJECT-TYPE
			SYNTAX Counter64
			MAX-ACCESS read-only
			STATUS current
			DESCRIPTION
				"This object indicates the number of passed packets."
			::= { hwhqosProfileCarStatisticsEntry 8 }
		
-- 1.3.6.1.4.1.2011.5.25.132.1.30.1.9
		hwhqosProfileCarStatisticsPassBytes OBJECT-TYPE
			SYNTAX Counter64
			MAX-ACCESS read-only
			STATUS current
			DESCRIPTION
				"This object indicates the number of passed bytes."
			::= { hwhqosProfileCarStatisticsEntry 9 }
		
-- 1.3.6.1.4.1.2011.5.25.132.1.30.1.10
		hwhqosProfileCarStatisticsDropPackets OBJECT-TYPE
			SYNTAX Counter64
			MAX-ACCESS read-only
			STATUS current
			DESCRIPTION
				"This object indicates the number of discarded packets."
			::= { hwhqosProfileCarStatisticsEntry 10 }
		
-- 1.3.6.1.4.1.2011.5.25.132.1.30.1.11
		hwhqosProfileCarStatisticsDropBytes OBJECT-TYPE
			SYNTAX Counter64
			MAX-ACCESS read-only
			STATUS current
			DESCRIPTION
				"This object indicates the number of discarded bytes."
			::= { hwhqosProfileCarStatisticsEntry 11 }
		
-- 1.3.6.1.4.1.2011.5.25.132.1.30.1.12
		hwhqosProfileCarStatisticsPassPacketsRate OBJECT-TYPE
			SYNTAX Counter64
			MAX-ACCESS read-only
			STATUS current
			DESCRIPTION
				"This object indicates the packet pass rate."
			::= { hwhqosProfileCarStatisticsEntry 12 }
		
-- 1.3.6.1.4.1.2011.5.25.132.1.30.1.13
		hwhqosProfileCarStatisticsPassBytesRate OBJECT-TYPE
			SYNTAX Counter64
			MAX-ACCESS read-only
			STATUS current
			DESCRIPTION
				"This object indicates the byte pass rate."
			::= { hwhqosProfileCarStatisticsEntry 13 }
		
-- 1.3.6.1.4.1.2011.5.25.132.1.30.1.14
		hwhqosProfileCarStatisticsDropPacketsRate OBJECT-TYPE
			SYNTAX Counter64
			MAX-ACCESS read-only
			STATUS current
			DESCRIPTION
				"This object indicates the packet discarding rate."
			::= { hwhqosProfileCarStatisticsEntry 14 }
		
-- 1.3.6.1.4.1.2011.5.25.132.1.30.1.15
		hwhqosProfileCarStatisticsDropBytesRate OBJECT-TYPE
			SYNTAX Counter64
			MAX-ACCESS read-only
			STATUS current
			DESCRIPTION
				"This object indicates the byte discarding rate."
			::= { hwhqosProfileCarStatisticsEntry 15 }
		
-- ******************************************************************
-- 
-- hwhqosUserQueueStatisticsTable
-- 
-- ******************************************************************
-- 1.3.6.1.4.1.2011.5.25.132.1.31
		hwhqosUserQueueStatisticsTable OBJECT-TYPE
			SYNTAX SEQUENCE OF HwhqosUserQueueStatisticsEntry
			MAX-ACCESS not-accessible
			STATUS current
			DESCRIPTION
				" hwhqosUserQueueStatisticsTable "
			::= { hwhqosStat 31 }
		
-- 1.3.6.1.4.1.2011.5.25.132.1.31.1
		hwhqosUserQueueStatisticsEntry OBJECT-TYPE
			SYNTAX HwhqosUserQueueStatisticsEntry
			MAX-ACCESS not-accessible
			STATUS current
			DESCRIPTION
				" hwhqosUserQueueStatisticsEntry "
			INDEX { hwhqosUserQueueStatisticsInterfaceIndex, hwhqosUserQueueStatisticsDirection, hwhqosUserQueueStatisticsSlotNumber, hwhqosUserQueueStatisticsQueueIndex }
			::= { hwhqosUserQueueStatisticsTable 1 }
		
		HwhqosUserQueueStatisticsEntry ::=
			SEQUENCE { 
				hwhqosUserQueueStatisticsInterfaceIndex
					InterfaceIndex,
				hwhqosUserQueueStatisticsDirection
					INTEGER,
				hwhqosUserQueueStatisticsSlotNumber
					Integer32,
				hwhqosUserQueueStatisticsQueueIndex
					INTEGER,
				hwhqosUserQueueStatisticsReset
					INTEGER,
				hwhqosUserQueueStatisticsPassPackets
					Counter64,
				hwhqosUserQueueStatisticsPassBytes
					Counter64,
				hwhqosUserQueueStatisticsDropPackets
					Counter64,
				hwhqosUserQueueStatisticsDropBytes
					Counter64,
				hwhqosUserQueueStatisticsPassPacketsRate
					Counter64,
				hwhqosUserQueueStatisticsPassBytesRate
					Counter64,
				hwhqosUserQueueStatisticsDropPacketsRate
					Counter64,
				hwhqosUserQueueStatisticsDropBytesRate
					Counter64
			 }

-- 1.3.6.1.4.1.2011.5.25.132.1.31.1.1
		hwhqosUserQueueStatisticsInterfaceIndex OBJECT-TYPE
			SYNTAX InterfaceIndex
			MAX-ACCESS read-only
			STATUS current
			DESCRIPTION
				"This object indicates the interface index."
			::= { hwhqosUserQueueStatisticsEntry 1 }
		
-- 1.3.6.1.4.1.2011.5.25.132.1.31.1.2
		hwhqosUserQueueStatisticsDirection OBJECT-TYPE
			SYNTAX INTEGER
				{
				inbound(1),
				outbound(2)
				}
			MAX-ACCESS read-only
			STATUS current
			DESCRIPTION
				"This object indicates the direction where a user queue is applied."
			::= { hwhqosUserQueueStatisticsEntry 2 }
		
-- 1.3.6.1.4.1.2011.5.25.132.1.31.1.3
		hwhqosUserQueueStatisticsSlotNumber OBJECT-TYPE
			SYNTAX Integer32 (0..128)
			MAX-ACCESS read-only
			STATUS current
			DESCRIPTION
				"The value of this object identifies the number of the slot where the interface for applying a user queue is located."
			::= { hwhqosUserQueueStatisticsEntry 3 }
		
-- 1.3.6.1.4.1.2011.5.25.132.1.31.1.4
		hwhqosUserQueueStatisticsQueueIndex OBJECT-TYPE
			SYNTAX INTEGER
				{
				be(1),
				af1(2),
				af2(3),
				af3(4),
				af4(5),
				ef(6),
				cs6(7),
				cs7(8),
				total(9)
				}
			MAX-ACCESS read-only
			STATUS current
			DESCRIPTION
				"This object indicates the priority of a user queue."
			::= { hwhqosUserQueueStatisticsEntry 4 }
		
-- 1.3.6.1.4.1.2011.5.25.132.1.31.1.5
		hwhqosUserQueueStatisticsReset OBJECT-TYPE
			SYNTAX INTEGER { reset(1) }
			MAX-ACCESS read-create
			STATUS current
			DESCRIPTION
				"This object indicates the resetting of statistics."
			::= { hwhqosUserQueueStatisticsEntry 5 }
		
-- 1.3.6.1.4.1.2011.5.25.132.1.31.1.6
		hwhqosUserQueueStatisticsPassPackets OBJECT-TYPE
			SYNTAX Counter64
			MAX-ACCESS read-only
			STATUS current
			DESCRIPTION
				"This object indicates the number of passed packets."
			::= { hwhqosUserQueueStatisticsEntry 6 }
		
-- 1.3.6.1.4.1.2011.5.25.132.1.31.1.7
		hwhqosUserQueueStatisticsPassBytes OBJECT-TYPE
			SYNTAX Counter64
			MAX-ACCESS read-only
			STATUS current
			DESCRIPTION
				"This object indicates the number of passed bytes."
			::= { hwhqosUserQueueStatisticsEntry 7 }
		
-- 1.3.6.1.4.1.2011.5.25.132.1.31.1.8
		hwhqosUserQueueStatisticsDropPackets OBJECT-TYPE
			SYNTAX Counter64
			MAX-ACCESS read-only
			STATUS current
			DESCRIPTION
				"This object indicates the number of discarded packets."
			::= { hwhqosUserQueueStatisticsEntry 8 }
		
-- 1.3.6.1.4.1.2011.5.25.132.1.31.1.9
		hwhqosUserQueueStatisticsDropBytes OBJECT-TYPE
			SYNTAX Counter64
			MAX-ACCESS read-only
			STATUS current
			DESCRIPTION
				"This object indicates the number of discarded bytes."
			::= { hwhqosUserQueueStatisticsEntry 9 }
		
-- 1.3.6.1.4.1.2011.5.25.132.1.31.1.10
		hwhqosUserQueueStatisticsPassPacketsRate OBJECT-TYPE
			SYNTAX Counter64
			MAX-ACCESS read-only
			STATUS current
			DESCRIPTION
				"This object indicates the packet pass rate."
			::= { hwhqosUserQueueStatisticsEntry 10 }
		
-- 1.3.6.1.4.1.2011.5.25.132.1.31.1.11
		hwhqosUserQueueStatisticsPassBytesRate OBJECT-TYPE
			SYNTAX Counter64
			MAX-ACCESS read-only
			STATUS current
			DESCRIPTION
				"This object indicates the byte pass rate."
			::= { hwhqosUserQueueStatisticsEntry 11 }
		
-- 1.3.6.1.4.1.2011.5.25.132.1.31.1.12
		hwhqosUserQueueStatisticsDropPacketsRate OBJECT-TYPE
			SYNTAX Counter64
			MAX-ACCESS read-only
			STATUS current
			DESCRIPTION
				"This object indicates the packet discarding rate."
			::= { hwhqosUserQueueStatisticsEntry 12 }
		
-- 1.3.6.1.4.1.2011.5.25.132.1.31.1.13
		hwhqosUserQueueStatisticsDropBytesRate OBJECT-TYPE
			SYNTAX Counter64
			MAX-ACCESS read-only
			STATUS current
			DESCRIPTION
				"This object indicates the byte discarding rate."
			::= { hwhqosUserQueueStatisticsEntry 13 }
		
--  ******************************************************************
-- 
-- hwhqosUserQueueClassifierStatisticsTable
-- 
-- ******************************************************************
-- 1.3.6.1.4.1.2011.5.25.132.1.32
		hwhqosUserQueueClassifierStatisticsTable OBJECT-TYPE
			SYNTAX SEQUENCE OF HwhqosUserQueueClassifierStatisticsEntry
			MAX-ACCESS not-accessible
			STATUS current
			DESCRIPTION
				" hwhqosUserQueueStatisticsTable "
			::= { hwhqosStat 32 }
		
-- 1.3.6.1.4.1.2011.5.25.132.1.32.1
		hwhqosUserQueueClassifierStatisticsEntry OBJECT-TYPE
			SYNTAX HwhqosUserQueueClassifierStatisticsEntry
			MAX-ACCESS not-accessible
			STATUS current
			DESCRIPTION
				" hwhqosUserQueueStatisticsEntry "
			INDEX { hwhqosUserQueueClassifierStatisticsInterfaceIndex, hwhqosUserQueueClassifierStatisticsDirection, hwhqosUserQueueClassifierStatisticsClassifierName, hwhqosUserQueueClassifierStatisticsSlotNumber, hwhqosUserQueueClassifierStatisticsQueueIndex
				 }
			::= { hwhqosUserQueueClassifierStatisticsTable 1 }
		
		HwhqosUserQueueClassifierStatisticsEntry ::=
			SEQUENCE { 
				hwhqosUserQueueClassifierStatisticsInterfaceIndex
					InterfaceIndex,
				hwhqosUserQueueClassifierStatisticsDirection
					INTEGER,
				hwhqosUserQueueClassifierStatisticsClassifierName
					OCTET STRING,
				hwhqosUserQueueClassifierStatisticsSlotNumber
					Integer32,
				hwhqosUserQueueClassifierStatisticsQueueIndex
					INTEGER,
				hwhqosUserQueueClassifierStatisticsReset
					INTEGER,
				hwhqosUserQueueClassifierStatisticsPassPackets
					Counter64,
				hwhqosUserQueueClassifierStatisticsPassBytes
					Counter64,
				hwhqosUserQueueClassifierStatisticsDropPackets
					Counter64,
				hwhqosUserQueueClassifierStatisticsDropBytes
					Counter64,
				hwhqosUserQueueClassifierStatisticsPassPacketsRate
					Counter64,
				hwhqosUserQueueClassifierStatisticsPassBytesRate
					Counter64,
				hwhqosUserQueueClassifierStatisticsDropPacketsRate
					Counter64,
				hwhqosUserQueueClassifierStatisticsDropBytesRate
					Counter64
			 }

-- 1.3.6.1.4.1.2011.5.25.132.1.32.1.1
		hwhqosUserQueueClassifierStatisticsInterfaceIndex OBJECT-TYPE
			SYNTAX InterfaceIndex
			MAX-ACCESS read-only
			STATUS current
			DESCRIPTION
				"This object indicates the interface index."
			::= { hwhqosUserQueueClassifierStatisticsEntry 1 }
		
-- 1.3.6.1.4.1.2011.5.25.132.1.32.1.2
		hwhqosUserQueueClassifierStatisticsDirection OBJECT-TYPE
			SYNTAX INTEGER
				{
				inbound(1),
				outbound(2)
				}
			MAX-ACCESS read-only
			STATUS current
			DESCRIPTION
				"This object indicates the direction where a policy is applied."
			::= { hwhqosUserQueueClassifierStatisticsEntry 2 }
		
-- 1.3.6.1.4.1.2011.5.25.132.1.32.1.3
		hwhqosUserQueueClassifierStatisticsClassifierName OBJECT-TYPE
			SYNTAX OCTET STRING (SIZE (1..31))
			MAX-ACCESS read-only
			STATUS current
			DESCRIPTION
				"The value of this object identifies the name of a class template."
			::= { hwhqosUserQueueClassifierStatisticsEntry 3 }
		
-- 1.3.6.1.4.1.2011.5.25.132.1.32.1.4
		hwhqosUserQueueClassifierStatisticsSlotNumber OBJECT-TYPE
			SYNTAX Integer32 (0..128)
			MAX-ACCESS read-only
			STATUS current
			DESCRIPTION
				"The value of this object identifies the number of the slot where the interface for applying a policy is located."
			::= { hwhqosUserQueueClassifierStatisticsEntry 4 }
		
-- 1.3.6.1.4.1.2011.5.25.132.1.32.1.5
		hwhqosUserQueueClassifierStatisticsQueueIndex OBJECT-TYPE
			SYNTAX INTEGER
				{
				be(1),
				af1(2),
				af2(3),
				af3(4),
				af4(5),
				ef(6),
				cs6(7),
				cs7(8),
				total(9)
				}
			MAX-ACCESS read-only
			STATUS current
			DESCRIPTION
				"This object indicates the priority of a user queue."
			::= { hwhqosUserQueueClassifierStatisticsEntry 5 }
		
-- 1.3.6.1.4.1.2011.5.25.132.1.32.1.6
		hwhqosUserQueueClassifierStatisticsReset OBJECT-TYPE
			SYNTAX INTEGER { reset(1) }
			MAX-ACCESS read-create
			STATUS current
			DESCRIPTION
				"This object indicates the resetting of statistics."
			::= { hwhqosUserQueueClassifierStatisticsEntry 6 }
		
-- 1.3.6.1.4.1.2011.5.25.132.1.32.1.7
		hwhqosUserQueueClassifierStatisticsPassPackets OBJECT-TYPE
			SYNTAX Counter64
			MAX-ACCESS read-only
			STATUS current
			DESCRIPTION
				"This object indicates the number of passed packets."
			::= { hwhqosUserQueueClassifierStatisticsEntry 7 }
		
-- 1.3.6.1.4.1.2011.5.25.132.1.32.1.8
		hwhqosUserQueueClassifierStatisticsPassBytes OBJECT-TYPE
			SYNTAX Counter64
			MAX-ACCESS read-only
			STATUS current
			DESCRIPTION
				"This object indicates the number of passed bytes."
			::= { hwhqosUserQueueClassifierStatisticsEntry 8 }
		
-- 1.3.6.1.4.1.2011.5.25.132.1.32.1.9
		hwhqosUserQueueClassifierStatisticsDropPackets OBJECT-TYPE
			SYNTAX Counter64
			MAX-ACCESS read-only
			STATUS current
			DESCRIPTION
				"This object indicates the number of discarded packets."
			::= { hwhqosUserQueueClassifierStatisticsEntry 9 }
		
-- 1.3.6.1.4.1.2011.5.25.132.1.32.1.10
		hwhqosUserQueueClassifierStatisticsDropBytes OBJECT-TYPE
			SYNTAX Counter64
			MAX-ACCESS read-only
			STATUS current
			DESCRIPTION
				"This object indicates the number of discarded bytes."
			::= { hwhqosUserQueueClassifierStatisticsEntry 10 }
		
-- 1.3.6.1.4.1.2011.5.25.132.1.32.1.11
		hwhqosUserQueueClassifierStatisticsPassPacketsRate OBJECT-TYPE
			SYNTAX Counter64
			MAX-ACCESS read-only
			STATUS current
			DESCRIPTION
				"This object indicates the packet pass rate."
			::= { hwhqosUserQueueClassifierStatisticsEntry 11 }
		
-- 1.3.6.1.4.1.2011.5.25.132.1.32.1.12
		hwhqosUserQueueClassifierStatisticsPassBytesRate OBJECT-TYPE
			SYNTAX Counter64
			MAX-ACCESS read-only
			STATUS current
			DESCRIPTION
				"This object indicates the byte pass rate."
			::= { hwhqosUserQueueClassifierStatisticsEntry 12 }
		
-- 1.3.6.1.4.1.2011.5.25.132.1.32.1.13
		hwhqosUserQueueClassifierStatisticsDropPacketsRate OBJECT-TYPE
			SYNTAX Counter64
			MAX-ACCESS read-only
			STATUS current
			DESCRIPTION
				"This object indicates the packet discarding rate."
			::= { hwhqosUserQueueClassifierStatisticsEntry 13 }
		
-- 1.3.6.1.4.1.2011.5.25.132.1.32.1.14
		hwhqosUserQueueClassifierStatisticsDropBytesRate OBJECT-TYPE
			SYNTAX Counter64
			MAX-ACCESS read-only
			STATUS current
			DESCRIPTION
				"This object indicates the byte discarding rate."
			::= { hwhqosUserQueueClassifierStatisticsEntry 14 }
		
--  ******************************************************************
-- 
-- hwhqosUserGroupQueueStatisticsTable
-- 
-- ******************************************************************
-- 1.3.6.1.4.1.2011.5.25.132.1.33
		hwhqosUserGroupQueueStatisticsTable OBJECT-TYPE
			SYNTAX SEQUENCE OF HwhqosUserGroupQueueStatisticsEntry
			MAX-ACCESS not-accessible
			STATUS current
			DESCRIPTION
				" hwhqosUserGroupQueueStatisticsTable "
			::= { hwhqosStat 33 }
		
-- 1.3.6.1.4.1.2011.5.25.132.1.33.1
		hwhqosUserGroupQueueStatisticsEntry OBJECT-TYPE
			SYNTAX HwhqosUserGroupQueueStatisticsEntry
			MAX-ACCESS not-accessible
			STATUS current
			DESCRIPTION
				" hwhqosUserGroupQueueStatisticsEntry "
			INDEX { hwhqosUserGroupQueueStatisticsGroupName, hwhqosUserGroupQueueStatisticsDirection, hwhqosUserGroupQueueStatisticsSlotNumber, hwhqosUserGroupQueueStatisticsQueueIndex }
			::= { hwhqosUserGroupQueueStatisticsTable 1 }
		
		HwhqosUserGroupQueueStatisticsEntry ::=
			SEQUENCE { 
				hwhqosUserGroupQueueStatisticsGroupName
					OCTET STRING,
				hwhqosUserGroupQueueStatisticsDirection
					INTEGER,
				hwhqosUserGroupQueueStatisticsSlotNumber
					Integer32,
				hwhqosUserGroupQueueStatisticsQueueIndex
					INTEGER,
				hwhqosUserGroupQueueStatisticsReset
					INTEGER,
				hwhqosUserGroupQueueStatisticsPassPackets
					Counter64,
				hwhqosUserGroupQueueStatisticsPassBytes
					Counter64,
				hwhqosUserGroupQueueStatisticsDropPackets
					Counter64,
				hwhqosUserGroupQueueStatisticsDropBytes
					Counter64,
				hwhqosUserGroupQueueStatisticsPassPacketsRate
					Counter64,
				hwhqosUserGroupQueueStatisticsPassBytesRate
					Counter64,
				hwhqosUserGroupQueueStatisticsDropPacketsRate
					Counter64,
				hwhqosUserGroupQueueStatisticsDropBytesRate
					Counter64
			 }

-- 1.3.6.1.4.1.2011.5.25.132.1.33.1.1
		hwhqosUserGroupQueueStatisticsGroupName OBJECT-TYPE
			SYNTAX OCTET STRING (SIZE (1..31))
			MAX-ACCESS read-only
			STATUS current
			DESCRIPTION
				"The value of this object identifies the name of a user group queue."
			::= { hwhqosUserGroupQueueStatisticsEntry 1 }
		
-- 1.3.6.1.4.1.2011.5.25.132.1.33.1.2
		hwhqosUserGroupQueueStatisticsDirection OBJECT-TYPE
			SYNTAX INTEGER
				{
				inbound(1),
				outbound(2)
				}
			MAX-ACCESS read-only
			STATUS current
			DESCRIPTION
				"This object indicates the direction where a user group queue template is applied."
			::= { hwhqosUserGroupQueueStatisticsEntry 2 }
		
-- 1.3.6.1.4.1.2011.5.25.132.1.33.1.3
		hwhqosUserGroupQueueStatisticsSlotNumber OBJECT-TYPE
			SYNTAX Integer32 (0..128)
			MAX-ACCESS read-only
			STATUS current
			DESCRIPTION
				"The value of this object identifies the number of the slot where a user group queue template is applied."
			::= { hwhqosUserGroupQueueStatisticsEntry 3 }
		
-- 1.3.6.1.4.1.2011.5.25.132.1.33.1.4
		hwhqosUserGroupQueueStatisticsQueueIndex OBJECT-TYPE
			SYNTAX INTEGER
				{
				be(1),
				af1(2),
				af2(3),
				af3(4),
				af4(5),
				ef(6),
				cs6(7),
				cs7(8),
				total(9)
				}
			MAX-ACCESS read-only
			STATUS current
			DESCRIPTION
				" hwhqosUserGroupQueueStatisticsQueueIndex "
			::= { hwhqosUserGroupQueueStatisticsEntry 4 }
		
-- 1.3.6.1.4.1.2011.5.25.132.1.33.1.5
		hwhqosUserGroupQueueStatisticsReset OBJECT-TYPE
			SYNTAX INTEGER { reset(1) }
			MAX-ACCESS read-create
			STATUS current
			DESCRIPTION
				"This object indicates the resetting of statistics."
			::= { hwhqosUserGroupQueueStatisticsEntry 5 }
		
-- 1.3.6.1.4.1.2011.5.25.132.1.33.1.6
		hwhqosUserGroupQueueStatisticsPassPackets OBJECT-TYPE
			SYNTAX Counter64
			MAX-ACCESS read-only
			STATUS current
			DESCRIPTION
				"This object indicates the number of passed packets."
			::= { hwhqosUserGroupQueueStatisticsEntry 6 }
		
-- 1.3.6.1.4.1.2011.5.25.132.1.33.1.7
		hwhqosUserGroupQueueStatisticsPassBytes OBJECT-TYPE
			SYNTAX Counter64
			MAX-ACCESS read-only
			STATUS current
			DESCRIPTION
				"This object indicates the number of passed bytes."
			::= { hwhqosUserGroupQueueStatisticsEntry 7 }
		
-- 1.3.6.1.4.1.2011.5.25.132.1.33.1.8
		hwhqosUserGroupQueueStatisticsDropPackets OBJECT-TYPE
			SYNTAX Counter64
			MAX-ACCESS read-only
			STATUS current
			DESCRIPTION
				"This object indicates the number of discarded packets."
			::= { hwhqosUserGroupQueueStatisticsEntry 8 }
		
-- 1.3.6.1.4.1.2011.5.25.132.1.33.1.9
		hwhqosUserGroupQueueStatisticsDropBytes OBJECT-TYPE
			SYNTAX Counter64
			MAX-ACCESS read-only
			STATUS current
			DESCRIPTION
				"This object indicates the number of discarded bytes."
			::= { hwhqosUserGroupQueueStatisticsEntry 9 }
		
-- 1.3.6.1.4.1.2011.5.25.132.1.33.1.10
		hwhqosUserGroupQueueStatisticsPassPacketsRate OBJECT-TYPE
			SYNTAX Counter64
			MAX-ACCESS read-only
			STATUS current
			DESCRIPTION
				" hwhqosUserGroupQueueStatisticsPassPacketsRate."
			::= { hwhqosUserGroupQueueStatisticsEntry 10 }
		
-- 1.3.6.1.4.1.2011.5.25.132.1.33.1.11
		hwhqosUserGroupQueueStatisticsPassBytesRate OBJECT-TYPE
			SYNTAX Counter64
			MAX-ACCESS read-only
			STATUS current
			DESCRIPTION
				" hwhqosUserGroupQueueStatisticsPassBytesRate."
			::= { hwhqosUserGroupQueueStatisticsEntry 11 }
		
-- 1.3.6.1.4.1.2011.5.25.132.1.33.1.12
		hwhqosUserGroupQueueStatisticsDropPacketsRate OBJECT-TYPE
			SYNTAX Counter64
			MAX-ACCESS read-only
			STATUS current
			DESCRIPTION
				" hwhqosUserGroupQueueStatisticsDropPacketsRate."
			::= { hwhqosUserGroupQueueStatisticsEntry 12 }
		
-- 1.3.6.1.4.1.2011.5.25.132.1.33.1.13
		-- 1.3.6.1.4.1.2011.5.25.132.1.33.1.13
		hwhqosUserGroupQueueStatisticsDropBytesRate OBJECT-TYPE
			SYNTAX Counter64
			MAX-ACCESS read-only
			STATUS current
			DESCRIPTION
				" hwhqosUserGroupQueueStatisticsDropBytesRate."
			::= { hwhqosUserGroupQueueStatisticsEntry 13 }
		
-- 1.3.6.1.4.1.2011.5.25.132.1.34
		hwhqosFlowQueueShaperTable OBJECT-TYPE
			SYNTAX SEQUENCE OF HwhqosFlowQueueShaperEntry
			MAX-ACCESS not-accessible
			STATUS current
			DESCRIPTION
				"Description."
			::= { hwhqosStat 34 }
		
-- 1.3.6.1.4.1.2011.5.25.132.1.34.1
		hwhqosFlowQueueShaperEntry OBJECT-TYPE
			SYNTAX HwhqosFlowQueueShaperEntry
			MAX-ACCESS not-accessible
			STATUS current
			DESCRIPTION
				"Description."
			INDEX { hwhqosFlowQueueName }
			::= { hwhqosFlowQueueShaperTable 1 }
		
		HwhqosFlowQueueShaperEntry ::=
			SEQUENCE { 
				hwhqosFlowQueueShaperBE
					INTEGER,
				hwhqosFlowQueueShaperAF1
					INTEGER,
				hwhqosFlowQueueShaperAF2
					INTEGER,
				hwhqosFlowQueueShaperAF3
					INTEGER,
				hwhqosFlowQueueShaperAF4
					INTEGER,
				hwhqosFlowQueueShaperEF
					INTEGER,
				hwhqosFlowQueueShaperCS6
					INTEGER,
				hwhqosFlowQueueShaperCS7
					INTEGER,
				hwhqosFlowQueueShaperValue
					Integer32,
				hwhqosFlowQueueShaperRowStatus
					RowStatus
			 }

-- 1.3.6.1.4.1.2011.5.25.132.1.34.1.1
		hwhqosFlowQueueShaperBE OBJECT-TYPE
			SYNTAX INTEGER
				{
				enable(1),
				disable(2)
				}
			MAX-ACCESS read-create
			STATUS current
			DESCRIPTION
				"Description."
			::= { hwhqosFlowQueueShaperEntry 1 }
		
-- 1.3.6.1.4.1.2011.5.25.132.1.34.1.2
		hwhqosFlowQueueShaperAF1 OBJECT-TYPE
			SYNTAX INTEGER
				{
				enable(1),
				disable(2)
				}
			MAX-ACCESS read-create
			STATUS current
			DESCRIPTION
				"Description."
			::= { hwhqosFlowQueueShaperEntry 2 }
		
-- 1.3.6.1.4.1.2011.5.25.132.1.34.1.3
		hwhqosFlowQueueShaperAF2 OBJECT-TYPE
			SYNTAX INTEGER
				{
				enable(1),
				disable(2)
				}
			MAX-ACCESS read-create
			STATUS current
			DESCRIPTION
				"Description."
			::= { hwhqosFlowQueueShaperEntry 3 }
		
-- 1.3.6.1.4.1.2011.5.25.132.1.34.1.4
		hwhqosFlowQueueShaperAF3 OBJECT-TYPE
			SYNTAX INTEGER
				{
				enable(1),
				disable(2)
				}
			MAX-ACCESS read-create
			STATUS current
			DESCRIPTION
				"Description."
			::= { hwhqosFlowQueueShaperEntry 4 }
		
-- 1.3.6.1.4.1.2011.5.25.132.1.34.1.5
		hwhqosFlowQueueShaperAF4 OBJECT-TYPE
			SYNTAX INTEGER
				{
				enable(1),
				disable(2)
				}
			MAX-ACCESS read-create
			STATUS current
			DESCRIPTION
				"Description."
			::= { hwhqosFlowQueueShaperEntry 5 }
		
-- 1.3.6.1.4.1.2011.5.25.132.1.34.1.6
		hwhqosFlowQueueShaperEF OBJECT-TYPE
			SYNTAX INTEGER
				{
				enable(1),
				disable(2)
				}
			MAX-ACCESS read-create
			STATUS current
			DESCRIPTION
				"Description."
			::= { hwhqosFlowQueueShaperEntry 6 }
		
-- 1.3.6.1.4.1.2011.5.25.132.1.34.1.7
		hwhqosFlowQueueShaperCS6 OBJECT-TYPE
			SYNTAX INTEGER
				{
				enable(1),
				disable(2)
				}
			MAX-ACCESS read-create
			STATUS current
			DESCRIPTION
				"Description."
			::= { hwhqosFlowQueueShaperEntry 7 }
		
-- 1.3.6.1.4.1.2011.5.25.132.1.34.1.8
		hwhqosFlowQueueShaperCS7 OBJECT-TYPE
			SYNTAX INTEGER
				{
				enable(1),
				disable(2)
				}
			MAX-ACCESS read-create
			STATUS current
			DESCRIPTION
				"Description."
			::= { hwhqosFlowQueueShaperEntry 8 }
		
-- 1.3.6.1.4.1.2011.5.25.132.1.34.1.9
		hwhqosFlowQueueShaperValue OBJECT-TYPE
			SYNTAX Integer32 (1..10000000)
			MAX-ACCESS read-create
			STATUS current
			DESCRIPTION
				"Description."
			::= { hwhqosFlowQueueShaperEntry 9 }
		
-- 1.3.6.1.4.1.2011.5.25.132.1.34.1.50
		hwhqosFlowQueueShaperRowStatus OBJECT-TYPE
			SYNTAX RowStatus
			MAX-ACCESS read-create
			STATUS current
			DESCRIPTION
				"Description."
			::= { hwhqosFlowQueueShaperEntry 50 }
		
-- 1.3.6.1.4.1.2011.5.25.132.1.35
		hwhqosWredQueueDepthTable OBJECT-TYPE
			SYNTAX SEQUENCE OF HwhqosWredQueueDepthEntry
			MAX-ACCESS not-accessible
			STATUS current
			DESCRIPTION
				"Description."
			::= { hwhqosStat 35 }
		
-- 1.3.6.1.4.1.2011.5.25.132.1.35.1
		hwhqosWredQueueDepthEntry OBJECT-TYPE
			SYNTAX HwhqosWredQueueDepthEntry
			MAX-ACCESS not-accessible
			STATUS current
			DESCRIPTION
				"Description."
			INDEX { hwhqosWredQueueDepthType, hwhqosWredQueueDepthWredName }
			::= { hwhqosWredQueueDepthTable 1 }
		
		HwhqosWredQueueDepthEntry ::=
			SEQUENCE { 
				hwhqosWredQueueDepthType
					INTEGER,
				hwhqosWredQueueDepthWredName
					OCTET STRING,
				hwhqosWredQueueDepthValue
					Integer32,
				hwhqosWredQueueDepthRowStatus
					RowStatus
			 }

-- 1.3.6.1.4.1.2011.5.25.132.1.35.1.1
		hwhqosWredQueueDepthType OBJECT-TYPE
			SYNTAX INTEGER
				{
				flowwred(1),
				portwred(2)
				}
			MAX-ACCESS read-only
			STATUS current
			DESCRIPTION
				"Description."
			::= { hwhqosWredQueueDepthEntry 1 }
		
-- 1.3.6.1.4.1.2011.5.25.132.1.35.1.2
		hwhqosWredQueueDepthWredName OBJECT-TYPE
			SYNTAX OCTET STRING (SIZE (1..31))
			MAX-ACCESS read-only
			STATUS current
			DESCRIPTION
				"Description."
			::= { hwhqosWredQueueDepthEntry 2 }
		
-- 1.3.6.1.4.1.2011.5.25.132.1.35.1.3
		hwhqosWredQueueDepthValue OBJECT-TYPE
			SYNTAX Integer32 (1..131072)
			MAX-ACCESS read-create
			STATUS current
			DESCRIPTION
				"Description."
			::= { hwhqosWredQueueDepthEntry 3 }
		
-- 1.3.6.1.4.1.2011.5.25.132.1.35.1.50
		hwhqosWredQueueDepthRowStatus OBJECT-TYPE
			SYNTAX RowStatus
			MAX-ACCESS read-create
			STATUS current
			DESCRIPTION
				"Description."
			::= { hwhqosWredQueueDepthEntry 50 }
		
-- 1.3.6.1.4.1.2011.5.25.132.1.36
		hwhqosBandwidthCheckTable OBJECT-TYPE
			SYNTAX SEQUENCE OF HwhqosBandwidthCheckEntry
			MAX-ACCESS not-accessible
			STATUS current
			DESCRIPTION
				"Description."
			::= { hwhqosStat 36 }
		
-- 1.3.6.1.4.1.2011.5.25.132.1.36.1
		hwhqosBandwidthCheckEntry OBJECT-TYPE
			SYNTAX HwhqosBandwidthCheckEntry
			MAX-ACCESS not-accessible
			STATUS current
			DESCRIPTION
				"Description."
			INDEX { hwhqosBandwidthCheckInterfaceIndex, hwhqosBandwidthCheckDirection }
			::= { hwhqosBandwidthCheckTable 1 }
		
		HwhqosBandwidthCheckEntry ::=
			SEQUENCE { 
				hwhqosBandwidthCheckInterfaceIndex
					InterfaceIndex,
				hwhqosBandwidthCheckDirection
					INTEGER,
				hwhqosBandwidthCheckValue
					INTEGER,
				hwhqosBandwidthCheckRowStatus
					RowStatus
			 }

-- 1.3.6.1.4.1.2011.5.25.132.1.36.1.1
		hwhqosBandwidthCheckInterfaceIndex OBJECT-TYPE
			SYNTAX InterfaceIndex
			MAX-ACCESS read-only
			STATUS current
			DESCRIPTION
				"Description."
			::= { hwhqosBandwidthCheckEntry 1 }
		
-- 1.3.6.1.4.1.2011.5.25.132.1.36.1.2
		hwhqosBandwidthCheckDirection OBJECT-TYPE
			SYNTAX INTEGER
				{
				inbound(1),
				outbound(2)
				}
			MAX-ACCESS read-create
			STATUS current
			DESCRIPTION
				"Description."
			::= { hwhqosBandwidthCheckEntry 2 }
		
-- 1.3.6.1.4.1.2011.5.25.132.1.36.1.3
		hwhqosBandwidthCheckValue OBJECT-TYPE
			SYNTAX INTEGER
				{
				enable(1),
				disable(2)
				}
			MAX-ACCESS read-create
			STATUS current
			DESCRIPTION
				"Description."
			::= { hwhqosBandwidthCheckEntry 3 }
		
-- 1.3.6.1.4.1.2011.5.25.132.1.36.1.50
		hwhqosBandwidthCheckRowStatus OBJECT-TYPE
			SYNTAX RowStatus
			MAX-ACCESS read-create
			STATUS current
			DESCRIPTION
				"Description."
			::= { hwhqosBandwidthCheckEntry 50 }
		
-- 1.3.6.1.4.1.2011.5.25.132.1.37
		hwhqosServiceIdentifyPolicyTable OBJECT-TYPE
			SYNTAX SEQUENCE OF HwhqosServiceIdentifyPolicyEntry
			MAX-ACCESS not-accessible
			STATUS current
			DESCRIPTION
				"Description."
			::= { hwhqosStat 37 }
		
-- 1.3.6.1.4.1.2011.5.25.132.1.37.1
		hwhqosServiceIdentifyPolicyEntry OBJECT-TYPE
			SYNTAX HwhqosServiceIdentifyPolicyEntry
			MAX-ACCESS not-accessible
			STATUS current
			DESCRIPTION
				"Description."
			INDEX { hwhqosServiceIdentifyPolicyName }
			::= { hwhqosServiceIdentifyPolicyTable 1 }
		
		HwhqosServiceIdentifyPolicyEntry ::=
			SEQUENCE { 
				hwhqosServiceIdentifyPolicyName
					OCTET STRING,
				hwhqosServiceIdentifyPolicyRowStatus
					RowStatus
			 }

-- 1.3.6.1.4.1.2011.5.25.132.1.37.1.1
		hwhqosServiceIdentifyPolicyName OBJECT-TYPE
			SYNTAX OCTET STRING (SIZE (1..31))
			MAX-ACCESS read-only
			STATUS current
			DESCRIPTION
				"Description."
			::= { hwhqosServiceIdentifyPolicyEntry 1 }
		
-- 1.3.6.1.4.1.2011.5.25.132.1.37.1.50
		hwhqosServiceIdentifyPolicyRowStatus OBJECT-TYPE
			SYNTAX RowStatus
			MAX-ACCESS read-create
			STATUS current
			DESCRIPTION
				"Description."
			::= { hwhqosServiceIdentifyPolicyEntry 50 }
		
-- 1.3.6.1.4.1.2011.5.25.132.1.38
		hwhqosServiceIdentifyPolicyApplyTable OBJECT-TYPE
			SYNTAX SEQUENCE OF HwhqosServiceIdentifyPolicyApplyEntry
			MAX-ACCESS not-accessible
			STATUS current
			DESCRIPTION
				"Description."
			::= { hwhqosStat 38 }
		
-- 1.3.6.1.4.1.2011.5.25.132.1.38.1
		hwhqosServiceIdentifyPolicyApplyEntry OBJECT-TYPE
			SYNTAX HwhqosServiceIdentifyPolicyApplyEntry
			MAX-ACCESS not-accessible
			STATUS current
			DESCRIPTION
				"Description."
			INDEX { hwhqosServiceIdentifyPolicyApplyInterfaceIndex }
			::= { hwhqosServiceIdentifyPolicyApplyTable 1 }
		
		HwhqosServiceIdentifyPolicyApplyEntry ::=
			SEQUENCE { 
				hwhqosServiceIdentifyPolicyApplyInterfaceIndex
					InterfaceIndex,
				hwhqosServiceIdentifyPolicyApplyName
					OCTET STRING,
				hwhqosServiceIdentifyPolicyApplyRowStatus
					RowStatus
			 }

-- 1.3.6.1.4.1.2011.5.25.132.1.38.1.1
		hwhqosServiceIdentifyPolicyApplyInterfaceIndex OBJECT-TYPE
			SYNTAX InterfaceIndex
			MAX-ACCESS read-only
			STATUS current
			DESCRIPTION
				"Description."
			::= { hwhqosServiceIdentifyPolicyApplyEntry 1 }
		
-- 1.3.6.1.4.1.2011.5.25.132.1.38.1.2
		hwhqosServiceIdentifyPolicyApplyName OBJECT-TYPE
			SYNTAX OCTET STRING (SIZE (1..31))
			MAX-ACCESS read-create
			STATUS current
			DESCRIPTION
				"Description."
			::= { hwhqosServiceIdentifyPolicyApplyEntry 2 }
		
-- 1.3.6.1.4.1.2011.5.25.132.1.38.1.50
		hwhqosServiceIdentifyPolicyApplyRowStatus OBJECT-TYPE
			SYNTAX RowStatus
			MAX-ACCESS read-create
			STATUS current
			DESCRIPTION
				"Description."
			::= { hwhqosServiceIdentifyPolicyApplyEntry 50 }
		
-- 1.3.6.1.4.1.2011.5.25.132.1.39
		hwhqosServiceIdentifyPolicyTypeTable OBJECT-TYPE
			SYNTAX SEQUENCE OF HwhqosServiceIdentifyPolicyTypeEntry
			MAX-ACCESS not-accessible
			STATUS current
			DESCRIPTION
				"Description."
			::= { hwhqosStat 39 }
		
-- 1.3.6.1.4.1.2011.5.25.132.1.39.1
		hwhqosServiceIdentifyPolicyTypeEntry OBJECT-TYPE
			SYNTAX HwhqosServiceIdentifyPolicyTypeEntry
			MAX-ACCESS not-accessible
			STATUS current
			DESCRIPTION
				"Description."
			INDEX { hwhqosServiceIdentifyPolicyName }
			::= { hwhqosServiceIdentifyPolicyTypeTable 1 }
		
		HwhqosServiceIdentifyPolicyTypeEntry ::=
			SEQUENCE { 
				hwhqosServiceIdentifyPolicyTypeValue
					INTEGER,
				hwhqosServiceIdentifyPolicyTypeRowStatus
					RowStatus
			 }

-- 1.3.6.1.4.1.2011.5.25.132.1.39.1.1
		hwhqosServiceIdentifyPolicyTypeValue OBJECT-TYPE
			SYNTAX INTEGER
				{
				innervlan(1),
				outervlan(2),
				cosinnervlan(3),
				cosoutervlan(4),
				dscp(5),
				dhcpoption60(6)
				}
			MAX-ACCESS read-create
			STATUS current
			DESCRIPTION
				"Description."
			::= { hwhqosServiceIdentifyPolicyTypeEntry 1 }
		
-- 1.3.6.1.4.1.2011.5.25.132.1.39.1.50
		hwhqosServiceIdentifyPolicyTypeRowStatus OBJECT-TYPE
			SYNTAX RowStatus
			MAX-ACCESS read-create
			STATUS current
			DESCRIPTION
				"Description."
			::= { hwhqosServiceIdentifyPolicyTypeEntry 50 }
		
-- 1.3.6.1.4.1.2011.5.25.132.1.40
		hwhqosServiceIdentifyPolicyVlanTable OBJECT-TYPE
			SYNTAX SEQUENCE OF HwhqosServiceIdentifyPolicyVlanEntry
			MAX-ACCESS not-accessible
			STATUS current
			DESCRIPTION
				"Description."
			::= { hwhqosStat 40 }
		
-- 1.3.6.1.4.1.2011.5.25.132.1.40.1
		hwhqosServiceIdentifyPolicyVlanEntry OBJECT-TYPE
			SYNTAX HwhqosServiceIdentifyPolicyVlanEntry
			MAX-ACCESS not-accessible
			STATUS current
			DESCRIPTION
				"Description."
			INDEX { hwhqosServiceIdentifyPolicyName, hwhqosServiceIdentifyPolicyVlanID }
			::= { hwhqosServiceIdentifyPolicyVlanTable 1 }
		
		HwhqosServiceIdentifyPolicyVlanEntry ::=
			SEQUENCE { 
				hwhqosServiceIdentifyPolicyVlanID
					Integer32,
				hwhqosServiceIdentifyPolicyVlanDomainName
					OCTET STRING,
				hwhqosServiceIdentifyPolicyVlanRowStatus
					RowStatus
			 }

-- 1.3.6.1.4.1.2011.5.25.132.1.40.1.1
		hwhqosServiceIdentifyPolicyVlanID OBJECT-TYPE
			SYNTAX Integer32 (1..4094)
			MAX-ACCESS read-only
			STATUS current
			DESCRIPTION
				"Description."
			::= { hwhqosServiceIdentifyPolicyVlanEntry 1 }
		
-- 1.3.6.1.4.1.2011.5.25.132.1.40.1.2
		hwhqosServiceIdentifyPolicyVlanDomainName OBJECT-TYPE
			SYNTAX OCTET STRING (SIZE (1..31))
			MAX-ACCESS read-create
			STATUS current
			DESCRIPTION
				"Description."
			::= { hwhqosServiceIdentifyPolicyVlanEntry 2 }
		
-- 1.3.6.1.4.1.2011.5.25.132.1.40.1.50
		hwhqosServiceIdentifyPolicyVlanRowStatus OBJECT-TYPE
			SYNTAX RowStatus
			MAX-ACCESS read-create
			STATUS current
			DESCRIPTION
				"Description."
			::= { hwhqosServiceIdentifyPolicyVlanEntry 50 }
		
-- 1.3.6.1.4.1.2011.5.25.132.1.41
		hwhqosServiceIdentifyPolicy8021pTable OBJECT-TYPE
			SYNTAX SEQUENCE OF HwhqosServiceIdentifyPolicy8021pEntry
			MAX-ACCESS not-accessible
			STATUS current
			DESCRIPTION
				"Description."
			::= { hwhqosStat 41 }
		
-- 1.3.6.1.4.1.2011.5.25.132.1.41.1
		hwhqosServiceIdentifyPolicy8021pEntry OBJECT-TYPE
			SYNTAX HwhqosServiceIdentifyPolicy8021pEntry
			MAX-ACCESS not-accessible
			STATUS current
			DESCRIPTION
				"Description."
			INDEX { hwhqosServiceIdentifyPolicyName, hwhqosServiceIdentifyPolicy8021pCosID }
			::= { hwhqosServiceIdentifyPolicy8021pTable 1 }
		
		HwhqosServiceIdentifyPolicy8021pEntry ::=
			SEQUENCE { 
				hwhqosServiceIdentifyPolicy8021pCosID
					Integer32,
				hwhqosServiceIdentifyPolicy8021pDomainName
					OCTET STRING,
				hwhqosServiceIdentifyPolicy8021pRowStatus
					RowStatus
			 }

-- 1.3.6.1.4.1.2011.5.25.132.1.41.1.1
		hwhqosServiceIdentifyPolicy8021pCosID OBJECT-TYPE
			SYNTAX Integer32 (1..8)
			MAX-ACCESS read-only
			STATUS current
			DESCRIPTION
				"Description."
			::= { hwhqosServiceIdentifyPolicy8021pEntry 1 }
		
-- 1.3.6.1.4.1.2011.5.25.132.1.41.1.2
		hwhqosServiceIdentifyPolicy8021pDomainName OBJECT-TYPE
			SYNTAX OCTET STRING (SIZE (1..31))
			MAX-ACCESS read-create
			STATUS current
			DESCRIPTION
				"Description."
			::= { hwhqosServiceIdentifyPolicy8021pEntry 2 }

-- 1.3.6.1.4.1.2011.5.25.132.1.41.1.50
		hwhqosServiceIdentifyPolicy8021pRowStatus OBJECT-TYPE
			SYNTAX RowStatus
			MAX-ACCESS read-create
			STATUS current
			DESCRIPTION
				"Description."
			::= { hwhqosServiceIdentifyPolicy8021pEntry 50 }
		
-- 1.3.6.1.4.1.2011.5.25.132.1.42
		hwhqosServiceIdentifyPolicyDscpTable OBJECT-TYPE
			SYNTAX SEQUENCE OF HwhqosServiceIdentifyPolicyDscpEntry
			MAX-ACCESS not-accessible
			STATUS current
			DESCRIPTION
				"Description."
			::= { hwhqosStat 42 }
		
-- 1.3.6.1.4.1.2011.5.25.132.1.42.1
		hwhqosServiceIdentifyPolicyDscpEntry OBJECT-TYPE
			SYNTAX HwhqosServiceIdentifyPolicyDscpEntry
			MAX-ACCESS not-accessible
			STATUS current
			DESCRIPTION
				"Description."
			INDEX { hwhqosServiceIdentifyPolicyName, hwhqosServiceIdentifyPolicyDscpID }
			::= { hwhqosServiceIdentifyPolicyDscpTable 1 }
		
		HwhqosServiceIdentifyPolicyDscpEntry ::=
			SEQUENCE { 
				hwhqosServiceIdentifyPolicyDscpID
					Integer32,
				hwhqosServiceIdentifyPolicyDscpDomainName
					OCTET STRING,
				hwhqosServiceIdentifyPolicyDscpRowStatus
					RowStatus
			 }

-- 1.3.6.1.4.1.2011.5.25.132.1.42.1.1
		hwhqosServiceIdentifyPolicyDscpID OBJECT-TYPE
			SYNTAX Integer32 (1..64)
			MAX-ACCESS read-only
			STATUS current
			DESCRIPTION
				"Description."
			::= { hwhqosServiceIdentifyPolicyDscpEntry 1 }
		
-- 1.3.6.1.4.1.2011.5.25.132.1.42.1.2
		hwhqosServiceIdentifyPolicyDscpDomainName OBJECT-TYPE
			SYNTAX OCTET STRING (SIZE (1..31))
			MAX-ACCESS read-create
			STATUS current
			DESCRIPTION
				"Description."
			::= { hwhqosServiceIdentifyPolicyDscpEntry 2 }
		
-- 1.3.6.1.4.1.2011.5.25.132.1.42.1.50
		hwhqosServiceIdentifyPolicyDscpRowStatus OBJECT-TYPE
			SYNTAX RowStatus
			MAX-ACCESS read-create
			STATUS current
			DESCRIPTION
				"Description."
			::= { hwhqosServiceIdentifyPolicyDscpEntry 50 }
		
-- 1.3.6.1.4.1.2011.5.25.132.1.43
		hwhqosServiceIdentifyPolicyOption60Table OBJECT-TYPE
			SYNTAX SEQUENCE OF HwhqosServiceIdentifyPolicyOption60Entry
			MAX-ACCESS not-accessible
			STATUS current
			DESCRIPTION
				"Description."
			::= { hwhqosStat 43 }
		
-- 1.3.6.1.4.1.2011.5.25.132.1.43.1
		hwhqosServiceIdentifyPolicyOption60Entry OBJECT-TYPE
			SYNTAX HwhqosServiceIdentifyPolicyOption60Entry
			MAX-ACCESS not-accessible
			STATUS current
			DESCRIPTION
				"Description."
			INDEX { hwhqosServiceIdentifyPolicyName }
			::= { hwhqosServiceIdentifyPolicyOption60Table 1 }
		
		HwhqosServiceIdentifyPolicyOption60Entry ::=
			SEQUENCE { 
				hwhqosServiceIdentifyPolicyOption60
					INTEGER,
				hwhqosServiceIdentifyPolicyOption60RowStatus
					RowStatus
			 }

-- 1.3.6.1.4.1.2011.5.25.132.1.43.1.1
		hwhqosServiceIdentifyPolicyOption60 OBJECT-TYPE
			SYNTAX INTEGER
				{
				enable(1),
				disable(2)
				}
			MAX-ACCESS read-create
			STATUS current
			DESCRIPTION
				"Description."
			::= { hwhqosServiceIdentifyPolicyOption60Entry 1 }
		
-- 1.3.6.1.4.1.2011.5.25.132.1.43.1.50
		hwhqosServiceIdentifyPolicyOption60RowStatus OBJECT-TYPE
			SYNTAX RowStatus
			MAX-ACCESS read-create
			STATUS current
			DESCRIPTION
				"Description."
			::= { hwhqosServiceIdentifyPolicyOption60Entry 50 }
		
-- 1.3.6.1.4.1.2011.5.25.132.1.44
		hwhqosDomainRateLimitModeTable OBJECT-TYPE
			SYNTAX SEQUENCE OF HwhqosDomainRateLimitModeEntry
			MAX-ACCESS not-accessible
			STATUS current
			DESCRIPTION
				"Description."
			::= { hwhqosStat 44 }
		
-- 1.3.6.1.4.1.2011.5.25.132.1.44.1
		hwhqosDomainRateLimitModeEntry OBJECT-TYPE
			SYNTAX HwhqosDomainRateLimitModeEntry
			MAX-ACCESS not-accessible
			STATUS current
			DESCRIPTION
				"Description."
			INDEX { hwhqosDomainRateLimitModeDomainName }
			::= { hwhqosDomainRateLimitModeTable 1 }
		
		HwhqosDomainRateLimitModeEntry ::=
			SEQUENCE { 
				hwhqosDomainRateLimitModeDomainName
					OCTET STRING,
				hwhqosDomainRateLimitModeDirection
					INTEGER,
				hwhqosDomainRateLimitModeRateLimitMode
					INTEGER,
				hwhqosDomainRateLimitModeRowStatus
					RowStatus
			 }

-- 1.3.6.1.4.1.2011.5.25.132.1.44.1.1
		hwhqosDomainRateLimitModeDomainName OBJECT-TYPE
			SYNTAX OCTET STRING (SIZE (1..31))
			MAX-ACCESS read-only
			STATUS current
			DESCRIPTION
				"Description."
			::= { hwhqosDomainRateLimitModeEntry 1 }
		
-- 1.3.6.1.4.1.2011.5.25.132.1.44.1.2
		hwhqosDomainRateLimitModeDirection OBJECT-TYPE
			SYNTAX INTEGER
				{
				inbound(1),
				outbound(2)
				}
			MAX-ACCESS read-create
			STATUS current
			DESCRIPTION
				"Description."
			::= { hwhqosDomainRateLimitModeEntry 2 }
		
-- 1.3.6.1.4.1.2011.5.25.132.1.44.1.3
		hwhqosDomainRateLimitModeRateLimitMode OBJECT-TYPE
			SYNTAX INTEGER
				{
				sq(1),
				car(2)
				}
			MAX-ACCESS read-create
			STATUS current
			DESCRIPTION
				"Description."
			::= { hwhqosDomainRateLimitModeEntry 3 }
		
-- 1.3.6.1.4.1.2011.5.25.132.1.44.1.50
		hwhqosDomainRateLimitModeRowStatus OBJECT-TYPE
			SYNTAX RowStatus
			MAX-ACCESS read-create
			STATUS current
			DESCRIPTION
				"Description."
			::= { hwhqosDomainRateLimitModeEntry 50 }
		
-- 1.3.6.1.4.1.2011.5.25.132.1.45
		hwhqosDomainSessionGroupExcludeTable OBJECT-TYPE
			SYNTAX SEQUENCE OF HwhqosDomainSessionGroupExcludeEntry
			MAX-ACCESS not-accessible
			STATUS current
			DESCRIPTION
				"Description."
			::= { hwhqosStat 45 }
		
-- 1.3.6.1.4.1.2011.5.25.132.1.45.1
		hwhqosDomainSessionGroupExcludeEntry OBJECT-TYPE
			SYNTAX HwhqosDomainSessionGroupExcludeEntry
			MAX-ACCESS not-accessible
			STATUS current
			DESCRIPTION
				"Description."
			INDEX { hwhqosDomainSessionGroupExcludeDomainName, hwhqosDomainSessionGroupExcludeDirection, hwhqosDomainSessionGroupExcludeMode }
			::= { hwhqosDomainSessionGroupExcludeTable 1 }
		
		HwhqosDomainSessionGroupExcludeEntry ::=
			SEQUENCE { 
				hwhqosDomainSessionGroupExcludeDomainName
					OCTET STRING,
				hwhqosDomainSessionGroupExcludeDirection
					INTEGER,
				hwhqosDomainSessionGroupExcludeMode
					INTEGER,
				hwhqosDomainSessionGroupExcludeRowStatus
					RowStatus
			 }

-- 1.3.6.1.4.1.2011.5.25.132.1.45.1.1
		hwhqosDomainSessionGroupExcludeDomainName OBJECT-TYPE
			SYNTAX OCTET STRING (SIZE (1..31))
			MAX-ACCESS read-only
			STATUS current
			DESCRIPTION
				"Description."
			::= { hwhqosDomainSessionGroupExcludeEntry 1 }
		
-- 1.3.6.1.4.1.2011.5.25.132.1.45.1.2
		hwhqosDomainSessionGroupExcludeDirection OBJECT-TYPE
			SYNTAX INTEGER
				{
				inbound(1),
				outbound(2)
				}
			MAX-ACCESS read-only
			STATUS current
			DESCRIPTION
				"Description."
			::= { hwhqosDomainSessionGroupExcludeEntry 2 }
		
-- 1.3.6.1.4.1.2011.5.25.132.1.45.1.3
		hwhqosDomainSessionGroupExcludeMode OBJECT-TYPE
			SYNTAX INTEGER
				{
				sq(1),
				car(2),
				all(3)
				}
			MAX-ACCESS read-only
			STATUS current
			DESCRIPTION
				"Description."
			::= { hwhqosDomainSessionGroupExcludeEntry 3 }
		
-- 1.3.6.1.4.1.2011.5.25.132.1.45.1.50
		hwhqosDomainSessionGroupExcludeRowStatus OBJECT-TYPE
			SYNTAX RowStatus
			MAX-ACCESS read-create
			STATUS current
			DESCRIPTION
				"Description."
			::= { hwhqosDomainSessionGroupExcludeEntry 50 }
		
-- 1.3.6.1.4.1.2011.5.25.132.1.46
		hwhqosDomainUserMaxSessionTable OBJECT-TYPE
			SYNTAX SEQUENCE OF HwhqosDomainUserMaxSessionEntry
			MAX-ACCESS not-accessible
			STATUS current
			DESCRIPTION
				"Description."
			::= { hwhqosStat 46 }
		
-- 1.3.6.1.4.1.2011.5.25.132.1.46.1
		hwhqosDomainUserMaxSessionEntry OBJECT-TYPE
			SYNTAX HwhqosDomainUserMaxSessionEntry
			MAX-ACCESS not-accessible
			STATUS current
			DESCRIPTION
				"Description."
			INDEX { hwhqosDomainUserMaxSessionDomainName }
			::= { hwhqosDomainUserMaxSessionTable 1 }
		
		HwhqosDomainUserMaxSessionEntry ::=
			SEQUENCE { 
				hwhqosDomainUserMaxSessionDomainName
					OCTET STRING,
				hwhqosDomainUserMaxSessionNum
					Integer32,
				hwhqosDomainUserMaxSessionRowStatus
					RowStatus
			 }

-- 1.3.6.1.4.1.2011.5.25.132.1.46.1.1
		hwhqosDomainUserMaxSessionDomainName OBJECT-TYPE
			SYNTAX OCTET STRING (SIZE (1..31))
			MAX-ACCESS read-only
			STATUS current
			DESCRIPTION
				"Description."
			::= { hwhqosDomainUserMaxSessionEntry 1 }
		
-- 1.3.6.1.4.1.2011.5.25.132.1.46.1.2
		hwhqosDomainUserMaxSessionNum OBJECT-TYPE
			SYNTAX Integer32 (0..147456)
			MAX-ACCESS read-create
			STATUS current
			DESCRIPTION
				"Description."
			::= { hwhqosDomainUserMaxSessionEntry 2 }
		
-- 1.3.6.1.4.1.2011.5.25.132.1.46.1.50
		hwhqosDomainUserMaxSessionRowStatus OBJECT-TYPE
			SYNTAX RowStatus
			MAX-ACCESS read-create
			STATUS current
			DESCRIPTION
				"Description."
			::= { hwhqosDomainUserMaxSessionEntry 50 }
		
-- 1.3.6.1.4.1.2011.5.25.132.1.47
		hwhqosUpdateUseridProfileTable OBJECT-TYPE
			SYNTAX SEQUENCE OF HwhqosUpdateUseridProfileEntry
			MAX-ACCESS not-accessible
			STATUS current
			DESCRIPTION
				"Description."
			::= { hwhqosStat 47 }
		
-- 1.3.6.1.4.1.2011.5.25.132.1.47.1
		hwhqosUpdateUseridProfileEntry OBJECT-TYPE
			SYNTAX HwhqosUpdateUseridProfileEntry
			MAX-ACCESS not-accessible
			STATUS current
			DESCRIPTION
				"Description."
			INDEX { hwhqosUpdateUseridProfileUserid, hwhqosUpdateUseridProfileDirection }
			::= { hwhqosUpdateUseridProfileTable 1 }
		
		HwhqosUpdateUseridProfileEntry ::=
			SEQUENCE { 
				hwhqosUpdateUseridProfileUserid
					Integer32,
				hwhqosUpdateUseridProfileDirection
					INTEGER,
				hwhqosUpdateUseridProfileName
					OCTET STRING,
				hwhqosUpdateUseridProfileRowStatus
					RowStatus
			 }

-- 1.3.6.1.4.1.2011.5.25.132.1.47.1.1
		hwhqosUpdateUseridProfileUserid OBJECT-TYPE
			SYNTAX Integer32 (0..164864)
			MAX-ACCESS read-only
			STATUS current
			DESCRIPTION
				"Description."
			::= { hwhqosUpdateUseridProfileEntry 1 }
		
-- 1.3.6.1.4.1.2011.5.25.132.1.47.1.2
		hwhqosUpdateUseridProfileDirection OBJECT-TYPE
			SYNTAX INTEGER
				{
				inbound(1),
				outbound(2)
				}
			MAX-ACCESS read-only
			STATUS current
			DESCRIPTION
				"Description."
			::= { hwhqosUpdateUseridProfileEntry 2 }
		
-- 1.3.6.1.4.1.2011.5.25.132.1.47.1.3
-- BEGIN: mod by l00248629, 2014/03/21
		hwhqosUpdateUseridProfileName OBJECT-TYPE
			SYNTAX OCTET STRING (SIZE (1..63))
			MAX-ACCESS read-create
			STATUS current
			DESCRIPTION
				"Description."
			::= { hwhqosUpdateUseridProfileEntry 3 }
-- END: mod by l00248629, 2014/03/21
-- 1.3.6.1.4.1.2011.5.25.132.1.47.1.50
		hwhqosUpdateUseridProfileRowStatus OBJECT-TYPE
			SYNTAX RowStatus
			MAX-ACCESS read-create
			STATUS current
			DESCRIPTION
				"Description."
			::= { hwhqosUpdateUseridProfileEntry 50 }
		
-- 1.3.6.1.4.1.2011.5.25.132.1.48
		hwhqosDomainUserPriorityTable OBJECT-TYPE
			SYNTAX SEQUENCE OF HwhqosDomainUserPriorityEntry
			MAX-ACCESS not-accessible
			STATUS current
			DESCRIPTION
				"Description."
			::= { hwhqosStat 48 }
		
-- 1.3.6.1.4.1.2011.5.25.132.1.48.1
		hwhqosDomainUserPriorityEntry OBJECT-TYPE
			SYNTAX HwhqosDomainUserPriorityEntry
			MAX-ACCESS not-accessible
			STATUS current
			DESCRIPTION
				"Description."
			INDEX { hwhqosDomainUserPriorityDomainName, hwhqosDomainUserPriorityDirection }
			::= { hwhqosDomainUserPriorityTable 1 }
		
		HwhqosDomainUserPriorityEntry ::=
			SEQUENCE { 
				hwhqosDomainUserPriorityDomainName
					OCTET STRING,
				hwhqosDomainUserPriorityDirection
					INTEGER,
				hwhqosDomainUserPriorityValue
					INTEGER,
				hwhqosDomainUserPriorityRowStatus
					RowStatus
			 }

-- 1.3.6.1.4.1.2011.5.25.132.1.48.1.1
		hwhqosDomainUserPriorityDomainName OBJECT-TYPE
			SYNTAX OCTET STRING (SIZE (1..31))
			MAX-ACCESS read-only
			STATUS current
			DESCRIPTION
				"Description."
			::= { hwhqosDomainUserPriorityEntry 1 }
		
-- 1.3.6.1.4.1.2011.5.25.132.1.48.1.2
		hwhqosDomainUserPriorityDirection OBJECT-TYPE
			SYNTAX INTEGER
				{
				inbound(1),
				outbound(2)
				}
			MAX-ACCESS read-only
			STATUS current
			DESCRIPTION
				"Description."
			::= { hwhqosDomainUserPriorityEntry 2 }
		
-- 1.3.6.1.4.1.2011.5.25.132.1.48.1.3
		hwhqosDomainUserPriorityValue OBJECT-TYPE
			SYNTAX INTEGER
				{
				priority0(1),
				priority1(2),
				priority2(3),
				priority3(4),
				priority4(5),
				priority5(6),
				priority6(7),
				priority7(8),
				trust8021pinner(9),
				trust8021pouter(10),
				trustexpinner(11),
				trustexpouter(12),
				trustdscpinner(13),
				trustdscpouter(14),
				unchangeable(15)
				}
			MAX-ACCESS read-create
			STATUS current
			DESCRIPTION
				"Description."
			::= { hwhqosDomainUserPriorityEntry 3 }
		
-- 1.3.6.1.4.1.2011.5.25.132.1.48.1.50
		hwhqosDomainUserPriorityRowStatus OBJECT-TYPE
			SYNTAX RowStatus
			MAX-ACCESS read-create
			STATUS current
			DESCRIPTION
				"Description."
			::= { hwhqosDomainUserPriorityEntry 50 }
		
-- 1.3.6.1.4.1.2011.5.25.132.1.50
		hwhqosTMScheduleModeTable OBJECT-TYPE
			SYNTAX SEQUENCE OF HwhqosTMScheduleModeEntry
			MAX-ACCESS not-accessible
			STATUS current
			DESCRIPTION
				"Description."
			::= { hwhqosStat 50 }
		
-- 1.3.6.1.4.1.2011.5.25.132.1.50.1
		hwhqosTMScheduleModeEntry OBJECT-TYPE
			SYNTAX HwhqosTMScheduleModeEntry
			MAX-ACCESS not-accessible
			STATUS current
			DESCRIPTION
				"Description."
			INDEX { hwhqosTMScheduleModeSlot }
			::= { hwhqosTMScheduleModeTable 1 }
		
		HwhqosTMScheduleModeEntry ::=
			SEQUENCE { 
				hwhqosTMScheduleModeSlot
					Integer32,
				hwhqosTMScheduleModeSimpleEnable
					INTEGER,
				hwhqosTMScheduleModeRowStatus
					RowStatus
			 }

-- 1.3.6.1.4.1.2011.5.25.132.1.50.1.1
		hwhqosTMScheduleModeSlot OBJECT-TYPE
			SYNTAX Integer32 (1..16)
			MAX-ACCESS read-only
			STATUS current
			DESCRIPTION
				"Description."
			::= { hwhqosTMScheduleModeEntry 1 }
		
-- 1.3.6.1.4.1.2011.5.25.132.1.50.1.2
		hwhqosTMScheduleModeSimpleEnable OBJECT-TYPE
			SYNTAX INTEGER { simple(1) }
			MAX-ACCESS read-create
			STATUS current
			DESCRIPTION
				"Description."
			::= { hwhqosTMScheduleModeEntry 2 }
		
-- 1.3.6.1.4.1.2011.5.25.132.1.50.1.50
		hwhqosTMScheduleModeRowStatus OBJECT-TYPE
			SYNTAX RowStatus
			MAX-ACCESS read-create
			STATUS current
			DESCRIPTION
				"Description."
			::= { hwhqosTMScheduleModeEntry 50 }
		
-- 1.3.6.1.4.1.2011.5.25.132.1.51
		hwhqosUserBandwidthTable OBJECT-TYPE
			SYNTAX SEQUENCE OF HwhqosUserBandwidthEntry
			MAX-ACCESS not-accessible
			STATUS current
			DESCRIPTION
				"Description."
			::= { hwhqosStat 51 }
		
-- 1.3.6.1.4.1.2011.5.25.132.1.51.1
		hwhqosUserBandwidthEntry OBJECT-TYPE
			SYNTAX HwhqosUserBandwidthEntry
			MAX-ACCESS not-accessible
			STATUS current
			DESCRIPTION
				"Description."
			INDEX { hwhqosUserBandwidthUserid }
			::= { hwhqosUserBandwidthTable 1 }
		
		HwhqosUserBandwidthEntry ::=
			SEQUENCE { 
				hwhqosUserBandwidthUserid
					Integer32,
				hwhqosUserBandwidthCir
					Integer32,
				hwhqosUserBandwidthPir
					Integer32,
				hwhqosUserBandwidthCommittedCir
					Integer32,
				hwhqosUserBandwidthRowStatus
					RowStatus
			 }

-- 1.3.6.1.4.1.2011.5.25.132.1.51.1.1
		hwhqosUserBandwidthUserid OBJECT-TYPE
			SYNTAX Integer32 (0..164864)
			MAX-ACCESS read-only
			STATUS current
			DESCRIPTION
				"Description."
			::= { hwhqosUserBandwidthEntry 1 }
		
-- 1.3.6.1.4.1.2011.5.25.132.1.51.1.2
		hwhqosUserBandwidthCir OBJECT-TYPE
			SYNTAX Integer32
			MAX-ACCESS read-only
			STATUS current
			DESCRIPTION
				"Description."
			::= { hwhqosUserBandwidthEntry 2 }
		
-- 1.3.6.1.4.1.2011.5.25.132.1.51.1.3
		hwhqosUserBandwidthPir OBJECT-TYPE
			SYNTAX Integer32
			MAX-ACCESS read-only
			STATUS current
			DESCRIPTION
				"Description."
			::= { hwhqosUserBandwidthEntry 3 }
		
-- 1.3.6.1.4.1.2011.5.25.132.1.51.1.4
		hwhqosUserBandwidthCommittedCir OBJECT-TYPE
			SYNTAX Integer32
			MAX-ACCESS read-only
			STATUS current
			DESCRIPTION
				"Description."
			::= { hwhqosUserBandwidthEntry 4 }
		
-- 1.3.6.1.4.1.2011.5.25.132.1.51.1.50
		hwhqosUserBandwidthRowStatus OBJECT-TYPE
			SYNTAX RowStatus
			MAX-ACCESS read-create
			STATUS current
			DESCRIPTION
				"Description."
			::= { hwhqosUserBandwidthEntry 50 }
		
-- 1.3.6.1.4.1.2011.5.25.132.1.52
		hwhqosUseridStatTable OBJECT-TYPE
			SYNTAX SEQUENCE OF HwhqosUseridStatEntry
			MAX-ACCESS not-accessible
			STATUS current
			DESCRIPTION
				"Description."
			::= { hwhqosStat 52 }
		
-- 1.3.6.1.4.1.2011.5.25.132.1.52.1
		hwhqosUseridStatEntry OBJECT-TYPE
			SYNTAX HwhqosUseridStatEntry
			MAX-ACCESS not-accessible
			STATUS current
			DESCRIPTION
				"Description."
			INDEX { hwhqosUseridStatUserid, hwhqosUseridStatQueue, hwhqosUseridStatDirection }
			::= { hwhqosUseridStatTable 1 }
		
		HwhqosUseridStatEntry ::=
			SEQUENCE { 
				hwhqosUseridStatUserid
					Unsigned32,
				hwhqosUseridStatQueue
					INTEGER,
				hwhqosUseridStatDirection
					INTEGER,
				hwhqosUseridStatPassBytes
					Counter64,
				hwhqosUseridStatDropBytes
					Counter64,
				hwhqosUseridStatPassPackets
					Counter64,
				hwhqosUseridStatDropPackets
					Counter64,
				hwhqosUseridStatPassPacketsRate
					Counter64,
				hwhqosUseridStatDropPacketsRate
					Counter64,
				hwhqosUseridStatReset
					INTEGER,
				hwhqosUseridStatPassBytesRate
					Counter64,
				hwhqosUseridStatDropBytesRate
					Counter64
			 }

-- 1.3.6.1.4.1.2011.5.25.132.1.52.1.1
		hwhqosUseridStatUserid OBJECT-TYPE
			SYNTAX Unsigned32
			MAX-ACCESS read-only
			STATUS current
			DESCRIPTION
				"Description."
			::= { hwhqosUseridStatEntry 1 }
		
-- 1.3.6.1.4.1.2011.5.25.132.1.52.1.2
		hwhqosUseridStatQueue OBJECT-TYPE
			SYNTAX INTEGER
				{
				be(1),
				af1(2),
				af2(3),
				af3(4),
				af4(5),
				ef(6),
				cs6(7),
				cs7(8),
				total(9)
				}
			MAX-ACCESS read-only
			STATUS current
			DESCRIPTION
				"Description."
			::= { hwhqosUseridStatEntry 2 }
		
-- 1.3.6.1.4.1.2011.5.25.132.1.52.1.3
		hwhqosUseridStatDirection OBJECT-TYPE
			SYNTAX INTEGER
				{
				inbound(1),
				outbound(2)
				}
			MAX-ACCESS read-only
			STATUS current
			DESCRIPTION
				"Description."
			::= { hwhqosUseridStatEntry 3 }
		
-- 1.3.6.1.4.1.2011.5.25.132.1.52.1.4
		hwhqosUseridStatPassBytes OBJECT-TYPE
			SYNTAX Counter64
			MAX-ACCESS read-only
			STATUS current
			DESCRIPTION
				"Description."
			::= { hwhqosUseridStatEntry 4 }
		
-- 1.3.6.1.4.1.2011.5.25.132.1.52.1.5
		hwhqosUseridStatDropBytes OBJECT-TYPE
			SYNTAX Counter64
			MAX-ACCESS read-only
			STATUS current
			DESCRIPTION
				"Description."
			::= { hwhqosUseridStatEntry 5 }
		
-- 1.3.6.1.4.1.2011.5.25.132.1.52.1.6
		hwhqosUseridStatPassPackets OBJECT-TYPE
			SYNTAX Counter64
			MAX-ACCESS read-only
			STATUS current
			DESCRIPTION
				"Description."
			::= { hwhqosUseridStatEntry 6 }
		
-- 1.3.6.1.4.1.2011.5.25.132.1.52.1.7
		hwhqosUseridStatDropPackets OBJECT-TYPE
			SYNTAX Counter64
			MAX-ACCESS read-only
			STATUS current
			DESCRIPTION
				"Description."
			::= { hwhqosUseridStatEntry 7 }
		
-- 1.3.6.1.4.1.2011.5.25.132.1.52.1.8
		hwhqosUseridStatPassPacketsRate OBJECT-TYPE
			SYNTAX Counter64
			MAX-ACCESS read-only
			STATUS current
			DESCRIPTION
				"Description."
			::= { hwhqosUseridStatEntry 8 }
		
-- 1.3.6.1.4.1.2011.5.25.132.1.52.1.9
		hwhqosUseridStatDropPacketsRate OBJECT-TYPE
			SYNTAX Counter64
			MAX-ACCESS read-only
			STATUS current
			DESCRIPTION
				"Description."
			::= { hwhqosUseridStatEntry 9 }
		
-- 1.3.6.1.4.1.2011.5.25.132.1.52.1.10
		hwhqosUseridStatReset OBJECT-TYPE
			SYNTAX INTEGER { reset(1) }
			MAX-ACCESS read-create
			STATUS current
			DESCRIPTION
				"Description."
			::= { hwhqosUseridStatEntry 10 }
		
-- 1.3.6.1.4.1.2011.5.25.132.1.52.1.11
		hwhqosUseridStatPassBytesRate OBJECT-TYPE
			SYNTAX Counter64
			MAX-ACCESS read-only
			STATUS current
			DESCRIPTION
				"Description."
			::= { hwhqosUseridStatEntry 11 }
		
-- 1.3.6.1.4.1.2011.5.25.132.1.52.1.12
		hwhqosUseridStatDropBytesRate OBJECT-TYPE
			SYNTAX Counter64
			MAX-ACCESS read-only
			STATUS current
			DESCRIPTION
				"Description."
			::= { hwhqosUseridStatEntry 12 }
		
-- 1.3.6.1.4.1.2011.5.25.132.1.53
		hwhqosFatherUserGroupQueueApplyTable OBJECT-TYPE
			SYNTAX SEQUENCE OF HwhqosFatherUserGroupQueueApplyEntry
			MAX-ACCESS not-accessible
			STATUS current
			DESCRIPTION
				"Description."
			::= { hwhqosStat 53 }
		
-- 1.3.6.1.4.1.2011.5.25.132.1.53.1
		hwhqosFatherUserGroupQueueApplyEntry OBJECT-TYPE
			SYNTAX HwhqosFatherUserGroupQueueApplyEntry
			MAX-ACCESS not-accessible
			STATUS current
			DESCRIPTION
				"Description."
			INDEX { hwhqosFatherUserGroupQueueApplyInterfaceIndex, hwhqosFatherUserGroupQueueApplyDirection }
			::= { hwhqosFatherUserGroupQueueApplyTable 1 }
		
		HwhqosFatherUserGroupQueueApplyEntry ::=
			SEQUENCE { 
				hwhqosFatherUserGroupQueueApplyInterfaceIndex
					InterfaceIndex,
				hwhqosFatherUserGroupQueueApplyDirection
					INTEGER,
				hwhqosFatherUserGroupQueueApplyName
					OCTET STRING,
				hwhqosFatherUserGroupQueueApplyRowStatus
					RowStatus
			 }

-- 1.3.6.1.4.1.2011.5.25.132.1.53.1.1
		hwhqosFatherUserGroupQueueApplyInterfaceIndex OBJECT-TYPE
			SYNTAX InterfaceIndex
			MAX-ACCESS read-only
			STATUS current
			DESCRIPTION
				"Description."
			::= { hwhqosFatherUserGroupQueueApplyEntry 1 }
		
-- 1.3.6.1.4.1.2011.5.25.132.1.53.1.2
		hwhqosFatherUserGroupQueueApplyDirection OBJECT-TYPE
			SYNTAX INTEGER { outbound(2) }
			MAX-ACCESS read-only
			STATUS current
			DESCRIPTION
				"Description."
			::= { hwhqosFatherUserGroupQueueApplyEntry 2 }
		
-- 1.3.6.1.4.1.2011.5.25.132.1.53.1.3
		hwhqosFatherUserGroupQueueApplyName OBJECT-TYPE
			SYNTAX OCTET STRING (SIZE (1..31))
			MAX-ACCESS read-create
			STATUS current
			DESCRIPTION
				"Description."
			::= { hwhqosFatherUserGroupQueueApplyEntry 3 }
		
-- 1.3.6.1.4.1.2011.5.25.132.1.53.1.50
		hwhqosFatherUserGroupQueueApplyRowStatus OBJECT-TYPE
			SYNTAX RowStatus
			MAX-ACCESS read-create
			STATUS current
			DESCRIPTION
				"Description."
			::= { hwhqosFatherUserGroupQueueApplyEntry 50 }
		
-- 1.3.6.1.4.1.2011.5.25.132.1.54
		hwhqosUserGroupQueueApplyTable OBJECT-TYPE
			SYNTAX SEQUENCE OF HwhqosUserGroupQueueApplyEntry
			MAX-ACCESS not-accessible
			STATUS current
			DESCRIPTION
				" "
			::= { hwhqosStat 54 }
		
-- 1.3.6.1.4.1.2011.5.25.132.1.54.1
		hwhqosUserGroupQueueApplyEntry OBJECT-TYPE
			SYNTAX HwhqosUserGroupQueueApplyEntry
			MAX-ACCESS not-accessible
			STATUS current
			DESCRIPTION
				" This table is used to apply a user group queue to interfaces. "
			INDEX { hwhqosUserGroupQueueApplyInterfaceIndex, hwhqosUserGroupQueueApplyPeVid, hwhqosUserGroupQueueApplyCeVid, hwhqosUserGroupQueueApplyDirection }
			::= { hwhqosUserGroupQueueApplyTable 1 }
		
		HwhqosUserGroupQueueApplyEntry ::=
			SEQUENCE { 
				hwhqosUserGroupQueueApplyInterfaceIndex
					InterfaceIndex,
				hwhqosUserGroupQueueApplyPeVid
					Integer32,
				hwhqosUserGroupQueueApplyCeVid
					Integer32,
				hwhqosUserGroupQueueApplyDirection
					INTEGER,
				hwhqosUserGroupQueueApplyName
					OCTET STRING,
				hwhqosUserGroupQueueApplyEachvlan
					INTEGER,
				hwhqosUserGroupQueueApplyRowStatus
					RowStatus
			 }

-- 1.3.6.1.4.1.2011.5.25.132.1.54.1.1
		hwhqosUserGroupQueueApplyInterfaceIndex OBJECT-TYPE
			SYNTAX InterfaceIndex
			MAX-ACCESS read-only
			STATUS current
			DESCRIPTION
				" This object indicates the index of interface."
			::= { hwhqosUserGroupQueueApplyEntry 1 }
		
-- 1.3.6.1.4.1.2011.5.25.132.1.54.1.2
		hwhqosUserGroupQueueApplyPeVid OBJECT-TYPE
			SYNTAX Integer32 (0 | 1..4094)
			MAX-ACCESS read-only
			STATUS current
			DESCRIPTION
				"This object indicates the index of vlan or l2tp group."
			::= { hwhqosUserGroupQueueApplyEntry 2 }
		
-- 1.3.6.1.4.1.2011.5.25.132.1.54.1.3
		hwhqosUserGroupQueueApplyCeVid OBJECT-TYPE
			SYNTAX Integer32 (1..4094)
			MAX-ACCESS read-only
			STATUS current
			DESCRIPTION
				"This object indicates the index of vlan or l2tp group."
			::= { hwhqosUserGroupQueueApplyEntry 3 }
		
-- 1.3.6.1.4.1.2011.5.25.132.1.54.1.4
		hwhqosUserGroupQueueApplyDirection OBJECT-TYPE
			SYNTAX INTEGER
				{
				inbound(1),
				outbound(2)
				}
			MAX-ACCESS read-only
			STATUS current
			DESCRIPTION
				" "
			::= { hwhqosUserGroupQueueApplyEntry 4 }
		
-- 1.3.6.1.4.1.2011.5.25.132.1.54.1.5
		hwhqosUserGroupQueueApplyName OBJECT-TYPE
			SYNTAX OCTET STRING
			MAX-ACCESS read-create
			STATUS current
			DESCRIPTION
				"This object indicates the name of user-group-queue."
			::= { hwhqosUserGroupQueueApplyEntry 5 }
		
-- 1.3.6.1.4.1.2011.5.25.132.1.54.1.6
		hwhqosUserGroupQueueApplyEachvlan OBJECT-TYPE
			SYNTAX INTEGER
				{
				eachVlan(1),
				eachPevid(2),
				eachCevid(3),
				none(4)
				}
			MAX-ACCESS read-create
			STATUS current
			DESCRIPTION
				" "
			::= { hwhqosUserGroupQueueApplyEntry 6 }
		
-- 1.3.6.1.4.1.2011.5.25.132.1.54.1.50
		hwhqosUserGroupQueueApplyRowStatus OBJECT-TYPE
			SYNTAX RowStatus
			MAX-ACCESS read-create
			STATUS current
			DESCRIPTION
				" "
			::= { hwhqosUserGroupQueueApplyEntry 50 }
		
-- 1.3.6.1.4.1.2011.5.25.132.1.55
		hwhqosProfileApplyDomainTable OBJECT-TYPE
			SYNTAX SEQUENCE OF HwhqosProfileApplyDomainEntry
			MAX-ACCESS not-accessible
			STATUS current
			DESCRIPTION
				" "
			::= { hwhqosStat 55 }
		
-- 1.3.6.1.4.1.2011.5.25.132.1.55.1
		hwhqosProfileApplyDomainEntry OBJECT-TYPE
			SYNTAX HwhqosProfileApplyDomainEntry
			MAX-ACCESS not-accessible
			STATUS current
			DESCRIPTION
				"Description."
			INDEX { hwhqosProfileApplyDomainName, hwhqosProfileApplyDomainDirection }
			::= { hwhqosProfileApplyDomainTable 1 }
		
		HwhqosProfileApplyDomainEntry ::=
			SEQUENCE { 
				hwhqosProfileApplyDomainName
					OCTET STRING,
				hwhqosProfileApplyDomainDirection
					INTEGER,
				hwhqosProfileApplyDomainProfileName
					OCTET STRING,
				hwhqosProfileApplyDomainRowStatus
					RowStatus
			 }

-- 1.3.6.1.4.1.2011.5.25.132.1.55.1.1
		hwhqosProfileApplyDomainName OBJECT-TYPE
			SYNTAX OCTET STRING
			MAX-ACCESS read-only
			STATUS current
			DESCRIPTION
				" "
			::= { hwhqosProfileApplyDomainEntry 1 }
		
-- 1.3.6.1.4.1.2011.5.25.132.1.55.1.2
		hwhqosProfileApplyDomainDirection OBJECT-TYPE
			SYNTAX INTEGER
				{
				inbound(1),
				outbound(2)
				}
			MAX-ACCESS read-only
			STATUS current
			DESCRIPTION
				" "
			::= { hwhqosProfileApplyDomainEntry 2 }
		
-- 1.3.6.1.4.1.2011.5.25.132.1.55.1.3
		hwhqosProfileApplyDomainProfileName OBJECT-TYPE
			SYNTAX OCTET STRING
			MAX-ACCESS read-create
			STATUS current
			DESCRIPTION
				" "
			::= { hwhqosProfileApplyDomainEntry 3 }
		
-- 1.3.6.1.4.1.2011.5.25.132.1.55.1.50
		hwhqosProfileApplyDomainRowStatus OBJECT-TYPE
			SYNTAX RowStatus
			MAX-ACCESS read-create
			STATUS current
			DESCRIPTION
				" "
			::= { hwhqosProfileApplyDomainEntry 50 }
		
-- 1.3.6.1.4.1.2011.5.25.132.1.56
		hwhqosProfileApplyUserVlanTable OBJECT-TYPE
			SYNTAX SEQUENCE OF HwhqosProfileApplyUserVlanEntry
			MAX-ACCESS not-accessible
			STATUS current
			DESCRIPTION
				" "
			::= { hwhqosStat 56 }
		
-- 1.3.6.1.4.1.2011.5.25.132.1.56.1
		hwhqosProfileApplyUserVlanEntry OBJECT-TYPE
			SYNTAX HwhqosProfileApplyUserVlanEntry
			MAX-ACCESS not-accessible
			STATUS current
			DESCRIPTION
				"Description."
			INDEX { hwhqosProfileApplyUserVlanInterfaceIndex, hwhqosProfileApplyUserVlanPeVid, hwhqosProfileApplyUserVlanCeVid, hwhqosProfileApplyUserVlanDirection }
			::= { hwhqosProfileApplyUserVlanTable 1 }
		
		HwhqosProfileApplyUserVlanEntry ::=
			SEQUENCE { 
				hwhqosProfileApplyUserVlanInterfaceIndex
					InterfaceIndex,
				hwhqosProfileApplyUserVlanPeVid
					Integer32,
				hwhqosProfileApplyUserVlanCeVid
					Integer32,
				hwhqosProfileApplyUserVlanDirection
					INTEGER,
				hwhqosProfileApplyUserVlanProfileName
					OCTET STRING,
				hwhqosProfileApplyUserVlanEach
					INTEGER,
				hwhqosProfileApplyUserVlanRowStatus
					RowStatus
			 }

-- 1.3.6.1.4.1.2011.5.25.132.1.56.1.1
		hwhqosProfileApplyUserVlanInterfaceIndex OBJECT-TYPE
			SYNTAX InterfaceIndex
			MAX-ACCESS read-only
			STATUS current
			DESCRIPTION
				" "
			::= { hwhqosProfileApplyUserVlanEntry 1 }
		
-- 1.3.6.1.4.1.2011.5.25.132.1.56.1.2
		hwhqosProfileApplyUserVlanPeVid OBJECT-TYPE
			SYNTAX Integer32 (0 | 1..4094)
			MAX-ACCESS read-only
			STATUS current
			DESCRIPTION
				"This object indicates the index of vlan or l2tp group."
			::= { hwhqosProfileApplyUserVlanEntry 2 }
		
-- 1.3.6.1.4.1.2011.5.25.132.1.56.1.3
		hwhqosProfileApplyUserVlanCeVid OBJECT-TYPE
			SYNTAX Integer32 (1..4094)
			MAX-ACCESS read-only
			STATUS current
			DESCRIPTION
				"This object indicates the index of vlan or l2tp group."
			::= { hwhqosProfileApplyUserVlanEntry 3 }
		
-- 1.3.6.1.4.1.2011.5.25.132.1.56.1.4
		hwhqosProfileApplyUserVlanDirection OBJECT-TYPE
			SYNTAX INTEGER
				{
				inbound(1),
				outbound(2)
				}
			MAX-ACCESS read-only
			STATUS current
			DESCRIPTION
				" "
			::= { hwhqosProfileApplyUserVlanEntry 4 }
		
-- 1.3.6.1.4.1.2011.5.25.132.1.56.1.5
		hwhqosProfileApplyUserVlanProfileName OBJECT-TYPE
			SYNTAX OCTET STRING
			MAX-ACCESS read-create
			STATUS current
			DESCRIPTION
				" "
			::= { hwhqosProfileApplyUserVlanEntry 5 }
		
-- 1.3.6.1.4.1.2011.5.25.132.1.56.1.6
		hwhqosProfileApplyUserVlanEach OBJECT-TYPE
			SYNTAX INTEGER
				{
				enable(1),
				disable(2)
				}
			MAX-ACCESS read-create
			STATUS current
			DESCRIPTION
				" "
			::= { hwhqosProfileApplyUserVlanEntry 6 }
		
-- 1.3.6.1.4.1.2011.5.25.132.1.56.1.50
		hwhqosProfileApplyUserVlanRowStatus OBJECT-TYPE
			SYNTAX RowStatus
			MAX-ACCESS read-create
			STATUS current
			DESCRIPTION
				" "
			::= { hwhqosProfileApplyUserVlanEntry 50 }
		
-- 1.3.6.1.4.1.2011.5.25.132.1.57
		hwhqosLinkAdjRemoteEnableTable OBJECT-TYPE
			SYNTAX SEQUENCE OF HwhqosLinkAdjRemoteEnableEntry
			MAX-ACCESS not-accessible
			STATUS current
			DESCRIPTION
				" "
			::= { hwhqosStat 57 }
		
-- 1.3.6.1.4.1.2011.5.25.132.1.57.1
		hwhqosLinkAdjRemoteEnableEntry OBJECT-TYPE
			SYNTAX HwhqosLinkAdjRemoteEnableEntry
			MAX-ACCESS not-accessible
			STATUS current
			DESCRIPTION
				"Description."
			INDEX { hwhqosLinkAdjRemoteEnableType, hwhqosLinkAdjRemoteEnableSlot, hwhqosLinkAdjRemoteEnableDomainName }
			::= { hwhqosLinkAdjRemoteEnableTable 1 }
		
		HwhqosLinkAdjRemoteEnableEntry ::=
			SEQUENCE { 
				hwhqosLinkAdjRemoteEnableType
					INTEGER,
				hwhqosLinkAdjRemoteEnableSlot
					Integer32,
				hwhqosLinkAdjRemoteEnableDomainName
					OCTET STRING,
				hwhqosLinkAdjRemoteEnable
					INTEGER,
				hwhqosLinkAdjRemoteEnableRowStatus
					RowStatus
			 }

-- 1.3.6.1.4.1.2011.5.25.132.1.57.1.1
		hwhqosLinkAdjRemoteEnableType OBJECT-TYPE
			SYNTAX INTEGER
				{
				system(1),
				domain(2)
				}
			MAX-ACCESS read-only
			STATUS current
			DESCRIPTION
				" "
			::= { hwhqosLinkAdjRemoteEnableEntry 1 }
		
-- 1.3.6.1.4.1.2011.5.25.132.1.57.1.2
		hwhqosLinkAdjRemoteEnableSlot OBJECT-TYPE
			SYNTAX Integer32
			MAX-ACCESS read-only
			STATUS current
			DESCRIPTION
				" "
			::= { hwhqosLinkAdjRemoteEnableEntry 2 }
		
-- 1.3.6.1.4.1.2011.5.25.132.1.57.1.3
		hwhqosLinkAdjRemoteEnableDomainName OBJECT-TYPE
			SYNTAX OCTET STRING (SIZE (1..31))
			MAX-ACCESS read-only
			STATUS current
			DESCRIPTION
				" hwhqosLinkAdjRemoteEnableDomainName"
			::= { hwhqosLinkAdjRemoteEnableEntry 3 }
		
-- 1.3.6.1.4.1.2011.5.25.132.1.57.1.4
		hwhqosLinkAdjRemoteEnable OBJECT-TYPE
			SYNTAX INTEGER
				{
				enable(1),
				disable(2)
				}
			MAX-ACCESS read-create
			STATUS current
			DESCRIPTION
				" "
			::= { hwhqosLinkAdjRemoteEnableEntry 4 }
		
-- 1.3.6.1.4.1.2011.5.25.132.1.57.1.50
		hwhqosLinkAdjRemoteEnableRowStatus OBJECT-TYPE
			SYNTAX RowStatus
			MAX-ACCESS read-create
			STATUS current
			DESCRIPTION
				" "
			::= { hwhqosLinkAdjRemoteEnableEntry 50 }
		
-- 1.3.6.1.4.1.2011.5.25.132.1.58
		hwhqosLinkAdjShapingModeTable OBJECT-TYPE
			SYNTAX SEQUENCE OF HwhqosLinkAdjShapingModeEntry
			MAX-ACCESS not-accessible
			STATUS current
			DESCRIPTION
				" "
			::= { hwhqosStat 58 }
		
-- 1.3.6.1.4.1.2011.5.25.132.1.58.1
		hwhqosLinkAdjShapingModeEntry OBJECT-TYPE
			SYNTAX HwhqosLinkAdjShapingModeEntry
			MAX-ACCESS not-accessible
			STATUS current
			DESCRIPTION
				"Description."
			INDEX { hwhqosLinkAdjShapingModeType, hwhqosLinkAdjShapingModeInterfaceIndex, hwhqosLinkAdjShapingModeDomainName }
			::= { hwhqosLinkAdjShapingModeTable 1 }
		
		HwhqosLinkAdjShapingModeEntry ::=
			SEQUENCE { 
				hwhqosLinkAdjShapingModeType
					INTEGER,
				hwhqosLinkAdjShapingModeInterfaceIndex
					Integer32,
				hwhqosLinkAdjShapingModeDomainName
					OCTET STRING,
				hwhqosLinkAdjShapingMode
					INTEGER,
				hwhqosLinkAdjShapingModeRowStatus
					RowStatus
			 }

-- 1.3.6.1.4.1.2011.5.25.132.1.58.1.1
		hwhqosLinkAdjShapingModeType OBJECT-TYPE
			SYNTAX INTEGER
				{
				interface(1),
				domain(2)
				}
			MAX-ACCESS read-only
			STATUS current
			DESCRIPTION
				"Specify whether the command is applied on a interface or in a domain "
			::= { hwhqosLinkAdjShapingModeEntry 1 }
		
-- 1.3.6.1.4.1.2011.5.25.132.1.58.1.2
		hwhqosLinkAdjShapingModeInterfaceIndex OBJECT-TYPE
			SYNTAX Integer32
			MAX-ACCESS read-only
			STATUS current
			DESCRIPTION
				" "
			::= { hwhqosLinkAdjShapingModeEntry 2 }
		
-- 1.3.6.1.4.1.2011.5.25.132.1.58.1.3
		hwhqosLinkAdjShapingModeDomainName OBJECT-TYPE
			SYNTAX OCTET STRING (SIZE (1..31))
			MAX-ACCESS read-only
			STATUS current
			DESCRIPTION
				" hwhqosLinkAdjShapingModeDomainName"
			::= { hwhqosLinkAdjShapingModeEntry 3 }
		
-- 1.3.6.1.4.1.2011.5.25.132.1.58.1.4
		hwhqosLinkAdjShapingMode OBJECT-TYPE
			SYNTAX INTEGER
				{
				frame(1),
				cell(2)
				}
			MAX-ACCESS read-create
			STATUS current
			DESCRIPTION
				" "
			::= { hwhqosLinkAdjShapingModeEntry 4 }
		
-- 1.3.6.1.4.1.2011.5.25.132.1.58.1.50
		hwhqosLinkAdjShapingModeRowStatus OBJECT-TYPE
			SYNTAX RowStatus
			MAX-ACCESS read-create
			STATUS current
			DESCRIPTION
				" "
			::= { hwhqosLinkAdjShapingModeEntry 50 }
		
-- 1.3.6.1.4.1.2011.5.25.132.1.59
		hwhqosLinkAdjRemoteTable OBJECT-TYPE
			SYNTAX SEQUENCE OF HwhqosLinkAdjRemoteEntry
			MAX-ACCESS not-accessible
			STATUS current
			DESCRIPTION
				" "
			::= { hwhqosStat 59 }
		
-- 1.3.6.1.4.1.2011.5.25.132.1.59.1
		hwhqosLinkAdjRemoteEntry OBJECT-TYPE
			SYNTAX HwhqosLinkAdjRemoteEntry
			MAX-ACCESS not-accessible
			STATUS current
			DESCRIPTION
				"Description."
			INDEX { hwhqosLinkAdjRemoteType, hwhqosLinkAdjRemoteInterfaceIndex, hwhqosLinkAdjRemoteDomainName }
			::= { hwhqosLinkAdjRemoteTable 1 }
		
		HwhqosLinkAdjRemoteEntry ::=
			SEQUENCE { 
				hwhqosLinkAdjRemoteType
					INTEGER,
				hwhqosLinkAdjRemoteInterfaceIndex
					Integer32,
				hwhqosLinkAdjRemoteDomainName
					OCTET STRING,
				hwhqosLinkAdjRemoteValue
					Integer32,
				hwhqosLinkAdjRemoteRowStatus
					RowStatus
			 }

-- 1.3.6.1.4.1.2011.5.25.132.1.59.1.1
		hwhqosLinkAdjRemoteType OBJECT-TYPE
			SYNTAX INTEGER
				{
				interface(1),
				domain(2)
				}
			MAX-ACCESS read-only
			STATUS current
			DESCRIPTION
				"Specify whether the command is applied on a interface or in a domain"
			::= { hwhqosLinkAdjRemoteEntry 1 }
		
-- 1.3.6.1.4.1.2011.5.25.132.1.59.1.2
        hwhqosLinkAdjRemoteInterfaceIndex OBJECT-TYPE
            SYNTAX Integer32
            MAX-ACCESS read-only
            STATUS current
            DESCRIPTION
                " "
            ::= { hwhqosLinkAdjRemoteEntry 2 }
        
        -- 1.3.6.1.4.1.2011.5.25.132.1.59.1.3
        hwhqosLinkAdjRemoteDomainName OBJECT-TYPE
            SYNTAX OCTET STRING (SIZE (1..31))
            MAX-ACCESS read-only
            STATUS current
            DESCRIPTION
                " hwhqosLinkAdjRemoteDomainName"
            ::= { hwhqosLinkAdjRemoteEntry 3 }
		
-- 1.3.6.1.4.1.2011.5.25.132.1.59.1.3
        hwhqosLinkAdjRemoteValue OBJECT-TYPE
            SYNTAX Integer32
            MAX-ACCESS read-create
            STATUS current
            DESCRIPTION
                " "
            ::= { hwhqosLinkAdjRemoteEntry 4 }
		
		
-- 1.3.6.1.4.1.2011.5.25.132.1.59.1.50
		hwhqosLinkAdjRemoteRowStatus OBJECT-TYPE
			SYNTAX RowStatus
			MAX-ACCESS read-create
			STATUS current
			DESCRIPTION
				" "
			::= { hwhqosLinkAdjRemoteEntry 50 }
		
-- 1.3.6.1.4.1.2011.5.25.132.1.60
		hwhqosLinkAdjLocalTable OBJECT-TYPE
			SYNTAX SEQUENCE OF HwhqosLinkAdjLocalEntry
			MAX-ACCESS not-accessible
			STATUS current
			DESCRIPTION
				" "
			::= { hwhqosStat 60 }
		
-- 1.3.6.1.4.1.2011.5.25.132.1.60.1
		hwhqosLinkAdjLocalEntry OBJECT-TYPE
			SYNTAX HwhqosLinkAdjLocalEntry
			MAX-ACCESS not-accessible
			STATUS current
			DESCRIPTION
				"Description."
			INDEX { hwhqosLinkAdjLocalSlotNumber }
			::= { hwhqosLinkAdjLocalTable 1 }
		
		HwhqosLinkAdjLocalEntry ::=
			SEQUENCE { 
				hwhqosLinkAdjLocalSlotNumber
					Integer32,
				hwhqosLinkAdjLocalValue
					Integer32,
				hwhqosLinkAdjLocalRowStatus
					RowStatus
			 }

-- 1.3.6.1.4.1.2011.5.25.132.1.60.1.1
		hwhqosLinkAdjLocalSlotNumber OBJECT-TYPE
			SYNTAX Integer32 (1..128)
			MAX-ACCESS read-only
			STATUS current
			DESCRIPTION
				" "
			::= { hwhqosLinkAdjLocalEntry 1 }
		
-- 1.3.6.1.4.1.2011.5.25.132.1.60.1.2
		hwhqosLinkAdjLocalValue OBJECT-TYPE
			SYNTAX Integer32
			MAX-ACCESS read-create
			STATUS current
			DESCRIPTION
				" "
			::= { hwhqosLinkAdjLocalEntry 2 }
		
-- 1.3.6.1.4.1.2011.5.25.132.1.60.1.50
		hwhqosLinkAdjLocalRowStatus OBJECT-TYPE
			SYNTAX RowStatus
			MAX-ACCESS read-create
			STATUS current
			DESCRIPTION
				" "
			::= { hwhqosLinkAdjLocalEntry 50 }
		
-- 1.3.6.1.4.1.2011.5.25.132.1.61
		hwhqosLinkAdjExcludeTable OBJECT-TYPE
			SYNTAX SEQUENCE OF HwhqosLinkAdjExcludeEntry
			MAX-ACCESS not-accessible
			STATUS current
			DESCRIPTION
				" "
			::= { hwhqosStat 61 }
		
-- 1.3.6.1.4.1.2011.5.25.132.1.61.1
		hwhqosLinkAdjExcludeEntry OBJECT-TYPE
			SYNTAX HwhqosLinkAdjExcludeEntry
			MAX-ACCESS not-accessible
			STATUS current
			DESCRIPTION
				"Description."
			INDEX { hwhqosLinkAdjExcludeSlotNumber }
			::= { hwhqosLinkAdjExcludeTable 1 }
		
		HwhqosLinkAdjExcludeEntry ::=
			SEQUENCE { 
				hwhqosLinkAdjExcludeSlotNumber
					Integer32,
				hwhqosLinkAdjExcludeEnable
					INTEGER,
				hwhqosLinkAdjExcludeRowStatus
					RowStatus
			 }

-- 1.3.6.1.4.1.2011.5.25.132.1.61.1.1
		hwhqosLinkAdjExcludeSlotNumber OBJECT-TYPE
			SYNTAX Integer32 (1..128)
			MAX-ACCESS read-only
			STATUS current
			DESCRIPTION
				" "
			::= { hwhqosLinkAdjExcludeEntry 1 }
		
-- 1.3.6.1.4.1.2011.5.25.132.1.61.1.2
		hwhqosLinkAdjExcludeEnable OBJECT-TYPE
			SYNTAX INTEGER
				{
				enable(1),
				disable(2)
				}
			MAX-ACCESS read-create
			STATUS current
			DESCRIPTION
				" "
			::= { hwhqosLinkAdjExcludeEntry 2 }
		
-- 1.3.6.1.4.1.2011.5.25.132.1.61.1.50
		hwhqosLinkAdjExcludeRowStatus OBJECT-TYPE
			SYNTAX RowStatus
			MAX-ACCESS read-create
			STATUS current
			DESCRIPTION
				" "
			::= { hwhqosLinkAdjExcludeEntry 50 }
		
--******************************************************************
-- 
-- hwhqosProfileInfoTable
-- 
-- ******************************************************************
-- 1.3.6.1.4.1.2011.5.25.132.1.62
		hwhqosProfileInfoTable OBJECT-TYPE
			SYNTAX SEQUENCE OF HwhqosProfileInfoEntry
			MAX-ACCESS not-accessible
			STATUS current
			DESCRIPTION
				" hwhqosProfileInfoTable "
			::= { hwhqosStat 62 }
		
-- 1.3.6.1.4.1.2011.5.25.132.1.62.1
		hwhqosProfileInfoEntry OBJECT-TYPE
			SYNTAX HwhqosProfileInfoEntry
			MAX-ACCESS not-accessible
			STATUS current
			DESCRIPTION
				" hwhqosProfileInfoEntry "
			INDEX { hwhqosProfileInfoName }
			::= { hwhqosProfileInfoTable 1 }
		
		HwhqosProfileInfoEntry ::=
			SEQUENCE { 
				hwhqosProfileInfoName
					OCTET STRING,
				hwhqosProfileInfoDescription
					OCTET STRING,
				hwhqosProfileInfoRowStatus
					RowStatus
			 }

-- 1.3.6.1.4.1.2011.5.25.132.1.62.1.1
-- BEGIN: mod by l00248629, 2014/03/21
		hwhqosProfileInfoName OBJECT-TYPE
			SYNTAX OCTET STRING (SIZE (1..63))
			MAX-ACCESS read-only
			STATUS current
			DESCRIPTION
				" hwhqosProfileInfoName "
			::= { hwhqosProfileInfoEntry 1 }
-- END: mod by l00248629, 2014/03/21
-- 1.3.6.1.4.1.2011.5.25.132.1.62.1.2
		hwhqosProfileInfoDescription OBJECT-TYPE
			SYNTAX OCTET STRING (SIZE (1..1023))
			MAX-ACCESS read-create
			STATUS current
			DESCRIPTION
				" hwhqosProfileInfoDescription "
			::= { hwhqosProfileInfoEntry 2 }
		
-- 1.3.6.1.4.1.2011.5.25.132.1.62.1.50
		hwhqosProfileInfoRowStatus OBJECT-TYPE
			SYNTAX RowStatus
			MAX-ACCESS read-create
			STATUS current
			DESCRIPTION
				"
				Row status. The value ranges from 1 to 6 but usually 4 and 6 are used.
				createAndGo[4] - create a row.
				destroy[6] -delete a row.
				"
			::= { hwhqosProfileInfoEntry 50 }
		
-- ******************************************************************
-- 
-- hwhqosUserGroupQueueTemplateTable
-- 
-- ******************************************************************
-- 1.3.6.1.4.1.2011.5.25.132.1.63
		hwhqosUserGroupQueueTemplateTable OBJECT-TYPE
			SYNTAX SEQUENCE OF HwhqosUserGroupQueueTemplateEntry
			MAX-ACCESS not-accessible
			STATUS current
			DESCRIPTION
				" hwhqosUserGroupQueueTemplateTable "
			::= { hwhqosStat 63 }
		
-- 1.3.6.1.4.1.2011.5.25.132.1.63.1
		hwhqosUserGroupQueueTemplateEntry OBJECT-TYPE
			SYNTAX HwhqosUserGroupQueueTemplateEntry
			MAX-ACCESS not-accessible
			STATUS current
			DESCRIPTION
				" hwhqosUserGroupQueueTemplateEntry "
			INDEX { hwhqosUserGroupQueueTemplateName }
			::= { hwhqosUserGroupQueueTemplateTable 1 }
		
		HwhqosUserGroupQueueTemplateEntry ::=
			SEQUENCE { 
				hwhqosUserGroupQueueTemplateName
					OCTET STRING,
				hwhqosUserGroupQueueTemplateModeTemplate
					Integer32,
				hwhqosUserGroupQueueTemplateRowStatus
					RowStatus
			 }

-- 1.3.6.1.4.1.2011.5.25.132.1.63.1.1
		hwhqosUserGroupQueueTemplateName OBJECT-TYPE
			SYNTAX OCTET STRING (SIZE (1..31))
			MAX-ACCESS read-only
			STATUS current
			DESCRIPTION
				" hwhqosUserGroupQueueTemplateName  "
			::= { hwhqosUserGroupQueueTemplateEntry 1 }
		
-- 1.3.6.1.4.1.2011.5.25.132.1.63.1.2
		hwhqosUserGroupQueueTemplateModeTemplate OBJECT-TYPE
			SYNTAX Integer32 (1..2)
			MAX-ACCESS read-create
			STATUS current
			DESCRIPTION
				" 
				1: modetemplate
				2: unmodetemplate  "
			::= { hwhqosUserGroupQueueTemplateEntry 2 }
		
-- 1.3.6.1.4.1.2011.5.25.132.1.63.1.50
		hwhqosUserGroupQueueTemplateRowStatus OBJECT-TYPE
			SYNTAX RowStatus
			MAX-ACCESS read-create
			STATUS current
			DESCRIPTION
				"
				Row status. The value ranges from 1 to 6 but usually 4 and 6 are used.
				createAndGo[4] - create a row.
				destroy[destroy[6] -delete a row.
				"
			::= { hwhqosUserGroupQueueTemplateEntry 50 }
		
-- ******************************************************************
-- 
-- hwhqosProfileWeightTable
-- 
-- ******************************************************************
-- 1.3.6.1.4.1.2011.5.25.132.1.64
		hwhqosProfileWeightTable OBJECT-TYPE
			SYNTAX SEQUENCE OF HwhqosProfileWeightEntry
			MAX-ACCESS not-accessible
			STATUS current
			DESCRIPTION
				" hwhqosProfileWeightTable "
			::= { hwhqosStat 64 }
		
-- 1.3.6.1.4.1.2011.5.25.132.1.64.1
		hwhqosProfileWeightEntry OBJECT-TYPE
			SYNTAX HwhqosProfileWeightEntry
			MAX-ACCESS not-accessible
			STATUS current
			DESCRIPTION
				" hwhqosProfileWeightTableEntry "
			INDEX { hwhqosProfileName, hwhqosProfileWeightDirection }
			::= { hwhqosProfileWeightTable 1 }
		
		HwhqosProfileWeightEntry ::=
			SEQUENCE { 
				hwhqosProfileWeightDirection
					INTEGER,
				hwhqosProfileWeightValue
					Integer32,
				hwhqosProfileWeightRowStatus
					RowStatus
			 }

-- 1.3.6.1.4.1.2011.5.25.132.1.64.1.1
		hwhqosProfileWeightDirection OBJECT-TYPE
			SYNTAX INTEGER
				{
				inbound(1),
				outbound(2),
				inout(3)
				}
			MAX-ACCESS read-only
			STATUS current
			DESCRIPTION
				"This object indicates the direction where weight is applied."
			::= { hwhqosProfileWeightEntry 1 }
		
-- 1.3.6.1.4.1.2011.5.25.132.1.64.1.2
		hwhqosProfileWeightValue OBJECT-TYPE
			SYNTAX Integer32 (1..63)
			MAX-ACCESS read-create
			STATUS current
			DESCRIPTION
				"This object indicates the weight value of user-queue."
			::= { hwhqosProfileWeightEntry 2 }
		
-- 1.3.6.1.4.1.2011.5.25.132.1.64.1.50
		hwhqosProfileWeightRowStatus OBJECT-TYPE
			SYNTAX RowStatus
			MAX-ACCESS read-create
			STATUS current
			DESCRIPTION
				"This object indicates the row status.
				Currently, three row statuses are supported: Active, CreateAndGo, and Destroy."
			::= { hwhqosProfileWeightEntry 50 }
		
--/*Begin Added by lishutian 00174417 for NP4_HQOS_RELEASE2 user-queue-apply-alarm  2013-4-20*/
-- ******************************************************************
-- 
-- hwhqosUserQueueApplyAlarmTable
-- 
-- ******************************************************************
-- 1.3.6.1.4.1.2011.5.25.132.1.65
		hwhqosUserQueueApplyAlarmTable OBJECT-TYPE
			SYNTAX SEQUENCE OF HwhqosUserQueueApplyAlarmEntry
			MAX-ACCESS not-accessible
			STATUS current
			DESCRIPTION
				" hwhqosUserQueueApplyAlarmTable "
			::= { hwhqosStat 65 }
		
-- 1.3.6.1.4.1.2011.5.25.132.1.65.1
		hwhqosUserQueueApplyAlarmEntry OBJECT-TYPE
			SYNTAX HwhqosUserQueueApplyAlarmEntry
			MAX-ACCESS not-accessible
			STATUS current
			DESCRIPTION
				" hwhqosUserQueueApplyAlarmEntry "
			INDEX { hwhqosUserQueueApplyAlarmIfNetName }
			::= { hwhqosUserQueueApplyAlarmTable 1 }
		
		HwhqosUserQueueApplyAlarmEntry ::=
			SEQUENCE { 
				hwhqosUserQueueApplyAlarmIfNetName
					OCTET STRING
			 }

-- 1.3.6.1.4.1.2011.5.25.132.1.65.1.1
		hwhqosUserQueueApplyAlarmIfNetName OBJECT-TYPE
			SYNTAX OCTET STRING (SIZE (1..511))
			MAX-ACCESS read-create
			STATUS current
			DESCRIPTION
				"This object indicates the name of the interface which apply user-queue.
				The object is a string of 1 to 31 characters."
			::= { hwhqosUserQueueApplyAlarmEntry 1 }
		
--           /*End Added by lishutian 00174417 for NP4_HQOS_RELEASE2 user-queue-apply-alarm 2013-4-20*/
-- beg:mod by j00126783 for port-queue-discard-trap 2012-07-31              
-- 1.3.6.1.4.1.2011.5.25.132.1.66
		hwhqosPortQueueStatDiscardAlarmTrapTable OBJECT-TYPE
			SYNTAX SEQUENCE OF HwhqosPortQueueStatDiscardAlarmTrapEntry
			MAX-ACCESS not-accessible
			STATUS current
			DESCRIPTION
				"hwhqosPortQueueStatDiscardAlarmTrapTable"
			::= { hwhqosStat 66 }
		
-- 1.3.6.1.4.1.2011.5.25.132.1.66.1
		hwhqosPortQueueStatDiscardAlarmTrapEntry OBJECT-TYPE
			SYNTAX HwhqosPortQueueStatDiscardAlarmTrapEntry
			MAX-ACCESS not-accessible
			STATUS current
			DESCRIPTION
				"hwhqosPortQueueStatDiscardAlarmTrapEntry"
			INDEX { hwhqosPortQueueInterfaceTrap, hwhqosPortQueueCosValueTrap, hwhqosPortQueueDiscardTypeTrap, hwhqosPortQueueDiscardValueTrap }
			::= { hwhqosPortQueueStatDiscardAlarmTrapTable 1 }
		
		HwhqosPortQueueStatDiscardAlarmTrapEntry ::=
			SEQUENCE { 
				hwhqosPortQueueInterfaceTrap
					OCTET STRING,
				hwhqosPortQueueCosValueTrap
					INTEGER,
				hwhqosPortQueueDiscardTypeTrap
					INTEGER,
				hwhqosPortQueueDiscardValueTrap
					OCTET STRING
			 }

-- 1.3.6.1.4.1.2011.5.25.132.1.66.1.1
		hwhqosPortQueueInterfaceTrap OBJECT-TYPE
			SYNTAX OCTET STRING (SIZE (1..511))
			MAX-ACCESS read-only
			STATUS current
			DESCRIPTION
				"The value of this object identifies the name of an interface."
			::= { hwhqosPortQueueStatDiscardAlarmTrapEntry 1 }
		
-- 1.3.6.1.4.1.2011.5.25.132.1.66.1.2
		hwhqosPortQueueCosValueTrap OBJECT-TYPE
			SYNTAX INTEGER
				{
				portqueueBE(1),
				portqueueAF1(2),
				portqueueAF2(3),
				portqueueAF3(4),
				portqueueAF4(5),
				portqueueEF(6),
				portqueueCS6(7),
				portqueueCS7(8)
				}
			MAX-ACCESS read-only
			STATUS current
			DESCRIPTION
				"
				The value of this object identifies the queue type.
				The value can be any of the following:
				PORTQUEUEBE(1),
				PORTQUEUEAF1(2),
				PORTQUEUEAF2(3),
				PORTQUEUEAF3(4),
				PORTQUEUEAF4(5),
				PORTQUEUEEF(6),
				PORTQUEUECS6(7),
				PORTQUEUECS7(8)   
				"
			::= { hwhqosPortQueueStatDiscardAlarmTrapEntry 2 }
		
-- 1.3.6.1.4.1.2011.5.25.132.1.66.1.3
		hwhqosPortQueueDiscardTypeTrap OBJECT-TYPE
			SYNTAX INTEGER
				{
				discardpacket(1),
				discardbyte(2),
				discardpacketratio(3)
				}
			MAX-ACCESS read-only
			STATUS current
			DESCRIPTION
				"The value of this object identifies the discard type.
				The value can be any of the following:
				DISCARD-PACKET(1), 
				DISCARD-BYTE(2), 
				DISCARD-PACKET-RATIO(3)
				"
			::= { hwhqosPortQueueStatDiscardAlarmTrapEntry 3 }
		
-- 1.3.6.1.4.1.2011.5.25.132.1.66.1.4
		hwhqosPortQueueDiscardValueTrap OBJECT-TYPE
			SYNTAX OCTET STRING (SIZE (1..511))
			MAX-ACCESS read-only
			STATUS current
			DESCRIPTION
				"This object indicates the discard value."
			::= { hwhqosPortQueueStatDiscardAlarmTrapEntry 4 }
		
-- 1.3.6.1.4.1.2011.5.25.132.1.67
		hwhqosPortQueueStatDiscardAlarmCancelTable OBJECT-TYPE
			SYNTAX SEQUENCE OF HwhqosPortQueueStatDiscardAlarmCancelEntry
			MAX-ACCESS not-accessible
			STATUS current
			DESCRIPTION
				"hwhqosPortQueueStatDiscardAlarmCancelTable"
			::= { hwhqosStat 67 }
		
-- 1.3.6.1.4.1.2011.5.25.132.1.67.1
		hwhqosPortQueueStatDiscardAlarmCancelEntry OBJECT-TYPE
			SYNTAX HwhqosPortQueueStatDiscardAlarmCancelEntry
			MAX-ACCESS not-accessible
			STATUS current
			DESCRIPTION
				"hwhqosPortQueueStatDiscardAlarmCancelEntry"
			INDEX { hwhqosPortQueueInterfaceCancel, hwhqosPortQueueCosValueCancel, hwhqosPortQueueDiscardTypeCancel, hwhqosPortQueueDiscardValueCancel }
			::= { hwhqosPortQueueStatDiscardAlarmCancelTable 1 }
		
		HwhqosPortQueueStatDiscardAlarmCancelEntry ::=
			SEQUENCE { 
				hwhqosPortQueueInterfaceCancel
					OCTET STRING,
				hwhqosPortQueueCosValueCancel
					INTEGER,
				hwhqosPortQueueDiscardTypeCancel
					INTEGER,
				hwhqosPortQueueDiscardValueCancel
					OCTET STRING
			 }

-- 1.3.6.1.4.1.2011.5.25.132.1.67.1.1
		hwhqosPortQueueInterfaceCancel OBJECT-TYPE
			SYNTAX OCTET STRING (SIZE (1..511))
			MAX-ACCESS read-only
			STATUS current
			DESCRIPTION
				"The value of this object identifies the name of an interface."
			::= { hwhqosPortQueueStatDiscardAlarmCancelEntry 1 }
		
-- 1.3.6.1.4.1.2011.5.25.132.1.67.1.2
		hwhqosPortQueueCosValueCancel OBJECT-TYPE
			SYNTAX INTEGER
				{
				portqueueBE(1),
				portqueueAF1(2),
				portqueueAF2(3),
				portqueueAF3(4),
				portqueueAF4(5),
				portqueueEF(6),
				portqueueCS6(7),
				portqueueCS7(8)
				}
			MAX-ACCESS read-only
			STATUS current
			DESCRIPTION
				"
				The value of this object identifies the queue type.
				The value can be any of the following:
				PORTQUEUEBE(1),
				PORTQUEUEAF1(2),
				PORTQUEUEAF2(3),
				PORTQUEUEAF3(4),
				PORTQUEUEAF4(5),
				PORTQUEUEEF(6),
				PORTQUEUECS6(7),
				PORTQUEUECS7(8)   
				"
			::= { hwhqosPortQueueStatDiscardAlarmCancelEntry 2 }
		
-- 1.3.6.1.4.1.2011.5.25.132.1.67.1.3
		hwhqosPortQueueDiscardTypeCancel OBJECT-TYPE
			SYNTAX INTEGER
				{
				discardpacket(1),
				discardbyte(2),
				discardpacketratio(3)
				}
			MAX-ACCESS read-only
			STATUS current
			DESCRIPTION
				"The value of this object identifies the discard type.
				The value can be any of the following:
				DISCARD-PACKET(1), 
				DISCARD-BYTE(2), 
				DISCARD-PACKET-RATIO(3)
				"
			::= { hwhqosPortQueueStatDiscardAlarmCancelEntry 3 }
		
-- 1.3.6.1.4.1.2011.5.25.132.1.67.1.4
		hwhqosPortQueueDiscardValueCancel OBJECT-TYPE
			SYNTAX OCTET STRING (SIZE (1..511))
			MAX-ACCESS read-only
			STATUS current
			DESCRIPTION
				"This object indicates the discard value."
			::= { hwhqosPortQueueStatDiscardAlarmCancelEntry 4 }
--           end:mod by j00126783 for port-queue-discard-trap 2012-07-31              
		
-- 1.3.6.1.4.1.2011.5.25.132.1.68
		hwhqosIfUserQueueTable OBJECT-TYPE
			SYNTAX SEQUENCE OF HwhqosIfUserQueueEntry
			MAX-ACCESS not-accessible
			STATUS current
			DESCRIPTION
				"Description."
			::= { hwhqosStat 68 }
		
-- 1.3.6.1.4.1.2011.5.25.132.1.68.1
		hwhqosIfUserQueueEntry OBJECT-TYPE
			SYNTAX HwhqosIfUserQueueEntry
			MAX-ACCESS not-accessible
			STATUS current
			DESCRIPTION
				"Description."
			INDEX { hwhqosIfUserQueueIfIndex, hwhqosIfUserQueueAclType, hwhqosIfUserQueueAclID1, hwhqosIfUserQueueAclID2 }
			::= { hwhqosIfUserQueueTable 1 }
		
		HwhqosIfUserQueueEntry ::=
			SEQUENCE { 
				hwhqosIfUserQueueIfIndex
					Integer32,
				hwhqosIfUserQueueAclType
					INTEGER,
				hwhqosIfUserQueueAclID1
					Integer32,
				hwhqosIfUserQueueAclID2
					Integer32,
				hwhqosIfUserQueuePir
					Integer32,
				hwhqosIfUserQueueFlowQueueProfileName
					OCTET STRING,
				hwhqosIfUserQueueFlowMappingProfileName
					OCTET STRING,
				hwhqosIfUserQueueRowStatus
					RowStatus
			 }

-- 1.3.6.1.4.1.2011.5.25.132.1.68.1.1
		hwhqosIfUserQueueIfIndex OBJECT-TYPE
			SYNTAX Integer32
			MAX-ACCESS not-accessible
			STATUS current
			DESCRIPTION
				"Description."
			::= { hwhqosIfUserQueueEntry 1 }
		
-- 1.3.6.1.4.1.2011.5.25.132.1.68.1.2
		hwhqosIfUserQueueAclType OBJECT-TYPE
			SYNTAX INTEGER
				{
				ipv4(1),
				ipv6(2)
				}
			MAX-ACCESS not-accessible
			STATUS current
			DESCRIPTION
				"Description."
			::= { hwhqosIfUserQueueEntry 2 }
		
-- 1.3.6.1.4.1.2011.5.25.132.1.68.1.3
		hwhqosIfUserQueueAclID1 OBJECT-TYPE
			SYNTAX Integer32
			MAX-ACCESS not-accessible
			STATUS current
			DESCRIPTION
				"Description."
			::= { hwhqosIfUserQueueEntry 3 }
		
-- 1.3.6.1.4.1.2011.5.25.132.1.68.1.4
		hwhqosIfUserQueueAclID2 OBJECT-TYPE
			SYNTAX Integer32
			MAX-ACCESS not-accessible
			STATUS current
			DESCRIPTION
				"Description."
			::= { hwhqosIfUserQueueEntry 4 }		
		
-- 1.3.6.1.4.1.2011.5.25.132.1.68.1.6
		hwhqosIfUserQueuePir OBJECT-TYPE
			SYNTAX Integer32 (64..10000000)
			MAX-ACCESS read-create
			STATUS current
			DESCRIPTION
				"Description."
			::= { hwhqosIfUserQueueEntry 6 }
		
-- 1.3.6.1.4.1.2011.5.25.132.1.68.1.7
		hwhqosIfUserQueueFlowQueueProfileName OBJECT-TYPE
			SYNTAX OCTET STRING (SIZE (1..31))
			MAX-ACCESS read-write
			STATUS current
			DESCRIPTION
				"Description."
			::= { hwhqosIfUserQueueEntry 7 }
		
-- 1.3.6.1.4.1.2011.5.25.132.1.68.1.8
		hwhqosIfUserQueueFlowMappingProfileName OBJECT-TYPE
			SYNTAX OCTET STRING (SIZE (1..31))
			MAX-ACCESS read-create
			STATUS current
			DESCRIPTION
				"Description."
			::= { hwhqosIfUserQueueEntry 8 }
		
-- 1.3.6.1.4.1.2011.5.25.132.1.68.1.9
		hwhqosIfUserQueueRowStatus OBJECT-TYPE
			SYNTAX RowStatus
			MAX-ACCESS read-create
			STATUS current
			DESCRIPTION
				"Description."
			::= { hwhqosIfUserQueueEntry 9 }
		
-- 1.3.6.1.4.1.2011.5.25.132.1.69
		hwhqosIfUserQueueStatisticsTable OBJECT-TYPE
			SYNTAX SEQUENCE OF HwhqosIfUserQueueStatisticsEntry
			MAX-ACCESS not-accessible
			STATUS current
			DESCRIPTION
				"Description."
			::= { hwhqosStat 69 }
		
-- 1.3.6.1.4.1.2011.5.25.132.1.69.1
		hwhqosIfUserQueueStatisticsEntry OBJECT-TYPE
			SYNTAX HwhqosIfUserQueueStatisticsEntry
			MAX-ACCESS not-accessible
			STATUS current
			DESCRIPTION
				"Description."
			INDEX { hwhqosIfUserQueueStatisticsIfIndex, hwhqosIfUserQueueStatisticsAclType, hwhqosIfUserQueueStatisticsAclID1, hwhqosIfUserQueueStatisticsAclID2, hwhqosIfUserQueueStatisticsQueueIndex
				 }
			::= { hwhqosIfUserQueueStatisticsTable 1 }
		
		HwhqosIfUserQueueStatisticsEntry ::=
			SEQUENCE { 
				hwhqosIfUserQueueStatisticsIfIndex
					Integer32,
				hwhqosIfUserQueueStatisticsAclType
					INTEGER,
				hwhqosIfUserQueueStatisticsAclID1
					Integer32,
				hwhqosIfUserQueueStatisticsAclID2
					Integer32,
				hwhqosIfUserQueueStatisticsQueueIndex
					INTEGER,
				hwhqosIfUserQueueStatisticsQueuePassPackets
					Counter64,
				hwhqosIfUserQueueStatisticsQueuePassBytes
					Counter64,
				hwhqosIfUserQueueStatisticsQueueDropPackets
					Counter64,
				hwhqosIfUserQueueStatisticsQueueDropBytes
					Counter64,
				hwhqosIfUserQueueStatisticsReset
					INTEGER
			 }

-- 1.3.6.1.4.1.2011.5.25.132.1.69.1.1
		hwhqosIfUserQueueStatisticsIfIndex OBJECT-TYPE
			SYNTAX Integer32
			MAX-ACCESS not-accessible
			STATUS current
			DESCRIPTION
				"Description."
			::= { hwhqosIfUserQueueStatisticsEntry 1 }
		
-- 1.3.6.1.4.1.2011.5.25.132.1.69.1.2
		hwhqosIfUserQueueStatisticsAclType OBJECT-TYPE
			SYNTAX INTEGER
				{
				ipv4(1),
				ipv6(2)
				}
			MAX-ACCESS not-accessible
			STATUS current
			DESCRIPTION
				"Description."
			::= { hwhqosIfUserQueueStatisticsEntry 2 }
		
-- 1.3.6.1.4.1.2011.5.25.132.1.69.1.3
		hwhqosIfUserQueueStatisticsAclID1 OBJECT-TYPE
			SYNTAX Integer32
			MAX-ACCESS not-accessible
			STATUS current
			DESCRIPTION
				"Description."
			::= { hwhqosIfUserQueueStatisticsEntry 3 }
		
-- 1.3.6.1.4.1.2011.5.25.132.1.69.1.4
		hwhqosIfUserQueueStatisticsAclID2 OBJECT-TYPE
			SYNTAX Integer32
			MAX-ACCESS not-accessible
			STATUS current
			DESCRIPTION
				"Description."
			::= { hwhqosIfUserQueueStatisticsEntry 4 }
		
-- 1.3.6.1.4.1.2011.5.25.132.1.69.1.5
		hwhqosIfUserQueueStatisticsQueueIndex OBJECT-TYPE
			SYNTAX INTEGER
				{
				be(1),
				af1(2),
				af2(3),
				af3(4),
				af4(5),
				ef(6),
				cs6(7),
				cs7(8),
				total(255)
				}
			MAX-ACCESS not-accessible
			STATUS current
			DESCRIPTION
				"Description."
			::= { hwhqosIfUserQueueStatisticsEntry 5 }
		
-- 1.3.6.1.4.1.2011.5.25.132.1.69.1.6
		hwhqosIfUserQueueStatisticsQueuePassPackets OBJECT-TYPE
			SYNTAX Counter64
			MAX-ACCESS read-only
			STATUS current
			DESCRIPTION
				"Description."
			::= { hwhqosIfUserQueueStatisticsEntry 6 }
		
-- 1.3.6.1.4.1.2011.5.25.132.1.69.1.7
		hwhqosIfUserQueueStatisticsQueuePassBytes OBJECT-TYPE
			SYNTAX Counter64
			MAX-ACCESS read-only
			STATUS current
			DESCRIPTION
				"Description."
			::= { hwhqosIfUserQueueStatisticsEntry 7 }
		
-- 1.3.6.1.4.1.2011.5.25.132.1.69.1.8
		hwhqosIfUserQueueStatisticsQueueDropPackets OBJECT-TYPE
			SYNTAX Counter64
			MAX-ACCESS read-only
			STATUS current
			DESCRIPTION
				"Description."
			::= { hwhqosIfUserQueueStatisticsEntry 8 }
		
-- 1.3.6.1.4.1.2011.5.25.132.1.69.1.9
		hwhqosIfUserQueueStatisticsQueueDropBytes OBJECT-TYPE
			SYNTAX Counter64
			MAX-ACCESS read-only
			STATUS current
			DESCRIPTION
				"Description."
			::= { hwhqosIfUserQueueStatisticsEntry 9 }
		
-- 1.3.6.1.4.1.2011.5.25.132.1.69.1.10
		hwhqosIfUserQueueStatisticsReset OBJECT-TYPE
			SYNTAX INTEGER
				{
				reset(1),
				other(2)
				}
			MAX-ACCESS read-write
			STATUS current
			DESCRIPTION
				"Description."
			::= { hwhqosIfUserQueueStatisticsEntry 10 }
			
-- 1.3.6.1.4.1.2011.5.25.132.1.70
		hwhqosUserQueueShapeAllTrafficTable OBJECT-TYPE
			SYNTAX SEQUENCE OF HwhqosUserQueueShapeAllTrafficEntry
			MAX-ACCESS not-accessible
			STATUS current
			DESCRIPTION
				"hwhqosUserQueueShapeAllTrafficTable"
			::= { hwhqosStat 70 }			

-- 1.3.6.1.4.1.2011.5.25.132.1.70.1
		hwhqosUserQueueShapeAllTrafficEntry OBJECT-TYPE
			SYNTAX HwhqosUserQueueShapeAllTrafficEntry
			MAX-ACCESS not-accessible
			STATUS current
			DESCRIPTION
				"hwhqosUserQueueShapeAllTrafficEntry"
			INDEX { hwhqosUserQueueShapeAllTrafficInterfaceIndex}
			::= { hwhqosUserQueueShapeAllTrafficTable 1 }
		
		HwhqosUserQueueShapeAllTrafficEntry ::=
			SEQUENCE { 
				hwhqosUserQueueShapeAllTrafficInterfaceIndex
					Integer32,
				hwhqosUserQueueShapeAllTrafficRowStatus
					RowStatus
			         }	
			    
-- 1.3.6.1.4.1.2011.5.25.132.1.70.1.1
		hwhqosUserQueueShapeAllTrafficInterfaceIndex OBJECT-TYPE
			SYNTAX Integer32
			MAX-ACCESS not-accessible
			STATUS current
			DESCRIPTION
				"hwhqosUserQueueShapeAllTrafficInterfaceIndex"
			::= { hwhqosUserQueueShapeAllTrafficEntry 1 }
		
-- 1.3.6.1.4.1.2011.5.25.132.1.70.1.2
		hwhqosUserQueueShapeAllTrafficRowStatus OBJECT-TYPE
			SYNTAX RowStatus
			MAX-ACCESS read-create
			STATUS current
			DESCRIPTION
				"
				Row status. The value ranges from 1 to 6 but usually 4 and 6 are used.
				createAndGo[4] - create a row.
				destroy[destroy[6] -delete a row.
				"
			::= { hwhqosUserQueueShapeAllTrafficEntry 2 }

--  ******************************************************************
-- 
-- hwhqosUserGroupQueueInterfaceStatisticsTable
-- 
-- ******************************************************************
-- 1.3.6.1.4.1.2011.5.25.132.1.71
		hwhqosUserGroupQueueInterfaceStatisticsTable OBJECT-TYPE
			SYNTAX SEQUENCE OF HwhqosUserGroupQueueInterfaceStatisticsEntry
			MAX-ACCESS not-accessible
			STATUS current
			DESCRIPTION
				" hwhqosUserGroupQueueInterfaceStatisticsTable "
			::= { hwhqosStat 71 }
		
-- 1.3.6.1.4.1.2011.5.25.132.1.71.1
		hwhqosUserGroupQueueInterfaceStatisticsEntry OBJECT-TYPE
			SYNTAX HwhqosUserGroupQueueInterfaceStatisticsEntry
			MAX-ACCESS not-accessible
			STATUS current
			DESCRIPTION
				" hwhqosUserGroupQueueInterfaceStatisticsEntry "
			INDEX { hwhqosUserGroupQueueInterfaceStatisticsIfIndex, hwhqosUserGroupQueueInterfaceStatisticsDirection, hwhqosUserGroupQueueInterfaceStatisticsPevid, hwhqosUserGroupQueueInterfaceStatisticsCevid, hwhqosUserGroupQueueInterfaceStatisticsVlanid, hwhqosUserGroupQueueInterfaceStatisticsQueueIndex }
			::= { hwhqosUserGroupQueueInterfaceStatisticsTable 1 }
		
		HwhqosUserGroupQueueInterfaceStatisticsEntry ::=
			SEQUENCE { 
				hwhqosUserGroupQueueInterfaceStatisticsIfIndex
					Integer32,
				hwhqosUserGroupQueueInterfaceStatisticsDirection
					INTEGER,
				hwhqosUserGroupQueueInterfaceStatisticsPevid
					Integer32,
				hwhqosUserGroupQueueInterfaceStatisticsCevid
					Integer32,
				hwhqosUserGroupQueueInterfaceStatisticsVlanid					
					Integer32,
				hwhqosUserGroupQueueInterfaceStatisticsQueueIndex
				    INTEGER,
				hwhqosUserGroupQueueInterfaceStatisticsReset
					INTEGER,
				hwhqosUserGroupQueueInterfaceStatisticsPassPackets
					Counter64,
				hwhqosUserGroupQueueInterfaceStatisticsPassBytes
					Counter64,
				hwhqosUserGroupQueueInterfaceStatisticsDropPackets
					Counter64,
				hwhqosUserGroupQueueInterfaceStatisticsDropBytes
					Counter64,
				hwhqosUserGroupQueueInterfaceStatisticsPassPacketsRate
					Counter64,
				hwhqosUserGroupQueueInterfaceStatisticsPassBytesRate
					Counter64,
				hwhqosUserGroupQueueInterfaceStatisticsDropPacketsRate
					Counter64,
				hwhqosUserGroupQueueInterfaceStatisticsDropBytesRate
					Counter64
			 }

-- 1.3.6.1.4.1.2011.5.25.132.1.71.1.1
		hwhqosUserGroupQueueInterfaceStatisticsIfIndex OBJECT-TYPE
			SYNTAX Integer32 (0..2147483647)
			MAX-ACCESS read-only
			STATUS current
			DESCRIPTION
				"The value of this object identifies the index of an interface."
			::= { hwhqosUserGroupQueueInterfaceStatisticsEntry 1 }

-- 1.3.6.1.4.1.2011.5.25.132.1.71.1.2
		hwhqosUserGroupQueueInterfaceStatisticsDirection OBJECT-TYPE
			SYNTAX INTEGER
				{
				inbound(1),
				outbound(2)
				}
			MAX-ACCESS read-only
			STATUS current
			DESCRIPTION
				"This object indicates the direction where a user group queue template is applied."
			::= { hwhqosUserGroupQueueInterfaceStatisticsEntry 2 }

-- 1.3.6.1.4.1.2011.5.25.132.1.71.1.3
		hwhqosUserGroupQueueInterfaceStatisticsPevid OBJECT-TYPE
			SYNTAX Integer32 (0..4094)
			MAX-ACCESS read-only
			STATUS current
			DESCRIPTION
				"The value of this object identifies the pevid of an interface."
			::= { hwhqosUserGroupQueueInterfaceStatisticsEntry 3 }

-- 1.3.6.1.4.1.2011.5.25.132.1.71.1.4
		hwhqosUserGroupQueueInterfaceStatisticsCevid OBJECT-TYPE
			SYNTAX Integer32 (0..4094)
			MAX-ACCESS read-only
			STATUS current
			DESCRIPTION
				"The value of this object identifies the cevid of an interface."
			::= { hwhqosUserGroupQueueInterfaceStatisticsEntry 4 }
						
-- 1.3.6.1.4.1.2011.5.25.132.1.71.1.5
		hwhqosUserGroupQueueInterfaceStatisticsVlanid OBJECT-TYPE
			SYNTAX Integer32 (0..4094)
			MAX-ACCESS read-only
			STATUS current
			DESCRIPTION
				"The value of this object identifies the vlanid of an interface."
			::= { hwhqosUserGroupQueueInterfaceStatisticsEntry 5 }
						
-- 1.3.6.1.4.1.2011.5.25.132.1.71.1.6
		hwhqosUserGroupQueueInterfaceStatisticsQueueIndex OBJECT-TYPE
			SYNTAX INTEGER
				{
				be(1),
				af1(2),
				af2(3),
				af3(4),
				af4(5),
				ef(6),
				cs6(7),
				cs7(8),
				total(9)
				}			
			MAX-ACCESS read-only
			STATUS current
			DESCRIPTION
				"hwhqosUserGroupQueueInterfaceStatisticsQueueIndex"
			::= { hwhqosUserGroupQueueInterfaceStatisticsEntry 6 }
						
-- 1.3.6.1.4.1.2011.5.25.132.1.71.1.7
		hwhqosUserGroupQueueInterfaceStatisticsReset OBJECT-TYPE
			SYNTAX INTEGER { reset(1) }
			MAX-ACCESS read-create
			STATUS current
			DESCRIPTION
				"This object indicates the resetting of statistics."
			::= { hwhqosUserGroupQueueInterfaceStatisticsEntry 7 }
						
-- 1.3.6.1.4.1.2011.5.25.132.1.71.1.8
		hwhqosUserGroupQueueInterfaceStatisticsPassPackets OBJECT-TYPE
			SYNTAX Counter64
			MAX-ACCESS read-only
			STATUS current
			DESCRIPTION
				"This object indicates the number of passed packets."
			::= { hwhqosUserGroupQueueInterfaceStatisticsEntry 8 }
						
-- 1.3.6.1.4.1.2011.5.25.132.1.71.1.9
		hwhqosUserGroupQueueInterfaceStatisticsPassBytes OBJECT-TYPE
			SYNTAX Counter64
			MAX-ACCESS read-only
			STATUS current
			DESCRIPTION
				"This object indicates the number of passed bytes."
			::= { hwhqosUserGroupQueueInterfaceStatisticsEntry 9 }
						
-- 1.3.6.1.4.1.2011.5.25.132.1.71.1.10
		hwhqosUserGroupQueueInterfaceStatisticsDropPackets OBJECT-TYPE
			SYNTAX Counter64
			MAX-ACCESS read-only
			STATUS current
			DESCRIPTION
				"This object indicates the number of discarded packets."
			::= { hwhqosUserGroupQueueInterfaceStatisticsEntry 10 }
						
-- 1.3.6.1.4.1.2011.5.25.132.1.71.1.11
		hwhqosUserGroupQueueInterfaceStatisticsDropBytes OBJECT-TYPE
			SYNTAX Counter64
			MAX-ACCESS read-only
			STATUS current
			DESCRIPTION
				"This object indicates the number of discarded bytes."
			::= { hwhqosUserGroupQueueInterfaceStatisticsEntry 11 }
						
-- 1.3.6.1.4.1.2011.5.25.132.1.71.1.12
		hwhqosUserGroupQueueInterfaceStatisticsPassPacketsRate OBJECT-TYPE
			SYNTAX Counter64
			MAX-ACCESS read-only
			STATUS current
			DESCRIPTION
				"hwhqosUserGroupQueueInterfaceStatisticsPassPacketsRate."
			::= { hwhqosUserGroupQueueInterfaceStatisticsEntry 12 }
						
-- 1.3.6.1.4.1.2011.5.25.132.1.71.1.13
		hwhqosUserGroupQueueInterfaceStatisticsPassBytesRate OBJECT-TYPE
			SYNTAX Counter64
			MAX-ACCESS read-only
			STATUS current
			DESCRIPTION
				"hwhqosUserGroupQueueInterfaceStatisticsPassBytesRate."
			::= { hwhqosUserGroupQueueInterfaceStatisticsEntry 13 }
						
-- 1.3.6.1.4.1.2011.5.25.132.1.71.1.14
		hwhqosUserGroupQueueInterfaceStatisticsDropPacketsRate OBJECT-TYPE
			SYNTAX Counter64
			MAX-ACCESS read-only
			STATUS current
			DESCRIPTION
				"hwhqosUserGroupQueueInterfaceStatisticsDropPacketsRate."
			::= { hwhqosUserGroupQueueInterfaceStatisticsEntry 14 }
						
-- 1.3.6.1.4.1.2011.5.25.132.1.71.1.15
		hwhqosUserGroupQueueInterfaceStatisticsDropBytesRate OBJECT-TYPE
			SYNTAX Counter64
			MAX-ACCESS read-only
			STATUS current
			DESCRIPTION
				"hwhqosUserGroupQueueInterfaceStatisticsDropBytesRate."
			::= { hwhqosUserGroupQueueInterfaceStatisticsEntry 15 }	

-- 1.3.6.1.4.1.2011.5.25.132.1.72
		hwhqosIfProfileUserQueueStatisticsIntervalTable OBJECT-TYPE
			SYNTAX SEQUENCE OF HwhqosIfProfileUserQueueStatisticsIntervalEntry
			MAX-ACCESS not-accessible
			STATUS current
			DESCRIPTION
				"This object indicates the table of queue statistics intervals."
			::= { hwhqosStat 72 }			

-- 1.3.6.1.4.1.2011.5.25.132.1.72.1
		hwhqosIfProfileUserQueueStatisticsIntervalEntry OBJECT-TYPE
			SYNTAX HwhqosIfProfileUserQueueStatisticsIntervalEntry
			MAX-ACCESS not-accessible
			STATUS current
			DESCRIPTION
				"This object indicates the entry of queue statistics intervals. "
			INDEX { hwhqosIfProfileUserQueueStatisticsInterfaceIndex}
			::= { hwhqosIfProfileUserQueueStatisticsIntervalTable 1 }
		
		HwhqosIfProfileUserQueueStatisticsIntervalEntry::=
			SEQUENCE { 
				hwhqosIfProfileUserQueueStatisticsInterfaceIndex
					InterfaceIndex,
				hwhqosIfProfileUserQueueStatisticsInterval
					INTEGER
			         }	
			    
-- 1.3.6.1.4.1.2011.5.25.132.1.72.1.1
		hwhqosIfProfileUserQueueStatisticsInterfaceIndex OBJECT-TYPE
			SYNTAX InterfaceIndex
			MAX-ACCESS read-only
			STATUS current
			DESCRIPTION
				"This object indicates the name of the interface."
			::= { hwhqosIfProfileUserQueueStatisticsIntervalEntry 1 }
		
-- 1.3.6.1.4.1.2011.5.25.132.1.72.1.2
		hwhqosIfProfileUserQueueStatisticsInterval OBJECT-TYPE
			SYNTAX INTEGER { interval0(0), interval5(5), interval30(30), interval300(300) }
			MAX-ACCESS read-create
			STATUS current
			DESCRIPTION
				"
				The value of this object identifies the interval of queue statistics.
				"
			::= { hwhqosIfProfileUserQueueStatisticsIntervalEntry 2 }					    	
-- ******************************************************************        
-- 1.3.6.1.4.1.2011.5.25.132.2
		hwhqosObjects OBJECT IDENTIFIER ::= { hwHQOS 2 }
		
-- 1.3.6.1.4.1.2011.5.25.132.2.1
		hwhqosUserFrameId OBJECT-TYPE
			SYNTAX Integer32
			MAX-ACCESS read-only
			STATUS current
			DESCRIPTION
				"The ID of the frame which the alarm device located."
			::= { hwhqosObjects 1 }
		
-- 1.3.6.1.4.1.2011.5.25.132.2.2
		hwhqosUserSlotId OBJECT-TYPE
			SYNTAX Integer32
			MAX-ACCESS read-only
			STATUS current
			DESCRIPTION
				"The ID of the slot on which the alarmed HQoS user applied."
			::= { hwhqosObjects 2 }
		
-- 1.3.6.1.4.1.2011.5.25.132.2.3
		hwhqosUserPortId OBJECT-TYPE
			SYNTAX Integer32
			MAX-ACCESS read-only
			STATUS current
			DESCRIPTION
				"The ID of port on which the alarmed HQoS user applied."
			::= { hwhqosObjects 3 }
		
-- 1.3.6.1.4.1.2011.5.25.132.2.4
		hwhqosUserQueueApplyFailDirection OBJECT-TYPE
			SYNTAX INTEGER
				{
				inbound(1),
				outbound(2)
				}
			MAX-ACCESS read-only
			STATUS current
			DESCRIPTION
				"The direction of alarmed HQoS which user applied."
			::= { hwhqosObjects 4 }
-- 1.3.6.1.4.1.2011.5.25.132.2.5 
                                          hwhqosUserQueueApplyFailPool OBJECT-TYPE 
                                          SYNTAX INTEGER 
                                          { 
                                          pool0(1), 
                                          pool1(2) 
                                          } 
                                          MAX-ACCESS read-only 
                                          STATUS current 
                                          DESCRIPTION 
                                          "The pool of alarmed HQoS which user applied." 
                                          ::= { hwhqosObjects 5 } 


		
-- 1.3.6.1.4.1.2011.5.25.132.3
		hwhqosTraps OBJECT IDENTIFIER ::= { hwHQOS 3 }
		
-- 1.3.6.1.4.1.2011.5.25.132.3.1
		hwhqosUserQueueStatDiscardAlarmTrap NOTIFICATION-TYPE
			OBJECTS { hwhqosUserFrameId, hwhqosUserSlotId, hwhqosUserPortId, hwhqosUserQueueStatPerDropPackets }
			STATUS current
			DESCRIPTION 
				"The user queue discard alarm trap."
			::= { hwhqosTraps 1 }
		
-- 1.3.6.1.4.1.2011.5.25.132.3.2
		hwhqosUserQueueApplyPirFailAlarmTrap NOTIFICATION-TYPE
			OBJECTS { entPhysicalIndex, entPhysicalName, hwhqosUserQueueApplyFailDirection }
			STATUS current
			DESCRIPTION 
				"The user apply pir fail alarm trap."
			::= { hwhqosTraps 2 }
		
-- 1.3.6.1.4.1.2011.5.25.132.3.3
		hwhqosUserQueueApplyPirSucessAlarmTrap NOTIFICATION-TYPE
			OBJECTS { entPhysicalIndex, entPhysicalName, hwhqosUserQueueApplyFailDirection }
			STATUS current
			DESCRIPTION 
				"The user apply pir success alarm trap."
			::= { hwhqosTraps 3 }
		
--/*Begin Added by lishutian 00174417 for NP4_HQOS_RELEASE2 user-queue-apply-alarm 2013-4-20*/            
-- 1.3.6.1.4.1.2011.5.25.132.3.4
		hwhqosUserQueueApplyAlarmTrap NOTIFICATION-TYPE
			OBJECTS { hwhqosUserQueueApplyAlarmIfNetName }
			STATUS current
			DESCRIPTION 
				"The user-queue apply alarm trap."
			::= { hwhqosTraps 4 }
		
--/*End Added by lishutian 00174417 for NP4_HQOS_RELEASE2 user-queue-apply-alarm 2013-4-20*/              
-- /*Begin Added by by yuzongwen 90005638 for port queue alarm 2013-8-01*/            
-- 1.3.6.1.4.1.2011.5.25.132.3.5
		hwhqosPortQueueStatDiscardAlarmTrap NOTIFICATION-TYPE
			OBJECTS { hwhqosPortQueueInterfaceTrap, hwhqosPortQueueCosValueTrap, hwhqosPortQueueDiscardTypeTrap, hwhqosPortQueueDiscardValueTrap }
			STATUS current
			DESCRIPTION 
				"The PortQueue Stat Discard alarm trap."
			::= { hwhqosTraps 5 }
		
--/*End Added by by yuzongwen 90005638 for port queue alarm 2013-8-01*/     
-- /*Begin Added by yuzongwen 90005638 for port queue alarm 2013-8-01*/            
-- 1.3.6.1.4.1.2011.5.25.132.3.6
		hwhqosPortQueueStatDiscardAlarmCancelTrap NOTIFICATION-TYPE
			OBJECTS { hwhqosPortQueueInterfaceCancel, hwhqosPortQueueCosValueCancel, hwhqosPortQueueDiscardTypeCancel, hwhqosPortQueueDiscardValueCancel }
			STATUS current
			DESCRIPTION 
				"The PortQueue Stat Discard Cancel alarm trap."
			::= { hwhqosTraps 6 }
		
--/*End Added by yuzongwen 90005638 for port queue alarm 2013-8-01*/

-- 1.3.6.1.4.1.2011.5.25.132.3.7 
		hwhqosUserQueueApplyPirFromPoolFailAlarmTrap NOTIFICATION-TYPE 
			OBJECTS { entPhysicalIndex, entPhysicalName, hwhqosUserQueueApplyFailPool } 
		                      STATUS current 
		                      DESCRIPTION 
		                                          "The user apply PIRs from pool fail alarm trap." 
			::= { hwhqosTraps 7 } 

-- 1.3.6.1.4.1.2011.5.25.132.3.8 
		hwhqosUserQueueApplyPirFromPoolSucessAlarmTrap NOTIFICATION-TYPE 
		OBJECTS { entPhysicalIndex, entPhysicalName, hwhqosUserQueueApplyFailPool } 
		STATUS current 
		DESCRIPTION 
		"The user apply PIRs sucess alarm trap." 
		::= { hwhqosTraps 8 } 

-- 1.3.6.1.4.1.2011.5.25.132.3.9
		hwHQoSPwifScheduleTreeCreateFailAlarm NOTIFICATION-TYPE 
		OBJECTS { entPhysicalName, entPhysicalName } 
		STATUS current 
		DESCRIPTION 
		"Failed to create scheduling tree alarm."
		::= { hwhqosTraps 9 } 

-- 1.3.6.1.4.1.2011.5.25.132.3.10
		hwHQoSPwifScheduleTreeCreateFailAlarmClear NOTIFICATION-TYPE 
		OBJECTS { entPhysicalName, entPhysicalName } 
		STATUS current 
		DESCRIPTION 
		"Failed to create scheduling tree clear alarm."
		::= { hwhqosTraps 10 } 

 -- 1.3.6.1.4.1.2011.5.25.132.4
		hwhqosConformance OBJECT IDENTIFIER ::= { hwHQOS 4 }
		
-- 1.3.6.1.4.1.2011.5.25.132.4.1
		hwhqosCompliances OBJECT IDENTIFIER ::= { hwhqosConformance 1 }
		
-- this module
-- 1.3.6.1.4.1.2011.5.25.132.4.1.1
		hwhqosUserQueueStatCompliances MODULE-COMPLIANCE
			STATUS current
			DESCRIPTION 
				"The compliance statment."
			MODULE -- this module
				MANDATORY-GROUPS { hwhqosUserQueueStatGroup, hwhqosUserQueueStatTrapGroup }
			::= { hwhqosCompliances 1 }
		
-- 1.3.6.1.4.1.2011.5.25.132.4.2
		hwhqosGroups OBJECT IDENTIFIER ::= { hwhqosConformance 2 }
		
-- 1.3.6.1.4.1.2011.5.25.132.4.2.1
		hwhqosIfStatGroup OBJECT-GROUP
			OBJECTS { hwhqosQueueForwardPackets, hwhqosQueueForwardBytes, hwhqosQueueDropPackets, hwhqosQueueDropBytes, hwhqosQueueRemarkPackets, 
				hwhqosQueueRemarkBytes, hwhqosSetZero, hwhqosQueueForwardPacketRate, hwhqosQueueForwardByteRate, hwhqosQueueDropPacketRate, 
				hwhqosQueueDropByteRate }
			STATUS current
			DESCRIPTION 
				"Description."
			::= { hwhqosGroups 1 }
		
-- 1.3.6.1.4.1.2011.5.25.132.4.2.2
		hqhqosAtmPvcStatGroup OBJECT-GROUP
			OBJECTS { hwhqosAtmPvcQueueForwardPackets, hwhqosAtmPvcQueueForwardBytes, hwhqosAtmPvcQueueDropPackets, hwhqosAtmPvcQueueDropBytes, hwhqosAtmPvcQueueRemarkPackets, 
				hwhqosAtmPvcQueueRemarkBytes }
			STATUS current
			DESCRIPTION 
				"Description."
			::= { hwhqosGroups 2 }
		
-- 1.3.6.1.4.1.2011.5.25.132.4.2.3
		hwhqosPortQueueGroup OBJECT-GROUP
			OBJECTS { hwhqosPortQueueArithmetic, hwhqosPortQueueWeightValue, hwhqosPortQueueShaValue, hwhqosPortQueueShaPercent, hwhqosPortQueueWredName, 
				hwhqosPortQueuePbsValue, hwhqosPortQueueRowStatus }
			STATUS current
			DESCRIPTION 
				"Description."
			::= { hwhqosGroups 3 }
		
-- 1.3.6.1.4.1.2011.5.25.132.4.2.4
		hwhqosWredGroup OBJECT-GROUP
			OBJECTS { hwhqosWredGreenLowLimit, hwhqosWredGreenHighLimit, hwhqosWredGreenDiscardPercent, hwhqosWredYellowLowLimit, hwhqosWredYellowHighLimit, 
				hwhqosWredYellowDiscardPercent, hwhqosWredRedLowLimit, hwhqosWredRedHighLimit, hwhqosWredRedDiscardPercent, hwhqosWredRowStatus
				 }
			STATUS current
			DESCRIPTION 
				"Description."
			::= { hwhqosGroups 4 }
		
-- 1.3.6.1.4.1.2011.5.25.132.4.2.5
		hwhqosIfQueueStatGroup OBJECT-GROUP
			OBJECTS { hwhqosIfQueueStatForwardPackets, hwhqosIfQueueStatForwardBytes, hwhqosIfQueueStatDropBytes, hwhqosIfQueueStatDropPackets }
			STATUS current
			DESCRIPTION 
				"Description."
			::= { hwhqosGroups 5 }
		
-- 1.3.6.1.4.1.2011.5.25.132.4.2.6
		hwhqosUserQueueStatGroup OBJECT-GROUP
			OBJECTS { hwhqosUserQueueStatForwardPackets, hwhqosUserQueueStatForwardBytes, hwhqosUserQueueStatDropPackets, hwhqosUserQueueStatDropBytes, hwhqosUserQueueStatReset, 
				hwhqosUserQueueStatLastResetTime, hwhqosUserQueueStatPerDropPackets }
			STATUS current
			DESCRIPTION 
				"Description."
			::= { hwhqosGroups 6 }
		
-- 1.3.6.1.4.1.2011.5.25.132.4.2.7
		hwhqosUserGroupQueueStatGroup OBJECT-GROUP
			OBJECTS { hwhqosUserGroupQueueStatReset, hwhqosUserGroupQueueDropBytes, hwhqosUserGroupQueueDropPackets, hwhqosUserGroupQueueForwardBytes, hwhqosUserGroupQueueForwardPackets, 
				hwhqosUserGroupQueueStatLastResetTime }
			STATUS current
			DESCRIPTION 
				"Description."
			::= { hwhqosGroups 7 }
		
-- 1.3.6.1.4.1.2011.5.25.132.4.2.8
		hwhqosObjectsGroup OBJECT-GROUP
			OBJECTS { hwhqosUserFrameId, hwhqosUserSlotId, hwhqosUserPortId, hwhqosUserQueueApplyFailDirection, hwhqosUserQueueApplyFailPool}
			STATUS current
			DESCRIPTION 
				"Description."
			::= { hwhqosGroups 8 }
		
-- 1.3.6.1.4.1.2011.5.25.132.4.2.9
		hwhqosUserQueueStatTrapGroup NOTIFICATION-GROUP
			NOTIFICATIONS { hwhqosUserQueueStatDiscardAlarmTrap, hwhqosUserQueueApplyPirFailAlarmTrap, hwhqosUserQueueApplyPirSucessAlarmTrap, hwhqosUserQueueApplyPirFromPoolFailAlarmTrap, hwhqosUserQueueApplyPirFromPoolSucessAlarmTrap  }
			STATUS current
			DESCRIPTION 
				"The notification group defined for discard packets of a user`s queue."
			::= { hwhqosGroups 9 }
		
-- 1.3.6.1.4.1.2011.5.25.132.4.2.10
		hwhqosVpnQoSTunnelStatGroup OBJECT-GROUP
			OBJECTS { hwVPNHQoSTunnelIfIndex, hwVPNHQoSVPNType, hwVPNHQoSVPNValue, hwVPNHQoSPassBytes, hwVPNHQoSPassPackets, 
				hwVPNHQoSDropPackets, hwVPNHQoSDropBytes }
			STATUS current
			DESCRIPTION 
				"Description."
			::= { hwhqosGroups 10 }
		
-- 1.3.6.1.4.1.2011.5.25.132.4.2.11
		hwhqosTunnelStatGroup OBJECT-GROUP
			OBJECTS { hwhqosTunnelIfIndex, hwhqosTunnelCosType, hwhqosTunnelVPNType, hwhqosTunnelVPNName, hwhqosTunnelPassBytes, 
				hwhqosTunnelPassPackets, hwhqosTunnelDropBytes, hwhqosTunnelDropPackets, hwhqosTunnelPassedByteRate, hwhqosTunnelPassPacketRate
				 }
			STATUS current
			DESCRIPTION 
				"Description."
			::= { hwhqosGroups 11 }
		
-- 1.3.6.1.4.1.2011.5.25.132.4.2.12
		hwhqosProfileGroup OBJECT-GROUP
			OBJECTS { hwhqosProfileName, hwhqosProfileRowStatus }
			STATUS current
			DESCRIPTION 
				"Description."
			::= { hwhqosGroups 12 }
		
-- 1.3.6.1.4.1.2011.5.25.132.4.2.13
		hwhqosProfileSuppressionGroup OBJECT-GROUP
			OBJECTS { hwhqosSuppressionDirection, hwhqosSuppressionType, hwhqosSuppressionCirValue, hwhqosSuppressionCbsValue, hwhqosSuppressionRowStatus
				 }
			STATUS current
			DESCRIPTION 
				"Description."
			::= { hwhqosGroups 13 }
		
-- 1.3.6.1.4.1.2011.5.25.132.4.2.14
		hwhqosProfileCarGroup OBJECT-GROUP
			OBJECTS { hwhqosProfileCarDirection, hwhqosProfileCarCirValue, hwhqosProfileCarPirValue, hwhqosProfileCarCbsValue, hwhqosProfileCarPbsValue, 
				hwhqosProfileCarGreenAction, hwhqosProfileCarYellowAction, hwhqosProfileCarRedAction, hwhqosProfileCarRowStatus }
			STATUS current
			DESCRIPTION 
				"Description."
			::= { hwhqosGroups 14 }
		
-- 1.3.6.1.4.1.2011.5.25.132.4.2.15
		hwhqosProfileUserQueueGroup OBJECT-GROUP
			OBJECTS { hwhqosProfileUserQueueDirection, hwhqosProfileUserQueueCirValue, hwhqosProfileUserQueuePirValue, hwhqosProfileUserQueueFlowQueueName, hwhqosProfileUserQueueMappingName, 
				hwhqosProfileUserQueueGroupName, hwhqosProfileUserQueueServiceTemplateName, hwhqosProfileUserQueueRowStatus }
			STATUS current
			DESCRIPTION 
				"Description."
			::= { hwhqosGroups 15 }
		
-- 1.3.6.1.4.1.2011.5.25.132.4.2.16
		hwhqosProfileUserApplyGroup OBJECT-GROUP
			OBJECTS { hwhqosProfileInterfaceIndex, hwhqosProfileApplyDirection, hwhqosProfileApplyPevid, hwhqosProfileApplyCevid, hwhqosProfileApplyName, 
				hwhqosProfileApplyIdentifier, hwhqosGroupName, hwhqosProfileApplyRowStatus }
			STATUS current
			DESCRIPTION 
				"Description."
			::= { hwhqosGroups 16 }
		
-- 1.3.6.1.4.1.2011.5.25.132.4.2.17
		hwhqosFlowMappingGroup OBJECT-GROUP
			OBJECTS { hwhqosFlowMappingName, hwhqosFlowMappingRowStatus }
			STATUS current
			DESCRIPTION 
				"Description."
			::= { hwhqosGroups 17 }
		
-- 1.3.6.1.4.1.2011.5.25.132.4.2.18
		hwhqosFlowMappingCfgGroup OBJECT-GROUP
			OBJECTS { hwhqosFolwMappingCfgQueueCosValue, hwhqosFlowMappingCfgPortQueueCosValue, hwhqosFlowMappingCfgRowStatus }
			STATUS current
			DESCRIPTION 
				"Description."
			::= { hwhqosGroups 18 }
		
-- 1.3.6.1.4.1.2011.5.25.132.4.2.19
		hwhqosFlowQueueGroup OBJECT-GROUP
			OBJECTS { hwhqosFlowQueueName, hwhqosFlowQueueRowStatus }
			STATUS current
			DESCRIPTION 
				"Description."
			::= { hwhqosGroups 19 }
		
-- 1.3.6.1.4.1.2011.5.25.132.4.2.20
		hwhqosFlowQueueCfgGroup OBJECT-GROUP
			OBJECTS { hwhqosFlowQueueCfgCosValue, hwhqosFlowQueueCfgType, hwhqosFlowQueueCfgWeightValue, hwhqosFlowQueueCfgShapingValue, hwhqosFlowQueueCfgShapingPercentageValue, 
				hwhqosFlowQueueCfgPbsValue, hwhqosFlowQueueCfgWredName, hwhqosFlowQueueCfgRowStatus }
			STATUS current
			DESCRIPTION 
				"Description."
			::= { hwhqosGroups 20 }
		
-- 1.3.6.1.4.1.2011.5.25.132.4.2.21
		hwhqosFlowWredGroup OBJECT-GROUP
			OBJECTS { hwhqosFlowWredName, hwhqosFlowWredRowStatus }
			STATUS current
			DESCRIPTION 
				"Description."
			::= { hwhqosGroups 21 }
		
-- 1.3.6.1.4.1.2011.5.25.132.4.2.22
		hwhqosFlowWredColorGroup OBJECT-GROUP
			OBJECTS { hwhqosFlowWredColor, hwhqosFlowWredColorLowlimitPercentage, hwhqosFlowWredColorHighlimitPercentage, hwhqosFlowWredColorDiscardPercentage, hwhqosFlowWredColorRowStatus
				 }
			STATUS current
			DESCRIPTION 
				"Description."
			::= { hwhqosGroups 22 }
		
-- 1.3.6.1.4.1.2011.5.25.132.4.2.23
		hwhqosUserGroupQueueGroup OBJECT-GROUP
			OBJECTS { hwhqosUserGroupQueueName, hwhqosUserGroupQueueSlotNumber, hwhqosUserGroupQueueRowStatus }
			STATUS current
			DESCRIPTION 
				"Description."
			::= { hwhqosGroups 23 }
		
-- 1.3.6.1.4.1.2011.5.25.132.4.2.24
		hwhqosUserGroupQueueShapingGroup OBJECT-GROUP
			OBJECTS { hwhqosUserGroupQueueShapingDirection, hwhqosUserGroupQueueShapingValue, hwhqosUserGroupQueuePbsValue, hwhqosUserGroupQueueShapingRowStatus }
			STATUS current
			DESCRIPTION 
				"Description."
			::= { hwhqosGroups 24 }
		
-- 1.3.6.1.4.1.2011.5.25.132.4.2.25
		hwhqosUserQueueGroup OBJECT-GROUP
			OBJECTS { hwhqosUserQueueInterfaceIndex, hwhqosUserQueueDirection, hwhqosUserQueueCirValue, hwhqosUserQueuePirValue, hwhqosUserQueueFlowQueueName, 
				hwhqosUserQueueFlowMappingName, hwhqosUserQueueGroupName, hwhqosUserQueueServiceTemplateName, hwhqosUserQueueRowStatus }
			STATUS current
			DESCRIPTION 
				"Description."
			::= { hwhqosGroups 25 }
		
-- 1.3.6.1.4.1.2011.5.25.132.4.2.26
		hwhqosBehaviorUserQueueGroup OBJECT-GROUP
			OBJECTS { hwhqosBehaviorName, hwhqosBehaviorCirValue, hwhqosBehaviorPirValue, hwhqosBehaviorFlowQueueName, hwhqosBehaviorFlowMappingName, 
				hwhqosBehaviorGroupName, hwhqosBehaviorServiceTemplateName, hwhqosBehaviorUserQueueRowStatus }
			STATUS current
			DESCRIPTION 
				"Description."
			::= { hwhqosGroups 26 }
		
-- 1.3.6.1.4.1.2011.5.25.132.4.2.27
		hwhqosBandwidthGroup OBJECT-GROUP
			OBJECTS { hwhqosBandwidthInterfaceIndex, hwhqosBandwidthValue, hwhqosBandwidthRowStatus }
			STATUS current
			DESCRIPTION 
				"Description."
			::= { hwhqosGroups 27 }
		
-- 1.3.6.1.4.1.2011.5.25.132.4.2.28
		hwhqosServiceTemplateGroup OBJECT-GROUP
			OBJECTS { hwhqosServiceTemplateName, hwhqosSlotNumber, hwhqosServiceTemplateRowStatus }
			STATUS current
			DESCRIPTION 
				"Description."
			::= { hwhqosGroups 28 }
		
-- 1.3.6.1.4.1.2011.5.25.132.4.2.29
		hwhqosNetworkHeaderLengthGroup OBJECT-GROUP
			OBJECTS { hwhqosNetworkHeaderLengthDirection, hwhqosNetWorkHeaderLengthValue, hwhqosNetWorkHeaderLengthRowStatus }
			STATUS current
			DESCRIPTION 
				"Description."
			::= { hwhqosGroups 29 }
		
-- 1.3.6.1.4.1.2011.5.25.132.4.2.30
		hwhqosServiceTemplateApplyGroup OBJECT-GROUP
			OBJECTS { hwhqosServiceTemplateApplyInterfaceIndex, hwhqosApplyServiceTemplateName, hwhqosServiceTemplateApplyRowStatus }
			STATUS current
			DESCRIPTION 
				"Description."
			::= { hwhqosGroups 30 }
		
-- 1.3.6.1.4.1.2011.5.25.132.4.2.31
		hwhqosProfileUserQueueStatisticsGroup OBJECT-GROUP
			OBJECTS { hwhqosProfileUserQueueStatisticsInterfaceIndex, hwhqosProfileUserQueueStatisticsDirection, hwhqosProfileUserQueueStatisticsPevid, hwhqosProfileUserQueueStatisticsCevid, hwhqosProfileUserQueueStatisticsSlotNumber, 
				hwhqosProfileUserQueueStatisticsQueueIndex, hwhqosProfileUserQueueStatisticsReset, hwhqosProfileUserQueueStatisticsPassPackets, hwhqosProfileUserQueueStatisticsPassBytes, hwhqosProfileUserQueueStatisticsDropPackets, 
				hwhqosProfileUserQueueStatisticsDropBytes, hwhqosProfileUserQueueStatisticsPassPacketsRate, hwhqosProfileUserQueueStatisticsPassBytesRate, hwhqosProfileUserQueueStatisticsDropPacketsRate, hwhqosProfileUserQueueStatisticsDropBytesRate, 
				hwhqosProfileUserQueueStatisticsTrafficTowardsThisInterface, hwhqosProfileUserQueueStatisticsConfiguredCir, hwhqosProfileUserQueueStatisticsConfiguredPir }
			STATUS current
			DESCRIPTION 
				"Description."
			::= { hwhqosGroups 31 }
		
-- 1.3.6.1.4.1.2011.5.25.132.4.2.32
		hwhqosProfileCarStatisticsGroup OBJECT-GROUP
			OBJECTS { hwhqosProfileCarStatisticsInterfaceIndex, hwhqosProfileCarStatisticsDirection, hwhqosProfileCarStatisticsPevid, hwhqosProfileCarStatisticsCevid, hwhqosProfileCarStatisticsType, 
				hwhqosProfileCarStatisticsSlotNumber, hwhqosProfileCarStatisticsReset, hwhqosProfileCarStatisticsPassPackets, hwhqosProfileCarStatisticsPassBytes, hwhqosProfileCarStatisticsDropPackets, 
				hwhqosProfileCarStatisticsDropBytes, hwhqosProfileCarStatisticsPassPacketsRate, hwhqosProfileCarStatisticsPassBytesRate, hwhqosProfileCarStatisticsDropPacketsRate, hwhqosProfileCarStatisticsDropBytesRate
				 }
			STATUS current
			DESCRIPTION 
				"Description."
			::= { hwhqosGroups 32 }
		
-- 1.3.6.1.4.1.2011.5.25.132.4.2.33
		hwhqosUserQueueStatisticsGroup OBJECT-GROUP
			OBJECTS { hwhqosUserQueueStatisticsInterfaceIndex, hwhqosUserQueueStatisticsDirection, hwhqosUserQueueStatisticsSlotNumber, hwhqosUserQueueStatisticsQueueIndex, hwhqosUserQueueStatisticsReset, 
				hwhqosUserQueueStatisticsPassPackets, hwhqosUserQueueStatisticsPassBytes, hwhqosUserQueueStatisticsDropPackets, hwhqosUserQueueStatisticsDropBytes, hwhqosUserQueueStatisticsPassPacketsRate, 
				hwhqosUserQueueStatisticsPassBytesRate, hwhqosUserQueueStatisticsDropPacketsRate, hwhqosUserQueueStatisticsDropBytesRate }
			STATUS current
			DESCRIPTION 
				"Description."
			::= { hwhqosGroups 33 }
		
-- 1.3.6.1.4.1.2011.5.25.132.4.2.34
		hwhqosUserQueueClassifierStatisticsGroup OBJECT-GROUP
			OBJECTS { hwhqosUserQueueClassifierStatisticsInterfaceIndex, hwhqosUserQueueClassifierStatisticsDirection, hwhqosUserQueueClassifierStatisticsClassifierName, hwhqosUserQueueClassifierStatisticsSlotNumber, hwhqosUserQueueClassifierStatisticsQueueIndex, 
				hwhqosUserQueueClassifierStatisticsReset, hwhqosUserQueueClassifierStatisticsPassPackets, hwhqosUserQueueClassifierStatisticsPassBytes, hwhqosUserQueueClassifierStatisticsDropPackets, hwhqosUserQueueClassifierStatisticsDropBytes, 
				hwhqosUserQueueClassifierStatisticsPassPacketsRate, hwhqosUserQueueClassifierStatisticsPassBytesRate, hwhqosUserQueueClassifierStatisticsDropPacketsRate, hwhqosUserQueueClassifierStatisticsDropBytesRate }
			STATUS current
			DESCRIPTION 
				"Description."
			::= { hwhqosGroups 34 }
		
-- 1.3.6.1.4.1.2011.5.25.132.4.2.35
		hwhqosUserGroupQueueStatisticsGroup OBJECT-GROUP
			OBJECTS { hwhqosUserGroupQueueStatisticsGroupName, hwhqosUserGroupQueueStatisticsDirection, hwhqosUserGroupQueueStatisticsSlotNumber, hwhqosUserGroupQueueStatisticsQueueIndex, hwhqosUserGroupQueueStatisticsReset, 
				hwhqosUserGroupQueueStatisticsPassPackets, hwhqosUserGroupQueueStatisticsPassBytes, hwhqosUserGroupQueueStatisticsDropPackets, hwhqosUserGroupQueueStatisticsDropBytes, hwhqosUserGroupQueueStatisticsPassPacketsRate, 
				hwhqosUserGroupQueueStatisticsPassBytesRate, hwhqosUserGroupQueueStatisticsDropPacketsRate, hwhqosUserGroupQueueStatisticsDropBytesRate }
			STATUS current
			DESCRIPTION 
				"Description."
			::= { hwhqosGroups 35 }
		
-- 1.3.6.1.4.1.2011.5.25.132.4.2.36
		hwhqosFlowQueueShaperGroup OBJECT-GROUP
			OBJECTS { hwhqosFlowQueueShaperBE, hwhqosFlowQueueShaperAF1, hwhqosFlowQueueShaperAF2, hwhqosFlowQueueShaperAF3, hwhqosFlowQueueShaperAF4, 
				hwhqosFlowQueueShaperEF, hwhqosFlowQueueShaperCS6, hwhqosFlowQueueShaperCS7, hwhqosFlowQueueShaperValue, hwhqosFlowQueueShaperRowStatus
				 }
			STATUS current
			DESCRIPTION 
				"Description."
			::= { hwhqosGroups 36 }
		
-- 1.3.6.1.4.1.2011.5.25.132.4.2.37
		hwhqosWredQueueDepthGroup OBJECT-GROUP
			OBJECTS { hwhqosWredQueueDepthType, hwhqosWredQueueDepthWredName, hwhqosWredQueueDepthValue, hwhqosWredQueueDepthRowStatus }
			STATUS current
			DESCRIPTION 
				"Description."
			::= { hwhqosGroups 37 }
		
-- 1.3.6.1.4.1.2011.5.25.132.4.2.38
		hwhqosBandwidthCheck OBJECT-GROUP
			OBJECTS { hwhqosBandwidthCheckInterfaceIndex, hwhqosBandwidthCheckValue, hwhqosBandwidthCheckRowStatus }
			STATUS current
			DESCRIPTION 
				"Description."
			::= { hwhqosGroups 38 }
		
-- 1.3.6.1.4.1.2011.5.25.132.4.2.39
		hwhqosServiceIdentifyPolicyGroup OBJECT-GROUP
			OBJECTS { hwhqosServiceIdentifyPolicyName, hwhqosServiceIdentifyPolicyRowStatus }
			STATUS current
			DESCRIPTION 
				"Description."
			::= { hwhqosGroups 39 }
		
-- 1.3.6.1.4.1.2011.5.25.132.4.2.40
		hwhqosServiceIdentifyPolicyApplyGroup OBJECT-GROUP
			OBJECTS { hwhqosServiceIdentifyPolicyApplyInterfaceIndex, hwhqosServiceIdentifyPolicyApplyName, hwhqosServiceIdentifyPolicyApplyRowStatus }
			STATUS current
			DESCRIPTION 
				"Description."
			::= { hwhqosGroups 40 }
		
-- 1.3.6.1.4.1.2011.5.25.132.4.2.41
		hwhqosServiceIdentifyPolicyTypeGroup OBJECT-GROUP
			OBJECTS { hwhqosServiceIdentifyPolicyTypeValue, hwhqosServiceIdentifyPolicyTypeRowStatus }
			STATUS current
			DESCRIPTION 
				"Description."
			::= { hwhqosGroups 41 }
		
-- 1.3.6.1.4.1.2011.5.25.132.4.2.42
		hwhqosServiceIdentifyPolicyVlanGroup OBJECT-GROUP
			OBJECTS { hwhqosServiceIdentifyPolicyVlanID, hwhqosServiceIdentifyPolicyVlanDomainName, hwhqosServiceIdentifyPolicyVlanRowStatus }
			STATUS current
			DESCRIPTION 
				"Description."
			::= { hwhqosGroups 42 }
		
-- 1.3.6.1.4.1.2011.5.25.132.4.2.43
		hwhqosServiceIdentifyPolicy8021pGroup OBJECT-GROUP
			OBJECTS { hwhqosServiceIdentifyPolicy8021pCosID, hwhqosServiceIdentifyPolicy8021pDomainName, hwhqosServiceIdentifyPolicy8021pRowStatus }
			STATUS current
			DESCRIPTION 
				"Description."
			::= { hwhqosGroups 43 }
		
-- 1.3.6.1.4.1.2011.5.25.132.4.2.44
		hwhqosServiceIdentifyPolicyDscpGroup OBJECT-GROUP
			OBJECTS { hwhqosServiceIdentifyPolicyDscpID, hwhqosServiceIdentifyPolicyDscpDomainName, hwhqosServiceIdentifyPolicyDscpRowStatus }
			STATUS current
			DESCRIPTION 
				"Description."
			::= { hwhqosGroups 44 }
		
-- 1.3.6.1.4.1.2011.5.25.132.4.2.45
		hwhqosServiceIdentifyPolicyOption60Group OBJECT-GROUP
			OBJECTS { hwhqosServiceIdentifyPolicyOption60, hwhqosServiceIdentifyPolicyOption60RowStatus }
			STATUS current
			DESCRIPTION 
				"Description."
			::= { hwhqosGroups 45 }
		
-- 1.3.6.1.4.1.2011.5.25.132.4.2.46
		hwhqosDomainRateLimitModeGroup OBJECT-GROUP
			OBJECTS { hwhqosDomainRateLimitModeDomainName, hwhqosDomainRateLimitModeRateLimitMode, hwhqosDomainRateLimitModeRowStatus }
			STATUS current
			DESCRIPTION 
				"Description."
			::= { hwhqosGroups 46 }
		
-- 1.3.6.1.4.1.2011.5.25.132.4.2.47
		hwhqosDomainSessionGroupExcludeGroup OBJECT-GROUP
			OBJECTS { hwhqosDomainSessionGroupExcludeDomainName, hwhqosDomainSessionGroupExcludeRowStatus, hwhqosDomainSessionGroupExcludeMode }
			STATUS current
			DESCRIPTION 
				"Description."
			::= { hwhqosGroups 47 }
		
-- 1.3.6.1.4.1.2011.5.25.132.4.2.48
		hwhqosDomainUserMaxSessionGroup OBJECT-GROUP
			OBJECTS { hwhqosDomainUserMaxSessionDomainName, hwhqosDomainUserMaxSessionNum, hwhqosDomainUserMaxSessionRowStatus }
			STATUS current
			DESCRIPTION 
				"Description."
			::= { hwhqosGroups 48 }
		
-- 1.3.6.1.4.1.2011.5.25.132.4.2.49
		hwhqosUpdateUseridProfileGroup OBJECT-GROUP
			OBJECTS { hwhqosUpdateUseridProfileUserid, hwhqosUpdateUseridProfileDirection, hwhqosUpdateUseridProfileName, hwhqosUpdateUseridProfileRowStatus }
			STATUS current
			DESCRIPTION 
				"Description."
			::= { hwhqosGroups 49 }
		
-- 1.3.6.1.4.1.2011.5.25.132.4.2.50
		hwhqosDomainUserPriorityGroup OBJECT-GROUP
			OBJECTS { hwhqosDomainUserPriorityDomainName, hwhqosDomainUserPriorityDirection, hwhqosDomainUserPriorityRowStatus, hwhqosDomainUserPriorityValue }
			STATUS current
			DESCRIPTION 
				"Description."
			::= { hwhqosGroups 50 }
		
-- 1.3.6.1.4.1.2011.5.25.132.4.2.52
		hwhqosUseridStatGroup OBJECT-GROUP
			OBJECTS { hwhqosUseridStatUserid, hwhqosUseridStatQueue, hwhqosUseridStatDirection }
			STATUS current
			DESCRIPTION 
				"Description."
			::= { hwhqosGroups 52 }
		
-- 1.3.6.1.4.1.2011.5.25.132.4.2.55
		hwhqosFatherUserGroupQueueApplyGroup OBJECT-GROUP
			OBJECTS { hwhqosFatherUserGroupQueueApplyInterfaceIndex, hwhqosFatherUserGroupQueueApplyDirection, hwhqosFatherUserGroupQueueApplyName, hwhqosFatherUserGroupQueueApplyRowStatus }
			STATUS current
			DESCRIPTION 
				"Description."
			::= { hwhqosGroups 55 }
		
-- 1.3.6.1.4.1.2011.5.25.132.4.2.56
		hwhqosUserGroupQueueApplyGroup OBJECT-GROUP
			OBJECTS { hwhqosUserGroupQueueApplyInterfaceIndex, hwhqosUserGroupQueueApplyDirection, hwhqosUserGroupQueueApplyPeVid, hwhqosUserGroupQueueApplyCeVid, hwhqosUserGroupQueueApplyName, 
				hwhqosUserGroupQueueApplyEachvlan, hwhqosUserGroupQueueApplyRowStatus }
			STATUS current
			DESCRIPTION 
				" "
			::= { hwhqosGroups 56 }
		
-- 1.3.6.1.4.1.2011.5.25.132.4.2.57
		hwhqosProfileApplyDomainGroup OBJECT-GROUP
			OBJECTS { hwhqosProfileApplyDomainName, hwhqosProfileApplyDomainDirection, hwhqosProfileApplyDomainProfileName, hwhqosProfileApplyDomainRowStatus }
			STATUS current
			DESCRIPTION 
				" "
			::= { hwhqosGroups 57 }
		
-- 1.3.6.1.4.1.2011.5.25.132.4.2.58
		hwhqosProfileApplyUserVlanGroup OBJECT-GROUP
			OBJECTS { hwhqosProfileApplyUserVlanInterfaceIndex, hwhqosProfileApplyUserVlanDirection, hwhqosProfileApplyUserVlanPeVid, hwhqosProfileApplyUserVlanCeVid, hwhqosProfileApplyUserVlanProfileName, 
				hwhqosProfileApplyUserVlanEach, hwhqosProfileApplyUserVlanRowStatus }
			STATUS current
			DESCRIPTION 
				" "
			::= { hwhqosGroups 58 }
		
-- 1.3.6.1.4.1.2011.5.25.132.4.2.59
		hwhqosLinkAdjRemoteEnableGroup OBJECT-GROUP
			OBJECTS { hwhqosLinkAdjRemoteEnableType, hwhqosLinkAdjRemoteEnable, hwhqosLinkAdjRemoteEnableSlot, hwhqosLinkAdjRemoteEnableRowStatus }
			STATUS current
			DESCRIPTION 
				" "
			::= { hwhqosGroups 59 }
		
-- 1.3.6.1.4.1.2011.5.25.132.4.2.60
		hwhqosLinkAdjShapingModeGroup OBJECT-GROUP
			OBJECTS { hwhqosLinkAdjShapingModeType, hwhqosLinkAdjShapingMode, hwhqosLinkAdjShapingModeRowStatus }
			STATUS current
			DESCRIPTION 
				" "
			::= { hwhqosGroups 60 }
		
-- 1.3.6.1.4.1.2011.5.25.132.4.2.61
		hwhqosLinkAdjRemoteGroup OBJECT-GROUP
			OBJECTS { hwhqosLinkAdjRemoteType, hwhqosLinkAdjRemoteValue, hwhqosLinkAdjRemoteRowStatus }
			STATUS current
			DESCRIPTION 
				" "
			::= { hwhqosGroups 61 }
		
-- 1.3.6.1.4.1.2011.5.25.132.4.2.62
		hwhqosLinkAdjLocalTableGroup OBJECT-GROUP
			OBJECTS { hwhqosLinkAdjLocalSlotNumber, hwhqosLinkAdjLocalValue, hwhqosLinkAdjLocalRowStatus }
			STATUS current
			DESCRIPTION 
				" "
			::= { hwhqosGroups 62 }
		
-- 1.3.6.1.4.1.2011.5.25.132.4.2.63
		hwhqosLinkAdjExcludeGroup OBJECT-GROUP
			OBJECTS { hwhqosLinkAdjExcludeSlotNumber, hwhqosLinkAdjExcludeEnable, hwhqosLinkAdjExcludeRowStatus }
			STATUS current
			DESCRIPTION 
				" "
			::= { hwhqosGroups 63 }
		
-- 1.3.6.1.4.1.2011.5.25.132.4.2.64
		hwhqosProfileInfoGroup OBJECT-GROUP
			OBJECTS { hwhqosProfileInfoName, hwhqosProfileInfoDescription, hwhqosProfileInfoRowStatus }
			STATUS current
			DESCRIPTION 
				"Description."
			::= { hwhqosGroups 64 }
		
-- 1.3.6.1.4.1.2011.5.25.132.4.2.65
		hwhqosUserGroupQueueTemplateGroup OBJECT-GROUP
			OBJECTS { hwhqosUserGroupQueueTemplateName, hwhqosUserGroupQueueTemplateModeTemplate, hwhqosUserGroupQueueTemplateRowStatus }
			STATUS current
			DESCRIPTION 
				"Description."
			::= { hwhqosGroups 65 }
		
-- 1.3.6.1.4.1.2011.5.25.132.4.2.66
		hwhqosProfileWeightGroup OBJECT-GROUP
			OBJECTS { hwhqosProfileWeightDirection, hwhqosProfileWeightValue, hwhqosProfileWeightRowStatus }
			STATUS current
			DESCRIPTION 
				"Description."
			::= { hwhqosGroups 66 }
		
--           /*Begin Added by lishutian 00174417 for NP4_HQOS_RELEASE2 user-queue-apply-alarm 2013-4-20*/ 
-- 1.3.6.1.4.1.2011.5.25.132.4.2.67
		hwhqosUserQueueApplyAlarmGroup NOTIFICATION-GROUP
			NOTIFICATIONS { hwhqosUserQueueApplyAlarmTrap }
			STATUS current
			DESCRIPTION 
				"Description."
			::= { hwhqosGroups 67 }
		
--           /*End Added by lishutian 00174417 for NP4_HQOS_RELEASE2 user-queue-apply-alarm 2013-4-20*/    
-- beg:mod by j00126783 for port-queue-discard-trap 2012-07-31            
-- 1.3.6.1.4.1.2011.5.25.132.4.2.68
		hwhqosPortQueueStatDiscardAlarmTrapGroup NOTIFICATION-GROUP
			NOTIFICATIONS { hwhqosPortQueueStatDiscardAlarmTrap }
			STATUS current
			DESCRIPTION 
				"Description."
			::= { hwhqosGroups 68 }
		
-- 1.3.6.1.4.1.2011.5.25.132.4.2.69
		hwhqosPortQueueStatDiscarAlarmCancelGroup NOTIFICATION-GROUP
			NOTIFICATIONS { hwhqosPortQueueStatDiscardAlarmCancelTrap }
			STATUS current
			DESCRIPTION 
				"Description."
			::= { hwhqosGroups 69 }
--end:mod by j00126783 for port-queue-discard-trap 2012-07-31        
		
-- 1.3.6.1.4.1.2011.5.25.132.4.2.70
		hwhqosUserGroupQueueInterfaceStatisticsGroup OBJECT-GROUP
			OBJECTS { hwhqosUserGroupQueueInterfaceStatisticsIfIndex, hwhqosUserGroupQueueInterfaceStatisticsDirection, hwhqosUserGroupQueueInterfaceStatisticsPevid, hwhqosUserGroupQueueInterfaceStatisticsCevid, hwhqosUserGroupQueueInterfaceStatisticsVlanid, hwhqosUserGroupQueueInterfaceStatisticsQueueIndex, hwhqosUserGroupQueueInterfaceStatisticsReset,
				hwhqosUserGroupQueueInterfaceStatisticsPassPackets, hwhqosUserGroupQueueInterfaceStatisticsPassBytes, hwhqosUserGroupQueueInterfaceStatisticsDropPackets, hwhqosUserGroupQueueInterfaceStatisticsDropBytes, hwhqosUserGroupQueueInterfaceStatisticsPassPacketsRate,  
				hwhqosUserGroupQueueInterfaceStatisticsPassBytesRate, hwhqosUserGroupQueueInterfaceStatisticsDropPacketsRate, hwhqosUserGroupQueueInterfaceStatisticsDropBytesRate }
			STATUS current
			DESCRIPTION 
				"Description."
			::= { hwhqosGroups 70 }
	
	END

--
-- HUAWEI-HQOS-MIB.my
--
