-- ==================================================================
-- Copyright (C) 2004 by  HUAWEI-3COM TECHNOLOGIES. All rights reserved.
--
-- Description:  Lan Switch Multicast MIB
-- Reference:
-- Version: V1.0
-- History:
--   V1.0 2004-12-20 Created by Wangxiaodong
--
-- ==================================================================
--
-- ==================================================================
--
-- Variables and types be imported
--
-- ==================================================================
H3C-MULTICAST-MIB DEFINITIONS ::= BEGIN
IMPORTS

    MODULE-IDENTITY,OBJECT-TYPE
        FROM SNMPv2-SMI

    TEXTUAL-CONVENTION
        FROM SNMPv2-TC

    h3cCommon
        FROM HUAWEI-3COM-OID-MIB;

    h3cMulticast MODULE-IDENTITY
        LAST-UPDATED "200504290000Z"
        ORGANIZATION "Huawei 3Com Technologies Co., Ltd."
        CONTACT-INFO
            "Platform Team Huawei 3Com Technologies Co., Ltd.
            Hai-Dian District Beijing P.R. China
            http://www.huawei-3com.com
            Zip:100085"
        DESCRIPTION
            "The multicast global configuration MIB"
        REVISION "200504290000Z"
        DESCRIPTION
            "The initial version of this MIB file."
        ::= { h3cCommon  50 }

    EnabledStatus ::= TEXTUAL-CONVENTION
        STATUS      current
        DESCRIPTION
            "A simple status value for the object."
        SYNTAX      INTEGER { enabled(1), disabled(2) }

-- ==================================================================
--
-- ======================= definition begin =========================
--
-- ==================================================================

    h3cMulticastObject OBJECT IDENTIFIER ::= {  h3cMulticast 1  }

    h3cMulticastEnable OBJECT-TYPE
        SYNTAX  EnabledStatus
        MAX-ACCESS read-write
        STATUS  current
        DESCRIPTION
            "To enable or disable global multicast."
        DEFVAL     { disabled }
        ::= { h3cMulticastObject  1 }


END
