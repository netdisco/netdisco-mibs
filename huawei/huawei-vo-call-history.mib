-- ==========================================================================
-- Copyright (C) 2002 by  HUAWEI TECHNOLOGIES. All rights reserved.
--
-- Description: The purpose of this MIB file is to provide the define of
--              voice call histroy MIB of HUAWEI quidway serial router,
--              which are used to save the past voice call history information.
-- Reference:
-- Version: V2.0
-- History:
-- V1.0 Initial version
-- V2.0 2004-10-20 Updated by gaolong
--      Re-write whole MIB with SNMPv2-SMI format.
--      Modify module name from 'HUAWEI-CALL-HISTORY-MIB' to 'HUAWEI-VO-CALL-HISTORY-MIB'
-- ==========================================================================
HUAWEI-VO-CALL-HISTORY-MIB DEFINITIONS ::= BEGIN
 
	IMPORTS
		OBJECT-TYPE, MODULE-IDENTITY, TimeTicks, IpAddress
			FROM SNMPv2-SMI
		TimeStamp,DateAndTime
			FROM SNMPv2-TC
		voice
			FROM HUAWEI-3COM-OID-MIB;	
	
		
		hwVoiceCallHistoryMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 7 }

		
		hwVoCallHistoryObjects OBJECT IDENTIFIER ::= { hwVoiceCallHistoryMIB 1 }

		
--  Voice Call History Record Table Max Length
		hwVoCallHistoryMaxLen OBJECT-TYPE
			SYNTAX INTEGER (0..500)
			MAX-ACCESS read-write
			STATUS current
			DESCRIPTION
				"The maximum number of entries that the hwVoCallHistoryGenericTable,
				hwVoCallHistoryVoIPTable and hwVoCallHistoryPSTNTable may contain.  
				The value 0 means that any history entry will not be saved. if 
				these table are full, the oldest history entry will be deleted
				and the new one will be added."
			DEFVAL { 50 }
			::= { hwVoCallHistoryObjects 1 }

		
--  Voice Call History Generic Table
		hwVoCallHistoryGenericTable OBJECT-TYPE
			SYNTAX SEQUENCE OF HWVoCallHistoryGenericEntry
			MAX-ACCESS not-accessible
			STATUS current
			DESCRIPTION
				"The table contains the Voice Call History Generic information ."
			::= { hwVoCallHistoryObjects 2 }

		
		hwVoCallHistoryGenericEntry OBJECT-TYPE
			SYNTAX HWVoCallHistoryGenericEntry
			MAX-ACCESS not-accessible
			STATUS current
			DESCRIPTION
				"The information regarding a single Connection."
			INDEX { hwVoCallHistoryGenericIndex }
			::= { hwVoCallHistoryGenericTable 1 }

		
		HWVoCallHistoryGenericEntry ::=
			SEQUENCE { 
				hwVoCallHistoryGenericIndex
					INTEGER,
				hwVoCallHistoryGenericCallerNumber
					OCTET STRING,
				hwVoCallHistoryGenericCalledNumber
					OCTET STRING,
				hwVoCallHistoryGenericEncodeType
					INTEGER,
				hwVoCallHistoryGenericChannel
					INTEGER,
				hwVoCallHistoryGenericLocalAddress
					IpAddress,
				hwVoCallHistoryGenericPeerAddress
					IpAddress,
				hwVoCallHistoryGenericDisconnectText
					INTEGER,
				hwVoCallHistoryGenericCallDuration
					TimeTicks,
				hwVoCallHistoryGenericVoiceCallDuration
					TimeTicks,
				hwVoCallHistoryGenericFaxCallDuration
					TimeTicks,
				hwVoCallHistoryGenericImgPages
					INTEGER,
				hwVoCallHistoryGenericCallOrigin
					INTEGER
			 }

		hwVoCallHistoryGenericIndex OBJECT-TYPE
			SYNTAX INTEGER (1..2147483647)
			MAX-ACCESS read-only
			STATUS current
			DESCRIPTION
				"Index variable to access the hwVoCallHistoryGenericEntry objects
				of the hwVoCallHistoryGenericTable."
			::= { hwVoCallHistoryGenericEntry 1 }

		
		hwVoCallHistoryGenericCallerNumber OBJECT-TYPE
			SYNTAX OCTET STRING (SIZE (0..31))
			MAX-ACCESS read-only
			STATUS current
			DESCRIPTION
				"This object expresses the calling number of this call."
			::= { hwVoCallHistoryGenericEntry 2 }

		
		hwVoCallHistoryGenericCalledNumber OBJECT-TYPE
			SYNTAX OCTET STRING (SIZE (0..31))
			MAX-ACCESS read-only
			STATUS current
			DESCRIPTION
				"This object expresses the called number of this call."
			::= { hwVoCallHistoryGenericEntry 3 }

		
		hwVoCallHistoryGenericEncodeType OBJECT-TYPE
			SYNTAX INTEGER
				{
				g711a(1),
				g711u(2),
				g723(3),
				g729(4),
				g729a(5),
				unknown(0)
				}
			MAX-ACCESS read-only
			STATUS current
			DESCRIPTION
				"This object expresses the encode type which is used by this call."
			::= { hwVoCallHistoryGenericEntry 4 }

		
		hwVoCallHistoryGenericChannel OBJECT-TYPE
			SYNTAX INTEGER
			MAX-ACCESS read-only
			STATUS current
			DESCRIPTION
				"This object expresses the logic channel of this call."
			::= { hwVoCallHistoryGenericEntry 5 }

		
		hwVoCallHistoryGenericLocalAddress OBJECT-TYPE
			SYNTAX IpAddress
			MAX-ACCESS read-only
			STATUS current
			DESCRIPTION
				"This object expresses the gateway's local address of this call."
			::= { hwVoCallHistoryGenericEntry 6 }

		
		hwVoCallHistoryGenericPeerAddress OBJECT-TYPE
			SYNTAX IpAddress
			MAX-ACCESS read-only
			STATUS current
			DESCRIPTION
				"This object expresses peer address of this call."
			::= { hwVoCallHistoryGenericEntry 7 }

		
		hwVoCallHistoryGenericDisconnectText OBJECT-TYPE
			SYNTAX INTEGER
				{
				normalRelease(1),
				cardNumberNotExist(2),
				invalidPassword(3),
				thisAccountsIsUsing(4),
				noEnoughBalance(5),
				theAccountsIsExpired(6),
				creditLimit(7),
				userReject(8),
				serviceInvalid(9),
				calledLimit(10),
				maxRedialTimesLimit(11),
				invalidParameter(12),
				callerHookOn(13),
				calledHookOn(14),
				networkProblem(15),
				unknownReason(16)
				}
			MAX-ACCESS read-only
			STATUS current
			DESCRIPTION
				"This object expresses the reason for the call termination."
			::= { hwVoCallHistoryGenericEntry 8 }

		
		hwVoCallHistoryGenericCallDuration OBJECT-TYPE
			SYNTAX TimeTicks
			MAX-ACCESS read-only
			STATUS current
			DESCRIPTION
				"This object expresses the duration of this call include voice duration 
				and fax duration."
			::= { hwVoCallHistoryGenericEntry 9 }

		
		hwVoCallHistoryGenericVoiceCallDuration OBJECT-TYPE
			SYNTAX TimeTicks
			MAX-ACCESS read-only
			STATUS current
			DESCRIPTION
				"This object expresses the duration of voice in this call."
			::= { hwVoCallHistoryGenericEntry 10 }

		
		hwVoCallHistoryGenericFaxCallDuration OBJECT-TYPE
			SYNTAX TimeTicks
			MAX-ACCESS read-only
			STATUS current
			DESCRIPTION
				"This object expresses the duration of fax in this call."
			::= { hwVoCallHistoryGenericEntry 11 }

		
		hwVoCallHistoryGenericImgPages OBJECT-TYPE
			SYNTAX INTEGER
			MAX-ACCESS read-only
			STATUS current
			DESCRIPTION
				"This object expresses the number of fax pages received or transmitted ."
			::= { hwVoCallHistoryGenericEntry 12 }

		
		hwVoCallHistoryGenericCallOrigin OBJECT-TYPE
			SYNTAX INTEGER
				{
				caller(1),
				called(2)
				}
			MAX-ACCESS read-only
			STATUS current
			DESCRIPTION
				"This object expresses the gateway is caller or called in this call."
			::= { hwVoCallHistoryGenericEntry 13 }

		
--  Voice Call History VoIP Table
		hwVoCallHistoryVoIPTable OBJECT-TYPE
			SYNTAX SEQUENCE OF HWVoCallHistoryVoIPEntry
			MAX-ACCESS not-accessible
			STATUS current
			DESCRIPTION
				"The table contains the voice call history information related with voip."
			::= { hwVoCallHistoryObjects 3 }

		
		hwVoCallHistoryVoIPEntry OBJECT-TYPE
			SYNTAX HWVoCallHistoryVoIPEntry
			MAX-ACCESS not-accessible
			STATUS current
			DESCRIPTION
				"Statistic informations related with VoIP in the call recorded by this entry. "
			INDEX { hwVoCallHistoryVoIPIndex }
			::= { hwVoCallHistoryVoIPTable 1 }

		
		HWVoCallHistoryVoIPEntry ::=
			SEQUENCE { 
				hwVoCallHistoryVoIPIndex
					INTEGER,
				hwVoCallHistoryVoIPSetupTime
					DateAndTime,
				hwVoCallHistoryVoIPConnectTime
					DateAndTime,
				hwVoCallHistoryVoIPDisconectTime
					DateAndTime,
				hwVoCallHistoryVoIPSendPackets
					INTEGER,
				hwVoCallHistoryVoIPSendBytes
					INTEGER,
				hwVoCallHistoryVoIPReceivePackets
					INTEGER,
				hwVoCallHistoryVoIPReceiveBytes
					INTEGER
			 }

		hwVoCallHistoryVoIPIndex OBJECT-TYPE
			SYNTAX INTEGER (1..2147483647)
			MAX-ACCESS read-only
			STATUS current
			DESCRIPTION
				"Index variable to access the hwVoCallHistoryVoIPEntry objects
				of the hwVoCallHistoryVoIPTable."
			::= { hwVoCallHistoryVoIPEntry 1 }

		
		hwVoCallHistoryVoIPSetupTime OBJECT-TYPE
			SYNTAX DateAndTime
			MAX-ACCESS read-only
			STATUS current
			DESCRIPTION
				"VoIP setup time of this call."
			::= { hwVoCallHistoryVoIPEntry 2 }

		
		hwVoCallHistoryVoIPConnectTime OBJECT-TYPE
			SYNTAX DateAndTime
			MAX-ACCESS read-only
			STATUS current
			DESCRIPTION
				"VoIP connect time of this call."
			::= { hwVoCallHistoryVoIPEntry 3 }

		
		hwVoCallHistoryVoIPDisconectTime OBJECT-TYPE
			SYNTAX DateAndTime
			MAX-ACCESS read-only
			STATUS current
			DESCRIPTION
				" VoIP disconnect time of this call."
			::= { hwVoCallHistoryVoIPEntry 4 }

		
		hwVoCallHistoryVoIPSendPackets OBJECT-TYPE
			SYNTAX INTEGER
			MAX-ACCESS read-only
			STATUS current
			DESCRIPTION
				" The number of packets which VoIP sent in this call."
			::= { hwVoCallHistoryVoIPEntry 5 }

		
		hwVoCallHistoryVoIPSendBytes OBJECT-TYPE
			SYNTAX INTEGER
			MAX-ACCESS read-only
			STATUS current
			DESCRIPTION
				" The number of bytes which VoIP sent in this call."
			::= { hwVoCallHistoryVoIPEntry 6 }

		
		hwVoCallHistoryVoIPReceivePackets OBJECT-TYPE
			SYNTAX INTEGER
			MAX-ACCESS read-only
			STATUS current
			DESCRIPTION
				" The number of packets which VoIP received in this call."
			::= { hwVoCallHistoryVoIPEntry 7 }

		
		hwVoCallHistoryVoIPReceiveBytes OBJECT-TYPE
			SYNTAX INTEGER
			MAX-ACCESS read-only
			STATUS current
			DESCRIPTION
				" The number of bytess which VoIP received in this call."
			::= { hwVoCallHistoryVoIPEntry 8 }

		

-- Voice Call History PSTN Table

		hwVoCallHistoryPSTNTable OBJECT-TYPE
			SYNTAX SEQUENCE OF HWVoCallHistoryPSTNEntry
			MAX-ACCESS not-accessible
			STATUS current
			DESCRIPTION
				" The table contains the Voice Call History information related with PSTN."
			::= { hwVoCallHistoryObjects 4 }

		
		hwVoCallHistoryPSTNEntry OBJECT-TYPE
			SYNTAX HWVoCallHistoryPSTNEntry
			MAX-ACCESS not-accessible
			STATUS current
			DESCRIPTION
				"Statistic informations related with PSTN in the call recorded by this entry."
			INDEX { hwVoCallHistoryPSTNIndex }
			::= { hwVoCallHistoryPSTNTable 1 }

		
		HWVoCallHistoryPSTNEntry ::=
			SEQUENCE { 
				hwVoCallHistoryPSTNIndex
					INTEGER,
				hwVoCallHistoryPSTNSetupTime
					DateAndTime,
				hwVoCallHistoryPSTNConnectTime
					DateAndTime,
				hwVoCallHistoryPSTNDisconectTime
					DateAndTime,
				hwVoCallHistoryPSTNSendPackets
					INTEGER,
				hwVoCallHistoryPSTNSendBytes
					INTEGER,
				hwVoCallHistoryPSTNReceivePackets
					INTEGER,
				hwVoCallHistoryPSTNReceiveBytes
					INTEGER
			 }

		hwVoCallHistoryPSTNIndex OBJECT-TYPE
			SYNTAX INTEGER (1..2147483647)
			MAX-ACCESS read-only
			STATUS current
			DESCRIPTION
				"Index variable to access the hwVoCallHistoryPSTNEntry objects
				of the hwVoCallHistoryPSTNTable."
			::= { hwVoCallHistoryPSTNEntry 1 }

		
		hwVoCallHistoryPSTNSetupTime OBJECT-TYPE
			SYNTAX DateAndTime
			MAX-ACCESS read-only
			STATUS current
			DESCRIPTION
				"PSTN setup time of this call."
			::= { hwVoCallHistoryPSTNEntry 2 }

		
		hwVoCallHistoryPSTNConnectTime OBJECT-TYPE
			SYNTAX DateAndTime
			MAX-ACCESS read-only
			STATUS current
			DESCRIPTION
				"PSTN connect time of this call."
			::= { hwVoCallHistoryPSTNEntry 3 }

		
		hwVoCallHistoryPSTNDisconectTime OBJECT-TYPE
			SYNTAX DateAndTime
			MAX-ACCESS read-only
			STATUS current
			DESCRIPTION
				" PSTN disconnect time of this call."
			::= { hwVoCallHistoryPSTNEntry 4 }

		
		hwVoCallHistoryPSTNSendPackets OBJECT-TYPE
			SYNTAX INTEGER
			MAX-ACCESS read-only
			STATUS current
			DESCRIPTION
				" The number of packets which PSTN sent in this call.s"
			::= { hwVoCallHistoryPSTNEntry 5 }

		
		hwVoCallHistoryPSTNSendBytes OBJECT-TYPE
			SYNTAX INTEGER
			MAX-ACCESS read-only
			STATUS current
			DESCRIPTION
				" The number of bytes which PSTN sent in this call."
			::= { hwVoCallHistoryPSTNEntry 6 }

		
		hwVoCallHistoryPSTNReceivePackets OBJECT-TYPE
			SYNTAX INTEGER
			MAX-ACCESS read-only
			STATUS current
			DESCRIPTION
				" The number of packets which PSTN received in this call."
			::= { hwVoCallHistoryPSTNEntry 7 }

		
		hwVoCallHistoryPSTNReceiveBytes OBJECT-TYPE
			SYNTAX INTEGER
			MAX-ACCESS read-only
			STATUS current
			DESCRIPTION
				" The number of bytes which PSTN received in this call."
			::= { hwVoCallHistoryPSTNEntry 8 }

--  Voice Call History Record Table Max Length
		hwVoCallHistoryMaxRetainTime OBJECT-TYPE
			SYNTAX INTEGER (0..2147483647)
			MAX-ACCESS read-write
			STATUS current
			DESCRIPTION
				"The maximum retain time of entries that the hwVoCallHistoryGenericTable,
				hwVoCallHistoryVoIPTable and hwVoCallHistoryPSTNTable may contain.  
				The value 0 means that any history entry will not be saved. if 
				these table are full, the oldest history entry will be deleted
				and the new one will be added."
			DEFVAL { 15 }
			::= { hwVoCallHistoryObjects 5 }
		
	
	END
