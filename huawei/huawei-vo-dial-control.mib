-- ==========================================================================
-- Copyright (C) 2002 by  HUAWEI TECHNOLOGIES. All rights reserved.
--
-- Description: The purpose of this MIB file is to provide the define of
--              voice dial control MIB of HUAWEI quidway serial router.
-- Reference:
-- Version: V2.1
-- History:
-- V1.0 Initial version
-- V2.0 2004-10-20 Updated by gaolong
--      Re-write whole MIB with SNMPv2-SMI format.
--      Modify module name from 'HUAWEI-VOICE-DIAL-CONTROL-MIB' to 'HUAWEI-VO-DIAL-CONTROL-MIB'
-- V2.1 2004-11-10 Updated by gaolong
--      Add objects in hwVoPeerCommonConfigTable
--          hwVoPeerConfigPriority
--          hwVoPeerConfigAuthorizationLevel
--          hwVoPeerConfigDescription
--          hwVoPeerConfigCallingNumberType
--          hwVoPeerConfigCalledNumberType
--          hwVoPeerConfigCallingNumberingPlan
--          hwVoPeerConfigCalledNumberingPlan
--          hwVoPeerConfigCallingNumSubstRule
--          hwVoPeerConfigCalledNumSubstRule
--          hwVoPeerConfigMaxCall            
--      Add objects in hwVoPOTSPeerConfigTable
--          hwVoPOTSPeerConfigSendNumber
--      Add table
--          hwVoPeerConfigCallerPermitNumTable
--      Deprecate objects
--          hwVoPOTSPeerConfigCancelTruncateEnable
--          hwVoPeerDefaultConfigCancelTrun
-- ==========================================================================
HUAWEI-VO-DIAL-CONTROL-MIB DEFINITIONS ::= BEGIN
 
	IMPORTS
		OBJECT-TYPE, MODULE-IDENTITY, IpAddress
			FROM SNMPv2-SMI
		voice
			FROM HUAWEI-3COM-OID-MIB;	
		
		hwVoiceDialControlMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 5 }

EntryStatus ::= INTEGER
                         { valid(1),
                           createRequest(2),
                           underCreation(3),
                           invalid(4)
                         }		
--  The status of a table entry.
-- 
-- Setting this object to the value invalid(4) has the
-- effect of invalidating the corresponding entry.
-- That is, it effectively disassociates the mapping
-- identified with said entry.
-- It is an implementation-specific matter as to whether
-- the agent removes an invalidated entry from the table.
-- Accordingly, management stations must be prepared to
-- receive tabular information from agents that
-- corresponds to entries currently not in use.  Proper
-- interpretation of such entries requires examination
-- of the relevant EntryStatus object.
-- 
-- An existing instance of this object cannot be set to
-- createRequest(2).  This object may only be set to
-- createRequest(2) when this instance is created.  When
-- this object is created, the agent may wish to create
-- supplemental object instances with default values
-- to complete a conceptual row in this table.  Because
-- the creation of these default objects is entirely at
-- the option of the agent, the manager must not assume
-- that any will be created, but may make use of any that
-- are created. Immediately after completing the create
-- operation, the agent must set this object to
-- underCreation(3).
-- 
-- When in the underCreation(3) state, an entry is
-- allowed to exist in a possibly incomplete, possibly
-- inconsistent state, usually to allow it to be
-- modified in mutiple PDUs.  When in this state, an
-- entry is not fully active.  Entries shall exist in
-- the underCreation(3) state until the management
-- station is finished configuring the entry and sets
-- this object to valid(1) or aborts, setting this
-- object to invalid(4).  If the agent determines that
-- an entry has been in the underCreation(3) state for
-- an abnormally long time, it may decide that the
-- management station has crashed.  If the agent makes
-- this decision, it may set this object to invalid(4)
-- to reclaim the entry.  A prudent agent will
-- understand that the management station may need to
-- wait for human input and will allow for that
-- possibility in its determination of this abnormally
-- long period.
-- 
-- An entry in the valid(1) state is fully configured and
-- consistent and fully represents the configuration or
-- operation such a row is intended to represent.  For
-- example, it could be a statistical function that is
-- configured and active, or a filter that is available
-- in the list of filters processed by the packet capture
-- process.
-- 
-- A manager is restricted to changing the state of an
-- entry in the following ways:
-- 
--                       create   under
--      To:       valid  Request  Creation  invalid
-- From:
-- valid             OK       NO        OK       OK
-- createRequest    N/A      N/A       N/A      N/A
-- underCreation     OK       NO        OK       OK
-- invalid           NO       NO        NO       OK
-- nonExistent       NO       OK        NO       OK
-- 
-- In the table above, it is not applicable to move the
-- state from the createRequest state to any other
-- state because the manager will never find the
-- variable in that state.  The nonExistent state is
-- not a value of the enumeration, rather it means that
-- the entryStatus variable does not exist at all.
-- 
-- An agent may allow an entryStatus variable to change
-- state in additional ways, so long as the semantics
-- of the states are followed.  This allowance is made
-- to ease the implementation of the agent and is made
-- despite the fact that managers should never
-- excercise these additional state transitions.
		hwVoPeerObjects OBJECT IDENTIFIER ::= { hwVoiceDialControlMIB 1 }

		
--  Voice Common Peer Configuration Table
-- 
-- Table to store common configuration parameters of all dial peer 
-- types ,including dial peer type , destination pattern ,some voice
-- function parameters and all fax configuration information.
		hwVoPeerCommonConfigTable OBJECT-TYPE
			SYNTAX SEQUENCE OF HWVoPeerCommonConfigEntry
			MAX-ACCESS not-accessible
			STATUS current
			DESCRIPTION
				"The table contains the voice peer common information ."
			::= { hwVoPeerObjects 1 }

		
		hwVoPeerCommonConfigEntry OBJECT-TYPE
			SYNTAX HWVoPeerCommonConfigEntry
			MAX-ACCESS not-accessible
			STATUS current
			DESCRIPTION
				"The common informatioin of voice peer."
			INDEX { hwVoPeerConfigIndex }
			::= { hwVoPeerCommonConfigTable 1 }

		
		HWVoPeerCommonConfigEntry ::=
			SEQUENCE { 
				hwVoPeerConfigIndex
					INTEGER,
				hwVoPeerConfigType
					INTEGER,
				hwVoPeerConfigDesPattern
					OCTET STRING,
				hwVoPeerConfigCodec1st
					INTEGER,
				hwVoPeerConfigCodec2st
					INTEGER,
				hwVoPeerConfigCodec3st
					INTEGER,
				hwVoPeerConfigCodec4st
					INTEGER,
				hwVoPeerConfigIpPreced
					INTEGER,
				hwVoPeerConfigShutDown
					INTEGER,
				hwVoPeerConfigVADSwitch
					INTEGER,
				hwVoPeerConfigDtmfRelay
					INTEGER,
				hwVoPeerConfigFaxLevel
					INTEGER,
				hwVoPeerConfigFaxRate
					INTEGER,
				hwVoPeerConfigFaxLocalTrainParam
					INTEGER,
				hwVoPeerConfigFaxProtocol
					INTEGER,
				hwVoPeerConfigFaxT38HighRedunPackNumber
					INTEGER,
				hwVoPeerConfigFaxT38LowRedunPackNumber
					INTEGER,
				hwVoPeerConfigFaxSendNSFSwitch
					INTEGER,
				hwVoPeerConfigFaxSupportMode
					INTEGER,
				hwVoPeerConfigFaxTrainMode
					INTEGER,
				hwVoPeerConfigFaxRelay
					INTEGER,
				hwVoPeerConfigRowStatus
					EntryStatus,
                                hwVoPeerConfigFaxPassthroughMode	--Passthrough                				
					INTEGER,
                                hwVoPeerConfigPriority
					INTEGER,
                                hwVoPeerConfigAuthorizationLevel
					INTEGER,
                                hwVoPeerConfigDescription
					OCTET STRING,
                                hwVoPeerConfigCallingNumberType
					INTEGER,
                                hwVoPeerConfigCalledNumberType
					INTEGER,
                                hwVoPeerConfigCallingNumberingPlan
					INTEGER,
                                hwVoPeerConfigCalledNumberingPlan
					INTEGER,
                                hwVoPeerConfigSelectStop
					INTEGER,
                                hwVoPeerConfigCallingNumSubstRule
					INTEGER,
                                hwVoPeerConfigCalledNumSubstRule
					INTEGER,
                                hwVoPeerConfigMaxCall
					INTEGER
			 }

		hwVoPeerConfigIndex OBJECT-TYPE
			SYNTAX INTEGER (1..2147483647)
			MAX-ACCESS read-only
			STATUS current
			DESCRIPTION
				"Index of voice peer common table. It identify the  
				number of the voice peer."
			::= { hwVoPeerCommonConfigEntry 1 }

		
		hwVoPeerConfigType OBJECT-TYPE
			SYNTAX INTEGER
				{
				pots(1),
				voip(2),
				vofr(3)
				}
			MAX-ACCESS read-write
			STATUS current
			DESCRIPTION
				"Specify the type of voice peer."
			::= { hwVoPeerCommonConfigEntry 2 }

		
		hwVoPeerConfigDesPattern OBJECT-TYPE
			SYNTAX OCTET STRING (SIZE (0..31))
			MAX-ACCESS read-write
			STATUS current
			DESCRIPTION
				"The number associated with this voice peer.Character include '0'
				to '9','*','#','+','.','T' can be configured in this number."
			::= { hwVoPeerCommonConfigEntry 3 }

		
		hwVoPeerConfigCodec1st OBJECT-TYPE
			SYNTAX INTEGER
				{
				g711a(1),
				g711u(2),
				g723r53(3),
				g723r63(4),
				g729(5),
				g729a(6),
				default(7)
				}
			MAX-ACCESS read-write
			STATUS current
			DESCRIPTION
				"This object expresses the first desirable codec  
				of speech for the peer."
			DEFVAL { default }
			::= { hwVoPeerCommonConfigEntry 4 }

		
		hwVoPeerConfigCodec2st OBJECT-TYPE
			SYNTAX INTEGER
				{
				g711a(1),
				g711u(2),
				g723r53(3),
				g723r63(4),
				g729(5),
				g729a(6),
				default(7)
				}
			MAX-ACCESS read-write
			STATUS current
			DESCRIPTION
				"This object expresses the second desirable codec  
				of speech for the peer."
			DEFVAL { default }
			::= { hwVoPeerCommonConfigEntry 5 }

		
		hwVoPeerConfigCodec3st OBJECT-TYPE
			SYNTAX INTEGER
				{
				g711a(1),
				g711u(2),
				g723r53(3),
				g723r63(4),
				g729(5),
				g729a(6),
				default(7)
				}
			MAX-ACCESS read-write
			STATUS current
			DESCRIPTION
				"This object expresses the third desirable codec  
				of speech for the peer."
			DEFVAL { default }
			::= { hwVoPeerCommonConfigEntry 6 }

		
		hwVoPeerConfigCodec4st OBJECT-TYPE
			SYNTAX INTEGER
				{
				g711a(1),
				g711u(2),
				g723r53(3),
				g723r63(4),
				g729(5),
				g729a(6),
				default(7)
				}
			MAX-ACCESS read-write
			STATUS current
			DESCRIPTION
				"This object expresses the forth desirable codec with 
				of speech for the peer."
			DEFVAL { default }
			::= { hwVoPeerCommonConfigEntry 7 }

		
		hwVoPeerConfigIpPreced OBJECT-TYPE
			SYNTAX INTEGER (0..7)
			MAX-ACCESS read-write
			STATUS current
			DESCRIPTION
				"This object expresses the ip precedence of voice packets.
				The default value is 0."
			DEFVAL { 0 }
			::= { hwVoPeerCommonConfigEntry 8 }

		
		hwVoPeerConfigShutDown OBJECT-TYPE
			SYNTAX INTEGER
				{
				enable(1),
				disable(2)
				}
			MAX-ACCESS read-write
			STATUS current
			DESCRIPTION
				"This object expresses the current status of the peer."
			DEFVAL { disable }
			::= { hwVoPeerCommonConfigEntry 9 }

		
		hwVoPeerConfigVADSwitch OBJECT-TYPE
			SYNTAX INTEGER
				{
				enable(1),
				disable(2)
				}
			MAX-ACCESS read-write
			STATUS current
			DESCRIPTION
				"Enable or disable the VAD (Voice Activity Detection)."
			DEFVAL { disable }
			::= { hwVoPeerCommonConfigEntry 10 }

		
		hwVoPeerConfigDtmfRelay OBJECT-TYPE
			SYNTAX INTEGER
				{
				h245Alphanumeric(1),
				voice(2),
				sip(12)
				}
			MAX-ACCESS read-write
			STATUS current
			DESCRIPTION
				"set the DTMF relay type in this dial-peer."
			DEFVAL { voice }
			::= { hwVoPeerCommonConfigEntry 11 }
		
		
		hwVoPeerConfigFaxLevel OBJECT-TYPE
			SYNTAX INTEGER (3..60)
			MAX-ACCESS read-write
			STATUS current
			DESCRIPTION
				"This object expresses the fax level in this dial-peer."
			DEFVAL { 15 }
			::= { hwVoPeerCommonConfigEntry 12 }

		
		hwVoPeerConfigFaxRate OBJECT-TYPE
			SYNTAX INTEGER
				{
				r14400(1),
				r2400(2),
				r4800(3),
				r9600(4),
				disable(5),
				voice(6)
				}
			MAX-ACCESS read-write
			STATUS current
			DESCRIPTION
				"This object expresses the fax transmit rate."
			DEFVAL { voice }
			::= { hwVoPeerCommonConfigEntry 13 }

		
		hwVoPeerConfigFaxLocalTrainParam OBJECT-TYPE
			SYNTAX INTEGER (0..100)
			MAX-ACCESS read-write
			STATUS current
			DESCRIPTION
				"This object expresses the fax local train threshold in this dial-peer.
				The default value is 10."
			DEFVAL { 10 }
			::= { hwVoPeerCommonConfigEntry 14 }

		
		hwVoPeerConfigFaxProtocol OBJECT-TYPE
			SYNTAX INTEGER
				{
				nonstandard-compatible(1),
				t38(2),             
				pcm(3),                                                  -- the pcm protocol is added newly    
				sip-t38(4),
				h323-t38(5)
				}
			MAX-ACCESS read-write
			STATUS current
			DESCRIPTION
				"This object expresses the fax protocol which this dial-peer support.
				The default value is t38."
			DEFVAL { t38 }
			::= { hwVoPeerCommonConfigEntry 15 }

		hwVoPeerConfigFaxT38HighRedunPackNumber OBJECT-TYPE
			SYNTAX INTEGER (0..2)
			MAX-ACCESS read-write
			STATUS current
			DESCRIPTION
				"This object expresses the high speed redundancy packet numbers when t38 
				fax protocol is used for this dial-peer ."
			DEFVAL { 0 }
			::= { hwVoPeerCommonConfigEntry 16 }

		
		hwVoPeerConfigFaxT38LowRedunPackNumber OBJECT-TYPE
			SYNTAX INTEGER (0..5)
			MAX-ACCESS read-write
			STATUS current
			DESCRIPTION
				"This object expresses the low speed redundancy packet numbers when t38 
				fax protocol is used for this dial-peer ."
			DEFVAL { 0 }
			::= { hwVoPeerCommonConfigEntry 17 }

		
		hwVoPeerConfigFaxSendNSFSwitch OBJECT-TYPE
			SYNTAX INTEGER
				{
				enable(1),
				disable(2)
				}
			MAX-ACCESS read-write
			STATUS current
			DESCRIPTION
				"This object expresses whether or not send nsf to fax in this dial-peer."
			DEFVAL { disable }
			::= { hwVoPeerCommonConfigEntry 18 }

		
		hwVoPeerConfigFaxSupportMode OBJECT-TYPE
			SYNTAX INTEGER
				{
				rtp(1),
				vt(2),
				sip-udp(4)
				}
			MAX-ACCESS read-write
			STATUS current
			DESCRIPTION
				"This object expresses the fax support mode in this dial-peer."
			DEFVAL { rtp }
			::= { hwVoPeerCommonConfigEntry 19 }

		
		hwVoPeerConfigFaxTrainMode OBJECT-TYPE
			SYNTAX INTEGER
				{
				local(1),
				ppp(2)
				}
			MAX-ACCESS read-write
			STATUS current
			DESCRIPTION
				"This object expresses the fax train mode in this dial-peer."
			DEFVAL { ppp }
			::= { hwVoPeerCommonConfigEntry 20 }

		
		hwVoPeerConfigFaxRelay OBJECT-TYPE
			SYNTAX INTEGER
				{
				ecm(1),
				noecm(2)
				}
			MAX-ACCESS read-write
			STATUS current
			DESCRIPTION
				"This object expresses ecm mode is used in fax transmit or not."
			DEFVAL { noecm }
			::= { hwVoPeerCommonConfigEntry 21 }

		
		hwVoPeerConfigRowStatus OBJECT-TYPE
			SYNTAX EntryStatus
			MAX-ACCESS read-write
			STATUS current
			DESCRIPTION
				"This object specifies the status of this conceptual row, 
				which is used to create a new row or 
				modify or delete an existing row in this table."
			::= { hwVoPeerCommonConfigEntry 22 }

		hwVoPeerConfigFaxPassthroughMode OBJECT-TYPE
			SYNTAX INTEGER
				{
				g711alaw(1),
				g711ulaw(3),
				unknown(0)
				}
			MAX-ACCESS read-write
			STATUS current
			DESCRIPTION
				"set pcm fax protocol passthrough mode It is valid only when fax protocol is pcm ."
			::= { hwVoPeerCommonConfigEntry 23 }
	
		hwVoPeerConfigPriority   OBJECT-TYPE 
			SYNTAX INTEGER(0..10)
			MAX-ACCESS read-write
			STATUS current
			DESCRIPTION
				"This object specifies the priority of this voice entity.
				It is between 0 and 10. The highest priority is 0,
				the lowest priority is 10, and 0 is the default value.
				"
			DEFVAL { 0 }
			::= { hwVoPeerCommonConfigEntry 24 }
        
        
		hwVoPeerConfigAuthorizationLevel  OBJECT-TYPE
			SYNTAX INTEGER(0..9)
			MAX-ACCESS read-write
			STATUS current
			DESCRIPTION
				"This object specifies the caller level for local authorization.
				The level is between 0 and 9. The highest level is 9, the lowest
				level is 0, and 0 is the default value.
				"
			DEFVAL { 0 }
			::= { hwVoPeerCommonConfigEntry 25 }
        
        
		hwVoPeerConfigDescription   OBJECT-TYPE
			SYNTAX OCTET STRING(SIZE(0..255))
			MAX-ACCESS read-write
			STATUS current
			DESCRIPTION
				"This object specifies the textual description of this
				voice entity.
				"
			::= { hwVoPeerCommonConfigEntry 26 }

        
		hwVoPeerConfigCallingNumberType   OBJECT-TYPE
			SYNTAX INTEGER
				{
				abbreviated(1),
				international(2),
				national(3),
				network(4),
				reserved(5),
				subscriber(6),
				unknown(7)
				}
			MAX-ACCESS read-write
			STATUS current
			DESCRIPTION
				"This object specifies the numbering type of calling number
				about this voice entity.
				abbreviated   - the numbering type is abbreviated.
				international - the numbering type is international.
				national      - the numbering type is national.
				network       - the numbering type is network.
				reserved      - the numbering type is reserved.
				subscriber    - the numbering type is subscriber.
				unknown       - the numbering type is unkown.
				"
			DEFVAL { unknown }
			::= { hwVoPeerCommonConfigEntry 27 }

        
		hwVoPeerConfigCalledNumberType   OBJECT-TYPE
			SYNTAX INTEGER
				{
				abbreviated(1),
				international(2),
				national(3),
				network(4),
				reserved(5),
				subscriber(6),
				unknown(7)
				}
			MAX-ACCESS read-write
			STATUS current
			DESCRIPTION
				"This object specifies the numbering type of called number
				about this voice entity.
				abbreviated   - the numbering type is abbreviated.
				international - the numbering type is international.
				national      - the numbering type is national.
				network       - the numbering type is network.
				reserved      - the numbering type is reserved.
				subscriber    - the numbering type is subscriber.
				unknown       - the numbering type is unkown.
				"
			DEFVAL { unknown }
			::= { hwVoPeerCommonConfigEntry 28 }


		hwVoPeerConfigCallingNumberingPlan   OBJECT-TYPE
			SYNTAX INTEGER
				{
				data(1),
				isdn(2),
				national(3),
				private(4),
				reserved(5),
				telex(6),
				unknown(7)
				}
			MAX-ACCESS read-write
			STATUS current
			DESCRIPTION
				"This object specifies the numbering plan of calling
				number about this voice entity.
				data     - data numbering plan.
				isdn     - ISDN/telephone numbering plan.
				national - national standard numbering plan.
				private  - Private numbering plan.
				reserved - Reserved for extension.
				telex    - telex numbering plan.
				unknown  - unknown.
				"
			DEFVAL     { unknown }
			::= { hwVoPeerCommonConfigEntry 29 }


		hwVoPeerConfigCalledNumberingPlan   OBJECT-TYPE
			SYNTAX INTEGER
				{
				data(1),
				isdn(2),
				national(3),
				private(4),
				reserved(5),
				telex(6),
				unknown(7)
				}       
			MAX-ACCESS read-write
			STATUS    current
			DESCRIPTION
				"This object specifies the numbering plan of called
				number about this voice entity.
				data     - data numbering plan.
				isdn     - ISDN/telephone numbering plan.
				national - national standard numbering plan.
				private  - Private numbering plan.
				reserved - Reserved for extension.
				telex    - telex numbering plan.
				unknown  - unknown.
				"
			DEFVAL     { unknown }
		::= { hwVoPeerCommonConfigEntry 30 }

        
		hwVoPeerConfigSelectStop   OBJECT-TYPE
			SYNTAX INTEGER
				{
				true(1),
				false(2)
				}
			MAX-ACCESS read-write
			STATUS current
			DESCRIPTION
				"This object specifies no further entity searching allowed
				if a call started on the this voice entity.
				"
			DEFVAL { false }
			::= { hwVoPeerCommonConfigEntry 31 }
		
		hwVoPeerConfigCallingNumSubstRule   OBJECT-TYPE
			SYNTAX INTEGER(0..2147483647)
			MAX-ACCESS read-write
			STATUS current
			DESCRIPTION
				"This object specifies number-substitute rule that apply calling
				number of this voice entity. It is valid if its value is between 1
				and 2147483647. This voice entity doesn't apply any number-substitute
				rule if its value is 0.
				"
			DEFVAL { 0 }
			::= { hwVoPeerCommonConfigEntry 32 }
                        
		hwVoPeerConfigCalledNumSubstRule   OBJECT-TYPE
			SYNTAX INTEGER(0..2147483647)
			MAX-ACCESS read-write
			STATUS current
			DESCRIPTION
				"This object specifies number-substitute rule that apply called
				number of this voice entity. It is valid if its value is between 1
				and 2147483647. This voice entity doesn't apply any number-substitute
				rule if its value is 0.
				"
			DEFVAL { 0 }
			::= { hwVoPeerCommonConfigEntry 33 }
		
		hwVoPeerConfigMaxCall   OBJECT-TYPE
			SYNTAX INTEGER(0..2147483647)
			MAX-ACCESS read-write
			STATUS current
			DESCRIPTION
				"The object specifies that this voice entity is bound with a tag that
				indicates a maximum call value. The value of 0 specifies that
				cancel the act of binding.
				"
			DEFVAL { 0 }
			::= {  hwVoPeerCommonConfigEntry 34 }

		--  POTS Peer Configuration Table
-- 
-- Table to store specific configuration parameters of POTS type dial 
-- peer .
		hwVoPOTSPeerConfigTable OBJECT-TYPE
			SYNTAX SEQUENCE OF HWVoPOTSPeerConfigEntry
			MAX-ACCESS not-accessible
			STATUS current
			DESCRIPTION
				"The table contains the pots peer information ."
			::= { hwVoPeerObjects 2 }

		
		hwVoPOTSPeerConfigEntry OBJECT-TYPE
			SYNTAX HWVoPOTSPeerConfigEntry
			MAX-ACCESS not-accessible
			STATUS current
			DESCRIPTION
				"Pots peer information."
			INDEX { hwVoPOTSPeerConfigIndex }
			::= { hwVoPOTSPeerConfigTable 1 }

		
		HWVoPOTSPeerConfigEntry ::=
			SEQUENCE { 
				hwVoPOTSPeerConfigIndex
					INTEGER,
				hwVoPOTSPeerConfigCancelTruncateEnable
					INTEGER,
				hwVoPOTSPeerConfigPrefix
					OCTET STRING,
				hwVoPOTSPeerConfigPort
					OCTET STRING,
			    hwVoPOTSPeerConfigSendNumber
			        INTEGER
			 }

		hwVoPOTSPeerConfigIndex OBJECT-TYPE
			SYNTAX INTEGER (1..2147483647)
			MAX-ACCESS read-only
			STATUS current
			DESCRIPTION
				"Index of voice pots peer table. It identify the  
				number of the voice pots peer."
			::= { hwVoPOTSPeerConfigEntry 1 }

		
		hwVoPOTSPeerConfigCancelTruncateEnable OBJECT-TYPE
			SYNTAX INTEGER
				{
				enable(1),
				disable(2)
				}
			MAX-ACCESS read-write
			STATUS deprecated
			DESCRIPTION
				"Cancel truncate the called number in this dial-peer."
			DEFVAL { disable }
			::= { hwVoPOTSPeerConfigEntry 2 }

		
		hwVoPOTSPeerConfigPrefix OBJECT-TYPE
			SYNTAX OCTET STRING (SIZE (0..31))
			MAX-ACCESS read-write
			STATUS current
			DESCRIPTION
				"This object expresses the pattern to be added before the dialed number. Valid character 
				include '0' to '9' and ','."
			::= { hwVoPOTSPeerConfigEntry 3 }

		
		hwVoPOTSPeerConfigPort OBJECT-TYPE
			SYNTAX OCTET STRING (SIZE (0..6))
			MAX-ACCESS read-write
			STATUS current
			DESCRIPTION
				"set the voice port and group associated with this peer.The port number is 
				seperated with group number by ':'.As analog voice port,the group number
				can be represented by 255."
			::= { hwVoPOTSPeerConfigEntry 4 }


		hwVoPOTSPeerConfigSendNumber OBJECT-TYPE
			SYNTAX INTEGER (-2..31)
			MAX-ACCESS read-write
			STATUS current
			DESCRIPTION
				"This object specifies the number digits to
				send to the destination. It can take the value:
				0-31 number of right-justified digits of the match-template
				     to be sent.
				-1   Truncate the called number(default).
				-2   send all match-template digits.
				"
			DEFVAL   { -1 }
			::= { hwVoPOTSPeerConfigEntry 5 }

--  VoIP Peer Configuration Table
-- 
-- Table to store specific configuration parameters of VoIP type dial 
-- peer .
		hwVoVoIPPeerConfigTable OBJECT-TYPE
			SYNTAX SEQUENCE OF HWVoVoIPPeerConfigEntry
			MAX-ACCESS not-accessible
			STATUS current
			DESCRIPTION
				"The table contains the voip peer information."
			::= { hwVoPeerObjects 3 }

		
		hwVoVoIPPeerConfigEntry OBJECT-TYPE
			SYNTAX HWVoVoIPPeerConfigEntry
			MAX-ACCESS not-accessible
			STATUS current
			DESCRIPTION
				"Voip peer information."
			INDEX { hwVoVoIPPeerConfigIndex }
			::= { hwVoVoIPPeerConfigTable 1 }

		
		HWVoVoIPPeerConfigEntry ::=
			SEQUENCE { 
				hwVoVoIPPeerConfigIndex
					INTEGER,
				hwVoVoIPPeerConfigSessionTargetType
					INTEGER,
				hwVoVoIPPeerConfigSessionTarget
					IpAddress,
				hwVoVoIPPeerConfigFastSwitch
					INTEGER,
				hwVoVoIPPeerConfigTunnelSwitch
					INTEGER,
				hwVoVoIPPeerConfigTeachPrefix
					OCTET STRING,
                                hwVoVoIPPeerConfigSendRing       -- SEND RING 
					INTEGER             
			 }

		hwVoVoIPPeerConfigIndex OBJECT-TYPE
			SYNTAX INTEGER (1..2147483647)
			MAX-ACCESS read-only
			STATUS current
			DESCRIPTION
				"Index of voice voip peer table. It identify the  
				number of the voip voice peer."
			::= { hwVoVoIPPeerConfigEntry 1 }

		
		hwVoVoIPPeerConfigSessionTargetType OBJECT-TYPE
			SYNTAX INTEGER
				{
				ipv4(1),
				ras(2),
				unknown(3)
				}
			MAX-ACCESS read-write
			STATUS current
			DESCRIPTION
				"This object expresses the type of the session target for this peer ."
			::= { hwVoVoIPPeerConfigEntry 2 }

		
		hwVoVoIPPeerConfigSessionTarget OBJECT-TYPE
			SYNTAX IpAddress
			MAX-ACCESS read-write
			STATUS current
			DESCRIPTION
				"This object expresses the ip address IPV4 peer."
			::= { hwVoVoIPPeerConfigEntry 3 }

		
		hwVoVoIPPeerConfigFastSwitch OBJECT-TYPE
			SYNTAX INTEGER
				{
				enable(1),
				disable(2)
				}
			MAX-ACCESS read-write
			STATUS current
			DESCRIPTION
				"This object expresses whether or not the fast connect function enable."
			DEFVAL { disable }
			::= { hwVoVoIPPeerConfigEntry 4 }

		
		hwVoVoIPPeerConfigTunnelSwitch OBJECT-TYPE
			SYNTAX INTEGER
				{
				enable(1),
				disable(2)
				}
			MAX-ACCESS read-write
			STATUS current
			DESCRIPTION
				"This object expresses whether or not the tunnel function enable. 
				It cannot be used when no fast connect ."
			DEFVAL { disable }
			::= { hwVoVoIPPeerConfigEntry 5 }

		
		hwVoVoIPPeerConfigTeachPrefix OBJECT-TYPE
			SYNTAX OCTET STRING (SIZE (0..31))
			MAX-ACCESS read-write
			STATUS current
			DESCRIPTION
				"This object expresses the technology prefix. Valid charater include '0' to '9',
				'#'."
			::= { hwVoVoIPPeerConfigEntry 6 }

		hwVoVoIPPeerConfigSendRing OBJECT-TYPE
			SYNTAX INTEGER
				{
				enable(1),
				disable(2)
				}
			MAX-ACCESS read-write
			STATUS current
			DESCRIPTION
				"enable/disable the send ring. It is valid only when fast connect is enabled ."
			DEFVAL { disable }
			::= { hwVoVoIPPeerConfigEntry 7 }
			
					
--  Dial Peer Default Configuration Objects
-- 
-- Object to store default  configuration parameters of Dial peer .
		hwVoPeerDefaultConfigObjects OBJECT IDENTIFIER ::= { hwVoPeerObjects 4 }
		
		hwVoPeerDefaultConfigCancelTrun OBJECT-TYPE
			SYNTAX INTEGER
				{
				enable(1),
				disable(2)
				}
			MAX-ACCESS read-write
			STATUS deprecated
			DESCRIPTION
				"The default value of dial peer's Cancel trun"
			DEFVAL { enable }
			::= { hwVoPeerDefaultConfigObjects 1 }

		hwVoPeerDefaultConfig1STCodecLevel OBJECT-TYPE
			SYNTAX INTEGER
				{
				g729r8(0),
				g711alaw(1),
				g723r63(2),
				g723r53(3),
				g711ulaw(4),
				g729a(5)
				}
			MAX-ACCESS read-write
			STATUS current
			DESCRIPTION
				"The default value of voice entity 1st codec level priority
				g711alaw G.711 A Law 64000 bps
				g711ulaw G.711 U Law 64000 bps
				g723r53  G.723.1 5300 bps
				g723r63  G.723.1 6300 bps
				g729r8   G.729 8000 bps
				g729a    G.729 A				
				"
			::= { hwVoPeerDefaultConfigObjects 2 }
		
		hwVoPeerDefaultConfig2NDCodecLevel OBJECT-TYPE
			SYNTAX INTEGER
				{
				g729r8(0),
				g711alaw(1),
				g723r63(2),
				g723r53(3),
				g711ulaw(4),
				g729a(5)
				}
			MAX-ACCESS read-write
			STATUS current
			DESCRIPTION
				"The default value of voice entity 2nd codec level priority
				g711alaw G.711 A Law 64000 bps
				g711ulaw G.711 U Law 64000 bps
				g723r53  G.723.1 5300 bps
				g723r63  G.723.1 6300 bps
				g729r8   G.729 8000 bps
				g729a    G.729 A				
				"
			::= { hwVoPeerDefaultConfigObjects 3 }
		
		hwVoPeerDefaultConfig3RDCodecLevel OBJECT-TYPE
			SYNTAX INTEGER
				{
				g729r8(0),
				g711alaw(1),
				g723r63(2),
				g723r53(3),
				g711ulaw(4),
				g729a(5)
				}
			MAX-ACCESS read-write
			STATUS current
			DESCRIPTION
				"The default value of voice entity 3rd codec level priority
				g711alaw G.711 A Law 64000 bps
				g711ulaw G.711 U Law 64000 bps
				g723r53  G.723.1 5300 bps
				g723r63  G.723.1 6300 bps
				g729r8   G.729 8000 bps
				g729a    G.729 A				
				"
			::= { hwVoPeerDefaultConfigObjects 4 }
		
		hwVoPeerDefaultConfig4THCodecLevel OBJECT-TYPE
			SYNTAX INTEGER
				{
				g729r8(0),
				g711alaw(1),
				g723r63(2),
				g723r53(3),
				g711ulaw(4),
				g729a(5)
				}
			MAX-ACCESS read-write
			STATUS current
			DESCRIPTION
				"The default value of voice entity 4th codec level priority
				g711alaw G.711 A Law 64000 bps
				g711ulaw G.711 U Law 64000 bps
				g723r53  G.723.1 5300 bps
				g723r63  G.723.1 6300 bps
				g729r8   G.729 8000 bps
				g729a    G.729 A				
				"
			::= { hwVoPeerDefaultConfigObjects 5 }
		
		hwVoPeerDefaultConfigVADOn OBJECT-TYPE
			SYNTAX INTEGER
				{
				enable(1),
				disable(2)
				}
			MAX-ACCESS read-write
			STATUS current
			DESCRIPTION
				"The default value of dial peer's VAD Switch"
			DEFVAL { disable }
			::= { hwVoPeerDefaultConfigObjects 6 }
			
		hwVoPeerDefaultConfigFaxTransmitLevel OBJECT-TYPE
			SYNTAX INTEGER ( 3..60 )
			MAX-ACCESS read-write
			STATUS current
			DESCRIPTION
				"The default value of dial peer's FaxTransmitLevel.The unit is db"
			DEFVAL { 15 }
			::= { hwVoPeerDefaultConfigObjects 7 }
			
		hwVoPeerDefaultConfigFaxLocalTrain OBJECT-TYPE
			SYNTAX INTEGER ( 0..100 )
			MAX-ACCESS read-write
			STATUS current
			DESCRIPTION
				"The default value of dial peer's Fax  local train threshold ."
			DEFVAL { 10 }
			::= { hwVoPeerDefaultConfigObjects 8 }
			
		hwVoPeerDefaultConfigFaxProtocol OBJECT-TYPE
			SYNTAX INTEGER
				{
				nonstandard-compatible(1),
				t38(2),
				h323-t38(3),
				sip-t38(4),
				pcm-alaw(5),
				pcm-ulaw(6)
				}
			MAX-ACCESS read-write
			STATUS current
			DESCRIPTION
				"The default value of dial peer's Fax Protocol ."
			DEFVAL { t38 }
			::= { hwVoPeerDefaultConfigObjects 9 }

		hwVoPeerDefaultConfigFaxHSRedundancy OBJECT-TYPE
			SYNTAX INTEGER (0..2)
			MAX-ACCESS read-write
			STATUS current
			DESCRIPTION
				"The default value of dial peer's T38 Fax Protocol High Redundancy."
			DEFVAL { 0 }
			::= { hwVoPeerDefaultConfigObjects 10 }

		hwVoPeerDefaultConfigFaxLSRedundancy OBJECT-TYPE
			SYNTAX INTEGER (0..2)
			MAX-ACCESS read-write
			STATUS current
			DESCRIPTION
				"The default value of dial peer's T38 Fax Protocol Low Redundancy."
			DEFVAL { 0 }
			::= { hwVoPeerDefaultConfigObjects 11 }
			
		hwVoPeerDefaultConfigFaxBaudrate OBJECT-TYPE
			SYNTAX INTEGER
				{
				disable(0),
				b2400(2),
				b4800(3),
				b9600(5),
				b14400(7),
				voice(8)
				}
			MAX-ACCESS read-write
			STATUS current
			DESCRIPTION
				"The default value of dial peer's Fax Baudrate ."
			DEFVAL { voice }
			::= { hwVoPeerDefaultConfigObjects 12 }

		hwVoPeerDefaultConfigFaxNSF OBJECT-TYPE
			SYNTAX INTEGER
				{
				enable(1),
				disable(2)
				}
			MAX-ACCESS read-write
			STATUS current
			DESCRIPTION
				"The default value of fax non-standard faculty ."
			DEFVAL { disable }
			::= { hwVoPeerDefaultConfigObjects 13 }
			
		hwVoPeerDefaultConfigFaxSupportMode OBJECT-TYPE
			SYNTAX INTEGER
				{
				rtp(1),
				vt(2)
				}
			MAX-ACCESS read-write
			STATUS current
			DESCRIPTION
				"The default value of fax SupportMode ."
			DEFVAL { rtp }
			::= { hwVoPeerDefaultConfigObjects 14 }
			
		hwVoPeerDefaultConfigFaxTrainMode OBJECT-TYPE
			SYNTAX INTEGER
				{
				ppp(1),
				local(2)
				}
			MAX-ACCESS read-write
			STATUS current
			DESCRIPTION
				"The default value of fax TrainMode ."
			DEFVAL { ppp }
			::= { hwVoPeerDefaultConfigObjects 15 }
			
		hwVoPeerDefaultConfigFaxECM OBJECT-TYPE
			SYNTAX INTEGER
				{
				enable(1),
				disable(2)
				}
			MAX-ACCESS read-write
			STATUS current
			DESCRIPTION
				"The default value of fax ECM Mode ."
			DEFVAL { disable }
			::= { hwVoPeerDefaultConfigObjects 16 }			
			
-- Caller number permitted Configuration Table
--
-- voPeerCfgCallerPermitNumTable
-- Table to store all of permitted incoming caller number set
-- by user.
		hwVoPeerConfigCallerPermitNumTable OBJECT-TYPE
			SYNTAX SEQUENCE OF HWVoPeerConfigCallerPermitNumEntry
			MAX-ACCESS not-accessible
			STATUS current
			DESCRIPTION
				"The table contains caller number permitted information
				in the specific voice entity for incoming call."
			::= { hwVoPeerObjects 5 }

                hwVoPeerConfigCallerPermitNumEntry OBJECT-TYPE
			SYNTAX HWVoPeerConfigCallerPermitNumEntry
			MAX-ACCESS not-accessible
			STATUS current
			DESCRIPTION
				"A single caller number permitted in the specific voice entity
				for incoming call. The entry is created when its associated
				voPeerCommonCfgEntry is created. This entry is deleted when
				its associated voPeerCommonCfgEntry is deleted."
			INDEX { hwVoPeerConfigIndex,hwVoPeerConfigCallerPermitNum }
			::= { hwVoPeerConfigCallerPermitNumTable 1 }

		HWVoPeerConfigCallerPermitNumEntry ::= 
			SEQUENCE {
				hwVoPeerConfigCallerPermitNum
					OCTET STRING,
				hwVoPeerConfigCallerPermitNumRowStatus
					EntryStatus
			}

		hwVoPeerConfigCallerPermitNum    OBJECT-TYPE
			SYNTAX OCTET STRING(SIZE(1..31))
			MAX-ACCESS read-write
			STATUS current
			DESCRIPTION
				"This object specifies caller number permitted that
				must be of the form ^(([0-9ABCD#*.!+%[]()\-]+(\$)!)|(\$))$.
				Specially set this object $ meaning allow caller null."
			::= { hwVoPeerConfigCallerPermitNumEntry 1 }

		hwVoPeerConfigCallerPermitNumRowStatus    OBJECT-TYPE
			SYNTAX EntryStatus
			MAX-ACCESS read-write
			STATUS current
			DESCRIPTION
				"This object is used to create a new row or modify or
				delete an existing row in this table."
			::= { hwVoPeerConfigCallerPermitNumEntry 2 }	

	END
