-- =================================================================
-- Copyright (C) 2002 by HUAWEI 3COM TECHNOLOGIES.  All rights reserved.
--
-- Description: protocol priority mib
-- Reference:
-- Version: V1.0
-- History:
--   V1.0 created by zhuangyu
--     The initial version, 2005-01-17
-- =================================================================
H3C-PROT-PRIORITY-MIB DEFINITIONS ::= BEGIN

    IMPORTS
        h3cCommon
            FROM HUAWEI-3COM-OID-MIB
        Integer32, OBJECT-TYPE, MODULE-IDENTITY
            FROM SNMPv2-SMI
        RowStatus
            FROM SNMPv2-TC;

    h3cProtocolPriority MODULE-IDENTITY
        LAST-UPDATED "200501171633Z"        -- January 17, 2005 at 16:33 GMT
        ORGANIZATION
            "Huawei 3Com Technologies Co., Ltd."
        CONTACT-INFO
            "Platform Team Huawei 3Com Technologies Co., Ltd.
            Hai-Dian District Beijing P.R. China
            http://www.huawei-3com.com
            Zip:100085
            "
        DESCRIPTION
            "This MIB is used to manage and configure the priority of specified protocol.
            This MIB is applicable to routers, switches and other products.
            "
        REVISION "200501171633Z"        -- January 17, 2005 at 16:33 GMT
        DESCRIPTION
            "The initial revision of this MIB module."
        ::= { h3cCommon 37 }


--
-- Node definitions
--
    h3cProtocolPriorityObjects OBJECT IDENTIFIER ::= { h3cProtocolPriority 1 }

    h3cPPri OBJECT IDENTIFIER ::= { h3cProtocolPriorityObjects 1 }

    h3cProtocolPriorityTable OBJECT-TYPE
        SYNTAX SEQUENCE OF H3cProtocolPriorityEntry
        MAX-ACCESS not-accessible
        STATUS current
        DESCRIPTION
            "A table is used to configure the priority of the protocol."
        ::= { h3cPPri 1 }

    h3cProtocolPriorityEntry OBJECT-TYPE
        SYNTAX H3cProtocolPriorityEntry
        MAX-ACCESS not-accessible
        STATUS current
        DESCRIPTION
            "An entry containing information about the priority of the protocol."
        INDEX { h3cPPriProtocolType }
        ::= { h3cProtocolPriorityTable 1 }

    H3cProtocolPriorityEntry ::=
        SEQUENCE {
            h3cPPriProtocolType
                INTEGER,
            h3cPPriPriorityType
                INTEGER,
            h3cPPriPriorityVlaue
                Integer32,
            h3cPPriRowStatus
                RowStatus
        }

    h3cPPriProtocolType OBJECT-TYPE
        SYNTAX INTEGER
               {
               ospf(1),
               telnet(2),
               snmp(3),
               icmp(4),
               bgp(5),
               ldp(6)
               }
        MAX-ACCESS not-accessible
        STATUS current
        DESCRIPTION
            "Protocol type."
        ::= { h3cProtocolPriorityEntry 1 }

    h3cPPriPriorityType OBJECT-TYPE
        SYNTAX INTEGER
               {
               ipPrecedence(1),
               dscp(2)
               }
        MAX-ACCESS read-create
        STATUS current
        DESCRIPTION
            "Priority type."
        ::= { h3cProtocolPriorityEntry 2 }

    h3cPPriPriorityVlaue OBJECT-TYPE
        SYNTAX Integer32 (0..63)
        MAX-ACCESS read-create
        STATUS current
        DESCRIPTION
            "Priority value.
            If setting h3cPPriPriorityType to ip-precedence(1),
            the range of h3cPPriPriorityVlaue is from 0 to 7.
            If setting h3cPPriPriorityType to dscp(2),
            the range of h3cPPriPriorityVlaue is from 0 to 63."
        ::= { h3cProtocolPriorityEntry 3 }

    h3cPPriRowStatus OBJECT-TYPE
        SYNTAX RowStatus
        MAX-ACCESS read-create
        STATUS current
        DESCRIPTION
            "RowStatus, Now support createAndGo,active and destroy.
            To create a new row, h3cPPriPriorityType and h3cPPriPriorityValue must be specified.
            To modify a row,h3cPPriPriorityType and h3cPPriPriorityValue
            must change at the same time and the h3cPPriRowStatus is active ."
        ::= { h3cProtocolPriorityEntry 4 }
END
