-- =================================================================
-- Copyright (C) 2006 by HUAWEI-3Com TECHNOLOGIES. All rights reserved
--
-- Description: RPR private MIB. Description of entity extend properties for
-- IEEE-802DOT17-RPR-MIB
-- Reference: IEEE-802DOT17-RPR-MIB
-- Version: V1.1
-- History:
--  V1.0 created by qinxia
--  V1.1 modified by hexuefei,Add the RPR packet drop counters table.
-- =================================================================
H3C-RPR-MIB DEFINITIONS ::= BEGIN

    IMPORTS
        h3cCommon
            FROM HUAWEI-3COM-OID-MIB
        rprTopoImageEntry, rprTopoImageMacAddress, rprTopoImageInetAddress
            FROM IEEE-802DOT17-RPR-MIB
        InterfaceIndex
            FROM IF-MIB
        SnmpAdminString
            FROM SNMP-FRAMEWORK-MIB
        RowStatus, TruthValue
            FROM SNMPv2-TC;

        h3cRpr MODULE-IDENTITY
            LAST-UPDATED "200503161000Z"  -- March 16, 2005 at 10:18:41 GMT
            ORGANIZATION
                "Huawei 3Com Technologies Co., Ltd."
            CONTACT-INFO
                "Platform Team Huawei 3Com Technologies Co., Ltd.
                 Hai-Dian District Beijing P.R. China
                 http://www.huawei-3com.com
                 Zip:100085"
            DESCRIPTION
                "This MIB manages RPR(Resilient Packet Ring)interfaces by
                 providing an operational table which controls parameters
                 of each RPR interface and reports alarm conditions.

                 A RPR ring is composed of two fiber rings: Outer and Inner."
            REVISION "200503161000Z"      -- March 16, 2005 at 10:18:41 GMT
            DESCRIPTION
                "First published version."
            ::= { h3cCommon 60 }

--
-- Textual conventions
--

    H3cRprRingletID ::= TEXTUAL-CONVENTION
        STATUS current
        DESCRIPTION
            "Indicates the path on which data flow is selected.
             The valid value is ringlet0 and ringlet1. They indicate
             two RPR fiber rings. Ringlet0 refers to outer ring and
             ringlet1 refers to inner ring."
        REFERENCE
            "IEEE 802.17 V3.3 Subclause 11.2.1.1 Span and
             ringlet parameterization."
        SYNTAX INTEGER
            {
             ringlet0(1),
             ringlet1(2)
        }

    H3cRprServiceClass ::= TEXTUAL-CONVENTION
        STATUS current
        DESCRIPTION
            "Indicates the service class of RPR.
             The valid value is ClassC, ClassB, ClassA1 and ClassA0."
        REFERENCE
                "IEEE 802.17 V3.3 Subclause 7.3 Service class."
        SYNTAX INTEGER
            {
             classC(1),
             classB(2),
             classA1(3),
             classA0(4)
        }

    h3cRprObjects OBJECT IDENTIFIER ::= { h3cRpr 1 }

-- RPR maximum define table

    h3cRprMaxmumDefine OBJECT IDENTIFIER ::= { h3cRprObjects 1 }

    h3cRprMaxmumDefineTable OBJECT-TYPE
        SYNTAX SEQUENCE OF H3cRprMaxmumDefineEntry
        MAX-ACCESS not-accessible
        STATUS current
        DESCRIPTION
            "This table contains the specs of RPR ring."
      ::= { h3cRprMaxmumDefine 1 }

    h3cRprMaxmumDefineEntry OBJECT-TYPE
        SYNTAX H3cRprMaxmumDefineEntry
        MAX-ACCESS not-accessible
        STATUS current
        DESCRIPTION
            "The entry of RPR Maximum Table."
        INDEX { h3cRprMaxMumIfIndex }
        ::= { h3cRprMaxmumDefineTable 1 }

    H3cRprMaxmumDefineEntry ::=
        SEQUENCE {
            h3cRprMaxMumIfIndex
                InterfaceIndex,
            h3cRprMaxStationNumDefine
                INTEGER,
            h3cRprMaxReservedRateDefine
                Gauge32
        }

    h3cRprMaxMumIfIndex OBJECT-TYPE
        SYNTAX InterfaceIndex
        MAX-ACCESS not-accessible
        STATUS current
        DESCRIPTION
            "The ifIndex of this RPR interface."
        ::= { h3cRprMaxmumDefineEntry 1 }

    h3cRprMaxStationNumDefine OBJECT-TYPE
        SYNTAX INTEGER
        MAX-ACCESS read-only
        STATUS current
        DESCRIPTION
            "Max station number supported by RPR ring."
        ::= { h3cRprMaxmumDefineEntry 2 }


    h3cRprMaxReservedRateDefine OBJECT-TYPE
        SYNTAX Gauge32
        MAX-ACCESS read-only
        STATUS current
        DESCRIPTION
            "Max reserved rate supported by each RPR ringlet.
             An estimate of the interface's current bandwidth in
             units of 1,000,000 bits per second.  If this object
             reports a value of 'n' then the speed of the interface
             is somewhere in the range of 'n-500,000' to
             'n+499,999'.  For interfaces which do not vary in
             bandwidth or for those where no accurate estimation
             can be made, this object should contain the nominal
             bandwidth.  For a sub-layer which has no concept of
             bandwidth, this object should be zero."
        ::= { h3cRprMaxmumDefineEntry 3 }

    h3cRprTopoImage OBJECT IDENTIFIER ::= { h3cRprObjects 2 }

-- extension to the RPR topology table

    h3cRprTopoImageXTable OBJECT-TYPE
        SYNTAX SEQUENCE OF H3cRprTopoImageXEntry
        MAX-ACCESS not-accessible
        STATUS current
        DESCRIPTION
            "This table contains additional objects
             for the rprTopoImageTable in IEEE-802DOT17-RPR-MIB."
        REFERENCE
            "rprTopoImageTable in IEEE-802DOT17-RPR-MIB."
        ::= { h3cRprTopoImage 1 }

    h3cRprTopoImageXEntry OBJECT-TYPE
        SYNTAX H3cRprTopoImageXEntry
        MAX-ACCESS not-accessible
        STATUS current
        DESCRIPTION
            "Each entry contains information specific to a particular
             station on the ring. The table has at least one entry for
             the station itself, this entry indicates zero hops on each
             ringlet."
         AUGMENTS { rprTopoImageEntry }
         ::= { h3cRprTopoImageXTable 1 }

    H3cRprTopoImageXEntry ::=
        SEQUENCE {
            h3cRprTopoImageXWestEdgeStatus
                TruthValue,
            h3cRprTopoImageXEastEdgeStatus
                TruthValue,
            h3cRprTopoImageXStationName
                SnmpAdminString
        }

    h3cRprTopoImageXWestEdgeStatus OBJECT-TYPE
        SYNTAX TruthValue
        MAX-ACCESS read-only
        STATUS current
        DESCRIPTION
            "The current edge status of the west span.
             If an edge exists,the h3cRprTopoImageXWestEdgeStatus is true.
             Otherwise, the h3cRprTopoImageXWestEdgeStatus is false."
        REFERENCE
            "IEEE 802.17  V3.3 Subclause 11.1.1.5, Edges"
        ::= { h3cRprTopoImageXEntry 3 }

    h3cRprTopoImageXEastEdgeStatus OBJECT-TYPE
        SYNTAX TruthValue
        MAX-ACCESS read-only
        STATUS current
        DESCRIPTION
            "The current edge status of the east span.
             If an edge exists, the h3cRprTopoImageXEastEdgeStatus is true.
             Otherwise, the h3cRprTopoImageXEastEdgeStatus is false."
        REFERENCE
             "IEEE 802.17  V3.3 Subclause 11.1.1.5, Edges"
        ::= { h3cRprTopoImageXEntry 4 }

    h3cRprTopoImageXStationName OBJECT-TYPE
        SYNTAX SnmpAdminString
        MAX-ACCESS read-write
        STATUS current
        DESCRIPTION
            "The operator assigned station name. The operator can assigned it
             by h3cRprTopoImageXStationName."
        REFERENCE
            "IEEE 802.17 V3.3 Subclause 11.2.6, stationName."
        ::= { h3cRprTopoImageXEntry 5 }

    h3cRprSpanCounters OBJECT IDENTIFIER ::= { h3cRprObjects 3 }

-- RPR source mac counters table

    h3cRprSrcMacCountTable OBJECT-TYPE
        SYNTAX SEQUENCE OF H3cRprSrcMacCountEntry
        MAX-ACCESS not-accessible
        STATUS current
        DESCRIPTION
            "The RPR Source Mac Count Table contains the cumulative sum
             of frames and octects from the particular source station."
        ::= { h3cRprSpanCounters 1 }

    h3cRprSrcMacCountEntry OBJECT-TYPE
        SYNTAX H3cRprSrcMacCountEntry
        MAX-ACCESS not-accessible
        STATUS current
        DESCRIPTION
            "An entry in the RPR Source Mac Count Table."
        INDEX { h3cRprSrcMacCountIfIndex, h3cRprSrcMacCountBySrcAddress }
        ::= { h3cRprSrcMacCountTable 1 }

    H3cRprSrcMacCountEntry ::=
        SEQUENCE {
            h3cRprSrcMacCountIfIndex
                InterfaceIndex,
            h3cRprSrcMacCountBySrcAddress
                MacAddress,
          h3cRprSrcMacCountReceivedFrames
                Counter64,
            h3cRprSrcMacCountReceivedOctets
                Counter64
        }

    h3cRprSrcMacCountIfIndex OBJECT-TYPE
        SYNTAX InterfaceIndex
        MAX-ACCESS not-accessible
        STATUS current
        DESCRIPTION
            "The ifIndex of this RPR interface."
        REFERENCE
            "RFC 2863, ifIndex."
        ::= { h3cRprSrcMacCountEntry 1 }

    h3cRprSrcMacCountBySrcAddress OBJECT-TYPE
        SYNTAX MacAddress
        MAX-ACCESS not-accessible
        STATUS current
        DESCRIPTION
            "MAC address of the source station where the frames come from."
        ::= { h3cRprSrcMacCountEntry 2 }

    h3cRprSrcMacCountReceivedFrames OBJECT-TYPE
        SYNTAX Counter64
        MAX-ACCESS read-only
        STATUS current
        DESCRIPTION
            "Frames received from a particular MAC address of source station."
        ::= { h3cRprSrcMacCountEntry 3 }

    h3cRprSrcMacCountReceivedOctets OBJECT-TYPE
        SYNTAX Counter64
        MAX-ACCESS read-only
        STATUS current
        DESCRIPTION
            "Octets received from a particular MAC address of source station."
        ::= { h3cRprSrcMacCountEntry 4 }

-- RPR destination mac counters table

    h3cRprDestMacCountTable OBJECT-TYPE
        SYNTAX SEQUENCE OF H3cRprDestMacCountEntry
        MAX-ACCESS not-accessible
        STATUS current
        DESCRIPTION
            "The RPR Destination MAC Count Table contains the cumulative sum
             of  frames and octects to the particular destination station."
        ::= { h3cRprSpanCounters 2 }

    h3cRprDestMacCountEntry OBJECT-TYPE
        SYNTAX H3cRprDestMacCountEntry
        MAX-ACCESS not-accessible
        STATUS current
        DESCRIPTION
            "An entry in the RPR MAC Destination Count Table."
        INDEX { h3cRprDestMacCountIfIndex, h3cRprDestMacCountByDestAddress }
        ::= { h3cRprDestMacCountTable 1 }

    H3cRprDestMacCountEntry ::=
        SEQUENCE {
            h3cRprDestMacCountIfIndex
                InterfaceIndex,
            h3cRprDestMacCountByDestAddress
                MacAddress,
            h3cRprDestMacCountReceivedFrames
                Counter64,
            h3cRprDestMacCountReceivedOctets
                Counter64
        }

    h3cRprDestMacCountIfIndex OBJECT-TYPE
        SYNTAX InterfaceIndex
        MAX-ACCESS not-accessible
        STATUS current
        DESCRIPTION
            "The ifIndex of RPR interface."
        REFERENCE
            "RFC 2863, ifIndex"
        ::= { h3cRprDestMacCountEntry 1 }

    h3cRprDestMacCountByDestAddress OBJECT-TYPE
        SYNTAX MacAddress
        MAX-ACCESS not-accessible
        STATUS current
        DESCRIPTION
            "MAC address of the destination station where the frames are sent
             to."
        ::= { h3cRprDestMacCountEntry 2 }

    h3cRprDestMacCountReceivedFrames OBJECT-TYPE
        SYNTAX Counter64
        MAX-ACCESS read-only
        STATUS current
        DESCRIPTION
            "Frames sent to a particular MAC address of destination station."
        ::= { h3cRprDestMacCountEntry 3 }

    h3cRprDestMacCountReceivedOctets OBJECT-TYPE
        SYNTAX Counter64
        MAX-ACCESS read-only
        STATUS current
        DESCRIPTION
            "Octets sent to a particular MAC address of destination station."
        ::= { h3cRprDestMacCountEntry 4 }

-- RPR packet drop counters table

     h3cRprPktDropCountTable OBJECT-TYPE
        SYNTAX SEQUENCE OF H3cRprPktDropCountEntry
        MAX-ACCESS not-accessible
        STATUS current
        DESCRIPTION
            "The RPR Packet Drop Count Table contains the cumulative sum
             of packets dropped for congestion."
        ::= { h3cRprSpanCounters 3 }

     h3cRprPktDropCountEntry OBJECT-TYPE
        SYNTAX H3cRprPktDropCountEntry
        MAX-ACCESS not-accessible
        STATUS current
        DESCRIPTION
            "An entry in the RPR Packet Drop Count Table."
        INDEX { h3cRprPktDropCntIfIndex, h3cRprPktDropCntRingletID }
        ::= { h3cRprPktDropCountTable 1 }

     H3cRprPktDropCountEntry ::=
        SEQUENCE {
                h3cRprPktDropCntIfIndex
                    InterfaceIndex,
                h3cRprPktDropCntRingletID
                    H3cRprRingletID,
                h3cRprDownFlowClassAPktDrops
                    Counter64,
                h3cRprUpFlowClassAPktDrops
                    Counter64,
                h3cRprDownFlowClassBPktDrops
                    Counter64,
                h3cRprUpFlowClassBPktDrops
                    Counter64,
                h3cRprDownFlowClassCPktDrops
                    Counter64,
                h3cRprUpFlowClassCPktDrops
                    Counter64
        }

     h3cRprPktDropCntIfIndex OBJECT-TYPE
        SYNTAX InterfaceIndex
        MAX-ACCESS not-accessible
        STATUS current
        DESCRIPTION
            "The ifIndex of this RPR interface."
        REFERENCE
             "RFC 2863, ifIndex."
        ::= { h3cRprPktDropCountEntry 1 }

     h3cRprPktDropCntRingletID OBJECT-TYPE
        SYNTAX H3cRprRingletID
        MAX-ACCESS not-accessible
        STATUS current
        DESCRIPTION
            "The RPR Ringlet of the station through which the packets transmit."
        ::= { h3cRprPktDropCountEntry 2 }

     h3cRprDownFlowClassAPktDrops OBJECT-TYPE
        SYNTAX Counter64
        MAX-ACCESS read-only
        STATUS current
        DESCRIPTION
            "The total dropped number of Class A packets which transmit
             down from the host."
        ::= { h3cRprPktDropCountEntry 3 }

     h3cRprUpFlowClassAPktDrops OBJECT-TYPE
        SYNTAX Counter64
        MAX-ACCESS read-only
        STATUS current
        DESCRIPTION
            "The total dropped number of Class A packets which transmit
             up to the host."
        ::= { h3cRprPktDropCountEntry 4 }

     h3cRprDownFlowClassBPktDrops OBJECT-TYPE
        SYNTAX Counter64
        MAX-ACCESS read-only
        STATUS current
        DESCRIPTION
            "The total dropped number of Class B packets which transmit
             down from the host."
        ::= { h3cRprPktDropCountEntry 5 }

     h3cRprUpFlowClassBPktDrops OBJECT-TYPE
         SYNTAX Counter64
         MAX-ACCESS read-only
         STATUS current
         DESCRIPTION
            "The total dropped number of Class B packets which transmit
             up to the host."
         ::= { h3cRprPktDropCountEntry 6 }

     h3cRprDownFlowClassCPktDrops OBJECT-TYPE
         SYNTAX Counter64
         MAX-ACCESS read-only
         STATUS current
         DESCRIPTION
             "The total dropped number of Class C packets which transmit
              down from the host."
         ::= { h3cRprPktDropCountEntry 7 }

     h3cRprUpFlowClassCPktDrops OBJECT-TYPE
         SYNTAX Counter64
         MAX-ACCESS read-only
         STATUS current
         DESCRIPTION
             "The total dropped number of Class C packets which transmit
              up to the host."
         ::= { h3cRprPktDropCountEntry 8 }

    h3cRprRS OBJECT IDENTIFIER ::= { h3cRprObjects 4 }

-- The RPR static ring selection table

    h3cRprStaticRSTable OBJECT-TYPE
        SYNTAX SEQUENCE OF H3cRprStaticRSEntry
        MAX-ACCESS not-accessible
        STATUS current
        DESCRIPTION
            "The RPR Static Ring Selection table contains the static
             ring selection information by the way of configuration."
        ::= { h3cRprRS 1 }

    h3cRprStaticRSEntry OBJECT-TYPE
        SYNTAX H3cRprStaticRSEntry
        MAX-ACCESS not-accessible
        STATUS current
        DESCRIPTION
            "An entry in the RPR Static Ring Selection table."
        INDEX { h3cRprStaticRSIfIndex, h3cRprStaticRSMacAddress }
        ::= { h3cRprStaticRSTable 1 }

    H3cRprStaticRSEntry ::=
        SEQUENCE {
            h3cRprStaticRSIfIndex
                InterfaceIndex,
            h3cRprStaticRSMacAddress
                MacAddress,
            h3cRprStaticRSRingletID
                H3cRprRingletID,
            h3cRprStaticRSTtl
                INTEGER,
            h3cRprStaticRSValid
                TruthValue,
            h3cRprStaticRSRowStatus
                RowStatus
        }

    h3cRprStaticRSIfIndex OBJECT-TYPE
        SYNTAX InterfaceIndex
        MAX-ACCESS not-accessible
        STATUS current
        DESCRIPTION
            "The ifIndex of RPR interface."
        REFERENCE
            "RFC 2863, ifIndex"
        ::= { h3cRprStaticRSEntry 1 }

    h3cRprStaticRSMacAddress OBJECT-TYPE
        SYNTAX MacAddress
        MAX-ACCESS not-accessible
        STATUS current
        DESCRIPTION
            "The MAC address of the station on the ring."
        ::= { h3cRprStaticRSEntry 2 }

    h3cRprStaticRSRingletID OBJECT-TYPE
        SYNTAX H3cRprRingletID
        MAX-ACCESS read-create
        STATUS current
        DESCRIPTION
            "The identifier of the ring which frames are sent
             from one station to another. Ringlet0 refers to outer ring,
             while ringlet1 does inner."
        ::= { h3cRprStaticRSEntry 3 }

    h3cRprStaticRSTtl  OBJECT-TYPE
        SYNTAX INTEGER
        MAX-ACCESS read-only
        STATUS current
        DESCRIPTION
            "The hops from source station to destination station by the
             selected ringlet."
        ::= { h3cRprStaticRSEntry 4 }

    h3cRprStaticRSValid OBJECT-TYPE
        SYNTAX TruthValue
        MAX-ACCESS read-only
        STATUS current
        DESCRIPTION
            "The flag identify whether the configed ringlet is valid.
             If it is true, the configed ringlet is valid, otherwise
             it's invalid."
        ::= { h3cRprStaticRSEntry 5 }

    h3cRprStaticRSRowStatus OBJECT-TYPE
        SYNTAX RowStatus
        MAX-ACCESS read-create
        STATUS current
        DESCRIPTION
            "The status of this table entry.
             The status includes createAndGo, active and destroy."
        ::= { h3cRprStaticRSEntry 6 }

-- The RPR Ipv4 dynamic ring selection table

    h3cRprIpv4DynamicRSTable OBJECT-TYPE
        SYNTAX SEQUENCE OF H3cRprIpv4DynamicRSEntry
        MAX-ACCESS not-accessible
        STATUS current
        DESCRIPTION
            "The RPR Ipv4Dynamic Ring Selection Table that contains the
             dynamic ring selection information by shortest path."
        ::= { h3cRprRS 2 }

    h3cRprIpv4DynamicRSEntry OBJECT-TYPE
        SYNTAX H3cRprIpv4DynamicRSEntry
        MAX-ACCESS not-accessible
        STATUS current
        DESCRIPTION
            "An entry in the RPR Ipv4Dynamic Ring Selection Table."
        INDEX { h3cRprIpv4DynamicRSIfIndex, h3cRprIpv4DynamicRSMacAddress }
        ::= { h3cRprIpv4DynamicRSTable 1 }

    H3cRprIpv4DynamicRSEntry ::=
        SEQUENCE {
            h3cRprIpv4DynamicRSIfIndex
                InterfaceIndex,
            h3cRprIpv4DynamicRSMacAddress
                MacAddress,
            h3cRprIpv4DynamicRSRingletID
                H3cRprRingletID,
            h3cRprIpv4DynamicRSTtl
                INTEGER
        }

    h3cRprIpv4DynamicRSIfIndex OBJECT-TYPE
        SYNTAX InterfaceIndex
        MAX-ACCESS not-accessible
        STATUS current
        DESCRIPTION
            "The ifIndex of RPR interface."
        REFERENCE
            "RFC 2863, ifIndex"
        ::= { h3cRprIpv4DynamicRSEntry 1 }

    h3cRprIpv4DynamicRSMacAddress OBJECT-TYPE
        SYNTAX MacAddress
        MAX-ACCESS not-accessible
        STATUS current
        DESCRIPTION
            "The Ipv4 MAC address of destination station on the ring."
        ::= { h3cRprIpv4DynamicRSEntry 2 }

    h3cRprIpv4DynamicRSRingletID OBJECT-TYPE
        SYNTAX H3cRprRingletID
        MAX-ACCESS read-only
        STATUS current
        DESCRIPTION
            "The identifier of the ring which frames are sent
             from the source station to the destination station."
        ::= { h3cRprIpv4DynamicRSEntry 3 }

    h3cRprIpv4DynamicRSTtl OBJECT-TYPE
        SYNTAX INTEGER
        MAX-ACCESS read-only
        STATUS current
        DESCRIPTION
            "The hops from source station to destination station by the
             selected ringlet."
        ::= { h3cRprIpv4DynamicRSEntry 4 }

-- The RPR Ipv6 dynamic ring selection table

    h3cRprIpv6DynamicRSTable OBJECT-TYPE
        SYNTAX SEQUENCE OF H3cRprIpv6DynamicRSEntry
        MAX-ACCESS not-accessible
        STATUS current
        DESCRIPTION
            "The RPR Ipv6 Dynamic Ring Selection Table that contains the Ipv6
             ring selection information by dynamic ring selection and static
             ring selection."
        ::= { h3cRprRS 3 }

    h3cRprIpv6DynamicRSEntry OBJECT-TYPE
        SYNTAX H3cRprIpv6DynamicRSEntry
        MAX-ACCESS not-accessible
        STATUS current
        DESCRIPTION
            "An entry in the RPR Ipv6 Ring Selection Table."
        INDEX { h3cRprIpv6DynamicRSIfIndex, h3cRprIpv6DynamicRSMacAddress }
        ::= { h3cRprIpv6DynamicRSTable 1 }

    H3cRprIpv6DynamicRSEntry ::=
        SEQUENCE {
            h3cRprIpv6DynamicRSIfIndex
                InterfaceIndex,
            h3cRprIpv6DynamicRSMacAddress
                MacAddress,
            h3cRprIpv6DynamicRSRingletID
                H3cRprRingletID,
            h3cRprIpv6DynamicRSTtl
                INTEGER
        }

    h3cRprIpv6DynamicRSIfIndex OBJECT-TYPE
        SYNTAX InterfaceIndex
        MAX-ACCESS not-accessible
        STATUS current
        DESCRIPTION
            "The ifIndex of RPR interface."
        REFERENCE
            "RFC 2863, ifIndex"
        ::= { h3cRprIpv6DynamicRSEntry 1 }

    h3cRprIpv6DynamicRSMacAddress OBJECT-TYPE
        SYNTAX MacAddress
        MAX-ACCESS not-accessible
        STATUS current
        DESCRIPTION
            "The Ipv6 MAC address of the destination station on the ring."
        ::= { h3cRprIpv6DynamicRSEntry 2 }

    h3cRprIpv6DynamicRSRingletID OBJECT-TYPE
        SYNTAX H3cRprRingletID
        MAX-ACCESS read-only
        STATUS current
        DESCRIPTION
            "The identifier of the ring which frames are sent
             from the source station to the destination station."
        ::= { h3cRprIpv6DynamicRSEntry 3 }

    h3cRprIpv6DynamicRSTtl OBJECT-TYPE
        SYNTAX INTEGER
        MAX-ACCESS read-only
        STATUS current
        DESCRIPTION
            "The hops from source station to destination station by selected
             ringlet."
        ::= { h3cRprIpv6DynamicRSEntry 4 }

-- The RPR Ipv4 overall ring selection table

    h3cRprIpv4OverallRSTable OBJECT-TYPE
        SYNTAX SEQUENCE OF H3cRprIpv4OverallRSEntry
        MAX-ACCESS not-accessible
        STATUS current
        DESCRIPTION
            "The RPR Ipv4 Overall Ring Selection Table that contains the
             overall and active  ring selection infomation by dynamic ring
             selection and static ring selection."
        ::= { h3cRprRS 4 }

    h3cRprIpv4OverallRSEntry OBJECT-TYPE
        SYNTAX H3cRprIpv4OverallRSEntry
        MAX-ACCESS not-accessible
        STATUS current
        DESCRIPTION
            "An entry in the RPR Overall Ring Selection Table."
        INDEX { h3cRprIpv4OverallRSIfIndex, h3cRprIpv4OverallRSMacAddress }
        ::= { h3cRprIpv4OverallRSTable 1 }

    H3cRprIpv4OverallRSEntry ::=
        SEQUENCE {
            h3cRprIpv4OverallRSIfIndex
                InterfaceIndex,
            h3cRprIpv4OverallRSMacAddress
                MacAddress,
            h3cRprIpv4OverallRSType
                INTEGER,
            h3cRprIpv4OverallRSRingletID
                H3cRprRingletID,
            h3cRprIpv4OverallRSTtl
                INTEGER
        }

    h3cRprIpv4OverallRSIfIndex OBJECT-TYPE
        SYNTAX InterfaceIndex
        MAX-ACCESS not-accessible
        STATUS current
        DESCRIPTION
            "The ifIndex of RPR interface."
        REFERENCE
            "RFC 2863, ifIndex"
        ::= { h3cRprIpv4OverallRSEntry 1 }

    h3cRprIpv4OverallRSMacAddress OBJECT-TYPE
        SYNTAX MacAddress
        MAX-ACCESS not-accessible
        STATUS current
        DESCRIPTION
            "The MAC address of the destination station on the ring."
        ::= { h3cRprIpv4OverallRSEntry 2 }

    h3cRprIpv4OverallRSType OBJECT-TYPE
        SYNTAX INTEGER {
            static(1),
            dynamic(2)
        }
        MAX-ACCESS read-only
        STATUS current
        DESCRIPTION
            "The ring selection item type indicates static or dynamic."
        ::= { h3cRprIpv4OverallRSEntry 3 }

    h3cRprIpv4OverallRSRingletID OBJECT-TYPE
        SYNTAX H3cRprRingletID
        MAX-ACCESS read-only
        STATUS current
        DESCRIPTION
            "The identifier of the ring which frames are sent
             from the source station to the destination station."
        ::= { h3cRprIpv4OverallRSEntry 4 }

    h3cRprIpv4OverallRSTtl OBJECT-TYPE
        SYNTAX INTEGER
        MAX-ACCESS read-only
        STATUS current
        DESCRIPTION
            "The hops from source station to destination station  by
             selected ringlet."
        ::= { h3cRprIpv4OverallRSEntry 5 }

-- The RPR VRRP ring selection table

    h3cRprVrrpRSTable OBJECT-TYPE
        SYNTAX SEQUENCE OF H3cRprVrrpRSEntry
        MAX-ACCESS not-accessible
        STATUS current
        DESCRIPTION
            "The RPR VRRP Ring Selection Table that contains the ring
             selection information when the vrrp group is configured."
        ::= { h3cRprRS 5 }

    h3cRprVrrpRSEntry OBJECT-TYPE
        SYNTAX H3cRprVrrpRSEntry
        MAX-ACCESS not-accessible
        STATUS current
        DESCRIPTION
            "An entry in the RPR VRRP Ring Selection Table."
        INDEX { h3cRprVrrpRSIfIndex, h3cRprVrrpRSVirtualMacAddress }
        ::= { h3cRprVrrpRSTable 1 }

    H3cRprVrrpRSEntry ::=
        SEQUENCE {
            h3cRprVrrpRSIfIndex
                InterfaceIndex,
            h3cRprVrrpRSVirtualMacAddress
                MacAddress,
            h3cRprVrrpRSMacAddress
                MacAddress,
            h3cRprVrrpRSRingletID
                H3cRprRingletID,
            h3cRprVrrpRSTtl
                INTEGER
        }

    h3cRprVrrpRSIfIndex OBJECT-TYPE
        SYNTAX InterfaceIndex
        MAX-ACCESS not-accessible
        STATUS current
        DESCRIPTION
            "The ifIndex of RPR interface."
        REFERENCE
            "RFC 2863, ifIndex"
        ::= { h3cRprVrrpRSEntry 1 }

    h3cRprVrrpRSVirtualMacAddress OBJECT-TYPE
        SYNTAX MacAddress
        MAX-ACCESS not-accessible
        STATUS current
        DESCRIPTION
            "The virtual MAC address of the staion in VRRP group."
        ::= { h3cRprVrrpRSEntry 2 }


    h3cRprVrrpRSMacAddress OBJECT-TYPE
        SYNTAX MacAddress
        MAX-ACCESS read-only
        STATUS current
        DESCRIPTION
            "The MAC address of the station that is  the master in VRRP group."
        ::= { h3cRprVrrpRSEntry 3 }

    h3cRprVrrpRSRingletID OBJECT-TYPE
        SYNTAX H3cRprRingletID
        MAX-ACCESS read-only
        STATUS current
        DESCRIPTION
            "The identifier of the ring which frames are sent
             from the source station to the destination station."
        ::= { h3cRprVrrpRSEntry 4 }

    h3cRprVrrpRSTtl OBJECT-TYPE
        SYNTAX INTEGER
        MAX-ACCESS read-only
        STATUS current
        DESCRIPTION
            "The hops from source station to destination station by
             selected ringlet."
        ::= { h3cRprVrrpRSEntry 5 }


-- The RPR default ring identifier config Table

    h3cRprDefaultRingIDTable OBJECT-TYPE
        SYNTAX SEQUENCE OF H3cRprDefaultRingIDEntry
        MAX-ACCESS not-accessible
        STATUS current
        DESCRIPTION
            "The RPR Default RingID Table specify the default ringID."
        ::= { h3cRprRS 6 }

    h3cRprDefaultRingIDEntry OBJECT-TYPE
        SYNTAX H3cRprDefaultRingIDEntry
        MAX-ACCESS not-accessible
        STATUS current
        DESCRIPTION
            "An entry in the RPR Default RingID Table."
        INDEX { h3cRprDefaultRingIDIfIndex }
        ::= { h3cRprDefaultRingIDTable 1 }

    H3cRprDefaultRingIDEntry ::=
        SEQUENCE {
            h3cRprDefaultRingIDIfIndex
                InterfaceIndex,
            h3cRprDefaultConfigRingletID
                H3cRprRingletID,
            h3cRprDefaultActiveRingID
                H3cRprRingletID
        }

    h3cRprDefaultRingIDIfIndex OBJECT-TYPE
        SYNTAX InterfaceIndex
        MAX-ACCESS not-accessible
        STATUS current
        DESCRIPTION
            "The ifIndex of RPR interface."
        REFERENCE
            "RFC 2863, ifIndex"
        ::= { h3cRprDefaultRingIDEntry 1 }

    h3cRprDefaultConfigRingletID OBJECT-TYPE
        SYNTAX H3cRprRingletID
        MAX-ACCESS read-write
        STATUS current
        DESCRIPTION
            "The default identifier of the ring configured by user."
        ::= { h3cRprDefaultRingIDEntry 2 }

    h3cRprDefaultActiveRingID OBJECT-TYPE
        SYNTAX H3cRprRingletID
        MAX-ACCESS read-only
        STATUS current
        DESCRIPTION
            "The identifier of the default ring which is active currently.
             The default ring configured by user may be inactive."
        ::= { h3cRprDefaultRingIDEntry 3 }

-- The RPR defect report table

    h3cRprDefect OBJECT IDENTIFIER ::= { h3cRprObjects 5 }

    h3cRprDefectReportTable OBJECT-TYPE
        SYNTAX SEQUENCE OF H3cRprDefectReportEntry
        MAX-ACCESS not-accessible
        STATUS current
        DESCRIPTION
            "The RPR Defect Report Table that contains the trap information on
             the ring."
        ::= { h3cRprDefect 1 }

    h3cRprDefectReportEntry OBJECT-TYPE
        SYNTAX H3cRprDefectReportEntry
        MAX-ACCESS not-accessible
        STATUS current
        DESCRIPTION
            "An entry in the RPR Defect Report Table."
        INDEX { h3cRprDefectIfIndex }
        ::= { h3cRprDefectReportTable 1 }

    H3cRprDefectReportEntry ::=
        SEQUENCE {
            h3cRprDefectIfIndex
                InterfaceIndex,
            h3cRprDefectCurrentStatus
                BITS
        }

    h3cRprDefectIfIndex OBJECT-TYPE
        SYNTAX InterfaceIndex
        MAX-ACCESS not-accessible
        STATUS current
        DESCRIPTION
            "The ifIndex of RPR interface."
        REFERENCE
            "RFC 2863, ifIndex"
        ::= { h3cRprDefectReportEntry 1 }

    h3cRprDefectCurrentStatus OBJECT-TYPE
        SYNTAX BITS {
            topologyOpenRing(0),
            topoInstability(1),
            topoInconsistent(2),
            dulpMacAddress(3),
            dulpIPAddress(4),
            lrttDefect(5),
            protCfgDefect(6),
            jumboCfgDefect(7),
            excessReservedRateDefect(8),
            excessMaxStationNum(9),
            miscabling(10),
            backPressure(11)
        }
        MAX-ACCESS read-only
        STATUS current
        DESCRIPTION
            "Indicates the current status of RPR ring.
             This attribute is used to notify the management system that
             alarms generate or clear about some RPR ring."
        REFERENCE
            "IEEE 802.17 V3.3 Subclause 11.2.9."
        ::= { h3cRprDefectReportEntry 2 }

-- The priority to RPR service class map table

    h3cRprPriorityMap OBJECT IDENTIFIER ::= { h3cRprObjects 6 }

    h3cRprPriority2ClassMapTable OBJECT-TYPE
        SYNTAX SEQUENCE OF H3cRprPriority2ClassMapEntry
        MAX-ACCESS not-accessible
        STATUS current
        DESCRIPTION
            "The Table is for Class Of Service and RPR Service Class Mapping."
        ::= { h3cRprPriorityMap 1 }

    h3cRprPriority2ClassMapEntry OBJECT-TYPE
        SYNTAX H3cRprPriority2ClassMapEntry
        MAX-ACCESS not-accessible
        STATUS current
        DESCRIPTION
            "An entry in the COS to Service Class Map Table."
        INDEX { h3cRprPriority2ClassMapIfIndex,
                h3cRprPriority2ClassMapType,
                h3cRprPriorityValue
        }
        ::= { h3cRprPriority2ClassMapTable 1 }

    H3cRprPriority2ClassMapEntry ::=
        SEQUENCE {
            h3cRprPriority2ClassMapIfIndex
                InterfaceIndex,
            h3cRprPriority2ClassMapType
                INTEGER,
            h3cRprPriorityValue
                INTEGER,
            h3cRprPriority2ClassMap
                H3cRprServiceClass
        }

    h3cRprPriority2ClassMapIfIndex OBJECT-TYPE
        SYNTAX InterfaceIndex
        MAX-ACCESS not-accessible
        STATUS current
        DESCRIPTION
            "The ifIndex of RPR interface."
        REFERENCE
            "RFC 2863, ifIndex"
        ::= { h3cRprPriority2ClassMapEntry 1 }

    h3cRprPriority2ClassMapType OBJECT-TYPE
        SYNTAX INTEGER {
            tag(1),
            mpls(2),
            ip(3)
        }
        MAX-ACCESS not-accessible
        STATUS current
        DESCRIPTION
            "The type of Priority,include tag, mpls, ip."
        ::= { h3cRprPriority2ClassMapEntry 2 }

    h3cRprPriorityValue OBJECT-TYPE
        SYNTAX INTEGER {
            pri0(1),
            pri1(2),
            pri2(3),
            pri3(4),
            pri4(5),
            pri5(6),
            pri6(7),
            pri7(8)
        }
        MAX-ACCESS not-accessible
        STATUS current
        DESCRIPTION
            "The priority of tag,mpls and ip, the value range is 0~7."
        ::= { h3cRprPriority2ClassMapEntry 3 }

    h3cRprPriority2ClassMap OBJECT-TYPE
        SYNTAX H3cRprServiceClass
        MAX-ACCESS read-write
        STATUS current
        DESCRIPTION
            "The RPR service class."
        REFERENCE
            "IEEE 802.17 V3.3 Subclause 7.3 Service class."
        ::= { h3cRprPriority2ClassMapEntry 4 }

-- The RPR rate-limit config table

    h3cRprRateLimitConfig OBJECT IDENTIFIER ::= { h3cRprObjects 7 }

    h3cRprRateLimitConfigTable  OBJECT-TYPE
        SYNTAX SEQUENCE OF H3cRprRateLimitConfigEntry
        MAX-ACCESS not-accessible
        STATUS current
        DESCRIPTION
            "The RPR Rate Limit Configuration Table that contains the rate
             limit infomation of RPR serviec class."
        ::= { h3cRprRateLimitConfig 1 }

    h3cRprRateLimitConfigEntry  OBJECT-TYPE
        SYNTAX H3cRprRateLimitConfigEntry
        MAX-ACCESS not-accessible
        STATUS current
        DESCRIPTION
            "An entry in the RPR Rate Limit Configuration Table."
        INDEX { h3cRprRateLimitConfigIfIndex,
                h3cRprRateLimitConfigRingletId,
                h3cRprRateLimitConfigServiceClass
        }
        ::= { h3cRprRateLimitConfigTable 1 }

    H3cRprRateLimitConfigEntry  ::=
        SEQUENCE {
            h3cRprRateLimitConfigIfIndex
                InterfaceIndex,
            h3cRprRateLimitConfigRingletId
                H3cRprRingletID,
            h3cRprRateLimitConfigServiceClass
                H3cRprServiceClass,
            h3cRprRateLimitConfigValue
                Integer32
        }

    h3cRprRateLimitConfigIfIndex OBJECT-TYPE
        SYNTAX InterfaceIndex
        MAX-ACCESS not-accessible
        STATUS current
        DESCRIPTION
            "The ifIndex of RPR interface."
        REFERENCE
            "RFC 2863, ifIndex"
        ::= { h3cRprRateLimitConfigEntry 1 }

    h3cRprRateLimitConfigRingletId OBJECT-TYPE
        SYNTAX H3cRprRingletID
        MAX-ACCESS not-accessible
        STATUS current
        DESCRIPTION
            "The identifier of the ring of RPR ringlet."
        ::= { h3cRprRateLimitConfigEntry 2 }

    h3cRprRateLimitConfigServiceClass OBJECT-TYPE
        SYNTAX H3cRprServiceClass
        MAX-ACCESS not-accessible
        STATUS current
        DESCRIPTION
            "The RPR service class."
        REFERENCE
            "IEEE 802.17 V3.3 Subclause 7.3 Service class."
        ::= { h3cRprRateLimitConfigEntry 3 }

    h3cRprRateLimitConfigValue OBJECT-TYPE
        SYNTAX Integer32
        MAX-ACCESS read-write
        STATUS current
        DESCRIPTION
            "The value of rate-limit that configured for diffrent service class.
             The unit is permillage."
        ::= { h3cRprRateLimitConfigEntry 4 }

-- The RPR mac address learning config table

    h3cRprMacAddrLearn  OBJECT IDENTIFIER ::= { h3cRprObjects 8 }

    h3cRprMacLearnCfgTable OBJECT-TYPE
        SYNTAX SEQUENCE OF H3cRprMacLearnCfgEntry
        MAX-ACCESS not-accessible
        STATUS current
        DESCRIPTION
            "The RPR MAC Address Table."
        ::= { h3cRprMacAddrLearn 1 }

    h3cRprMacLearnCfgEntry OBJECT-TYPE
        SYNTAX H3cRprMacLearnCfgEntry
        MAX-ACCESS not-accessible
        STATUS current
        DESCRIPTION
            "The entry of RPR MAC Address Table."
        INDEX { h3cRprMacLearnIfIndex, h3cRprMacLearnRprMac }
        ::= { h3cRprMacLearnCfgTable 1 }

    H3cRprMacLearnCfgEntry ::=
        SEQUENCE {
            h3cRprMacLearnIfIndex
                InterfaceIndex,
            h3cRprMacLearnRprMac
                MacAddress,
            h3cRprMacLearnType
                INTEGER,
            h3cRprMacLearnDestMac
                MacAddress,
            h3cRprMacLearnVlanId
                Integer32,
            h3cRprMacLearnRinglet
                H3cRprRingletID,
            h3cRprMacLearnTtl
                INTEGER,
            h3cRprMacLearnIsValid
                TruthValue,
            h3cRprMacLearnRowStatus
                RowStatus
        }

    h3cRprMacLearnIfIndex OBJECT-TYPE
        SYNTAX InterfaceIndex
        MAX-ACCESS not-accessible
        STATUS current
        DESCRIPTION
            "The ifIndex of RPR interface."
        REFERENCE
            "RFC 2863, ifIndex"
        ::= { h3cRprMacLearnCfgEntry 1 }

    h3cRprMacLearnRprMac OBJECT-TYPE
        SYNTAX MacAddress
        MAX-ACCESS not-accessible
        STATUS current
        DESCRIPTION
            "The MAC address of the RPR station."
        ::= { h3cRprMacLearnCfgEntry 2 }

    h3cRprMacLearnType OBJECT-TYPE
        SYNTAX INTEGER
        MAX-ACCESS read-create
        STATUS current
        DESCRIPTION
            "The type of MAC address item that the user built. The type
             includes static and dynamic."
        ::= { h3cRprMacLearnCfgEntry 3 }

    h3cRprMacLearnDestMac OBJECT-TYPE
        SYNTAX MacAddress
        MAX-ACCESS read-create
        STATUS current
        DESCRIPTION
            "The destination of MAC address."
        ::= { h3cRprMacLearnCfgEntry 4 }

    h3cRprMacLearnVlanId OBJECT-TYPE
        SYNTAX Integer32 (1..4094)
        MAX-ACCESS read-create
        STATUS current
        DESCRIPTION
            "The vlan ID that the MAC address learned from by RPR staion."
        ::= { h3cRprMacLearnCfgEntry 5 }

    h3cRprMacLearnRinglet OBJECT-TYPE
        SYNTAX H3cRprRingletID
        MAX-ACCESS read-create
        STATUS current
        DESCRIPTION
            "The identifier of the ring which frames are sent
             from the source station to the destination station."
        ::= { h3cRprMacLearnCfgEntry 6 }

    h3cRprMacLearnTtl OBJECT-TYPE
        SYNTAX INTEGER
        MAX-ACCESS read-only
        STATUS current
        DESCRIPTION
            "The hops from source station to destination station on the
             selected ringlet."
        ::= { h3cRprMacLearnCfgEntry 7 }

    h3cRprMacLearnIsValid OBJECT-TYPE
        SYNTAX TruthValue
        MAX-ACCESS read-only
        STATUS current
        DESCRIPTION
            "The flag identify whether the configured mac address is valid.
             If it is true, the configured mac address is valid,
             otherwise it's invalid."
        ::= { h3cRprMacLearnCfgEntry 8 }

    h3cRprMacLearnRowStatus OBJECT-TYPE
        SYNTAX RowStatus
        MAX-ACCESS read-create
        STATUS current
        DESCRIPTION
            "The status of this table entry.
             The status includes createAndGo, active and destroy."
        ::= { h3cRprMacLearnCfgEntry 9 }

-- The RPR table for trap

    h3cRprTrapVar OBJECT IDENTIFIER ::= { h3cRprObjects 9 }

    h3cRprTrapVarTable OBJECT-TYPE
        SYNTAX SEQUENCE OF H3cRprTrapVarEntry
        MAX-ACCESS not-accessible
        STATUS current
        DESCRIPTION
            "The RPR Defect Report Table that contains varible that
             used to bind in trap."
        ::= { h3cRprTrapVar 1 }

    h3cRprTrapVarEntry OBJECT-TYPE
        SYNTAX H3cRprTrapVarEntry
        MAX-ACCESS not-accessible
        STATUS current
        DESCRIPTION
            "An entry in the RPR Trap Var Table."
        INDEX { h3cRprTrapIfIndex }
        ::= { h3cRprTrapVarTable 1 }

    H3cRprTrapVarEntry ::=
        SEQUENCE {
            h3cRprTrapIfIndex
                InterfaceIndex,
            h3cRprTrapRinglet
                H3cRprRingletID,
            h3cRprTrapTopoMacAddress
                MacAddress,
            h3cRprTrapIpAddress
                InetAddress
        }

    h3cRprTrapIfIndex OBJECT-TYPE
        SYNTAX InterfaceIndex
        MAX-ACCESS accessible-for-notify
        STATUS current
        DESCRIPTION
            "The ifIndex of RPR interface. It is only used for trap to bind."
        REFERENCE
            "RFC 2863, ifIndex"
        ::= { h3cRprTrapVarEntry 1 }

     h3cRprTrapRinglet OBJECT-TYPE
        SYNTAX H3cRprRingletID
        MAX-ACCESS accessible-for-notify
        STATUS current
        DESCRIPTION
            "The span of RPR station. It is only used for trap to bind."
        ::= { h3cRprTrapVarEntry 2 }

     h3cRprTrapTopoMacAddress OBJECT-TYPE
        SYNTAX MacAddress
        MAX-ACCESS accessible-for-notify
        STATUS current
        DESCRIPTION
            "The MAC address of RPR station. It is only used for trap to bind."
        ::= { h3cRprTrapVarEntry 3 }

    h3cRprTrapIpAddress OBJECT-TYPE
        SYNTAX InetAddress
        MAX-ACCESS accessible-for-notify
        STATUS current
        DESCRIPTION
            "The IP address of RPR station. It is only used for trap to bind."
        ::= { h3cRprTrapVarEntry 4 }


-- The RPR Traps

    h3cRprTrap  OBJECT IDENTIFIER ::= { h3cRprObjects 10 }

    h3cRprTopologyOpenRing NOTIFICATION-TYPE
        OBJECTS { h3cRprTrapIfIndex, h3cRprTrapRinglet }
        STATUS  current
        DESCRIPTION
            "The topology openRing trap indicates that the RPR ring is opened."
        REFERENCE
            "IEEE 802.17 Subclause 3.2.77 open ring."
        ::= { h3cRprTrap 1 }

    h3cRprTopologyCloseRing NOTIFICATION-TYPE
        OBJECTS { h3cRprTrapIfIndex, h3cRprTrapRinglet }
        STATUS  current
        DESCRIPTION
            "The topology openRing trap indicates that the RPR ring is closed."
        REFERENCE
            "IEEE 802.17 Subclause 3.2.77 close ring."
        ::= { h3cRprTrap 2 }

    h3cRprTopologyInconsistent NOTIFICATION-TYPE
        OBJECTS { h3cRprTrapIfIndex }
        STATUS  current
        DESCRIPTION
            "The topology inconsistent trap indicates that the topology of
             RPR is inconsistent."
        REFERENCE
            "IEEE 802.17 Subclause 11.6.6.1 topology consistency."
        ::= { h3cRprTrap 3 }

    h3cRprTopologyInstability NOTIFICATION-TYPE
        OBJECTS { h3cRprTrapIfIndex }
        STATUS  current
        DESCRIPTION
            "The topology instability trap indicates that the topology of
             RPR is instability."
        ::= { h3cRprTrap 4 }


    h3cRprDuplicateMacAddress NOTIFICATION-TYPE
        OBJECTS { h3cRprTrapIfIndex, h3cRprTrapTopoMacAddress }
        STATUS  current
        DESCRIPTION
            "The duplicate MAC address trap indicates that the mac address
             of the station on the ring is dulplicate. That means there is the
             same MAC address between two stations on the ring."
        ::= { h3cRprTrap 5 }

    h3cRprDulplicateIPAddress NOTIFICATION-TYPE
        OBJECTS { h3cRprTrapIfIndex, h3cRprTrapIpAddress }
        STATUS  current
        DESCRIPTION
            "The dulplicate IP address trap indicates that the IP address of
             the station on the ring is dulplicate. That means there is the same
             IP address between two stations on the ring."
        ::= { h3cRprTrap 6 }

    h3cRprIncompleteLRTT NOTIFICATION-TYPE
        OBJECTS { h3cRprTrapIfIndex }
        STATUS  current
        DESCRIPTION
            "The incomplete LRTT trap indicates that LRTT is not completed."
        ::= { h3cRprTrap 7 }

    h3cRprProtecConfigInconsistent NOTIFICATION-TYPE
        OBJECTS { h3cRprTrapIfIndex }
        STATUS  current
        DESCRIPTION
            "The protection configuration inconsistent trap indicates that
             the configuration of protection mode on the ring is inconsistent.
             That is one station is configured steer mode while the other is
             configured wrap mode."
        ::= { h3cRprTrap 8 }

    h3cRprJumboConfigInconsistent NOTIFICATION-TYPE
        OBJECTS { h3cRprTrapIfIndex }
        STATUS  current
        DESCRIPTION
            "The jumbo configuration inconsistent trap indicates that the
             configuration of jumbo mode on the ring is inconsistent.
             That is one station supports jumbo frame while the other
             doesn't support jumbo frame."
        ::= { h3cRprTrap 9 }

    h3cRprExceedMaxReservRate NOTIFICATION-TYPE
        OBJECTS { h3cRprTrapIfIndex,h3cRprTrapRinglet }
        STATUS  current
        DESCRIPTION
            "The exceeded max reserved rate trap indicates that the rate
             on the ringlet exceeded the max reserved rate. The operator can
             configure reserved rate for every station, but the sum of all
             stations' reserved rate of each RPR ringlet can't exceed maximum."
        ::= { h3cRprTrap 10 }

    h3cRprExceedMaxStationNum NOTIFICATION-TYPE
        OBJECTS { h3cRprTrapIfIndex }
        STATUS  current
        DESCRIPTION
            "The exceeded max station number trap indicates that the number
             of the stations on the ring exceeded the max station number."
        ::= { h3cRprTrap 11 }

    h3cRprMiscabling NOTIFICATION-TYPE
        OBJECTS { h3cRprTrapIfIndex,h3cRprTrapRinglet }
        STATUS  current
        DESCRIPTION
            "The miscabling trap indicates that the miscabling event occurred."
        REFERENCE
            "IEEE 802.17 V3.0 Subclause 11.9.2.1 miscabling defect."
        ::= { h3cRprTrap 12 }

    h3cRprBackPressure NOTIFICATION-TYPE
        OBJECTS { h3cRprTrapIfIndex, h3cRprTrapRinglet, h3cRprPriority2ClassMap }
        STATUS  current
        DESCRIPTION
            "The back pressure trap indicates that the backpressure is generated
             on the ringlet. That is the data flow on the ringlet exceeded
             the range of rate-limit configured."
        ::= { h3cRprTrap 13 }

    h3cRprBackPressureOver NOTIFICATION-TYPE
        OBJECTS { h3cRprTrapIfIndex, h3cRprTrapRinglet, h3cRprPriority2ClassMap }
        STATUS  current
        DESCRIPTION
            "The back pressure over trap indicates that the backpressure is
             disappeared on the ringlet."
        ::= { h3cRprTrap 14 }

END
