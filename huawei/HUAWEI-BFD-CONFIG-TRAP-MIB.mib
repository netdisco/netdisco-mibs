--
-- HUAWEI-BFD-CONFIG-TRAP-MIB.mib
-- Copyright (C) 2012-2019 by HUAWEI TECHNOLOGIES. All rights reserved
-- Tuesday, November 05, 2019 at 17:45:00
-- Version: V2.03

	HUAWEI-BFD-CONFIG-TRAP-MIB DEFINITIONS ::= BEGIN
 
		IMPORTS
			entPhysicalName			
				FROM ENTITY-MIB			
			hwDatacomm			
				FROM HUAWEI-MIB
			InetAddress, InetPortNumber, InetAddressType, InetAddressPrefixLength			
				FROM INET-ADDRESS-MIB			
			OBJECT-GROUP, MODULE-COMPLIANCE, NOTIFICATION-GROUP			
				FROM SNMPv2-CONF			
			Unsigned32, Integer32,OBJECT-TYPE, MODULE-IDENTITY, NOTIFICATION-TYPE			
				FROM SNMPv2-SMI;
	
	
		hwBfdConfigTrapMIB MODULE-IDENTITY 
			LAST-UPDATED  "201911051745Z"		-- November 05, 2019 at 17:45 GMT
			ORGANIZATION 
				"Huawei Technologies Co.,Ltd."
			CONTACT-INFO 
                                "Huawei Industrial Base
                                  Bantian, Longgang
                                   Shenzhen 518129
                                   People's Republic of China
                                   Website: http://www.huawei.com
                                   Email: support@huawei.com
                                 "
			DESCRIPTION 
				"The private mib file includes the alarm  
				information of FEI reported."
                                                          REVISION "201911051745Z"		-- November 05, 2019 at 17:45 GMT
			DESCRIPTION
				"ver 2.03"
                                                          REVISION "201801121745Z"		-- January 12, 2018 at 17:45 GMT
			DESCRIPTION
				"ver 2.02"
                                                         REVISION "201706131440Z"		-- June 13, 2017 at 14:40 GMT
			DESCRIPTION
				"ver 2.01"
			REVISION "201203152024Z"		-- March 15, 2012 at 20:24 GMT
			DESCRIPTION
				"ver 1.0"
			::= { hwDatacomm 228 }
		
	
	
--
-- Node definitions
--
	
		-- 1.3.6.1.4.1.2011.5.25.228.1
		hwBfdConfigTrapObject OBJECT IDENTIFIER ::= { hwBfdConfigTrapMIB 1 }
		
		-- 1.3.6.1.4.1.2011.5.25.228.1.1
		hwBfdConfigIpAddress OBJECT-TYPE
			SYNTAX InetAddress
			MAX-ACCESS accessible-for-notify
			STATUS current
			DESCRIPTION
				"This object indicates the IP address to which the BFD session is bound to."
			::= { hwBfdConfigTrapObject 1 }
				
		-- 1.3.6.1.4.1.2011.5.25.228.1.2
		hwBfdConfigReasonId OBJECT-TYPE
			SYNTAX INTEGER
				{
				bfdIncorrectConfig(1)
				}
			MAX-ACCESS accessible-for-notify
			STATUS current
			DESCRIPTION
				"This object indicates the alarm reason ID."
			::= { hwBfdConfigTrapObject 2 }

		-- 1.3.6.1.4.1.2011.5.25.228.1.3
		hwBfdConfigLocalDis OBJECT-TYPE
                                                          SYNTAX Integer32 (1..16383)
			MAX-ACCESS accessible-for-notify
			STATUS current
			DESCRIPTION
				"This object indicates the BFD local discriminator."
			::= { hwBfdConfigTrapObject 3 }
		
		-- 1.3.6.1.4.1.2011.5.25.228.2
		hwBfdConfigTraps OBJECT IDENTIFIER ::= { hwBfdConfigTrapMIB 2 }
		
		-- 1.3.6.1.4.1.2011.5.25.228.2.1
		hwBfdConfigIncorrectTrap OBJECT IDENTIFIER ::= { hwBfdConfigTraps 1 }
		
		-- 1.3.6.1.4.1.2011.5.25.228.2.1.1
		hwWholeBfdConfigWrong NOTIFICATION-TYPE
			OBJECTS { hwBfdConfigIpAddress, hwBfdConfigReasonId }
			STATUS current
			DESCRIPTION 
				"This object indicates an alarm generated for BFD configuration errors."
			::= { hwBfdConfigIncorrectTrap 1 }
		
		-- 1.3.6.1.4.1.2011.5.25.228.2.1.2
		hwWholeBfdConfigWrongResume NOTIFICATION-TYPE
			OBJECTS { hwBfdConfigIpAddress, hwBfdConfigReasonId }
			STATUS current
			DESCRIPTION 
				"This object indicates that an alarm generated for BFD configuration errors is cleared."
			::= { hwBfdConfigIncorrectTrap 2 }

		-- 1.3.6.1.4.1.2011.5.25.228.2.1.3
		hwBfdConfigIntervalShort NOTIFICATION-TYPE
			OBJECTS {hwBfdConfigLocalDis }
			STATUS current
			DESCRIPTION 
				"This object indicates that an alarm generated for too small interval for receiving or sending BFD packets."
			::= { hwBfdConfigIncorrectTrap 3 }
				
		-- 1.3.6.1.4.1.2011.5.25.228.3
		hwBfdConfigTrapConformance OBJECT IDENTIFIER ::= { hwBfdConfigTrapMIB 3 }
		
		-- 1.3.6.1.4.1.2011.5.25.228.3.1
		hwBfdConfigTrapCompliances OBJECT IDENTIFIER ::= { hwBfdConfigTrapConformance 1 }
		
		-- 1.3.6.1.4.1.2011.5.25.228.3.1.1
		hwBfdConfigTrapCompliance MODULE-COMPLIANCE
			STATUS current
			DESCRIPTION 
				"Compliance statement for agents that provide full support for hwBaseTrapMIB."
			MODULE -- this module
				MANDATORY-GROUPS { hwBfdConfigObjectGroup }
			::= { hwBfdConfigTrapCompliances 1 }
		
		-- 1.3.6.1.4.1.2011.5.25.228.3.2
		hwBfdConfigTrapGroups OBJECT IDENTIFIER ::= { hwBfdConfigTrapConformance 2 }
		
		-- 1.3.6.1.4.1.2011.5.25.228.3.2.1
		hwBfdConfigObjectGroup OBJECT-GROUP
			OBJECTS { hwBfdConfigIpAddress, hwBfdConfigReasonId }
			STATUS current
			DESCRIPTION 
				"Group for base trap objects."
			::= { hwBfdConfigTrapGroups 1 }
		
		-- 1.3.6.1.4.1.2011.5.25.228.3.2.2
		hwBfdConfigTrapGroup NOTIFICATION-GROUP
			NOTIFICATIONS { hwWholeBfdConfigWrong, hwWholeBfdConfigWrongResume }
			STATUS current
			DESCRIPTION 
				"Group for all base traps."
			::= { hwBfdConfigTrapGroups 2 }
		
	
	END

--
-- HUAWEI-BFD-CONFIG-TRAP-MIB.mib
--
