-- =================================================================
-- Copyright (c) 2004-2009 Hangzhou H3C Tech. Co., Ltd. All rights reserved.
--
-- Description:  DHCP Server MIB
-- Reference:   H3C Enterprise MIB
-- Version:     V1.0 Created by y04444 Initial version
-- History:
-- V1.0 Initial version
-- =================================================================
H3C-DHCP-SERVER-MIB DEFINITIONS ::= BEGIN
IMPORTS
    h3cCommon
        FROM HUAWEI-3COM-OID-MIB
    OBJECT-TYPE, NOTIFICATION-TYPE, MODULE-IDENTITY, Integer32
        FROM SNMPv2-SMI;

h3cDHCPServer MODULE-IDENTITY
    LAST-UPDATED "200905060000Z"            -- May 06th, 2009 at 00:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "The MIB module is used for DHCP server."
    REVISION    "200905060000Z"
    DESCRIPTION
        "Initial version"
    ::= { h3cCommon 101 }

--
-- Define the DHCP Server GLOBAL.
--
    h3cDHCPServerObjects OBJECT IDENTIFIER ::= { h3cDHCPServer 1 }

    h3cDHCPServerIPPoolUsage OBJECT-TYPE
        SYNTAX      Integer32
        MAX-ACCESS  read-only
        STATUS      current
        DESCRIPTION
            "Usage factor of DHCP server ip pool."
        ::= { h3cDHCPServerObjects 1 }

    h3cDHCPServerReqTimes OBJECT-TYPE
        SYNTAX      Integer32
        MAX-ACCESS  read-only
        STATUS      current
        DESCRIPTION
            "Number of requests received by the DHCP server."
        ::= { h3cDHCPServerObjects 2 }

    h3cDHCPServerReqSuccessTimes OBJECT-TYPE
        SYNTAX      Integer32
        MAX-ACCESS  read-only
        STATUS      current
        DESCRIPTION
            "Number of requests success responses sent by the DHCP server."
        ::= { h3cDHCPServerObjects 3 }

--
-- Define the DHCP Server Tables.
--
    h3cDHCPServerTables OBJECT IDENTIFIER ::= { h3cDHCPServer 2 }

    h3cDHCPServerPoolName OBJECT-TYPE
        SYNTAX      OCTET STRING(SIZE(0..255))
        MAX-ACCESS  accessible-for-notify
        STATUS      current
        DESCRIPTION
            "DHCP server pool name."
        ::= { h3cDHCPServerTables 1 }

--
-- Define the DHCP Server Traps.
--
    h3cDHCPServerTraps OBJECT IDENTIFIER ::= { h3cDHCPServer 3 }

    h3cDHCPServerTrapPrefix OBJECT IDENTIFIER ::= { h3cDHCPServerTraps 0 }

    h3cDHCPServerAddrExhaust NOTIFICATION-TYPE
        OBJECTS
        {
            h3cDHCPServerPoolName
        }
        STATUS      current
        DESCRIPTION
            "This trap is generated when the device DHCP server address
            exhaust."
        ::= { h3cDHCPServerTrapPrefix 1 }

    h3cDHCPServerAddrExhaustRecover NOTIFICATION-TYPE
        OBJECTS
        {
            h3cDHCPServerPoolName
        }
        STATUS      current
        DESCRIPTION
            "This trap is generated when the device DHCP server address
            exhaust recover."
        ::= { h3cDHCPServerTrapPrefix 2 }

END
