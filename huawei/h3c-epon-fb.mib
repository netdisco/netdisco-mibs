-- ===========================================================
-- Copyright (C) 2007 by  H3C TECHNOLOGIES. All rights reserved.
--
-- Description:
-- The information of EPON fiber backup.
-- Reference:
-- Version: V1.0
-- History:
-- V1.0 created by zhaodan.
-- Initial version for h3cEponFBMibObjects of h3cEpon.
-- ===========================================================
H3C-EPON-FB-MIB DEFINITIONS ::= BEGIN

IMPORTS
        h3cEpon
    FROM HUAWEI-3COM-OID-MIB
        Integer32, OBJECT-TYPE, MODULE-IDENTITY
    FROM SNMPv2-SMI
        RowStatus
    FROM SNMPv2-TC;


h3cEponFBMibObjects MODULE-IDENTITY
    LAST-UPDATED "200711271008Z"
    ORGANIZATION
        "Hangzhou H3C Technologies Co., Ltd."
    CONTACT-INFO
        "Platform Team H3C Technologies Co., Ltd.
         Hai-Dian District Beijing P.R. China
         Http://www.h3c.com
         Zip:100085"
    DESCRIPTION
        "
        The objects in this MIB module are used to manage and
        display current configuration of fiber backup groups
        based on EPON OLT port.
        "
    ::= { h3cEpon 6 }

h3cEponFBMIB OBJECT IDENTIFIER ::= { h3cEponFBMibObjects 1 }
--
-- h3cEponFBMIBTable
--

h3cEponFBMIBTable OBJECT-TYPE
    SYNTAX      SEQUENCE OF H3cEponFBMIBEntry
    MAX-ACCESS  not-accessible
    STATUS      current
    DESCRIPTION
        "This table defines several optical fiber-backup system parameters."
    ::= { h3cEponFBMIB  1 }

h3cEponFBMIBEntry OBJECT-TYPE
    SYNTAX      H3cEponFBMIBEntry
    MAX-ACCESS  not-accessible
    STATUS      current
    DESCRIPTION
        "The entry of h3cEponFBMIBTable."
    INDEX
        {
            h3cEponFBGroupIndex
        }
    ::= { h3cEponFBMIBTable 1}


H3cEponFBMIBEntry ::= SEQUENCE
    {
        h3cEponFBGroupIndex          Integer32,
        h3cEponFBGroupRowStatus      RowStatus,
        h3cEponFBMasterPort          Integer32,
        h3cEponFBSlavePort           Integer32,
        h3cEponFBMasterPortStatus    INTEGER,
        h3cEponFBSlavePortStatus     INTEGER,
        h3cEponFBSwitchover          INTEGER
    }

h3cEponFBGroupIndex OBJECT-TYPE
    SYNTAX      Integer32
    MAX-ACCESS  not-accessible
    STATUS      current
    DESCRIPTION
        "The EPON fiber-backup group ID."
    ::= { h3cEponFBMIBEntry 1 }

h3cEponFBGroupRowStatus OBJECT-TYPE
    SYNTAX      RowStatus
    MAX-ACCESS  read-create
    STATUS      current
    DESCRIPTION
        "This object allows entry to be created and deleted
        from the h3cEponFBMIBTable."
    ::= { h3cEponFBMIBEntry 2 }

h3cEponFBMasterPort OBJECT-TYPE
    SYNTAX      Integer32
    MAX-ACCESS  read-create
    STATUS      current
    DESCRIPTION
        "OLT port ifindex of the fiber-backup group.
        Use it to set or get the group master port."
    ::= { h3cEponFBMIBEntry 3 }

h3cEponFBSlavePort OBJECT-TYPE
    SYNTAX      Integer32
    MAX-ACCESS  read-create
    STATUS      current
    DESCRIPTION
        "OLT port ifindex of the fiber-backup group.
        Use it to set or get the group slave port.
        h3cEponFBSlavePort must be set after h3cEponFBMasterPort.
        "
    ::= { h3cEponFBMIBEntry 4 }

h3cEponFBMasterPortStatus OBJECT-TYPE
    SYNTAX      INTEGER
        {
            active(1),
            down(2)
        }
    MAX-ACCESS  read-only
    STATUS      current
    DESCRIPTION
        "The master port status of the fiber-backup group.
        The active state indicates that the port's role is master, the olt chip is right
        and the optical module is inserted.
        The down state indicates others conditions."
    ::= { h3cEponFBMIBEntry 5 }

h3cEponFBSlavePortStatus OBJECT-TYPE
    SYNTAX      INTEGER
        {
            ready(1),
            down(2)
        }
    MAX-ACCESS  read-only
    STATUS      current
    DESCRIPTION
        "The slave port status of the fiber-backup group.
        The ready state indicates that the port's role is slave, the olt chip is right
        and optical module is inserted.
        The down state indicates others conditions."
    ::= { h3cEponFBMIBEntry 6 }

h3cEponFBSwitchover OBJECT-TYPE
    SYNTAX      INTEGER
        {
            false(1),
            true(2)
        }
    MAX-ACCESS  read-create
    STATUS      current
    DESCRIPTION
        "Switch the fiber backup group's two port manually.
        The group must has two ports
        and the value of h3cEponFBSlavePortStatus must be ready before Switchover.
        after Switchover the port's role will be changed.
        The value true is for switch-over.  The default value is false."
    ::= { h3cEponFBMIBEntry 7 }

END
