-- =================================================================
-- Copyright (C) 1996-2002 by  HUAWEI TECHNOLOGIES. All rights reserved.
--
-- Description:Huawei QOS MIB
-- Reference:HUAWEI Enterprise MIB
-- Version: V2.4
-- History:
--   V1.0
--	 6th Mar 2004
--   Initial version
--   v1.1
--       1.Add mpls(2) to qosPqlProName's SYNTAX INTEGER
--       2.Add exp(8)  to qosPqlProQueKey's SYNTAX INTEGER
--       3.Add mpls(2) to qosCqlProName's SYNTAX INTEGER
--       4.Add exp(8)  to qosCqlProQueKey's SYNTAX INTEGER
--       7th Aug 2004
--   v1.2
--       1.Change MODULE name from HUAWEI-QOS-MIB to HUAWEI-IF-QOS-MIB
--       2.Change the old node name from "huawei-qos" to "hwIfQoSMib"
--       3.Change qosPqlProQueKey's "exp(8)" to "exp-mask(8)"
--       4.Modify qosPqlProQueKeyValue's DESCRIPTION
--       5.Change qosCqlProQueKey's "exp(8)" to "exp-mask(8)"
--       6.Modify qosCqlProQueKeyValue's DESCRIPTION
--       7.Modify the range of qosCARListNum to "SYNTAX INTEGER (0..199|2000..3999)"
--       8.Add "remark-mplsexp-continue(6)" and "remark-mplsexp-pass(7)" to qosCARConformAction
--       9.Add "remark-mplsexp-continue(6)" and "remark-mplsexp-pass(7)" to qosCARExceedAction
--       10.Modify the range of qosGTSACLNum to "SYNTAX INTEGER (0..199|2000..3999)"
--       11.Add qosIfBandwidthTable
--       12.Add qosRTPIfApplyTable
--       13.Add qosRTPIfQueueRunInfoTable
--       27th Aug 2004 changed by yuhui
--  V2.0 2004-10-12 updated by gaolong
--       Import from SNMPv2-SMI instead from RFC-1212.
--       Add hwIfQoSMib MODULE-IDENTITY clause.
--       Change ACCESS clauses to MAX-ACCESS.
--       Change STATUS clauses from mandatory to current.
--       Remove chinese characters.
--       Change Counter to Counter32.
--       Change MAX-ACCESS clause value of qosIfBandwidthIfIndex to not-accessible
--       because this is an index object.
--       Change MAX-ACCESS clause value of qosIFBandwidthMaxBW and qosIFBandwidthMaxReservedBWPct
--       from read-write to read-create according to RFC2578.
--  V2.1 2004-11-18 updated by wanghao
--       1.Add dscp-mask(3) to qosCarlParaType's SYNTAX INTEGER
--       2.Fix syntax bugs and adjust format of the whole file.
--  V2.2 2005-2-22 updated by wanghao
--       1.Add qosWFQQueueType to qosWFQTable
--       2.Change index syntax from read-only to not-accessible by tangshun
--  V2.3 2005-7-5 updated by gaolong
--       1.Modify SYNTAX of qosGTSIfName
--  V2.4 2006-03-02 updated by huguohua
--       1.Remove the value range of qosCARCIR, qosCARBurstSize and qosCARExcessBurstSize
--       2.Remove the value range of qosGTSCIR, qosGTSBurstSize and qosGTSExcessBurstSize
--       3.Remove the value range of qosLRCIR, qosLRBurstSize and qosLRExcessBurstSize
--       4.Remove the value range of qosRTPIfApplyCbs
-- =================================================================
HUAWEI-IF-QOS-MIB DEFINITIONS ::= BEGIN

IMPORTS
        hwQoS
                FROM HUAWEI-3COM-OID-MIB
        OBJECT-TYPE, MODULE-IDENTITY, Integer32, Counter32
                FROM SNMPv2-SMI
        RowStatus
                FROM SNMPv2-TC;

--  Node definitions
--

            hwIfQoSMib MODULE-IDENTITY
                    LAST-UPDATED "200410110000Z"            -- OCT 11, 2004 at 00:00 GMT
                    ORGANIZATION
                            "Huawei Technologies Co. Ltd."
                    CONTACT-INFO
                            " R&D Beijing, Huawei Technologies Co. Ltd.
                            Huawei Bld.,NO.3 Xinxi Rd.,
                            Shang-Di Information Industry Base,
                            Hai-Dian District Beijing P.R. China
                            Zip:100085
                            Http://www.huawei.com
                            E-mail:support@huawei.com "
                    DESCRIPTION
                            " "
                    ::= { hwQoS 2 }

--  HUAWEI QOS config group

--  qos fifo 1
                qosFIFOTable OBJECT-TYPE
                        SYNTAX SEQUENCE OF QosFIFOEntry
                        MAX-ACCESS not-accessible
                        STATUS current
                        DESCRIPTION
                                "FIFO(First In First Out) queuing table"
                        ::= { hwIfQoSMib 1 }


                qosFIFOEntry OBJECT-TYPE
                        SYNTAX QosFIFOEntry
                        MAX-ACCESS not-accessible
                        STATUS current
                        DESCRIPTION
                                "FIFO configuration and running information Command:qos fifo queue-length"
                        INDEX { qosFIFOIfIndex }
                        ::= { qosFIFOTable 1 }


                QosFIFOEntry ::=
                        SEQUENCE {
                                qosFIFOIfIndex
                                        INTEGER,
                                qosFIFOIfName
                                        OCTET STRING,
                                qosFIFOMaxQueueLen
                                        INTEGER,
                                qosFIFOCurQueueLen
                                        INTEGER,
                                qosFIFODiscardPkt
                                        Counter32,
                                qosUndoFIFO
                                        INTEGER
                         }

                qosFIFOIfIndex OBJECT-TYPE
                        SYNTAX INTEGER
                        MAX-ACCESS not-accessible
                        STATUS current
                        DESCRIPTION
                                "The index of interface."
                        ::= { qosFIFOEntry 1 }


                qosFIFOIfName OBJECT-TYPE
                        SYNTAX OCTET STRING
                        MAX-ACCESS read-only
                        STATUS current
                        DESCRIPTION
                                "The description of interface."
                        ::= { qosFIFOEntry 2 }


                qosFIFOMaxQueueLen OBJECT-TYPE
                        SYNTAX INTEGER (1..1024)
                        MAX-ACCESS read-write
                        STATUS current
                        DESCRIPTION
                                "The maximum length of fifo queue."
                        ::= { qosFIFOEntry 3 }


                qosFIFOCurQueueLen OBJECT-TYPE
                        SYNTAX INTEGER
                        MAX-ACCESS read-only
                        STATUS current
                        DESCRIPTION
                                "The current length of queue."
                        ::= { qosFIFOEntry 4 }


                qosFIFODiscardPkt OBJECT-TYPE
                        SYNTAX Counter32
                        MAX-ACCESS read-only
                        STATUS current
                        DESCRIPTION
                                "The discarded packet number of queue."
                        ::= { qosFIFOEntry 5 }


                qosUndoFIFO OBJECT-TYPE
                        SYNTAX INTEGER
                                {
                                qosFIFO(0),
                                qosNoFIFO(1)
                                }
                        MAX-ACCESS read-write
                        STATUS current
                        DESCRIPTION
                                "
                                0: Only for get.
                                1: Set default value of the maximum length of fifo queue.
                                "
                        ::= { qosFIFOEntry 6 }

-- qos pql default-queue 2
--         ListNum                        1-16
--         QueueType                        0-3        corresponding top、middle、normal、bottom
--         UndoPqlDefault                     1
-- ListNum is index
                qosPqlDefaultTable OBJECT-TYPE
                        SYNTAX SEQUENCE OF QosPqlDefaultEntry
                        MAX-ACCESS not-accessible
                        STATUS current
                        DESCRIPTION
                                "PQL(Priority Queue List) default-queue table"
                        ::= { hwIfQoSMib 2 }


                qosPqlDefaultEntry OBJECT-TYPE
                        SYNTAX QosPqlDefaultEntry
                        MAX-ACCESS not-accessible
                        STATUS current
                        DESCRIPTION
                                "PQL default-queue configuration information."
                        INDEX { qosPqlDefaultListNum }
                        ::= { qosPqlDefaultTable 1 }


                QosPqlDefaultEntry ::=
                        SEQUENCE {
                                qosPqlDefaultListNum
                                        INTEGER,
                                qosPqlDefaultQueueType
                                        INTEGER,
                                qosUndoPqlDefault
                                        INTEGER
                         }

                qosPqlDefaultListNum OBJECT-TYPE
                        SYNTAX INTEGER (1..16)
                        MAX-ACCESS not-accessible
                        STATUS current
                        DESCRIPTION
                                "The index of table, which is the PQL number."
                        ::= { qosPqlDefaultEntry 1 }


                qosPqlDefaultQueueType OBJECT-TYPE
                        SYNTAX INTEGER
                                {
                                top(0),
                                middle(1),
                                normal(2),
                                bottom(3)
                                }
                        MAX-ACCESS read-write
                        STATUS current
                        DESCRIPTION
                                "The type of default priority queue, the default value is normal."
                        DEFVAL { 2 }
                        ::= { qosPqlDefaultEntry 2 }

                qosUndoPqlDefault OBJECT-TYPE
                        SYNTAX INTEGER
                                {
                                qosPqlDefault(0),
                                qosNoPqlDefault(1)
                                }
                        MAX-ACCESS read-write
                        STATUS current
                        DESCRIPTION
                                "
                                0: Only for get.
                                1: Set default value of the defualt priority queue.
                                "
                        ::= { qosPqlDefaultEntry 3 }


-- qos pql queue-length  3
--         ListNum                        1-16
--         QueueType                        0-3        corresponding top、middle、normal、bottom
--         QueLenValue                        1-1024
--         UndoPqlQueLen                        1
-- ListNum and QueueType is index
                qosPqlQueueLenTable OBJECT-TYPE
                        SYNTAX SEQUENCE OF QosPqlQueueLenEntry
                        MAX-ACCESS not-accessible
                        STATUS current
                        DESCRIPTION
                                "PQL(Priority Queue List) queue-length table"
                        ::= { hwIfQoSMib 3 }

                qosPqlQueueLenEntry OBJECT-TYPE
                        SYNTAX QosPqlQueueLenEntry
                        MAX-ACCESS not-accessible
                        STATUS current
                        DESCRIPTION
                                "PQL queue-length configuration information."
                        INDEX { qosPqlQueLenListNum, qosPqlQueLenQueueType }
                        ::= { qosPqlQueueLenTable 1 }

                QosPqlQueueLenEntry ::=
                        SEQUENCE {
                                qosPqlQueLenListNum
                                        INTEGER,
                                qosPqlQueLenQueueType
                                        INTEGER,
                                qosPqlQueLenValue
                                        INTEGER,
                                qosUndoPqlQueLen
                                        INTEGER
                         }

                qosPqlQueLenListNum OBJECT-TYPE
                        SYNTAX INTEGER (1..16)
                        MAX-ACCESS not-accessible
                        STATUS current
                        DESCRIPTION
                                "The index of table, which is the PQL number."
                        ::= { qosPqlQueueLenEntry 1 }


                qosPqlQueLenQueueType OBJECT-TYPE
                        SYNTAX INTEGER
                                {
                                top(0),
                                middle(1),
                                normal(2),
                                bottom(3)
                                }
                        MAX-ACCESS not-accessible
                        STATUS current
                        DESCRIPTION
                                "The index of table, which is the type of priority queue."
                        ::= { qosPqlQueueLenEntry 2 }


                qosPqlQueLenValue OBJECT-TYPE
                        SYNTAX INTEGER (1..1024)
                        MAX-ACCESS read-write
                        STATUS current
                        DESCRIPTION
                                "The maximum length of specified queue."
                        ::= { qosPqlQueueLenEntry 3 }


                qosUndoPqlQueLen OBJECT-TYPE
                        SYNTAX INTEGER
                                {
                                qosPqlQueLen(0),
                                qosNoPqlQueLen(1)
                                }
                        MAX-ACCESS read-write
                        STATUS current
                        DESCRIPTION
                                "
                                0: Only for get.
                                1: Set default value of the maximum length of specified queue.
                                "
                        ::= { qosPqlQueueLenEntry 4 }


--  qos pql inbound-interface        4
-- ListNum                        1-16
-- IfIndex                        interface index
-- IfName                        (read-only）
-- QueueType                        0-3 corresponding top、middle、normal、bottom
-- UndoPqlIf                        1
-- ListNum and IfIndex are the index of the table
                qosPqlIfTable OBJECT-TYPE
                        SYNTAX SEQUENCE OF QosPqlIfEntry
                        MAX-ACCESS not-accessible
                        STATUS current
                        DESCRIPTION
                                "PQL(Priority Queue List) inbound-interface table"
                        ::= { hwIfQoSMib 4 }


                qosPqlIfEntry OBJECT-TYPE
                        SYNTAX QosPqlIfEntry
                        MAX-ACCESS not-accessible
                        STATUS current
                        DESCRIPTION
                                "PQL inbound-interface configuration information."
                        INDEX { qosPqlIfListNum, qosPqlIfIndex }
                        ::= { qosPqlIfTable 1 }


                QosPqlIfEntry ::=
                        SEQUENCE {
                                qosPqlIfListNum
                                        INTEGER,
                                qosPqlIfIndex
                                        INTEGER,
                                qosPqlIfName
                                        OCTET STRING,
                                qosPqlIfQueueType
                                        INTEGER,
                                qosUndoPqlIf
                                        INTEGER
                         }

                qosPqlIfListNum OBJECT-TYPE
                        SYNTAX INTEGER
                        MAX-ACCESS not-accessible
                        STATUS current
                        DESCRIPTION
                                "The index of table, which is the PQL number."
                        ::= { qosPqlIfEntry 1 }


                qosPqlIfIndex OBJECT-TYPE
                        SYNTAX INTEGER
                        MAX-ACCESS not-accessible
                        STATUS current
                        DESCRIPTION
                                "The index of table, which is the index of interface."
                        ::= { qosPqlIfEntry 2 }


                qosPqlIfName OBJECT-TYPE
                        SYNTAX OCTET STRING
                        MAX-ACCESS read-only
                        STATUS current
                        DESCRIPTION
                                "The description of interface."
                        ::= { qosPqlIfEntry 3 }


                qosPqlIfQueueType OBJECT-TYPE
                        SYNTAX INTEGER
                                {
                                top(0),
                                middle(1),
                                normal(2),
                                bottom(3)
                                }
                        MAX-ACCESS read-write
                        STATUS current
                        DESCRIPTION
                                "The type of priority queue."
                        ::= { qosPqlIfEntry 4 }


                qosUndoPqlIf OBJECT-TYPE
                        SYNTAX INTEGER
                                {
                                qosPqlIF(0),
                                qosNoPqlIF(1)
                                }
                        MAX-ACCESS read-write
                        STATUS current
                        DESCRIPTION
                                "
                                0: Only for get.
                                1: delete the corresponding inbound-interface rule of the specified PQL number
                                "
                        ::= { qosPqlIfEntry 5 }


--  qos pql protocol        5
                qosPqlProtocolTable OBJECT-TYPE
                        SYNTAX SEQUENCE OF QosPqlProtocolEntry
                        MAX-ACCESS not-accessible
                        STATUS current
                        DESCRIPTION
                                "PQL(Priority Queue List) protocol table"
                        ::= { hwIfQoSMib 5 }


                qosPqlProtocolEntry OBJECT-TYPE
                        SYNTAX QosPqlProtocolEntry
                        MAX-ACCESS not-accessible
                        STATUS current
                        DESCRIPTION
                                "PQL protocol configuration information."
                        INDEX { qosPqlProListNum, qosPqlProName, qosPqlProQueKey, qosPqlProQueKeyValue }
                        ::= { qosPqlProtocolTable 1 }


                QosPqlProtocolEntry ::=
                        SEQUENCE {
                                qosPqlProListNum
                                        INTEGER,
                                qosPqlProName
                                        INTEGER,
                                qosPqlProQueKey
                                        INTEGER,
                                qosPqlProQueKeyValue
                                        INTEGER,
                                qosPqlProQueType
                                        INTEGER,
                                qosUndoPqlProtocol
                                        INTEGER
                         }

                qosPqlProListNum OBJECT-TYPE
                        SYNTAX INTEGER
                        MAX-ACCESS not-accessible
                        STATUS current
                        DESCRIPTION
                                "The index of table, which is the PQL number."
                        ::= { qosPqlProtocolEntry 1 }


                qosPqlProName OBJECT-TYPE
                        SYNTAX INTEGER { ip(1),mpls(2) }
                        MAX-ACCESS not-accessible
                        STATUS current
                        DESCRIPTION
                                "The index of table, which is the protocol name. Only IP supported currently."
                        ::= { qosPqlProtocolEntry 2 }


                qosPqlProQueKey OBJECT-TYPE
                        SYNTAX INTEGER
                                {
                                null(1),
                                fragment(2),
                                acl(3),
                                less-than(4),
                                greater-than(5),
                                tcp(6),
                                udp(7),
                                exp-mask(8)
                                }
                        MAX-ACCESS not-accessible
                        STATUS current
                        DESCRIPTION
                                "The index of table, which is the key words of traffic-classify rule."
                        ::= { qosPqlProtocolEntry 3 }


                qosPqlProQueKeyValue OBJECT-TYPE
                        SYNTAX INTEGER (0..65535)
                        MAX-ACCESS not-accessible
                        STATUS current
                        DESCRIPTION
                                "
                                The index of table, which is the value of key words.
                                for greater-than,less-than,tcp,udp:0~65535
                                for acl:2000~3999
                                for NULL and fragment: null
                                for exp-mask: 1~255"
                        ::= { qosPqlProtocolEntry 4 }


                qosPqlProQueType OBJECT-TYPE
                        SYNTAX INTEGER
                                {
                                top(0),
                                middle(1),
                                normal(2),
                                bottom(3)
                                }
                        MAX-ACCESS read-write
                        STATUS current
                        DESCRIPTION
                                "The type of priority queue. "
                        ::= { qosPqlProtocolEntry 5 }


                qosUndoPqlProtocol OBJECT-TYPE
                        SYNTAX INTEGER
                                {
                                qosPqlProtocol(0),
                                qosNoPqlProtocol(1)
                                }
                        MAX-ACCESS read-write
                        STATUS current
                        DESCRIPTION
                                "
                                0: Only for get.
                                1: delete the corresponding protocol rule of the specified PQL number
                                "
                        ::= { qosPqlProtocolEntry 6 }

--  qos pq / display qos pq interface   6
                qosPQTable OBJECT-TYPE
                        SYNTAX SEQUENCE OF QosPQEntry
                        MAX-ACCESS not-accessible
                        STATUS current
                        DESCRIPTION
                                "PQ(Priority Queuing) table"
                        ::= { hwIfQoSMib 6 }


                qosPQEntry OBJECT-TYPE
                        SYNTAX QosPQEntry
                        MAX-ACCESS not-accessible
                        STATUS current
                        DESCRIPTION
                                "PQ configuration and running infomation"
                        INDEX { qosPQIfIndex }
                        ::= { qosPQTable 1 }


                QosPQEntry ::=
                        SEQUENCE {
                                qosPQIfIndex
                                        INTEGER,
                                qosPQListNum
                                        INTEGER,
                                qosPQIfName
                                        OCTET STRING,
                                qosPQTopPkt
                                        INTEGER,
                                qosPQTopDiscard
                                        Counter32,
                                qosPQTopMaxQueLen
                                        INTEGER,
                                qosPQMiddlePkt
                                        INTEGER,
                                qosPQMiddleDiscard
                                        Counter32,
                                qosPQMiddleMaxQueLen
                                        INTEGER,
                                qosPQNormalPkt
                                        INTEGER,
                                qosPQNormalDiscard
                                        Counter32,
                                qosPQNormalMaxQueLen
                                        INTEGER,
                                qosPQBottomPkt
                                        INTEGER,
                                qosPQBottomDiscard
                                        Counter32,
                                qosPQBottomMaxQueLen
                                        INTEGER,
                                qosUndoPQ
                                        INTEGER
                         }

                qosPQIfIndex OBJECT-TYPE
                        SYNTAX INTEGER
                        MAX-ACCESS not-accessible
                        STATUS current
                        DESCRIPTION
                                "The index of table, which is the index of interface."
                        ::= { qosPQEntry 1 }


                qosPQListNum OBJECT-TYPE
                        SYNTAX INTEGER (1..16)
                        MAX-ACCESS read-write
                        STATUS current
                        DESCRIPTION
                                "The PQL number."
                        ::= { qosPQEntry 2 }


                qosPQIfName OBJECT-TYPE
                        SYNTAX OCTET STRING
                        MAX-ACCESS read-only
                        STATUS current
                        DESCRIPTION
                                "The description of the interface."
                        ::= { qosPQEntry 3 }


                qosPQTopPkt OBJECT-TYPE
                        SYNTAX INTEGER (0..32767)
                        MAX-ACCESS read-only
                        STATUS current
                        DESCRIPTION
                                "The number of packets in the top priority queue."
                        ::= { qosPQEntry 4 }


                qosPQTopDiscard OBJECT-TYPE
                        SYNTAX Counter32
                        MAX-ACCESS read-only
                        STATUS current
                        DESCRIPTION
                                "The number of discarded packets in top priority queue."
                        ::= { qosPQEntry 5 }


                qosPQTopMaxQueLen OBJECT-TYPE
                        SYNTAX INTEGER (1..1024)
                        MAX-ACCESS read-only
                        STATUS current
                        DESCRIPTION
                                "The max length of top priority queue."
                        ::= { qosPQEntry 6 }


                qosPQMiddlePkt OBJECT-TYPE
                        SYNTAX INTEGER (0..32767)
                        MAX-ACCESS read-only
                        STATUS current
                        DESCRIPTION
                                "The number of packets in the middle priority queue."
                        ::= { qosPQEntry 7 }


                qosPQMiddleDiscard OBJECT-TYPE
                        SYNTAX Counter32
                        MAX-ACCESS read-only
                        STATUS current
                        DESCRIPTION
                                "The number of discarded packets in middle priority queue."
                        ::= { qosPQEntry 8 }


                qosPQMiddleMaxQueLen OBJECT-TYPE
                        SYNTAX INTEGER (1..1024)
                        MAX-ACCESS read-only
                        STATUS current
                        DESCRIPTION
                                "The max length of middle priority queue."
                        ::= { qosPQEntry 9 }


                qosPQNormalPkt OBJECT-TYPE
                        SYNTAX INTEGER (0..32767)
                        MAX-ACCESS read-only
                        STATUS current
                        DESCRIPTION
                                "The number of packets in the  normal priority queue."
                        ::= { qosPQEntry 10 }


                qosPQNormalDiscard OBJECT-TYPE
                        SYNTAX Counter32
                        MAX-ACCESS read-only
                        STATUS current
                        DESCRIPTION
                                "The number of discarded packets in normal priority queue."
                        ::= { qosPQEntry 11 }


                qosPQNormalMaxQueLen OBJECT-TYPE
                        SYNTAX INTEGER (1..1024)
                        MAX-ACCESS read-only
                        STATUS current
                        DESCRIPTION
                                "The max length of normal priority queue."
                        ::= { qosPQEntry 12 }


                qosPQBottomPkt OBJECT-TYPE
                        SYNTAX INTEGER (0..32767)
                        MAX-ACCESS read-only
                        STATUS current
                        DESCRIPTION
                                "The number of packets in the bottom priority queue."
                        ::= { qosPQEntry 13 }


                qosPQBottomDiscard OBJECT-TYPE
                        SYNTAX Counter32
                        MAX-ACCESS read-only
                        STATUS current
                        DESCRIPTION
                                "The number of discarded packets in bottom priority queue."
                        ::= { qosPQEntry 14 }


                qosPQBottomMaxQueLen OBJECT-TYPE
                        SYNTAX INTEGER (1..1024)
                        MAX-ACCESS read-only
                        STATUS current
                        DESCRIPTION
                                "The max length of bottom priority queue."
                        ::= { qosPQEntry 15 }


                qosUndoPQ OBJECT-TYPE
                        SYNTAX INTEGER
                                {
                                qosPQ(0),
                                qosNoPQ(1)
                                }
                        MAX-ACCESS read-write
                        STATUS current
                        DESCRIPTION
                                "
                                0:Only for get.
                                1:Set the default queuing on interface: FIFO.
                                "
                        ::= { qosPQEntry 16 }


-- qos cql default-queue 7
--         ListNum                        1-16
--         QueueNum                0-16
--         UndoCqlDefault                1
-- ListNum is index
                qosCqlDefaultTable OBJECT-TYPE
                        SYNTAX SEQUENCE OF QosCqlDefaultEntry
                        MAX-ACCESS not-accessible
                        STATUS current
                        DESCRIPTION
                                "CQL(Custom Queue List) default-queue table"
                        ::= { hwIfQoSMib 7 }


                qosCqlDefaultEntry OBJECT-TYPE
                        SYNTAX QosCqlDefaultEntry
                        MAX-ACCESS not-accessible
                        STATUS current
                        DESCRIPTION
                                "CQL default-queue configuration information."
                        INDEX { qosCqlListNum }
                        ::= { qosCqlDefaultTable 1 }


                QosCqlDefaultEntry ::=
                        SEQUENCE {
                                qosCqlListNum
                                        INTEGER,
                                qosCqlQueueNum
                                        INTEGER,
                                qosUndoCqlDefault
                                        INTEGER
                         }

                qosCqlListNum OBJECT-TYPE
                        SYNTAX INTEGER (1..16)
                        MAX-ACCESS not-accessible
                        STATUS current
                        DESCRIPTION
                                "The index of table, which is the CQL number."
                        ::= { qosCqlDefaultEntry 1 }


                qosCqlQueueNum OBJECT-TYPE
                        SYNTAX INTEGER (0..16)
                        MAX-ACCESS read-write
                        STATUS current
                        DESCRIPTION
                                "The queue number(0~16)"
                        DEFVAL { 1 }
                        ::= { qosCqlDefaultEntry 2 }


                qosUndoCqlDefault OBJECT-TYPE
                        SYNTAX INTEGER
                                {
                                qosCqlDefault(0),
                                qosNoCqlDefault(1)
                                }
                        MAX-ACCESS read-write
                        STATUS current
                        DESCRIPTION
                                "
                                0: Only for get.
                                1: Set default value of the defualt custom queue.
                                "
                        ::= { qosCqlDefaultEntry 3 }


--  qos cql inbound-interface   8
-- ListNum                        1-16
-- IfIndex                        index of interface
-- IfName                        (read-only）
-- QueueNum                        0-16
-- UndoCqlIf                1
-- GroupNum and IfIndex are index.
                qosCqlIfTable OBJECT-TYPE
                        SYNTAX SEQUENCE OF QosCqlIfEntry
                        MAX-ACCESS not-accessible
                        STATUS current
                        DESCRIPTION
                                "CQL(Custom Queue List) inbound-interface table"
                        ::= { hwIfQoSMib 8 }


                qosCqlIfEntry OBJECT-TYPE
                        SYNTAX QosCqlIfEntry
                        MAX-ACCESS not-accessible
                        STATUS current
                        DESCRIPTION
                                "CQL inbound-interface configuration information."
                        INDEX { qosCqlIfListNum, qosCqlIfIndex }
                        ::= { qosCqlIfTable 1 }


                QosCqlIfEntry ::=
                        SEQUENCE {
                                qosCqlIfListNum
                                        INTEGER,
                                qosCqlIfIndex
                                        INTEGER,
                                qosCqlIfName
                                        OCTET STRING,
                                qosCqlIfQueueNum
                                        INTEGER,
                                qosUndoCqlIf
                                        INTEGER
                         }

                qosCqlIfListNum OBJECT-TYPE
                        SYNTAX INTEGER
                        MAX-ACCESS not-accessible
                        STATUS current
                        DESCRIPTION
                                "The index of table, which is the CQL number."
                        ::= { qosCqlIfEntry 1 }


                qosCqlIfIndex OBJECT-TYPE
                        SYNTAX INTEGER
                        MAX-ACCESS not-accessible
                        STATUS current
                        DESCRIPTION
                                "The index of interface."
                        ::= { qosCqlIfEntry 2 }


                qosCqlIfName OBJECT-TYPE
                        SYNTAX OCTET STRING
                        MAX-ACCESS read-only
                        STATUS current
                        DESCRIPTION
                                "The description of interface."
                        ::= { qosCqlIfEntry 3 }


                qosCqlIfQueueNum OBJECT-TYPE
                        SYNTAX INTEGER (0..16)
                        MAX-ACCESS read-write
                        STATUS current
                        DESCRIPTION
                                "The queue number(0~16)"
                        DEFVAL { 1 }
                        ::= { qosCqlIfEntry 4 }


                qosUndoCqlIf OBJECT-TYPE
                        SYNTAX INTEGER
                                {
                                qosCqlIf(0),
                                qosNoCqlIf(1)
                                }
                        MAX-ACCESS read-write
                        STATUS current
                        DESCRIPTION
                                "
                                0: Only for get.
                                1: delete the corresponding inbound-interface rule of the specified CQL number
                                "
                        ::= { qosCqlIfEntry 5 }


--  qos cql protocol   9
                qosCqlProtocolTable OBJECT-TYPE
                        SYNTAX SEQUENCE OF QosCqlProtocolEntry
                        MAX-ACCESS not-accessible
                        STATUS current
                        DESCRIPTION
                                "CQL(Custom Queue List) protocol table"
                        ::= { hwIfQoSMib 9 }


                qosCqlProtocolEntry OBJECT-TYPE
                        SYNTAX QosCqlProtocolEntry
                        MAX-ACCESS not-accessible
                        STATUS current
                        DESCRIPTION
                                "CQL protocol configuration information."
                        INDEX { qosCqlProListNum, qosCqlProName, qosCqlProQueKey, qosCqlProQueKeyValue }
                        ::= { qosCqlProtocolTable 1 }


                QosCqlProtocolEntry ::=
                        SEQUENCE {
                                qosCqlProListNum
                                        INTEGER,
                                qosCqlProName
                                        INTEGER,
                                qosCqlProQueKey
                                        INTEGER,
                                qosCqlProQueKeyValue
                                        INTEGER,
                                qosCqlProQueNum
                                        INTEGER,
                                qosUndoCqlProtocol
                                        INTEGER
                         }

                qosCqlProListNum OBJECT-TYPE
                        SYNTAX INTEGER
                        MAX-ACCESS not-accessible
                        STATUS current
                        DESCRIPTION
                                "The index of table, which is the CQL number."
                        ::= { qosCqlProtocolEntry 1 }


                qosCqlProName OBJECT-TYPE
                        SYNTAX INTEGER { ip(1),mpls(2) }
                        MAX-ACCESS not-accessible
                        STATUS current
                        DESCRIPTION
                                "The index of table, which is the protocol name. Only IP supported currently."
                        ::= { qosCqlProtocolEntry 2 }


                qosCqlProQueKey OBJECT-TYPE
                        SYNTAX INTEGER
                                {
                                null(1),
                                fragment(2),
                                acl(3),
                                less-than(4),
                                greater-than(5),
                                tcp(6),
                                udp(7),
                                exp-mask(8)
                                }
                        MAX-ACCESS not-accessible
                        STATUS current
                        DESCRIPTION
                                "The index of table, which is the key words of traffic-classify rule."
                        ::= { qosCqlProtocolEntry 3 }


                qosCqlProQueKeyValue OBJECT-TYPE
                        SYNTAX INTEGER (0..65535)
                        MAX-ACCESS not-accessible
                        STATUS current
                        DESCRIPTION
                                "
                                The index of table, which is the value of key words.
                                for greater-than,less-than,tcp,udp:0~65535
                                for acl:2000~3999
                                for NULL and fragment: null
                                for exp-mask: 0~255 "
                        ::= { qosCqlProtocolEntry 4 }


                qosCqlProQueNum OBJECT-TYPE
                        SYNTAX INTEGER (0..16)
                        MAX-ACCESS read-write
                        STATUS current
                        DESCRIPTION
                                "The queue number."
                        ::= { qosCqlProtocolEntry 5 }


                qosUndoCqlProtocol OBJECT-TYPE
                        SYNTAX INTEGER
                                {
                                qosCqlProtocol(0),
                                qosNoCqlProtocol(1)
                                }
                        MAX-ACCESS read-write
                        STATUS current
                        DESCRIPTION
                                "
                                0: Only for get.
                                1: delete the corresponding protocol rule of the specified CQL number
                                "
                        ::= { qosCqlProtocolEntry 6 }


--  qos cql serving/queue-length   10
                qosCqlQueParaTable OBJECT-TYPE
                        SYNTAX SEQUENCE OF QosCqlQueParaEntry
                        MAX-ACCESS not-accessible
                        STATUS current
                        DESCRIPTION
                                "CQL(Custom Queue List) serving/queue-length table"
                        ::= { hwIfQoSMib 10 }


                qosCqlQueParaEntry OBJECT-TYPE
                        SYNTAX QosCqlQueParaEntry
                        MAX-ACCESS not-accessible
                        STATUS current
                        DESCRIPTION
                                "CQL serving/queue-length configuration information."
                        INDEX { qosCqlQueParaListNum, qosCqlQueParaQueNum }
                        ::= { qosCqlQueParaTable  1 }


                QosCqlQueParaEntry ::=
                        SEQUENCE {
                                qosCqlQueParaListNum
                                        INTEGER,
                                qosCqlQueParaQueNum
                                        INTEGER,
                                qosCqlQueParaServing
                                        INTEGER,
                                qosCqlQueParaMaxQueLen
                                        INTEGER,
                                qosUndoCqlQueParaServing
                                        INTEGER,
                                qosUndoCqlQueParaMaxQueLen
                                        INTEGER
                         }

                qosCqlQueParaListNum OBJECT-TYPE
                        SYNTAX INTEGER
                        MAX-ACCESS not-accessible
                        STATUS current
                        DESCRIPTION
                                "The index of table, which is the CQL number."
                        ::= { qosCqlQueParaEntry 1 }


                qosCqlQueParaQueNum OBJECT-TYPE
                        SYNTAX INTEGER (0..16)
                        MAX-ACCESS not-accessible
                        STATUS current
                        DESCRIPTION
                                "The index of table, which is the queue number."
                        ::= { qosCqlQueParaEntry 2 }


                qosCqlQueParaServing OBJECT-TYPE
                        SYNTAX INTEGER (1..16777215)
                        MAX-ACCESS read-write
                        STATUS current
                        DESCRIPTION
                                "The maximum bytes that the specified queue can transmit in each turn"
                        DEFVAL { 1500 }
                        ::= { qosCqlQueParaEntry 3 }


                qosCqlQueParaMaxQueLen OBJECT-TYPE
                        SYNTAX INTEGER (1..1024)
                        MAX-ACCESS read-write
                        STATUS current
                        DESCRIPTION
                                "The maximum length of the specified queue."
                        DEFVAL { 20 }
                        ::= { qosCqlQueParaEntry 4 }


                qosUndoCqlQueParaServing OBJECT-TYPE
                        SYNTAX INTEGER
                                {
                                qosCqlQueParaServing(0),
                                qosNoCqlQueParaServing(1)
                                }
                        MAX-ACCESS read-write
                        STATUS current
                        DESCRIPTION
                                "
                                0: Only for get.
                                1: Set the defualt value of the maximum bytes 
                                   that the specified queue can transmit in each turn.
                                "
                        ::= { qosCqlQueParaEntry 5 }


                qosUndoCqlQueParaMaxQueLen OBJECT-TYPE
                        SYNTAX INTEGER
                                {
                                qosCqlQueParaMaxQueLen(0),
                                qosNoCqlQueParaMaxQueLen(1)
                                }
                        MAX-ACCESS read-write
                        STATUS current
                        DESCRIPTION
                                "
                                0: Only for get.
                                1: Set the defualt value of the maximum length of the specified queue.
                                "
                        ::= { qosCqlQueParaEntry 6 }


--  qos cq   11
                qosCQTable OBJECT-TYPE
                        SYNTAX SEQUENCE OF QosCQEntry
                        MAX-ACCESS not-accessible
                        STATUS current
                        DESCRIPTION
                                "CQ(Custom Queuing) table"
                        ::= { hwIfQoSMib 11 }


                qosCQEntry OBJECT-TYPE
                        SYNTAX QosCQEntry
                        MAX-ACCESS not-accessible
                        STATUS current
                        DESCRIPTION
                                "CQ configuration infomation"
                        INDEX { qosCQIfIndex }
                        ::= { qosCQTable 1 }


                QosCQEntry ::=
                        SEQUENCE {
                                qosCQIfIndex
                                        INTEGER,
                                qosCQListNum
                                        INTEGER,
                                qosCQIfName
                                        OCTET STRING,
                                qosUndoCQ
                                        INTEGER
                         }

                qosCQIfIndex OBJECT-TYPE
                        SYNTAX INTEGER
                        MAX-ACCESS not-accessible
                        STATUS current
                        DESCRIPTION
                                "The index of table, which is the index of interface."
                        ::= { qosCQEntry 1 }


                qosCQListNum OBJECT-TYPE
                        SYNTAX INTEGER (1..16)
                        MAX-ACCESS read-write
                        STATUS current
                        DESCRIPTION
                                "the CQL number."
                        ::= { qosCQEntry 2 }


                qosCQIfName OBJECT-TYPE
                        SYNTAX OCTET STRING
                        MAX-ACCESS read-only
                        STATUS current
                        DESCRIPTION
                                "The description of interface."
                        ::= { qosCQEntry 3 }


                qosUndoCQ OBJECT-TYPE
                        SYNTAX INTEGER
                                {
                                qosCQ(0),
                                qosNoCQ(1)
                                }
                        MAX-ACCESS read-write
                        STATUS current
                        DESCRIPTION
                                "
                                0:Only for get.
                                1:Set the default queuing on interface: FIFO
                                "
                        ::= { qosCQEntry 4 }


--  display qos cq interface   12
                qosCQRunInfoTable OBJECT-TYPE
                        SYNTAX SEQUENCE OF QosCQRunInfoEntry
                        MAX-ACCESS not-accessible
                        STATUS current
                        DESCRIPTION
                                "CQ(Custom Queuing) statistics table"
                        ::= { hwIfQoSMib 12 }


                qosCQRunInfoEntry OBJECT-TYPE
                        SYNTAX QosCQRunInfoEntry
                        MAX-ACCESS not-accessible
                        STATUS current
                        DESCRIPTION
                                "CQ running infomation"
                        INDEX { qosCQRunInfoIfIndex, qosCQRunInfoQueNum }
                        ::= { qosCQRunInfoTable 1 }


                QosCQRunInfoEntry ::=
                        SEQUENCE {
                                qosCQRunInfoIfIndex
                                        INTEGER,
                                qosCQRunInfoQueNum
                                        INTEGER,
                                qosCQRunInfoIfName
                                        OCTET STRING,
                                qosCQRunInfoQuePkt
                                        INTEGER,
                                qosCQRunInfoQueDiscard
                                        Counter32,
                                qosCQRunInfoMaxQueLen
                                        INTEGER
                         }

                qosCQRunInfoIfIndex OBJECT-TYPE
                        SYNTAX INTEGER
                        MAX-ACCESS not-accessible
                        STATUS current
                        DESCRIPTION
                                "The index of the table, which is the index of interface."
                        ::= { qosCQRunInfoEntry 1 }


                qosCQRunInfoQueNum OBJECT-TYPE
                        SYNTAX INTEGER (0..16)
                        MAX-ACCESS not-accessible
                        STATUS current
                        DESCRIPTION
                                "The index of the table, which is the queue number"
                        ::= { qosCQRunInfoEntry 2 }


                qosCQRunInfoIfName OBJECT-TYPE
                        SYNTAX OCTET STRING
                        MAX-ACCESS read-only
                        STATUS current
                        DESCRIPTION
                                "The description of interface."
                        ::= { qosCQRunInfoEntry 3 }


                qosCQRunInfoQuePkt OBJECT-TYPE
                        SYNTAX INTEGER (0..32767)
                        MAX-ACCESS read-only
                        STATUS current
                        DESCRIPTION
                                "The number of packets in the specified queue."
                        ::= { qosCQRunInfoEntry 4 }


                qosCQRunInfoQueDiscard OBJECT-TYPE
                        SYNTAX Counter32
                        MAX-ACCESS read-only
                        STATUS current
                        DESCRIPTION
                                "The number of discarded packets of the specified queue."
                        ::= { qosCQRunInfoEntry 5 }


                qosCQRunInfoMaxQueLen OBJECT-TYPE
                        SYNTAX INTEGER (1..1024)
                        MAX-ACCESS read-only
                        STATUS current
                        DESCRIPTION
                                "The maximum length of the specified queue."
                        ::= { qosCQRunInfoEntry 6 }


--  qos wfq / display qos wfq interface  13
                qosWFQTable OBJECT-TYPE
                        SYNTAX SEQUENCE OF QosWFQEntry
                        MAX-ACCESS not-accessible
                        STATUS current
                        DESCRIPTION
                                "WFQ(Weighted Fair Queueing) table"
                        ::= { hwIfQoSMib 13 }


                qosWFQEntry OBJECT-TYPE
                        SYNTAX QosWFQEntry
                        MAX-ACCESS not-accessible
                        STATUS current
                        DESCRIPTION
                                "WFQ configuration and running infomation"
                        INDEX { qosWFQIfIndex }
                        ::= { qosWFQTable 1 }


                QosWFQEntry ::=
                        SEQUENCE {
                                qosWFQIfIndex
                                        INTEGER,
                                qosWFQIfName
                                        OCTET STRING,
                                qosWFQMaxQueLen
                                        INTEGER,
                                qosWFQTotalQueNum
                                        INTEGER,
                                qosWFQCurQueLen
                                        INTEGER,
                                qosWFQTotalDiscard
                                        Counter32,
                                qosWFQActiveQueNum
                                        INTEGER,
                                qosWFQMaxActiveQueNum
                                        INTEGER,
                                qosUndoWFQ
                                        INTEGER,
                                qosWFQQueueType
                                        INTEGER
                         }

                qosWFQIfIndex OBJECT-TYPE
                        SYNTAX INTEGER
                        MAX-ACCESS not-accessible
                        STATUS current
                        DESCRIPTION
                                "The index of the table, which is the index of interface."
                        ::= { qosWFQEntry 1 }


                qosWFQIfName OBJECT-TYPE
                        SYNTAX OCTET STRING
                        MAX-ACCESS read-only
                        STATUS current
                        DESCRIPTION
                                "The description of interface."
                        ::= { qosWFQEntry 2 }


                qosWFQMaxQueLen OBJECT-TYPE
                        SYNTAX INTEGER (1..1024)
                        MAX-ACCESS read-write
                        STATUS current
                        DESCRIPTION
                                "The maximum length of the queue."
                        ::= { qosWFQEntry 3 }


                qosWFQTotalQueNum OBJECT-TYPE
                        SYNTAX INTEGER
                                {
                                a16(16),
                                a32(32),
                                a64(64),
                                a128(128),
                                a256(256),
                                a512(512),
                                a1024(1024),
                                a2048(2048),
                                a4096(4096)
                                }
                        MAX-ACCESS read-write
                        STATUS current
                        DESCRIPTION
                                "The total number of queues."
                        ::= { qosWFQEntry 4 }


                qosWFQCurQueLen OBJECT-TYPE
                        SYNTAX INTEGER
                        MAX-ACCESS read-only
                        STATUS current
                        DESCRIPTION
                                "The number of packets in all the queues."
                        ::= { qosWFQEntry 5 }


                qosWFQTotalDiscard OBJECT-TYPE
                        SYNTAX Counter32
                        MAX-ACCESS read-only
                        STATUS current
                        DESCRIPTION
                                "The number of discarded packets in all the queues."
                        ::= { qosWFQEntry 6 }


                qosWFQActiveQueNum OBJECT-TYPE
                        SYNTAX INTEGER (0..32767)
                        MAX-ACCESS read-only
                        STATUS current
                        DESCRIPTION
                                "The number of active queues."
                        ::= { qosWFQEntry 7 }


                qosWFQMaxActiveQueNum OBJECT-TYPE
                        SYNTAX INTEGER (0..32767)
                        MAX-ACCESS read-only
                        STATUS current
                        DESCRIPTION
                                "The maximum number of active queues."
                        ::= { qosWFQEntry 8 }


                qosUndoWFQ OBJECT-TYPE
                        SYNTAX INTEGER
                                {
                                qosWFQ(0),
                                qosNoWFQ(1)
                                }
                        MAX-ACCESS read-write
                        STATUS current
                        DESCRIPTION
                                "
                                0:Only for get.
                                1:Set the default queuing on interface: FIFO
                                "
                        ::= { qosWFQEntry 9 }

                qosWFQQueueType OBJECT-TYPE
                        SYNTAX INTEGER
                                {
                                ip-precedence(1),
                                dscp(2)
                                }
                        MAX-ACCESS read-write
                        STATUS current
                        DESCRIPTION
                                "
                                1: hashed by ip precedence
                                2: hashed by dscp
                                "
                        ::= { qosWFQEntry 10 }


--  qos wred / qos wred weighting-constant  13
                qosWREDTable OBJECT-TYPE
                        SYNTAX SEQUENCE OF QosWREDEntry
                        MAX-ACCESS not-accessible
                        STATUS current
                        DESCRIPTION
                                "WRED(Weighted Random Early Detect) table"
                        ::= { hwIfQoSMib 14 }


                qosWREDEntry OBJECT-TYPE
                        SYNTAX QosWREDEntry
                        MAX-ACCESS not-accessible
                        STATUS current
                        DESCRIPTION
                                "WRED configuration infomation"
                        INDEX { qosWREDIfIndex }
                        ::= { qosWREDTable 1 }


                QosWREDEntry ::=
                        SEQUENCE {
                                qosWREDIfIndex
                                        INTEGER,
                                qosWREDIfName
                                        OCTET STRING,
                                qosWREDWeightConstant
                                        INTEGER,
                                qosWREDEnable
                                        INTEGER,
                                qosUndoWREDWeightConstant
                                        INTEGER
                         }

                qosWREDIfIndex OBJECT-TYPE
                        SYNTAX INTEGER
                        MAX-ACCESS not-accessible
                        STATUS current
                        DESCRIPTION
                                "The index of the table, which is the index of interface."
                        ::= { qosWREDEntry 1 }


                qosWREDIfName OBJECT-TYPE
                        SYNTAX OCTET STRING
                        MAX-ACCESS read-only
                        STATUS current
                        DESCRIPTION
                                "The description of interface."
                        ::= { qosWREDEntry 2 }


                qosWREDWeightConstant OBJECT-TYPE
                        SYNTAX INTEGER (1..16)
                        MAX-ACCESS read-write
                        STATUS current
                        DESCRIPTION
                                "
                                Weighted factor in formula for calculating the mean length of queue.
                                From 1 to 16, the default value is 9
                                "
                        DEFVAL { 9 }
                        ::= { qosWREDEntry 3 }


                qosWREDEnable OBJECT-TYPE
                        SYNTAX INTEGER
                                {
                                disable(0),
                                enable(1)
                                }
                        MAX-ACCESS read-write
                        STATUS current
                        DESCRIPTION
                                "
                                0:disable wred. Recover the default configuration: tail-drop
                                1:enable wred
                                "
                        ::= { qosWREDEntry 4 }


                qosUndoWREDWeightConstant OBJECT-TYPE
                        SYNTAX INTEGER
                                {
                                qosWREDExponent(0),
                                qosNoWREDExponent(1)
                                }
                        MAX-ACCESS read-write
                        STATUS current
                        DESCRIPTION
                                "
                                0:Only for get.
                                1:Recover the default value of weighted factor: 9
                                "
                        ::= { qosWREDEntry 5 }


-- qos wred ip-precedence   15
                qosWREDPreTable OBJECT-TYPE
                        SYNTAX SEQUENCE OF QosWREDPreEntry
                        MAX-ACCESS not-accessible
                        STATUS current
                        DESCRIPTION
                                "WRED(Weighted Random Early Detect) precedence table"
                        ::= { hwIfQoSMib 15 }


                qosWREDPreEntry OBJECT-TYPE
                        SYNTAX QosWREDPreEntry
                        MAX-ACCESS not-accessible
                        STATUS current
                        DESCRIPTION
                                "WRED precedence configuration infomation"
                        INDEX { qosWREDPreIfIndex, qosWREDPrecedence }
                        ::= { qosWREDPreTable 1 }


                QosWREDPreEntry ::=
                        SEQUENCE {
                                qosWREDPreIfIndex
                                        INTEGER,
                                qosWREDPrecedence
                                        INTEGER,
                                qosWREDPreIfName
                                        OCTET STRING,
                                qosWREDPreLowLimit
                                        INTEGER,
                                qosWREDPreHighLimit
                                        INTEGER,
                                qosWREDPreDiscardProbability
                                        INTEGER,
                                qosWREDPreRandomDropNum
                                        Counter32,
                                qosWREDPreTailDropNum
                                        Counter32,
                                qosUndoWREDPre
                                        INTEGER
                         }

                qosWREDPreIfIndex OBJECT-TYPE
                        SYNTAX INTEGER
                        MAX-ACCESS not-accessible
                        STATUS current
                        DESCRIPTION
                                "The index of the table, which is the index of interface."
                        ::= { qosWREDPreEntry 1 }


                qosWREDPrecedence OBJECT-TYPE
                        SYNTAX INTEGER (0..7)
                        MAX-ACCESS not-accessible
                        STATUS current
                        DESCRIPTION
                                "IP precedence, from 0 to 7"
                        ::= { qosWREDPreEntry 2 }


                qosWREDPreIfName OBJECT-TYPE
                        SYNTAX OCTET STRING
                        MAX-ACCESS read-only
                        STATUS current
                        DESCRIPTION
                                "The description of interface."
                        ::= { qosWREDPreEntry 3 }


                qosWREDPreLowLimit OBJECT-TYPE
                        SYNTAX INTEGER (1..1024)
                        MAX-ACCESS read-write
                        STATUS current
                        DESCRIPTION
                                "Low Limit(number of packets)"
                        ::= { qosWREDPreEntry 4 }


               qosWREDPreHighLimit OBJECT-TYPE
                        SYNTAX INTEGER (1..1024)
                        MAX-ACCESS read-write
                        STATUS current
                        DESCRIPTION
                                "High limit(number of packets)"
                        ::= { qosWREDPreEntry 5 }


                qosWREDPreDiscardProbability OBJECT-TYPE
                        SYNTAX INTEGER (1..255)
                        MAX-ACCESS read-write
                        STATUS current
                        DESCRIPTION
                                "Discard probability denominator"
                        DEFVAL { 10 }
                        ::= { qosWREDPreEntry 6 }


                qosWREDPreRandomDropNum OBJECT-TYPE
                        SYNTAX Counter32
                        MAX-ACCESS read-only
                        STATUS current
                        DESCRIPTION
                                "Number of packets random-dropped for WRED"
                        ::= { qosWREDPreEntry 7 }


                qosWREDPreTailDropNum OBJECT-TYPE
                        SYNTAX Counter32
                        MAX-ACCESS read-only
                        STATUS current
                        DESCRIPTION
                                "Number of packets tail-dropped for WRED"
                        ::= { qosWREDPreEntry 8 }


                qosUndoWREDPre OBJECT-TYPE
                        SYNTAX INTEGER
                                {
                                qosWREDPre(0),
                                qosNoWREDPre(1)
                                }
                        MAX-ACCESS read-write
                        STATUS current
                        DESCRIPTION
                                "
                                0:Only for get.
                                1:Recover the default value of low-limit, high-limit 
                                  and discard-probability on relevant precedence.
                                "
                        ::= { qosWREDPreEntry 9 }


--  qos carl  16
                qosCarlTable OBJECT-TYPE
                        SYNTAX SEQUENCE OF QosCarlEntry
                        MAX-ACCESS not-accessible
                        STATUS current
                        DESCRIPTION
                                "CARL(Committed Access Rate List) table"
                        ::= { hwIfQoSMib 16 }


                qosCarlEntry OBJECT-TYPE
                        SYNTAX QosCarlEntry
                        MAX-ACCESS not-accessible
                        STATUS current
                        DESCRIPTION
                                "CARL configuration infomation"
                        INDEX { qosCarlListNum }
                        ::= { qosCarlTable 1 }


                QosCarlEntry ::=
                        SEQUENCE {
                                qosCarlListNum
                                        INTEGER,
                                qosCarlParaType
                                        INTEGER,
                                qosCarlParaValue
                                        OCTET STRING,
                                qosUndoCarl
                                        INTEGER
                         }

                qosCarlListNum OBJECT-TYPE
                        SYNTAX INTEGER
                        MAX-ACCESS not-accessible
                        STATUS current
                        DESCRIPTION
                                "The index of the table, which is the CARL number"
                        ::= { qosCarlEntry 1 }


                qosCarlParaType OBJECT-TYPE
                        SYNTAX INTEGER
                                {
                                mac-address(1),
                                prec-mask(2),
                                dscp-mask(3)
                                }
                        MAX-ACCESS read-write
                        STATUS current
                        DESCRIPTION
                                "Parameter type of the CARL number"
                        ::= { qosCarlEntry 2 }


                qosCarlParaValue OBJECT-TYPE
                        SYNTAX OCTET STRING
                        MAX-ACCESS read-write
                        STATUS current
                        DESCRIPTION
                                "Parameter value of the CARL table"
                        ::= { qosCarlEntry 3 }


                qosUndoCarl OBJECT-TYPE
                        SYNTAX INTEGER
                                {
                                qosCARL(0),
                                qosNoCARL(1)
                                }
                        MAX-ACCESS read-write
                        STATUS current
                        DESCRIPTION
                                "0:Only for get.
                                1:Delete the specified CARL"
                        ::= { qosCarlEntry 4 }


-- qos car / display qos car interface 17
               qosCARTable OBJECT-TYPE
                        SYNTAX SEQUENCE OF QosCAREntry
                        MAX-ACCESS not-accessible
                        STATUS current
                        DESCRIPTION
                                "CAR(Committed Access Rate) table"
                        ::= { hwIfQoSMib 17 }


               qosCAREntry OBJECT-TYPE
                        SYNTAX QosCAREntry
                        MAX-ACCESS not-accessible
                        STATUS current
                        DESCRIPTION
                                "CAR configuration and running infomation."
                        INDEX { qosCARIfIndex, qosCARPktDirection, qosCARType, qosCARListNum, qosCARCIR,
                                qosCARBurstSize, qosCARExcessBurstSize }
                        ::= { qosCARTable 1 }


                QosCAREntry ::=
                        SEQUENCE {
                                qosCARIfIndex
                                        INTEGER,
                                qosCARIfName
                                        OCTET STRING,
                                qosCARPktDirection
                                        INTEGER,
                                qosCARType
                                        INTEGER,
                                qosCARListNum
                                        INTEGER,
                                qosCARCIR
                                        INTEGER,
                                qosCARBurstSize
                                        INTEGER,
                                qosCARExcessBurstSize
                                        INTEGER,
                                qosCARConformAction
                                        INTEGER,
                                qosCARExceedAction
                                        INTEGER,
                                qosCARConformNewPrec
                                        INTEGER,
                                qosCARExceedNewPrec
                                        INTEGER,
                                qosCARConformPkt
                                        Counter32,
                                qosCARConformByte
                                        Counter32,
                                qosCARExceedPkt
                                        Counter32,
                                qosCARExceedByte
                                        Counter32,
                                qosUndoCAR
                                        INTEGER
                         }

                qosCARIfIndex OBJECT-TYPE
                        SYNTAX INTEGER
                        MAX-ACCESS not-accessible
                        STATUS current
                        DESCRIPTION
                                "The index of the table, which is the index of interface."
                        ::= { qosCAREntry 1 }


                qosCARIfName OBJECT-TYPE
                        SYNTAX OCTET STRING
                        MAX-ACCESS read-only
                        STATUS current
                        DESCRIPTION
                                "The description of interface."
                        ::= { qosCAREntry 2 }


                qosCARPktDirection OBJECT-TYPE
                        SYNTAX INTEGER
                                {
                                inbound(1),
                                outbound(2)
                                }
                        MAX-ACCESS not-accessible
                        STATUS current
                        DESCRIPTION
                                "The index of the table, which is direction of the processed packet."
                        ::= { qosCAREntry 3 }


                qosCARType OBJECT-TYPE
                        SYNTAX INTEGER
                                {
                                acl(1),
                                carl(2),
                                all(3)
                                }
                        MAX-ACCESS not-accessible
                        STATUS current
                        DESCRIPTION
                                "
                                The index of the table, which is the matching type for the packets
                                on interface:ACL,CARL,ANY.
                                "
                        ::= { qosCAREntry 4 }


                qosCARListNum OBJECT-TYPE
                        SYNTAX INTEGER (0..199|2000..3999)
                        MAX-ACCESS not-accessible
                        STATUS current
                        DESCRIPTION
                                "
                                The index of the table, which is
                                CARType=1,the number is ACL number;
                                CARType=2,the number is CARL number;
                                CARType=3,the parameter is 0.
                                "
                        ::= { qosCAREntry 5 }


                qosCARCIR OBJECT-TYPE
                        SYNTAX INTEGER
                        MAX-ACCESS not-accessible
                        STATUS current
                        DESCRIPTION
                                "The index of the table, which is  Committed Information Rate."
                        ::= { qosCAREntry 6 }


                qosCARBurstSize OBJECT-TYPE
                        SYNTAX INTEGER
                        MAX-ACCESS not-accessible
                        STATUS current
                        DESCRIPTION
                                "The index of the table, which is Burst Size."
                        ::= { qosCAREntry 7 }


                qosCARExcessBurstSize OBJECT-TYPE
                        SYNTAX INTEGER
                        MAX-ACCESS not-accessible
                        STATUS current
                        DESCRIPTION
                                "The index of the table, which is Excess Burst Size."
                        ::= { qosCAREntry 8 }


                qosCARConformAction OBJECT-TYPE
                        SYNTAX INTEGER
                                {
                                continue(1),
                                discard(2),
                                remark-prec-continue(3),
                                remark-prec-pass(4),
                                pass(5),
                                remark-mplsexp-continue(6),
                                remark-mplsexp-pass(7)
                                }
                        MAX-ACCESS read-write
                        STATUS current
                        DESCRIPTION
                                "Action on packets when traffic is within the CIR"
                        ::= { qosCAREntry 9 }


                qosCARExceedAction OBJECT-TYPE
                        SYNTAX INTEGER
                                {
                                continue(1),
                                discard(2),
                                remark-prec-continue(3),
                                remark-prec-pass(4),
                                pass(5),
                                remark-mplsexp-continue(6),
                                remark-mplsexp-pass(7)
                                }
                        MAX-ACCESS read-write
                        STATUS current
                        DESCRIPTION
                                "Action on packets when traffic is out of CIR"
                        ::= { qosCAREntry 10 }


                qosCARConformNewPrec OBJECT-TYPE
                        SYNTAX INTEGER (0..7)
                        MAX-ACCESS read-write
                        STATUS current
                        DESCRIPTION
                                "Rewrite the precedence value on packets when traffic is within the CIR"
                        ::= { qosCAREntry 11 }


                qosCARExceedNewPrec OBJECT-TYPE
                        SYNTAX INTEGER (0..7)
                        MAX-ACCESS read-write
                        STATUS current
                        DESCRIPTION
                                "Rewrite the precedence value on packets when traffic is out of CIR"
                        ::= { qosCAREntry 12 }


                qosCARConformPkt OBJECT-TYPE
                        SYNTAX Counter32
                        MAX-ACCESS read-only
                        STATUS current
                        DESCRIPTION
                                "Number of Conformed packets."
                        ::= { qosCAREntry 13 }


                qosCARConformByte OBJECT-TYPE
                        SYNTAX Counter32
                        MAX-ACCESS read-only
                        STATUS current
                        DESCRIPTION
                                "Bytes of Conformed packets."
                        ::= { qosCAREntry 14 }


                qosCARExceedPkt OBJECT-TYPE
                        SYNTAX Counter32
                        MAX-ACCESS read-only
                        STATUS current
                        DESCRIPTION
                                "Number of Exceeded packets."
                        ::= { qosCAREntry 15 }


                qosCARExceedByte OBJECT-TYPE
                        SYNTAX Counter32
                        MAX-ACCESS read-only
                        STATUS current
                        DESCRIPTION
                                "Bytes of Exceeded packets."
                        ::= { qosCAREntry 16 }


                qosUndoCAR OBJECT-TYPE
                        SYNTAX INTEGER
                                {
                                qosCAR(0),
                                qosNoCAR(1)
                                }
                        MAX-ACCESS read-write
                        STATUS current
                        DESCRIPTION
                                "
                                0:Only for get.
                                1:Delete the relevant CAR policy
                                "
                        ::= { qosCAREntry 17 }


-- qos gts / display qos gts interface  18
                qosGTSTable OBJECT-TYPE
                        SYNTAX SEQUENCE OF QosGTSEntry
                        MAX-ACCESS not-accessible
                        STATUS current
                        DESCRIPTION
                                "GTS(Generic Traffic Shaping) table"
                        ::= { hwIfQoSMib 18 }


                qosGTSEntry OBJECT-TYPE
                        SYNTAX QosGTSEntry
                        MAX-ACCESS not-accessible
                        STATUS current
                        DESCRIPTION
                                "GTS configuration information"
                        INDEX { qosGTSIfIndex, qosGTSType, qosGTSACLNum }
                        ::= { qosGTSTable 1 }


                QosGTSEntry ::=
                        SEQUENCE {
                                qosGTSIfIndex
                                        INTEGER,
                                qosGTSIfName
                                        OCTET STRING,
                                qosGTSType
                                        INTEGER,
                                qosGTSACLNum
                                        INTEGER,
                                qosGTSCIR
                                        INTEGER,
                                qosGTSBurstSize
                                        INTEGER,
                                qosGTSExcessBurstSize
                                        INTEGER,
                                qosGTSMaxQueLen
                                        INTEGER,
                                qosGTSCurQueLen
                                        INTEGER,
                                qosGTSPassPkt
                                        Counter32,
                                qosGTSPassByte
                                        Counter32,
                                qosGTSDelayPkt
                                        Counter32,
                                qosGTSDelayByte
                                        Counter32,
                                qosGTSDiscardPkt
                                        Counter32,
                                qosGTSDiscardByte
                                        Counter32,
                                qosUndoGTS
                                        INTEGER
                         }


                qosGTSIfIndex OBJECT-TYPE
                        SYNTAX INTEGER
                        MAX-ACCESS not-accessible
                        STATUS current
                        DESCRIPTION
                                "The index of the table, which is the index of interface."
                        ::= { qosGTSEntry 1 }


                qosGTSIfName OBJECT-TYPE
                        SYNTAX OCTET STRING
                        MAX-ACCESS read-only
                        STATUS current
                        DESCRIPTION
                                "The description of interface."
                        ::= { qosGTSEntry 2 }


                qosGTSType OBJECT-TYPE
                        SYNTAX INTEGER
                                {
                                acl(1),
                                all(2)
                                }
                        MAX-ACCESS not-accessible
                        STATUS current
                        DESCRIPTION
                                "
                                The index of the table, which is the matching type for the packets
                                on interface:ACL, ANY
                                "
                        ::= { qosGTSEntry 3 }


                qosGTSACLNum OBJECT-TYPE
                        SYNTAX INTEGER (0|2000..3999)
                        MAX-ACCESS read-only
                        STATUS current
                        DESCRIPTION
                                "
                                qosGTSType = 1:The index of the table, which is ACL number
                                qosGTSType = 2:The index of the table is 0
                                "
                        ::= { qosGTSEntry 4 }


                qosGTSCIR OBJECT-TYPE
                        SYNTAX INTEGER
                        MAX-ACCESS read-write
                        STATUS current
                        DESCRIPTION
                                "The Committed Information Rate for shaping"
                        ::= { qosGTSEntry 5 }


                qosGTSBurstSize OBJECT-TYPE
                        SYNTAX INTEGER
                        MAX-ACCESS read-write
                        STATUS current
                        DESCRIPTION
                                "The Burst Size for shaping"
                        ::= { qosGTSEntry 6 }


                qosGTSExcessBurstSize OBJECT-TYPE
                        SYNTAX INTEGER
                        MAX-ACCESS read-write
                        STATUS current
                        DESCRIPTION
                                "The Excess Burst Size for shaping"
                        ::= { qosGTSEntry 7 }


                qosGTSMaxQueLen OBJECT-TYPE
                        SYNTAX INTEGER (1..1024)
                        MAX-ACCESS read-write
                        STATUS current
                        DESCRIPTION
                                "The maximum queue length for shaping"
                        ::= { qosGTSEntry 8 }


                qosGTSCurQueLen OBJECT-TYPE
                        SYNTAX INTEGER
                        MAX-ACCESS read-only
                        STATUS current
                        DESCRIPTION
                                "The current queue length for shaping"
                        ::= { qosGTSEntry 9 }


                qosGTSPassPkt OBJECT-TYPE
                        SYNTAX Counter32
                        MAX-ACCESS read-only
                        STATUS current
                        DESCRIPTION
                                "Number of transmitted packets for shaping"
                        ::= { qosGTSEntry 10 }


                qosGTSPassByte OBJECT-TYPE
                        SYNTAX Counter32
                        MAX-ACCESS read-only
                        STATUS current
                        DESCRIPTION
                                "Bytes of transmitted packets for shaping"
                        ::= { qosGTSEntry 11 }


                qosGTSDelayPkt OBJECT-TYPE
                        SYNTAX Counter32
                        MAX-ACCESS read-only
                        STATUS current
                        DESCRIPTION
                                "Number of delayed packets for shaping"
                        ::= { qosGTSEntry 12 }


                qosGTSDelayByte OBJECT-TYPE
                        SYNTAX Counter32
                        MAX-ACCESS read-only
                        STATUS current
                        DESCRIPTION
                                "Bytes of delayed packets for shaping"
                        ::= { qosGTSEntry 13 }


                qosGTSDiscardPkt OBJECT-TYPE
                        SYNTAX Counter32
                        MAX-ACCESS read-only
                        STATUS current
                        DESCRIPTION
                                "Number of discarded packets for shaping"
                        ::= { qosGTSEntry 14 }


                qosGTSDiscardByte OBJECT-TYPE
                        SYNTAX Counter32
                        MAX-ACCESS read-only
                        STATUS current
                        DESCRIPTION
                                "Bytes of discarded packets for shaping"
                        ::= { qosGTSEntry 15 }


                qosUndoGTS OBJECT-TYPE
                        SYNTAX INTEGER
                                {
                                qosGTS(0),
                                qosNoGTS(1)
                                }
                        MAX-ACCESS read-write
                        STATUS current
                        DESCRIPTION
                                "
                                0:Only for get.
                                1:Delete the relevant GTS policy
                                "
                        ::= { qosGTSEntry 16 }


-- LR        19
-- IfIndex                        interface index
-- IfName                        (read-only）
-- CIR                                8000-155000000
-- BurstSize                        15000-155000000
-- ExcessBurstSize                0-155000000
-- PassPkt                        number of transmitted packet(read-only）
-- PassByte                     bytes of transmitted packet(read-only）
-- DelayPkt                        number of delayed packet(read-only）
-- DelayByte                        bytes of delayed packet(read-only）
-- UndoLR                        1
-- IfIndex is index
                qosLRTable OBJECT-TYPE
                        SYNTAX SEQUENCE OF QosLREntry
                        MAX-ACCESS not-accessible
                        STATUS current
                        DESCRIPTION
                                "LR(Line Rate) table."
                        ::= { hwIfQoSMib 19 }


                qosLREntry OBJECT-TYPE
                        SYNTAX QosLREntry
                        MAX-ACCESS not-accessible
                        STATUS current
                        DESCRIPTION
                                "LR configuration and running information."
                        INDEX { qosLRIfIndex }
                        ::= { qosLRTable 1 }


                QosLREntry ::=
                        SEQUENCE {
                                qosLRIfIndex
                                        INTEGER,
                                qosLRIfName
                                        OCTET STRING,
                                qosLRCIR
                                        INTEGER,
                                qosLRBurstSize
                                        INTEGER,
                                qosLRExcessBurstSize
                                        INTEGER,
                                qosLRPassPkt
                                        Counter32,
                                qosLRPassByte
                                        Counter32,
                                qosLRDelayPkt
                                        Counter32,
                                qosLRDelayByte
                                        Counter32,
                                qosUndoLR
                                        INTEGER
                         }

                qosLRIfIndex OBJECT-TYPE
                        SYNTAX INTEGER
                        MAX-ACCESS not-accessible
                        STATUS current
                        DESCRIPTION
                                "The index of the table, which is the index of interface."
                        ::= { qosLREntry 1 }


                qosLRIfName OBJECT-TYPE
                        SYNTAX OCTET STRING
                        MAX-ACCESS read-only
                        STATUS current
                        DESCRIPTION
                                "The description of interface."
                        ::= { qosLREntry 2 }


                qosLRCIR OBJECT-TYPE
                        SYNTAX INTEGER
                        MAX-ACCESS read-write
                        STATUS current
                        DESCRIPTION
                                "The Committed Information Rate on the physical port."
                        ::= { qosLREntry 3 }


                qosLRBurstSize OBJECT-TYPE
                        SYNTAX INTEGER
                        MAX-ACCESS read-write
                        STATUS current
                        DESCRIPTION
                                "Burst Size."
                        ::= { qosLREntry 4 }


                qosLRExcessBurstSize OBJECT-TYPE
                        SYNTAX INTEGER
                        MAX-ACCESS read-write
                        STATUS current
                        DESCRIPTION
                                "Excess Burst Size."
                        ::= { qosLREntry 5 }


                qosLRPassPkt OBJECT-TYPE
                        SYNTAX Counter32
                        MAX-ACCESS read-only
                        STATUS current
                        DESCRIPTION
                                "Number of transmitted packets."
                        ::= { qosLREntry 6 }


                qosLRPassByte OBJECT-TYPE
                        SYNTAX Counter32
                        MAX-ACCESS read-only
                        STATUS current
                        DESCRIPTION
                                "Bytes of transmitted packets."
                        ::= { qosLREntry 7 }


                qosLRDelayPkt OBJECT-TYPE
                        SYNTAX Counter32
                        MAX-ACCESS read-only
                        STATUS current
                        DESCRIPTION
                                "Number of delayed packets"
                        ::= { qosLREntry 8 }


                qosLRDelayByte OBJECT-TYPE
                        SYNTAX Counter32
                        MAX-ACCESS read-only
                        STATUS current
                        DESCRIPTION
                                "Bytes of delayed packets"
                        ::= { qosLREntry 9 }


                qosUndoLR OBJECT-TYPE
                        SYNTAX INTEGER
                                {
                                qosLR(0),
                                qosNoLR(1)
                                }
                        MAX-ACCESS read-write
                        STATUS current
                        DESCRIPTION
                                "
                                0:Only for get.
                                1:Delete the relevant LR policy
                                "
                        ::= { qosLREntry 10 }

-- bandwidth parameter on interface
                qosIfBandwidthTable OBJECT-TYPE
                        SYNTAX SEQUENCE OF QosIfBandwidthEntry
                        MAX-ACCESS not-accessible
                        STATUS current
                        DESCRIPTION
                                "A table of bandwidth parameter on interface."
                        ::= { hwIfQoSMib 20 }

                qosIfBandwidthEntry OBJECT-TYPE
                        SYNTAX QosIfBandwidthEntry
                        MAX-ACCESS not-accessible
                        STATUS current
                        DESCRIPTION
                                "Bandwidth parameter applied on Interface."
                        INDEX { qosIfBandwidthIfIndex }
                        ::= { qosIfBandwidthTable 1 }

                QosIfBandwidthEntry ::=
                        SEQUENCE {
                              qosIfBandwidthIfIndex
                                             Integer32,
                              qosIFBandwidthMaxBW
                                             Integer32,
                              qosIFBandwidthMaxReservedBWPct
                                             Integer32,
                              qosIFBandwidthMaxReservedBW
                                             Integer32,
                              qosIFBandwidthAvailable
                                             Integer32,
                              qosIFBandwidthRowStatus
                                             RowStatus
                              }

                qosIfBandwidthIfIndex OBJECT-TYPE
                        SYNTAX Integer32
                        MAX-ACCESS not-accessible
                        STATUS current
                        DESCRIPTION
                            "Interface Index, equal to ifIndex."
                        ::= { qosIfBandwidthEntry 1 }

                qosIFBandwidthMaxBW OBJECT-TYPE
                        SYNTAX Integer32 (1..1000000)
                        MAX-ACCESS read-create
                        STATUS current
                        DESCRIPTION
                                "Max bandwidth Value (Unit: Kbps) applied on the interface."
                        ::= { qosIfBandwidthEntry 2 }

                qosIFBandwidthMaxReservedBWPct OBJECT-TYPE
                        SYNTAX Integer32 (1..100)
                        MAX-ACCESS read-create
                        STATUS current
                        DESCRIPTION
                                "Max reserved bandwidth as percent of the interface bandwidth (Unit: percent)."
                        ::= { qosIfBandwidthEntry 3 }

                qosIFBandwidthMaxReservedBW OBJECT-TYPE
                        SYNTAX Integer32
                        MAX-ACCESS read-only
                        STATUS current
                        DESCRIPTION
                                "Max reserved bandwidth. Unit : Kbps"
                        ::= { qosIfBandwidthEntry 4 }

                qosIFBandwidthAvailable OBJECT-TYPE
                        SYNTAX Integer32
                        MAX-ACCESS read-only
                        STATUS current
                        DESCRIPTION
                                "Available bandwidth. Unit : Kbps"
                        ::= { qosIfBandwidthEntry 5 }

                qosIFBandwidthRowStatus OBJECT-TYPE
                        SYNTAX RowStatus
                        MAX-ACCESS read-create
                        STATUS current
                        DESCRIPTION
                                "RowStatus for qosIfBandwidthTable Table.
                                Three actions are used: active, createAndGo, destroy"
                        ::= { qosIfBandwidthEntry 6 }

-- Rtpq applied on the interface
                qosRTPIfApplyTable OBJECT-TYPE
                        SYNTAX SEQUENCE OF QosRTPIfApplyEntry
                        MAX-ACCESS not-accessible
                        STATUS current
                        DESCRIPTION
                                "A table of QoS RTP(Realtime Transport Protocol) Queue instance."
                        ::= { hwIfQoSMib 21 }

                qosRTPIfApplyEntry OBJECT-TYPE
                        SYNTAX QosRTPIfApplyEntry
                        MAX-ACCESS not-accessible
                        STATUS current
                        DESCRIPTION
                                "Apply RTP(Realtime Transport Protocol) queuing on interface."
                        INDEX { qosRTPIfApplyIfIndex }
                        ::= { qosRTPIfApplyTable 1 }

                QosRTPIfApplyEntry ::=
                        SEQUENCE {
                                qosRTPIfApplyIfIndex
                                        Integer32,
                                qosRTPIfApplyStartPort
                                        Integer32,
                                qosRTPIfApplyEndPort
                                        Integer32,
                                qosRTPIfApplyBandWidth
                                        Integer32,
                                qosRTPIfApplyCbs
                                        Integer32,
                                qosRTPIfApplyRowStatus
                                        RowStatus
                                    }

                qosRTPIfApplyIfIndex OBJECT-TYPE
                        SYNTAX Integer32
                        MAX-ACCESS not-accessible
                        STATUS current
                        DESCRIPTION
                                "Interface Index, equal to ifIndex."
                        ::= { qosRTPIfApplyEntry 1 }

                qosRTPIfApplyStartPort OBJECT-TYPE
                        SYNTAX Integer32(2000..65535)
                        MAX-ACCESS read-create
                        STATUS current
                        DESCRIPTION
                                "
                                RTP-PORT(3): start-port: 2000~65535
                                "
                        ::= { qosRTPIfApplyEntry 2 }

                qosRTPIfApplyEndPort OBJECT-TYPE
                        SYNTAX Integer32(2000..65535)
                        MAX-ACCESS read-create
                        STATUS current
                        DESCRIPTION
                                "
                                RTP-PORT(3): end-port: 2000~65535
                                "
                        ::= { qosRTPIfApplyEntry 3 }

                qosRTPIfApplyBandWidth OBJECT-TYPE
                        SYNTAX Integer32 (8..1000000)
                        MAX-ACCESS read-create
                        STATUS current
                        DESCRIPTION
                                "Max bandwidth Value:
                                Absolute value: 8..1000000. Unit: Kbps
                                "
                        ::= { qosRTPIfApplyEntry 4 }

                qosRTPIfApplyCbs OBJECT-TYPE
                        SYNTAX Integer32
                        MAX-ACCESS read-create
                        STATUS current
                        DESCRIPTION
                                "
                                Committed Burst Size: 1500..2000000. Unit: bytes
                                "
                        ::= { qosRTPIfApplyEntry 5 }

                qosRTPIfApplyRowStatus OBJECT-TYPE
                        SYNTAX RowStatus
                        MAX-ACCESS read-create
                        STATUS current
                        DESCRIPTION
                                "RowStatus for RTPQoSIfApply Table.
                                Three actions are used: active, createAndGo, destroy"
                        ::= { qosRTPIfApplyEntry 6 }

-- RTPQ statistics on the interface
                qosRTPIfQueueRunInfoTable OBJECT-TYPE
                        SYNTAX SEQUENCE OF QosRTPIfQueueRunInfoEntry
                        MAX-ACCESS not-accessible
                        STATUS current
                        DESCRIPTION
                                "A table of Running statistics for RTP(Realtime Transport Protocol) Queue
                                applied on the interface."
                        ::= { hwIfQoSMib 22 }

                qosRTPIfQueueRunInfoEntry OBJECT-TYPE
                        SYNTAX QosRTPIfQueueRunInfoEntry
                        MAX-ACCESS not-accessible
                        STATUS current
                        DESCRIPTION
                                "RTP(Realtime Transport Protocol) Queue statistics entry."
                        INDEX { qosRTPIfApplyIfIndex        }
                        ::= { qosRTPIfQueueRunInfoTable 1 }

                QosRTPIfQueueRunInfoEntry ::=
                        SEQUENCE {
                                qosRTPIfQueueSize
                                        Counter32,
                                qosRTPIfQueueMaxSize
                                        Counter32,
                                qosRTPIfQueueOutputs
                                        Counter32,
                                qosRTPIfQueueDiscards
                                        Counter32
                                 }

                qosRTPIfQueueSize OBJECT-TYPE
                        SYNTAX Counter32
                        MAX-ACCESS read-only
                        STATUS current
                        DESCRIPTION
                                "Size of Rtpq Queue."
                        ::= { qosRTPIfQueueRunInfoEntry 1 }

                qosRTPIfQueueMaxSize OBJECT-TYPE
                        SYNTAX Counter32
                        MAX-ACCESS read-only
                        STATUS current
                        DESCRIPTION
                                " Max packet number of RTP(Realtime Transport Protocol) Queue."
                        ::= { qosRTPIfQueueRunInfoEntry 2 }

                qosRTPIfQueueOutputs OBJECT-TYPE
                        SYNTAX Counter32
                        MAX-ACCESS read-only
                        STATUS current
                        DESCRIPTION
                                "Output packet number of RTP(Realtime Transport Protocol) Queue."
                        ::= { qosRTPIfQueueRunInfoEntry 3 }

                qosRTPIfQueueDiscards OBJECT-TYPE
                        SYNTAX Counter32
                        MAX-ACCESS read-only
                        STATUS current
                        DESCRIPTION
                                "Discarded packet number of RTP(Realtime Transport Protocol) Queue."
                        ::= { qosRTPIfQueueRunInfoEntry 4 }

END
