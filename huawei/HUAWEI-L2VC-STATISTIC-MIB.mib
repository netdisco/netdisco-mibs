-- ==================================================================
-- Copyright (C) 2021 by  HUAWEI TECHNOLOGIES. All rights reserved.
-- 
-- Description:  HUAWEI VLL traffic statistics on a specified interface MIB
-- Reference:
-- Version: V1.00
-- History:
-- ==================================================================
-- HUAWEI-MPLSOAM-MIB.mib
-- ==================================================================
-- 
-- Variables and types to be imported
--
-- ==================================================================
   HUAWEI-L2VC-STATISTIC-MIB DEFINITIONS::= BEGIN
    	
        IMPORTS
            hwDatacomm            
                FROM HUAWEI-MIB
            InterfaceIndex
                FROM IF-MIB
            OBJECT-GROUP, MODULE-COMPLIANCE           
                FROM SNMPv2-CONF            
            Counter64, OBJECT-TYPE, MODULE-IDENTITY, TimeTicks, Unsigned32
                FROM SNMPv2-SMI         
            TruthValue, TEXTUAL-CONVENTION, DateAndTime           
                FROM SNMPv2-TC;
				
-- May 27, 2021 at 11:35 GMT
        hwL2vcStatistics MODULE-IDENTITY 
            LAST-UPDATED "202106151628Z" 
            ORGANIZATION 
                "Huawei Technologies Co.,Ltd."
            CONTACT-INFO 
                "Huawei Industrial Base
                   Bantian, Longgang
                   Shenzhen 518129
                   People's Republic of China
                   Website: http://www.huawei.com
                   Email: support@huawei.com
                "
            DESCRIPTION 
                "The HUAWEI-L2VC-STATISTIC-MIB contains objects to enable the system 
				to collect VLL traffic statistics and get VLL traffic statistics on a specified."
				
			REVISION"202106151628Z"                    -- June 15, 2021 at 16:00 GMT		
			DESCRIPTION
                "Create file."	
				
			::= { hwL2vcStatisticsMib 1 }
			
		EnabledStatus ::= TEXTUAL-CONVENTION
			STATUS      current
			DESCRIPTION
				"A simple status value for the object."
			SYNTAX      INTEGER 
			{ 
			  enabled(1),
			  disabled(2)
			}	
			
	hwL2vcStatisticsMib 
		OBJECT IDENTIFIER ::= { hwDatacomm 666 }
			
	hwL2vcStatisticsInfo     
        OBJECT IDENTIFIER ::= { hwL2vcStatistics 1 }

		hwL2vcStatisticEnable OBJECT-TYPE
            SYNTAX EnabledStatus
            MAX-ACCESS read-write
            STATUS current
            DESCRIPTION
                "This object indicates the VLL traffic statistics is whether enabled or not." 
            ::= { hwL2vcStatisticsInfo 1 }
			
		hwL2vcStatisticsTable OBJECT-TYPE
			SYNTAX       SEQUENCE OF HwL2vcStatisticsEntry 
			MAX-ACCESS   not-accessible
			STATUS       current
			DESCRIPTION
				"This object indicates the VLL traffic statistics table."
			::= { hwL2vcStatisticsInfo 2 }
			
		hwL2vcStatisticsEntry OBJECT-TYPE
			SYNTAX       HwL2vcStatisticsEntry
			MAX-ACCESS   not-accessible
			STATUS       current
			DESCRIPTION
				"This object indicates the VLL traffic statistics entry." 
			INDEX { hwL2vcStatisticIfIndex } 
			::= { hwL2vcStatisticsTable 1 }
			
		HwL2vcStatisticsEntry::= SEQUENCE { 
			hwL2vcStatisticIfIndex              InterfaceIndex,
			hwL2vcStatisticOutputPackets      Counter64,
			hwL2vcStatisticOutputBytes        Counter64,
			hwL2vcStatisticInputPackets       Counter64,
			hwL2vcStatisticInputBytes         Counter64,
			hwL2vcStatisticResetTraffic       TruthValue
		}
		
		hwL2vcStatisticIfIndex OBJECT-TYPE
			SYNTAX       InterfaceIndex
			MAX-ACCESS   not-accessible
			STATUS       current
			DESCRIPTION  
				"This object indicates port name."
			::= { hwL2vcStatisticsEntry 1}
			
		hwL2vcStatisticOutputPackets OBJECT-TYPE
			SYNTAX       Counter64
			MAX-ACCESS   read-only
			STATUS       current
			DESCRIPTION  
				"This object indicates statistics of output packets."
			::= { hwL2vcStatisticsEntry 2}
			
		hwL2vcStatisticOutputBytes OBJECT-TYPE
			SYNTAX       Counter64
			MAX-ACCESS   read-only
			STATUS       current
			DESCRIPTION  
				"This object indicates statistics of output bytes."
			::= { hwL2vcStatisticsEntry 3}
			
		hwL2vcStatisticInputPackets OBJECT-TYPE
			SYNTAX       Counter64
			MAX-ACCESS   read-only
			STATUS       current
			DESCRIPTION  
				"This object indicates statistics of input packets."
			::= { hwL2vcStatisticsEntry 4}
			
		hwL2vcStatisticInputBytes OBJECT-TYPE
			SYNTAX       Counter64
			MAX-ACCESS   read-only
			STATUS       current
			DESCRIPTION  
				"This object indicates statistics of bytes."
			::= { hwL2vcStatisticsEntry 5}
			
		hwL2vcStatisticResetTraffic OBJECT-TYPE
			SYNTAX       TruthValue
			MAX-ACCESS   read-write
			STATUS       current
			DESCRIPTION  
				"Clear statistics information."
			::= { hwL2vcStatisticsEntry 6}

	END
