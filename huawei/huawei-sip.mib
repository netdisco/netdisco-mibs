-- =========================================================================
-- Copyright (C) 2003,2004 by  HUAWEI TECHNOLOGIES. All rights reserved.
--
-- Description: implement the parameters configuration and information browser
--              of the SIP module.
-- Reference: Huawei enterprise MIB
-- Version: V1.1
-- History:
--	V1.0 <guoxiaojun>,<2003-09-01>,<initial>
--      V1.1 2004-10-25 updated by xiejianping
--           Remove OID comments.
-- =========================================================================

HUAWEI-SIP-MIB DEFINITIONS ::= BEGIN
 
	IMPORTS
		enterprises			
			FROM RFC1155-SMI			
		mib-2, TimeTicks, Integer32, OBJECT-TYPE, MODULE-IDENTITY, 
		NOTIFICATION-TYPE			
			FROM SNMPv2-SMI			
		DisplayString, RowStatus, DateAndTime			
			FROM SNMPv2-TC
	    	huawei, huaweiMgmt, huaweiDatacomm, voice
		        FROM HUAWEI-3COM-OID-MIB;
	
	
--  March 15,2003 GMT
-- March 15,2003 GMT
		hwSIPMIB MODULE-IDENTITY 
			LAST-UPDATED "200309010000Z"		-- Sept. 01, 2003 at 00:00 GMT
			ORGANIZATION 
				"Huawei Technologies co.,Ltd."
			CONTACT-INFO 
				" R&D BeiJing, Huawei Technologies co.,Ltd.
				Huawei Bld.,NO.3 Xinxi Rd., 
				Shang-Di Information Industry Base,
				Hai-Dian District Beijing P.R. China
				Zip:100085 
				Http://www.huawei.com                                       
				E-mail:support@huawei.com "
			DESCRIPTION 
				"The HUAWEI-SIP-MIB contains objects to Manage 
				the SIP client configuration."
			REVISION "200309010000Z"		-- Sept. 01, 2003 at 00:00 GMT
			DESCRIPTION 
				"The initial revision of this MIB module."
			::= { voice 12 }
		
		hwSIPServerMIB OBJECT IDENTIFIER ::= { hwSIPMIB 1 }
        
        
		hwSIPClientMIB OBJECT IDENTIFIER ::= { hwSIPMIB 2 }

		
		hwSIPClientMIBObjects OBJECT IDENTIFIER ::= { hwSIPClientMIB 1 }

		
		hwSIPID OBJECT-TYPE
			SYNTAX OCTET STRING (SIZE (1..32))
			MAX-ACCESS read-write
			STATUS current
			DESCRIPTION
				"The unique identification of a SIP gateway. By default, 
				this object should have the value 'VRP-GATEWAY'."
			DEFVAL { "VRP-GATEWAY" }
			::= { hwSIPClientMIBObjects 1 }

		
		hwSIPPasswordType OBJECT-TYPE
			SYNTAX INTEGER
				{
				simple(1),
				cipher(2)
				}
			MAX-ACCESS read-write
			STATUS current
			DESCRIPTION
				"The display type of a SIP gateway password. By default, 
				this object should have the value simple(1)."
			DEFVAL { 1 }
			::= { hwSIPClientMIBObjects 2 }

				
		hwSIPPassword OBJECT-TYPE
			SYNTAX OCTET STRING (SIZE (0..32))
			MAX-ACCESS read-write
			STATUS current
			DESCRIPTION
				"a SIP gateway password. By default, this object should have 
				the value 'VRP-SIP'."
			DEFVAL { "VRP-SIP" }
			::= { hwSIPClientMIBObjects 3 }

		
		hwSIPTransport OBJECT-TYPE
			SYNTAX INTEGER
				{
				udp(1),
				tcp(2)
				}
			MAX-ACCESS read-write
			STATUS current
			DESCRIPTION
				"the transport type of SIP packets. By default, this object should
				have the value udp(1)."
			DEFVAL { 1 }
			::= { hwSIPClientMIBObjects 4 }			
			
		hwSIPSourceIP OBJECT-TYPE
			SYNTAX IpAddress
			MAX-ACCESS read-write
			STATUS current
			DESCRIPTION
				"The source IP address of the local peer acted as UA."
--			DEFVAL { 1 }
			::= { hwSIPClientMIBObjects 5 }			
		
		hwSIPCallDebugSwitch OBJECT-TYPE
			SYNTAX INTEGER
				{
				enabled(1),
				disabled(2)
				}
			MAX-ACCESS read-write
			STATUS current
			DESCRIPTION
				"Indicate whether the SIP calls debug information should be generated.
				By default, this object should have the value disabled(2)."
			DEFVAL { 2 }
			::= { hwSIPClientMIBObjects 6 }

		hwSIPRegisterDebugSwitch OBJECT-TYPE
			SYNTAX INTEGER
				{
				enabled(1),
				disabled(2)
				}
			MAX-ACCESS read-write
			STATUS current
			DESCRIPTION
				"Indicate whether the SIP calls debug information should be generated.
				By default, this object should have the value disabled(2)."
			DEFVAL { 2 }
			::= { hwSIPClientMIBObjects 7 }
		
		hwSIPRegPrimitiveDebugSwitch OBJECT-TYPE
			SYNTAX INTEGER
				{
				enabled(1),
				disabled(2)
				}
			MAX-ACCESS read-write
			STATUS current
			DESCRIPTION
				"Indicate whether the SIP register primitives debug information should be generated.
				By default, this object should have the value disabled(2)."
			DEFVAL { 2 }
			::= { hwSIPClientMIBObjects 8 }  
		
		hwSIPCallPrimitiveDebugSwitch OBJECT-TYPE
			SYNTAX INTEGER
				{
				enabled(1),
				disabled(2)
				}
			MAX-ACCESS read-write
			STATUS current
			DESCRIPTION
				"Indicate whether the SIP call primitives debug information should be generated.
				By default, this object should have the value disabled(2)."
			DEFVAL { 2 }
			::= { hwSIPClientMIBObjects 9 }  
		
		hwSIPWarningDebugSwitch OBJECT-TYPE
			SYNTAX INTEGER
				{
				enabled(1),
				disabled(2)
				}
			MAX-ACCESS read-write
			STATUS current
			DESCRIPTION
				"Indicate whether the SIP warnings debug information should be generated.
				By default, this object should have the value disabled(2)."
			DEFVAL { 2 }
			::= { hwSIPClientMIBObjects 10 }
			
		
		hwSIPErrorDebugSwitch OBJECT-TYPE
			SYNTAX INTEGER
				{
				enabled(1),
				disabled(2)
				}
			MAX-ACCESS read-write
			STATUS current
			DESCRIPTION
				"Indicate whether the SIP errors debug information should be generated.
				By default, this object should have the value disabled(2)."
			DEFVAL { 2 }
			::= { hwSIPClientMIBObjects 11 }

		
		hwSIPTrapsControl OBJECT-TYPE
			SYNTAX INTEGER
				{
				enabled(1),
				disabled(2)
				}
			MAX-ACCESS read-write
			STATUS current
			DESCRIPTION
				"Indicates wether the SIP module is permitted to generate
				traps. By default, this object should have the value disabled(2)."
			DEFVAL { 2 }
			::= { hwSIPClientMIBObjects 12 }
			
		hwSIPStatisticClear OBJECT-TYPE
			SYNTAX INTEGER
				{
				clear(1)
				}
			MAX-ACCESS read-write
			STATUS current
			DESCRIPTION
				"The object is used to clear the statistic information of a SIP gateway. 
				Note that it is significative only when this object is executed 'set' operation."
			::= { hwSIPClientMIBObjects 13 }
			
		
		hwSIPRegisterFailReason OBJECT-TYPE
			SYNTAX DisplayString
			MAX-ACCESS accessible-for-notify
			STATUS current
			DESCRIPTION
				"The object describes the reason that a SIP gateway fails to register."
			::= { hwSIPClientMIBObjects 14 }
			
		
		hwSIPAuthenticatedRequestMethord OBJECT-TYPE
			SYNTAX INTEGER
				{
				unknow(1),
				register(2),
				invite(3),
				ack(4),
				prack(5),
				cancel(6),
				bye(7),
				info(8)
				}
			MAX-ACCESS accessible-for-notify
			STATUS current
			DESCRIPTION
				"The object denotes the methord of a request that fails to authenticate."
			::= { hwSIPClientMIBObjects 15 }
			
		
		hwSIPStatisticObjects OBJECT IDENTIFIER ::= { hwSIPClientMIBObjects 16 }
		
		
		hwSIPRegisters OBJECT-TYPE
			SYNTAX Integer32
			MAX-ACCESS read-only
			STATUS current
			DESCRIPTION
				"The number of REGISTERs which a SIP gateway has received and sent."
			::= { hwSIPStatisticObjects 1 }
			
		
		hwSIPInvites OBJECT-TYPE
			SYNTAX Integer32
			MAX-ACCESS read-only
			STATUS current
			DESCRIPTION
				"The number of INVITEs which a SIP gateway has received and sent."
			::= { hwSIPStatisticObjects 2 } 
			
		
		hwSIPAcks OBJECT-TYPE
			SYNTAX Integer32
			MAX-ACCESS read-only
			STATUS current
			DESCRIPTION
				"The number of ACKs which a SIP gateway has received and sent."
			::= { hwSIPStatisticObjects 3 }
			
			
		hwSIPPracks OBJECT-TYPE
			SYNTAX Integer32
			MAX-ACCESS read-only
			STATUS current
			DESCRIPTION
				"The number of PRACKs which a SIP gateway has received and sent."
			::= { hwSIPStatisticObjects 4 }
			
		hwSIPByes OBJECT-TYPE
			SYNTAX Integer32
			MAX-ACCESS read-only
			STATUS current
			DESCRIPTION
				"The number of BYEs which a SIP gateway has received and sent."
			::= { hwSIPStatisticObjects 5 }
			
			
		hwSIPCancels OBJECT-TYPE
			SYNTAX Integer32
			MAX-ACCESS read-only
			STATUS current
			DESCRIPTION
				"The number of CANCELs which a SIP gateway has received and sent."
			::= { hwSIPStatisticObjects 6 }
			
		hwSIPInfos OBJECT-TYPE
			SYNTAX Integer32
			MAX-ACCESS read-only
			STATUS current
			DESCRIPTION
				"The number of INFOs which a SIP gateway has received and sent."
			::= { hwSIPStatisticObjects 7 }
			
			
		hwSIPOKRegisters OBJECT-TYPE
			SYNTAX Integer32
			MAX-ACCESS read-only
			STATUS current
			DESCRIPTION
				"The number of successful REGISTERs which a SIP gateway has received and sent."
			::= { hwSIPStatisticObjects 8 }
			
		
		hwSIPOKInvites OBJECT-TYPE
			SYNTAX Integer32
			MAX-ACCESS read-only
			STATUS current
			DESCRIPTION
				"The number of successful INVITEs which a SIP gateway has received and sent."
			::= { hwSIPStatisticObjects 9 } 
			
		
		hwSIPOKAcks OBJECT-TYPE
			SYNTAX Integer32
			MAX-ACCESS read-only
			STATUS current
			DESCRIPTION
				"The number of successful ACKs which a SIP gateway has received and sent."
			::= { hwSIPStatisticObjects 10 }
			
			
		hwSIPOKPracks OBJECT-TYPE
			SYNTAX Integer32
			MAX-ACCESS read-only
			STATUS current
			DESCRIPTION
				"The number of successful PRACKs which a SIP gateway has received and sent."
			::= { hwSIPStatisticObjects 11 }
			
		hwSIPOKByes OBJECT-TYPE
			SYNTAX Integer32
			MAX-ACCESS read-only
			STATUS current
			DESCRIPTION
				"The number of successful BYEs which a SIP gateway has received and sent."
			::= { hwSIPStatisticObjects 12 }
			
			
		hwSIPOKCancels OBJECT-TYPE
			SYNTAX Integer32
			MAX-ACCESS read-only
			STATUS current
			DESCRIPTION
				"The number of successful CANCELs which a SIP gateway has received and sent."
			::= { hwSIPStatisticObjects 13 }
			
		hwSIPOKInfos OBJECT-TYPE
			SYNTAX Integer32
			MAX-ACCESS read-only
			STATUS current
			DESCRIPTION
				"The number of successful INFOs which a SIP gateway has received and sent."
			::= { hwSIPStatisticObjects 14 }
			
		
		hwSIPResp3MultipleChoice OBJECT-TYPE
			SYNTAX Integer32
			MAX-ACCESS read-only
			STATUS current
			DESCRIPTION
				"The number of  300(Mutiple Choices) responses which a SIP gateway has received."
			::= { hwSIPStatisticObjects 15 }
			
			
		hwSIPResp3MovedPermanently OBJECT-TYPE
			SYNTAX Integer32
			MAX-ACCESS read-only
			STATUS current
			DESCRIPTION
				"The number of  301(Moved Permanently) responses which a SIP gateway has received."
			::= { hwSIPStatisticObjects 16 }
			
			
		hwSIPResp3MovedTemporarily OBJECT-TYPE
			SYNTAX Integer32
			MAX-ACCESS read-only
			STATUS current
			DESCRIPTION
				"The number of 302(Moved Temporarily) responses which a SIP gateway has received."
			::= { hwSIPStatisticObjects 17 } 
			
		
		hwSIPResp3UseProxy OBJECT-TYPE
			SYNTAX Integer32
			MAX-ACCESS read-only
			STATUS current
			DESCRIPTION
				"The number of 305(Use Proxy) responses which a SIP gateway has received."
			::= { hwSIPStatisticObjects 18 }
			                                
			                                
		hwSIPResp3Other OBJECT-TYPE
			SYNTAX Integer32
			MAX-ACCESS read-only
			STATUS current
			DESCRIPTION
				"The number of other 3xx responses which a SIP gateway has received."
			::= { hwSIPStatisticObjects 19 }
			
			
		hwSIPResp4BadRequest OBJECT-TYPE
			SYNTAX Integer32
			MAX-ACCESS read-only
			STATUS current
			DESCRIPTION
				"The number of 400(Use Proxy) responses which a SIP gateway has received."
			::= { hwSIPStatisticObjects 20 }
			
			
		hwSIPResp4Unauthorized OBJECT-TYPE
			SYNTAX Integer32
			MAX-ACCESS read-only
			STATUS current
			DESCRIPTION
				"The number of 401(Unauthorized) responses which a SIP gateway has received."
			::= { hwSIPStatisticObjects 21 }
			
		
		hwSIPResp4Forbidden OBJECT-TYPE
			SYNTAX Integer32
			MAX-ACCESS read-only
			STATUS current
			DESCRIPTION
				"The number of 403(Forbidden) responses which a SIP gateway has received."
			::= { hwSIPStatisticObjects 22 }
			
			
		hwSIPResp4NotFound OBJECT-TYPE
			SYNTAX Integer32
			MAX-ACCESS read-only
			STATUS current
			DESCRIPTION
				"The number of 404(Not Found) responses which a SIP gateway has received."
			::= { hwSIPStatisticObjects 23 }
			
			
		hwSIPResp4MethodNotAllowed OBJECT-TYPE
			SYNTAX Integer32
			MAX-ACCESS read-only
			STATUS current
			DESCRIPTION
				"The number of 405(Methord Not Allowed) responses which a SIP gateway has received."
			::= { hwSIPStatisticObjects 24 }
			
			
		hwSIPResp4NotAcceptable OBJECT-TYPE
			SYNTAX Integer32
			MAX-ACCESS read-only
			STATUS current
			DESCRIPTION
				"The number of 406(Not Acceptable) responses which a SIP gateway has received."
			::= { hwSIPStatisticObjects 25 }
			
			
		hwSIPResp4ProxyAuthRequired OBJECT-TYPE
			SYNTAX Integer32
			MAX-ACCESS read-only
			STATUS current
			DESCRIPTION
				"The number of 407(Proxy Authentication Required) responses which a SIP gateway has received."
			::= { hwSIPStatisticObjects 26 }
			
			
		hwSIPResp4ReqTimeout OBJECT-TYPE
			SYNTAX Integer32
			MAX-ACCESS read-only
			STATUS current
			DESCRIPTION
				"The number of 408(Request Timeout) responses which a SIP gateway has received."
			::= { hwSIPStatisticObjects 27 }
			
			
		hwSIPResp4ReqEntityTooLarge OBJECT-TYPE
			SYNTAX Integer32
			MAX-ACCESS read-only
			STATUS current
			DESCRIPTION
				"The number of 413(Request Entity Too Large) responses which a SIP gateway has received."
			::= { hwSIPStatisticObjects 28 }
			
			
		hwSIPResp4ReqURITooLarge OBJECT-TYPE
			SYNTAX Integer32
			MAX-ACCESS read-only
			STATUS current
			DESCRIPTION
				"The number of 414(Request-URI Too Long) responses which a SIP gateway has received."
			::= { hwSIPStatisticObjects 29 }
			
			
		hwSIPResp4UnsupportedMediaType OBJECT-TYPE
			SYNTAX Integer32
			MAX-ACCESS read-only
			STATUS current
			DESCRIPTION
				"The number of 415(Unsupported Media Type) responses which a SIP gateway has received."
			::= { hwSIPStatisticObjects 30 }
			
			
		hwSIPResp4UnsupportedURIScheme OBJECT-TYPE
			SYNTAX Integer32
			MAX-ACCESS read-only
			STATUS current
			DESCRIPTION
				"The number of 416(Unsupported URI Scheme) responses which a SIP gateway has received."
			::= { hwSIPStatisticObjects 31 }
			
			
		hwSIPResp4BadExtension OBJECT-TYPE
			SYNTAX Integer32
			MAX-ACCESS read-only
			STATUS current
			DESCRIPTION
				"The number of 420(Bad Extension) responses which a SIP gateway has received."
			::= { hwSIPStatisticObjects 32 }
			
			
		hwSIPResp4ExtensionRequired OBJECT-TYPE
			SYNTAX Integer32
			MAX-ACCESS read-only
			STATUS current
			DESCRIPTION
				"The number of 421(Extension Required) responses which a SIP gateway has received."
			::= { hwSIPStatisticObjects 33 }
			
			
		hwSIPResp4AddrIncomplete OBJECT-TYPE
			SYNTAX Integer32
			MAX-ACCESS read-only
			STATUS current
			DESCRIPTION
				"The number of 484(Address Incomplete) responses which a SIP gateway has received."
			::= { hwSIPStatisticObjects 34 }
			
			
		hwSIPResp4BusyHere OBJECT-TYPE
			SYNTAX Integer32
			MAX-ACCESS read-only
			STATUS current
			DESCRIPTION
				"The number of 486(Busy Here) responses which a SIP gateway has received."
			::= { hwSIPStatisticObjects 35 }                            
			
		
		hwSIPResp4RequestTerminated OBJECT-TYPE
			SYNTAX Integer32
			MAX-ACCESS read-only
			STATUS current
			DESCRIPTION
				"The number of 487(Request Terminated) responses which a SIP gateway has received."
			::= { hwSIPStatisticObjects 36 }                            
			
		
		hwSIPResp4Other OBJECT-TYPE
			SYNTAX Integer32
			MAX-ACCESS read-only
			STATUS current
			DESCRIPTION
				"The number of other 4xx responses which a SIP gateway has received."
			::= { hwSIPStatisticObjects 37 }                            
			
		
		hwSIPResp5InternalError OBJECT-TYPE
			SYNTAX Integer32
			MAX-ACCESS read-only
			STATUS current
			DESCRIPTION
				"The number of 500(Server Internal Error) responses which a SIP gateway has received."
			::= { hwSIPStatisticObjects 38 }                            
			
		
		hwSIPResp5NotImplemented OBJECT-TYPE
			SYNTAX Integer32
			MAX-ACCESS read-only
			STATUS current
			DESCRIPTION
				"The number of 501(Not Implemented) responses which a SIP gateway has received."
			::= { hwSIPStatisticObjects 39 }                            
			
		
		hwSIPResp5BadGateway OBJECT-TYPE
			SYNTAX Integer32
			MAX-ACCESS read-only
			STATUS current
			DESCRIPTION
				"The number of 502(Bad Gateway) responses which a SIP gateway has received."
			::= { hwSIPStatisticObjects 40 }                            
			
		
		hwSIPResp5ServiceUnavailable OBJECT-TYPE
			SYNTAX Integer32
			MAX-ACCESS read-only
			STATUS current
			DESCRIPTION
				"The number of 503(ServiceUnavailabe) responses which a SIP gateway has received."
			::= { hwSIPStatisticObjects 41 }                            
			
		
		hwSIPResp5GatewayTimeout OBJECT-TYPE
			SYNTAX Integer32
			MAX-ACCESS read-only
			STATUS current
			DESCRIPTION
				"The number of 504(Server Time-Out) responses which a SIP gateway has received."
			::= { hwSIPStatisticObjects 42 }                            
			
		
		hwSIPResp5BadSipVersion OBJECT-TYPE
			SYNTAX Integer32
			MAX-ACCESS read-only
			STATUS current
			DESCRIPTION
				"The number of 505(Version Not Supported) responses which a SIP gateway has received."
			::= { hwSIPStatisticObjects 43 }                            
			
		
		hwSIPResp5MessageTooLarge OBJECT-TYPE
			SYNTAX Integer32
			MAX-ACCESS read-only
			STATUS current
			DESCRIPTION
				"The number of 513(Message Too Large) responses which a SIP gateway has received."
			::= { hwSIPStatisticObjects 44 }                            
			
		
		hwSIPResp5Other OBJECT-TYPE
			SYNTAX Integer32
			MAX-ACCESS read-only
			STATUS current
			DESCRIPTION
				"The number of other 5xx responses which a SIP gateway has received."
			::= { hwSIPStatisticObjects 45 }                            
			
		
		hwSIPResp6xx OBJECT-TYPE
			SYNTAX Integer32
			MAX-ACCESS read-only
			STATUS current
			DESCRIPTION
				"The number of 6xx responses which a SIP gateway has received."
			::= { hwSIPStatisticObjects 46 }                            
			
		
		hwSIPServerConfigTable OBJECT-TYPE
			SYNTAX SEQUENCE OF SIPServerConfigEntry
			MAX-ACCESS not-accessible
			STATUS current
			DESCRIPTION
				"A list of the SIP server configuration entries."
			::= { hwSIPClientMIBObjects 21 }

		
		hwSIPServerConfigEntry OBJECT-TYPE
			SYNTAX SIPServerConfigEntry
			MAX-ACCESS not-accessible
			STATUS current
			DESCRIPTION
				"A SIP server configuration entry contains some associated information,
				e.g. IP address, port, etc.."
			INDEX { hwSIPServerIPAddress, hwSIPServerPort }
			::= { hwSIPServerConfigTable 1 }

		
		SIPServerConfigEntry ::=
			SEQUENCE { 
				hwSIPServerIPAddress
					IpAddress,
				hwSIPServerPort
					Integer32,
				hwSIPServerType
					INTEGER,
				hwSIPAcceptType
					INTEGER,
				hwSIPServerStatus
					RowStatus
			 }
           
        
		hwSIPServerIPAddress OBJECT-TYPE
			SYNTAX IpAddress
			MAX-ACCESS read-create
			STATUS current
			DESCRIPTION
				"The IP address of a SIP server."
			::= { hwSIPServerConfigEntry 1 }
			
		hwSIPServerPort OBJECT-TYPE
			SYNTAX Integer32
			MAX-ACCESS read-create
			STATUS current
			DESCRIPTION
				"The port of a SIP server. By default, the object value is 5060."
			DEFVAL { 5060 }
			::= { hwSIPServerConfigEntry 2 }

		
		hwSIPServerType OBJECT-TYPE
			SYNTAX INTEGER
				{
				master(1),
				slaver(2)
				}
			MAX-ACCESS read-create
			STATUS current
			DESCRIPTION
				"The type of SIP Server. By default, the object value is master(1)."
			DEFVAL { 1 }
			::= { hwSIPServerConfigEntry 3 }
			
			
		hwSIPAcceptType OBJECT-TYPE
			SYNTAX INTEGER
				{
				inbound(1),
				all(2)
				}
			MAX-ACCESS read-create
			STATUS current
			DESCRIPTION
				"The accept type of SIP calls. By default, the object value is all(2)."
			DEFVAL { 2 }
			::= { hwSIPServerConfigEntry 4 }

		
		hwSIPServerStatus OBJECT-TYPE
			SYNTAX RowStatus
			MAX-ACCESS read-create
			STATUS current
			DESCRIPTION
				"The status of this SIP Server entry."
			::= { hwSIPServerConfigEntry 5 }

		
		hwSIPClientNotifications OBJECT IDENTIFIER ::= { hwSIPClientMIB 2 }

		
		hwSIPRegisterFailure NOTIFICATION-TYPE
			OBJECTS { hwSIPServerIPAddress, hwSIPServerPort, hwSIPRegisterFailReason, hwSIPID }
			STATUS current
			DESCRIPTION 
				"The trap is generated when a SIP gateway fails to register."
			::= { hwSIPClientNotifications 1 } 
			
		
		hwSIPAuthenticateFailure NOTIFICATION-TYPE
			OBJECTS { hwSIPID, hwSIPAuthenticatedRequestMethord }
			STATUS current
			DESCRIPTION 
				"The trap is generated when a requests with its credential fail to authenticate."
			::= { hwSIPClientNotifications 2 }
			
		
		hwSIPServerSwitch NOTIFICATION-TYPE
			STATUS current
			DESCRIPTION 
				"The trap is generated when a switch happens between master and slaver SIP server."
			::= { hwSIPClientNotifications 3 }
		
	
	END
