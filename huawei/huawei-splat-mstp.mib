-- ==================================================================
-- Copyright (C) 2002 by  HUAWEI TECHNOLOGIES. All rights reserved.
--
-- Description: HUAWEI Lan Switch MSTP MIB
-- Reference:
-- Version: V1.14
-- History:
--      v1.0 (1) Created by Zhang Shilin, 2001.6.29
--           (2) Revised by Qi Zhenglin, 2002.01.08
--      v1.01 2004-7-13 remove default value
--         of hwdot1sMstDefaultVlanAllo & hwdot1sMstDefaultRegionName
--      v1.02 2004-08-19 Revised by Song Jianyong,
--            add hwdot1sStpPathCostStandard in mstp global table
--      v1.1 2004-10-12 updated by gaolong
--           Import OBJECT-IDENTITY, NOTIFICATION-TYPE, TEXTUAL-CONVENTION.
--           Import dot1dStpPort.
--           Relocate hwdot1sMstp MODULE-IDENTITY clause.
--           Fix default value errors for hwdot1sMstBpduGuard, hwdot1sMstiStpPortEdgeport,
--           hwdot1sMstiStpStatus, hwdot1sMstiPortRootGuard, hwdot1sMstiPortLoopGuard.
--      v1.11 2004-10-23 Revised by Song Jianyong,
--            modify the range of hwdot1sMstiPathCost value in hwdot1sPortTable
--      v1.12 2005-01-22 Revised by Song Jianyong,
--            Add an enumeration for hwdot1sStpForceVersion in mstp global table
--            Add an enumeration for hwdot1sStpPathCostStandard in hwdot1sPortTable
--            Adjust format of objects' description
--     V1.13 2005-6-30 Updated by zhanghaihong
--            add hwdot1sMstiStpPortSendingBPDUType, hwdot1sMstiStpOperPortPointToPoint
--            in hwdot1sPortTable
--     V1.14 2005-11-07 Updated by zhanghaihong
--            Modify the description of hwdot1sMstiStpOperPortPointToPoint in
--            hwdot1sPortTable.
--            Add hwdot1sMstiStpPortAdminBPDUFmt, hwdot1sMstiStpPortOperBPDUFmt
--            in hwdot1sPortTable.
-- ==================================================================
-- ==================================================================
--
-- Varibles and types be imported
--
-- ==================================================================
-- ------------------------------------------------------------------
-- ------------------------------------------------------------------
HUAWEI-LswMSTP-MIB DEFINITIONS ::= BEGIN

IMPORTS

    MODULE-IDENTITY,OBJECT-TYPE,Counter32, OBJECT-IDENTITY, NOTIFICATION-TYPE
        FROM SNMPv2-SMI
    TEXTUAL-CONVENTION
        FROM SNMPv2-TC
    dot1dStpPortEntry, dot1dStpPort
        FROM BRIDGE-MIB
    lswCommon
        FROM HUAWEI-3COM-OID-MIB;

    hwdot1sMstp MODULE-IDENTITY
            LAST-UPDATED "200106290000Z"
            ORGANIZATION ""
            CONTACT-INFO
            ""
            DESCRIPTION
            ""
            REVISION "200106290000Z"
            DESCRIPTION
            ""
            ::= { lswCommon  14 }

    EnabledStatus ::= TEXTUAL-CONVENTION
    STATUS      current
    DESCRIPTION
        "A simple status value for the object."
    SYNTAX      INTEGER { enabled(1), disabled(2) }

    BridgeId ::= OCTET STRING (SIZE (8))

    Hwdot1sFormatStatus ::= TEXTUAL-CONVENTION
    STATUS      current
    DESCRIPTION
        "Legacy means that the BPDU format is legacy.  Dot1s means that the
        BPDU format is IEEE 802.1s.  Auto means that the format of BPDU sending
        on the port is determined by the BPDU format of its connective port."
    SYNTAX      INTEGER { legacy(1), dot1s(2), auto(3) }


  hwdot1sStpStatus OBJECT-TYPE
    SYNTAX      EnabledStatus
    MAX-ACCESS  read-write
    STATUS      current
    DESCRIPTION
      "Whether the Bridge MSTP is enabled."
    DEFVAL      { 2 }
    ::= { hwdot1sMstp 1 }

  hwdot1sStpForceVersion OBJECT-TYPE
    SYNTAX      INTEGER{stp(0),rstp(2),mstp(3)}
    MAX-ACCESS  read-write
    STATUS      current
    DESCRIPTION
      " The mode of this Bridge spanning-tree protocol."
    DEFVAL      { mstp}
    ::= { hwdot1sMstp 2 }

  hwdot1sStpDiameter OBJECT-TYPE
    SYNTAX      INTEGER(2..7)
    MAX-ACCESS  read-write
    STATUS      current
    DESCRIPTION
      "The diameter of Bridge."
    DEFVAL      { 7 }
    ::= { hwdot1sMstp 3 }

  hwdot1sMstBridgeMaxHops OBJECT-TYPE
    SYNTAX      INTEGER(1..40)
    MAX-ACCESS  read-write
    STATUS      current
    DESCRIPTION
      "The maximum value of the  Bridge hops."
    DEFVAL      { 20}
    ::= { hwdot1sMstp 4 }

  hwdot1sMstMasterBridgeID OBJECT-TYPE
    SYNTAX      BridgeId
    MAX-ACCESS  read-only
    STATUS      current
    DESCRIPTION
      "The Bridge Identifier of the current Master Bridge."
    ::= { hwdot1sMstp 5 }

  hwdot1sMstMasterPathCost OBJECT-TYPE
    SYNTAX      INTEGER
    MAX-ACCESS  read-only
    STATUS      current
    DESCRIPTION
      "The CIST path cost from the transmitting Bridge to the Master Bridge."
    DEFVAL      { 0}
    ::= { hwdot1sMstp 6 }

  hwdot1sMstBpduGuard OBJECT-TYPE
    SYNTAX      EnabledStatus
    MAX-ACCESS  read-write
    STATUS      current
    DESCRIPTION
      "Whether the Bridge BPDU Guard function is enabled. If the function
      is enabled, the port will shutdown when received BPDU and the port
      is configured as portfast."
    DEFVAL      { disabled}
    ::= { hwdot1sMstp 7 }

  hwdot1sMstAdminFormatSelector OBJECT-TYPE
    SYNTAX      INTEGER
    MAX-ACCESS  read-write
    STATUS      current
    DESCRIPTION
      "The administrative Configuration Identifier Format Selector in use
      by the Bridge. This has a value of 0 indicate the format specified
      in the Standard of IEEE 802.1s."
    DEFVAL      { 0}
    ::= { hwdot1sMstp 8 }

  hwdot1sMstAdminRegionName OBJECT-TYPE
    SYNTAX      OCTET STRING(SIZE(1..32))
    MAX-ACCESS  read-write
    STATUS      current
    DESCRIPTION
      "This MSTP administrative region name."
    ::= { hwdot1sMstp 9 }

  hwdot1sMstAdminRevisionLevel OBJECT-TYPE
    SYNTAX      INTEGER(0..65535)
    MAX-ACCESS  read-write
    STATUS      current
    DESCRIPTION
      "This MSTP administrative revision level."
    DEFVAL      { 0}
    ::= { hwdot1sMstp 10 }

  hwdot1sMstOperFormatSelector OBJECT-TYPE
    SYNTAX      INTEGER
    MAX-ACCESS  read-only
    STATUS      current
    DESCRIPTION
      "The operative Configuration Identifier Format Selector in use by the
      Bridge. This has a value of 0 indicate the format specified in the
      Standard of IEEE 802.1s."
    DEFVAL      { 0}
    ::= { hwdot1sMstp 11 }

  hwdot1sMstOperRegionName OBJECT-TYPE
    SYNTAX      OCTET STRING( SIZE(0..32) )
    MAX-ACCESS  read-only
    STATUS      current
    DESCRIPTION
      "This MSTP operative region name."
    ::= { hwdot1sMstp 12 }

  hwdot1sMstOperRevisionLevel OBJECT-TYPE
    SYNTAX      INTEGER(0..65535)
    MAX-ACCESS  read-only
    STATUS      current
    DESCRIPTION
      "This MSTP operative revision level."
    DEFVAL      { 0}
    ::= { hwdot1sMstp 13 }

  hwdot1sMstOperConfigDigest OBJECT-TYPE
    SYNTAX      OCTET STRING(SIZE(0..16))
    MAX-ACCESS  read-only
    STATUS      current
    DESCRIPTION
      "This MSTP Region's Configuration Digest Signature Key."
    ::= { hwdot1sMstp 14 }

  hwdot1sMstRegionConfActive OBJECT-TYPE
    SYNTAX      INTEGER{enable(1),disable(2)}
    MAX-ACCESS  read-write
    STATUS      current
    DESCRIPTION
      "Active the region configuration."
    DEFVAL      { disable }
    ::= { hwdot1sMstp 15 }

  hwdot1sMstDefaultVlanAllo OBJECT-TYPE
    SYNTAX      INTEGER{enable(1),unused(65535)}
    MAX-ACCESS  read-write
    STATUS      current
    DESCRIPTION
      "Set default configuration about VLAN allocation and all VLANs
      are mapped to CIST."
    ::= { hwdot1sMstp 16 }

  hwdot1sMstDefaultRegionName OBJECT-TYPE
    SYNTAX      INTEGER{enable(1),unused(65535)}
    MAX-ACCESS  read-write
    STATUS      current
    DESCRIPTION
      "Set default region name."
    ::= { hwdot1sMstp 17 }

-- TABLE: hwdot1sVIDAllocationTable ------
  hwdot1sVIDAllocationTable OBJECT-TYPE
    SYNTAX      SEQUENCE OF Hwdot1sVIDAllocationEntry
    MAX-ACCESS  not-accessible
    STATUS      current
    DESCRIPTION
      ""
    ::= { hwdot1sMstp 18 }

  hwdot1sVIDAllocationEntry OBJECT-TYPE
    SYNTAX      Hwdot1sVIDAllocationEntry
    MAX-ACCESS  not-accessible
    STATUS      current
    DESCRIPTION
      ""
    INDEX {
              hwdot1sMstVID
             }
    ::= { hwdot1sVIDAllocationTable 1 }

  Hwdot1sVIDAllocationEntry ::=
    SEQUENCE
    {
      hwdot1sMstVID INTEGER,
      hwdot1sAdminMstID INTEGER,
      hwdot1sOperMstID  INTEGER
    }

  hwdot1sMstVID OBJECT-TYPE
    SYNTAX      INTEGER(1..4094)
    MAX-ACCESS  read-only
    STATUS      current
    DESCRIPTION
        "VLAN Identifier"
    ::= { hwdot1sVIDAllocationEntry 1 }

  hwdot1sAdminMstID OBJECT-TYPE
    SYNTAX      INTEGER(0..64)
    MAX-ACCESS  read-write
    STATUS      current
    DESCRIPTION
        "Administrative Multiple spanning-tree instance Identifier."
    ::= { hwdot1sVIDAllocationEntry 2 }

  hwdot1sOperMstID OBJECT-TYPE
    SYNTAX      INTEGER(0..64)
    MAX-ACCESS  read-only
    STATUS      current
    DESCRIPTION
        "Operative Multiple spanning-tree instance Identifier."
    ::= { hwdot1sVIDAllocationEntry 3 }

-- TABLE: hwdot1sInstanceTable ------
  hwdot1sInstanceTable OBJECT-TYPE
    SYNTAX      SEQUENCE OF Hwdot1sInstanceEntry
    MAX-ACCESS  not-accessible
    STATUS      current
    DESCRIPTION
      ""
    ::= { hwdot1sMstp 19 }

  hwdot1sInstanceEntry OBJECT-TYPE
    SYNTAX      Hwdot1sInstanceEntry
    MAX-ACCESS  not-accessible
    STATUS      current
    DESCRIPTION
      ""
    INDEX {
              hwdot1sInstanceID
             }
    ::= { hwdot1sInstanceTable 1 }

  Hwdot1sInstanceEntry ::=
    SEQUENCE
    {
      hwdot1sInstanceID INTEGER,
      hwdot1sMstiBridgeID   BridgeId,
      hwdot1sMstiBridgePriority INTEGER,
      hwdot1sMstiDesignedRoot   BridgeId,
      hwdot1sMstiRootPathCost   INTEGER,
      hwdot1sMstiRootPort   INTEGER,
      hwdot1sMstiRootType   INTEGER,
      hwdot1sMstiRemainingHops  INTEGER,
      hwdot1sMstiAdminMappedVlanListLow OCTET STRING,
      hwdot1sMstiAdminMappedVlanListHigh OCTET STRING,
      hwdot1sMstiOperMappedVlanListLow OCTET STRING,
      hwdot1sMstiOperMappedVlanListHigh OCTET STRING
    }

  hwdot1sInstanceID OBJECT-TYPE
    SYNTAX      INTEGER(0..64)
    MAX-ACCESS  read-only
    STATUS      current
    DESCRIPTION
        "Multiple spanning-tree instance Identifier"
    ::= { hwdot1sInstanceEntry 1 }

  hwdot1sMstiBridgeID OBJECT-TYPE
    SYNTAX      BridgeId
    MAX-ACCESS  read-only
    STATUS      current
    DESCRIPTION
        "The Bridge Identifier for the spanning tree instance
        identified by MSTID"
    ::= { hwdot1sInstanceEntry 2 }

  hwdot1sMstiBridgePriority OBJECT-TYPE
    SYNTAX      INTEGER(0..61440)
    MAX-ACCESS  read-write
    STATUS      current
    DESCRIPTION
        "The Bridge Priority for the spanning tree instance
        identified by MSTID. Step of 4096"
    DEFVAL      { 32768 }
    ::= { hwdot1sInstanceEntry 3 }

  hwdot1sMstiDesignedRoot OBJECT-TYPE
    SYNTAX      BridgeId
    MAX-ACCESS  read-only
    STATUS      current
    DESCRIPTION
        "The Bridge Identifier of the Root Bridge for the spanning
        tree instance identified by MSTID"
    ::= { hwdot1sInstanceEntry 4 }

  hwdot1sMstiRootPathCost OBJECT-TYPE
    SYNTAX      INTEGER
    MAX-ACCESS  read-only
    STATUS      current
    DESCRIPTION
        "The path cost from the transmitting Bridge to the Root Bridge
        for the spanning tree instance  identified by MSTID"
    ::= { hwdot1sInstanceEntry 5 }

  hwdot1sMstiRootPort OBJECT-TYPE
    SYNTAX      INTEGER
    MAX-ACCESS  read-only
    STATUS      current
    DESCRIPTION
        "The Root Port for the spanning tree instance identified by the MSTID"
    ::= { hwdot1sInstanceEntry 6 }

  hwdot1sMstiRootType OBJECT-TYPE
    SYNTAX      INTEGER{normal(0), secondary(1), primary(2)}
    MAX-ACCESS  read-write
    STATUS      current
    DESCRIPTION
        "Config this Bridge as a primary root or seconary root and or cancel
        the root for this spanning tree instance  identified by MSTID"
    DEFVAL      { normal }
    ::= { hwdot1sInstanceEntry 7 }

  hwdot1sMstiRemainingHops OBJECT-TYPE
    SYNTAX      INTEGER
    MAX-ACCESS  read-only
    STATUS      current
    DESCRIPTION
        "The remaining hops of the spanning tree instance  identified by MSTID"
    ::= { hwdot1sInstanceEntry 8 }

  hwdot1sMstiAdminMappedVlanListLow  OBJECT-TYPE
    SYNTAX  OCTET STRING (SIZE(0..256))
    MAX-ACCESS read-only
    STATUS current
    DESCRIPTION
        " The lower part of administrative Vlan list mapped to the spanning
        tree instance identified by MSTID"
    ::= { hwdot1sInstanceEntry 9 }

  hwdot1sMstiAdminMappedVlanListHigh  OBJECT-TYPE
    SYNTAX  OCTET STRING (SIZE(0..256))
    MAX-ACCESS read-only
    STATUS current
    DESCRIPTION
        " The higher part of administrative Vlan  list mapped to the spanning
        tree instance identified by MSTID"
    ::= { hwdot1sInstanceEntry 10 }

  hwdot1sMstiOperMappedVlanListLow  OBJECT-TYPE
    SYNTAX  OCTET STRING (SIZE(0..256))
    MAX-ACCESS read-only
    STATUS current
    DESCRIPTION
        " The lower part of operative Vlan list mapped to the spanning
        tree instance identified by MSTID"
    ::= { hwdot1sInstanceEntry 11 }

  hwdot1sMstiOperMappedVlanListHigh  OBJECT-TYPE
    SYNTAX  OCTET STRING (SIZE(0..256))
    MAX-ACCESS read-only
    STATUS current
    DESCRIPTION
        " The higher part of operative Vlan list mapped to the spanning
        tree instance identified by MSTID"
    ::= { hwdot1sInstanceEntry 12 }

-- TABLE: hwdot1sPortTable ------
  hwdot1sPortTable OBJECT-TYPE
    SYNTAX      SEQUENCE OF Hwdot1sPortEntry
    MAX-ACCESS  not-accessible
    STATUS      current
    DESCRIPTION
      ""
    ::= { hwdot1sMstp 20 }

  hwdot1sPortEntry OBJECT-TYPE
    SYNTAX      Hwdot1sPortEntry
    MAX-ACCESS  not-accessible
    STATUS      current
    DESCRIPTION
      ""
    INDEX {   hwdot1sInstanceID,
              hwdot1sMstiPortIndex
             }
    ::= { hwdot1sPortTable 1 }

  Hwdot1sPortEntry ::=
    SEQUENCE
    {
      hwdot1sMstiPortIndex  INTEGER,
      hwdot1sMstiState  INTEGER,
      hwdot1sMstiPortPriority   INTEGER,
      hwdot1sMstiPathCost   INTEGER,
      hwdot1sMstiDesignatedRoot BridgeId,
      hwdot1sMstiDesignatedCost INTEGER,
      hwdot1sMstiDesignatedBridge   BridgeId,
      hwdot1sMstiDesignatedPort OCTET STRING,
      hwdot1sMstiMasterBridgeID BridgeId,
      hwdot1sMstiMasterPortCost INTEGER,
      hwdot1sMstiStpPortEdgeport    EnabledStatus,
      hwdot1sMstiStpPortPointToPoint    INTEGER,
      hwdot1sMstiStpMcheck  INTEGER,
      hwdot1sMstiStpTransLimit  INTEGER,
      hwdot1sMstiStpRXStpBPDU   Counter32,
      hwdot1sMstiStpTXStpBPDU   Counter32,
      hwdot1sMstiStpRXTCNBPDU   Counter32,
      hwdot1sMstiStpTXTCNBPDU   Counter32,
      hwdot1sMstiStpRXRSTPBPDU  Counter32,
      hwdot1sMstiStpTXRSTPBPDU  Counter32,
      hwdot1sMstiStpRXMSTPBPDU  Counter32,
      hwdot1sMstiStpTXMSTPBPDU  Counter32,
      hwdot1sMstiStpClearStatistics INTEGER,
      hwdot1sMstiStpDefaultPortCost INTEGER,
      hwdot1sMstiStpStatus  EnabledStatus,
      hwdot1sMstiPortRootGuard  EnabledStatus,
      hwdot1sMstiPortLoopGuard  EnabledStatus,
      hwdot1sMstiStpPortSendingBPDUType  INTEGER,
      hwdot1sMstiStpOperPortPointToPoint INTEGER,
      hwdot1sMstiStpPortAdminBPDUFmt  Hwdot1sFormatStatus,
      hwdot1sMstiStpPortOperBPDUFmt  Hwdot1sFormatStatus
    }

  hwdot1sMstiPortIndex OBJECT-TYPE
    SYNTAX      INTEGER
    MAX-ACCESS  read-only
    STATUS      current
    DESCRIPTION
        "The index of the Bridge Port"
    ::= { hwdot1sPortEntry 1 }

  hwdot1sMstiState OBJECT-TYPE
    SYNTAX      INTEGER{disabled(1),discarding(2),learning(4),forwarding(5)}
    MAX-ACCESS  read-only
    STATUS      current
    DESCRIPTION
        "The current state of the Port (i.e., Disabled, Discarding ,
        Learning, Forwarding)"
    ::= { hwdot1sPortEntry 2 }

  hwdot1sMstiPortPriority OBJECT-TYPE
    SYNTAX      INTEGER(0..240)
    MAX-ACCESS  read-write
    STATUS      current
    DESCRIPTION
        "The value of the priority field which is contained in the
        first (in network byte order)  four bits of the (2 octet long) Port ID.
        The other octet of the Port ID is given by the value of mstiPortIndex.
        And step of 16"
    DEFVAL      { 128 }
    ::= { hwdot1sPortEntry 3 }

  hwdot1sMstiPathCost OBJECT-TYPE
    SYNTAX      INTEGER(1..200000000)
    MAX-ACCESS  read-write
    STATUS      current
    DESCRIPTION
        "The contribution of this port to the path cost of paths towards the
        spanning tree root which include this port. The range of path cost
        is 1..65535 for 802.1d standard, is 1..200000000 for 802.1t standard,
        and is 1..200000 for the legacy standard. "
    ::= { hwdot1sPortEntry 4 }

  hwdot1sMstiDesignatedRoot OBJECT-TYPE
    SYNTAX      BridgeId
    MAX-ACCESS  read-only
    STATUS      current
    DESCRIPTION
        "The Bridge Identifier of the Root Bridge for the port of the Spanning
         Tree instance identified by the MSTID"
    ::= { hwdot1sPortEntry 5 }

  hwdot1sMstiDesignatedCost OBJECT-TYPE
    SYNTAX      INTEGER
    MAX-ACCESS  read-only
    STATUS      current
    DESCRIPTION
        "The path cost of the Designated Port of the segment connected to
        this port.  This value is compared to the Root Path Cost field
        in received bridge PDUs."
    ::= { hwdot1sPortEntry 6 }

  hwdot1sMstiDesignatedBridge OBJECT-TYPE
    SYNTAX      BridgeId
    MAX-ACCESS  read-only
    STATUS      current
    DESCRIPTION
        "The Bridge Identifier of the bridge which this port considers to
        be the Designated Bridge for this port's segment."
    ::= { hwdot1sPortEntry 7 }

  hwdot1sMstiDesignatedPort OBJECT-TYPE
    SYNTAX      OCTET STRING(SIZE (2))
    MAX-ACCESS  read-only
    STATUS      current
    DESCRIPTION
        "The Port Identifier of the port on the Designated Bridge
        for this port's segment."
    ::= { hwdot1sPortEntry 8 }

  hwdot1sMstiMasterBridgeID OBJECT-TYPE
    SYNTAX      BridgeId
    MAX-ACCESS  read-only
    STATUS      current
    DESCRIPTION
        "The Bridge Idnetifier of the current Master Bridge.
        Effective in CIST."
    ::= { hwdot1sPortEntry 9 }

  hwdot1sMstiMasterPortCost OBJECT-TYPE
    SYNTAX      INTEGER
    MAX-ACCESS  read-only
    STATUS      current
    DESCRIPTION
        "The CIST path cost from the transmitting Bridge to
        the Master Bridge. Effective in CIST."
    ::= { hwdot1sPortEntry 10 }

  hwdot1sMstiStpPortEdgeport OBJECT-TYPE
    SYNTAX      EnabledStatus
    MAX-ACCESS  read-write
    STATUS      current
    DESCRIPTION
        " Whether the port fast is enabled. Effective in CIST."
    DEFVAL      { disabled }
    ::= { hwdot1sPortEntry 11 }

  hwdot1sMstiStpPortPointToPoint OBJECT-TYPE
    SYNTAX      INTEGER{forceTrue (1),forceFalse (2),auto  (3)}
    MAX-ACCESS  read-write
    STATUS      current
    DESCRIPTION
        " Whether the port conects the point to point link. Effective in CIST."
    DEFVAL      { auto }
    ::= { hwdot1sPortEntry 12 }

  hwdot1sMstiStpMcheck OBJECT-TYPE
    SYNTAX      INTEGER{enable(1),unused(65535)}
    MAX-ACCESS  read-write
    STATUS      current
    DESCRIPTION
        " Forcing the state machine to send MST BPDUs in this manner
        can be used to test whether all legacy Bridges on a given LAN
        have been removed. Effective in CIST."
    ::= { hwdot1sPortEntry 13 }

  hwdot1sMstiStpTransLimit OBJECT-TYPE
    SYNTAX      INTEGER(1..255)
    MAX-ACCESS  read-write
    STATUS      current
    DESCRIPTION
        "The value used by the Port Transmit state machine to limit
        the maximum transmission rate. Effective in CIST."
    DEFVAL      { 3 }
    ::= { hwdot1sPortEntry 14 }

  hwdot1sMstiStpRXStpBPDU OBJECT-TYPE
    SYNTAX      Counter32
    MAX-ACCESS  read-only
    STATUS      current
    DESCRIPTION
        "The number of received Config BPDU. Effective in CIST."
    ::= { hwdot1sPortEntry 15 }

  hwdot1sMstiStpTXStpBPDU OBJECT-TYPE
    SYNTAX      Counter32
    MAX-ACCESS  read-only
    STATUS      current
    DESCRIPTION
        "The number of transimitted Config BPDU. Effective in CIST."
    ::= { hwdot1sPortEntry 16 }

  hwdot1sMstiStpRXTCNBPDU OBJECT-TYPE
    SYNTAX      Counter32
    MAX-ACCESS  read-only
    STATUS      current
    DESCRIPTION
        "The number of received TCN BPDU. Effective in CIST."
    ::= { hwdot1sPortEntry 17 }

  hwdot1sMstiStpTXTCNBPDU OBJECT-TYPE
    SYNTAX      Counter32
    MAX-ACCESS  read-only
    STATUS      current
    DESCRIPTION
        "The number of transimitted TCN BPDU. Effective in CIST."
    ::= { hwdot1sPortEntry 18 }

  hwdot1sMstiStpRXRSTPBPDU OBJECT-TYPE
    SYNTAX      Counter32
    MAX-ACCESS  read-only
    STATUS      current
    DESCRIPTION
        "The number of received RST BPDU. Effective in CIST."
    ::= { hwdot1sPortEntry 19 }

  hwdot1sMstiStpTXRSTPBPDU OBJECT-TYPE
    SYNTAX      Counter32
    MAX-ACCESS  read-only
    STATUS      current
    DESCRIPTION
        "The number of transimitted RST BPDU. Effective in CIST."
    ::= { hwdot1sPortEntry 20 }

  hwdot1sMstiStpRXMSTPBPDU OBJECT-TYPE
    SYNTAX      Counter32
    MAX-ACCESS  read-only
    STATUS      current
    DESCRIPTION
        "The number of received MST BPDU. Effective in CIST."
    ::= { hwdot1sPortEntry 21 }

  hwdot1sMstiStpTXMSTPBPDU OBJECT-TYPE
    SYNTAX      Counter32
    MAX-ACCESS  read-only
    STATUS      current
    DESCRIPTION
        "The number of transimitted MST BPDU. Effective in CIST."
    ::= { hwdot1sPortEntry 22 }

  hwdot1sMstiStpClearStatistics OBJECT-TYPE
    SYNTAX      INTEGER{clear(1),unused(65535)}
    MAX-ACCESS  read-write
    STATUS      current
    DESCRIPTION
        "Clear the spanning tree statistic. Effective in CIST."
    ::= { hwdot1sPortEntry 23 }

  hwdot1sMstiStpDefaultPortCost OBJECT-TYPE
    SYNTAX      INTEGER{enable(1),unused(65535)}
    MAX-ACCESS  read-write
    STATUS      current
    DESCRIPTION
        "Set default Port path cost. "
    ::= { hwdot1sPortEntry 24 }

  hwdot1sMstiStpStatus OBJECT-TYPE
    SYNTAX      EnabledStatus
    MAX-ACCESS  read-write
    STATUS      current
    DESCRIPTION
        "Whether the spanning tree protocol is enabled on this port.
        Effective in CIST."
    DEFVAL      { enabled}
    ::= { hwdot1sPortEntry 25 }

  hwdot1sMstiPortRootGuard OBJECT-TYPE
    SYNTAX      EnabledStatus
    MAX-ACCESS  read-write
    STATUS      current
    DESCRIPTION
        "Whether the root guard is enabled. Effective in CIST."
    DEFVAL      { disabled }
    ::= { hwdot1sPortEntry 26 }

  hwdot1sMstiPortLoopGuard OBJECT-TYPE
    SYNTAX      EnabledStatus
    MAX-ACCESS  read-write
    STATUS      current
    DESCRIPTION
        "Whether the loop protection is enabled. Effective in CIST."
    DEFVAL      { disabled }
    ::= { hwdot1sPortEntry 27 }

  hwdot1sMstiStpPortSendingBPDUType  OBJECT-TYPE
    SYNTAX  INTEGER {
                    stp(1),
                    rstp(2),
                    mstp(3)
                    }
    MAX-ACCESS read-only
    STATUS     current
    DESCRIPTION
        "Type of BPDU which the port is sending."
    ::= { hwdot1sPortEntry 28 }

  hwdot1sMstiStpOperPortPointToPoint  OBJECT-TYPE
    SYNTAX  INTEGER {
                    true(1),
                    false(2)
                    }
    MAX-ACCESS read-only
    STATUS current
    DESCRIPTION
        "This object indicates whether the port has connected to a
        point-to-point link or not.  The value of the node is an operative value.
        The administrative value can be read from the node
        hwdot1sMstiStpPortPointToPoint.  If the value of
        hwdot1sMstiStpPortPointToPoint is auto, the value of this node
        should be calculated by the network topology of this port.  If the
        value of hwdot1sMstiStpPortPointToPoint is forceFalse, the value of this
        node is false.  If the value of hwdot1sMstiStpPortPointToPoint is
        forceTrue, the value of this node is true."
    ::= { hwdot1sPortEntry 29 }

  hwdot1sMstiStpPortAdminBPDUFmt  OBJECT-TYPE
    SYNTAX     Hwdot1sFormatStatus
    MAX-ACCESS read-write
    STATUS     current
    DESCRIPTION
       "The value of the node is an administrative value.  Value legacy means that
       the MST BPDU format is forced to legacy.  Value dot1s means that the MST BPDU format
       is forced to IEEE 802.1s.  Value auto means that the format of MST BPDU sending
       on the port is determined by the MST BPDU that the port has received.  Effective in
       CIST."
      ::= { hwdot1sPortEntry 30 }

  hwdot1sMstiStpPortOperBPDUFmt  OBJECT-TYPE
    SYNTAX     Hwdot1sFormatStatus
    MAX-ACCESS read-only
    STATUS     current
    DESCRIPTION
      "The format of MST BPDU which the port is sending.  Value legacy means that the
      format of MST BPDU sending on the port is legacy.  Value dot1s means that the
      format of MST BPDU sending on the port is IEEE 802.1s.  Effective in CIST."
    ::= { hwdot1sPortEntry 31 }

  hwdot1sStpPathCostStandard  OBJECT-TYPE
    SYNTAX      INTEGER{legacy(0),dot1d-1998(1),dot1t(2)}
    MAX-ACCESS  read-write
    STATUS      current
    DESCRIPTION
      "Path cost standard of the bridge.  Value dot1d-1998 is
      IEEE 802.1d standard in 1998, value dot1t is IEEE 802.1t standard,
      and value legacy is a private legacy standard."
    ::= { hwdot1sMstp 21 }

--  Mstp Traps

  hwMstpEventsV2 OBJECT-IDENTITY
     STATUS      current
     DESCRIPTION "Definition point for Mstp notifications."
     ::= { hwdot1sMstp 0 }

  hwPortMstiStateForwarding NOTIFICATION-TYPE
     OBJECTS  { hwdot1sInstanceID , hwdot1sMstiPortIndex}
     STATUS   current
     DESCRIPTION
         "The SNMP trap that is generated when a port turns into
         forwarding state form other state."
     ::= { hwMstpEventsV2 1 }

  hwPortMstiStateDiscarding NOTIFICATION-TYPE
     OBJECTS  { hwdot1sInstanceID , hwdot1sMstiPortIndex}
     STATUS   current
     DESCRIPTION
         "The SNMP trap that is generated when a port turns into
         discarding state form forwarding state."
     ::= { hwMstpEventsV2 2 }


  hwBridgeLostRootPrimary NOTIFICATION-TYPE
     OBJECTS  { hwdot1sInstanceID }
     STATUS   current
     DESCRIPTION
         "The SNMP trap that is generated when the bridge is no longer
         the root bridge of the instance. Another switch with higher
         priority has already been the root bridge of the instance."
     ::= { hwMstpEventsV2 3 }

  hwPortMstiRootGuarded NOTIFICATION-TYPE
     OBJECTS  { hwdot1sInstanceID , hwdot1sMstiPortIndex}
     STATUS   current
     DESCRIPTION
         "The SNMP trap that is generated when a root-guard port
         receives a superior message on the relevant instance."
     ::= { hwMstpEventsV2 4 }

  hwPortMstiBpduGuarded NOTIFICATION-TYPE
     OBJECTS  { dot1dStpPort }
     STATUS   current
     DESCRIPTION
         "The SNMP trap that is generated when an edged port of
         the BPDU-guard switch recevies BPDU packets."
     ::= { hwMstpEventsV2 5 }

  hwPortMstiLoopGuarded NOTIFICATION-TYPE
     OBJECTS  { hwdot1sInstanceID , hwdot1sMstiPortIndex}
     STATUS   current
     DESCRIPTION
         "The SNMP trap that is generated when an Alternate-Port
         or Root-Port is aged out."
     ::= { hwMstpEventsV2 6 }

END
