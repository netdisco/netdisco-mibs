-- ==========================================================================
-- Copyright (C) 2002 by  HUAWEI TECHNOLOGIES. All rights reserved.
--
-- Description: The purpose of this MIB file is to provide the define of
--              the analog voice interface general configuration MIB of 
--              HUAWEI quidway serial router.
-- Reference:
-- Version: V2.1
-- History:
-- V1.0 Initial version
-- V2.0 2004-10-20 Updated by gaolong
--      Re-write whole MIB with SNMPv2-SMI format.
--      Modify value of hwVoAnaloglfFXOConfigPortImpedance, Capital character should be lowercase.
--      Fix DEFVAL clause value of hwVoAnalogIfFXSConfigStartMode.
--      Modify module name from 'HUAWEI-VOICE-ANALOG-IF-MIB' to 'HUAWEI-VO-ANALOG-IF-MIB'
-- V2.1 2004-11-10 Updated by gaolong
--      Change SYNTAX range of hwVoAnalogIfConfigInitialDigitTimeOut
--      and hwVoAnalogIfConfigInterDigitTimeOut from 1.120 to 1..300.
-- ==========================================================================
HUAWEI-VO-ANALOG-IF-MIB DEFINITIONS ::= BEGIN

	IMPORTS
		OBJECT-TYPE, MODULE-IDENTITY
			FROM SNMPv2-SMI
		voice
			FROM HUAWEI-3COM-OID-MIB;	
	
		
		hwVoiceAnalogInterfaceMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 3 }

		
		hwVoAnalogIfCommonObjects OBJECT IDENTIFIER ::= { hwVoiceAnalogInterfaceMIB 1 }

		
--  The Analog Voice Interface Common Group
-- The Analog Voice Interface Common Configuration Table
		hwVoAnalogIfCommonConfigTable OBJECT-TYPE
			SYNTAX SEQUENCE OF HWVoAnalogIfCommonConfigEntry
			MAX-ACCESS not-accessible
			STATUS current
			DESCRIPTION
				"The voice analog interface common configuration table contains information
				about configuration parameters for analog voice interface."
			::= { hwVoAnalogIfCommonObjects 1 }

		
		hwVoAnalogIfCommonConfigEntry OBJECT-TYPE
			SYNTAX HWVoAnalogIfCommonConfigEntry
			MAX-ACCESS not-accessible
			STATUS current
			DESCRIPTION
				"An entry in the voice analog interface common configuration table. 
				The entry is automatically created when a analog voice interface hardware is found."
			INDEX { hwVoAnalogIfConfigPortNumber }
			::= { hwVoAnalogIfCommonConfigTable 1 }

		
		HWVoAnalogIfCommonConfigEntry ::=
			SEQUENCE { 
				hwVoAnalogIfConfigPortNumber
					INTEGER,
				hwVoAnalogIfConfigPortType
					INTEGER,
				hwVoAnaloglfConfigPortImpedance
					INTEGER,
				hwVoAnalogIfConfigInitialDigitTimeOut
					INTEGER,
				hwVoAnalogIfConfigInterDigitTimeOut
					INTEGER,
				hwVoAnalogIfConfigCallDisconnect
					INTEGER
			 }

		hwVoAnalogIfConfigPortNumber OBJECT-TYPE
			SYNTAX INTEGER
			MAX-ACCESS read-only
			STATUS current
			DESCRIPTION
				"Index of voice analog interface common config table. It identify the  
				number of the voice port."
			::= { hwVoAnalogIfCommonConfigEntry 1 }

		
		hwVoAnalogIfConfigPortType OBJECT-TYPE
			SYNTAX INTEGER
				{
				fxs(1),
				fxo(2),
				em(3)
				}
			MAX-ACCESS read-only
			STATUS current
			DESCRIPTION
				"This object expresses the type of the voice analog interfaces.
				fxs : the type of the voice port is FXS.
				fxo : the type of the voice port is FXO.
				em  : the type of the voice port is E&M."
			::= { hwVoAnalogIfCommonConfigEntry 2 }

		
		hwVoAnaloglfConfigPortImpedance OBJECT-TYPE
			SYNTAX INTEGER
				{
				impedance600Real(1),
				impedanceComplex(2)
				}
			MAX-ACCESS read-only
			STATUS current
			DESCRIPTION
				"This object expresses the port impedance of voice analog interfaces.
				impedance600Real : 600 Ohms 
				           This impedance is primarily used by FXS.                          
				impedanceComplex : 200 Ohms + 680 Ohms || 100nF
				           This impedance is primarily used by FX0 and E&M."
			::= { hwVoAnalogIfCommonConfigEntry 3 }

		
		hwVoAnalogIfConfigInitialDigitTimeOut OBJECT-TYPE
			SYNTAX INTEGER (0..300)
			MAX-ACCESS read-write
			STATUS current
			DESCRIPTION
				"This object states the longgest time to wait the first input digit from 
				caller side. The default value is 10 seconds."
			DEFVAL { 10 }
			::= { hwVoAnalogIfCommonConfigEntry 4 }

		
		hwVoAnalogIfConfigInterDigitTimeOut OBJECT-TYPE
			SYNTAX INTEGER (0..300)
			MAX-ACCESS read-write
			STATUS current
			DESCRIPTION
				"This object states the longest time to wait between two input digit from
				caller side. The default value is 10 seconds."
			DEFVAL { 10 }
			::= { hwVoAnalogIfCommonConfigEntry 5 }

		
		hwVoAnalogIfConfigCallDisconnect OBJECT-TYPE
			SYNTAX INTEGER (0..120)
			MAX-ACCESS read-only
			STATUS current
			DESCRIPTION
				"This object states the time the system waits for the caller side to hang up 
				after the connect is disable. The default value is 10 seconds."
			DEFVAL { 10 }
			::= { hwVoAnalogIfCommonConfigEntry 6 }

		
		hwVoAnalogIfFXSObjects OBJECT IDENTIFIER ::= { hwVoiceAnalogInterfaceMIB 2 }

		
--  The Analog Voice Interface FXS Group
-- The Analog Voice Interface FXS Configuration Table
		hwVoAnalogIfFXSConfigTable OBJECT-TYPE
			SYNTAX SEQUENCE OF HWVoAnalogIfFXSConfigEntry
			MAX-ACCESS not-accessible
			STATUS current
			DESCRIPTION
				"The voice analog interface fxs configuration table contains information
				about configuration parameters for analog fxs voice interface."
			::= { hwVoAnalogIfFXSObjects 1 }

		
		hwVoAnalogIfFXSConfigEntry OBJECT-TYPE
			SYNTAX HWVoAnalogIfFXSConfigEntry
			MAX-ACCESS not-accessible
			STATUS current
			DESCRIPTION
				"An entry in the voice analog interface fxs configuration table. 
				The entry is automatically created when a analog fxs voice interface hardware is found."
			INDEX { hwVoAnalogIfFXSConfigPortNumber }
			::= { hwVoAnalogIfFXSConfigTable 1 }

		
		HWVoAnalogIfFXSConfigEntry ::=
			SEQUENCE { 
				hwVoAnalogIfFXSConfigPortNumber
					INTEGER,
				hwVoAnalogIfFXSConfigStartMode
					INTEGER
			 }

		hwVoAnalogIfFXSConfigPortNumber OBJECT-TYPE
			SYNTAX INTEGER
			MAX-ACCESS read-only
			STATUS current
			DESCRIPTION
				"Index of voice analog interface fxs config table. It identify the  
				number of the fxs voice port."
			::= { hwVoAnalogIfFXSConfigEntry 1 }

		
		hwVoAnalogIfFXSConfigStartMode OBJECT-TYPE
			SYNTAX INTEGER
				{
				loopStart(1),
				groundStart(2)
				}
			MAX-ACCESS read-only
			STATUS current
			DESCRIPTION
				"This object expresses the signaling type of analog fxs interface.
				The default value is loopStart."
			DEFVAL { loopStart }
			::= { hwVoAnalogIfFXSConfigEntry 2 }

		
--  The Analog Voice Interface FXS Timer Table
		hwVoAnalogIfFXSTimerTable OBJECT-TYPE
			SYNTAX SEQUENCE OF HWVoAnalogIfFXSTimerEntry
			MAX-ACCESS not-accessible
			STATUS current
			DESCRIPTION
				"The voice analog interface fxs timer table contains information
				about timer parameters for analog fxs voice interface."
			::= { hwVoAnalogIfFXSObjects 3 }

		
		hwVoAnalogIfFXSTimerEntry OBJECT-TYPE
			SYNTAX HWVoAnalogIfFXSTimerEntry
			MAX-ACCESS not-accessible
			STATUS current
			DESCRIPTION
				"An entry in the voice analog interface fxs configuration table. 
				The entry is automatically created when a analog fxs voice interface hardware is found."
			INDEX { hwVoAnalogIfFXSTimerPortNumber }
			::= { hwVoAnalogIfFXSTimerTable 1 }

		
		HWVoAnalogIfFXSTimerEntry ::=
			SEQUENCE { 
				hwVoAnalogIfFXSTimerPortNumber
					INTEGER,
				hwVoAnalogIfFXSTimerDtmf
					INTEGER,
				hwVoAnalogIfFXSTimerDtmfInterval
					INTEGER
			 }

		hwVoAnalogIfFXSTimerPortNumber OBJECT-TYPE
			SYNTAX INTEGER
			MAX-ACCESS read-only
			STATUS current
			DESCRIPTION
				"Index of voice analog interface fxs timer table. It identify the  
				number of the fxs voice port."
			::= { hwVoAnalogIfFXSTimerEntry 1 }

		
		hwVoAnalogIfFXSTimerDtmf OBJECT-TYPE
			SYNTAX INTEGER (50..500)
			MAX-ACCESS read-only
			STATUS current
			DESCRIPTION
				"This object expresses outgoing dtmf digit duration of the analog 
				fxs interface. The default value is 120 milliseconds"
			DEFVAL { 120 }
			::= { hwVoAnalogIfFXSTimerEntry 2 }

		
		hwVoAnalogIfFXSTimerDtmfInterval OBJECT-TYPE
			SYNTAX INTEGER (50..500)
			MAX-ACCESS read-only
			STATUS current
			DESCRIPTION
				"This object expresses outgoing dtmf interval duration of the analog 
				fxs interface. The default value is 120 milliseconds"
			DEFVAL { 120 }
			::= { hwVoAnalogIfFXSTimerEntry 3 }

		
		hwVoAnalogIfFXOObjects OBJECT IDENTIFIER ::= { hwVoiceAnalogInterfaceMIB 3 }

		
--  The Analog Voice Interface FXO Group
-- The Analog Voice Interface FXO Configuration Table
		hwVoAnalogIfFXOConfigTable OBJECT-TYPE
			SYNTAX SEQUENCE OF HWVoAnalogIfFXOConfigEntry
			MAX-ACCESS not-accessible
			STATUS current
			DESCRIPTION
				"The voice analog interface fxo configuration table contains information
				about configuration parameters for analog fxo voice interface."
			::= { hwVoAnalogIfFXOObjects 1 }

		
		hwVoAnalogIfFXOConfigEntry OBJECT-TYPE
			SYNTAX HWVoAnalogIfFXOConfigEntry
			MAX-ACCESS not-accessible
			STATUS current
			DESCRIPTION
				"An entry in the voice analog interface fxo configuration table. 
				The entry is automatically created when a analog fxo voice interface hardware is found."
			INDEX { hwVoAnalogIfFXOConfigPortNumber }
			::= { hwVoAnalogIfFXOConfigTable 1 }

		
		HWVoAnalogIfFXOConfigEntry ::=
			SEQUENCE { 
				hwVoAnalogIfFXOConfigPortNumber
					INTEGER,
				hwVoAnalogIfFXOConfigStartMode
					INTEGER,
				hwVoAnalogIfFXOConfigAlertNumber
					INTEGER,
				hwVoAnalogIfFXOConfigArea
					INTEGER,
				hwVoAnalogIfFXOPreDialDelay
					INTEGER,
				hwVoAnaloglfFXOConfigPortImpedance
				    INTEGER
			 }

		hwVoAnalogIfFXOConfigPortNumber OBJECT-TYPE
			SYNTAX INTEGER
			MAX-ACCESS read-only
			STATUS current
			DESCRIPTION
				"Index of voice analog interface fxo config table. It identify the  
				number of the fxo voice port."
			::= { hwVoAnalogIfFXOConfigEntry 1 }

		
		hwVoAnalogIfFXOConfigStartMode OBJECT-TYPE
			SYNTAX INTEGER
				{
				loopStart(1),
				groundStart(2)
				}
			MAX-ACCESS read-only
			STATUS current
			DESCRIPTION
				"This object expresses the signal type of analog fxo interface.
				The default value is fxoLoopStart."
			DEFVAL { loopStart }
			::= { hwVoAnalogIfFXOConfigEntry 2 }

		
		hwVoAnalogIfFXOConfigAlertNumber OBJECT-TYPE
			SYNTAX INTEGER
			MAX-ACCESS read-only
			STATUS current
			DESCRIPTION
				"This object expresses the number of rings detected before loop 
				being closed. The default value is 2."
			DEFVAL { 2 }
			::= { hwVoAnalogIfFXOConfigEntry 3 }

		
		hwVoAnalogIfFXOConfigArea OBJECT-TYPE
			SYNTAX INTEGER
				{
				europe(1),
				custom(2),
				north-america(3)
				}
			MAX-ACCESS read-write
			STATUS current
			DESCRIPTION
				"This object expresses the busy tone of analog fxo interface.
				The default value is europe."
			DEFVAL { europe }
			::= { hwVoAnalogIfFXOConfigEntry 4 }

		
		hwVoAnalogIfFXOPreDialDelay OBJECT-TYPE
			SYNTAX INTEGER (0..10)
			MAX-ACCESS read-write
			STATUS current
			DESCRIPTION
				"This object expresses the pre-dial delay of analog fxo interface.
				The default value is 1 seconds."
			DEFVAL { 1 }
			::= { hwVoAnalogIfFXOConfigEntry 5 }

		
		hwVoAnaloglfFXOConfigPortImpedance OBJECT-TYPE
			SYNTAX INTEGER 
				{
				impedance550r(0),
				impedance600r(1),
				impedance600c(2),
				impedancecomplex(3)
				}
			MAX-ACCESS read-write
			STATUS current
			DESCRIPTION
                "This object expresses the port impedance of FXO interfaces."
		    DEFVAL { impedance600c }						           	
			::= { hwVoAnalogIfFXOConfigEntry 6 }

		
--  The Analog Voice Interface FXO Timer Table
		hwVoAnalogIfFXOTimerTable OBJECT-TYPE
			SYNTAX SEQUENCE OF HWVoAnalogIfFXOTimerEntry
			MAX-ACCESS not-accessible
			STATUS current
			DESCRIPTION
				"The voice analog interface fxo timer table contains information
				about timer parameters for analog fxo voice interface."
			::= { hwVoAnalogIfFXOObjects 3 }

		
		hwVoAnalogIfFXOTimerEntry OBJECT-TYPE
			SYNTAX HWVoAnalogIfFXOTimerEntry
			MAX-ACCESS not-accessible
			STATUS current
			DESCRIPTION
				"An entry in the voice analog interface fxo timer table. 
				The entry is automatically created when a analog fxo voice interface hardware is found."
			INDEX { hwVoAnalogIfFXOTimerPortNumber }
			::= { hwVoAnalogIfFXOTimerTable 1 }

		
		HWVoAnalogIfFXOTimerEntry ::=
			SEQUENCE { 
				hwVoAnalogIfFXOTimerPortNumber
					INTEGER,
				hwVoAnalogIfFXOTimerDtmf
					INTEGER,
				hwVoAnalogIfFXOTimerDtmfInterval
					INTEGER
			 }

		hwVoAnalogIfFXOTimerPortNumber OBJECT-TYPE
			SYNTAX INTEGER
			MAX-ACCESS read-only
			STATUS current
			DESCRIPTION
				"Index of voice analog interface fxo timer table. It identify the  
				number of the fxo voice port."
			::= { hwVoAnalogIfFXOTimerEntry 1 }

		
		hwVoAnalogIfFXOTimerDtmf OBJECT-TYPE
			SYNTAX INTEGER (50..500)
			MAX-ACCESS read-write
			STATUS current
			DESCRIPTION
				"This object expresses outgoing dtmf digit duration of the analog 
				fxo interface. The default value is 120 milliseconds"
			DEFVAL { 120 }
			::= { hwVoAnalogIfFXOTimerEntry 2 }

		
		hwVoAnalogIfFXOTimerDtmfInterval OBJECT-TYPE
			SYNTAX INTEGER (50..500)
			MAX-ACCESS read-write
			STATUS current
			DESCRIPTION
				"This object expresses outgoing dtmf interval duration of the analog 
				fxo interface. The default value is 120 milliseconds"
			DEFVAL { 120 }
			::= { hwVoAnalogIfFXOTimerEntry 3 }


		hwVoAnalogIfEMObjects OBJECT IDENTIFIER ::= { hwVoiceAnalogInterfaceMIB 4 }

--  The Analog Voice Interface E&M Group
-- The Analog Voice Interface E&M Configuration Table
		hwVoAnalogIfEMConfigTable OBJECT-TYPE
			SYNTAX SEQUENCE OF HWVoAnalogIfEMConfigEntry
			MAX-ACCESS not-accessible
			STATUS current
			DESCRIPTION
				"The voice analog interface e&m configuration table contains information
				about configuration parameters for analog e&m voice interface."
			::= { hwVoAnalogIfEMObjects 1 }

		
		hwVoAnalogIfEMConfigEntry OBJECT-TYPE
			SYNTAX HWVoAnalogIfEMConfigEntry
			MAX-ACCESS not-accessible
			STATUS current
			DESCRIPTION
				"An entry in the voice analog interface e&m configuration table. 
				The entry is automatically created when a analog e&m voice interface hardware is found."
			INDEX { hwVoAnalogIfEMConfigPortNumber }
			::= { hwVoAnalogIfEMConfigTable 1 }

		
		HWVoAnalogIfEMConfigEntry ::=
			SEQUENCE { 
				hwVoAnalogIfEMConfigPortNumber
					INTEGER,
				hwVoAnalogIfEMConfigSignalMode
					INTEGER,
				hwVoAnalogIfEMConfigPhyParm
					INTEGER,
				hwVoAnalogIfEMConfigPhyType
					INTEGER,
				hwVoAnalogIfEMConfigTimeoutRinging
					INTEGER,
				hwVoAnalogIfEMConfigTimeoutWaitDigit
					INTEGER
			 }

		hwVoAnalogIfEMConfigPortNumber OBJECT-TYPE
			SYNTAX INTEGER
			MAX-ACCESS read-only
			STATUS current
			DESCRIPTION
				"Index of voice analog interface e&m config table. It identify the  
				number of the e&m voice port."
			::= { hwVoAnalogIfEMConfigEntry 1 }

		
		hwVoAnalogIfEMConfigSignalMode OBJECT-TYPE
			SYNTAX INTEGER
				{
				delayDial(1),
				immediateDial(2),
				winkStart(3)
				}
			MAX-ACCESS read-write
			STATUS current
			DESCRIPTION
				"This object expresses the signal mode of the analog e&m interfaces.
				The default value is immediateDial.
				"
			DEFVAL { immediateDial }
			::= { hwVoAnalogIfEMConfigEntry 2 }

		
		hwVoAnalogIfEMConfigPhyParm OBJECT-TYPE
			SYNTAX INTEGER
				{
				twoWiresOperation(1),
				fourWiresOperation(2)
				}
			MAX-ACCESS read-write
			STATUS current
			DESCRIPTION
				"This object expresses the operation of the analog e&m signal.
				The default value of this object is fourWiresOperation."
			DEFVAL { fourWiresOperation }
			::= { hwVoAnalogIfEMConfigEntry 3 }

		
		hwVoAnalogIfEMConfigPhyType OBJECT-TYPE
			SYNTAX INTEGER
				{
				type1(1),
				type2(2),
				type3(3),
				type5(5)
				}
			MAX-ACCESS read-write
			STATUS current
			DESCRIPTION
				"This object expresses the e&m lead signaling type of the analog e&m interface.
				The default is type5."
			DEFVAL { type5 }
			::= { hwVoAnalogIfEMConfigEntry 4 }

		
		hwVoAnalogIfEMConfigTimeoutRinging OBJECT-TYPE
			SYNTAX INTEGER (5..600 | 65535)
			MAX-ACCESS read-write
			STATUS current
			DESCRIPTION
				"This object expresses the ring timeout of the analog e&m interface.
				The value of 65535 indicates the timer is approach infinity. The 
				default value of this object is 60 seconds."
			DEFVAL { 60 }
			::= { hwVoAnalogIfEMConfigEntry 5 }

		
		hwVoAnalogIfEMConfigTimeoutWaitDigit OBJECT-TYPE
			SYNTAX INTEGER (3..600 | 65535)
			MAX-ACCESS read-write
			STATUS current
			DESCRIPTION
				"This object expresses the wait digit timeout of the analog e&m interface.
				The value of 65535 indicates the timer is approach infinity. The 
				default value of this object is 5 seconds."
			DEFVAL { 5 }
			::= { hwVoAnalogIfEMConfigEntry 6 }

		
--  The Analog Voice Interface E&M Timer Table
		hwVoAnalogIfEMTimerTable OBJECT-TYPE
			SYNTAX SEQUENCE OF HWVoAnalogIfEMTimerEntry
			MAX-ACCESS not-accessible
			STATUS current
			DESCRIPTION
				"The voice analog interface e&m timer table contains information
				about timer parameters for analog e&m voice interface."
			::= { hwVoAnalogIfEMObjects 3 }

		
		hwVoAnalogIfEMTimerEntry OBJECT-TYPE
			SYNTAX HWVoAnalogIfEMTimerEntry
			MAX-ACCESS not-accessible
			STATUS current
			DESCRIPTION
				"An entry in the voice analog interface e&m timer table. 
				The entry is automatically created when a analog e&m voice interface hardware is found."
			INDEX { hwVoAnalogIfEMTimerPortNumber }
			::= { hwVoAnalogIfEMTimerTable 1 }

		
		HWVoAnalogIfEMTimerEntry ::=
			SEQUENCE { 
				hwVoAnalogIfEMTimerPortNumber
					INTEGER,
				hwVoAnalogIfEMTimerDtmf
					INTEGER,
				hwVoAnalogIfEMTimerDtmfInterval
					INTEGER,
				hwVoAnalogIfEMTimerCallInterval
					INTEGER,
				hwVoAnalogIfEMTimerSendWink
					INTEGER,
				hwVoAnalogIfEMTimerWinkRising
					INTEGER,
				hwVoAnalogIfEMTimerWinkHold
					INTEGER,
				hwVoAnalogIfEMTimerDialoutDelay
					INTEGER,
				hwVoAnalogIfEMTimerRising
					INTEGER,
				hwVoAnalogIfEMTimerHold
					INTEGER
			 }

		hwVoAnalogIfEMTimerPortNumber OBJECT-TYPE
			SYNTAX INTEGER
			MAX-ACCESS read-only
			STATUS current
			DESCRIPTION
				"Index of voice analog interface e&m timer table. It identify the  
				number of the e&m voice port."
			::= { hwVoAnalogIfEMTimerEntry 1 }

		
		hwVoAnalogIfEMTimerDtmf OBJECT-TYPE
			SYNTAX INTEGER (50..500)
			MAX-ACCESS read-write
			STATUS current
			DESCRIPTION
				"This object expresses outgoing dtmf digit duration of the analog 
				e&m interface. The default value is 120 milliseconds"
			DEFVAL { 120 }
			::= { hwVoAnalogIfEMTimerEntry 2 }

		
		hwVoAnalogIfEMTimerDtmfInterval OBJECT-TYPE
			SYNTAX INTEGER (50..500)
			MAX-ACCESS read-write
			STATUS current
			DESCRIPTION
				"This object expresses outgoing dtmf interval duration of the analog 
				e&m interface. The default value is 120 milliseconds"
			DEFVAL { 120 }
			::= { hwVoAnalogIfEMTimerEntry 3 }

		
		hwVoAnalogIfEMTimerCallInterval OBJECT-TYPE
			SYNTAX INTEGER (200..2000)
			MAX-ACCESS read-write
			STATUS current
			DESCRIPTION
				"This object expresses the dureation of call clearing. The default value 
				is 200 milliseconds."
			DEFVAL { 200 }
			::= { hwVoAnalogIfEMTimerEntry 4 }

		
		hwVoAnalogIfEMTimerSendWink OBJECT-TYPE
			SYNTAX INTEGER (100..5000)
			MAX-ACCESS read-write
			STATUS current
			DESCRIPTION
				"This object expresses the max time between receiving seizure signal 
				and sending wink signal. This object can olny be used when 
				hwVoAnalogIfEMConfigSignalMode is 'winkStart'. The default value is 
				500 milliseconds."
			DEFVAL { 200 }
			::= { hwVoAnalogIfEMTimerEntry 5 }

		
		hwVoAnalogIfEMTimerWinkRising OBJECT-TYPE
			SYNTAX INTEGER (100..5000)
			MAX-ACCESS read-write
			STATUS current
			DESCRIPTION
				"This object expresses the max time between sending seizure signal and 
				receiving wink signal. This object can only be used when 
				hwVoAnalogIfEMConfigSignalMode is 'winkStart'. The default value is 
				2000 milliseconds."
			DEFVAL { 2000 }
			::= { hwVoAnalogIfEMTimerEntry 6 }

		
		hwVoAnalogIfEMTimerWinkHold OBJECT-TYPE
			SYNTAX INTEGER (100..3000)
			MAX-ACCESS read-write
			STATUS current
			DESCRIPTION
				"This object expresses the max duration for sending wink signal. This 
				object can only be used when hwVoAnalogIfEMConfigSignalMode is 'winkStart'.
				The default value is 500 milliseconds."
			DEFVAL { 500 }
			::= { hwVoAnalogIfEMTimerEntry 7 }

		
		hwVoAnalogIfEMTimerDialoutDelay OBJECT-TYPE
			SYNTAX INTEGER (50..5000)
			MAX-ACCESS read-write
			STATUS current
			DESCRIPTION
				"This object expresses max time sending called digits. This object can
				only be used when hwVoAnalogIfEMConfigSignalMode is 'immediate'. The 
				default value is 300 milliseconds."
			DEFVAL { 300 }
			::= { hwVoAnalogIfEMTimerEntry 8 }

		
		hwVoAnalogIfEMTimerRising OBJECT-TYPE
			SYNTAX INTEGER (20..2000)
			MAX-ACCESS read-write
			STATUS current
			DESCRIPTION
				"This object expresses the wait duration between receiveing seizure 
				signal and sending delay signal. This object can only be used when
				hwVoAnalogIfEMConfigSignalMode is 'delayDial'. The default value is
				300 milliseconds."
			DEFVAL { 300 }
			::= { hwVoAnalogIfEMTimerEntry 9 }

		
		hwVoAnalogIfEMTimerHold OBJECT-TYPE
			SYNTAX INTEGER (100..5000)
			MAX-ACCESS read-write
			STATUS current
			DESCRIPTION
				"This object expresses the max time sending delay signal. This object 
				can only be used when hwVoAnalogIfEMConfigSignalMode is 'delayDial'. 
				The default value is 400 milliseconds."
			DEFVAL { 400 }
			::= { hwVoAnalogIfEMTimerEntry 10 }

		
		
				
	
	END
