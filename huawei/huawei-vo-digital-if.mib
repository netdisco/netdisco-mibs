-- ==========================================================================
-- Copyright (C) 2002 by  HUAWEI TECHNOLOGIES. All rights reserved.
--
-- Description: The purpose of this MIB file is to provide the define of
--              the digital voice interface general configuration MIB of 
--              HUAWEI quidway serial router.
-- Reference:
-- Version: V3.0
-- History:
-- V1.0 Initial version
-- V2.0 2004-10-20 Updated by gaolong
--      Re-write whole MIB with SNMPv2-SMI format.
--      Modify module name from 'HUAWAI-VOICE-DIGITAL-IF-MIB' to 'HUAWEI-VO-DIGITAL-IF-MIB'
-- V3.0 2004-11-10 Updated by gaolong
--      Add objects in hwVoDigitalIfR2CfgTable
--          hwVoDigitalIfR2CfgBillingCategory
--          hwVoDigitalIfR2CfgCallingCategory
--          hwVoDigitalIfR2CfgCongestion
--          hwVoDigitalIfR2CfgDemandRefused
--          hwVoDigitalIfR2CfgDigitEnd
--          hwVoDigitalIfR2CfgNullnum
--          hwVoDigitalIfR2CfgReqBillingCategory
--          hwVoDigitalIfR2CfgReqCallingCategory
--          hwVoDigitalIfR2CfgReqCurrentdigit
--          hwVoDigitalIfR2CfgReqFirstCallingnum
--          hwVoDigitalIfR2CfgReqFirstDigit
--          hwVoDigitalIfR2CfgReqNextCallednum
--          hwVoDigitalIfR2CfgReqNextCallingnum
--          hwVoDigitalIfR2CfgReqLastFirstDigit
--          hwVoDigitalIfR2CfgReqLastSecondDigit
--          hwVoDigitalIfR2CfgReqLastThirdDigit
--          hwVoDigitalIfR2CfgReqSwitchGroupB
--          hwVoDigitalIfR2CfgSubscriberIdle
--          hwVoDigitalIfR2CfgSubscriberBusy
--          hwVoDigitalIfR2CfgDebounceTime
--          hwVoDigitalIfR2CfgSendringBackTime
--          hwVoDigitalIfR2CfgSendringBusyTime
--          hwVoDigitalIfR2CfgPulseSignalPersistenceTime
--          hwVoDigitalIfR2CfgDlAnswerTime
--          hwVoDigitalIfR2CfgDlClearBackTime
--          hwVoDigitalIfR2CfgDlClearForwardTime
--          hwVoDigitalIfR2CfgDlSeizureTime
--          hwVoDigitalIfR2CfgDlReanswerTime
--          hwVoDigitalIfR2CfgDlReleaseGuardTime
--          hwVoDigitalIfR2CfgMfcGroupBTime
--          hwVoDigitalIfR2CfgAniEnable
--          hwVoDigitalIfR2CfgGroupBEnable
--          hwVoDigitalIfR2CfgClearForwardAckEnable
--          hwVoDigitalIfR2CfgDlSeizureAckEnable
--          hwVoDigitalIfR2CfgDTMFEnable
--          hwVoDigitalIfR2CfgAnswerEnable
--          hwVoDigitalIfR2CfgReanswerEnable
--          hwVoDigitalIfR2CfgFinalCallnumEnable
--          hwVoDigitalIfR2CfgForceMeteringEnable
--          hwVoDigitalIfR2CfgSendRingBackEnable
--          hwVoDigitalIfR2CfgSendRingBusyEnable
--          hwVoDigitalIfR2CfgReqCategoryOffset
--          hwVoDigitalIfR2CfgReqCallingnumOffset
--          hwVoDigitalIfR2CfgCountryMode
--          hwVoDigitalIfR2CfgSpecialCharacter
--          hwVoDigitalIfR2CfgSpecialSignal
--          hwVoDigitalIfR2CfgSelectMode
--          hwVoDigitalIfR2CfgDTMFTime
--          hwVoDigitalIfR2CfgReqCallCreate
--      Add objects in hwVoDigitalIfR2ABCDCfgTable
--          hwVoDigitalIfR2ABCDRxIdle
--          hwVoDigitalIfR2ABCDTxIdle
--          hwVoDigitalIfR2ABCDRxSeizure
--          hwVoDigitalIfR2ABCDTxSeizure
--          hwVoDigitalIfR2ABCDRxSeizureAck
--          hwVoDigitalIfR2ABCDTxSeizureAck
--          hwVoDigitalIfR2ABCDRxAnswer
--          hwVoDigitalIfR2ABCDTxAnswer
--          hwVoDigitalIfR2ABCDRxClearForward
--          hwVoDigitalIfR2ABCDTxClearForward
--          hwVoDigitalIfR2ABCDRxClearBack
--          hwVoDigitalIfR2ABCDTxClearBack
--          hwVoDigitalIfR2ABCDRxReleaseGuard
--          hwVoDigitalIfR2ABCDTxReleaseGuard
--          hwVoDigitalIfR2ABCDRxBlocking
--          hwVoDigitalIfR2ABCDTxBlocking
--      Rename objects in hwVoDigitalIfR2ABCDCfgTable
--          from hwVoDigitalIfR2ABCDReverseABCD to hwVoDigitalIfR2ABCDInvertABCD
--          from hwVoDigitalIfR2ABCDRenewABCD to hwVoDigitalIfR2ABCDUnusedABCD
--      Deprecate ojbects in hwVoDigitalIfR2CfgTable
--          hwVoDigitalIfR2CfgAniSwitch
--          hwVoDigitalIfR2CallerDigits
--          hwVoDigitalIfR2DebounceTime
--          hwVoDigitalIfR2Ka
--          hwVoDigitalIfR2Kd
--          hwVoDigitalIfR2SeizureAckTime
--          hwVoDigitalIfR2SelectMode
--          hwVoDigitalIfR2TimeoutKb
--          hwVoDigitalIfR2TimeoutKd
--          hwVoDigitalIfR2TimeoutNextNumber
--          hwVoDigitalIfR2TimeoutReleaseApprove
--          hwVoDigitalIfR2TimeoutRing
--          hwVoDigitalIfR2TimeoutSendAnswer
-- ==========================================================================
HUAWEI-VO-DIGITAL-IF-MIB DEFINITIONS ::= BEGIN
 
		IMPORTS
			OBJECT-TYPE, MODULE-IDENTITY, Integer32
				FROM SNMPv2-SMI
		voice
				FROM HUAWEI-3COM-OID-MIB;
	
		
		hwVoiceDigitalInterfaceMIB  MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 4 }

		
		hwVoDigitalIfCommonObjects OBJECT IDENTIFIER ::= { hwVoiceDigitalInterfaceMIB 1 }

		
--  The Digital Voice Interface Common Group
-- The Digital Voice Interface Common Configuration Table
		hwVoDigitalIfCommonCfgTable OBJECT-TYPE
			SYNTAX SEQUENCE OF HWVoDigitalIfCommonCfgEntry
			MAX-ACCESS not-accessible
			STATUS current
			DESCRIPTION
				"The voice digital interface common configuration table contains information
				about configuration parameters for digital voice interface."
			::= { hwVoDigitalIfCommonObjects 1 }

		
		hwVoDigitalIfCommonCfgEntry OBJECT-TYPE
			SYNTAX HWVoDigitalIfCommonCfgEntry
			MAX-ACCESS not-accessible
			STATUS current
			DESCRIPTION
				"An entry in the voice digital interface common configuration table. 
				The entry is automatically created when a digital voice interface hardware is found."
			INDEX { hwVoDigitalIfCfgPortNumber, hwVoDigitalIfCfgGroupNumber }
			::= { hwVoDigitalIfCommonCfgTable 1 }

		
		HWVoDigitalIfCommonCfgEntry ::=
			SEQUENCE { 
				hwVoDigitalIfCfgPortNumber
					INTEGER,
				hwVoDigitalIfCfgGroupNumber
					INTEGER,
				hwVoDigitalIfCfgBoardType
					INTEGER,
				hwVoDigitalIfCfgSignalType
					INTEGER,
				hwVoDigitalIfCfgTimeSlotsConfigurable
					OCTET STRING
			 }

		hwVoDigitalIfCfgPortNumber OBJECT-TYPE
			SYNTAX INTEGER
			MAX-ACCESS read-only
			STATUS current
			DESCRIPTION
				"Index of voice digital interface common config table. It identify the  
				number of the voice port."
			::= { hwVoDigitalIfCommonCfgEntry 1 }

		
		hwVoDigitalIfCfgGroupNumber OBJECT-TYPE
			SYNTAX INTEGER (0..30)
			MAX-ACCESS read-only
			STATUS current
			DESCRIPTION
				"Index of voice digital interface common config table. It identify the  
				number of the ds0 or pri group."
			::= { hwVoDigitalIfCommonCfgEntry 2 }

		
		hwVoDigitalIfCfgBoardType OBJECT-TYPE
			SYNTAX INTEGER
				{
				e1vi(1),
				t1vi(2)
				}
			MAX-ACCESS read-only
			STATUS current
			DESCRIPTION
				"This object expresses the type of digital voice interface."
			::= { hwVoDigitalIfCommonCfgEntry 3 }

		
		hwVoDigitalIfCfgSignalType OBJECT-TYPE
			SYNTAX INTEGER
				{
				r2(1),
				dss1(2),
				em(3)
				}
			MAX-ACCESS read-only
			STATUS current
			DESCRIPTION
				"This object expresses the signal type of ds0 or pri group."
			::= { hwVoDigitalIfCommonCfgEntry 4 }

		
		hwVoDigitalIfCfgTimeSlotsConfigurable OBJECT-TYPE
			SYNTAX OCTET STRING (SIZE (24 | 32))
			MAX-ACCESS read-only
			STATUS current
			DESCRIPTION
				"This object expresses whether the timeslot is available. 
				'1' states the timeslot is available for the E1VI or T1VI,
				'0' states the timeslot is not available. For T1VI, the 
				length is 24. For E1VI, the length is 32."
			::= { hwVoDigitalIfCommonCfgEntry 5 }

		
		hwVoDigitalIfEMObjects OBJECT IDENTIFIER ::= { hwVoiceDigitalInterfaceMIB 2 }

		
--  The Digital Voice Interface E&M Group
-- The Digital Voice Interface E&M Configuration Table
		hwVoDigitalIfEMCfgTable OBJECT-TYPE
			SYNTAX SEQUENCE OF HWVoDigitalIfEMCfgEntry
			MAX-ACCESS not-accessible
			STATUS current
			DESCRIPTION
				"The voice digital interface e&m configuration table contains information
				about configuration parameters for digital e&m voice interface."
			::= { hwVoDigitalIfEMObjects 1 }

		
		hwVoDigitalIfEMCfgEntry OBJECT-TYPE
			SYNTAX HWVoDigitalIfEMCfgEntry
			MAX-ACCESS not-accessible
			STATUS current
			DESCRIPTION
				"An entry in the voice digital interface e&m configuration table. 
				The entry is automatically created when a digital voice interface is
				configed for digital e&m signal."
			INDEX { hwVoDigitalIfEMCfgPortNumber, hwVoDigitalIfEMCfgGroupNumber }
			::= { hwVoDigitalIfEMCfgTable 1 }

		
		HWVoDigitalIfEMCfgEntry ::=
			SEQUENCE { 
				hwVoDigitalIfEMCfgPortNumber
					INTEGER,
				hwVoDigitalIfEMCfgGroupNumber
					INTEGER,
				hwVoDigitalIfEMCfgTimeoutInterDigits
					INTEGER,
				hwVoDigitalIfEMCfgTimeoutRinging
					INTEGER,
				hwVoDigitalIfEMCfgTimeoutWaitDigit
					INTEGER
			 }

		hwVoDigitalIfEMCfgPortNumber OBJECT-TYPE
			SYNTAX INTEGER
			MAX-ACCESS read-only
			STATUS current
			DESCRIPTION
				"Index of voice digital interface e&m config table. It identify the  
				number of the voice port."
			::= { hwVoDigitalIfEMCfgEntry 1 }

		
		hwVoDigitalIfEMCfgGroupNumber OBJECT-TYPE
			SYNTAX INTEGER (0..30)
			MAX-ACCESS read-only
			STATUS current
			DESCRIPTION
				"Index of voice digital interface e&m config table. It identify the  
				number of the ds0 group."
			::= { hwVoDigitalIfEMCfgEntry 2 }

		
		hwVoDigitalIfEMCfgTimeoutInterDigits OBJECT-TYPE
			SYNTAX INTEGER (0..120)
			MAX-ACCESS read-write
			STATUS current
			DESCRIPTION
				"This object states the longest time to wait between two input digit from
				caller side. The default value is 10 seconds."
			DEFVAL { 10 }
			::= { hwVoDigitalIfEMCfgEntry 3 }

		
		hwVoDigitalIfEMCfgTimeoutRinging OBJECT-TYPE
			SYNTAX INTEGER (5..600 | 65535)
			MAX-ACCESS read-write
			STATUS current
			DESCRIPTION
				"This object expresses the ring timeout of the digital e&m interface.
				The value of 65535 indicates the timer is approach infinity. The 
				default value of this object is 60 seconds."
			DEFVAL { 60 }
			::= { hwVoDigitalIfEMCfgEntry 4 }

		
		hwVoDigitalIfEMCfgTimeoutWaitDigit OBJECT-TYPE
			SYNTAX INTEGER (3..600 | 65535)
			MAX-ACCESS read-write
			STATUS current
			DESCRIPTION
				"This object expresses the wait digit timeout of the digital e&m interface.
				The value of 65535 indicates the timer is approach infinity. The 
				default value of this object is 5 seconds."
			DEFVAL { 5 }
			::= { hwVoDigitalIfEMCfgEntry 5 }

		
--  The Digital Voice Interface EM ABCD Configuration Table
		hwVoDigitalIfEMABCDCfgTable OBJECT-TYPE
			SYNTAX SEQUENCE OF HWVoDigitalIfEMABCDCfgEntry
			MAX-ACCESS not-accessible
			STATUS current
			DESCRIPTION
				"The voice digital interface e&m abcd configuration table contains information
				about abcd bits configuration parameters for digital e&m voice interface."
			::= { hwVoDigitalIfEMObjects 2 }

		
		hwVoDigitalIfEMABCDCfgEntry OBJECT-TYPE
			SYNTAX HWVoDigitalIfEMABCDCfgEntry
			MAX-ACCESS not-accessible
			STATUS current
			DESCRIPTION
				"An entry in the voice digital interface e&m abcd configuration table. 
				The entry is automatically created when a digital voice interface is
				configed for digital e&m signal."
			INDEX { hwVoDigitalIfEMABCDCfgPortNumber, hwVoDigitalIfEMABCDCfgGroupNumber }
			::= { hwVoDigitalIfEMABCDCfgTable 1 }

		
		HWVoDigitalIfEMABCDCfgEntry ::=
			SEQUENCE { 
				hwVoDigitalIfEMABCDCfgPortNumber
					INTEGER,
				hwVoDigitalIfEMABCDCfgGroupNumber
					INTEGER,
				hwVoDigitalIfEMABCDRxIdle
					OCTET STRING,
				hwVoDigitalIfEMABCDRxSeize
					OCTET STRING,
				hwVoDigitalIfEMABCDTxIdle
					OCTET STRING,
				hwVoDigitalIfEMABCDTxSeize
					OCTET STRING
			 }

		hwVoDigitalIfEMABCDCfgPortNumber OBJECT-TYPE
			SYNTAX INTEGER
			MAX-ACCESS read-only
			STATUS current
			DESCRIPTION
				"Index of voice digital interface e&m abcd config table. It identify the  
				number of the voice port."
			::= { hwVoDigitalIfEMABCDCfgEntry 1 }

		
		hwVoDigitalIfEMABCDCfgGroupNumber OBJECT-TYPE
			SYNTAX INTEGER (0..30)
			MAX-ACCESS read-only
			STATUS current
			DESCRIPTION
				"Index of voice digital interface e&m abcd config table. It identify the  
				number of the ds0 group."
			::= { hwVoDigitalIfEMABCDCfgEntry 2 }

		
		hwVoDigitalIfEMABCDRxIdle OBJECT-TYPE
			SYNTAX OCTET STRING (SIZE (4))
			MAX-ACCESS read-write
			STATUS current
			DESCRIPTION
				"This object expresses the a b c d bits for receiving idle signal.
				The default value is '1101'."
			DEFVAL { "1101" }
			::= { hwVoDigitalIfEMABCDCfgEntry 3 }

		
		hwVoDigitalIfEMABCDRxSeize OBJECT-TYPE
			SYNTAX OCTET STRING (SIZE (4))
			MAX-ACCESS read-write
			STATUS current
			DESCRIPTION
				"This object expresses the a b c d bits for receiving seize signal.
				The default value is '0101'."
			DEFVAL { "0101" }
			::= { hwVoDigitalIfEMABCDCfgEntry 4 }

		
		hwVoDigitalIfEMABCDTxIdle OBJECT-TYPE
			SYNTAX OCTET STRING (SIZE (4))
			MAX-ACCESS read-write
			STATUS current
			DESCRIPTION
				"This object expresses the a b c d bits for sending idle signal.
				The default value is '1101'."
			DEFVAL { "1101" }
			::= { hwVoDigitalIfEMABCDCfgEntry 5 }

		
		hwVoDigitalIfEMABCDTxSeize OBJECT-TYPE
			SYNTAX OCTET STRING (SIZE (4))
			MAX-ACCESS read-write
			STATUS current
			DESCRIPTION
				"This object expresses the a b c d bits for sending seize signal.
				The default value is '0101'."
			DEFVAL { "0101" }
			::= { hwVoDigitalIfEMABCDCfgEntry 6 }

		
--  The Digital Voice Interface E&M Timer Table
		hwVoDigitalIfEMTimerTable OBJECT-TYPE
			SYNTAX SEQUENCE OF HWVoDigitalIfEMTimerEntry
			MAX-ACCESS not-accessible
			STATUS current
			DESCRIPTION
				"The voice digital interface e&m timer table contains information
				about timer parameters for digital e&m voice interface."
			::= { hwVoDigitalIfEMObjects 4 }

		
		hwVoDigitalIfEMTimerEntry OBJECT-TYPE
			SYNTAX HWVoDigitalIfEMTimerEntry
			MAX-ACCESS not-accessible
			STATUS current
			DESCRIPTION
				"An entry in the voice digital interface e&m timer table. 
				The entry is automatically created when a digital voice interface is
				configed for digital e&m signal."
			INDEX { hwVoDigitalIfEMTimerPortNumber, hwVoDigitalIfEMTimerGroupNumber }
			::= { hwVoDigitalIfEMTimerTable 1 }

		
		HWVoDigitalIfEMTimerEntry ::=
			SEQUENCE { 
				hwVoDigitalIfEMTimerPortNumber
					INTEGER,
				hwVoDigitalIfEMTimerGroupNumber
					INTEGER,
				hwVoDigitalIfEMTimerCallInterval
					INTEGER,
				hwVoDigitalIfEMTimerSendWink
					INTEGER,
				hwVoDigitalIfEMTimerWinkRising
					INTEGER,
				hwVoDigitalIfEMTimerWinkHold
					INTEGER,
				hwVoDigitalIfEMTimerDialoutDelay
					INTEGER,
				hwVoDigitalIfEMTimerRising
					INTEGER,
				hwVoDigitalIfEMTimerHold
					INTEGER,
				hwVoDigitalIfEMTimerDtmf
					INTEGER,
				hwVoDigitalIfEMTimerDtmfInterval
					INTEGER
			 }

		hwVoDigitalIfEMTimerPortNumber OBJECT-TYPE
			SYNTAX INTEGER
			MAX-ACCESS read-only
			STATUS current
			DESCRIPTION
				"Index of voice digital interface e&m timer config table. It identify the  
				number of the voice port."
			::= { hwVoDigitalIfEMTimerEntry 1 }

		
		hwVoDigitalIfEMTimerGroupNumber OBJECT-TYPE
			SYNTAX INTEGER (0..30)
			MAX-ACCESS read-only
			STATUS current
			DESCRIPTION
				"Index of voice digital interface e&m timer config table. It identify the  
				number of the ds0 group."
			::= { hwVoDigitalIfEMTimerEntry 2 }

		
		hwVoDigitalIfEMTimerCallInterval OBJECT-TYPE
			SYNTAX INTEGER (200..2000)
			MAX-ACCESS read-write
			STATUS current
			DESCRIPTION
				"This object expresses the dureation of call clearing. The default value 
				is 200 milliseconds."
			DEFVAL { 200 }
			::= { hwVoDigitalIfEMTimerEntry 3 }

		
		hwVoDigitalIfEMTimerSendWink OBJECT-TYPE
			SYNTAX INTEGER (100..5000)
			MAX-ACCESS read-write
			STATUS current
			DESCRIPTION
				"This object expresses the max time between receiving seizure signal 
				and sending wink signal. The default value is 500 milliseconds."
			DEFVAL { 500 }
			::= { hwVoDigitalIfEMTimerEntry 4 }

		
		hwVoDigitalIfEMTimerWinkRising OBJECT-TYPE
			SYNTAX INTEGER (100..5000)
			MAX-ACCESS read-write
			STATUS current
			DESCRIPTION
				"This object expresses the max time between sending seizure signal and 
				receiving wink signal. The default value is 1000 milliseconds."
			DEFVAL { 1000 }
			::= { hwVoDigitalIfEMTimerEntry 5 }

		
		hwVoDigitalIfEMTimerWinkHold OBJECT-TYPE
			SYNTAX INTEGER (100..3000)
			MAX-ACCESS read-write
			STATUS current
			DESCRIPTION
				"This object expresses the max duration for sending wink signal. 
				The default value is 500 milliseconds."
			DEFVAL { 500 }
			::= { hwVoDigitalIfEMTimerEntry 6 }

		
		hwVoDigitalIfEMTimerDialoutDelay OBJECT-TYPE
			SYNTAX INTEGER (50..5000)
			MAX-ACCESS read-write
			STATUS current
			DESCRIPTION
				"This object expresses max time sending called digits.  The 
				default value is 300 milliseconds."
			DEFVAL { 300 }
			::= { hwVoDigitalIfEMTimerEntry 7 }

		
		hwVoDigitalIfEMTimerRising OBJECT-TYPE
			SYNTAX INTEGER (20..2000)
			MAX-ACCESS read-write
			STATUS current
			DESCRIPTION
				"This object expresses the wait duration between receiveing seizure 
				signal and sending delay signal. The default value is 300 milliseconds."
			DEFVAL { 300 }
			::= { hwVoDigitalIfEMTimerEntry 8 }

		
		hwVoDigitalIfEMTimerHold OBJECT-TYPE
			SYNTAX INTEGER (100..5000)
			MAX-ACCESS read-write
			STATUS current
			DESCRIPTION
				"This object expresses the max time sending delay signal. 
				The default value is 400 milliseconds."
			DEFVAL { 400 }
			::= { hwVoDigitalIfEMTimerEntry 9 }

		
		hwVoDigitalIfEMTimerDtmf OBJECT-TYPE
			SYNTAX INTEGER (50..500)
			MAX-ACCESS read-write
			STATUS current
			DESCRIPTION
				"This object expresses outgoing dtmf digit duration of the digital 
				e&m interface. The default value is 120 milliseconds"
			DEFVAL { 120 }
			::= { hwVoDigitalIfEMTimerEntry 10 }

		
		hwVoDigitalIfEMTimerDtmfInterval OBJECT-TYPE
			SYNTAX INTEGER (50..500)
			MAX-ACCESS read-write
			STATUS current
			DESCRIPTION
				"This object expresses outgoing dtmf inter-digit duration of the digital 
				e&m interface. The default value is 120 milliseconds"
			DEFVAL { 120 }
			::= { hwVoDigitalIfEMTimerEntry 11 }

		
		hwVoDigitalIfR2Objects OBJECT IDENTIFIER ::= { hwVoiceDigitalInterfaceMIB 3 }

		
--  The Digital Voice Interface R2 Group
-- The Digital Voice Interface R2 Configuration Table
		hwVoDigitalIfR2CfgTable OBJECT-TYPE
			SYNTAX SEQUENCE OF HWVoDigitalIfR2CfgEntry
			MAX-ACCESS not-accessible
			STATUS current
			DESCRIPTION
				"The voice digital interface r2 configuration table contains information
				about configuration parameters for digital r2 voice interface."
			::= { hwVoDigitalIfR2Objects 1 }

		
		hwVoDigitalIfR2CfgEntry OBJECT-TYPE
			SYNTAX HWVoDigitalIfR2CfgEntry
			MAX-ACCESS not-accessible
			STATUS current
			DESCRIPTION
				"An entry in the voice digital interface r2 configuration table. 
				The entry is automatically created when a digital voice interface is
				configed for digital r2 signal."
			INDEX { hwVoDigitalIfR2CfgPortNumber, hwVoDigitalIfR2CfgGroupNumber }
			::= { hwVoDigitalIfR2CfgTable 1 }

		
		HWVoDigitalIfR2CfgEntry ::=
			SEQUENCE { 
				hwVoDigitalIfR2CfgPortNumber
					INTEGER,
				hwVoDigitalIfR2CfgGroupNumber
					INTEGER,
				hwVoDigitalIfR2CfgAniSwitch
					INTEGER,
				hwVoDigitalIfR2CallerDigits
					INTEGER,
				hwVoDigitalIfR2DebounceTime
					INTEGER,
				hwVoDigitalIfR2Ka
					INTEGER,
				hwVoDigitalIfR2Kd
					INTEGER,
				hwVoDigitalIfR2SeizureAckTime
					INTEGER,
				hwVoDigitalIfR2SelectMode
					INTEGER,
				hwVoDigitalIfR2TimeoutKb
					INTEGER,
				hwVoDigitalIfR2TimeoutKd
					INTEGER,
				hwVoDigitalIfR2TimeoutNextNumber
					INTEGER,
				hwVoDigitalIfR2TimeoutReleaseApprove
					INTEGER,
				hwVoDigitalIfR2TimeoutRing
					Integer32,
				hwVoDigitalIfR2TimeoutSendAnswer
					INTEGER,
				hwVoDigitalIfR2CfgBillingCategory
					INTEGER,
				hwVoDigitalIfR2CfgCallingCategory
					INTEGER,		
				hwVoDigitalIfR2CfgCongestion
					INTEGER,	
				hwVoDigitalIfR2CfgDemandRefused
					INTEGER,											
				hwVoDigitalIfR2CfgDigitEnd
					INTEGER,	
				hwVoDigitalIfR2CfgNullnum
					INTEGER,	
				hwVoDigitalIfR2CfgReqBillingCategory
					INTEGER,
				hwVoDigitalIfR2CfgReqCallingCategory
					INTEGER,
				hwVoDigitalIfR2CfgReqCurrentdigit
					INTEGER,
				hwVoDigitalIfR2CfgReqFirstCallingnum
					INTEGER,
				hwVoDigitalIfR2CfgReqFirstDigit
					INTEGER,
				hwVoDigitalIfR2CfgReqNextCallednum
					INTEGER,
				hwVoDigitalIfR2CfgReqNextCallingnum
					INTEGER,
				hwVoDigitalIfR2CfgReqLastFirstDigit
					INTEGER,
				hwVoDigitalIfR2CfgReqLastSecondDigit
					INTEGER,
				hwVoDigitalIfR2CfgReqLastThirdDigit
					INTEGER,
				hwVoDigitalIfR2CfgReqSwitchGroupB
					INTEGER,
				hwVoDigitalIfR2CfgSubscriberIdle
					INTEGER,
				hwVoDigitalIfR2CfgSubscriberBusy
					INTEGER,
				hwVoDigitalIfR2CfgDebounceTime
					INTEGER,		
				hwVoDigitalIfR2CfgSendringBackTime
					INTEGER,	
				hwVoDigitalIfR2CfgSendringBusyTime
					INTEGER,														
				hwVoDigitalIfR2CfgPulseSignalPersistenceTime
					INTEGER,
				hwVoDigitalIfR2CfgDlAnswerTime
					INTEGER,
				hwVoDigitalIfR2CfgDlClearBackTime
					INTEGER,
				hwVoDigitalIfR2CfgDlClearForwardTime
					INTEGER,
				hwVoDigitalIfR2CfgDlSeizureTime
					INTEGER,
				hwVoDigitalIfR2CfgDlReanswerTime
					INTEGER,
				hwVoDigitalIfR2CfgDlReleaseGuardTime
					INTEGER,
				hwVoDigitalIfR2CfgMfcGroupBTime
					INTEGER,
				hwVoDigitalIfR2CfgAniEnable
					INTEGER,					
				hwVoDigitalIfR2CfgGroupBEnable
					INTEGER,
				hwVoDigitalIfR2CfgClearForwardAckEnable
					INTEGER,
				hwVoDigitalIfR2CfgDlSeizureAckEnable
					INTEGER,	
				hwVoDigitalIfR2CfgDTMFEnable
					INTEGER,
				hwVoDigitalIfR2CfgAnswerEnable
					INTEGER,
				hwVoDigitalIfR2CfgReanswerEnable
					INTEGER,	
				hwVoDigitalIfR2CfgFinalCallnumEnable
					INTEGER,
				hwVoDigitalIfR2CfgForceMeteringEnable
					INTEGER,
				hwVoDigitalIfR2CfgSendRingBackEnable
					INTEGER,
				hwVoDigitalIfR2CfgSendRingBusyEnable
					INTEGER,
				hwVoDigitalIfR2CfgReqCategoryOffset
					INTEGER,
				hwVoDigitalIfR2CfgReqCallingnumOffset
					INTEGER,
				hwVoDigitalIfR2CfgCountryMode
					INTEGER,
				hwVoDigitalIfR2CfgSpecialCharacter
					INTEGER,
				hwVoDigitalIfR2CfgSpecialSignal
					INTEGER,		
				hwVoDigitalIfR2CfgSelectMode
					INTEGER,
				hwVoDigitalIfR2CfgDTMFTime
					INTEGER,
				hwVoDigitalIfR2CfgReqCallCreate
					INTEGER						
			 }

		hwVoDigitalIfR2CfgPortNumber OBJECT-TYPE
			SYNTAX INTEGER
			MAX-ACCESS read-only
			STATUS current
			DESCRIPTION
				"Index of voice digital interface r2 config table. It identify the  
				number of the voice port."
			::= { hwVoDigitalIfR2CfgEntry 1 }

		
		hwVoDigitalIfR2CfgGroupNumber OBJECT-TYPE
			SYNTAX INTEGER (0..30)
			MAX-ACCESS read-only
			STATUS current
			DESCRIPTION
				"Index of voice digital interface r2 config table. It identify the  
				number of the ds0 group."
			::= { hwVoDigitalIfR2CfgEntry 2 }

		
		-- obsoleted begin
		hwVoDigitalIfR2CfgAniSwitch OBJECT-TYPE
			SYNTAX INTEGER
				{
				enable(1),
				disable(2)
				}
			MAX-ACCESS read-only
			STATUS deprecated
			DESCRIPTION
				"This object expresses the ANI funtion is enable or disable.
				The default value is disable."
			DEFVAL { disable }
			::= { hwVoDigitalIfR2CfgEntry 3 }

		
		hwVoDigitalIfR2CallerDigits OBJECT-TYPE
			SYNTAX INTEGER (1..10)
			MAX-ACCESS read-write
			STATUS deprecated
			DESCRIPTION
				"This object expresses how many digits will be collected befor sending A6.
				The default value of this object is 1."
			DEFVAL { 1 }
			::= { hwVoDigitalIfR2CfgEntry 4 }

		
		hwVoDigitalIfR2DebounceTime OBJECT-TYPE
			SYNTAX INTEGER (10..40)
			MAX-ACCESS read-write
			STATUS deprecated
			DESCRIPTION
				"This object expresses the minimus duration the line signal to persist.
				The default value of this object is 40."
			DEFVAL { 40 }
			::= { hwVoDigitalIfR2CfgEntry 5 }

		
		hwVoDigitalIfR2Ka OBJECT-TYPE
			SYNTAX INTEGER (1..15)
			MAX-ACCESS read-write
			STATUS deprecated
			DESCRIPTION
				"This object expresses the code of KA signal.               
				The default value is 1."
			DEFVAL { 1 }
			::= { hwVoDigitalIfR2CfgEntry 6 }

		
		hwVoDigitalIfR2Kd OBJECT-TYPE
			SYNTAX INTEGER (1..15)
			MAX-ACCESS read-write
			STATUS deprecated
			DESCRIPTION
				"This object expresses the code of KD signal.               
				The default value is 3."
			DEFVAL { 3 }
			::= { hwVoDigitalIfR2CfgEntry 7 }

		
		hwVoDigitalIfR2SeizureAckTime OBJECT-TYPE
			SYNTAX INTEGER (200..3000)
			MAX-ACCESS read-write
			STATUS deprecated
			DESCRIPTION
				"This object expresses the longgest time to wait the seizure 
				acknowldge signal. The default value is 1000 milliseconds."
			DEFVAL { 1000 }
			::= { hwVoDigitalIfR2CfgEntry 8 }

		
		hwVoDigitalIfR2SelectMode OBJECT-TYPE
			SYNTAX INTEGER
				{
				max(1),
				maxpoll(2),
				min(3),
				minpoll(4)
				}
			MAX-ACCESS read-write
			STATUS deprecated
			DESCRIPTION
				"This object expresses the trunk mode to be selected.
				max            set select trunk mode to max-mode
				maxpoll        set select trunk mode to max-poll-mode
				min            set select trunk mode to min-mode
				minpoll        set select trunk mode to min-poll-mode  
				The default value is min."
			DEFVAL { min }
			::= { hwVoDigitalIfR2CfgEntry 9 }

		
		hwVoDigitalIfR2TimeoutKb OBJECT-TYPE
			SYNTAX INTEGER (1000..50000)
			MAX-ACCESS read-write
			STATUS deprecated
			DESCRIPTION
				"This object expresses the maxinum time to wait kb signal.
				The default value of this object is 5000 milliseconds."
			DEFVAL { 5000 }
			::= { hwVoDigitalIfR2CfgEntry 10 }

		
		hwVoDigitalIfR2TimeoutKd OBJECT-TYPE
			SYNTAX INTEGER (1000..50000)
			MAX-ACCESS read-write
			STATUS deprecated
			DESCRIPTION
				"This object expresses the maxinum time to wait kd signal.
				The default value of this object is 5000 milliseconds."
			DEFVAL { 5000 }
			::= { hwVoDigitalIfR2CfgEntry 11 }

		
		hwVoDigitalIfR2TimeoutNextNumber OBJECT-TYPE
			SYNTAX INTEGER (1000..50000)
			MAX-ACCESS read-write
			STATUS deprecated
			DESCRIPTION
				"This object expresses the maxinum time to wait next number.
				The default value of this object is 5000 milliseconds."
			DEFVAL { 5000 }
			::= { hwVoDigitalIfR2CfgEntry 12 }

		
		hwVoDigitalIfR2TimeoutReleaseApprove OBJECT-TYPE
			SYNTAX INTEGER (200..3000)
			MAX-ACCESS read-write
			STATUS deprecated
			DESCRIPTION
				"This object expresses the maxinum time to wait release approve.
				The default value of this object is 1000 milliseconds."
			DEFVAL { 1000 }
			::= { hwVoDigitalIfR2CfgEntry 13 }

		
		hwVoDigitalIfR2TimeoutRing OBJECT-TYPE
			SYNTAX Integer32 (1000..240000)
			MAX-ACCESS read-write
			STATUS deprecated
			DESCRIPTION
				"This object expresses the maxinum time to wait the end of ring.
				The default value is 30000 milliseconds."
			DEFVAL { 30000 }
			::= { hwVoDigitalIfR2CfgEntry 14 }

		
		hwVoDigitalIfR2TimeoutSendAnswer OBJECT-TYPE
			SYNTAX INTEGER (50..1000)
			MAX-ACCESS read-write
			STATUS deprecated
			DESCRIPTION
				"This object expresses the maxinum time to wait Answer signal.
				The default value is 500 milliseconds."
			DEFVAL { 500 }
			::= { hwVoDigitalIfR2CfgEntry 15 }

		-- obsoleted end

		hwVoDigitalIfR2CfgBillingCategory OBJECT-TYPE
			SYNTAX INTEGER (1..16)
			MAX-ACCESS read-write
			STATUS current
			DESCRIPTION
				"This object expresses the value of signal BillingCategory.
				The default value is 2."
			DEFVAL { 2 }
			::= { hwVoDigitalIfR2CfgEntry 16 }			
			
							
		hwVoDigitalIfR2CfgCallingCategory OBJECT-TYPE
			SYNTAX INTEGER (1..16)
			MAX-ACCESS read-write
			STATUS current
			DESCRIPTION
				"This object expresses the value of signal CallingCategory.
				The default value is 1."
			DEFVAL { 1 }
			::= { hwVoDigitalIfR2CfgEntry 17 }
		
		
		hwVoDigitalIfR2CfgCongestion OBJECT-TYPE
			SYNTAX INTEGER (1..16)
			MAX-ACCESS read-write
			STATUS current
			DESCRIPTION
				"This object expresses the value of signal Congestion.
				The default value is 4."
			DEFVAL { 4 }
			::= { hwVoDigitalIfR2CfgEntry 18 }


		hwVoDigitalIfR2CfgDemandRefused OBJECT-TYPE
			SYNTAX INTEGER (1..16)
			MAX-ACCESS read-write
			STATUS current
			DESCRIPTION
				"This object expresses the value of signal DemandRefused.
				The default value is 12."
			DEFVAL { 12 }
			::= { hwVoDigitalIfR2CfgEntry 19 }


		hwVoDigitalIfR2CfgDigitEnd OBJECT-TYPE
			SYNTAX INTEGER (1..16)
			MAX-ACCESS read-write
			STATUS current
			DESCRIPTION
				"This object expresses the value of signal DigitEnd.
				The default value is 15."
			DEFVAL { 15 }
			::= { hwVoDigitalIfR2CfgEntry 20 }


		hwVoDigitalIfR2CfgNullnum OBJECT-TYPE
			SYNTAX INTEGER (1..16)
			MAX-ACCESS read-write
			STATUS current
			DESCRIPTION
				"This object expresses the value of signal Nullnum.
				The default value is 5."
			DEFVAL { 5 }
			::= { hwVoDigitalIfR2CfgEntry 21 }


		hwVoDigitalIfR2CfgReqBillingCategory OBJECT-TYPE
			SYNTAX INTEGER (1..16)
			MAX-ACCESS read-write
			STATUS current
			DESCRIPTION
				"This object expresses the value of signal requesting BillingCategory.
				The default value is 16."
			DEFVAL { 16 }
			::= { hwVoDigitalIfR2CfgEntry 22 }


		hwVoDigitalIfR2CfgReqCallingCategory OBJECT-TYPE
			SYNTAX INTEGER (1..16)
			MAX-ACCESS read-write
			STATUS current
			DESCRIPTION
				"This object expresses the value of signal requesting CallingCategory.
				The default value is 5."
			DEFVAL { 5 }
			::= { hwVoDigitalIfR2CfgEntry 23 }


		hwVoDigitalIfR2CfgReqCurrentdigit OBJECT-TYPE
			SYNTAX INTEGER (1..16)
			MAX-ACCESS read-write
			STATUS current
			DESCRIPTION
				"This object expresses the value of signal requesting Currentdigit.
				The default value is 16."
			DEFVAL { 16 }
			::= { hwVoDigitalIfR2CfgEntry 24 }


		hwVoDigitalIfR2CfgReqFirstCallingnum OBJECT-TYPE
			SYNTAX INTEGER (1..16)
			MAX-ACCESS read-write
			STATUS current
			DESCRIPTION
				"This object expresses the value of signal requesting FirstCallingnum.
				The default value is 5."
			DEFVAL { 5}
			::= { hwVoDigitalIfR2CfgEntry 25 }


		hwVoDigitalIfR2CfgReqFirstDigit OBJECT-TYPE
			SYNTAX INTEGER (1..16)
			MAX-ACCESS read-write
			STATUS current
			DESCRIPTION
				"This object expresses the value of signal requesting FirstDigit.
				The default value is 16."
			DEFVAL { 16}
			::= { hwVoDigitalIfR2CfgEntry 26 }


		hwVoDigitalIfR2CfgReqNextCallednum OBJECT-TYPE
			SYNTAX INTEGER (1..16)
			MAX-ACCESS read-write
			STATUS current
			DESCRIPTION
				"This object expresses the value of signal requesting NextCallednum.
				The default value is 1."
			DEFVAL { 1}
			::= { hwVoDigitalIfR2CfgEntry 27 }


		hwVoDigitalIfR2CfgReqNextCallingnum OBJECT-TYPE
			SYNTAX INTEGER (1..16)
			MAX-ACCESS read-write
			STATUS current
			DESCRIPTION
				"This object expresses the value of signal requesting NextCallingnum.
				The default value is 5."
			DEFVAL { 5}
			::= { hwVoDigitalIfR2CfgEntry 28 }


		hwVoDigitalIfR2CfgReqLastFirstDigit OBJECT-TYPE
			SYNTAX INTEGER (1..16)
			MAX-ACCESS read-write
			STATUS current
			DESCRIPTION
				"This object expresses the value of signal requesting LastFirstDigit.
				The default value is 2."
			DEFVAL { 2}
			::= { hwVoDigitalIfR2CfgEntry 29 }


		hwVoDigitalIfR2CfgReqLastSecondDigit OBJECT-TYPE
			SYNTAX INTEGER (1..16)
			MAX-ACCESS read-write
			STATUS current
			DESCRIPTION
				"This object expresses the value of signal requesting LastSecondDigit.
				The default value is 7."
			DEFVAL { 7}
			::= { hwVoDigitalIfR2CfgEntry 30 }


		hwVoDigitalIfR2CfgReqLastThirdDigit OBJECT-TYPE
			SYNTAX INTEGER (1..16)
			MAX-ACCESS read-write
			STATUS current
			DESCRIPTION
				"This object expresses the value of signal requesting LastFirstDigit.
				The default value is 8."
			DEFVAL { 8}
			::= { hwVoDigitalIfR2CfgEntry 31 }


		hwVoDigitalIfR2CfgReqSwitchGroupB OBJECT-TYPE
			SYNTAX INTEGER (1..16)
			MAX-ACCESS read-write
			STATUS current
			DESCRIPTION
				"This object expresses the value of signal requesting SwitchGroupB.
				The default value is 3."
			DEFVAL { 3}
			::= { hwVoDigitalIfR2CfgEntry 32 }


		hwVoDigitalIfR2CfgSubscriberIdle OBJECT-TYPE
			SYNTAX INTEGER (1..16)
			MAX-ACCESS read-write
			STATUS current
			DESCRIPTION
				"This object expresses the value of signal SubscriberIdle.
				The default value is 6."
			DEFVAL { 6}
			::= { hwVoDigitalIfR2CfgEntry 33 }


		hwVoDigitalIfR2CfgSubscriberBusy OBJECT-TYPE
			SYNTAX INTEGER (1..16)
			MAX-ACCESS read-write
			STATUS current
			DESCRIPTION
				"This object expresses the value of signal SubscriberBusy.
				The default value is 3."
			DEFVAL { 3}
			::= { hwVoDigitalIfR2CfgEntry 34 }
					
					
		hwVoDigitalIfR2CfgDebounceTime OBJECT-TYPE
			SYNTAX INTEGER (10..40)
			MAX-ACCESS read-write
			STATUS current
			DESCRIPTION
				"This object expresses the minimus duration the line signal to persist.
				The default value of this object is 10."
			DEFVAL { 10 }
			::= { hwVoDigitalIfR2CfgEntry 35 }
			
			
		hwVoDigitalIfR2CfgSendringBackTime OBJECT-TYPE
			SYNTAX INTEGER (1000..90000)
			MAX-ACCESS read-write
			STATUS current
			DESCRIPTION
				"This object expresses the minimus duration the back-ring to persist.
				The default value of this object is 60000."
			DEFVAL { 60000 }
			::= { hwVoDigitalIfR2CfgEntry 36 }
			
			
		hwVoDigitalIfR2CfgSendringBusyTime OBJECT-TYPE
			SYNTAX INTEGER (1000..90000)
			MAX-ACCESS read-write
			STATUS current
			DESCRIPTION
				"This object expresses the minimus duration the busy-ring to persist.
				The default value of this object is 30000."
			DEFVAL { 30000 }
			::= { hwVoDigitalIfR2CfgEntry 37 }
		
		
		hwVoDigitalIfR2CfgPulseSignalPersistenceTime OBJECT-TYPE
			SYNTAX INTEGER (50..3000)
			MAX-ACCESS read-write
			STATUS current
			DESCRIPTION
				"This object expresses the value of PulseSignalPersistence-Timer.
				The default value is 150."
			DEFVAL { 150}
			::= { hwVoDigitalIfR2CfgEntry 38 }



		hwVoDigitalIfR2CfgDlAnswerTime OBJECT-TYPE
			SYNTAX INTEGER (100..120000)
			MAX-ACCESS read-write
			STATUS current
			DESCRIPTION
				"This object expresses the value of Answer-Timer.
				The default value is 60000."
			DEFVAL { 60000}
			::= { hwVoDigitalIfR2CfgEntry 39 }


		hwVoDigitalIfR2CfgDlClearBackTime OBJECT-TYPE
			SYNTAX INTEGER (100..60000)
			MAX-ACCESS read-write
			STATUS current
			DESCRIPTION
				"This object expresses the value of ClearBack-Timer.
				The default value is 1000."
			DEFVAL { 1000}
			::= { hwVoDigitalIfR2CfgEntry 40 }


		hwVoDigitalIfR2CfgDlClearForwardTime OBJECT-TYPE
			SYNTAX INTEGER (100..60000)
			MAX-ACCESS read-write
			STATUS current
			DESCRIPTION
				"This object expresses the value of ClearForward-Timer.
				The default value is 1000."
			DEFVAL { 1000}
			::= { hwVoDigitalIfR2CfgEntry 41 }


		hwVoDigitalIfR2CfgDlSeizureTime OBJECT-TYPE
			SYNTAX INTEGER (100..5000)
			MAX-ACCESS read-write
			STATUS current
			DESCRIPTION
				"This object expresses the value of Seize-Timer.
				The default value is 1000."
			DEFVAL { 1000}
			::= { hwVoDigitalIfR2CfgEntry 42 }


		hwVoDigitalIfR2CfgDlReanswerTime OBJECT-TYPE
			SYNTAX INTEGER (100..60000)
			MAX-ACCESS read-write
			STATUS current
			DESCRIPTION
				"This object expresses the value of ReAnswer-Timer.
				The default value is 1000."
			DEFVAL { 1000}
			::= { hwVoDigitalIfR2CfgEntry 43}


		hwVoDigitalIfR2CfgDlReleaseGuardTime OBJECT-TYPE
			SYNTAX INTEGER (100..60000)
			MAX-ACCESS read-write
			STATUS current
			DESCRIPTION
				"This object expresses the value of ReleaseGuard-Timer.
				The default value is 1000."
			DEFVAL { 1000}
			::= { hwVoDigitalIfR2CfgEntry 44 }


		hwVoDigitalIfR2CfgMfcGroupBTime OBJECT-TYPE
			SYNTAX INTEGER (100..90000)
			MAX-ACCESS read-write
			STATUS current
			DESCRIPTION
				"This object expresses the value of GroupB-Timer.
				The default value is 30000."
			DEFVAL { 30000}
			::= { hwVoDigitalIfR2CfgEntry 45 }


		hwVoDigitalIfR2CfgAniEnable OBJECT-TYPE
			SYNTAX INTEGER
				{
				enable(1),
				disable(2)
				}
			MAX-ACCESS read-write
			STATUS current
			DESCRIPTION
				"This object expresses the ANI is enable or disable.
				The default value is disable."
			DEFVAL { disable}
			::= { hwVoDigitalIfR2CfgEntry 46 }


		hwVoDigitalIfR2CfgGroupBEnable OBJECT-TYPE
			SYNTAX INTEGER
				{
				enable(1),
				disable(2)
				}
			MAX-ACCESS read-write
			STATUS current
			DESCRIPTION
				"This object expresses the GroupB-Process is enable or disable .
				The default value is enable."
			DEFVAL { enable}
			::= { hwVoDigitalIfR2CfgEntry 47 }

		hwVoDigitalIfR2CfgClearForwardAckEnable OBJECT-TYPE
			SYNTAX INTEGER
				{
				enable(1),
				disable(2)
				}
			MAX-ACCESS read-write
			STATUS current
			DESCRIPTION
				"This object expresses the ClearForwardAck-Signal is enable or disable .
				The default value is disable."
			DEFVAL { disable}
			::= { hwVoDigitalIfR2CfgEntry 48 }


		hwVoDigitalIfR2CfgDlSeizureAckEnable OBJECT-TYPE
			SYNTAX INTEGER
				{
				enable(1),
				disable(2)
				}
			MAX-ACCESS read-write
			STATUS current
			DESCRIPTION
				"This object expresses the SeizureAck-Signal is enable or disable .
				The default value is enable."
			DEFVAL { enable}
			::= { hwVoDigitalIfR2CfgEntry 49 }


		hwVoDigitalIfR2CfgDTMFEnable OBJECT-TYPE
			SYNTAX INTEGER
				{
				enable(1),
				disable(2)
				}
			MAX-ACCESS read-write
			STATUS current
			DESCRIPTION
				"This object expresses the DTMF is enable or disable .
				The default value is disable."
			DEFVAL {disable}
			::= { hwVoDigitalIfR2CfgEntry 50 }


		hwVoDigitalIfR2CfgAnswerEnable OBJECT-TYPE
			SYNTAX INTEGER
				{
				enable(1),
				disable(2)
				}
			MAX-ACCESS read-write
			STATUS current
			DESCRIPTION
				"This object expresses the Answer-Signal is enable or disable .
				The default value is enable."
			DEFVAL {enable}
			::= { hwVoDigitalIfR2CfgEntry 51 }


		hwVoDigitalIfR2CfgReanswerEnable OBJECT-TYPE
			SYNTAX INTEGER
				{
				enable(1),
				disable(2)
				}
			MAX-ACCESS read-write
			STATUS current
			DESCRIPTION
				"This object expresses the ReAnswer-Signal is enable or disable .
				The default value is disable."
			DEFVAL {disable}
			::= { hwVoDigitalIfR2CfgEntry 52 } 


		hwVoDigitalIfR2CfgFinalCallnumEnable OBJECT-TYPE
			SYNTAX INTEGER
				{
				enable(1),
				disable(2)
				}
			MAX-ACCESS read-write
			STATUS current
			DESCRIPTION
				"This object expresses the FinalCallnum-Signal is enable or disable .
				The default value is disable."
			DEFVAL {disable}
			::= { hwVoDigitalIfR2CfgEntry 53 }

		hwVoDigitalIfR2CfgForceMeteringEnable OBJECT-TYPE
			SYNTAX INTEGER
				{
				enable(1),
				disable(2)
				}
			MAX-ACCESS read-write
			STATUS current
			DESCRIPTION
				"This object expresses the Metering-Signal is enable or disable .
				The default value is disable."
			DEFVAL {disable}
			::= { hwVoDigitalIfR2CfgEntry 54 }

		hwVoDigitalIfR2CfgSendRingBackEnable OBJECT-TYPE
			SYNTAX INTEGER
				{
				enable(1),
				disable(2)
				}
			MAX-ACCESS read-write
			STATUS current
			DESCRIPTION
				"This object expresses the SendRingBack is enable or disable .
				The default value is enable."
			DEFVAL {enable}
			::= { hwVoDigitalIfR2CfgEntry 55 }

		hwVoDigitalIfR2CfgSendRingBusyEnable OBJECT-TYPE
			SYNTAX INTEGER
				{
				enable(1),
				disable(2)
				}
			MAX-ACCESS read-write
			STATUS current
			DESCRIPTION
				"This object expresses the SendRingBusy is enable or disable .
				The default value is enable."
			DEFVAL {enable}
			::= { hwVoDigitalIfR2CfgEntry 56 }
							

		hwVoDigitalIfR2CfgReqCategoryOffset OBJECT-TYPE
			SYNTAX INTEGER (1..10)
			MAX-ACCESS read-write
			STATUS current
			DESCRIPTION
				"This object expresses the value of CategoryOffset .
				The default value is 1."
			DEFVAL {1}
			::= { hwVoDigitalIfR2CfgEntry 57}

		hwVoDigitalIfR2CfgReqCallingnumOffset OBJECT-TYPE
			SYNTAX INTEGER (1..10)
			MAX-ACCESS read-write
			STATUS current
			DESCRIPTION
				"This object expresses the value of CallingnumOffset .
				The default value is 1."
			DEFVAL {1}
			::= { hwVoDigitalIfR2CfgEntry 58 }

		hwVoDigitalIfR2CfgCountryMode OBJECT-TYPE
			SYNTAX INTEGER 
				{
				argentina (0),
				australia (1),
				bengal (2),
				brazil (3),
				china (4),
				customer (5),
				hongkong (6),
				india (7),
				indonesia (8),
				itu-t (9),
				korea (10),
				malaysia (11),
				mexico (12),
				newzealand (13),
				singapore (14),
				thailand (15)
				}
			MAX-ACCESS read-write
			STATUS current
			DESCRIPTION
				"This object expresses the value of CountryMode .
				The default value is 9."
			DEFVAL {9}
			::= { hwVoDigitalIfR2CfgEntry 59}
			
		hwVoDigitalIfR2CfgSpecialCharacter OBJECT-TYPE
			SYNTAX INTEGER 
				{
				null (0),
				a (65),
				b (66),
				c (67),
				d (68),
				pound (35),
				asterisk (42)
				}
			MAX-ACCESS read-write
			STATUS current
			DESCRIPTION
				"This object expresses the SpecialCharacter(A,B,C,D,#,*).
				The default value is NULL."
			DEFVAL {0}
			::= { hwVoDigitalIfR2CfgEntry 60 }


		hwVoDigitalIfR2CfgSpecialSignal OBJECT-TYPE
			SYNTAX INTEGER (11..16)
			MAX-ACCESS read-write
			STATUS current
			DESCRIPTION
				"This object expresses the signal of SpecialCharacter.
				The default value is 16."
			DEFVAL {16}
			::= { hwVoDigitalIfR2CfgEntry 61 }


		hwVoDigitalIfR2CfgSelectMode OBJECT-TYPE
			SYNTAX INTEGER
				{
				min(1),
				max(2),
				minpoll(3),
				maxpoll(4)
				}
			MAX-ACCESS read-write
			STATUS current
			DESCRIPTION
				"This object expresses the trunk mode to be selected.
				max            set select trunk mode to max-mode
				maxpoll        set select trunk mode to max-poll-mode
				min            set select trunk mode to min-mode
				minpoll        set select trunk mode to min-poll-mode  
				The default value is min."
			DEFVAL { min }
			::= { hwVoDigitalIfR2CfgEntry 62 }
			

		hwVoDigitalIfR2CfgDTMFTime OBJECT-TYPE
			SYNTAX INTEGER (0..10000)
			MAX-ACCESS read-write
			STATUS current
			DESCRIPTION
				"This object expresses the value of DTMF-Timer.
				The default value is 0."
			DEFVAL { 0 }
			::= { hwVoDigitalIfR2CfgEntry 63 }

		hwVoDigitalIfR2CfgReqCallCreate OBJECT-TYPE
			SYNTAX INTEGER (1..16)
			MAX-ACCESS read-write
			STATUS current
			DESCRIPTION
				"This object expresses the value of signal callcreate in group-a.
				The default value is 6."
			DEFVAL { 6 }
			::= { hwVoDigitalIfR2CfgEntry 64 }

--  The Digital Voice Interface R2 ABCD Configuration  Table
		hwVoDigitalIfR2ABCDCfgTable OBJECT-TYPE
			SYNTAX SEQUENCE OF HWVoDigitalIfR2ABCDCfgEntry
			MAX-ACCESS not-accessible
			STATUS current
			DESCRIPTION
				"The voice digital interface r2 abcd configuration table contains information
				about abcd bits configuration parameters for digital r2 voice interface."
			::= { hwVoDigitalIfR2Objects 2 }

		
		hwVoDigitalIfR2ABCDCfgEntry OBJECT-TYPE
			SYNTAX HWVoDigitalIfR2ABCDCfgEntry
			MAX-ACCESS not-accessible
			STATUS current
			DESCRIPTION
				"An entry in the voice digital interface r2 abcd configuration table. 
				The entry is automatically created when a digital voice interface is
				configed for digital r2 signal."
			INDEX { hwVoDigitalIfR2ABCDCfgPortNumber, hwVoDigitalIfR2ABCDCfgGroupNumber }
			::= { hwVoDigitalIfR2ABCDCfgTable 1 }

		
		HWVoDigitalIfR2ABCDCfgEntry ::=
			SEQUENCE { 
				hwVoDigitalIfR2ABCDCfgPortNumber
					INTEGER,
				hwVoDigitalIfR2ABCDCfgGroupNumber
					INTEGER,
				hwVoDigitalIfR2ABCDReverseABCD
					OCTET STRING,
				hwVoDigitalIfR2ABCDRenewABCD
					OCTET STRING,
				hwVoDigitalIfR2ABCDRxIdle
					OCTET STRING,
				hwVoDigitalIfR2ABCDTxIdle
					OCTET STRING,
                		hwVoDigitalIfR2ABCDRxSeizure
					OCTET STRING,
                		hwVoDigitalIfR2ABCDTxSeizure
					OCTET STRING,
                		hwVoDigitalIfR2ABCDRxSeizureAck
					OCTET STRING,
                		hwVoDigitalIfR2ABCDTxSeizureAck
					OCTET STRING,
                		hwVoDigitalIfR2ABCDRxAnswer
					OCTET STRING,
                		hwVoDigitalIfR2ABCDTxAnswer
					OCTET STRING,
		        	hwVoDigitalIfR2ABCDRxClearForward
					OCTET STRING,
                		hwVoDigitalIfR2ABCDTxClearForward
					OCTET STRING,
			    	hwVoDigitalIfR2ABCDRxClearBack
					OCTET STRING,
                		hwVoDigitalIfR2ABCDTxClearBack
					OCTET STRING,
		        	hwVoDigitalIfR2ABCDRxReleaseGuard
					OCTET STRING,
                		hwVoDigitalIfR2ABCDTxReleaseGuard
					OCTET STRING,
				hwVoDigitalIfR2ABCDRxBlocking
					OCTET STRING,
                		hwVoDigitalIfR2ABCDTxBlocking
					OCTET STRING			
			 }

		hwVoDigitalIfR2ABCDCfgPortNumber OBJECT-TYPE
			SYNTAX INTEGER
			MAX-ACCESS read-only
			STATUS current
			DESCRIPTION
				"Index of voice digital interface r2 abcd config table. It identify the  
				number of the voice port."
			::= { hwVoDigitalIfR2ABCDCfgEntry 1 }

		
		hwVoDigitalIfR2ABCDCfgGroupNumber OBJECT-TYPE
			SYNTAX INTEGER (0..30)
			MAX-ACCESS read-only
			STATUS current
			DESCRIPTION
				"Index of voice digital interface r2 abcd config table. It identify the  
				number of the ds0 group."
			::= { hwVoDigitalIfR2ABCDCfgEntry 2 }

		
		hwVoDigitalIfR2ABCDReverseABCD OBJECT-TYPE
			SYNTAX OCTET STRING (SIZE (4))
			MAX-ACCESS read-write
			STATUS current
			DESCRIPTION
				"This object expresses whether or not the a b c d bits should be invert.
				'0' : disable invert.
				'1' : enable invert.
				The default value is '0000'."
			DEFVAL { "0000" }
			::= { hwVoDigitalIfR2ABCDCfgEntry 3 }

		
		hwVoDigitalIfR2ABCDRenewABCD OBJECT-TYPE
			SYNTAX OCTET STRING (SIZE (4))
			MAX-ACCESS read-write
			STATUS current
			DESCRIPTION
				"This object expresses the unused a b c d bits to be sent. The default value
				is '1111'."
			DEFVAL { "1111" }
			::= { hwVoDigitalIfR2ABCDCfgEntry 4 }


		hwVoDigitalIfR2ABCDRxIdle OBJECT-TYPE
			SYNTAX OCTET STRING (SIZE (4))
			MAX-ACCESS read-write
			STATUS current
			DESCRIPTION
				"This object expresses the idle line signal bits to be received. The default value
				is '1001'."
			DEFVAL { "1001" }
			::= { hwVoDigitalIfR2ABCDCfgEntry 5 }


		hwVoDigitalIfR2ABCDTxIdle OBJECT-TYPE
			SYNTAX OCTET STRING (SIZE (4))
			MAX-ACCESS read-write
			STATUS current
			DESCRIPTION
				"This object expresses the idle line signal bits to be sent. The default value
				is '1001'."
			DEFVAL { "1001" }
			::= { hwVoDigitalIfR2ABCDCfgEntry 6 }

		
		hwVoDigitalIfR2ABCDRxSeizure OBJECT-TYPE
			SYNTAX OCTET STRING (SIZE (4))
			MAX-ACCESS read-write
			STATUS current
			DESCRIPTION
				"This object expresses the seizure line signal bits to be received. The default value
				is '0001'."
			DEFVAL { "0001" }
			::= { hwVoDigitalIfR2ABCDCfgEntry 7 }


		hwVoDigitalIfR2ABCDTxSeizure OBJECT-TYPE
			SYNTAX OCTET STRING (SIZE (4))
			MAX-ACCESS read-write
			STATUS current
			DESCRIPTION
				"This object expresses the seizure line signal bits to be sent. The default value
				is '0001'."
			DEFVAL { "0001" }
			::= { hwVoDigitalIfR2ABCDCfgEntry 8 }
	

		hwVoDigitalIfR2ABCDRxSeizureAck OBJECT-TYPE
			SYNTAX OCTET STRING (SIZE (4))
			MAX-ACCESS read-write
			STATUS current
			DESCRIPTION
				"This object expresses the seizureAck line signal bits to be received. The default value
				is '1101'."
			DEFVAL { "1101" }
			::= { hwVoDigitalIfR2ABCDCfgEntry 9 }


		hwVoDigitalIfR2ABCDTxSeizureAck OBJECT-TYPE
			SYNTAX OCTET STRING (SIZE (4))
			MAX-ACCESS read-write
			STATUS current
			DESCRIPTION
				"This object expresses the seizureAck line signal bits to be sent. The default value
				is '1101'."
			DEFVAL { "1101" }
			::= { hwVoDigitalIfR2ABCDCfgEntry 10 }


		hwVoDigitalIfR2ABCDRxAnswer OBJECT-TYPE
			SYNTAX OCTET STRING (SIZE (4))
			MAX-ACCESS read-write
			STATUS current
			DESCRIPTION
				"This object expresses the answer line signal bits to be received. The default value
				is '0101'."
			DEFVAL { "0101" }
			::= { hwVoDigitalIfR2ABCDCfgEntry 11 }


		hwVoDigitalIfR2ABCDTxAnswer OBJECT-TYPE
			SYNTAX OCTET STRING (SIZE (4))
			MAX-ACCESS read-write
			STATUS current
			DESCRIPTION
				"This object expresses the answer line signal bits to be sent. The default value
				is '0101'."
			DEFVAL { "0101" }
			::= { hwVoDigitalIfR2ABCDCfgEntry 12 }


		hwVoDigitalIfR2ABCDRxClearForward OBJECT-TYPE
			SYNTAX OCTET STRING (SIZE (4))
			MAX-ACCESS read-write
			STATUS current
			DESCRIPTION
				"This object expresses the ClearForward line signal bits to be received. The default value
				is '1001'."
			DEFVAL { "1001" }
			::= { hwVoDigitalIfR2ABCDCfgEntry 13 }


		hwVoDigitalIfR2ABCDTxClearForward OBJECT-TYPE
			SYNTAX OCTET STRING (SIZE (4))
			MAX-ACCESS read-write
			STATUS current
			DESCRIPTION
				"This object expresses the ClearForward line signal bits to be sent. The default value
				is '1001'."
			DEFVAL { "1001" }
			::= { hwVoDigitalIfR2ABCDCfgEntry 14 }


		hwVoDigitalIfR2ABCDRxClearBack OBJECT-TYPE
			SYNTAX OCTET STRING (SIZE (4))
			MAX-ACCESS read-write
			STATUS current
			DESCRIPTION
				"This object expresses the ClearBackward line signal bits to be received. The default value
				is '1101'."
			DEFVAL { "1101" }
			::= { hwVoDigitalIfR2ABCDCfgEntry 15 }


		hwVoDigitalIfR2ABCDTxClearBack OBJECT-TYPE
			SYNTAX OCTET STRING (SIZE (4))
			MAX-ACCESS read-write
			STATUS current
			DESCRIPTION
				"This object expresses the ClearBackward line signal bits to be sent. The default value
				is '1101'."
			DEFVAL { "1101" }
			::= { hwVoDigitalIfR2ABCDCfgEntry 16 }


		hwVoDigitalIfR2ABCDRxReleaseGuard OBJECT-TYPE
			SYNTAX OCTET STRING (SIZE (4))
			MAX-ACCESS read-write
			STATUS current
			DESCRIPTION
				"This object expresses the ReleaseGuard line signal bits to be received. The default value
				is '1001'."
			DEFVAL { "1001" }
			::= { hwVoDigitalIfR2ABCDCfgEntry 17 }


		hwVoDigitalIfR2ABCDTxReleaseGuard OBJECT-TYPE
			SYNTAX OCTET STRING (SIZE (4))
			MAX-ACCESS read-write
			STATUS current
			DESCRIPTION
				"This object expresses the ReleaseGuard line signal bits to be sent. The default value
				is '1001'."
			DEFVAL { "1001" }
			::= { hwVoDigitalIfR2ABCDCfgEntry 18 }

			
		hwVoDigitalIfR2ABCDRxBlocking OBJECT-TYPE
			SYNTAX OCTET STRING (SIZE (4))
			MAX-ACCESS read-write
			STATUS current
			DESCRIPTION
				"This object expresses the Blocking line signal bits to be received. The default value
				is '1101'."
			DEFVAL { "1101" }
			::= { hwVoDigitalIfR2ABCDCfgEntry 19 }


		hwVoDigitalIfR2ABCDTxBlocking OBJECT-TYPE
			SYNTAX OCTET STRING (SIZE (4))
			MAX-ACCESS read-write
			STATUS current
			DESCRIPTION
				"This object expresses the Blocking line signal bits to be sent. The default value
				is '1101'."
			DEFVAL { "1101" }
			::= { hwVoDigitalIfR2ABCDCfgEntry 20}

	END
