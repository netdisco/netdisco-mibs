-- =============================================================
-- Copyright (c) 2004-2009 Hangzhou H3C Tech. Co., Ltd. All rights reserved.
--
-- Description: E1T1VI MIB
-- Reference: None
-- Version: V1.1
-- History:
--   V1.0 2007-04-05 Initial Version by yandehan
--   V1.1 2009-06-08 modified by TONGWEI
--        Added h3cE1T1VIUsingTimeslotsRatio
--          and h3cE1T1VINotifications
-- =============================================================
H3C-E1T1VI-MIB DEFINITIONS ::= BEGIN
    IMPORTS
        MODULE-IDENTITY, OBJECT-TYPE, Integer32, NOTIFICATION-TYPE
            FROM SNMPv2-SMI
        ifIndex, ifDescr
            FROM RFC1213-MIB
        h3cCommon
            FROM HUAWEI-3COM-OID-MIB;


-- =============================================================
-- E1T1VI Module
-- =============================================================
h3cE1T1VI MODULE-IDENTITY
    LAST-UPDATED    "200906081741Z"         -- Jun. 8, 2009 at 17:41 GMT
    ORGANIZATION
        "Hangzhou H3C Technologies Co., Ltd."
    CONTACT-INFO
        "Platform Team H3C Technologies Co., Ltd.
         Hai-Dian District Beijing P.R. China
         http://www.h3c.com
         Zip: 100085"    
    DESCRIPTION
        "This MIB provides E1/T1 voice interface information that are
        excluded by RFC 1213 and RFC 2233"
    REVISION        "200906081741Z"
    DESCRIPTION
        "To fix bugs in the MIB file."
    REVISION        "200704051542Z"
    DESCRIPTION
        "Initial version of this MIB module."
    ::= { h3cCommon 76 }


h3cE1T1VITable OBJECT-TYPE
    SYNTAX      SEQUENCE OF H3cE1T1VIEntry
    MAX-ACCESS  not-accessible
    STATUS      current
    DESCRIPTION
        "This table contains E1/T1 voice interface information,
        such as the total number of using time slot."
    ::= { h3cE1T1VI 1 }

h3cE1T1VIEntry OBJECT-TYPE
    SYNTAX      H3cE1T1VIEntry
    MAX-ACCESS  not-accessible
    STATUS      current
    DESCRIPTION
        "This entry contains E1/T1 voice interface information.
        The index of this Entry is ifIndex defined in ifTable
        of RFC1213-MIB."
    INDEX
        {
            ifIndex
        }
    ::= { h3cE1T1VITable 1 }

H3cE1T1VIEntry ::= SEQUENCE
    {
        h3cE1T1VIUsingTimeslots    Integer32,
        h3cE1T1VIUsingTimeslotsRatio    Integer32
    }

h3cE1T1VIUsingTimeslots OBJECT-TYPE
    SYNTAX      Integer32
    MAX-ACCESS  read-only
    STATUS      current
    DESCRIPTION
        "The total number of using time slots on this interface."
    ::= { h3cE1T1VIEntry 1 }

h3cE1T1VIUsingTimeslotsRatio OBJECT-TYPE
    SYNTAX      Integer32
    MAX-ACCESS  read-only
    STATUS      current
    DESCRIPTION
        "The total ratio of using time slots on this interface."
    ::= { h3cE1T1VIEntry 2 }

h3cE1T1VINotifications OBJECT IDENTIFIER ::= { h3cE1T1VI 2 }
h3cE1T1VITrapPrefix    OBJECT IDENTIFIER ::= { h3cE1T1VINotifications 0 }

h3cE1T1VITrapTimeSlot NOTIFICATION-TYPE
    OBJECTS { ifIndex, ifDescr }
    STATUS current
    DESCRIPTION
        "This trap is sent to the manager under the following
         condidion: All the available time slots of a E1/T1
         voice interface has been in use."
    ::= { h3cE1T1VITrapPrefix 1 }

END
