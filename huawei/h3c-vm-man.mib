-- ===========================================================================================================
-- Copyright (C) 2007 by H3C TECHNOLOGIES. All rights reserved.
--
-- Description: H3C VM(Video Management) Feature Configuration management MIB
-- Reference:
-- Version: V1.0
-- History:
-- V1.0 Initial version 2007-04-13 created by zhoujianming
--- ============================================================================================================
H3C-VM-MAN-MIB DEFINITIONS ::= BEGIN

IMPORTS
    entPhysicalAssetID
        FROM ENTITY-MIB
    Integer32, Unsigned32,IpAddress, Counter32, OBJECT-TYPE,
    MODULE-IDENTITY, NOTIFICATION-TYPE
        FROM SNMPv2-SMI
    DateAndTime, DisplayString
        FROM SNMPv2-TC
    h3cSurveillanceMIB
        FROM HUAWEI-3COM-OID-MIB;


h3cVMMan MODULE-IDENTITY
    LAST-UPDATED "200704130000Z"        -- April 13, 2007  GMT
    ORGANIZATION
        "H3C Technologies Co., Ltd."
    CONTACT-INFO
        "Surveillance Network Management Team H3C Technologies Co.,Ltd.
        Shang-Di Information Industry Base,
        Hai-Dian District Beijing P.R. China
        http://www.h3c.com
        Zip:100085"
    DESCRIPTION
        "VM is one of surveillance features, implementing user authentication,
        configuration management, network management and control signalling
        forwarding.
        This MIB contains objects to manage the VM feature."
    ::= { h3cSurveillanceMIB 1 }

--
-- Node definitions
--

h3cVMManMIBObjects OBJECT IDENTIFIER ::= { h3cVMMan 1 }

h3cVMCapabilitySet OBJECT-TYPE
    SYNTAX BITS
    {
        cms(0),
        css(1),
        dm(2)
    }
    MAX-ACCESS read-only
    STATUS current
    DESCRIPTION
        "Components included in the VM feature represented by bit fields. VM feature
        includes three componets: CMS(Central Management Server), CSS(Control Signalling
        Server) and DM(Data Managment).
        A bit set to 1 indicates the corresponding component of this bit is included
        otherwise indicates the corresponding component of this bit is not included. VM
        can include one or more components at one time.
        "
    ::= { h3cVMManMIBObjects 1 }

--
-- statistics
--
h3cVMStat OBJECT IDENTIFIER ::= { h3cVMManMIBObjects 2 }

h3cVMStatTotalConnEstablishRequests OBJECT-TYPE
    SYNTAX      Counter32
    MAX-ACCESS  read-only
    STATUS      current
    DESCRIPTION
        "The total number of establishment requests for video connection."
    ::= { h3cVMStat 1 }

h3cVMStatSuccConnEstablishRequests OBJECT-TYPE
    SYNTAX      Counter32
    MAX-ACCESS  read-only
    STATUS      current
    DESCRIPTION
        "The total number of successful establishment requests for video connection."
    ::= { h3cVMStat 2 }

h3cVMStatFailConnEstablishRequests OBJECT-TYPE
    SYNTAX      Counter32
    MAX-ACCESS  read-only
    STATUS      current
    DESCRIPTION
        "The total number of unsuccessful establishment requests for video connection."
    ::= { h3cVMStat 3 }

h3cVMStatTotalConnReleaseRequests OBJECT-TYPE
    SYNTAX      Counter32
    MAX-ACCESS  read-only
    STATUS      current
    DESCRIPTION
        "The total number of release requests for video connection."
    ::= { h3cVMStat 4 }

h3cVMStatSuccConnReleaseRequests OBJECT-TYPE
    SYNTAX      Counter32
    MAX-ACCESS  read-only
    STATUS      current
    DESCRIPTION
        "The total number of successful release requests for video connection."
    ::= { h3cVMStat 5 }

h3cVMStatFailConnReleaseRequests OBJECT-TYPE
    SYNTAX      Counter32
    MAX-ACCESS  read-only
    STATUS      current
    DESCRIPTION
        "The total number of unsuccessful release requests for video connection."
    ::= { h3cVMStat 6 }

h3cVMStatExceptionTerminationConn OBJECT-TYPE
    SYNTAX      Counter32
    MAX-ACCESS  read-only
    STATUS      current
    DESCRIPTION
        "The total number of exceptional termination for video connection."
    ::= { h3cVMStat 7 }


--
-- Notification definitions
--
-- =================================================================
-- Traps are defined below.
h3cVMManMIBTrap OBJECT IDENTIFIER ::= { h3cVMMan 2 }

-- All trap definitions should be placed under this object.
h3cVMManTrapPrex OBJECT IDENTIFIER ::= { h3cVMManMIBTrap 0 }

h3cVMManDeviceOnlineTrap NOTIFICATION-TYPE
    OBJECTS
    {
        entPhysicalAssetID,
        h3cVMManRegDevIP,
        h3cVMManRegDevName
    }
    STATUS  current
    DESCRIPTION
        "Send a trap about the device having been registered to VM."
    ::= { h3cVMManTrapPrex 1 }

h3cVMManDeviceOfflineTrap NOTIFICATION-TYPE
    OBJECTS
    {
        entPhysicalAssetID,
        h3cVMManRegDevIP,
        h3cVMManRegDevName
    }
    STATUS  current
    DESCRIPTION
        "Send a trap about the device having been unregistered to VM."
    ::= { h3cVMManTrapPrex 2 }

h3cVMManForwardDeviceExternalSemaphoreTrap NOTIFICATION-TYPE
    OBJECTS
    {
        entPhysicalAssetID,
        h3cVMManRegDevIP,
        h3cVMManRegDevName,
        h3cVMManPUExternalInputAlarmChannelID
    }
    STATUS  current
    DESCRIPTION
        "Forward a trap about external semaphore alarm, which is created
        by the third party device."
    ::= { h3cVMManTrapPrex 3 }

h3cVMManForwardDeviceVideoLossTrap NOTIFICATION-TYPE
    OBJECTS
    {
        entPhysicalAssetID,
        h3cVMManRegDevIP,
        h3cVMManRegDevName,
        h3cVMManPUECVideoChannelName
    }
    STATUS  current
    DESCRIPTION
        "Forward a trap about video loss, which is created by the third
        party device."
    ::= { h3cVMManTrapPrex 4 }

h3cVMManForwardDeviceVideoRecoverTrap NOTIFICATION-TYPE
    OBJECTS
    {
        entPhysicalAssetID,
        h3cVMManRegDevIP,
        h3cVMManRegDevName,
        h3cVMManPUECVideoChannelName
    }
    STATUS  current
    DESCRIPTION
        "Forward a trap about video recovery after loss, which is created
        by the third party device."
    ::= { h3cVMManTrapPrex 5 }

h3cVMManForwardDeviceMotionDetectTrap NOTIFICATION-TYPE
    OBJECTS
    {
        entPhysicalAssetID,
        h3cVMManRegDevIP,
        h3cVMManRegDevName,
        h3cVMManPUECVideoChannelName,
        h3cVMManRegionCoordinateX1,
        h3cVMManRegionCoordinateY1,
        h3cVMManRegionCoordinateX2,
        h3cVMManRegionCoordinateY2
    }
    STATUS  current
    DESCRIPTION
        "Forward a trap about motion detection, which is created by the
        third party device."
    ::= { h3cVMManTrapPrex 6 }

h3cVMManForwardDeviceCoverTrap NOTIFICATION-TYPE
    OBJECTS
    {
        entPhysicalAssetID,
        h3cVMManRegDevIP,
        h3cVMManRegDevName,
        h3cVMManPUECVideoChannelName,
        h3cVMManRegionCoordinateX1,
        h3cVMManRegionCoordinateY1,
        h3cVMManRegionCoordinateX2,
        h3cVMManRegionCoordinateY2
    }
    STATUS  current
    DESCRIPTION
        "Forward a trap about video cover, which is created by the third
        party device."
    ::= { h3cVMManTrapPrex 7 }

h3cVMManForwardDeviceCpuUsageThresholdTrap NOTIFICATION-TYPE
    OBJECTS
    {
        entPhysicalAssetID,
        h3cVMManRegDevIP,
        h3cVMManRegDevName,
        h3cVMManCpuUsage,
        h3cVMManCpuUsageThreshold
    }
    STATUS  current
    DESCRIPTION
        "Forward a trap about cpu usage exceeding its threshold, which is
        created by the third party device."
    ::= { h3cVMManTrapPrex 8 }

h3cVMManForwardDeviceMemUsageThresholdTrap NOTIFICATION-TYPE
    OBJECTS
    {
        entPhysicalAssetID,
        h3cVMManRegDevIP,
        h3cVMManRegDevName,
        h3cVMManMemUsage,
        h3cVMManMemUsageThreshold
    }
    STATUS  current
    DESCRIPTION
        "Forward a trap about memory usage exceeding its threshold, which is
        created by the third party device."
    ::= { h3cVMManTrapPrex 9 }

h3cVMManForwardDeviceHardDiskUsageThresholdTrap NOTIFICATION-TYPE
    OBJECTS
    {
        entPhysicalAssetID,
        h3cVMManRegDevIP,
        h3cVMManRegDevName,
        h3cVMManHardDiskUsage,
        h3cVMManHardDiskUsageThreshold
    }
    STATUS  current
    DESCRIPTION
        "Forward a trap about harddisk usage exceeding its threshold, which is
        created by the third party device."
    ::= { h3cVMManTrapPrex 10 }


h3cVMManForwardDeviceTemperatureThresholdTrap NOTIFICATION-TYPE
    OBJECTS
    {
        entPhysicalAssetID,
        h3cVMManRegDevIP,
        h3cVMManRegDevName,
        h3cVMManTemperature,
        h3cVMManTemperatureThreshold
    }
    STATUS  current
    DESCRIPTION
        "Forward a trap about temperature exceeding its threshold, which is created
        by the third party device."
    ::= { h3cVMManTrapPrex 11 }

h3cVMManForwardDeviceStartKinescopeTrap NOTIFICATION-TYPE
    OBJECTS
    {
        entPhysicalAssetID,
        h3cVMManRegDevIP,
        h3cVMManRegDevName,
        h3cVMManPUECVideoChannelName
    }
    STATUS  current
    DESCRIPTION
        "Forward a trap about starting kinescope, which is created by the third party
        device."
    ::= { h3cVMManTrapPrex 12 }

h3cVMManForwardDeviceStopKinescopeTrap NOTIFICATION-TYPE
    OBJECTS
    {
        entPhysicalAssetID,
        h3cVMManRegDevIP,
        h3cVMManRegDevName,
        h3cVMManPUECVideoChannelName
    }
    STATUS  current
    DESCRIPTION
        "Forward a trap about stopping kinescope, which is created by the third party
        device."
    ::= { h3cVMManTrapPrex 13 }

h3cVMManClientReportTrap NOTIFICATION-TYPE
    OBJECTS
    {
        entPhysicalAssetID,
        h3cVMManClientIP,
        h3cVMManUserName,
        h3cVMManReportContent
    }
    STATUS  current
    DESCRIPTION
        "Send a trap about the fault which is reported by clients."
    ::= { h3cVMManTrapPrex 14 }

h3cVMManClientRealtimeSurveillanceNoVideoTrap NOTIFICATION-TYPE
    OBJECTS
    {
        entPhysicalAssetID,
        h3cVMManClientIP,
        h3cVMManUserName,
        h3cVMManRegDevIP,
        h3cVMManRegDevName,
        h3cVMManPUECVideoChannelName
    }
    STATUS  current
    DESCRIPTION
        "Send a trap about no realtime surveillance video stream which is reported by clients.
        h3cVMManRegDevIP, entPhysicalAssetID, h3cVMManRegDevName and h3cVMManPUECVideoChannelName
        describe an EC's relative information. "
    ::= { h3cVMManTrapPrex 15 }

h3cVMManClientVODNoVideoTrap NOTIFICATION-TYPE
    OBJECTS
    {
        entPhysicalAssetID,
        h3cVMManClientIP,
        h3cVMManUserName,
        h3cVMManRegDevIP,
        h3cVMManRegDevName,
        h3cVMManPUECVideoChannelName,
        h3cVMManClientVODStart,
        h3cVMManClientVODEnd,
        h3cVMManIPSANDevIP
    }
    STATUS  current
    DESCRIPTION
        "Send a trap about no VOD video stream which is reported by clients. h3cVMManRegDevIP,
        entPhysicalAssetID, h3cVMManRegDevName and h3cVMManPUECVideoChannelName describe an EC's relative information."
    ::= { h3cVMManTrapPrex 16 }

h3cVMManClientRealtimeSurveillanceVideoStreamDiscontinuityTrap NOTIFICATION-TYPE
    OBJECTS
    {
        entPhysicalAssetID,
        h3cVMManClientIP,
        h3cVMManUserName,
        h3cVMManRegDevIP,
        h3cVMManRegDevName,
        h3cVMManPUECVideoChannelName,
        h3cVMManClientVideoStreamDiscontinuityInterval,
        h3cVMManClientVideoStreamDiscontinuityIntervalThreshold,
        h3cVMManClientStatPeriod
    }
    STATUS  current
    DESCRIPTION
        "Send a trap about the realtime surveillance video stream discontinuity which is reported by clients.
        entPhysicalAssetID, h3cVMManRegDevIP, h3cVMManRegDevName and h3cVMManPUECVideoChannelName describe an EC's relative
        information."
    ::= { h3cVMManTrapPrex 17 }

h3cVMManClientVODVideoStreamDiscontinuityTrap NOTIFICATION-TYPE
    OBJECTS
    {
        entPhysicalAssetID,
        h3cVMManClientIP,
        h3cVMManUserName,
        h3cVMManRegDevIP,
        h3cVMManRegDevName,
        h3cVMManPUECVideoChannelName,
        h3cVMManClientVODStart,
        h3cVMManClientVODEnd,
        h3cVMManIPSANDevIP,
        h3cVMManClientVideoStreamDiscontinuityInterval,
        h3cVMManClientVideoStreamDiscontinuityIntervalThreshold,
        h3cVMManClientStatPeriod
    }
    STATUS  current
    DESCRIPTION
        "Send a trap about the VOD video stream discontinuity which is reported by clients.
        h3cVMManRegDevIP, entPhysicalAssetID, h3cVMManRegDevName and h3cVMManPUECVideoChannelName
        describe an EC's relative information."
    ::= { h3cVMManTrapPrex 18 }

h3cVMManClientCtlConnExceptionTerminationTrap NOTIFICATION-TYPE
    OBJECTS
    {
        entPhysicalAssetID,
        h3cVMManClientIP,
        h3cVMManUserName
    }
    STATUS  current
    DESCRIPTION
        "Send a trap about the exceptional termination for control connection. "
    ::= { h3cVMManTrapPrex 19 }

h3cVMManClientFrequencyLoginFailTrap NOTIFICATION-TYPE
    OBJECTS
    {
        entPhysicalAssetID,
        h3cVMManClientIP,
        h3cVMManUserName,
        h3cVMManClientLoginFailNum,
        h3cVMManClientLoginFailNumThreshold,
        h3cVMManClientStatPeriod
    }
    STATUS  current
    DESCRIPTION
        "Send a trap about the frequency of client login failure."
    ::= { h3cVMManTrapPrex 20 }

h3cVMManClientFrequencyVODFailTrap NOTIFICATION-TYPE
    OBJECTS
    {
        entPhysicalAssetID,
        h3cVMManClientIP,
        h3cVMManUserName,
        h3cVMManClientVODFailNum,
        h3cVMManClientVODFailNumThreshold,
        h3cVMManClientStatPeriod
    }
    STATUS  current
    DESCRIPTION
        "Send a trap about the frequency of client VOD failure."
    ::= { h3cVMManTrapPrex 21 }

-- All DM trap definitions should be placed here.
h3cVMManDMECDisobeyStorageScheduleTrap NOTIFICATION-TYPE
    OBJECTS
    {
        entPhysicalAssetID,
        h3cVMManRegDevIP,
        h3cVMManPUECVideoChannelName
    }
    STATUS  current
    DESCRIPTION
        "Send a trap about EC disobeying storage schedule created by DM."
    ::= { h3cVMManTrapPrex 22 }

h3cVMManDMECDisobeyStorageScheduleRecoverTrap NOTIFICATION-TYPE
    OBJECTS
    {
        entPhysicalAssetID,
        h3cVMManRegDevIP,
        h3cVMManPUECVideoChannelName
    }
    STATUS  current
    DESCRIPTION
        "Send a trap about recovery after EC disobeying storage schedule created by DM."
    ::= { h3cVMManTrapPrex 23 }


-- All objects used for TRAP only are defined here.
h3cVMManTrapObjects OBJECT IDENTIFIER ::= { h3cVMManMIBTrap 1 }

h3cVMManIPSANDevIP OBJECT-TYPE
    SYNTAX      IpAddress
    MAX-ACCESS  accessible-for-notify
    STATUS      current
    DESCRIPTION
        "IP address of IPSAN Device which can store video data."
    ::= { h3cVMManTrapObjects 1 }

h3cVMManRegDevIP OBJECT-TYPE
    SYNTAX      IpAddress
    MAX-ACCESS  accessible-for-notify
    STATUS      current
    DESCRIPTION
        "IP address of devices which can registered or unregistered to VM."
    ::= { h3cVMManTrapObjects 2 }

h3cVMManRegDevName OBJECT-TYPE
    SYNTAX      DisplayString (SIZE (0..64))
    MAX-ACCESS  accessible-for-notify
    STATUS      current
    DESCRIPTION
        "Name of devices which can registered or unregistered to VM."
    ::= { h3cVMManTrapObjects 3 }

h3cVMManRegionCoordinateX1 OBJECT-TYPE
    SYNTAX      Unsigned32
    MAX-ACCESS  accessible-for-notify
    STATUS      current
    DESCRIPTION
        "The horizontal coordinate of top left point of the motion detection region."
    ::= { h3cVMManTrapObjects 4 }

h3cVMManRegionCoordinateY1 OBJECT-TYPE
    SYNTAX      Unsigned32
    MAX-ACCESS  accessible-for-notify
    STATUS      current
    DESCRIPTION
        "The vertical coordinate of top left point of the motion detection region."
    ::= { h3cVMManTrapObjects 5 }

h3cVMManRegionCoordinateX2 OBJECT-TYPE
    SYNTAX      Unsigned32
    MAX-ACCESS  accessible-for-notify
    STATUS      current
    DESCRIPTION
        "The horizontal coordinate of botton right point of the motion detection region."
    ::= { h3cVMManTrapObjects 6 }

h3cVMManRegionCoordinateY2 OBJECT-TYPE
    SYNTAX      Unsigned32
    MAX-ACCESS  accessible-for-notify
    STATUS      current
    DESCRIPTION
        "The horizontal coordinate of botton right point of the motion detection region."
    ::= { h3cVMManTrapObjects 7 }

h3cVMManCpuUsage OBJECT-TYPE
    SYNTAX      Unsigned32 ( 0..100 )
    MAX-ACCESS  accessible-for-notify
    STATUS      current
    DESCRIPTION
        "The CPU usage for this entity. Generally, the CPU usage
        will caculate the overall CPU usage on the entity, and it
        is not sensible with the number of CPU on the entity. "
    ::= { h3cVMManTrapObjects 8 }

h3cVMManCpuUsageThreshold OBJECT-TYPE
    SYNTAX      Unsigned32 ( 0..100 )
    MAX-ACCESS  accessible-for-notify
    STATUS      current
    DESCRIPTION
        "The threshold for the CPU usage. When the CPU usage exceeds
        the threshold, a notification will be sent."
    ::= { h3cVMManTrapObjects 9 }

h3cVMManMemUsage OBJECT-TYPE
    SYNTAX      Unsigned32 ( 0..100 )
    MAX-ACCESS  accessible-for-notify
    STATUS      current
    DESCRIPTION
        "The memory usage for the entity. This object indicates what
        percent of memory are used. "
    ::= { h3cVMManTrapObjects 10 }

h3cVMManMemUsageThreshold OBJECT-TYPE
    SYNTAX      Unsigned32 ( 0..100 )
    MAX-ACCESS  accessible-for-notify
    STATUS      current
    DESCRIPTION
        "The threshold for the Memory usage. When the memory usage
        exceeds the threshold, a notification will be sent. "
    ::= { h3cVMManTrapObjects 11 }

h3cVMManHardDiskUsage OBJECT-TYPE
    SYNTAX      Unsigned32 ( 0..100 )
    MAX-ACCESS  accessible-for-notify
    STATUS      current
    DESCRIPTION
        "The hard disk usage for the entity. This object indicates what
        percent of hard disk are used. "
    ::= { h3cVMManTrapObjects 12 }

h3cVMManHardDiskUsageThreshold OBJECT-TYPE
    SYNTAX      Unsigned32 ( 0..100 )
    MAX-ACCESS  accessible-for-notify
    STATUS      current
    DESCRIPTION
        "The threshold for the hard disk usage. When the hard disk usage
        exceeds the threshold, a notification will be sent. "
    ::= { h3cVMManTrapObjects 13 }

h3cVMManTemperature OBJECT-TYPE
    SYNTAX      Integer32
    MAX-ACCESS  accessible-for-notify
    STATUS      current
    DESCRIPTION
        "The temperature for the entity. "
    ::= { h3cVMManTrapObjects 14 }

h3cVMManTemperatureThreshold OBJECT-TYPE
    SYNTAX      Integer32
    MAX-ACCESS  accessible-for-notify
    STATUS      current
    DESCRIPTION
        "The threshold for the temperature. When the temperature
        exceeds the threshold, a notification will be sent. "
    ::= { h3cVMManTrapObjects 15 }

h3cVMManClientIP OBJECT-TYPE
    SYNTAX      IpAddress
    MAX-ACCESS  accessible-for-notify
    STATUS      current
    DESCRIPTION
        "The client device IP address."
    ::= { h3cVMManTrapObjects 16 }

h3cVMManUserName OBJECT-TYPE
    SYNTAX      DisplayString (SIZE (0..32))
    MAX-ACCESS  accessible-for-notify
    STATUS      current
    DESCRIPTION
        "The client user name."
    ::= { h3cVMManTrapObjects 17 }

h3cVMManReportContent OBJECT-TYPE
    SYNTAX      DisplayString (SIZE (0..128))
    MAX-ACCESS  accessible-for-notify
    STATUS      current
    DESCRIPTION
        "The details of the fault which reported by clients"
    ::= { h3cVMManTrapObjects 18 }

h3cVMManClientVideoStreamDiscontinuityInterval OBJECT-TYPE
    SYNTAX      Unsigned32
    MAX-ACCESS  accessible-for-notify
    STATUS      current
    DESCRIPTION
        "Video stream discontinuity interval. "
    ::= { h3cVMManTrapObjects 19 }

h3cVMManClientVideoStreamDiscontinuityIntervalThreshold OBJECT-TYPE
    SYNTAX      Unsigned32
    MAX-ACCESS  accessible-for-notify
    STATUS      current
    DESCRIPTION
        "The threshold for the video stream discontinuity interval. When the
        discontinuity interval exceeds the threshold, a notification will be sent. "
    ::= { h3cVMManTrapObjects 20 }

h3cVMManClientStatPeriod OBJECT-TYPE
    SYNTAX      Unsigned32
    MAX-ACCESS  accessible-for-notify
    STATUS      current
    DESCRIPTION
        "The client statistic period. "
    ::= { h3cVMManTrapObjects 21 }

h3cVMManClientLoginFailNum OBJECT-TYPE
    SYNTAX      Unsigned32
    MAX-ACCESS  accessible-for-notify
    STATUS      current
    DESCRIPTION
        "The total number of client login failure in last statistic period which is
        defined by h3cVMManClientStatPeriod entity."
    ::= { h3cVMManTrapObjects 22 }

h3cVMManClientLoginFailNumThreshold OBJECT-TYPE
    SYNTAX      Unsigned32
    MAX-ACCESS  accessible-for-notify
    STATUS      current
    DESCRIPTION
        "The threshold for the total number of client login failure in last statistic
        period. When the number exceeds the threshold, a notification will be sent. "
    ::= { h3cVMManTrapObjects 23 }

h3cVMManClientVODFailNum OBJECT-TYPE
    SYNTAX      Unsigned32
    MAX-ACCESS  accessible-for-notify
    STATUS      current
    DESCRIPTION
        "The total number of client VOD failure in last statistic period which is
        defined by h3cVMManClientStatPeriod entity."
    ::= { h3cVMManTrapObjects 24 }

h3cVMManClientVODFailNumThreshold OBJECT-TYPE
    SYNTAX      Unsigned32
    MAX-ACCESS  accessible-for-notify
    STATUS      current
    DESCRIPTION
        "The threshold for the total number of client VOD failure in last statistic
        period. When the number exceeds the threshold, a notification will be sent. "
    ::= { h3cVMManTrapObjects 25 }

h3cVMManClientVODStart OBJECT-TYPE
    SYNTAX DateAndTime
    MAX-ACCESS accessible-for-notify
    STATUS current
    DESCRIPTION
        "The start time for VOD."
    ::= { h3cVMManTrapObjects 26 }

h3cVMManClientVODEnd OBJECT-TYPE
    SYNTAX DateAndTime
    MAX-ACCESS accessible-for-notify
    STATUS current
    DESCRIPTION
        "The end time for VOD."
    ::= { h3cVMManTrapObjects 27 }

h3cVMManPUExternalInputAlarmChannelID  OBJECT-TYPE
    SYNTAX  Unsigned32
    MAX-ACCESS accessible-for-notify
    STATUS current
    DESCRIPTION
        "The ID of the external input alarm channel."
    ::= { h3cVMManTrapObjects 28 }

h3cVMManPUECVideoChannelName  OBJECT-TYPE
    SYNTAX  DisplayString (SIZE (0..32))
    MAX-ACCESS accessible-for-notify
    STATUS current
    DESCRIPTION
        "The name of the video channel. It is suggested that the name includes
        the channel ID information."
    ::= { h3cVMManTrapObjects 29 }

END
