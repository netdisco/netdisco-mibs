-- =================================================================
-- Copyright (C) 2014 by  HUAWEI TECHNOLOGIES. All rights reserved
-- 
-- Description: HUAWEI-LSP-PING-TRACE-TRAP-MIB. 
-- Reference:
-- Version:     V2.01
-- History:
--              
--  
-- =================================================================

	HUAWEI-LSP-PING-TRACE-TRAP-MIB DEFINITIONS ::= BEGIN
 
		IMPORTS
			hwDatacomm			
				FROM HUAWEI-MIB			
			OBJECT-GROUP, NOTIFICATION-GROUP, MODULE-COMPLIANCE			
				FROM SNMPv2-CONF			
			mgmt, Integer32, OBJECT-TYPE, MODULE-IDENTITY, NOTIFICATION-TYPE			
				FROM SNMPv2-SMI;
	
	
--  November 16, 2011 at 15:41 GMT
		-- 1.3.6.1.4.1.2011.5.25.302
		hwLsppttMIB MODULE-IDENTITY 
			LAST-UPDATED "201411171914Z"
			ORGANIZATION 
			        "Huawei Technologies Co.,Ltd."
			CONTACT-INFO 
				"Huawei Industrial Base
                                  Bantian, Longgang
                                   Shenzhen 518129
                                   People's Republic of China
                                   Website: http://www.huawei.com
                                   Email: support@huawei.com
                                 "
			DESCRIPTION 
				"HUAWEI lsp quality detect funcion."

			REVISION    "201411171914Z"   
                        DESCRIPTION "Add ipv4-vpn lsp ping trap."  
			
			REVISION    "201108071600Z"   
                        DESCRIPTION "V1.00, initial version."                          
			::= { hwDatacomm 302 }

		
	
	
--
-- Node definitions
--
	
		-- 1.3.6.1.4.1.2011.5.25.302.2
		hwLspTrapObject OBJECT IDENTIFIER ::= { hwLsppttMIB 2 }

		
		-- 1.3.6.1.4.1.2011.5.25.302.2.1
		hwLspTunnelID OBJECT-TYPE
			SYNTAX Integer32
			MAX-ACCESS accessible-for-notify
			STATUS current
			DESCRIPTION
				"lsp tunnel id."
			::= { hwLspTrapObject 1 }

		
		-- 1.3.6.1.4.1.2011.5.25.302.2.2
		hwLspSenderAddress OBJECT-TYPE
			SYNTAX Integer32
			MAX-ACCESS accessible-for-notify
			STATUS current
			DESCRIPTION
				"lsp sender address."
			::= { hwLspTrapObject 2 }

		
		-- 1.3.6.1.4.1.2011.5.25.302.2.3
		hwLspEndPointAddress OBJECT-TYPE
			SYNTAX Integer32
			MAX-ACCESS accessible-for-notify
			STATUS current
			DESCRIPTION
				"lsp end point address."
			::= { hwLspTrapObject 3 }

		
		-- 1.3.6.1.4.1.2011.5.25.302.2.4
		hwLspTTL OBJECT-TYPE
			SYNTAX Integer32
			MAX-ACCESS accessible-for-notify
			STATUS current
			DESCRIPTION
				"lsp ttl."
			::= { hwLspTrapObject 4 }

		
		-- 1.3.6.1.4.1.2011.5.25.302.2.5
		hwLspHandle OBJECT-TYPE
			SYNTAX Integer32
			MAX-ACCESS accessible-for-notify
			STATUS current
			DESCRIPTION
				"lsp handle."
			::= { hwLspTrapObject 5 }


		-- 1.3.6.1.4.1.2011.5.25.302.2.6
		hwLspIPv4VpnName OBJECT-TYPE
			SYNTAX OCTET STRING (SIZE(0..31)) 
			MAX-ACCESS accessible-for-notify
			STATUS current
			DESCRIPTION
				"Ipv4 vpn name."
			::= { hwLspTrapObject 6 }


		-- 1.3.6.1.4.1.2011.5.25.302.2.7
		hwLspIPv4VpnSrcAddr OBJECT-TYPE
			SYNTAX Integer32                               
			MAX-ACCESS accessible-for-notify
			STATUS current
			DESCRIPTION
				"destination address of IPv4-Vpn lsp."
			::= { hwLspTrapObject 7 }



		-- 1.3.6.1.4.1.2011.5.25.302.2.8
		hwLspIPv4VpnDstAddr OBJECT-TYPE
			SYNTAX Integer32                               
			MAX-ACCESS accessible-for-notify
			STATUS current
			DESCRIPTION
				"Destination address mask of IPv4-Vpn lsp."
			::= { hwLspTrapObject 8 }	

		
		-- 1.3.6.1.4.1.2011.5.25.302.3
		hwLspNotifications OBJECT IDENTIFIER ::= { hwLsppttMIB 3 }

		
		-- 1.3.6.1.4.1.2011.5.25.302.3.1
		hwLspPingProbe NOTIFICATION-TYPE
			OBJECTS { hwLspTunnelID, hwLspSenderAddress, hwLspEndPointAddress, hwLspTTL, hwLspHandle
				 }
			STATUS current
			DESCRIPTION 
				"lsp ping probe trap."
			::= { hwLspNotifications 1 }

		
		-- 1.3.6.1.4.1.2011.5.25.302.3.2
		hwLspTraceProbe NOTIFICATION-TYPE
			OBJECTS { hwLspTunnelID, hwLspSenderAddress, hwLspEndPointAddress, hwLspTTL, hwLspHandle
				 }
			STATUS current
			DESCRIPTION 
				"lsp trace probe trap."
			::= { hwLspNotifications 2 }


		-- 1.3.6.1.4.1.2011.5.25.302.3.3
		hwLspPingIPv4VpnProbe NOTIFICATION-TYPE
			OBJECTS { hwLspIPv4VpnName, hwLspIPv4VpnSrcAddr, hwLspIPv4VpnDstAddr, hwLspTTL, hwLspHandle }
			STATUS current
			DESCRIPTION 
			"The trap indicates that a device received a not-reply ping request on IPv4 VPN LSP."
			::= { hwLspNotifications 3 }


		hwLspConformance OBJECT IDENTIFIER ::= { hwLsppttMIB 4 }				                             
        
		-- 1.3.6.1.4.1.2011.5.25.302.4
		hwLspGroup OBJECT IDENTIFIER ::= { hwLspConformance 1 }
		
		hwLspCompliances OBJECT IDENTIFIER ::= { hwLspConformance 2 }
				
		hwLspCompliance MODULE-COMPLIANCE
			STATUS current
			DESCRIPTION 
				"Description."
			MODULE -- this module
			MANDATORY-GROUPS { hwLspNotificationsGroup, hwLspObjectGroup}
			::= { hwLspCompliances 1 }	

		
		-- 1.3.6.1.4.1.2011.5.25.302.4.1
		hwLspNotificationsGroup NOTIFICATION-GROUP
			NOTIFICATIONS { hwLspPingProbe, hwLspTraceProbe, hwLspPingIPv4VpnProbe }
			STATUS current
			DESCRIPTION 
				"trap group."
			::= { hwLspGroup 1 }

		
		-- 1.3.6.1.4.1.2011.5.25.302.4.2
		hwLspObjectGroup OBJECT-GROUP
			OBJECTS { hwLspTunnelID, hwLspTTL, hwLspHandle, hwLspSenderAddress, hwLspEndPointAddress, hwLspIPv4VpnName, hwLspIPv4VpnSrcAddr, hwLspIPv4VpnDstAddr }
			STATUS current
			DESCRIPTION 
				"lsp object group."
			::= { hwLspGroup 2 }
					
	
	END

--
-- HUAWEI-LSP-PING-TRACE-TRAP-MIB.mib
--
