--===========================================================
-- Copyright (C) 2003 by HUAWEI-3Com TECHNOLOGIES.  All rights reserved.
--
-- Description:  HUAWEI LAN Switch huawei-3com Interface Management MIB
-- Reference:  IF-MIB
-- Version:  V1.1
-- History:
-- V1.0 created by liuhongxu and zoudian.
--   Initial version 2006-01-10
-- V1.1 2006-06-08 Updated by chenzhaojie
--   Change description of h3cTransceiverWaveLength
--=================================================================
H3C-TRANSCEIVER-INFO-MIB DEFINITIONS ::= BEGIN
IMPORTS

    MODULE-IDENTITY, OBJECT-TYPE, Integer32
        FROM SNMPv2-SMI

    ifEntry, ifIndex
        FROM RFC1213-MIB
        
    h3cCommon
        FROM HUAWEI-3COM-OID-MIB;

    h3cTransceiver MODULE-IDENTITY
        LAST-UPDATED "200601101452Z"
        ORGANIZATION
            "Huawei-3COM Technologies Co., Ltd."
        CONTACT-INFO
            "Platform Team Huawei 3Com Technologies Co., Ltd.
            Hai-Dian District Beijing P.R.  China
            http://www.huawei-3com.com
            Zip:100085"

        DESCRIPTION
            "The objects in this MIB module are used to display the
            information of transceiver on interface."
            ::= { h3cCommon 70 }    
            
    h3cTransceiverInfoAdm OBJECT IDENTIFIER ::= { h3cTransceiver 1 }

    h3cTransceiverInfoTable OBJECT-TYPE
        SYNTAX SEQUENCE OF H3cTransceiverInfoEntry
        MAX-ACCESS not-accessible
        STATUS current
        DESCRIPTION
            "This table show the information of transceiver on interface."
        ::= { h3cTransceiverInfoAdm 1 }
      
    h3cTransceiverInfoEntry OBJECT-TYPE
        SYNTAX H3cTransceiverInfoEntry
        MAX-ACCESS not-accessible
        STATUS current
        DESCRIPTION
            "The entry of the h3cTransceiverInfoTable."
        INDEX { ifIndex }
        ::= { h3cTransceiverInfoTable 1 }

    H3cTransceiverInfoEntry ::=
        SEQUENCE {
            h3cTransceiverHardwareType
                OCTET STRING,
            h3cTransceiverType
                OCTET STRING,
            h3cTransceiverWaveLength
                Integer32,
            h3cTransceiverVendorName
                OCTET STRING,
            h3cTransceiverSerialNumber 
                OCTET STRING,
            h3cTransceiverFiberDiameterType  
                INTEGER,   
            h3cTransceiverTransferDistance  
                Integer32                     
        }

    h3cTransceiverHardwareType OBJECT-TYPE
        SYNTAX OCTET STRING
        MAX-ACCESS read-only
        STATUS current
        DESCRIPTION
            "Hardware type of the interface, such as SM(single mode)."
        ::= { h3cTransceiverInfoEntry 1 }                           
                
    h3cTransceiverType OBJECT-TYPE
        SYNTAX OCTET STRING
        MAX-ACCESS read-only
        STATUS current
        DESCRIPTION
            "Type of the interface, such as SFP/XFP/GBIC."
        ::= { h3cTransceiverInfoEntry 2 }           
        
    h3cTransceiverWaveLength OBJECT-TYPE
        SYNTAX Integer32
        MAX-ACCESS read-only
        STATUS current
        DESCRIPTION
            "Wave length of the interface, measured in nanometer."
        ::= { h3cTransceiverInfoEntry 3 } 
            
    h3cTransceiverVendorName OBJECT-TYPE
        SYNTAX OCTET STRING
        MAX-ACCESS read-only
        STATUS current
        DESCRIPTION
            "Vendor name of the interface."
        ::= { h3cTransceiverInfoEntry 4 }                            
                
    h3cTransceiverSerialNumber OBJECT-TYPE
        SYNTAX OCTET STRING
        MAX-ACCESS read-only
        STATUS current
        DESCRIPTION
            "Serial number of the interface."
        ::= { h3cTransceiverInfoEntry 5 }          
        
    h3cTransceiverFiberDiameterType OBJECT-TYPE
        SYNTAX INTEGER
            {
              fiber9(1),
              fiber50(2),
              fiber625(3),
              copper(4)                 
            }
        MAX-ACCESS read-only
        STATUS current
        DESCRIPTION
            "The diameter of the fiber, measured in micron.
            fiber9 - 9 micron multi-mode fiber
            fiber50 - 50 micron multi-mode fiber
            fiber625 - 62.5 micron multi-mode fiber
            copper - copper cable."
        ::= { h3cTransceiverInfoEntry 6 }
     
    h3cTransceiverTransferDistance OBJECT-TYPE
        SYNTAX Integer32    
        MAX-ACCESS read-only
        STATUS current
        DESCRIPTION
            "The max distance which the interface could transmit,
            measured in micron."
        ::= { h3cTransceiverInfoEntry 7 }     
           
END
