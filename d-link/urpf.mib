-- -----------------------------------------------------------------------------
-- MIB NAME : Unicast Reverse Path Forwarding Common mib
-- FILE NAME: URPF.mib
-- DATE     : 2012/07/20
-- VERSION  : 1.00
-- PURPOSE  : To construct the MIB structure of Unicast Reverse Path
--            Forwarding for proprietary enterprise
-- -----------------------------------------------------------------------------
-- MODIFICTION HISTORY:
-- -----------------------------------------------------------------------------
-- Version, Date, Author
-- Description:
-- [New Object]
-- [Modification]
-- Notes: (Requested by who and which project)
--
-- Version 1.00, 2012/07/20, Eric Shu
-- This is the first formal version for universal MIB definition.
-- -----------------------------------------------------------------------------

URPF-MIB DEFINITIONS ::= BEGIN

	IMPORTS

	          MODULE-IDENTITY, OBJECT-TYPE
        			FROM SNMPv2-SMI
	          dlink-common-mgmt
	          		FROM DLINK-ID-REC-MIB;

	swUrpfMIB MODULE-IDENTITY
	    LAST-UPDATED "1207200000Z"
	    ORGANIZATION "D-Link Corp."
	    CONTACT-INFO
	        "http://support.dlink.com"
	    DESCRIPTION
		    "The MIB module for managing
		     Unicast Reverse Path Forwarding."
        ::= { dlink-common-mgmt 107 }

-- -----------------------------------------------------------------------------
-- swUrpfChekingTable
-- -----------------------------------------------------------------------------

    swUrpfGlobalState OBJECT-TYPE
        SYNTAX  INTEGER {
                    enabled(1),
                    disabled(2)
                }
        MAX-ACCESS  read-write
        STATUS  current
        DESCRIPTION
            "Enable or disable the URPF global state.
             Note that the new state will not take
             effect until saving and rebooting"
        ::= { swUrpfMIB 1 }

    swUrpfTable OBJECT-TYPE
        SYNTAX  SEQUENCE OF SwUrpfEntry
        MAX-ACCESS  not-accessible
        STATUS  current
        DESCRIPTION
            "A table containing URPF checking
            information of ports."
        ::= { swUrpfMIB 2 }

    swUrpfEntry OBJECT-TYPE
        SYNTAX  SwUrpfEntry
        MAX-ACCESS  not-accessible
        STATUS  current
        DESCRIPTION
            "A list containing URPF checking
            information of ports."
        INDEX  { swUrpfPorts }
        ::= { swUrpfTable 1 }

   SwUrpfEntry ::=
        SEQUENCE {
            swUrpfPorts
                INTEGER,
            swUrpfMode
                INTEGER,
            swUrpfDefaultRouteCheck
                INTEGER
        }

    swUrpfPorts OBJECT-TYPE
        SYNTAX  INTEGER
        MAX-ACCESS  not-accessible
        STATUS  current
        DESCRIPTION
            "The port number."
        ::= { swUrpfEntry 1 }

    swUrpfMode OBJECT-TYPE
        SYNTAX  INTEGER {
                    loose(1),
                    strict(2),
                    disabled(3)
                }
        MAX-ACCESS  read-write
        STATUS  current
        DESCRIPTION
            "The type of URPF checks. There are two
            types:
            loose: It will merely verify the source
            IP address is present in the routing table.
            strict: Checks are performed to ensure
            that the SIP address is present in the
            routing table and the incoming L3
            interface matches the SIP's L3 interface
            in the routing table."
        ::= { swUrpfEntry 2 }

    swUrpfDefaultRouteCheck OBJECT-TYPE
        SYNTAX  INTEGER{	
                    enabled(1),
                    disabled(2)
                }
        MAX-ACCESS  read-write
        STATUS  current
        DESCRIPTION
            "Whether perform URPF check on default
            route in the routing table.
            Enabled: If the source IP address of the
            incoming packet only matches the default
            route, the packet will be dropped.
            Disable: If the source IP address of the
            incoming packet only matches the default
            route, the packet will be passed."
        ::= { swUrpfEntry 3 }

END
