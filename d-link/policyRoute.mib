-- -----------------------------------------------------------------------------
-- MIB NAME : POLICY-ROUTE-MIB
-- FILE NAME: policyRoute.mib
-- DATE     : 2012/05/28
-- VERSION  : 0.10
-- PURPOSE  : To construct the MIB structure of policy base route function
-- -----------------------------------------------------------------------------
-- MODIFICTION HISTORY:
-- -----------------------------------------------------------------------------
-- Version, Date, Author
-- Description:
--  [New Object]
--  [Modification]
-- Notes: (Requested by who and which project)
--
-- Revision 0.10, 2012/05/28, Dinah Zhou
-- [New Object]
--   [1]Add the object swPolicyRoutePreference.
-- Notes: Requested by Dinah for project DGS3600R3.
--
-- Version 0.09, 2006/2/23
-- This is the first formal version for universal MIB definition.
-- -----------------------------------------------------------------------------

POLICY-ROUTE-MIB DEFINITIONS ::= BEGIN

    IMPORTS
        MODULE-IDENTITY,OBJECT-TYPE,IpAddress, Unsigned32
                                        FROM SNMPv2-SMI
        MacAddress, RowStatus           FROM SNMPv2-TC
        DisplayString                   FROM RFC1213-MIB
    	SnmpAdminString					FROM SNMP-FRAMEWORK-MIB

        dlink-common-mgmt				FROM DLINK-ID-REC-MIB;
        
		 
    	
    swPolicyRouteMIB MODULE-IDENTITY
	    LAST-UPDATED "0007150000Z"
	    ORGANIZATION " "
	    CONTACT-INFO
	        "    "
	    DESCRIPTION
		    "The Structure of policy route management for the
		    proprietary enterprise."
        ::= { dlink-common-mgmt 32 }

-- *****************************************************************************
-- Textual Conventions
-- *****************************************************************************

   swPolicyRouteCtrl            OBJECT IDENTIFIER ::= { swPolicyRouteMIB 1 }
   swPolicyRouteInfo            OBJECT IDENTIFIER ::= { swPolicyRouteMIB 2 }
   swPolicyRouteMgmt            OBJECT IDENTIFIER ::= { swPolicyRouteMIB 3 }
   
--***********************************************************************************************
-- swPolicyRouteMgmt            OBJECT IDENTIFIER ::= { swPolicyRouteMIB 3 }
--*********************************************************************************************** 
   swPolicyRouteTable OBJECT-TYPE
        SYNTAX   SEQUENCE OF SwPolicyRouteEntry
        MAX-ACCESS not-accessible
        STATUS   current
        DESCRIPTION
        "This entity's policy Routing table."
        ::= { swPolicyRouteMgmt 1 }

    swPolicyRouteEntry OBJECT-TYPE
        SYNTAX   SwPolicyRouteEntry
        MAX-ACCESS not-accessible
        STATUS   current
        DESCRIPTION
           "A particular route to  a  particular  destination, under a particular policy."
        INDEX {
            swPolicyRouteName
            }
        ::= { swPolicyRouteTable 1 }
    
    SwPolicyRouteEntry ::=
        SEQUENCE {
            swPolicyRouteName
            	DisplayString,
            swPolicyRouteProfileId
                INTEGER,
            swPolicyRouteAccessId
                INTEGER,            
            swPolicyRouteNextHop
                IpAddress,
            swPolicyRouteRowStatus
                RowStatus,
            swPolicyRoutePreference
                INTEGER
        }
        
    swPolicyRouteName OBJECT-TYPE
        SYNTAX   DisplayString(SIZE(1..32))
        MAX-ACCESS read-only
        STATUS   current
        DESCRIPTION
           "Policy route rule name. Max length is 32 characters."
        ::= { swPolicyRouteEntry 1 }
    
    swPolicyRouteProfileId OBJECT-TYPE
        SYNTAX   INTEGER
        MAX-ACCESS read-write
        STATUS   current
        DESCRIPTION
           "The destination ACL profile ID of this route."
        ::= { swPolicyRouteEntry 2 }
    
    swPolicyRouteAccessId OBJECT-TYPE
        SYNTAX   INTEGER
        MAX-ACCESS read-write
        STATUS   current
        DESCRIPTION
           "The destination ACL access ID of this route."
        ::= { swPolicyRouteEntry 3 }    
        
    swPolicyRouteNextHop OBJECT-TYPE
        SYNTAX   IpAddress
        MAX-ACCESS read-write
        STATUS   current
        DESCRIPTION
           "On remote routes, the IP address of the next hop."
        ::= { swPolicyRouteEntry 4 }
    
    swPolicyRouteRowStatus  OBJECT-TYPE
        SYNTAX   RowStatus
        MAX-ACCESS read-create
        STATUS   current
        DESCRIPTION
           "To create a row in this table, a manager sets this object
         to either createAndGo(4) or createAndWait(5).
          
         When `swPolicyRouteRowStatus' is set to active(1),action this rule.
         
         When `swPolicyRouteRowStatus' is set to notInService(2),not action this rule."
        ::= { swPolicyRouteEntry 5 }      

    swPolicyRoutePreference OBJECT-TYPE
        SYNTAX      INTEGER     {
                    pbr (0) ,
                    default (1)
                  }
        MAX-ACCESS  read-write
        STATUS      current
        DESCRIPTION
           "The route preference of the policy route rule.
            The value 'default' indicate that the policy route rule has
            lower priority than the route in routing table, otherwise,
            the value 'pbr' indicate that the policy route rule has
            higher priority than the route in routing table."
        ::= { swPolicyRouteEntry 6 }

END
