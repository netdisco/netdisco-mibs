-- ***************************************************************************
-- MIB NAME : PPPoE Common mib
-- FILE NAME: PPPoEmgmt.mib
-- DATE     : 2014/05/23
-- VERSION  : 1.03
-- PURPOSE  : To construct the MIB structure for PPPoE feature
--            for proprietary enterprise
-- ***************************************************************************
-- MODIFICATION HISTORY:
-- ***************************************************************************
-- Version, Date, Author
-- Description:
-- Notes: (Requested by who and which project)

-- Version 1.03, 2014/05/23, Wayne Kuo
--  [New Object]
--   1.	Add new OID swPPPoECirIDInsertPortRemoteIDUDFString 
--   2.	Add new "vendor3" in OID swPPPoECirIDInsertPortCirID and swPPPoECirIDInsertPortRemoteID value list
-- Request by Wayne Kuo for project DES3200C1 R4.38 to support SNR-20140110-001 (PPPoE Vendor3 Format)

-- Version 1.02, 2012/07/06, King Cao
-- Correct the spelling mistake, change "vender2" to "vendor2".

-- Version 1.01, 2012/05/11, Tina he
-- [New Object]
--   1.	Add new OID swPPPoECirIDInsertPortRemoteID 
--   2.	Add new "vendor2" in OID swPPPoECirIDInsertPortCirID value list
-- Request by Tina he for project DES3200 to support SNR-20111226-003
--  (Support ZTE PPPoE Circuit ID and Remote ID format)(use vendor2 as parameter)

-- Version 1.00, 2009/04/02, Ronald
-- This is the first formal version for universal MIB definition.
-- ***************************************************************************

PPPOE-MGMT-MIB DEFINITIONS ::= BEGIN
  IMPORTS
	MODULE-IDENTITY,OBJECT-TYPE			FROM SNMPv2-SMI
	dlink-common-mgmt					FROM DLINK-ID-REC-MIB
	DisplayString             FROM RFC1213-MIB;
		
	swPPPoEMIB MODULE-IDENTITY
		LAST-UPDATED "1405230000Z"
	  	ORGANIZATION "D-Link Corp"
	  	CONTACT-INFO
	   		"http://support.dlink.com"
	  	DESCRIPTION
	    		"The structure of PPPoE management for the proprietary enterprise."
	  	::= {dlink-common-mgmt 79}
	  	
	swPPPoEMgmtCtrl      OBJECT IDENTIFIER ::= { swPPPoEMIB 1 }	  	
	  		
-- ********************************************************************
--  swPPPoEMgmtCtrl               OBJECT IDENTIFIER ::= { swPPPoEMgmt 1 }
-- ********************************************************************
    swPPPoECirIDInsertState OBJECT-TYPE
        SYNTAX  INTEGER {
               enabled(1),  
               disabled(2)
               }
        MAX-ACCESS  read-write
        STATUS  current
        DESCRIPTION
            "This object indicates the status of the PPPoE circuit ID 
            insertion state of the switch."
        ::= { swPPPoEMgmtCtrl 1 }

-- ***************************************************************************
    swPPPoECirIDInsertPortMgmt       OBJECT IDENTIFIER ::= { swPPPoEMgmtCtrl 2 }

    swPPPoECirIDInsertPortTable OBJECT-TYPE
        SYNTAX      SEQUENCE OF SwPPPoECirIDInsertPortEntry
        MAX-ACCESS  not-accessible
        STATUS      current
        DESCRIPTION
            "The table specifies the PPPoE circuit ID insertion function 
             specified by the port."
        ::= { swPPPoECirIDInsertPortMgmt 1 }

    swPPPoECirIDInsertPortEntry OBJECT-TYPE
        SYNTAX      SwPPPoECirIDInsertPortEntry
        MAX-ACCESS  not-accessible
        STATUS      current
        DESCRIPTION
            "A list of information contained in swPPPoECirIDInsertPortTable."
        INDEX  { swPPPoECirIDInsertPortIndex }
        ::= { swPPPoECirIDInsertPortTable 1 }

    SwPPPoECirIDInsertPortEntry ::=
        SEQUENCE {
            swPPPoECirIDInsertPortIndex
                INTEGER,
            swPPPoECirIDInsertPortState
                INTEGER,
            swPPPoECirIDInsertPortCirID
                INTEGER,
            swPPPoECirIDInsertPortUDFString
                DisplayString,
            swPPPoECirIDInsertPortRemoteID
                INTEGER,
            swPPPoECirIDInsertPortRemoteIDUDFString
                DisplayString                
        }

    swPPPoECirIDInsertPortIndex OBJECT-TYPE
        SYNTAX      INTEGER (1..65535)
        MAX-ACCESS  not-accessible
        STATUS      current
        DESCRIPTION
            "This object indicates the module's port number. The range is from 1 to
             the maximum port number specified in the module"
        ::= { swPPPoECirIDInsertPortEntry 1 }

    swPPPoECirIDInsertPortState OBJECT-TYPE
        SYNTAX      INTEGER {
                       enabled(1),
                       disabled(2)
                    }
        MAX-ACCESS  read-write
        STATUS      current
        DESCRIPTION
            "This object indicates the PPPoE circuit ID insertion function state 
             on the port."
        ::= { swPPPoECirIDInsertPortEntry 2 }

    swPPPoECirIDInsertPortCirID OBJECT-TYPE
        SYNTAX      INTEGER {
                       switch-ip(1),
                       switch-mac(2),
                       udf-string(3),
                       vendor2(4),
                       vendor3(5)
                    }
        MAX-ACCESS  read-write
        STATUS      current
        DESCRIPTION
            "This object indicates the port circuit ID."
        ::= { swPPPoECirIDInsertPortEntry 3 }

    swPPPoECirIDInsertPortUDFString OBJECT-TYPE
        SYNTAX      DisplayString
        MAX-ACCESS  read-write
        STATUS      current
        DESCRIPTION
            "This object indicates the user define string when the circuit ID is 
             UDF string or vendor3."
        ::= { swPPPoECirIDInsertPortEntry 4 }

    swPPPoECirIDInsertPortRemoteID OBJECT-TYPE
        SYNTAX      INTEGER {
                       default(1),
                       vendor2(2),
                       vendor3(3)
                    }
        MAX-ACCESS  read-write
        STATUS      current
        DESCRIPTION
            "This object indicates the port remote ID."
        ::= { swPPPoECirIDInsertPortEntry 5 }

    swPPPoECirIDInsertPortRemoteIDUDFString OBJECT-TYPE
        SYNTAX      DisplayString
        MAX-ACCESS  read-write
        STATUS      current
        DESCRIPTION
            "This object indicates the user define string when the remote ID is vendor3."
        ::= { swPPPoECirIDInsertPortEntry 6 }
       
END
