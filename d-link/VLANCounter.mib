-- -----------------------------------------------------------------------------
-- MIB NAME : VLAN-COUNTER-MIB
-- FILE NAME: VLANCounter.mib
-- DATE     : 2013/8/27
-- VERSION  : 1.04
-- PURPOSE  : To construct the MIB structure of VLAN counter function for
--            proprietary enterprise
-- -----------------------------------------------------------------------------
-- MODIFICTION HISTORY:
-- -----------------------------------------------------------------------------
-- Version, Date, Author
-- Description:
--  [New Object]
--  [Modification]
-- Notes: (Requested by who and which project)
-- -----------------------------------------------------------------------------
-- Version 1.04, 2013/8/27, Oran Tang
-- Description:
--  [New Object]
--  [Modification]: Obsolete old table and add index for table swVLANCounterExtTable 
--                  and swVLANCounterExtClearTable to support TX VLAN counter. 
-- Notes: (Requested by Oran Tang for project DGS-3120)
-- -----------------------------------------------------------------------------
-- Version 1.03, 2013/8/2, Oran Tang
-- Description:
--  [New Object]
--  [Modification]: Keep old table and create new table swVLANCounterExtTable 
--                  and swVLANCounterExtClearTable to support TX VLAN counter. 
-- Notes: (Requested by Oran Tang for project DGS-3120)
-- -----------------------------------------------------------------------------
-- Version 1.02, 2013/8/2, Oran Tang
-- Description:
--  [New Object]
--  [Modification]: Replace the object name swVLANCounterPipelineStage with 
--                  swVLANCounterDirection
-- Notes: (Requested by Oran Tang for project DGS-3120)
-- -----------------------------------------------------------------------------
-- Version 1.01, 2013/7/18, Oran Tang
-- Description:
--  [New Object]: swVLANCounterPipelineStage
--  [Modification]
-- Notes: (Requested by Oran Tang for project DGS-3120)
-- -----------------------------------------------------------------------------
-- Version 1.00, 2008/10/28, Kelvin Tao
-- This is the first formal version for universal MIB definition.
-- -----------------------------------------------------------------------------


VLAN-COUNTER-MIB DEFINITIONS ::= BEGIN

    IMPORTS
        MODULE-IDENTITY,OBJECT-TYPE,Integer32,Counter64
                                        FROM SNMPv2-SMI
        RowStatus                       FROM SNMPv2-TC
        dlink-common-mgmt		FROM DLINK-ID-REC-MIB;
		
    	
    swVLANCounterMIB MODULE-IDENTITY
          LAST-UPDATED "201308270000Z"
          ORGANIZATION "D-Link Corp."
          CONTACT-INFO
                       "http://support.dlink.com"
          DESCRIPTION
		    "The structure of VLAN counter for the proprietary enterprise."
        ::= { dlink-common-mgmt 65 }

    PortList                ::= OCTET STRING(SIZE (0..127))
    
    swVLANCounterCtrl               OBJECT IDENTIFIER ::= { swVLANCounterMIB 1 }
    swVLANCounterInfo               OBJECT IDENTIFIER ::= { swVLANCounterMIB 2 }
    swVLANCounterMgmt               OBJECT IDENTIFIER ::= { swVLANCounterMIB 3 }

-- -----------------------------------------------------------------------------
-- swVLANCounterCtrl
-- -----------------------------------------------------------------------------

-- -----------------------------------------------------------------------------
-- swVLANCounterInfo
-- -----------------------------------------------------------------------------
	
-- -----------------------------------------------------------------------------
-- swVLANCounterMgmt
-- -----------------------------------------------------------------------------

    swVLANCounterTable OBJECT-TYPE
        SYNTAX  SEQUENCE OF SwVLANCounterEntry
        MAX-ACCESS  not-accessible
        STATUS  deprecated
        DESCRIPTION
            "A table that contains the VLAN level received packets
            or received bytes ."
        ::= { swVLANCounterMgmt 1 }

    swVLANCounterEntry OBJECT-TYPE
        SYNTAX  SwVLANCounterEntry
        MAX-ACCESS  not-accessible
        STATUS  deprecated
        DESCRIPTION
            "A list with the VLAN level received packets or received bytes ."
        INDEX   { swVLANCounterVID,swVLANCounterPort,swVLANCounterPktType,swVLANCounterLevel }
        ::= { swVLANCounterTable 1 }

    SwVLANCounterEntry ::=
        SEQUENCE {
            swVLANCounterVID
                INTEGER,
            swVLANCounterPort
            	INTEGER,
            swVLANCounterPktType
                INTEGER,
            swVLANCounterLevel
                INTEGER,
            swVLANCounterTotalStats
                Counter64,
            swVLANCounterRateStats
                Counter64,
            swVLANCounterRowStatus
                RowStatus
        }

    swVLANCounterVID OBJECT-TYPE
        SYNTAX  INTEGER
        MAX-ACCESS  read-only
        STATUS  deprecated
        DESCRIPTION
        "This object indicates the VLAN ID."
    ::= { swVLANCounterEntry 1 }

    swVLANCounterPort OBJECT-TYPE
        SYNTAX  INTEGER(0..65535)
        MAX-ACCESS  read-only
        STATUS  deprecated
        DESCRIPTION
        "This object indicates the port number. 
        If the port number is 0, it indicates that the rule belongs to the vlan."
    ::= { swVLANCounterEntry 2 }

    swVLANCounterPktType OBJECT-TYPE
        SYNTAX INTEGER {
               broadcast(1),
               multicast(2),
               unicast(3),
               allFrame(4)
               }
        MAX-ACCESS  read-only
        STATUS deprecated
        DESCRIPTION
            "This object indicates the type of packet."
    	::= { swVLANCounterEntry 3 }
    	
    swVLANCounterLevel OBJECT-TYPE
        SYNTAX INTEGER {
               packet(1),
               byte(2)
               }
        MAX-ACCESS  read-only
        STATUS deprecated
        DESCRIPTION
            "This object indicates the level of the count."
    	::= { swVLANCounterEntry 4 }

    swVLANCounterTotalStats OBJECT-TYPE
        SYNTAX Counter64
        MAX-ACCESS  read-only
        STATUS deprecated
        DESCRIPTION
            "This object indicates the raw statistics."
    	::= { swVLANCounterEntry 5 }

    swVLANCounterRateStats OBJECT-TYPE
        SYNTAX Counter64
        MAX-ACCESS  read-only
        STATUS deprecated
        DESCRIPTION
            "This object indicates the rate statistics."
    	::= { swVLANCounterEntry 6 }
	
    swVLANCounterRowStatus OBJECT-TYPE
        SYNTAX  RowStatus
        MAX-ACCESS  read-create
        STATUS  deprecated
        DESCRIPTION
            "This object indicates the status of this entry."
        ::= { swVLANCounterEntry 7 }

-- -----------------------------------------------------------------------------
    

    swVLANCounterClearTable OBJECT-TYPE
        SYNTAX  SEQUENCE OF SwVLANCounterClearEntry
        MAX-ACCESS  not-accessible
        STATUS  deprecated
        DESCRIPTION
            "This table is used to clear vlan counter statistics."
        ::= { swVLANCounterMgmt 2 }

    swVLANCounterClearEntry OBJECT-TYPE
        SYNTAX  SwVLANCounterClearEntry
        MAX-ACCESS  not-accessible
        STATUS  deprecated
        DESCRIPTION
            "A list with the swVLANCounterClearTable."
        INDEX   { swVLANCounterVID,swVLANCounterPort }
        ::= { swVLANCounterClearTable 1 }
        
    SwVLANCounterClearEntry ::=
        SEQUENCE {
            swVLANCounterClearAction
            	INTEGER
        }
          	   
    swVLANCounterClearAction OBJECT-TYPE
        SYNTAX  INTEGER{
                other(1),
                start(2)
                }
        MAX-ACCESS  read-write
        STATUS  deprecated
        DESCRIPTION
            "Used to clear the statistics on the specified VLAN.
            
            Setting this value to 'start' will execute the clear action,
            Once cleared, the value returns to 'other'."
        ::= { swVLANCounterClearEntry 1 }

-- -----------------------------------------------------------------------------
    swVLANCounterExtTable OBJECT-TYPE
        SYNTAX  SEQUENCE OF SwVLANCounterExtEntry
        MAX-ACCESS  not-accessible
        STATUS  current
        DESCRIPTION
            "A table that creates entries for counting the received or transmitted
            packets bytes at VLAN level and displays the statistics."
        ::= { swVLANCounterMgmt 3 }

    swVLANCounterExtEntry OBJECT-TYPE
        SYNTAX  SwVLANCounterExtEntry
        MAX-ACCESS  not-accessible
        STATUS  current
        DESCRIPTION
            "A list of entries for counting the received or transmitted
            packets bytes at VLAN level and displays the statistics."
        INDEX   { swVLANCounterExtDirection, swVLANCounterExtVID,swVLANCounterExtPort,swVLANCounterExtPktType,swVLANCounterExtLevel }
        ::= { swVLANCounterExtTable 1 }

    SwVLANCounterExtEntry ::=
        SEQUENCE {
            swVLANCounterExtDirection
                INTEGER,
            swVLANCounterExtVID
                INTEGER,  
            swVLANCounterExtPort
                INTEGER,               
            swVLANCounterExtPktType
                 INTEGER,              
            swVLANCounterExtLevel
                 INTEGER,              
            swVLANCounterExtTotalStats
                Counter64,
            swVLANCounterExtRateStats
                Counter64,
            swVLANCounterExtRowStatus
                RowStatus
                 }
                 
     swVLANCounterExtDirection OBJECT-TYPE
        SYNTAX INTEGER {
               rx(1),
               tx(2)
               }
        MAX-ACCESS  read-only
        STATUS current
        DESCRIPTION
            "This object indicates the VLAN counter is counting for
            received or transmitted traffic."
    	::= { swVLANCounterExtEntry 1 }

                 
    swVLANCounterExtVID OBJECT-TYPE
        SYNTAX  INTEGER
        MAX-ACCESS  read-only
        STATUS  current
        DESCRIPTION
        "This object indicates the VLAN ID."
    ::= { swVLANCounterExtEntry 2 }

    swVLANCounterExtPort OBJECT-TYPE
        SYNTAX  INTEGER(0..65535)
        MAX-ACCESS  read-only
        STATUS  current
        DESCRIPTION
        "This object indicates the port number. 
        If the port number is 0, it indicates that the rule belongs to the vlan."
    ::= { swVLANCounterExtEntry 3 }

    swVLANCounterExtPktType OBJECT-TYPE
        SYNTAX INTEGER {
               broadcast(1),
               multicast(2),
               unicast(3),
               allFrame(4)
               }
        MAX-ACCESS  read-only
        STATUS current
        DESCRIPTION
            "This object indicates the type of packet."
    	::= { swVLANCounterExtEntry 4 }
    	
    swVLANCounterExtLevel OBJECT-TYPE
        SYNTAX INTEGER {
               packet(1),
               byte(2)
               }
        MAX-ACCESS  read-only
        STATUS current
        DESCRIPTION
            "This object indicates the unit level of the counter."
    	::= { swVLANCounterExtEntry 5 }


    	
    swVLANCounterExtTotalStats OBJECT-TYPE
        SYNTAX Counter64
        MAX-ACCESS  read-only
        STATUS current
        DESCRIPTION
            "This object indicates the total statistics by packets or bytes."
    	::= { swVLANCounterExtEntry 6 }

    swVLANCounterExtRateStats OBJECT-TYPE
        SYNTAX Counter64
        MAX-ACCESS  read-only
        STATUS current
        DESCRIPTION
            "This object indicates the rate statisticsby packets or bytes."
    	::= { swVLANCounterExtEntry 7 }
	
    swVLANCounterExtRowStatus OBJECT-TYPE
        SYNTAX  RowStatus
        MAX-ACCESS  read-create
        STATUS  current
        DESCRIPTION
            "This object indicates the status of this entry."
        ::= { swVLANCounterExtEntry 8 }
    	
-- -----------------------------------------------------------------------------

    swVLANCounterExtClearTable OBJECT-TYPE
        SYNTAX  SEQUENCE OF SwVLANCounterExtClearEntry
        MAX-ACCESS  not-accessible
        STATUS  current
        DESCRIPTION
            "This table is used to clear the received or transmitted statistics
            at VLAN level by VLAN ID and port."
        ::= { swVLANCounterMgmt 4 }

    swVLANCounterExtClearEntry OBJECT-TYPE
        SYNTAX  SwVLANCounterExtClearEntry
        MAX-ACCESS  not-accessible
        STATUS  current
        DESCRIPTION
            "A list with the swVLANCounterExtClearTable."
        INDEX   { swVLANCounterExtDirection, swVLANCounterExtVID, swVLANCounterExtPort }
        ::= { swVLANCounterExtClearTable 1 }
        
    SwVLANCounterExtClearEntry ::=
        SEQUENCE {
            swVLANCounterExtClearAction
            	INTEGER
        }
          	   
    swVLANCounterExtClearAction OBJECT-TYPE
        SYNTAX  INTEGER{
                other(1),
                start(2)
                }
        MAX-ACCESS  read-write
        STATUS  current
        DESCRIPTION
            "Used to clear the received or transmitted statistics 
            on the specified VLAN and port.            
            Setting this value to 'start' will execute the clear action,
            Once cleared, the value returns to 'other'."
        ::= { swVLANCounterExtClearEntry 1 }
             	             	
END
