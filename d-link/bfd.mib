-- -----------------------------------------------------------------------------
-- MIB NAME : BFD Common mib
-- FILE NAME: bfd.mib
-- DATE     : 2013/06/17
-- VERSION  : 2.00
-- PURPOSE  : To construct the MIB structure of BFD for proprietary enterprise
-- -----------------------------------------------------------------------------
-- MODIFICTION HISTORY:
-- -----------------------------------------------------------------------------
-- Version 2.00, 2013/06/17, Welsey Wang
-- This is the first formal version for universal MIB definition.
-- Notes: Requested by Wesley Wang for DGS3620 R2.6.
-- -----------------------------------------------------------------------------
BFD-MIB DEFINITIONS ::= BEGIN

    IMPORTS
        Counter32,MODULE-IDENTITY,OBJECT-TYPE,IpAddress,
        NOTIFICATION-TYPE, Integer32,Unsigned32,TimeTicks
                                                FROM SNMPv2-SMI
        PhysAddress,TruthValue,DisplayString,RowStatus,MacAddress
                                                FROM SNMPv2-TC
        dlink-common-mgmt                       FROM DLINK-ID-REC-MIB
        InterfaceIndex                          FROM IF-MIB;

    swBfdMIB MODULE-IDENTITY
        LAST-UPDATED "201306170000Z"
        ORGANIZATION "D-Link Corp."
        CONTACT-INFO
            "http://support.dlink.com"
        DESCRIPTION
            "The Structure of BFD Information for the
            proprietary enterprise."
        ::= { dlink-common-mgmt 111 }

    swBfdCtrl           OBJECT IDENTIFIER ::= { swBfdMIB 1 }
    swBfdMgmt           OBJECT IDENTIFIER ::= { swBfdMIB 2 }
    swBfdInfo           OBJECT IDENTIFIER ::= { swBfdMIB 3 }
    
-- -----------------------------------------------------------------------------
swBfdGlobalState OBJECT-TYPE
        SYNTAX     INTEGER{
                    other(0),
                    disabled(1),
                    enabled(2)
                    }
        MAX-ACCESS read-write
        STATUS     current
        DESCRIPTION
                " Used to control BFD state."
        ::= { swBfdCtrl 1 }
-- -----------------------------------------------------------------------------
-- The BFD IF Table
-- -----------------------------------------------------------------------------
swBfdIfTable OBJECT-TYPE
        SYNTAX     SEQUENCE OF SwBfdIfEntry
        MAX-ACCESS not-accessible
        STATUS     current
        DESCRIPTION
                "The BFD interface table contains BFD related information, such as detection time
                multiplier."
        ::= { swBfdMgmt 1 }

    swBfdIfEntry OBJECT-TYPE
        SYNTAX     SwBfdIfEntry
        MAX-ACCESS not-accessible
        STATUS     current
        DESCRIPTION
                "An entry in the BFD Interface Table."
        INDEX      { swBfdIfIndex }
        ::= { swBfdIfTable 1 }

    SwBfdIfEntry ::= SEQUENCE {
        swBfdIfIndex          InterfaceIndex,
        swBfdIfMinTxInterval      INTEGER,
        swBfdIfMinRxInterval      INTEGER,
        swBfdIfMinMultiplier      INTEGER,
        swBfdIfSlowTime           INTEGER,
        swBfdIfEachState          INTEGER
    }

    swBfdIfIndex    OBJECT-TYPE
        SYNTAX     InterfaceIndex
        MAX-ACCESS not-accessible
        STATUS     current
        DESCRIPTION
                "The ifIndex value of this BFD interface."
        ::= { swBfdIfEntry 1 }

    swBfdIfMinTxInterval OBJECT-TYPE
        SYNTAX     INTEGER(50..1000)
        MAX-ACCESS read-write
        STATUS     current
        DESCRIPTION
                "BFD Desired Minimum TX Interval on this interface. The unit is millisecond."
        ::= { swBfdIfEntry 2 }

    swBfdIfMinRxInterval OBJECT-TYPE
        SYNTAX     INTEGER(50..1000)
        MAX-ACCESS read-write
        STATUS     current
        DESCRIPTION
                "BFD Desired Minimum RX Interval on this interface. The unit is millisecond."
        ::= { swBfdIfEntry 3 }
        
    swBfdIfMinMultiplier OBJECT-TYPE
        SYNTAX     INTEGER(3..99)
        MAX-ACCESS read-write
        STATUS     current
        DESCRIPTION
                "BFD detection time multiplier on this interface."
        ::= { swBfdIfEntry 4 }
    
    swBfdIfSlowTime OBJECT-TYPE
        SYNTAX     INTEGER(1000..3000)
        MAX-ACCESS read-write
        STATUS     current
        DESCRIPTION
                "BFD slow time on this interface. The unit is millisecond."
        ::= { swBfdIfEntry 5 }
        
    swBfdIfEachState OBJECT-TYPE
        SYNTAX     INTEGER { 
        		enabled(1), 
                        disabled(2) }
        MAX-ACCESS read-write
        STATUS     current
        DESCRIPTION
                "BFD echo funtion state on this interface."
        ::= { swBfdIfEntry 6 }
-- -----------------------------------------------------------------------------
-- The BFD Neighbor Table
-- -----------------------------------------------------------------------------
    swBfdNbrTable OBJECT-TYPE
        SYNTAX     SEQUENCE OF SwBfdNbrEntry
        MAX-ACCESS not-accessible
        STATUS     current
        DESCRIPTION
                "The (conceptual) table listing the BFD neighbors."
        ::= { swBfdInfo 1 }

    swBfdNbrEntry OBJECT-TYPE
        SYNTAX     SwBfdNbrEntry
        MAX-ACCESS not-accessible
        STATUS     current
        DESCRIPTION
                "An entry (conceptual row) in the swBfdNeighborEntry."
        INDEX   { swBfdNbrAddress }
        ::= { swBfdNbrTable 1 }

    SwBfdNbrEntry ::= SEQUENCE {
        swBfdNbrAddress               IpAddress,
        swBfdNbrIfIndex               InterfaceIndex,
        swBfdNbrLocalDiscr            INTEGER,
        swBfdNbrRemoteDiscr           INTEGER,
        swBfdNbrDetectTime            INTEGER,
        swBfdNbrLocalDiag             INTEGER,
        swBfdNbrPoolBit               INTEGER,
        swBfdNbrRemoteRxInterval      INTEGER,
        swBfdNbrRemoteTxInterval      INTEGER,
        swBfdNbrRemoteMultiplier      INTEGER,
        swBfdNbrStatus                INTEGER
    }
    
    swBfdNbrAddress OBJECT-TYPE
        SYNTAX     IpAddress
        MAX-ACCESS not-accessible
        STATUS     current
        DESCRIPTION
                "The IP address of the BFD neighbor."
        ::= { swBfdNbrEntry 1 }

    swBfdNbrIfIndex OBJECT-TYPE
        SYNTAX     InterfaceIndex
        MAX-ACCESS read-only
        STATUS     current
        DESCRIPTION
                "The ifIndex value of the BFD neighbor."
        ::= { swBfdNbrEntry 2 }

    swBfdNbrLocalDiscr OBJECT-TYPE
        SYNTAX     INTEGER
        MAX-ACCESS read-only
        STATUS     current
        DESCRIPTION
                "The local discriminator value for the BFD neighbor."
        ::= { swBfdNbrEntry 3 }
        
        
    swBfdNbrRemoteDiscr OBJECT-TYPE
        SYNTAX     INTEGER
        MAX-ACCESS read-only
        STATUS     current
        DESCRIPTION
                "The discriminator value received from the BFD neighbor."
        ::= { swBfdNbrEntry 4 }
        
    swBfdNbrDetectTime OBJECT-TYPE
        SYNTAX     INTEGER
        MAX-ACCESS read-only
        STATUS     current
        DESCRIPTION
                "The detection time value for the BFD neighbor."
        ::= { swBfdNbrEntry 5 }
        
    swBfdNbrLocalDiag OBJECT-TYPE
        SYNTAX     INTEGER{ 
        		no-diagnostic(1),
        		detect-time-expired(2),
        		echo-function-fail(3),
        		neighbor-signaled-session-down(4),
        		forwarding-plan-reset(5),
        		path-down(6),
        		concatenated-path-down(7),
        		administratively-down(8),
        		reserve-concatenated-path-down(9), 
                        other(10) }
        MAX-ACCESS read-only
        STATUS     current
        DESCRIPTION
                "The local diagnostic value for the BFD neighbor."
        ::= { swBfdNbrEntry 6 }
        
    swBfdNbrPoolBit OBJECT-TYPE
        SYNTAX     INTEGER{ 
        		set(1), 
                        notSet(2) }
        MAX-ACCESS read-only
        STATUS     current
        DESCRIPTION
                "The pool bit value for the BFD neighbor."
        ::= { swBfdNbrEntry 7 }
        
    swBfdNbrRemoteRxInterval OBJECT-TYPE
        SYNTAX     INTEGER
        MAX-ACCESS read-only
        STATUS     current
        DESCRIPTION
                "The minimum rx interval value received from the BFD neighbor."
        ::= { swBfdNbrEntry 8 }
        
    swBfdNbrRemoteTxInterval OBJECT-TYPE
        SYNTAX     INTEGER
        MAX-ACCESS read-only
        STATUS     current
        DESCRIPTION
                "The minimum tx interval value received from the BFD neighbor."
        ::= { swBfdNbrEntry 9 }    
        
     swBfdNbrRemoteMultiplier OBJECT-TYPE
        SYNTAX     INTEGER
        MAX-ACCESS read-only
        STATUS     current
        DESCRIPTION
                "The multiplier value received from the BFD neighbor."
        ::= { swBfdNbrEntry 10 }
        
     swBfdNbrStatus OBJECT-TYPE
        SYNTAX     INTEGER{ 
        		admin-down(1), 
                        down(2), 
                        init(3),
                        up(4)}
        MAX-ACCESS read-only
        STATUS     current
        DESCRIPTION
                "The pool bit value for the BFD neighbor."
        ::= { swBfdNbrEntry 11 }          
-- -----------------------------------------------------------------------------
 
END
