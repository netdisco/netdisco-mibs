-- -----------------------------------------------------------------------------
-- MIB NAME : CpuPortCounter-MIB
-- FILE NAME: CpuPortCounter.mib  
-- DATE     : 2016/06/07
-- VERSION  : 1.00  
-- PURPOSE  : To construct the MIB structure of CPU Port counter statistics
--            function for proprietary enterprise			 
-- -----------------------------------------------------------------------------
-- MODIFICTION HISTORY:
-- -----------------------------------------------------------------------------
-- Version, Date, Author
-- Description:
-- [New Object]
-- [Modification]
-- Notes: (Requested by who and which project)
--
-- Version 1.00, 2016/06/07, Dinah Zhou
-- This is the first formal version for universal MIB definition.
-- Notes:Requested by Dinah Zhou for project DGS3420 R3.00	
-- -----------------------------------------------------------------------------

CPU-PORT-COUNTER-MIB DEFINITIONS ::= BEGIN

	IMPORTS
        MODULE-IDENTITY,OBJECT-TYPE,
        Unsigned32      					FROM SNMPv2-SMI
        TruthValue,DisplayString			FROM SNMPv2-TC
        MODULE-COMPLIANCE, OBJECT-GROUP		FROM SNMPv2-CONF
        dlink-common-mgmt               FROM DLINK-ID-REC-MIB;

	dlinkSwCpuCounterMIB MODULE-IDENTITY
        LAST-UPDATED "201606070000Z"
        ORGANIZATION    "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
                "The Structure of CPU Port Statistics Information for the
                 proprietary enterprise."         

        REVISION        "201606070000Z"
        DESCRIPTION
            "Initial revision of this MIB module."              
		::= { dlink-common-mgmt 116 }

-- -----------------------------------------------------------------------------    
    dCpuCounterMIBNotifications    OBJECT IDENTIFIER ::= { dlinkSwCpuCounterMIB 0 }
	dCpuCounterMIBObjects          OBJECT IDENTIFIER ::= { dlinkSwCpuCounterMIB 1 }
    dCpuCounterMIBConformance	 	OBJECT IDENTIFIER ::= { dlinkSwCpuCounterMIB 2 }

-- ----------------------------------------------------------------------------- 
	dCpuCounterGlobalCtrl          OBJECT IDENTIFIER ::= { dCpuCounterMIBObjects 1 }

	dCpuCounterClear OBJECT-TYPE
        SYNTAX          TruthValue
        MAX-ACCESS      read-write
        STATUS  current
        DESCRIPTION
           "This object is used to reset all counters for L2/L3 control 
            packets that are trapped to CPU."
		::= { dCpuCounterGlobalCtrl 1 }

-- -----------------------------------------------------------------------------
	dCpuCounterBriefTable OBJECT-TYPE
	    SYNTAX          SEQUENCE OF DCpuCounterBriefEntry
	    MAX-ACCESS      not-accessible
	    STATUS          current
	    DESCRIPTION
	        "This table contains brief information of counters of all protocols."
	    ::= { dCpuCounterMIBObjects 2 }
	
	dCpuCounterBriefEntry OBJECT-TYPE
	    SYNTAX       DCpuCounterBriefEntry
	    MAX-ACCESS   not-accessible
	    STATUS       current
	    DESCRIPTION
	        "An entry contains the brief information of counters of all protocols."
	    INDEX    { dCpuCounterProtoType }
	    ::= { dCpuCounterBriefTable 1 }

	DCpuCounterBriefEntry ::= 	    SEQUENCE {
	    dCpuCounterProtoType				DisplayString,	
        dCpuCounterPPS						Unsigned32,
        dCpuCounterRcved					Unsigned32,
        dCpuCounterDrop						Unsigned32 
	}

	dCpuCounterProtoType OBJECT-TYPE
	    SYNTAX          DisplayString (SIZE(0..32))
	    MAX-ACCESS      not-accessible
	    STATUS          current
	    DESCRIPTION
	        "The name of protocols."
	    ::= { dCpuCounterBriefEntry 1 }

	dCpuCounterPPS OBJECT-TYPE
        SYNTAX          Unsigned32
        MAX-ACCESS      read-only
        STATUS  current
        DESCRIPTION
           "Received packets per second."
		::= { dCpuCounterBriefEntry 2 }

	dCpuCounterRcved OBJECT-TYPE
        SYNTAX          Unsigned32
        MAX-ACCESS      read-only
        STATUS  current
        DESCRIPTION
           "The number of packets trapped to CPU for each protocol."
		::= { dCpuCounterBriefEntry 3 }

	dCpuCounterDrop OBJECT-TYPE
        SYNTAX          Unsigned32
        MAX-ACCESS      read-only
        STATUS  current
        DESCRIPTION
           "The number of packets that are dropped."
		::= { dCpuCounterBriefEntry 4 }


-- Conformance Information        

    dCpuCounterMIBGroups      OBJECT IDENTIFIER ::= { dCpuCounterMIBConformance 1 }
    dCpuCounterMIBCompliances OBJECT IDENTIFIER ::= { dCpuCounterMIBConformance 2 }

-- Compliance Statements

    dCpuCounterFullCompliance MODULE-COMPLIANCE
        STATUS          current
        DESCRIPTION     "The compliance statement"
        MODULE          -- this module
        MANDATORY-GROUPS {
            dCpuCounterGlobalCtrlGroup,
            dCpuCounterBriefGroup
        }
			              
        ::= { dCpuCounterMIBCompliances 1 }

    -- units of conformance

    dCpuCounterGlobalCtrlGroup OBJECT-GROUP
        OBJECTS         {
			dCpuCounterClear
        }
        STATUS          current
        DESCRIPTION
            "The object is used to reset all counters."
        ::= { dCpuCounterMIBGroups 1 }

    dCpuCounterBriefGroup OBJECT-GROUP
        OBJECTS         {
            dCpuCounterPPS,
            dCpuCounterRcved,
            dCpuCounterDrop
        }
        STATUS          current
        DESCRIPTION
            "The object is used to check the counter of each protocol."
       ::= { dCpuCounterMIBGroups 2 }

END
