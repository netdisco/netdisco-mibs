-- ACLMGMT mib 
-- History:  
-- ********************************************************************************
-- Version 2.9, 2012/03/05, Fred Lu
-- Description:
-- 1.add swACLEtherRuleMatchVID in swACLEtherRuleTable
-- 2.add swACLIpRuleMatchVID in swACLIpRuleTable
-- 3.add swCpuAclEtherRuleMatchVID in swCpuAclEtherRuleTable
-- 4.add swCpuAclIpRuleMatchVID in swCpuAclIpRuleTable
-- for config the VLAN-ID which has the access rule.
-- Requested by Fred Lu for project DGS3600 R3.
-- ********************************************************************************
-- Revision 2.8 2010/03/02 by Grape Pu 
-- 1.Delete swACLIpv6Maskvlan
--		swACLIpv6MaskMacAddrState  
--		swACLIpv6MaskSrcMacAddrMask
--		swACLIpv6MaskDstMacAddrMask
-- 2.Delete swACLIpv6RuleVlan
--		swACLIpv6RuleSrcMacAddress
--		swACLIpv6RuleDstMacAddress
-- ********************************************************************************
-- Revision 2.7 2009/10/15 by henry Chen for DGS34XXr2.7
-- 1.Add swACLIpv6MaskUseProtoType
--		swACLIpv6MaskTcpOption  
--		swACLIpv6MaskUdpOption
--		swACLIpv6MaskTCPorUDPSrcPortMask
--		swACLIpv6MaskTCPorUDPDstPortMask
--		swACLIpv6Maskvlan
--		swACLIpv6MaskMacAddrState  
--		swACLIpv6MaskSrcMacAddrMask
--		swACLIpv6MaskDstMacAddrMask to support ipv6 mask.
-- 2.Add swACLIpv6RuleProtocol
--		swACLIpv6RuleSrcPort
--		swACLIpv6RuleDstPort
--		swACLIpv6RuleMirrorGroupID
--		swACLIpv6RuleVlan
--		swACLIpv6RuleSrcMacAddress
--		swACLIpv6RuleDstMacAddress to support ipv6 rule.    
-- 3.Add swACLEtherRuleMirrorGroupID
--		swACLIpRuleMirrorGroupID
--		swACLPktContRuleOptionMirrorGroupID to support mirror.
-- ********************************************************************************
-- Revision 2.6 2009/2/6 by Grape Pu for DGS34XXr2.6
-- 1.Add jwac-upserver and jwac-authentication for ACL owner type value list.
-- ********************************************************************************
-- Revision 2.5 2009/1/12 by Grape Pu for DGS34XXr2.6
-- 1.Add swACLPktContRuleOptionEnableReplaceDscp and swACLPktContRuleOptionRepDscp in
--	swACLPktContRuleOptionEntry .
-- ********************************************************************************
-- Revision 2.4 2008/11/28 by Grape Pu for DGS34XXr2.6
-- 1.make a synchronization from MIB base for some description .
-- 2.add cpu ipv6 ACL.
-- 3.add swACLipusevlan , swACLipicmpOption and swACLigmpOption in swACLIpEntry
-- 4.add swACLIpRulevlan in swACLIpRuleEntry
-- ********************************************************************************
-- Revision 2.3 2008/10/21 by xxx for DGS34XXr2.6
-- 1.add swAclMeteringMgmt
-- 2.add swACLTotalUsedRuleEntries swACLTotalUnusedRuleEntries
-- 3.add swACLEthernetOwner swACLEthernetUnusedRuleEntries
--       swACLIpOwner swACLIpUnusedRuleEntries
--       swACLIpv6Owner swACLIpv6UnusedRuleEntries
-- 4.add swACLPktContMaskOptionTable swACLPktContRuleOptionTable
-- 5.add swACLEtherRuleOwner swACLEtherRuleEnableReplaceDscp swACLEtherRuleRepDscp
--       swACLIpRuleOwner swACLIpv6RuleOwner
-- 6.add new value of mirror for swACLEtherRulePermit
--   add new value of mirror for swACLIpRulePermit
--   add new value of mirror for swACLIpv6RulePermit
-- 7.add swACLCounterTable
-- ********************************************************************************
-- Revision 2.2 2006/11/29 by Tina Zheng for DGS34XX
-- for new CLI command:delete access_profile [all]
-- add swACLMaskDelAllState 
-- ********************************************************************************
-- Revision 2.1 2005/7/27 
-- For auto-assign feature : 
-- [1] Modify description of swACLEtherRuleAccessID ,swACLIpRuleAccessID,swACLPktContRuleAccessID
-- swACLIpv6RuleAccessID,
-- [2] Change syntax of swACLEtherRulePort, swACLIpRulePort,swACLPktContRulePort,swACLIpv6RulePort
-- from INTEGER to Portlist
-- ********************************************************************************
-- Revision 1.9 2005/4/26 by Chrissy Chen
-- separate the hardware ACL and CPU ACL tables from two tbls to four tbls. 
--[1] remove MaskSwAclState , RuleSwAclCheck from all mask and rule tables.
-- ********************************************************************************
-- Revision 1.8 2005/2/3 11:00AM by Chrissy Chen
-- Add Software ACL mib 
--[1] add SwAclState as first table index and apply to all mask and rule tables.

-- ********************************************************************************
-- Revision 1.7 2005/1/28 11:00AM by Chrissy Chen
-- Add Software ACL mib 
--[1] add swAclCtrl
--[1] add MaskSwAclState object into mask tebles 
--[2] add RuleSwAclCheck object into rule tables 
--[3] move RuleSwAclState object to third item for all rule tables
-- ********************************************************************************
-- Revision 1.6 2004/9/3 12:00AM by Scott Sung
-- [1]in swACLIpv6RuleFlowlabel,SYNTAX OCTET STRING (SIZE(4)) -> 6 modify as 4
-- ********************************************************************************
-- Revision 1.6 2004/9/3 12:00AM by Scott Sung(reported from PX)
-- [1] Remove swACLEthernetPort,swACLIpPort,swACLPktContMaskPort,swACLIpv6MaskPort
--     ;and some object's OID should be modified(shifted).   
-- [2] Modify SYNTAX "PortList" of swACLEtherRulePort,swACLIpRulePort,
--     swACLPktContRulePort,swACLIpv6RulePort as "INTEGER"    
-- [3] Add object 'swACLIpv6RuleEnablePriority'
-- ********************************************************************************
-- Revision 1.5 2004/8/9 03:20PM by Scott Sung
-- [1] Add two tables : swACLIpv6RuleTable,swACLIpv6MaskTable
-- [2] import SYNTAX Ipv6Address from IPV6-TC(now comment),
-- Memo: This SYNTAX "Ipv6Address" is originally defined in IPV6-TC.mib.
--       In order to convenient,now,we defined "Ipv6Address" locally.
--       But if a project supported IPv6,for coherency,it should
--       be refered to IPV6-TC.mib. 
-- [3] in each RuleTable,
--  add RulePort and RuleSwAclState
--********************************************************************************
-- Revision 1.0 2004/2/5 01:14PM by Richard Chang
-- [1] in swACLEtherRuleTable
--	change the SYNTAX of swACLEtherRuleEnablePriority, swACLEtherRuleReplacePriority	
--  and swACLEtherRuleEnableReplaceDscp from read-create to read-only
-- [2] in swACLIpRuleTable
--	change the SYNTAX of swACLIpRuleEnablePriority, swACLIpRuleReplacePriority	
--  and swACLIpRuleEnableReplaceDscp from read-create to read-only
-- [3] in swACLPktContRuleTable
--  add swACLPktContRuleEnablePriority
--	change the SYNTAX of swACLPktContRuleReplacePriority	
--  and swACLPktContRuleEnableReplaceDscp from read-create to read-only  
-- ********************************************************************************
-- Revision 0.3 2003/8/13 10:43PM by Scott Sung ,add swACLIpTCPFlagBit for DGS3x12S
-- Draft Ver 0.3 2004/1/7  11:50AM by Scott Sung
-- [1]in swACLEthernetTable,
--	remove object 'swACLEthernetPermit' add object 'swACLEthernetPort'
-- [2]in swACLIpTable,
-- 	add object 'swACLIpTCPFlagBitMask',object 'swACLIpPort',and remove object 'swACLIpPermit'
-- [3]Add swACLPktContMaskTable
-- [4]in swACLEtherRuleTable,
--	add object 'swACLEtherRulePermit'
-- [5]in swACLIpRuleTable,
-- 	add object 'swACLIpRulePermit'
-- [6]Add swACLPktContRuleTable
-- [7]Change SW-ACLMGMT-MIB OID from 'dlink-mgmt 5' to 'dlink-common-mgmt 9'
--********************************************************************************
-- Revision 0.2 2003/3/12 10:43PM by Richard Chang
-- Revision 0.1 2003/2/27 02:44PM by Scott Sung
-- ********************************************************************************


ACLMGMT-MIB DEFINITIONS ::= BEGIN

    IMPORTS
        Counter32,Counter64,TimeTicks,NOTIFICATION-TYPE,
        MODULE-IDENTITY,OBJECT-TYPE,IpAddress, Unsigned32
                                        FROM SNMPv2-SMI
        DateAndTime,MacAddress, RowStatus           FROM SNMPv2-TC
        DisplayString                   FROM RFC1213-MIB
    	SnmpAdminString					FROM SNMP-FRAMEWORK-MIB
--		Ipv6Address                     FROM IPV6-TC
        dlink-common-mgmt				FROM DLINK-ID-REC-MIB;

    swAclMgmtMIB MODULE-IDENTITY
	    LAST-UPDATED "1003020000Z"
	    ORGANIZATION "D-Link Corp."
	    CONTACT-INFO
	        "http://support.dlink.com"
	    DESCRIPTION
		    "The structure of Access Control List information for the
		    proprietary enterprise."
        ::= { dlink-common-mgmt 9 }

    PortList                ::= OCTET STRING(SIZE (0..127))

    swAclCtrl 				     OBJECT IDENTIFIER ::= { swAclMgmtMIB 1 }
    swAclMaskMgmt                OBJECT IDENTIFIER ::= { swAclMgmtMIB 2 }
    swAclRuleMgmt                OBJECT IDENTIFIER ::= { swAclMgmtMIB 3 }
    swCpuAclMaskMgmt             OBJECT IDENTIFIER ::= { swAclMgmtMIB 4 }
    swCpuAclRuleMgmt             OBJECT IDENTIFIER ::= { swAclMgmtMIB 5 }
    swAclMeteringMgmt            OBJECT IDENTIFIER ::= { swAclMgmtMIB 6 }

-- -----------------------------------------------------------------------------
-- Textual Conventions
-- -----------------------------------------------------------------------------
-- This definition may be excluded if IPv6 Supported
Ipv6Address ::= TEXTUAL-CONVENTION
	DISPLAY-HINT "2x:"
	STATUS       current
	DESCRIPTION
		"This data type is used to model IPv6 addresses.
		This is a binary string of 16 octets in network
		byte-order."
	SYNTAX       OCTET STRING (SIZE (16))

-- -----------------------------------------------------------------------------
-- swAclCtrl
-- -----------------------------------------------------------------------------
    swCpuInterfacefilterState OBJECT-TYPE
    	SYNTAX INTEGER{
    		enable(1),
    		disable(2)
    	}
    	MAX-ACCESS read-write
    	STATUS current
    	DESCRIPTION
    	    "Enable or disable CPU Interface Filtering (also called Software ACL).
    	     The default is disabled. If enabled, the filtering entries in the
    	     swAclRuleMgmt tables will be set to active if its RuleSwAclState is
    	     enabled. If disabled, the software ACL function will be disabled."
    	::={ swAclCtrl 1}

    swACLTotalUsedRuleEntries OBJECT-TYPE
    	SYNTAX INTEGER
    	MAX-ACCESS read-only
    	STATUS current
    	DESCRIPTION
    	    "The total number of used ACL rule entries."
    	::={ swAclCtrl 2}

    swACLTotalUnusedRuleEntries OBJECT-TYPE
    	SYNTAX INTEGER
    	MAX-ACCESS read-only
    	STATUS current
    	DESCRIPTION
    	    "The total number of unused ACL rule entries."
    	::={ swAclCtrl 3}

-- -----------------------------------------------------------------------------
-- swACLEthernetTable
-- -----------------------------------------------------------------------------
    swACLEthernetTable OBJECT-TYPE
        SYNTAX  SEQUENCE OF SwACLEthernetEntry
        MAX-ACCESS  not-accessible
        STATUS  current
        DESCRIPTION
            "This table contains ACL mask Ethernet information.
             The access profile will be created on the switch to define which
             part of each incoming frame's layer 2 header will be examined
             by the switch. Masks entered will be combined with the
             values the switch finds in the specified frame header fields."
        ::= { swAclMaskMgmt 1 }

    swACLEthernetEntry OBJECT-TYPE
        SYNTAX  SwACLEthernetEntry
        MAX-ACCESS  not-accessible
        STATUS  current
        DESCRIPTION
            "A list of information about the ACL for Ethernet."
        INDEX  { swACLEthernetProfileID }
        ::= { swACLEthernetTable 1 }

    SwACLEthernetEntry ::=
        SEQUENCE {
            swACLEthernetProfileID
                INTEGER,
--            swACLEthernetPort
--                PortList,
            swACLEthernetUsevlan
                INTEGER,
            swACLEthernetMacAddrMaskState
                INTEGER,
            swACLEthernetSrcMacAddrMask
                MacAddress,
            swACLEthernetDstMacAddrMask
                MacAddress,
            swACLEthernetUse8021p
                INTEGER,
            swACLEthernetUseEthernetType
                INTEGER,
            swACLEthernetRowStatus
                RowStatus,
            swACLEthernetOwner
                INTEGER,
            swACLEthernetUnusedRuleEntries
            	INTEGER                  
        }

    swACLEthernetProfileID OBJECT-TYPE
        SYNTAX  INTEGER (1..255)
        MAX-ACCESS  read-only	--read-create
        STATUS  current
        DESCRIPTION
            "The ID of the ACL mask entry unique to the mask list. The maximum value of this object depends on the device."
        ::= { swACLEthernetEntry 1 }

--    swACLEthernetPort OBJECT-TYPE
--        SYNTAX  PortList
--        MAX-ACCESS  read-create
--        STATUS  current
--        DESCRIPTION
--            "This object indicates which port(s) should be filtered."
--        ::= { swACLEthernetEntry 2 }

    swACLEthernetUsevlan OBJECT-TYPE
        SYNTAX  INTEGER {
               enabled(1),
               disabled(2)
               }
        MAX-ACCESS  read-create
        STATUS  current
        DESCRIPTION
            "Specifies that the switch will examine the VLAN part of each packet header."
        ::= { swACLEthernetEntry 2 }

    swACLEthernetMacAddrMaskState OBJECT-TYPE
		SYNTAX  INTEGER {
               other(1),
               dst-mac-addr(2),
               src-mac-addr(3),
               dst-src-mac-addr(4)
               }
        MAX-ACCESS  read-create
        STATUS  current
        DESCRIPTION
            "This object indicates the status of the MAC address mask.
          	other (1) - Neither source MAC address nor destination MAC address are masked.
          	dst-mac-addr (2) - Destination MAC addresses within received frames are
          	    to be filtered when matched with the MAC address entry for the table.
          	src-mac-addr (3) - Source MAC addresses within received frames are to
          	    be filtered when matched with the MAC address entry for the table.
          	dst-src-mac-addr (4) - Source or destination MAC addresses within received
          	    frames are to be filtered when matched with the MAC address entry of the table."
        ::= { swACLEthernetEntry 3 }

    swACLEthernetSrcMacAddrMask OBJECT-TYPE
        SYNTAX  MacAddress
        MAX-ACCESS  read-create
        STATUS  current
        DESCRIPTION
            "This object specifies the MAC address mask for the source MAC address."
        ::= { swACLEthernetEntry 4 }

    swACLEthernetDstMacAddrMask OBJECT-TYPE
        SYNTAX  MacAddress
        MAX-ACCESS  read-create
        STATUS  current
        DESCRIPTION
            "This object specifies the MAC address mask for the destination MAC address."
        ::= { swACLEthernetEntry 5 }

    swACLEthernetUse8021p OBJECT-TYPE
        SYNTAX  INTEGER {
               enabled(1),
               disabled(2)
               }
        MAX-ACCESS  read-create
        STATUS  current
        DESCRIPTION
            "Specifies if the switch will examine the 802.1p priority value in the frame's header
              or not."
        ::= { swACLEthernetEntry 6 }

    swACLEthernetUseEthernetType OBJECT-TYPE
        SYNTAX  INTEGER {
               enabled(1),
               disabled(2)
               }
        MAX-ACCESS  read-create
        STATUS  current
        DESCRIPTION
            "Specifies if the switch will examine the Ethernet type value in each frame's header
              or not."
        ::= { swACLEthernetEntry 7 }

    swACLEthernetRowStatus OBJECT-TYPE --swACLEthernetState
        SYNTAX  RowStatus
        MAX-ACCESS  read-create
        STATUS  current
        DESCRIPTION
            "This object indicates the status of this entry."
        ::= { swACLEthernetEntry 8 }

    swACLEthernetOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
            "The owner of ACL mask entry. The type of ACL entry created. ACL type
             entries can only be modified when being configured through the same
             type command. For example IP-MAC Binding entries can only be modified
             or deleted through the IP-MAC Binding configurations or commands."
        ::= { swACLEthernetEntry 9 }

    swACLEthernetUnusedRuleEntries OBJECT-TYPE
    	SYNTAX INTEGER
    	MAX-ACCESS read-only
    	STATUS current
    	DESCRIPTION
    	    "The number of unused rule entries  of this Ethernet profile entry."
    	::={ swACLEthernetEntry 10}
    	
-- -----------------------------------------------------------------------------
-- swACLIpTable
-- -----------------------------------------------------------------------------
    swACLIpTable OBJECT-TYPE
        SYNTAX  SEQUENCE OF SwACLIpEntry
        MAX-ACCESS  not-accessible
        STATUS  current
        DESCRIPTION
            "This table contains the ACL mask for IP information.
             Access profiles will be created on the switch to define which
             part of the incoming frame's IP layer packet header will be
             examined by the switch. Masks entered will be combined
             with the values the switch finds in the specified frame
             header fields."
        ::= { swAclMaskMgmt 2 }

    swACLIpEntry OBJECT-TYPE
        SYNTAX  SwACLIpEntry
        MAX-ACCESS  not-accessible
        STATUS  current
        DESCRIPTION
            "A list of information about the ACL of the IP Layer."
        INDEX  { swACLIpProfileID }
        ::= { swACLIpTable 1 }

    SwACLIpEntry ::=
        SEQUENCE {
            swACLIpProfileID
                INTEGER,
--            swACLIpPort
--                PortList,
            swACLIpUsevlan
                INTEGER,
            swACLIpIpAddrMaskState
                INTEGER,
            swACLIpSrcIpAddrMask
                IpAddress,
            swACLIpDstIpAddrMask
                IpAddress,
            swACLIpUseDSCP
                INTEGER,
            swACLIpUseProtoType
                INTEGER,
            swACLIpIcmpOption
                INTEGER,
            swACLIpIgmpOption
                INTEGER,
            swACLIpTcpOption
                INTEGER,
            swACLIpUdpOption
             	INTEGER,
            swACLIpTCPorUDPSrcPortMask
				OCTET STRING,
	    	swACLIpTCPorUDPDstPortMask
				OCTET STRING,
	    	swACLIpTCPFlagBit
				INTEGER,
            swACLIpTCPFlagBitMask
            	INTEGER,
            swACLIpProtoIDOption
                INTEGER,
			swACLIpProtoID
			    INTEGER,
            swACLIpProtoIDMask
                OCTET STRING,
            swACLIpRowStatus
                RowStatus,
            swACLIpOwner
                INTEGER,
            swACLIpSrcMacAddrMask
                MacAddress,
            swACLIpUnusedRuleEntries
            	INTEGER                  
        }
    swACLIpProfileID OBJECT-TYPE
        SYNTAX  INTEGER (1..255)
        MAX-ACCESS  read-only
        STATUS  current
        DESCRIPTION
            "The ID of the ACL mask entry, which is unique to the mask list. The maximum value of this object depends on the device."
        ::= { swACLIpEntry 1 }

--    swACLIpPort OBJECT-TYPE
--        SYNTAX  PortList
--        MAX-ACCESS  read-create
--        STATUS  current
--        DESCRIPTION
--            "This object indicates which port(s) should be filtered."
--        ::= { swACLIpEntry 2 }

    swACLIpUsevlan OBJECT-TYPE
        SYNTAX  INTEGER {
               enabled(1),
               disabled(2)
               }
        MAX-ACCESS  read-create
        STATUS  current
        DESCRIPTION
            "This object indicates if the IP layer VLAN part is examined or not."
        ::= { swACLIpEntry 2 }

    swACLIpIpAddrMaskState OBJECT-TYPE
		SYNTAX  INTEGER {
               other(1),
               dst-ip-addr(2),
               src-ip-addr(3),
               dst-src-ip-addr(4)
               }
        MAX-ACCESS  read-create
        STATUS  current
        DESCRIPTION
            "This object indicates the status of IP address mask.

            other (1) - Neither source IP address nor destination IP address are
                masked.
             dst-ip-addr (2) - Destination IP addresses within received frames
          	are to be filtered when matched with the IP address entry of the table.
             src-ip-addr (3) - Source IP addresses within received frames are
          	to be filtered when matched with the IP address entry of the table.
             dst-src-ip-addr (4) - Destination or source IP addresses within received
          	frames are to be filtered when matched with the IP address entry of the
          	table."
        ::= { swACLIpEntry 3 }

    swACLIpSrcIpAddrMask OBJECT-TYPE
        SYNTAX  IpAddress
        MAX-ACCESS  read-create
        STATUS  current
        DESCRIPTION
            "This object specifies the IP address mask for the source IP address."
        ::= { swACLIpEntry 4 }

    swACLIpDstIpAddrMask OBJECT-TYPE
        SYNTAX  IpAddress
        MAX-ACCESS  read-create
        STATUS  current
        DESCRIPTION
            "This object specifies the IP address mask for the destination IP address."
        ::= { swACLIpEntry 5 }

    swACLIpUseDSCP OBJECT-TYPE
        SYNTAX  INTEGER {
               enabled(1),
               disabled(2)
               }
        MAX-ACCESS  read-create
        STATUS  current
        DESCRIPTION
            "This object indicates if the DSCP protocol in the packet header
             is to be examined or not."
        ::= { swACLIpEntry 6 }

    swACLIpUseProtoType OBJECT-TYPE
        SYNTAX  INTEGER {
               none(1),
               icmp(2),
               igmp(3),
               tcp(4),
               udp(5),
               protocolId(6)
               }
        MAX-ACCESS  read-create
        STATUS  current
        DESCRIPTION
            "That object indicates which protocol will be examined."
        ::= { swACLIpEntry 7 }

    swACLIpIcmpOption OBJECT-TYPE
        SYNTAX  INTEGER {
               none(1),
               type(2),
               code(3),
               type-code(4)
               }
        MAX-ACCESS  read-create
        STATUS  current
        DESCRIPTION
            "This object indicates which fields are defined for ICMP.
             none (1)- Both fields are null.
             type (2)- Type field identified.
             code (3)- Code field identified.
             type-code (4)- Both ICMP fields identified.
            "
        ::= { swACLIpEntry 8 }

    swACLIpIgmpOption OBJECT-TYPE
        SYNTAX  INTEGER {
               enable(1),
               disable(2)
              }
        MAX-ACCESS  read-create
        STATUS  current
        DESCRIPTION
            "Indicates if the IGMP options field is identified or not."
        ::= { swACLIpEntry 9 }

    swACLIpTcpOption OBJECT-TYPE
        SYNTAX  INTEGER {
               other(1),
               dst-addr(2),
               src-addr(3),
               dst-src-addr(4)
               }
        MAX-ACCESS  read-create
        STATUS  current
        DESCRIPTION
            "This object indicates the status of the filtered address of TCP.

             other (1) - Neither source port nor destination port are
                masked.
             dst-addr (2) - Packets will be filtered if this destination port
          	is identified in received frames.
             src-addr (3) - Packets will be filtered if this source port is
          	identified in received frames.
             dst-src-addr (4) - Packets will be filtered if this destination
          	or source port is identified in received frames."
        ::= { swACLIpEntry 10 }

    swACLIpUdpOption OBJECT-TYPE
        SYNTAX  INTEGER {
               other(1),
               dst-addr(2),
               src-addr(3),
               dst-src-addr(4)
               }
        MAX-ACCESS  read-create
        STATUS  current
        DESCRIPTION
            "This object indicates the status of the filtered address of UDP .

             other (1) - Neither source port nor destination port are
                masked.
             dst-addr (2) - Packets will be filtered if this destination port
          	is identified in received frames.
             src-addr (3) - Packets will be filtered if this source port is
          	identified in received frames.
             dst-src-addr (4) - Packets will be filtered if this destination
          	or source port is identified in received frames."

        ::= { swACLIpEntry 11 }

    swACLIpTCPorUDPSrcPortMask OBJECT-TYPE
        SYNTAX  OCTET STRING (SIZE(2))
        MAX-ACCESS  read-create
        STATUS  current
        DESCRIPTION
            "Specifies a TCP port mask for the source port if swACLIpUseProtoType is TCP
             Specifies a UDP port mask for the source port if swACLIpUseProtoType is UDP.
             "
        ::= { swACLIpEntry 12 }

    swACLIpTCPorUDPDstPortMask OBJECT-TYPE
        SYNTAX  OCTET STRING (SIZE(2))
        MAX-ACCESS  read-create
        STATUS  current
        DESCRIPTION
            "Specifies a TCP port mask for the destination port if swACLIpUseProtoType is TCP
             Specifies a UDP port mask for the destination port if swACLIpUseProtoType is UDP."
        ::= { swACLIpEntry 13 }

    swACLIpTCPFlagBit OBJECT-TYPE
		SYNTAX  INTEGER {
               enable(1),
               disable(2)
               }
        MAX-ACCESS  read-create
        STATUS  current
        DESCRIPTION
            "Specifies a TCP connection flag mask."
        ::= { swACLIpEntry 14 }

    swACLIpTCPFlagBitMask OBJECT-TYPE
        SYNTAX  INTEGER(0..63)
        MAX-ACCESS  read-create
        STATUS  current
        DESCRIPTION
            "A value which indicates the set of TCP flags that this
             entity may potentially offer. The value is a sum of flag bits.
             This sum initially takes the value zero. Then, for each flag, L,
             is added in the range 1 through 6, for which this node performs
             transactions where 2^(L-1) is added to the sum.
             Note that values should be calculated accordingly:

                 Flag      functionality
                   6        urg bit
                   5        ack bit
                   4        psh bit
                   3        rst bit
                   2		syn bit
                   1 		fin bit
		For example, if you want to enable urg bit and ack bit, you
		should set value 48{2^(5-1) + 2^(6-1)}."
        ::= { swACLIpEntry 15 }

    swACLIpProtoIDOption OBJECT-TYPE
        SYNTAX  INTEGER {
               enable(1),
               disable(2)
               }
        MAX-ACCESS  read-create
        STATUS  current
        DESCRIPTION
            "Specifies if the switch will examine each frame's protocol ID field or not."
        ::= { swACLIpEntry 16 }

    swACLIpProtoID OBJECT-TYPE
        SYNTAX  INTEGER(0..255)
        MAX-ACCESS  read-create
        STATUS  current
        DESCRIPTION
            "Specifies that the rule applies to the IP protocol ID behind the IP header."
        ::= { swACLIpEntry 17 }



    swACLIpProtoIDMask OBJECT-TYPE
        SYNTAX  OCTET STRING (SIZE(4))
        MAX-ACCESS  read-create
        STATUS  current
        DESCRIPTION
            "Specifies that the rule applies to the IP protocol ID and the mask options
             behind the IP header."
        ::= { swACLIpEntry 18 }

    swACLIpRowStatus OBJECT-TYPE
        SYNTAX  RowStatus
        MAX-ACCESS  read-create
        STATUS  current
        DESCRIPTION
            "This object indicates the status of this entry."
        ::= { swACLIpEntry 19 }

    swACLIpOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
            "The owner of the ACL mask entry. The type of ACL entry created. ACL type
             entries can only be modified when being configured through the same
             type command. For example, IP-MAC Binding entries can only be modified
             or deleted through the IP-MAC Binding configurations or commands."
        ::= { swACLIpEntry 20 }

    swACLIpSrcMacAddrMask OBJECT-TYPE
        SYNTAX  MacAddress
        MAX-ACCESS  read-only
        STATUS  current
        DESCRIPTION
            "This object specifies the MAC address mask for the source MAC address."
        ::= { swACLIpEntry 21 }

    swACLIpUnusedRuleEntries OBJECT-TYPE
    	SYNTAX INTEGER
    	MAX-ACCESS read-only
    	STATUS current
    	DESCRIPTION
    	    "The number of unused rule entries this IP profile entry."
    	::={ swACLIpEntry 22}

-- -----------------------------------------------------------------------------
-- swACLIpv6MaskTable
-- -----------------------------------------------------------------------------
    swACLIpv6MaskTable OBJECT-TYPE
        SYNTAX  SEQUENCE OF SwACLIpv6MaskEntry
        MAX-ACCESS  not-accessible
        STATUS  current
        DESCRIPTION
          "This table contains user-defined ACL mask information.
           An access profile will be created on the switch to define which
           parts of each incoming frame's IPv6 part of the packet header will
           be examined by the switch. Masks entered will be combined
           with the values the switch finds in the specified frame header fields."
        ::= { swAclMaskMgmt 4 }

    swACLIpv6MaskEntry OBJECT-TYPE
        SYNTAX  SwACLIpv6MaskEntry
        MAX-ACCESS  not-accessible
        STATUS  current
        DESCRIPTION
          "A list of information about user-defined ACLs."
        INDEX  { swACLIpv6MaskProfileID }
        ::= { swACLIpv6MaskTable 1 }

    SwACLIpv6MaskEntry ::=
        SEQUENCE {
            swACLIpv6MaskProfileID
                INTEGER,
--            swACLIpv6MaskPort
--                PortList,
            swACLIpv6MaskClass
                INTEGER,
            swACLIpv6MaskFlowlabel
                INTEGER,
            swACLIpv6IpAddrMaskState
                INTEGER,
            swACLIpv6MaskSrcIpv6Mask
                Ipv6Address,
            swACLIpv6MaskDstIpv6Mask
                Ipv6Address,
            swACLIpv6MaskRowStatus
                RowStatus,
            swACLIpv6MaskOwner
                INTEGER,
            swACLIpv6MaskUnusedRuleEntries 
                INTEGER,
            swACLIpv6MaskUseProtoType
                INTEGER,
            swACLIpv6MaskTcpOption
                INTEGER,
            swACLIpv6MaskUdpOption
                INTEGER,
            swACLIpv6MaskTCPorUDPSrcPortMask
                OCTET STRING,
            swACLIpv6MaskTCPorUDPDstPortMask
                OCTET STRING
        }
    swACLIpv6MaskProfileID OBJECT-TYPE
        SYNTAX  INTEGER (1..255)
        MAX-ACCESS  read-only	--read-create
        STATUS  current
        DESCRIPTION
            "The ID of the ACL mask entry, which is unique to the mask list. The maximum value of this object depends on the device."
        ::= { swACLIpv6MaskEntry 1 }

--    swACLIpv6MaskPort OBJECT-TYPE
--        SYNTAX  PortList
--        MAX-ACCESS  read-create
--        STATUS  current
--        DESCRIPTION
--            "This object indicates which port(s) should be filtered."
--        ::= { swACLIpv6MaskEntry 2 }

    swACLIpv6MaskClass OBJECT-TYPE
        SYNTAX  INTEGER {
               enable(1),
               disable(2)
               }
        MAX-ACCESS  read-create
        STATUS  current
        DESCRIPTION
            "Specifies that the rule applies to the IPv6 class field and the mask options."
        ::= { swACLIpv6MaskEntry 2 }

    swACLIpv6MaskFlowlabel OBJECT-TYPE
        SYNTAX  INTEGER {
               enable(1),
               disable(2)
               }
        MAX-ACCESS  read-create
        STATUS  current
        DESCRIPTION
            "Specifies that the rule applies to the IPv6 flowlabel field and the mask options."
        ::= { swACLIpv6MaskEntry 3 }

    swACLIpv6IpAddrMaskState OBJECT-TYPE
		SYNTAX  INTEGER {
               other(1),
               dst-ipv6-addr(2),
               src-ipv6-addr(3),
               dst-src-ipv6-addr(4)
               }
        MAX-ACCESS  read-create
        STATUS  current
        DESCRIPTION
            "This object indicates the status of the IPv6 address mask.

            other (1) - Neither source IPv6 address nor destination IPv6 address are
                masked.
            dst-ipv6-addr (2) - Received frame destination IPv6 address is
                currently used to be filtered as it meets with the IPv6
                address entry of the table.
            src-ipv6-addr (3) - Received frame source IPv6 address is currently
                used to be filtered as it meets with the IPv6 address entry of
                the table.
            dst-src-ipv6-addr (4) - Received frame destination IPv6 address or
                source IPv6 address is currently used to be filtered as it meets
                with the IPv6 address entry of the table."
        ::= { swACLIpv6MaskEntry 4 }

    swACLIpv6MaskSrcIpv6Mask OBJECT-TYPE
        SYNTAX  Ipv6Address
        MAX-ACCESS  read-create
        STATUS  current
        DESCRIPTION
            "Specifies that the rule applies to the Source IPv6 address and the mask options.
            This should be a 16 byte octet string."
        ::= { swACLIpv6MaskEntry 5 }

    swACLIpv6MaskDstIpv6Mask OBJECT-TYPE
        SYNTAX  Ipv6Address
        MAX-ACCESS  read-create
        STATUS  current
        DESCRIPTION
            "Specifies that the rule applies to the Destination IPv6 address and the mask options.
            This should be a 16 byte octet string."
        ::= { swACLIpv6MaskEntry 6 }

    swACLIpv6MaskRowStatus OBJECT-TYPE
        SYNTAX  RowStatus
        MAX-ACCESS  read-create
        STATUS  current
        DESCRIPTION
            "This object indicates the status of this entry."
        ::= { swACLIpv6MaskEntry 7 }

    swACLIpv6MaskOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
           "The owner of the ACL mask entry. The type of ACL entry created. ACL type
            entries can only be modified when being configured through the same
            type command. For example, IP-MAC Binding entries can only be modified
            or deleted through the IP-MAC Binding configurations or commands."
        ::= { swACLIpv6MaskEntry 8 }

    swACLIpv6MaskUnusedRuleEntries OBJECT-TYPE
    	SYNTAX INTEGER
    	MAX-ACCESS read-only
    	STATUS current
    	DESCRIPTION
    	    "The number of unused rule entries of this IP profile entry."
    	::={ swACLIpv6MaskEntry 9}

    swACLIpv6MaskUseProtoType OBJECT-TYPE
        SYNTAX  INTEGER {
               none(1),
               tcp(2),
               udp(3)
--             ,icmp(4)
               }
        MAX-ACCESS  read-create
        STATUS  current
        DESCRIPTION
            "That object indicates which protocol will be examined."
        ::= { swACLIpv6MaskEntry 11 }

    swACLIpv6MaskTcpOption OBJECT-TYPE
        SYNTAX  INTEGER {
               other(1),
               dst-addr(2),
               src-addr(3),
               dst-src-addr(4)
               }
        MAX-ACCESS  read-create
        STATUS  current
        DESCRIPTION
            "This object indicates the status of the filtered address of TCP.

             other (1) - Neither source port nor destination port are
                masked.
             dst-addr (2) - Packets will be filtered if this destination port
                is identified in received frames.
             src-addr (3) - Packets will be filtered if this source port is
                identified in received frames.
             dst-src-addr (4) - Packets will be filtered if this destination
                or source port is identified in received frames."
        ::= { swACLIpv6MaskEntry 12 }

    swACLIpv6MaskUdpOption OBJECT-TYPE
        SYNTAX  INTEGER {
               other(1),
               dst-addr(2),
               src-addr(3),
               dst-src-addr(4)
               }
        MAX-ACCESS  read-create
        STATUS  current
        DESCRIPTION
            "This object indicates the status of the filtered address of UDP.

             other (1) - Neither source port nor destination port is
                masked.
             dst-addr (2) - Packets will be filtered if this destination port
                is identified in received frames.
             src-addr (3) - Packets will be filtered if this source port is
                identified in received frames.
             dst-src-addr (4) - Packets will be filtered if this destination
                or source port is identified in received frames."

        ::= { swACLIpv6MaskEntry 13 }

    swACLIpv6MaskTCPorUDPSrcPortMask OBJECT-TYPE
        SYNTAX  OCTET STRING (SIZE(2))
        MAX-ACCESS  read-create
        STATUS  current
        DESCRIPTION
            "Specifies a TCP port mask for the source port if swACLIpv6MaskUseProtoType is TCP
             Specifies a UDP port mask for the source port if swACLIpv6MaskUseProtoType is UDP.
             "
        ::= { swACLIpv6MaskEntry 14 }

    swACLIpv6MaskTCPorUDPDstPortMask OBJECT-TYPE
        SYNTAX  OCTET STRING (SIZE(2))
        MAX-ACCESS  read-create
        STATUS  current
        DESCRIPTION
            "Specifies a TCP port mask for the destination port if swACLIpv6MaskUseProtoType is TCP
             Specifies a UDP port mask for the destination port if swACLIpv6MaskUseProtoType is UDP."
        ::= { swACLIpv6MaskEntry 15 }    
        
-- -----------------------------------------------------------------------------
--swIBPACLEthernetTable
-- -----------------------------------------------------------------------------
    swIBPACLEthernetTable OBJECT-TYPE
        SYNTAX  SEQUENCE OF SwIBPACLEthernetEntry
        MAX-ACCESS  not-accessible
        STATUS  current
        DESCRIPTION
            "This table contains IP-MAC-Binding ACL mask Ethernet information.
             Access profiles will be created on the switch by row creation and to
              define which parts of each incoming frame's layer 2 header part
              the switch will examine. Masks can be entered that will be combined
              with the values the switch finds in the specified frame header fields."
        ::= { swAclMaskMgmt 6 }

    swIBPACLEthernetEntry OBJECT-TYPE
        SYNTAX  SwIBPACLEthernetEntry
        MAX-ACCESS  not-accessible
        STATUS  current
        DESCRIPTION
            "A list of information about the Ethernet ACL."
        INDEX  { swIBPACLEthernetProfileID }
        ::= { swIBPACLEthernetTable 1 }

    SwIBPACLEthernetEntry ::=
        SEQUENCE {
            swIBPACLEthernetProfileID
                INTEGER,
            swIBPACLEthernetUseEthernetType
                INTEGER
        }
    swIBPACLEthernetProfileID OBJECT-TYPE
        SYNTAX  INTEGER (1..6)
        MAX-ACCESS  read-only
        STATUS  current
        DESCRIPTION
            "The ID of the ACL mask entry, unique in the mask list. The maximum value of this object depends on the device."
        ::= { swIBPACLEthernetEntry 1 }

    swIBPACLEthernetUseEthernetType OBJECT-TYPE
        SYNTAX  INTEGER {
               enabled(1),
               disabled(2)
               }
        MAX-ACCESS  read-only
        STATUS  current
        DESCRIPTION
            "Specifies if the switch will examine the Ethernet type value in each frame's header
              or not."
        ::= { swIBPACLEthernetEntry 2 }

-- -----------------------------------------------------------------------------
--swIBPACLIpTable
-- -----------------------------------------------------------------------------
    swIBPACLIpTable OBJECT-TYPE
        SYNTAX  SEQUENCE OF SwIBPACLIpEntry
        MAX-ACCESS  not-accessible
        STATUS  current
        DESCRIPTION
            "This table contains IP-MAC-Binding IP ACL mask information.
             Access profiles will be created on the switch by row creation and to
              define which parts of each incoming frame's IP layer part of the header
              the switch will examine. Masks can be entered that will be combined
              with the values the switch finds in the specified frame header fields."
        ::= { swAclMaskMgmt 7 }

    swIBPACLIpEntry OBJECT-TYPE
        SYNTAX  SwIBPACLIpEntry
        MAX-ACCESS  not-accessible
        STATUS  current
        DESCRIPTION
            "A list of information about the IP layer of the ACL."
        INDEX  { swIBPACLIpProfileID }
        ::= { swIBPACLIpTable 1 }

    SwIBPACLIpEntry ::=
        SEQUENCE {
            swIBPACLIpProfileID
                INTEGER,
            swIBPACLIpSrcMacAddrMask
                MacAddress,
            swIBPACLIpSrcIpAddrMask
                IpAddress
        }
    swIBPACLIpProfileID OBJECT-TYPE
        SYNTAX  INTEGER (1..255)
        MAX-ACCESS  read-only
        STATUS  current
        DESCRIPTION
            "The ID of the ACL mask entry, unique in the mask list. The maximum value of this object depends on the device."
        ::= { swIBPACLIpEntry 1 }

    swIBPACLIpSrcMacAddrMask OBJECT-TYPE
        SYNTAX  MacAddress
        MAX-ACCESS  read-only
        STATUS  current
        DESCRIPTION
            "This object specifies the MAC address mask for the source MAC address."
        ::= { swIBPACLIpEntry 2 }

    swIBPACLIpSrcIpAddrMask OBJECT-TYPE
        SYNTAX  IpAddress
        MAX-ACCESS  read-only
        STATUS  current
        DESCRIPTION
            "This object specifies IP address masks for the source IP address."
        ::= { swIBPACLIpEntry 3 }


-- -----------------------------------------------------------------------------
-- swACLPktContMaskOptionTable
-- -----------------------------------------------------------------------------
    swACLPktContMaskOptionTable OBJECT-TYPE
        SYNTAX  SEQUENCE OF SwACLPktContMaskOptionEntry
        MAX-ACCESS  not-accessible
        STATUS  current
        DESCRIPTION
	    "This table contains the ACL mask for user-defined option information.
	     An access profile will be created on the switch to define which part
	     of each incoming frame's user-defined part of the packet header
	     will be examined by switch. Masks entered will be combined
              with the values the switch finds in the specified frame header fields."
        ::= { swAclMaskMgmt 8 }

    swACLPktContMaskOptionEntry OBJECT-TYPE
        SYNTAX  SwACLPktContMaskOptionEntry
        MAX-ACCESS  not-accessible
        STATUS  current
        DESCRIPTION
            "A list of information about the user-defined ACL."
        INDEX  { swACLPktContMaskOptionProfileID }
        ::= { swACLPktContMaskOptionTable 1 }

    SwACLPktContMaskOptionEntry ::=
        SEQUENCE {
            swACLPktContMaskOptionProfileID
                INTEGER,
	    swACLPktContMaskOffsetChunk1State
	          INTEGER,
	    swACLPktContMaskOffsetChunk1OffsetValue
	          INTEGER,
	    swACLPktContMaskOffsetChunk1Mask
	          OCTET STRING,
	    swACLPktContMaskOffsetChunk2State
	          INTEGER,
	    swACLPktContMaskOffsetChunk2OffsetValue
	          INTEGER,
	    swACLPktContMaskOffsetChunk2Mask
	          OCTET STRING,
	    swACLPktContMaskOffsetChunk3State
	          INTEGER,
	    swACLPktContMaskOffsetChunk3OffsetValue
	          INTEGER,
	    swACLPktContMaskOffsetChunk3Mask
	          OCTET STRING,
	    swACLPktContMaskOffsetChunk4State
	          INTEGER,
	    swACLPktContMaskOffsetChunk4OffsetValue
	          INTEGER,
	    swACLPktContMaskOffsetChunk4Mask
	          OCTET STRING,
            swACLPktContMaskOptionRowStatus
                RowStatus,
            swACLPktContMaskOptionOwner
                INTEGER,
            swACLPktContMaskOptionUnusedRuleEntries
            	INTEGER       
        }
    swACLPktContMaskOptionProfileID OBJECT-TYPE
        SYNTAX  INTEGER (1..255)
        MAX-ACCESS  read-only
        STATUS  current
        DESCRIPTION
	    "The ID of the ACL mask entry, unique to the mask list. The maximum value of this object depends on the device."
        ::= { swACLPktContMaskOptionEntry 1 }


   swACLPktContMaskOffsetChunk1State OBJECT-TYPE
        SYNTAX  INTEGER {
        	enabled(1),
        	disabled(2)
        	}
        MAX-ACCESS  read-create
        STATUS  current
        DESCRIPTION
	    "Specifies the state of chunk1."
        ::= { swACLPktContMaskOptionEntry 2 }

   swACLPktContMaskOffsetChunk1OffsetValue OBJECT-TYPE
        SYNTAX  INTEGER (0..31)
        MAX-ACCESS  read-create
        STATUS  current
        DESCRIPTION
	    "Specifies the frame content offset of chunk1."
        ::= { swACLPktContMaskOptionEntry 3 }

   swACLPktContMaskOffsetChunk1Mask OBJECT-TYPE
        SYNTAX  OCTET STRING (SIZE(4))
        MAX-ACCESS  read-create
        STATUS  current
        DESCRIPTION
	    "Specifies the frame content mask of chunk1."
        ::= { swACLPktContMaskOptionEntry 4 }

   swACLPktContMaskOffsetChunk2State OBJECT-TYPE
        SYNTAX  INTEGER {
        	enabled(1),
        	disabled(2)
        	}
        MAX-ACCESS  read-create
        STATUS  current
        DESCRIPTION
	    "Specifies the state of chunk2."
        ::= { swACLPktContMaskOptionEntry 5 }

   swACLPktContMaskOffsetChunk2OffsetValue OBJECT-TYPE
        SYNTAX  INTEGER (0..31)
        MAX-ACCESS  read-create
        STATUS  current
        DESCRIPTION
	    "Specifies the frame content offset of chunk2."
        ::= { swACLPktContMaskOptionEntry 6 }

   swACLPktContMaskOffsetChunk2Mask OBJECT-TYPE
        SYNTAX  OCTET STRING (SIZE(4))
        MAX-ACCESS  read-create
        STATUS  current
        DESCRIPTION
	    "Specifies the frame content mask of chunk2."
        ::= { swACLPktContMaskOptionEntry 7 }

   swACLPktContMaskOffsetChunk3State OBJECT-TYPE
        SYNTAX  INTEGER {
        	enabled(1),
        	disabled(2)
        	}
        MAX-ACCESS  read-create
        STATUS  current
        DESCRIPTION
	    "Specifies the state of chunk3."
        ::= { swACLPktContMaskOptionEntry 8 }

   swACLPktContMaskOffsetChunk3OffsetValue OBJECT-TYPE
        SYNTAX  INTEGER (0..31)
        MAX-ACCESS  read-create
        STATUS  current
        DESCRIPTION
	    "Specifies the frame content offset of chunk3."
        ::= { swACLPktContMaskOptionEntry 9 }

   swACLPktContMaskOffsetChunk3Mask OBJECT-TYPE
        SYNTAX  OCTET STRING (SIZE(4))
        MAX-ACCESS  read-create
        STATUS  current
        DESCRIPTION
	    "Specifies the frame content mask of chunk3."
        ::= { swACLPktContMaskOptionEntry 10 }

   swACLPktContMaskOffsetChunk4State OBJECT-TYPE
        SYNTAX  INTEGER {
        	enabled(1),
        	disabled(2)
        	}
        MAX-ACCESS  read-create
        STATUS  current
        DESCRIPTION
	    "Specifies the state of chunk4."
        ::= { swACLPktContMaskOptionEntry 11 }

   swACLPktContMaskOffsetChunk4OffsetValue OBJECT-TYPE
        SYNTAX  INTEGER (0..31)
        MAX-ACCESS  read-create
        STATUS  current
        DESCRIPTION
	    "Specifies the frame content offset of chunk4."
        ::= { swACLPktContMaskOptionEntry 12 }

   swACLPktContMaskOffsetChunk4Mask OBJECT-TYPE
        SYNTAX  OCTET STRING (SIZE(4))
        MAX-ACCESS  read-create
        STATUS  current
        DESCRIPTION
	    "Specifies the frame content mask of chunk4."
        ::= { swACLPktContMaskOptionEntry 13 }

    swACLPktContMaskOptionRowStatus OBJECT-TYPE
        SYNTAX  RowStatus
        MAX-ACCESS  read-create
        STATUS  current
        DESCRIPTION
            "This object indicates the status of this entry."
        ::= { swACLPktContMaskOptionEntry 14 }

    swACLPktContMaskOptionOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
             "The owner of the ACL mask entry. The type of ACL entry created. ACL type
             entries can only be modified when being configured through the same
             type command. For example, IP-MAC Binding entries can only be modified
             or deleted through the IP-MAC Binding configurations or commands."
        ::= { swACLPktContMaskOptionEntry 15 }

    swACLPktContMaskOptionUnusedRuleEntries OBJECT-TYPE
    	SYNTAX INTEGER
    	MAX-ACCESS read-only
    	STATUS current
    	DESCRIPTION
    	    "The number of unused rule entries of this IP profile entry."
    	::={ swACLPktContMaskOptionEntry 16}

--***************************************************************************
--swACLMaskDelAllState
--***************************************************************************
    swACLMaskDelAllState OBJECT-TYPE
        SYNTAX      INTEGER{
    		none(1),
    		start(2)
    		}
        MAX-ACCESS  read-write
        STATUS      current
        DESCRIPTION
            "Used to delete all ACL masks."
        ::= { swAclMaskMgmt 5 }

-- -----------------------------------------------------------------------------
-- swACLEtherRuleTable
-- -----------------------------------------------------------------------------
    swACLEtherRuleTable OBJECT-TYPE
        SYNTAX  SEQUENCE OF SwACLEtherRuleEntry
        MAX-ACCESS  not-accessible
        STATUS  current
        DESCRIPTION
            "This table contains Ethernet ACL information."
        ::= { swAclRuleMgmt 1 }

    swACLEtherRuleEntry OBJECT-TYPE
        SYNTAX  SwACLEtherRuleEntry
        MAX-ACCESS  not-accessible
        STATUS  current
        DESCRIPTION
            "A list of information about the ACL rule of the layer 2 part of each packet."
        INDEX  { swACLEtherRuleProfileID,swACLEtherRuleAccessID }
        ::= { swACLEtherRuleTable 1 }

    SwACLEtherRuleEntry ::=
        SEQUENCE {
            swACLEtherRuleProfileID
                INTEGER,
            swACLEtherRuleAccessID
                INTEGER,
            swACLEtherRuleVlan
                SnmpAdminString,
            swACLEtherRuleSrcMacAddress
                MacAddress,
            swACLEtherRuleDstMacAddress
                MacAddress,
            swACLEtherRule8021P
                INTEGER,
            swACLEtherRuleEtherType
                OCTET STRING,
            swACLEtherRuleEnablePriority
                INTEGER,
            swACLEtherRulePriority
                INTEGER,
            swACLEtherRuleReplacePriority
                INTEGER,
            swACLEtherRuleEnableReplaceDscp
                INTEGER,
            swACLEtherRuleRepDscp
                INTEGER,
            swACLEtherRulePermit
                INTEGER,
            swACLEtherRulePort
                  PortList,
--                INTEGER,
	       swACLEtherRuleRxRate
                INTEGER,  
           swACLEtherRuleRowStatus
                RowStatus,
           swACLEtherRuleTimeRangeName
                SnmpAdminString,                                                         
           swACLEtherRuleOwner
                INTEGER,
           swACLEtherRuleMatchVID
                INTEGER,
           swACLEtherRuleMirrorGroupID
                INTEGER
                             
        }
    swACLEtherRuleProfileID OBJECT-TYPE
        SYNTAX  INTEGER (1..255)
        MAX-ACCESS  read-only
        STATUS  current
        DESCRIPTION
            "The ID of the ACL rule entry, which is unique to the mask list. 
             The maximum value of this object depends on the device."
        ::= { swACLEtherRuleEntry 1 }

    swACLEtherRuleAccessID OBJECT-TYPE
        SYNTAX  INTEGER (0..65535)
        MAX-ACCESS  read-only
        STATUS  current
        DESCRIPTION
            "The ID of the the ACL rule entry relates to the swACLEtherRuleProfileID.
             When row creation is set to 0, assignment of an Access ID for ports is automatic
             and the swACLEtherRulePort creates Rule entries for the swACLEtherRulePort accordingly.
             When set from 1 to 65535, an access ID will be created for the swACLEtherRulePort.
             The swACLEtherRulePort must be set to one port only otherwise the row creation will fail.
            "
        ::= { swACLEtherRuleEntry 2 }

    swACLEtherRuleVlan OBJECT-TYPE
        SYNTAX  SnmpAdminString (SIZE (1..32))
        MAX-ACCESS  read-create
        STATUS  current
        DESCRIPTION
            "Specifies that the access rule will apply to this VLAN only."
        ::= { swACLEtherRuleEntry 3 }

    swACLEtherRuleSrcMacAddress OBJECT-TYPE
        SYNTAX  MacAddress
        MAX-ACCESS  read-create
        STATUS  current
        DESCRIPTION
            "Specifies that the access rule will apply to only packets with
             this source MAC address."
        ::= { swACLEtherRuleEntry 4 }

    swACLEtherRuleDstMacAddress OBJECT-TYPE
        SYNTAX  MacAddress
        MAX-ACCESS  read-create
        STATUS  current
        DESCRIPTION
            "Specifies that the access rule will apply to only packets
              with this destination MAC address."
        ::= { swACLEtherRuleEntry 5 }

    swACLEtherRule8021P OBJECT-TYPE
        SYNTAX  INTEGER(0..7)
        MAX-ACCESS  read-create
        STATUS  current
        DESCRIPTION
	    "Specifies that the access rule will apply only to packets with
              this 802.1p priority value."
        ::= { swACLEtherRuleEntry 6 }

    swACLEtherRuleEtherType OBJECT-TYPE
        SYNTAX  OCTET STRING (SIZE (2))
        MAX-ACCESS  read-create
        STATUS  current
        DESCRIPTION
            "Specifies that the access rule will apply only to packets with this
             hexadecimal 802.1Q Ethernet type value in the packet header."
        ::= { swACLEtherRuleEntry 7 }

    swACLEtherRuleEnablePriority OBJECT-TYPE
        SYNTAX  INTEGER {
               enabled(1),
               disabled(2)
               }
        MAX-ACCESS  read-create
        STATUS  current
        DESCRIPTION
            "Specifies that the access rule will apply only to packets with
             priority value."
        ::= { swACLEtherRuleEntry 8 }

    swACLEtherRulePriority OBJECT-TYPE
        SYNTAX  INTEGER(0..7)
        MAX-ACCESS  read-create
        STATUS  current
        DESCRIPTION
            "Specifies that the priority will be changed in packets while the swACLEtherRuleEnablePriority
             is enabled ."
        ::= { swACLEtherRuleEntry 9 }

    swACLEtherRuleReplacePriority OBJECT-TYPE
        SYNTAX  INTEGER {
               enabled(1),
               disabled(2)
               }
        MAX-ACCESS  read-create
        STATUS  current
        DESCRIPTION
            "Specifies if the switch will change priorities of packets that match the access profile
             802.1p priority tag field or not ."
        ::= { swACLEtherRuleEntry 10 }

    swACLEtherRuleEnableReplaceDscp OBJECT-TYPE
        SYNTAX  INTEGER {
               enabled(1),
               disabled(2)
               }
        MAX-ACCESS  read-create
        STATUS  current
        DESCRIPTION
            "Specifies if the switch will change priorities of packets that match the access profile
             DSCP field or not.
             Replace DSCP and replace ToS precedence can not both be supported. 
	    "
        ::= { swACLEtherRuleEntry 11 }

    swACLEtherRuleRepDscp OBJECT-TYPE
        SYNTAX  INTEGER(0..63)
        MAX-ACCESS  read-create
        STATUS  current
        DESCRIPTION
            "Specifies a value to be written to the DSCP field of an incoming packet
             that meets the criteria specified in the first part of the command.
             This value will over-write the value in the DSCP field of the packet."
        ::= { swACLEtherRuleEntry 12 }

    swACLEtherRulePermit OBJECT-TYPE
        SYNTAX  INTEGER {
               deny(1),
               permit(2),
               mirror(3)
               }
        MAX-ACCESS  read-create
        STATUS  current
        DESCRIPTION
            "This object indicates if the result of the packet examination is 'permit' or 'deny'.
             The default is 'permit'.
             permit - Specifies that packets that match the access profile are
                      permitted to be forwarded by the switch.
             deny - Specifies that packets that match the access profile
                    are not permitted to be forwarded by the switch and will be filtered.
             mirror - Specifies the packets that match the access profile are copied to the mirror port.
                      Note: The ACL mirror function will function after mirror has been enabled
                             and the mirror port has been configured."
        ::= { swACLEtherRuleEntry 13 }

    swACLEtherRulePort OBJECT-TYPE
--        SYNTAX  INTEGER (1..65535)
        SYNTAX  PortList
        MAX-ACCESS  read-create
        STATUS  current
        DESCRIPTION
            "Specifies that the access rule will only apply to port(s). 
             This object and swACLEtherRuleVID can not be set together."
        ::= { swACLEtherRuleEntry 14 }

--    swACLEtherRuleSwAclState OBJECT-TYPE
--        SYNTAX  INTEGER {
--               enable(1),
--               disable(2)
--               }
--        MAX-ACCESS  read-create
--        STATUS  current
--        DESCRIPTION
--            "Specifies that the access rule will only apply to the software ACL state."
--        ::= { swACLEtherRuleEntry 15 }

    swACLEtherRuleRxRate  OBJECT-TYPE
        SYNTAX  INTEGER (0..156249)
        MAX-ACCESS  read-create
        STATUS  current
        DESCRIPTION
            "Specifies the rx rate, 0 denotes no_limit."
        ::= { swACLEtherRuleEntry 15 }
        
    swACLEtherRuleRowStatus OBJECT-TYPE	--swACLEtherRuleState
        SYNTAX  RowStatus
        MAX-ACCESS  read-create
        STATUS  current
        DESCRIPTION
            "This object indicates the status of this entry."
        ::= { swACLEtherRuleEntry 16 }

    swACLEtherRuleTimeRangeName OBJECT-TYPE
    		SYNTAX      SnmpAdminString (SIZE (0..32))
    		MAX-ACCESS  read-write
    		STATUS      current
    		DESCRIPTION
        	"Specifies the time_range that applies to this rule."    
    	::= { swACLEtherRuleEntry 17 }        

    swACLEtherRuleOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
            "The owner of the ACL rule entry. Only owners can modify this entry."
        ::= { swACLEtherRuleEntry 18 }	
        
    swACLEtherRuleMatchVID OBJECT-TYPE
        SYNTAX  INTEGER (0..4094)
        MAX-ACCESS  read-create
        STATUS  current
        DESCRIPTION
            "Specifies that the access rule will apply only to packets with
             this VLAN ID. It is applied to the specified ports configured by swACLEtherRulePort."
        ::= { swACLEtherRuleEntry 21 }

    swACLEtherRuleMirrorGroupID OBJECT-TYPE
        SYNTAX  INTEGER
        MAX-ACCESS  read-create
        STATUS  current
        DESCRIPTION
            "Specifies that packets matching the access profile are copied to the group ID,and the swACLEtherRulePermit should be set
             to mirror first.   
             Note : The default value is 1."
        ::= { swACLEtherRuleEntry 25 }        
-- -----------------------------------------------------------------------------
-- swACLIpRuleTable
-- -----------------------------------------------------------------------------
    swACLIpRuleTable OBJECT-TYPE
        SYNTAX  SEQUENCE OF SwACLIpRuleEntry
        MAX-ACCESS  not-accessible
        STATUS  current
        DESCRIPTION
            ""
        ::= { swAclRuleMgmt 2 }

    swACLIpRuleEntry OBJECT-TYPE
        SYNTAX  SwACLIpRuleEntry
        MAX-ACCESS  not-accessible
        STATUS  current
        DESCRIPTION
            ""
        INDEX  { swACLIpRuleProfileID , swACLIpRuleAccessID }
        ::= { swACLIpRuleTable 1 }

    SwACLIpRuleEntry ::=
        SEQUENCE {
            swACLIpRuleProfileID
                INTEGER,
            swACLIpRuleAccessID
                INTEGER,
            swACLIpRuleVlan
                SnmpAdminString,
            swACLIpRuleSrcIpaddress
            	IpAddress,
            swACLIpRuleDstIpaddress
            	IpAddress,
            swACLIpRuleDscp
            	INTEGER,
            swACLIpRuleProtocol
                INTEGER,
            swACLIpRuleIcmp			
            	INTEGER,
            swACLIpRuleIgmp			
            	INTEGER,
            swACLIpRuleSrcPort
            	INTEGER,
            swACLIpRuleDstPort
            	INTEGER,
            swACLIpRuleFlagBits
            	INTEGER,
            swACLIpRuleProtoID
            	INTEGER,
            swACLIpRuleUserMask
            	OCTET STRING,
            swACLIpRuleEnablePriority
                INTEGER,
            swACLIpRulePriority
                INTEGER,
            swACLIpRuleReplacePriority
                INTEGER,
            swACLIpRuleEnableReplaceDscp
                INTEGER,
            swACLIpRuleRepDscp
                INTEGER,
            swACLIpRulePermit
            	INTEGER,
            swACLIpRulePort
--            	INTEGER,         
                PortList,
            swACLIpRuleRxRate
                INTEGER,
            swACLIpRuleRowStatus
                RowStatus,
            swACLIpRuleTimeRangeName
    		    SnmpAdminString,                                                               
	        swACLIpRuleSrcMacAddress
                MacAddress,
            swACLIpRuleOwner
                INTEGER,
            swACLIpRuleType
            	INTEGER,
            swACLIpRuleCode
            	INTEGER,
            swACLIpRuleMatchVID
                INTEGER,
            swACLIpRuleMirrorGroupID
                INTEGER                                  	                
        }

    swACLIpRuleProfileID OBJECT-TYPE
        SYNTAX  INTEGER (1..255)
        MAX-ACCESS  read-only
        STATUS  current
        DESCRIPTION
            "The ID of the ACL mask entry, which is unique to the mask list. The maximum value of this object depends on the device."
        ::= { swACLIpRuleEntry 1 }

    swACLIpRuleAccessID OBJECT-TYPE
        SYNTAX  INTEGER (0..65535)
        MAX-ACCESS  read-only	--read-create
        STATUS  current
        DESCRIPTION
            "The ID of the ACL rule entry relates to swACLIPRuleProfileID.
             Row creation set to 0 indicates automatic assignment of the Access ID
             for the ports in the swACLIpRulePort to create Rule entries
             for swACLIpRulePort accordingly.
             Set to 1-65535 causes creation of an access ID for the swACLIpRulePort.
             The swACLIpRulePort must be set to one port only otherwise the row
             creation will fail."
        ::= { swACLIpRuleEntry 2 }

    swACLIpRuleVlan OBJECT-TYPE
        SYNTAX  SnmpAdminString (SIZE (1..32))
        MAX-ACCESS  read-create
        STATUS  current
        DESCRIPTION
            "Specifies that the access rule will only apply to this VLAN."
        ::= { swACLIpRuleEntry 3 }

    swACLIpRuleSrcIpaddress OBJECT-TYPE
        SYNTAX  IpAddress
        MAX-ACCESS  read-create
        STATUS  current
        DESCRIPTION
            "Specifies an IP source address."
        ::= { swACLIpRuleEntry 4 }

    swACLIpRuleDstIpaddress OBJECT-TYPE
        SYNTAX  IpAddress
        MAX-ACCESS  read-create
        STATUS  current
        DESCRIPTION
            "Specifies an IP destination address."
        ::= { swACLIpRuleEntry 5 }

    swACLIpRuleDscp OBJECT-TYPE
        SYNTAX  INTEGER(0..63)
        MAX-ACCESS  read-create
        STATUS  current
        DESCRIPTION
            "Specifies the value of DSCP. The value can be configured 0 to 63"
        ::= { swACLIpRuleEntry 6 }

    swACLIpRuleProtocol OBJECT-TYPE
        SYNTAX  INTEGER {
               none(1),
               icmp(2),
               igmp(3),
               tcp(4),
               udp(5),
               protocolId(6)
               }
        MAX-ACCESS  read-only
        STATUS  current
        DESCRIPTION
            "Specifies the IP protocol which has been configured in swACLIpEntry  ."
        ::= { swACLIpRuleEntry 7 }   

    swACLIpRuleIcmp OBJECT-TYPE
        SYNTAX  INTEGER{
	       enabled(1),
               disabled(2)
		}
        MAX-ACCESS  read-create
        STATUS  current
        DESCRIPTION
            "Specific that the rule applies to the igmp type traffic."
        ::= { swACLIpRuleEntry 8 }    

    swACLIpRuleIgmp OBJECT-TYPE
        SYNTAX  INTEGER{
	       enabled(1),
               disabled(2)
		}
        MAX-ACCESS  read-create
        STATUS  current
        DESCRIPTION
            "Specific that the rule applies to the igmp type traffic."
        ::= { swACLIpRuleEntry 9 }    

    swACLIpRuleSrcPort OBJECT-TYPE
        SYNTAX  INTEGER(0..65535)
        MAX-ACCESS  read-create
        STATUS  current
        DESCRIPTION
            "Specifies that the rule applies to the range of the TCP/UDP source ports."
        ::= { swACLIpRuleEntry 10 }

    swACLIpRuleDstPort OBJECT-TYPE
        SYNTAX  INTEGER(0..65535)
        MAX-ACCESS  read-create
        STATUS  current
        DESCRIPTION
            "Specifies the range of TCP/UDP destination port range"
        ::= { swACLIpRuleEntry 11 }

    swACLIpRuleFlagBits OBJECT-TYPE
        SYNTAX  INTEGER(0..63)
        MAX-ACCESS  read-create
        STATUS  current
        DESCRIPTION
            "A value which indicates the set of TCP flags that this
             entity may potentially offer.  The value is a sum of flag bits.
             This sum initially takes the value zero. Then, for each flag, L
             is added in the range 1 through 6, for which this node performs
             transactions, where 2^(L - 1) is added to the sum.
             Note that values should be calculated accordingly:

                 Flag      functionality
                   6        urg bit
                   5        ack bit
                   4        psh bit
                   3        rst bit
                   2		syn bit
                   1 		fin bit
	     For example, it you want to enable urg bit and ack bit, you
	     should set value 48{2^(5-1) + 2^(6-1)}."
        ::= { swACLIpRuleEntry 12 }

    swACLIpRuleProtoID OBJECT-TYPE
        SYNTAX  INTEGER(0..255)
        MAX-ACCESS  read-create
        STATUS  current
        DESCRIPTION
            "Specifies that the rule applies to the value of IP protocol ID traffic"
        ::= { swACLIpRuleEntry 13 }

    swACLIpRuleUserMask OBJECT-TYPE
        SYNTAX  OCTET STRING (SIZE(4))
        MAX-ACCESS  read-create
        STATUS  current
        DESCRIPTION
            "Specifies that the rule applies to the IP protocol ID and the range of
             options behind the IP header."
        ::= { swACLIpRuleEntry 14 }

    swACLIpRuleEnablePriority OBJECT-TYPE
        SYNTAX  INTEGER {
               enabled(1),
               disabled(2)
               }
        MAX-ACCESS  read-create
        STATUS  current
        DESCRIPTION
            "Specifies that the access rule will apply only to packets with this
             priority value."
        ::= { swACLIpRuleEntry 15 }

    swACLIpRulePriority OBJECT-TYPE
        SYNTAX  INTEGER(0..7)
        MAX-ACCESS  read-create
        STATUS  current
        DESCRIPTION
            "Specifies the priority will change in packets while the swACLIpRuleEnablePriority
             is enabled."
        ::= { swACLIpRuleEntry 16 }

    swACLIpRuleReplacePriority OBJECT-TYPE
        SYNTAX  INTEGER {
               enabled(1),
               disabled(2)
               }
        MAX-ACCESS  read-create
        STATUS  current
        DESCRIPTION
            "Specifies whether the packets that match the access profile will change the
             802.1p priority tag field by the switch or not."
        ::= { swACLIpRuleEntry 17 }

    swACLIpRuleEnableReplaceDscp OBJECT-TYPE
        SYNTAX  INTEGER {
               enabled(1),
               disabled(2)
               }
        MAX-ACCESS  read-create
        STATUS  current
        DESCRIPTION
            "Specifies if the switch will change priorities of packets that match the access profile
             DSCP field or not.
             Replace DSCP and replace ToS precedence can not both be supported.
            "
        ::= { swACLIpRuleEntry 18 }

    swACLIpRuleRepDscp OBJECT-TYPE
        SYNTAX  INTEGER(0..63)
        MAX-ACCESS  read-create
        STATUS  current
        DESCRIPTION
            "Specifies a value to be written to the DSCP field of an incoming packet
             that meets the criteria specified in the first part of the command.
             This value will over-write the value in the DSCP field of the packet."
        ::= { swACLIpRuleEntry 19 }

    swACLIpRulePermit OBJECT-TYPE
        SYNTAX  INTEGER {
               deny(1),
               permit(2),
               mirror(3)
               }
        MAX-ACCESS  read-create
        STATUS  current
        DESCRIPTION
            "This object indicates if the result of the packet examination is to 'permit' or 'deny'.
             The default is 'permit'.
             permit - Specifies that packets that match the access profile are
                      permitted to be forwarded by the switch.
             deny - Specifies that packets that match the access profile
                    are not permitted to be forwarded by the switch and will be filtered.
             mirror - Specifies the packets that match the access profile are sent the copied one
                      to the mirror port.
                      Note: The ACL mirror function will work after the mirror is enabled and the mirror port has
                      been configured."
        ::= { swACLIpRuleEntry 20 }

    swACLIpRulePort OBJECT-TYPE
--        SYNTAX  INTEGER (1..65535)
        SYNTAX  PortList
        MAX-ACCESS  read-create
        STATUS  current
        DESCRIPTION
            "Specifies that the access rule will only apply to port(s). 
             This object and swACLIpRuleVID can not be set together. "
        ::= { swACLIpRuleEntry 21 }

swACLIpRuleRxRate  OBJECT-TYPE
        SYNTAX  INTEGER (0..156249)
        MAX-ACCESS  read-create
        STATUS  current
        DESCRIPTION
            "Specifies the rx-rate, 0 denotes no_limit."
        ::= { swACLIpRuleEntry 22 }   
        
    swACLIpRuleRowStatus OBJECT-TYPE	
        SYNTAX  RowStatus
        MAX-ACCESS  read-create
        STATUS  current
        DESCRIPTION
            "This object indicates the status of this entry."
        ::= { swACLIpRuleEntry 23 }

     swACLIpRuleTimeRangeName OBJECT-TYPE
    		SYNTAX      SnmpAdminString (SIZE (0..32))
    		MAX-ACCESS  read-write
    		STATUS      current
    		DESCRIPTION
        	""    
    	::= { swACLIpRuleEntry 24 }                    	  
        
   swACLIpRuleSrcMacAddress OBJECT-TYPE
        SYNTAX  MacAddress
        MAX-ACCESS  read-only
        STATUS  current
        DESCRIPTION
            "Specifies that the access will apply to only packets with
             this source MAC address."
        ::= { swACLIpRuleEntry 25 } 

    swACLIpRuleOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
            "The owner of the ACL rule entry. Only owners can modify this entry."
        ::= { swACLIpRuleEntry 26 }
        
    swACLIpRuleType OBJECT-TYPE
        SYNTAX  INTEGER(0..255)
        MAX-ACCESS  read-create
        STATUS  current
        DESCRIPTION
            "Specifies that the rule applies to the value of ICMP type traffic."
        ::= { swACLIpRuleEntry 27}

    swACLIpRuleCode OBJECT-TYPE
        SYNTAX  INTEGER(0..255)
        MAX-ACCESS  read-create
        STATUS  current
        DESCRIPTION
            "Specifies that the rule applies to the value of ICMP code traffic."
        ::= { swACLIpRuleEntry 28 }    
        
    swACLIpRuleMatchVID OBJECT-TYPE
        SYNTAX  INTEGER (0..4094)
        MAX-ACCESS  read-create
        STATUS  current
        DESCRIPTION
            "Specifies that the access rule will apply only to packets with
             this VLAN ID. It is applied to the specified ports configured by swACLIpRulePort."
        ::= { swACLIpRuleEntry 29 }
        
    swACLIpRuleMirrorGroupID  OBJECT-TYPE
        SYNTAX  INTEGER
        MAX-ACCESS  read-create
        STATUS  current
        DESCRIPTION
            "Specifies that packets matching the access profile are copied to the group ID,and the swACLIpRulePermit should be set
             to mirror first.   
             Note : The default value is 1."
        ::= { swACLIpRuleEntry 35 }                        
--***************************************************************************
--swACLPktContRuleTable
--***************************************************************************  
--    swACLPktContRuleTable OBJECT-TYPE 
--        SYNTAX  SEQUENCE OF SwACLPktContRuleEntry
--        MAX-ACCESS  not-accessible
--        STATUS  current
--        DESCRIPTION
--            "This table contains ACL rules regarding user-defined information."
--        ::= { swAclRuleMgmt 3 }
        
--    swACLPktContRuleEntry OBJECT-TYPE
--        SYNTAX  SwACLPktContRuleEntry
--        MAX-ACCESS  not-accessible
--        STATUS  current
--        DESCRIPTION
--            "A list of information about the ACL rule of the user-defined part of each packet."
--        INDEX  { swACLPktContRuleProfileID,swACLPktContRuleAccessID }
--        ::= { swACLPktContRuleTable 1 }
      
--    SwACLPktContRuleEntry ::= 
--        SEQUENCE {
--            swACLPktContRuleProfileID		
--                INTEGER,
--            swACLPktContRuleAccessID
--                INTEGER,
--            swACLPktContRuleOffset0to15
--                OCTET STRING,
--            swACLPktContRuleOffset16to31
--                OCTET STRING,
--            swACLPktContRuleOffset32to47
 --               OCTET STRING,
--            swACLPktContRuleOffset48to63
--                OCTET STRING,             
--            swACLPktContRuleOffset64to79
--                OCTET STRING,
--            swACLPktContRuleEnablePriority
--            	INTEGER,      
--            swACLPktContRulePriority
--                INTEGER,             
--            swACLPktContRuleReplacePriority	
--                INTEGER,       
--            swACLPktContRuleEnableReplaceDscp
--                INTEGER,                    
--            swACLPktContRuleRepDscp	
--               INTEGER,              
--            swACLPktContRulePermit
--                INTEGER,         
--            swACLPktContRulePort
--                INTEGER,         
--               PortList,
--            swACLPktContRuleSwAclState
--                INTEGER,
--            swACLPktContRuleRowStatus
--                RowStatus                                                         
--        }
--    swACLPktContRuleProfileID OBJECT-TYPE
--        SYNTAX  INTEGER (1..255)
--        MAX-ACCESS  read-only
--        STATUS  current
--        DESCRIPTION
--            "The ID of ACL mask entry ,and is unique in the mask list."
 --       ::= { swACLPktContRuleEntry 1 }
    
--    swACLPktContRuleAccessID OBJECT-TYPE
--        SYNTAX  INTEGER (1..65535)
--        MAX-ACCESS  read-only	
--        STATUS  current
--        DESCRIPTION
--            "The ID of ACL rule entry relate to swACLPktContRuleProfileID."
--        ::= { swACLPktContRuleEntry 2 }        

--    swACLPktContRuleOffset0to15 OBJECT-TYPE
--        SYNTAX  OCTET STRING (SIZE(16)) 
--        MAX-ACCESS  read-create
--        STATUS  current
--        DESCRIPTION
--            "Specifies that the rule applies to the user-defined packet."
--        ::= { swACLPktContRuleEntry 3 }      
--         
--    swACLPktContRuleOffset16to31 OBJECT-TYPE
--        SYNTAX  OCTET STRING (SIZE(16)) 
--        MAX-ACCESS  read-create
--        STATUS  current
--        DESCRIPTION
--            "Specifies that the rule applies to the user-defined packet."
--        ::= { swACLPktContRuleEntry 4 }      
        
--    swACLPktContRuleOffset32to47 OBJECT-TYPE
--        SYNTAX  OCTET STRING (SIZE(16)) 
--        MAX-ACCESS  read-create
--        STATUS  current
--        DESCRIPTION
--            "Specifies that the rule applies to the user-defined packet."
--        ::= { swACLPktContRuleEntry 5 }      
        
--    swACLPktContRuleOffset48to63 OBJECT-TYPE
--        SYNTAX  OCTET STRING (SIZE(16)) 
--        MAX-ACCESS  read-create
--       STATUS  current
--        DESCRIPTION
--            "Specifies that the rule applies to the user-defined packet."
--        ::= { swACLPktContRuleEntry 6 }           
        
--    swACLPktContRuleOffset64to79 OBJECT-TYPE
--        SYNTAX  OCTET STRING (SIZE(16)) 
--        MAX-ACCESS  read-create
--       STATUS  current
--        DESCRIPTION
--            "Specifies that the rule applies to the user-defined packet."
--        ::= { swACLPktContRuleEntry 7 }               

--    swACLPktContRuleEnablePriority OBJECT-TYPE
--        SYNTAX  INTEGER {
--               enabled(1),
--               disabled(2)
--               }
--        MAX-ACCESS  read-create
--        STATUS  current
--        DESCRIPTION
--            "Specifies that the access will apply only to packets with
--             priority value."
--        ::= { swACLPktContRuleEntry 8 }  
                
--    swACLPktContRulePriority OBJECT-TYPE
--        SYNTAX  INTEGER(0..7)
--        MAX-ACCESS  read-create
--        STATUS  current
--        DESCRIPTION
--            "Specific the priority will change to the packets while the swACLPktContRuleReplacePriority
--             is enabled ."
--       ::= { swACLPktContRuleEntry 9 }     
        
--    swACLPktContRuleReplacePriority OBJECT-TYPE
--        SYNTAX  INTEGER {
 --              enabled(1),
--               disabled(2)
--               }
--        MAX-ACCESS  read-create
--        STATUS  current
--        DESCRIPTION
--            "Specific the packets that match the access profile will changed the
--             802.1p priority tag field by the switch or not ."
--        ::= { swACLPktContRuleEntry 10 }  
        
--    swACLPktContRuleEnableReplaceDscp OBJECT-TYPE
--        SYNTAX  INTEGER {
--               enabled(1),
--               disabled(2)
--               }
--        MAX-ACCESS  read-create
--        STATUS  current
--        DESCRIPTION
--            "Specific the packets that match the access profile will replaced the
--             DSCP field by the switch or not ."
--        ::= { swACLPktContRuleEntry 11 }  

--    swACLPktContRuleRepDscp OBJECT-TYPE	
--       SYNTAX  INTEGER(0..63)
--        MAX-ACCESS  read-create
--        STATUS  current
--        DESCRIPTION
--            "specify a value to be written to the DSCP field of an incoming packet
--             that meets the criteria specified in the first part of the command.
--             This value will over-write the value in the DSCP field of the packet."
--        ::= { swACLPktContRuleEntry 12 }  

--    swACLPktContRulePermit OBJECT-TYPE
--        SYNTAX  INTEGER {
--               deny(1),
--               permit(2)
--               }
--        MAX-ACCESS  read-create
--        STATUS  current
--        DESCRIPTION
--            "This object indicates resoult of examination is permit or deny;default is permit(1)
--             permit - Specifies that packets that match the access profile are 
--                      permitted to be forwarded by the switch.
--             deny - Specifies that packets that do not match the access profile
--                    are not permitted to be forwarded by the switch and will be filtered."
--        ::= { swACLPktContRuleEntry 13 }  

--    swACLPktContRulePort OBJECT-TYPE
--        SYNTAX  INTEGER (1..65535)
--        SYNTAX  PortList
--        MAX-ACCESS  read-create
--        STATUS  current
--        DESCRIPTION
--             "Specifies that the access  will apply to only to port(s)."
--         ::= { swACLPktContRuleEntry 14 }  
 
 --   swACLPktContRuleSwAclState OBJECT-TYPE
 --       SYNTAX  INTEGER {
 --              enable(1),
 --              disable(2)
--              }
--       MAX-ACCESS  read-create
--       STATUS  current
--       DESCRIPTION
--           "Specifies that the access will apply to only to software ACL state."
--       ::= { swACLPktContRuleEntry 15 }    
        
--    swACLPktContRuleRowStatus OBJECT-TYPE
--        SYNTAX  RowStatus
--        MAX-ACCESS  read-create
--        STATUS  current
--        DESCRIPTION
--            "This object indicates the status of this entry."
 --       ::= { swACLPktContRuleEntry 15 }   

-- -----------------------------------------------------------------------------
-- swACLIpv6RuleTable
-- -----------------------------------------------------------------------------
    swACLIpv6RuleTable OBJECT-TYPE
        SYNTAX  SEQUENCE OF SwACLIpv6RuleEntry
        MAX-ACCESS  not-accessible
        STATUS  current
        DESCRIPTION
            "This table contains the IPv6 ACL rule information."
        ::= { swAclRuleMgmt 4 }

    swACLIpv6RuleEntry OBJECT-TYPE
        SYNTAX  SwACLIpv6RuleEntry
        MAX-ACCESS  not-accessible
        STATUS  current
        DESCRIPTION
            "A list of information about ACL rules regarding the IPv6 part of each packet."
        INDEX  { swACLIpv6RuleProfileID,swACLIpv6RuleAccessID }
        ::= { swACLIpv6RuleTable 1 }

    SwACLIpv6RuleEntry ::=
        SEQUENCE {
            swACLIpv6RuleProfileID
                INTEGER,
            swACLIpv6RuleAccessID
                INTEGER,
            swACLIpv6RuleClass
                INTEGER,
            swACLIpv6RuleFlowlabel
                OCTET STRING,
            swACLIpv6RuleSrcIpv6Addr
                Ipv6Address,
            swACLIpv6RuleDstIpv6Addr
                Ipv6Address,
            swACLIpv6RuleEnablePriority
            	INTEGER,
            swACLIpv6RulePriority
                INTEGER,
            swACLIpv6RuleReplacePriority
                INTEGER,
--            swACLIpv6RuleEnableReplaceDscp
--                INTEGER,                    
--            swACLIpv6RuleRepDscp	
--                INTEGER,              
            swACLIpv6RulePermit
                INTEGER,         
            swACLIpv6RulePort
--                INTEGER,         
                PortList,
	    	swACLIpv6RuleRxRate
                INTEGER,   
            swACLIpv6RuleRowStatus
                RowStatus,
            swACLIpv6RuleTimeRangeName
            	SnmpAdminString,
            swACLIpv6RuleOwner
                INTEGER,
            swACLIpv6RuleProtocol
                INTEGER,
            swACLIpv6RuleSrcPort
                INTEGER,
            swACLIpv6RuleDstPort
                INTEGER,                                                                 
            swACLIpv6RuleMirrorGroupID
                INTEGER            
        }
    swACLIpv6RuleProfileID OBJECT-TYPE
        SYNTAX  INTEGER (1..255)
        MAX-ACCESS  read-only
        STATUS  current
        DESCRIPTION
            "The ID of the ACL mask entry, which is unique to the mask list. The maximum value of this object depends on the device."
        ::= { swACLIpv6RuleEntry 1 }

    swACLIpv6RuleAccessID OBJECT-TYPE
        SYNTAX  INTEGER (0..65535)
        MAX-ACCESS  read-only
        STATUS  current
        DESCRIPTION
            "The ID of the ACL rule entry relates to swACLIpv6RuleProfileID.
             When row creation is set to 0, this indicates the access ID
             will be assigned automatically for the ports in the swACLIpv6RulePort
             to create rule entries for swACLIpv6RulePort accordingly.
             Set to 1-65535 indicates creation of an access ID for the swACLIpv6RulePort.
             The swACLIpv6RulePort must be set to one port only, otherwise
             the row creation will fail."
        ::= { swACLIpv6RuleEntry 2 }

    swACLIpv6RuleClass OBJECT-TYPE
        SYNTAX  INTEGER (0..255)
        MAX-ACCESS  read-create
        STATUS  current
        DESCRIPTION
            "Specifies that the rule applies to the IPv6 class field."
        ::= { swACLIpv6RuleEntry 3 }

    swACLIpv6RuleFlowlabel OBJECT-TYPE
        SYNTAX  OCTET STRING (SIZE(4))
        MAX-ACCESS  read-create
        STATUS  current
        DESCRIPTION
            "Specifies that the rule applies to the IPv6 flow label field."
        ::= { swACLIpv6RuleEntry 4 }

    swACLIpv6RuleSrcIpv6Addr OBJECT-TYPE
        SYNTAX  Ipv6Address
        MAX-ACCESS  read-create
        STATUS  current
        DESCRIPTION
            "Specifies that the rule applies to the source IPv6 address.
            This should be a 16 byte octet string."
        ::= { swACLIpv6RuleEntry 5 }

    swACLIpv6RuleDstIpv6Addr OBJECT-TYPE
        SYNTAX  Ipv6Address
        MAX-ACCESS  read-create
        STATUS  current
        DESCRIPTION
            "Specifies that the rule applies to the destination IPv6 address.
            This should be a 16 byte octet string."
        ::= { swACLIpv6RuleEntry 6 }

    swACLIpv6RuleEnablePriority OBJECT-TYPE
        SYNTAX  INTEGER {
               enabled(1),
               disabled(2)
               }
        MAX-ACCESS  read-create
        STATUS  current
        DESCRIPTION
            "Specifies that the access rule will apply only to packets with
             priority value."
        ::= { swACLIpv6RuleEntry 7 }

    swACLIpv6RulePriority OBJECT-TYPE
        SYNTAX  INTEGER(0..7)
        MAX-ACCESS  read-create
        STATUS  current
        DESCRIPTION
            "Specifies the priority will change in packets while the swACLIpv6RuleReplacePriority
             is enabled."
        ::= { swACLIpv6RuleEntry 8 }

    swACLIpv6RuleReplacePriority OBJECT-TYPE
        SYNTAX  INTEGER {
               enabled(1),
               disabled(2)
               }
        MAX-ACCESS  read-create
        STATUS  current
        DESCRIPTION
            "Specifies if the switch will change priorities of packets that match the access profile
             802.1p priority tag or not."
        ::= { swACLIpv6RuleEntry 9 }

--    swACLIpv6RuleEnableReplaceDscp OBJECT-TYPE
--        SYNTAX  INTEGER {
--               enabled(1),
--               disabled(2)
--               }
--        MAX-ACCESS  read-create
--        STATUS  current
--        DESCRIPTION
--            "Specifies if the switch will change priorities of packets that match the access profile
--             DSCP field or not."
--        ::= { swACLIpv6RuleEntry 9 }
--
--    swACLIpv6RuleRepDscp OBJECT-TYPE
--        SYNTAX  INTEGER(0..63)
--        MAX-ACCESS  read-create
--        STATUS  current
--        DESCRIPTION
--            "Specifies a value to be written to the DSCP field of an incoming packet
--             that meets the criteria specified in the first part of the command.
--             This value will over-write the value in the DSCP field of the packet."
--        ::= { swACLIpv6RuleEntry 10 }

    swACLIpv6RulePermit OBJECT-TYPE
        SYNTAX  INTEGER {
               deny(1),
               permit(2),
               mirror(3)
               }
        MAX-ACCESS  read-create
        STATUS  current
        DESCRIPTION
            "This object indicates if the result of packet examination is to 'permit' or 'deny'.
	     The default is 'permit'.
             permit - Specifies that packets that match the access profile are
                      permitted to be forwarded by the switch.
             deny - Specifies that packets that match the access profile
                    are not permitted to be forwarded by the switch and will be filtered.
             mirror - Specifies the packets that match the access profile are copied to
                      the mirror port.
                      Note: The ACL mirror function will work after mirror has been enabled
                      and the mirror port has been configured."
        ::= { swACLIpv6RuleEntry 10 }

    swACLIpv6RulePort OBJECT-TYPE
--        SYNTAX  INTEGER (1..65535)
        SYNTAX  PortList
        MAX-ACCESS  read-create
        STATUS  current
        DESCRIPTION
            "Specifies that the access rule will apply only to port(s)."
        ::= { swACLIpv6RuleEntry 11 }

   swACLIpv6RuleRxRate  OBJECT-TYPE
        SYNTAX  INTEGER (0..156249)
        MAX-ACCESS  read-create
        STATUS  current
        DESCRIPTION
            "Specifies the rx-rate, 0 denotes no_limit."
        ::= { swACLIpv6RuleEntry 12 }
        
    swACLIpv6RuleRowStatus OBJECT-TYPE
        SYNTAX  RowStatus
        MAX-ACCESS  read-create
        STATUS  current
        DESCRIPTION
            "This object indicates the status of this entry."
        ::= { swACLIpv6RuleEntry 13 }

    swACLIpv6RuleTimeRangeName OBJECT-TYPE
    		SYNTAX      SnmpAdminString (SIZE (0..32))
    		MAX-ACCESS  read-write
    		STATUS      current
    		DESCRIPTION
        	""    
    	::= { swACLIpv6RuleEntry 14 }         

    swACLIpv6RuleOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
            "The owner of the ACL rule entry. Only owners can modify this entry."
        ::= { swACLIpv6RuleEntry 15 }
    swACLIpv6RuleProtocol OBJECT-TYPE
        SYNTAX  INTEGER {
               none(1),
               tcp(2),
               udp(3)
--             ,icmp(4)
               }
        MAX-ACCESS  read-create
        STATUS  current
        DESCRIPTION
            "Specifies the IPv6 protocol.
             For some older chips, this object can not be set. When getting this object,
             it always returns the type which has been configured in swACLIpv6Entry.

             For some newer chips, this object can only set the type which
             has been configured in swACLIpv6Entry. The default value is none (1).
            "
        ::= { swACLIpv6RuleEntry 20 }

    swACLIpv6RuleSrcPort OBJECT-TYPE
        SYNTAX  INTEGER(0..65535)
        MAX-ACCESS  read-create
        STATUS  current
        DESCRIPTION
            "Specifies that the rule applies to the range of the TCP/UDP source ports."
        ::= { swACLIpv6RuleEntry 21 }

    swACLIpv6RuleDstPort OBJECT-TYPE
        SYNTAX  INTEGER(0..65535)
        MAX-ACCESS  read-create
        STATUS  current
        DESCRIPTION
            "Specifies the TCP/UDP destination ports range."
        ::= { swACLIpv6RuleEntry 22 }
    swACLIpv6RuleMirrorGroupID OBJECT-TYPE
        SYNTAX  INTEGER
        MAX-ACCESS  read-create
        STATUS  current
        DESCRIPTION
            "Specifies that packets matching the access profile are copied to the group ID,and the swACLIpv6RulePermit should be set
             to mirror first.   
             Note : The default value is 1."
        ::= { swACLIpv6RuleEntry 29 }
	   
-- -----------------------------------------------------------------------------
--swIBPACLEtherRuleTable
-- -----------------------------------------------------------------------------
    swIBPACLEtherRuleTable OBJECT-TYPE
        SYNTAX  SEQUENCE OF SwIBPACLEtherRuleEntry
        MAX-ACCESS  not-accessible
        STATUS  current
        DESCRIPTION
            "This table contains IP-MAC-Binding Ethernet ACL Rule information."
        ::= { swAclRuleMgmt 5 }

    swIBPACLEtherRuleEntry OBJECT-TYPE
        SYNTAX  SwIBPACLEtherRuleEntry
        MAX-ACCESS  not-accessible
        STATUS  current
        DESCRIPTION
            "A list of information about the ACL rule of the layer 2 part of each packet."
        INDEX  { swIBPACLEtherRuleProfileID,swIBPACLEtherRuleAccessID }
        ::= { swIBPACLEtherRuleTable 1 }

    SwIBPACLEtherRuleEntry ::=
        SEQUENCE {
            swIBPACLEtherRuleProfileID
                INTEGER,
            swIBPACLEtherRuleAccessID
                INTEGER,
            swIBPACLEtherRuleEtherType
                OCTET STRING,
            swIBPACLEtherRulePermit
                INTEGER,
            swIBPACLEtherRulePort
                  PortList
        }
    swIBPACLEtherRuleProfileID OBJECT-TYPE
        SYNTAX  INTEGER (1..255)
        MAX-ACCESS  read-only
        STATUS  current
        DESCRIPTION
            "The ID of the ACL mask entry, unique in the mask list. The maximum value of this object depends on the device."
        ::= { swIBPACLEtherRuleEntry 1 }

    swIBPACLEtherRuleAccessID OBJECT-TYPE
        SYNTAX  INTEGER (0..65535)
        MAX-ACCESS  read-only
        STATUS  current
        DESCRIPTION
            "The ID of the ACL rule entry in relation to swACLEtherRuleProfileID.
            When row creation is set to 0, this indicates automatically assigning an Access 
            for the ports in the swACLEtherRulePort  to create rule entries for swACLEtherRulePort
            accordingly.
            Set to 1-65535 indicates to create the exact access ID for the swACLEtherRulePort
            and the swACLEtherRulePort must set one port only, otherwise the row creation will
            fail."
        ::= { swIBPACLEtherRuleEntry 2 }

    swIBPACLEtherRuleEtherType OBJECT-TYPE
        SYNTAX  OCTET STRING (SIZE (2))
        MAX-ACCESS  read-only
        STATUS  current
        DESCRIPTION
            "Specifies that the access rule will apply only to packets with this
             802.1Q Ethernet type value in the packet header."
        ::= { swIBPACLEtherRuleEntry 3 }

    swIBPACLEtherRulePermit OBJECT-TYPE
        SYNTAX  INTEGER {
               deny(1),
               permit(2)
               }
        MAX-ACCESS  read-only
        STATUS  current
        DESCRIPTION
            "This object indicates if the result of the examination is 'permit' or 'deny'.
             The default is 'permit' (1).
             permit - Specifies that packets that match the access profile are
                      permitted to be forwarded by the switch.
             deny - Specifies that packets that match the access profile
                    are not permitted to be forwarded by the switch and will be filtered."
        ::= { swIBPACLEtherRuleEntry 4 }

    swIBPACLEtherRulePort OBJECT-TYPE
        SYNTAX  PortList
        MAX-ACCESS  read-only
        STATUS  current
        DESCRIPTION
            "Specifies that the access rule will only apply to port(s)."
        ::= { swIBPACLEtherRuleEntry 5 }

-- -----------------------------------------------------------------------------
--swIBPACLIpRuleTable
-- -----------------------------------------------------------------------------
    swIBPACLIpRuleTable OBJECT-TYPE
        SYNTAX  SEQUENCE OF SwIBPACLIpRuleEntry
        MAX-ACCESS  not-accessible
        STATUS  current
        DESCRIPTION
            ""
        ::= { swAclRuleMgmt 6 }

    swIBPACLIpRuleEntry OBJECT-TYPE
        SYNTAX  SwIBPACLIpRuleEntry
        MAX-ACCESS  not-accessible
        STATUS  current
        DESCRIPTION
            ""
        INDEX  { swIBPACLIpRuleProfileID , swIBPACLIpRuleAccessID }
        ::= { swIBPACLIpRuleTable 1 }

    SwIBPACLIpRuleEntry ::=
        SEQUENCE {
            swIBPACLIpRuleProfileID
                INTEGER,
            swIBPACLIpRuleAccessID
                INTEGER,
	    swIBPACLIpRuleSrcMacAddress
                MacAddress,
            swIBPACLIpRuleSrcIpaddress
            	IpAddress,
            swIBPACLIpRulePermit
            	INTEGER,
            swIBPACLIpRulePort
                PortList
        }
    swIBPACLIpRuleProfileID OBJECT-TYPE
        SYNTAX  INTEGER (1..255)
        MAX-ACCESS  read-only
        STATUS  current
        DESCRIPTION
            "The ID of the ACL mask entry, unique in the mask list. The maximum value of this object depends on the device."
        ::= { swIBPACLIpRuleEntry 1 }

    swIBPACLIpRuleAccessID OBJECT-TYPE
        SYNTAX  INTEGER (0..65535)
        MAX-ACCESS  read-only	--read-create
        STATUS  current
        DESCRIPTION
            "The ID of the ACL rule entry in relation to swACLIPRuleProfileID.
            When the row creation is set to 0, this indicates assigning an access ID automatically
            for the ports in the swACLIpRulePort  to create rule entries for swACLIpRulePort
            accordingly.
            Set to 1-65535 indicates to create the exact access ID for the swACLIpRulePort
            and the swACLIpRulePort must be set for one port only, otherwise the row creation will
            fail."
        ::= { swIBPACLIpRuleEntry 2 }

   swIBPACLIpRuleSrcMacAddress OBJECT-TYPE
        SYNTAX  MacAddress
        MAX-ACCESS  read-only
        STATUS  current
        DESCRIPTION
            "Specifies that the access rule will apply to only packets with
             this source MAC address."
        ::= { swIBPACLIpRuleEntry 3 }

    swIBPACLIpRuleSrcIpaddress OBJECT-TYPE
        SYNTAX  IpAddress
        MAX-ACCESS  read-only
        STATUS  current
        DESCRIPTION
            "Specifies an IP source address."
        ::= { swIBPACLIpRuleEntry 4 }

    swIBPACLIpRulePermit OBJECT-TYPE
        SYNTAX  INTEGER {
               deny(1),
               permit(2)
               }
        MAX-ACCESS  read-only
        STATUS  current
        DESCRIPTION
            "This object indicates if the result of the examination is 'permit' or 'deny'; the default is 'permit' (1)
             permit - Specifies that packets that match the access profile are
                      permitted to be forwarded by the switch.
             deny - Specifies that packets that match the access profile
                    are not permitted to be forwarded by the switch and will be filtered."
        ::= { swIBPACLIpRuleEntry 5 }

    swIBPACLIpRulePort OBJECT-TYPE
        SYNTAX  PortList
        MAX-ACCESS  read-only
        STATUS  current
        DESCRIPTION
            "Specifies that the access rule will only apply to port(s)."
        ::= { swIBPACLIpRuleEntry 6 }

-- -----------------------------------------------------------------------------
--swACLPktContRuleOptionTable
-- -----------------------------------------------------------------------------
    swACLPktContRuleOptionTable OBJECT-TYPE
        SYNTAX  SEQUENCE OF SwACLPktContRuleOptionEntry
        MAX-ACCESS  not-accessible
        STATUS  current
        DESCRIPTION
            "This table contains user-defined ACL information."
        ::= { swAclRuleMgmt 7 }

    swACLPktContRuleOptionEntry OBJECT-TYPE
        SYNTAX  SwACLPktContRuleOptionEntry
        MAX-ACCESS  not-accessible
        STATUS  current
        DESCRIPTION
            "A list of information about the ACL rule regarding the user-defined part of each packet."
        INDEX  { swACLPktContRuleOptionProfileID,swACLPktContRuleOptionAccessID }
        ::= { swACLPktContRuleOptionTable 1 }

    SwACLPktContRuleOptionEntry ::=
        SEQUENCE {
            swACLPktContRuleOptionProfileID
                INTEGER,
            swACLPktContRuleOptionAccessID
                INTEGER,
           swACLPktContRuleOffsetChunk1OffsetValue
               INTEGER,
           swACLPktContRuleOffsetChunk1Content
               OCTET STRING,
           swACLPktContRuleOffsetChunk2OffsetValue
               INTEGER,
           swACLPktContRuleOffsetChunk2Content
               OCTET STRING,
           swACLPktContRuleOffsetChunk3OffsetValue
               INTEGER,
           swACLPktContRuleOffsetChunk3Content
               OCTET STRING,
           swACLPktContRuleOffsetChunk4OffsetValue
               INTEGER,
           swACLPktContRuleOffsetChunk4Content
               OCTET STRING,
            swACLPktContRuleOptionEnablePriority
            	INTEGER,
            swACLPktContRuleOptionPriority
                INTEGER,
            swACLPktContRuleOptionReplacePriority
                INTEGER,
            swACLPktContRuleOptionEnableReplaceDscp
                INTEGER,
            swACLPktContRuleOptionRepDscp
                INTEGER,
            swACLPktContRuleOptionPermit
                INTEGER,
            swACLPktContRuleOptionPort
                PortList,
            swACLPktContRuleOptionRowStatus
                RowStatus,
            swACLPktContRuleOptionOwner
                INTEGER,
	    	swACLPktContRuleOptionRxRate
                INTEGER,
            swACLPktContRuleOptionTimeRangeName
            	SnmpAdminString,
            swACLPktContRuleOptionMirrorGroupID 
                 INTEGER
       	
        }
    swACLPktContRuleOptionProfileID OBJECT-TYPE
        SYNTAX  INTEGER (1..255)
        MAX-ACCESS  read-only
        STATUS  current
        DESCRIPTION
	    "The ID of the ACL mask entry, which is unique to the mask list. The maximum value of this object depends on the device."
        ::= { swACLPktContRuleOptionEntry 1 }

    swACLPktContRuleOptionAccessID OBJECT-TYPE
        SYNTAX  INTEGER (0..65535)
        MAX-ACCESS  read-only
        STATUS  current
        DESCRIPTION
            "The ID of the ACL rule entry in relation to the swACLPktContRuleProfileID.
             When row creation is set to 0, access ID is automatically created
             for the ports in the swACLPktContRulePort to create rule entries
             for swACLPktContRulePort accordingly.
             Set to 1-65535 indicates to creswACLPktContRuleRepDscpate the exact access ID
             for the swACLPktContRulePort. The swACLPktContRulePort must be set to
             one port only, otherwise the row creation will fail."
        ::= { swACLPktContRuleOptionEntry 2 }

   swACLPktContRuleOffsetChunk1OffsetValue  OBJECT-TYPE
        SYNTAX  INTEGER (0..31)
        MAX-ACCESS  read-only
        STATUS  current
        DESCRIPTION
	    "Displays the frame content offset of chunk1."
        ::= { swACLPktContRuleOptionEntry 3 }

   swACLPktContRuleOffsetChunk1Content  OBJECT-TYPE
       SYNTAX  OCTET STRING (SIZE(4))
       MAX-ACCESS  read-create
       STATUS  current
       DESCRIPTION
           "Specifies the frame content of chunk1."
       ::= { swACLPktContRuleOptionEntry 4 }

   swACLPktContRuleOffsetChunk2OffsetValue  OBJECT-TYPE
        SYNTAX  INTEGER (0..31)
        MAX-ACCESS  read-only
        STATUS  current
        DESCRIPTION
	    "Displays the frame content offset of chunk2."
        ::= { swACLPktContRuleOptionEntry 5 }

    swACLPktContRuleOffsetChunk2Content  OBJECT-TYPE
       SYNTAX  OCTET STRING (SIZE(4))
       MAX-ACCESS  read-create
       STATUS  current
       DESCRIPTION
           "Specifies the frame content of chunk2."
       ::= { swACLPktContRuleOptionEntry 6 }

    swACLPktContRuleOffsetChunk3OffsetValue  OBJECT-TYPE
        SYNTAX  INTEGER (0..31)
        MAX-ACCESS  read-only
        STATUS  current
        DESCRIPTION
	    "Displays the frame content offset of chunk3."
        ::= { swACLPktContRuleOptionEntry 7 }

    swACLPktContRuleOffsetChunk3Content  OBJECT-TYPE
       SYNTAX  OCTET STRING (SIZE(4))
       MAX-ACCESS  read-create
       STATUS  current
       DESCRIPTION
           "Specifies the frame content of chunk3."
       ::= { swACLPktContRuleOptionEntry 8 }

     swACLPktContRuleOffsetChunk4OffsetValue  OBJECT-TYPE
        SYNTAX  INTEGER (0..31)
        MAX-ACCESS  read-only
        STATUS  current
        DESCRIPTION
	    "Displays the frame content offset of chunk4."
        ::= { swACLPktContRuleOptionEntry 9 }

     swACLPktContRuleOffsetChunk4Content  OBJECT-TYPE
       SYNTAX  OCTET STRING (SIZE(4))
       MAX-ACCESS  read-create
       STATUS  current
       DESCRIPTION
           "Specifies the frame content of chunk4."
       ::= { swACLPktContRuleOptionEntry 10 }

    swACLPktContRuleOptionEnablePriority OBJECT-TYPE
        SYNTAX  INTEGER {
               enabled(1),
               disabled(2)
               }
        MAX-ACCESS  read-create
        STATUS  current
        DESCRIPTION
            "Specifies that the access rule will only apply to packets with this
             priority value."
        ::= { swACLPktContRuleOptionEntry 11 }

    swACLPktContRuleOptionPriority OBJECT-TYPE
        SYNTAX  INTEGER(0..7)
        MAX-ACCESS  read-create
        STATUS  current
        DESCRIPTION
	    "Specifies that the priority will change for the packets while the swACLPktContRuleReplacePriority
         is enabled ."
        ::= { swACLPktContRuleOptionEntry 12 }

    swACLPktContRuleOptionReplacePriority OBJECT-TYPE
        SYNTAX  INTEGER {
               enabled(1),
               disabled(2)
               }
        MAX-ACCESS  read-create
        STATUS  current
        DESCRIPTION
	    "Specifies if the switch will change priorities of packets that match the access profile
	    802.1p priority tag or not."
        ::= { swACLPktContRuleOptionEntry 13 }

    swACLPktContRuleOptionEnableReplaceDscp OBJECT-TYPE
        SYNTAX  INTEGER {
               enabled(1),
               disabled(2)
               }
        MAX-ACCESS  read-create
        STATUS  current
        DESCRIPTION
            "Specifies if the switch will change priorities of packets that match the access profile
             DSCP field or not."
        ::= { swACLPktContRuleOptionEntry 14 }

    swACLPktContRuleOptionRepDscp OBJECT-TYPE
        SYNTAX  INTEGER(0..63)
        MAX-ACCESS  read-create
        STATUS  current
        DESCRIPTION
            "Specifies a value to be written to the DSCP field of an incoming packet
             that meets the criteria specified in the first part of the command.
             This value will over-write the value in the DSCP field of the packet."
        ::= { swACLPktContRuleOptionEntry 15 }

    swACLPktContRuleOptionPermit OBJECT-TYPE
        SYNTAX  INTEGER {
               deny(1),
               permit(2),
               mirror(3)
               }
        MAX-ACCESS  read-create
        STATUS  current
        DESCRIPTION
	    "This object indicates if the result of the packet examination is 'permit' or 'deny'.
	     The default is 'permit'.
             permit - Specifies that packets that match the access profile are
                      permitted to be forwarded by the switch.
             deny - Specifies that packets that match the access profile
                    are not permitted to be forwarded by the switch and will be filtered.
             mirror - Specifies that the packets that match the access profile are copied to
                      the mirror port.
                      Note: The ACL mirror function will function after mirror is enabled
                      and a mirror port has been configured."
        ::= { swACLPktContRuleOptionEntry 16 }

    swACLPktContRuleOptionPort OBJECT-TYPE
        SYNTAX  PortList
        MAX-ACCESS  read-create
        STATUS  current
        DESCRIPTION
             "Specifies that the access rule will only apply to port(s). 
              This object and swACLPktContRuleOptionVID can not be set together. "
         ::= { swACLPktContRuleOptionEntry 17 }

    swACLPktContRuleOptionRowStatus OBJECT-TYPE
        SYNTAX  RowStatus
        MAX-ACCESS  read-create
        STATUS  current
        DESCRIPTION
            "This object indicates the status of this entry."
        ::= { swACLPktContRuleOptionEntry 18 }

    swACLPktContRuleOptionOwner OBJECT-TYPE
        SYNTAX  INTEGER {
               any(1),
               acl(2),
               ipbind(3),
               other(4),
               dhcp(5),
               netbios(6),
               ext-netbios(7),
               ismvlan(8),
               dhcp-relay(9),
               jwac-upserver(13),
               jwac-authentication(14)
               }
        MAX-ACCESS  read-only
        STATUS  current
        DESCRIPTION
            "The owner of the ACL rule entry. Only owners can modify this entry."
        ::= { swACLPktContRuleOptionEntry 19 }

   swACLPktContRuleOptionRxRate  OBJECT-TYPE
        SYNTAX  INTEGER (0..15624)
        MAX-ACCESS  read-create
        STATUS  current
        DESCRIPTION
            "Specifies the rx-rate, 0 denotes no_limit."
        ::= { swACLPktContRuleOptionEntry 20 }

    swACLPktContRuleOptionTimeRangeName OBJECT-TYPE
    		SYNTAX      SnmpAdminString (SIZE (0..32))
    		MAX-ACCESS  read-write
    		STATUS      current
    		DESCRIPTION
        	""    
    	::= { swACLPktContRuleOptionEntry 21 } 
    	
    swACLPktContRuleOptionMirrorGroupID OBJECT-TYPE
        SYNTAX  INTEGER
        MAX-ACCESS  read-create
        STATUS  current
        DESCRIPTION
            "Specifies that packets matching the access profile are copied to the group ID,and the swACLPktContRuleOptionPermit should be set
             to mirror first.   
             Note : The default value is 1."
        ::= { swACLPktContRuleOptionEntry 22 }      
    	        
-- -----------------------------------------------------------------------------
-- swACLCounterTable
-- -----------------------------------------------------------------------------
       swACLCounterTable OBJECT-TYPE
           SYNTAX      SEQUENCE OF SwACLCounterEntry
           MAX-ACCESS  not-accessible
           STATUS      current
           DESCRIPTION
               "This table maintains counter information associated with a specific
                rule in the ACL rule table. Please refer to the swACLEtherRuleTable,
                swACLIpRuleTable, swACLIpv6RuleTable and swACLPktContRuleTable
                for detailed ACL rule information."
           ::= { swAclRuleMgmt 8 }

       swACLCounterEntry OBJECT-TYPE
           SYNTAX      SwACLCounterEntry
           MAX-ACCESS  not-accessible
           STATUS      current
           DESCRIPTION
               "The entry maintains counter information associated with the ACL
                rule table."
           INDEX { swACLCounterProfileID, swACLCounterAccessID}
           ::= { swACLCounterTable 1 }

       SwACLCounterEntry ::=
           SEQUENCE {
               swACLCounterProfileID
                   INTEGER,
               swACLCounterAccessID
                   INTEGER,
               swACLCounterState
                   INTEGER,
               swACLCounterTotalCounter
                   Counter64,
               swACLCounterGreenCounter
                   Counter64,
               swACLCounterYellowCounter
                   Counter64,
               swACLCounterRedCounter
              	   Counter64
           }

    swACLCounterProfileID OBJECT-TYPE
        SYNTAX      INTEGER
        MAX-ACCESS  read-only
        STATUS      current
        DESCRIPTION
            "The ID of the ACL mask entry, which is unique in the mask
             list."
        ::= { swACLCounterEntry 1 }

    swACLCounterAccessID OBJECT-TYPE
        SYNTAX      INTEGER(1..65535)
        MAX-ACCESS  read-only
        STATUS      current
        DESCRIPTION
            "The ID of the ACL rule entry as related to the
             swACLCounterProfileID."
        ::= { swACLCounterEntry 2 }

    swACLCounterState OBJECT-TYPE
        SYNTAX  INTEGER {
               enabled(1),
               disabled(2)
               }
        MAX-ACCESS  read-write
        STATUS  current
        DESCRIPTION
            "Specifies whether the counter feature will be enabled/disabled.
	     1.	This is optional. The default is disable.
	     2.	If the rule is not bound with flow_meter, then all packets that match will be counted.
	     If the rule is bound with flow_meter, then the 'counter' will be overridden.
	     "
        ::= { swACLCounterEntry 3 }

    swACLCounterTotalCounter OBJECT-TYPE
        SYNTAX  Counter64
        MAX-ACCESS  read-only
        STATUS  current
        DESCRIPTION
            "The number of matched packets."
        ::= { swACLCounterEntry 4 }

    swACLCounterGreenCounter OBJECT-TYPE
        SYNTAX  Counter64
        MAX-ACCESS  read-only
        STATUS  current
        DESCRIPTION
            "The number of matched green packets."
        ::= { swACLCounterEntry 5 }

    swACLCounterYellowCounter OBJECT-TYPE
        SYNTAX  Counter64
        MAX-ACCESS  read-only
        STATUS  current
        DESCRIPTION
            "The number of matched yellow packets."
        ::= { swACLCounterEntry 6 }

    swACLCounterRedCounter OBJECT-TYPE
        SYNTAX  Counter64
        MAX-ACCESS  read-only
        STATUS  current
        DESCRIPTION
            "The number of matched red packets."
        ::= { swACLCounterEntry 7 }


-- -----------------------------------------------------------------------------
-- swCpuAclEthernetTable
-- -----------------------------------------------------------------------------
    swCpuAclEthernetTable OBJECT-TYPE
        SYNTAX  SEQUENCE OF SwCpuAclEthernetEntry
        MAX-ACCESS  not-accessible
        STATUS  current
        DESCRIPTION
            "This table contains software ACL mask Ethernet information.
             Access profiles will be created on the switch to define which
             part of each incoming frame's layer 2 header will be examined by
             the switch. Masks entered will be combined with the values
             the switch finds in the specified frame header fields."
        ::= { swCpuAclMaskMgmt 1 }

    swCpuAclEthernetEntry OBJECT-TYPE
        SYNTAX  SwCpuAclEthernetEntry
        MAX-ACCESS  not-accessible
        STATUS  current
        DESCRIPTION
            "A list of information about Ethernet ACL masks."
        INDEX  { swCpuAclEthernetProfileID }
        ::= { swCpuAclEthernetTable 1 }

    SwCpuAclEthernetEntry ::=
        SEQUENCE {
            swCpuAclEthernetProfileID
                INTEGER,
            swCpuAclEthernetUsevlan
                INTEGER,
            swCpuAclEthernetMacAddrMaskState
                INTEGER,
            swCpuAclEthernetSrcMacAddrMask
                MacAddress,
            swCpuAclEthernetDstMacAddrMask
                MacAddress,
--            swCpuAclEthernetUse8021p
--                INTEGER,
            swCpuAclEthernetUseEthernetType
                INTEGER,
            swCpuAclEthernetRowStatus
                RowStatus
        }
    swCpuAclEthernetProfileID OBJECT-TYPE
        SYNTAX  INTEGER (1..255)
        MAX-ACCESS  read-only	--read-create
        STATUS  current
        DESCRIPTION
            "The ID of the software ACL mask entry, which is unique to the mask list. The maximum value of this object depends on the device."
        ::= { swCpuAclEthernetEntry 1 }

    swCpuAclEthernetUsevlan OBJECT-TYPE
        SYNTAX  INTEGER {
               enabled(1),
               disabled(2)
               }
        MAX-ACCESS  read-create
        STATUS  current
        DESCRIPTION
            "Specifies that the switch will examine the VLAN part of each packet header."
        ::= { swCpuAclEthernetEntry 2 }

    swCpuAclEthernetMacAddrMaskState OBJECT-TYPE
		SYNTAX  INTEGER {
               other(1),
               dst-mac-addr(2),
               src-mac-addr(3),
               dst-src-mac-addr(4)
               }
        MAX-ACCESS  read-create
        STATUS  current
        DESCRIPTION
            "This object indicates the status of the MAC address mask.

            other (1) - Neither source MAC addresses nor destination MAC addresses are
                masked.
            dst-mac-addr (2) - Destination MAC addresses within received frames are
            	to be filtered when matched with the MAC address entry of the table.
            src-mac-addr (3) - Source MAC address within received frames are to
            	be filtered when matched with the MAC address entry of the table.
            dst-src-mac-addr (4) - Source or destination MAC addresses within received
            	frames are to be filtered when matched with the MAC address entry of this table."
        ::= { swCpuAclEthernetEntry 3 }

    swCpuAclEthernetSrcMacAddrMask OBJECT-TYPE
        SYNTAX  MacAddress
        MAX-ACCESS  read-create
        STATUS  current
        DESCRIPTION
            "This object specifies the MAC address mask for the source MAC address."
        ::= { swCpuAclEthernetEntry 4 }

    swCpuAclEthernetDstMacAddrMask OBJECT-TYPE
        SYNTAX  MacAddress
        MAX-ACCESS  read-create
        STATUS  current
        DESCRIPTION
            "This object specifies the MAC address mask for the destination MAC address."
        ::= { swCpuAclEthernetEntry 5 }

 --   swCpuAclEthernetUse8021p OBJECT-TYPE
 --       SYNTAX  INTEGER {
 --              enabled(1),
 --              disabled(2)
 --              }
 --       MAX-ACCESS  read-create
 --       STATUS  current
 --       DESCRIPTION
 --           "Specifies if the switch will examine the 802.1p priority value in the frame's header
 --             or not."
 --       ::= { swCpuAclEthernetEntry 6 }

    swCpuAclEthernetUseEthernetType OBJECT-TYPE
        SYNTAX  INTEGER {
               enabled(1),
               disabled(2)
               }
        MAX-ACCESS  read-create
        STATUS  current
        DESCRIPTION
            "Specifies if the switch will examine the Ethernet type value in each frame's header
              or not."
        ::= { swCpuAclEthernetEntry 7 }

    swCpuAclEthernetRowStatus OBJECT-TYPE --swCpuAclEthernetState
        SYNTAX  RowStatus
        MAX-ACCESS  read-create
        STATUS  current
        DESCRIPTION
            "This object indicates the status of this entry."
        ::= { swCpuAclEthernetEntry 8 }

-- -----------------------------------------------------------------------------
-- swCpuAclIpTable
-- -----------------------------------------------------------------------------
    swCpuAclIpTable OBJECT-TYPE
        SYNTAX  SEQUENCE OF SwCpuAclIpEntry
        MAX-ACCESS  not-accessible
        STATUS  current
        DESCRIPTION
            "This table contains software ACL mask IP information.
             Access profiles will be created on the switch to define which
             parts of each incoming frame's IP layer 2 header will be examined
             by the switch. Masks entered will be combined with the
             values the switch finds in the specified frame header fields."
        ::= { swCpuAclMaskMgmt 2 }

    swCpuAclIpEntry OBJECT-TYPE
        SYNTAX  SwCpuAclIpEntry
        MAX-ACCESS  not-accessible
        STATUS  current
        DESCRIPTION
            "A list of information about the software ACL of the IP Layer."
        INDEX  { swCpuAclIpProfileID }
        ::= { swCpuAclIpTable 1 }

    SwCpuAclIpEntry ::=
        SEQUENCE {
            swCpuAclIpProfileID
                INTEGER,
            swCpuAclIpUsevlan
                INTEGER,
            swCpuAclIpIpAddrMaskState
                INTEGER,
            swCpuAclIpSrcIpAddrMask
                IpAddress,
            swCpuAclIpDstIpAddrMask
                IpAddress,
            swCpuAclIpUseDSCP
                INTEGER,
            swCpuAclIpUseProtoType
                INTEGER,
            swCpuAclIpIcmpOption
                INTEGER,
            swCpuAclIpIgmpOption
                INTEGER,
            swCpuAclIpTcpOption
                INTEGER,
            swCpuAclIpUdpOption
             	INTEGER,
            swCpuAclIpTCPorUDPSrcPortMask
				OCTET STRING,
	    	swCpuAclIpTCPorUDPDstPortMask
				OCTET STRING,
	    	swCpuAclIpTCPFlagBit
				INTEGER,
            swCpuAclIpTCPFlagBitMask
            	INTEGER,
            swCpuAclIpProtoIDOption
                INTEGER,
			swCpuAclIpProtoID
			    INTEGER,
            swCpuAclIpProtoIDMask
                OCTET STRING,
            swCpuAclIpRowStatus
                RowStatus
        }

    swCpuAclIpProfileID OBJECT-TYPE
        SYNTAX  INTEGER (1..255)
        MAX-ACCESS  read-only
        STATUS  current
        DESCRIPTION
            "The ID of the software ACL mask entry, which is unique to the mask list. The maximum value of this object depends on the device."
        ::= { swCpuAclIpEntry 1 }

    swCpuAclIpUsevlan OBJECT-TYPE
        SYNTAX  INTEGER {
               enabled(1),
               disabled(2)
               }
        MAX-ACCESS  read-create
        STATUS  current
        DESCRIPTION
            "This object indicates if the IP layer VLAN part is examined or not."
        ::= { swCpuAclIpEntry 2 }

    swCpuAclIpIpAddrMaskState OBJECT-TYPE
		SYNTAX  INTEGER {
               other(1),
               dst-ip-addr(2),
               src-ip-addr(3),
               dst-src-ip-addr(4)
               }
        MAX-ACCESS  read-create
        STATUS  current
        DESCRIPTION
            "This object indicates the status of IP address mask.

            other (1) - Neither source IP addresses nor destination IP address are
                masked.
            dst-ip-addr (2) - Destination IP addresses within received frames are
            	to be filtered when matched with the IP address entry of this table.
            src-ip-addr (3) - Source IP addresses within received frames are to
            	be filtered when matched with the IP address entry of this table.
            dst-src-ip-addr (4) - Destination or source IP addresses within received
            	frames are to be filtered when matched with the IP address entry of the
            	table."
        ::= { swCpuAclIpEntry 3 }

    swCpuAclIpSrcIpAddrMask OBJECT-TYPE
        SYNTAX  IpAddress
        MAX-ACCESS  read-create
        STATUS  current
        DESCRIPTION
            "This object specifies the IP address mask for the source IP address."
        ::= { swCpuAclIpEntry 4 }

    swCpuAclIpDstIpAddrMask OBJECT-TYPE
        SYNTAX  IpAddress
        MAX-ACCESS  read-create
        STATUS  current
        DESCRIPTION
            "This object specifies the IP address mask for the destination IP address."
        ::= { swCpuAclIpEntry 5 }

    swCpuAclIpUseDSCP OBJECT-TYPE
        SYNTAX  INTEGER {
               enabled(1),
               disabled(2)
               }
        MAX-ACCESS  read-create
        STATUS  current
        DESCRIPTION
            "This object indicates if the DSCP protocol in the packet header is to be examined or not."
        ::= { swCpuAclIpEntry 6 }

    swCpuAclIpUseProtoType OBJECT-TYPE
        SYNTAX  INTEGER {
               none(1),
               icmp(2),
               igmp(3),
               tcp(4),
               udp(5),
               protocolId(6)
               }
        MAX-ACCESS  read-create
        STATUS  current
        DESCRIPTION
            "This object indicates which protocol will be examined."
        ::= { swCpuAclIpEntry 7 }

    swCpuAclIpIcmpOption OBJECT-TYPE
        SYNTAX  INTEGER {
               none(1),
               type(2),
               code(3),
               type-code(4)
               }
        MAX-ACCESS  read-create
        STATUS  current
        DESCRIPTION
            "This object indicates which fields are identified for ICMP.
            none (1)- Both fields are null.
            type (2)- Type field identified.
            code (3)- Code field identified.
            type-code (4)- Both ICMP fields identified.
            "
        ::= { swCpuAclIpEntry 8 }

    swCpuAclIpIgmpOption OBJECT-TYPE
        SYNTAX  INTEGER {
               enable(1),
               disable(2)
              }
        MAX-ACCESS  read-create
        STATUS  current
        DESCRIPTION
            "This object indicates if the IGMP options field is identified or not."
        ::= { swCpuAclIpEntry 9 }

    swCpuAclIpTcpOption OBJECT-TYPE
        SYNTAX  INTEGER {
               other(1),
               dst-addr(2),
               src-addr(3),
               dst-src-addr(4)
               }
        MAX-ACCESS  read-create
        STATUS  current
        DESCRIPTION
            "This object indicates the status of filtered addresses of TCP.

           	other (1) - Neither source port nor destination port are
                masked.
             dst-addr (2) - Packets will be filtered if this destination port is
            	identified in received frames.
             src-addr (3) - Packets will be filtered if this source port is
            	identified in received frames.
             dst-src-addr (4) - Packets will be filtered is this destination or
            	source port is identified in received frames."
        ::= { swCpuAclIpEntry 10 }

    swCpuAclIpUdpOption OBJECT-TYPE
        SYNTAX  INTEGER {
               other(1),
               dst-addr(2),
               src-addr(3),
               dst-src-addr(4)
               }
        MAX-ACCESS  read-create
        STATUS  current
        DESCRIPTION
            "This object indicates the status of filtered addresses of UDP.

            other (1) - Neither source port nor destination port are
                masked.
            dst-addr (2) - Packets will be filtered if this destination port
            	is identified in received frames.
            src-addr (3) - Packets will be filtered if this source port
            	is identified in received frames.
            dst-src-addr (4) - Packets will be filtered if this destination
            	or source port is identified in received frames."

        ::= { swCpuAclIpEntry 11 }

    swCpuAclIpTCPorUDPSrcPortMask OBJECT-TYPE
        SYNTAX  OCTET STRING (SIZE(2))
        MAX-ACCESS  read-create
        STATUS  current
        DESCRIPTION
            "Specifies a TCP port mask for the source port if swCpuAclIpUseProtoType is TCP.
             Specifies a UDP port mask for the source port if swCpuAclIpUseProtoType is UDP.
             "
        ::= { swCpuAclIpEntry 12 }

    swCpuAclIpTCPorUDPDstPortMask OBJECT-TYPE
        SYNTAX  OCTET STRING (SIZE(2))
        MAX-ACCESS  read-create
        STATUS  current
        DESCRIPTION
            "Specifies a TCP port mask for the destination port if swCpuAclIpUseProtoType is TCP.
             Specifies a UDP port mask for the destination port if swCpuAclIpUseProtoType is UDP."
        ::= { swCpuAclIpEntry 13 }

    swCpuAclIpTCPFlagBit OBJECT-TYPE
		SYNTAX  INTEGER {
               enable(1),
               disable(2)
               }
        MAX-ACCESS  read-create
        STATUS  current
        DESCRIPTION
            "Specifies a TCP connection flag mask."
        ::= { swCpuAclIpEntry 14 }

    swCpuAclIpTCPFlagBitMask OBJECT-TYPE
        SYNTAX  INTEGER(0..63)
        MAX-ACCESS  read-create
        STATUS  current
        DESCRIPTION
            "A value which indicates the set of TCP flags that this
             entity may potentially offer. The value is a sum of flag bits.
             This sum initially takes the value zero. Then, for each flag, L
             is added in the range 1 through 6, for which this node performs
             transactions where 2^(L - 1) is added to the sum.
             Note that values should be calculated accordingly:

                 Flag      functionality
                   6        urg bit
                   5        ack bit
                   4        psh bit
                   3        rst bit
                   2		 syn bit
                   1 		 fin bit
			For example, if you want to enable urg bit and ack bit, you
	     should set value 48{2^(5-1) + 2^(6-1)}."
        ::= { swCpuAclIpEntry 15 }

    swCpuAclIpProtoIDOption OBJECT-TYPE
        SYNTAX  INTEGER {
               enable(1),
               disable(2)
               }
        MAX-ACCESS  read-create
        STATUS  current
        DESCRIPTION
            "Specifies if the switch will examine each frame's Protocol ID field or not."
        ::= { swCpuAclIpEntry 16 }

    swCpuAclIpProtoID OBJECT-TYPE
        SYNTAX  INTEGER(0..255)
        MAX-ACCESS  read-create
        STATUS  current
        DESCRIPTION
            ""
        ::= { swCpuAclIpEntry 17 }


    swCpuAclIpProtoIDMask OBJECT-TYPE
        SYNTAX  OCTET STRING (SIZE(4))
        MAX-ACCESS  read-create
        STATUS  current
        DESCRIPTION
            "Specifies that the rule applies to the IP protocol ID and the mask options
             behind the IP header."
        ::= { swCpuAclIpEntry 18 }

    swCpuAclIpRowStatus OBJECT-TYPE
        SYNTAX  RowStatus
        MAX-ACCESS  read-create
        STATUS  current
        DESCRIPTION
            "This object indicates the status of this entry."
        ::= { swCpuAclIpEntry 19 }

-- -----------------------------------------------------------------------------
-- swCpuAclPktContMaskTable
-- -----------------------------------------------------------------------------
    swCpuAclPktContMaskTable OBJECT-TYPE
        SYNTAX  SEQUENCE OF SwCpuAclPktContMaskEntry
        MAX-ACCESS  not-accessible
        STATUS  current
        DESCRIPTION
	    "This table contains user-defined software ACL information.
	     Access profiles will be created on the switch to define which
	     part of each incoming frame's user-defined part of the packet header
	     will be examined by the switch. Masks entered will be combined
              with the values the switch finds in the specified frame header fields."
        ::= { swCpuAclMaskMgmt 3 }

    swCpuAclPktContMaskEntry OBJECT-TYPE
        SYNTAX  SwCpuAclPktContMaskEntry
        MAX-ACCESS  not-accessible
        STATUS  current
        DESCRIPTION
            "A list of information about user-defined software ACLs."
        INDEX  { swCpuAclPktContMaskProfileID }
        ::= { swCpuAclPktContMaskTable 1 }

    SwCpuAclPktContMaskEntry ::=
        SEQUENCE {
            swCpuAclPktContMaskProfileID
                INTEGER,
            swCpuAclPktContMaskOffset0to15
                OCTET STRING,
            swCpuAclPktContMaskOffset16to31
                OCTET STRING,
            swCpuAclPktContMaskOffset32to47
                OCTET STRING,
            swCpuAclPktContMaskOffset48to63
                OCTET STRING,
            swCpuAclPktContMaskOffset64to79
                OCTET STRING,
            swCpuAclPktContMaskRowStatus
                RowStatus
        }
    swCpuAclPktContMaskProfileID OBJECT-TYPE
        SYNTAX  INTEGER (1..255)
        MAX-ACCESS  read-only	--read-create
        STATUS  current
        DESCRIPTION
            "The ID of the software ACL mask entry, which is unique to the mask list. The maximum value of this object depends on the device."
        ::= { swCpuAclPktContMaskEntry 1 }

    swCpuAclPktContMaskOffset0to15 OBJECT-TYPE
        SYNTAX  OCTET STRING (SIZE(16))
        MAX-ACCESS  read-create
        STATUS  current
        DESCRIPTION
            "Specifies that the rule applies to the packet content (Offset0to15) and
             the mask options."
        ::= { swCpuAclPktContMaskEntry 2 }

    swCpuAclPktContMaskOffset16to31 OBJECT-TYPE
        SYNTAX  OCTET STRING (SIZE(16))
        MAX-ACCESS  read-create
        STATUS  current
        DESCRIPTION
            "Specifies that the rule applies to the packet content (Offset16to31) and
             the mask options."
         ::= { swCpuAclPktContMaskEntry 3 }

    swCpuAclPktContMaskOffset32to47 OBJECT-TYPE
        SYNTAX  OCTET STRING (SIZE(16))
        MAX-ACCESS  read-create
        STATUS  current
        DESCRIPTION
            "Specifies that the rule applies to the packet content (Offset32to47) and
             the mask options."
        ::= { swCpuAclPktContMaskEntry 4 }

    swCpuAclPktContMaskOffset48to63 OBJECT-TYPE
        SYNTAX  OCTET STRING (SIZE(16))
        MAX-ACCESS  read-create
        STATUS  current
        DESCRIPTION
            "Specifies that the rule applies to the packet content (Offset48to63) and
             the mask options."
        ::= { swCpuAclPktContMaskEntry 5 }

    swCpuAclPktContMaskOffset64to79 OBJECT-TYPE
        SYNTAX  OCTET STRING (SIZE(16))
        MAX-ACCESS  read-create
        STATUS  current
        DESCRIPTION
            "Specifies that the rule applies to the packet content (Offset64to79) and
             the mask options."
        ::= { swCpuAclPktContMaskEntry 6 }

    swCpuAclPktContMaskRowStatus OBJECT-TYPE --swCpuAclEthernetState
        SYNTAX  RowStatus
        MAX-ACCESS  read-create
        STATUS  current
        DESCRIPTION
            "This object indicates the status of this entry."
        ::= { swCpuAclPktContMaskEntry 7 }

-- -----------------------------------------------------------------------------
-- swCpuAclIpv6MaskTable
-- -----------------------------------------------------------------------------
    swCpuAclIpv6MaskTable OBJECT-TYPE
        SYNTAX  SEQUENCE OF SwCpuAclIpv6MaskEntry
        MAX-ACCESS  not-accessible
        STATUS  current
        DESCRIPTION
            "This table contains IPv6 software ACL mask information.
             An access profile will be created on the switch to define which
             part of each incoming frame's IPv6 part of the packet header
             will be examined by switch. Masks entered will be combined
              with the values the switch finds in the specified frame header fields.  "
        ::= { swCpuAclMaskMgmt 4 }

    swCpuAclIpv6MaskEntry OBJECT-TYPE
        SYNTAX  SwCpuAclIpv6MaskEntry
        MAX-ACCESS  not-accessible
        STATUS  current
        DESCRIPTION
            "A list of information about user-defined software ACLs."
        INDEX  { swCpuAclIpv6MaskProfileID }
        ::= { swCpuAclIpv6MaskTable 1 }

    SwCpuAclIpv6MaskEntry ::=
        SEQUENCE {
            swCpuAclIpv6MaskProfileID
                INTEGER,
            swCpuAclIpv6MaskClass
                INTEGER,
            swCpuAclIpv6MaskFlowlabel
                INTEGER,
            swCpuAclIpv6IpAddrMaskState
                INTEGER,
            swCpuAclIpv6MaskSrcIpv6Mask
                Ipv6Address,
            swCpuAclIpv6MaskDstIpv6Mask
                Ipv6Address,
            swCpuAclIpv6MaskRowStatus
                RowStatus
        }
    swCpuAclIpv6MaskProfileID OBJECT-TYPE
        SYNTAX  INTEGER (1..255)
        MAX-ACCESS  read-only	--read-create
        STATUS  current
        DESCRIPTION
            "The ID of the software ACL mask entry, which is unique to the mask list. The maximum value of this object depends on the device."
        ::= { swCpuAclIpv6MaskEntry 1 }

    swCpuAclIpv6MaskClass OBJECT-TYPE
        SYNTAX  INTEGER {
               enable(1),
               disable(2)
               }
        MAX-ACCESS  read-create
        STATUS  current
        DESCRIPTION
            "Specifies that the rule applies to the IPv6 class field and the mask options."
        ::= { swCpuAclIpv6MaskEntry 2 }

    swCpuAclIpv6MaskFlowlabel OBJECT-TYPE
        SYNTAX  INTEGER {
               enable(1),
               disable(2)
               }
        MAX-ACCESS  read-create
        STATUS  current
        DESCRIPTION
            "Specifies that the rule applies to the IPv6 flowlabel field and the mask options."
        ::= { swCpuAclIpv6MaskEntry 3 }

    swCpuAclIpv6IpAddrMaskState OBJECT-TYPE
		SYNTAX  INTEGER {
               other(1),
               dst-ipv6-addr(2),
               src-ipv6-addr(3),
               dst-src-ipv6-addr(4)
               }
        MAX-ACCESS  read-create
        STATUS  current
        DESCRIPTION
            "This object indicates the status of IPv6 address mask.

            other (1) - Neither source IPv6 address nor destination IPv6 address are
                masked.
             dst-ipv6-addr (2) - Packets will be filtered if this destination IPv6 address
		is identified as a match in received frames.
             src-ipv6-addr (3) - Packets will be filtered if this source IPv6 address
		is identified as a match in received frames.
             dst-src-ipv6-addr (4) - Packets will be filtered if this destination or source
		IPv6 address is identified as a match in received frames."
        ::= { swCpuAclIpv6MaskEntry 4 }

    swCpuAclIpv6MaskSrcIpv6Mask OBJECT-TYPE
        SYNTAX  Ipv6Address
        MAX-ACCESS  read-create
        STATUS  current
        DESCRIPTION
            "Specifies that the rule applies to the source IPv6 address and the mask options.
            This should be a 16 byte octet string."
        ::= { swCpuAclIpv6MaskEntry 5 }

    swCpuAclIpv6MaskDstIpv6Mask OBJECT-TYPE
        SYNTAX  Ipv6Address
        MAX-ACCESS  read-create
        STATUS  current
        DESCRIPTION
            "Specifies that the rule applies to the destination IPv6 address and the mask options.
            This should be a 16 byte octet string."
        ::= { swCpuAclIpv6MaskEntry 6 }

    swCpuAclIpv6MaskRowStatus OBJECT-TYPE
        SYNTAX  RowStatus
        MAX-ACCESS  read-create
        STATUS  current
        DESCRIPTION
            "This object indicates the status of this entry."
        ::= { swCpuAclIpv6MaskEntry 7 }

-- -----------------------------------------------------------------------------
--swCpuACLMaskDelAllState
-- -----------------------------------------------------------------------------
    swCpuACLMaskDelAllState OBJECT-TYPE
        SYNTAX      INTEGER{
    		none(1),
    		start(2)
    		}
        MAX-ACCESS  read-write
        STATUS      current
        DESCRIPTION
            "Used to delete all software ACL masks."
        ::= { swCpuAclMaskMgmt 5 }

-- -----------------------------------------------------------------------------
-- swCpuAclEtherRuleTable
-- -----------------------------------------------------------------------------
    swCpuAclEtherRuleTable OBJECT-TYPE
        SYNTAX  SEQUENCE OF SwCpuAclEtherRuleEntry
        MAX-ACCESS  not-accessible
        STATUS  current
        DESCRIPTION
            "This table contains Ethernet software ACL rule information."
        ::= { swCpuAclRuleMgmt 1 }

    swCpuAclEtherRuleEntry OBJECT-TYPE
        SYNTAX  SwCpuAclEtherRuleEntry
        MAX-ACCESS  not-accessible
        STATUS  current
        DESCRIPTION
            "A list of information about the software ACL rule of the layer 2 part of each packet."
        INDEX  { swCpuAclEtherRuleProfileID,swCpuAclEtherRuleAccessID }
        ::= { swCpuAclEtherRuleTable 1 }

    SwCpuAclEtherRuleEntry ::=
        SEQUENCE {
            swCpuAclEtherRuleProfileID
                INTEGER,
            swCpuAclEtherRuleAccessID
                INTEGER,
            swCpuAclEtherRuleVlan
                SnmpAdminString,
            swCpuAclEtherRuleSrcMacAddress
                MacAddress,
            swCpuAclEtherRuleDstMacAddress
                MacAddress,
--            swCpuAclEtherRule8021P
--                INTEGER,
            swCpuAclEtherRuleEtherType
                OCTET STRING,
            swCpuAclEtherRulePermit
                INTEGER,
            swCpuAclEtherRulePort
              	PortList,  
            swCpuAclEtherRuleRowStatus
                RowStatus,
            swCpuAclEtherRuleTimeRangeName
    						SnmpAdminString,
    				swCpuAclEtherRuleMatchVID
                INTEGER                                                                     
        }

    swCpuAclEtherRuleProfileID OBJECT-TYPE
        SYNTAX  INTEGER (1..255)
        MAX-ACCESS  read-only
        STATUS  current
        DESCRIPTION
            "The ID of the software ACL mask entry, which is unique to the mask list. The maximum value of this object depends on the device."
        ::= { swCpuAclEtherRuleEntry 1 }

    swCpuAclEtherRuleAccessID OBJECT-TYPE
        SYNTAX  INTEGER (1..65535)
        MAX-ACCESS  read-only
        STATUS  current
        DESCRIPTION
            "The ID of the software ACL rule entry as it relates to swCpuAclEtherRuleProfileID."
        ::= { swCpuAclEtherRuleEntry 2 }

    swCpuAclEtherRuleVlan OBJECT-TYPE
        SYNTAX  SnmpAdminString (SIZE (1..32))
        MAX-ACCESS  read-create
        STATUS  current
        DESCRIPTION
            "Specifies that the access rule will only apply to this VLAN."
        ::= { swCpuAclEtherRuleEntry 3 }

    swCpuAclEtherRuleSrcMacAddress OBJECT-TYPE
        SYNTAX  MacAddress
        MAX-ACCESS  read-create
        STATUS  current
        DESCRIPTION
            "Specifies that the access rule will only apply to the packets with
             this source MAC address."
        ::= { swCpuAclEtherRuleEntry 4 }

    swCpuAclEtherRuleDstMacAddress OBJECT-TYPE
        SYNTAX  MacAddress
        MAX-ACCESS  read-create
        STATUS  current
        DESCRIPTION
            "Specifies that the access rule will only apply to the packets               with this destination MAC address."
        ::= { swCpuAclEtherRuleEntry 5 }

 --   swCpuAclEtherRule8021P OBJECT-TYPE
 --      SYNTAX  INTEGER(0..7)
 --       MAX-ACCESS  read-create
 --       STATUS  current
 --       DESCRIPTION
 --           "Specifies that the access rule will apply only to packets with
 --             this 802.1p priority value."
 --       ::= { swCpuAclEtherRuleEntry 6 }

    swCpuAclEtherRuleEtherType OBJECT-TYPE
        SYNTAX  OCTET STRING (SIZE (2))
        MAX-ACCESS  read-create
        STATUS  current
        DESCRIPTION
            "Specifies that the access rule will only apply to packets with this
             802.1Q Ethernet type value in the packet header."
        ::= { swCpuAclEtherRuleEntry 7 }

    swCpuAclEtherRulePermit OBJECT-TYPE
        SYNTAX  INTEGER {
               deny(1),
               permit(2)
               }
        MAX-ACCESS  read-create
        STATUS  current
        DESCRIPTION
            "This object indicates if the result of the packet examination is to 'permit' or 'deny'.
             The default is 'permit'.
             permit - Specifies that packets that match the access profile are
                      permitted to be forwarded by the switch.
             deny - Specifies that packets that match the access profile
                    are not permitted to be forwarded by the switch and will be filtered."
        ::= { swCpuAclEtherRuleEntry 8 }

     swCpuAclEtherRulePort OBJECT-TYPE
        SYNTAX  PortList
        MAX-ACCESS  read-create
        STATUS  current
        DESCRIPTION
            "Specifies that the access rule will apply to only to port(s)."
        ::= { swCpuAclEtherRuleEntry 9 }
        
    swCpuAclEtherRuleRowStatus OBJECT-TYPE
        SYNTAX  RowStatus
        MAX-ACCESS  read-create
        STATUS  current
        DESCRIPTION
            "This object indicates the status of this entry."
        ::= { swCpuAclEtherRuleEntry 10 }

    swCpuAclEtherRuleTimeRangeName OBJECT-TYPE
    		SYNTAX      SnmpAdminString (SIZE (0..32))
    		MAX-ACCESS  read-write
    		STATUS      current
    		DESCRIPTION
        	""    
    	::= { swCpuAclEtherRuleEntry 11 }   
    	
    swCpuAclEtherRuleMatchVID OBJECT-TYPE
       SYNTAX  INTEGER (0..4094)
       MAX-ACCESS  read-create
       STATUS  current
       DESCRIPTION
           "Specifies that the access rule will apply only to packets with
            this VLAN ID."
       ::= { swCpuAclEtherRuleEntry 12 }


-- -----------------------------------------------------------------------------
-- swCpuAclIpRuleTable
-- -----------------------------------------------------------------------------
    swCpuAclIpRuleTable OBJECT-TYPE
        SYNTAX  SEQUENCE OF SwCpuAclIpRuleEntry
        MAX-ACCESS  not-accessible
        STATUS  current
        DESCRIPTION
            "This table contains IPv4 software ACL rule information."
        ::= { swCpuAclRuleMgmt 2 }

    swCpuAclIpRuleEntry OBJECT-TYPE
        SYNTAX  SwCpuAclIpRuleEntry
        MAX-ACCESS  not-accessible
        STATUS  current
        DESCRIPTION
            "A list of information about this software ACL rule."
        INDEX  { swCpuAclIpRuleProfileID , swCpuAclIpRuleAccessID }
        ::= { swCpuAclIpRuleTable 1 }

    SwCpuAclIpRuleEntry ::=
        SEQUENCE {
            swCpuAclIpRuleProfileID
                INTEGER,
            swCpuAclIpRuleAccessID
                INTEGER,
            swCpuAclIpRuleVlan
                SnmpAdminString,
            swCpuAclIpRuleSrcIpaddress
            	IpAddress,
            swCpuAclIpRuleDstIpaddress
            	IpAddress,
            swCpuAclIpRuleDscp
            	INTEGER,
            swCpuAclIpRuleProtocol
                INTEGER,
            swCpuAclIpRuleType
            	INTEGER,
            swCpuAclIpRuleCode
            	INTEGER,
            swCpuAclIpRuleSrcPort
            	INTEGER,
            swCpuAclIpRuleDstPort
            	INTEGER,
            swCpuAclIpRuleFlagBits
            	INTEGER,
            swCpuAclIpRuleProtoID
            	INTEGER,
            swCpuAclIpRuleUserMask
            	OCTET STRING,
            swCpuAclIpRulePermit
            	INTEGER,
            swCpuAclIpRulePort
            	PortList,
            swCpuAclIpRuleRowStatus
                RowStatus,
            swCpuAclIpRuleTimeRangeName
            	SnmpAdminString,
            swCpuAclIpRuleMatchVID
              INTEGER                                                         

        }

    swCpuAclIpRuleProfileID OBJECT-TYPE
        SYNTAX  INTEGER (1..255)
        MAX-ACCESS  read-only
        STATUS  current
        DESCRIPTION
            "The ID of the software ACL mask entry, which is unique to the mask list. The maximum value of this object depends on the device."
        ::= { swCpuAclIpRuleEntry 1 }

    swCpuAclIpRuleAccessID OBJECT-TYPE
        SYNTAX  INTEGER (1..65535)
        MAX-ACCESS  read-only	--read-create
        STATUS  current
        DESCRIPTION
            "The ID of the software ACL for the IPv4 rule entry."
        ::= { swCpuAclIpRuleEntry 2 }

    swCpuAclIpRuleVlan OBJECT-TYPE
        SYNTAX  SnmpAdminString (SIZE (1..32))
        MAX-ACCESS  read-create
        STATUS  current
        DESCRIPTION
            "Specifies that the access rule will apply only to this VLAN."
        ::= { swCpuAclIpRuleEntry 3 }

    swCpuAclIpRuleSrcIpaddress OBJECT-TYPE
        SYNTAX  IpAddress
        MAX-ACCESS  read-create
        STATUS  current
        DESCRIPTION
            "Specifies an IP source address."
        ::= { swCpuAclIpRuleEntry 4 }

    swCpuAclIpRuleDstIpaddress OBJECT-TYPE
        SYNTAX  IpAddress
        MAX-ACCESS  read-create
        STATUS  current
        DESCRIPTION
            "Specifies an IP destination address."
        ::= { swCpuAclIpRuleEntry 5 }

    swCpuAclIpRuleDscp OBJECT-TYPE
        SYNTAX  INTEGER(0..63)
        MAX-ACCESS  read-create
        STATUS  current
        DESCRIPTION
            "Specifies the value of DSCP, the value can be configured 0 to 63"
        ::= { swCpuAclIpRuleEntry 6 }

    swCpuAclIpRuleProtocol OBJECT-TYPE
        SYNTAX  INTEGER {
               none(1),
               icmp(2),
               igmp(3),
               tcp(4),
               udp(5),
               protocolId(6)
               }
        MAX-ACCESS  read-only
        STATUS  current
        DESCRIPTION
            "Specifies the IP protocol which has been configured in swCpuAclIpEntry."
        ::= { swCpuAclIpRuleEntry 7 }

    swCpuAclIpRuleType OBJECT-TYPE
        SYNTAX  INTEGER(0..255)
        MAX-ACCESS  read-create
        STATUS  current
        DESCRIPTION
            "Specifies the rule applies to the value of  ICMP type traffic."
        ::= { swCpuAclIpRuleEntry 8 }

    swCpuAclIpRuleCode OBJECT-TYPE
        SYNTAX  INTEGER(0..255)
        MAX-ACCESS  read-create
        STATUS  current
        DESCRIPTION
            "Specifies the rule applies to the value of ICMP code traffic."
        ::= { swCpuAclIpRuleEntry 9 }

    swCpuAclIpRuleSrcPort OBJECT-TYPE
        SYNTAX  INTEGER(0..65535)
        MAX-ACCESS  read-create
        STATUS  current
        DESCRIPTION
            "Specifies the rule applies the range of TCP/UDP source port"
        ::= { swCpuAclIpRuleEntry 10 }

    swCpuAclIpRuleDstPort OBJECT-TYPE
        SYNTAX  INTEGER(0..65535)
        MAX-ACCESS  read-create
        STATUS  current
        DESCRIPTION
            "Specifies the range of TCP/UDP destination port."
        ::= { swCpuAclIpRuleEntry 11 }

    swCpuAclIpRuleFlagBits OBJECT-TYPE
        SYNTAX  INTEGER(0..63)
        MAX-ACCESS  read-create
        STATUS  current
        DESCRIPTION
            "A value which indicates the set of TCP flags that this
            entity may potentially offer. The value is a sum of flag bits.
            This sum initially takes the value zero. Then, for each flag, L
            is added in the range 1 through 6, for which this node performs
            transactions where, 2^(L - 1) is added to the sum.
            Note that values should be calculated accordingly:

                 Flag      functionality
                   6        urg bit
                   5        ack bit
                   4        psh bit
                   3        rst bit
                   2		 syn bit
                   1 		 fin bit
		For example, it you want to enable urg bit and ack bit, you
		should set the value 48{2^(5-1) + 2^(6-1)}."
        ::= { swCpuAclIpRuleEntry 12 }

    swCpuAclIpRuleProtoID OBJECT-TYPE
        SYNTAX  INTEGER(0..255)
        MAX-ACCESS  read-create
        STATUS  current
        DESCRIPTION
            "Specifies the rule applies to the value of IP protocol ID traffic"
        ::= { swCpuAclIpRuleEntry 13 }

    swCpuAclIpRuleUserMask OBJECT-TYPE
        SYNTAX  OCTET STRING (SIZE(4))
        MAX-ACCESS  read-create
        STATUS  current
        DESCRIPTION
            "Specifies that the rule applies to the IP protocol ID and the range of
             options behind the IP header."
        ::= { swCpuAclIpRuleEntry 14 }

    swCpuAclIpRulePermit OBJECT-TYPE
        SYNTAX  INTEGER {
               deny(1),
               permit(2)
               }
        MAX-ACCESS  read-create
        STATUS  current
        DESCRIPTION
            "This object indicates if the result of the packet examination is to 'permit' or 'deny'.
             The default is 'permit'.
             permit - Specifies that packets that match the access profile are
                      permitted to be forwarded by the switch.
             deny - Specifies that packets that match the access profile
                    are not permitted to be forwarded by the switch and will be filtered."
        ::= { swCpuAclIpRuleEntry 15 }

     swCpuAclIpRulePort OBJECT-TYPE
        SYNTAX  PortList
        MAX-ACCESS  read-create
        STATUS  current
        DESCRIPTION
            "Specifies that the access rule will apply to only to port(s)."
        ::= { swCpuAclIpRuleEntry 16 }
        
    swCpuAclIpRuleRowStatus OBJECT-TYPE
        SYNTAX  RowStatus
        MAX-ACCESS  read-create
        STATUS  current
        DESCRIPTION
            "This object indicates the status of this entry."
        ::= { swCpuAclIpRuleEntry 17 }

    swCpuAclIpRuleTimeRangeName OBJECT-TYPE
    		SYNTAX      SnmpAdminString (SIZE (0..32))
    		MAX-ACCESS  read-write
    		STATUS      current
    		DESCRIPTION
        	""    
    	::= { swCpuAclIpRuleEntry 18 } 
    	
    swCpuAclIpRuleMatchVID OBJECT-TYPE
       SYNTAX  INTEGER (0..4094)
       MAX-ACCESS  read-create
       STATUS  current
       DESCRIPTION
          "Specifies that the access rule will apply only to packets with
            this VLAN ID."
       ::= { swCpuAclIpRuleEntry 19 }               


-- -----------------------------------------------------------------------------
-- swCpuAclPktContRuleTable
-- -----------------------------------------------------------------------------
    swCpuAclPktContRuleTable OBJECT-TYPE
        SYNTAX  SEQUENCE OF SwCpuAclPktContRuleEntry
        MAX-ACCESS  not-accessible
        STATUS  current
        DESCRIPTION
	    "This table contains user-defined software ACL rule information."
        ::= { swCpuAclRuleMgmt 3 }

    swCpuAclPktContRuleEntry OBJECT-TYPE
        SYNTAX  SwCpuAclPktContRuleEntry
        MAX-ACCESS  not-accessible
        STATUS  current
        DESCRIPTION
	    "A list of information about the software ACL rule of the user-defined part of each packet."
        INDEX  { swCpuAclPktContRuleProfileID,swCpuAclPktContRuleAccessID }
        ::= { swCpuAclPktContRuleTable 1 }

    SwCpuAclPktContRuleEntry ::=
        SEQUENCE {
            swCpuAclPktContRuleProfileID
                INTEGER,
            swCpuAclPktContRuleAccessID
                INTEGER,
            swCpuAclPktContRuleOffset0to15
                OCTET STRING,
            swCpuAclPktContRuleOffset16to31
                OCTET STRING,
            swCpuAclPktContRuleOffset32to47
                OCTET STRING,
            swCpuAclPktContRuleOffset48to63
                OCTET STRING,
            swCpuAclPktContRuleOffset64to79
                OCTET STRING,
            swCpuAclPktContRulePermit
                INTEGER,
            swCpuAclPktContRulePort
                PortList, 
            swCpuAclPktContRuleRowStatus
                RowStatus,
            swCpuAclPktContRuleTimeRangeName
    		SnmpAdminString                                                         
               
        }
    swCpuAclPktContRuleProfileID OBJECT-TYPE
        SYNTAX  INTEGER (1..255)
        MAX-ACCESS  read-only
        STATUS  current
        DESCRIPTION
	    "The ID of the software ACL mask entry, which is unique to the mask list. The maximum value of this object depends on the device."
        ::= { swCpuAclPktContRuleEntry 1 }

    swCpuAclPktContRuleAccessID OBJECT-TYPE
        SYNTAX  INTEGER (1..65535)
        MAX-ACCESS  read-only
        STATUS  current
        DESCRIPTION
	    "The ID of the software ACL rule entry related to swCpuAclPktContRuleProfileID."
        ::= { swCpuAclPktContRuleEntry 2 }

    swCpuAclPktContRuleOffset0to15 OBJECT-TYPE
        SYNTAX  OCTET STRING (SIZE(16))
        MAX-ACCESS  read-create
        STATUS  current
        DESCRIPTION
            "Specifies that the rule applies to the user-defined packet."
        ::= { swCpuAclPktContRuleEntry 3 }

    swCpuAclPktContRuleOffset16to31 OBJECT-TYPE
        SYNTAX  OCTET STRING (SIZE(16))
        MAX-ACCESS  read-create
        STATUS  current
        DESCRIPTION
            "Specifies that the rule applies to the user-defined packet."
        ::= { swCpuAclPktContRuleEntry 4 }

    swCpuAclPktContRuleOffset32to47 OBJECT-TYPE
        SYNTAX  OCTET STRING (SIZE(16))
        MAX-ACCESS  read-create
        STATUS  current
        DESCRIPTION
            "Specifies that the rule applies to the user-defined packet."
        ::= { swCpuAclPktContRuleEntry 5 }

    swCpuAclPktContRuleOffset48to63 OBJECT-TYPE
        SYNTAX  OCTET STRING (SIZE(16))
        MAX-ACCESS  read-create
        STATUS  current
        DESCRIPTION
            "Specifies that the rule applies to the user-defined packet."
        ::= { swCpuAclPktContRuleEntry 6 }

    swCpuAclPktContRuleOffset64to79 OBJECT-TYPE
        SYNTAX  OCTET STRING (SIZE(16))
        MAX-ACCESS  read-create
        STATUS  current
        DESCRIPTION
            "Specifies that the rule applies to the user-defined packet."
        ::= { swCpuAclPktContRuleEntry 7 }

    swCpuAclPktContRulePermit OBJECT-TYPE
        SYNTAX  INTEGER {
               deny(1),
               permit(2)
               }
        MAX-ACCESS  read-create
        STATUS  current
        DESCRIPTION
	    "This object indicates if the result of the packet examination is to 'permit' or 'deny'.
	     The default is 'permit'.
             permit - Specifies that packets that match the access profile are
                      permitted to be forwarded by the switch.
             deny - Specifies that packets that match the access profile
                    are not permitted to be forwarded by the switch and will be filtered."
        ::= { swCpuAclPktContRuleEntry 8 }

    swCpuAclPktContRulePort OBJECT-TYPE
        SYNTAX  PortList
        MAX-ACCESS  read-create
        STATUS  current
        DESCRIPTION
            "Specifies that the access rule will apply to only to port(s)."
       ::= { swCpuAclPktContRuleEntry 9 }
       
    swCpuAclPktContRuleRowStatus OBJECT-TYPE
        SYNTAX  RowStatus
        MAX-ACCESS  read-create
        STATUS  current
        DESCRIPTION
            "This object indicates the status of this entry."
        ::= { swCpuAclPktContRuleEntry 10 }

     swCpuAclPktContRuleTimeRangeName OBJECT-TYPE
    		SYNTAX      SnmpAdminString (SIZE (0..32))
    		MAX-ACCESS  read-write
    		STATUS      current
    		DESCRIPTION
        	""    
    	::= { swCpuAclPktContRuleEntry 11 }        


-- -----------------------------------------------------------------------------
-- swCpuAclIpv6RuleTable
-- -----------------------------------------------------------------------------
    swCpuAclIpv6RuleTable OBJECT-TYPE
        SYNTAX  SEQUENCE OF SwCpuAclIpv6RuleEntry
        MAX-ACCESS  not-accessible
        STATUS  current
        DESCRIPTION
            "This table contains user-defined ACL rule information."
        ::= { swCpuAclRuleMgmt 4 }

    swCpuAclIpv6RuleEntry OBJECT-TYPE
        SYNTAX  SwCpuAclIpv6RuleEntry
        MAX-ACCESS  not-accessible
        STATUS  current
        DESCRIPTION
            "A list of information about the ACL rule of the user-defined part of each packet."
        INDEX  { swCpuAclIpv6RuleProfileID,swCpuAclIpv6RuleAccessID }
        ::= { swCpuAclIpv6RuleTable 1 }

    SwCpuAclIpv6RuleEntry ::=
        SEQUENCE {
            swCpuAclIpv6RuleProfileID
                INTEGER,
            swCpuAclIpv6RuleAccessID
                INTEGER,
            swCpuAclIpv6RuleClass
                INTEGER,
            swCpuAclIpv6RuleFlowlabel
                OCTET STRING,
            swCpuAclIpv6RuleSrcIpv6Addr
                Ipv6Address,
            swCpuAclIpv6RuleDstIpv6Addr
                Ipv6Address,
            swCpuAclIpv6RulePermit
                INTEGER,
            swCpuAclIpv6RuleRowStatus
                RowStatus,
            swCpuAclIpv6RulePort
                PortList,
            swCpuAclIpv6RuleTimeRangeName
                SnmpAdminString                    
        }
    swCpuAclIpv6RuleProfileID OBJECT-TYPE
        SYNTAX  INTEGER (1..255)
        MAX-ACCESS  read-only
        STATUS  current
        DESCRIPTION
            "The ID of the ACL mask entry. This is unique in the mask list. The maximum value of this object depends on the device."
        ::= { swCpuAclIpv6RuleEntry 1 }

    swCpuAclIpv6RuleAccessID OBJECT-TYPE
        SYNTAX  INTEGER (1..65535)
        MAX-ACCESS  read-only
        STATUS  current
        DESCRIPTION
            "The ID of the ACL rule entry in relation to swCpuAclIpv6RuleProfileID."
        ::= { swCpuAclIpv6RuleEntry 2 }

    swCpuAclIpv6RuleClass OBJECT-TYPE
        SYNTAX  INTEGER (0..255)
        MAX-ACCESS  read-create
        STATUS  current
        DESCRIPTION
            "Specifies that the rule applies to the IPv6 class field."
        ::= { swCpuAclIpv6RuleEntry 3 }

    swCpuAclIpv6RuleFlowlabel OBJECT-TYPE
        SYNTAX  OCTET STRING (SIZE(4))
        MAX-ACCESS  read-create
        STATUS  current
        DESCRIPTION
            "Specifies that the rule applies to the IPv6 flowlabel field."
        ::= { swCpuAclIpv6RuleEntry 4 }

    swCpuAclIpv6RuleSrcIpv6Addr OBJECT-TYPE
        SYNTAX  Ipv6Address
        MAX-ACCESS  read-create
        STATUS  current
        DESCRIPTION
            "Specifies that the rule applies to the source IPv6 address.
            This should be a 16 byte octet string."
        ::= { swCpuAclIpv6RuleEntry 5 }

    swCpuAclIpv6RuleDstIpv6Addr OBJECT-TYPE
        SYNTAX  Ipv6Address
        MAX-ACCESS  read-create
        STATUS  current
        DESCRIPTION
            "Specifies that the rule applies to the destination IPv6 address.
            This should be a 16 byte octet string."
        ::= { swCpuAclIpv6RuleEntry 6 }

    swCpuAclIpv6RulePermit OBJECT-TYPE
        SYNTAX  INTEGER {
               deny(1),
               permit(2)
               }
        MAX-ACCESS  read-create
        STATUS  current
        DESCRIPTION
            "This object indicates if the result of the examination is to 'permit' or 'deny'.
             The default is 'permit' (1).
             permit - Specifies that packets that match the access profile are
                      permitted to be forwarded by the switch.
             deny - Specifies that packets that match the access profile
                    are not permitted to be forwarded by the switch and will be filtered."
        ::= { swCpuAclIpv6RuleEntry 7 }

    swCpuAclIpv6RuleRowStatus OBJECT-TYPE
        SYNTAX  RowStatus
        MAX-ACCESS  read-create
        STATUS  current
        DESCRIPTION
            "This object indicates the status of this entry."
        ::= { swCpuAclIpv6RuleEntry 8 }

    swCpuAclIpv6RulePort OBJECT-TYPE
        SYNTAX  PortList
        MAX-ACCESS  read-create
        STATUS  current
        DESCRIPTION
            "Specifies that the access rule will apply only to port(s)."
       ::= { swCpuAclIpv6RuleEntry 9 }

     swCpuAclIpv6RuleTimeRangeName OBJECT-TYPE
    		SYNTAX      SnmpAdminString (SIZE (0..32))
    		MAX-ACCESS  read-write
    		STATUS      current
    		DESCRIPTION
        	""    
    	::= { swCpuAclIpv6RuleEntry 10 }        

    	
-- -----------------------------------------------------------------------------
-- swAclMeteringMgmt
-- -----------------------------------------------------------------------------
	swAclMeterTable OBJECT-TYPE
		SYNTAX      SEQUENCE OF SwAclMeterEntry
		MAX-ACCESS  not-accessible
		STATUS      current
		DESCRIPTION
		   "This table is used to configure the flow-based metering function.
		    The access rule must first be created before the parameters of this
		    function can be applied. Users may set the preferred bandwidth for
		    this rule, in Kbps; Once the bandwidth has been exceeded, overflow
		    packets will be either dropped or set for a drop precedence,
		    depending on user configuration."
		::= { swAclMeteringMgmt 1 }

	swAclMeterEntry OBJECT-TYPE
		SYNTAX      SwAclMeterEntry
		MAX-ACCESS  not-accessible
		STATUS      current
		DESCRIPTION
		   "This entry displays parameters and configurations set for the flow
		    metering function."
		INDEX { swAclMeterProfileID, swAclMeterAccessID}
		::= { swAclMeterTable 1 }

	SwAclMeterEntry ::=
	   SEQUENCE {
	       swAclMeterProfileID
	           INTEGER,
	       swAclMeterAccessID
	           INTEGER,
--	       swAclMeterRate
--	           INTEGER,
--	       swAclMeterActionForRateExceed
--	           INTEGER,
--               swAclMeterRemarkDscp  
--                   INTEGER, 	           
--               swAclMeterBurstSize  
--               	   INTEGER,                             
               swAclMeterMode
               	   INTEGER,
               swAclMeterTrtcmCir
                   INTEGER,
               swAclMeterTrtcmCbs
                   INTEGER,
	       swAclMeterTrtcmPir
                   INTEGER,
               swAclMeterTrtcmPbs
               	   INTEGER,
--               swAclMeterTrtcmColorMode
--                   INTEGER,
               swAclMeterTrtcmConformState
                   INTEGER,
	       swAclMeterTrtcmConformReplaceDscp
                   INTEGER,
               swAclMeterTrtcmConformCounterState
               	   INTEGER,
 	       swAclMeterTrtcmExceedState
                   INTEGER,
	       swAclMeterTrtcmExceedReplaceDscp
                   INTEGER,
               swAclMeterTrtcmExceedCounterState
               	   INTEGER,
               swAclMeterTrtcmViolateState
                   INTEGER,
               swAclMeterTrtcmViolateReplaceDscp
                   INTEGER,
	       swAclMeterTrtcmViolateCounterState
                   INTEGER,
 	       swAclMeterSrtcmCir
                   INTEGER,
               swAclMeterSrtcmCbs
               	   INTEGER,
               swAclMeterSrtcmEbs
               	   INTEGER,
--               swAclMeterSrtcmColorMode
--                   INTEGER,
               swAclMeterSrtcmConformState
                   INTEGER,
	       swAclMeterSrtcmConformReplaceDscp
                   INTEGER,
               swAclMeterSrtcmConformCounterState
               	   INTEGER,
 	       swAclMeterSrtcmExceedState
                   INTEGER,
	       swAclMeterSrtcmExceedReplaceDscp
                   INTEGER,
               swAclMeterSrtcmExceedCounterState
               	   INTEGER,
               swAclMeterSrtcmViolateState
                   INTEGER,
               swAclMeterSrtcmViolateReplaceDscp
                   INTEGER,
	       swAclMeterSrtcmViolateCounterState
                   INTEGER,
               swAclMeterRowStatus
               	   RowStatus
	   }

	swAclMeterProfileID OBJECT-TYPE
		SYNTAX      INTEGER
		MAX-ACCESS  read-only
		STATUS      current
		DESCRIPTION
		   "The ID of the ACL mask entry is unique in the mask list. The maximum value of this object depends on the device."
		::= { swAclMeterEntry 1 }

	swAclMeterAccessID OBJECT-TYPE
		SYNTAX      INTEGER(1..65535)
		MAX-ACCESS  read-only
		STATUS      current
		DESCRIPTION
		   "The ID of the ACL rule entry as related to the swAclMeterProfileID."
		::= { swAclMeterEntry 2 }

--	swAclMeterRate OBJECT-TYPE
--		SYNTAX INTEGER
--		MAX-ACCESS  read-create
--		STATUS      current
--		DESCRIPTION
--		   "Specify the committed bandwidth in Kbps for the flow.
--		    NOTE:
--		    	1. Specifying 0 will disable this flow meter setting.
--		    	2. Users must set the swAclMeterActionForRateExceed object to activate this entry."
--		::= { swAclMeterEntry 3 }

--	swAclMeterActionForRateExceed OBJECT-TYPE
--		SYNTAX INTEGER {
--		other(1),
--               	drop-packet(2),
--               	set-drop-precedence(3),
--               	remark-dscp(4)
--               }
--		MAX-ACCESS  read-create
--		STATUS      current
--		DESCRIPTION
--		   "Specifies the action to take for those packets exceeding the committed rate.
--		    NOTE:
--		    	Users must also set the swAclMeterRate to activate this entry."
--		::= { swAclMeterEntry 4 } 

--        swAclMeterRemarkDscp OBJECT-TYPE
--            SYNTAX  INTEGER (0..63)
--            MAX-ACCESS  read-create
--            STATUS  current
--            DESCRIPTION
--                "Mark the packet with a specified DSCP. 
--                 It can be set when swAclMeterActionForRateExceed sets remark-dscp(3)."
--            ::= { swAclMeterEntry 5 } 
            
--       swAclMeterBurstSize OBJECT-TYPE
--            SYNTAX  INTEGER
--            MAX-ACCESS  read-create
--            STATUS  current
--            DESCRIPTION
--                "This specifies the burst size for the single rate two color mode.
--                 The unit is Kbytes. That is to say, 1 means 1kbytes.
--                 The set value range is 0..n, the value n is determined by project, 
--                 the value of 0 means to delete this flow_meter setting."
--            ::= { swAclMeterEntry 6 } 
      
        swAclMeterMode OBJECT-TYPE
            SYNTAX  INTEGER {
                   other(1),
                   tr-tcm(2),
                   sr-tcm(3)
                   }
            MAX-ACCESS  read-create
            STATUS  current
            DESCRIPTION
                "tr-tcm: two rate three color mode;
                 sr-tcm: single rate three color mode.
                "
            ::= { swAclMeterEntry 7 }

        swAclMeterTrtcmCir OBJECT-TYPE
            SYNTAX  INTEGER (1..156249)
            MAX-ACCESS  read-create
            STATUS  current
            DESCRIPTION
                "Specifies the 'committed information rate' of 'two rate three color mode'.
                 The unit is Kbps."
            ::= { swAclMeterEntry 8 }

        swAclMeterTrtcmCbs OBJECT-TYPE
            SYNTAX  INTEGER (1..16384)
            MAX-ACCESS  read-create
            STATUS  current
            DESCRIPTION
                "Specifies the 'committed burst size' of 'two rate three color mode'.
                 1.	The unit is Kbytes. That is to say, 1 means 1Kbytes.
	         2. This parameter is an optional parameter. The default value is 4*1024.
	         3. The max set value is 16*1024.
	        "
            ::= { swAclMeterEntry 9 }

        swAclMeterTrtcmPir OBJECT-TYPE
            SYNTAX  INTEGER (1..156249)
            MAX-ACCESS  read-create
            STATUS  current
            DESCRIPTION
                "Specifies the 'Peak Information Rate' of 'two rate three color mode'.
                 The unit is Kbps."
            ::= { swAclMeterEntry 10 }

        swAclMeterTrtcmPbs OBJECT-TYPE
            SYNTAX  INTEGER (1..16384)
            MAX-ACCESS  read-create
            STATUS  current
            DESCRIPTION
                "Specifies the 'peak burst size' of 'two rate three color mode'.
                 1.	The unit is Kbytes. That is to say, 1 means 1kbytes.
	         2. This parameter is an optional parameter. The default value is 4*1024.
	         3. The max set value is 16*1024.
	        "
            ::= { swAclMeterEntry 11 }

--        swAclMeterTrtcmColorMode OBJECT-TYPE
--            SYNTAX  INTEGER {
--                   color-blind(1),
--                   color-aware(2)
--                   }
--            MAX-ACCESS  read-create
--            STATUS  current
--            DESCRIPTION
--                "Specifies the meter mode.
--                 The default is color-blind mode. The final color of the packet is determined 
--                 by the initial color of packet and the metering result."
--            ::= { swAclMeterEntry 12 } 
                                                            
        swAclMeterTrtcmConformState OBJECT-TYPE
            SYNTAX  INTEGER {
                   other(1),
                   permit(2),
                   replace-dscp(3)
                   }
            MAX-ACCESS  read-create
            STATUS  current
            DESCRIPTION
                "Specifies the action state when packet is in 'green color'.
                 permit: permit the packet.
                 replace-dscp:  change the DSCP value of packet.
                "
            ::= { swAclMeterEntry 13 }

        swAclMeterTrtcmConformReplaceDscp OBJECT-TYPE
            SYNTAX  INTEGER (0..63)
            MAX-ACCESS  read-create
            STATUS  current
            DESCRIPTION
                "Specifies the DSCP value of the packet when the packet is in 'green color'."
            ::= { swAclMeterEntry 14 }

        swAclMeterTrtcmConformCounterState OBJECT-TYPE
            SYNTAX  INTEGER {
                   enabled(1),
                   disabled(2)
                   }
            MAX-ACCESS  read-create
            STATUS  current
            DESCRIPTION
                "Specifies the counter state when the packet is in 'green color'.
	         1.	This is optional. The default is 'disable'.
	         2.	The resource may be limited so that the counter can not be turned on. The limitation is project dependent.
	         3.	counter will be cleared when the function is disabled.
	        "
            ::= { swAclMeterEntry 15 }

        swAclMeterTrtcmExceedState OBJECT-TYPE
            SYNTAX  INTEGER {
                   other(1),
                   permit(2),
                   replace-dscp(3),
                   drop(4)
                   }
            MAX-ACCESS  read-create
            STATUS  current
            DESCRIPTION
                "Specifies the action state when packet is in 'yellow color'.
                 permit: permit the packet.
                 replace-dscp: change the DSCP value of the packet.
                 drop: drop the packet.
                "
            ::= { swAclMeterEntry 16 }

        swAclMeterTrtcmExceedReplaceDscp OBJECT-TYPE
            SYNTAX  INTEGER (0..63)
            MAX-ACCESS  read-create
            STATUS  current
            DESCRIPTION
                "Specifies the DSCP value of packet when packet is in 'yellow color'."
            ::= { swAclMeterEntry 17 }

        swAclMeterTrtcmExceedCounterState OBJECT-TYPE
            SYNTAX  INTEGER {
                   enabled(1),
                   disabled(2)
                   }
            MAX-ACCESS  read-create
            STATUS  current
            DESCRIPTION
                "Specifies the counter state when packet is in 'yellow color'.
	         1.	This is optional. The default is 'disable'.
	         2.	The resource may be limited so that the counter can not be turned on. The limitation is project dependent.
	         3.	counter will be cleared when the function is disabled.
	        "
            ::= { swAclMeterEntry 18 }

        swAclMeterTrtcmViolateState OBJECT-TYPE
            SYNTAX  INTEGER {
                   other(1),
                   permit(2),
                   replace-dscp(3),
                   drop(4)
                   }
            MAX-ACCESS  read-create
            STATUS  current
            DESCRIPTION
                "Specifies the action state when packet is in 'red color'.
                 permit: permit the packet.
                 replace-dscp: change the DSCP value of packet.
                 drop: drop the packet.
                "
            ::= { swAclMeterEntry 19 }

        swAclMeterTrtcmViolateReplaceDscp OBJECT-TYPE
            SYNTAX  INTEGER (0..63)
            MAX-ACCESS  read-create
            STATUS  current
            DESCRIPTION
                "Specifies the DSCP value of the packet when packet is in 'red color'."
            ::= { swAclMeterEntry 20 }

        swAclMeterTrtcmViolateCounterState OBJECT-TYPE
            SYNTAX  INTEGER {
                   enabled(1),
                   disabled(2)
                   }
            MAX-ACCESS  read-create
            STATUS  current
            DESCRIPTION
                "Specifies the counter state when packet is in 'red color'.
	         1.	This is optional. The default is 'disable'.
	         2.	The resource may be limited so that the counter can not be turned on. The limitation is project dependent.
	         3.	counter will be cleared when the function is disabled.
	        "
            ::= { swAclMeterEntry 21 }

        swAclMeterSrtcmCir OBJECT-TYPE
            SYNTAX  INTEGER (1..156249)
            MAX-ACCESS  read-create
            STATUS  current
            DESCRIPTION
                "Specifies the 'committed information rate' of 'single rate three color mode'.
                 The unit is Kbps."
            ::= { swAclMeterEntry 22 }

        swAclMeterSrtcmCbs OBJECT-TYPE
            SYNTAX  INTEGER (1..16384)
            MAX-ACCESS  read-create
            STATUS  current
            DESCRIPTION
                "Specifies the 'committed burst size' of 'single rate three color mode'.
                 1.	The unit is Kbytes. That is to say, 1 means 1Kbytes.
	         2. The max set value is 16*1024.
	        "
            ::= { swAclMeterEntry 23 }

        swAclMeterSrtcmEbs OBJECT-TYPE
            SYNTAX  INTEGER (1..16384)
            MAX-ACCESS  read-create
            STATUS  current
            DESCRIPTION
                "Specifies the 'Excess burst size' of 'single rate three color mode'.
                 1.	The unit is Kbytes. That is to say, 1 means 1kbytes.
	         2. The max set value is 16*1024.
	        "
            ::= { swAclMeterEntry 24 }
            
--        swAclMeterSrtcmColorMode OBJECT-TYPE
--            SYNTAX  INTEGER {
--                   color-blind(1),
--                   color-aware(2)
--                   }
--            MAX-ACCESS  read-create
--            STATUS  current
--            DESCRIPTION
--                "Specifies the meter mode.
--                 The default is color-blind mode. The final color of packet is determined 
--                 by the initial color of packet and the metering result."
--            ::= { swAclMeterEntry 25 } 
                                                            
        swAclMeterSrtcmConformState OBJECT-TYPE
            SYNTAX  INTEGER {
                   other(1),
                   permit(2),
                   replace-dscp(3)
                   }
            MAX-ACCESS  read-create
            STATUS  current
            DESCRIPTION
                "Specifies the action state when the packet is in 'green color'.
                 permit: permit the packet.
                 replace-dscp: change the DSCP value of packet.
                "
            ::= { swAclMeterEntry 26 }

        swAclMeterSrtcmConformReplaceDscp OBJECT-TYPE
            SYNTAX  INTEGER (0..63)
            MAX-ACCESS  read-create
            STATUS  current
            DESCRIPTION
                "Specifies the DSCP value of the packet when packet is in 'green color'."
            ::= { swAclMeterEntry 27 }

        swAclMeterSrtcmConformCounterState OBJECT-TYPE
            SYNTAX  INTEGER {
                   enabled(1),
                   disabled(2)
                   }
            MAX-ACCESS  read-create
            STATUS  current
            DESCRIPTION
                "Specifies the counter state when the packet is in 'green color'.
	         1.	This is optional. The default is 'disable'.
	         2.	The resource may be limited such that counter can not be turned on. The limitation is project dependent.
	         3.	counter will be cleared when the function is disabled.
	        "
            ::= { swAclMeterEntry 28 }

        swAclMeterSrtcmExceedState OBJECT-TYPE
            SYNTAX  INTEGER {
                   other(1),
                   permit(2),
                   replace-dscp(3),
                   drop(4)
                   }
            MAX-ACCESS  read-create
            STATUS  current
            DESCRIPTION
                "Specifies the action state when the packet is in 'yellow color'.
                 permit: permit the packet.
                 replace-dscp: change the DSCP value of packet.
                 drop: drop the packet.
                "
            ::= { swAclMeterEntry 29 }

        swAclMeterSrtcmExceedReplaceDscp OBJECT-TYPE
            SYNTAX  INTEGER (0..63)
            MAX-ACCESS  read-create
            STATUS  current
            DESCRIPTION
                "Specifies the DSCP value of the packet when packet is in 'yellow color'."
            ::= { swAclMeterEntry 30 }

        swAclMeterSrtcmExceedCounterState OBJECT-TYPE
            SYNTAX  INTEGER {
                   enabled(1),
                   disabled(2)
                   }
            MAX-ACCESS  read-create
            STATUS  current
            DESCRIPTION
                "Specifies the counter state when the packet is in 'yellow color'.
	         1.	This is optional. The default is 'disable'.
	         2.	The resource may be limited such that counter can not be turned on. The limitation is project dependent.
	         3.	counter will be cleared when the function is disabled.
	        "
            ::= { swAclMeterEntry 31 }

        swAclMeterSrtcmViolateState OBJECT-TYPE
            SYNTAX  INTEGER {
                   other(1),
                   permit(2),
                   replace-dscp(3),
                   drop(4)
                   }
            MAX-ACCESS  read-create
            STATUS  current
            DESCRIPTION
                "Specifies the action state when the packet is in 'red color'.
                 permit: permit the packet.
                 replace-dscp: change the DSCP value of packet.
                 drop: drop the packet.
                "
            ::= { swAclMeterEntry 32 }

        swAclMeterSrtcmViolateReplaceDscp OBJECT-TYPE
            SYNTAX  INTEGER (0..63)
            MAX-ACCESS  read-create
            STATUS  current
            DESCRIPTION
                "Specifies the DSCP value of the packet when packet is in 'red color'."
            ::= { swAclMeterEntry 33 }

        swAclMeterSrtcmViolateCounterState OBJECT-TYPE
            SYNTAX  INTEGER {
                   enabled(1),
                   disabled(2)
                   }
            MAX-ACCESS  read-create
            STATUS  current
            DESCRIPTION
                "Specifies the counter state when the packet is in 'red color'.
	         1.	This is optional. The default is 'disable'.
	         2.	The resource may be limited so that the counter can not be turned on. The limitation is project dependent.
	         3.	counter will be cleared when the function is disabled.
	        "
            ::= { swAclMeterEntry 34 }

        swAclMeterRowStatus OBJECT-TYPE
            SYNTAX  RowStatus
            MAX-ACCESS  read-create
            STATUS  current
            DESCRIPTION
                "This object indicates the status of this entry."
            ::= { swAclMeterEntry 35 }

	swAclMeteringNumOfEntryInUse OBJECT-TYPE
		SYNTAX      INTEGER
		MAX-ACCESS  read-only
		STATUS      current
		DESCRIPTION
		   "Used to display total entries of the flow metering."
		::= { swAclMeteringMgmt 2 }

END
