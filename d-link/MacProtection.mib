-- -----------------------------------------------------------------------------
-- MIB NAME : Mac Protection Common mib
-- FILE NAME: MacProtection.mib
-- DATE     : 2016/5/23
-- VERSION  : 1.01
-- PURPOSE  : To construct the MIB structure of MAC Protection
--            for proprietary enterprise
-- -----------------------------------------------------------------------------
-- MODIFICTION HISTORY:
-- -----------------------------------------------------------------------------
-- Version, Date, Author
-- Description:
--  [New Object]
--  [Modification]
-- Notes: (Requested by who and which project)
--
-- Version 1.01, 2016/05/23, Shawn Chen
-- Using uppercase for naming the DEFINITIONS:
-- Modify “Mac-Protection-MIB” to “MAC-PROTECTION-MIB”.
--
-- Version 1.00, 2016/05/04, Shawn Chen
-- This is the first formal version for universal MIB definition.
-- -----------------------------------------------------------------------------

MAC-PROTECTION-MIB DEFINITIONS ::= BEGIN

    IMPORTS
        MODULE-IDENTITY,OBJECT-TYPE     	    FROM SNMPv2-SMI
        MacAddress,RowStatus                    FROM SNMPv2-TC
        dlink-common-mgmt               	    FROM DLINK-ID-REC-MIB;

     swMacProtectMIB MODULE-IDENTITY
          LAST-UPDATED "201605230000Z"
          ORGANIZATION "D-Link Corp."
          CONTACT-INFO
            "http://support.dlink.com"
          DESCRIPTION
            "."
          ::= { dlink-common-mgmt 115 }

    swMacProtectCtrl            OBJECT IDENTIFIER ::= { swMacProtectMIB 1 }
    swMacProtectInfo            OBJECT IDENTIFIER ::= { swMacProtectMIB 2 }
    swMacProtectPortMgmt        OBJECT IDENTIFIER ::= { swMacProtectMIB 3 }
    swMacProtectMgmt            OBJECT IDENTIFIER ::= { swMacProtectMIB 4 }


-- -----------------------------------------------------------------------------
-- swMacProtectCtrl            OBJECT IDENTIFIER ::= { swMacProtectMIB 1 }
-- -----------------------------------------------------------------------------

-- -----------------------------------------------------------------------------
-- swMacProtectInfo            OBJECT IDENTIFIER ::= { swMacProtectMIB 2 }
-- -----------------------------------------------------------------------------

-- -----------------------------------------------------------------------------
-- swMacProtectPortMgmt        OBJECT IDENTIFIER ::= { swMacProtectMIB 3 }
-- -----------------------------------------------------------------------------

-- -----------------------------------------------------------------------------
-- swMacProtectMgmt            OBJECT IDENTIFIER ::= { swMacProtectMIB 4 }
-- -----------------------------------------------------------------------------
swMacProtectDatabaseTable OBJECT-TYPE
    SYNTAX      SEQUENCE OF SwMacProtectDatabaseEntry
    MAX-ACCESS  not-accessible
    STATUS      current
    DESCRIPTION
		"A table that contains the MAC protection entries information."
    ::= { swMacProtectMgmt 1 }

swMacProtectDatabaseEntry OBJECT-TYPE
    SYNTAX      SwMacProtectDatabaseEntry
    MAX-ACCESS  not-accessible
    STATUS      current
    DESCRIPTION
		"A list that contains the MAC protection entries information."
    INDEX {
        swMacProtectDatabaseMacAddress,
        swMacProtectDatabaseMacMask
    }
    ::= { swMacProtectDatabaseTable 1 }

SwMacProtectDatabaseEntry ::=
    SEQUENCE {
        swMacProtectDatabaseMacAddress
            MacAddress,
        swMacProtectDatabaseMacMask
            MacAddress,
        swMacProtectDatabaseStatus
            RowStatus
        }

swMacProtectDatabaseMacAddress OBJECT-TYPE
    SYNTAX      MacAddress
    MAX-ACCESS  read-only
    STATUS      current
    DESCRIPTION
		"This object indicates the MAC address for this MAC protection entry."
    ::= { swMacProtectDatabaseEntry 1 }

swMacProtectDatabaseMacMask OBJECT-TYPE
    SYNTAX      MacAddress
    MAX-ACCESS  read-only
    STATUS      current
    DESCRIPTION
		"This object indicates the Mask of MAC adress for this MAC protection entry."
    ::= { swMacProtectDatabaseEntry 2 }

swMacProtectDatabaseStatus OBJECT-TYPE
    SYNTAX      RowStatus
    MAX-ACCESS  read-create
    STATUS      current
    DESCRIPTION
		"The status of this entry."
    ::= { swMacProtectDatabaseEntry 99 }

END
