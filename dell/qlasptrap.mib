QLGC-QLASPTrap-MIB DEFINITIONS ::= BEGIN

          -- QLogic Advanced Server Trap MIB
          -- 

          IMPORTS
                  enterprises
                          FROM RFC1155-SMI
                  OBJECT-TYPE
                          FROM RFC-1212
                  TRAP-TYPE
                          FROM RFC-1215
                  DisplayString
                          FROM RFC1213-MIB;


    qlogic       OBJECT IDENTIFIER ::= { enterprises 3873 }
    enet         OBJECT IDENTIFIER ::= { qlogic 1 }
    qlasp        OBJECT IDENTIFIER ::= { enet 2 }
    qlaspConfig  OBJECT IDENTIFIER ::= { qlasp 1 }
    qlaspStat    OBJECT IDENTIFIER ::= { qlasp 2 }
    qlaspTrap    OBJECT IDENTIFIER ::= { qlasp 3 }

--
-- Object Definitions
--
    trapAdapterName OBJECT-TYPE
        SYNTAX    DisplayString
        ACCESS    read-only
        STATUS    mandatory
        DESCRIPTION
            "The adapter name."
        ::= { qlaspTrap 1 }

    trapTeamName OBJECT-TYPE
        SYNTAX    DisplayString
        ACCESS    read-only
        STATUS    mandatory
        DESCRIPTION
            "The team name."
        ::= { qlaspTrap 2 }

    trapCauseDirection OBJECT-TYPE
        SYNTAX INTEGER 
              {
				   adapterActive(1),
				   adapterInactive(2)
              }
        ACCESS    read-only
        STATUS    mandatory
        DESCRIPTION
            "Event caused by failover condition."
        ::= { qlaspTrap 3 }

    trapAdapterActivityCause OBJECT-TYPE
        SYNTAX INTEGER 
              {
				   none(1),
				   linkChange(2),
				   adapterEnabledOrDisabled(3),
                   adapterAddedOrRemoved(4)
              }
        ACCESS    read-only
        STATUS    mandatory
        DESCRIPTION
            "Addition explanation for the Event trapCauseDirection."
        ::= { qlaspTrap 4 }

--
-- Trap Definitions
--
   failoverEvent TRAP-TYPE
        ENTERPRISE     qlaspTrap
        VARIABLES      {	trapAdapterName,
        				 	trapTeamName, 
        					trapCauseDirection,
        					trapAdapterActivityCause }
        DESCRIPTION     
            "This trap is generated to indicate that adapter Fail-Over 
            event has occured"
            --#SEVERITY MINOR
        ::= 1
END
