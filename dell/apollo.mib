RADLAN-MIB DEFINITIONS ::= BEGIN

-- Title:      RADLAN ROS
-- Version:    7.38.00.00
-- Date:       11 Nov 2004
--
-- 05-Jun-2003  Added rlHostParamTable
-- 12-Jun-2003  Added enumeration to rndErrorSeverity
-- 14-Jun-2003  Added field rlCopyHistoryErrorMessage to table rlCopyHistoryTable
-- 29-Jun-2003  Tables rlOspf...LnkTable replayed tables rlOspf...LSATable)
-- 08-Jul-2003  The low range boundary and the default value of rlDvmrpPruneLifetime
--              were changed from 300 to 200 seconds
-- 16-Jul-2003  The following values VesuvioT and VesuvioF were added to
--              rlPhDModuleType
-- 22-Jul-2003  Added rlStartupCDBChanged, rlManualReboot
-- 23-Jul-2003  New group rldot1x was added
-- 24-Jul-2003  Changed ipMRouteStdMIB to rlIpMRouteStdMIB
-- 27-Jul-2003  Changed access of rlMaxNumberOfAccessRules to read-only
-- 27-Jul-2003  Changed access of rlMaxNumberOfAccessRulesAfterReset to read-write
-- 30-Jul-2003  Added 802.1x traps rldot1xPortStatusAuthorizedTrap and
--              rldot1xPortStatusUnauthorizedTrap
-- 30-Jul-2003  Added rlFile
-- 31-Jul-2003  Added rlAAAEap
-- 10-Aug-2003  Renamed enumeration values resetCDB to resetStartupCDB and
--                                         eraseCDB to eraseStartupCDB and
--              added enumeration values eraseRunningCDB and copyStartupToRunning
-- 16-Aug-2003  Added rlSnmp
-- 18-Aug-2002 Added rldot1xExtAuthSessionStatsTable
-- 21-Aug-2003  Added rlOspfTuning
-- 09-Sep-2003  Added rlPortCopyVlanTaggingTable
-- 13-Sep-2003  Added IMPLIED to INDEX { IMPLIED rlTranslationNameToIpName }
-- 15-Sep-2003  rlPhysicalDescription's version (a value of variable rlPhDMibVersion)
--              was changed from 2 to 3
-- 15-Sep-2003  Added field rldot1dStpPortRole to rldot1dStpPortTable
-- 15-Sep-2003  Added field rldot1sMStpInstancePortRole to rldot1sMstpInstancePortTable
-- 15-Sep-2003  Added field rldot1sMstpExtPortBoundary to rldot1sMstpExtPortEntryTable
-- 19-Sep-2003  Added rldot1xGuestVlanSupported, rldot1xGuestVlanVID, rldot1xGuestVlanPorts,
--                    rldot1xUnAuthenticatedVlanSupported, rldot1xUnAuthenticatedVlanTable,
--                    rldot1xUserBasedVlanSupported, rldot1xUserBasedVlanPorts
-- 26-Sep-2003  Added rlMridTable
-- 26-Sep-2003  Added rlMirModel
-- 26-Sep-2003  Deleted JackType from IMPORTS clause
-- 26-Sep-2003  Changed naming of SMIv2-like types
-- 26-Sep-2003  Moved rlSyslog branch to new MIB
-- 26-Sep-2003  Moved rlCopy branch to new MIB
-- 26-Sep-2003  Editorial changes
-- 02-Oct-2003  Added vlanSpecialTagTable
-- 02-Oct-2003  Added field branch rlMibTree and table rlMibTreeTable
-- 02-Oct-2003  rlPhysicalDescription's version (a value of variable rlPhDMibVersion)
--              was changed from 3 to 4
-- 02-Oct-2003  Added vlanSpecialTagCurrentTable
-- 09-Oct-2003  Added field rldot1sMstpInstanceRemainingHopes to rldot1sMstpInstanceTable
-- 11-Oct-2003  Changed OSPF tuning
-- 24-Oct-2003  Change range of rldot1sMstpInstancePortPathCost
--              from (1..65535) to (1..200000000)
-- 26-Oct-2003  Added rsMaxNumberRpAddresesInGroupRange,rsMaxNumberRpAddresesInGroupRangeAfterReset
-- 26-Oct-2003  Removed rlPimSMBootStrapInfoEnable
-- 27-Oct-2003  Change range of rldot1sMStpInstancePortAdminPathCost
--              from (0..65535) to (0..200000000)
-- 29-Oct-2003  Added rlIfExistingPortList
-- 07-Nov-2003  rldot1sMstpMaxHopes:
--                a. range was changed from 1..20 to 1..40
--                b. default value was chaged from 10 to 20
--                   rldot1sMstpDesignatedMaxHopes:
--                a. range was changed from 1..40 to 1..20
-- 02-Dec-2003   Unused group rsIpZeroHopRouting was deleted
-- 03-Dec-2003  Added rlSNMPDomains branch
-- 03-Dec-3003  Added rlTstBasicRateTable
-- 14-Dec-2003  Added field rldot1dStpBpduType to rldot1dStpPortEntry
-- 14-Dec-2003  Added rldot1dStpFilterBpdu
-- 21-Dec-2003  Updated imports of  DisplayString, PhysAddress, TimeInterval,
--              DateAndTime, ipAddrEntry
-- 21-Dec-3003  Added rlEmWebHttpsActiveCertificateId and rlSsl
-- 24-Dec-3003  Added rldot1sMstpRemainingHops
-- 13-Jan-2004 Change MSTP tables indexes to read-only.
-- 30-Jan-2004 add field rldot1sMstpExtPortInternalAdminPathCost to rldot1sMstpExtPortTable.
-- 30-Jan-2004 change field rldot1sMstpExtPortInternalPathCost to rldot1sMstpExtPortInternalOperPathCost
--             and make it read-only, change range to (0..200000000).
-- 03-Feb-2004 traps 186-191 are implemeted in the Physicaldescription MIB - for stacking.
-- 09-Feb-2004 Change the upper rage of rldot1sMstpVlan to 4094.
-- 11-Mar-2004 Added swIfPortLockIfRangeTable
-- 26-Mar-2004 rlLcli MIB was moved to separated file
-- 30-Mar-2004 Added traps swIfTablePortLock and swIfTablePortUnLock
-- 19-Apr-2004 Moved to separate MIBS IP Multicast & DVMRP
-- 24-Apr-2004 Moved to separate MIBS VLAN
-- 05-May-2004 Deleted default values in swIfEntry
-- 07-May-2004 Added mac base priority MIB as RND 101
-- 16-May-2004 Added value invalidImage(3) to rndActiveSoftwareFileAfterReset
--             of rndActiveSoftwareFileTable
-- 18-May-2004 Moved to separate files: ipSpec, rlBgp, rsTunning, rlFft,
--             rndMng, rndApplications
-- 31-May-2004 Added rlWlanAccessPoint
-- 31-May-2004 Moved to separate files: rsUDP, swInterfaces, rlRmonControl
-- 09-Jun-2004 change field rldot1sMstpInstancePortEnable in rldot1sMstpInstancePortEntry
--             to read-only
-- 16-Jun-2004 Added rndIpHostManagementSupported and rndIpHostManagementIfIndex
-- 10-Nov-2004 Added rndNotifications
-- 11-Nov-2004 Added rlAAAUserLocked trap
-- 23-Nov-2004 Added type kiloBitsPerSecond RlStormCtrlRateUnit.
-- 29-Nov-2004 limit rldot1sMstpPendingConfigurationName to 32 characters.

IMPORTS
    IpAddress, Counter,
    TimeTicks, enterprises
                FROM RFC1155-SMI
    OBJECT-TYPE
                FROM RFC-1212
    DisplayString, PhysAddress, TimeInterval, DateAndTime, TEXTUAL-CONVENTION
                FROM SNMPv2-TC
    TRAP-TYPE
              FROM RFC-1215
    InterfaceIndexOrZero, InterfaceIndex, ifIndex
              FROM IF-MIB
    BridgeId, Timeout, dot1dBasePort, dot1dBasePortEntry
              FROM BRIDGE-MIB
    TruthValue, RowStatus, zeroDotZero,
    RowPointer
              FROM RADLAN-SNMPv2
    EnabledStatus
              FROM P-BRIDGE-MIB
    PortList
              FROM Q-BRIDGE-MIB
    dot3adAggIndex, dot3adAggPortIndex
              FROM IEEE8023-LAG-MIB
    dot1xAuthSessionStatsEntry
              FROM IEEE8021-PAE-MIB
    MacAddress
          FROM BRIDGE-MIB
    Unsigned32, Counter32, Integer32
              FROM SNMPv2-SMI
    SnmpAdminString
           FROM SNMP-FRAMEWORK-MIB
    VlanIndex, dot1qFdbId
            FROM Q-BRIDGE-MIB;

    Percents ::= INTEGER (0..100)
    NetNumber ::=  OCTET STRING (SIZE(4))
    VlanPriority ::= INTEGER (0..7)
    RlStormCtrlRateUnit ::= INTEGER {
        packetsPerSecond(1),
        bytesPerSecond(2),
        framesPerBuffer(3),
        precentages(4),
        kiloBytesPerSecond(5),
        kiloBitsPerSecond(6)
    }


-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }
 rnd            OBJECT IDENTIFIER ::= { enterprises 89  }

--   Objects in this MIB are arranged into groups:
--01 rndMng             - Management/Action
--02 rndDeviceParams    - General parameters
--04 rndInterface       - Obsolete
--09 rndBackup          - Obsolete
--12 rndIPX             - Parameters for management of IPX router
--16 rndFACS            - Obsolete
--20 rndCOD             - Obsolete
--22 rndBrgHub          - Obsolete
--23 rndAdapter         - Obsolete
--24 rndBootP           - BootP configurgaration.
--26 ipSpec             - IP Private MIBs
--27 virtualLan         - Obsolete
--28 rsConf             - Obsolete
--29 rsTunning          - Tunning sub group
--30 rndISDN            - Obsolete
--31 rndPPP             - Obsolete
--34 frameRelay         - Obsolete
--35 rndApplications    -
--38 rsDHCP             - DHCP server configuration
--39 radWiz             - Obsolete
--40 rsCfgUpgrade       - Obsolete
--42 rsUDP              -
--43 swInterfaces       -
--44 securityZone       - Obsolete
--45 rll3SwtchETMdl     - Obsolete
--46 rlIPmulticast      -
--47 rlFFT              -
--48 vlan               -
--49 rlRmonControl      -
--50 rlBrgMacSwitch     -
--51 rlExperience       -
--52 rlCli              -
--53 rlPhysicalDescription -
--54 rlIfInterfaces     -
--55 rlMacMulticast     -
--56 rlGalileo          -
--57 rlpBridgeMIBObjects-
--58 rlTelnet           -
--59 rlPolicy           -
--60 rlArpSpoofing      -
--61 rlMir              -
--62 rlIpMRouteStdMIB     -
--63 rl3sw2swTables     -
--64 rlGvrp             -
--65 rlDot3adAgg        -
--66 rlEmbWeb           -
--67 rlSwPackageVersion -
--68 rlBroadcom          -
--69 rlMultiSessionTerminal -
--70 rlRCli             -
--71 rlBgp              -
--72 rlAgentsCapabilitiesGroups -
--73 rlAggregateVlan    -
--74 rlLCli             -
--75 rlGmrp             -
--76 rlDhcpCl           - Dhcp client
--77 rlStormCtrl        -
--78 rlSsh              -
--79 rlAAA              -
--80 Radius             -
--81 rlTraceRoute       -
--82 rlSyslog           -
--83 rlEnv              - HardWare status indication
--84 rlSmon             -
--85 rlSocket           -
--86 rlDigitalKeyManage -
--87 rlCopy             -
--88 rlQosCliMib        -
--89 rlMngInf           -
--90 rlPhy              -
--91 rlJumboFrames      -
--92 rlTimeSynchronization
--93 rlDnsCl            - Dns client
--94 rlCDB
--95 rldot1x
--96 rlFile
--97 rlAAAEap           - AAA for 1x
--98 rlSNMP
--99 rlQosServ
--100 rlSsl
--101 rlMacBasePrio
--102 Wireless Access Point Private MIB

-- At the end of the MIB there is a definition of all RND-specific traps.

rndNotifications OBJECT-IDENTITY
           STATUS      current
           DESCRIPTION " All the rnd notifications will reside under this branch
                         as specified in
                         RFC2578 'Structure of Management Information Version 2 (SMIv2)' 8.5"
           ::= { rnd 0 }


-- rndMng group contains Management Variables for RND devices

rndMng   OBJECT IDENTIFIER ::= { rnd 1  }
-- see rlMng.mib

-- rndDeviceParams group contains a number of general variables

rndDeviceParams       OBJECT IDENTIFIER ::= { rnd 2  }

rndBridgeType  OBJECT-TYPE
    SYNTAX  INTEGER {
       reb(1),
       ceb(2),
       ceblb(3),
       xeb(4),
       xeb1(5),
       rebsx(6),
       rtb(7),
       ltb(8),
       tre(9),
       rtre(10),      -- remote TRE
       xtb(11),
       ete(12),
       rete(13),      -- remote ETE
       ielb(30),
       leb(31),
       openGate12(32),
       openGate4(33),
       ran(34),
       itlb(35),
       gatelinx(36),
       openGate2(37),
       ogRanTR(38),
       rdapter(39),
       ogVan(40),
       wanGate(41),
       ogRubE(42),
       ogRubT(43),
       wanGateI(44),
       vGate4(45),
       lre(46),
       mrt(47),
       vGate2(48)
     }
    ACCESS  read-only
    STATUS  mandatory
    DESCRIPTION
      "Identification of the RND bridge type."
    ::= { rndDeviceParams 1  }


rndInactiveArpTimeOut OBJECT-TYPE
    SYNTAX INTEGER
    ACCESS  read-write
    STATUS  mandatory
    DESCRIPTION
      "This variable defines the maximum time period that can pass
       between ARP requests concerning an entry in the ARP table.
       After this time period, the entry is deleted from the table."
    ::= { rndDeviceParams 2  }

-- The following two variables define the format of RND specific
-- error messages issued by the RND devices

rndBridgeAlarm  OBJECT IDENTIFIER ::= { rndDeviceParams 3  }

rndErrorDesc OBJECT-TYPE
    SYNTAX DisplayString
    ACCESS  read-only
    STATUS  mandatory
    DESCRIPTION
       "A textual description of the enterprise-specific trap sent
        to the Network Management Station by the RND managed device."
    ::= { rndBridgeAlarm 1  }

rndErrorSeverity OBJECT-TYPE
    SYNTAX INTEGER  {
         info(0),
         warning(1),
         error(2),
         fatal-error(3)
    }
    ACCESS  read-only
    STATUS  mandatory
    DESCRIPTION
      "The severity type of the enterprise-specific trap sent to the
      Network Management Station by the RND managed device."
    ::= { rndBridgeAlarm 2  }

rndBrgVersion OBJECT-TYPE
    SYNTAX  DisplayString
    ACCESS  read-only
    STATUS  mandatory
    DESCRIPTION
      "The bridge version."
   ::= { rndDeviceParams 4  }

rndBrgFeatures OBJECT-TYPE
    SYNTAX   OCTET STRING  -- SIZE 20
    ACCESS  read-only
    STATUS  mandatory
    DESCRIPTION
      "A bit mask that defines the features supported by a particular configuration
       of this network element:
       __________________________________________
       |  Byte 1|Byte 2 |Byte 3 | ....|Byte 20  |
       |87654321|                     | 87654321|
       |________|_______________________________|

 Byte1 :
      bit1: TX Block mask
      bit2: Source Routing Encapulation
      bit3: SNA/SDLC
      bit4: Frame Relay
      bit5: SNMP
      bit6: LAN Manager
      bit7: High Performance
      bit8: Translation
 Byte2 :
      bit1: DEC Router
      bit2: IPX Router
      bit3: IP  Router
 Byte3 :
      bit1: Dial Up Backup
      bit2: COD
      bit3: FACS
      bit4: Load Balance
      bit5: Remote Configuration
      bit6: RIP 2
      bit7: OSPF
      bit8: IPX RIP/SAP Filter
 Byte4 :
      bit1: BootP Server
      bit2: BootP Client
      bit3: Compression
      bit4: V25.bis
      bit5: ISDN
      bit6: CODv2
      bit7: NSPF
      bit8: UDP Relay

 Byte5
      bit1:VirtualLAN
      bit2:Static IP Multicast
      bit3:IP Redundancy
      bit4:CCM2
      bit5:ISDN Bonding
      bit6:Backup Link Selection -- for the  VAN/Rdapter ver 4.0
      bit7:IP/IPX Forwarding     -- for the  WANgate ver 4.0
      bit8:Improved COD

 Byte6
      bit1: Server Disptacher
      bit2: ISDN_US             -- for the  VANSX/WANGATE ver 5.0
      bit3: PPP
      bit4: IP Rip Filter       -- for Vgate3
      bit5: Zero Hop Routing    -- for Vgate3
      bit6: ISDN Japan
      bit7: PPP-Security

 Byte7
     bit1: With unmanaged Switch
     bit2: 2 LANs
     bit3: OSPF Ver 2.0
     bit4: FACS Ver 2.0
     bit5: Multiple WEB Farm
     bit6: Backup Server
     bit7: Check Connectivity
     bit8: WSD multiplexing

Byte8
     bit1: MRT3
     bit2: WSD Redundancy
     bit3: DHCP Server
     bit4: WSD Connection Limit
     bit5: WSD Distributed System
     bit6: WSD Load Report
     bit7: WSD super farm
     bit8: RadWiz leased line

Byte9
     bit1: PPP IP address negotiaton
     bit2: DNS
     bit3: Nat
     bit4: WSD Static proximity
     bit5: WSD Dynamic proximity
     bit6: WSD Proxy
     bit7: WSD Proximity client
     bit8: MAC Load balancing

Byte10
     bit1: Unnum Inf
     bit2: Power Supply redundancy
     bit3: MRT PPP Compression
     bit4: ZHR Apolo
     bit5: Copy port
     bit6: UDP Relay 2.0
     bit7: NVRAM
     bit8: URL table

Byte11
     bit1: URL super farm
     bit2: NAT on LAN
     bit3: Remote Con
     bit4: AP5000
     bit5: Session tracking
     bit6: Mirroring
     bit7: Alias IP
     bit8: CSD Nat

Byte12
     bit1: content check
     bit2: mlb virtual ip
     bit3: reserved RadLan
     bit4: csd nat exception
     bit5: statistics monitor
     bit6: reserved-for-radware          "

   ::= { rndDeviceParams 5  }

rndBrgLicense OBJECT-TYPE
    SYNTAX   OCTET STRING  -- SIZE 20
    ACCESS  read-write
    STATUS  mandatory
    DESCRIPTION
       "This parameter is used for entering a s/w license number for a device.
        A separate license number is supplied for each device."
   ::= { rndDeviceParams 6  }

-- IP Host Parameters

--All the new parameters under this section will be added to the
-- rndMng group, as rndIpHost sub-group.
--
rndIpHost  OBJECT IDENTIFIER   ::= { rndDeviceParams 7 }
--
--ICMP Transmission Enable\Disable
--The new variable will be

-- Obsolete
-- rndICMPTransmitionEnable   OBJECT-TYPE
--   SYNTAX INTEGER {
--      enable(1),
--      disable(2)
--  }
--   ACCESS  read-write
--   STATUS  mandatory
--  DESCRIPTION
--    "This variable controlls the ability to transmit ICMP frames"
--    ::= { rndIpHost 1 }

rndCommunityTable OBJECT-TYPE
   SYNTAX SEQUENCE OF RndCommunityEntry
   ACCESS not-accessible
   STATUS mandatory
   DESCRIPTION
    "The community table of the agent"
     ::= { rndIpHost 2 }

rndCommunityEntry  OBJECT-TYPE
   SYNTAX RndCommunityEntry
   ACCESS not-accessible
   STATUS mandatory
   DESCRIPTION
       " The row definition for this table."
   INDEX { rndCommunityMngStationAddr,
           IMPLIED rndCommunityString }
   ::= { rndCommunityTable 1 }

RndCommunityEntry ::= SEQUENCE {
  rndCommunityMngStationAddr   IpAddress,
  rndCommunityString           DisplayString,
  rndCommunityAccess           INTEGER,
  rndCommunityTrapsEnable      INTEGER,
  rndCommunityStatus           INTEGER,
  rndCommunityPortSecurity     INTEGER,
  rndCommunityOwner            DisplayString,
  rndCommunityTrapDestPort     INTEGER
}


rndCommunityMngStationAddr OBJECT-TYPE
   SYNTAX IpAddress
   ACCESS   read-write
   STATUS mandatory
   DESCRIPTION
    "The management station that will be allowed to
    communicate with the agent IP address"
     ::=  { rndCommunityEntry 1 }

rndCommunityString OBJECT-TYPE
   SYNTAX DisplayString (SIZE(1..20))
   ACCESS read-write
   STATUS mandatory
   DESCRIPTION
    "The community string with which the management
     station will communicate with the agent"
     ::= { rndCommunityEntry 2 }

rndCommunityAccess OBJECT-TYPE
   SYNTAX INTEGER {
    readOnly(1),
    readWrite(2),
    super(3)
      }
   ACCESS read-write
   STATUS mandatory
   DESCRIPTION
    "The allowed access to this management station"
     ::= { rndCommunityEntry 3}

rndCommunityTrapsEnable OBJECT-TYPE
   SYNTAX INTEGER {
        snmpV1(1),
        snmpV2(2),
        snmpV3(3),
        trapsDisable(4)
   }
   ACCESS   read-write
   STATUS mandatory
   DESCRIPTION
    "Should the agent send traps to the management station,
     and what version is required"
      ::= { rndCommunityEntry 4 }

rndCommunityStatus OBJECT-TYPE
   SYNTAX INTEGER {
    enable(1),
    invalid(2)
     }
   ACCESS read-write
   STATUS mandatory
   DESCRIPTION
    "The status of this entry. If the status is invalid the
    community entry will be deleted"
    ::= { rndCommunityEntry 5 }

rndCommunityPortSecurity OBJECT-TYPE
   SYNTAX INTEGER {
    enabled(1),
    disabled(2)
   }
   ACCESS read-write
   STATUS mandatory
   DESCRIPTION
    "If enabled the device will only receive SNMP messages from the port,
     through which this NMS is reachable from the device."
   DEFVAL { disabled }
   ::= { rndCommunityEntry 6 }

rndCommunityOwner OBJECT-TYPE
   SYNTAX DisplayString (SIZE(1..32))
   ACCESS read-write
   STATUS mandatory
   DESCRIPTION
    "The owner of this community"
     ::= { rndCommunityEntry 7 }

rndCommunityTrapDestPort OBJECT-TYPE
   SYNTAX INTEGER(0..65535)
   ACCESS read-write
   STATUS mandatory
   DESCRIPTION
    "The transport protocol (usually UDP) port to which traps to the
    management station represebted by this entry will be sent. The default
    is the well-known IANA assigned port number for SNMP traps.
    This object is relevant only if rndCommunityTrapsEnable has a value
    different from trapsDisable."
   DEFVAL { 162 }
   ::= { rndCommunityEntry 8 }

rlMridTable OBJECT-TYPE
   SYNTAX SEQUENCE OF RlMridEntry
   ACCESS not-accessible
   STATUS mandatory
   DESCRIPTION
    "The MRID related configurations table of the agent"
     ::= { rndIpHost 3 }

rlMridEntry  OBJECT-TYPE
   SYNTAX RlMridEntry
   ACCESS not-accessible
   STATUS mandatory
   DESCRIPTION
       " The row definition for this table."
   INDEX { rndCommunityMngStationAddr,
           IMPLIED rndCommunityString }
   ::= { rlMridTable 1 }

RlMridEntry ::= SEQUENCE {
       rlMridConnection    INTEGER,
       rlManagedMrid INTEGER
}

rlMridConnection OBJECT-TYPE
   SYNTAX INTEGER
   ACCESS read-write
   STATUS mandatory
   DESCRIPTION
    "The router instance connecting the NMS who accessed the agent
     through the community table entry corresponding to the keys of this entry."
     ::=  { rlMridEntry 1 }

rlManagedMrid OBJECT-TYPE
   SYNTAX INTEGER
   ACCESS read-write
   STATUS mandatory
   DESCRIPTION
    "The router instance currently managed by the NMS who accessed the agent
     through the community table entry corresponding to the keys of this entry "
     ::=  { rlMridEntry 2 }

rndManagedTime  OBJECT-TYPE
   SYNTAX DisplayString (SIZE(6))
   ACCESS read-write
   STATUS mandatory
   DESCRIPTION
    "The time will be sent in the format hhmmss"
   ::= { rndDeviceParams 8 }

rndManagedDate  OBJECT-TYPE
   SYNTAX DisplayString (SIZE(6))
   ACCESS read-write
   STATUS mandatory
   DESCRIPTION
    "The date will be sent in the format ddmmyy"
    ::= { rndDeviceParams 9 }

rndBaseBootVersion OBJECT-TYPE
   SYNTAX DisplayString
   ACCESS  read-only
   STATUS  mandatory
   DESCRIPTION
      "Defines the boot version of the product."
   ::= { rndDeviceParams 10 }

rndIpHostManagement  OBJECT IDENTIFIER   ::= { rndIpHost 4 }

rndIpHostManagementSupported OBJECT-TYPE
    SYNTAX TruthValue
    ACCESS read-only
    STATUS mandatory
    DESCRIPTION
         "ifindex manage supported."
    ::= { rndIpHostManagement  1 }

rndIpHostManagementIfIndex OBJECT-TYPE
    SYNTAX INTEGER
    ACCESS read-write
    STATUS mandatory
    DESCRIPTION
         "if supported manage , indicate ifindex, if 0 thaen disable"
    ::= { rndIpHostManagement  2 }

genGroup  OBJECT IDENTIFIER   ::= { rndDeviceParams 11 }
genGroupHWVersion OBJECT-TYPE
   SYNTAX  DisplayString
   ACCESS  read-only
   STATUS  mandatory
   DESCRIPTION
        "Defines the HW version of the product."
   ::= { genGroup 1 }

genGroupConfigurationSymbol OBJECT-TYPE
      SYNTAX  DisplayString (SIZE(1))
      ACCESS  read-only
      STATUS  mandatory
      DESCRIPTION
      "Defines the Configuration Symbol attached to any hardware module
      manufactured by LANNET. One single character A..Z defines the CS
      version."
      ::= { genGroup 2 }

genGroupHWStatus OBJECT-TYPE
      SYNTAX  INTEGER {
        ok(1),
        hardwareProblems(2),
        notSupported(255)
      }
      ACCESS  read-only
      STATUS  mandatory
      DESCRIPTION
      "This attribute describes the status of the group hardware as detected
      by the sensors software."
      ::= { genGroup 3 }

rndBasePhysicalAddress OBJECT-TYPE
    SYNTAX PhysAddress
    ACCESS  read-only
    STATUS  mandatory
    DESCRIPTION
      "The Base physical (MAC) address of the device."
    ::= { rndDeviceParams 12  }

rndSoftwareFile  OBJECT IDENTIFIER ::= { rndDeviceParams 13 }

rndActiveSoftwareFileTable OBJECT-TYPE
    SYNTAX SEQUENCE OF RndActiveSoftwareFileEntry
    ACCESS not-accessible
    STATUS mandatory
    DESCRIPTION
        " The (conceptual) table listing the active software file of the
          requested unit."
    ::= {rndSoftwareFile 1 }

rndActiveSoftwareFileEntry  OBJECT-TYPE
    SYNTAX RndActiveSoftwareFileEntry
    ACCESS not-accessible
    STATUS mandatory
    DESCRIPTION
        " An entry (conceptual row) in the rndActiveSoftwareFileTable."
    INDEX {rndUnitNumber }
    ::= {rndActiveSoftwareFileTable  1 }

RndActiveSoftwareFileEntry ::= SEQUENCE {
    rndUnitNumber                      INTEGER,
    rndActiveSoftwareFile              INTEGER,
    rndActiveSoftwareFileAfterReset    INTEGER
}

rndUnitNumber OBJECT-TYPE
    SYNTAX      INTEGER
    ACCESS      read-write
    STATUS      mandatory
    DESCRIPTION
        "The unit number (for stackable devices) or 1 for 'stand alone' device."
    ::= {rndActiveSoftwareFileEntry 1 }

rndActiveSoftwareFile OBJECT-TYPE
    SYNTAX INTEGER {
        image1(1),
        image2(2)
    }
    ACCESS      read-only
    STATUS      mandatory
    DESCRIPTION
        "Indicates the current active software file, image1 or image2."
    ::= {rndActiveSoftwareFileEntry 2 }

rndActiveSoftwareFileAfterReset OBJECT-TYPE
    SYNTAX INTEGER {
        image1(1),
        image2(2),
        invalidImage(3)
    }
    ACCESS read-write
    STATUS mandatory
    DESCRIPTION
        "Indicates the software file that will be active after reset (image1 or image2).
         If an error occurred in the download process, resulting in the corruption
         of the single software file, The value 'invalidImage' will be returned.
         This value can not be set by the user."
    ::= {rndActiveSoftwareFileEntry 3 }

-- Obsolete
-- rndInterface OBJECT IDENTIFIER ::= { rnd 4  }

-- Obsolete
-- rndBackup    OBJECT IDENTIFIER ::= { rnd 9 }

-- Obsolete
-- rndIPX   OBJECT IDENTIFIER ::= { rnd 12 }

-- Obsolete
-- rndFACS    OBJECT IDENTIFIER ::=  { rnd 16 }

-- Obsolete
-- rndCOD    OBJECT IDENTIFIER ::=  { rnd 20 }

-- Obsolete
-- rndBrgHub     OBJECT IDENTIFIER ::=  { rnd 22 }

-- Obsolete
-- rndAdapter    OBJECT IDENTIFIER ::=  { rnd 23 }

rndBootP    OBJECT IDENTIFIER ::=  { rnd 24 }

rndBootPServerAddress  OBJECT-TYPE
    SYNTAX IpAddress
    ACCESS read-write
    STATUS mandatory
    DESCRIPTION
     " The IPAddress of the BOOTP server. the OpenGate will act as a BootP relay if
       this parameter is not equale to 0.0.0.0."
    DEFVAL  {'00000000'H}
      ::= { rndBootP 1 }

rndBootPRelaySecThreshold OBJECT-TYPE
    SYNTAX INTEGER
    ACCESS read-write
    STATUS mandatory
    DESCRIPTION
       "BootP requests are relayed only if their SEC field is greater or
        equal to the threshold value in order to allow local BootP Servers
        to answer first."
    ::= { rndBootP 2 }

-- ip Specific group  Addition parameters to ip group in MIB-2

ipSpec      OBJECT IDENTIFIER ::= { rnd 26 }
-- see rlIp.mib

-- Obsolete
-- virtualLan  OBJECT IDENTIFIER ::= { rnd 27 }

-- Obsolete
-- rsConf  OBJECT IDENTIFIER ::= { rnd 28 }

rsTunning  OBJECT IDENTIFIER ::= { rnd 29 }
-- see rlTuning.mib

-- Obsolete
-- rndISDN      OBJECT IDENTIFIER ::= { rnd 30}

-- Obsolete
-- rndPPP   OBJECT IDENTIFIER ::= { rnd 31 }

-- Obsolete
-- frameRelay    OBJECT IDENTIFIER ::= { rnd 34 }

rndApplications  OBJECT IDENTIFIER ::= { rnd 35 }
-- see rlApplication.mib

-- Obsolete
-- rndOGCompression  OBJECT IDENTIFIER ::= { rnd 36 }

-- Obsolete
-- rndEthernet  OBJECT IDENTIFIER ::= { rnd 37 }

--rsDHCP  OBJECT IDENTIFIER ::= { rnd 38 }
--see rlDhcl.mib

-- Obsolete
-- radWiz  OBJECT IDENTIFIER ::= { rnd 39 }

-- Obsolete
-- rsCfgUpgrade  OBJECT IDENTIFIER ::= { rnd 40 }

-- Obsolete
--rsRMON  OBJECT IDENTIFIER ::= { rnd 41 }

-- rsCopyPort was deleted
-- { rsRMON 1 } reserved

-- rsMonitPort was deleted
-- { rsRMON 2 } reserved

rsUDP    OBJECT IDENTIFIER ::=  { rnd 42}
-- see rlUdp.mib

swInterfaces  OBJECT IDENTIFIER ::= { rnd 43 }
-- see rlInterfaces.mib

-- Obsolete
-- securityZone  OBJECT IDENTIFIER ::= { rnd 44 }

-- Obsolete
-- rll3SwtchETMdl OBJECT IDENTIFIER ::= { rnd 45 }

rlIPmulticast OBJECT IDENTIFIER ::= { rnd 46 }

rlFFT OBJECT IDENTIFIER ::= { rnd 47 }

vlan  OBJECT IDENTIFIER ::= { rnd 48 }

rlRmonControl   OBJECT IDENTIFIER ::=  { rnd 49}
-- see rlRmon.mib

rlBrgMacSwitch  OBJECT IDENTIFIER ::= { rnd 50 }

rlBrgMacSwVersion OBJECT-TYPE
    SYNTAX  INTEGER
    ACCESS  read-only
    STATUS  mandatory
    DESCRIPTION
        "MIB's version, the current version is 2."
    ::= { rlBrgMacSwitch 1 }

rlBrgMacSwMaxTableNumber OBJECT-TYPE
    SYNTAX  INTEGER
    ACCESS  read-only
    STATUS  mandatory
    DESCRIPTION
        "Maximum number of MAC Tables supported by the device."
    ::= { rlBrgMacSwitch 2 }

rlBrgMacSwDynamicTables OBJECT-TYPE
    SYNTAX  INTEGER {
        supported (1),
        unsupported (2)
    }
    ACCESS  read-only
    STATUS  mandatory
    DESCRIPTION
        "Specifies whether the device supports port dynamic MAC tables."
    ::= { rlBrgMacSwitch 3 }

--rlBrgMacSwTblPollingTimeout  OBJECT-TYPE
--    SYNTAX  INTEGER
--    ACCESS  read-write
--    STATUS  mandatory
--    DESCRIPTION
--        "The units of this MIB object is seconds."
--    ::= { rlBrgMacSwitch 4 }

rlBrgMacSwOldEntryDeleteMode  OBJECT-TYPE
    SYNTAX  INTEGER {
        refreshFlag (1),
        agingFlag(2),
        agingTime(3),
        boundaries(4)
    }
    ACCESS  read-only
    STATUS  mandatory
    DESCRIPTION
        "The method used to delete old unused entries
         refresh_flag:
            The high level sets a flag when it adds or updates an entry,
            the Switch clears the flag each time, when it learns the
            station once more.
        aging_flag:
            The high level clears a flag when it adds or updates an entry,
            the Switch sets the flag each time, when it learns the station
            once more.
        aging_time:
            The high level defines a timeout, the Switch sends a message
            to the high level each time when the station doesn't send
            messages during interval between timeout and 2*timeout.
        Boundaries:
            The Switch doesn't support any mechanism, and the high level
            uses two boundaries: red and yellow. When the number of entries
            exceeds the red boundary, the high level deletes the oldest entries."
    ::= { rlBrgMacSwitch 5 }

rlBrgMacSwSpanningTree OBJECT-TYPE
    SYNTAX  INTEGER {
        supported (1),
        unsupported (2)
    }
    ACCESS  read-only
    STATUS  mandatory
    DESCRIPTION
        "Specifies whether the device supports port the Spanning Tree Protocol."
    ::= { rlBrgMacSwitch 6 }

rlBrgMacSwKeyType  OBJECT-TYPE
    SYNTAX  INTEGER {
        macOnly (1),
        tagAndMac(2)
    }
    ACCESS  read-only
    STATUS  mandatory
    DESCRIPTION
        "Specified the used MAC Address Table kye format:
         macOnly:
            One global MAC Address Table per device (leaky VLANs).
         tagAndMac:
            MAC Address Table per each VLAN (strick VLANs)."
    ::= { rlBrgMacSwitch 7 }

rlBrgMacSwYellowBoundary  OBJECT-TYPE
    SYNTAX  INTEGER
    ACCESS  read-write
    STATUS  mandatory
    DESCRIPTION
        "The yellow boundary."
    ::= { rlBrgMacSwitch 8 }

rlBrgMacSwRedBoundary  OBJECT-TYPE
    SYNTAX  INTEGER
    ACCESS  read-write
    STATUS  mandatory
    DESCRIPTION
        "The yellow boundary."
    ::= { rlBrgMacSwitch 9 }

rlBrgMacSwTrapEnable OBJECT-TYPE
    SYNTAX  TruthValue
    ACCESS  read-write
    STATUS  mandatory
    DESCRIPTION
        "This variable indicates whether to create a SNMP trap
         if adding dynamic mac failed due to full hash chain."
    DEFVAL { false }
    ::= { rlBrgMacSwitch 10 }

rlBrgMacSwOperTrapCount  OBJECT-TYPE
    SYNTAX  INTEGER
    ACCESS  read-only
    STATUS  mandatory
    DESCRIPTION
        "This variable indicates the trap counter status
         (i.e. number of received MAC addresses since the last trap
         sent that haven't been inserted into the hash).
         It is relevant only when trap is enabled."
    ::= { rlBrgMacSwitch 11 }

rlBrgMacSwAdminTrapFrequency OBJECT-TYPE
    SYNTAX  INTEGER (1 .. 86400)
--    UNITS    "seconds"
    ACCESS   read-write
    STATUS   mandatory
    DESCRIPTION
        "This variable indicates the minimal frequency (in seconds)
         of sending a trap.
         It is relevant only when trap is enabled."
    DEFVAL { 60 }
    ::= { rlBrgMacSwitch 12 }

rlExperience OBJECT IDENTIFIER ::= { rnd 51 }

-- Used for Drafts not received yet OBJECT IDENTIFIER

rlCli  OBJECT IDENTIFIER ::= { rnd 52 }

rlCliMibVersion OBJECT-TYPE
    SYNTAX  INTEGER
    ACCESS  read-only
    STATUS  mandatory
    DESCRIPTION
        "MIB's version, the current version is 1."
    ::= { rlCli 1 }

rlCliPassword OBJECT-TYPE
   SYNTAX DisplayString (SIZE(0..20))
   ACCESS read-write
   STATUS mandatory
   DESCRIPTION
       "CLI Password"
   ::= { rlCli 2 }

rlCliTimer OBJECT-TYPE
   SYNTAX INTEGER (5..3600)
   ACCESS read-write
   STATUS mandatory
   DESCRIPTION
       "CLI Timer"
   ::= { rlCli 3 }

rlCliFileEnable OBJECT-TYPE
   SYNTAX TruthValue
   ACCESS read-only
   STATUS mandatory
   DESCRIPTION
       "CLI File Enable/Disable"
   ::= { rlCli 4 }

rlCliFileEnableAfterReset OBJECT-TYPE
   SYNTAX TruthValue
   ACCESS read-write
   STATUS mandatory
   DESCRIPTION
       "CLI File Enable/Disable After Reset"
   ::= { rlCli 5 }

rlPhysicalDescription OBJECT IDENTIFIER ::= { rnd 53 }

rlIfInterfaces OBJECT IDENTIFIER ::= { rnd 54 }
-- see rlInterfaces.mib

rlMacMulticast OBJECT IDENTIFIER ::= { rnd 55 }

rlMacMulticastEnable OBJECT-TYPE
    SYNTAX      TruthValue
    ACCESS      read-write
    STATUS      mandatory
    DESCRIPTION
        "Enable/Disable MAC Multicast bridging in the device."
    ::= { rlMacMulticast 1 }

rlIgmpSnoop  OBJECT IDENTIFIER ::= { rlMacMulticast 2 }

rlIgmpSnoopMibVersion OBJECT-TYPE
    SYNTAX  INTEGER
    ACCESS  read-only
    STATUS  mandatory
    DESCRIPTION
        "MIB's version, the current version is 2.
        The addition is that IGMP Snooping is per vlan instead of per device.
        There are additional timers to the protocol: leave time-out and query time-out. "
    ::= { rlIgmpSnoop 1 }

rlIgmpSnoopEnable OBJECT-TYPE
    SYNTAX  TruthValue
    ACCESS  read-write
    STATUS  mandatory
    DESCRIPTION
        "Enable/Disable IGMP Snooping in the switch."
    ::= { rlIgmpSnoop 2 }

rlIgmpSnoopHostAgingTime OBJECT-TYPE
    SYNTAX  INTEGER (1 .. 2147483647 )
--  UNITS   "seconds"
    ACCESS  read-write
    STATUS  mandatory
    DESCRIPTION
        "The amount of time that should pass before aging out
         an entry in the rlIgmpSnoopGroupTable will be aged out."
    DEFVAL  {360}
    ::= { rlIgmpSnoop 3 }

rlIgmpSnoopRouterAgingTime OBJECT-TYPE
    SYNTAX  INTEGER (1 .. 2147483647 )
--  UNITS   "seconds"
    ACCESS  read-write
    STATUS  mandatory
    DESCRIPTION
    "The amount of time that should pass before aging out
     an entry in the rlIgmpSnoopInterfaceTable will be aged out."
    DEFVAL  {900}
    ::= { rlIgmpSnoop 4 }

rlIgmpSnoopGroupTable OBJECT-TYPE
    SYNTAX  SEQUENCE OF RlIgmpSnoopGroupEntry
    ACCESS  not-accessible
    STATUS  mandatory
    DESCRIPTION
        "The (conceptual) table listing the IP multicast groups
         for which there are members on a particular interface."
    ::= { rlIgmpSnoop 5 }

rlIgmpSnoopGroupEntry OBJECT-TYPE
    SYNTAX  RlIgmpSnoopGroupEntry
    ACCESS  not-accessible
    STATUS  mandatory
    DESCRIPTION
        "An entry (conceptual row) in the rlIgmpSnoopGroupTable."
    INDEX  { rlIgmpSnoopGroupTag, rlIgmpSnoopGroupAddress,
             rlIgmpSnoopGroupPort}
    ::= { rlIgmpSnoopGroupTable 1 }

RlIgmpSnoopGroupEntry ::= SEQUENCE {
    rlIgmpSnoopGroupTag         INTEGER,
    rlIgmpSnoopGroupAddress     MacAddress,
    rlIgmpSnoopGroupPort        INTEGER,
    rlIgmpSnoopGroupExpiryTime  INTEGER
}

rlIgmpSnoopGroupTag OBJECT-TYPE
    SYNTAX  INTEGER
    ACCESS  read-only
    STATUS  mandatory
    DESCRIPTION
        "The VLAN tag for which this entry contains
         information for an IP multicast group address."
    ::= { rlIgmpSnoopGroupEntry 1 }

rlIgmpSnoopGroupAddress OBJECT-TYPE
    SYNTAX  MacAddress
    ACCESS  read-only
    STATUS  mandatory
    DESCRIPTION
    "The MAC multicast group address for which this entry
     contains information."
    ::= { rlIgmpSnoopGroupEntry 2 }

rlIgmpSnoopGroupPort OBJECT-TYPE
    SYNTAX  INTEGER
    ACCESS  read-only
    STATUS  mandatory
    DESCRIPTION
        "The ifIndex value of the port for which this entry contains
         information for an IP multicast group address."
    ::= { rlIgmpSnoopGroupEntry 3 }

rlIgmpSnoopGroupExpiryTime OBJECT-TYPE
    SYNTAX  INTEGER
    ACCESS  read-only
    STATUS  mandatory
    DESCRIPTION
        "The minimum amount of time remaining before this entry will aged out."
    ::= { rlIgmpSnoopGroupEntry 4 }

rlIgmpSnoopRouterTable OBJECT-TYPE
    SYNTAX  SEQUENCE OF RlIgmpSnoopRouterEntry
    ACCESS  not-accessible
    STATUS  mandatory
    DESCRIPTION
        "The (conceptual) table listing the ports for which there are
         IP Multicast Routers."
    ::= { rlIgmpSnoop 6 }

rlIgmpSnoopRouterEntry OBJECT-TYPE
    SYNTAX  RlIgmpSnoopRouterEntry
    ACCESS  not-accessible
    STATUS  mandatory
    DESCRIPTION
        "An entry (conceptual row) in the rlIgmpSnoopRouterTable."
    INDEX  { rlIgmpSnoopRouterTag, rlIgmpSnoopRouterPort }
    ::= { rlIgmpSnoopRouterTable 1 }

RlIgmpSnoopRouterEntry ::= SEQUENCE {
    rlIgmpSnoopRouterTag        INTEGER,
    rlIgmpSnoopRouterPort       INTEGER,
    rlIgmpSnoopRouterExpiryTime INTEGER
}

rlIgmpSnoopRouterTag OBJECT-TYPE
    SYNTAX  INTEGER
    ACCESS  read-only
    STATUS  mandatory
    DESCRIPTION
        "The tag of the VLAN for which this entry contains
         information for an IP Multicast Router."
    ::= { rlIgmpSnoopRouterEntry 1 }

rlIgmpSnoopRouterPort OBJECT-TYPE
    SYNTAX  INTEGER
    ACCESS  read-only
    STATUS  mandatory
    DESCRIPTION
        "The interface for which this entry contains information for
         an IP multicast Router."
    ::= { rlIgmpSnoopRouterEntry 2 }

rlIgmpSnoopRouterExpiryTime OBJECT-TYPE
    SYNTAX  INTEGER
    ACCESS  read-only
    STATUS  mandatory
    DESCRIPTION
        "The minimum amount of time remaining before this entry will aged out."
    ::= { rlIgmpSnoopRouterEntry 3 }

rlIgmpSnoopVlanTable OBJECT-TYPE
    SYNTAX  SEQUENCE OF RlIgmpSnoopVlanEntry
    ACCESS  not-accessible
    STATUS  mandatory
    DESCRIPTION
        "The table listing the per vlan parameters : enable/disable ,
        aging-out timers , filter ports and permanent ports."
    ::= { rlIgmpSnoop 7 }

rlIgmpSnoopVlanEntry OBJECT-TYPE
    SYNTAX  RlIgmpSnoopVlanEntry
    ACCESS  not-accessible
    STATUS  mandatory
    DESCRIPTION
        "An entry (conceptual row) in the rlIgmpSnoopVlanTable."
    INDEX  { rlIgmpSnoopVlanTag }
    ::= { rlIgmpSnoopVlanTable 1 }

RlIgmpSnoopVlanEntry ::= SEQUENCE {
    rlIgmpSnoopVlanTag                  INTEGER,
    rlIgmpSnoopVlanEnable               TruthValue,
    rlIgmpSnoopVlanRouterLearn          TruthValue,
    rlIgmpSnoopVlanHostTimeOut          INTEGER,
    rlIgmpSnoopVlanQuerierTimeOut       INTEGER,
    rlIgmpSnoopVlanRouterTimeOut        INTEGER,
    rlIgmpSnoopVlanLeaveTimeOut         INTEGER
}

rlIgmpSnoopVlanTag OBJECT-TYPE
    SYNTAX  INTEGER
    ACCESS  read-only
    STATUS  mandatory
    DESCRIPTION
        "The tag of the VLAN for which this entry contains
         information for an IP Multicast Router."
    ::= { rlIgmpSnoopVlanEntry 1 }


rlIgmpSnoopVlanEnable OBJECT-TYPE
    SYNTAX  TruthValue
    ACCESS  read-write
    STATUS  mandatory
    DESCRIPTION
        "Enable/Disable IGMP Snooping in the vlan."
    ::= { rlIgmpSnoopVlanEntry 2 }

rlIgmpSnoopVlanRouterLearn OBJECT-TYPE
    SYNTAX  TruthValue
    ACCESS  read-write
    STATUS  mandatory
    DESCRIPTION
        "Enable/Disable of Learning of routers in the vlan."
    ::= { rlIgmpSnoopVlanEntry 3 }

rlIgmpSnoopVlanHostTimeOut OBJECT-TYPE
    SYNTAX  INTEGER (1 .. 2147483647 )
--    UNITS   "seconds"
    ACCESS  read-write
    STATUS  mandatory
    DESCRIPTION
        "The amount of time that should pass before aging out
         an entry in the rlIgmpSnoopGroupTable for this vlan."
    DEFVAL  {250}
    ::= { rlIgmpSnoopVlanEntry 4 }

rlIgmpSnoopVlanQuerierTimeOut OBJECT-TYPE
    SYNTAX  INTEGER (1 .. 2147483647 )
--    UNITS   "seconds"
    ACCESS  read-write
    STATUS  mandatory
    DESCRIPTION
        "The amount of time that should pass before aging out
         an entry in the rlIgmpSnoopRouterTable for this vlan."
    DEFVAL  {260}
    ::= { rlIgmpSnoopVlanEntry 5 }

rlIgmpSnoopVlanRouterTimeOut OBJECT-TYPE
    SYNTAX  INTEGER (1 .. 2147483647 )
--    UNITS   "seconds"
    ACCESS  read-write
    STATUS  mandatory
    DESCRIPTION
        "The amount of time that should pass before aging out
         an entry in the rlIgmpSnoopRouterTable for this vlan."
    DEFVAL  {140}
    ::= { rlIgmpSnoopVlanEntry 6 }

rlIgmpSnoopVlanLeaveTimeOut OBJECT-TYPE
    SYNTAX  INTEGER (0 .. 2147483647 )
--    UNITS   "seconds"
    ACCESS  read-write
    STATUS  mandatory
    DESCRIPTION
        "The amount of time that should pass before aging out
         an entry in the rlIgmpSnoopGroupTable for this vlan, after  recieving a leave
         message from the port of the entry."
    DEFVAL  {10}
    ::= { rlIgmpSnoopVlanEntry 7 }

rlIgmpSnoopIGMP224ReportsHandle OBJECT-TYPE
   SYNTAX  INTEGER {
        allow(1),
        ignore (2)
    }
    ACCESS   read-write
    STATUS   mandatory
    DESCRIPTION
       "This varaiable indicates whether to allow IGMP reports for groups in the
        224.0.0.X range when the group address is already manually configured or to ignore."
    ::= {  rlIgmpSnoop 8 }

rlIgmpSnoopMrouterEnabled OBJECT-TYPE
    SYNTAX  TruthValue
    ACCESS  read-only
    STATUS  mandatory
    DESCRIPTION
        "Indicates whether the device functions as a multicast router."
    ::= {  rlIgmpSnoop 9 }

rlMacMulticastMaxEntriesNum OBJECT-TYPE
    SYNTAX  INTEGER
    ACCESS  read-only
    STATUS  mandatory
    DESCRIPTION
        "The maximum number of Mac Multicast entries the device supports."
    ::= { rlMacMulticast 3 }

rlGalileo OBJECT IDENTIFIER ::= { rnd 56 }

rlpBridgeMIBObjects  OBJECT IDENTIFIER ::= { rnd 57 }

rldot1dPriority  OBJECT IDENTIFIER ::= { rlpBridgeMIBObjects 1 }

rldot1dPriorityMibVersion OBJECT-TYPE
    SYNTAX  INTEGER
    ACCESS  read-only
    STATUS  mandatory
    DESCRIPTION
        "MIB's version, the current version is 1."
    ::= { rldot1dPriority 1 }

--
-- rldot1dPriorityPortGroupTable
--

rldot1dPriorityPortGroupTable  OBJECT-TYPE
    SYNTAX  SEQUENCE OF Rldot1dPriorityPortGroupEntry
    ACCESS  not-accessible
    STATUS  mandatory
    DESCRIPTION
        "A list of PortGroupNumber for each port."
    ::= { rldot1dPriority 2 }

rldot1dPriorityPortGroupEntry OBJECT-TYPE
    SYNTAX  Rldot1dPriorityPortGroupEntry
    ACCESS  not-accessible
    STATUS  mandatory
    DESCRIPTION
        "All ports belonging to a same group have
         the same User Priority to Traffic Class mapping."
   INDEX   { dot1dBasePort }
    ::= { rldot1dPriorityPortGroupTable 1 }

Rldot1dPriorityPortGroupEntry ::= SEQUENCE {
    rldot1dPriorityPortGroupNumber       INTEGER
}

rldot1dPriorityPortGroupNumber OBJECT-TYPE
    SYNTAX  INTEGER
    ACCESS  read-only
    STATUS  mandatory
    DESCRIPTION
        "A group, that port belongs to. All ports belonging
         to a same group have the same User Priority to
         Traffic Class mapping."
    ::= { rldot1dPriorityPortGroupEntry 1 }


rldot1dStp  OBJECT IDENTIFIER ::= { rlpBridgeMIBObjects 2 }

--
-- Scalars
--
rldot1dStpMibVersion OBJECT-TYPE
    SYNTAX  INTEGER
    ACCESS  read-only
    STATUS  mandatory
    DESCRIPTION
        "MIB's version, the current version is 2."
    ::= { rldot1dStp 1 }

rldot1dStpType OBJECT-TYPE
    SYNTAX  INTEGER {
        perDevice  (1),
        mstp       (4)
    }
    ACCESS  read-only
    STATUS  mandatory
    DESCRIPTION
        "Specifies whether the device supports Spanning Tree per device,
         or per group."
    ::= { rldot1dStp 2 }

rldot1dStpEnable OBJECT-TYPE
    SYNTAX  TruthValue
    ACCESS  read-write
    STATUS  mandatory
    DESCRIPTION
        "Enable / Disable spanning tree. When working in per vlan mode
         enable / disable STP per all vlans."
    DEFVAL { true }
    ::= { rldot1dStp 3 }

rldot1dStpPortMustBelongToVlan OBJECT-TYPE
    SYNTAX  TruthValue
    ACCESS  read-write
    STATUS  mandatory
    DESCRIPTION
        "Specifies whether a port must belong to a VLAN in order
         to participate in the STP."
    DEFVAL { true }
    ::= { rldot1dStp 4 }

rldot1dStpExtendedPortNumberFormat OBJECT-TYPE
    SYNTAX  TruthValue
    ACCESS  read-write
    STATUS  mandatory
    DESCRIPTION
        "Specifies whether the STP uses the extended port fnumber format."
    DEFVAL { false }
    ::= { rldot1dStp 5 }

--
--   The Spanning Tree Vlan Table
--
rldot1dStpVlanTable OBJECT-TYPE
    SYNTAX  SEQUENCE OF Rldot1dStpVlanEntry
    ACCESS  not-accessible
    STATUS  mandatory
    DESCRIPTION
            "A table that contains vlan-specific information
            for the Spanning Tree Protocol."
    ::= { rldot1dStp 6 }

rldot1dStpVlanEntry OBJECT-TYPE
    SYNTAX  Rldot1dStpVlanEntry
    ACCESS  not-accessible
    STATUS  mandatory
    DESCRIPTION
        "A list of information maintained by every Vlan
         about the Spanning Tree Protocol state for that
         Vlan."
    INDEX   { rldot1dStpVlan }
    ::= { rldot1dStpVlanTable 1 }

Rldot1dStpVlanEntry ::= SEQUENCE {
    rldot1dStpVlan                      INTEGER,
    rldot1dStpVlanEnable                TruthValue,
    rldot1dStpTimeSinceTopologyChange   TimeTicks,
    rldot1dStpTopChanges                Counter,
    rldot1dStpDesignatedRoot            BridgeId,
    rldot1dStpRootCost                  INTEGER,
    rldot1dStpRootPort                  INTEGER,
    rldot1dStpMaxAge                    Timeout,
    rldot1dStpHelloTime                 Timeout,
    rldot1dStpHoldTime                  INTEGER,
    rldot1dStpForwardDelay              Timeout
}

rldot1dStpVlan OBJECT-TYPE
    SYNTAX  INTEGER
    ACCESS  read-only
    STATUS  mandatory
    DESCRIPTION
        "The Vlan index."
    ::= { rldot1dStpVlanEntry 1 }

rldot1dStpVlanEnable OBJECT-TYPE
    SYNTAX  TruthValue
    ACCESS  read-write
    STATUS  mandatory
    DESCRIPTION
        "Specifies whether this vlan is STP enable or disable"
    REFERENCE
        " ??  "
    DEFVAL { true }
    ::= { rldot1dStpVlanEntry 2 }

rldot1dStpTimeSinceTopologyChange OBJECT-TYPE
    SYNTAX  TimeTicks
    ACCESS  read-only
    STATUS  mandatory
    DESCRIPTION
        "The time (in hundredths of a second) since the
         last time a topology change was detected by the
         bridge entity."
    REFERENCE
        "IEEE 802.1D-1990: Section 6.8.1.1.3"
    ::= { rldot1dStpVlanEntry 3 }

rldot1dStpTopChanges OBJECT-TYPE
    SYNTAX  Counter
    ACCESS  read-only
    STATUS  mandatory
    DESCRIPTION
        "The total number of topology changes detected by
         this bridge since the management entity was last
         reset or initialized."
    REFERENCE
        "IEEE 802.1D-1990: Section 6.8.1.1.3"
    ::= { rldot1dStpVlanEntry 4 }

rldot1dStpDesignatedRoot OBJECT-TYPE
    SYNTAX  BridgeId
    ACCESS  read-only
    STATUS  mandatory
    DESCRIPTION
        "The bridge identifier of the root of the spanning
         tree as determined by the Spanning Tree Protocol
         as executed by this node.  This value is used as
         the Root Identifier parameter in all Configuration
         Bridge PDUs originated by this node."
    REFERENCE
        "IEEE 802.1D-1990: Section 4.5.3.1"
    ::= { rldot1dStpVlanEntry 5 }

rldot1dStpRootCost OBJECT-TYPE
    SYNTAX  INTEGER
    ACCESS  read-only
    STATUS  mandatory
    DESCRIPTION
        "The cost of the path to the root as seen from
         this bridge."
    REFERENCE
        "IEEE 802.1D-1990: Section 4.5.3.2"
    ::= { rldot1dStpVlanEntry 6 }

rldot1dStpRootPort OBJECT-TYPE
    SYNTAX  INTEGER
    ACCESS  read-only
    STATUS  mandatory
    DESCRIPTION
        "The port number of the port which offers the
         lowest cost path from this bridge to the root
         bridge."
    REFERENCE
        "IEEE 802.1D-1990: Section 4.5.3.3"
    ::= { rldot1dStpVlanEntry 7 }

rldot1dStpMaxAge OBJECT-TYPE
    SYNTAX  Timeout
    ACCESS  read-only
    STATUS  mandatory
    DESCRIPTION
        "The maximum age of Spanning Tree Protocol
         information learned from the network on any port
         before it is discarded, in units of hundredths of
         a second.  This is the actual value that this
         bridge is currently using."
    REFERENCE
        "IEEE 802.1D-1990: Section 4.5.3.4"
    ::= { rldot1dStpVlanEntry 8 }

rldot1dStpHelloTime OBJECT-TYPE
    SYNTAX  Timeout
    ACCESS  read-only
    STATUS  mandatory
    DESCRIPTION
        "The amount of time between the transmission of
         Configuration bridge PDUs by this node on any port
         when it is the root of the spanning tree or trying
         to become so, in units of hundredths of a second.
         This is the actual value that this bridge is
         currently using."
    REFERENCE
        "IEEE 802.1D-1990: Section 4.5.3.5"
    ::= { rldot1dStpVlanEntry 9 }

rldot1dStpHoldTime OBJECT-TYPE
    SYNTAX  INTEGER
    ACCESS  read-only
    STATUS  mandatory
    DESCRIPTION
        "This time value determines the interval length
         during which no more than two Configuration bridge
         PDUs shall be transmitted by this node, in units
         of hundredths of a second."
    REFERENCE
        "IEEE 802.1D-1990: Section 4.5.3.14"
    ::= { rldot1dStpVlanEntry 10 }

rldot1dStpForwardDelay OBJECT-TYPE
    SYNTAX  Timeout
    ACCESS  read-only
    STATUS  mandatory
    DESCRIPTION
        "This time value, measured in units of hundredths
         of a second, controls how fast a port changes its
         spanning state when moving towards the Forwarding
         state.  The value determines how long the port
         stays in each of the Listening and Learning
         states, which precede the Forwarding state.  This
         value is also used, when a topology change has
         been detected and is underway, to age all dynamic
         entries in the Forwarding Database.  [Note that
         this value is the one that this bridge is
         currently using, in contrast to
         dot1dStpBridgeForwardDelay which is the value that
         this bridge and all others would start using
         if/when this bridge were to become the root.]"
    REFERENCE
        "IEEE 802.1D-1990: Section 4.5.3.6"
    ::= { rldot1dStpVlanEntry 11 }

--
-- rldot1dStpVlanPortTable
--
rldot1dStpVlanPortTable OBJECT-TYPE
    SYNTAX  SEQUENCE OF Rldot1dStpVlanPortEntry
    ACCESS  not-accessible
    STATUS  mandatory
    DESCRIPTION
        "A table that contains pair <vlan, port> specific information
         for the Spanning Tree Protocol."
    ::= { rldot1dStp 7 }

rldot1dStpVlanPortEntry OBJECT-TYPE
    SYNTAX  Rldot1dStpVlanPortEntry
    ACCESS  not-accessible
    STATUS  mandatory
    DESCRIPTION
        "A list of information maintained by every pair <vlan, port>
         about the Spanning Tree Protocol state for that pair."
    INDEX   { rldot1dStpVlanPortVlan, rldot1dStpVlanPortPort }
    ::= { rldot1dStpVlanPortTable 1 }

Rldot1dStpVlanPortEntry ::= SEQUENCE {
    rldot1dStpVlanPortVlan                  INTEGER,
    rldot1dStpVlanPortPort                  INTEGER,
    rldot1dStpVlanPortPriority              INTEGER,
    rldot1dStpVlanPortState                 INTEGER,
    rldot1dStpVlanPortEnable                INTEGER,
    rldot1dStpVlanPortPathCost              INTEGER,
    rldot1dStpVlanPortDesignatedRoot        BridgeId,
    rldot1dStpVlanPortDesignatedCost        INTEGER,
    rldot1dStpVlanPortDesignatedBridge      BridgeId,
    rldot1dStpVlanPortDesignatedPort        OCTET STRING,
    rldot1dStpVlanPortForwardTransitions    Counter
}

rldot1dStpVlanPortVlan OBJECT-TYPE
    SYNTAX  INTEGER (1..4095)
    ACCESS  read-only
    STATUS  mandatory
    DESCRIPTION
        "The Vlan number that the port belongs to, and for which this entry
         contains Spanning Tree Protocol management
         information."
    REFERENCE
         "IEEE 802.1s/D2-1999 "
    ::= { rldot1dStpVlanPortEntry 1 }

rldot1dStpVlanPortPort OBJECT-TYPE
    SYNTAX  INTEGER (1..4096)
    ACCESS  read-only
    STATUS  mandatory
    DESCRIPTION
        "The port number of the port for which this entry
         contains Spanning Tree Protocol management
         information."
    REFERENCE
         "IEEE 802.1t/D2-1999: Section 9.2.6"
    ::= { rldot1dStpVlanPortEntry 2 }

rldot1dStpVlanPortPriority OBJECT-TYPE
    SYNTAX  INTEGER (0..255)
    ACCESS  read-write
    STATUS  mandatory
    DESCRIPTION
        "The value of the priority field which is
         contained in the more significant  4 bits of the most
         significant octet of the (2 octet long) Port ID.
         The other octet of the Port ID is given by the value
         of rldot1dStpVlanPort."
    REFERENCE
        "IEEE 802.1t/D2-1999: Section 9.2.6"
    ::= { rldot1dStpVlanPortEntry 3 }

rldot1dStpVlanPortState OBJECT-TYPE
    SYNTAX  INTEGER {
        disabled(1),
        blocking(2),
        listening(3),
        learning(4),
        forwarding(5),
        broken(6)
    }
    ACCESS  read-only
    STATUS  mandatory
    DESCRIPTION
        "The port's current state as defined by application of
         the Spanning Tree Protocol. This state controls what
         action a port takes on reception of a frame.
         If the bridge has detected a port that is malfunctioning
         it will place that port into the broken(6) state.  For ports
         which are disabled (see dot1dStpVlanPortEnable), this object
         will have a value of disabled(1)."
    REFERENCE
            "IEEE 802.1D-1990: Section 4.5.5.2"
    ::= { rldot1dStpVlanPortEntry 4 }

rldot1dStpVlanPortEnable OBJECT-TYPE
    SYNTAX  INTEGER {
        enabled(1),
        disabled(2)
    }
    ACCESS  read-write
    STATUS  mandatory
    DESCRIPTION
        "The enabled/disabled status of the port."
    REFERENCE
        "IEEE 802.1D-1990: Section 4.5.5.2"
    ::= { rldot1dStpVlanPortEntry 5 }

rldot1dStpVlanPortPathCost OBJECT-TYPE
    SYNTAX  INTEGER (1..65535)
    ACCESS  read-write
    STATUS  mandatory
    DESCRIPTION
        "The contribution of this port to the path cost of
         paths towards the spanning tree root which include
         this port.  802.1D-1990 recommends that the
         default value of this parameter be in inverse
         proportion to the speed of the attached LAN."
    REFERENCE
        "IEEE 802.1D-1990: Section 4.5.5.3"
    ::= { rldot1dStpVlanPortEntry 6 }

rldot1dStpVlanPortDesignatedRoot OBJECT-TYPE
    SYNTAX  BridgeId
    ACCESS  read-only
    STATUS  mandatory
    DESCRIPTION
        "The unique Bridge Identifier of the Bridge
         recorded as the Root in the Configuration BPDUs
         transmitted by the Designated Bridge for the
         segment to which the port is attached."
    REFERENCE
        "IEEE 802.1D-1990: Section 4.5.5.4"
    ::= { rldot1dStpVlanPortEntry 7 }

rldot1dStpVlanPortDesignatedCost OBJECT-TYPE
    SYNTAX  INTEGER
    ACCESS  read-only
    STATUS  mandatory
    DESCRIPTION
        "The path cost of the Designated Port of the
         segment connected to this port.  This value is
         compared to the Root Path Cost field in received
         bridge PDUs."
    REFERENCE
        "IEEE 802.1D-1990: Section 4.5.5.5"
    ::= { rldot1dStpVlanPortEntry 8 }

rldot1dStpVlanPortDesignatedBridge OBJECT-TYPE
    SYNTAX  BridgeId
    ACCESS  read-only
    STATUS  mandatory
    DESCRIPTION
        "The Bridge Identifier of the bridge which this
         port considers to be the Designated Bridge for
         this port's segment."
    REFERENCE
        "IEEE 802.1D-1990: Section 4.5.5.6"
    ::= { rldot1dStpVlanPortEntry 9 }

rldot1dStpVlanPortDesignatedPort OBJECT-TYPE
    SYNTAX  OCTET STRING (SIZE (2))
    ACCESS  read-only
    STATUS  mandatory
    DESCRIPTION
        "The Port Identifier of the port on the Designated
         Bridge for this port's segment."
    REFERENCE
        "IEEE 802.1D-1990: Section 4.5.5.7"
    ::= { rldot1dStpVlanPortEntry 10 }

rldot1dStpVlanPortForwardTransitions OBJECT-TYPE
    SYNTAX  Counter
    ACCESS  read-only
    STATUS  mandatory
    DESCRIPTION
        "The number of times this port has transitioned
         from the Learning state to the Forwarding state."
    ::= { rldot1dStpVlanPortEntry 11 }

--
-- STP Private TRAP variables
--
rldot1dStpTrapVariable  OBJECT IDENTIFIER ::= { rldot1dStp 8 }

rldot1dStpTrapVrblifIndex OBJECT-TYPE
    SYNTAX InterfaceIndex
    ACCESS  read-only
    STATUS  mandatory
    DESCRIPTION
       "The ifIndex of port which STP status was changed"
    ::= { rldot1dStpTrapVariable 1  }

rldot1dStpTrapVrblVID OBJECT-TYPE
    SYNTAX INTEGER
    ACCESS  read-only
    STATUS  mandatory
    DESCRIPTION
       "The VID of VLAN to which the port belongs which STP status was changed"
    ::= { rldot1dStpTrapVariable 2  }

rldot1dStpTypeAfterReset OBJECT-TYPE
    SYNTAX  INTEGER {
        perDevice(1),
        mstp(4)
    }
    ACCESS  read-write
    STATUS  mandatory
    DESCRIPTION
        "New mode of spaning tree supported by the device after the next reset."
    DEFVAL { perDevice }
    ::= { rldot1dStp 9 }

rldot1dStpMonitorTime OBJECT-TYPE
    SYNTAX  INTEGER (1..20)
    ACCESS  read-write
    STATUS  mandatory
    DESCRIPTION
        "Factor of hello-time during which a port is monotored to determine if it is stable."
    DEFVAL { 10 }
    ::= { rldot1dStp 10 }

rldot1dStpBpduCount OBJECT-TYPE
    SYNTAX  INTEGER (1..60)
    ACCESS  read-write
    STATUS  mandatory
    DESCRIPTION
        "The number of bpdu that need to received for the link to be considered stable."
    DEFVAL { 10 }
    ::= { rldot1dStp 11 }

rldot1dStpLastChanged  OBJECT-TYPE
    SYNTAX  TimeTicks
    ACCESS  read-only
    STATUS  mandatory
    DESCRIPTION
         "The last time any object in this table was changed
          by SNMP or other local management means."
    REFERENCE
        ""
    ::= { rldot1dStp 12 }

--
-- rldot1dStpPortTable
--
rldot1dStpPortTable OBJECT-TYPE
    SYNTAX  SEQUENCE OF Rldot1dStpPortEntry
    ACCESS  not-accessible
    STATUS  mandatory
    DESCRIPTION
        "A table that contains extended pair port specific information."
    ::= { rldot1dStp 13 }

rldot1dStpPortEntry OBJECT-TYPE
    SYNTAX  Rldot1dStpPortEntry
    ACCESS  not-accessible
    STATUS  mandatory
    DESCRIPTION
        "A list of information maintained by every port
         about the Spanning Tree Protocol state for that port."
    INDEX   { rldot1dStpPortPort }
    ::= { rldot1dStpPortTable 1 }

Rldot1dStpPortEntry ::= SEQUENCE {
    rldot1dStpPortPort                  INTEGER,
    rldot1dStpPortDampEnable            TruthValue,
    rldot1dStpPortDampStable            TruthValue,
    rldot1dStpPortFilterBpdu            TruthValue,
    rldot1dStpPortBpduSent              Counter,
    rldot1dStpPortBpduReceived          Counter,
    rldot1dStpPortRole                  INTEGER,
    rldot1dStpBpduType                  INTEGER
}

rldot1dStpPortPort OBJECT-TYPE
    SYNTAX  INTEGER (1..4096)
    ACCESS  read-only
    STATUS  mandatory
    DESCRIPTION
        "The port number of the port for which this entry
         contains Spanning Tree Protocol management
         information."
    REFERENCE
         "IEEE 802.1t/D2-1999: Section 9.2.6"
    ::= { rldot1dStpPortEntry 1 }

rldot1dStpPortDampEnable OBJECT-TYPE
    SYNTAX  TruthValue
    ACCESS  read-write
    STATUS  mandatory
    DESCRIPTION
        "Specified if dampening is enabled on this port."
    REFERENCE
        ""
    DEFVAL { false }
    ::= { rldot1dStpPortEntry 2 }

rldot1dStpPortDampStable OBJECT-TYPE
    SYNTAX  TruthValue
    ACCESS  read-only
    STATUS  mandatory
    DESCRIPTION
        "Specified if the port is stable."
    REFERENCE
        ""
    DEFVAL { true }
    ::= { rldot1dStpPortEntry 3 }

rldot1dStpPortFilterBpdu OBJECT-TYPE
    SYNTAX  TruthValue
    ACCESS  read-write
    STATUS  mandatory
    DESCRIPTION
        "Specified if this port should filter bpdus when stp is disabled."
    REFERENCE
        ""
    DEFVAL { false }
    ::= { rldot1dStpPortEntry 4 }

rldot1dStpPortBpduSent OBJECT-TYPE
    SYNTAX  Counter
    ACCESS  read-only
    STATUS  mandatory
    DESCRIPTION
        "Specified the number of bpdu sent from this port."
    REFERENCE
        ""
    ::= { rldot1dStpPortEntry 5 }

rldot1dStpPortBpduReceived OBJECT-TYPE
    SYNTAX  Counter
    ACCESS  read-only
    STATUS  mandatory
    DESCRIPTION
        "Specified the number of bpdu received in this port."
    REFERENCE
        ""
    ::= { rldot1dStpPortEntry 6 }

rldot1dStpPortRole OBJECT-TYPE
    SYNTAX  INTEGER {
                    unknown(0),
                    disabled(1),
                    alternate(2),
                    backup(3),
                    root(4),
                    designated(5)
                }

    ACCESS  read-only
    STATUS  mandatory
    DESCRIPTION
        "Specified the role of this this port."
    REFERENCE
        ""
    ::= { rldot1dStpPortEntry 7 }

rldot1dStpBpduType OBJECT-TYPE
    SYNTAX  INTEGER {
        stp(0),
        rstp(1)
    }
    ACCESS  read-only
    STATUS  mandatory
    DESCRIPTION
        "Specified the type of BPDU transmitted by this port."
    ::= { rldot1dStpPortEntry 8 }

rldot1dStpPortsEnable OBJECT-TYPE
    SYNTAX  TruthValue
    ACCESS  read-only
    STATUS  mandatory
    DESCRIPTION
        "Enable / Disable spanning tree on ports by default ."
    DEFVAL { true }
    ::= { rldot1dStp 14 }

rldot1dStpTaggedFlooding OBJECT-TYPE
    SYNTAX  TruthValue
    ACCESS  read-only
    STATUS  mandatory
    DESCRIPTION
        "flooding can be done in tagged bpdu ."
    ::= { rldot1dStp 15 }

rldot1dStpPortBelongToVlanDefault OBJECT-TYPE
    SYNTAX  TruthValue
    ACCESS  read-only
    STATUS  mandatory
    DESCRIPTION
        "The default value of rldot1dStpPortMustBelongToVlan ."
    ::= { rldot1dStp 16 }

rldot1dStpEnableByDefault OBJECT-TYPE
    SYNTAX  TruthValue
    ACCESS  read-only
    STATUS  mandatory
    DESCRIPTION
        "The default value of rldot1dStpEnable ."
    ::= { rldot1dStp 17 }

rldot1dStpPortToDefault OBJECT-TYPE
    SYNTAX  INTEGER
    ACCESS  read-write
    STATUS  mandatory
    DESCRIPTION
        "To order port/s to revert to default setings ."
    ::= { rldot1dStp 18 }

rldot1dStpSupportedType OBJECT-TYPE
    SYNTAX  INTEGER {
        perDevice(1),
        perVlan(2),
        mstp(3)
    }
    ACCESS  read-only
    STATUS  mandatory
    DESCRIPTION
        "The type of stp supported by the device."
    ::= { rldot1dStp 19 }

rldot1dStpEdgeportSupportInStp OBJECT-TYPE
    SYNTAX  TruthValue
    ACCESS  read-only
    STATUS  mandatory
    DESCRIPTION
        "If EdgePort is supported in stpCompatible mode ."
    ::= { rldot1dStp 20 }

rldot1dStpFilterBpdu OBJECT-TYPE
    SYNTAX  TruthValue
    ACCESS  read-write
    STATUS  mandatory
    DESCRIPTION
        "Specified if the device should filter BPDUs when STP is disabled."
    ::= { rldot1dStp 21 }

rldot1dExtBase  OBJECT IDENTIFIER ::= { rlpBridgeMIBObjects 3 }

rldot1dExtBaseMibVersion OBJECT-TYPE
    SYNTAX  INTEGER
    ACCESS  read-only
    STATUS  mandatory
    DESCRIPTION
        "MIB's version, the current version is 1."
    ::= { rldot1dExtBase 1 }

rldot1dDeviceCapabilities OBJECT-TYPE
--    SYNTAX      BITS {
--        rldot1dIGMPSnoopingFilteringServices(0)
--                              ## can perform filtering of
--                              ## individual multicast addresses
--                              ## controlled by IGMP snooping.
--        rldot1dDefaultFilteringAllServices(1)
--                              ## can perform default filtering
--                              ## behavior for All multicast addresses.
--                              ## controlled by Multicast DB.
--        rldot1dDefaultFilteringUnregServices(2)
--                              ## can perform default filtering
--                              ## behavior for Unregistered
--                              ## multicast addresses.
--                              ## controlled by Multicast DB.
--    }
    SYNTAX  OCTET STRING (SIZE(1))
    ACCESS  read-only
    STATUS  mandatory
    DESCRIPTION
        "Indicates the optional parts of private extension of
         IEEE 802.1D and 802.1Q that are implemented by this
         device and are manageable through this MIB.
         Capabilities that are allowed on a per-port basis are
         indicated in dot1dPortCapabilities."
    ::= { rldot1dExtBase 2 }

rldot1wRStp  OBJECT IDENTIFIER ::= { rlpBridgeMIBObjects 4 }

--
-- rldot1wStpVlanEdgePortTable
--
rldot1wRStpVlanEdgePortTable OBJECT-TYPE
    SYNTAX  SEQUENCE OF Rldot1wRStpVlanEdgePortEntry
    ACCESS  not-accessible
    STATUS  mandatory
    DESCRIPTION
        "A table that contains pair <vlan, port> specific information
         for the Rapid Spanning Tree Protocol."
    ::= { rldot1wRStp 1 }

rldot1wRStpVlanEdgePortEntry OBJECT-TYPE
    SYNTAX  Rldot1wRStpVlanEdgePortEntry
    ACCESS  not-accessible
    STATUS  mandatory
    DESCRIPTION
        "A list of information maintained by every pair <vlan, port>
         about the RAPID Spanning Tree Protocol state for that pair."
    INDEX   { rldot1wRStpVlanEdgePortVlan, rldot1wRStpVlanEdgePortPort }
    ::= { rldot1wRStpVlanEdgePortTable 1 }

Rldot1wRStpVlanEdgePortEntry ::= SEQUENCE {
    rldot1wRStpVlanEdgePortVlan         INTEGER,
    rldot1wRStpVlanEdgePortPort         INTEGER,
    rldot1wRStpEdgePortStatus           TruthValue
}

rldot1wRStpVlanEdgePortVlan OBJECT-TYPE
    SYNTAX  INTEGER (1..4095)
    ACCESS  read-only
    STATUS  mandatory
    DESCRIPTION
        "The Vlan number that the port belongs to, and for which this entry
         contains Spanning Tree Protocol management information,
         If STP per device then only one value of 1 is allowed.
         If STP per a VLAN then all value of 1..4095 are allowed."
    ::= { rldot1wRStpVlanEdgePortEntry 1 }

rldot1wRStpVlanEdgePortPort OBJECT-TYPE
    SYNTAX  INTEGER
    ACCESS  read-only
    STATUS  mandatory
    DESCRIPTION
        "The port number of the port for which this entry
         contains Spanning Tree Protocol management information."
    ::= { rldot1wRStpVlanEdgePortEntry 2 }

rldot1wRStpEdgePortStatus OBJECT-TYPE
    SYNTAX  TruthValue
    ACCESS  read-write
    STATUS  mandatory
    DESCRIPTION
        "Specifies whether this port is an Edge Port or not"
    REFERENCE
        "IEEE 802.1wd6-2000: Section 17.13.3.1 "
    DEFVAL { false }
    ::= { rldot1wRStpVlanEdgePortEntry 3 }

--
-- rldot1wStpForceVersionTable
--
rldot1wRStpForceVersionTable OBJECT-TYPE
    SYNTAX  SEQUENCE OF Rldot1wRStpForceVersionEntry
    ACCESS  not-accessible
    STATUS  mandatory
    DESCRIPTION
        "A table that contains  <vlan> specific information
         for the Rapid Spanning Tree Protocol."
    ::= { rldot1wRStp 2 }

rldot1wRStpForceVersionEntry OBJECT-TYPE
    SYNTAX  Rldot1wRStpForceVersionEntry
    ACCESS  not-accessible
    STATUS  mandatory
    DESCRIPTION
        "A list of information maintained by every  <vlan>
         about the RAPID Spanning Tree Protocol state for that pair."
    INDEX   { rldot1wRStpForceVersionVlan }
    ::= { rldot1wRStpForceVersionTable 1 }

Rldot1wRStpForceVersionEntry ::= SEQUENCE {
    rldot1wRStpForceVersionVlan         INTEGER,
    rldot1wRStpForceVersionState        INTEGER
}

rldot1wRStpForceVersionVlan OBJECT-TYPE
    SYNTAX  INTEGER (1..4095)
    ACCESS  read-only
    STATUS  mandatory
    DESCRIPTION
        "The Vlan number that the port belongs to, and for which this entry
         contains Spanning Tree Protocol management information,
         If STP per device then only one value of 1 is allowed.
         If STP per a VLAN then all value of 1..4095 are allowed."
    ::= { rldot1wRStpForceVersionEntry 1 }

rldot1wRStpForceVersionState OBJECT-TYPE
    SYNTAX  INTEGER
    ACCESS  read-write
    STATUS  mandatory
    DESCRIPTION
        "Specifies whether this Bridge uses the normal RSTP algorithm,
         or STP Compatibility algorythm:
         0 - STP Compatibility
         2 - Normal RSTP"
    REFERENCE
        "IEEE 802.1wd9-2000: Section 17.16.1 "
    DEFVAL { 2 }
    ::= { rldot1wRStpForceVersionEntry 2 }

rldot1pPriorityMap  OBJECT IDENTIFIER ::= { rlpBridgeMIBObjects 5 }

rldot1pPriorityMapState OBJECT-TYPE
   SYNTAX  INTEGER {
        enable (1),
        disable (2)
   }
   ACCESS read-write
   STATUS mandatory
   DESCRIPTION
       "enable / disable"
   ::= { rldot1pPriorityMap 1 }

rldot1pPriorityMapTable OBJECT-TYPE
    SYNTAX  SEQUENCE OF Rldot1pPriorityMapEntry
    ACCESS  not-accessible
    STATUS  mandatory
    DESCRIPTION
        "This table hold information the priority maps"
    ::= { rldot1pPriorityMap 2 }

rldot1pPriorityMapEntry OBJECT-TYPE
    SYNTAX  Rldot1pPriorityMapEntry
    ACCESS  not-accessible
    STATUS  mandatory
    DESCRIPTION
        "The row definition for this table."
    INDEX { rldot1pPriorityMapName }
    ::= { rldot1pPriorityMapTable 1 }

Rldot1pPriorityMapEntry ::= SEQUENCE {
    rldot1pPriorityMapName     DisplayString,
    rldot1pPriorityMapPriority OCTET STRING,
    rldot1pPriorityMapPort     PortList,
    rldot1pPriorityMapPortList PortList,
    rldot1pPriorityMapStatus   RowStatus
}

rldot1pPriorityMapName OBJECT-TYPE
    SYNTAX  DisplayString (SIZE (1..25))
    ACCESS  read-only
    STATUS  mandatory
    DESCRIPTION
        "The map name"
    ::=  { rldot1pPriorityMapEntry 1 }

rldot1pPriorityMapPriority OBJECT-TYPE
    SYNTAX  OCTET STRING (SIZE (8))
    ACCESS  read-write
    STATUS  mandatory
    DESCRIPTION
        "The map holding the queue"
    ::=  { rldot1pPriorityMapEntry 2 }

rldot1pPriorityMapPort OBJECT-TYPE
    SYNTAX      PortList
    ACCESS      read-write
    STATUS      mandatory
    DESCRIPTION
        "the port that the map, is applied on in config"
    ::= { rldot1pPriorityMapEntry 3 }

rldot1pPriorityMapPortList OBJECT-TYPE
    SYNTAX      PortList
    ACCESS      read-only
    STATUS      mandatory
    DESCRIPTION
        "the ports that the map, is applied on in actual"
    ::= { rldot1pPriorityMapEntry 4 }

rldot1pPriorityMapStatus OBJECT-TYPE
    SYNTAX  RowStatus
    ACCESS  read-write
    STATUS  mandatory
    DESCRIPTION
        "The status of the  table entry. It's used to delete an entry"
    ::= { rldot1pPriorityMapEntry 5 }

rldot1sMstp  OBJECT IDENTIFIER ::= { rlpBridgeMIBObjects 6 }

--
--   The Multiple Spanning Tree Instance Table
--
rldot1sMstpInstanceTable OBJECT-TYPE
    SYNTAX  SEQUENCE OF Rldot1sMstpInstanceEntry
    ACCESS  not-accessible
    STATUS  mandatory
    DESCRIPTION
            "A table that contains Mstp instance specific information
            for the Multiple Spanning Tree Protocol."
    ::= { rldot1sMstp 1 }

rldot1sMstpInstanceEntry OBJECT-TYPE
    SYNTAX  Rldot1sMstpInstanceEntry
    ACCESS  not-accessible
    STATUS  mandatory
    DESCRIPTION
        "A list of information maintained by every instance
         about the multiple Spanning Tree Protocol state for
         that instance."
    INDEX   { rldot1sMstpInstanceId }
    ::= { rldot1sMstpInstanceTable 1 }

Rldot1sMstpInstanceEntry ::= SEQUENCE {
    rldot1sMstpInstanceId                        INTEGER,
    rldot1sMstpInstanceEnable                    TruthValue,
    rldot1sMstpInstanceTimeSinceTopologyChange   TimeTicks,
    rldot1sMstpInstanceTopChanges                Counter,
    rldot1sMstpInstanceDesignatedRoot            BridgeId,
    rldot1sMstpInstanceRootCost                  INTEGER,
    rldot1sMstpInstanceRootPort                  INTEGER,
    rldot1sMstpInstanceMaxAge                    Timeout,
    rldot1sMstpInstanceHelloTime                 Timeout,
    rldot1sMstpInstanceHoldTime                  INTEGER,
    rldot1sMstpInstanceForwardDelay              Timeout,
    rldot1sMstpInstancePriority                  INTEGER,
    rldot1sMstpInstanceRemainingHopes            INTEGER
}

rldot1sMstpInstanceId OBJECT-TYPE
    SYNTAX  INTEGER (1..64)
    ACCESS  read-only
    STATUS  mandatory
    DESCRIPTION
        "The Instance index."
    ::= { rldot1sMstpInstanceEntry 1 }

rldot1sMstpInstanceEnable OBJECT-TYPE
    SYNTAX  TruthValue
    ACCESS  read-only
    STATUS  mandatory
    DESCRIPTION
        "Specifies whether this Instance is STP enable or disable"
    REFERENCE
        " ??  "
    ::= { rldot1sMstpInstanceEntry 2 }

rldot1sMstpInstanceTimeSinceTopologyChange OBJECT-TYPE
    SYNTAX  TimeTicks
    ACCESS  read-only
    STATUS  mandatory
    DESCRIPTION
        "The time (in hundredths of a second) since the
         last time a topology change was detected by the
         Mstp Instance ."
    REFERENCE
        "IEEE 802.1D-1990: Section 6.8.1.1.3"
    ::= { rldot1sMstpInstanceEntry 3 }

rldot1sMstpInstanceTopChanges OBJECT-TYPE
    SYNTAX  Counter
    ACCESS  read-only
    STATUS  mandatory
    DESCRIPTION
        "The total number of topology changes detected by
         this Instance since the management entity was last
         reset or initialized."
    REFERENCE
        "IEEE 802.1D-1990: Section 6.8.1.1.3"
    ::= { rldot1sMstpInstanceEntry 4 }

rldot1sMstpInstanceDesignatedRoot OBJECT-TYPE
    SYNTAX  BridgeId
    ACCESS  read-only
    STATUS  mandatory
    DESCRIPTION
        "The bridge identifier of the root of the spanning
         tree as determined by the Muliple Spanning Tree Protocol
         as executed by this node.  This value is used as
         the Root Identifier parameter in all Configuration
         Bridge PDUs originated by this node."
    REFERENCE
        "IEEE 802.1D-1990: Section 4.5.3.1"
    ::= { rldot1sMstpInstanceEntry 5 }

rldot1sMstpInstanceRootCost OBJECT-TYPE
    SYNTAX  INTEGER
    ACCESS  read-only
    STATUS  mandatory
    DESCRIPTION
        "The cost of the path to the root as seen from
         this bridge."
    REFERENCE
        "IEEE 802.1D-1990: Section 4.5.3.2"
    ::= { rldot1sMstpInstanceEntry 6 }

rldot1sMstpInstanceRootPort OBJECT-TYPE
    SYNTAX  INTEGER
    ACCESS  read-only
    STATUS  mandatory
    DESCRIPTION
        "The port number of the port which offers the
         lowest cost path from this bridge to the root
         bridge."
    REFERENCE
        "IEEE 802.1D-1990: Section 4.5.3.3"
    ::= { rldot1sMstpInstanceEntry 7 }

rldot1sMstpInstanceMaxAge OBJECT-TYPE
    SYNTAX  Timeout
    ACCESS  read-only
    STATUS  mandatory
    DESCRIPTION
        "The maximum age of Spanning Tree Protocol
         information learned from the network on any port
         before it is discarded, in units of hundredths of
         a second.  This is the actual value that this
         bridge is currently using."
    REFERENCE
        "IEEE 802.1D-1990: Section 4.5.3.4"
    ::= { rldot1sMstpInstanceEntry 8 }

rldot1sMstpInstanceHelloTime OBJECT-TYPE
    SYNTAX  Timeout
    ACCESS  read-only
    STATUS  mandatory
    DESCRIPTION
        "The amount of time between the transmission of
         Configuration bridge PDUs by this node on any port
         when it is the root of the spanning tree or trying
         to become so, in units of hundredths of a second.
         This is the actual value that this bridge is
         currently using."
    REFERENCE
        "IEEE 802.1D-1990: Section 4.5.3.5"
    ::= { rldot1sMstpInstanceEntry 9 }

rldot1sMstpInstanceHoldTime OBJECT-TYPE
    SYNTAX  INTEGER
    ACCESS  read-only
    STATUS  mandatory
    DESCRIPTION
        "This time value determines the interval length
         during which no more than two Configuration bridge
         PDUs shall be transmitted by this node, in units
         of hundredths of a second."
    REFERENCE
        "IEEE 802.1D-1990: Section 4.5.3.14"
    ::= { rldot1sMstpInstanceEntry 10 }

rldot1sMstpInstanceForwardDelay OBJECT-TYPE
    SYNTAX  Timeout
    ACCESS  read-only
    STATUS  mandatory
    DESCRIPTION
        "This time value, measured in units of hundredths
         of a second, controls how fast a port changes its
         spanning state when moving towards the Forwarding
         state.  The value determines how long the port
         stays in each of the Listening and Learning
         states, which precede the Forwarding state.  This
         value is also used, when a topology change has
         been detected and is underway, to age all dynamic
         entries in the Forwarding Database.  [Note that
         this value is the one that this bridge is
         currently using, in contrast to
         dot1dStpBridgeForwardDelay which is the value that
         this bridge and all others would start using
         if/when this bridge were to become the root.]"
    REFERENCE
        "IEEE 802.1D-1990: Section 4.5.3.6"
    ::= { rldot1sMstpInstanceEntry 11 }

rldot1sMstpInstancePriority OBJECT-TYPE
    SYNTAX  INTEGER (0..61440)
    ACCESS  read-write
    STATUS  mandatory
    DESCRIPTION
            "The value of the write-able portion of the Bridge
            ID, i.e., the first four bits of the first octet
            of the (8 octet long) Bridge ID.The value is a product
            of 4096. The next 12 bit are the msti id .
            The other (last) 6 octets of the Bridge ID are given
            by the value of dot1dBaseBridgeAddress."
    REFERENCE
            "IEEE 802.1S-2001: Section 13.24.2"
    ::= {rldot1sMstpInstanceEntry 12 }

rldot1sMstpInstanceRemainingHopes OBJECT-TYPE
    SYNTAX  INTEGER
    ACCESS  read-only
    STATUS  mandatory
    DESCRIPTION
        "This count value determines the amount of hopes
         the information transmited by this bridge on this
         instance can travel."
    REFERENCE
        "IEEE 802.1D-1990: Section 4.5.3.14"
    ::= { rldot1sMstpInstanceEntry 13 }

--
-- rldot1sMstpInstancePortTable
--
rldot1sMstpInstancePortTable OBJECT-TYPE
    SYNTAX  SEQUENCE OF Rldot1sMstpInstancePortEntry
    ACCESS  not-accessible
    STATUS  mandatory
    DESCRIPTION
        "A table that contains pair <msti, port> specific information
         for the Spanning Tree Protocol."
    ::= { rldot1sMstp 2 }

rldot1sMstpInstancePortEntry OBJECT-TYPE
    SYNTAX  Rldot1sMstpInstancePortEntry
    ACCESS  not-accessible
    STATUS  mandatory
    DESCRIPTION
        "A list of information maintained by every pair <msti, port>
         about the Spanning Tree Protocol state for that pair."
    INDEX   { rldot1sMstpInstancePortMstiId, rldot1sMstpInstancePortPort }
    ::= { rldot1sMstpInstancePortTable 1 }

Rldot1sMstpInstancePortEntry ::= SEQUENCE {
    rldot1sMstpInstancePortMstiId                INTEGER,
    rldot1sMstpInstancePortPort                  INTEGER,
    rldot1sMstpInstancePortPriority              INTEGER,
    rldot1sMstpInstancePortState                 INTEGER,
    rldot1sMstpInstancePortEnable                INTEGER,
    rldot1sMstpInstancePortPathCost              INTEGER,
    rldot1sMstpInstancePortDesignatedRoot        BridgeId,
    rldot1sMstpInstancePortDesignatedCost        INTEGER,
    rldot1sMstpInstancePortDesignatedBridge      BridgeId,
    rldot1sMstpInstancePortDesignatedPort        OCTET STRING,
    rldot1sMstpInstancePortForwardTransitions    Counter,
    rldot1sMStpInstancePortAdminPathCost         INTEGER,
    rldot1sMStpInstancePortRole                  INTEGER

}

rldot1sMstpInstancePortMstiId OBJECT-TYPE
    SYNTAX  INTEGER (1..64)
    ACCESS  read-only
    STATUS  mandatory
    DESCRIPTION
        "The Vlan group number that the port belongs to, and for which this entry
         contains Spanning Tree Protocol management
         information."
    REFERENCE
         "IEEE 802.1s/D11-2001 "
    ::= { rldot1sMstpInstancePortEntry 1 }

rldot1sMstpInstancePortPort OBJECT-TYPE
    SYNTAX  INTEGER (1..4096)
    ACCESS  read-only
    STATUS  mandatory
    DESCRIPTION
        "The port number of the port for which this entry
         contains Spanning Tree Protocol management
         information."
    REFERENCE
         "IEEE 802.1t/D2-1999: Section 9.2.6"
    ::= { rldot1sMstpInstancePortEntry 2 }

rldot1sMstpInstancePortPriority OBJECT-TYPE
    SYNTAX  INTEGER (0..240)
    ACCESS  read-write
    STATUS  mandatory
    DESCRIPTION
        "The value of the priority field which is
         contained in the more significant  4 bits of the most
         significant octet of the (2 octet long) Port ID.
         The value is a product of 16.
         The other octet of the Port ID is given by the value
         of rldot1dStpVlanGroupPort."
    REFERENCE
        "IEEE 802.1t/D2-1999: Section 9.2.6"
    ::= { rldot1sMstpInstancePortEntry 3 }

rldot1sMstpInstancePortState OBJECT-TYPE
    SYNTAX  INTEGER {
        disabled(1),
        blocking(2),
        listening(3),
        learning(4),
        forwarding(5),
        broken(6)
    }
    ACCESS  read-only
    STATUS  mandatory
    DESCRIPTION
        "The port's current state as defined by application of
         the Spanning Tree Protocol. This state controls what
         action a port takes on reception of a frame.
         If the bridge has detected a port that is malfunctioning
         it will place that port into the broken(6) state.  For ports
         which are disabled (see dot1dStpVlanPortEnable), this object
         will have a value of disabled(1)."
    REFERENCE
            "IEEE 802.1D-1990: Section 4.5.5.2"
    ::= { rldot1sMstpInstancePortEntry 4 }

rldot1sMstpInstancePortEnable OBJECT-TYPE
    SYNTAX  INTEGER {
        enabled(1),
        disabled(2)
    }
    ACCESS  read-only
    STATUS  mandatory
    DESCRIPTION
        "The enabled/disabled status of the port."
    REFERENCE
        "IEEE 802.1D-1990: Section 4.5.5.2"
    ::= { rldot1sMstpInstancePortEntry 5 }

rldot1sMstpInstancePortPathCost OBJECT-TYPE
    SYNTAX  INTEGER (1..200000000)
    ACCESS  read-only
    STATUS  mandatory
    DESCRIPTION
        "The contribution of this port to the path cost of
         paths towards the spanning tree root which include
         this port.  802.1D-1990 recommends that the
         default value of this parameter be in inverse
         proportion to the speed of the attached LAN."
    REFERENCE
        "IEEE 802.1D-1990: Section 4.5.5.3"
    ::= { rldot1sMstpInstancePortEntry 6 }

rldot1sMstpInstancePortDesignatedRoot OBJECT-TYPE
    SYNTAX  BridgeId
    ACCESS  read-only
    STATUS  mandatory
    DESCRIPTION
        "The unique Bridge Identifier of the Bridge
         recorded as the Root in the Configuration BPDUs
         transmitted by the Designated Bridge for the
         segment to which the port is attached."
    REFERENCE
        "IEEE 802.1D-1990: Section 4.5.5.4"
    ::= { rldot1sMstpInstancePortEntry 7 }

rldot1sMstpInstancePortDesignatedCost OBJECT-TYPE
    SYNTAX  INTEGER
    ACCESS  read-only
    STATUS  mandatory
    DESCRIPTION
        "The path cost of the Designated Port of the
         segment connected to this port.  This value is
         compared to the Root Path Cost field in received
         bridge PDUs."
    REFERENCE
        "IEEE 802.1D-1990: Section 4.5.5.5"
    ::= { rldot1sMstpInstancePortEntry 8 }

rldot1sMstpInstancePortDesignatedBridge OBJECT-TYPE
    SYNTAX  BridgeId
    ACCESS  read-only
    STATUS  mandatory
    DESCRIPTION
        "The Bridge Identifier of the bridge which this
         port considers to be the Designated Bridge for
         this port's segment."
    REFERENCE
        "IEEE 802.1D-1990: Section 4.5.5.6"
    ::= { rldot1sMstpInstancePortEntry 9 }

rldot1sMstpInstancePortDesignatedPort OBJECT-TYPE
    SYNTAX  OCTET STRING (SIZE (2))
    ACCESS  read-only
    STATUS  mandatory
    DESCRIPTION
        "The Port Identifier of the port on the Designated
         Bridge for this port's segment."
    REFERENCE
        "IEEE 802.1D-1990: Section 4.5.5.7"
    ::= { rldot1sMstpInstancePortEntry 10 }

rldot1sMstpInstancePortForwardTransitions OBJECT-TYPE
    SYNTAX  Counter
    ACCESS  read-only
    STATUS  mandatory
    DESCRIPTION
        "The number of times this port has transitioned
         from the Learning state to the Forwarding state."
    ::= { rldot1sMstpInstancePortEntry 11 }

rldot1sMStpInstancePortAdminPathCost OBJECT-TYPE
    SYNTAX      INTEGER (0..200000000)
    ACCESS  read-write
    STATUS      mandatory
    DESCRIPTION
        "The administratively assigned value for the contribution
         of this port to the path cost of paths towards the spanning
         tree root.

         Writing a value of '0' assigns the automatically calculated
         default Path Cost value to the port.  If the default Path
         Cost is being used, this object returns '0' when read.

         This complements the object dot1dStpPortPathCost, which
         returns the operational value of the path cost."
    REFERENCE
        "IEEE 802.1D-1998: Section 8.5.5.3"
    ::= { rldot1sMstpInstancePortEntry 12 }

rldot1sMStpInstancePortRole OBJECT-TYPE
    SYNTAX  INTEGER {
                    unknown(0),
                    disabled(1),
                    alternate(2),
                    backup(3),
                    root(4),
                    designated(5),
                    master(6)
                }

    ACCESS  read-only
    STATUS  mandatory
    DESCRIPTION
        "Specify the role of this this port."
    REFERENCE
        ""
    ::= { rldot1sMstpInstancePortEntry 13 }

rldot1sMstpMaxHopes OBJECT-TYPE
    SYNTAX  INTEGER (1..40)
    ACCESS  read-write
    STATUS  mandatory
    DESCRIPTION
        "Max number of hopes that an MST BPDU will travel inside a region."
    DEFVAL { 20 }
    ::= { rldot1sMstp 3 }

rldot1sMstpConfigurationName OBJECT-TYPE
    SYNTAX  SnmpAdminString
    ACCESS  read-only
    STATUS  mandatory
    DESCRIPTION
        "The active configuration name as will be caried in MST BPDU's."
    ::= { rldot1sMstp 4 }

rldot1sMstpRevisionLevel OBJECT-TYPE
    SYNTAX  INTEGER (0..65535)
    ACCESS  read-only
    STATUS  mandatory
    DESCRIPTION
        "The active revision level."
    DEFVAL { 0 }
    ::= { rldot1sMstp 5 }

--
-- rldot1sMstpVlanTable
--
rldot1sMstpVlanTable OBJECT-TYPE
    SYNTAX  SEQUENCE OF Rldot1sMstpVlanEntry
    ACCESS  not-accessible
    STATUS  mandatory
    DESCRIPTION
        "A table that contains information about the alocation of vlans to groups."
    ::= { rldot1sMstp 6 }

rldot1sMstpVlanEntry OBJECT-TYPE
    SYNTAX  Rldot1sMstpVlanEntry
    ACCESS  not-accessible
    STATUS  mandatory
    DESCRIPTION
        "A list of information maintained by every vlan
         about the group it belongs to."
    INDEX   { rldot1sMstpVlan }
    ::= { rldot1sMstpVlanTable 1 }

Rldot1sMstpVlanEntry ::= SEQUENCE {
      rldot1sMstpVlan              INTEGER,
      rldot1sMstpGroup             INTEGER,
      rldot1sMstpPendingGroup      INTEGER

}

rldot1sMstpVlan OBJECT-TYPE
    SYNTAX  INTEGER (1..4094)
    ACCESS  read-only
    STATUS  mandatory
    DESCRIPTION
        "The vlan number of the vlan for which this entry
         contains Spanning Tree Protocol management
         information."
    REFERENCE
         "IEEE 802.1s/D11-2001: Section 13.7"
    ::= { rldot1sMstpVlanEntry 1 }

rldot1sMstpGroup OBJECT-TYPE
    SYNTAX  INTEGER (0..64)
    ACCESS  read-only
    STATUS  mandatory
    DESCRIPTION
        "Specifid the active group number this vlan belonges to."
    REFERENCE
        ""
    DEFVAL { 0 }
    ::= { rldot1sMstpVlanEntry 2 }

rldot1sMstpPendingGroup OBJECT-TYPE
    SYNTAX  INTEGER (0..64)
    ACCESS  read-write
    STATUS  mandatory
    DESCRIPTION
        "Specifid the pending group number this vlan belonges to."
    REFERENCE
        ""
    DEFVAL { 0 }
    ::= { rldot1sMstpVlanEntry 3 }

--
-- rldot1sMstpExtPortTable
--
rldot1sMstpExtPortTable OBJECT-TYPE
    SYNTAX  SEQUENCE OF Rldot1sMstpExtPortEntry
    ACCESS  not-accessible
    STATUS  mandatory
    DESCRIPTION
        "A table that contains MSTP information about ports of the CIST."
    ::= { rldot1sMstp 7 }

rldot1sMstpExtPortEntry OBJECT-TYPE
SYNTAX  Rldot1sMstpExtPortEntry
    ACCESS  not-accessible
    STATUS  mandatory
    DESCRIPTION
        "A list of information maintained by every port
         of the CIST."
    INDEX   { rldot1sMstpExtPortPort }
    ::= { rldot1sMstpExtPortTable 1 }

Rldot1sMstpExtPortEntry ::= SEQUENCE {
      rldot1sMstpExtPortPort                   INTEGER,
      rldot1sMstpExtPortInternalOperPathCost   INTEGER,
      rldot1sMstpExtPortDesignatedRegionalRoot BridgeId,
      rldot1sMstpExtPortDesignatedRegionalCost INTEGER,
      rldot1sMstpExtPortBoundary               TruthValue,
      rldot1sMstpExtPortInternalAdminPathCost  INTEGER

}
rldot1sMstpExtPortPort OBJECT-TYPE
    SYNTAX  INTEGER (1..4096)
    ACCESS  read-only
    STATUS  mandatory
    DESCRIPTION
        "The port number of the port for which this entry
         contains Spanning Tree Protocol management
         information."
    REFERENCE
         "IEEE 802.1t/D2-1999: Section 9.2.6"
    ::= { rldot1sMstpExtPortEntry 1 }

rldot1sMstpExtPortInternalOperPathCost OBJECT-TYPE
    SYNTAX  INTEGER (1..200000000)
    ACCESS  read-only
    STATUS  mandatory
    DESCRIPTION
        "The contribution of this port to the path cost of
         paths towards the spanning tree regional root which
         include this port.  802.1S-2002 recommends that the
         default value of this parameter be in inverse
         proportion to the speed of the attached LAN."
    ::= { rldot1sMstpExtPortEntry 2 }

rldot1sMstpExtPortDesignatedRegionalRoot OBJECT-TYPE
    SYNTAX  BridgeId
    ACCESS  read-only
    STATUS  mandatory
    DESCRIPTION
        "The unique Bridge Identifier of the Bridge
         recorded as the Root in the Configuration BPDUs
         transmitted by the Designated Bridge for the
         segment to which the port is attached."
    REFERENCE
        "IEEE 802.1D-1990: Section 4.5.5.4"
    ::= { rldot1sMstpExtPortEntry 3 }

rldot1sMstpExtPortDesignatedRegionalCost OBJECT-TYPE
    SYNTAX  INTEGER
    ACCESS  read-only
    STATUS  mandatory
    DESCRIPTION
        "The regional path cost of the Designated Port of the
         segment connected to this port.  This value is
         compared to the Root Path Cost field in received
         bridge PDUs."
    REFERENCE
        "IEEE 802.1D-1990: Section 4.5.5.5"
    ::= { rldot1sMstpExtPortEntry 4 }

rldot1sMstpExtPortBoundary OBJECT-TYPE
    SYNTAX  TruthValue
    ACCESS  read-only
    STATUS  mandatory
    DESCRIPTION
        "Indication if the port is conented to to a lan segment
         outside or inside the region."
    REFERENCE
        "IEEE 802.1D-1990: Section 4.5.5.5"
    ::= { rldot1sMstpExtPortEntry 5 }

rldot1sMstpExtPortInternalAdminPathCost OBJECT-TYPE
    SYNTAX  INTEGER (0..200000000)
    ACCESS  read-write
    STATUS  mandatory
    DESCRIPTION
        "The administratively assigned value for the contribution
         of this port to the path cost of paths towards the spanning
         tree root.

         Writing a value of '0' assigns the automatically calculated
         default Path Cost value to the port.  If the default Path
         Cost is being used, this object returns '0' when read.

         This complements the object dot1dStpPortPathCost, which
         returns the operational value of the path cost."

    ::= { rldot1sMstpExtPortEntry 6 }

rldot1sMstpDesignatedMaxHopes OBJECT-TYPE
    SYNTAX  INTEGER (1..40)
    ACCESS  read-only
    STATUS  mandatory
    DESCRIPTION
        "Max number of hopes that an MST BPDU will travel inside a region."
    ::= { rldot1sMstp 8 }

rldot1sMstpRegionalRoot OBJECT-TYPE
    SYNTAX  BridgeId
    ACCESS  read-only
    STATUS  mandatory
    DESCRIPTION
            "CIST Regional Root Identifier (13.16.4).
            The Bridge Identifier of the current CIST Regional Root."
    REFERENCE
            "IEEE 802.1S-2002: Section 13.16.4"
    ::= { rldot1sMstp 9 }

rldot1sMstpRegionalRootCost OBJECT-TYPE
    SYNTAX  INTEGER
    ACCESS  read-only
    STATUS  mandatory
    DESCRIPTION
            "The CIST path cost from the transmitting Bridge to the
            CIST Regional Root."
    REFERENCE
            "IEEE 802.1S-2002: Section 12.8.1.1.3"
    ::= { rldot1sMstp 10 }

rldot1sMstpPendingConfigurationName OBJECT-TYPE
    SYNTAX  SnmpAdminString (SIZE(1..32))
    ACCESS  read-write
    STATUS  mandatory
    DESCRIPTION
        "The pending configuration name."
    ::= { rldot1sMstp 11 }

rldot1sMstpPendingRevisionLevel OBJECT-TYPE
    SYNTAX  INTEGER (0..65535)
    ACCESS  read-write
    STATUS  mandatory
    DESCRIPTION
        "The pending revision level."
    DEFVAL { 0 }
    ::= { rldot1sMstp 12 }

rldot1sMstpPendingAction OBJECT-TYPE
    SYNTAX  INTEGER {
        copyPendingActive(1),
        copyActivePending(2)
    }
    ACCESS  read-write
    STATUS  mandatory
    DESCRIPTION
        "The action to be done with the pending configuration.
         copyPendingActive - to copy the pending mst configuration to the active one.
         copyActivePending - to copy the active mst configuration to the pending one. "
    ::= { rldot1sMstp 13 }

rldot1sMstpRemainingHops OBJECT-TYPE
    SYNTAX  INTEGER
    ACCESS  read-only
    STATUS  mandatory
    DESCRIPTION
        "This count value determines the amount of hops
         the information transmitted by this bridge can travel."
    ::= { rldot1sMstp 14 }

rldot1dTpAgingTime  OBJECT IDENTIFIER ::= { rlpBridgeMIBObjects 7 }

rldot1dTpAgingTimeMin OBJECT-TYPE
    SYNTAX  INTEGER
    ACCESS  read-only
    STATUS  mandatory
    DESCRIPTION
        "The min timeout period in seconds for aging out
         dynamically learned forwarding information."
    REFERENCE
        "P802.1d/D9, July 14, 1989: Section 6.7.1.1.3"
    ::= { rldot1dTpAgingTime 1 }

rldot1dTpAgingTimeMax OBJECT-TYPE
    SYNTAX  INTEGER
    ACCESS  read-only
    STATUS  mandatory
    DESCRIPTION
        "The max timeout period in seconds for aging out
         dynamically learned forwarding information."
    REFERENCE
        "P802.1d/D9, July 14, 1989: Section 6.7.1.1.3"
    ::= { rldot1dTpAgingTime 2 }


rlTelnet  OBJECT IDENTIFIER ::= { rnd 58 }

rlTelnetMibVersion OBJECT-TYPE
    SYNTAX  INTEGER
    ACCESS  read-only
    STATUS  mandatory
    DESCRIPTION
        "MIB's version, the current version is 1."
    ::= { rlTelnet 1 }

rlTelnetPassword OBJECT-TYPE
    SYNTAX DisplayString (SIZE(0..20))
    ACCESS read-write
    STATUS mandatory
    DESCRIPTION
        "Telnet Password"
    ::= { rlTelnet 2 }

rlTelnetTimeout OBJECT-TYPE
    SYNTAX  INTEGER (0..65535)
    ACCESS  read-write
    STATUS  mandatory
    DESCRIPTION
        "The number of minutes after which the TCP connection is closed
         if no activity is detected from the Client"
    DEFVAL  {0}
    ::= { rlTelnet 3 }

rlTelnetUsersTable OBJECT-TYPE
    SYNTAX  SEQUENCE OF RlTelnetUsersEntry
    ACCESS  not-accessible
    STATUS  mandatory
    DESCRIPTION
        "This table hold information about current telnet sessions"
    ::= { rlTelnet 4 }

rlTelnetUsersEntry OBJECT-TYPE
    SYNTAX  RlTelnetUsersEntry
    ACCESS  not-accessible
    STATUS  mandatory
    DESCRIPTION
        "The row definition for this table."
    INDEX { rlTelnetSessionId }
    ::= { rlTelnetUsersTable 1 }

RlTelnetUsersEntry ::= SEQUENCE {
    rlTelnetSessionId                INTEGER,
    rlTelnetSessionClientAddress     IpAddress,
    rlTelnetSessionLoginTime         DisplayString,
    rlTelnetSessionStatus            INTEGER
}

rlTelnetSessionId OBJECT-TYPE
    SYNTAX  INTEGER
    ACCESS  read-only
    STATUS  mandatory
    DESCRIPTION
        "Telnet Session ID"
    ::= { rlTelnetUsersEntry 1 }

rlTelnetSessionClientAddress OBJECT-TYPE
    SYNTAX  IpAddress
    ACCESS  read-only
    STATUS  mandatory
    DESCRIPTION
        "Telnet Session Client IP address"
    ::= { rlTelnetUsersEntry 2 }

rlTelnetSessionLoginTime OBJECT-TYPE
    SYNTAX  DisplayString
    ACCESS  read-only
    STATUS  mandatory
    DESCRIPTION
        "Telnet Session Login Time string"
    ::= { rlTelnetUsersEntry 3 }

rlTelnetSessionStatus OBJECT-TYPE
    SYNTAX  INTEGER {
        connected(1),
        disconnect(2)
    }
    ACCESS  read-write
    STATUS  mandatory
    DESCRIPTION
        "Telnet Session status. After status has been set to diconnect the
         sessions is closed and the matching entry is deleted from the table."
    ::= { rlTelnetUsersEntry 4 }

rlTelnetLoginBanner OBJECT-TYPE
    SYNTAX DisplayString
    ACCESS read-write
    STATUS mandatory
    DESCRIPTION
        "Telnet Login Banner. When telnet connection is established,
         the banner is the concatanation of this MIB and rlTelnetSecondLoginBanner."
    ::= { rlTelnet 5 }

rlTelnetSecondLoginBanner OBJECT-TYPE
    SYNTAX DisplayString
    ACCESS read-write
    STATUS mandatory
    DESCRIPTION
        "Telnet Login Banner Extension. When telnet connection is established,
         the banner is the concatanation of rlTelnetLoginBanner and this MIB"
    ::= { rlTelnet 6 }


rlPolicy  OBJECT IDENTIFIER ::= { rnd 59 }

rlArpSpoofing OBJECT IDENTIFIER ::= { rnd 60 }

rlArpSpoofingMibVersion OBJECT-TYPE
    SYNTAX  INTEGER
    ACCESS  read-only
    STATUS  mandatory
    DESCRIPTION
        "MIB's version, the current version is 1."
    ::= { rlArpSpoofing 1 }

rlArpSpoofingTable  OBJECT-TYPE
    SYNTAX  SEQUENCE OF RlArpSpoofingEntry
    ACCESS  not-accessible
    STATUS  mandatory
    DESCRIPTION
        "A list of the ifIndexes, IP addresses and corresponding MAC addresses."
    ::= { rlArpSpoofing 2 }

rlArpSpoofingEntry OBJECT-TYPE
    SYNTAX  RlArpSpoofingEntry
    ACCESS  not-accessible
    STATUS  mandatory
    DESCRIPTION
        "An entry of this table specifis ifIndex,IP Address and
         MAC address."
    INDEX  { rlArpSpoofingIfIndex, rlArpSpoofingLocalIpAddr }
    ::= { rlArpSpoofingTable 1 }

RlArpSpoofingEntry ::= SEQUENCE {
    rlArpSpoofingIfIndex        InterfaceIndex,
    rlArpSpoofingLocalIpAddr    IpAddress,
    rlArpSpoofingMacAddr        PhysAddress,
    rlArpSpoofingRemoteIpAddr   IpAddress,
    rlArpSpoofingOutPhysIfIndex InterfaceIndexOrZero,
    rlArpSpoofingStatus         RowStatus
}

rlArpSpoofingIfIndex OBJECT-TYPE
    SYNTAX      InterfaceIndex
    ACCESS      read-write
    STATUS      mandatory
    DESCRIPTION
        "The physical interface for which this entry contains information."
    ::= { rlArpSpoofingEntry 1 }

rlArpSpoofingLocalIpAddr OBJECT-TYPE
    SYNTAX  IpAddress
    ACCESS  read-write
    STATUS  mandatory
    DESCRIPTION
        "Ip addres for which the device will send ARP reply (ARP spoofing)."
    ::= { rlArpSpoofingEntry 2 }

rlArpSpoofingMacAddr OBJECT-TYPE
    SYNTAX  PhysAddress
    ACCESS  read-write
    STATUS  mandatory
    DESCRIPTION
        "MAC addres with which the device will send ARP reply.
        If the field is ommited or its value 0.0.0.0 the device will
        send with the interface's MAC address."
    ::= { rlArpSpoofingEntry 3 }

rlArpSpoofingRemoteIpAddr OBJECT-TYPE
    SYNTAX  IpAddress
    ACCESS  read-write
    STATUS  mandatory
    DESCRIPTION
        "Ip addres for which the device will send periodically ARP requests
         if its value differs from 0.0.0.0."
    ::= { rlArpSpoofingEntry 4 }

rlArpSpoofingOutPhysIfIndex OBJECT-TYPE
    SYNTAX      InterfaceIndexOrZero
    ACCESS      read-write
    STATUS      mandatory
    DESCRIPTION
        "The physical interface to which the device will send periodically
         ARP requests if its value differs from 0. If its value is 0 then ARP
         requests will send to all the VLAN's ports."
    DEFVAL { 0 }
    ::= { rlArpSpoofingEntry 5 }

rlArpSpoofingStatus OBJECT-TYPE
    SYNTAX  RowStatus
    ACCESS  read-write
    STATUS  mandatory
    DESCRIPTION
        "It is used to insert, update or delete an entry"
    ::= { rlArpSpoofingEntry 6 }

rlMir  OBJECT IDENTIFIER ::= { rnd 61 }

rlMirMibVersion OBJECT-TYPE
    SYNTAX  INTEGER
    ACCESS  read-only
    STATUS  mandatory
    DESCRIPTION
        "MIB's version, the current version is 1."
    ::= { rlMir 1 }

rlMirMaxNumOfMRIsAfterReset OBJECT-TYPE
    SYNTAX  INTEGER
    ACCESS  read-write
    STATUS  mandatory
    DESCRIPTION
        "The maximun instanses of IP Multi Instance Routers after the
         following reset."
    DEFVAL { 1 }
    ::= { rlMir 2 }

rlMirMaxNumOfMRIs OBJECT-TYPE
    SYNTAX  INTEGER
    ACCESS  read-only
    STATUS  mandatory
    DESCRIPTION
        "The maximun instanses of IP Multi Instance Routers."
    ::= { rlMir 3 }

rlMirCurMriNum OBJECT-TYPE
    SYNTAX  INTEGER
    ACCESS  read-write
    STATUS  mandatory
    DESCRIPTION
        "The number of the MRI of which MIB variables are treated at
        the same time by the SNMP agent."
    ::= { rlMir 4 }

rlMirInterfaceTable  OBJECT-TYPE
    SYNTAX  SEQUENCE OF RlMirInterfaceEntry
    ACCESS  not-accessible
    STATUS  mandatory
    DESCRIPTION
        "A list of the assignment ifinterfaces to IP Router instances."
    ::= { rlMir 5 }

rlMirInterfaceEntry OBJECT-TYPE
    SYNTAX  RlMirInterfaceEntry
    ACCESS  not-accessible
    STATUS  mandatory
    DESCRIPTION
        "An entry of this table specifies the MRID assignement to a L2
        interfrace."
    INDEX  { rlMirInterfaceIfIndex }
    ::= { rlMirInterfaceTable 1 }

RlMirInterfaceEntry ::= SEQUENCE {
    rlMirInterfaceIfIndex       InterfaceIndex,
    rlMirInterfaceMrid          INTEGER
}

rlMirInterfaceIfIndex OBJECT-TYPE
    SYNTAX      InterfaceIndex
    ACCESS      read-write
    STATUS      mandatory
    DESCRIPTION
        "The L2 interface for which this entry contains information."
    ::= { rlMirInterfaceEntry 1 }

rlMirInterfaceMrid OBJECT-TYPE
    SYNTAX  INTEGER
    ACCESS  read-write
    STATUS  mandatory
    DESCRIPTION
        "Multi IP Router Instance Identifier to which the
         interface is assgned."
    DEFVAL { 0 }
    ::= { rlMirInterfaceEntry 2 }

rlMirVlanBaseReservedPortsTable  OBJECT-TYPE
    SYNTAX  SEQUENCE OF RlMirVlanBaseReservedPortsEntry
    ACCESS  not-accessible
    STATUS  mandatory
    DESCRIPTION
        "A list VLAN based reserved physical ports."
    ::= { rlMir 6 }

rlMirVlanBaseReservedPortsEntry OBJECT-TYPE
    SYNTAX  RlMirVlanBaseReservedPortsEntry
    ACCESS  not-accessible
    STATUS  mandatory
    DESCRIPTION
        "A VLAN based reserved physical port."
    INDEX  { rlMirVlanBaseReservedPortsIfIndex }
    ::= { rlMirVlanBaseReservedPortsTable 1 }

RlMirVlanBaseReservedPortsEntry ::= SEQUENCE {
    rlMirVlanBaseReservedPortsIfIndex       InterfaceIndex,
    rlMirVlanBaseReservedPortsStatus        RowStatus
}

rlMirVlanBaseReservedPortsIfIndex OBJECT-TYPE
    SYNTAX      InterfaceIndex
    ACCESS      read-write
    STATUS      mandatory
    DESCRIPTION
        "IfIndex of VLAN based reserved physical port."
    ::= { rlMirVlanBaseReservedPortsEntry 1 }

rlMirVlanBaseReservedPortsStatus OBJECT-TYPE
    SYNTAX  RowStatus
    ACCESS  read-write
    STATUS  mandatory
    DESCRIPTION
        "It is used to delete an entry"
    ::= { rlMirVlanBaseReservedPortsEntry 2 }

rlMirVlanBaseLogicalPortsTable  OBJECT-TYPE
    SYNTAX  SEQUENCE OF RlMirVlanBaseLogicalPortsEntry
    ACCESS  not-accessible
    STATUS  mandatory
    DESCRIPTION
        "A list VLAN based logical ports."
    ::= { rlMir 7 }

rlMirVlanBaseLogicalPortsEntry OBJECT-TYPE
    SYNTAX  RlMirVlanBaseLogicalPortsEntry
    ACCESS  not-accessible
    STATUS  mandatory
    DESCRIPTION
        "A VLAN based logical point-to-point port."
    INDEX  { rlMirVlanBaseLogicalPortsIfIndex }
    ::= { rlMirVlanBaseLogicalPortsTable 1 }

RlMirVlanBaseLogicalPortsEntry ::= SEQUENCE {
    rlMirVlanBaseLogicalPortsIfIndex                InterfaceIndex,
    rlMirVlanBaseLogicalPortsReservedIfIndex        InterfaceIndex,
    rlMirVlanBaseLogicalPortsVlanTag                INTEGER,
    rlMirVlanBaseLogicalPortsStatus                 RowStatus
}

rlMirVlanBaseLogicalPortsIfIndex OBJECT-TYPE
    SYNTAX      InterfaceIndex
    ACCESS      read-write
    STATUS      mandatory
    DESCRIPTION
        "IfIndex of VLAN based Logical point-to-point port."
    ::= { rlMirVlanBaseLogicalPortsEntry 1 }

rlMirVlanBaseLogicalPortsReservedIfIndex OBJECT-TYPE
    SYNTAX      InterfaceIndex
    ACCESS      read-write
    STATUS      mandatory
    DESCRIPTION
        "IfIndex of VLAN based reserved physical port on which the logical
         port is defined."
    ::= { rlMirVlanBaseLogicalPortsEntry 2 }

rlMirVlanBaseLogicalPortsVlanTag OBJECT-TYPE
    SYNTAX      INTEGER (1..4095)
    ACCESS      read-write
    STATUS      mandatory
    DESCRIPTION
        "VLAN tag."
    ::= { rlMirVlanBaseLogicalPortsEntry 3 }

rlMirVlanBaseLogicalPortsStatus OBJECT-TYPE
    SYNTAX  RowStatus
    ACCESS  read-write
    STATUS  mandatory
    DESCRIPTION
        "It is used to add, update and delete an entry"
    ::= { rlMirVlanBaseLogicalPortsEntry 4 }

rlIpMRouteStdMIB OBJECT IDENTIFIER ::= { rnd 62 }

rl3sw2swTables OBJECT IDENTIFIER ::= { rnd 63 }

rl3sw2swTablesPollingInterval OBJECT-TYPE
    SYNTAX  INTEGER
    ACCESS  read-write
    STATUS  mandatory
    DESCRIPTION
        "The polling interval for dynamic 3SW/2SW tables in seconds."
    DEFVAL { 3 }
    ::= { rl3sw2swTables 1 }

rlGvrp  OBJECT IDENTIFIER ::= { rnd 64 }

rlPortGvrpTimersTable OBJECT-TYPE
    SYNTAX  SEQUENCE OF RlPortGvrpTimersEntry
    ACCESS  not-accessible
    STATUS  mandatory
    DESCRIPTION
        "A table of GVRP timer values for every bridge
         port.  This is indexed by dot1dBasePort."
    ::= { rlGvrp 1 }

rlPortGvrpTimersEntry OBJECT-TYPE
    SYNTAX  RlPortGvrpTimersEntry
    ACCESS  not-accessible
    STATUS  mandatory
    DESCRIPTION
        "GVRP timer values for a bridge port."
    INDEX   { dot1dBasePort }
    ::= { rlPortGvrpTimersTable 1 }

RlPortGvrpTimersEntry ::=
    SEQUENCE {
        rlPortGvrpJoinTime          TimeInterval,
        rlPortGvrpLeaveTime         TimeInterval,
        rlPortGvrpLeaveAllTime      TimeInterval,
        rlPortGvrpOverrideGarp      EnabledStatus
    }

rlPortGvrpJoinTime OBJECT-TYPE
    SYNTAX  TimeInterval
    ACCESS  read-write
    STATUS  mandatory
    DESCRIPTION
        "The GVRP Join time, in centiseconds."
    DEFVAL { 20 }
    ::= { rlPortGvrpTimersEntry 1 }

rlPortGvrpLeaveTime OBJECT-TYPE
    SYNTAX  TimeInterval
    ACCESS  read-write
    STATUS  mandatory
    DESCRIPTION
        "The GVRP Leave time, in centiseconds."
    DEFVAL { 60 }
    ::= { rlPortGvrpTimersEntry 2 }

rlPortGvrpLeaveAllTime OBJECT-TYPE
    SYNTAX  TimeInterval
    ACCESS  read-write
    STATUS  mandatory
    DESCRIPTION
        "The GVRP LeaveAll time, in centiseconds."
    DEFVAL { 1000 }
    ::= { rlPortGvrpTimersEntry 3 }

rlPortGvrpOverrideGarp OBJECT-TYPE
    SYNTAX  EnabledStatus
    ACCESS  read-write
    STATUS  mandatory
    DESCRIPTION
        "If enabled{1}, GVRP timer values for this port are
         determined by the values in this entry. Otherwise, they
         are determined by the values in dot1dPortGarpTable."
    DEFVAL { disabled }
    ::= { rlPortGvrpTimersEntry 4 }

rlGvrpSupported OBJECT-TYPE
    SYNTAX  TruthValue
    ACCESS  read-only
    STATUS  mandatory
    DESCRIPTION
        "Is GVRP supported in this device or not"
    ::= { rlGvrp 2 }

rlGvrpMibVersion OBJECT-TYPE
    SYNTAX  INTEGER
    ACCESS  read-only
    STATUS  mandatory
    DESCRIPTION
        "MIB's version, the current version is 3."
    ::= { rlGvrp 3 }

-- rlPortGvrpStatisticsTable

rlPortGvrpStatisticsTable OBJECT-TYPE
    SYNTAX  SEQUENCE OF RlPortGvrpStatisticsEntry
    ACCESS  not-accessible
    STATUS  mandatory
    DESCRIPTION
        "A table of GVRP statistics values for every bridge
         port.  This is indexed by dot1dBasePort."
    ::= { rlGvrp 4 }

rlPortGvrpStatisticsEntry OBJECT-TYPE
    SYNTAX  RlPortGvrpStatisticsEntry
    ACCESS  not-accessible
    STATUS  mandatory
    DESCRIPTION
        "GVRP statistics values for a bridge port."
    INDEX   { dot1dBasePort }
    ::= { rlPortGvrpStatisticsTable 1 }

RlPortGvrpStatisticsEntry ::=
    SEQUENCE {
        rlPortGvrpStatisticsRJE       Counter,
        rlPortGvrpStatisticsRJIn      Counter,
        rlPortGvrpStatisticsREmp      Counter,
        rlPortGvrpStatisticsRLIn      Counter,
        rlPortGvrpStatisticsRLE       Counter,
        rlPortGvrpStatisticsRLA       Counter,
        rlPortGvrpStatisticsSJE       Counter,
        rlPortGvrpStatisticsSJIn      Counter,
        rlPortGvrpStatisticsSEmp      Counter,
        rlPortGvrpStatisticsSLIn      Counter,
        rlPortGvrpStatisticsSLE       Counter,
        rlPortGvrpStatisticsSLA       Counter,
        rlPortGvrpStatisticsClear     INTEGER
    }

rlPortGvrpStatisticsRJE OBJECT-TYPE
    SYNTAX  Counter
    ACCESS  read-only
    STATUS  mandatory
    DESCRIPTION
        "The number of Join Empty  Received  on the port,
         since the last clearance."
    ::= { rlPortGvrpStatisticsEntry 1 }

rlPortGvrpStatisticsRJIn OBJECT-TYPE
    SYNTAX  Counter
    ACCESS  read-only
    STATUS  mandatory
    DESCRIPTION
        "The number of Join In  Received  on the port,
         since the last clearance."
    ::= { rlPortGvrpStatisticsEntry 2 }

rlPortGvrpStatisticsREmp OBJECT-TYPE
    SYNTAX  Counter
    ACCESS  read-only
    STATUS  mandatory
    DESCRIPTION
        "The number of Empty  Received  on the port,
         since the last clearance."
    ::= { rlPortGvrpStatisticsEntry 3 }

rlPortGvrpStatisticsRLIn OBJECT-TYPE
    SYNTAX  Counter
    ACCESS  read-only
    STATUS  mandatory
    DESCRIPTION
        "The number of Leave In Received on the port,
         since the last clearance."
    ::= { rlPortGvrpStatisticsEntry 4 }

rlPortGvrpStatisticsRLE OBJECT-TYPE
    SYNTAX  Counter
    ACCESS  read-only
    STATUS  mandatory
    DESCRIPTION
        "The number of Leave Empty Received on the port,
         since the last clearance."
    ::= { rlPortGvrpStatisticsEntry 5 }

rlPortGvrpStatisticsRLA OBJECT-TYPE
    SYNTAX  Counter
    ACCESS  read-only
    STATUS  mandatory
    DESCRIPTION
        "The number of Leave All Received on the port,
         since the last clearance."
    ::= { rlPortGvrpStatisticsEntry 6 }

rlPortGvrpStatisticsSJE OBJECT-TYPE
    SYNTAX  Counter
    ACCESS  read-only
    STATUS  mandatory
    DESCRIPTION
        "The number of Join Empty Sent on the port,
         since the last clearance."
    ::= { rlPortGvrpStatisticsEntry 7 }

rlPortGvrpStatisticsSJIn OBJECT-TYPE
    SYNTAX  Counter
    ACCESS  read-only
    STATUS  mandatory
    DESCRIPTION
        "The number of Join In Sent on the port,
         since the last clearance."
    ::= { rlPortGvrpStatisticsEntry 8 }

rlPortGvrpStatisticsSEmp OBJECT-TYPE
    SYNTAX  Counter
    ACCESS  read-only
    STATUS  mandatory
    DESCRIPTION
        "The number of Empty Sent on the port,
         since the last clearance."
    ::= { rlPortGvrpStatisticsEntry 9 }

rlPortGvrpStatisticsSLIn OBJECT-TYPE
    SYNTAX  Counter
    ACCESS  read-only
    STATUS  mandatory
    DESCRIPTION
        "The number of Leave In Sent on the port,
         since the last clearance."
    ::= { rlPortGvrpStatisticsEntry 10 }

rlPortGvrpStatisticsSLE OBJECT-TYPE
    SYNTAX  Counter
    ACCESS  read-only
    STATUS  mandatory
    DESCRIPTION
        "The number of Leave Empty Sent on the port,
         since the last clearance."
    ::= { rlPortGvrpStatisticsEntry 11 }

rlPortGvrpStatisticsSLA OBJECT-TYPE
    SYNTAX  Counter
    ACCESS  read-only
    STATUS  mandatory
    DESCRIPTION
        "The number of Leave All Sent on the port,
         since the last clearance."
    ::= { rlPortGvrpStatisticsEntry 12 }

rlPortGvrpStatisticsClear OBJECT-TYPE
    SYNTAX  INTEGER {
        activate(1),
        passive(2)
    }
    ACCESS  read-write
    STATUS  mandatory
    DESCRIPTION
        "activate - the signal/trigger to clear ALL
                    the rlPortGvrpStatisticsEntry's fields.
         passive  - specify that the rlPortGvrpStatisticsClear field is not
                    activate, or finshed the clearnce process.
                    the rlPortGvrpStatisticsClear return automatically to
                    passive after it was activate."
    DEFVAL { passive }
    ::= { rlPortGvrpStatisticsEntry 13 }

-- rlPortGvrpErrorStatisticsTable

rlPortGvrpErrorStatisticsTable OBJECT-TYPE
    SYNTAX  SEQUENCE OF RlPortGvrpErrorStatisticsEntry
    ACCESS  not-accessible
    STATUS  mandatory
    DESCRIPTION
        "A table of GVRP ErrorStatistics values for every bridge
         port.  This is indexed by dot1dBasePort."
    ::= { rlGvrp 5 }

rlPortGvrpErrorStatisticsEntry OBJECT-TYPE
    SYNTAX  RlPortGvrpErrorStatisticsEntry
    ACCESS  not-accessible
    STATUS  mandatory
    DESCRIPTION
        "GVRP ErrorStatistics values for a bridge port."
    INDEX   { dot1dBasePort }
    ::= { rlPortGvrpErrorStatisticsTable 1 }

RlPortGvrpErrorStatisticsEntry ::=
    SEQUENCE {
        rlPortGvrpErrorStatisticsInvProt    Counter,
        rlPortGvrpErrorStatisticsInvAtyp    Counter,
        rlPortGvrpErrorStatisticsInvAval    Counter,
        rlPortGvrpErrorStatisticsInvPlen    Counter,
        rlPortGvrpErrorStatisticsInvAlen    Counter,
        rlPortGvrpErrorStatisticsInvEvent   Counter,
        rlPortGvrpErrorStatisticsClear      INTEGER
    }

rlPortGvrpErrorStatisticsInvProt OBJECT-TYPE
    SYNTAX  Counter
    ACCESS  read-only
    STATUS  mandatory
    DESCRIPTION
        "The number of Invalid Protocol Id encountered by
         the GVRP port. (since the last clearance)"
    ::= { rlPortGvrpErrorStatisticsEntry 1 }

rlPortGvrpErrorStatisticsInvAtyp OBJECT-TYPE
    SYNTAX  Counter
    ACCESS  read-only
    STATUS  mandatory
    DESCRIPTION
        "The number of Invalid Attribute Type encountered by
         the GVRP port. (since the last clearance)"
    ::= { rlPortGvrpErrorStatisticsEntry 2 }

rlPortGvrpErrorStatisticsInvAval OBJECT-TYPE
    SYNTAX  Counter
    ACCESS  read-only
    STATUS  mandatory
    DESCRIPTION
        "The number of Invalid Attribute Value encountered by
         the GVRP port. (since the last clearance)"
    ::= { rlPortGvrpErrorStatisticsEntry 3 }

rlPortGvrpErrorStatisticsInvPlen OBJECT-TYPE
    SYNTAX  Counter
    ACCESS  read-only
    STATUS  mandatory
    DESCRIPTION
        "The number of Invalid PDU Length encountered by
         the GVRP port. (since the last clearance)"
    ::= { rlPortGvrpErrorStatisticsEntry 4 }

rlPortGvrpErrorStatisticsInvAlen OBJECT-TYPE
    SYNTAX  Counter
    ACCESS  read-only
    STATUS  mandatory
    DESCRIPTION
       "The number of Invalid Attribute Length encountered by
         the GVRP port. (since the last clearance)"
    ::= { rlPortGvrpErrorStatisticsEntry 5 }

rlPortGvrpErrorStatisticsInvEvent OBJECT-TYPE
    SYNTAX  Counter
    ACCESS  read-only
    STATUS  mandatory
    DESCRIPTION
        "The number of Invalid Event encountered by
         the GVRP port. (since the last clearance)"
    ::= { rlPortGvrpErrorStatisticsEntry 6 }

rlPortGvrpErrorStatisticsClear OBJECT-TYPE
    SYNTAX  INTEGER {
        activate(1),
        passive(2)
    }
    ACCESS  read-write
    STATUS  mandatory
    DESCRIPTION
        "activate - the signal/trigger to clear ALL
                    the rlPortGvrpErrorStatisticsEntry's fields.
         passive  - specify that the rlPortGvrpErrorStatisticsClear field is not
                    activate, or finshed the clearnce process.
                    the rlPortGvrpErrorStatisticsClear return automatically to
                    passive after it was activate."
    DEFVAL { passive }
    ::= { rlPortGvrpErrorStatisticsEntry 7 }

-- rlPortGvrpApplicantStatusTable

rlPortGvrpApplicantStatusTable OBJECT-TYPE
    SYNTAX  SEQUENCE OF RlPortGvrpApplicantStatusEntry
    ACCESS  not-accessible
    STATUS  mandatory
    DESCRIPTION
        "A table of GVRP Applicant Status values for every bridge
         port.  This is indexed by dot1dBasePort."
    ::= { rlGvrp 6 }

rlPortGvrpApplicantStatusEntry OBJECT-TYPE
    SYNTAX  RlPortGvrpApplicantStatusEntry
    ACCESS  not-accessible
    STATUS  mandatory
    DESCRIPTION
        "GVRP Applicant Status value for a bridge port."
    INDEX   { dot1dBasePort }
    ::= { rlPortGvrpApplicantStatusTable 1 }

RlPortGvrpApplicantStatusEntry ::=
    SEQUENCE {
        rlPortGvrpApplicantStatusValue        INTEGER
    }

rlPortGvrpApplicantStatusValue OBJECT-TYPE
    SYNTAX  INTEGER {
        participant(1),
        nonParticipant(2)
    }
    ACCESS  read-write
    STATUS  mandatory
    DESCRIPTION
        "participant -  the Gvrp enabled port sending GARP PDUs.
         nonParticipant - preventing the Gvrp enabled port from sending GARP PDUs."
    DEFVAL { participant }
    ::= { rlPortGvrpApplicantStatusEntry 1 }

-- rlGvrpDynamicVlanCreation was deleted
-- { rlGvrp 7 } reserved

-- rlPortGvrpRegistrationModeTable

rlPortGvrpRegistrationModeTable OBJECT-TYPE
    SYNTAX  SEQUENCE OF RlPortGvrpRegistrationModeEntry
    ACCESS  not-accessible
    STATUS  mandatory
    DESCRIPTION
        "A table of GVRP Registration Mode values for every bridge
         port.  This is indexed by dot1dBasePort."
    ::= { rlGvrp 8 }

rlPortGvrpRegistrationModeEntry OBJECT-TYPE
    SYNTAX  RlPortGvrpRegistrationModeEntry
    ACCESS  not-accessible
    STATUS  mandatory
    DESCRIPTION
        "GVRP  Registration Mode value for a bridge port."
    INDEX   { dot1dBasePort }
    ::= { rlPortGvrpRegistrationModeTable 1 }

RlPortGvrpRegistrationModeEntry ::=
    SEQUENCE {
        rlPortGvrpRegistrationModeForbidden        TruthValue
    }

rlPortGvrpRegistrationModeForbidden OBJECT-TYPE
    SYNTAX  TruthValue
    ACCESS  read-write
    STATUS  mandatory
    DESCRIPTION
        "true -  deregisters all VLANS on the specified port and prevents any
                 VLAN creation or registration on that port.
         false - the registration operation on this port behaves normally."
    DEFVAL { false }
    ::= { rlPortGvrpRegistrationModeEntry 1 }


rlDot3adAgg  OBJECT IDENTIFIER ::= { rnd 65 }

rlDot3adAggMibVersion OBJECT-TYPE
    SYNTAX  INTEGER
    ACCESS  read-only
    STATUS  mandatory
    DESCRIPTION
        "MIB's version, the current version is 1."
    ::= { rlDot3adAgg 1 }

--
-- rlDot3adAggBalanceTable
--
rlDot3adAggBalanceTable  OBJECT-TYPE
    SYNTAX  SEQUENCE OF RlDot3adAggBalanceEntry
    ACCESS  not-accessible
    STATUS  mandatory
    DESCRIPTION
        "An entry of this table specifies a balancing criterion used
         for the corresponding dot3adAggIndex."
    ::= { rlDot3adAgg 2 }

rlDot3adAggBalanceEntry OBJECT-TYPE
    SYNTAX  RlDot3adAggBalanceEntry
    ACCESS  not-accessible
    STATUS  mandatory
    DESCRIPTION
        "A list of information for each dot3adAggIndex."
    INDEX  { dot3adAggIndex, rlDot3adAggBalanceForwardType }
    ::= { rlDot3adAggBalanceTable 1 }

RlDot3adAggBalanceEntry ::= SEQUENCE {
    rlDot3adAggBalanceForwardType       INTEGER,
    rlDot3adAggBalanceLayer             INTEGER,
    rlDot3adAggBalanceUsedAddresses     INTEGER,
    rlDot3adAggBalanceBroadcastType     INTEGER
}

rlDot3adAggBalanceForwardType OBJECT-TYPE
    SYNTAX  INTEGER {
        bridging(1),
        routing(2)
    }
    ACCESS  read-only
    STATUS  mandatory
    DESCRIPTION
        "A Forwarding type: Bridging or Routing."
    ::= { rlDot3adAggBalanceEntry 1 }

rlDot3adAggBalanceLayer OBJECT-TYPE
    SYNTAX  INTEGER
    ACCESS  read-write
    STATUS  mandatory
    DESCRIPTION
        "A Network Layer Number, may have the following values: 2, 3 or 4.
         The default value is:
           Bridging: 2
           Routing:  3."
    ::= { rlDot3adAggBalanceEntry 2 }

rlDot3adAggBalanceUsedAddresses  OBJECT-TYPE
    SYNTAX  INTEGER {
        notApplied(0),
        dstAddr(1),
        srcAddr(2),
        dstAndSrcAddr(3),
        vlanId(4),
        ethType(5)
    }
    ACCESS  read-write
    STATUS  mandatory
    DESCRIPTION
        "Specifies the Network Layer addresses used for Balancing of
         unicast frames.
         The function sets the criterion (by layer and used address in it)."
    DEFVAL { dstAddr }
    ::= { rlDot3adAggBalanceEntry 3 }

rlDot3adAggBalanceBroadcastType  OBJECT-TYPE
    SYNTAX  INTEGER {
        common(0),
        dedicated(1)
    }
    ACCESS  read-write
    STATUS  mandatory
    DESCRIPTION
        "Specifies a balancing criterion used for L2 broadcast and unknown
         frames:
            common:
                a link allocated for broadcast and unknown frames is used
                for unicast frames too
            dedicated:
                a link allocated for broadcast and unknown frames is not used
                for unicast frames"
    DEFVAL { common }
    ::= { rlDot3adAggBalanceEntry 4 }

rlDot3adAggNumOfTrunks OBJECT-TYPE
    SYNTAX  INTEGER
    ACCESS  read-only
    STATUS  mandatory
    DESCRIPTION
        "The number of trunks supported by the device."
    ::= { rlDot3adAgg 3 }

rlDot3adAggMaxPortsInTrunks OBJECT-TYPE
    SYNTAX  INTEGER
    ACCESS  read-only
    STATUS  mandatory
    DESCRIPTION
        "The maximun number of ports in a trunk."
    ::= { rlDot3adAgg 4 }

rlDot3adAggTrunkCreationSupport OBJECT-TYPE
    SYNTAX  INTEGER {
        notSupported(0),
        supportsTrunkOrLacp(1)
    }
    ACCESS  read-write
    STATUS  mandatory
    DESCRIPTION
        "Specifies if there is support to rldot3adAggCreationTable,
         and the type of the support:
         supportedTrunkOrLacp - ports that are members in some trunk
         are belongs to it by manual configuration or by lacp,
         but not togther.
         notSupported - there is not support to rldot3adAggCreationTable."
    ::= { rlDot3adAgg 5 }

--
-- rlDot3adAggCreationTable
--
rlDot3adAggCreationTable  OBJECT-TYPE
    SYNTAX  SEQUENCE OF RlDot3adAggCreationEntry
    ACCESS  not-accessible
    STATUS  mandatory
    DESCRIPTION
        "An entry of this table is for creation of an aggregator
         for the corresponding dot3adAggIndex, when the value of the
         rlDot3adAggCreationSupport is diffrent from notSupported."
    ::= { rlDot3adAgg 6 }

rlDot3adAggCreationEntry OBJECT-TYPE
    SYNTAX  RlDot3adAggCreationEntry
    ACCESS  not-accessible
    STATUS  mandatory
    DESCRIPTION
        "An information for each dot3adAggIndex."
    INDEX  { dot3adAggIndex }
    ::= { rlDot3adAggCreationTable 1 }

RlDot3adAggCreationEntry ::= SEQUENCE {
    rlDot3adAggCreationTrunk       TruthValue,
    rlDot3adAggCreationLacp        TruthValue
}

rlDot3adAggCreationTrunk OBJECT-TYPE
    SYNTAX  TruthValue
    ACCESS  read-write
    STATUS  mandatory
    DESCRIPTION
        "The aggregator can aggregate ports in manual configuration."
    ::= { rlDot3adAggCreationEntry 1 }

rlDot3adAggCreationLacp OBJECT-TYPE
    SYNTAX  TruthValue
    ACCESS  read-write
    STATUS  mandatory
    DESCRIPTION
        "The aggregator can aggregate ports by lacp."
    ::= { rlDot3adAggCreationEntry 2 }

rlDot3adAggLoadBalancingPerTrunk OBJECT-TYPE
    SYNTAX  TruthValue
    ACCESS  read-only
    STATUS  mandatory
    DESCRIPTION
        "Specifies if load balancing is defined per trunk
         or per device."
    ::= { rlDot3adAgg 7 }

--
-- rlDot3adAggPortLacpTable
--
rlDot3adAggPortLacpTable  OBJECT-TYPE
    SYNTAX  SEQUENCE OF RlDot3adAggPortLacpEntry
    ACCESS  not-accessible
    STATUS  mandatory
    DESCRIPTION
        "An entry of this table specifies lacp protocol state and
         statistics for the corresponding dot3adAggPortIndex."
    ::= { rlDot3adAgg 8 }

rlDot3adAggPortLacpEntry OBJECT-TYPE
    SYNTAX  RlDot3adAggPortLacpEntry
    ACCESS  not-accessible
    STATUS  mandatory
    DESCRIPTION
        "A list of information for each dot3adAggPortIndex."
    INDEX  { dot3adAggPortIndex }
    ::= { rlDot3adAggPortLacpTable 1 }

RlDot3adAggPortLacpEntry ::= SEQUENCE {
    rlDot3adAggPortLacpPdusRx               Counter,
    rlDot3adAggPortLacpPDUsTx               Counter,
    rlDot3adAggPortLacpRxState              INTEGER,
    rlDot3adAggPortLacpMuxState             INTEGER,
    rlDot3adAggPortLacpPeriodicState        INTEGER,
    rlDot3adAggPortLacpSelected             INTEGER,
    rlDot3adAggPortLacpReady                TruthValue,
    rlDot3adAggPortLacpPortMoved            TruthValue,
    rlDot3adAggPortLacpNNT                  TruthValue,
    rlDot3adAggPortLacpPeriodicTxTimer      INTEGER,
    rlDot3adAggPortLacpCurrentWhileTimer    INTEGER,
    rlDot3adAggPortLacpWaitWhileTimer       INTEGER
}

rlDot3adAggPortLacpPdusRx OBJECT-TYPE
    SYNTAX Counter
    ACCESS read-only
    STATUS mandatory
    DESCRIPTION
        "The number of valid LACPDUs received on this
         Aggregation Port. This value is read-only."
    ::= { rlDot3adAggPortLacpEntry 1 }

rlDot3adAggPortLacpPDUsTx OBJECT-TYPE
    SYNTAX Counter
    ACCESS read-only
    STATUS mandatory
    DESCRIPTION
        "The number of LACPDUs transmitted on this
         Aggregation Port. This value is read-only."
    ::= { rlDot3adAggPortLacpEntry 2 }

rlDot3adAggPortLacpRxState OBJECT-TYPE
    SYNTAX INTEGER {
        current(1),
        expired(2),
        defaulted(3),
        initialize(4),
        portDisabled(5),
        lacpDisabled(6)
    }
    ACCESS read-only
    STATUS mandatory
    DESCRIPTION
        "This attribute holds the value 'current' if the Receive
         state machine for the Aggregation Port is in the
         CURRENT state, 'expired' if the Receive state machine
         is in the EXPIRED state, 'defaulted' if the Receive state
         machine is in the DEFAULTED state, 'initialize' if the
         Receive state machine is in the INITIALIZE state,
         'portDisabled' if the Receive state machine is in the
         PORT_DISABLED state, or 'lacpDisabled' if the Receive state
         machine is in the LACP_DISABLED state.
         This value is read-only."
    ::= { rlDot3adAggPortLacpEntry 3 }

rlDot3adAggPortLacpMuxState OBJECT-TYPE
    SYNTAX INTEGER {
        detached(1),
        waiting(2),
        attached(3),
        collecting(4),
        distributing(5),
        collectingDistributing(6)
    }
    ACCESS read-only
    STATUS mandatory
    DESCRIPTION
        "This attribute holds the value 'detached' if the Mux
         state machine for the Aggregation Port is
         in the DETACHED state, 'waiting' if the Mux state machine
         is in the WAITING state, 'attached' if the Mux state
         machine for the Aggregation Port is in the ATTACHED
         state, 'collecting' if the Mux state machine for the
         Aggregation Port is in the COLLECTING state, 'distributing'
         if the Mux state machine for the Aggregation Port is
         in the DISTRIBUTING state, and 'collecting_ distributing'
         if the Mux state machine for the Aggregation Port is in
         the COLLECTING_DISTRIBUTING state.
         This value is read-only."
    ::= { rlDot3adAggPortLacpEntry 4 }

rlDot3adAggPortLacpPeriodicState OBJECT-TYPE
    SYNTAX INTEGER {
        noPeriodic(1),
        fastPeriodic(2),
        slowPeriodic(3),
        periodicTx(4)
    }
    ACCESS read-only
    STATUS mandatory
    DESCRIPTION
        "This attribute holds the value 'noPeriodic' if the Periodic
         state machine for the Aggregation Port is
         in the NO_PERIODIC state, 'fastPeriodic' if the Mux state machine
         is in the FAST_PERIODIC state, 'slowPeriodic' if the Mux state
         machine for the Aggregation Port is in the SLOW_PERIODIC
         state, or 'periodicTx' if the Periodic state machine
         for the Aggregation Port is in the PERIODIC_TX state.
         This value is read-only."
    ::= { rlDot3adAggPortLacpEntry 5 }

rlDot3adAggPortLacpSelected OBJECT-TYPE
    SYNTAX INTEGER {
        unselected(1),
        selected(2),
        waiting(3)
    }
    ACCESS read-only
    STATUS mandatory
    DESCRIPTION
        "This attribute holds the value 'unselected' if the Selected variable
         for the Aggregation Port is set to UNSELECTED, 'selected' if the
         Selected variable for the Aggregation Port is set to SELECTED,
         or 'waiting' if the Selected variable for the Aggregation Port
         is set to WAITING.
         This value is read-only."
    ::= { rlDot3adAggPortLacpEntry 6 }

rlDot3adAggPortLacpReady OBJECT-TYPE
    SYNTAX TruthValue
    ACCESS read-only
    STATUS mandatory
    DESCRIPTION
        "A read-only Boolean value indicating whether the
         Aggregation Port is in the WAITING state in the Mux state machine
         and its wait_while_timer has expired ('TRUE').
         otherwise, its valus is 'FALSE'."
    ::= { rlDot3adAggPortLacpEntry 7 }

rlDot3adAggPortLacpPortMoved OBJECT-TYPE
    SYNTAX TruthValue
    ACCESS read-only
    STATUS mandatory
    DESCRIPTION
        "A read-only Boolean value indicating whether the
         Partner_Oper_System or Partner_Oper_Port_Number in use by the
         Aggregation Port has been changed in an incoming LACPDU ('TRUE').
         otherwise, its valus is 'FALSE'."
    ::= { rlDot3adAggPortLacpEntry 8 }

rlDot3adAggPortLacpNNT OBJECT-TYPE
    SYNTAX TruthValue
    ACCESS read-only
    STATUS mandatory
    DESCRIPTION
        "A read-only Boolean value indicating whether there is a new protocol
         information that should be transmitted on the link, or that the Partner
         needs to be reminded of the old information.
         otherwise, its valus is 'FALSE'."
    ::= { rlDot3adAggPortLacpEntry 9 }

rlDot3adAggPortLacpPeriodicTxTimer OBJECT-TYPE
    SYNTAX INTEGER
    ACCESS read-only
    STATUS mandatory
    DESCRIPTION
        "The amount of time in seconds remaining before the Periodeic Tx timer
         will expire.
         This value is read-only."
    ::= { rlDot3adAggPortLacpEntry 10 }

rlDot3adAggPortLacpCurrentWhileTimer OBJECT-TYPE
    SYNTAX INTEGER
    ACCESS read-only
    STATUS mandatory
    DESCRIPTION
        "The amount of time in seconds remaining before the Current While timer
         will expire.
         This value is read-only."
    ::= { rlDot3adAggPortLacpEntry 11 }

rlDot3adAggPortLacpWaitWhileTimer OBJECT-TYPE
    SYNTAX INTEGER
    ACCESS read-only
    STATUS mandatory
    DESCRIPTION
        "The amount of time in seconds remaining before the Wait While timer
         will expire.
         This value is read-only."
    ::= { rlDot3adAggPortLacpEntry 12 }

rlDot3adAggLacpMembershipRestrictionsSupport OBJECT-TYPE
    SYNTAX  TruthValue
    ACCESS  read-write
    STATUS  mandatory
    DESCRIPTION
        "Specifies if there is support to
         rlDot3adAggLacpMembershipRestrictionsTable."
    ::= { rlDot3adAgg 9 }

--
-- rlDot3adAggLacpMembershipRestrictionsTable
--
rlDot3adAggLacpMembershipRestrictionsTable  OBJECT-TYPE
    SYNTAX  SEQUENCE OF RlDot3adAggLacpMembershipRestrictionsEntry
    ACCESS  not-accessible
    STATUS  mandatory
    DESCRIPTION
        "An entry of this table specifies membership restrictions
         for ports that lacp is enbaled on them, and try to attach to
         the corresponding dot3adAggIndex."
    ::= { rlDot3adAgg 10 }

rlDot3adAggLacpMembershipRestrictionsEntry OBJECT-TYPE
    SYNTAX  RlDot3adAggLacpMembershipRestrictionsEntry
    ACCESS  not-accessible
    STATUS  mandatory
    DESCRIPTION
        "A list of information for each dot3adAggIndex."
    INDEX  { dot3adAggIndex }
    ::= { rlDot3adAggLacpMembershipRestrictionsTable 1 }

RlDot3adAggLacpMembershipRestrictionsEntry ::= SEQUENCE {
    rlDot3adAggLacpMembershipRestrictionsPartnerAdminKey            Unsigned32,
    rlDot3adAggLacpMembershipRestrictionsSpeedAdminMode             Unsigned32,
    rlDot3adAggLacpMembershipRestrictionsPartnerAdminSystemId       PhysAddress,
    rlDot3adAggLacpMembershipRestrictionsPartnerAdminSystemPriority Unsigned32,
    rlDot3adAggLacpMembershipRestrictionsIndividualAggregator       TruthValue
}

rlDot3adAggLacpMembershipRestrictionsPartnerAdminKey OBJECT-TYPE
    SYNTAX Unsigned32 (0.. 65535)
    ACCESS read-write
    STATUS mandatory
    DESCRIPTION
        "This variable specifies the administrative key
         of the remote LACP aggregator.
         A value of 0 is returned if the value of the variable
         hasn't been set."
    DEFVAL { 0 }
    ::= { rlDot3adAggLacpMembershipRestrictionsEntry 1 }

rlDot3adAggLacpMembershipRestrictionsSpeedAdminMode OBJECT-TYPE
    SYNTAX  Unsigned32
    ACCESS read-write
    STATUS mandatory
    DESCRIPTION
        "This variable specifies the required speed of the LACP aggregator
         in bits per second.
         A value of 10 is returned for 10G.
         A value of 0 is returned if the value of the variable
         hasn't been set."
    DEFVAL { 0 }
    ::= { rlDot3adAggLacpMembershipRestrictionsEntry 2 }

rlDot3adAggLacpMembershipRestrictionsPartnerAdminSystemId OBJECT-TYPE
    SYNTAX PhysAddress
    ACCESS read-write
    STATUS mandatory
    DESCRIPTION
        "This variable specifies the administrative MAC Address
         of the remote LACP aggregator.
         A null mac address is returned if the value of the variable
         hasn't been set."
    ::= { rlDot3adAggLacpMembershipRestrictionsEntry 3 }

rlDot3adAggLacpMembershipRestrictionsPartnerAdminSystemPriority OBJECT-TYPE
    SYNTAX Unsigned32 (0.. 65535)
    ACCESS read-write
    STATUS mandatory
    DESCRIPTION
        "This variable specifies the administrative System Priority
         of the remote LACP aggregator.
         A value of 0 is returned if the value of the variable
         hasn't been set."
    DEFVAL { 0 }
    ::= { rlDot3adAggLacpMembershipRestrictionsEntry 4 }

rlDot3adAggLacpMembershipRestrictionsIndividualAggregator OBJECT-TYPE
    SYNTAX TruthValue
    ACCESS read-write
    STATUS mandatory
    DESCRIPTION
        "This variable specifies if the lacp aggregator represents an
         Aggregate ('FALSE') or an Individual link ('TRUE')."
    DEFVAL { false }
    ::= { rlDot3adAggLacpMembershipRestrictionsEntry 5 }

rlEmbWeb  OBJECT IDENTIFIER ::= { rnd 66 }

rlEmWebMibVersion OBJECT-TYPE
    SYNTAX  INTEGER
    ACCESS  read-only
    STATUS  mandatory
    DESCRIPTION
        "Embedded web version, the current version is 2."
    ::= { rlEmbWeb 1 }

rlEmWebWebSite OBJECT-TYPE
    SYNTAX  DisplayString
    ACCESS  read-write
    STATUS  mandatory
    DESCRIPTION
        "Link for the vendor web site used to retrive information."
    ::= { rlEmbWeb 2 }

rlEmWebSecurityTable OBJECT-TYPE
    SYNTAX  SEQUENCE OF RlEmWebSecurityEntry
    ACCESS  not-accessible
    STATUS  mandatory
    DESCRIPTION
        "Security Table whose entry is composed of username and
         Password, group and access privileges for each user.
         The access privileges can be one or more of none, read-files,
         read-write, and super."
    ::= { rlEmbWeb 3 }

rlEmWebSecurityEntry OBJECT-TYPE
    SYNTAX  RlEmWebSecurityEntry
    ACCESS  not-accessible
    STATUS  mandatory
    DESCRIPTION
        "The row definition for this table."
    INDEX { rlEmWebSecurityUserName }
    ::= { rlEmWebSecurityTable 1 }

RlEmWebSecurityEntry ::= SEQUENCE {
    rlEmWebSecurityUserName     DisplayString,
    rlEmWebSecurityPassword     DisplayString,
    rlEmWebSecurityAccess       INTEGER,
    rlEmWebSecurityIpAddr       IpAddress,
    rlEmWebSecurityPort         INTEGER,
    rlEmWebSecuritySnmpVersion  INTEGER,
    rlEmWebSecurityStatus       RowStatus
}

rlEmWebSecurityUserName OBJECT-TYPE
    SYNTAX  DisplayString (SIZE (1..16))
    ACCESS  read-write
    STATUS  mandatory
    DESCRIPTION
        "The User name."
    ::=  { rlEmWebSecurityEntry 1 }

rlEmWebSecurityPassword OBJECT-TYPE
    SYNTAX  DisplayString (SIZE (1..16))
    ACCESS  read-write
    STATUS  mandatory
    DESCRIPTION
        "The User password."
    ::=  { rlEmWebSecurityEntry 2 }

rlEmWebSecurityAccess OBJECT-TYPE
    SYNTAX  INTEGER {
        none(1),
        readOnly(2),
        readWrite(3),
        super(4)
    }
    ACCESS  read-write
    STATUS  mandatory
    DESCRIPTION
        "Access rights for this user ."
    ::= { rlEmWebSecurityEntry 3 }

rlEmWebSecurityIpAddr OBJECT-TYPE
    SYNTAX  IpAddress
    ACCESS  read-write
    STATUS  mandatory
    DESCRIPTION
        "IP Address to send the traps to.0 means doesn't want
         to receive traps."
    ::= { rlEmWebSecurityEntry 4 }

rlEmWebSecurityPort OBJECT-TYPE
    SYNTAX  INTEGER
    ACCESS  read-write
    STATUS  mandatory
    DESCRIPTION
        "Port to send the traps to."
    ::= { rlEmWebSecurityEntry 5 }

rlEmWebSecuritySnmpVersion OBJECT-TYPE
    SYNTAX  INTEGER {
        ver1(1),
        ver2(2),
        ver3(3)
    }
    ACCESS  read-write
    STATUS  mandatory
    DESCRIPTION
        "SNMP version supported by this user. For the agent use."
    ::= { rlEmWebSecurityEntry 6 }

rlEmWebSecurityStatus OBJECT-TYPE
    SYNTAX  RowStatus
    ACCESS  read-write
    STATUS  mandatory
    DESCRIPTION
        "The status of the security table entry. It's used to delete an entry"
    ::= { rlEmWebSecurityEntry 7 }

rlEmWebCloseTimeout OBJECT-TYPE
    SYNTAX  INTEGER (1..255)
    ACCESS  read-write
    STATUS  mandatory
    DESCRIPTION
        "This variable defines the maximum time period
         in seconds that a TCP connection can stay open
         without depending on the TCP timeout mechanism"
    DEFVAL  { 30 }
    ::= { rlEmbWeb 5 }

rlEmWebReceiveTimeout OBJECT-TYPE
    SYNTAX  INTEGER (1..255)
    ACCESS  read-write
    STATUS  mandatory
    DESCRIPTION
        "This variable defines the maximum time period
         in seconds that a TCP connection can wait for
         data which hasn't arrived "
    DEFVAL  { 30 }
    ::= { rlEmbWeb 6 }

rlEmWebMaxIdleTimeout OBJECT-TYPE
    SYNTAX  INTEGER (1..255)
    ACCESS  read-write
    STATUS  mandatory
    DESCRIPTION
        "This variable defines the maximum Idle time
         period in seconds for a TCP connection.If another request
         isn't made at this period, the connection is closed "
    DEFVAL  { 30 }
    ::= { rlEmbWeb 7 }

rlEmWebSetEWSfilesStatus OBJECT-TYPE
    SYNTAX  INTEGER {
        opened (1),
        closed (2)
    }
    ACCESS  read-write
    STATUS  mandatory
    DESCRIPTION
        "This variable sets the status of the embedded Web Server
        files to either closed or opened."
    DEFVAL  { opened }
    ::= { rlEmbWeb 8 }

rlEmbeddedWebApplied OBJECT-TYPE
    SYNTAX  TruthValue
    ACCESS  read-only
    STATUS  mandatory
    DESCRIPTION
        "Specifies if the device supports Embedded WEB:
                true  - suppotrs
                false - does not support"
    ::= { rlEmbWeb 9 }

rlEmWebHttpPort OBJECT-TYPE
    SYNTAX  INTEGER (0..65535)
    ACCESS  read-write
    STATUS  mandatory
    DESCRIPTION
        "Specifies the TCP port the embedded web uses for HTTP sessions."
    ::= { rlEmbWeb 10 }

rlEmWebHttpEnable OBJECT-TYPE
    SYNTAX  TruthValue
    ACCESS  read-write
    STATUS  mandatory
    DESCRIPTION
        "Enable/Disable HTTP sessions"
    ::= { rlEmbWeb 11 }

rlEmWebHttpsPort OBJECT-TYPE
    SYNTAX  INTEGER (0..65535)
    ACCESS  read-write
    STATUS  mandatory
    DESCRIPTION
        "Specifies the TCP port the embedded web uses for HTTPS sessions."
    ::= { rlEmbWeb 12 }

rlEmWebHttpsEnable OBJECT-TYPE
    SYNTAX  TruthValue
    ACCESS  read-write
    STATUS  mandatory
    DESCRIPTION
        "Enable/Disable HTTPS sessions"
    ::= { rlEmbWeb 13 }

rlEmWebCertificateCountryName OBJECT-TYPE
    SYNTAX  DisplayString (SIZE(2))
    ACCESS  read-write
    STATUS  mandatory
    DESCRIPTION
        "Value of country name field that will appear when a new certificate is generated."
    ::= { rlEmbWeb 14 }

rlEmWebCertificateStateOrProvinceName OBJECT-TYPE
    SYNTAX  DisplayString (SIZE(1..128))
    ACCESS  read-write
    STATUS  mandatory
    DESCRIPTION
        "Value of state or province name field that will appear when a new certificate is generated."
    ::= { rlEmbWeb 15 }


rlEmWebCertificateLocalityName OBJECT-TYPE
    SYNTAX  DisplayString (SIZE(1..64))
    ACCESS  read-write
    STATUS  mandatory
    DESCRIPTION
        "Value of locality field that will appear when a new certificate is generated."
    ::= { rlEmbWeb 16 }


rlEmWebCertificateOrganizationName OBJECT-TYPE
    SYNTAX  DisplayString (SIZE(1..64))
    ACCESS  read-write
    STATUS  mandatory
    DESCRIPTION
        "Value of organization field that will appear when a new certificate is generated."
    ::= { rlEmbWeb 17 }

rlEmWebCertificateCommonName OBJECT-TYPE
    SYNTAX  IpAddress
    ACCESS  read-write
    STATUS  mandatory
    DESCRIPTION
        "Value of common name field that will appear when a new certificate is generated."
    ::= { rlEmbWeb 19 }

rlEmWebCertificateRegenerate OBJECT-TYPE
    SYNTAX  INTEGER {
       noAction(0),
       regenerateCertificate(1),
       regenerateRsaKeyAndCertificate(2)
     }
    ACCESS      read-write
    STATUS      mandatory
    DESCRIPTION
        "Setting to a regenerateCertificate causes a new certifiacte to be generated and to be used for all new sessions."
    ::= { rlEmbWeb 20 }


rlEmWebRsaKeyLength OBJECT-TYPE
    SYNTAX  INTEGER (512..2048)
    ACCESS      read-write
    STATUS      mandatory
    DESCRIPTION
        "Setting the RSA key size that will be created when rlEmWebRegenerateCertificateAndKey will be
         set to regenerateCertificateAndKey."
    ::= { rlEmbWeb 21 }

 rlEmWebDebug OBJECT-TYPE
    SYNTAX  INTEGER
    ACCESS      read-write
    STATUS      mandatory
    DESCRIPTION
        "MIB variable for setting debug information."
    ::= { rlEmbWeb 22  }

rlEmWebURL OBJECT-TYPE
    SYNTAX  DisplayString
    ACCESS      read-only
    STATUS      mandatory
    DESCRIPTION
        "The URL through which the EWS of this device can be accessed."
    ::= { rlEmbWeb 23 }

rlEmWebDisplayNonPresentEntities OBJECT-TYPE
    SYNTAX  TruthValue
    ACCESS      read-only
    STATUS      mandatory
    DESCRIPTION
        "This object indicates whether the EWS is required to display non-present entities
         (like non-present ports, IP addresses on non-present ports etc.) on it's screens."
    ::= { rlEmbWeb 24 }

rlEmWebCertificateExists OBJECT-TYPE
    SYNTAX  TruthValue
    ACCESS      read-only
    STATUS      mandatory
    DESCRIPTION
        "This object indicates whether a certificate has been generated."
    ::= { rlEmbWeb 25 }


rlEmWebHttpsActiveCertificateId OBJECT-TYPE
    SYNTAX  INTEGER
    ACCESS      read-write
    STATUS      mandatory
    DESCRIPTION
        "By setting this scalar https is notified that the certificate and key with this index
        should be used for new https sessions. Even if the certifcate or key doesn't exist yet
        the operation will succeed."
    ::= { rlEmbWeb  26 }

rlSwPackageVersion OBJECT IDENTIFIER ::= { rnd 67 }

rlSwPackageVersionTable OBJECT-TYPE
    SYNTAX  SEQUENCE OF RlSwPackageVersionEntry
    ACCESS  not-accessible
    STATUS  mandatory
    DESCRIPTION
        "The table listing the current versions of packages
         that are included in the running software."
    ::= { rlSwPackageVersion 1 }

rlSwPackageVersionEntry OBJECT-TYPE
    SYNTAX  RlSwPackageVersionEntry
    ACCESS  not-accessible
    STATUS  mandatory
    DESCRIPTION
        "The row definition for this table."
    INDEX {IMPLIED rlSwPackageVersionName }
    ::= { rlSwPackageVersionTable 1 }

RlSwPackageVersionEntry ::= SEQUENCE {
    rlSwPackageVersionName        DisplayString,
    rlSwPackageVersionVesrion     DisplayString
}

rlSwPackageVersionName OBJECT-TYPE
    SYNTAX  DisplayString (SIZE (1..20))
    ACCESS  read-only
    STATUS  mandatory
    DESCRIPTION
        "The Package name."
    ::=  { rlSwPackageVersionEntry 1 }

rlSwPackageVersionVesrion OBJECT-TYPE
    SYNTAX  DisplayString (SIZE (1..20))
    ACCESS  read-only
    STATUS  mandatory
    DESCRIPTION
        "The Package version."
    ::=  { rlSwPackageVersionEntry 2 }

rlBroadcom OBJECT IDENTIFIER ::= { rnd 68 }

rlMultiSessionTerminal  OBJECT IDENTIFIER ::= { rnd 69 }

rlTerminalDebugModePassword OBJECT-TYPE
  SYNTAX DisplayString (SIZE(0..20))
    ACCESS read-write
    STATUS mandatory
    DESCRIPTION
           "When a user wants to change the terminal mode
            from debug mode to ASCII he must enter this password first"
    ::=  { rlMultiSessionTerminal 1 }

rlRCli  OBJECT IDENTIFIER ::= { rnd 70 }

rlRCliMibVersion OBJECT-TYPE
    SYNTAX  INTEGER
    ACCESS  read-only
    STATUS  mandatory
    DESCRIPTION
        "MIB's version, the current version is 1."
    ::= { rlRCli 1 }

rlRCliUserPassword OBJECT-TYPE
   SYNTAX OCTET STRING (SIZE(0..32))
   ACCESS read-write
   STATUS mandatory
   DESCRIPTION
       "RCLI User mode Password"
   ::= { rlRCli 2 }

rlRCliEnablePassword OBJECT-TYPE
   SYNTAX OCTET STRING (SIZE(0..32))
   ACCESS read-write
   STATUS mandatory
   DESCRIPTION
       "RCLI Enable mode Password"
   ::= { rlRCli 3 }

rlRCliConfigPassword OBJECT-TYPE
   SYNTAX OCTET STRING (SIZE(0..32))
   ACCESS read-write
   STATUS mandatory
   DESCRIPTION
       "RCLI Config mode Password"
   ::= { rlRCli 4 }

rlRCliTimer OBJECT-TYPE
   SYNTAX INTEGER (5..3600)
   ACCESS read-write
   STATUS mandatory
   DESCRIPTION
       "RCLI Timeout"
   ::= { rlRCli 5 }

rlRcliFileAction OBJECT-TYPE
    SYNTAX INTEGER {
        notUsedAfterReset(1),
        usedAfterReset   (2)
       }
   ACCESS read-write
   STATUS mandatory
   DESCRIPTION
       "RCLI Configuration File action determines whether
        The device configuration after reset will be set by
        the configuration file content or not."
   ::= { rlRCli 6 }

rlBgp OBJECT IDENTIFIER ::= { rnd 71 }

rlAgentsCapabilitiesGroups  OBJECT IDENTIFIER ::= { rnd 72 }

rlAggregateVlan OBJECT IDENTIFIER ::= {rnd 73}

rlAggregateVlanMibVersion OBJECT-TYPE
    SYNTAX      INTEGER
    ACCESS      read-only
    STATUS      mandatory
    DESCRIPTION
        "MIB's version, the current version is 1."
::= { rlAggregateVlan 1 }

rlAggregateVlanTable OBJECT-TYPE
    SYNTAX  SEQUENCE OF RlAggregateVlanEntry
    ACCESS  not-accessible
    STATUS  mandatory
    DESCRIPTION
        "The table creates an aggregateVlans, the IfIndex is from 10000"
    ::= { rlAggregateVlan 2 }

rlAggregateVlanEntry OBJECT-TYPE
    SYNTAX  RlAggregateVlanEntry
    ACCESS  not-accessible
    STATUS  mandatory
    DESCRIPTION
        "The row definition for this table."
    INDEX { rlAggregateVlanIndex }
    ::= { rlAggregateVlanTable 1 }

RlAggregateVlanEntry ::= SEQUENCE {
    rlAggregateVlanIndex        InterfaceIndex,
    rlAggregateVlanName         DisplayString,
    rlAggregateVlanPhysAddressType  INTEGER,
    rlAggregateVlanStatus       RowStatus
}

rlAggregateVlanIndex OBJECT-TYPE
    SYNTAX  InterfaceIndex
    ACCESS  not-accessible
    STATUS  mandatory
    DESCRIPTION
        "This index indicate the aggrigateVlan id, the aggregate
        vlan index is starting from 10000 "
    ::= { rlAggregateVlanEntry 1 }

rlAggregateVlanName OBJECT-TYPE
    SYNTAX  DisplayString (SIZE(0..32))
    ACCESS  read-write
    STATUS  mandatory
    DESCRIPTION
        "The name of the aggregateVlan "
    DEFVAL {""}
    ::= { rlAggregateVlanEntry 2 }

rlAggregateVlanPhysAddressType OBJECT-TYPE
   SYNTAX  INTEGER {
        default(1),
        reserve(2)
   }
   ACCESS   read-write
   STATUS   mandatory
   DESCRIPTION
        " This variable indicates whether the physical address assigned to this
          VLAN should be the default one or be chosen from the set of
          reserved physical addresses of the device."
   DEFVAL{default}
   ::=  { rlAggregateVlanEntry 3}

rlAggregateVlanStatus OBJECT-TYPE
    SYNTAX  RowStatus
    ACCESS  read-write
    STATUS  mandatory
    DESCRIPTION
        "The status of the aggregateVlan table entry. It's used to delete an entry"
    ::= { rlAggregateVlanEntry 4}

rlAggregateSubVlanTable OBJECT-TYPE
    SYNTAX  SEQUENCE OF RlAggregateSubVlanEntry
    ACCESS  not-accessible
    STATUS  mandatory
    DESCRIPTION
        "The table indicates all the allocated sub-vlans to the
        aggregateVlans, an entry in the rlAggregateVlanTable must
        be exist before allocating the subVlans"
    ::= { rlAggregateVlan 3 }

rlAggregateSubVlanEntry OBJECT-TYPE
    SYNTAX  RlAggregateSubVlanEntry
    ACCESS  not-accessible
    STATUS  mandatory
    DESCRIPTION
        "The row definition for this table."
    INDEX { rlAggregateVlanIndex, rlAggregateSubVlanIfIndex }
    ::= { rlAggregateSubVlanTable 1 }

RlAggregateSubVlanEntry ::= SEQUENCE {
    rlAggregateSubVlanIfIndex   InterfaceIndex,
    rlAggregateSubVlanStatus    RowStatus
}

rlAggregateSubVlanIfIndex OBJECT-TYPE
    SYNTAX  InterfaceIndex
    ACCESS  read-only
    STATUS  mandatory
    DESCRIPTION
        "Indicate the subVlan that allocated to the aggregate vlan"
    ::= { rlAggregateSubVlanEntry 1}

rlAggregateSubVlanStatus OBJECT-TYPE
    SYNTAX  RowStatus
    ACCESS  read-write
    STATUS  mandatory
    DESCRIPTION
        "The status of the aggregateSubVlan table entry.
        It's used to delete an entry"
    ::= { rlAggregateSubVlanEntry 2}

rlAggregateVlanArpProxy OBJECT-TYPE
    SYNTAX INTEGER {
       enable(1),
       disable(2)
    }
    ACCESS read-write
    STATUS mandatory
    DESCRIPTION
         "When ARP Proxy is enabled, the router can respond to
          ARP requests for nodes located on different sub-vlans,
          which belong to the same Super VLAN.The router responds
          with its own MAC address.
          When ARP Proxy is disabled, the router responds only
          to ARP requests for its own IP addresses."
    DEFVAL  { disable }
    ::= { rlAggregateVlan 4 }

-- rlLCli  OBJECT IDENTIFIER ::= { rnd 74 }

rlGmrp  OBJECT IDENTIFIER ::= { rnd 75 }

rlGmrpSupported OBJECT-TYPE
    SYNTAX  TruthValue
    ACCESS  read-only
    STATUS  mandatory
    DESCRIPTION
        "Is Gmrp supported in the device or not."
    ::= { rlGmrp 1 }

rlGmrpMibVersion OBJECT-TYPE
    SYNTAX  INTEGER
    ACCESS  read-only
    STATUS  mandatory
    DESCRIPTION
        "MIB's version, the current version is 1."
    ::= { rlGmrp 2 }

rlPortGmrpTimersTable OBJECT-TYPE
    SYNTAX  SEQUENCE OF RlPortGmrpTimersEntry
    ACCESS  not-accessible
    STATUS  mandatory
    DESCRIPTION
        "A table of Gmrp timer values for every bridge
         port.  This is indexed by dot1dBasePort."
    ::= { rlGmrp 3 }

rlPortGmrpTimersEntry OBJECT-TYPE
    SYNTAX  RlPortGmrpTimersEntry
    ACCESS  not-accessible
    STATUS  mandatory
    DESCRIPTION
        "Gmrp timer values for a bridge port."
    INDEX   { dot1dBasePort }
    ::= { rlPortGmrpTimersTable 1 }

RlPortGmrpTimersEntry ::=
    SEQUENCE {
        rlPortGmrpJoinTime          TimeInterval,
        rlPortGmrpLeaveTime         TimeInterval,
        rlPortGmrpLeaveAllTime      TimeInterval,
        rlPortGmrpOverrideGarp      EnabledStatus
    }

rlPortGmrpJoinTime OBJECT-TYPE
    SYNTAX  TimeInterval
    ACCESS  read-write
    STATUS  mandatory
    DESCRIPTION
        "The Gmrp Join time, in centiseconds."
    DEFVAL { 20 }
    ::= { rlPortGmrpTimersEntry 1 }

rlPortGmrpLeaveTime OBJECT-TYPE
    SYNTAX  TimeInterval
    ACCESS  read-write
    STATUS  mandatory
    DESCRIPTION
        "The Gmrp Leave time, in centiseconds."
    DEFVAL { 60 }
    ::= { rlPortGmrpTimersEntry 2 }

rlPortGmrpLeaveAllTime OBJECT-TYPE
    SYNTAX  TimeInterval
    ACCESS  read-write
    STATUS  mandatory
    DESCRIPTION
        "The Gmrp LeaveAll time, in centiseconds."
    DEFVAL { 1000 }
    ::= { rlPortGmrpTimersEntry 3 }

rlPortGmrpOverrideGarp OBJECT-TYPE
    SYNTAX  EnabledStatus
    ACCESS  read-write
    STATUS  mandatory
    DESCRIPTION
        "If enabled{1}, Gmrp timer values for this port are
         determined by the values in this entry. Otherwise, they
         are determined by the values in dot1dPortGarpTable."
    DEFVAL { disabled }
    ::= { rlPortGmrpTimersEntry 4 }

rlGmrpVlanTable OBJECT-TYPE
    SYNTAX  SEQUENCE OF RlGmrpVlanEntry
    ACCESS  not-accessible
    STATUS  mandatory
    DESCRIPTION
        "This table is to Enable/Disable Gmrp in the vlan."
    ::= { rlGmrp 4 }

rlGmrpVlanEntry OBJECT-TYPE
    SYNTAX  RlGmrpVlanEntry
    ACCESS  not-accessible
    STATUS  mandatory
    DESCRIPTION
        "An entry in the rlGmrpVlanTable."
    INDEX  { rlGmrpVlanTag }
    ::= { rlGmrpVlanTable 1 }

RlGmrpVlanEntry ::= SEQUENCE {
    rlGmrpVlanTag                  INTEGER,
    rlGmrpVlanEnable               TruthValue
}

rlGmrpVlanTag OBJECT-TYPE
    SYNTAX  INTEGER
    ACCESS  read-only
    STATUS  mandatory
    DESCRIPTION
        "The tag of the VLAN for which this entry contains information."
    ::= { rlGmrpVlanEntry 1 }

rlGmrpVlanEnable OBJECT-TYPE
    SYNTAX  TruthValue
    ACCESS  read-write
    STATUS  mandatory
    DESCRIPTION
        "Enable/Disable Gmrp in the vlan."
    DEFVAL { false }
    ::= { rlGmrpVlanEntry 2 }


rlDhcpCl OBJECT IDENTIFIER ::= { rnd 76 }

-- rlDhcpCl 1,2 saved for future use

rlDhcpClActionTable OBJECT-TYPE
    SYNTAX     SEQUENCE OF RlDhcpClActionEntry
    ACCESS     not-accessible
    STATUS     mandatory
    DESCRIPTION
            " The (conceptual) table mentione IP address which must be
              released/renewed on the interface."
    ::= { rlDhcpCl 3 }

rlDhcpClActionEntry OBJECT-TYPE
    SYNTAX     RlDhcpClActionEntry
    ACCESS     not-accessible
    STATUS     mandatory
    DESCRIPTION
            "An entry (conceptual row) in dhcpClActionTable."
    INDEX      { rlDhcpClActionIfIndex }
    ::= { rlDhcpClActionTable 1 }

RlDhcpClActionEntry ::= SEQUENCE {
    rlDhcpClActionIfIndex            InterfaceIndex,
    rlDhcpClActionStatus             RowStatus,
    rlDhcpClActionHostName           SnmpAdminString
}

rlDhcpClActionIfIndex          OBJECT-TYPE
    SYNTAX             InterfaceIndex
    ACCESS         read-only
    STATUS      mandatory
    DESCRIPTION
        " The interface which the action is implemented for
        or NULL if it implemented for all device. "
    ::= { rlDhcpClActionEntry  1 }

rlDhcpClActionStatus OBJECT-TYPE
    SYNTAX     RowStatus
    ACCESS     read-write
    STATUS     mandatory
    DESCRIPTION
            "The status of this entry.  Creating the entry renewing Dhcp
              address on the interface; destroying the entry release Dhcp
              address on the interface."
    ::= { rlDhcpClActionEntry   2}

rlDhcpClActionHostName OBJECT-TYPE
    SYNTAX SnmpAdminString (SIZE(0..20))
    ACCESS read-write
    STATUS mandatory
    DESCRIPTION
       " This option specifies the name of the client."
    ::= { rlDhcpClActionEntry   3 }


rlStormCtrl OBJECT IDENTIFIER ::= { rnd 77 }

rlStormCtrlSupport OBJECT-TYPE
    SYNTAX      TruthValue
    ACCESS      read-only
    STATUS      mandatory
    DESCRIPTION
        "Identify if the strom control protection is supported"
    ::= { rlStormCtrl 1 }

rlStormCtrlMibVersion OBJECT-TYPE
    SYNTAX      INTEGER
    ACCESS      read-only
    STATUS      mandatory
    DESCRIPTION
        "MIB's version, the current version is 3."
    ::= { rlStormCtrl 2 }

rlStormCtrlRateUnitTypeSupport OBJECT-TYPE
--    SYNTAX      BITS {
--            packetsPerSecond(0),
--            bytesPerSecond(1),
--            framesPerBuffer(2),
--            percentages(3),
--            kiloBytesPerSecond(4),
--            kiloBitsPerSecond(5)
--    }
    SYNTAX  OCTET STRING (SIZE(1))
    ACCESS  read-only
    STATUS  mandatory
    DESCRIPTION
        "the supported rate unit type for the storm rate control"
    ::= { rlStormCtrl 3 }

rlStormCtrlTypeSupport  OBJECT-TYPE
--    SYNTAX      BITS {
--            unknownUnicast(0),
--            unknownMulticast(1),
--            broadcast(2),
--            multicast(3),
--    }
    SYNTAX  OCTET STRING (SIZE(1))
    ACCESS  read-only
    STATUS  mandatory
    DESCRIPTION
        "the supported frame type for the storm control protection"
    ::= { rlStormCtrl 4 }

rlStormCtrlRateSupportPerType OBJECT-TYPE
--    SYNTAX      BITS {
--            unknownUnicast(0),
--            unknownMulticast(1),
--            broadcast(2),
--            multicast(3),
--    }
    SYNTAX  OCTET STRING (SIZE(1))
    ACCESS  read-only
    STATUS  mandatory
    DESCRIPTION
        "identify if rate control is supported for each frame type"
    ::= { rlStormCtrl 5 }

rlStormCtrlEnbaleDependencyBetweenTypes OBJECT-TYPE
--    SYNTAX      BITS {
--            unknownUnicast(0),
--            unknownMulticast(1),
--            broadcast(2),
--            multicast(3),
--    }
    SYNTAX  OCTET STRING (SIZE(1))
    ACCESS  read-only
    STATUS  mandatory
    DESCRIPTION
        "indicate enable limitation of dependency between frame types,
         such as enabling of multicast should be with the enabling of
         broadcast type (bcm 5632)"
    ::= { rlStormCtrl 6 }

rlStormCtrlRateDependencyBetweenTypes OBJECT-TYPE
--    SYNTAX      BITS {
--            unknownUnicast(0),
--            unknownMulticast(1),
--            broadcast(2),
--            multicast(3),
--    }
    SYNTAX  OCTET STRING (SIZE(1))
    ACCESS  read-only
    STATUS  mandatory
    DESCRIPTION
        "indicate limitation of dependency between frame types for
         rate assignment, for example: assigning of rate limit for unicast
         frame must assigning the same rate for multicast and bradcast
         frame (bcm 5615), in case the device support enbale per each frame
         type but with the same rate limitation."
    ::= { rlStormCtrl 7 }

--
-- rlStormCtrlTable
--
rlStormCtrlTable   OBJECT-TYPE
    SYNTAX  SEQUENCE OF RlStormCtrlEntry
    ACCESS  not-accessible
    STATUS  mandatory
    DESCRIPTION
        "The table contains the storm control protection per port"
    ::= { rlStormCtrl 8 }

rlStormCtrlEntry   OBJECT-TYPE
    SYNTAX  RlStormCtrlEntry
    ACCESS  not-accessible
    STATUS  mandatory
    DESCRIPTION
        "storm control protection, defined per port,frame type and rate"
    INDEX { dot1dBasePort }
    ::= { rlStormCtrlTable 1 }

RlStormCtrlEntry ::= SEQUENCE {
    rlStormCtrlRateType                         RlStormCtrlRateUnit,
    rlStormCtrlUnknownUnicastEnable             TruthValue,
    rlStormCtrlUnknownUnicastRate               Unsigned32,
    rlStormCtrlUnknownMulticastEnable           TruthValue,
    rlStormCtrlUnknownMulticastRate             Unsigned32,
    rlStormCtrlBroadcastEnable                  TruthValue,
    rlStormCtrlBroadcastRate                    Unsigned32,
    rlStormCtrlMulticastEnable                  TruthValue,
    rlStormCtrlMulticastRate                    Unsigned32,
    rlStormCtrlSetDefaultRateType               TruthValue,
    rlStormCtrlSetDefaultUnknownUnicastEnable   TruthValue,
    rlStormCtrlSetDefaultUnknownUnicastRate     TruthValue,
    rlStormCtrlSetDefaultUnknownMulticastEnable TruthValue,
    rlStormCtrlSetDefaultUnknownMulticastRate   TruthValue,
    rlStormCtrlSetDefaultBroadcastEnable        TruthValue,
    rlStormCtrlSetDefaultBroadcastRate          TruthValue,
    rlStormCtrlSetDefaultMulticastEnable        TruthValue,
    rlStormCtrlSetDefaultMulticastRate          TruthValue
}

rlStormCtrlRateType OBJECT-TYPE
    SYNTAX  RlStormCtrlRateUnit
    ACCESS  read-write
    STATUS  mandatory
    DESCRIPTION
        "indicate the rate unit type"
    ::= { rlStormCtrlEntry 1 }

rlStormCtrlUnknownUnicastEnable OBJECT-TYPE
    SYNTAX  TruthValue
    ACCESS  read-write
    STATUS  mandatory
    DESCRIPTION
        "enable or disable the storm control for unknown unicast frames"
    DEFVAL { false }
    ::= { rlStormCtrlEntry 2 }

rlStormCtrlUnknownUnicastRate OBJECT-TYPE
    SYNTAX  Unsigned32
    ACCESS  read-write
    STATUS  mandatory
    DESCRIPTION
        "set the storm control rate limit for the unknown unicast frames,
        0 indicate blocking of frames from this type."
    DEFVAL { 0 }
    ::= { rlStormCtrlEntry 3 }

rlStormCtrlUnknownMulticastEnable OBJECT-TYPE
    SYNTAX  TruthValue
    ACCESS  read-write
    STATUS  mandatory
    DESCRIPTION
        "enable or disable the storm control for unknown multicast frames"
    DEFVAL { false }
    ::= { rlStormCtrlEntry 4 }

rlStormCtrlUnknownMulticastRate OBJECT-TYPE
    SYNTAX  Unsigned32
    ACCESS  read-write
    STATUS  mandatory
    DESCRIPTION
        "set the storm control rate limit for the unknown multicast frames,
        0 indicate blocking of frames from this type."
    DEFVAL { 0 }
    ::= { rlStormCtrlEntry 5 }

rlStormCtrlBroadcastEnable OBJECT-TYPE
    SYNTAX  TruthValue
    ACCESS  read-write
    STATUS  mandatory
    DESCRIPTION
        "enable or disable the storm control for Broadcast frames"
    DEFVAL { false }
    ::= { rlStormCtrlEntry 6 }

rlStormCtrlBroadcastRate OBJECT-TYPE
    SYNTAX  Unsigned32
    ACCESS  read-write
    STATUS  mandatory
    DESCRIPTION
        "set the storm control rate limit for the Broadcast frames,
        0 indicate blocking of frames from this type."
    DEFVAL { 0 }
    ::= { rlStormCtrlEntry 7 }

rlStormCtrlMulticastEnable OBJECT-TYPE
    SYNTAX  TruthValue
    ACCESS  read-write
    STATUS  mandatory
    DESCRIPTION
        "enable or disable the storm control for multicast frames"
    DEFVAL { false }
    ::= { rlStormCtrlEntry 8 }

rlStormCtrlMulticastRate OBJECT-TYPE
    SYNTAX  Unsigned32
    ACCESS  read-write
    STATUS  mandatory
    DESCRIPTION
        "set the storm control rate limit for the multicast frames,
        0 indicate blocking of frames from this type."
    DEFVAL { 0 }
    ::= { rlStormCtrlEntry 9 }

rlStormCtrlSetDefaultRateType OBJECT-TYPE
    SYNTAX  TruthValue
    ACCESS  read-write
    STATUS  mandatory
    DESCRIPTION
        "indicate if return the rate unit type to its default."
    DEFVAL { false }
    ::= { rlStormCtrlEntry 10 }

rlStormCtrlSetDefaultUnknownUnicastEnable OBJECT-TYPE
    SYNTAX  TruthValue
    ACCESS  read-write
    STATUS  mandatory
    DESCRIPTION
        "indicate if return the storm control enable for unknown unicast frames
         to its default."
    DEFVAL { false }
    ::= { rlStormCtrlEntry 11 }

rlStormCtrlSetDefaultUnknownUnicastRate OBJECT-TYPE
    SYNTAX  TruthValue
    ACCESS  read-write
    STATUS  mandatory
    DESCRIPTION
        "indicate if return the storm control rate limit for the unknown unicast frames
         to its default."
    DEFVAL { false }
    ::= { rlStormCtrlEntry 12 }

rlStormCtrlSetDefaultUnknownMulticastEnable OBJECT-TYPE
    SYNTAX  TruthValue
    ACCESS  read-write
    STATUS  mandatory
    DESCRIPTION
        "indicate if return the storm control enable for unknown multicast frames
         to its default."
    DEFVAL { false }
    ::= { rlStormCtrlEntry 13 }

rlStormCtrlSetDefaultUnknownMulticastRate OBJECT-TYPE
    SYNTAX  TruthValue
    ACCESS  read-write
    STATUS  mandatory
    DESCRIPTION
        "indicate if return the storm control rate limit for the unknown multicast frames
         to its default."
    DEFVAL { false }
    ::= { rlStormCtrlEntry 14 }

rlStormCtrlSetDefaultBroadcastEnable OBJECT-TYPE
    SYNTAX  TruthValue
    ACCESS  read-write
    STATUS  mandatory
    DESCRIPTION
        "indicate if return the storm control enable for Broadcast frames
         to its default."
    DEFVAL { false }
    ::= { rlStormCtrlEntry 15 }

rlStormCtrlSetDefaultBroadcastRate OBJECT-TYPE
    SYNTAX  TruthValue
    ACCESS  read-write
    STATUS  mandatory
    DESCRIPTION
        "indicate if return the storm control rate limit for the Broadcast frames
         to its default."
    DEFVAL { false }
    ::= { rlStormCtrlEntry 16 }

rlStormCtrlSetDefaultMulticastEnable OBJECT-TYPE
    SYNTAX  TruthValue
    ACCESS  read-write
    STATUS  mandatory
    DESCRIPTION
        "indicate if return the storm control for multicast frames
         to its default."
    DEFVAL { false }
    ::= { rlStormCtrlEntry 17 }

rlStormCtrlSetDefaultMulticastRate OBJECT-TYPE
    SYNTAX  TruthValue
    ACCESS  read-write
    STATUS  mandatory
    DESCRIPTION
        "indicate if return the storm control rate limit for the multicast frames
         to its default."
    DEFVAL { false }
    ::= { rlStormCtrlEntry 18 }

--
-- rlStormCtrlGroupTable
--
rlStormCtrlGroupTable   OBJECT-TYPE
    SYNTAX   SEQUENCE OF RlStormCtrlGroupEntry
    ACCESS   not-accessible
    STATUS   mandatory
    DESCRIPTION
        "The table contains per port for each supported frame type
        to which group it belongs."
    ::= { rlStormCtrl 9 }

rlStormCtrlGroupEntry   OBJECT-TYPE
    SYNTAX   RlStormCtrlGroupEntry
    ACCESS   not-accessible
    STATUS   mandatory
    DESCRIPTION
        "group id for each supported frame type defined per port."
    INDEX { dot1dBasePort }
    ::= { rlStormCtrlGroupTable 1 }

RlStormCtrlGroupEntry ::= SEQUENCE {
    rlStormCtrlGroupUnknownUnicastId      INTEGER,
    rlStormCtrlGroupUnknownMulticastId    INTEGER,
    rlStormCtrlGroupBroadcastId           INTEGER,
    rlStormCtrlGroupMulticastId           INTEGER
}

rlStormCtrlGroupUnknownUnicastId OBJECT-TYPE
    SYNTAX   INTEGER
    ACCESS   read-only
    STATUS   mandatory
    DESCRIPTION
        "Indicates the id of the group for unknown unicast frame type that
        the port belongs to,
        0 indicates that unknown unicast frame type is not supported."
    ::= { rlStormCtrlGroupEntry 1 }

rlStormCtrlGroupUnknownMulticastId OBJECT-TYPE
    SYNTAX   INTEGER
    ACCESS   read-only
    STATUS   mandatory
    DESCRIPTION
        "Indicates the id of the group for unknown multicast frame type that
        the port belongs to,
        0 indicates that unknown multicast frame type is not supported."
    ::= { rlStormCtrlGroupEntry 2 }

rlStormCtrlGroupBroadcastId OBJECT-TYPE
    SYNTAX   INTEGER
    ACCESS   read-only
    STATUS   mandatory
    DESCRIPTION
        "Indicates the id of the group for broadcast frame type that
        the port belongs to,
        0 indicates that broadcast frame type is not supported."
    ::= { rlStormCtrlGroupEntry 3 }

rlStormCtrlGroupMulticastId  OBJECT-TYPE
    SYNTAX   INTEGER
    ACCESS   read-only
    STATUS   mandatory
    DESCRIPTION
        "Indicates the id of the group for multicast frame type that
        the port belongs to,
        0 indicates that multicast frame type is not supported."
    ::= { rlStormCtrlGroupEntry 4 }

rlSsh OBJECT IDENTIFIER ::= { rnd 78 }

rlAAA OBJECT IDENTIFIER ::= { rnd 79 }

rlRadius  OBJECT IDENTIFIER ::= { rnd 80 }

-- see rlAAA.mib

rlTraceRoute  OBJECT IDENTIFIER ::= { rnd 81 }

rlTraceRouteMibVersion OBJECT-TYPE
    SYNTAX  INTEGER
    ACCESS  read-only
    STATUS  mandatory
    DESCRIPTION
        "MIB's version, the current version is 1."
    ::= { rlTraceRoute 1 }

rlSyslog  OBJECT IDENTIFIER ::= { rnd 82 }

rlEnv  OBJECT IDENTIFIER ::= { rnd 83 }
-- rlPhysicalDescription OBJECT IDENTIFIER ::= { rlEnv 1 }
-- entitySensorMIB OBJECT IDENTIFIER ::= { rlEnv 2 }

rlSmon  OBJECT IDENTIFIER ::= { rnd 84 }

rlPortCopyMibVersion OBJECT-TYPE
    SYNTAX  INTEGER
    ACCESS  read-only
    STATUS  mandatory
    DESCRIPTION
        "MIB's version, the current version is 1."
    ::= { rlSmon 1 }

rlPortCopySupport OBJECT-TYPE
   SYNTAX INTEGER {
       supported(1),
       notSupported(2)
   }
   ACCESS read-only
   STATUS mandatory
   DESCRIPTION
       "supported - The standard portCopy is supported.
        notSupported - the standard portCopy is not supported.
                       only basic portCopy operation is supported. "
   ::= { rlSmon 2 }

rlPortCopyVlanTaggingTable OBJECT-TYPE
    SYNTAX  SEQUENCE OF RlPortCopyVlanTaggingEntry
    ACCESS  not-accessible
    STATUS  mandatory
    DESCRIPTION
        "A supplementing table for portCopyTable.
         For every portCopyDest a vlan-tagging option is available."
    ::= { rlSmon 3 }

rlPortCopyVlanTaggingEntry OBJECT-TYPE
    SYNTAX  RlPortCopyVlanTaggingEntry
    ACCESS  not-accessible
    STATUS  mandatory
    DESCRIPTION
        "Each entry specify how  mirrored packets will transmit from
         the portCopyDest:   Tagged or unTagged.
         The values in this entry will be valid only when the
         dot1dBasePort will be configured as a portCopyDest
         in the portCopyTable."
    INDEX   { dot1dBasePort }
    ::= { rlPortCopyVlanTaggingTable 1 }

RlPortCopyVlanTaggingEntry ::=
    SEQUENCE {
        rlPortCopyVlanTagging     TruthValue
    }

rlPortCopyVlanTagging  OBJECT-TYPE
    SYNTAX  TruthValue
    ACCESS  read-write
    STATUS  mandatory
    DESCRIPTION
        "TRUE  - Mirrored packets will transmit from portCopyDest - Tagged
         FALSE - Mirrored packets will transmit from portCopyDest - unTagged"
    DEFVAL { false }
    ::= { rlPortCopyVlanTaggingEntry 1 }

rlSocket OBJECT IDENTIFIER ::= { rnd 85 }

rlSocketMibVersion OBJECT-TYPE
    SYNTAX      INTEGER
    ACCESS      read-only
    STATUS      mandatory
    DESCRIPTION
        "MIB's version, the current version is 1."
    ::= { rlSocket 1 }

rlSocketTable OBJECT-TYPE
    SYNTAX
    SEQUENCE OF RlSocketEntry
    ACCESS      not-accessible
    STATUS      mandatory
    DESCRIPTION
        "The (conceptual) table listing the sockets which are currently
        open in the system."
    ::= { rlSocket 2 }

rlSocketEntry OBJECT-TYPE
    SYNTAX      RlSocketEntry
    ACCESS      not-accessible
    STATUS      mandatory
    DESCRIPTION
        "An entry (conceptual row) in the SocketTable."
    INDEX      { rlSocketId }
    ::= { rlSocketTable 1 }

RlSocketEntry ::= SEQUENCE {
    rlSocketId                      INTEGER,
    rlSocketType                    INTEGER,
    rlSocketState                   INTEGER,
    rlSocketBlockMode               INTEGER,
    rlSocketUpTime                  TimeTicks
}

rlSocketId OBJECT-TYPE
    SYNTAX  INTEGER
    ACCESS  read-only
    STATUS  mandatory
    DESCRIPTION
        "The value of the id of the socket. "
    ::= { rlSocketEntry 1 }

rlSocketType OBJECT-TYPE
    SYNTAX  INTEGER {
        stream(1),
        dgram(2),
        raw(3)
    }
    ACCESS  read-only
    STATUS  mandatory
    DESCRIPTION
        "Specifies the type of the socket. "
    ::= { rlSocketEntry 2 }

rlSocketState OBJECT-TYPE
    SYNTAX  INTEGER {
        connected(1),
        notConnected(2),
        recvClosed(3),
        sendClosed(4),
        closed(5)
    }
    ACCESS  read-only
    STATUS  mandatory
    DESCRIPTION
        "Specifies the state in which the socket is in. "
    ::= { rlSocketEntry 3 }

rlSocketBlockMode OBJECT-TYPE
    SYNTAX  INTEGER {
        blocking(1),
        nonBlocking(2)
    }
    ACCESS  read-only
    STATUS  mandatory
    DESCRIPTION
        "Specifies the blocking mode of the socket. "
    ::= { rlSocketEntry 4 }

rlSocketUpTime OBJECT-TYPE
    SYNTAX      TimeTicks
    ACCESS      read-only
    STATUS      mandatory
    DESCRIPTION
        "The time elapsed since this socket was created."
    ::= { rlSocketEntry 5 }

rlDigitalKeyManage OBJECT IDENTIFIER ::= { rnd 86 }

rlMD5KeyChainTable OBJECT-TYPE
    SYNTAX  SEQUENCE  OF RlMD5KeyChainEntry
    ACCESS  not-accessible
    STATUS  mandatory
    DESCRIPTION
       "Key-chains and key ID's"
    ::=   { rlDigitalKeyManage 1 }

rlMD5KeyChainEntry   OBJECT-TYPE
    SYNTAX  RlMD5KeyChainEntry
    ACCESS  not-accessible
    STATUS  mandatory
    DESCRIPTION
            "Key-chain with key ID that belongs to this chain"
    INDEX  {rlMD5KeyChainName, rlMD5KeyChainKeyId}
    ::=  { rlMD5KeyChainTable 1 }

RlMD5KeyChainEntry ::= SEQUENCE {
    rlMD5KeyChainName                        DisplayString,
    rlMD5KeyChainKeyId                       INTEGER,
    rlMD5KeyChainKeyRowStatus                RowStatus
}

rlMD5KeyChainName OBJECT-TYPE
    SYNTAX  DisplayString
    ACCESS  read-only
    STATUS  mandatory
    DESCRIPTION
        "Name of the key-chain to which belongs
         the secret authentication key"
    ::= { rlMD5KeyChainEntry 1 }

rlMD5KeyChainKeyId OBJECT-TYPE
    SYNTAX  INTEGER  (1..255)
    ACCESS  read-only
    STATUS  mandatory
    DESCRIPTION
        "A 8-bit identifier for the secret authentication key.
         This identifier is the same as key ID used in rlMD5KeyTable."
    ::= { rlMD5KeyChainEntry 2 }

rlMD5KeyChainKeyRowStatus OBJECT-TYPE
    SYNTAX  RowStatus
    ACCESS  read-write
    STATUS  mandatory
    DESCRIPTION
        "It is used to insert, update or delete an entry"
    ::= { rlMD5KeyChainEntry 3 }


rlMD5KeyTable OBJECT-TYPE
    SYNTAX  SEQUENCE  OF RlMD5KeyEntry
    ACCESS  not-accessible
    STATUS  mandatory
    DESCRIPTION
       "Secret authentication keys
         used by MD5 Authentication Algorithm"
    ::=   { rlDigitalKeyManage 2 }

rlMD5KeyEntry   OBJECT-TYPE
    SYNTAX  RlMD5KeyEntry
    ACCESS  not-accessible
    STATUS  mandatory
    DESCRIPTION
            "Secret authentication key with all related parameters"
    INDEX  {rlMD5KeyId}
    ::=  { rlMD5KeyTable 1 }

RlMD5KeyEntry ::= SEQUENCE {
    rlMD5KeyId                          INTEGER,
    rlMD5Key                            DisplayString,
    rlMD5KeyStartAccept                        DateAndTime,
    rlMD5KeyStartGenerate                DateAndTime,
    rlMD5KeyStopGenerate                DateAndTime,
    rlMD5KeyStopAccept                        DateAndTime,
    rlMD5KeyRowStatus                   RowStatus
}

rlMD5KeyId OBJECT-TYPE
    SYNTAX  INTEGER  (1..255)
    ACCESS  read-only
    STATUS  mandatory
    DESCRIPTION
        "A 8-bit identifier for the secret authentication key"
    ::= { rlMD5KeyEntry 1 }

rlMD5Key OBJECT-TYPE
    SYNTAX  DisplayString (SIZE (1..16))
    ACCESS  read-write
    STATUS  mandatory
    DESCRIPTION
        "The 128-bit secret authentication key.
         The key can get value only once and cannot be modified.
         When read, rlMD5KeyChainKey always returns an
         Octet String of length zero."
    ::= { rlMD5KeyEntry 2 }

rlMD5KeyStartAccept OBJECT-TYPE
    SYNTAX  DateAndTime
    ACCESS  read-write
    STATUS  mandatory
    DESCRIPTION
        "The time that the router will start accepting packets
          that have been created with the given key"
    DEFVAL   { '00000000'H }
    ::= { rlMD5KeyEntry 3 }

rlMD5KeyStartGenerate OBJECT-TYPE
    SYNTAX  DateAndTime
    ACCESS  read-write
    STATUS  mandatory
    DESCRIPTION
        "The time that the router will start using the key
         for packet generation"
    DEFVAL   { '00000000'H }
    ::= { rlMD5KeyEntry 4 }

rlMD5KeyStopGenerate OBJECT-TYPE
    SYNTAX  DateAndTime
    ACCESS  read-write
    STATUS  mandatory
    DESCRIPTION
        "The time that the router will stop using the key
         for packet generation"
    DEFVAL   { 'FFFFFFFF'H }
    ::= { rlMD5KeyEntry 5 }

rlMD5KeyStopAccept OBJECT-TYPE
    SYNTAX  DateAndTime
    ACCESS  read-write
    STATUS  mandatory
    DESCRIPTION
        "The time that the router will stop accepting packets
          that have been created with the given key"
    DEFVAL   { 'FFFFFFFF'H }
    ::= { rlMD5KeyEntry 6 }

rlMD5KeyRowStatus OBJECT-TYPE
    SYNTAX  RowStatus
    ACCESS  read-write
    STATUS  mandatory
    DESCRIPTION
        "It is used to insert, update or delete an entry"
    ::= { rlMD5KeyEntry 7 }

rlCopy  OBJECT IDENTIFIER ::= { rnd 87 }

rlQosCliMib OBJECT IDENTIFIER ::= { rnd 88 }

rlMngInf OBJECT IDENTIFIER ::= { rnd 89 }

rlPhy OBJECT IDENTIFIER ::= { rnd 90 }

rlJumboFrames OBJECT IDENTIFIER ::= { rnd 91 }

rlJumboFramesCurrentStatus OBJECT-TYPE
    SYNTAX  INTEGER {
        enable(1),
        disable(2)
    }
    ACCESS  read-only
    STATUS  mandatory
    DESCRIPTION
        "Show the current Jumbo Frames status"
    ::= { rlJumboFrames 1 }

rlJumboFramesStatusAfterReset OBJECT-TYPE
    SYNTAX  INTEGER {
        enable(1),
        disable(2)
    }
    ACCESS  read-write
    STATUS  mandatory
    DESCRIPTION
        "Set the Jumbo Frames status after reset"
    ::= { rlJumboFrames 2 }

rlTimeSynchronization OBJECT IDENTIFIER ::= { rnd 92 }

rlDnsCl OBJECT IDENTIFIER ::= { rnd 93 }

rlCDB  OBJECT IDENTIFIER ::= { rnd 94 }

rlStartupCDBChanged OBJECT-TYPE
    SYNTAX TruthValue
    ACCESS read-only
    STATUS mandatory
    DESCRIPTION
        "Indicates whether the startup CDB has changed between the router's
         last two reboots"
    ::= {rlCDB 1 }

rlManualReboot OBJECT-TYPE
    SYNTAX TruthValue
    ACCESS read-only
    STATUS mandatory
    DESCRIPTION
        "Indicates whether the device was shutdown orderly before reboot or
         not (i.e. power failure)"
    ::= {rlCDB 2 }

rldot1x  OBJECT IDENTIFIER ::= { rnd 95 }

rldot1xMibVersion OBJECT-TYPE
    SYNTAX  INTEGER
    ACCESS  read-only
    STATUS  mandatory
    DESCRIPTION
        "MIB's version, the current version is 1."
    ::= { rldot1x 1 }

rldot1xExtAuthSessionStatsTable OBJECT-TYPE
    SYNTAX      SEQUENCE OF Rldot1xExtAuthSessionStatsEntry
    ACCESS      not-accessible
    STATUS      mandatory
    DESCRIPTION
        "A table that contains the session statistics objects
        for the Authenticator PAE associated with each Port.
        An entry appears in this table for each port that may
        authenticate access to itself."
    ::= { rldot1x 2 }

rldot1xExtAuthSessionStatsEntry OBJECT-TYPE
    SYNTAX      Rldot1xExtAuthSessionStatsEntry
    ACCESS      not-accessible
    STATUS      mandatory
    DESCRIPTION
        "The session statistics information for an Authenticator
        PAE.  This shows the current values being collected for
        each session that is still in progress, or the final
        values for the last valid session on each port where
        there is no session currently active."
    AUGMENTS    { dot1xAuthSessionStatsEntry }
    ::= { rldot1xExtAuthSessionStatsTable 1 }

Rldot1xExtAuthSessionStatsEntry ::=
    SEQUENCE {
        rlDot1xAuthSessionAuthenticMethod
            INTEGER
    }

rlDot1xAuthSessionAuthenticMethod OBJECT-TYPE
    SYNTAX      INTEGER {
                    remoteAuthServer(1),
                    localAuthServer(2),
                    none(3)
                }
    ACCESS      read-only
    STATUS      mandatory
    DESCRIPTION
        "The authentication method used to establish the
        session."
    ::= { rldot1xExtAuthSessionStatsEntry 1 }

rldot1xGuestVlanSupported OBJECT-TYPE
    SYNTAX TruthValue
    ACCESS read-only
    STATUS mandatory
    DESCRIPTION
         "indicate if guest vlan is supported."
    ::= { rldot1x  3 }

rldot1xGuestVlanVID OBJECT-TYPE
    SYNTAX VlanIndex
    ACCESS read-write
    STATUS mandatory
    DESCRIPTION
         "specify the guest vlan tag , 0 for non exiting."
    ::= { rldot1x  4 }

rldot1xGuestVlanPorts OBJECT-TYPE
    SYNTAX      PortList
    ACCESS      read-write
    STATUS      mandatory
    DESCRIPTION
        "the ports that can be members in the guest vlan"
    ::= { rldot1x  5 }

rldot1xUnAuthenticatedVlanSupported OBJECT-TYPE
    SYNTAX TruthValue
    ACCESS read-only
    STATUS mandatory
    DESCRIPTION
         "indicate if unauthenticated Vlan is supported."
    ::= { rldot1x  6 }

rldot1xUnAuthenticatedVlanTable OBJECT-TYPE
    SYNTAX  SEQUENCE OF Rldot1xUnAuthenticatedVlanEntry
    ACCESS  not-accessible
    STATUS  mandatory
    DESCRIPTION
        "port belong to vlan in all port authenticated state except force unauthenticated table"
    ::= { rldot1x  7 }

rldot1xUnAuthenticatedVlanEntry OBJECT-TYPE
    SYNTAX  Rldot1xUnAuthenticatedVlanEntry
    ACCESS  not-accessible
    STATUS  mandatory
    DESCRIPTION
        " port belong to vlan in all port authenticated state except force unauthenticated entry"
    INDEX   { dot1qFdbId  }
    ::= { rldot1xUnAuthenticatedVlanTable 1 }

Rldot1xUnAuthenticatedVlanEntry ::= SEQUENCE {
        rldot1xUnAuthenticatedVlanStatus  RowStatus
    }

rldot1xUnAuthenticatedVlanStatus OBJECT-TYPE
    SYNTAX   RowStatus
    ACCESS read-write
    STATUS   mandatory
    DESCRIPTION
       "The row status variable, used according to
       row installation and removal conventions."
    ::= { rldot1xUnAuthenticatedVlanEntry 1 }

rldot1xUserBasedVlanSupported OBJECT-TYPE
    SYNTAX TruthValue
    ACCESS read-only
    STATUS mandatory
    DESCRIPTION
         "indicate if user based Vlan is supported."
    ::= { rldot1x  8 }

rldot1xUserBasedVlanPorts OBJECT-TYPE
    SYNTAX      PortList
    ACCESS      read-write
    STATUS      mandatory
    DESCRIPTION
        "the ports that can be members in the user based vlan"
    ::= { rldot1x  9 }

rlFile  OBJECT IDENTIFIER ::= { rnd 96 }

rlAAAEap OBJECT IDENTIFIER ::= { rnd 97 }

rlSNMP OBJECT IDENTIFIER ::= { rnd 98 }


--rlQosServ OBJECT IDENTIFIER ::= { rnd 99 }

rlSsl OBJECT IDENTIFIER ::= { rnd 100 }

rlMacBasePrio OBJECT IDENTIFIER ::= { rnd 101 }

rlWlanAccessPoint OBJECT IDENTIFIER ::= { rnd 101 }

--xxxx  OBJECT IDENTIFIER ::= { rnd 103 }

rndEndOfMibGroup   OBJECT IDENTIFIER ::= { rnd 1000  }

rndEndOfMib OBJECT-TYPE
      SYNTAX  INTEGER
      ACCESS   read-only
      STATUS   mandatory
      DESCRIPTION
        " This variable indicates this is the end of RND MIB."
      ::= {  rndEndOfMibGroup 1  }


-- Enterprise-specific traps for RND
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rnd
--       VARIABLES   { rndErrorDesc, rndErrorSeverity }
--       DESCRIPTION
--             ""
--       ::=
-- -------------

rxOverflowHWFault TRAP-TYPE
    ENTERPRISE  rnd
    VARIABLES   { rndErrorDesc, rndErrorSeverity }
    DESCRIPTION
        "An RX buffer overflow has occurred in one of the LAN or link
         interfaces. The bound variable rndErrorDesc provides the
         interface number."
    ::= 3

txOverflowHWFault TRAP-TYPE
    ENTERPRISE  rnd
    VARIABLES   { rndErrorDesc, rndErrorSeverity }
    DESCRIPTION
        "Interport queue overflow has occurred in one of the LAN or link interfaces.
         The bound variable rndErrorDesc provides the interface number."
    ::= 4

routeTableOverflow TRAP-TYPE
    ENTERPRISE  rnd
    VARIABLES   { rndErrorDesc, rndErrorSeverity }
    DESCRIPTION
        "An overflow condition has occurred in the Routing Table. The Routing
         Table is used for IP routing algorithm (RIP)."
    ::= 5

resetRequired TRAP-TYPE
    ENTERPRISE  rnd
    VARIABLES   { rndErrorDesc, rndErrorSeverity }
    DESCRIPTION
        "This trap indicates that in order to perform the last SET request, a reset operation
         of the router/bridge is required. This occurs when the layer 2 routing algorithm is
         changed between SPF and Spanning Tree. The reset can be performed manually or
         using the variable rndAction."
    ::= 10

endTftp  TRAP-TYPE
    ENTERPRISE  rnd
    VARIABLES   { rndErrorDesc, rndErrorSeverity }
    DESCRIPTION
        "This trap indicates that in the device finished a TFTP
         transaction with the management station.
         variable rndErrorDesc and rndErrorSeverity provides the actual message
         text and severity respectively."
    ::= 12

abortTftp TRAP-TYPE
    ENTERPRISE  rnd
    VARIABLES   { rndErrorDesc, rndErrorSeverity }
    DESCRIPTION
       "This trap indicates that in the device aborted a TFTP session with
        the management station. Variable rndErrorDesc  and rndErrorSeverity
        provides the actual  message text  and severity  respectively."
    ::= 13

startTftp TRAP-TYPE
    ENTERPRISE  rnd
    VARIABLES   { rndErrorDesc, rndErrorSeverity }
    DESCRIPTION
        "Informational trap indicating that the device has intiated a
         TFTP session. rndErrorDesc will contain the file type in
         question"
    ::= 14

faultBackUp TRAP-TYPE
    ENTERPRISE  rnd
    VARIABLES   { rndErrorDesc, rndErrorSeverity }
    DESCRIPTION
        "Automantic switchover to backup link because of main link fault."
    ::= 23

mainLinkUp TRAP-TYPE
    ENTERPRISE  rnd
    VARIABLES   { rndErrorDesc, rndErrorSeverity }
    DESCRIPTION
        "Communication returened to main link."
    ::= 24

ipxRipTblOverflow  TRAP-TYPE
    ENTERPRISE  rnd
    VARIABLES   { rndErrorDesc, rndErrorSeverity }
    DESCRIPTION
        "This trap indicates that in an OpenGate IPX RIP table overflow.
         The bound variable rndErrorDesc, rndErrorSeverity
         provides the actual  message text and severity respectively."
   ::= 36

ipxSapTblOverflow  TRAP-TYPE
    ENTERPRISE  rnd
    VARIABLES   { rndErrorDesc, rndErrorSeverity }
    DESCRIPTION
        "This trap indicates that in an OpenGate IPX SAP table overflow.
         The bound variable rndErrorDesc, rndErrorSeverity
         provides the actual  message text and severity respectively."
    ::= 37

facsAccessVoilation TRAP-TYPE
    ENTERPRISE  rnd
    VARIABLES   { rndErrorDesc, rndErrorSeverity }
    DESCRIPTION
        "This trap indicates that message that fits FACS statenebt with
         operation blockAndReport was forward to the interface. The bound
         variable rndErrorDesc, rndErrorSeverity(== info ) and
         interface Number."
    ::= 49

autoConfigurationCompleted TRAP-TYPE
    ENTERPRISE  rnd
    VARIABLES   { rndErrorDesc, rndErrorSeverity }
    DESCRIPTION
        "This trap indicates that auto comfiguration completetd succssefully.
         The bound variable rndErrorDesc, rndErrorSeverity(== info )"
    ::= 50

forwardingTabOverflow  TRAP-TYPE
    ENTERPRISE  rnd
    VARIABLES   { rndErrorDesc, rndErrorSeverity }
    DESCRIPTION
        "This trap indicates that an overflow condition has occurred in the
         layer II Forward Table.
         The bound variable rndErrorDesc, rndErrorSeverity(== warning )"
   ::= 51

framRelaySwitchConnectionUp  TRAP-TYPE
    ENTERPRISE  rnd
    VARIABLES   { rndErrorDesc, rndErrorSeverity }
    DESCRIPTION
        "This trap indicates that a connection establish between the Frame
         relay Switch and the WanGate.
         The bound variable rndErrorDesc, rndErrorSeverity(== warning )"
    ::= 53

framRelaySwitchConnectionDown  TRAP-TYPE
    ENTERPRISE  rnd
    VARIABLES   { rndErrorDesc, rndErrorSeverity }
    DESCRIPTION
        "This trap indicates that a connection between the Frame Relay Switch
         and the WanGate failed.
         The bound variable rndErrorDesc, rndErrorSeverity(== warning )"
    ::= 54

errorsDuringInit  TRAP-TYPE
    ENTERPRISE  rnd
    VARIABLES   { rndErrorDesc, rndErrorSeverity }
    DESCRIPTION
        "This trap indicates that the an error occured during initialization
         The bound variable rndErrorDesc, rndErrorSeverity(== error )"
    ::=  61

vlanDynPortAdded  TRAP-TYPE
    ENTERPRISE  rnd
    VARIABLES   { rndErrorDesc, rndErrorSeverity }
    DESCRIPTION
         ""
    ::=  66

vlanDynPortRemoved  TRAP-TYPE
    ENTERPRISE  rnd
    VARIABLES   { rndErrorDesc, rndErrorSeverity }
    DESCRIPTION
         ""
    ::=  67

rsSDclientsTableOverflow  TRAP-TYPE
    ENTERPRISE  rnd
    VARIABLES   { rndErrorDesc, rndErrorSeverity }
    DESCRIPTION
        "This warning is generated when an overflow occurs in the clients table."
    ::=  68

rsSDinactiveServer  TRAP-TYPE
    ENTERPRISE  rnd
    VARIABLES   { rndErrorDesc, rndErrorSeverity }
    DESCRIPTION
        "This warning is generated when a server does not respond to the dispatchers polling
         and is thought to be inactive."
    ::=  69

rsIpZhrConnectionsTableOverflow TRAP-TYPE
    ENTERPRISE  rnd
    VARIABLES   { rndErrorDesc, rndErrorSeverity }
    DESCRIPTION
         "The Zero Hop Routing connections Table has been overflown."
    ::= 70

rsIpZhrReqStaticConnNotAccepted TRAP-TYPE
    ENTERPRISE  rnd
    VARIABLES   { rndErrorDesc, rndErrorSeverity }
    DESCRIPTION
         "The requested static connection was not accepted because there is
          no available IP virtual address to allocate to it."
    ::= 71

rsIpZhrVirtualIpAsSource TRAP-TYPE
    ENTERPRISE  rnd
    VARIABLES   { rndErrorDesc, rndErrorSeverity }
    DESCRIPTION
         "The virtual IP address appeared as a source IP.
          All the connections using it will be deleted and
          it will not be further allocated to new connections."
    ::=  72

rsIpZhrNotAllocVirtualIp TRAP-TYPE
    ENTERPRISE  rnd
    VARIABLES   { rndErrorDesc, rndErrorSeverity }
    DESCRIPTION
         "The source IP address sent an ARP specifying a virtual IP
          which was not allocated for this source.
          This virtual IP will not be allocated to connections of this
          specific source IP."
    ::= 73

rsSnmpSetRequestInSpecialCfgState TRAP-TYPE
    ENTERPRISE  rnd
    VARIABLES   { rndErrorDesc, rndErrorSeverity }
    DESCRIPTION
         "An incoming SNMP SET request was rejected because no such
          requests (except action requests) are accepted after start of
          new configuration reception or during sending the current
          configuration to an NMS."
    ::= 74

rsPingCompletion TRAP-TYPE
    ENTERPRISE rnd
    VARIABLES   { rndErrorDesc, rndErrorSeverity }
    DESCRIPTION
        "A rsPingCompleted trap is sent at the completion
         of a sequence of pings if such a trap was requested
         when the sequence was initiated. The trap severity is info.
         The trap text will specify the following information:
         rsPingCompletionStatus, rsPingSentPackets, rsPingReceivedPackets
         In addition to the above listed objects (which are always present),
         the message will also specify the following quantities:
         if any responses were received:
            rsPingMinReturnTime
            rsPingAvgReturnTime
            rsPingMaxReturnTime"
    ::= 136

pppSecurityViolation TRAP-TYPE
    ENTERPRISE  rnd
    VARIABLES   { rndErrorDesc, rndErrorSeverity }
    DESCRIPTION
        "This trap indicates that a PPP link got an unrecognized secret.
         The bound variables rndErrorDesc,
         rndErrorSeverity(== warning ), interface Number. and pppSecurityIdentity"
    ::= 137

frDLCIStatudChange TRAP-TYPE
    ENTERPRISE rnd
    VARIABLES   { rndErrorDesc, rndErrorSeverity }
    DESCRIPTION
        ""
    ::= 138

papFailedCommunication TRAP-TYPE
    ENTERPRISE rnd
    VARIABLES   { rndErrorDesc, rndErrorSeverity }
    DESCRIPTION
        ""
    ::= 139

chapFailedCommunication TRAP-TYPE
    ENTERPRISE rnd
    VARIABLES   { rndErrorDesc, rndErrorSeverity }
    DESCRIPTION
        ""
    ::= 140

rsWSDRedundancySwitch TRAP-TYPE
    ENTERPRISE rnd
    VARIABLES   { rndErrorDesc, rndErrorSeverity }
    DESCRIPTION
        "Whenever main server fails and backup takes over or server comes
         up after failure a trap of this type is issued."
    ::= 141

rsDhcpAllocationFailure TRAP-TYPE
    ENTERPRISE rnd
    VARIABLES   { rndErrorDesc, rndErrorSeverity }
    DESCRIPTION
        "DHCP failed to allocate an IP address to a requesting host
         because of memory shortage or inadequate configuration of
         available IP addresses."
    ::= 142

--  Traps 143 - 144 reserved for IP Multicast

rlIpFftStnOverflow TRAP-TYPE
    ENTERPRISE rnd
    VARIABLES   { rndErrorDesc, rndErrorSeverity }
    DESCRIPTION
        "The IP SFFT overflow."
    ::= 145

rlIpFftSubOverflow TRAP-TYPE
    ENTERPRISE rnd
    VARIABLES   { rndErrorDesc, rndErrorSeverity }
    DESCRIPTION
        "The IP NFFT overflow."
    ::= 146

rlIpxFftStnOverflow TRAP-TYPE
    ENTERPRISE rnd
    VARIABLES   { rndErrorDesc, rndErrorSeverity }
    DESCRIPTION
        "The IPX SFFT overflow."
    ::= 147

rlIpxFftSubOverflow TRAP-TYPE
    ENTERPRISE rnd
    VARIABLES   { rndErrorDesc, rndErrorSeverity }
    DESCRIPTION
        "The IPX NFFT overflow."
    ::= 148

rlIpmFftOverflow TRAP-TYPE
    ENTERPRISE rnd
    VARIABLES   { rndErrorDesc, rndErrorSeverity }
    DESCRIPTION
        "The IPM FFT overflow."
    ::= 149

rlPhysicalDescriptionChanged TRAP-TYPE
    ENTERPRISE rnd
    VARIABLES   { rndErrorDesc, rndErrorSeverity }
    DESCRIPTION
        "Indicates that the physical decription of the device has
         changed"
    ::= 150

rldot1dStpPortStateForwarding TRAP-TYPE
    ENTERPRISE rnd
    VARIABLES   { rndErrorDesc, rndErrorSeverity,
                  rldot1dStpTrapVrblifIndex, rldot1dStpTrapVrblVID }
    DESCRIPTION
        "The trap is sent by a bridge when any of its configured ports
         transitions from the Learning state to the Forwarding state."
    ::= 151

rldot1dStpPortStateNotForwarding TRAP-TYPE
    ENTERPRISE rnd
    VARIABLES   { rndErrorDesc, rndErrorSeverity,
                  rldot1dStpTrapVrblifIndex, rldot1dStpTrapVrblVID }
    DESCRIPTION
        "The trap is sent by a bridge when any of its configured ports
         transitions from the Forwarding state to the Blocking state."
    ::= 152

rlPolicyDropPacketTrap TRAP-TYPE
    ENTERPRISE rnd
    VARIABLES   { rndErrorDesc, rndErrorSeverity }
    DESCRIPTION
        "Indicates that the packet drop due to the policy "
    ::= 153

rlPolicyForwardPacketTrap TRAP-TYPE
    ENTERPRISE rnd
    VARIABLES   { rndErrorDesc, rndErrorSeverity }
    DESCRIPTION
        "Indicates that the packet has forward based on policy"
    ::= 154

--  Trap 155 - 144 reserved for DVMRP

rlIgmpProxyTableOverflow TRAP-TYPE
    ENTERPRISE rnd
    VARIABLES   { rndErrorDesc, rndErrorSeverity }
    DESCRIPTION
        "An IGMP PROXY Table overflow."
    ::= 156

rlIgmpV1MsgReceived TRAP-TYPE
    ENTERPRISE rnd
    VARIABLES   { rndErrorDesc, rndErrorSeverity }
    DESCRIPTION
        "An IGMP Message of v1 received on ifIndex. "
    ::= 157

rlVrrpEntriesDeleted TRAP-TYPE
    ENTERPRISE rnd
    VARIABLES   { rndErrorDesc, rndErrorSeverity}
    DESCRIPTION
        "One or more VRRP entries deleted due to IP interface deletion or transition. "
    ::= 158

rlHotSwapTrap TRAP-TYPE
    ENTERPRISE rnd
    VARIABLES   {rndErrorDesc, rndErrorSeverity}
    DESCRIPTION
        "Hot swap trap."
     ::= 159

rlTrunkPortAddedTrap TRAP-TYPE
    ENTERPRISE  rnd
    VARIABLES   { rndErrorDesc, rndErrorSeverity }
    DESCRIPTION
        "Informational trap indicating that a port is added to a trunk"
    ::= 160

rlTrunkPortRemovedTrap TRAP-TYPE
    ENTERPRISE  rnd
    VARIABLES   { rndErrorDesc, rndErrorSeverity }
    DESCRIPTION
        "This warning is generated when a port removed from a trunk."
    ::=  161

rlTrunkPortNotCapableTrap TRAP-TYPE
    ENTERPRISE  rnd
    VARIABLES   { rndErrorDesc, rndErrorSeverity }
    DESCRIPTION
        "Informational trap indicating that a port can not be added to
         a trunk because of device limitations or diffrent swIfType."
    ::=  162

--  Traps 163 - 169 reserved for IP Multicast

rlLockPortTrap TRAP-TYPE
    ENTERPRISE  rnd
    VARIABLES   { rndErrorDesc, rndErrorSeverity }
    DESCRIPTION
        "Informational trap indicating that a locked port receive
        a frame with new source Mac Address."
    ::=  170

vlanDynVlanAdded  TRAP-TYPE
    ENTERPRISE  rnd
    VARIABLES   { rndErrorDesc, rndErrorSeverity }
    DESCRIPTION
         "add gvrp dynamic vlan"
    ::=  171

vlanDynVlanRemoved  TRAP-TYPE
    ENTERPRISE  rnd
    VARIABLES   { rndErrorDesc, rndErrorSeverity }
    DESCRIPTION
         "remove gvrp dynamic vlan"
    ::=  172

vlanDynamicToStatic  TRAP-TYPE
    ENTERPRISE  rnd
    VARIABLES   { rndErrorDesc, rndErrorSeverity }
    DESCRIPTION
         "vlan status was changed from dynamic to static"
    ::=  173

vlanStaticToDynamic  TRAP-TYPE
    ENTERPRISE  rnd
    VARIABLES   { rndErrorDesc, rndErrorSeverity }
    DESCRIPTION
         "vlan status was changed from static to dynamic"
    ::=  174

dstrSysLog  TRAP-TYPE
    ENTERPRISE  rnd
    VARIABLES   { rndErrorDesc, rndErrorSeverity }
    DESCRIPTION
         "Master receive trap from slave , and forward it as trap"
    ::=  175

rlEnvMonFanStateChange TRAP-TYPE
    ENTERPRISE  rnd
    VARIABLES   { rndErrorDesc, rndErrorSeverity }
    DESCRIPTION
        "Trap indicating the fan state.
         rndErrorSeverity will be:
                0 for fan state  nomal, notPresent
                1 for fan state warning, notFunctioning
                2 for fan state critical
                3 for fan state fatal
         The error text will specify the fan index, fan description and the exact fan state"
    ::=  176

rlEnvMonPowerSupplyStateChange TRAP-TYPE
    ENTERPRISE  rnd
    VARIABLES   { rndErrorDesc, rndErrorSeverity }
    DESCRIPTION
        "Trap indicating the power supply state.
         rndErrorSeverity will be:
                0 for power supply state  nomal, notPresent
                1 for power supply state warning, notFunctioning
                2 for power supply state critical
                3 for power supply state fatal
         The error text will specify the power supply index, power supply description and the exact power supply state"

    ::=  177

rlStackStateChange TRAP-TYPE
    ENTERPRISE  rnd
    VARIABLES   { rndErrorDesc, rndErrorSeverity }
    DESCRIPTION
        "Trap indicating the stack connection state
                0 for stack state connected,
                1 for stack state disconnected "

    ::=  178

rlEnvMonTemperatureRisingAlarm TRAP-TYPE
    ENTERPRISE  rnd
    VARIABLES   { rndErrorDesc, rndErrorSeverity }
    DESCRIPTION
        "Trap indicating that the temperature in the device has exceeded the
         device specific safe temperature threshold."

    ::=  179

rlCopyFinished TRAP-TYPE
    ENTERPRISE  rnd
    VARIABLES   { rndErrorDesc, rndErrorSeverity }
    DESCRIPTION
        "Informational trap indicating that the device has finished
         a copy operation successfully."
    ::= 180

rlCopyFailed TRAP-TYPE
    ENTERPRISE  rnd
    VARIABLES   { rndErrorDesc, rndErrorSeverity }
    DESCRIPTION
        "Informational trap indicating that the copy operation has failed."
    ::= 181

--  Trap 182 reserved for IP Multicast

rlBrgMacAddFailedTrap TRAP-TYPE
    ENTERPRISE  rnd
    VARIABLES   { rndErrorDesc, rndErrorSeverity }
    DESCRIPTION
        "Informational trap indicating that adding dynamic mac/s
         failed due to full hash chain."
    ::= 183

rldot1xPortStatusAuthorizedTrap TRAP-TYPE
    ENTERPRISE  rnd
    VARIABLES   { rndErrorDesc, rndErrorSeverity }
    DESCRIPTION
        "Informational trap indicating that port 802.1x status is authorized."
    ::= 184

rldot1xPortStatusUnauthorizedTrap TRAP-TYPE
    ENTERPRISE  rnd
    VARIABLES   { rndErrorDesc, rndErrorSeverity }
    DESCRIPTION
        "Warning trap is indicating that port 802.1x status is unAuthorized."
    ::=  185

swIfTablePortLock TRAP-TYPE
    ENTERPRISE  rnd
    VARIABLES   { rndErrorDesc, rndErrorSeverity }
    DESCRIPTION
        "Warning trap is indicating port lock hase began."
    ::=  192

swIfTablePortUnLock TRAP-TYPE
    ENTERPRISE  rnd
    VARIABLES   { rndErrorDesc, rndErrorSeverity }
    DESCRIPTION
        "Warning trap is indicating port lock has ended."
    ::=  193

rlAAAUserLocked TRAP-TYPE
    ENTERPRISE  rnd
    VARIABLES   { rndErrorDesc, rndErrorSeverity }
    DESCRIPTION
        "Warning trap indicating that the user was locked after
         number of consecutives unsuccessful login attempts."
    ::= 194

-- 186-191 are used in the Physicaldescription MIB

END
