-- 
-- Dell Management Module MIB
-- Management Information Base
-- 
-- This MIB is intended for use with the OpenManage Enterprise-Modular management software.
--
-- Note that the Dell Management Module MIB file is published in both types of SMI (Structure
-- of Managed Information). This copy of the Dell Management Module MIB file is the SMIv2 version of the MIB file.
--
-- Copyright (c) 2020 Dell Inc.
--
-- Last Changed Revision: 1
-- Last Changed Date: 2020-01-22 13:00:00 -0500 (Wed, 22 Jan 2020)
--

------------------------------------------------------------------------------
-- Begin MIB
------------------------------------------------------------------------------

DELL-MM-MIB-SMIv2 DEFINITIONS ::= BEGIN

IMPORTS
    MODULE-IDENTITY, OBJECT-TYPE, NOTIFICATION-TYPE, enterprises
        FROM SNMPv2-SMI
    TEXTUAL-CONVENTION, DisplayString
        FROM SNMPv2-TC
	OBJECT-GROUP,NOTIFICATION-GROUP
        FROM SNMPv2-CONF;

------------------------------------------------------------------------------
-- Textual Conventions
------------------------------------------------------------------------------

	DellString              ::= TEXTUAL-CONVENTION
		STATUS current
		DESCRIPTION
			"General string type."
		SYNTAX              OCTET STRING (SIZE (0..1023))

	--
	-- Management Module Types
	--
	DellMmType  ::= TEXTUAL-CONVENTION
		STATUS current
		DESCRIPTION
			"Management Module Types."
		SYNTAX              INTEGER {
		other(1),               -- the MM type is not one of the following
		unknown(2),             -- the MM type is unknown
		mxMM(3)                 -- MX Chassis (MM)

	}

	DellStatus  ::= TEXTUAL-CONVENTION
		STATUS current
		DESCRIPTION
			"Status Information."
		SYNTAX              INTEGER {
		other(1),               -- the status of the object is not one of the following:
		unknown(2),             -- the status of the object is unknown
											--  (not known or monitored)
		ok(3),                  -- the status of the object is ok
		nonCritical(4),         -- the status of the object is warning, non-critical
		critical(5),            -- the status of the object is critical (failure)
		nonRecoverable(6)       -- the status of the object is non-recoverable (dead)

	}

	-------------------------------------------------------------------------------
	-- DellPowerReading is a string representation of a floating point value,
	--   having exactly 3 digits of precision, and a maximum of 31 characters.
	--
	-- DellChassisPowerIndexRange defines the possible chassis power instances
	--   in this MIB.
	--
	-- DellPSUIndexRange defines the possible Power Supply Unit (PSU)
	--   instances, per chassis power instance, in this MIB.
	--
	-- DellPSUCapable is an enumeration of PSU presence and/or monitoring
	--   capabilities.
	--
	-- DellTemperatureReading is an integer value, expressed in degrees Celsius.
	-------------------------------------------------------------------------------
	DellPowerReading              ::= TEXTUAL-CONVENTION
    STATUS current
    DESCRIPTION
        "Power Reading."
    SYNTAX              OCTET STRING (SIZE (0..32))

	DellPowerIndexRange      ::= TEXTUAL-CONVENTION
    STATUS current
    DESCRIPTION
        "Integer with a range of (1..1)."
    SYNTAX              INTEGER (1..1)

	DellPSUIndexRange      ::= TEXTUAL-CONVENTION
    STATUS current
    DESCRIPTION
        "Integer with a range of (1..6)."
    SYNTAX              INTEGER (1..6)

	DellPSUCapable  ::= TEXTUAL-CONVENTION
    STATUS current
    DESCRIPTION
        "Power Supply Information."
    SYNTAX              INTEGER {
    absent(1),      -- power supply is not present
	none(2),        -- no power monitoring abilities
	basic(3)        -- basic power monitoring abilities

	}

	DellTemperatureReading      ::= TEXTUAL-CONVENTION
    STATUS current
    DESCRIPTION
        "Temperature Reading."
    SYNTAX              INTEGER

	-------------------------------------------------------------------------------
	-- DellTimestamp is defined in the displayable format:
	--
	--			yyyymmddHHMMSS.uuuuuuDooo
	--
	-- where yyyy is the year, mm is the month number, dd is the day of the month,
	-- HHMMSS are the hours, minutes and seconds, respectively, uuuuuu is the
	-- number of microseconds, D is the UTC offset direction, and ooo is the
	-- offset from UTC, in minutes.
	--
	-- Note: D is a plus (+) sign if east of UTC, and a minus (-) if west of UTC.
	--
	-- For example, Wednesday, May 25, 1994, at 1:30:15 PM EDT
	--   would be represented as: 19940525133015.000000-300
	-------------------------------------------------------------------------------
	DellTimestamp              ::= TEXTUAL-CONVENTION
    STATUS current
    DESCRIPTION
        "Time Stamp."
    SYNTAX              OCTET STRING (SIZE (26))

-- MIB Objects and Tables --------------------------------------------------------

	dell                          OBJECT IDENTIFIER ::= { enterprises    674   }
	server3                       OBJECT IDENTIFIER ::= { dell           10892 }
	dmmOutOfBandGroup             OBJECT IDENTIFIER ::= { server3             6 }

	dmmInformationGroup           OBJECT IDENTIFIER ::= { dmmOutOfBandGroup     1 }
	dmmProductInfoGroup           OBJECT IDENTIFIER ::= { dmmInformationGroup   1 }
	dmmFirmwareGroup              OBJECT IDENTIFIER ::= { dmmInformationGroup   2 }

	dmmStatusGroup                OBJECT IDENTIFIER ::= { dmmOutOfBandGroup     2 }

	dmmChassisStatusGroup         OBJECT IDENTIFIER ::= { dmmOutOfBandGroup     3 }
	dmmStatusNowGroup             OBJECT IDENTIFIER ::= { dmmChassisStatusGroup 1 }

	dmmChassisPowerGroup          OBJECT IDENTIFIER ::= { dmmOutOfBandGroup     4 }

		DmmPowerTableEntry ::= SEQUENCE
		{
			dmmPowerChassisIndex			DellPowerIndexRange,
			dmmPowerIdlePower				DellPowerReading,
			dmmPowerKWhCumulative			DellPowerReading,
			dmmPowerKWhCumulativeTime		DellTimestamp,
			dmmPowerWattsPeakUsage			DellPowerReading,
			dmmPowerWattsPeakTime			DellTimestamp,
			dmmPowerWattsMinUsage			DellPowerReading,
			dmmPowerWattsMinTime			DellTimestamp,
			dmmPowerWattsReading			DellPowerReading
		}

		DmmPSUTableEntry ::= SEQUENCE
		{
			dmmPSUChassisIndex		DellPowerIndexRange,
			dmmPSUIndex				DellPSUIndexRange,
			dmmPSULocation			DellString,
			dmmPSUState				DellString,
			dmmPSUType 				DellString,
			dmmPSUCapacity 			DellPowerReading,
			dmmPSUVoltage  			DellPowerReading,
			dmmPSUCurrStatus  		DellStatus
		}

	dmmChassisAlert2Group         OBJECT IDENTIFIER ::= { dmmOutOfBandGroup    5 }
	dmmChassisAlert2Variables     OBJECT IDENTIFIER ::= { dmmChassisAlert2Group   1 }

	dmmGenericAlertGroup          OBJECT IDENTIFIER ::= { dmmOutOfBandGroup    6 }
	dmmGenericAlertVariables      OBJECT IDENTIFIER ::= { dmmGenericAlertGroup  1 }

	conformanceGroup                OBJECT IDENTIFIER ::= { dmmOutOfBandGroup 7 }
	conformanceMIBGroups            OBJECT IDENTIFIER ::= { conformanceGroup 1   }
	conformanceMIBnotificationGroup OBJECT IDENTIFIER ::= { conformanceGroup 2  }


-- Variables and Traps ------------------------------------------------------------------------

	-------------------------------------------------------------------------------
	-- group: product information
	-------------------------------------------------------------------------------
	dmmProductInfoObjGroup OBJECT-GROUP
		OBJECTS { dmmProductName, dmmProductShortName, dmmProductDescription, dmmProductManufacturer, dmmProductVersion,
				  dmmChassisServiceTag, dmmProductURL, dmmProductChassisAssetTag, dmmProductChassisName, dmmProductType,
				  dmmProductChassisDataCenter, dmmProductChassisAisle, dmmProductChassisRack, dmmProductChassisRackSlot,dmmProductChassisModel, dmmProductChassisExpressServiceCode, dmmProductChassisSystemID
				  }
		STATUS  current
		DESCRIPTION
			"A collection of objects providing information about the chassis management module."
		::= { conformanceMIBGroups 1  }

	dmmProductName      OBJECT-TYPE
		SYNTAX          DellString
		MAX-ACCESS      read-only
		STATUS          current
		DESCRIPTION     "This attribute defines the product name of a chassis management module."
			::= { dmmProductInfoGroup 1 }

	dmmProductShortName OBJECT-TYPE
		SYNTAX          DellString
		MAX-ACCESS      read-only
		STATUS          current
		DESCRIPTION     "This attribute defines the short product name of a chassis management module. "
			::= { dmmProductInfoGroup 2 }

	dmmProductDescription OBJECT-TYPE
		SYNTAX          DellString
		MAX-ACCESS      read-only
		STATUS          current
		DESCRIPTION     "This attribute defines the product description of a chassis management module. "
			::= { dmmProductInfoGroup 3 }

	dmmProductManufacturer OBJECT-TYPE
		SYNTAX          DellString
		MAX-ACCESS      read-only
		STATUS          current
		DESCRIPTION     "This attribute defines the product manufacturer of a chassis management module. "
			::= { dmmProductInfoGroup 4 }

	dmmProductVersion OBJECT-TYPE
		SYNTAX          DellString
		MAX-ACCESS      read-only
		STATUS          current
		DESCRIPTION     "This attribute defines the product version of a chassis management module. "
			::= { dmmProductInfoGroup 5 }

	dmmChassisServiceTag OBJECT-TYPE
		SYNTAX          DellString
		MAX-ACCESS      read-only
		STATUS          current
		DESCRIPTION     "This attribute defines the Service Tag of the chassis. "
			::= { dmmProductInfoGroup 6 }

	dmmProductURL       OBJECT-TYPE
		SYNTAX          DellString
		MAX-ACCESS      read-only
		STATUS          current
		DESCRIPTION     "This attribute defines the out-of-band UI URL of a chassis management module. "
			::= { dmmProductInfoGroup 7 }

	dmmProductChassisAssetTag  OBJECT-TYPE
		SYNTAX          DellString
		MAX-ACCESS      read-only
		STATUS          current
		DESCRIPTION     "This attribute defines the Asset Tag of the chassis. "
			::= { dmmProductInfoGroup 8 }

	dmmProductChassisName  OBJECT-TYPE
		SYNTAX          DellString
		MAX-ACCESS      read-only
		STATUS          current
		DESCRIPTION     "This attribute defines the name of the chassis. "
			::= { dmmProductInfoGroup 9 }

	dmmProductType  OBJECT-TYPE
		SYNTAX          DellMmType
		MAX-ACCESS      read-only
		STATUS          current
		DESCRIPTION     "This attribute defines type of a remote management module "
			::= { dmmProductInfoGroup 10 }

	dmmProductChassisDataCenter  OBJECT-TYPE
		SYNTAX          DellString
		MAX-ACCESS      read-only
		STATUS          current
		DESCRIPTION     "This attribute defines the Data Center locator of the chassis. "
			::= { dmmProductInfoGroup 11 }

	dmmProductChassisAisle  OBJECT-TYPE
		SYNTAX          DellString
		MAX-ACCESS      read-only
		STATUS          current
		DESCRIPTION     "This attribute defines the Aisle locator of the chassis. "
			::= { dmmProductInfoGroup 12 }

	dmmProductChassisRack  OBJECT-TYPE
		SYNTAX          DellString
		ACCESS          read-only
		STATUS          current
		DESCRIPTION     "This attribute defines the Rack locator of the chassis. "
			::= { dmmProductInfoGroup 13 }

	dmmProductChassisRackSlot  OBJECT-TYPE
		SYNTAX          DellString
		MAX-ACCESS      read-only
		STATUS          current
		DESCRIPTION     "This attribute defines the Rack Slot locator of the chassis. "
			::= { dmmProductInfoGroup 14 }

	dmmProductChassisModel  OBJECT-TYPE
		SYNTAX          DellString
		MAX-ACCESS      read-only
		STATUS          current
		DESCRIPTION     "This attribute defines the Model of the chassis."
			::= { dmmProductInfoGroup 15 }

	dmmProductChassisExpressServiceCode  OBJECT-TYPE
		SYNTAX          DellString
		MAX-ACCESS      read-only
		STATUS          current
		DESCRIPTION     "This attribute defines the Express Service Code of the chassis."
			::= { dmmProductInfoGroup 16 }

	dmmProductChassisSystemID  OBJECT-TYPE
		SYNTAX          INTEGER
		MAX-ACCESS      read-only
		STATUS          current
		DESCRIPTION     "This attribute defines the System ID of the chassis."
			::= { dmmProductInfoGroup 17 }

	-------------------------------------------------------------------------------
	-- group: firmware
	-------------------------------------------------------------------------------
	dmmFirmwareObjGroup OBJECT-GROUP
		OBJECTS { dmmFirmwareVersion, dmmFirmwareVersion2
				  }
		STATUS  current
		DESCRIPTION
			"A collection of objects providing information about the chassis firmware version."
		::= { conformanceMIBGroups 2  }

	dmmFirmwareVersion  OBJECT-TYPE
			SYNTAX          DellString
			MAX-ACCESS      read-only
			STATUS          current
			DESCRIPTION     "This attribute defines the firmware version of chassis management module 1."
				::= { dmmFirmwareGroup 1 }

	dmmFirmwareVersion2 OBJECT-TYPE
			SYNTAX          DellString
			MAX-ACCESS      read-only
			STATUS          current
			DESCRIPTION     "This attribute defines the firmware version of chassis management module 2."
				::= { dmmFirmwareGroup 2 }

	-------------------------------------------------------------------------------
	-- group: chassis status
	-------------------------------------------------------------------------------

	dmmStatusObjGroup OBJECT-GROUP
		OBJECTS { dmmGlobalSystemStatus
				  }
		STATUS  current
		DESCRIPTION
			"Object is providing information about the overall chassis status."
		::= { conformanceMIBGroups 3  }

	dmmGlobalSystemStatus OBJECT-TYPE
		SYNTAX          DellStatus
		MAX-ACCESS      read-only
		STATUS          current
		DESCRIPTION     "This attribute defines the overall chassis status
						  being monitored by the chassis management module."
			::= { dmmStatusGroup 1 }

	dmmStatusNowObjGroup OBJECT-GROUP
		OBJECTS { dmmIOMCurrStatus, dmmRedCurrStatus, dmmPowerCurrStatus, dmmFanCurrStatus, dmmBladeCurrStatus,
					dmmTempCurrStatus, dmmMMCurrStatus, dmmChassisFrontPanelAmbientTemperature
				  }
		STATUS  current
		DESCRIPTION
			"A collection of objects providing information about the chassis subsystem status."
		::= { conformanceMIBGroups 4  }


	dmmIOMCurrStatus  OBJECT-TYPE
		SYNTAX          DellStatus
		MAX-ACCESS      read-only
		STATUS          current
		DESCRIPTION     "This attribute defines the IOM subsystem status
						  being monitored by the chassis management module."
			::= { dmmStatusNowGroup 1 }

	dmmRedCurrStatus  OBJECT-TYPE
		SYNTAX          DellStatus
		MAX-ACCESS      read-only
		STATUS          current
		DESCRIPTION     "This attribute defines the Redundancy status
						  being monitored by the chassis management module."
				::= { dmmStatusNowGroup 2 }

	dmmPowerCurrStatus OBJECT-TYPE
		SYNTAX          DellStatus
		MAX-ACCESS      read-only
		STATUS          current
		DESCRIPTION     "This attribute defines the power subsystem health status
						  being monitored by the chassis management module."
			::= { dmmStatusNowGroup 3 }

	dmmFanCurrStatus OBJECT-TYPE
		SYNTAX          DellStatus
		MAX-ACCESS      read-only
		STATUS          current
		DESCRIPTION     "This attribute defines the Fan subsystem health status
						  being monitored by the chassis management module."
			::= { dmmStatusNowGroup 4 }

	dmmBladeCurrStatus OBJECT-TYPE
		SYNTAX          DellStatus
		MAX-ACCESS      read-only
		STATUS          current
		DESCRIPTION     "This attribute defines the Blade subsystem health status
						  being monitored by the chassis management module."
			::= { dmmStatusNowGroup 5 }

	dmmTempCurrStatus OBJECT-TYPE
		SYNTAX          DellStatus
		MAX-ACCESS      read-only
		STATUS          current
		DESCRIPTION     "This attribute defines the Temp Sensor subsystem health status
						  being monitored by the chassis management module."
			::= { dmmStatusNowGroup 6 }

	dmmMMCurrStatus OBJECT-TYPE
		SYNTAX          DellStatus
		MAX-ACCESS          read-only
		STATUS          current
		DESCRIPTION     "This attribute defines the health status
						  being monitored by the chassis management module."
			::= { dmmStatusNowGroup 7 }

	dmmChassisFrontPanelAmbientTemperature OBJECT-TYPE
		SYNTAX          DellTemperatureReading
		MAX-ACCESS      read-only
		STATUS          current
		DESCRIPTION     "This attribute defines the ambient temperature
						  reading (in degrees Celsius) for the chassis front panel module."
			::= { dmmStatusNowGroup 8 }

	-------------------------------------------------------------------------------
	-- group: chassis power
	-------------------------------------------------------------------------------
	dmmChassisPowerObjGroup OBJECT-GROUP
		OBJECTS { dmmPowerTable, dmmPSUTable
				  }
		STATUS  current
		DESCRIPTION
			"A collection of objects providing information about the chassis Power."
		::= { conformanceMIBGroups 5  }



	dmmPowerTable OBJECT-TYPE
		SYNTAX			SEQUENCE OF DmmPowerTableEntry
		MAX-ACCESS		not-accessible
		STATUS			current
		DESCRIPTION		"This object defines the power table."
			::= { dmmChassisPowerGroup 1 }

	dmmPowerTableEntry OBJECT-TYPE
		SYNTAX			DmmPowerTableEntry
		MAX-ACCESS      not-accessible
		STATUS      	current
		DESCRIPTION 	"This object defines the power table entry."
		INDEX       	{ dmmPowerChassisIndex }
			::= { dmmPowerTable 1 }

	dmmPSUTable OBJECT-TYPE
		SYNTAX			SEQUENCE OF DmmPSUTableEntry
		MAX-ACCESS		not-accessible
		STATUS			current
		DESCRIPTION		"This object defines the PSU table."
			::= { dmmChassisPowerGroup 2 }

	dmmPSUTableEntry OBJECT-TYPE
		SYNTAX			DmmPSUTableEntry
		MAX-ACCESS      not-accessible
		STATUS      	current
		DESCRIPTION 	"This object defines the PSU table entry."
		INDEX       	{ dmmPSUChassisIndex, dmmPSUIndex }
			::= { dmmPSUTable 1 }

	-------------------------------------------------------------------------------
	-- table: power information
	-------------------------------------------------------------------------------
	dmmPowerTableObjEntry OBJECT-GROUP
		OBJECTS { dmmPowerChassisIndex, dmmPowerIdlePower, dmmPowerKWhCumulative, dmmPowerKWhCumulativeTime, dmmPowerWattsPeakUsage,
					 dmmPowerWattsPeakTime, dmmPowerWattsMinUsage, dmmPowerWattsMinTime, dmmPowerWattsReading
				  }
		STATUS  current
		DESCRIPTION
			"A collection of objects providing information about the chassis Power Information."
		::= { conformanceMIBGroups 6  }

	dmmPowerChassisIndex OBJECT-TYPE
		SYNTAX			DellPowerIndexRange
		MAX-ACCESS		read-only
		STATUS			current
		DESCRIPTION		"This attribute defines the index
								(one-based) of the associated chassis."
			::= { dmmPowerTableEntry 1 }


	dmmPowerIdlePower OBJECT-TYPE
		SYNTAX			DellPowerReading
		MAX-ACCESS		read-only
		STATUS			current
		DESCRIPTION		"This attribute defines the power (in Watts) required by
								the chassis	infrastructure, plus the sum of the minimum power requirements
								for all currently powered-on servers."
			::= { dmmPowerTableEntry 2 }

	dmmPowerKWhCumulative OBJECT-TYPE
		SYNTAX			DellPowerReading
		MAX-ACCESS		read-only
		STATUS			current
		DESCRIPTION		"This attribute defines the cumulative chassis power
								usage (in KWh) since last reset."
			::= { dmmPowerTableEntry 3 }

	dmmPowerKWhCumulativeTime OBJECT-TYPE
		SYNTAX			DellTimestamp
		MAX-ACCESS		read-only
		STATUS			current
		DESCRIPTION		"This attribute defines the timestamp of the most recent
								chassis power accumulator reset."
			::= { dmmPowerTableEntry 4 }

	dmmPowerWattsPeakUsage OBJECT-TYPE
		SYNTAX			DellPowerReading
		MAX-ACCESS		read-only
		STATUS			current
		DESCRIPTION		"This attribute defines the chassis peak power
								usage (in Watts) since last reset."
			::= { dmmPowerTableEntry 5 }

	dmmPowerWattsPeakTime OBJECT-TYPE
		SYNTAX			DellTimestamp
		MAX-ACCESS		read-only
		STATUS			current
		DESCRIPTION		"This attribute defines the timestamp of the most recent
								chassis peak power usage."
			::= { dmmPowerTableEntry 6 }

	dmmPowerWattsMinUsage OBJECT-TYPE
		SYNTAX			DellPowerReading
		MAX-ACCESS		read-only
		STATUS			current
		DESCRIPTION		"This attribute defines the chassis mimimum power
								usage (in Watts) since last reset."
			::= { dmmPowerTableEntry 7 }

	dmmPowerWattsMinTime OBJECT-TYPE
		SYNTAX			DellTimestamp
		MAX-ACCESS		read-only
		STATUS			current
		DESCRIPTION		"This attribute defines the timestamp of the most recent
								chassis minimum power usage."
			::= { dmmPowerTableEntry 8 }

	dmmPowerWattsReading OBJECT-TYPE
		SYNTAX			DellPowerReading
		MAX-ACCESS		read-only
		STATUS			current
		DESCRIPTION		"This attribute defines the instantaneous chassis power
								usage (in Watts)."
			::= { dmmPowerTableEntry 9 }

	-------------------------------------------------------------------------------
	-- table: PSU info
	-------------------------------------------------------------------------------

	dmmPSUTableObjEntry OBJECT-GROUP
		OBJECTS { dmmPSUChassisIndex, dmmPSUIndex, dmmPSULocation, dmmPSUState, dmmPSUType,
					 dmmPSUCapacity, dmmPSUVoltage, dmmPSUCurrStatus
				  }
		STATUS  current
		DESCRIPTION
			"A collection of objects providing information about the chassis Power Supply."
		::= { conformanceMIBGroups 7  }

	dmmPSUChassisIndex OBJECT-TYPE
		SYNTAX			DellPowerIndexRange
		MAX-ACCESS		read-only
		STATUS			current
		DESCRIPTION		"This attribute defines the index
								(one-based) of the associated chassis."
			::= { dmmPSUTableEntry 1 }

	dmmPSUIndex OBJECT-TYPE
		SYNTAX			DellPSUIndexRange
		MAX-ACCESS		read-only
		STATUS			current
		DESCRIPTION		"This attribute defines the index
								(one-based) of the associated PSU."
			::= { dmmPSUTableEntry 2 }

	dmmPSULocation OBJECT-TYPE
		SYNTAX			DellString
		MAX-ACCESS		read-only
		STATUS			current
		DESCRIPTION		"This attribute defines the location
								of the PSU."
			::= { dmmPSUTableEntry 3 }

	dmmPSUState    OBJECT-TYPE
		SYNTAX			DellString
		MAX-ACCESS		read-only
		STATUS			current
		DESCRIPTION		"This attribute defines the enabled state of
								of the PSU."
			::= { dmmPSUTableEntry 4 }

	dmmPSUType 	OBJECT-TYPE
		SYNTAX			DellString
		MAX-ACCESS		read-only
		STATUS			current
		DESCRIPTION		"This attribute defines the type
								of the PSU."
			::= { dmmPSUTableEntry 5 }

	dmmPSUCapacity  OBJECT-TYPE
		SYNTAX			DellPowerReading
		MAX-ACCESS		read-only
		STATUS			current
		DESCRIPTION		"This attribute defines the capacity in watts
								of the PSU."
			::= { dmmPSUTableEntry 6 }

	dmmPSUVoltage		OBJECT-TYPE
		SYNTAX			DellPowerReading
		MAX-ACCESS		read-only
		STATUS			current
		DESCRIPTION		"This attribute defines the input voltage
								of the PSU."
			::= { dmmPSUTableEntry 7 }

	dmmPSUCurrStatus	OBJECT-TYPE
		SYNTAX			DellStatus
		MAX-ACCESS		read-only
		STATUS			current
		DESCRIPTION		"This attribute defines the current status
								of the PSU."
			::= { dmmPSUTableEntry 8 }

	-------------------------------------------------------------------------------
	-- group: Chassis Alerts 2
	-------------------------------------------------------------------------------
	dmmChassisAlert2VariablesObj OBJECT-GROUP
		OBJECTS { dmmCA2MessageID, dmmCA2Message, dmmCA2MessageArgs, dmmCA2AlertStatus, dmmCA2FQDD
				  }
		STATUS  current
		DESCRIPTION
			"A collection of objects providing information about the chassis Alerts."
			::= { conformanceMIBGroups 8  }

	dmmCA2MessageID     OBJECT-TYPE
		SYNTAX          DisplayString (SIZE (0..8))
		MAX-ACCESS      read-only
		STATUS          current
		DESCRIPTION     "Message ID of the alert."
			::= { dmmChassisAlert2Variables 1 }

	dmmCA2Message       OBJECT-TYPE
		SYNTAX          DellString
		ACCESS          read-only
		STATUS          mandatory
		DESCRIPTION     "Message describing the alert."
			::= { dmmChassisAlert2Variables 2 }

	dmmCA2MessageArgs   OBJECT-TYPE
		SYNTAX          DellString
		MAX-ACCESS      read-only
		STATUS          current
		DESCRIPTION     "Concatenated set of strings representing any message arguments
							 that were used to construct the alert message.  Each message
							 argument string is enclosed in double quotes, and there is a
							 comma after the ending double quote of each message argument
							 string, except the last one.  Any double quotes found within a
							 message argument string were preprocessed and changed to single
							 quotes."
			::= { dmmChassisAlert2Variables 3 }

	dmmCA2AlertStatus   OBJECT-TYPE
		SYNTAX          DellStatus
		MAX-ACCESS      read-only
		STATUS          current
		DESCRIPTION     "Status of the alert."
			::= { dmmChassisAlert2Variables 4 }

	dmmCA2FQDD          OBJECT-TYPE
		SYNTAX          DisplayString (SIZE (0..512))
		MAX-ACCESS      read-only
		STATUS          current
			DESCRIPTION     "Fully qualified device descriptor of device causing the alert."
			::= { dmmChassisAlert2Variables 5 }

	-------------------------------------------------------------------------------
	-- group: Generic Alerts
	-------------------------------------------------------------------------------
	dmmGenericAlertVariablesObj OBJECT-GROUP
		OBJECTS { dmmDeviceServiceTag
				  }
		STATUS  current
		DESCRIPTION
			"A collection of objects providing information about the chassis Alerts."
			::= { conformanceMIBGroups 9  }

	dmmDeviceServiceTag   OBJECT-TYPE
		SYNTAX            DellString
		MAX-ACCESS        read-only
		STATUS            current
		DESCRIPTION
				"Service tag of the device."

			::= { dmmGenericAlertVariables 1 }

------------------------------------------------------------------------------
-- Chassis Alerts 2: System: Amperage Probe Traps
--
-- Category: System/1
-- Subcategory: AMP/16
    ------------------------------------------------------------------------------

dmmChassisAlert2NotificationGroup NOTIFICATION-GROUP
	NOTIFICATIONS { alert2AmperageProbeNormal, alert2AmperageProbeWarning, alert2AmperageProbeFailure, alert2BatteryNormal,
		alert2BatteryWarning, alert2BatteryFailure, alert2CableFailure, alert2CMCWarning, alert2CMCFailure, alert2FanInformation,
		alert2FanWarning, alert2FanFailure, alert2HardwareConfigurationInformation, alert2HardwareConfigurationWarning,
		alert2HardwareConfigurationFailure, alert2IOVirtualizationInformation, alert2IOVirtualizationWarning, alert2IOVirtualizationFailure,
		alert2LinkStatusInformation, alert2LinkStatusWarning, alert2LinkStatusFailure, alert2PowerSupplyNormal,	alert2PowerSupplyWarning,
		alert2PowerSupplyFailure, alert2PowerSupplyAbsent, alert2PowerUsageInformation, alert2PowerUsageWarning, alert2PowerUsageFailure,
		alert2RedundancyInformation, alert2RedundancyDegraded, alert2RedundancyLost, alert2SecurityInformation, alert2SecurityWarning,
		alert2SecurityFailure, alert2SystemEventLogInformation, alert2SystemEventLogWarning, alert2SystemEventLogFailure,alert2SoftwareConfigurationInformation, alert2SoftwareConfigurationWarning, alert2SoftwareConfigurationFailure,	alert2TemperatureProbeNormal, alert2TemperatureProbeWarning, alert2TemperatureProbeFailure, alert2VoltageProbeNormal,
		alert2VoltageProbeWarning, alert2VoltageProbeFailure, alert2StorageBatteryInformation, alert2StorageBatteryWarning,
		alert2StorageBatteryFailure, alert2StorageControllerInformation, alert2StorageControllerWarning, alert2StorageControllerFailure,
		alert2StorageEnclosureInformation, alert2StorageEnclosureWarning, alert2StorageEnclosureFailure, alert2StorageFanInformation,
		alert2StorageFanWarning, alert2StorageFanFailure, alert2StoragePhysicalDiskInformation, alert2StoragePhysicalDiskWarning,
		alert2StoragePhysicalDiskFailure, alert2StoragePowerSupplyInformation, alert2StoragePowerSupplyWarning, alert2StoragePowerSupplyFailure,
		alert2StorageSecurityInformation, alert2StorageSecurityWarning, alert2StorageSecurityFailure, alert2StorageManagementInformation,
		alert2StorageManagementWarning, alert2StorageManagementFailure, alert2StorageTemperatureProbeInformation, alert2StorageTemperatureProbeWarning, alert2StorageTemperatureProbeFailure, alert2StorageVirtualDiskInformation,
		alert2StorageVirtualDiskWarning, alert2StorageVirtualDiskFailure, alert2SoftwareChangeUpdateWarning, alert2CMCAuditInformation,
		alert2CMCAuditWarning, alert2CMCAuditFailure, alert2IOVirtualizationAuditWarning, alert2LicenseInformation,
		alert2LicenseWarning, alert2LicenseFailure, alert2PCIDeviceAuditWarning, alert2PowerSupplyAuditWarning,
		alert2PowerSupplyAuditFailure, alert2PowerUsageAuditInformation, alert2PowerUsageAuditWarning, alert2PowerUsageAuditFailure,
		alert2SoftwareChangeAuditFailure, alert2IOVConfigurationInformation, alert2IOVConfigurationWarning,
		alert2PCIDeviceConfigurationInformation, alert2SWCConfigurationWarning, alert2SWCConfigurationFailure, alert2CMCTestTrap }
	STATUS  current
	DESCRIPTION
			"The two notifications which an SNMPv2 entity is required to
				implement."
	::= { conformanceMIBnotificationGroup 1 }

	alert2AmperageProbeNormal NOTIFICATION-TYPE
		OBJECTS { dmmCA2MessageID,
						dmmCA2Message,
						dmmCA2MessageArgs,
						dmmCA2AlertStatus,
						dmmCA2FQDD,
						dmmProductChassisName,
						dmmChassisServiceTag }
		STATUS	current
		DESCRIPTION
				"Current sensor reading is within range."
			--#TYPE       "System: Amperage Normal"
			--#SEVERITY   INFORMATIONAL
			--#SUMMARY    "Message ID: %s, Message: %s,"
			--#SUMMARY    "Device Status: %d, Device FQDD: %s,"
			--#SUMMARY    "Chassis Service Tag: %s, Chassis Name: %s"
			--#ARGUMENTS  {0, 1, 3, 4, 6, 5}
			--#CATEGORY   "Status Events"
			--#STATE      OPERATIONAL
			--#STATUS     current
		::= { dmmChassisAlert2Group 0 2179 }

	alert2AmperageProbeWarning NOTIFICATION-TYPE
		OBJECTS { dmmCA2MessageID,
						dmmCA2Message,
						dmmCA2MessageArgs,
						dmmCA2AlertStatus,
						dmmCA2FQDD,
						dmmProductChassisName,
						dmmChassisServiceTag}
		STATUS	current
		DESCRIPTION
			"Current sensor has detected a warning value."
			--#TYPE       "System: Amperage Warning"
			--#SEVERITY   MINOR
			--#SUMMARY    "Message ID: %s, Message: %s,"
			--#SUMMARY    "Device Status: %d, Device FQDD: %s,"
			--#SUMMARY    "Chassis Service Tag: %s, Chassis Name: %s"
			--#ARGUMENTS  {0, 1, 3, 4, 6, 5}
			--#CATEGORY   "Status Events"
			--#STATE      DEGRADED
			--#STATUS     current
		::= { dmmChassisAlert2Group 0 2178 }

	alert2AmperageProbeFailure NOTIFICATION-TYPE
		OBJECTS { dmmCA2MessageID,
						dmmCA2Message,
						dmmCA2MessageArgs,
						dmmCA2AlertStatus,
						dmmCA2FQDD,
						dmmProductChassisName,
						dmmChassisServiceTag}
		STATUS	current
		DESCRIPTION
			"Current sensor has detected a failure value."
			--#TYPE       "System: Amperage Failure"
			--#SEVERITY   CRITICAL
			--#SUMMARY    "Message ID: %s, Message: %s,"
			--#SUMMARY    "Device Status: %d, Device FQDD: %s,"
			--#SUMMARY    "Chassis Service Tag: %s, Chassis Name: %s"
			--#ARGUMENTS  {0, 1, 3, 4, 6, 5}
			--#CATEGORY   "Error Events"
			--#STATE      DEGRADED
			--#STATUS     current
		::= { dmmChassisAlert2Group 0 2177 }

    ------------------------------------------------------------------------------
    -- Chassis Alerts 2: System: Battery Traps
    --
    -- Category: System/1
    -- Subcategory: BAT/22
    ------------------------------------------------------------------------------

    alert2BatteryNormal NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Battery state has returned to normal;
             or battery presence had been detected."
        --#TYPE       "System: Battery Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2227 }

    alert2BatteryWarning NOTIFICATION-TYPE
		OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Battery is low."
        --#TYPE       "System: Battery Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2226 }

    alert2BatteryFailure NOTIFICATION-TYPE
		OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Battery has failed or battery is absent."
        --#TYPE       "System: Battery Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2225 }

    ------------------------------------------------------------------------------
    -- Chassis Alerts 2: System: Cable Traps
    --
    -- Category: System/1
    -- Subcategory: CBL/43
    ------------------------------------------------------------------------------

    alert2CableFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Cable failure."
        --#TYPE       "System: Cable Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2393 }

    ------------------------------------------------------------------------------
    -- Chassis Alerts 2: System: Traps
    --
    -- Category: System/1
    -- Subcategory: MM/62
    ------------------------------------------------------------------------------

    alert2CMCWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Chassis Management Module detected a warning."
        --#TYPE       "System: Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2546 }

    alert2CMCFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Chassis Management Module detected an error."
        --#TYPE       "System: Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2545 }

    ------------------------------------------------------------------------------
    -- Chassis Alerts 2: System: Fan Traps
    --
    -- Category: System/1
    -- Subcategory: FAN/13
    ------------------------------------------------------------------------------

    alert2FanInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Fan information."
        --#TYPE       "System: Fan Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2155 }

    alert2FanWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Fan warning."
        --#TYPE       "System: Fan Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2154 }

    alert2FanFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Fan failure."
        --#TYPE       "System: Fan Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2153 }

    ------------------------------------------------------------------------------
    -- Chassis Alerts 2: System: Hardware Configuration Traps
    --
    -- Category: System/1
    -- Subcategory: HWC/35
    ------------------------------------------------------------------------------

    alert2HardwareConfigurationInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Hardware configuration information."
        --#TYPE       "System: Hardware Configuration Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2331 }

    alert2HardwareConfigurationWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Hardware configuration warning."
        --#TYPE       "System: Hardware Configuration Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2330 }

    alert2HardwareConfigurationFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Hardware configuration failure or critical event."
        --#TYPE       "System: Hardware Configuration Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2329 }

    ------------------------------------------------------------------------------
    -- Chassis Alerts 2: System: IO Virtualization Traps
    --
    -- Category: System/1
    -- Subcategory: IOV/63
    ------------------------------------------------------------------------------

    alert2IOVirtualizationInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "IO Virtualization information."
        --#TYPE       "System: IO Virtualization Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2555 }

    alert2IOVirtualizationWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "IO Virtualization warning."
        --#TYPE       "System: IO Virtualization Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2554 }

    alert2IOVirtualizationFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "IO Virtualization failure or critical event."
        --#TYPE       "System: IO Virtualization Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2553 }

    ------------------------------------------------------------------------------
    -- Chassis Alerts 2: System: Link Status Traps
    --
    -- Category: System/1
    -- Subcategory: LNK/25
    ------------------------------------------------------------------------------

    alert2LinkStatusInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Link status information."
        --#TYPE       "System: Link Status Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2251 }

    alert2LinkStatusWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Link status warning."
        --#TYPE       "System: Link Status Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2250 }

    alert2LinkStatusFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Link status failure or critical event."
        --#TYPE       "System: Link Status Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2249 }

    ------------------------------------------------------------------------------
    -- Chassis Alerts 2: System: Power Supply Traps
    --
    -- Category: System/1
    -- Subcategory: PSU/17
    ------------------------------------------------------------------------------

    alert2PowerSupplyNormal NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power supply has returned to normal."
        --#TYPE       "System: Power Supply Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2187 }

    alert2PowerSupplyWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power supply has detected a warning."
        --#TYPE       "System: Power Supply Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2186 }

    alert2PowerSupplyFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power supply has detected a failure."
        --#TYPE       "System: Power Supply Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2185 }

    ------------------------------------------------------------------------------
    -- Chassis Alerts 2: System: Power Supply Absent Traps
    --
    -- Category: System/1
    -- Subcategory: PSUA/52
    ------------------------------------------------------------------------------

    alert2PowerSupplyAbsent NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power supply is absent."
        --#TYPE       "System: Power Supply Absent"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2465 }

    ------------------------------------------------------------------------------
    -- Chassis Alerts 2: System: Power Usage Traps
    --
    -- Category: System/1
    -- Subcategory: PWR/28
    ------------------------------------------------------------------------------

    alert2PowerUsageInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power usage information."
        --#TYPE       "System: Power Usage Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2275 }

    alert2PowerUsageWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power usage warning."
        --#TYPE       "System: Power Usage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2274 }

    alert2PowerUsageFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power usage failure."
        --#TYPE       "System: Power Usage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2273 }

    ------------------------------------------------------------------------------
    -- Chassis Alerts 2: System: Redundancy Traps
    --
    -- Category: System/1
    -- Subcategory: RDU/53
    ------------------------------------------------------------------------------

    alert2RedundancyInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Redundancy information."
        --#TYPE       "System: Redundancy Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2475 }

    alert2RedundancyDegraded NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Redundancy is degraded."
        --#TYPE       "System: Redundancy Degraded"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2474 }

    alert2RedundancyLost NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Redundancy is lost."
        --#TYPE       "System: Redundancy Lost"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2473 }

    ------------------------------------------------------------------------------
    -- Chassis Alerts 2: System: Security Event Traps
    --
    -- Category: System/1
    -- Subcategory: SEC/42
    ------------------------------------------------------------------------------

    alert2SecurityInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Security information."
        --#TYPE       "System: Security Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2387 }

    alert2SecurityWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Security warning."
        --#TYPE       "System: Security Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2386 }

    alert2SecurityFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Security failure or critical event."
        --#TYPE       "System: Security Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 2385 }

    ------------------------------------------------------------------------------
    -- Chassis Alerts 2: System: System Event Log Traps
    --
    -- Category: System/1
    -- Subcategory: SEL/41
    ------------------------------------------------------------------------------

    alert2SystemEventLogInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "System Event Log information."
        --#TYPE       "System: System Event Log Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2379 }

    alert2SystemEventLogWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "System Event Log warning."
        --#TYPE       "System: System Event Log Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2378 }

    alert2SystemEventLogFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "System Event Log failure or critical event."
        --#TYPE       "System: System Event Log Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 2377 }

    ------------------------------------------------------------------------------
    -- Chassis Alerts 2: System: Software Configuration Traps
    --
    -- Category: System/1
    -- Subcategory: SWC/36
    ------------------------------------------------------------------------------

    alert2SoftwareConfigurationInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software configuration information."
        --#TYPE       "System: Software Configuration Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2339 }

    alert2SoftwareConfigurationWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software configuration warning."
        --#TYPE       "System: Software Configuration Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2338 }

    alert2SoftwareConfigurationFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software configuration failure."
        --#TYPE       "System: Software Configuration Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2337 }

    ------------------------------------------------------------------------------
    -- Chassis Alerts 2: System: Temperature Probe Traps
    --
    -- Category: System/1
    -- Subcategory: TMP/14
    ------------------------------------------------------------------------------

    alert2TemperatureProbeNormal NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Temperature sensor value is within range."
        --#TYPE       "System: Temperature Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2163 }

    alert2TemperatureProbeWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Temperature sensor has detected a warning value."
        --#TYPE       "System: Temperature Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2162 }

    alert2TemperatureProbeFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Temperature sensor has detected a failure value."
        --#TYPE       "System: Temperature Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2161 }

    ------------------------------------------------------------------------------
    -- Chassis Alerts 2: System: Voltage Probe Traps
    --
    -- Category: System/1
    -- Subcategory: VLT/15
    ------------------------------------------------------------------------------

    alert2VoltageProbeNormal NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Voltage sensor reading is within range."
        --#TYPE       "System: Voltage Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 2171 }

    alert2VoltageProbeWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Voltage sensor has detected a warning value."
        --#TYPE       "System: Voltage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 2170 }

    alert2VoltageProbeFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Voltage sensor has detected a failure value."
        --#TYPE       "System: Voltage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 2169 }

    -------------------------------------------------------------------------------
    -- Chassis Alerts 2: Storage: Battery Traps
    --
    -- Category: Storage/2
    -- Subcategory: BAT/22
    -------------------------------------------------------------------------------

    alert2StorageBatteryInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Battery information."
        --#TYPE       "Storage: Battery Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4275 }

    alert2StorageBatteryWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Battery warning."
        --#TYPE       "Storage: Battery Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4274 }

    alert2StorageBatteryFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Battery failure."
        --#TYPE       "Storage: Battery Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4273 }

    ------------------------------------------------------------------------------
    -- Chassis Alerts 2: Storage: Controller Traps
    --
    -- Category: Storage/2
    -- Subcategory: CTL/29
    ------------------------------------------------------------------------------

    alert2StorageControllerInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Controller information."
        --#TYPE       "Storage: Controller Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4331 }

    alert2StorageControllerWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Controller warning."
        --#TYPE       "Storage: Controller Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4330 }

    alert2StorageControllerFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Controller failure."
        --#TYPE       "Storage: Controller Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4329 }

    ------------------------------------------------------------------------------
    -- Chassis Alerts 2: Storage: Enclosure Traps
    --
    -- Category: Storage/2
    -- Subcategory: ENC/30
    ------------------------------------------------------------------------------

    alert2StorageEnclosureInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Enclosure information."
        --#TYPE       "Storage: Enclosure Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4339 }

    alert2StorageEnclosureWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Enclosure warning."
        --#TYPE       "Storage: Enclosure Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4338 }

    alert2StorageEnclosureFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Enclosure failure."
        --#TYPE       "Storage: Enclosure Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4337 }

    ------------------------------------------------------------------------------
    -- Chassis Alerts 2: Storage: Fan Traps
    --
    -- Category: Storage/2
    -- Subcategory: FAN/13
    ------------------------------------------------------------------------------

    alert2StorageFanInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Fan information."
        --#TYPE       "Storage: Fan Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4203 }

    alert2StorageFanWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Fan warning."
        --#TYPE       "Storage: Fan Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 4202 }

    alert2StorageFanFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Fan failure."
        --#TYPE       "Storage: Fan Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4201 }

    ------------------------------------------------------------------------------
    -- Chassis Alerts 2: Storage: Physical Disk Traps
    --
    -- Category: Storage/2
    -- Subcategory: PDR/31
    ------------------------------------------------------------------------------

    alert2StoragePhysicalDiskInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Physical disk information."
        --#TYPE       "Storage: Physical Disk Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4347 }

    alert2StoragePhysicalDiskWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Physical disk warning."
        --#TYPE       "Storage: Physical Disk Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4346 }

    alert2StoragePhysicalDiskFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Physical disk failure."
        --#TYPE       "Storage: Physical Disk Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4345 }

    ------------------------------------------------------------------------------
    -- Chassis Alerts 2: Storage: Power Supply Traps
    --
    -- Category: Storage/2
    -- Subcategory: PSU/17
    ------------------------------------------------------------------------------

    alert2StoragePowerSupplyInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Power supply information."
        --#TYPE       "Storage: Power Supply Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4235 }

    alert2StoragePowerSupplyWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Power supply warning."
        --#TYPE       "Storage: Power Supply Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4234 }

    alert2StoragePowerSupplyFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Power supply failure."
        --#TYPE       "Storage: Power Supply Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4233 }

    ------------------------------------------------------------------------------
    -- Chassis Alerts 2: Storage: Security Event Traps
    --
    -- Category: Storage/2
    -- Subcategory: SEC/42
    ------------------------------------------------------------------------------

    alert2StorageSecurityInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Security information."
        --#TYPE       "Storage: Security Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 4435 }

    alert2StorageSecurityWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Security warning."
        --#TYPE       "Storage: Security Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 4434 }

    alert2StorageSecurityFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Security failure or critical event."
        --#TYPE       "Storage: Security Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4433 }

    ------------------------------------------------------------------------------
    -- Chassis Alerts 2: Storage: Storage Management Status Traps
    --
    -- Category: Storage/2
    -- Subcategory: STOR/10
    ------------------------------------------------------------------------------

    alert2StorageManagementInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Management information.
            There is no global status change associated with this trap."
        --#TYPE       "Storage: Storage Management Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4179 }

    alert2StorageManagementWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Management has detected a device independent warning
            condition. There is no global status change associated with this
            trap."
        --#TYPE       "Storage: Storage Management Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4178 }

    alert2StorageManagementFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Storage Management has detected a device independent error condition.
            There is no global status change associated with this trap."
        --#TYPE       "Storage: Storage Management Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4177 }

    ------------------------------------------------------------------------------
    -- Chassis Alerts 2: Storage: Temperature Probe Traps
    --
    -- Category: Storage/2
    -- Subcategory: TMP/14
    ------------------------------------------------------------------------------

    alert2StorageTemperatureProbeInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Temperature probe information."
        --#TYPE       "Storage: Temperature Probe Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4211 }

    alert2StorageTemperatureProbeWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Temperature probe warning."
        --#TYPE       "Storage: Temperature Probe Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4210 }

    alert2StorageTemperatureProbeFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Temperature probe failure."
        --#TYPE       "Storage: Temperature Probe Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4209 }

    ------------------------------------------------------------------------------
    -- Chassis Alerts 2: Storage: Virtual Disk Traps
    --
    -- Category: Storage/2
    -- Subcategory: VDR/32
    ------------------------------------------------------------------------------

    alert2StorageVirtualDiskInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Virtual disk information."
        --#TYPE       "Storage: Virtual Disk Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     current
        ::= { dmmChassisAlert2Group 0 4355 }

    alert2StorageVirtualDiskWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Virtual disk warning."
        --#TYPE       "Storage: Virtual Disk Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 4354 }

    alert2StorageVirtualDiskFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
             "Storage Virtual disk failure."
        --#TYPE       "Storage: Virtual Disk Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     current
        ::= { dmmChassisAlert2Group 0 4353 }

    ------------------------------------------------------------------------------
    -- Chassis Alerts 2: Updates: Software Change Traps
    --
    -- Category: Updates/3
    -- Subcategory: SWU/21
    ------------------------------------------------------------------------------

    alert2SoftwareChangeUpdateWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software change update warning."
        --#TYPE       "Updates: Software Change Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 6314 }

    ------------------------------------------------------------------------------
    -- Chassis Alerts 2: Audit: Traps
    --
    -- Category: Audit/4
    -- Subcategory: /62
    ------------------------------------------------------------------------------

    alert2CMCAuditInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Chassis Management Module audit information."
        --#TYPE       "Audit: Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 8691 }

    alert2CMCAuditWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Chassis Management Module audit warning."
        --#TYPE       "Audit: Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 8690 }

    alert2CMCAuditFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Chassis Management Module audit failure or critical event."
        --#TYPE       "Audit: Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 8689 }

    ------------------------------------------------------------------------------
    -- Chassis Alerts 2: Audit: IO Virtualization Traps
    --
    -- Category: Audit/4
    -- Subcategory: IOV/63
    ------------------------------------------------------------------------------

    alert2IOVirtualizationAuditWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "IO Virtualization audit warning."
        --#TYPE       "Audit: IO Virtualization Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 8698 }

    ------------------------------------------------------------------------------
    -- Chassis Alerts 2: Audit: License Traps
    --
    -- Category: Audit/4
    -- Subcategory: LIC/40
    ------------------------------------------------------------------------------

    alert2LicenseInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "License information."
        --#TYPE       "Audit: License Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 8515 }

    alert2LicenseWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "License warning."
        --#TYPE       "Audit: License Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 8514 }

    alert2LicenseFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "License failure."
        --#TYPE       "Audit: License Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 8513 }

    ------------------------------------------------------------------------------
    -- Chassis Alerts 2: Audit: PCI Device Traps
    --
    -- Category: Audit/4
    -- Subcategory: PCI/46
    ------------------------------------------------------------------------------

    alert2PCIDeviceAuditWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "PCI device audit warning."
        --#TYPE       "Audit: PCI Device Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 8562 }

    ------------------------------------------------------------------------------
    -- Chassis Alerts 2: Audit: Power Supply Traps
    --
    -- Category: Audit/4
    -- Subcategory: PSU/17
    ------------------------------------------------------------------------------

    alert2PowerSupplyAuditWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power Supply audit warning."
        --#TYPE       "Audit: Power Supply Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 8330 }

    alert2PowerSupplyAuditFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power Supply audit failure or critical event."
        --#TYPE       "Audit: Power Supply Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 8329 }

    ------------------------------------------------------------------------------
    -- Chassis Alerts 2: Audit: Power Usage Traps
    --
    -- Category: Audit/4
    -- Subcategory: PWR/28
    ------------------------------------------------------------------------------

    alert2PowerUsageAuditInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power usage audit information."
        --#TYPE       "Audit: Power Usage Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 8419 }

    alert2PowerUsageAuditWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power usage audit warning."
        --#TYPE       "Audit: Power Usage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 8418 }

    alert2PowerUsageAuditFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Power usage audit failure or critical event."
        --#TYPE       "Audit: Power Usage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 8417 }

    ------------------------------------------------------------------------------
    -- Chassis Alerts 2: Audit: Software Change Traps
    --
    -- Category: Audit/4
    -- Subcategory: SWU/21
    ------------------------------------------------------------------------------

    alert2SoftwareChangeAuditFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software change audit failure or critical event."
        --#TYPE       "Audit: Software Change Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 8361 }

    ------------------------------------------------------------------------------
    -- Chassis Alerts 2: Configuration: IO Virtualization Traps
    --
    -- Category: Configuration/5
    -- Subcategory: IOV/63
    ------------------------------------------------------------------------------

    alert2IOVConfigurationInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "IO Virtualization configuration information."
        --#TYPE       "Configuration: IO Virtualization Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 10747 }

    alert2IOVConfigurationWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "IO Virtualization configuration warning."
        --#TYPE       "Configuration: IO Virtualization Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 10746 }

    ------------------------------------------------------------------------------
    -- Chassis Alerts 2: Configuration: PCI Device Traps
    --
    -- Category: Configuration/5
    -- Subcategory: PCI/46
    ------------------------------------------------------------------------------

    alert2PCIDeviceConfigurationInformation NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "PCI device configuration information."
        --#TYPE       "Configuration: PCI Device Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     current
        ::= { dmmChassisAlert2Group 0 10611 }

    ------------------------------------------------------------------------------
    -- Chassis Alerts 2: Configuration: Software Configuration Traps
    --
    -- Category: Configuration/5
    -- Subcategory: SWC/36
    ------------------------------------------------------------------------------

    alert2SWCConfigurationWarning NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software configuration warning."
        --#TYPE       "Configuration: Software Configuration Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     current
        ::= { dmmChassisAlert2Group 0 10530 }

    alert2SWCConfigurationFailure NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Software configuration failure."
        --#TYPE       "Configuration: Software Configuration Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     current
        ::= { dmmChassisAlert2Group 0 10529 }

    ------------------------------------------------------------------------------
    -- Chassis Alerts 2: Configuration: Test Traps
    --
    -- Category: Configuration/5
    -- Subcategory: TST/19
    ------------------------------------------------------------------------------

    alert2CMCTestTrap NOTIFICATION-TYPE
        OBJECTS { dmmCA2MessageID,
                    dmmCA2Message,
                    dmmCA2MessageArgs,
                    dmmCA2AlertStatus,
                    dmmCA2FQDD,
                    dmmProductChassisName,
                    dmmChassisServiceTag}
        STATUS	current
		DESCRIPTION
            "Test trap generated in response to a user request."
        --#TYPE       "Configuration:  Test Trap"
        --#SEVERITY   INFORMATIONAL
        --#SUMMARY    "%s"
        --#ARGUMENTS  {1}
        --#CATEGORY   "Status Events"
        --#STATE      OPERATIONAL
        --#STATUS     current
        ::= { dmmChassisAlert2Group 0 10395 }


dmmGenericAlertNotificationGroup NOTIFICATION-GROUP
    NOTIFICATIONS { alertGenericCritical, alertGenericWarning, alertGenericNormal,
					alertGenericInformational, alertGenericTestTrapEvent }
    STATUS        current
    DESCRIPTION
            "The two notifications which an SNMPv2 entity is required to
            implement."
    ::= { conformanceMIBnotificationGroup 2 }


    ------------------------------------------------------------------------------
    -- Alert 1: Internal: Internal MM Traps
    --
    -- Category: Internal/1
    -- Subcategory: Internal/1
    ------------------------------------------------------------------------------
    alertGenericCritical NOTIFICATION-TYPE
        OBJECTS { dmmCA2MessageID,
                    dmmCA2Message,
                    dmmCA2MessageArgs,
                    dmmCA2AlertStatus,
					dmmDeviceServiceTag
                    }
		STATUS current
        DESCRIPTION
            "MM generic critical system alert."
        --#TYPE       "Internal: MM System Alert"
        --#SEVERITY   CRITICAL
        --#SUMMARY    "Message ID: %s, Message: %s,"
        --#SUMMARY    "Device Status: %d "
        --#ARGUMENTS  {0, 1, 3}
        --#CATEGORY   "Internal Events"
        --#STATE      OPERATIONAL
        --#STATUS     current
        ::= { dmmGenericAlertGroup 0 100 }

    ------------------------------------------------------------------------------
    -- MM Alert 2: Internal: Internal MM Traps
    --
    -- Category: Internal/1
    -- Subcategory: Internal/2
    ------------------------------------------------------------------------------
    alertGenericWarning NOTIFICATION-TYPE
        OBJECTS { dmmCA2MessageID,
                    dmmCA2Message,
                    dmmCA2MessageArgs,
                    dmmCA2AlertStatus,
					dmmDeviceServiceTag
                    }
		STATUS current
        DESCRIPTION
            "MM generic warning system alert."
        --#TYPE       "Internal: MM System Alert"
        --#SEVERITY   WARNING
        --#SUMMARY    "Message ID: %s, Message: %s,"
        --#SUMMARY    "Device Status: %d "
        --#ARGUMENTS  {0, 1, 3}
        --#CATEGORY   "Internal Events"
        --#STATE      OPERATIONAL
        --#STATUS     current
        ::= { dmmGenericAlertGroup 0 200 }

    ------------------------------------------------------------------------------
    -- MM Alert 3: Internal: Internal MM Traps
    --
    -- Category: Internal/1
    -- Subcategory: Internal/3
    ------------------------------------------------------------------------------
    alertGenericNormal NOTIFICATION-TYPE
        OBJECTS { dmmCA2MessageID,
                    dmmCA2Message,
                    dmmCA2MessageArgs,
                    dmmCA2AlertStatus,
					dmmDeviceServiceTag
                    }
		STATUS current
        DESCRIPTION
            "MM generic normal system alert."
        --#TYPE       "Internal: MM System Alert"
        --#SEVERITY   NORMAL
        --#SUMMARY    "Message ID: %s, Message: %s,"
        --#SUMMARY    "Device Status: %d "
        --#ARGUMENTS  {0, 1, 3}
        --#CATEGORY   "Internal Events"
        --#STATE      OPERATIONAL
        --#STATUS     current
        ::= { dmmGenericAlertGroup 0 300 }

    ------------------------------------------------------------------------------
    -- MM Alert 4: Internal: Internal MM Traps
    --
    -- Category: Internal/1
    -- Subcategory: Internal/4
    ------------------------------------------------------------------------------
    alertGenericInformational NOTIFICATION-TYPE
        OBJECTS { dmmCA2MessageID,
                    dmmCA2Message,
                    dmmCA2MessageArgs,
                    dmmCA2AlertStatus,
					dmmDeviceServiceTag
                    }
		STATUS 	current
        DESCRIPTION
            "MM generic information system alert."
        --#TYPE       "Internal: MM System Alert"
        --#SEVERITY   INFORMATIONAL
        --#SUMMARY    "Message ID: %s, Message: %s,"
        --#SUMMARY    "Device Status: %d "
        --#ARGUMENTS  {0, 1, 3}
        --#CATEGORY   "Internal Events"
        --#STATE      OPERATIONAL
        --#STATUS     current
        ::= { dmmGenericAlertGroup 0 400 }

   ------------------------------------------------------------------------------
    -- MM Alert 5: Internal: Internal MM Traps
    --
    -- Category: Internal/1
    -- Subcategory: Internal/5
    ------------------------------------------------------------------------------
    alertGenericTestTrapEvent NOTIFICATION-TYPE
        OBJECTS { dmmCA2Message
                    }
		STATUS current
        DESCRIPTION
            "MM Generated a test trap event in response to a user request."
        --#TYPE       "Internal: Dell MM Test TRAP Event"
        --#SEVERITY   INFORMATIONAL
        --#SUMMARY    "%s"
        --#ARGUMENTS  {0}
        --#CATEGORY   "Status Events"
        ::= { dmmGenericAlertGroup 0 500 }

END

------------------------------------------------------------------------------
-- End MIB
------------------------------------------------------------------------------
