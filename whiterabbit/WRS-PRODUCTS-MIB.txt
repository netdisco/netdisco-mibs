WRS-PRODUCTS-MIB DEFINITIONS ::= BEGIN

--
-- Example OIDs to identify WR switch models
--

IMPORTS
    MODULE-IDENTITY             FROM SNMPv2-SMI
    wrSwitchMIB                 FROM WR-SWITCH-MIB
;

wrsProductId MODULE-IDENTITY
    LAST-UPDATED "202003130000Z"
    ORGANIZATION "GSI"
    CONTACT-INFO
	    "postal:   TOS/ACO, GSI
                 Planckstr.1
                 64291 Darmstadt

      email:    tos@gsi.de"
    DESCRIPTION
      "Example OIDs to identify WR switches used in GSI"
    REVISION "202003130000Z"
    DESCRIPTION
	    "First draft"
      ::= { wrSwitchMIB 1000 }

--
-- OIDs for identifying WR switch models
--

-- wrsProduct (.1000.1)
wrsProduct                        OBJECT IDENTIFIER ::= { wrsProductId 1 }

-- wrsProductHwRev (.1000.2)
wrsProductHwRev                   OBJECT IDENTIFIER ::= { wrsProductId 2 }
wrsProductHwRev33                 OBJECT IDENTIFIER ::= { wrsProductHwRev 33 }
wrsProductHWRev34                 OBJECT IDENTIFIER ::= { wrsProductHwRev 34 }

-- wrsProductRef (.1000.3)
wrsProductRef                     OBJECT IDENTIFIER ::= { wrsProductId 3 }
wrsProductRef318                  OBJECT IDENTIFIER ::= { wrsProductRef 1 }
wrsProductRefFl18                 OBJECT IDENTIFIER ::= { wrsProductRef 2 }

-- wrsProductModel (.1000.4)
wrsProductModel                   OBJECT IDENTIFIER ::= { wrsProductId 4 }
wrsProductModel7Sol               OBJECT IDENTIFIER ::= { wrsProductModel 1 }
wrsProductModelCreoTech           OBJECT IDENTIFIER ::= { wrsProductModel 2 }
wrsProductModelSyncTech           OBJECT IDENTIFIER ::= { wrsProductModel 3 }

wrsProductModel7SolH33R318        OBJECT IDENTIFIER ::= { wrsProductModel7Sol 1 }
wrsProductModel7SolH34R318        OBJECT IDENTIFIER ::= { wrsProductModel7Sol 2 }

wrsProductModelCreoTechH33R318    OBJECT IDENTIFIER ::= { wrsProductModelCreoTech 1 }
wrsProductModelCreoTechH34R318    OBJECT IDENTIFIER ::= { wrsProductModelCreoTech 2 }

wrsProductModelSyncTechH33RFl18   OBJECT IDENTIFIER ::= { wrsProductModelSyncTech 1 }

--
-- Examples setting 'sysObjectID' OID
--

-- In order to identify any WR switch a simple value of 'wrsProductId', which
-- is equivalent to '1.3.6.1.4.1.96.100.1000.1' can be used for 'sysObjectID' as
-- an WR switch identification.

-- If more precise identification is needed, then model specific IDs can be used.
-- In case of WR switches from CreoTech (HW v3.4, Ref 3/18) a value of
-- 'wrsProductModelCreoTechH34R318', which is equivalent to
-- '1.3.6.1.4.1.96.100.1000.4.2.2' is used for 'sysObjectID'.

END
