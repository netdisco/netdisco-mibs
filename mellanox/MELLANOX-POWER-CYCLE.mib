MELLANOX-POWER-CYCLE-MIB DEFINITIONS ::= BEGIN

IMPORTS
    NOTIFICATION-TYPE, MODULE-IDENTITY, OBJECT-TYPE, Integer32
        FROM SNMPv2-SMI
	mellanoxPowerCycle
		FROM MELLANOX-SMI-MIB;

-- Mellanox Power Cycle MIB

mellanoxPowerCycleMib MODULE-IDENTITY
	LAST-UPDATED "201806040000Z"
	ORGANIZATION 
		"Mellanox Technologies, Inc."
	CONTACT-INFO 
		"
		Mellanox Technologies, Inc.
		350 Oakmead Parkway, Suite 100
		Sunnyvale, CA 94085
		Tel: 408-970-3400
		Fax: 408-970-3403
		E-mail: info@mellanox.com
		        "
	DESCRIPTION 
		"Mellanox PowerCycle MIB"

	REVISION "201806040000Z"
	DESCRIPTION 
		"Added planned reload traps"
::= { mellanoxPowerCycle 1 }
		
mellanoxPowerCycleMibObjects  OBJECT IDENTIFIER ::= { mellanoxPowerCycleMib 1 }

mellanoxPowerCycleCmd     OBJECT IDENTIFIER ::= { mellanoxPowerCycleMibObjects 2 }

mellanoxPowerCycleNotifications     OBJECT IDENTIFIER ::= { mellanoxPowerCycleMibObjects 3 }

mellanoxPowerCycleCmdExecute  OBJECT-TYPE
	SYNTAX     INTEGER {
		mellanoxPowerCycleCmdExecuteReload (1),
		mellanoxPowerCycleCmdExecuteReloadDiscard (2),
		mellanoxPowerCycleCmdExecuteReloadForce (3),
		mellanoxPowerCycleCmdExecuteReloadSlave (4)
	}
	MAX-ACCESS     read-write
	STATUS     current
	DESCRIPTION 
		"The operation to execute
		Setting this value will initiate the operation"
	::= { mellanoxPowerCycleCmd 1 }

mellanoxPowerCycleCmdStatus  OBJECT-TYPE
	SYNTAX     INTEGER
	MAX-ACCESS     read-only
	STATUS     current
	DESCRIPTION 
		"The status of the operation:
		0: No operation
		1-100: progress percentage
		101: success
		>200: failure"
	::= { mellanoxPowerCycleCmd 2 }

mellanoxPowerCycleCmdStatusString  OBJECT-TYPE
	SYNTAX     OCTET STRING
	MAX-ACCESS     read-only
	STATUS     current
	DESCRIPTION 
		"String value describing the operation status or error"
	::= { mellanoxPowerCycleCmd 3 }

mellanoxPowerCyclePlannedReload  NOTIFICATION-TYPE
	STATUS     current
	DESCRIPTION 
		"Device has resumed after a planned reload operation"
	::= { mellanoxPowerCycleNotifications 1 }

END
