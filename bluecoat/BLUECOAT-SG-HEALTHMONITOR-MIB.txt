BLUECOAT-SG-HEALTHMONITOR-MIB DEFINITIONS ::= BEGIN

IMPORTS
        MODULE-IDENTITY, OBJECT-TYPE, NOTIFICATION-TYPE
                FROM SNMPv2-SMI
        TEXTUAL-CONVENTION
                FROM SNMPv2-TC
        blueCoatMgmt
                FROM BLUECOAT-MIB;

bluecoatSGHealthMonitorMIB MODULE-IDENTITY
        LAST-UPDATED    "200711050300Z"
        ORGANIZATION    "Blue Coat Systems, Inc."
        CONTACT-INFO    "support.services@bluecoat.com
                         http://www.bluecoat.com"
        DESCRIPTION     "The health monitoring MIB is used to monitor
                         changes in the health of the SG appliance."
        REVISION        "200711050300Z"
        DESCRIPTION     "Initial revision of this MIB."
        ::= { blueCoatMgmt 12 }

bluecoatSgHealthMonitorMIBObjects
        OBJECT IDENTIFIER ::= { bluecoatSGHealthMonitorMIB 1 }

bluecoatSgHealthMonitorMIBNotifications
        OBJECT IDENTIFIER ::= { bluecoatSGHealthMonitorMIB 2 }

bluecoatSgHealthMonitorMIBNotificationsPrefix
        OBJECT IDENTIFIER ::= { bluecoatSgHealthMonitorMIBNotifications 0 }

--
-- Textual conventions
--

HealthMonitorMessageString ::= TEXTUAL-CONVENTION
        DISPLAY-HINT     "255a"
        STATUS           current
        DESCRIPTION      "The message describing a change in the health
                          of the SG system."
        SYNTAX           OCTET STRING (SIZE (0..255))

--
-- MIB variables
--

bluecoatSgHealthMonitorValues
        OBJECT IDENTIFIER ::= { bluecoatSgHealthMonitorMIBObjects 1 }

bluecoatSgHealthMonitorMessage OBJECT-TYPE
        SYNTAX          HealthMonitorMessageString
        MAX-ACCESS      accessible-for-notify
        STATUS          current
        DESCRIPTION     "The custom message generated for this change in health."
        ::= { bluecoatSgHealthMonitorValues 1 }

--
-- notifications
--

bluecoatSgHealthMonitorTrap NOTIFICATION-TYPE
        OBJECTS { bluecoatSgHealthMonitorMessage }
        STATUS          current
        DESCRIPTION     "A notification is generated when the health
                         of the SG system changes."
        ::= { bluecoatSgHealthMonitorMIBNotificationsPrefix 1 }

END
