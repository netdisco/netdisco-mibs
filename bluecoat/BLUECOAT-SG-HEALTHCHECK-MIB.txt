BLUECOAT-SG-HEALTHCHECK-MIB DEFINITIONS ::= BEGIN

IMPORTS
        MODULE-IDENTITY, OBJECT-TYPE, NOTIFICATION-TYPE
                FROM SNMPv2-SMI
        TEXTUAL-CONVENTION
                FROM SNMPv2-TC
        blueCoatMgmt
                FROM BLUECOAT-MIB;

deviceHealthCheckMIB MODULE-IDENTITY
        LAST-UPDATED    "200711050300Z"
        ORGANIZATION    "Blue Coat Systems, Inc."
        CONTACT-INFO    "support.services@bluecoat.com
                         http://www.bluecoat.com"
        DESCRIPTION     "The health check MIB is used to monitor
                         changes in the health of upstream systems."
        REVISION        "200711050300Z"
        DESCRIPTION     "Minor corrections and reformatting. Changed the
                         trap OID for compatibility with SNMPv1."
        REVISION        "200208280300Z"
        DESCRIPTION     "Initial revision of this MIB."
        ::= { blueCoatMgmt 7 }

deviceHealthCheckMIBObjects
        OBJECT IDENTIFIER ::= { deviceHealthCheckMIB 1 }

deviceHealthCheckMIBNotifications
        OBJECT IDENTIFIER ::= { deviceHealthCheckMIB 2 }

deviceHealthCheckMIBNotificationsPrefix
        OBJECT IDENTIFIER ::= { deviceHealthCheckMIBNotifications 0 }

--
-- Textual conventions
--

HealthCheckMessageString ::= TEXTUAL-CONVENTION
        DISPLAY-HINT     "255a"
        STATUS           current
        DESCRIPTION      "The message describing a change in the health
                          of an upstream system."
        SYNTAX           OCTET STRING (SIZE (0..255))

--
-- MIB variables
--

deviceHealthCheckValues
        OBJECT IDENTIFIER ::= { deviceHealthCheckMIBObjects 1 }

deviceHealthCheckMessage OBJECT-TYPE
        SYNTAX          HealthCheckMessageString
        MAX-ACCESS      accessible-for-notify
        STATUS          current
        DESCRIPTION     "The custom message generated for this change in health."
        ::= { deviceHealthCheckValues 1 }

--
-- notifications
--

deviceHealthCheckTrap NOTIFICATION-TYPE
        OBJECTS { deviceHealthCheckMessage }
        STATUS          current
        DESCRIPTION     "A notification is generated when the health
                         of a monitored system changes."
        ::= { deviceHealthCheckMIBNotificationsPrefix 1 }

END
