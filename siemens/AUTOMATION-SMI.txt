-- ----------------------------------------------------------------------
-- automationSmi.mib
--
-- SIEMENS AG 
-- Industry Sector
--     
-- Industry Automation Division Structure of Management Information
--
-- Copyright (c) 2005-2013 Siemens AG
-- All rights reserved.
-- ----------------------------------------------------------------------

AUTOMATION-SMI                  DEFINITIONS ::= BEGIN

IMPORTS
    siemens                     FROM SIEMENS-SMI
    MODULE-IDENTITY,
    OBJECT-IDENTITY             FROM SNMPv2-SMI;

automation                      MODULE-IDENTITY
    LAST-UPDATED                "201306250000Z"
    ORGANIZATION                "Siemens AG"
    CONTACT-INFO                "
                                Siemens AG
                                Industry Sector
                                I IA AS CTO SYA
                                SNMP Automation Registration Authority
                                
                                Postal: Gleiwitzer Strasse 555
                                        Nuremberg-Moorenbrunn
                                        D-90475
                                Tel:    +49 911 895 0
                                E-mail: automation-mib.industry@siemens.com
                                "
    DESCRIPTION                 "
                                The root object identifier of Siemens automation MIB.
                                The MIB module provides the structure of
                                management information of Siemens AG,
                                Industry Sector
                                Industry Automation Division
                                "

  REVISION                      "201306250000Z"
  DESCRIPTION                   "added SitopPower branch"

  REVISION                      "201207270000Z"
  DESCRIPTION                   "Bugfixes and corrections according to SPH V1.2."

  REVISION                      "200811100000Z"
  DESCRIPTION                   "Update the contact information"

  REVISION                      "200806020000Z"
  DESCRIPTION                   "declaration of siemens node will be imported
                                 now from SIEMENS-SMI"

  REVISION                      "200804290000Z"
  DESCRIPTION                   "declaration of siemens node moved into
                                 declaration of MODULE IDENTITY."

  REVISION                      "200501120000Z"
  DESCRIPTION                   "Initial Version of the MIB module."
  ::= { siemens 6 }

automationProducts              OBJECT-IDENTITY
    STATUS                      current
    DESCRIPTION                 "
                                automationProducts is the product specific
                                subtree. The root OIDs of the product
                                subtrees are used as sysObjectID as well.
                                "
    ::= { automation 1 }

automationPlc                   OBJECT-IDENTITY
    STATUS                      current
    DESCRIPTION                 "Subtree for SIMATIC S7 PLC products."
    ::= { automationProducts 1 }

automationSimaticNet            OBJECT-IDENTITY
    STATUS                      current
    DESCRIPTION                 "Subtree for SIMATIC NET products."
    ::= { automationProducts 2 }
               
automationMotionControl         OBJECT-IDENTITY
    STATUS                      current
    DESCRIPTION                 "Subtree for motion control products of
                                Siemens."
    ::= { automationProducts 3 }

automationHmi                   OBJECT-IDENTITY
    STATUS                      current
    DESCRIPTION                 "Subtree for SIMATIC HMI products."
    ::= { automationProducts 4 }

automationSitopPower            OBJECT-IDENTITY
    STATUS                      current
    DESCRIPTION                 "Subtree for Sitop Power products."
    ::= { automationProducts 5 }

automationModules               OBJECT-IDENTITY
    STATUS                      current
    DESCRIPTION                 "
                                This subtree is reserved for
                                administratively assigned
                                OBJECT IDENTIFIERS, i.e. those which
                                are not associated with MIB objects.
                                These could be TEXTUAL CONVENTIONS,
                                module registration and so on.
                                "
    ::= { automation 2 }

automationMgmt                  OBJECT-IDENTITY
    STATUS                      current
    DESCRIPTION                 "The subtree which contains the MIB
                                modules to manage a Siemens
                                automation system."
    ::= { automation 3 }

automationAgentCapability       OBJECT-IDENTITY
    STATUS                      current
    DESCRIPTION                 "Subtree for agent profiles."
    ::= { automation 4 }

automationPlcAgentCapability    OBJECT-IDENTITY
    STATUS                      current
    DESCRIPTION                 "Subtree for SIMATIC S7 agent profiles."
    ::= { automationAgentCapability 1 }

automationSimaticNetAgentCapability OBJECT-IDENTITY
    STATUS                      current
    DESCRIPTION                 "Subtree for SIMATIC NET agent profiles."
    ::= { automationAgentCapability 2 }

automationMotionControlAgentCapability OBJECT-IDENTITY
    STATUS                      current
    DESCRIPTION                 "Subtree for motion control agent profiles."
    ::= { automationAgentCapability 3 }

automationHmiAgentCapability    OBJECT-IDENTITY
    STATUS                      current
    DESCRIPTION                 "Subtree for HMI agent profiles."
    ::= { automationAgentCapability 4 }

automationSitopPowerCapability  OBJECT-IDENTITY
    STATUS                      current
    DESCRIPTION                 "Subtree for Sitop Power agent profiles."
    ::= { automationAgentCapability 5 }

END
