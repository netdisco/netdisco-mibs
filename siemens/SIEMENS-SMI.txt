-- ----------------------------------------------------------------------
-- siemensSmi.mib
--
-- SIEMENS AG 
-- Industry Sector
--     
-- Siemens Structure of Management Information
--
-- Copyright (c) 2005-2012 Siemens AG
-- All rights reserved.
-- ----------------------------------------------------------------------
      
SIEMENS-SMI             DEFINITIONS ::= BEGIN

IMPORTS
  MODULE-IDENTITY,
  enterprises           FROM SNMPv2-SMI;

siemens                 MODULE-IDENTITY
  LAST-UPDATED          "201206010000Z"
  ORGANIZATION          "Siemens AG"
  CONTACT-INFO          "
                         Siemens AG
                         Industry Sector
                         I IA AS CTO SYA
                         SNMP Automation Registration Authority

                         Postal: Gleiwitzer Strasse 555
                                 Nuremberg-Moorenbrunn
                                 D-90475
                         Tel:    +49 911 895 0
                         E-mail: automation-mib.industry@siemens.com
                        "
  DESCRIPTION           "
                        The root object identifier of Siemens. The
                        MIB module provides the structure of
                        management information of Siemens AG.
                        "
  REVISION              "201206010000Z"
  DESCRIPTION           "Update contact information"

  REVISION              "200811100000Z"
  DESCRIPTION           "Update the contact information."

  REVISION              "200806020000Z"
  DESCRIPTION           "Initial Version of the MIB module."
  ::= { enterprises 4329 }

END
