SYNOLOGY-SMB-MIB DEFINITIONS ::= BEGIN

IMPORTS
    OBJECT-GROUP, MODULE-COMPLIANCE
        FROM SNMPv2-CONF
    OBJECT-TYPE, Integer32, enterprises, MODULE-IDENTITY
        FROM SNMPv2-SMI;

synologySMB MODULE-IDENTITY
    LAST-UPDATED    "202302080000Z"
    ORGANIZATION    "www.synology.com"
    CONTACT-INFO
          "Synology Inc.
          Email: snmp@synology.com"
    DESCRIPTION     "Characteristics of the SMB information"
    ::= { synology 111 }

synology    OBJECT IDENTIFIER
    ::= { enterprises 6574 }

SMBCpuTable OBJECT-TYPE
    SYNTAX      SEQUENCE OF SMBCpuEntry
    MAX-ACCESS  not-accessible
    STATUS      current
    DESCRIPTION "Table of SMB Cpu data."
    ::= { synologySMB 1 }

SMBCpuEntry OBJECT-TYPE
    SYNTAX      SMBCpuInfo
    MAX-ACCESS  not-accessible
    STATUS      current
    DESCRIPTION "An entry containing SMB cpu information"
    INDEX       { SMBCpuIndex }
    ::= { SMBCpuTable 1 }

SMBCpuInfo ::= SEQUENCE {
    SMBCpuIndex       Integer32,
    SMBCpuName        DisplayString,
    SMBCpuUser        Integer32,
    SMBCpuSystem      Integer32
}

SMBCpuIndex OBJECT-TYPE
    SYNTAX      Integer32(0..2147483647)
    MAX-ACCESS  not-accessible
    STATUS      current
    DESCRIPTION "SMB cpu index"
    ::= { SMBCpuEntry 1 }

SMBCpuName OBJECT-TYPE
    SYNTAX      DisplayString
    MAX-ACCESS  read-only
    STATUS      current
    DESCRIPTION "SMB cpu name"
    ::= { SMBCpuEntry 2 }

SMBCpuUser OBJECT-TYPE
    SYNTAX      Integer32(0..2147483647)
    MAX-ACCESS  read-only
    STATUS      current
    DESCRIPTION "SMB % cpu user"
    ::= { SMBCpuEntry 3 }

SMBCpuSystem OBJECT-TYPE
    SYNTAX      Integer32(0..2147483647)
    MAX-ACCESS  read-only
    STATUS      current
    DESCRIPTION "SMB % cpu system"
    ::= { SMBCpuEntry 4 }

SMBCmdTable OBJECT-TYPE
    SYNTAX      SEQUENCE OF SMBCmdEntry
    MAX-ACCESS  not-accessible
    STATUS      current
    DESCRIPTION "Table of SMB Cmd data."
    ::= { synologySMB 2 }

SMBCmdEntry OBJECT-TYPE
    SYNTAX      SMBCmdInfo
    MAX-ACCESS  not-accessible
    STATUS      current
    DESCRIPTION "An entry containing SMB cmds information"
    INDEX       { SMBCmdIndex }
    ::= { SMBCmdTable 1 }

SMBCmdInfo ::= SEQUENCE {
    SMBCmdIndex       Integer32,
    SMBCmdName        OCTET STRING,
    SMBCmdCMDPS       Integer32,
    SMBCmdAvgLatency  Integer32
}

SMBCmdIndex OBJECT-TYPE
    SYNTAX      Integer32(0..2147483647)
    MAX-ACCESS  not-accessible
    STATUS      current
    DESCRIPTION "SMB cmds index"
    ::= { SMBCmdEntry 1 }

SMBCmdName OBJECT-TYPE
    SYNTAX      OCTET STRING (SIZE(0..64))
    MAX-ACCESS  read-only
    STATUS      current
    DESCRIPTION "SMB cmd name"
    ::= { SMBCmdEntry 2 }

SMBCmdCMDPS OBJECT-TYPE
    SYNTAX      Integer32(0..2147483647)
    MAX-ACCESS  read-only
    STATUS      current
    DESCRIPTION "SMB cmd per second"
    ::= { SMBCmdEntry 3 }

SMBCmdAvgLatency OBJECT-TYPE
    SYNTAX      Integer32(0..2147483647)
    MAX-ACCESS  read-only
    STATUS      current
    DESCRIPTION "SMB cmd avg latency"
    ::= { SMBCmdEntry 4 }

SMBRWPktTable OBJECT-TYPE
    SYNTAX      SEQUENCE OF SMBRWPktEntry
    MAX-ACCESS  not-accessible
    STATUS      current
    DESCRIPTION "Table of SMB RW packets length data."
    ::= { synologySMB 3 }

SMBRWPktEntry OBJECT-TYPE
    SYNTAX      SMBRWPktInfo
    MAX-ACCESS  not-accessible
    STATUS      current
    DESCRIPTION "An entry containing SMB RW packets length information"
    INDEX       { SMBRWPktIndex }
    ::= { SMBRWPktTable 1 }

SMBRWPktInfo ::= SEQUENCE {
    SMBRWPktIndex       Integer32,
    SMBRWPktName        OCTET STRING,
    SMBRWPktPS          Integer32,
    SMBRWPktAvgLatency  Integer32
}

SMBRWPktIndex OBJECT-TYPE
    SYNTAX      Integer32(0..2147483647)
    MAX-ACCESS  not-accessible
    STATUS      current
    DESCRIPTION "SMB RW packets index"
    ::= { SMBRWPktEntry 1 }

SMBRWPktName OBJECT-TYPE
    SYNTAX      OCTET STRING (SIZE(0..64))
    MAX-ACCESS  read-only
    STATUS      current
    DESCRIPTION "SMB RW packets name"
    ::= { SMBRWPktEntry 2 }

SMBRWPktPS OBJECT-TYPE
    SYNTAX      Integer32(0..2147483647)
    MAX-ACCESS  read-only
    STATUS      current
    DESCRIPTION "SMB RW packets per second"
    ::= { SMBRWPktEntry 3 }

SMBRWPktAvgLatency OBJECT-TYPE
    SYNTAX      Integer32(0..2147483647)
    MAX-ACCESS  read-only
    STATUS      current
    DESCRIPTION "SMB RW packets avg latency"
    ::= { SMBRWPktEntry 4 }

synologySMBConformance  OBJECT IDENTIFIER ::= { synologySMB 4 }
synologySMBCompliances  OBJECT IDENTIFIER ::= { synologySMBConformance 1 }
synologySMBGroups       OBJECT IDENTIFIER ::= { synologySMBConformance 2 }

synologySMBCompliance MODULE-COMPLIANCE
    STATUS           current
    DESCRIPTION
                     "The compliance statement for SMB information."
    MODULE           -- this module
    MANDATORY-GROUPS { synologySMBCPUGroup, synologySMBCmdGroup , synologySMBRWPktGroup}
    ::= { synologySMBCompliances 1 }

synologySMBCPUGroup OBJECT-GROUP
    OBJECTS {   SMBCpuName,
                SMBCpuUser,
                SMBCpuSystem   }
    STATUS      current
    DESCRIPTION
                "A collection of smb cpu utilization providing performance
                characteristics of an synology SMB entity."
    ::= { synologySMBGroups 1 }

synologySMBCmdGroup OBJECT-GROUP
    OBJECTS {   SMBCmdName,
                SMBCmdCMDPS,
                SMBCmdAvgLatency   }
    STATUS      current
    DESCRIPTION
                "A collection of smb cmds providing performance
                characteristics of an synology SMB entity."
    ::= { synologySMBGroups 2 }

synologySMBRWPktGroup OBJECT-GROUP
    OBJECTS {   SMBRWPktName,
                SMBRWPktPS,
                SMBRWPktAvgLatency   }
    STATUS      current
    DESCRIPTION
                "A collection of smb RW packets length providing performance
                characteristics of an synology SMB entity."
    ::= { synologySMBGroups 3 }

END
