SYNOLOGY-ISCSITarget-MIB DEFINITIONS ::= BEGIN

IMPORTS
	OBJECT-GROUP, MODULE-COMPLIANCE
		FROM SNMPv2-CONF
	OBJECT-TYPE, Integer32, enterprises, MODULE-IDENTITY
		FROM SNMPv2-SMI;

synologyiSCSITarget MODULE-IDENTITY
	LAST-UPDATED	"202004150000Z"
	ORGANIZATION	"www.synology.com"
	CONTACT-INFO
		 "Synology Inc.
		  Email: snmp@synology.com"
	DESCRIPTION		"Characteristics of the iscsi target information"
	::= { synology 110 }

synology	OBJECT IDENTIFIER
	::= { enterprises 6574 }

iSCSITargetTable OBJECT-TYPE
	SYNTAX		SEQUENCE OF ISCSITargetEntry
	MAX-ACCESS	not-accessible
	STATUS		current
	DESCRIPTION	"Table of iSCSI Target data."
	::= { synologyiSCSITarget 1 }

iSCSITargetEntry OBJECT-TYPE
	SYNTAX		ISCSITargetEntry
	MAX-ACCESS	not-accessible
	STATUS		current
	DESCRIPTION "An entry containing iscsi target information"
	INDEX		{ iSCSITargetInfoIndex }
	::= { iSCSITargetTable 1 }

ISCSITargetEntry ::= SEQUENCE {
	iSCSITargetInfoIndex		Integer32,
	iSCSITargetName	OCTET STRING,
	iSCSITargetIQN	OCTET STRING,
	iSCSITargetConnectionStatus	OCTET STRING
}

iSCSITargetInfoIndex OBJECT-TYPE
	SYNTAX		Integer32(0..2147483647)
	MAX-ACCESS  not-accessible
	STATUS		current
	DESCRIPTION	"Target info index"
	::= { iSCSITargetEntry 1 }

iSCSITargetName OBJECT-TYPE
	SYNTAX		OCTET STRING (SIZE(0..255))
	MAX-ACCESS	read-only
	STATUS		current
	DESCRIPTION "Target name"
	::= { iSCSITargetEntry 2 }

iSCSITargetIQN OBJECT-TYPE
	SYNTAX		OCTET STRING (SIZE(0..255))
	MAX-ACCESS	read-only
	STATUS		current
	DESCRIPTION "Target iqn"
	::= { iSCSITargetEntry 3 }

iSCSITargetConnectionStatus OBJECT-TYPE
	SYNTAX		OCTET STRING (SIZE(0..4096))
	MAX-ACCESS	read-only
	STATUS		current
	DESCRIPTION "Target connection status"
	::= { iSCSITargetEntry 4 }

synologyiSCSITargetConformance	OBJECT IDENTIFIER ::= { synologyiSCSITarget 2 }
synologyiSCSITargetCompliances	OBJECT IDENTIFIER ::= { synologyiSCSITargetConformance 1 }
synologyiSCSITargetGroups			OBJECT IDENTIFIER ::= { synologyiSCSITargetConformance 2 }

synologyiSCSITargetCompliance MODULE-COMPLIANCE
	STATUS				current
	DESCRIPTION
						"The compliance statement for iSCSI Target information."
	MODULE				-- this module
	MANDATORY-GROUPS	{ synologyiSCSITargetGroup }
	::= { synologyiSCSITargetCompliances 1 }

synologyiSCSITargetGroup OBJECT-GROUP
	OBJECTS {	iSCSITargetName,
				iSCSITargetIQN,
				iSCSITargetConnectionStatus }
	STATUS		current
	DESCRIPTION
				"A collection of objects providing basic information
				of an synology iSCSI Target entity."
	::= { synologyiSCSITargetGroups 1 }

END
