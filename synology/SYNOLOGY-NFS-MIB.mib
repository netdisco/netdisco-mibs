SYNOLOGY-NFS-MIB DEFINITIONS ::= BEGIN

IMPORTS
	DisplayString
		FROM SNMPv2-TC
	OBJECT-GROUP, MODULE-COMPLIANCE
		FROM SNMPv2-CONF
	OBJECT-TYPE, Integer32, Counter64, enterprises, MODULE-IDENTITY
		FROM SNMPv2-SMI;

nfs MODULE-IDENTITY
    LAST-UPDATED "201808100000Z"
    ORGANIZATION "www.synology.com"
    CONTACT-INFO
         "Synology Inc.
          Email: snmp@synology.com"
    DESCRIPTION
        "Characteristics of the nfs information"
    REVISION     "201808100000Z"
    DESCRIPTION
        "First draft."
    ::= { synology 107 }

synology	OBJECT IDENTIFIER
	::= { enterprises 6574 }

nfsTable OBJECT-TYPE
    SYNTAX      SEQUENCE OF NfsEntry
    MAX-ACCESS  not-accessible
    STATUS      current
    DESCRIPTION
        "Table of nfs data."
    ::= { nfs 1 }

nfsEntry OBJECT-TYPE
    SYNTAX      NfsEntry
    MAX-ACCESS  not-accessible
    STATUS      current
    DESCRIPTION
        "An entry containing nfs information."
    INDEX       { nfsIndex }
    ::= { nfsTable 1 }

NfsEntry ::= SEQUENCE {
    nfsIndex			Integer32,
    nfsName			DisplayString,
    nfsTotalMaxLatency		Integer32,
    nfsReadMaxLatency		Integer32,
    nfsWriteMaxLatency		Integer32,
    nfsTotalOPS			Counter64,
    nfsReadOPS			Counter64,
    nfsWriteOPS			Counter64
}

nfsIndex OBJECT-TYPE
    SYNTAX      Integer32 (0..65535)
    MAX-ACCESS  not-accessible
    STATUS      current
    DESCRIPTION
        "Reference index for each observed device."
    ::= { nfsEntry 1 }

nfsName OBJECT-TYPE
	SYNTAX		DisplayString
	MAX-ACCESS	read-only
	STATUS		current
	DESCRIPTION	"nfs name"
	::= { nfsEntry 2 }


nfsTotalMaxLatency OBJECT-TYPE
    SYNTAX      Integer32
    MAX-ACCESS  read-only
    STATUS      current
    DESCRIPTION
        "The number of nfs total max latency."
    ::= { nfsEntry 3 }

nfsReadMaxLatency OBJECT-TYPE
    SYNTAX      Integer32
    MAX-ACCESS  read-only
    STATUS      current
    DESCRIPTION
        "The number of nfs read max latency."
    ::= { nfsEntry 4 }

nfsWriteMaxLatency OBJECT-TYPE
    SYNTAX      Integer32
    MAX-ACCESS  read-only
    STATUS      current
    DESCRIPTION
        "The number of nfs write max latency."
    ::= { nfsEntry 5 }

nfsTotalOPS OBJECT-TYPE
    SYNTAX      Counter64
    MAX-ACCESS  read-only
    STATUS      current
    DESCRIPTION
        "The number of nfs total OPS."
    ::= { nfsEntry 6 }

nfsReadOPS OBJECT-TYPE
    SYNTAX      Counter64
    MAX-ACCESS  read-only
    STATUS      current
    DESCRIPTION
        "The number of nfs read OPS."
    ::= { nfsEntry 7 }

nfsWriteOPS OBJECT-TYPE
    SYNTAX      Counter64
    MAX-ACCESS  read-only
    STATUS      current
    DESCRIPTION
        "The number of nfs write OPS."
    ::= { nfsEntry 8 }

nfsConformance OBJECT IDENTIFIER ::= { nfs 2 }
nfsCompliances OBJECT IDENTIFIER ::= { nfsConformance 1 }
nfsGroups 			OBJECT IDENTIFIER ::= { nfsConformance 2 }

nfsCompliance MODULE-COMPLIANCE
    STATUS  current
    DESCRIPTION
            "The compliance statement for nfs entities which
            implement the SYNOLOGY NFS MIB."
    MODULE  -- this module
        MANDATORY-GROUPS { nfsGroup }

    ::= { nfsCompliances 1 }

nfsGroup OBJECT-GROUP
    OBJECTS { nfsName,
              nfsTotalMaxLatency,
              nfsReadMaxLatency,
              nfsWriteMaxLatency,
              nfsTotalOPS,
              nfsReadOPS,
              nfsWriteOPS}
    STATUS  current
    DESCRIPTION
            "A collection of objects providing basic information
             of an synology nfs entity."
    ::= { nfsGroups 1 }


END
