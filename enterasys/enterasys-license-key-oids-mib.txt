ENTERASYS-LICENSE-KEY-OIDS-MIB DEFINITIONS ::= BEGIN

--  enterasys-license-key-oids-mib.txt
--
--  Part Number:
--
--

--  This module provides authoritative definitions for Extreme
--  Networks' licensable feature OIDs.
--
--  This module will be extended, as needed.

--  Extreme Networks reserves the right to make changes in
--  specification and other information contained in this document
--  without prior notice.  The reader should consult Extreme
--  Networks to determine whether any such changes have been made.
--
--  In no event shall Extreme Networks be liable for any incidental,
--  indirect, special, or consequential damages whatsoever (including
--  but not limited to lost profits) arising out of or related to this
--  document or the information contained in it, even if Extreme
--  Networks has been advised of, known, or should have known, the
--  possibility of such damages.
--
--  Extreme Networks grants vendors, end-users, and other interested
--  parties a non-exclusive license to use this Specification in connection
--  with the management of Extreme products.

--  Copyright March, (2004-2015) Extreme Networks, Inc.

IMPORTS
    MODULE-IDENTITY, OBJECT-IDENTITY
        FROM SNMPv2-SMI
    etsysOidOtherLicenseKeyId
        FROM ENTERASYS-OIDS-MIB
    etsysModules
        FROM ENTERASYS-MIB-NAMES;


etsysLicenseKeyOidsMIB MODULE-IDENTITY
    LAST-UPDATED "201503121610Z"  -- Thu Mar 12 16:10 UTC 2015
    ORGANIZATION "Extreme Networks"
    CONTACT-INFO
        "Postal:  Extreme Networks, Inc.
                  145 Rio Robles
                  San Jose, CA 95134 USA

         Phone:   +1 408 579-2800
         E-mail:  support@extremenetworks.com
         WWW:     http://www.extremenetworks.com"

    DESCRIPTION
        "This MIB module defines a portion of the SNMP enterprise
         MIBs under Enterasys Networks' enterprise OID pertaining to
         OIDs for licensable features on Extreme Networks' 
         devices.  The OIDs contained in this module are intended to
         be returned by the etsysLicenseKeyIdentifier of the
         ENTERASYS-LICENSE-KEY-MIB."

    REVISION    "201503121610Z"  -- Thu Mar 12 16:10 UTC 2015
    DESCRIPTION "Added a OIDs for MACSEC on S-Series and 7100 
                 series products."

    REVISION    "201408071311Z"  -- Thu Aug  7 13:11 UTC 2014
    DESCRIPTION "Updated the CONTACT-INFO clause. Added OIDs for
                 S1 User Capacity and SSA/Purview Appliance Flow
                 Capacity."

    REVISION    "201310071246Z"  -- Mon Oct  7 12:46 UTC 2013
    DESCRIPTION "Added an OID for 7100G Series Advanced Routing."
    
    REVISION    "201307311352Z"  -- Wed Jul 31 13:52 UTC 2013
    DESCRIPTION "Updated the CONTACT-INFO clause. Added OIDs for
                 K Series Chassis Virtual Switch Bonding and
                 7100K Series Advanced Routing."
 
    REVISION    "201201271711Z"  -- Fri Jan 27 17:11 UTC 2012
    DESCRIPTION "Added an OID for the S Series S1 Chassis 
                 Virtual Switch Bonding."

    REVISION    "201108191253Z"  -- Fri Aug 19 12:53 UTC 2011
    DESCRIPTION "Added OIDs for the S Series Multi-slot Virtual Switch
                 Bonding and S Series Standalone Virtual Switch
                 Bonding."

    REVISION    "201103081511Z"  -- Tue Mar  8 15:11 UTC 2011
    DESCRIPTION "Added OIDs for the K Series per port user capacity
                 license and S Series standalone user capacity license."

    REVISION    "201011181409Z"  -- Thu Nov 18 14:09 UTC 2010
    DESCRIPTION "Added an OID for the K Series routing feature."

    REVISION    "200908052014Z"  -- Wed Aug  5 20:14 UTC 2009
    DESCRIPTION "Added OIDs for the S Series licensable features."

    REVISION    "200802261351Z"  -- Tue Feb 26 13:51 UTC 2008
    DESCRIPTION "Added an OID for the G Series Routing feature."

    REVISION    "200801181556Z"  -- Fri Jan 18 15:56 UTC 2008
    DESCRIPTION "Added an OID for the D Series Policy feature."

    REVISION    "200706111424Z"  -- Mon Jun 11 14:24 UTC 2007
    DESCRIPTION "Added an OID for the hardware based N-EOS-L3-DIAMOND 
                 license key."

    REVISION    "200611131529Z"  -- Mon Nov 13 15:29 UTC 2006
    DESCRIPTION "Added an OID for the N-EOS-GPOLICY license key."

    REVISION    "200609051737Z"  -- Tue Sep  5 17:37 UTC 2006
    DESCRIPTION "Added an OID for the C Series IPV6 Routing feature."

    REVISION    "200608151956Z"  -- Tue Aug 15 19:56 UTC 2006
    DESCRIPTION "Added OIDs for the B Series Routing feature and
                 the C Series Advanced Routing feature."
    
    REVISION    "200512132112Z"  -- Tue Dec 13 21:12 GMT 2005
    DESCRIPTION "Added an OID for the B Series Policy feature."

    REVISION    "200411031701Z"  -- Wed Nov  3 17:01 GMT 2004
    DESCRIPTION "Added an OID for the N-EOS-PPC license key."

    REVISION    "200408241329Z"  -- Tue Aug 24 13:29 GMT 2004
    DESCRIPTION "The initial version of this MIB module."
    ::= { etsysModules 56 }

--  This part of the OID tree is used for licensable feature OID 
--  assignments for the various N-Series platforms.

etsysLicKeyIdNSeries OBJECT IDENTIFIER ::= { etsysOidOtherLicenseKeyId 1 }

etsysLicKeyIdNL3AdvancedFeature OBJECT-IDENTITY
    STATUS      current
--  Date        "200408241329Z"  - Tue Aug 24 13:29 GMT 2004
    DESCRIPTION
        "N-Series Layer 3 Advanced Features license.  This is the
         N-EOS-L3 license key."
    ::= { etsysLicKeyIdNSeries 1 }

etsysLicKeyIdNGoldRedundancy OBJECT-IDENTITY
    STATUS      current
--  Date        "200408241329Z"  - Tue Aug 24 13:29 GMT 2004
    DESCRIPTION
        "N-Series DFE-Gold Master Redundancy license.  This is the
         N-EOS-RED license key."
    ::= { etsysLicKeyIdNSeries 2 }

etsysLicKeyIdNPlatinumHighCapacity OBJECT-IDENTITY
    STATUS      current
--  Date        "200408241329Z"  - Tue Aug 24 13:29 GMT 2004
    DESCRIPTION
        "N-Series DFE-Platinum User Capacity license.  This is 
         the N-EOS-PUC license key."
    ::= { etsysLicKeyIdNSeries 3 }

etsysLicKeyIdNPlatinumPortCapacity OBJECT-IDENTITY
    STATUS      current
--  Date        "200411031701Z"  - Wed Nov  3 17:01 GMT 2004
    DESCRIPTION
        "N-Series DFE-Platinum Port Capacity license.  This is 
         the N-EOS-PPC license key."
    ::= { etsysLicKeyIdNSeries 4 }

etsysLicKeyIdNGoldPolicy OBJECT-IDENTITY
    STATUS      current
--  Date        "200611131529Z"  - Mon Nov 13 15:29 UTC 2006
    DESCRIPTION
        "N-Series DFE-Gold Policy license.  This is the N-EOS-GPOLICY 
         license key."
    ::= { etsysLicKeyIdNSeries 5 }

etsysLicKeyIdNL3DiamondFeature OBJECT-IDENTITY
    STATUS      current
--  Date        "200706111424Z"  - Mon Jun 11 14:24 UTC 2007
--  Date        "200906031443Z"  - Wed Jun  3 14:43 UTC 2009
    DESCRIPTION
        "N-Series Layer 3 hardware based Advanced Features 
         license.  This is the N-EOS-L3-HW license key."
    ::= { etsysLicKeyIdNSeries 6 }

--  This part of the OID tree is used for licensable feature OID 
--  assignments for the various C-Series platforms.
etsysLicKeyIdCSeries OBJECT IDENTIFIER ::= { etsysOidOtherLicenseKeyId 2 }

etsysLicKeyIdCAdvancedRouting OBJECT-IDENTITY
    STATUS      current
--  Date        "200608151956Z"  - Tue Aug 15 19:56 UTC 2006
    DESCRIPTION
        "C-Series Advanced Routing License."
    ::= { etsysLicKeyIdCSeries 1 }

etsysLicKeyIdC3IpV6Routing OBJECT-IDENTITY
    STATUS      current
--  Date        "200609051737Z"  - Tue Sep  5 17:37 UTC 2006
    DESCRIPTION
        "C3 IP Version 6 Routing License."
    ::= { etsysLicKeyIdCSeries 2 }

--  This part of the OID tree is used for licensable feature OID 
--  assignments for the various B-Series platforms.
etsysLicKeyIdBSeries OBJECT IDENTIFIER ::= { etsysOidOtherLicenseKeyId 3 }

etsysLicKeyIdBPolicy OBJECT-IDENTITY
    STATUS      current
--  Date        "200512132113Z"  - Tue Dec 13 21:13 UTC 2005
    DESCRIPTION
        "B-Series Policy License."
    ::= { etsysLicKeyIdBSeries 1 }

etsysLicKeyIdBRouting OBJECT-IDENTITY
    STATUS      current
--  Date        "200608151956Z"  - Tue Aug 15 19:56 UTC 2006
    DESCRIPTION
        "B-Series Routing License."
    ::= { etsysLicKeyIdBSeries 2 }

--  This part of the OID tree is used for licensable feature OID 
--  assignments for the various D-Series platforms.
etsysLicKeyIdDSeries OBJECT IDENTIFIER ::= { etsysOidOtherLicenseKeyId 4 }

etsysLicKeyIdDPolicy OBJECT-IDENTITY
    STATUS      current
--  Date        "200801181556Z"  - Fri Jan 18 15:56 UTC 2008
    DESCRIPTION
        "D-Series Policy License."
    ::= { etsysLicKeyIdDSeries 1 }

--  This part of the OID tree is used for licensable feature OID 
--  assignments for the various G-Series platforms.
etsysLicKeyIdGSeries OBJECT IDENTIFIER ::= { etsysOidOtherLicenseKeyId 5 }

etsysLicKeyIdGRouting OBJECT-IDENTITY
    STATUS      current
--  Date        "200802261351Z"  - Tue Feb 26 13:51 UTC 2008
    DESCRIPTION
        "G-Series Routing License."
    ::= { etsysLicKeyIdGSeries 1 }

--  This part of the OID tree is used for licensable feature OID 
--  assignments for the various S-Series platforms.
etsysLicKeyIdSSeries OBJECT IDENTIFIER ::= { etsysOidOtherLicenseKeyId 6 }

etsysLicKeyIdSxEOSxPPC OBJECT-IDENTITY
    STATUS      current
--  Name        "S-EOS-PPC"
--  Date        "200908052014Z"  - Wed Aug  5 20:14 UTC 2009
    DESCRIPTION
        "S-Series Per Port User Capacity License Upgrade for use on 
         S-Series Access Modules."
    ::= { etsysLicKeyIdSSeries 1 }

etsysLicKeyIdSxEOSxL3xACCESS OBJECT-IDENTITY
    STATUS      current
--  Name        "S-EOS-L3-ACCESS"
--  Date        "200908052014Z"  - Wed Aug  5 20:14 UTC 2009
    DESCRIPTION
        "S-Series Advanced Routing License for use on S-Series Access 
         Modules."
    ::= { etsysLicKeyIdSSeries 2 }

etsysLicKeyIdSxEOSxL3xCORE OBJECT-IDENTITY
    STATUS      current
--  Name        "S-EOS-L3-CORE"
--  Date        "200908052014Z"  - Wed Aug  5 20:14 UTC 2009
    DESCRIPTION
        "S-Series Advanced Routing License for use on S-Series 
         Distribution/Core Modules."
    ::= { etsysLicKeyIdSSeries 3 }

etsysLicKeyIdSSAxEOSx2XUSER OBJECT-IDENTITY
    STATUS      current
--  Name        "SSA-EOS-2XUSER"
--  Date        "201103081511Z"  - Tue Mar  8 15:11 UTC 2011
    DESCRIPTION
        "S-Series Standalone System User Capacity License Upgrade for use
         on S-Series Standalone S150 and S155 Class devices."
    ::= { etsysLicKeyIdSSeries 4 }

etsysLicKeyIdSxEOSxVSB OBJECT-IDENTITY
    STATUS      current
--  Name        "S-EOS-VSB"
--  Date        "201108191253Z"  - Fri Aug 19 12:53 UTC 2011
    DESCRIPTION
        "S-Series Multi-slot Virtual Switch Bonding License for use 
         on S-Series S130/S150 Class Modules."
    ::= { etsysLicKeyIdSSeries 5 }

etsysLicKeyIdSSAxEOSxVSB OBJECT-IDENTITY
    STATUS      current
--  Name        "SSA-EOS-VSB"
--  Date        "201108191253Z"  - Fri Aug 19 12:53 UTC 2011
    DESCRIPTION
        "S-Series Standalone Virtual Switch Bonding License for use 
         on S-Series Standalone (SSA) devices."
    ::= { etsysLicKeyIdSSeries 6 }

etsysLicKeyIdS1xEOSxVSB OBJECT-IDENTITY
    STATUS      current
--  Name        "S1-EOS-VSB"
--  Date        "201201271711Z"  - Fri Jan 27 17:11 UTC 2012
    DESCRIPTION
        "S-Series S1 Chassis Virtual Switch Bonding License for use 
         on S-Series S130/S150 Class Modules."
    ::= { etsysLicKeyIdSSeries 7 }

etsysLicKeyIdS1xEOSxUSER OBJECT-IDENTITY
    STATUS      current
--  Name        "S1-EOS-USER"
--  Date        "201408071311Z"  - Thu Aug  7 13:11 UTC 2014
    DESCRIPTION
        "S-Series S1 Chassis 8000 User Capacity License on S-Series 
         Modules."
    ::= { etsysLicKeyIdSSeries 8 }

etsysLicKeyIdSxEOSxFLOW OBJECT-IDENTITY
    STATUS      current
--  Name        "S-EOS-FLOW"
--  Date        "201408071311Z"  - Thu Aug  7 13:11 UTC 2014
    DESCRIPTION
        "S-Series Flow Capacity License for SSA and Purview appliance SFP+
         ports."
    ::= { etsysLicKeyIdSSeries 9 }

etsysLicKeyIdSxEOSxMACSEC OBJECT-IDENTITY
    STATUS      current
--  Name        "S-EOS-MACSEC"
--  Date        "201503101416Z"  - Tue Mar 10 14:16 UTC 2015
    DESCRIPTION
        "S-Series MACSEC License for Gigabit Ethernet modules and their
         uplinks."
    ::= { etsysLicKeyIdSSeries 10 }

etsysLicKeyIdSxEOSxKMACSEC OBJECT-IDENTITY
    STATUS      current
--  Name        "S-EOS-KMACSEC"
--  Date        "201503101416Z"  - Tue Mar 10 14:16 UTC 2015
    DESCRIPTION
        "S-Series MACSEC License for 10-Gigabit Ethernet modules."
    ::= { etsysLicKeyIdSSeries 11 }

--  This part of the OID tree is used for licensable feature OID 
--  assignments for the various K-Series platforms.
etsysLicKeyIdKSeries OBJECT IDENTIFIER ::= { etsysOidOtherLicenseKeyId 7 }

etsysLicKeyIdKxEOSxL3 OBJECT-IDENTITY
    STATUS      current
--  Name        "K-EOS-L3"
--  Date        "201011181409Z"  - Thu Nov 18 14:09 UTC 2010
    DESCRIPTION
        "K-Series Advanced Routing License for use on K-Series Modules."
    ::= { etsysLicKeyIdKSeries 1 }

etsysLicKeyIdKxEOSxPPC OBJECT-IDENTITY
    STATUS      current
--  Name        "K-EOS-PPC"
--  Date        "201103081511Z"  - Tue Mar  8 15:11 UTC 2011
    DESCRIPTION
        "K-Series Per Port User Capacity License Upgrade for use on 
         K-Series Modules."
    ::= { etsysLicKeyIdKSeries 2 }

etsysLicKeyIdKxEOSxVSB OBJECT-IDENTITY
    STATUS      current
--  Name        "K-EOS-VSB"
--  Date        "201307311352Z"  - Wed Jul 31 13:52 UTC 2013
    DESCRIPTION
        "K-Series Chassis Virtual Switch Bonding License for use on 
         K6 and K10 chassis."
    ::= { etsysLicKeyIdKSeries 3 }

--  This part of the OID tree is used for licensable feature OID
--  assignments for the various 7100 Series platforms.
etsysLicKeyId7100Series OBJECT IDENTIFIER 
                              ::= { etsysOidOtherLicenseKeyId 8 }

etsysLicKeyId71AxEOSxADVL3 OBJECT-IDENTITY
    STATUS      current
--  Name        "71A-EOS-ADVL3"
--  Date        "201307311352Z"  - Wed Jul 31 13:52 UTC 2013
    DESCRIPTION
        "7100 Series Advanced Routing License for use on 7100K Series 
         devices."
    ::= { etsysLicKeyId7100Series 1 }

etsysLicKeyId71AxEOSxGxADVL3 OBJECT-IDENTITY
    STATUS      current
--  Name        "71A-EOS-G-ADVL3"
--  Date        "201310071246Z"  - Mon Oct  7 12:46 UTC 2013
    DESCRIPTION
        "7100 Series Advanced Routing License for use on 7100G Series 
         devices."
    ::= { etsysLicKeyId7100Series 2 }

etsysLicKeyId71AxEOSxGMACSEC OBJECT-IDENTITY
    STATUS      current
--  Name        "71A-EOS-GMACSEC"
--  Date        "201503101416Z"  - Tue Mar 10 14:16 UTC 2015
    DESCRIPTION
        "7100 Series MACSEC License for use on 7100G Series devices."
    ::= { etsysLicKeyId7100Series 3 }

etsysLicKeyId71AxEOSxKMACSEC OBJECT-IDENTITY
    STATUS      current
--  Name        "71A-EOS-KMACSEC"
--  Date        "201503101416Z"  - Tue Mar 10 14:16 UTC 2015
    DESCRIPTION
        "7100 Series MACSEC License for use on 7100K Series devices."
    ::= { etsysLicKeyId7100Series 4 }

END
