FORCEPOINT-SMI-MOCKUP DEFINITIONS ::= BEGIN

IMPORTS
    MODULE-IDENTITY, OBJECT-IDENTITY, enterprises
        FROM SNMPv2-SMI;


forcepoint MODULE-IDENTITY
    LAST-UPDATED "202503080000Z"
    ORGANIZATION "netdisco mockup for forcepoint"
    CONTACT-INFO
               "  netisco project
               
                  the internet"
         
    DESCRIPTION
            "no main module found, quick mockup"
    REVISION        "202503080000Z"
    DESCRIPTION
            "first"
    ::= { enterprises 47565 }

ngfw OBJECT-IDENTITY
    STATUS current
    DESCRIPTION
            "root for ngfw stuff"
    ::= { forcepoint 1 }

END
