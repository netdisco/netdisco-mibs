TIMETRA-CHASSIS-INTERCONNECT-MIB DEFINITIONS ::= BEGIN

IMPORTS
    MODULE-IDENTITY, OBJECT-TYPE, NOTIFICATION-TYPE, Unsigned32, Integer32,
    Counter32, Gauge32, IpAddress
    FROM SNMPv2-SMI

    MODULE-COMPLIANCE, OBJECT-GROUP, NOTIFICATION-GROUP
    FROM SNMPv2-CONF

    TEXTUAL-CONVENTION, RowStatus, TruthValue, TimeStamp
    FROM SNMPv2-TC

    timetraSRMIBModules, tmnxSRObjs, tmnxSRNotifyPrefix, tmnxSRConfs
    FROM TIMETRA-GLOBAL-MIB

    tmnxChassisIndex, tmnxCpmCardSlotNum, tmnxChassisNotifyCpmCardSlotNum,
    tmnxChassisNotifyFabricSlotNum, tmnxFabricSlotNum, tmnxHwClass,
    TmnxSlotNum
    FROM TIMETRA-CHASSIS-MIB

    tmnxDDMFailedObject, tmnxDDMLaneIdOrModule, TmnxSFFStatus
    FROM TIMETRA-PORT-MIB
    ;

timetraChassisInterconMIBModule MODULE-IDENTITY
        LAST-UPDATED "201310310000Z"
        ORGANIZATION "Nokia"
        CONTACT-INFO
            "Nokia SROS Support
             Web: http://www.nokia.com"
        DESCRIPTION

        "This document is the SNMP MIB module for the Nokia SROS
        implementation for managing the components used in connecting
        chassis together.

        Copyright 2013-2016 Nokia. All rights reserved.
        Reproduction of this document is authorized on the condition that
        the foregoing copyright notice is included.

        This SNMP MIB module (Specification) embodies Nokia's
        proprietary intellectual property.  Nokia retains all
        title and ownership in the Specification, including any
        revisions.

        Nokia grants all interested parties a non-exclusive
        license to use and distribute an unmodified copy of this
        Specification in connection with management of Nokia products,
        and without fee, provided this copyright notice and license
        appear on all copies.

        This Specification is supplied `as is', and Nokia makes
        no warranty, either express or implied, as to the use,
        operation, condition, or performance of the Specification."

--
-- Revision History
--
        REVISION        "201310310000Z"
        DESCRIPTION     "Rev 0.1               31 Oct 2013 00:00
                         Initial version of the TIMETRA-CHASSIS-INTERCONNECT-MIB."

        ::= { timetraSRMIBModules 94 }

tmnxChassisInterconObjs         OBJECT IDENTIFIER ::= { tmnxSRObjs         94 }
tmnxChassisInterconConformance  OBJECT IDENTIFIER ::= { tmnxSRConfs        94 }
tmnxChassisInterconNotifyPrefix OBJECT IDENTIFIER ::= { tmnxSRNotifyPrefix 94 }

-- Notification Groups in the Nokia CHASSIS-INTERCONNECT MIB Module
tmnxChassisInterconNotification OBJECT IDENTIFIER ::= { tmnxChassisInterconNotifyPrefix 0 }

-- Compliance Groups in the Nokia CHASSIS-INTERCONNECT MIB Module
tmnxChassisInterconCompliances  OBJECT IDENTIFIER ::= { tmnxChassisInterconConformance 1 }
tmnxChassisInterconGroups       OBJECT IDENTIFIER ::= { tmnxChassisInterconConformance 2 }

--%%%%%%%%%%%%%%%%%%%%%%%%%%%%%%%%%%%%%%%%%%%%%%%%%%%%%%%%%%%%%%%%%%%%%%%%%%%
--
--  Textual Conventions
--
TmnxIcPortState ::= TEXTUAL-CONVENTION
    STATUS      current
    DESCRIPTION
        "TmnxIcPortState specifies the state of a given interconnect port.

         The possible values are:
             up                (1) - The port is operational
             invalidConnection (2) - The point-to-point link layer is correctly
                                     established but the logical layer has
                                     detected that the port is connected to the
                                     wrong far-end port
             noLink            (3) - The point-to-point link layer could not
                                     be fully established
             indeterminate     (4) - The system cannot determine the state of
                                     the port. Examples of when this value
                                     is used include:
                                     a) the state of a CPM or SFM IcPort in
                                     the extension chassis of an XRS-40 system
                                     when control communications with the
                                     extension chassis is down
                                     b) the state of a CPM or SFM IcPort when
                                     the parent card is not physically present
                                     or is initializing
             unsupportedSff    (5) - the SFF module part number is not a
                                     supported number for the system"
    SYNTAX      INTEGER {
                    up                (1),
                    invalidConnection (2),
                    noLink            (3),
                    indeterminate     (4),
                    unsupportedSff    (5)
                }

--%%%%%%%%%%%%%%%%%%%%%%%%%%%%%%%%%%%%%%%%%%%%%%%%%%%%%%%%%%%%%%%%%%%%%%%%%%%
--
--  CPM Interconnect Port Information
--
tmnxIcPortObjs  OBJECT IDENTIFIER ::= { tmnxChassisInterconObjs 1 }

tmnxCpmIcPortTable              OBJECT-TYPE
    SYNTAX      SEQUENCE OF TmnxCpmIcPortEntry
    MAX-ACCESS  not-accessible
    STATUS      current
    DESCRIPTION
        "The value of tmnxCpmIcPortTable represents CPM interconnect
         port information.
         
         A Control Plane Module (CPM) interconnect port (CPM IcPort) is a
         port on a CPM which provides the capability for two (or more) chassis
         to be connected and communicate with each other."
    ::= { tmnxIcPortObjs 1 }

tmnxCpmIcPortEntry              OBJECT-TYPE
    SYNTAX       TmnxCpmIcPortEntry
    MAX-ACCESS   not-accessible
    STATUS       current
    DESCRIPTION     
        "Each tmnxCpmIcPortEntry consists of the specific information
         pertaining to a CPM interconnect port for a particular card on a
         given chassis."
    INDEX { tmnxChassisIndex, tmnxCpmCardSlotNum, tmnxCpmIcPortNum }
    ::= { tmnxCpmIcPortTable 1 }

TmnxCpmIcPortEntry ::=
    SEQUENCE {
        tmnxCpmIcPortNum                Unsigned32,
        tmnxCpmIcPortOperState          TmnxIcPortState,
        tmnxCpmIcPortSFFEquipped        TruthValue,
        tmnxCpmIcPortSFFStatus          TmnxSFFStatus
    }

tmnxCpmIcPortNum                OBJECT-TYPE
    SYNTAX      Unsigned32 (1..2)
    MAX-ACCESS  not-accessible
    STATUS      current
    DESCRIPTION
        "The value of tmnxCpmIcPortNum specifies a CPM interconnect port
         within a particular card on a given chassis."
    ::= { tmnxCpmIcPortEntry 1 }

tmnxCpmIcPortOperState          OBJECT-TYPE
    SYNTAX      TmnxIcPortState
    MAX-ACCESS  read-only
    STATUS      current
    DESCRIPTION
        "The value of tmnxCpmIcPortOperState indicates the operational state
         for a given CPM interconnect port."
    ::= { tmnxCpmIcPortEntry 2 }

tmnxCpmIcPortSFFEquipped        OBJECT-TYPE
    SYNTAX      TruthValue
    MAX-ACCESS  read-only
    STATUS      current
    DESCRIPTION
        "The value of tmnxCpmIcPortSFFEquipped indicates whether or not a small
         form factor (SFF) pluggable optical module (e.g. QSFP) is inserted
         into the CPM interconnect port."
    ::= { tmnxCpmIcPortEntry 3 }

tmnxCpmIcPortSFFStatus          OBJECT-TYPE
    SYNTAX      TmnxSFFStatus
    MAX-ACCESS  read-only
    STATUS      current
    DESCRIPTION
        "The value of tmnxCpmIcPortSFFStatus indicates the operational status
         of the inserted SFF. If tmnxCpmIcPortSFFEquipped is false, the
         tmnxCpmIcPortSFFStatus will be 'not-equipped (0)', otherwise
         'operational (1)' if no failure is detected."
    ::= { tmnxCpmIcPortEntry 4 }

--%%%%%%%%%%%%%%%%%%%%%%%%%%%%%%%%%%%%%%%%%%%%%%%%%%%%%%%%%%%%%%%%%%%%%%%%%%%
--
--  SFM Interconnect Port Information
--
tmnxSfmIcPortTable              OBJECT-TYPE
    SYNTAX      SEQUENCE OF TmnxSfmIcPortEntry
    MAX-ACCESS  not-accessible
    STATUS      current
    DESCRIPTION
        "The value of tmnxSfmIcPortTable represents SFM interconnect
         port information.

         A Switch Fabric Module (SFM) interconnect port (SFM IcPort) is a
         port on an SFM which provides the capability for two (or more) chassis
         to be connected and communicate with each other."
    ::= { tmnxIcPortObjs 2 }

tmnxSfmIcPortEntry              OBJECT-TYPE
    SYNTAX       TmnxSfmIcPortEntry
    MAX-ACCESS   not-accessible
    STATUS       current
    DESCRIPTION     
        "Each tmnxSfmIcPortEntry consists of the specific information
         pertaining to an SFM interconnect port for a particular card on a
         given chassis."
    INDEX { tmnxChassisIndex, tmnxFabricSlotNum, tmnxSfmIcPortNum }
    ::= { tmnxSfmIcPortTable 1 }

TmnxSfmIcPortEntry ::=
    SEQUENCE {
        tmnxSfmIcPortNum                Unsigned32,
        tmnxSfmIcPortOperState          TmnxIcPortState,
        tmnxSfmIcPortSFFEquipped        TruthValue,
        tmnxSfmIcPortSFFStatus          TmnxSFFStatus,
        tmnxSfmIcPortDegradeState       INTEGER,
        tmnxSfmIcPortMisconSfm          Unsigned32,
        tmnxSfmIcPortMisconSfmIcPort    Unsigned32
    }

tmnxSfmIcPortNum                OBJECT-TYPE
    SYNTAX      Unsigned32 (1..14)
    MAX-ACCESS  not-accessible
    STATUS      current
    DESCRIPTION
        "The value of tmnxSfmIcPortNum specifies an SFM interconnect port
         within a particular card on a given chassis."
    ::= { tmnxSfmIcPortEntry 1 }

tmnxSfmIcPortOperState          OBJECT-TYPE
    SYNTAX      TmnxIcPortState
    MAX-ACCESS  read-only
    STATUS      current
    DESCRIPTION
        "The value of tmnxSfmIcPortOperState indicates the operational state
         for a given SFM interconnect port."
    ::= { tmnxSfmIcPortEntry 2 }

tmnxSfmIcPortSFFEquipped        OBJECT-TYPE
    SYNTAX      TruthValue
    MAX-ACCESS  read-only
    STATUS      current
    DESCRIPTION
        "The value of tmnxSfmIcPortSFFEquipped indicates whether or not a small
         form factor (SFF) pluggable optical module (e.g. CXP) is inserted
         into the SFM interconnect port."
    ::= { tmnxSfmIcPortEntry 3 }

tmnxSfmIcPortSFFStatus          OBJECT-TYPE
    SYNTAX      TmnxSFFStatus
    MAX-ACCESS  read-only
    STATUS      current
    DESCRIPTION
        "The value of tmnxSfmIcPortSFFStatus indicates the operational status
         of the inserted SFF. If tmnxSfmIcPortSFFEquipped is false, the
         tmnxSfmIcPortSFFStatus will be 'not-equipped (0)', otherwise
         'operational (1)' if no failure is detected."
    ::= { tmnxSfmIcPortEntry 4 }

tmnxSfmIcPortDegradeState       OBJECT-TYPE
    SYNTAX      INTEGER {
                    none     (1),
                    degraded (2)
                }
    MAX-ACCESS  read-only
    STATUS      current
    DESCRIPTION
        "The value of tmnxSfmIcPortDegradeState indicates degradation of the
         switch fabric that is carried over a particular SFM interconnect port.

         The possible values are:
             none     (1) - The port is not considered as degraded.
             degraded (2) - There is a degradation of the switch fabric that is
                            carried over the port. The port can still carry
                            some traffic but not at the full capacity of the
                            port."
::= { tmnxSfmIcPortEntry 5 }

tmnxSfmIcPortMisconSfm          OBJECT-TYPE
    SYNTAX      Unsigned32
    MAX-ACCESS  read-only
    STATUS      current
    DESCRIPTION
        "The value of tmnxSfmIcPortMisconSfm indicates the SFM that contains
         the SFM IcPort that is incorrectly connected to this SFM IcPort.

         If the value of tmnxSfmIcPortOperState is not 'invalid-connection (2)',
         the value of tmnxSfmIcPortMisconSfm is '0'."
::= { tmnxSfmIcPortEntry 6 }

tmnxSfmIcPortMisconSfmIcPort    OBJECT-TYPE
    SYNTAX      Unsigned32
    MAX-ACCESS  read-only
    STATUS      current
    DESCRIPTION
        "The value of tmnxSfmIcPortMisconSfmIcPort indicates the SFM IcPort that
         this SFM IcPort is incorrectly connected to.

         If the value of tmnxSfmIcPortOperState is not 'invalid-connection (2)',
         the value of tmnxSfmIcPortMisconSfmIcPort is '0'."
::= { tmnxSfmIcPortEntry 7 }

--%%%%%%%%%%%%%%%%%%%%%%%%%%%%%%%%%%%%%%%%%%%%%%%%%%%%%%%%%%%%%%%%%%%%%%%%%%%
--
--  Notification Objects
--
tmnxChassIcNotifObjs OBJECT IDENTIFIER ::= { tmnxChassisInterconObjs 2 }

tmnxNotifyIcPortNum             OBJECT-TYPE
    SYNTAX      Unsigned32
    MAX-ACCESS  accessible-for-notify
    STATUS      current
    DESCRIPTION
        "The unique value of tmnxNotifyIcPortNum identifies the interconnect
         port number within a chassis in the system."
    ::= { tmnxChassIcNotifObjs 1 }

--%%%%%%%%%%%%%%%%%%%%%%%%%%%%%%%%%%%%%%%%%%%%%%%%%%%%%%%%%%%%%%%%%%%%%%%%%%%
--
--  Notifications
--
tmnxInterChassisNotifications OBJECT IDENTIFIER ::= { tmnxChassisInterconNotification 1 }

tmnxInterChassisCommsDown       NOTIFICATION-TYPE
    OBJECTS {
        tmnxHwClass
    }
    STATUS  current
    DESCRIPTION
        "[CAUSE] The tmnxInterChassisCommsDown alarm is generated when
         the active CPM cannot reach the far-end chassis.

         [EFFECT] The resources on the far-end chassis are not available. This
         event for the far-end chassis means that the CPM, SFM, and XCM cards
         in the far-end chassis will reboot and remain operationally down until
         communications are re-established.

         [RECOVERY] Ensure that all CPM interconnect ports in the system are
         properly cabled together with working cables."
    ::= { tmnxInterChassisNotifications 1 }

tmnxInterChassisCommsUp         NOTIFICATION-TYPE
    OBJECTS {
        tmnxHwClass
    }
    STATUS  current
    DESCRIPTION
        "[CAUSE] The tmnxInterChassisCommsUp notification is generated when
         the control communications are re-established between the active
         CPM and the far-end chassis.

         [EFFECT] The resources on the far-end chassis are now available. This
         event for the far-end chassis means that the CPM, SFM and XCM cards in
         the far-end chassis will start the process of coming back into
         service."
    ::= { tmnxInterChassisNotifications 2 }

tmnxCpmIcPortNotifications OBJECT IDENTIFIER ::= { tmnxChassisInterconNotification 2 }

tmnxCpmIcPortDown               NOTIFICATION-TYPE
    OBJECTS {
        tmnxHwClass,
        tmnxCpmIcPortOperState
    }
    STATUS  current
    DESCRIPTION
        "[CAUSE] The tmnxCpmIcPortDown alarm is generated when the CPM
         interconnect port is not operational. The reason may be a cable
         connected incorrectly, a disconnected cable, a faulty cable, or a
         misbehaving CPM interconnect port or card.

         [EFFECT] At least one of the control plane paths used for
         inter-chassis CPM communication is not operational. Other paths may
         be available.

         [RECOVERY] A manual verification and testing of each CPM
         interconnect port is required to ensure fully functional operation.
         Physical replacement of cabling may be required."
    ::= { tmnxCpmIcPortNotifications 1 }

tmnxCpmIcPortUp                 NOTIFICATION-TYPE
    OBJECTS {
        tmnxHwClass,
        tmnxCpmIcPortOperState
    }
    STATUS  current
    DESCRIPTION
        "[CAUSE] The tmnxCpmIcPortUp notification is generated when the CPM
         interconnect port is operational again.

         [EFFECT] A control plane communication path between CPM cards in the
         different chassis have been established."
    ::= { tmnxCpmIcPortNotifications 2 }

tmnxCpmIcPortSFFInserted        NOTIFICATION-TYPE
    OBJECTS {
        tmnxCpmIcPortSFFEquipped
    }
    STATUS  current
    DESCRIPTION
        "[CAUSE] The tmnxCpmIcPortSFFInserted notification is generated when
         the small form factor (SFF) pluggable optical module (e.g. QSFP) is
         inserted into a CPM interconnect port.

         [EFFECT] This event is for notification only."
    ::= { tmnxCpmIcPortNotifications 3 }

tmnxCpmIcPortSFFRemoved         NOTIFICATION-TYPE
    OBJECTS {
        tmnxCpmIcPortSFFEquipped
    }
    STATUS  current
    DESCRIPTION
        "[CAUSE] The tmnxCpmIcPortSFFRemoved notification is generated when
         the SFF (e.g. QSFP) is removed from the CPM interconnect
         port. Removing an SFF causes both this trap, and also a
         tmnxCpmIcPortDown event.

         [EFFECT] Removing the SFF will cause the CPM interconnect port
         to go down. This port will no longer be able to be used as part of
         the control plane between chassis but other paths may be available.

         [RECOVERY] Insert a working SFF into the port."
    ::= { tmnxCpmIcPortNotifications 4 }

tmnxCpmNoLocalIcPort            NOTIFICATION-TYPE
    OBJECTS {
        tmnxHwClass,
        tmnxChassisNotifyCpmCardSlotNum
    }
    STATUS  current
    DESCRIPTION
        "[CAUSE] The tmnxCpmNoLocalIcPort alarm is generated when the CPM
         cannot reach the other chassis using its local CPM interconnect
         ports.

         [EFFECT] Another control communications path may still be available 
         between the CPM and the other chassis via the mate CPM in the same
         chassis. If that alternative path is not available then complete 
         disruption of control communications to the other chassis will occur
         and the tmnxInterChassisCommsDown alarm is raised. 
         
         A tmnxCpmNoLocalIcPort alarm on the active CPM indicates that a
         further failure of the local CPM interconnect ports on the standby
         CPM will cause complete disruption of control communications to the
         other chassis and the tmnxInterChassisCommsDown alarm is raised. 
         
         A tmnxCpmNoLocalIcPort alarm on the standby CPM indicates that a
         CPM switchover may cause temporary disruption of control 
         communications to the other chassis while the rebooting CPM comes
         back into service.

         [RECOVERY] Ensure that all CPM interconnect ports in the system are
         properly cabled together with working cables."
    ::= { tmnxCpmIcPortNotifications 5 }

tmnxCpmLocalIcPortAvail         NOTIFICATION-TYPE
    OBJECTS {
        tmnxHwClass,
        tmnxChassisNotifyCpmCardSlotNum
    }
    STATUS  current
    DESCRIPTION
        "[CAUSE] The tmnxCpmLocalIcPortAvail notification is generated when
         the CPM re-establishes communication with the other chassis using its
         local CPM interconnect ports.

         [EFFECT] A new control communications path is now available between
         the CPM and the other chassis."
    ::= { tmnxCpmIcPortNotifications 6 }

tmnxCpmIcPortSFFStatusFailure   NOTIFICATION-TYPE
    OBJECTS {
        tmnxCpmIcPortSFFStatus
    }
    STATUS  current
    DESCRIPTION
        "[CAUSE] The tmnxCpmIcPortSFFStatusFailure notification is generated
         when the value of tmnxCpmIcPortSFFStatus results in a value other
         than 'not-equipped (0)', or 'operational (1)'.

         [EFFECT] The SFF device is not operational and the associated CPM
         interconnect port can not be used. The SFF and port will not recover
         without operator intervention.

         [RECOVERY] Remove and re-insert the SFF device. If the problem
         persists then replace the SFF device."
    ::= { tmnxCpmIcPortNotifications 7 }

tmnxCpmIcPortDDMFailure         NOTIFICATION-TYPE
    OBJECTS {
        tmnxChassisNotifyCpmCardSlotNum,
        tmnxNotifyIcPortNum,
        tmnxDDMFailedObject,
        tmnxDDMLaneIdOrModule
    }
    STATUS  current
    DESCRIPTION
        "[CAUSE] The tmnxCpmIcPortDDMFailure notification is generated when
         an SFF in a CPM interconnect port that supports Digital Diagnostic
         Monitoring (DDM) enters a failed state."
    ::= { tmnxCpmIcPortNotifications 8 }

tmnxCpmIcPortDDMClear           NOTIFICATION-TYPE
    OBJECTS {
        tmnxChassisNotifyCpmCardSlotNum,
        tmnxNotifyIcPortNum,
        tmnxDDMFailedObject,
        tmnxDDMLaneIdOrModule
    }
    STATUS  current
    DESCRIPTION
        "[CAUSE] The tmnxCpmIcPortDDMFailure notification is generated when
         an SFF in a CPM interconnect port that supports Digital Diagnostic
         Monitoring (DDM) clears a failed state."
    ::= { tmnxCpmIcPortNotifications 9 }

tmnxSfmIcPortNotifications OBJECT IDENTIFIER ::= { tmnxChassisInterconNotification 3 }

tmnxSfmIcPortDown               NOTIFICATION-TYPE
    OBJECTS {
        tmnxHwClass,
        tmnxSfmIcPortOperState,
        tmnxSfmIcPortMisconSfm,
        tmnxSfmIcPortMisconSfmIcPort
    }
    STATUS  current
    DESCRIPTION
        "[CAUSE] The tmnxSfmIcPortDown alarm is generated when the SFM
         interconnect port is not operational. The reason may be a cable
         connected incorrectly, a disconnected cable, a faulty cable, or a
         misbehaving SFM interconnect port or SFM card.

         [EFFECT] This port can no longer be used as part of the user plane
         fabric between chassis. Other fabric paths may be available resulting
         in no loss of capacity.

         [RECOVERY] A manual verification and testing of each SFM
         interconnect port is required to ensure fully functional
         operation. Physical replacement of cabling may be required."
    ::= { tmnxSfmIcPortNotifications 1 }

tmnxSfmIcPortUp                 NOTIFICATION-TYPE
    OBJECTS {
        tmnxHwClass,
        tmnxSfmIcPortOperState
    }
    STATUS  current
    DESCRIPTION
        "[CAUSE] The tmnxSfmIcPortUp notification is generated when the
         SFM interconnect port is operational again.

         [EFFECT] This port can now be used as part of the user plane fabric
         between chassis."
    ::= { tmnxSfmIcPortNotifications 2 }

tmnxSfmIcPortSFFInserted        NOTIFICATION-TYPE
    OBJECTS {
        tmnxSfmIcPortSFFEquipped
    }
    STATUS  current
    DESCRIPTION
        "[CAUSE] The tmnxSfmIcPortSFFInserted notification is generated when
         the Small Form Factor (SFF) pluggable optical module (e.g. CXP) is
         inserted into an SFM interconnect port.

         [EFFECT] This event is for notification only."
    ::= { tmnxSfmIcPortNotifications 3 }

tmnxSfmIcPortSFFRemoved         NOTIFICATION-TYPE
    OBJECTS {
        tmnxSfmIcPortSFFEquipped
    }
    STATUS  current
    DESCRIPTION
        "[CAUSE] The tmnxSfmIcPortSFFRemoved notification is generated when
         the SFF (e.g. CXP) is removed from the SFM interconnect port.

         [EFFECT] Removing the module will cause the port to go down. This
         port can  no longer be used as part of the user plane fabric between
         chassis. Other fabric paths may be available resulting in no loss of
         capacity.

         [RECOVERY] Insert a working SFF into the SFM interconnect port."
    ::= { tmnxSfmIcPortNotifications 4 }

tmnxSfmIcPortSFFStatusFailure   NOTIFICATION-TYPE
    OBJECTS {
        tmnxSfmIcPortSFFStatus
    }
    STATUS  current
    DESCRIPTION
        "[CAUSE] The tmnxSfmIcPortSFFStatusFailure notification is generated
         when the value of tmnxSfmIcPortSFFStatus results in a value other
         than 'not-equipped (0)', or 'operational (1)'.

         [EFFECT] The SFF device is not operational and the associated SFM
         interconnect port can not be used. The SFF and port will not recover
         without operator intervention.

         [RECOVERY] Remove and re-insert the SFF device. If the problem
         persists then replace the SFF device."
    ::= { tmnxSfmIcPortNotifications 5 }

tmnxSfmIcPortDDMFailure         NOTIFICATION-TYPE
    OBJECTS {
        tmnxChassisNotifyFabricSlotNum,
        tmnxNotifyIcPortNum,
        tmnxDDMFailedObject,
        tmnxDDMLaneIdOrModule
    }
    STATUS  current
    DESCRIPTION
        "[CAUSE] The tmnxSfmIcPortDDMFailure notification is generated when
         an SFF in an SFM interconnect port that supports Digital Diagnostic
         Monitoring (DDM) enters a failed state."
    ::= { tmnxSfmIcPortNotifications 6 }

tmnxSfmIcPortDDMClear           NOTIFICATION-TYPE
    OBJECTS {
        tmnxChassisNotifyFabricSlotNum,
        tmnxNotifyIcPortNum,
        tmnxDDMFailedObject,
        tmnxDDMLaneIdOrModule
    }
    STATUS  current
    DESCRIPTION
        "[CAUSE] The tmnxSfmIcPortDDMFailure notification is generated when
         an SFF in an SFM interconnect port that supports Digital Diagnostic
         Monitoring (DDM) clears a failed state."
    ::= { tmnxSfmIcPortNotifications 7 }

tmnxSfmIcPortDegraded           NOTIFICATION-TYPE
    OBJECTS {
        tmnxSfmIcPortDegradeState
    }
    STATUS  current
    DESCRIPTION
        "[CAUSE] The tmnxSfmIcPortDegraded notification is generated when the 
         system has detected a degradation of the switch fabric that is
         associated with a particular SFM interconnect port. The value of
         tmnxSfmIcPortDegradeState will reflect this condition by having a
         value that is NOT 'none (1)'. If the value of tmnxSfmIcPortDegradeState
         is 'degraded (2)' the SFM interconnect port can still carry some
         traffic but not at the full capacity of the port. The port and
         attached cable are not necessarily the cause of the degradation but are
         a likely cause.

         [EFFECT] Switch fabric capacity on this port is reduced when 
         tmnxSfmIcPortDegradeState is degraded. This may not be causing any
         impact to service because of redundancy in the fabric.

         [RECOVERY] Although it may not be necessary to maintain full service,
         replacing the affected components may restore some fabric capacity."
    ::= { tmnxSfmIcPortNotifications 8 }

tmnxSfmIcPortDegradedClear      NOTIFICATION-TYPE
    OBJECTS {
        tmnxSfmIcPortDegradeState
    }
    STATUS  current
    DESCRIPTION
        "[CAUSE] The tmnxSfmIcPortDegradedClear notification is generated when
         the switch fabric associated with the SFM interconnect port is not
         degraded. This occurs when the value of tmnxSfmIcPortDegradeState is
         'none (1)'."
    ::= { tmnxSfmIcPortNotifications 9 }

--%%%%%%%%%%%%%%%%%%%%%%%%%%%%%%%%%%%%%%%%%%%%%%%%%%%%%%%%%%%%%%%%%%%%%%%%%%%
--
--  Compliance Statements
--
tmnxChassisInterconCompliance   MODULE-COMPLIANCE
    STATUS      current
    DESCRIPTION
         "The compliance statement for the management of chassis interconnect
          capabilities on SROS series systems for release 12.0."
    MODULE -- this module
        MANDATORY-GROUPS {
            tmnxChassIcNotifV12v0Group,
            tmnxChassIcNotifyObjsV12v0Group,
            tmnxCpmIcPortV12v0Group,
            tmnxCpmIcPortNotifV12v0Group,
            tmnxSfmIcPortV12v0Group,
            tmnxSfmIcPortNotifV12v0Group
        }
    ::= { tmnxChassisInterconCompliances 1 }

--%%%%%%%%%%%%%%%%%%%%%%%%%%%%%%%%%%%%%%%%%%%%%%%%%%%%%%%%%%%%%%%%%%%%%%%%%%%
--
--  Group Statements
--
tmnxChassIcV12v0Groups OBJECT IDENTIFIER ::= { tmnxChassisInterconGroups 1 }

tmnxChassIcNotifV12v0Group      NOTIFICATION-GROUP
    NOTIFICATIONS {
        tmnxInterChassisCommsDown,
        tmnxInterChassisCommsUp
    }
    STATUS      current
    DESCRIPTION
        "The group of notifications supporting the interconnect capabilities
         for the chassis on Nokia SROS series systems in release 12.0."
    ::= { tmnxChassIcV12v0Groups 1 }

tmnxChassIcNotifyObjsV12v0Group OBJECT-GROUP
    OBJECTS {
        tmnxNotifyIcPortNum
    }
    STATUS      current
    DESCRIPTION
        "The group of notification-objects supporting the interconnect
         capabilities for the chassis on release 12.0 of Nokia SROS
         series systems."
    ::= { tmnxChassIcV12v0Groups 2 }

tmnxCpmIcPortV12v0Group         OBJECT-GROUP
    OBJECTS {
        tmnxCpmIcPortOperState,
        tmnxCpmIcPortSFFEquipped,
        tmnxCpmIcPortSFFStatus
    }
    STATUS      current
    DESCRIPTION
        "The group of objects supporting the interconnect port capabilities
         for the control plane on Nokia SROS series systems in
         release 12.0."
    ::= { tmnxChassIcV12v0Groups 3 }

tmnxCpmIcPortNotifV12v0Group    NOTIFICATION-GROUP
    NOTIFICATIONS {
        tmnxCpmIcPortDown,
        tmnxCpmIcPortUp,
        tmnxCpmIcPortSFFInserted,
        tmnxCpmIcPortSFFRemoved,
        tmnxCpmNoLocalIcPort,
        tmnxCpmLocalIcPortAvail,
        tmnxCpmIcPortSFFStatusFailure,
        tmnxCpmIcPortDDMFailure,
        tmnxCpmIcPortDDMClear
    }
    STATUS      current
    DESCRIPTION
        "The group of notifications supporting the interconnect port
         capabilities for the control plane on Nokia SROS series
         systems in release 12.0."
    ::= { tmnxChassIcV12v0Groups 4 }

tmnxSfmIcPortV12v0Group         OBJECT-GROUP
    OBJECTS {
        tmnxSfmIcPortOperState,
        tmnxSfmIcPortSFFEquipped,
        tmnxSfmIcPortSFFStatus,
        tmnxSfmIcPortDegradeState,
        tmnxSfmIcPortMisconSfm,
        tmnxSfmIcPortMisconSfmIcPort
    }
    STATUS      current
    DESCRIPTION
        "The group of objects supporting the interconnect port capabilities
         for the switch fabric on Nokia SROS series systems in release
         12.0."
    ::= { tmnxChassIcV12v0Groups 5 }

tmnxSfmIcPortNotifV12v0Group    NOTIFICATION-GROUP
    NOTIFICATIONS {
        tmnxSfmIcPortDown,
        tmnxSfmIcPortUp,
        tmnxSfmIcPortSFFInserted,
        tmnxSfmIcPortSFFRemoved,
        tmnxSfmIcPortSFFStatusFailure,
        tmnxSfmIcPortDDMFailure,
        tmnxSfmIcPortDDMClear,
        tmnxSfmIcPortDegraded,
        tmnxSfmIcPortDegradedClear
    }
    STATUS      current
    DESCRIPTION
        "The group of notifications supporting the interconnect port
         capabilities for the switch fabric on Nokia SROS series
         systems in release 12.0."
    ::= { tmnxChassIcV12v0Groups 6 }

END
