-- ===========================================================================
-- AT-UFO.MIB, Allied Telesis enterprise MIB: Upstream Forwarding Only (UFO) for private VLANs
--
-- Copyright (c) 2018 by Allied Telesis, Inc.
-- All rights reserved.
--
-- ===========================================================================

    AT-UFO-MIB DEFINITIONS ::= BEGIN

        IMPORTS
            modules
                FROM AT-SMI-MIB
            OBJECT-TYPE, MODULE-IDENTITY, NOTIFICATION-TYPE, Integer32
                FROM SNMPv2-SMI
            TruthValue
                FROM SNMPv2-TC;

        atUfo MODULE-IDENTITY
            LAST-UPDATED "201809200000Z"
            ORGANIZATION
                "Allied Telesis, Inc."
            CONTACT-INFO
                "http://www.alliedtelesis.com"
            DESCRIPTION
                "This MIB file contains definitions of managed objects for the
                 UFO module."
            REVISION    "201809200000Z"
            DESCRIPTION
                "Initial version of this MIB module."
            ::= { modules 605 }

--
-- Node definitions
--

        atUfoTraps OBJECT IDENTIFIER ::= { atUfo 0 }

        atUfoTrapVariables OBJECT IDENTIFIER ::= { atUfo 1 }

        atUfoVlanBlackHoleTrap NOTIFICATION-TYPE
            OBJECTS { atUfoVlanId, atUfoPreviousState, atUfoCurrentState }
            STATUS current
            DESCRIPTION
                "Generated when a UFO private VLAN changes blackhole state."
            ::= { atUfoTraps 1 }

        atUfoBlackHoleAlarmTrap NOTIFICATION-TYPE
            OBJECTS { atUfoAlarmState }
            STATUS current
            DESCRIPTION
                "Generated when the first UFO private VLAN transitions to the blackhole state
                 indicating an alarm has been trigged and when the last UFO private VLAN
                 transitions to non-blackhole state indicating the alarm has been cleared."
            ::= { atUfoTraps 2 }

        atUfoVlanId OBJECT-TYPE
            SYNTAX Integer32
            MAX-ACCESS read-only
            STATUS current
            DESCRIPTION
                "VLAN identifier of the UFO private VLAN."
            ::= { atUfoTrapVariables 1 }

        atUfoPreviousState OBJECT-TYPE
            SYNTAX TruthValue
            MAX-ACCESS read-only
            STATUS current
            DESCRIPTION
                "The previous blackhole state of the UFO private VLAN.
                 Has the value of 1 (true) if the UFO private VLAN was not blackholed.
                 Otherwise has the value of 2 (false) if the UFO VLAN was being blackholed."
            ::= { atUfoTrapVariables 2 }

        atUfoCurrentState OBJECT-TYPE
            SYNTAX TruthValue
            MAX-ACCESS read-only
            STATUS current
            DESCRIPTION
                "The current blackhole state of the UFO private VLAN.
                 Has the value of 1 (true) if the UFO private VLAN is not blackholed.
                 Otherwise has the value of 2 (false) if the UFO VLAN is being blackholed."
            ::= { atUfoTrapVariables 3 }

        atUfoAlarmState OBJECT-TYPE
            SYNTAX TruthValue
            MAX-ACCESS read-only
            STATUS current
            DESCRIPTION
                "Has the value of 1 (true) if one or more UFO privateVLAN is in the blackhole
                 state, indicating an alarm has been triggered.
                 Otherwise has the value of 2 (false) indicating the alarm has been cleared."
            ::= { atUfoTrapVariables 4 }

    END

--
-- at-ufo.mib
--
