-- =================================================================
-- Copyright (c) 2004-2023 New H3C Tech. Co., Ltd.  All rights reserved.
--
-- Description: TCP MIB File
-- Reference:
-- Version: V1.2
-- History:
-- V1.0 2021-12-15 created by zhuqiuxue
-- V1.1 2022-07-15 Modify by yuanyuchen
--      Add hh3cTcpSynFloodFlowTraps, hh3cTcpSynFloodIfTraps
-- V1.2 2023-04-20 Modify by yuanyuchen
--      Add hh3cTcpNumExceedAlarm, hh3cTcpNumExceedResume,
--      hh3cTcpExceptionClose, hh3cTcpNumExceedState,
--      hh3cTcpRcvVrfName, hh3cTcpSndVrfName
-- =================================================================
HH3C-TCP-MIB DEFINITIONS ::= BEGIN

IMPORTS
    hh3cCommon
        FROM HH3C-OID-MIB
    OBJECT-TYPE, MODULE-IDENTITY, Integer32, NOTIFICATION-TYPE, Unsigned32
        FROM SNMPv2-SMI
    InetAddressType, InetAddress
        FROM INET-ADDRESS-MIB
    InterfaceIndex
        FROM IF-MIB;

hh3cTcp MODULE-IDENTITY
    LAST-UPDATED
        "202304200930Z"
    ORGANIZATION
        "New H3C Technologies Co., Ltd."
    CONTACT-INFO
        "Platform Team New H3C Technologies Co., Ltd.
         Hai-Dian District Beijing P.R. China
         http://www.h3c.com
         Zip: 100085"
    DESCRIPTION
        "This MIB file defines the Tcp trap warning feature only."
    REVISION
        "202304200930Z"
    DESCRIPTION
        "Add hh3cTcpNumExceedAlarm, hh3cTcpNumExceedResume, hh3cTcpExceptionClose,
         hh3cTcpNumExceedState, hh3cTcpRcvVrfName and hh3cTcpSndVrfName."
    REVISION
        "202207151110Z"
    DESCRIPTION
        "Add hh3cTcpSynFloodFlowTraps and hh3cTcpSynFloodIfTraps."
    REVISION
        "202112152017Z"
    DESCRIPTION
        "The initial version of this MIB file."
    ::= { hh3cCommon 215 }


hh3cTcpMIBTraps OBJECT IDENTIFIER ::= { hh3cTcp 1 }

hh3cTcpMIBTrap            OBJECT IDENTIFIER ::= { hh3cTcpMIBTraps 0 }

-- hh3cTcpMIBTrap
hh3cTcpMD5AuthenFail NOTIFICATION-TYPE
    OBJECTS
        {
            hh3cTcpConnLocalAddressTCP,
            hh3cTcpConnLocalPortTCP,
            hh3cTcpConnRemAddressTCP,
            hh3cTcpConnRemPortTCP,
            hh3cTcpProtocol,
            hh3cTcpVrfNameVRF
        }
    STATUS      current
    DESCRIPTION
        "The MD5 connected of TCP is failing to authenticate."
    ::= { hh3cTcpMIBTrap 1 }

hh3cTcpNumExceedAlarm NOTIFICATION-TYPE
    OBJECTS
        {
            hh3cTcpNumExceedState
        }
    STATUS      current
    DESCRIPTION
        "The number of TCP connections exceeds the maximum limit."
    ::= { hh3cTcpMIBTrap 2 }

hh3cTcpNumExceedResume NOTIFICATION-TYPE
    OBJECTS
        {
            hh3cTcpNumExceedState
        }
    STATUS      current
    DESCRIPTION
        "The number of TCP connections has returned to normal."
    ::= { hh3cTcpMIBTrap 3 }

hh3cTcpExceptionClose NOTIFICATION-TYPE
    OBJECTS
        {
            hh3cTcpConnLocalAddressTCP,
            hh3cTcpConnLocalPortTCP,
            hh3cTcpConnRemAddressTCP,
            hh3cTcpConnRemPortTCP,
            hh3cTcpRcvVrfName,
            hh3cTcpSndVrfName
        }
    STATUS      current
    DESCRIPTION
        "The TCP connection is disconnected because a large number of
        abnormal messages are received."
    ::= { hh3cTcpMIBTrap 4 }

hh3cTcpMIBTrapobjects            OBJECT IDENTIFIER ::= { hh3cTcpMIBTraps 1 }
-- hh3cTcpMIBTrapobjects
hh3cTcpConnLocalAddressTCP OBJECT-TYPE
    SYNTAX      OCTET STRING (SIZE(0..255))
    MAX-ACCESS  accessible-for-notify
    STATUS      current
    DESCRIPTION
        "The local address of the TCP connection."
    ::= { hh3cTcpMIBTrapobjects 1 }

hh3cTcpConnLocalPortTCP OBJECT-TYPE
    SYNTAX      Integer32 (0..65535)
    MAX-ACCESS  accessible-for-notify
    STATUS      current
    DESCRIPTION
        "The port number of the TCP connection."
    ::= { hh3cTcpMIBTrapobjects 2 }

hh3cTcpConnRemAddressTCP OBJECT-TYPE
    SYNTAX      OCTET STRING (SIZE(0..255))
    MAX-ACCESS  accessible-for-notify
    STATUS      current
    DESCRIPTION
        "The destination address of the TCP connection."
    ::= { hh3cTcpMIBTrapobjects 3 }

hh3cTcpConnRemPortTCP OBJECT-TYPE
    SYNTAX      Integer32 (0..65535)
    MAX-ACCESS  accessible-for-notify
    STATUS      current
    DESCRIPTION
        "The destination port number of the TCP connection."
    ::= { hh3cTcpMIBTrapobjects 4 }

hh3cTcpProtocol OBJECT-TYPE
    SYNTAX      OCTET STRING (SIZE(0..255))
    MAX-ACCESS  accessible-for-notify
    STATUS      current
    DESCRIPTION
        "The information of Protocol, the TCP protocol value is six."
    ::= { hh3cTcpMIBTrapobjects 5 }

hh3cTcpVrfNameVRF OBJECT-TYPE
    SYNTAX      OCTET STRING (SIZE(0..255))
    MAX-ACCESS  accessible-for-notify
    STATUS      current
    DESCRIPTION
        "The information of VrfName."
    ::= { hh3cTcpMIBTrapobjects 6 }

hh3cTcpNumExceedState OBJECT-TYPE
    SYNTAX      INTEGER
        {
            established(1),
            finWait1(2),
            closing(3),
            lastAck(4),
            finWait2(5)
        }
    MAX-ACCESS  accessible-for-notify
    STATUS      current
    DESCRIPTION
        "TCP connection status."
    ::= { hh3cTcpMIBTrapobjects 7 }

hh3cTcpRcvVrfName OBJECT-TYPE
    SYNTAX      OCTET STRING (SIZE(0..255))
    MAX-ACCESS  accessible-for-notify
    STATUS      current
    DESCRIPTION
        "The name of the VPN instance used for receiving."
    ::= { hh3cTcpMIBTrapobjects 8 }

hh3cTcpSndVrfName OBJECT-TYPE
    SYNTAX      OCTET STRING (SIZE(0..255))
    MAX-ACCESS  accessible-for-notify
    STATUS      current
    DESCRIPTION
        "The name of the VPN instance used for sending."
    ::= { hh3cTcpMIBTrapobjects 9 }

hh3cTcpSynFloodFlowTraps OBJECT IDENTIFIER ::= { hh3cTcp 2 }

hh3cTcpSynFloodFlowTrap OBJECT IDENTIFIER ::= { hh3cTcpSynFloodFlowTraps 0 }

-- hh3cTcpSynFloodFlowTrap
hh3cTcpSynFloodFlow NOTIFICATION-TYPE
    OBJECTS
        {
            hh3cTcpSynFloodFlowChassis,
            hh3cTcpSynFloodFlowSlot,
            hh3cTcpSynFloodFlowIpType,
            hh3cTcpSynFloodFlowIpAddress,
            hh3cTcpSynFloodFlowPort,
            hh3cTcpSynFloodFlowVrfName,
            hh3cTcpSynFloodFlowPktType,
            hh3cTcpSynFloodFlowRate
        }
    STATUS      current
    DESCRIPTION
        "The number of received SYN packets exceeds the threshold."
    ::= { hh3cTcpSynFloodFlowTrap 1 }


hh3cTcpSynFloodFlowTrapobjects OBJECT IDENTIFIER ::= { hh3cTcpSynFloodFlowTraps 1 }
-- hh3cTcpSynFloodFlowTrapobjects
hh3cTcpSynFloodFlowChassis OBJECT-TYPE
    SYNTAX      Unsigned32
    MAX-ACCESS  accessible-for-notify
    STATUS      current
    DESCRIPTION
        "The information of chassis ID. If the value is 65535, the device is
        not a stacked device."
    ::= { hh3cTcpSynFloodFlowTrapobjects 1 }

hh3cTcpSynFloodFlowSlot OBJECT-TYPE
    SYNTAX      Unsigned32
    MAX-ACCESS  accessible-for-notify
    STATUS      current
    DESCRIPTION
        "The information of slot."
    ::= { hh3cTcpSynFloodFlowTrapobjects 2 }

hh3cTcpSynFloodFlowIpType OBJECT-TYPE
    SYNTAX      InetAddressType
    MAX-ACCESS  accessible-for-notify
    STATUS      current
    DESCRIPTION
        "The type of address."
    ::= { hh3cTcpSynFloodFlowTrapobjects 3 }

hh3cTcpSynFloodFlowIpAddress OBJECT-TYPE
    SYNTAX      InetAddress
    MAX-ACCESS  accessible-for-notify
    STATUS      current
    DESCRIPTION
        "The source address of packet."
    ::= { hh3cTcpSynFloodFlowTrapobjects 4 }

hh3cTcpSynFloodFlowPort OBJECT-TYPE
    SYNTAX      Integer32 (0..65535)
    MAX-ACCESS  accessible-for-notify
    STATUS      current
    DESCRIPTION
        "The destination port number of packet."
    ::= { hh3cTcpSynFloodFlowTrapobjects 5 }

hh3cTcpSynFloodFlowVrfName OBJECT-TYPE
    SYNTAX      OCTET STRING (SIZE(0..255))
    MAX-ACCESS  accessible-for-notify
    STATUS      current
    DESCRIPTION
        "The information of VrfName."
    ::= { hh3cTcpSynFloodFlowTrapobjects 6 }

hh3cTcpSynFloodFlowPktType OBJECT-TYPE
    SYNTAX      INTEGER
        {
            ip(1),
            mpls(2)
        }
    MAX-ACCESS  accessible-for-notify
    STATUS      current
    DESCRIPTION
        "The type of packet."
    ::= { hh3cTcpSynFloodFlowTrapobjects 7 }

hh3cTcpSynFloodFlowRate OBJECT-TYPE
    SYNTAX      Unsigned32
    MAX-ACCESS  accessible-for-notify
    STATUS      current
    DESCRIPTION
        "The rate of syn flood."
    ::= { hh3cTcpSynFloodFlowTrapobjects 8 }

hh3cTcpSynFloodIfTraps OBJECT IDENTIFIER ::= { hh3cTcp 3 }

hh3cTcpSynFloodIfTrap OBJECT IDENTIFIER ::= { hh3cTcpSynFloodIfTraps 0 }

-- hh3cTcpSynFloodIfTrap
hh3cTcpSynFloodIf NOTIFICATION-TYPE
    OBJECTS
        {
            hh3cTcpSynFloodIfChassis,
            hh3cTcpSynFloodIfSlot,
            hh3cTcpSynFloodIfIndex,
            hh3cTcpSynFloodIfPktType,
            hh3cTcpSynFloodIfRate
        }
    STATUS      current
    DESCRIPTION
        "The number of received SYN packets exceeds the threshold."
    ::= { hh3cTcpSynFloodIfTrap 1 }


hh3cTcpSynFloodIfTrapobjects OBJECT IDENTIFIER ::= { hh3cTcpSynFloodIfTraps 1 }
-- hh3cTcpSynFloodIfTrapobjects
hh3cTcpSynFloodIfChassis OBJECT-TYPE
    SYNTAX      Unsigned32
    MAX-ACCESS  accessible-for-notify
    STATUS      current
    DESCRIPTION
        "The information of chassis ID. If the value is 65535, the device is
        not a stacked device."
    ::= { hh3cTcpSynFloodIfTrapobjects 1 }

hh3cTcpSynFloodIfSlot OBJECT-TYPE
    SYNTAX      Unsigned32
    MAX-ACCESS  accessible-for-notify
    STATUS      current
    DESCRIPTION
        "The information of slot."
    ::= { hh3cTcpSynFloodIfTrapobjects 2 }

hh3cTcpSynFloodIfIndex OBJECT-TYPE
    SYNTAX      InterfaceIndex
    MAX-ACCESS  accessible-for-notify
    STATUS      current
    DESCRIPTION
        "The index value of the interface."
    ::= { hh3cTcpSynFloodIfTrapobjects 3 }

hh3cTcpSynFloodIfPktType OBJECT-TYPE
    SYNTAX      INTEGER
        {
            ip(1),
            mpls(2)
        }
    MAX-ACCESS  accessible-for-notify
    STATUS      current
    DESCRIPTION
        "The type of packet."
    ::= { hh3cTcpSynFloodIfTrapobjects 4 }

hh3cTcpSynFloodIfRate OBJECT-TYPE
    SYNTAX      Unsigned32
    MAX-ACCESS  accessible-for-notify
    STATUS      current
    DESCRIPTION
        "The rate of syn flood."
    ::= { hh3cTcpSynFloodIfTrapobjects 5 }

END
