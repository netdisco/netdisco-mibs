-- ============================================================================
-- Copyright (c) 2004-2022 New H3C Tech. Co., Ltd. All rights reserved.
-- Description:  The purpose of this MIB file is to provide the definition of
--               the DAC(Data Analysis Center) trap.
-- Reference:
-- Version: V1.0
-- History:
-- V1.0 2022/07/15 created by suncao
--      The initial revision of this MIB module.
--      Add hh3cDacTrapStoreFull,
--      hh3cDacTrapStoreDeleteFile,
--      hh3cDacTrapStorageChange,
--      hh3cDacTrapTotalStoreFull.
-- ============================================================================
HH3C-DAC-MIB DEFINITIONS ::= BEGIN

IMPORTS
    hh3cCommon
        FROM HH3C-OID-MIB
    Unsigned32, OBJECT-TYPE, MODULE-IDENTITY, NOTIFICATION-TYPE
        FROM SNMPv2-SMI;

hh3cDac MODULE-IDENTITY
    LAST-UPDATED "202207151100Z"             -- July 15, 2022 at 11:00 GMT
    ORGANIZATION
    "New H3C Tech. Co., Ltd."
    CONTACT-INFO
        "Platform Team New H3C Tech. Co., Ltd.
        Hai-Dian District Beijing P.R. China
        http://www.h3c.com
        Zip:100085"
    DESCRIPTION
        "Add hh3cDacTrapStoreFull,
        hh3cDacTrapStoreDeleteFile,
        hh3cDacTrapStorageChange,
        hh3cDacTrapTotalStoreFull"

    REVISION "202207151100Z"                -- July 15, 2022 at 11:00 GMT
    DESCRIPTION
        "The initial revision of this MIB module."
    ::= { hh3cCommon 237 }

--
-- Node definitions
--

-- Global Variants
hh3cDacStoreTraps OBJECT IDENTIFIER ::= { hh3cDac 1 }

--                     **************Global Variants***************
-- Describe objects for dac trap
hh3cDacTrapsStorePrefix OBJECT IDENTIFIER ::= { hh3cDacStoreTraps 0 }
hh3cDacTrapStoreFull NOTIFICATION-TYPE
    OBJECTS
        {
            hh3cDacStoreServiceName,
            hh3cDacStoreThresholdType,
            hh3cDacStoreThresholdValue
        }
    STATUS    current
    DESCRIPTION
        "Send trap when storage space or storage time reaches the upper limit."
    ::= { hh3cDacTrapsStorePrefix 1 }
hh3cDacTrapStoreDeleteFile NOTIFICATION-TYPE
    OBJECTS
        {
            hh3cDacStoreServiceName,
            hh3cDacStoreThresholdType
        }
    STATUS    current
    DESCRIPTION
        "When the storage space or storage time reaches the upper limit,
        delete the data beyond the upper limit."
    ::= { hh3cDacTrapsStorePrefix 2 }
hh3cDacTrapStorageChange NOTIFICATION-TYPE
    OBJECTS
        {
            hh3cDacNewStorageMedia,
            hh3cDacOldStorageMedia,
            hh3cDacStorageChangeReason,
            hh3cDacStorageChangeTip
        }
    STATUS    current
    DESCRIPTION
        "Log storage media switching."
    ::= { hh3cDacTrapsStorePrefix 3 }
hh3cDacTrapTotalStoreFull NOTIFICATION-TYPE
    STATUS    current
    DESCRIPTION
        "The total storage space utilization rate of DAC business has reached 98%."
    ::= { hh3cDacTrapsStorePrefix 4 }

hh3cDacTrapsStoreObjects OBJECT IDENTIFIER ::= { hh3cDacStoreTraps 1 }
hh3cDacStoreServiceName OBJECT-TYPE
    SYNTAX    OCTET STRING(SIZE(0..36))
    MAX-ACCESS    accessible-for-notify
    STATUS    current
    DESCRIPTION
        "Service identification of storage alarm."
    ::= { hh3cDacTrapsStoreObjects 1 }
hh3cDacStoreThresholdType OBJECT-TYPE
    SYNTAX    Unsigned32(1..2)
    MAX-ACCESS    accessible-for-notify
    STATUS    current
    DESCRIPTION
        "Storage time alarm or storage space alarm."
    ::= { hh3cDacTrapsStoreObjects 2 }
hh3cDacStoreThresholdValue OBJECT-TYPE
    SYNTAX    OCTET STRING(SIZE(0..16))
    MAX-ACCESS    accessible-for-notify
    STATUS    current
    DESCRIPTION
        "Storage alarm threshold."
    ::= { hh3cDacTrapsStoreObjects 3 }
hh3cDacNewStorageMedia OBJECT-TYPE
    SYNTAX    OCTET STRING(SIZE(0..32))
    MAX-ACCESS    accessible-for-notify
    STATUS    current
    DESCRIPTION
        "New storage media file system name after switching."
    ::= { hh3cDacTrapsStoreObjects 4 }
hh3cDacOldStorageMedia OBJECT-TYPE
    SYNTAX    OCTET STRING(SIZE(0..32))
    MAX-ACCESS    accessible-for-notify
    STATUS    current
    DESCRIPTION
        "Old storage media file system name after switching."
    ::= { hh3cDacTrapsStoreObjects 5 }
hh3cDacStorageChangeReason OBJECT-TYPE
    SYNTAX    OCTET STRING(SIZE(0..128))
    MAX-ACCESS    accessible-for-notify
    STATUS    current
    DESCRIPTION
        "The reason for switching storage media."
    ::= { hh3cDacTrapsStoreObjects 6 }
hh3cDacStorageChangeTip OBJECT-TYPE
    SYNTAX    OCTET STRING(SIZE(0..128))
    MAX-ACCESS    accessible-for-notify
    STATUS    current
    DESCRIPTION
        "If the new storage medium is not memory, this item is empty.
        Otherwise, the corresponding prompt message will be prompted."
    ::= { hh3cDacTrapsStoreObjects 7 }

END
