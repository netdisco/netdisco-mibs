-- =================================================================
-- Copyright (c) 2004-2023 New H3C Tech. Co., Ltd. All rights reserved.
--
-- Description: policy-based routing(PBR) MIB File
-- Reference:
-- Version: V1.3
-- History:
--      V1.0 created by Hou Yefei
--        initial version 2010-12-10
--      V1.1 2012-7-21 modified by Hou Yefei
--         Add hh3cPBRLocalPolicy
--         Add hh3cPBRMibPolicyNodeTable, hh3cPBRMibIfPolicyTable,
--             hh3cPBRMibMatchAclTable, hh3cPBRMibMatchAclTable,
--             hh3cPBRMibApplyNexthopTablel,
--             hh3cPBRMibApplyDefaultNexthopTable
--           2012-8-13 modified by Hou Yefei
--         Modify hh3cPBRNexthopTrapEnabled
--         Add hh3cPBRIPv6NexthopTrapEnabled
--      V1.2 2022-6-27 modified by Li Ke
--         Add hh3cPBRMibMinPktLen, hh3cPBRMibMaxPktLen,
--             hh3cPBRMibQosId, hh3cPBRMibQosIdMode,
--             hh3cPBRMibVxlanId, hh3cPBRMibDescription, hh3cPBRMibApplyContinue,
--             hh3cPBRMibApplyFailDropNextHop, hh3cPBRMibApplyIpDf,
--             hh3cPBRMibApplyLoadShareNextHop, hh3cPBRMibApplyLoadShareOutIf,
--             hh3cPBRMibApplyLSDefaultNextHop, hh3cPBRMibApplyLSDefaultOutIf,
--             hh3cPBRMibApplyStatisticsValue
--         Add hh3cPBRMibIfPolicyShareMode
--         Add hh3cPBRMibAclGroupName, hh3cPBRMibAclGroupVersion
--         Add hh3cPBRMibApplyNexthopInboundVpn, hh3cPBRMibApplyNexthopWeight,
--             hh3cPBRMibApplyNexthopPathId, hh3cPBRMibApplyNexthopPathIndex
--         Add hh3cPBRMibApplyDefNexthopInbVpn, hh3cPBRMibApplyDefNexthopPathId,
--             hh3cPBRMibApplyDefNexthopPathInd
--      V1.3 2023-1-5 modified by Li Ke
--         Modify hh3cPBRMibApplyNexthopTrackId,
--             hh3cPBRMibApplyDefaultNexthopTrackId
-- =================================================================
HH3C-PBR-MIB DEFINITIONS ::= BEGIN

IMPORTS
    hh3cCommon
        FROM HH3C-OID-MIB
    OBJECT-TYPE, MODULE-IDENTITY, NOTIFICATION-TYPE, Integer32
        FROM SNMPv2-SMI
    TruthValue, DisplayString, RowStatus
        FROM SNMPv2-TC
    ifIndex
        FROM IF-MIB
    InetAddress, InetAddressType
        FROM INET-ADDRESS-MIB;

hh3cPBR MODULE-IDENTITY
    LAST-UPDATED
        "202301051023Z"
    ORGANIZATION
        "New H3C Technologies Co., Ltd."
    CONTACT-INFO
        "Platform Team New H3C Technologies Co., Ltd.
        Hai-Dian District Beijing P.R. China
        http://www.h3c.com
        Zip:100085
        "
    DESCRIPTION
        "This MIB contains objects to manage the configuration and information
        of PBR.  It routes IP packets by user defined policy
        other than normal destination address based routing.
        "
    REVISION
        "202301051023Z"
    DESCRIPTION
        "Modify hh3cPBRMibApplyNexthopTrackId and
             hh3cPBRMibApplyDefaultNexthopTrackId."
    REVISION
        "202206271115Z"
    DESCRIPTION
        "Add hh3cPBRMibMinPktLen, hh3cPBRMibMaxPktLen,
             hh3cPBRMibQosId, hh3cPBRMibQosIdMode,
             hh3cPBRMibVxlanId, hh3cPBRMibDescription, hh3cPBRMibApplyContinue,
             hh3cPBRMibApplyFailDropNextHop, hh3cPBRMibApplyIpDf,
             hh3cPBRMibApplyLoadShareNextHop, hh3cPBRMibApplyLoadShareOutIf,
             hh3cPBRMibApplyLSDefaultNextHop, hh3cPBRMibApplyLSDefaultOutIf,
             hh3cPBRMibApplyStatisticsValue
         Add hh3cPBRMibIfPolicyShareMode
         Add hh3cPBRMibAclGroupName, hh3cPBRMibAclGroupVersion
         Add hh3cPBRMibApplyNexthopInboundVpn, hh3cPBRMibApplyNexthopWeight,
             hh3cPBRMibApplyNexthopPathId, hh3cPBRMibApplyNexthopPathIndex
         Add hh3cPBRMibApplyDefNexthopInbVpn, hh3cPBRMibApplyDefNexthopPathId,
             hh3cPBRMibApplyDefNexthopPathInd."
    REVISION
        "201012101558Z"
    DESCRIPTION
        "The initial version of this MIB file."
    ::= { hh3cCommon 113 }

-- Objects define
hh3cPBRObjects OBJECT IDENTIFIER ::= { hh3cPBR 1 }

hh3cPBRGlobal OBJECT IDENTIFIER ::= { hh3cPBRObjects 1 }

hh3cPBRNexthopTrapEnabled OBJECT-TYPE
    SYNTAX      TruthValue
    MAX-ACCESS  read-write
    STATUS      current
    DESCRIPTION
        "The value is a global setting only for IPv4 PBR.  If the
         value is set to 'false', the feature is disabled."
    DEFVAL { true }
    ::= { hh3cPBRGlobal 1 }

hh3cPBRLocalPolicy OBJECT-TYPE
    SYNTAX      DisplayString (SIZE (0..19))
    MAX-ACCESS  read-write
    STATUS      current
    DESCRIPTION
        "The value is a global setting.  An existing policy name setting enables
        local PBR for IPv4 packets initiated by the device.
        Only one policy can be applied locally.
        An empty name setting disables the feature.
        "
    ::= { hh3cPBRGlobal 2 }

hh3cPBRIPv6NexthopTrapEnabled OBJECT-TYPE
    SYNTAX      TruthValue
    MAX-ACCESS  read-write
    STATUS      current
    DESCRIPTION
        "The value is a global setting only for IPv6 PBR.  If the
         value is set to 'false', the feature is disabled."
    DEFVAL { true }
    ::= { hh3cPBRGlobal 3 }

-- PBR trap table
hh3cPBRMibTrap OBJECT IDENTIFIER ::= { hh3cPBRObjects 2 }

hh3cPBRTrapObjects OBJECT IDENTIFIER  ::= { hh3cPBRMibTrap 1 }

hh3cPBRNexthopAddrType OBJECT-TYPE
    SYNTAX      InetAddressType
    MAX-ACCESS  accessible-for-notify
    STATUS      current
    DESCRIPTION
        "Indicating address type of hh3cPBRNexthopAddr, which can be IPv4
        or IPv6."
    ::= { hh3cPBRTrapObjects 1 }

hh3cPBRNexthopAddr OBJECT-TYPE
    SYNTAX      InetAddress
    MAX-ACCESS  accessible-for-notify
    STATUS      current
    DESCRIPTION
        "The involved next hop IP address of trap information."
    ::= { hh3cPBRTrapObjects 2 }

hh3cPBRTraps OBJECT IDENTIFIER  ::= { hh3cPBRMibTrap 2 }

hh3cPBRTrapsPrefix OBJECT IDENTIFIER  ::= { hh3cPBRTraps 0 }

hh3cPBRNexthopFailedTrap NOTIFICATION-TYPE
    OBJECTS
    {
        hh3cPBRNexthopAddrType,
        hh3cPBRNexthopAddr
    }
    STATUS      current
    DESCRIPTION
        "When the next hop of PBR apply clause became
        unreachable according to routing information, trap is generated
        and is sent to the remote monitoring device."
    ::= { hh3cPBRTrapsPrefix 1 }

-- PBR policy node table
hh3cPBRTables OBJECT IDENTIFIER ::= { hh3cPBR 2 }

hh3cPBRMibPolicyNodeTable  OBJECT-TYPE
    SYNTAX      SEQUENCE OF Hh3cPBRMibPolicyNodeEntry
    MAX-ACCESS  not-accessible
    STATUS      current
    DESCRIPTION "A table for PBR nodes.
                "
    ::= { hh3cPBRTables 1 }

hh3cPBRMibPolicyNodeEntry  OBJECT-TYPE
    SYNTAX      Hh3cPBRMibPolicyNodeEntry
    MAX-ACCESS  not-accessible
    STATUS      current
    DESCRIPTION "An entry for PBR nodes.
                "
    INDEX
    {
            hh3cPBRMibPolicyNodeAddrType,
            hh3cPBRMibPolicyName,
            hh3cPBRMibPolicyNodeId
    }
    ::= { hh3cPBRMibPolicyNodeTable 1 }

Hh3cPBRMibPolicyNodeEntry ::=
    SEQUENCE
    {
            hh3cPBRMibPolicyNodeAddrType           InetAddressType,
            hh3cPBRMibPolicyName                   DisplayString,
            hh3cPBRMibPolicyNodeId                 Integer32,
            hh3cPBRMibPolicyNodeMode               TruthValue,
            hh3cPBRMibPolicyNodeRowStatus          RowStatus,
            hh3cPBRMibMinPktLen                    Integer32,
            hh3cPBRMibMaxPktLen                    Integer32,
            hh3cPBRMibQosId                        Integer32,
            hh3cPBRMibQosIdMode                    INTEGER,
            hh3cPBRMibVxlanId                      Integer32,
            hh3cPBRMibDescription                  DisplayString,
            hh3cPBRMibApplyContinue                TruthValue,
            hh3cPBRMibApplyFailDropNextHop         TruthValue,
            hh3cPBRMibApplyIpDf                    Integer32,
            hh3cPBRMibApplyLoadShareNextHop        TruthValue,
            hh3cPBRMibApplyLoadShareOutIf          TruthValue,
            hh3cPBRMibApplyLSDefaultNextHop        TruthValue,
            hh3cPBRMibApplyLSDefaultOutIf          TruthValue,
            hh3cPBRMibApplyStatisticsValue         TruthValue
    }

hh3cPBRMibPolicyNodeAddrType    OBJECT-TYPE
    SYNTAX      InetAddressType
    MAX-ACCESS  not-accessible
    STATUS      current
    DESCRIPTION "Address type of policy node, which can be IPv4 or IPv6, Dual-stack."
    ::= { hh3cPBRMibPolicyNodeEntry 1 }

hh3cPBRMibPolicyName    OBJECT-TYPE
    SYNTAX      DisplayString (SIZE (1..19))
    MAX-ACCESS  not-accessible
    STATUS      current
    DESCRIPTION "Policy name of PBR node."
    ::= { hh3cPBRMibPolicyNodeEntry 2 }

hh3cPBRMibPolicyNodeId   OBJECT-TYPE
    SYNTAX      Integer32 (0..65535)
    MAX-ACCESS  not-accessible
    STATUS      current
    DESCRIPTION "Sequence identifier of PBR node."
    ::= { hh3cPBRMibPolicyNodeEntry 3 }

hh3cPBRMibPolicyNodeMode   OBJECT-TYPE
    SYNTAX      TruthValue
    MAX-ACCESS  read-create
    STATUS      current
    DESCRIPTION "Mode of PBR node.  If the mode of a node is marked as true,
                the packets that meet the matching rules are processed by
                action rules in the node.  If the mode of a node is marked as
                false, the packets that meet the matching rules are
                sent back to the normal forwarding path."
    DEFVAL { true }
    ::= { hh3cPBRMibPolicyNodeEntry 4 }

hh3cPBRMibPolicyNodeRowStatus   OBJECT-TYPE
    SYNTAX      RowStatus
    MAX-ACCESS  read-create
    STATUS      current
    DESCRIPTION
            "Operation status of this table entry.
            Three actions are used: active,
            createAndGo, and destroy.
            "
    ::= { hh3cPBRMibPolicyNodeEntry 5 }

hh3cPBRMibMinPktLen    OBJECT-TYPE
    SYNTAX      Integer32
    MAX-ACCESS  read-write
    STATUS      current
    DESCRIPTION "Specifies the minimum IP packet length in the range of 1 and 65535.
                 Value 0 indicates that this rule is not set."
    ::= { hh3cPBRMibPolicyNodeEntry 6 }

hh3cPBRMibMaxPktLen    OBJECT-TYPE
    SYNTAX      Integer32
    MAX-ACCESS  read-write
    STATUS      current
    DESCRIPTION "Specifies the maximum IP packet length in the range of 1 and 65535.
                 The maximum length must be no less than the minimum length.
                 The maximum and the minimum lengths must be both configured.
                 Value 0 indicates that this rule is not set."
    ::= { hh3cPBRMibPolicyNodeEntry 7 }

hh3cPBRMibQosId    OBJECT-TYPE
    SYNTAX      Integer32
    MAX-ACCESS  read-write
    STATUS      current
    DESCRIPTION "Specifies a local Quality of Service(QoS) ID in the range of 1 and 4095.
                 Value 0 indicates that this rule is not set."
    ::= { hh3cPBRMibPolicyNodeEntry 8 }

hh3cPBRMibQosIdMode    OBJECT-TYPE
    SYNTAX INTEGER
    {
        invalid(1),
        normal(2),
        qppb(3)
    }
    MAX-ACCESS  read-write
    STATUS      current
    DESCRIPTION "The mode of the QoS Local ID.
                 The default value is normal."
    ::= { hh3cPBRMibPolicyNodeEntry 9 }

hh3cPBRMibVxlanId    OBJECT-TYPE
    SYNTAX      Integer32
    MAX-ACCESS  read-write
    STATUS      current
    DESCRIPTION "Specifies a VXLAN ID in the range of 0 to 16777215.
                 Value -1 indicates that this rule is not set."
    ::= { hh3cPBRMibPolicyNodeEntry 10 }

hh3cPBRMibDescription    OBJECT-TYPE
    SYNTAX      DisplayString (SIZE (0..127))
    MAX-ACCESS  read-write
    STATUS      current
    DESCRIPTION "A description for a policy node."
    ::= { hh3cPBRMibPolicyNodeEntry 11 }

hh3cPBRMibApplyContinue    OBJECT-TYPE
    SYNTAX      TruthValue
    MAX-ACCESS  read-write
    STATUS      current
    DESCRIPTION "Use apply continue to compare packets
                 with the next policy node upon failure on the current node.
                 Value FALSE indicates that this action is not set."
    ::= { hh3cPBRMibPolicyNodeEntry 12 }

hh3cPBRMibApplyFailDropNextHop    OBJECT-TYPE
    SYNTAX      TruthValue
    MAX-ACCESS  read-write
    STATUS      current
    DESCRIPTION "Configure the policy node to drop matching packets when
                 the next hop is invalid.  If no next hops are specified
                 on the policy node, this command drops all packets that
                 match the node. Value FALSE indicates that this action is not set."
    ::= { hh3cPBRMibPolicyNodeEntry 13 }

hh3cPBRMibApplyIpDf    OBJECT-TYPE
    SYNTAX      Integer32
    MAX-ACCESS  read-write
    STATUS      current
    DESCRIPTION "Sets the Don't Fragment(DF) bit in the IP header of
                 matching packets. The value can be 0 or 1.
                 Value -1 indicates that this action is not set."
    ::= { hh3cPBRMibPolicyNodeEntry 14 }

hh3cPBRMibApplyLoadShareNextHop    OBJECT-TYPE
    SYNTAX      TruthValue
    MAX-ACCESS  read-write
    STATUS      current
    DESCRIPTION "Enables load sharing among multiple next hops.
                 Value FALSE indicates that this action is not set."
    ::= { hh3cPBRMibPolicyNodeEntry 15 }

hh3cPBRMibApplyLoadShareOutIf    OBJECT-TYPE
    SYNTAX      TruthValue
    MAX-ACCESS  read-write
    STATUS      current
    DESCRIPTION "Enables load sharing among multiple output interfaces.
                 Value FALSE indicates that this action is not set."
    ::= { hh3cPBRMibPolicyNodeEntry 16 }

hh3cPBRMibApplyLSDefaultNextHop    OBJECT-TYPE
    SYNTAX      TruthValue
    MAX-ACCESS  read-write
    STATUS      current
    DESCRIPTION "Enables load sharing among multiple default next hops.
                 Value FALSE indicates that this action is not set."
    ::= { hh3cPBRMibPolicyNodeEntry 17 }

hh3cPBRMibApplyLSDefaultOutIf    OBJECT-TYPE
    SYNTAX      TruthValue
    MAX-ACCESS  read-write
    STATUS      current
    DESCRIPTION "Enables load sharing among multiple default output interfaces.
                 Value FALSE indicates that this action is not set."
    ::= { hh3cPBRMibPolicyNodeEntry 18 }

hh3cPBRMibApplyStatisticsValue    OBJECT-TYPE
    SYNTAX      TruthValue
    MAX-ACCESS  read-write
    STATUS      current
    DESCRIPTION "Use apply statistics to enable match counting on a policy node.
                 Value FALSE indicates that this action is not set."
    ::= { hh3cPBRMibPolicyNodeEntry 19 }

-- PBR local policy


-- PBR interface policy relation table

hh3cPBRMibIfPolicyTable OBJECT-TYPE
    SYNTAX      SEQUENCE OF Hh3cPBRMibIfPolicyEntry
    MAX-ACCESS  not-accessible
    STATUS      current
    DESCRIPTION "A table for interfaces being applied with PBR
                 nodes with the same policy name.
                "
    ::= { hh3cPBRTables 2 }

hh3cPBRMibIfPolicyEntry  OBJECT-TYPE
    SYNTAX      Hh3cPBRMibIfPolicyEntry
    MAX-ACCESS  not-accessible
    STATUS      current
    DESCRIPTION "An entry for reference relation between interface and policy
                nodes."
    INDEX
    {
            hh3cPBRMibPolicyAddressType,
            ifIndex
    }
    ::= { hh3cPBRMibIfPolicyTable 1 }

Hh3cPBRMibIfPolicyEntry ::=
    SEQUENCE
    {
            hh3cPBRMibPolicyAddressType   InetAddressType,
            hh3cPBRMibAppliedPolicyName   DisplayString,
            hh3cPBRMibIfPolicyRowStatus   RowStatus,
            hh3cPBRMibIfPolicyShareMode   TruthValue
    }

hh3cPBRMibPolicyAddressType    OBJECT-TYPE
    SYNTAX      InetAddressType
    MAX-ACCESS  not-accessible
    STATUS      current
    DESCRIPTION  "Address type of policy node, which can be
                 IPv4 or IPv6, Dual-stack."
    ::= { hh3cPBRMibIfPolicyEntry 1 }

hh3cPBRMibAppliedPolicyName    OBJECT-TYPE
    SYNTAX      DisplayString (SIZE (1..19))
    MAX-ACCESS  read-create
    STATUS      current
    DESCRIPTION "Policy name of PBR nodes."
    ::= { hh3cPBRMibIfPolicyEntry 2 }

hh3cPBRMibIfPolicyRowStatus  OBJECT-TYPE
    SYNTAX      RowStatus
    MAX-ACCESS  read-create
    STATUS      current
    DESCRIPTION
            "Operation status of this table entry.
            Three actions are used: active,
            createAndGo, and destroy.
            "
    ::= { hh3cPBRMibIfPolicyEntry 3 }

hh3cPBRMibIfPolicyShareMode    OBJECT-TYPE
    SYNTAX      TruthValue
    MAX-ACCESS  read-create
    STATUS      current
    DESCRIPTION "Applies the policy in resource sharing mode.
                 In this mode, all interfaces on an interface card
                 with the same policy applied share one hardware resource."
    DEFVAL { false }
    ::= { hh3cPBRMibIfPolicyEntry 4 }

-- PBR policy node acl rule table

hh3cPBRMibMatchAclTable OBJECT-TYPE
    SYNTAX      SEQUENCE OF Hh3cPBRMibMatchAclEntry
    MAX-ACCESS  not-accessible
    STATUS      current
    DESCRIPTION "A table for ACLs being used by a policy node.  Only one ACL
                 can be used within a node at most.
                "
    ::= { hh3cPBRTables 3 }

hh3cPBRMibMatchAclEntry  OBJECT-TYPE
    SYNTAX      Hh3cPBRMibMatchAclEntry
    MAX-ACCESS  not-accessible
    STATUS      current
    DESCRIPTION "An entry for policy node that uses an ACL group as its
                if-match rule."
    INDEX
    {
            hh3cPBRMibPolicyNodeAddrType,
            hh3cPBRMibPolicyName,
            hh3cPBRMibPolicyNodeId
    }
    ::= { hh3cPBRMibMatchAclTable 1 }

Hh3cPBRMibMatchAclEntry ::=
    SEQUENCE
    {
            hh3cPBRMibAclGroupId   Integer32,
            hh3cPBRMibAclGroupName OCTET STRING,
            hh3cPBRMibAclGroupVersion   INTEGER
    }

hh3cPBRMibAclGroupId    OBJECT-TYPE
    SYNTAX      Integer32
    MAX-ACCESS  read-write
    STATUS      current
    DESCRIPTION "Index of number-acl group.
                 Setting -1 indicates closing this rule.
                 When ACLName is configured with a valid value,
                 value -1 will be returned for ACLNumber.
                "
    ::= { hh3cPBRMibMatchAclEntry 1 }

hh3cPBRMibAclGroupName   OBJECT-TYPE
    SYNTAX OCTET STRING (SIZE (0..63))
    MAX-ACCESS  read-write
    STATUS  current
    DESCRIPTION "ACL match criterion by name. The ACL name must start with
                 letter a to z or A to Z.  The ACL name cannot be all in
                 any combination of upper-case and lower-case letters.
                 To delete an ACL match criterion, you must configure the value
                 for ACLNumber as -1."
    ::= { hh3cPBRMibMatchAclEntry 2 }

hh3cPBRMibAclGroupVersion    OBJECT-TYPE
    SYNTAX INTEGER
    {
        invalid(1),
        ipv4(2),
        ipv6(3),
        userdefined(4)
    }
    MAX-ACCESS  read-write
    STATUS      current
    DESCRIPTION "The type of the ACL.
                 The hh3cPBRMibAclGroupVersion can only be configured
                 when the policy node type is Dual-stack, and cannot be empty."
    ::= { hh3cPBRMibMatchAclEntry 3 }

-- PBR policy node apply precedence action table

hh3cPBRMibApplyPrecedenceTable OBJECT-TYPE
    SYNTAX      SEQUENCE OF Hh3cPBRMibApplyPrecedenceEntry
    MAX-ACCESS  not-accessible
    STATUS      current
    DESCRIPTION "A table for precedence values being used by a policy node.
                 Only one precedence value can be used within a node at most.
                "
    ::= { hh3cPBRTables 4 }

hh3cPBRMibApplyPrecedenceEntry  OBJECT-TYPE
    SYNTAX      Hh3cPBRMibApplyPrecedenceEntry
    MAX-ACCESS  not-accessible
    STATUS      current
    DESCRIPTION "An entry for policy node with an action
                 to set IP precedence for matching packets.
                "
    INDEX
    {
            hh3cPBRMibPolicyNodeAddrType,
            hh3cPBRMibPolicyName,
            hh3cPBRMibPolicyNodeId
    }
    ::= { hh3cPBRMibApplyPrecedenceTable 1 }

Hh3cPBRMibApplyPrecedenceEntry ::=
    SEQUENCE
    {
            hh3cPBRMibApplyPrecedenceValue Integer32
    }

hh3cPBRMibApplyPrecedenceValue    OBJECT-TYPE
    SYNTAX      Integer32
    MAX-ACCESS  read-write
    STATUS      current
    DESCRIPTION "Value of precedence being applied on IP header.
                   <0-7>           Value of precedence
                   routine         Specify routine precedence(0)
                   priority        Specify priority precedence(1)
                   immediate       Specify immediate precedence(2)
                   flash           Specify flash precedence(3)
                   flash-override  Specify flash-override precedence(4)
                   critical        Specify critical precedence(5)
                   internet        Specify internetwork control precedence(6)
                   network         Specify network control precedence(7)
                 Setting -1 indicates closing this action.
                "
    ::= { hh3cPBRMibApplyPrecedenceEntry 1 }

-- PBR policy node apply next hop action table

hh3cPBRMibApplyNexthopTable OBJECT-TYPE
    SYNTAX      SEQUENCE OF Hh3cPBRMibApplyNexthopEntry
    MAX-ACCESS  not-accessible
    STATUS      current
    DESCRIPTION "A table for next hop actions being used by a policy node.
                "
    ::= { hh3cPBRTables 5 }

hh3cPBRMibApplyNexthopEntry  OBJECT-TYPE
    SYNTAX      Hh3cPBRMibApplyNexthopEntry
    MAX-ACCESS  not-accessible
    STATUS      current
    DESCRIPTION "An entry for policy node with an action
                 to set next hop for matching packets.
                "
    INDEX
    {
            hh3cPBRMibPolicyNodeAddrType,
            hh3cPBRMibPolicyName,
            hh3cPBRMibPolicyNodeId,
            hh3cPBRMibApplyNexthopIndex
    }
    ::= { hh3cPBRMibApplyNexthopTable 1 }

Hh3cPBRMibApplyNexthopEntry ::=
    SEQUENCE
    {
            hh3cPBRMibApplyNexthopIndex       Integer32,
            hh3cPBRMibApplyNexthopVpnName     DisplayString,
            hh3cPBRMibApplyNexthopAddressType InetAddressType,
            hh3cPBRMibApplyNexthopAddress     InetAddress,
            hh3cPBRMibApplyNexthopTrackId     Integer32,
            hh3cPBRMibApplyNexthopDirect      TruthValue,
            hh3cPBRMibApplyNexthopRowStatus   RowStatus,
            hh3cPBRMibApplyNexthopInboundVpn  TruthValue,
            hh3cPBRMibApplyNexthopWeight      Integer32,
            hh3cPBRMibApplyNexthopPathId      Integer32,
            hh3cPBRMibApplyNexthopPathIndex   Integer32
    }

hh3cPBRMibApplyNexthopIndex    OBJECT-TYPE
    SYNTAX      Integer32 (0..2147483647)
    MAX-ACCESS  not-accessible
    STATUS      current
    DESCRIPTION "Index of next hop for the apply next hop action."
    ::= { hh3cPBRMibApplyNexthopEntry 1 }

hh3cPBRMibApplyNexthopVpnName    OBJECT-TYPE
    SYNTAX      DisplayString (SIZE (0..31))
    MAX-ACCESS  read-create
    STATUS      current
    DESCRIPTION "Name of VPN instance where apply next hop action is used."
    ::= { hh3cPBRMibApplyNexthopEntry 2 }

hh3cPBRMibApplyNexthopAddressType     OBJECT-TYPE
    SYNTAX      InetAddressType
    MAX-ACCESS  read-create
    STATUS      current
    DESCRIPTION "Address type of hh3cPBRMibApplyNexthopAddress,
                 which can be IPv4 or IPv6."
    ::= { hh3cPBRMibApplyNexthopEntry 3 }

hh3cPBRMibApplyNexthopAddress     OBJECT-TYPE
    SYNTAX      InetAddress
    MAX-ACCESS  read-create
    STATUS      current
    DESCRIPTION "Next hop IP address of apply next hop action."
    ::= { hh3cPBRMibApplyNexthopEntry 4 }

hh3cPBRMibApplyNexthopTrackId     OBJECT-TYPE
    SYNTAX      Integer32
    MAX-ACCESS  read-create
    STATUS      current
    DESCRIPTION "Identifier of track object related with next hop.
                 Specifies a track entry by its number in the range of 1 to 1024.
                 Setting 0 indicates closing this function.
                "
    ::= { hh3cPBRMibApplyNexthopEntry 5 }

hh3cPBRMibApplyNexthopDirect        OBJECT-TYPE
    SYNTAX      TruthValue
    MAX-ACCESS  read-create
    STATUS      current
    DESCRIPTION "Direct route attribute of next hop
                according to route information."
    DEFVAL { false }
    ::= { hh3cPBRMibApplyNexthopEntry 6 }


hh3cPBRMibApplyNexthopRowStatus  OBJECT-TYPE
    SYNTAX      RowStatus
    MAX-ACCESS  read-create
    STATUS      current
    DESCRIPTION
            "Operation status of this table entry.
            Three actions are used: active,
            createAndGo, and destroy.
            "
    ::= { hh3cPBRMibApplyNexthopEntry 7 }

hh3cPBRMibApplyNexthopInboundVpn        OBJECT-TYPE
    SYNTAX      TruthValue
    MAX-ACCESS  read-create
    STATUS      current
    DESCRIPTION "Specifies the VPN instance where the inbound interface belongs.
                 If the value is set to TRUE, the VPN instance name will be ignored."
    DEFVAL { false }
    ::= { hh3cPBRMibApplyNexthopEntry 8 }

hh3cPBRMibApplyNexthopWeight     OBJECT-TYPE
    SYNTAX      Integer32
    MAX-ACCESS  read-create
    STATUS      current
    DESCRIPTION "Specifies a load sharing weight in the range of 1 and 100 for the next hop."
    DEFVAL { 10 }
    ::= { hh3cPBRMibApplyNexthopEntry 9 }

hh3cPBRMibApplyNexthopPathId     OBJECT-TYPE
    SYNTAX      Integer32
    MAX-ACCESS  read-create
    STATUS      current
    DESCRIPTION "Specifies a service chain by its path ID in the range of 1 and 16777215."
    ::= { hh3cPBRMibApplyNexthopEntry 10 }

hh3cPBRMibApplyNexthopPathIndex     OBJECT-TYPE
    SYNTAX      Integer32
    MAX-ACCESS  read-create
    STATUS      current
    DESCRIPTION "Specifies a node in the service chain as
                 a next hop by its index in the range of 1 and 255."
    ::= { hh3cPBRMibApplyNexthopEntry 11 }

-- PBR policy node apply default next hop action table

hh3cPBRMibApplyDefaultNexthopTable OBJECT-TYPE
    SYNTAX      SEQUENCE OF Hh3cPBRMibApplyDefaultNexthopEntry
    MAX-ACCESS  not-accessible
    STATUS      current
    DESCRIPTION "A table for default next hop actions being used by a policy
                node."
    ::= { hh3cPBRTables 6 }

hh3cPBRMibApplyDefaultNexthopEntry  OBJECT-TYPE
    SYNTAX      Hh3cPBRMibApplyDefaultNexthopEntry
    MAX-ACCESS  not-accessible
    STATUS      current
    DESCRIPTION "An entry for policy node with an action
                 to set default next hop for matching packets.
                "
    INDEX
    {
            hh3cPBRMibPolicyNodeAddrType,
            hh3cPBRMibPolicyName,
            hh3cPBRMibPolicyNodeId,
            hh3cPBRMibApplyDefaultNexthopIndex
    }
    ::= { hh3cPBRMibApplyDefaultNexthopTable 1 }

Hh3cPBRMibApplyDefaultNexthopEntry ::=
    SEQUENCE
    {
            hh3cPBRMibApplyDefaultNexthopIndex       Integer32,
            hh3cPBRMibApplyDefaultNexthopVpnName     DisplayString,
            hh3cPBRMibApplyDefaultNexthopAddressType InetAddressType,
            hh3cPBRMibApplyDefaultNexthopAddress     InetAddress,
            hh3cPBRMibApplyDefaultNexthopTrackId     Integer32,
            hh3cPBRMibApplyDefaultNexthopDirect      TruthValue,
            hh3cPBRMibApplyDefaultNexthopRowStatus   RowStatus,
            hh3cPBRMibApplyDefNexthopInbVpn          TruthValue,
            hh3cPBRMibApplyDefNexthopPathId          Integer32,
            hh3cPBRMibApplyDefNexthopPathInd         Integer32
    }

hh3cPBRMibApplyDefaultNexthopIndex    OBJECT-TYPE
    SYNTAX      Integer32 (0..2147483647)
    MAX-ACCESS  not-accessible
    STATUS      current
    DESCRIPTION "Index of default next hop for the apply
                default next hop action."
    ::= { hh3cPBRMibApplyDefaultNexthopEntry 1 }

hh3cPBRMibApplyDefaultNexthopVpnName    OBJECT-TYPE
    SYNTAX      DisplayString (SIZE (0..31))
    MAX-ACCESS  read-create
    STATUS      current
    DESCRIPTION "Name of VPN instance where apply default next hop action
                 is used."
    ::= { hh3cPBRMibApplyDefaultNexthopEntry 2 }

hh3cPBRMibApplyDefaultNexthopAddressType     OBJECT-TYPE
    SYNTAX      InetAddressType
    MAX-ACCESS  read-create
    STATUS      current
    DESCRIPTION "Address type of hh3cPBRMibApplyDefaultNexthopAddress,
                 which can be IPv4 or IPv6."
    ::= { hh3cPBRMibApplyDefaultNexthopEntry 3 }

hh3cPBRMibApplyDefaultNexthopAddress     OBJECT-TYPE
    SYNTAX      InetAddress
    MAX-ACCESS  read-create
    STATUS      current
    DESCRIPTION "Next hop IP address of apply default next hop action."
    ::= { hh3cPBRMibApplyDefaultNexthopEntry 4 }

hh3cPBRMibApplyDefaultNexthopTrackId     OBJECT-TYPE
    SYNTAX      Integer32
    MAX-ACCESS  read-create
    STATUS      current
    DESCRIPTION "Identifier of track object related with default next hop.
                 Specifies a track entry by its number in the range of 1 to 1024.
                 Setting 0 indicates closing this function."
    ::= { hh3cPBRMibApplyDefaultNexthopEntry 5 }

hh3cPBRMibApplyDefaultNexthopDirect        OBJECT-TYPE
    SYNTAX      TruthValue
    MAX-ACCESS  read-create
    STATUS      current
    DESCRIPTION "Direct route attribute of apply default next hop
                address according to route information."
    DEFVAL { false }
    ::= { hh3cPBRMibApplyDefaultNexthopEntry 6 }

hh3cPBRMibApplyDefaultNexthopRowStatus  OBJECT-TYPE
    SYNTAX      RowStatus
    MAX-ACCESS  read-create
    STATUS      current
    DESCRIPTION
            "Operation status of this table entry.
            Three actions are used: active,
            createAndGo, and destroy.
            "
    ::= { hh3cPBRMibApplyDefaultNexthopEntry 7 }

hh3cPBRMibApplyDefNexthopInbVpn        OBJECT-TYPE
    SYNTAX      TruthValue
    MAX-ACCESS  read-create
    STATUS      current
    DESCRIPTION "Specifies the VPN instance where the inbound interface belongs.
                If the value is set to TRUE, the VPN instance name will be ignored."
    DEFVAL { false }
    ::= { hh3cPBRMibApplyDefaultNexthopEntry 8 }

hh3cPBRMibApplyDefNexthopPathId     OBJECT-TYPE
    SYNTAX      Integer32
    MAX-ACCESS  read-create
    STATUS      current
    DESCRIPTION "Specifies a service chain by its path ID in the range of 1 and 16777215."
    ::= { hh3cPBRMibApplyDefaultNexthopEntry 9 }

hh3cPBRMibApplyDefNexthopPathInd     OBJECT-TYPE
    SYNTAX      Integer32
    MAX-ACCESS  read-create
    STATUS      current
    DESCRIPTION "Specifies a node in the service chain as
                 a default next hop by its index in the range of 1 and 255."
    ::= { hh3cPBRMibApplyDefaultNexthopEntry 10 }

END
