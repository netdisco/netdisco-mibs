-- ============================================================================
-- Copyright (c) 2004-2022 New H3C Tech. Co., Ltd. All rights reserved.
--
-- Description: The purpose of this MIB file is to provide the definition of
--              the IPv6 netstream trap.
-- Reference:
-- Version: V1.0
-- History:
-- V1.0 2022-11-16
--   Initial version, created by wangyuqing
-- ============================================================================
HH3C-NETSTREAM6-MIB DEFINITIONS ::= BEGIN

IMPORTS
        hh3cCommon
    FROM HH3C-OID-MIB
        Unsigned32, OBJECT-TYPE, MODULE-IDENTITY, NOTIFICATION-TYPE
    FROM SNMPv2-SMI;

-- Node definitions
hh3cNetstream6 MODULE-IDENTITY
    LAST-UPDATED "202211231800Z"        -- Nov 23, 2022 at 18:00 GMT
    ORGANIZATION
        "New H3C Technologies Co., Ltd."
    CONTACT-INFO
        "Platform Team New H3C Technologies Co., Ltd.
         Hai-Dian District Beijing P.R. China
         http://www.h3c.com
         Zip: 100085"
    DESCRIPTION
        "This MIB file is to provide the definition of the IPv6 netstream."
    REVISION "202211231800Z"
    DESCRIPTION
        "The initial version of this MIB file."
    ::= { hh3cCommon 257}

-- hh3cNetstream6TrapEntry
hh3cNetstream6TrapEntry OBJECT IDENTIFIER ::= { hh3cNetstream6 1 }

hh3cNetstream6TrapEntrys OBJECT IDENTIFIER  ::= { hh3cNetstream6TrapEntry 0 }

hh3cNetstream6TrapEntryTHAlarm NOTIFICATION-TYPE
    OBJECTS
        {
            hh3cNetstream6TrapEntrySpec,
            hh3cNetstream6TrapEntryChassis,
            hh3cNetstream6TrapEntrySlot
        }
    STATUS      current
    DESCRIPTION
        "If the number of netstream6 tables exceeds the maximum value of the board by 80%,
         a trap message is generated and sent to the remote monitoring device."
    ::= { hh3cNetstream6TrapEntrys 1 }

hh3cNetstream6TrapEntryTHResume NOTIFICATION-TYPE
    OBJECTS
        {
            hh3cNetstream6TrapEntrySpec,
            hh3cNetstream6TrapEntryChassis,
            hh3cNetstream6TrapEntrySlot
        }
    STATUS      current
    DESCRIPTION
        "If the number of Netstream6 tables drops below 70% of the board maximum,
         a trap message is generated and sent to the remote monitoring device."
    ::= { hh3cNetstream6TrapEntrys 2 }

hh3cNetstream6TrapEntryObjects OBJECT IDENTIFIER  ::= { hh3cNetstream6TrapEntry 1 }

-- hh3cNetstream6TrapEntryObjects

hh3cNetstream6TrapEntrySpec OBJECT-TYPE
    SYNTAX      Unsigned32
    MAX-ACCESS  accessible-for-notify
    STATUS      current
    DESCRIPTION
        "The Maximum number of entries in the IPv6 netStream cache."
    ::= { hh3cNetstream6TrapEntryObjects 1 }

hh3cNetstream6TrapEntryChassis OBJECT-TYPE
    SYNTAX      Unsigned32
    MAX-ACCESS  accessible-for-notify
    STATUS      current
    DESCRIPTION
        "The information of chassis ID. If the value is 65535, the device is
        not a stacked device ."
    ::= { hh3cNetstream6TrapEntryObjects 2 }

hh3cNetstream6TrapEntrySlot OBJECT-TYPE
    SYNTAX      Unsigned32
    MAX-ACCESS  accessible-for-notify
    STATUS      current
    DESCRIPTION
        "The information of slot."
    ::= { hh3cNetstream6TrapEntryObjects 3 }

END
