-- ============================================================================
-- Copyright (c) 2004-2022 New H3C Tech. Co., Ltd. All rights reserved.
-- Description:  This MIB file is used for configuration of VSRP (Virtual Service
--               Redundancy Protocol).
--                include :1.VSRP Peer trap
-- Reference:
-- Version: V1.0
-- History:
-- V1.0 2022/08/31 created by w22500
-- ============================================================================
HH3C-VSRP-MIB DEFINITIONS ::= BEGIN

IMPORTS
    hh3cCommon
        FROM HH3C-OID-MIB
    OBJECT-TYPE, MODULE-IDENTITY, NOTIFICATION-TYPE
        FROM SNMPv2-SMI
    DisplayString
        FROM SNMPv2-TC;


hh3cVsrp MODULE-IDENTITY
    LAST-UPDATED "202208312041Z"             -- august 31, 2022 at 20:41 GMT
    ORGANIZATION
        "New H3C Tech. Co., Ltd."
    CONTACT-INFO
        "Platform Team New H3C Tech. Co., Ltd.
        Hai-Dian District Beijing P.R. China
        http://www.h3c.com
        Zip:100085
        "
    DESCRIPTION
        "The initial revision of this MIB module."

    REVISION "202208312041Z"             -- august 31, 2022 at 20:41 GMT
    DESCRIPTION
        "The initial revision of this MIB module."
    ::= { hh3cCommon 254 }


--
-- Node definitions
--


-- Describes objects for VSRP peer connect traps
hh3cVsrpTraps OBJECT IDENTIFIER ::= { hh3cVsrp 1 }

hh3cVsrpTrapsPrefix OBJECT IDENTIFIER ::= { hh3cVsrpTraps 0 }
hh3cVsrpPeerConnDownTrap NOTIFICATION-TYPE
    OBJECTS
    {
        hh3cVsrpPeerName,
        hh3cVsrpPeerConnDownReason
    }
    STATUS current
    DESCRIPTION
        "Send trap when the TCP connection of VSRP peer was torn down."
    ::= { hh3cVsrpTrapsPrefix 1 }

hh3cVsrpPeerConnUPTrap NOTIFICATION-TYPE
    OBJECTS
    {
        hh3cVsrpPeerName
    }
    STATUS current
    DESCRIPTION
        "Send traps when the TCP connection of VSRP peer is established."
    ::= { hh3cVsrpTrapsPrefix 2 }

hh3cVsrpInstanceStateChangeTrap NOTIFICATION-TYPE
    OBJECTS
    {
        hh3cVsrpInstanceName,
        hh3cVsrpInstanceOldState,
        hh3cVsrpInstanceNewState,
        hh3cVsrpInstChangeReason
    }
    STATUS current
    DESCRIPTION
        "Send traps when VSRP instance state changed."
    ::= { hh3cVsrpTrapsPrefix 3 }


hh3cVsrpTrapsInfo OBJECT IDENTIFIER ::= { hh3cVsrpTraps 1 }
hh3cVsrpPeerName OBJECT-TYPE
    SYNTAX DisplayString(SIZE (1..31))
    MAX-ACCESS accessible-for-notify
    STATUS current
    DESCRIPTION
        "VSRP Peer name."
    ::= { hh3cVsrpTrapsInfo 1 }

hh3cVsrpPeerConnDownReason OBJECT-TYPE
    SYNTAX DisplayString(SIZE (1..255))
    MAX-ACCESS accessible-for-notify
    STATUS current
    DESCRIPTION
        "The reason for TCP connection torn down."
    ::= { hh3cVsrpTrapsInfo 2 }

hh3cVsrpInstanceName OBJECT-TYPE
    SYNTAX DisplayString(SIZE (1..31))
    MAX-ACCESS accessible-for-notify
    STATUS current
    DESCRIPTION
        "VSRP instance name."
    ::= { hh3cVsrpTrapsInfo 3 }

hh3cVsrpInstanceOldState OBJECT-TYPE
    SYNTAX DisplayString(SIZE (1..255))
    MAX-ACCESS accessible-for-notify
    STATUS current
    DESCRIPTION
        "The old state of VSRP instance."
    ::= { hh3cVsrpTrapsInfo 4 }

hh3cVsrpInstanceNewState OBJECT-TYPE
    SYNTAX DisplayString(SIZE (1..255))
    MAX-ACCESS accessible-for-notify
    STATUS current
    DESCRIPTION
        "The new state of VSRP instance."
    ::= { hh3cVsrpTrapsInfo 5 }

hh3cVsrpInstChangeReason OBJECT-TYPE
    SYNTAX DisplayString(SIZE (1..255))
    MAX-ACCESS accessible-for-notify
    STATUS current
    DESCRIPTION
        "The reason for VSRP instance state change."
    ::= { hh3cVsrpTrapsInfo 6 }

END
