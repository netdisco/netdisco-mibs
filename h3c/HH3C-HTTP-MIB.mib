-- =================================================================
-- Copyright (c) 2004-2022 New H3C Tech. Co., Ltd. All rights reserved.
--
-- Description: HTTP mib
-- Reference:
-- Version: V1.0
-- History:
--  V1.0 Created by xiexiang
--      Initial version 2022-09-13
-- =================================================================
HH3C-HTTP-MIB DEFINITIONS ::= BEGIN

IMPORTS
    MODULE-IDENTITY, OBJECT-TYPE, NOTIFICATION-TYPE
        FROM SNMPv2-SMI
    DisplayString
        FROM SNMPv2-TC
    InetAddressType
        FROM INET-ADDRESS-MIB
    hh3cCommon
        FROM HH3C-OID-MIB;

hh3cHttp MODULE-IDENTITY
    LAST-UPDATED "202209130000Z"
    ORGANIZATION
        "New H3C Tech. Co., Ltd."
    CONTACT-INFO
        "Platform Team New H3C Tech. Co., Ltd.
        Hai-Dian District Beijing P.R. China
        http://www.h3c.com
        Zip:100085"
    DESCRIPTION
        "The MIB module is used for HTTP connection notification."
    REVISION    "202209130000Z"
    DESCRIPTION    "The initial version."
    ::= { hh3cCommon 255 }

-- ==================================================================
--
-- HTTP trap object
--
-- ==================================================================
hh3cHttpObjects OBJECT IDENTIFIER ::= { hh3cHttp 1 }

hh3cHttpConnObjects OBJECT IDENTIFIER ::= { hh3cHttpObjects 1 }

hh3cHttpUserName OBJECT-TYPE
    SYNTAX       DisplayString (SIZE(1..80))
    MAX-ACCESS   accessible-for-notify
    STATUS   current
    DESCRIPTION
    "The name of an HTTP user."
    ::= { hh3cHttpConnObjects 1 }

hh3cHttpUserIPAddressType OBJECT-TYPE
    SYNTAX       InetAddressType
    MAX-ACCESS   accessible-for-notify
    STATUS   current
    DESCRIPTION
    "The IP address type of the HTTP user."
    ::= { hh3cHttpConnObjects 2 }

hh3cHttpUserIPAddress OBJECT-TYPE
    SYNTAX       DisplayString (SIZE(1..80))
    MAX-ACCESS   accessible-for-notify
    STATUS   current
    DESCRIPTION
    "The IP address of the HTTP user."
    ::= { hh3cHttpConnObjects 3 }

hh3cHttpUserService OBJECT-TYPE
    SYNTAX       DisplayString (SIZE(1..80))
    MAX-ACCESS   accessible-for-notify
    STATUS   current
    DESCRIPTION
    "The service type of the HTTP user, such as web and soap."
    ::= { hh3cHttpConnObjects 4 }

hh3cHttpTrap OBJECT IDENTIFIER ::= { hh3cHttp 2 }

hh3cHttpConnTrapPrefix OBJECT IDENTIFIER ::= { hh3cHttpTrap 0 }

hh3cHttpUserLogin NOTIFICATION-TYPE
    OBJECTS {
            hh3cHttpUserName,
            hh3cHttpUserIPAddressType,
            hh3cHttpUserIPAddress,
            hh3cHttpUserService
        }
    STATUS  current
    DESCRIPTION
        "This notification is generated when a user logs in successfully through HTTP."
::= { hh3cHttpConnTrapPrefix 1 }

hh3cHttpUserLoginFail NOTIFICATION-TYPE
    OBJECTS {
            hh3cHttpUserName,
            hh3cHttpUserIPAddressType,
            hh3cHttpUserIPAddress,
            hh3cHttpUserService
        }
    STATUS  current
    DESCRIPTION
        "This notification is generated when a user fails to log in through HTTP."
::= { hh3cHttpConnTrapPrefix 2 }

hh3cHttpUserLogout NOTIFICATION-TYPE
    OBJECTS {
            hh3cHttpUserName,
            hh3cHttpUserIPAddressType,
            hh3cHttpUserIPAddress,
            hh3cHttpUserService
        }
    STATUS  current
    DESCRIPTION
        "This notification is generated when a user logs out successfully through HTTP."
::= { hh3cHttpConnTrapPrefix 3 }

END
