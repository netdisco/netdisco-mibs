-- =================================================================
-- Copyright (C) 2006 by H3C TECHNOLOGIES.  All rights reserved.
--
-- Description: Mirror group MIB
-- Reference:
-- Version: V1.0
-- History:
--   2006-01-10 created by xialei
--     Initial version V1.0
-- =================================================================
-- =================================================================
--
-- Import and definition
--
-- =================================================================
HH3C-MIRRORGROUP-MIB DEFINITIONS ::= BEGIN

IMPORTS

    hh3cCommon
        FROM HH3C-OID-MIB
    RowStatus
        FROM SNMPv2-TC
    Integer32, OBJECT-TYPE, MODULE-IDENTITY
        FROM SNMPv2-SMI;

    hh3cMirrGroup MODULE-IDENTITY
        LAST-UPDATED "200601131403Z"
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "This MIB defines objects for managing mirror group."
        REVISION "200601101903Z"
        DESCRIPTION
            "The initial revision of this MIB module."
        ::= { hh3cCommon  68 }

    hh3cMGInfoObjects OBJECT IDENTIFIER ::= {  hh3cMirrGroup 1  }

    hh3cMGObjects OBJECT IDENTIFIER ::= {  hh3cMGInfoObjects 1  }

    hh3cMGTable OBJECT-TYPE
        SYNTAX      SEQUENCE OF Hh3cMGEntry
        MAX-ACCESS  not-accessible
        STATUS      current
        DESCRIPTION
            "A list of mirror group entries."
        ::= { hh3cMGObjects 1 }

    hh3cMGEntry OBJECT-TYPE
        SYNTAX      Hh3cMGEntry
        MAX-ACCESS  not-accessible
        STATUS      current
        DESCRIPTION
            "A list of parameters that describe a mirror group to be created."
        INDEX
        {
            hh3cMGID
        }
      ::= { hh3cMGTable 1 }

    Hh3cMGEntry ::=
        SEQUENCE
        {
            hh3cMGID           Integer32,
            hh3cMGType         INTEGER,
            hh3cMGStatus       INTEGER,
            hh3cMGRowStatus    RowStatus
        }

    hh3cMGID OBJECT-TYPE
        SYNTAX      Integer32
        MAX-ACCESS  not-accessible
        STATUS      current
        DESCRIPTION
            "An index that uniquely identifies an entry in the mirror group table."
        ::= { hh3cMGEntry 1 }

    hh3cMGType OBJECT-TYPE
        SYNTAX      INTEGER
                    {
                        local(1),
                        remoteSource(2),
                        remoteDestination(3)
                    }
        MAX-ACCESS  read-create
        STATUS      current
        DESCRIPTION
            "GroupType."
        ::= { hh3cMGEntry 2 }

    hh3cMGStatus OBJECT-TYPE
        SYNTAX      INTEGER
                    {
                        active(1),
                        inactive(2)
                    }
        MAX-ACCESS  read-only
        STATUS      current
        DESCRIPTION
            "The status of a mirror group.  A mirror group will be inactive
            when it was created.

            The status of a mirror group can be changed automatically from inactive
            to active when appropriate conditions were met, also, it can be changed
            automatically from active to inactive when these conditions disappeared.

            Followings are conditions for a mirror group to become active:
              group type          conditions
              ============================================================================
              local               mirroring-port, monitor-port
              remoteSource        mirroring-port, remote-probe vlan, reflector-port(may not
                                  be supported by some products)
              remoteDestination   monitor-port, remote-probe vlan
              "
        ::= { hh3cMGEntry 3 }

    hh3cMGRowStatus OBJECT-TYPE
        SYNTAX      RowStatus
        MAX-ACCESS  read-create
        STATUS      current
        DESCRIPTION
            "RowStatus"
        ::= { hh3cMGEntry 4 }

    hh3cMGMirrorIfObjects OBJECT IDENTIFIER ::= {  hh3cMGInfoObjects 2  }

    hh3cMGMirrorIfTable OBJECT-TYPE
        SYNTAX      SEQUENCE OF Hh3cMGMirrorIfEntry
        MAX-ACCESS  not-accessible
        STATUS      current
        DESCRIPTION
            "A list of mirror group mirroring-port entries."
        ::= { hh3cMGMirrorIfObjects 1 }

    hh3cMGMirrorIfEntry OBJECT-TYPE
        SYNTAX      Hh3cMGMirrorIfEntry
        MAX-ACCESS  not-accessible
        STATUS      current
        DESCRIPTION
            "A list of parameters that describe a mirroring-port to be added to
            a mirror group."
        INDEX
        {
            hh3cMGID,
            hh3cMGMirrorIfIndex,
            hh3cMGMirrorDirection
        }
        ::= { hh3cMGMirrorIfTable 1 }

    Hh3cMGMirrorIfEntry ::=
        SEQUENCE
        {
            hh3cMGMirrorIfIndex      Integer32,
            hh3cMGMirrorDirection    INTEGER,
            hh3cMGMirrorRowStatus    RowStatus
        }

    hh3cMGMirrorIfIndex OBJECT-TYPE
        SYNTAX      Integer32
        MAX-ACCESS  not-accessible
        STATUS      current
        DESCRIPTION
            "IfIndex of mirror group mirroring-port."
        ::= { hh3cMGMirrorIfEntry 1 }

    hh3cMGMirrorDirection OBJECT-TYPE
        SYNTAX      INTEGER
                    {
                        inbound(1),
                        outbound(2),
                        both(3)
                    }
        MAX-ACCESS  not-accessible
        STATUS      current
        DESCRIPTION
            "Mirror direction of mirroring-port.  Once mirror direction
             was configured for a mirroring-port, it can not be changed
             unless the mirroring-port was removed from mirror group.

             If a mirror port is configured with two mirror directions
             'outbound' and 'inbound', though it is functionally equal
             to 'both', it will be handled as two table items.  If a
             mirror port is configured with mirror direction 'outbound'
             or 'inbound', or both of them, it will not be allowed to
             configure 'both', more details please refer to mirror group
             manual."
        ::= { hh3cMGMirrorIfEntry 2 }

    hh3cMGMirrorRowStatus OBJECT-TYPE
        SYNTAX      RowStatus
        MAX-ACCESS  read-create
        STATUS      current
        DESCRIPTION
            "RowStatus"
        ::= { hh3cMGMirrorIfEntry 3 }

    hh3cMGMonitorIfObjects OBJECT IDENTIFIER ::= {  hh3cMGInfoObjects 3  }

    hh3cMGMonitorIfTable OBJECT-TYPE
        SYNTAX      SEQUENCE OF Hh3cMGMonitorIfEntry
        MAX-ACCESS  not-accessible
        STATUS      current
        DESCRIPTION
            "A list of mirror group monitor-port entries."
        ::= { hh3cMGMonitorIfObjects 1 }

    hh3cMGMonitorIfEntry OBJECT-TYPE
        SYNTAX      Hh3cMGMonitorIfEntry
        MAX-ACCESS  not-accessible
        STATUS      current
        DESCRIPTION
            "A list of parameters that describe a monitor-port to be added to
            a mirror group."
        INDEX
        {
            hh3cMGID,
            hh3cMGMonitorIfIndex
        }
        ::= { hh3cMGMonitorIfTable 1 }

    Hh3cMGMonitorIfEntry ::=
        SEQUENCE
        {
            hh3cMGMonitorIfIndex      Integer32,
            hh3cMGMonitorRowStatus    RowStatus
        }

    hh3cMGMonitorIfIndex OBJECT-TYPE
        SYNTAX      Integer32
        MAX-ACCESS  not-accessible
        STATUS      current
        DESCRIPTION
            "IfIndex of mirror group monitor-port."
        ::= { hh3cMGMonitorIfEntry 1 }

    hh3cMGMonitorRowStatus OBJECT-TYPE
        SYNTAX      RowStatus
        MAX-ACCESS  read-create
        STATUS      current
        DESCRIPTION
            "RowStatus"
        ::= { hh3cMGMonitorIfEntry 2 }

    hh3cMGReflectorIfObjects OBJECT IDENTIFIER ::= {  hh3cMGInfoObjects 4  }

    hh3cMGReflectorIfTable OBJECT-TYPE
        SYNTAX      SEQUENCE OF Hh3cMGReflectorIfEntry
        MAX-ACCESS  not-accessible
        STATUS      current
        DESCRIPTION
            "A list of mirror group reflector-port entries."
        ::= { hh3cMGReflectorIfObjects 1 }

    hh3cMGReflectorIfEntry OBJECT-TYPE
        SYNTAX      Hh3cMGReflectorIfEntry
        MAX-ACCESS  not-accessible
        STATUS      current
        DESCRIPTION
            "A list of parameters that describe a reflector-port to be added to
            a mirror group."
        INDEX
        {
            hh3cMGID,
            hh3cMGReflectorIfIndex
        }
        ::= { hh3cMGReflectorIfTable 1 }

    Hh3cMGReflectorIfEntry ::=
        SEQUENCE
        {
            hh3cMGReflectorIfIndex      Integer32,
            hh3cMGReflectorRowStatus    RowStatus
        }

    hh3cMGReflectorIfIndex OBJECT-TYPE
        SYNTAX      Integer32
        MAX-ACCESS  not-accessible
        STATUS      current
        DESCRIPTION
            "IfIndex of mirror group reflector-port."
        ::= { hh3cMGReflectorIfEntry 1 }

    hh3cMGReflectorRowStatus OBJECT-TYPE
        SYNTAX      RowStatus
        MAX-ACCESS  read-create
        STATUS      current
        DESCRIPTION
            "RowStatus"
        ::= { hh3cMGReflectorIfEntry 2 }

    hh3cMGRprobeVlanObjects OBJECT IDENTIFIER ::= {  hh3cMGInfoObjects 5  }

    hh3cMGRprobeVlanTable OBJECT-TYPE
        SYNTAX      SEQUENCE OF Hh3cMGRprobeVlanEntry
        MAX-ACCESS  not-accessible
        STATUS      current
        DESCRIPTION
            "A list of mirror group remote-probe vlan entries."
        ::= { hh3cMGRprobeVlanObjects 1 }

    hh3cMGRprobeVlanEntry OBJECT-TYPE
        SYNTAX      Hh3cMGRprobeVlanEntry
        MAX-ACCESS  not-accessible
        STATUS      current
        DESCRIPTION
            "A list of parameters that describe a remote-probe vlan to be added
            to a mirror group.  Details about remote-probe vlan please refer to
            mirror group manual."
        INDEX
        {
            hh3cMGID,
            hh3cMGRprobeVlanID
        }
        ::= { hh3cMGRprobeVlanTable 1 }

    Hh3cMGRprobeVlanEntry ::=
        SEQUENCE
        {
            hh3cMGRprobeVlanID           Integer32,
            hh3cMGRprobeVlanRowStatus    RowStatus
        }

    hh3cMGRprobeVlanID OBJECT-TYPE
        SYNTAX      Integer32(1..4094)
        MAX-ACCESS  not-accessible
        STATUS      current
        DESCRIPTION
            "An index that uniquely identifies an entry in the remote-probe vlan table."
        ::= { hh3cMGRprobeVlanEntry 1 }

    hh3cMGRprobeVlanRowStatus OBJECT-TYPE
        SYNTAX      RowStatus
        MAX-ACCESS  read-create
        STATUS      current
        DESCRIPTION
            "RowStatus"
        ::= { hh3cMGRprobeVlanEntry 2 }

END
