-- ==========================================================================
-- Copyright (c) 2004-2017 New H3C Tech. Co., Ltd.  All rights reserved.
--
-- Description: The MIB is designed to show information on high-end driver products.
-- Reference:
-- Version: V1.0
-- History:
-- V1.0  2017-09 Initial version created by meirongjun 14958.
-- ==========================================================================
HH3C-SECHIGH-MIB DEFINITIONS ::= BEGIN

IMPORTS
    hh3cCommon
        FROM HH3C-OID-MIB
    MODULE-IDENTITY, OBJECT-TYPE, Integer32, NOTIFICATION-TYPE
        FROM SNMPv2-SMI;         -- [RFC2578]

hh3cSecHigh MODULE-IDENTITY
    LAST-UPDATED "201709162020Z"
    ORGANIZATION
        "New H3C Technologies Co., Ltd."
    CONTACT-INFO
        "Platform Team New H3C Tech. Co., Ltd.
        Hai-Dian District Beijing P.R. China
        http://www.h3c.com
        Zip:100085
        "
    DESCRIPTION
        "The private MIB file includes the information on high-end driver products."
    REVISION      "201709162020Z"
    DESCRIPTION
        "Initial revision of this MIB module."
    ::= { hh3cCommon 171 }
--
-- Node definitions
--
hh3cSecHighMonitor OBJECT IDENTIFIER ::= { hh3cSecHigh 1 }


--
-- hh3cSecHighHgMonitorAlarm context table definitions
--
hh3cSecHighHgMonitorAlarmVar OBJECT IDENTIFIER   ::= { hh3cSecHighMonitor 1 }

hh3cSecHighHgMonitorAlarmType OBJECT-TYPE
    SYNTAX      Integer32
    MAX-ACCESS  accessible-for-notify
    STATUS      current
    DESCRIPTION
            "Type of the alarm,0 represent recovery normal,1 represent link status error,
            2 represent Some packets were dropped on the link."
    ::= { hh3cSecHighHgMonitorAlarmVar 1 }

hh3cSecHighHgMonitorAlarmSrcChassis OBJECT-TYPE
    SYNTAX      Integer32
    MAX-ACCESS  accessible-for-notify
    STATUS      current
    DESCRIPTION
            "Number of the chassis where the source end of the alarmed link resides."
    ::= { hh3cSecHighHgMonitorAlarmVar 2 }

hh3cSecHighHgMonitorAlarmSrcSlot OBJECT-TYPE
    SYNTAX      Integer32
    MAX-ACCESS  accessible-for-notify
    STATUS      current
    DESCRIPTION
            "Number of the slot where the source end of the alarmed link resides."
    ::= { hh3cSecHighHgMonitorAlarmVar 3 }

hh3cSecHighHgMonitorAlarmSrcChip OBJECT-TYPE
    SYNTAX      Integer32
    MAX-ACCESS  accessible-for-notify
    STATUS      current
    DESCRIPTION
            "Number of the chip where the source end of the alarmed link resides."
    ::= { hh3cSecHighHgMonitorAlarmVar 4 }

hh3cSecHighHgMonitorAlarmSrcPort OBJECT-TYPE
    SYNTAX      Integer32
    MAX-ACCESS  accessible-for-notify
    STATUS      current
    DESCRIPTION
            "Number of the port where the source end of the alarmed link resides."
    ::= { hh3cSecHighHgMonitorAlarmVar 5 }

hh3cSecHighHgMonitorAlarmDstChassis OBJECT-TYPE
    SYNTAX      Integer32
    MAX-ACCESS  accessible-for-notify
    STATUS      current
    DESCRIPTION
            "Number of the chassis where the destination end of the alarmed link resides."
    ::= { hh3cSecHighHgMonitorAlarmVar 6 }

hh3cSecHighHgMonitorAlarmDstSlot OBJECT-TYPE
    SYNTAX      Integer32
    MAX-ACCESS  accessible-for-notify
    STATUS      current
    DESCRIPTION
            "Number of the slot where the destination end of the alarmed link resides."
    ::= { hh3cSecHighHgMonitorAlarmVar 7 }

hh3cSecHighHgMonitorAlarmDstChip OBJECT-TYPE
    SYNTAX      Integer32
    MAX-ACCESS  accessible-for-notify
    STATUS      current
    DESCRIPTION
            "Number of the chip where the destination end of the alarmed link resides."
    ::= { hh3cSecHighHgMonitorAlarmVar 8 }

hh3cSecHighHgMonitorAlarmDstPort OBJECT-TYPE
    SYNTAX      Integer32
    MAX-ACCESS  accessible-for-notify
    STATUS      current
    DESCRIPTION
            "Number of the port where the destination end of the alarmed link resides."
    ::= { hh3cSecHighHgMonitorAlarmVar 9 }

hh3cSecHighHgMonitorAlarmReason OBJECT-TYPE
    SYNTAX      OCTET STRING(SIZE(0..512))
    MAX-ACCESS  accessible-for-notify
    STATUS      current
    DESCRIPTION
            "Cause of the alarm."
    ::= { hh3cSecHighHgMonitorAlarmVar 10 }



-- ===============================================
-- Definition of traps.
-- ===============================================
hh3cSecHighHgMonitorAlarmTrap OBJECT IDENTIFIER ::= { hh3cSecHighMonitor 2 }
hh3cSecHighHgMonitorAlarmNotifications OBJECT IDENTIFIER ::= { hh3cSecHighHgMonitorAlarmTrap 0 }

hh3cSecHighHgMonitorAlarmNotification NOTIFICATION-TYPE
    OBJECTS {
                hh3cSecHighHgMonitorAlarmType,
                hh3cSecHighHgMonitorAlarmSrcChassis,
                hh3cSecHighHgMonitorAlarmSrcSlot,
                hh3cSecHighHgMonitorAlarmSrcChip,
                hh3cSecHighHgMonitorAlarmSrcPort,
                hh3cSecHighHgMonitorAlarmDstChassis,
                hh3cSecHighHgMonitorAlarmDstSlot,
                hh3cSecHighHgMonitorAlarmDstChip,
                hh3cSecHighHgMonitorAlarmDstPort,
                hh3cSecHighHgMonitorAlarmReason
            }
    STATUS     current
    DESCRIPTION
           "This notification is generated when an HgMonitor alarm is generated."
    ::= { hh3cSecHighHgMonitorAlarmNotifications 1 }
END
