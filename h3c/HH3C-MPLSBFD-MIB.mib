-- =============================================================================
-- Copyright (c) 2004-2023 New H3C Tech.  Co.  , Ltd.  All rights reserved.
--
-- Description: Multiprotocol Label Switching BFD MIB
-- Reference:
-- Version: V1.0
-- History:
--   V1.0 2023-03-14 Initial version Created by Longlewen
-- =============================================================================
HH3C-MPLSBFD-MIB DEFINITIONS ::= BEGIN
IMPORTS
    MODULE-IDENTITY, OBJECT-TYPE, NOTIFICATION-TYPE
        FROM SNMPv2-SMI
    hh3cCommon
        FROM HH3C-OID-MIB
    ;

-- =============================================================================
-- module identity part
-- =============================================================================
hh3cMplsBfd MODULE-IDENTITY
    LAST-UPDATED
        "202303141400Z"   -- Mar 14, 2023 at 14:00 GMT
    ORGANIZATION
        "New H3C Technologies Co., Ltd."
    CONTACT-INFO
        "No.466 Changhe Road, Binjiang District, Hangzhou, Zhejiang
         http://www.h3c.com
         Zip: 310052"
    DESCRIPTION
        "Multiprotocol Label Switching Bfd MIB"
    REVISION
        "202303141400Z"   -- Mar 14, 2023 at 14:00 GMT
    DESCRIPTION
        "Initial version of this MIB."
    ::= { hh3cCommon 261 }

-- =============================================================================
-- Top level components of this MIB module.
-- =============================================================================
hh3cMplsBfdNotifications OBJECT IDENTIFIER ::= { hh3cMplsBfd 0 }

hh3cMplsBfdObjects      OBJECT IDENTIFIER  ::= { hh3cMplsBfd 1 }

hh3cMplsBfdScalarGroup   OBJECT IDENTIFIER ::= { hh3cMplsBfdObjects 1 }

hh3cMplsBfdBaseInfo    OBJECT-TYPE
    SYNTAX      OCTET STRING (SIZE (1..127))
    MAX-ACCESS  accessible-for-notify
    STATUS      current
    DESCRIPTION
        "The base information of MPLS Bfd."
    ::= { hh3cMplsBfdScalarGroup 1 }

hh3cMplsBfdExtInfo    OBJECT-TYPE
    SYNTAX      OCTET STRING (SIZE (1..127))
    MAX-ACCESS  accessible-for-notify
    STATUS      current
    DESCRIPTION
        "The external information of MPLS Bfd."
    ::= { hh3cMplsBfdScalarGroup 2 }

-- =============================================================================
-- Notifications
-- =============================================================================
hh3cMplsBfdTracerouteFailed  NOTIFICATION-TYPE
    OBJECTS {
            hh3cMplsBfdBaseInfo,
            hh3cMplsBfdExtInfo
            }
    STATUS      current
    DESCRIPTION
      "This notification is generated when the echo reply is failed."
    ::= { hh3cMplsBfdNotifications 1 }

-- =============================================================================
-- End of notifications.
-- =============================================================================

END
