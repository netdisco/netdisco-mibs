-- =================================================================
-- Copyright (c) 2004-2009 New H3C Tech. Co., Ltd. All rights reserved.
--
-- Description:
-- Reference:
-- Version: V1.0
-- History:
-- V1.0 created by zhanghaiyang.
--    Initial version of the MIB
-- =================================================================
HH3C-RS485-MIB DEFINITIONS ::= BEGIN

IMPORTS
        hh3cCommon
    FROM HH3C-OID-MIB
        ifIndex
    FROM IF-MIB
        Integer32, OBJECT-TYPE, MODULE-IDENTITY
    FROM SNMPv2-SMI
        InetAddressType, InetAddress
    FROM INET-ADDRESS-MIB
        DisplayString, RowStatus
    FROM SNMPv2-TC;


hh3cRS485 MODULE-IDENTITY
    LAST-UPDATED "200910210000Z" -- October 21, 2009
    ORGANIZATION
        "New H3C Technologies Co., Ltd."
    CONTACT-INFO
        "Platform Team New H3C Technologies Co., Ltd.
         Hai-Dian District Beijing P.R. China
         http://www.h3c.com
         Zip: 100085"
    DESCRIPTION
        "The objects in this MIB module are used to manage RS485 interfaces,
        and manage sessions on them."
    ::= { hh3cCommon 109 }

--
-- hh3cRS485Properties
--
hh3cRS485Properties OBJECT IDENTIFIER ::= { hh3cRS485 1 }

--
-- hh3cRS485PropertiesTable
--

hh3cRS485PropertiesTable OBJECT-TYPE
    SYNTAX          SEQUENCE OF Hh3cRS485PropertiesEntry
    MAX-ACCESS      not-accessible
    STATUS          current
    DESCRIPTION
            "Propertie table."
    ::= { hh3cRS485Properties 1 }

hh3cRS485PropertiesEntry OBJECT-TYPE
    SYNTAX          Hh3cRS485PropertiesEntry
    MAX-ACCESS      not-accessible
    STATUS          current
    DESCRIPTION
            "Propertie entry."
    INDEX           { ifIndex }
    ::= { hh3cRS485PropertiesTable 1 }

Hh3cRS485PropertiesEntry ::=
    SEQUENCE{
        hh3cRS485RawSessionNextIndex
            Integer32,
        hh3cRS485BaudRate
            INTEGER,
        hh3cRS485DataBits
            INTEGER,
        hh3cRS485Parity
            INTEGER,
        hh3cRS485StopBits
            INTEGER,
        hh3cRS485FlowControl
            INTEGER,
        hh3cRS485TXCharacters
            Integer32,
        hh3cRS485RXCharacters
            Integer32,
        hh3cRS485TXErrCharacters
            Integer32,
        hh3cRS485RXErrCharacters
            Integer32,
        hh3cRS485ResetCharacters
            INTEGER
    }

hh3cRS485RawSessionNextIndex OBJECT-TYPE
    SYNTAX          Integer32 (1..64)
    MAX-ACCESS      read-only
    STATUS          current
    DESCRIPTION
        "The next valid index of raw sessions, from 1 to 64,
        which session has been created.

        When there is no valid index left, it will return 0."
    ::= { hh3cRS485PropertiesEntry 1 }

hh3cRS485BaudRate OBJECT-TYPE
    SYNTAX          INTEGER {
                        bautRate300(1),         -- baud rate 300
                        bautRate600(2),         -- baud rate 600
                        bautRate1200(3),        -- baud rate 1200
                        bautRate2400(4),        -- baud rate 2400
                        bautRate4800(5),        -- baud rate 4800
                        bautRate9600(6),        -- baud rate 9600
                        bautRate19200(7),       -- baud rate 19200
                        bautRate38400(8),       -- baud rate 38400
                        bautRate57600(9),       -- baud rate 57600
                        bautRate115200(10)      -- baud rate 115200
                    }
    MAX-ACCESS      read-write
    STATUS          current
    DESCRIPTION
            "The port's baud rate."
    DEFVAL          { bautRate9600 }
    ::= { hh3cRS485PropertiesEntry 2 }

hh3cRS485DataBits OBJECT-TYPE
    SYNTAX          INTEGER {
                        five(1),            -- 5 data bits
                        six(2),             -- 6 data bits
                        seven(3),           -- 7 data bits
                        eight(4)            -- 8 data bits
                    }
    UNITS           "bit"
    MAX-ACCESS      read-write
    STATUS          current
    DESCRIPTION
            "The port's number of data bits in a character."
    DEFVAL          { eight }
    ::= { hh3cRS485PropertiesEntry 3 }

hh3cRS485Parity OBJECT-TYPE
    SYNTAX          INTEGER {
                        none(1),
                        odd(2),
                        even(3),
                        mark(4),
                        space(5)
                    }
    MAX-ACCESS      read-write
    STATUS          current
    DESCRIPTION
            "The port's sense of a character parity bit."
    DEFVAL          { none }
    ::= { hh3cRS485PropertiesEntry 4 }

hh3cRS485StopBits OBJECT-TYPE
    SYNTAX          INTEGER {
                        one(1),               -- 1 stop bit
                        two(2),               -- 2 stop bits
                        oneAndHalf(3)         -- 1.5 stop bits
                    }
    UNITS           "bit"
    MAX-ACCESS      read-write
    STATUS          current
    DESCRIPTION
            "The port's number of stop bits."
    DEFVAL          { one }
    ::= { hh3cRS485PropertiesEntry 5 }

hh3cRS485FlowControl OBJECT-TYPE
    SYNTAX          INTEGER{
                        none(1),
                        hardware(2),
                        xonOrxoff(3)
                    }
    MAX-ACCESS      read-write
    STATUS          current
    DESCRIPTION
            "The port's type of input flow control.  'none'
             indicates no flow control at this level.
             'hardware' indicates use of hardware signals.
             'xonOrxoff' indicates use of software function."
    DEFVAL          { none }
    ::= { hh3cRS485PropertiesEntry 6 }

hh3cRS485TXCharacters OBJECT-TYPE
    SYNTAX          Integer32
    MAX-ACCESS      read-only
    STATUS          current
    DESCRIPTION
            "The number of output characters for the port."
    ::= { hh3cRS485PropertiesEntry 7 }

hh3cRS485RXCharacters OBJECT-TYPE
    SYNTAX          Integer32
    MAX-ACCESS      read-only
    STATUS          current
    DESCRIPTION
            "The number of input characters for the port."
    ::= { hh3cRS485PropertiesEntry 8 }

hh3cRS485TXErrCharacters OBJECT-TYPE
    SYNTAX          Integer32
    MAX-ACCESS      read-only
    STATUS          current
    DESCRIPTION
            "The number of output error characters for the port."
    ::= { hh3cRS485PropertiesEntry 9 }

hh3cRS485RXErrCharacters OBJECT-TYPE
    SYNTAX          Integer32
    MAX-ACCESS      read-only
    STATUS          current
    DESCRIPTION
            "The number of input error characters for the port."
    ::= { hh3cRS485PropertiesEntry 10 }

hh3cRS485ResetCharacters OBJECT-TYPE
    SYNTAX          INTEGER {
                        counting(1),
                        clear(2)
                    }
    MAX-ACCESS      read-write
    STATUS          current
    DESCRIPTION
            "Reset the counters to zero, inlucding hh3cRS485TXCharacters,
            hh3cRS485RXCharacters, hh3cRS485TXErrCharacters and
            hh3cRS485RXErrCharacters."
    DEFVAL          { counting }
    ::= { hh3cRS485PropertiesEntry 11 }

--
-- hh3cRS485RawSessions
--
hh3cRS485RawSessions OBJECT IDENTIFIER ::= { hh3cRS485 2 }

--
-- hh3cRS485RawSessionSummary
--
hh3cRS485RawSessionSummary OBJECT IDENTIFIER ::= { hh3cRS485RawSessions 1 }

hh3cRS485RawSessionMaxNum OBJECT-TYPE
    SYNTAX          Integer32 (1..64)
    MAX-ACCESS      read-only
    STATUS          current
    DESCRIPTION
        "The max number of raw sessions what we can support."
    ::= { hh3cRS485RawSessionSummary 1 }

--
-- hh3cRS485RawSessionTable
--
hh3cRS485RawSessionTable OBJECT-TYPE
    SYNTAX          SEQUENCE OF Hh3cRS485RawSessionEntry
    MAX-ACCESS      not-accessible
    STATUS          current
    DESCRIPTION
        "RS485 raw session table.  Data recieved from rs485 will be sent to
        the destination by raw sockets."
    ::= { hh3cRS485RawSessions 2}

hh3cRS485RawSessionEntry OBJECT-TYPE
    SYNTAX          Hh3cRS485RawSessionEntry
    MAX-ACCESS      not-accessible
    STATUS          current
    DESCRIPTION
            "Parameters of a session, including remote IP address, remote port,
            local port, and so on."
    INDEX           { ifIndex, hh3cRS485SessionIndex }
    ::= { hh3cRS485RawSessionTable 1 }

Hh3cRS485RawSessionEntry ::=
    SEQUENCE{
        hh3cRS485SessionIndex
            Integer32,
        hh3cRS485SessionType
            INTEGER,
        hh3cRS485SessionAddType
            InetAddressType,
        hh3cRS485SessionRemoteIP
            InetAddress,
        hh3cRS485SessionRemotePort
            Integer32,
        hh3cRS485SessionLocalPort
            Integer32,
        hh3cRS485SessionStatus
            RowStatus
    }

hh3cRS485SessionIndex OBJECT-TYPE
    SYNTAX          Integer32 (1..64)
    MAX-ACCESS      not-accessible
    STATUS          current
    DESCRIPTION
            "Raw session index."
    ::= { hh3cRS485RawSessionEntry 1 }

hh3cRS485SessionType OBJECT-TYPE
    SYNTAX          INTEGER {
                        udp(1),
                        tcpClient(2),
                        tcpServer(3)
                    }
    MAX-ACCESS      read-write
    STATUS          current
    DESCRIPTION
            "The type of a session.  A session can use UDP socket,
            TCP socket as a client, or TCP socket as a server."
    ::= { hh3cRS485RawSessionEntry 2 }

hh3cRS485SessionAddType OBJECT-TYPE
    SYNTAX          InetAddressType
    MAX-ACCESS      read-write
    STATUS          current
    DESCRIPTION
            "This object indicates the transport type of the
             address contained in hh3cRS485SessionRemoteIP object."
    DEFVAL          { ipv4 }
    ::= { hh3cRS485RawSessionEntry 3 }

hh3cRS485SessionRemoteIP OBJECT-TYPE
    SYNTAX          InetAddress
    MAX-ACCESS      read-create
    STATUS          current
    DESCRIPTION
            "The IP of remote entry.

            When session type is 'udp', this is the IP of the peer.

            When session type is 'tcpClient', this is the IP of the server .

            When session type is 'tcpServer', this is invalid,
            it will return 0.
            "
    ::= { hh3cRS485RawSessionEntry 4 }

hh3cRS485SessionRemotePort OBJECT-TYPE
    SYNTAX          Integer32 (1024..65535)
    MAX-ACCESS      read-create
    STATUS          current
    DESCRIPTION
            "The port of remote entry.

            When session type is 'udp', this is port of the peer.

            When session type is 'tcpClient', this is the port of the server.

            When session type is 'tcpServer', this is invalid,
            it will return 0.
            "
    ::= { hh3cRS485RawSessionEntry 5 }

hh3cRS485SessionLocalPort OBJECT-TYPE
    SYNTAX          Integer32 (1024..65535)
    MAX-ACCESS      read-create
    STATUS          current
    DESCRIPTION
            "Local socket port.

            When session type is 'udp', this is local UDP socket port.

            When session type is 'tcpClient', this is invalid,
            it will return 0.

            When session type is 'tcpServer', this is the local port which
            will be listened.
            "
    ::= { hh3cRS485RawSessionEntry 6 }

hh3cRS485SessionStatus OBJECT-TYPE
    SYNTAX          RowStatus
    MAX-ACCESS      read-create
    STATUS          current
    DESCRIPTION
            "The status column used for creating,
            modifying, and deleting instances of
            the columnar objects in raw session table."
    ::= { hh3cRS485RawSessionEntry 7 }

--
-- hh3cRS485RawSessionErrInfoTable
--

hh3cRS485RawSessionErrInfoTable OBJECT-TYPE
    SYNTAX          SEQUENCE OF Hh3cRS485RawSessionErrInfoEntry
    MAX-ACCESS      not-accessible
    STATUS          current
    DESCRIPTION
        "Error infomation table.  It is fail to create a session, management
        station can get infomation from this table."
    ::= { hh3cRS485RawSessions 3}

hh3cRS485RawSessionErrInfoEntry OBJECT-TYPE
    SYNTAX          Hh3cRS485RawSessionErrInfoEntry
    MAX-ACCESS      not-accessible
    STATUS          current
    DESCRIPTION
        "Error infomaition."
    INDEX           { ifIndex, hh3cRS485SessionIndex }
    ::= { hh3cRS485RawSessionErrInfoTable 1 }

Hh3cRS485RawSessionErrInfoEntry ::=
    SEQUENCE{
        hh3cRS485RawSessionErrInfo
            DisplayString
    }

hh3cRS485RawSessionErrInfo OBJECT-TYPE
    SYNTAX          DisplayString
    MAX-ACCESS      read-only
    STATUS          current
    DESCRIPTION
        "Error infomation string.  When a response with 'noCreeation' for
        row creation in table hh3cRS485RawSessionTable,
        the management station should display this string to users,
        thus users can konw the reason."
    ::= { hh3cRS485RawSessionErrInfoEntry 1 }

END
