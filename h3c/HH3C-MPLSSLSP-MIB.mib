-- =============================================================================
-- Copyright (c) 2004-2023 New H3C Tech.  Co.  , Ltd.  All rights reserved.
--
-- Description: Multiprotocol Label Switching Static Lsp MIB
-- Reference:
-- Version: V1.1
-- History:
--   V1.0 2022-06-01 Initial version Created by Zhouwan
--   V1.1 2023-03-14 Modified by Long lewen, Modified hh3cMplsExtNotifications
-- =============================================================================
HH3C-MPLSSLSP-MIB DEFINITIONS ::= BEGIN
IMPORTS
    MODULE-IDENTITY, OBJECT-TYPE, NOTIFICATION-TYPE
        FROM SNMPv2-SMI
    hh3cCommon
        FROM HH3C-OID-MIB
    ;

-- =============================================================================
-- module identity part
-- =============================================================================
hh3cMplsSlsp MODULE-IDENTITY
    LAST-UPDATED
        "202303141400Z"   -- Mar 14, 2023 at 14:00 GMT
    ORGANIZATION
        "New H3C Technologies Co., Ltd."
    CONTACT-INFO
        "Platform Team New H3C Technologies Co., Ltd.
         Hai-Dian District Beijing P.R.  China
         http://www.h3c.com
         Zip:100085"
    DESCRIPTION
        "Multiprotocol Label Switching Static Lsp MIB"
    REVISION
        "202303141400Z"   -- Mar 14, 2023 at 14:00 GMT
    DESCRIPTION
        "Modified hh3cMplsExtNotifications"
    REVISION
        "202206070920Z"   -- June 07, 2022 at 09:20 GMT
    DESCRIPTION
        "Initial version of this MIB."
    ::= { hh3cCommon 230 }

-- =============================================================================
-- Top level components of this MIB module.
-- =============================================================================
hh3cMplsSlspNotifications OBJECT IDENTIFIER ::= { hh3cMplsSlsp 0 }

hh3cMplsSlspObjects      OBJECT IDENTIFIER  ::= { hh3cMplsSlsp 1 }

hh3cMplsSlspScalarGroup   OBJECT IDENTIFIER ::= { hh3cMplsSlspObjects 1 }

hh3cMplsSlspBaseInfo    OBJECT-TYPE
    SYNTAX      OCTET STRING (SIZE (1..127))
    MAX-ACCESS  accessible-for-notify
    STATUS      current
    DESCRIPTION
        "The base information of MPLS static LSP."
    ::= { hh3cMplsSlspScalarGroup 1 }

hh3cMplsSlspExtInfo    OBJECT-TYPE
    SYNTAX      OCTET STRING (SIZE (1..127))
    MAX-ACCESS  accessible-for-notify
    STATUS      current
    DESCRIPTION
        "The external information of MPLS static LSP"
    ::= { hh3cMplsSlspScalarGroup 2 }

-- =============================================================================
-- Notifications
-- =============================================================================
hh3cMplsSlspDown  NOTIFICATION-TYPE
    OBJECTS {
            hh3cMplsSlspBaseInfo,
            hh3cMplsSlspExtInfo
            }
    STATUS      current
    DESCRIPTION
      "This notification is generated when the Static LSP changed to Down."
    ::= { hh3cMplsSlspNotifications 1 }

hh3cMplsSlspUp  NOTIFICATION-TYPE
    OBJECTS {
            hh3cMplsSlspBaseInfo,
            hh3cMplsSlspExtInfo
            }
    STATUS      current
    DESCRIPTION
      "This notification is generated when the Static LSP changed to Up."
    ::= { hh3cMplsSlspNotifications 2 }

hh3cMplsSlspLabelDup  NOTIFICATION-TYPE
    OBJECTS {
            hh3cMplsSlspBaseInfo,
            hh3cMplsSlspExtInfo
            }
    STATUS      current
    DESCRIPTION
      "This notification is generated when the Incoming label is duplicate."
    ::= { hh3cMplsSlspNotifications 3 }

-- =============================================================================
-- End of notifications.
-- =============================================================================

END
