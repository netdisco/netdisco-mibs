-- ============================================================================
-- Copyright (c) 2004-2022 New H3C Tech. Co., Ltd. All rights reserved.
-- Description: The purpose of this MIB file is to provide the definition of
--              the DIM(Deep Inspect Management) trap.
-- Reference:
-- Version: V1.0
-- History:
-- V1.0 2022/07/15 created by suncao
--      The initial revision of this MIB module.
--      Add hh3cDimTrapSigUpdateSuccess,
--      hh3cDimTrapSigUpdateFailed.
-- ============================================================================
HH3C-DIM-MIB DEFINITIONS ::= BEGIN

IMPORTS
    hh3cCommon
        FROM HH3C-OID-MIB
    Unsigned32, OBJECT-TYPE, MODULE-IDENTITY, NOTIFICATION-TYPE
        FROM SNMPv2-SMI;

hh3cDim MODULE-IDENTITY
    LAST-UPDATED "202207151711Z"             -- July 15, 2022 at 17:11 GMT
    ORGANIZATION
        "New H3C Tech. Co., Ltd."
    CONTACT-INFO
        "Platform Team New H3C Tech. Co., Ltd.
        Hai-Dian District Beijing P.R. China
        http://www.h3c.com
        Zip:100085"
    DESCRIPTION
        "Add hh3cDimTrapSigUpdateSuccess,
        hh3cDimTrapSigUpdateFailed"
    REVISION "202207151711Z"                -- July 15, 2022 at 17:11 GMT
    DESCRIPTION
        "The initial revision of this MIB module."
    ::= { hh3cCommon 236 }

--
-- Node definitions
--

-- Global Variants
hh3cDimSignatureTraps OBJECT IDENTIFIER ::= { hh3cDim 1 }

--                     **************Global Variants***************
-- Describe objects for dim trap
hh3cDimTrapsSigUpdatePrefix OBJECT IDENTIFIER ::= { hh3cDimSignatureTraps 0 }
hh3cDimTrapSigUpdateSuccess NOTIFICATION-TYPE
    OBJECTS
        {
            hh3cDimSigUpdateFeatureId,
            hh3cDimSigUpdateType,
            hh3cDimSigUpdateLastVersion,
            hh3cDimSigUpdateCurrentVersion
        }
    STATUS    current
    DESCRIPTION
        "Send trap when the signature update success."
    ::= { hh3cDimTrapsSigUpdatePrefix 1 }
hh3cDimTrapSigUpdateFailed NOTIFICATION-TYPE
    OBJECTS
        {
            hh3cDimSigUpdateFeatureId,
            hh3cDimSigUpdateType,
            hh3cDimSigUpdateFailedReason
        }
    STATUS    current
    DESCRIPTION
        "Send trap when the signature update failed."
    ::= { hh3cDimTrapsSigUpdatePrefix 2 }

hh3cDimTrapsSigUpdateObjects OBJECT IDENTIFIER ::= { hh3cDimSignatureTraps 1 }
hh3cDimSigUpdateFeatureId OBJECT-TYPE
    SYNTAX    Unsigned32(1..8)
    MAX-ACCESS    accessible-for-notify
    STATUS    current
    DESCRIPTION
        "The signature feature identification.
        1-APR.
        2-IPS.
        3-AV.
        4-UFLT.
        5-IP-REPUTATION.
        6-WAF.
        7-URL-REPUTATION.
        8-DNS-REPUTATION."
    ::= { hh3cDimTrapsSigUpdateObjects 1 }
hh3cDimSigUpdateType OBJECT-TYPE
    SYNTAX    Unsigned32(1..2)
    MAX-ACCESS    accessible-for-notify
    STATUS    current
    DESCRIPTION
        "The signature update type,automatic upgrade or manual upgrade.
        1-Manual upgrade.
        2-Automatic upgrade."
    ::= { hh3cDimTrapsSigUpdateObjects 2 }
hh3cDimSigUpdateLastVersion OBJECT-TYPE
    SYNTAX    OCTET STRING(SIZE(0..255))
    MAX-ACCESS    accessible-for-notify
    STATUS    current
    DESCRIPTION
        "The last signature version."
    ::= { hh3cDimTrapsSigUpdateObjects 3 }
hh3cDimSigUpdateCurrentVersion OBJECT-TYPE
    SYNTAX    OCTET STRING(SIZE(0..255))
    MAX-ACCESS    accessible-for-notify
    STATUS    current
    DESCRIPTION
        "The current signature version."
    ::= { hh3cDimTrapsSigUpdateObjects 4 }
hh3cDimSigUpdateFailedReason OBJECT-TYPE
    SYNTAX    OCTET STRING(SIZE(0..255))
    MAX-ACCESS    accessible-for-notify
    STATUS    current
    DESCRIPTION
        "The reason of failure feature library upgrade."
    ::= { hh3cDimTrapsSigUpdateObjects 5 }

END
