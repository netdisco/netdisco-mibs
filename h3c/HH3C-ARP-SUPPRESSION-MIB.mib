-- ============================================================================
-- Copyright (c) 2004-2022 New H3C Tech. Co., Ltd. All rights reserved.
--
-- Description: The purpose of this MIB file is to provide the definition of
--              the ARP suppression feature.
-- Reference:
-- Version: V1.0
-- History:
-- V1.0 2022-02-08
--   Initial version, created by qiankangkang
-- ============================================================================

HH3C-ARP-SUPPRESSION-MIB DEFINITIONS ::= BEGIN

IMPORTS
        hh3cCommon
    FROM HH3C-OID-MIB
        IpAddress, Unsigned32, OBJECT-TYPE, MODULE-IDENTITY
    FROM SNMPv2-SMI
        DisplayString, MacAddress
    FROM SNMPv2-TC;

-- Node definitions
hh3cARPSuppression MODULE-IDENTITY
    LAST-UPDATED "202202071800Z"        -- FEB 07, 2022 at 18:00 GMT
    ORGANIZATION
        "New H3C Technologies Co., Ltd."
    CONTACT-INFO
        "Platform Team New H3C Technologies Co., Ltd.
         Hai-Dian District Beijing P.R. China
         http://www.h3c.com
         Zip: 100085"
    DESCRIPTION
        "This MIB file defines the ARP suppression feature only."
    REVISION "202202071800Z"
    DESCRIPTION
        "The initial version of this MIB file."
    ::= { hh3cCommon 220}

hh3cARPSuppressionVsiTable  OBJECT-TYPE
    SYNTAX      SEQUENCE OF Hh3cARPSuppressionVsiEntry
    MAX-ACCESS  not-accessible
    STATUS      current
    DESCRIPTION
        "A table for ARP Vsi suppression."
    ::= { hh3cARPSuppression 1 }

hh3cARPSuppressionVsiEntry  OBJECT-TYPE
    SYNTAX      Hh3cARPSuppressionVsiEntry
    MAX-ACCESS  not-accessible
    STATUS      current
    DESCRIPTION
        "The ARP Vsi suppression entry info."
    INDEX
    {
        hh3cARPSuppressionChassis,
        hh3cARPSuppressionSlot,
        hh3cARPSuppressionVsiName,
        hh3cARPSuppressionIpAddr
    }
    ::= { hh3cARPSuppressionVsiTable 1 }

Hh3cARPSuppressionVsiEntry ::=
    SEQUENCE
    {
        hh3cARPSuppressionChassis           Unsigned32,
        hh3cARPSuppressionSlot              Unsigned32,
        hh3cARPSuppressionVsiName           DisplayString,
        hh3cARPSuppressionIpAddr            IpAddress,
        hh3cARPSuppressionMacAddr           MacAddress,
        hh3cARPSuppressionLinkID            Unsigned32,
        hh3cARPSuppressionAging             Unsigned32
    }


hh3cARPSuppressionChassis    OBJECT-TYPE
    SYNTAX      Unsigned32
    MAX-ACCESS  not-accessible
    STATUS      current
    DESCRIPTION
        "The chassis ID of ARP Vsi suppression.If the device is not a stacked device,
         the value is 65535.
        ."
    ::= { hh3cARPSuppressionVsiEntry 1 }

hh3cARPSuppressionSlot    OBJECT-TYPE
    SYNTAX      Unsigned32
    MAX-ACCESS  not-accessible
    STATUS      current
    DESCRIPTION
        "The slot ID of ARP Vsi suppression."
    ::= { hh3cARPSuppressionVsiEntry 2 }

hh3cARPSuppressionVsiName    OBJECT-TYPE
    SYNTAX      DisplayString(SIZE (1..32))
    MAX-ACCESS  not-accessible
    STATUS      current
    DESCRIPTION
        "The vsi name of ARP Vsi suppression."
    ::= { hh3cARPSuppressionVsiEntry 3 }

hh3cARPSuppressionIpAddr    OBJECT-TYPE
    SYNTAX      IpAddress
    MAX-ACCESS  not-accessible
    STATUS      current
    DESCRIPTION
        "The ip address of ARP Vsi suppression."
    ::= { hh3cARPSuppressionVsiEntry 4 }

hh3cARPSuppressionMacAddr    OBJECT-TYPE
    SYNTAX      MacAddress
    MAX-ACCESS  read-only
    STATUS      current
    DESCRIPTION
        "The mac address of ARP Vsi suppression."
    ::= { hh3cARPSuppressionVsiEntry 5 }

hh3cARPSuppressionLinkID    OBJECT-TYPE
    SYNTAX      Unsigned32
    MAX-ACCESS  read-only
    STATUS      current
    DESCRIPTION
        "The link ID of ARP Vsi suppression."
    ::= { hh3cARPSuppressionVsiEntry 6 }

hh3cARPSuppressionAging    OBJECT-TYPE
    SYNTAX      Unsigned32
    UNITS       "minutes"
    MAX-ACCESS  read-only
    STATUS      current
    DESCRIPTION
        "The aging time of ARP Vsi suppression."
    ::= { hh3cARPSuppressionVsiEntry 7 }

END
