-- ==========================================================================
-- Copyright (c) 2004-2022 New H3C Tech. Co., Ltd. All rights reserved.
--
-- Description: Bit Index Explicit Replication MIB
-- Reference:
-- Version: V1.0
-- History:
--   V1.0 Initial version 2022-08-10 by liziyi kf9672.
-- ==========================================================================
HH3C-BIER-MIB DEFINITIONS ::= BEGIN

IMPORTS
    hh3cCommon
        FROM HH3C-OID-MIB
    Integer32, OBJECT-TYPE, MODULE-IDENTITY, NOTIFICATION-TYPE
        FROM SNMPv2-SMI
    SnmpAdminString
        FROM SNMP-FRAMEWORK-MIB;

-- ==================================================================
--
-- ======================= definition begin =========================
--
-- ==================================================================

hh3cBier MODULE-IDENTITY
    LAST-UPDATED "202208100000Z"
    ORGANIZATION
      "New H3C Tech. Co., Ltd."
    CONTACT-INFO
      "Platform Team New H3C Tech. Co., Ltd.
      Hai-Dian District Beijing P.R. China
      http://www.h3c.com
      Zip:100085"
    DESCRIPTION
      "All the configuration of the bier can be managed
        by bier Mib."
    REVISION "202208100000Z"
    DESCRIPTION
    "Initial revision"
    ::= { hh3cCommon 244 }

--
-- Notification definitions
--
-- =================================================================
-- Traps are defined below.

hh3cBierTrap OBJECT IDENTIFIER ::= { hh3cBier 1 }
hh3cBierTrapPrefix OBJECT IDENTIFIER ::= { hh3cBierTrap 0 }
-- All trap definitions should be placed under this object.

hh3cBierTrapPrefixBfridConflict  NOTIFICATION-TYPE
    OBJECTS
        {
            hh3cBierSubdomain,
            hh3cBierBfrid,
            hh3cBierAddressFamily,
            hh3cBierPrefix
        }
    STATUS current
    DESCRIPTION
        "This notification is generated when a Bit-Forwarding Router Identifier conflict occurs in a subdomain."
    ::= { hh3cBierTrapPrefix 1 }

hh3cBierTrapObject OBJECT IDENTIFIER ::= { hh3cBierTrap 1 }

hh3cBierSubdomain  OBJECT-TYPE
    SYNTAX      Integer32
    MAX-ACCESS  accessible-for-notify
    STATUS      current
    DESCRIPTION
        "Current subdomain."
    ::= {hh3cBierTrapObject 1 }

hh3cBierBfrid  OBJECT-TYPE
    SYNTAX      Integer32
    MAX-ACCESS  accessible-for-notify
    STATUS      current
    DESCRIPTION
        "The Bit-Forwarding Router Identifier of the current conflict."
    ::= {hh3cBierTrapObject 2 }

hh3cBierAddressFamily  OBJECT-TYPE
    SYNTAX      SnmpAdminString (SIZE (0..255))
    MAX-ACCESS  accessible-for-notify
    STATUS      current
    DESCRIPTION
        "The address family of the conflicting node."
    ::= {hh3cBierTrapObject 3 }

hh3cBierPrefix  OBJECT-TYPE
    SYNTAX      SnmpAdminString (SIZE (0..255))
    MAX-ACCESS  accessible-for-notify
    STATUS      current
    DESCRIPTION
        "The prefix of the node."
    ::= {hh3cBierTrapObject 4 }

END
