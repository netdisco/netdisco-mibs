-- =============================================================================
-- Copyright (c) 2004-2021 New H3C Tech. Co., Ltd. All rights reserved.
--
-- Description:
--   The file defines a MIB to provide WLAN configuration information.
-- Reference:
-- Version: V3.7
-- History:
--   V1.0 2006-05-10 Initial version, created by shiyang (Richard)
--   V1.1 2007-02-01 modified by xingjichen(Daniel)
--        Added hh3cDot11RadioIntfConfigTable,hh3cDot11RadioIntfBindTable,
--        hh3cDot11StaKeepALiveTimerIntvl,hh3cDot11StaIdleTimerIntvl,
--        hh3cDot11BroadcastProbeReply.
--   V1.2 2007-04-27 modified by shiyang(Richard)
--        Replace hh3cDot11UnicastCipherKeyIndex, hh3cDot11UnicastCipherKey,
--        hh3cDot11BroadcastCipherKeyIndex and hh3cDot11BroadcastCipherKey
--        with hh3cDot11CipherKeyIndex, hh3cDot11CipherKey as per CLI change.
--        Delete hh3cDot11MaxTxLifetime as per CLI change.
--        Add hh3cDot11GlobalCountryCode,hh3cDot11APScanMode.
--        hh3cDot11ACCtrlTunnelSecSupport and hh3cDot11ACDataTunnelSecSupport.
--        Move hh3cDot11StaKeepALiveTimerIntvl,hh3cDot11StaIdleTimerIntvl
--        and so on to hh3cDot11GlobeConfigGroup.
--        Split hh3cDot11ServicePolicyTable into hh3cDot11ServicePolicyTable
--        and hh3cDot11ServicePolicyExtTable.
--        For hh3cDot11SecurityCiphers node,update its description for case of
--        value equals to zero.
--   V1.3 2007-06-19 modified by Vikas K
--        Add new table of hh3cDot11DataRateConfigTable for AP Configuration
--        Group.
--        Add new node of hh3cDot11APName for hh3cDot11APTemplateTable.
--        Modify the hh3cDot11APScanMode from read-only to read-write.
--        Add undo functionality to node hh3cDot11WlanInfBindingID and
--        hh3cDot11Description.
--        Add hh3cDot11StatisInterv to the hh3cDot11APTemplateTable.
--   V1.4 2007-10-9 modified by Jagan K
--        Add new table hh3cDot11WlanBssIfTable for WLAN BSS interface
--        configuration.
--        Add new table hh3cDot11WlanEssIfTable for WLAN ESS interface
--        configuration.
--        Add new table hh3cDot11WlanEthernetIfTable for WLAN Ethernet interface
--        configuration.
--   V1.5 2007-12-21 modified by wanghao (Kumar)
--        Add hh3cDot11ACAutoAPSupport, hh3cDot11AutoAPName,
--        hh3cDot11PersistentName to hh3cDot11GlobeConfigGroup
--        Add hh3cDot11ClientMaxCount to hh3cDot11ServicePolicyTable
--        Add hh3cDot11APBroadcastProbeReply, hh3cDot11StaIdleTimerInterv,
--        hh3cDot11StaKeepAliveTimerInterv, hh3cDot11APCir, hh3cDot11APCbs
--        to hh3cDot11APTemplateTable.
--   V1.6 2008-02-25 modified by wanghao (Kumar)
--        Add hh3cDot11RdoClientMaxCount to hh3cDot11RadioPolicyTable.
--   V1.7 2008-04-01 modified by wangbin
--        Add hh3cDot11PortSecurityTable to hh3cDot11InterfaceConfigGroup.
--        Add hh3cDot11PortSecurityMode, hh3cDot11SecurityUserLoginTxKeyType,
--        hh3cDot11SecurityPskKeyMode, hh3cDot11SecurityPskKeyString
--        to hh3cDot11PortSecurityTable.
--   V1.8 2008-08-01 modified by ChangHuifeng
--        Add hh3cDot11ACBackupGroup and
--        hh3cDot11RadioElementConfigGroup.
--        Add hh3cDot11WlanMeshIfTable to hh3cDot11InterfaceConfigGroup.
--        Add hh3cDot11APPriorityLevel and hh3cDot11APElementID to
--        hh3cDot11APTemplateTable.
--        Add hh3cDot11CfgRdElementID to hh3cDot11RadioToConfigTable.
--        Add hh3cDot11APDevDetectEnable to hh3cDot11APTemplateEntry.
--        Obsolete hh3cDot11StatisInterv
--        Change default value of hh3cDot11APScanMode to passive.
--        Change units of hh3cDot11BeaconInterval and
--        hh3cDot11RadioCfgBeaconIntvl to TU.
--        Remove default value of hh3cDot11SSIDEncryptionMode.
--        Change MAC-ACCESS of objects in hh3cDot11RadioToConfigTable
--        from read-create to read-write.
--        Change name of hh3cDot11IWlanEssRowStatus to hh3cDot11WlanEssRowStatus.
--        Change description of hh3cDot11PortSecurityTable.
--   V1.9 2008-11-07 modified by Wang Lu and Li Yugang
--        Add hh3cDot11IntfTrapThreshold to hh3cDot11GlobeConfigGroup
--        Add hh3cDot11SPInCirMode, hh3cDot11SPInCirValue, hh3cDot11SPOutCirMode,
--        hh3cDot11SPOutCirValue to hh3cDot11ServicePolicyTable
--        Add hh3cDot11CfgWorkMode to hh3cDot11RadioToConfigTable
--        Add hh3cDot11RadioCfgWorkMode to hh3cDot11RadioIntfConfigTable.
--        Add new traps hh3cDot11CfgCipherChange and hh3cDot11CfgPSKChange.
--        Add hh3cDot11MonitorInterval, hh3cDot11SampleInterval,
--        hh3cDot11ChnlSwitChkInterval, hh3cDot11APUserUplimit,
--        hh3cDot11APL2IsolateEnable to hh3cDot11GlobeConfigGroup.
--        Add hh3cDot11RadioCfgOnly11gEnable to hh3cDot11RadioIntfConfigTable.
--        Add hh3cDot11RadioWDSTable to hh3cDot11RadioElementConfigGroup.
--   V2.0 2009-03-20 modified by caizibin
--        Add value ext(6) to hh3cDot11PortSecurityMode
--   V2.1 2009-05-07 modified by Li Yugang, Wang Shaojie, Jin Yi
--        Add hh3cDot11APBSSIDSupportNum, hh3cDot11APLastUpdateStatTime,
--        hh3cDot11APDoSProtectEnable, hh3cDot11MaxAPPerIf to
--        hh3cDot11GlobeConfigGroup.
--        Add hh3cDot11WlanInfPVID to hh3cDot11ServicePolicyTable.
--        Add hh3cDot11CipherKeyType to hh3cDot11ServicePolicyExtTable.
--        Add hh3cDot11CfgPwrAttValue to hh3cDot11RadioToConfigTable.
--        Add new table hh3cDot11APSysInfoSetTable to hh3cDot11APConfigGroup.
--        Add hh3cDot11SSIDWepIDConflictTrap to hh3cDot11CfgNotifications.
--        Add new table hh3cDot11CfgTrapVarObjects to hh3cDot11CfgNotifyGroup.
--   V2.2 2009-07-29 modified by Heziqi
--        Add new node hh3cDot11ServiceSetVlanId for hh3cDot11APServiceSetTable.
--        Add hh3cDot11UplinkTrackId to hh3cDot11GlobeConfigGroup.
--        Add hh3cDot11APLimitTable.
--        Change description of hh3cDot11StaKeepALiveTimerIntvl.
--        Add new node hh3cDot11RadioTxArithmetic for Hh3cDot11RadioToConfigTable.
--   V2.3 2009-07-29 modified by Jinyi
--        Add new table hh3cDot11APIfSetTable
--   V2.4 2009-12-01 modified by Wang Shaojie
--        Add new node hh3cDot11APGetIPMethod for hh3cDot11APTemplateTable.
--        Add new group hh3cDot11CfgTrapConfigGroup.
--        Add new table hh3cDot11CfgSwitchTrapTable to hh3cDot11CfgTrapConfigGroup.
--        Add new node hh3cDot11BeaconIntervalMs to hh3cDot11RadioPolicyTable.
--        Add new node hh3cDot11SPInCirStaticValue, hh3cDot11SPOutCirStaticValue
--        to hh3cDot11ServicePolicyTable.
--        Modify description of hh3cDot11SecurityCiphers.
--        Add new node hh3cDot11StatisIntervMode to hh3cDot11APTemplateTable.
--        Modify SYNTAX of hh3cDot11APWorkMode.
--        Modify STATUS of hh3cDot11StatisInterv.
--        Add new node hh3cDot11SmartRateSet to hh3cDot11DataRateConfigTable.
--        2010-02-22 modified by Wang Chunsheng
--        Add new node hh3cDot11CfgChannelLockStat, hh3cDot11CfgPowerLockStat,
--        hh3cDot11CfgLBRdGroupId, hh3cDot11CfgRRMSDRdGroupId to hh3cDot11RadioToConfigTable.
--        2010-03-15 modified by Wang Lu
--        Add hh3cDot11RtCollectSwitch, hh3cDot11RglCollectIntvl, and
--        hh3cDot11RtCollectIntvl to hh3cDot11GlobeConfigGroup
--        Add hh3cDot11SPIsolate to hh3cDot11ServicePolicyTable
--        Add hh3cDot11APServiceVlanTable, hh3cDot11RadioConfigTable,
--        hh3cDot11RadioPolicyExtTable and hh3cDot11RadioSSIDCfgTable
--        Remove hh3cDot11CfgTrapConfigGroup
--        Add hh3cDot11SrvPortSecurityTable
--        2010-06-01 Modified by Wang Shaojie, Yin Junjie
--        Add hh3cDot11RCApPowerLevel, hh3cDot11RCDynamicChlState,
--        hh3cDot11RCDynamicPowerState to hh3cDot11RadioConfigTable.
--        Add hh3cDot11APSerialIDTable
--        Add hh3cDot11APSTVlanTable
--        2010-07-08 Modified the index of hh3cDot11APSysInfoSetTable by jinyi
--        2010-08-05 Modified by Yin Junjie
--        Add new table hh3cDot11SrvPolicyExtendTable
--        Add hh3cDot11SPEnable to hh3cDot11SrvPolicyExtendTable
--        2010-09-02 Modified by Yin Junjie
--        Add new node hh3cDot11AdjIntfTrapThreshold
--        to hh3cDot11GlobeConfigGroup
--        Add hh3cDot11RCRadioStatus to hh3cDot11RadioConfigTable
--   V2.5 2010-09-25 Modified by Wu Xiaopeng
--        Remove Size list of hh3cDot11APName.
--   V2.6 2011-05-23 Modified by Cui Kai
--        Add new node hh3cDot11WlanexAuthServerIP to hh3cDot11ServicePolicyTable
--        2011-07-08 Modified by Niu Jian
--        Change type of hh3cDot11CfgSTNASPortID to OCTET STRING
--   V2.7 2011-07-13 Modified by Yu Bo
--        Add new node hh3cDot11RCRadioRate to hh3cDot11RadioConfigTable
--        Add new node hh3cDot11RCPwrAdjustStepLength to hh3cDot11RadioConfigTable
--        2011-08-08 Modified by Xiao Min
--        Add new table hh3cDot11nRadioCfg2Table
--        2011-08-10 Modified by limingjin
--        Add hh3cDot11RadioCfgType2 to hh3cDot11RadioIntfConfigTable
--        Add hh3cDot11RCRadioType2 to hh3cDot11RadioConfigTable
--        Add hh3cDot11CfgRadioType2 to hh3cDot11RadioToConfigTable
--   V2.8 2011-09-28 Modified by zhanghu
--        Add hh3cDot11ApTrapEnabled to hh3cDot11APTemplateTable
--        Add hh3cDot11AllAPMonitorMode to hh3cDot11APTemplateTable
--        Add hh3cDot11SIDAPTemplateName, hh3cDot11SIDModelAlias, hh3cDot11SIDAPDescription, hh3cDot11SIDRowStatus,
--        hh3cDot11SIDAPName, hh3cDot11SIDStatisInterv, hh3cDot11SIDAPBroadcastProbeReply,
--        hh3cDot11SIDAPStaIdleTimerInterv, hh3cDot11SIDStaKeepAliveTimerInterv,
--        hh3cDot11SIDAPCir, hh3cDot11SIDAPCbs, hh3cDot11SIDAPPriorityLevel,
--        hh3cDot11SIDAPElementID, hh3cDot11SIDAPDevDetectEnable, hh3cDot11SIDAPStatisIntervMode
--        to hh3cDot11APSerialIDTable
--        2011-08-28 Modified by Wang Lu
--        Add hh3cDot11CfgSaEnable, hh3cDot11CfgSaBand, hh3cDot11CfgIDSEnable,
--        hh3cDot11CfgSaCltRtFFTData to hh3cDot11RadioToConfigTable
--   V2.9 2012-08-10 by Zhang Cong cong
--        Add new node   hh3cDot11ConfigureAPMacAddress to hh3cDot11CfgTrapVarObjects
--        Add new object hh3cDot11ConfigureAPMacAddress to hh3cDot11SSIDWepIDConflictTrap
--   V3.0 2013-04-15 by Shao Pengfei & Li Shihao
--        Add new node hh3cDot11GlobalApFmwUpdState to hh3cDot11GlobeConfigGroup
--        Add new node hh3cDot11ApFmwUpdState to hh3cDot11APTemplateTable
--        Add new node hh3cDot11SPBeaconMeasEnable to hh3cDot11ServicePolicyTable
--        Add new node hh3cDot11SPBeaconMeasType to hh3cDot11ServicePolicyTable
--        Add new node hh3cDot11SPBeaconMeasInterval to hh3cDot11ServicePolicyTable
--   V3.1 2013-08-30 by Xiao Mengmeng & Li Qian & Ji Chunyu & Liu Yawen
--        Add hh3cDot11AuthenModeCM to hh3cDot11ServicePolicyTable
--        Add hh3cDot11SecIEStatusCM to hh3cDot11ServicePolicyTable
--        Add hh3cDot11SecurityCiphersCM to hh3cDot11ServicePolicyTable
--        Add hh3cDot11SrvPolicyStatusCM to hh3cDot11ServicePolicyTable
--        Add hh3cDot11CfgSTNASID to hh3cDot11APSTVlanTable
--        Add hh3cDot11RCPreambleLenCM to hh3cDot11RadioConfigTable
--        Add hh3cDot11RCDynamicChlStateCM to hh3cDot11RadioConfigTable
--        Add hh3cDot11RCRadioStatusCM to hh3cDot11RadioConfigTable
--        Add hh3cDot11SIDAPWorkModeCM to hh3cDot11APSerialIDTable
--        Add hh3cDot11nRadioCfg2AMpduEnableCM to hh3cDot11nRadioCfg2Table
--        Add hh3cDot11nRadioCfg2ChannelBandCM to hh3cDot11nRadioCfg2Table
--        Add hh3cDot11nRadioCfg2ShortGiEnableCM to hh3cDot11nRadioCfg2Table
--        2013-12-24 Modified by Chen Guoxi
--        Add mode80 to hh3cDot11nChanelBand and hh3cDot11nRadioCfg2ChannelBand
--        Add new node hh3cDot11nClientDot11acOnly to hh3cDot11nRadioCfgTable
--        Add new node hh3cDot11nRadioCfg2ClientDot11acOnly to hh3cDot11nRadioCfg2Table
--   V3.2 2014-02-10 by Zhou Weichao
--        Add hh3cDot11ACNasIDCM to hh3cDot11GlobeConfigGroup
--        Add hh3cDot11SSIDHiddenCM to hh3cDot11ServicePolicyTable
--        Add hh3cDot11SPIsolateCM to hh3cDot11ServicePolicyTable
--        Add hh3cDot11RPBeaconIntervalCM to hh3cDot11RadioPolicyExtTable
--        Add hh3cDot11StatisIntervModeCM to hh3cDot11APTemplateTable
--        Add hh3cDot11APNasIDCM to hh3cDot11APTemplateTable
--        Add hh3cDot11RCDynamicPowerStateCM to hh3cDot11RadioConfigTable
--        Add hh3cDot11RCRadioRateCM to hh3cDot11RadioConfigTable
--        Add hh3cDot11nRadioCfg2ClientDot11nOnlyCM to hh3cDot11nRadioCfg2Table
--        Modify hh3cDot11WlanexAuthServerIP
--        Add hh3cDot11RadioCfgRssithresholdCM to hh3cDot11RadioIntfConfigTable
--        Add hh3cDot11SrvPortSecurityModeCM to hh3cDot11SrvPortSecurityTable
--   V3.3 2014-5-14 Add by yubo
--        Add hh3cDot11RCRssiThresholdCM to hh3cDot11RadioConfigTable
--   V3.4 2014-9-19 Add by wanglu
--        Add hh3cDot11SrvL2AuthenTable
--        Add hh3cDot11AkmMode to hh3cDot11ServicePolicyExtTable
--        Add hh3cDot11PskKey to hh3cDot11ServicePolicyExtTable
--        Add hh3cDot11CfgSaRptDevType to hh3cDot11RadioToConfigTable
--        Add hh3cDot11CfgSaTrapDevEnable to hh3cDot11RadioToConfigTable
--        Add hh3cDot11CfgSaTrapDevType to hh3cDot11RadioToConfigTable
--        Add hh3cDot11CfgSaTrapAQEnable to hh3cDot11RadioToConfigTable
--        Add hh3cDot11CfgSaTrapAQThreshold to hh3cDot11RadioToConfigTable
--        Add hh3cDot11CfgSaDrivenRRMEnable to hh3cDot11RadioToConfigTable
--        Add hh3cDot11CfgSaDrivenRRMSnt to hh3cDot11RadioToConfigTable
--   V3.5 2016-3-11 Add by wuqinggen
--        Add hh3cDot11FwdVlanBitMapLow to hh3cDot11ServicePolicyTable
--        Add hh3cDot11FwdVlanBitMapHigh to hh3cDot11ServicePolicyTable
--        Add hh3cDot11ServicePolicyName to hh3cDot11ServicePolicyTable
--        2016-3-11 add by yubo 04460
--        Add hh3cDot11ApCoveragetype to hh3cDot11APTemplateTable
--        Add hh3cDot11RCDynamicChlStateSelfDecisiveCM to hh3cDot11RadioConfigTable
--        Add hh3cDot11RCDynamicPowerStateSelfDecisiveCM to hh3cDot11RadioConfigTable
--        2016-06-15 Add by zhouwenshuai zkf6157
--        Add hh3cDot11LocalACTemplateTable
--        Add new node hh3cDot11ACRole to hh3cDot11GlobeConfigGroup
--        Add new node hh3cDot11GlobalLocalACState to hh3cDot11GlobeConfigGroup
--        Add new node hh3cDot11CentralACIPAddress to hh3cDot11GlobeConfigGroup
--        Add new node hh3cDot11CentralACIPv6Address to hh3cDot11GlobeConfigGroup
--        Add new node hh3cDot11APControlAddressState  to hh3cDot11APTemplateTable
--        Add new node hh3cDot11APControlAddressIPv4 to hh3cDot11APTemplateTable
--        Add new node hh3cDot11APControlAddressIPv6 to hh3cDot11APTemplateTable
--        Add new node hh3cDot11APLocalACName to hh3cDot11APTemplateTable
--        2016-12-06 Add by zhouwenshuai zkf6157
--        Add value mode160(4) mode80and80(5) to hh3cDot11nChanelBand
--        Add value mode160(4) mode80and80(5) to hh3cDot11nRadioCfg2ChannelBand
--        2017-10-09 Add by lixiaoyi, jiaohaina, guozhanhua, chenxueke
--        Add new node hh3cDot11APEchoInterval to hh3cDot11APTemplateTable
--        Add new node hh3cDot11SIDEchoInterval to hh3cDot11APSerialIDTable
--        Add new node hh3cDot11SecurityModeCM to hh3cDot11ServicePolicyTable
--        Add new node hh3cDot11PreConflictTemplateSSID,hh3cDot11CurrConflictTemplateSSID
--        to hh3cDot11SSIDWepIDConflictTrap
--        Add new node hh3cDot11SPInCbsValue to hh3cDot11ServicePolicyTable
--        Add new node hh3cDot11SPOutCbsValue to hh3cDot11ServicePolicyTable
--        Add value mode80(3), mode160(4), mode80and80(5) to hh3cDot11nRadioCfg2ChannelBandCM
-- V3.6   Add value 0 to hh3cDot11EchoInterval
--        2018-06-04 Add by licheng
--        Add new node hh3cDot11iMcIP to hh3cDot11GlobeConfigGroup
--        Add new node hh3cDot11iMcPort to hh3cDot11GlobeConfigGroup
--        2018-08-08 Add by wanghailong
--        Add new node hh3cDot11APProvisionAPIPv4 to hh3cDot11APTemplateTable
--        Add new node hh3cDot11APProvisionIPv4Mask to hh3cDot11APTemplateTable
--        Add new node hh3cDot11APProvisionAPIPv6 to hh3cDot11APTemplateTable
--        Add new node hh3cDot11APProvisionIPv6PrefixLen to hh3cDot11APTemplateTable
--        Add new node hh3cDot11APProvisionACIPv4 to hh3cDot11APTemplateTable
--        Add new node hh3cDot11APProvisionACIpv6 to hh3cDot11APTemplateTable
--        Add new node hh3cDot11APProvisionGateWayIPV4 to hh3cDot11APTemplateTable
--        Add new node hh3cDot11APProvisionGateWayIPV6 to hh3cDot11APTemplateTable
--        Add new node hh3cDot11APProvisionSave to hh3cDot11GlobeConfigGroup
--        2018-10-17 Add by huanglu,zhangming
--        Add new node hh3cDot11ServiceSetVlanGroup to hh3cDot11APServiceSetTable
--        Add macAndDot1x(7) to hh3cDot11L2AuthenMode
--        2018-12-11 Add by wangshujuan
--        Add new node hh3cDot11ApRenameCurrentName to hh3cDot11GlobeConfigGroup
--        Add new node hh3cDot11ApRenameNewName     to hh3cDot11GlobeConfigGroup
--        Add hh3cDot11RemoteCfgApTable
--        Add hh3cDot11RemoteCfgIFTable
--        2020-08-03 Add by qiuchunxia
--        Add new hh3cDot11IPLearningTable
--        Add new node hh3cDot11IPLearningServiceName to hh3cDot11IPLearningVlanBitMapH
--        2020-08-12 Add by suting
--        Add new node hh3cDot11APMapConfigFileName to hh3cDot11APTemplateTable
--        Add hh3cDot11CfgSPInCirMode to hh3cDot11RadioToConfigTable
--        Add hh3cDot11CfgSPInCirValue to hh3cDot11RadioToConfigTable
--        Add hh3cDot11CfgSPOutCirMode to hh3cDot11RadioToConfigTable
--        Add hh3cDot11CfgSPOutCirValue to hh3cDot11RadioToConfigTable
--        2020-12-29 Add by zhoucailu,sunchangquan
--        Add hh3cDot11RmtIfManagement to hh3cDot11RemoteCfgIFTable
--        Add hh3cDot11WlanInfCustomerPVID to hh3cDot11ServicePolicyTable
--   V3.7 2021-06-18 modified by liyapeng
--        Modify description of hh3cDot11PreambleLen
--        Modify description of hh3cDot11StatisIntervMode, hh3cDot11StatisIntervModeCM And hh3cDot11SIDAPStatisIntervMode
-- =============================================================================
HH3C-DOT11-CFG-MIB DEFINITIONS ::= BEGIN

IMPORTS
        TruthValue,
        RowStatus,
        DisplayString,
        DateAndTime,
        MacAddress
    FROM SNMPv2-TC
        ifIndex
    FROM RFC1213-MIB
        MODULE-IDENTITY,
        NOTIFICATION-TYPE,
        OBJECT-TYPE,
        Integer32,
        Unsigned32,
        IpAddress
    FROM SNMPv2-SMI
        InetAddress
    FROM INET-ADDRESS-MIB
        hh3cDot11,
        Hh3cDot11RadioType,
        Hh3cDot11TxPwrLevelScopeType,
        Hh3cDot11ChannelScopeType,
        Hh3cDot11SSIDStringType,
        Hh3cDot11AuthenType,
        Hh3cDot11RadioScopeType,
        Hh3cDot11SSIDEncryptModeType,
        Hh3cDot11SecIEStatusType,
        Hh3cDot11PreambleType,
        Hh3cDot11ServicePolicyIDType,
        Hh3cDot11TunnelSecSchemType,
        Hh3cDot11RadioElementIndex,
        Hh3cDot11WorkMode,
        Hh3cDot11CirMode,
        hh3cDot11APElementIndex,
        Hh3cDot11ObjectIDType,
        Hh3cDot11RadioType2,
        Hh3cDot11TruthValueCM
    FROM HH3C-DOT11-REF-MIB;

hh3cDot11CFG MODULE-IDENTITY
    LAST-UPDATED "202106181800Z"        -- Jun 18, 2021 at 18:00 GMT
    ORGANIZATION
        "New H3C Technologies Co., Ltd."
    CONTACT-INFO
        "Platform Team New H3C Technologies Co., Ltd.
         Hai-Dian District Beijing P.R. China
         http://www.h3c.com
         Zip: 100085"
    DESCRIPTION
        "This MIB provides information about WLAN configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP.  AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."
    REVISION "202106181800Z"        -- Jun 18, 2021 at 18:00 GMT
    DESCRIPTION
        " Modify nodes with incorrect description information "
    REVISION "202012111800Z"        -- Dec 11, 2020 at 18:00 GMT
    DESCRIPTION
        "Modified to add new nodes and new tables."
    REVISION "201710091800Z"        -- Oct 09, 2017 at 18:00 GMT
    DESCRIPTION
        "Modified to add new nodes and new table."
    REVISION "201603111800Z"        -- Mar 11, 2016 at 18:00 GMT
    DESCRIPTION
        "Modified to add new nodes and new table."
    REVISION "201409191800Z"        -- Sep 19, 2014 at 18:00 GMT
    DESCRIPTION
        "Modified to add new nodes and new table."
    REVISION "201009251800Z"        -- Sep 25, 2010 at 18:00 GMT
    DESCRIPTION
        "Modified to remove some issue."
    REVISION "201009021800Z"        -- Sep 2, 2010 at 18:00 GMT
    DESCRIPTION
        "Modified to add new node."
    REVISION "200907291800Z"        -- Jul 29, 2009 at 18:00 GMT
    DESCRIPTION
        "Modified to add new nodes and new table."
    REVISION "200905072000Z"        -- May 7, 2009 at 20:00 GMT
    DESCRIPTION
        "Modified to add new nodes and new table."
    REVISION "200903201530Z"        -- Mar 20, 2009 at 15:30 GMT
    DESCRIPTION
        "Modified to add new value for appointed node."
    REVISION "200811071530Z"        -- Nov 07, 2008 at 15:30 GMT
    DESCRIPTION
        "Modified to add new nodes and new table."
    REVISION "200807091800Z"        -- July 09, 2008 at 18:00 GMT
    DESCRIPTION
        "Modified to add new groups."
    REVISION "200802251800Z"        -- Feb 25, 2008 at 18:00 GMT
    DESCRIPTION
        "Modified to add new nodes."
    REVISION "200712211800Z"        -- Dec 21, 2007 at 18:00 GMT
    DESCRIPTION
        "Modified to add new nodes."
    REVISION "200710091655Z"    -- October 09, 2007 at 16:55 GMT
    DESCRIPTION
        "changed for new requirements"
    REVISION "200706191800Z"        -- June 19, 2007 at 18:00 GMT
    DESCRIPTION
        "Modified to add new table."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { hh3cDot11 4 }

-- *****************************************************************************
-- *  Major sections
-- *****************************************************************************
--  AP Configuration Group
--  DEFINED AS "The group to provide the configuration information
--  for APs.
hh3cDot11GlobeConfigGroup OBJECT IDENTIFIER  ::= { hh3cDot11CFG 1 }

hh3cDot11PolicyConfigGroup OBJECT IDENTIFIER ::= { hh3cDot11CFG 2 }
--  Policy Configuration Group has the following children:
--  hh3cDot11RadioPolicyTable            ::= { hh3cDot11PolicyConfigGroup 1 }
--  hh3cDot11ServicePolicyTable          ::= { hh3cDot11PolicyConfigGroup 2 }
--  hh3cDot11ServicePolicyExtTable       ::= { hh3cDot11PolicyConfigGroup 3 }
--  hh3cDot11RadioPolicyExtTable         ::= { hh3cDot11PolicyConfigGroup 4 }
--  hh3cDot11SrvPortSecurityTable        ::= { hh3cDot11PolicyConfigGroup 5 }
--  hh3cDot11SrvPolicyExtendTable        ::= { hh3cDot11PolicyConfigGroup 6 }
--  hh3cDot11SrvL2AuthenTable            ::= { hh3cDot11PolicyConfigGroup 7 }
--  hh3cDot11IPLearningTable             ::= { hh3cDot11PolicyConfigGroup 8 }

hh3cDot11APConfigGroup OBJECT IDENTIFIER     ::= { hh3cDot11CFG 3 }
--  AP Configuration Group has the following children:
--  hh3cDot11APTemplateTable                 ::= { hh3cDot11APConfigGroup 1 }
--  hh3cDot11RadioToConfigTable              ::= { hh3cDot11APConfigGroup 2 }
--  hh3cDot11APServiceSetTable               ::= { hh3cDot11APConfigGroup 3 }
--  hh3cDot11APSysInfoSetTable               ::= { hh3cDot11APConfigGroup 4 }
--  hh3cDot11APLimitTable                    ::= { hh3cDot11APConfigGroup 5 }
--  hh3cDot11APSerialIDTable                 ::= { hh3cDot11APConfigGroup 10 }
--  hh3cDot11APSTVlanTable                   ::= { hh3cDot11APConfigGroup 11 }
hh3cDot11RadioIntfConfigGroup OBJECT IDENTIFIER ::= { hh3cDot11CFG 4 }
--  Radio Interface Group has the following children:
--  hh3cDot11RadioIntfConfigTable          ::= { hh3cDot11RadioIntfConfigGroup 1 }
--  hh3cDot11RadioIntfBindTable            ::= { hh3cDot11RadioIntfConfigGroup 2 }

hh3cDot11DataRateConfigGroup OBJECT IDENTIFIER ::= { hh3cDot11CFG 5 }
--  Data Rate Config Group has the following children:
--  hh3cDot11DataRateConfigTable           ::= { hh3cDot11DataRateConfigGroup 1 }

hh3cDot11InterfaceConfigGroup OBJECT IDENTIFIER ::= { hh3cDot11CFG 6 }
--  Interface Config Group has the following children:
--  hh3cDot11WlanEssIfTable               ::= { hh3cDot11InterfaceConfigGroup 1 }
--  hh3cDot11WlanBssIfTable               ::= { hh3cDot11InterfaceConfigGroup 2 }
--  hh3cDot11WLANEthernetIfTable          ::= { hh3cDot11InterfaceConfigGroup 3 }
--  hh3cDot11PortSecurityTable            ::= { hh3cDot11InterfaceConfigGroup 4 }
--  hh3cDot11WlanMeshIfTable              ::= { hh3cDot11InterfaceConfigGroup 5 }

hh3cDot11ACBackupGroup OBJECT IDENTIFIER ::= { hh3cDot11CFG 7 }

hh3cDot11RadioElementConfigGroup OBJECT IDENTIFIER ::= { hh3cDot11CFG 8 }
--  Radio Element Config Group has the following children:
--  hh3cDot11nRadioCfgTable           ::= { hh3cDot11RadioElementConfigGroup 1 }
--  hh3cDot11RadioWDSTable            ::= { hh3cDot11RadioElementConfigGroup 2 }
--  hh3cDot11nRadioCfg2Table          ::= { hh3cDot11RadioElementConfigGroup 3 }

hh3cDot11CfgNotifyGroup OBJECT IDENTIFIER ::= { hh3cDot11CFG 9 }

hh3cDot11LocalACConfigGroup OBJECT IDENTIFIER     ::= { hh3cDot11CFG 10 }
--  LocalAC Configuration Group has the following children:
--  hh3cDot11LocalACTemplateTable                 ::= { hh3cDot11LocalACConfigGroup 1 }

hh3cDot11RemoteConfigGroup  OBJECT IDENTIFIER     ::= { hh3cDot11CFG 11 }
--  Remote Configuration Group has the following children:
--  hh3cDot11RemoteCfgApTable               ::= { hh3cDot11RemoteConfigGroup 1 }
--  hh3cDot11RemoteCfgIFTable               ::= { hh3cDot11RemoteConfigGroup 2 }

-- *****************************************************************************
-- *  hh3cDot11GlobeConfigGroup Definition
-- *****************************************************************************
hh3cDot11GlobalCountryCode OBJECT-TYPE
    SYNTAX      OCTET STRING(SIZE(3))
    MAX-ACCESS  read-write
    STATUS      current
    DESCRIPTION
        "Represents the country code for wireless network."
    ::= { hh3cDot11GlobeConfigGroup 1 }

hh3cDot11StaKeepALiveTimerIntvl OBJECT-TYPE
    SYNTAX      Unsigned32
    UNITS       "second"
    MAX-ACCESS  read-write
    STATUS      current
    DESCRIPTION
        "Represents the interval of the keep alive requests sent between
        AP and STA.
        Default value 0 : The keep alive function is disabled."
    DEFVAL      { 0 }
    ::= { hh3cDot11GlobeConfigGroup 2 }

hh3cDot11StaIdleTimerIntvl OBJECT-TYPE
    SYNTAX      Integer32
    UNITS       "second"
    MAX-ACCESS  read-write
    STATUS      current
    DESCRIPTION
        "Represents the interval for which the link between AP and STA
        ( power-save or awake ) can be idle."
    ::= { hh3cDot11GlobeConfigGroup 3 }

hh3cDot11BroadcastProbeReply OBJECT-TYPE
    SYNTAX      TruthValue
    MAX-ACCESS  read-write
    STATUS      current
    DESCRIPTION
        "Represents enable the AP to reply broadcast probe or not.
        'true' : The AP to reply broadcast probe is enabled.
        'false': The AP to reply broadcast probe is disabled"
    DEFVAL      { true }
    ::= { hh3cDot11GlobeConfigGroup 4 }

hh3cDot11APScanMode OBJECT-TYPE
    SYNTAX      INTEGER
        {
            active(1),
            passive(2)
        }
    MAX-ACCESS  read-write
    STATUS      current
    DESCRIPTION
        "Represents the scanning mode for AP.
        The following values are supported:
        active   - AP will actively do scan.
        passive  - AP will passively do scan."
    DEFVAL      { passive }
    ::= { hh3cDot11GlobeConfigGroup 5 }

hh3cDot11ACCtrlTunnelSecSupport OBJECT-TYPE
    SYNTAX      Hh3cDot11TunnelSecSchemType
    MAX-ACCESS  read-write
    STATUS      current
    DESCRIPTION
        "Represents what security schemes are supported for CAPWAP Control
        tunnel."
    ::= { hh3cDot11GlobeConfigGroup 6 }

hh3cDot11ACDataTunnelSecSupport OBJECT-TYPE
    SYNTAX      Hh3cDot11TunnelSecSchemType
    MAX-ACCESS  read-write
    STATUS      current
    DESCRIPTION
        "Represents what security schemes are supported for CAPWAP data
        tunnel.  The cleartxt is the default scheme."
    DEFVAL      { cleartxt }
    ::= { hh3cDot11GlobeConfigGroup 7 }

hh3cDot11ACAutoAPSupport OBJECT-TYPE
    SYNTAX      TruthValue
    MAX-ACCESS  read-write
    STATUS      current
    DESCRIPTION
        "Represents enable the auto AP functionality or not.
        'true' : The auto AP functionality is enabled.
        'false': The auto AP functionality is disabled"
    DEFVAL      { false }
    ::= { hh3cDot11GlobeConfigGroup 8 }

hh3cDot11AutoAPName OBJECT-TYPE
    SYNTAX      OCTET STRING(SIZE(0..127))
    MAX-ACCESS  read-write
    STATUS      current
    DESCRIPTION
        "Represents the name of auto AP that needs to be made persistent.
        When read the value from the node, NULL value be returned."
    ::= { hh3cDot11GlobeConfigGroup 9 }

hh3cDot11PersistentName OBJECT-TYPE
    SYNTAX      OCTET STRING(SIZE(0..127))
    MAX-ACCESS  read-write
    STATUS      current
    DESCRIPTION
        "Represents the new name of auto AP after being made persistent.
        When read the value from the node, NULL value be returned."
    ::= { hh3cDot11GlobeConfigGroup 10 }

hh3cDot11IntfTrapThreshold OBJECT-TYPE
    SYNTAX      Integer32
    UNITS       "dbm"
    MAX-ACCESS  read-write
    STATUS      current
    DESCRIPTION
        "Represents threshold of interference trap.  If signal strength of
        the device exceeds this threshold, corresponding trap will
        be sent."
    ::= { hh3cDot11GlobeConfigGroup 11 }

hh3cDot11MonitorInterval OBJECT-TYPE
    SYNTAX      Unsigned32(0 | 5..15)
    UNITS       "minute"
    MAX-ACCESS  read-write
    STATUS      current
    DESCRIPTION
        "Represents the monitoring interval.
        Default value 0 : The monitoring functionality is changed to
        real-time mode."
    DEFVAL      { 0 }
    ::= { hh3cDot11GlobeConfigGroup 12 }

hh3cDot11SampleInterval OBJECT-TYPE
    SYNTAX      Unsigned32(0 | 10..300)
    UNITS       "second"
    MAX-ACCESS  read-write
    STATUS      current
    DESCRIPTION
        "Represents the sampling interval.
        Default value 0 : The sampling functionality is disabled."
    DEFVAL      { 0 }
    ::= { hh3cDot11GlobeConfigGroup 13 }

hh3cDot11ChnlSwitChkInterval OBJECT-TYPE
    SYNTAX      Unsigned32(8..180)
    UNITS       "minute"
    MAX-ACCESS  read-write
    STATUS      current
    DESCRIPTION
        "Represents the checking interval of channel switch."
    DEFVAL      { 8 }
    ::= { hh3cDot11GlobeConfigGroup 14 }

hh3cDot11APUserUplimit OBJECT-TYPE
    SYNTAX      Unsigned32(0..65535)
    MAX-ACCESS  read-write
    STATUS      current
    DESCRIPTION
        "Represents the upper limit of user which has access to this AP."
    ::= { hh3cDot11GlobeConfigGroup 15 }

hh3cDot11APL2IsolateEnable OBJECT-TYPE
    SYNTAX      TruthValue
    MAX-ACCESS  read-write
    STATUS      current
    DESCRIPTION
        "Represents enable the layer2 isolation or not.
        'true' : The layer2 isolation functionality is enabled.
        'false': The layer2 isolation functionality is disabled."
    DEFVAL      { false }
    ::= { hh3cDot11GlobeConfigGroup 16 }

hh3cDot11APBSSIDSupportNum OBJECT-TYPE
    SYNTAX      Integer32
    MAX-ACCESS  read-only
    STATUS      current
    DESCRIPTION
        "Represents the max number of BSSID supported by Current AP."
    ::= { hh3cDot11GlobeConfigGroup 17 }

hh3cDot11APLastUpdateStatTime OBJECT-TYPE
    SYNTAX      DateAndTime
    MAX-ACCESS  read-only
    STATUS      current
    DESCRIPTION
        "Represents date and time update statistic information lately."
    ::= { hh3cDot11GlobeConfigGroup 18 }

hh3cDot11APDoSProtectEnable OBJECT-TYPE
    SYNTAX      TruthValue
    MAX-ACCESS  read-write
    STATUS      current
    DESCRIPTION
        "Represents enable the DOS protection or not.
        'true' : The DOS protection functionality is enabled.
        'false': The DOS protection functionality is disabled."
    DEFVAL      { false }
    ::= { hh3cDot11GlobeConfigGroup 19 }

hh3cDot11MaxAPPerIf OBJECT-TYPE
    SYNTAX      Unsigned32(0..65535)
    MAX-ACCESS  read-write
    STATUS      current
    DESCRIPTION
        "Represents max AP number that can be connected to AC interface."
    ::= { hh3cDot11GlobeConfigGroup 20 }

hh3cDot11SampleTimeStamp OBJECT-TYPE
    SYNTAX      DateAndTime
    MAX-ACCESS  read-only
    STATUS      current
    DESCRIPTION
        "Represents the start time of current sample period."
    ::= { hh3cDot11GlobeConfigGroup 21 }

hh3cDot11UplinkTrackId OBJECT-TYPE
    SYNTAX      Unsigned32
    MAX-ACCESS  read-write
    STATUS      current
    DESCRIPTION
        "Represents the track id of AP.
        Default value 0 : The uplink track function for AP is disabled."
    DEFVAL      { 0 }
    ::= { hh3cDot11GlobeConfigGroup 22 }

hh3cDot11RtCollectSwitch OBJECT-TYPE
    SYNTAX      TruthValue
    MAX-ACCESS  read-write
    STATUS      current
    DESCRIPTION
        "This object is used to turn on/off real-time statistics collection
         between AC and AP.  If the value is true, hh3cDot11RtCollectIntvl will
         take effect.  Otherwise, hh3cDot11RglCollectIntvl will take effect."
    DEFVAL      { false }
    ::= { hh3cDot11GlobeConfigGroup 23 }

hh3cDot11RglCollectIntvl OBJECT-TYPE
    SYNTAX      Integer32
    UNITS       "second"
    MAX-ACCESS  read-write
    STATUS      current
    DESCRIPTION
        "This object represents interval to regularly collect statistics from
         AC to AP."
    ::= { hh3cDot11GlobeConfigGroup 24 }

hh3cDot11RtCollectIntvl OBJECT-TYPE
    SYNTAX      Integer32
    UNITS       "second"
    MAX-ACCESS  read-write
    STATUS      current
    DESCRIPTION
        "This object represents interval to collect real-time statistics from
         AC to AP."
    ::= { hh3cDot11GlobeConfigGroup 25 }

hh3cDot11AllAPCpuUsageThreshold OBJECT-TYPE
    SYNTAX      Integer32(0..100)
    UNITS       "onepercent"
    MAX-ACCESS  read-write
    STATUS      current
    DESCRIPTION
        "The CPU usage threshold for all AP."
    ::= { hh3cDot11GlobeConfigGroup 26 }

hh3cDot11AllAPMemUsageThreshold OBJECT-TYPE
    SYNTAX      Integer32(0..100)
    UNITS       "onepercent"
    MAX-ACCESS  read-write
    STATUS      current
    DESCRIPTION
        "The memory usage threshold for all AP."
    ::= { hh3cDot11GlobeConfigGroup 27 }

hh3cDot11AdjIntfTrapThreshold OBJECT-TYPE
    SYNTAX      Integer32
    UNITS       "dbm"
    MAX-ACCESS  read-write
    STATUS      current
    DESCRIPTION
        "Represents threshold of adjacent interference trap.  If signal strength
        of the device exceeds this threshold, corresponding trap will be sent."
    ::= { hh3cDot11GlobeConfigGroup 28 }

hh3cDot11AllAPMonitorMode OBJECT-TYPE
    SYNTAX      INTEGER
        {
            normal(1),
            monitor(2),
            hybrid(3)
        }
    MAX-ACCESS  read-write
    STATUS      current
    DESCRIPTION
        "Represents what work mode for All AP.
        The following values are supported:
        normal,     - AP will supply WLAN service.
        monitor     - AP will be a monitor to find attack.
        hybrid      - AP will supply WLAN service and Device detection is
        enabled."
    DEFVAL      { normal }
    ::= { hh3cDot11GlobeConfigGroup 29 }

hh3cDot11GlobalApFmwUpdState OBJECT-TYPE
    SYNTAX      INTEGER
        {
            enable(1),
            disable(2)
        }
    MAX-ACCESS  read-write
    STATUS      current
    DESCRIPTION
        "Represents the status of version auto-update for an AP.
        The following values are supported:
        enable      - AP version will be updated automatically.
        disable     - AP version will not be updated automatically."
    DEFVAL      { enable }
    ::= { hh3cDot11GlobeConfigGroup 30 }

hh3cDot11ACNasIDCM OBJECT-TYPE
    SYNTAX      OCTET STRING
    MAX-ACCESS  read-write
    STATUS      current
    DESCRIPTION
        "Represents the NAS-ID of current AC."
    ::= { hh3cDot11GlobeConfigGroup 31 }

hh3cDot11ACRole OBJECT-TYPE
    SYNTAX      INTEGER
        {
            normal(1),
            central(2),
            local(3)
        }
    MAX-ACCESS  read-only
    STATUS      current
    DESCRIPTION
        "Current network status of AC.
        The following values are supported:
        normal,     - normal ac.
        central     - A central AC is an AC where local ACs are
                      configured, and it establishes CAPWAP tunnels
                      with the local ACs.
        local       - Local ACs provide network access to APs
                      and process client traffic. They are managed
                      by the central AC."
    DEFVAL      { normal }
    ::= { hh3cDot11GlobeConfigGroup 32 }

hh3cDot11GlobalLocalACState OBJECT-TYPE
    SYNTAX      INTEGER
        {
            enable(1),
            disable(2)
        }
    MAX-ACCESS  read-write
    STATUS      current
    DESCRIPTION
        "Represents the status of local-ac for an AC.
        The following values are supported:
        enable      - LocalAC state will be enabled.
        disable     - LocalAC state will not be enabled."
    DEFVAL      { disable }
    ::= { hh3cDot11GlobeConfigGroup 33 }

hh3cDot11CentralACIPAddress OBJECT-TYPE
    SYNTAX      IpAddress
    MAX-ACCESS  read-write
    STATUS      current
    DESCRIPTION
        "Represents the CentralAC IP address of LocalAC."
    ::= { hh3cDot11GlobeConfigGroup 34 }

hh3cDot11CentralACIPv6Address OBJECT-TYPE
    SYNTAX      OCTET STRING
    MAX-ACCESS  read-write
    STATUS      current
    DESCRIPTION
        "Represents the CentralAC IPv6 address of LocalAC."
    ::= { hh3cDot11GlobeConfigGroup 35 }

hh3cDot11iMcIP OBJECT-TYPE
    SYNTAX      IpAddress
    MAX-ACCESS  read-write
    STATUS      current
    DESCRIPTION
        "Represents the iMc IP address."
    ::= { hh3cDot11GlobeConfigGroup 36 }

hh3cDot11iMcPort OBJECT-TYPE
    SYNTAX      Integer32
    MAX-ACCESS  read-write
    STATUS      current
    DESCRIPTION
        "Represents the iMc Port."
    ::= { hh3cDot11GlobeConfigGroup 37 }

hh3cDot11APProvisionSave OBJECT-TYPE
    SYNTAX      OCTET STRING(SIZE(0..127))
    MAX-ACCESS  read-write
    STATUS      current
    DESCRIPTION
        "Sends the provisioned configuration to APs.
        When you read from this node, the system returns NULL."
    ::= { hh3cDot11GlobeConfigGroup 38 }

hh3cDot11ApRenameCurrentName OBJECT-TYPE
    SYNTAX      OCTET STRING(SIZE(0..127))
    MAX-ACCESS  read-write
    STATUS      current
    DESCRIPTION
        "Represents the current name of the AP that needs to be changed.
         When you read from the node, the system returns NULL."
    ::= { hh3cDot11GlobeConfigGroup 39 }

hh3cDot11ApRenameNewName OBJECT-TYPE
    SYNTAX      OCTET STRING(SIZE(0..127))
    MAX-ACCESS  read-write
    STATUS      current
    DESCRIPTION
        "Represents the new name of the AP.
         When you read from the node, the system returns NULL."
    ::= { hh3cDot11GlobeConfigGroup 40 }

hh3cDot11ACDescription OBJECT-TYPE
    SYNTAX      OCTET STRING
    MAX-ACCESS  read-write
    STATUS      current
    DESCRIPTION
        "This attribute will give more information about AC.
        Administrator could suggest the location, owner or
        other information for each AC.
        If the value is set to NULL, the description will be removed."
    ::= { hh3cDot11GlobeConfigGroup 41 }
-- *****************************************************************************
-- * End of hh3cDot11GlobeConfigGroup Definition
-- *****************************************************************************

-- *****************************************************************************
-- *  hh3cDot11RadioPolicyTable Definition
-- *****************************************************************************
hh3cDot11RadioPolicyTable OBJECT-TYPE
    SYNTAX      SEQUENCE OF Hh3cDot11RadioPolicyEntry
    MAX-ACCESS  not-accessible
    STATUS      current
    DESCRIPTION
        "The table defines the parameters for radio policy, as per
        radio policy of CLI.
        One radio policy could be assigned to the different radios (AP)."
    ::= { hh3cDot11PolicyConfigGroup 1 }

hh3cDot11RadioPolicyEntry OBJECT-TYPE
    SYNTAX      Hh3cDot11RadioPolicyEntry
    MAX-ACCESS  not-accessible
    STATUS      current
    DESCRIPTION
        "Each entry contains information of each radio policy."
    INDEX
        {
            IMPLIED hh3cDot11RadioPolicyName
        }
    ::= { hh3cDot11RadioPolicyTable 1 }

Hh3cDot11RadioPolicyEntry ::= SEQUENCE
    {
        hh3cDot11RadioPolicyName        OCTET STRING,
        hh3cDot11BeaconInterval         Integer32,
        hh3cDot11DtimInterval           Integer32,
        hh3cDot11RtsThreshold           Integer32,
        hh3cDot11FragThreshold          Integer32,
        hh3cDot11ShortRetryThreshold    Integer32,
        hh3cDot11LongRetryThreshold     Integer32,
        hh3cDot11MaxRxLifetime          Unsigned32,
        hh3cDot11RdoPolicyRowStatus     RowStatus,
        hh3cDot11RdoClientMaxCount      Integer32,
        hh3cDot11BeaconIntervalMs       Integer32
    }

hh3cDot11RadioPolicyName OBJECT-TYPE
    SYNTAX      OCTET STRING(SIZE(0..127))
    MAX-ACCESS  not-accessible
    STATUS      current
    DESCRIPTION
        "Represents the name of radio policy."
    ::= { hh3cDot11RadioPolicyEntry 1 }

hh3cDot11BeaconInterval OBJECT-TYPE
    SYNTAX      Integer32
    UNITS       "TU"
    MAX-ACCESS  read-create
    STATUS      current
    DESCRIPTION
        "Represents the interval for Beacon management frame."
    DEFVAL      { 100 }
    ::= { hh3cDot11RadioPolicyEntry 2 }

hh3cDot11DtimInterval OBJECT-TYPE
    SYNTAX      Integer32
    MAX-ACCESS  read-create
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL      { 1 }
    ::= { hh3cDot11RadioPolicyEntry 3 }

hh3cDot11RtsThreshold OBJECT-TYPE
    SYNTAX      Integer32
    UNITS       "byte"
    MAX-ACCESS  read-create
    STATUS      current
    DESCRIPTION
        "Represents the current minimum size, in octets, of the MAC
        protocol data unit (MPDU), below which a Request to send/Clear
        to send (RTS/CTS) handshake shall not be performed."
    DEFVAL      { 2346 }
    ::= { hh3cDot11RadioPolicyEntry 4 }

hh3cDot11FragThreshold OBJECT-TYPE
    SYNTAX      Integer32
    UNITS       "byte"
    MAX-ACCESS  read-create
    STATUS      current
    DESCRIPTION
        "Represents the current maximum size, in octets, of the MPDU that
        may be delivered to the PHY.  A MSDU shall be broken into
        fragments if its size exceeds the value of this attribute after
        adding MAC headers and trailers."
    DEFVAL      { 2346 }
    ::= { hh3cDot11RadioPolicyEntry 5 }

hh3cDot11ShortRetryThreshold OBJECT-TYPE
    SYNTAX      Integer32
    MAX-ACCESS  read-create
    STATUS      current
    DESCRIPTION
        "Represents the maximum number of transmission attempts of a
        frame, the length of which is less than or equal to
        hh3cDot11RTSThreshold, which shall be made before a failure
        condition is indicated."
    DEFVAL      { 7 }
    ::= { hh3cDot11RadioPolicyEntry 6 }

hh3cDot11LongRetryThreshold OBJECT-TYPE
    SYNTAX      Integer32
    MAX-ACCESS  read-create
    STATUS      current
    DESCRIPTION
        "Represents the maximum number of transmission attempts of a
        frame, the length of which is longer than hh3cDot11RTSThreshold,
        that shall be made before a failure condition is indicated."
    DEFVAL      { 4 }
    ::= { hh3cDot11RadioPolicyEntry 7 }

hh3cDot11MaxRxLifetime OBJECT-TYPE
    SYNTAX      Unsigned32
    UNITS       "millisecond"
    MAX-ACCESS  read-create
    STATUS      current
    DESCRIPTION
        "Represents the elapsed time.  After the time specified by
        hh3cDot11MaxRxLifetime, the further attempts to reassemble the
        MSDU shall be terminated."
    DEFVAL      { 2000 }
    ::= { hh3cDot11RadioPolicyEntry 8 }

hh3cDot11RdoPolicyRowStatus OBJECT-TYPE
    SYNTAX      RowStatus
    MAX-ACCESS  read-create
    STATUS      current
    DESCRIPTION
        "The status of this table entry."
    ::= { hh3cDot11RadioPolicyEntry 9 }

hh3cDot11RdoClientMaxCount OBJECT-TYPE
    SYNTAX      Integer32(0..2147483647)
    MAX-ACCESS  read-create
    STATUS      current
    DESCRIPTION
        "Represent the maximum number of stations supported by
        this radio policy."
    ::= { hh3cDot11RadioPolicyEntry 10 }

hh3cDot11BeaconIntervalMs OBJECT-TYPE
    SYNTAX      Integer32
    UNITS       "ms"
    MAX-ACCESS  read-create
    STATUS      current
    DESCRIPTION
        "Represents the interval for Beacon management frame."
    ::= { hh3cDot11RadioPolicyEntry 11 }
-- *****************************************************************************
-- * End of hh3cDot11RadioPolicyTable Definition
-- *****************************************************************************

-- *****************************************************************************
-- *  hh3cDot11ServicePolicyTable Definition
-- *****************************************************************************
hh3cDot11ServicePolicyTable OBJECT-TYPE
    SYNTAX      SEQUENCE OF Hh3cDot11ServicePolicyEntry
    MAX-ACCESS  not-accessible
    STATUS      current
    DESCRIPTION
        "The table defines the parameters for ESS, as per service policy
        of CLI.
        One service policy could be assigned to the different radios
        (AP)."
    ::= { hh3cDot11PolicyConfigGroup 2 }

hh3cDot11ServicePolicyEntry OBJECT-TYPE
    SYNTAX      Hh3cDot11ServicePolicyEntry
    MAX-ACCESS  not-accessible
    STATUS      current
    DESCRIPTION
        "Each entry contains information of each service policy."
    INDEX
        {
            hh3cDot11ServicePolicyID
        }
    ::= { hh3cDot11ServicePolicyTable 1 }

Hh3cDot11ServicePolicyEntry ::= SEQUENCE
    {
        hh3cDot11ServicePolicyID       Hh3cDot11ServicePolicyIDType,
        hh3cDot11SSIDName              Hh3cDot11SSIDStringType,
        hh3cDot11SSIDHidden            TruthValue,
        hh3cDot11AuthenMode            Hh3cDot11AuthenType,
        hh3cDot11SSIDEncryptionMode    Hh3cDot11SSIDEncryptModeType,
        hh3cDot11WlanInfBindingType    OCTET STRING,
        hh3cDot11WlanInfBindingID      Integer32,
        hh3cDot11SrvPolicyRowStatus    RowStatus,
        hh3cDot11ClientMaxCount        Integer32,
        hh3cDot11SPInCirMode           Hh3cDot11CirMode,
        hh3cDot11SPInCirValue          Integer32,
        hh3cDot11SPOutCirMode          Hh3cDot11CirMode,
        hh3cDot11SPOutCirValue         Integer32,
        hh3cDot11WlanInfPVID           Integer32,
        hh3cDot11SPInCirStaticValue    Integer32,
        hh3cDot11SPOutCirStaticValue   Integer32,
        hh3cDot11SPIsolate             TruthValue,
        hh3cDot11WlanexAuthServerIP    IpAddress,
        hh3cDot11SPBeaconMeasEnable    TruthValue,
        hh3cDot11SPBeaconMeasType      INTEGER,
        hh3cDot11SPBeaconMeasInterval  Integer32,
        hh3cDot11AuthenModeCM          INTEGER,
        hh3cDot11SecIEStatusCM         INTEGER,
        hh3cDot11SecurityCiphersCM     INTEGER,
        hh3cDot11SrvPolicyStatusCM     INTEGER,
        hh3cDot11SSIDHiddenCM          Hh3cDot11TruthValueCM,
        hh3cDot11SPIsolateCM           Hh3cDot11TruthValueCM,
        hh3cDot11FwdVlanBitMapLow      OCTET STRING,
        hh3cDot11FwdVlanBitMapHigh     OCTET STRING,
        hh3cDot11ServicePolicyName     OCTET STRING,
        hh3cDot11SecurityModeCM        INTEGER,
        hh3cDot11SPInCbsValue          Integer32,
        hh3cDot11SPOutCbsValue         Integer32,
        hh3cDot11WlanInfCustomerPVID   Integer32
    }

hh3cDot11ServicePolicyID OBJECT-TYPE
    SYNTAX      Hh3cDot11ServicePolicyIDType
    MAX-ACCESS  not-accessible
    STATUS      current
    DESCRIPTION
        "Represents the ID of each service policy."
    ::= { hh3cDot11ServicePolicyEntry 1 }

hh3cDot11SSIDName OBJECT-TYPE
    SYNTAX      Hh3cDot11SSIDStringType
    MAX-ACCESS  read-create
    STATUS      current
    DESCRIPTION
        "Represents the ESS.  As per CLI, the value of
        service policy name will be SSID."
    ::= { hh3cDot11ServicePolicyEntry 2 }

hh3cDot11SSIDHidden OBJECT-TYPE
    SYNTAX      TruthValue
    MAX-ACCESS  read-create
    STATUS      current
    DESCRIPTION
        "This attribute controls whether the SSID will be advertised in
        the beacon frame.
        If it is true, then SSID will not be advertised in the beacon
        frame."
    DEFVAL      { false }
    ::= { hh3cDot11ServicePolicyEntry 3 }

hh3cDot11AuthenMode OBJECT-TYPE
    SYNTAX      Hh3cDot11AuthenType
    MAX-ACCESS  read-create
    STATUS      current
    DESCRIPTION
        "Represents the Authentication mode defined by 802.11."
    ::= { hh3cDot11ServicePolicyEntry 4 }

hh3cDot11SSIDEncryptionMode OBJECT-TYPE
    SYNTAX      Hh3cDot11SSIDEncryptModeType
    MAX-ACCESS  read-create
    STATUS      current
    DESCRIPTION
        "Represents the encryption mode for this ESS."
    ::= { hh3cDot11ServicePolicyEntry 5 }

hh3cDot11WlanInfBindingType OBJECT-TYPE
    SYNTAX      OCTET STRING
    MAX-ACCESS  read-create
    STATUS      current
    DESCRIPTION
        "Represents the service policy will bind to what kind of
        data forwarding interface."
    DEFVAL      { "WLAN-ESS" }
    ::= { hh3cDot11ServicePolicyEntry 6 }

hh3cDot11WlanInfBindingID OBJECT-TYPE
    SYNTAX      Integer32
    MAX-ACCESS  read-create
    STATUS      current
    DESCRIPTION
        "Represents the interface ID of the interface that ESS will
        bind to.
        If the value is set to -1, the binding will be removed."
    ::= { hh3cDot11ServicePolicyEntry 7 }

hh3cDot11SrvPolicyRowStatus OBJECT-TYPE
    SYNTAX      RowStatus
    MAX-ACCESS  read-create
    STATUS      current
    DESCRIPTION
        "The status of this table entry."
    ::= { hh3cDot11ServicePolicyEntry 8 }

hh3cDot11ClientMaxCount OBJECT-TYPE
    SYNTAX      Integer32(0..2147483647)
    MAX-ACCESS  read-create
    STATUS      current
    DESCRIPTION
        "Represent the maximum number of stations supported by
        this service policy."
    ::= { hh3cDot11ServicePolicyEntry 9 }

hh3cDot11SPInCirMode OBJECT-TYPE
    SYNTAX      Hh3cDot11CirMode
    MAX-ACCESS  read-create
    STATUS      current
    DESCRIPTION
        "
        CIR(committed information rate) mode of inbound direction.
        This object is useful only when the corresponding CIR is nonzero.
        If value of this object is changed, corresponding CIR will be reset."
    DEFVAL      { static }
    ::= { hh3cDot11ServicePolicyEntry 10 }

hh3cDot11SPInCirValue OBJECT-TYPE
    SYNTAX      Integer32
    UNITS       "Kbps"
    MAX-ACCESS  read-create
    STATUS      current
    DESCRIPTION
        "Represents the CIR of inbound direction of this service policy.
        If the value is 0, it means that no flow control is applied to
        the service policy, and the corresponding CIR mode is meaningless."
    DEFVAL      { 0 }
    ::= { hh3cDot11ServicePolicyEntry 11 }

hh3cDot11SPOutCirMode OBJECT-TYPE
    SYNTAX      Hh3cDot11CirMode
    MAX-ACCESS  read-create
    STATUS      current
    DESCRIPTION
        "
        CIR(committed information rate) mode of outbound direction.
        This object is useful only when the corresponding CIR is nonzero.
        If value of this object is changed, corresponding CIR will be reset."
    DEFVAL      { static }
    ::= { hh3cDot11ServicePolicyEntry 12 }

hh3cDot11SPOutCirValue OBJECT-TYPE
    SYNTAX      Integer32
    UNITS       "Kbps"
    MAX-ACCESS  read-create
    STATUS      current
    DESCRIPTION
        "Represents the CIR of outbound direction of this service policy.
        If the value is 0, it means that no flow control is applied to
        the service policy, and the corresponding CIR mode is meaningless."
    DEFVAL      { 0 }
    ::= { hh3cDot11ServicePolicyEntry 13 }

hh3cDot11WlanInfPVID OBJECT-TYPE
    SYNTAX      Integer32
    MAX-ACCESS  read-create
    STATUS      current
    DESCRIPTION
        "Represents the VLAN ID of SSID."
    DEFVAL      { 1 }
    ::= { hh3cDot11ServicePolicyEntry 14 }

hh3cDot11SPInCirStaticValue  OBJECT-TYPE
    SYNTAX      Integer32
    UNITS       "Kbps"
    MAX-ACCESS  read-create
    STATUS      current
    DESCRIPTION
        "Represents the CIR of inbound direction for static CIR mode."
    DEFVAL      { 0 }
        ::= { hh3cDot11ServicePolicyEntry 15 }

hh3cDot11SPOutCirStaticValue  OBJECT-TYPE
    SYNTAX      Integer32
    UNITS       "Kbps"
    MAX-ACCESS  read-create
    STATUS      current
    DESCRIPTION
        "Represents the CIR of outbound direction for static CIR mode."
    DEFVAL      { 0 }
        ::= { hh3cDot11ServicePolicyEntry 16 }

hh3cDot11SPIsolate OBJECT-TYPE
    SYNTAX      TruthValue
    MAX-ACCESS  read-create
    STATUS      current
    DESCRIPTION
        "If it is true, then stations connected with the service policy are
         isolated."
    DEFVAL      { false }
    ::= { hh3cDot11ServicePolicyEntry 17 }

hh3cDot11WlanexAuthServerIP OBJECT-TYPE
    SYNTAX     IpAddress
    MAX-ACCESS read-create
    STATUS     current
    DESCRIPTION
        "Represents the IP address of the Wlanex Authentication server"
    ::= {  hh3cDot11ServicePolicyEntry 18 }

hh3cDot11SPBeaconMeasEnable OBJECT-TYPE
    SYNTAX      TruthValue
    MAX-ACCESS  read-create
    STATUS      current
    DESCRIPTION
        "If it is true, then beacon-measurement is enabled."
    DEFVAL      { false }
    ::= { hh3cDot11ServicePolicyEntry 19  }

hh3cDot11SPBeaconMeasType OBJECT-TYPE
      SYNTAX      INTEGER
        {
            passive(1),
            active(2),
            beaconTable(3)
        }
    MAX-ACCESS  read-create
    STATUS      current
    DESCRIPTION
        "Represents what the work mode for BeaconMeasurement type.
        The following values are supported:
        passive,      - BeaconMeasurement will use the passive type.
        active        - BeaconMeasurement will use the active type.
        beaconTable   - BeaconMeasurement will use the beacon table type."
    DEFVAL      { beaconTable }
    ::= { hh3cDot11ServicePolicyEntry 20 }

hh3cDot11SPBeaconMeasInterval OBJECT-TYPE
    SYNTAX      Integer32(10..200)
    UNITS       "second"
    MAX-ACCESS  read-create
    STATUS      current
    DESCRIPTION
        "Represents the beacon-measurement interval."
    DEFVAL      { 60 }
    ::= { hh3cDot11ServicePolicyEntry 21 }

hh3cDot11AuthenModeCM OBJECT-TYPE
    SYNTAX      INTEGER
        {
            opensystem(0),
            sharedkey(1)
        }
    MAX-ACCESS  read-create
    STATUS      current
    DESCRIPTION
        "Represents the Authentication mode defined by 802.11."
    ::= { hh3cDot11ServicePolicyEntry 22 }

hh3cDot11SecIEStatusCM OBJECT-TYPE
    SYNTAX      INTEGER
        {
            none(0),
            wpa(1),
            wpa2(2),
            wlanex(3)
        }
    MAX-ACCESS  read-create
    STATUS      current
    DESCRIPTION
        "To enable the security Information element in the beacon and
        probe response frames sent by AP."
    ::= { hh3cDot11ServicePolicyEntry 23 }

hh3cDot11SecurityCiphersCM OBJECT-TYPE
    SYNTAX      INTEGER
        {
            none(0),
            wep40(1),
            wep104(2),
            tkip(3),
            aesccmp(4),
            wpisms4(5)
        }
    MAX-ACCESS  read-create
    STATUS      current
    DESCRIPTION
        "The WLAN system support the following cipher type for data frame
        encryption.
        none
        wep40
        wep104
        tkip
        aesccmp
        wpi-SMS4
        When the value of node equals to zero, it means no configuration or
        undo operation."
    ::= { hh3cDot11ServicePolicyEntry 24 }

hh3cDot11SrvPolicyStatusCM OBJECT-TYPE
    SYNTAX      INTEGER
        {
            off(0),
            on(1)
        }
    MAX-ACCESS read-create
    STATUS     current
    DESCRIPTION
        "The status of the Service Policy."
    ::= {  hh3cDot11ServicePolicyEntry 25 }

hh3cDot11SSIDHiddenCM OBJECT-TYPE
    SYNTAX      Hh3cDot11TruthValueCM
    MAX-ACCESS  read-create
    STATUS      current
    DESCRIPTION
        "This attribute controls whether the SSID will be advertised in
        beacon frames.
        If it is dot11true, the SSID will not be advertised in beacon
        frames."
    DEFVAL      { dot11false }
    ::= { hh3cDot11ServicePolicyEntry 26 }

hh3cDot11SPIsolateCM OBJECT-TYPE
    SYNTAX      Hh3cDot11TruthValueCM
    MAX-ACCESS  read-create
    STATUS      current
    DESCRIPTION
        "If it is dot11true, the clients connected with the service policy are
        isolated to each other."
    DEFVAL      { dot11false }
    ::= { hh3cDot11ServicePolicyEntry 27 }

hh3cDot11FwdVlanBitMapLow OBJECT-TYPE
    SYNTAX OCTET STRING (SIZE(0..256))
    MAX-ACCESS read-create
    STATUS current
    DESCRIPTION
        "Each octet within this value specifies a set of eight
         VLANs, with the first octet specifying VLANs 1 through 8,
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1' then that VLAN is untagged in the set of VLANs; the
         VLAN is not untagged if its bit has a value of '0'."
    ::= { hh3cDot11ServicePolicyEntry 28 }

hh3cDot11FwdVlanBitMapHigh OBJECT-TYPE
    SYNTAX OCTET STRING (SIZE(0..256))
    MAX-ACCESS read-create
    STATUS current
    DESCRIPTION
        "Each octet within this value specifies a set of eight
         VLANs, with the first octet specifying VLANs 1 through 8,
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1' then that VLAN is untagged in the set of VLANs; the
         VLAN is not untagged if its bit has a value of '0'."
    ::= { hh3cDot11ServicePolicyEntry 29 }

hh3cDot11ServicePolicyName OBJECT-TYPE
    SYNTAX      OCTET STRING
    MAX-ACCESS  read-create
    STATUS      current
    DESCRIPTION
        "Represents the name of each service policy."
    ::= { hh3cDot11ServicePolicyEntry 30 }

hh3cDot11SecurityModeCM OBJECT-TYPE
    SYNTAX INTEGER
        {
            none(0),
            psk(1),
            radius(2),
            wlanex(3)
        }
    MAX-ACCESS read-write
    STATUS current
    DESCRIPTION
        "Determines the security modes of the WLAN port.

        none  - The default value. No security mode is set.

        psk  - Access to the port is denied until the port client is
        authorized (by 802.1X key negotiation).

        radius  - Access to the port is denied until the port
        client is authorized (by 802.1X).

        wlanex  - Access to the port is denied until the port client is
        authenticated by wlan cert."
    ::= { hh3cDot11ServicePolicyEntry 31 }

 hh3cDot11SPInCbsValue  OBJECT-TYPE
    SYNTAX      Integer32
    UNITS       "byte"
    MAX-ACCESS  read-create
    STATUS      current
    DESCRIPTION
        "Represents the CBS of inbound direction of this service policy.
        If the value is 0, it means that the CBS is automatically calculated
        from the value of CIR."
    DEFVAL      { 0 }
    ::= { hh3cDot11ServicePolicyEntry 32 }

hh3cDot11SPOutCbsValue  OBJECT-TYPE
    SYNTAX      Integer32
    UNITS       "byte"
    MAX-ACCESS  read-create
    STATUS      current
    DESCRIPTION
        "Represents the CBS of outbound direction of this service policy.
        If the value is 0, it means that the CBS is automatically calculated
        from the value of CIR."
    DEFVAL      { 0 }
    ::= { hh3cDot11ServicePolicyEntry 33 }

hh3cDot11WlanInfCustomerPVID OBJECT-TYPE
    SYNTAX      Integer32
    MAX-ACCESS  read-create
    STATUS      current
    DESCRIPTION
        "Represents the customer PVID."
    ::= { hh3cDot11ServicePolicyEntry 34 }
-- *****************************************************************************
-- * End of hh3cDot11ServicePolicyTable Definition
-- *****************************************************************************

-- *****************************************************************************
-- *  hh3cDot11ServicePolicyExtTable Definition
-- *****************************************************************************
hh3cDot11ServicePolicyExtTable OBJECT-TYPE
    SYNTAX      SEQUENCE OF Hh3cDot11ServicePolicyExtEntry
    MAX-ACCESS  not-accessible
    STATUS      current
    DESCRIPTION
        "The table defines the parameters for ESS, as per service policy
        of CLI.
        When the value of hh3cDot11SSIDEncryptionMode equals to cipher(2),
        more configuration for a ESS will be put into the table."
    ::= { hh3cDot11PolicyConfigGroup 3 }

hh3cDot11ServicePolicyExtEntry OBJECT-TYPE
    SYNTAX      Hh3cDot11ServicePolicyExtEntry
    MAX-ACCESS  not-accessible
    STATUS      current
    DESCRIPTION
        "Each entry contains information of each service policy under cipher(2)
        mode."
    INDEX
        {
            hh3cDot11ServicePolicyExtID
        }
    ::= { hh3cDot11ServicePolicyExtTable 1 }

Hh3cDot11ServicePolicyExtEntry ::= SEQUENCE
    {
        hh3cDot11ServicePolicyExtID       Hh3cDot11ServicePolicyIDType,
        hh3cDot11SecIEStatus              Hh3cDot11SecIEStatusType,
        hh3cDot11SecurityCiphers          Integer32,
        hh3cDot11CipherKeyIndex           Integer32,
        hh3cDot11CipherKey                OCTET STRING,
        hh3cDot11SrvPolicyExtRowStatus    RowStatus,
        hh3cDot11CipherKeyType            INTEGER,
        hh3cDot11AkmMode                  INTEGER,
        hh3cDot11PskKey                   OCTET STRING
    }

hh3cDot11ServicePolicyExtID OBJECT-TYPE
    SYNTAX      Hh3cDot11ServicePolicyIDType
    MAX-ACCESS  not-accessible
    STATUS      current
    DESCRIPTION
        "Represents the ID of each service policy."
    ::= { hh3cDot11ServicePolicyExtEntry 1 }

hh3cDot11SecIEStatus OBJECT-TYPE
    SYNTAX      Hh3cDot11SecIEStatusType
    MAX-ACCESS  read-create
    STATUS      current
    DESCRIPTION
        "To enable the security Information element in the beacon and
        probe response frames sent by AP."
    ::= { hh3cDot11ServicePolicyExtEntry 2 }

hh3cDot11SecurityCiphers OBJECT-TYPE
    SYNTAX      Integer32
    MAX-ACCESS  read-create
    STATUS      current
    DESCRIPTION
        "The WLAN system support the following cipher type for data frame
        encryption.
        wep40(2)
        tkip(4)
        aesccmp(16)
        wep104(32)
        wpisms4(64)
        wep128(128)
        For each service policy, it could support multiple cipher types at
        the same time.  So the value of object could combine multiple value
        of cipher type above.
        When the value of node equals to zero, it means no configuration or
        undo operation."
    ::= { hh3cDot11ServicePolicyExtEntry 3 }

hh3cDot11CipherKeyIndex OBJECT-TYPE
    SYNTAX      Integer32
    MAX-ACCESS  read-create
    STATUS      current
    DESCRIPTION
        "Represents the key index of cipher key for packet.
        When hh3cDot11SecurityCiphers value is wep40 or wep104,
        the configuration will take effective."
    DEFVAL      { 1 }
    ::= { hh3cDot11ServicePolicyExtEntry 4 }

hh3cDot11CipherKey OBJECT-TYPE
    SYNTAX      OCTET STRING
    MAX-ACCESS  read-create
    STATUS      current
    DESCRIPTION
        "Represents the cipher key for packet.
        When hh3cDot11SecurityCiphers value is wep40 or wep104,
        the configuration will take effective."
    ::= { hh3cDot11ServicePolicyExtEntry 5 }

hh3cDot11SrvPolicyExtRowStatus OBJECT-TYPE
    SYNTAX      RowStatus
    MAX-ACCESS  read-create
    STATUS      current
    DESCRIPTION
        "The status of this table entry."
    ::= { hh3cDot11ServicePolicyExtEntry 6 }

hh3cDot11CipherKeyType OBJECT-TYPE
    SYNTAX      INTEGER
    {
        char(1),
        hex(2)
    }
    MAX-ACCESS  read-create
    STATUS      current
    DESCRIPTION
        "Represents the cipher key type of hh3cDot11CipherKey."
    DEFVAL    {1}
    ::= { hh3cDot11ServicePolicyExtEntry 7 }

hh3cDot11AkmMode OBJECT-TYPE
    SYNTAX      INTEGER
    {
        none(0),
        dot1x(1),
        psk(2)
    }
    MAX-ACCESS  read-create
    STATUS      current
    DESCRIPTION
        "The authentication and key management mode."
    DEFVAL    {0}
    ::= { hh3cDot11ServicePolicyExtEntry 8 }

hh3cDot11PskKey OBJECT-TYPE
    SYNTAX      OCTET STRING
    MAX-ACCESS  read-create
    STATUS      current
    DESCRIPTION
        "Represents the preshared key.  This configuration takes effect
        if the hh3cDot11AkmMode value is psk."
    ::= { hh3cDot11ServicePolicyExtEntry 9 }

-- *****************************************************************************
-- * End of hh3cDot11ServicePolicyExtTable Definition
-- *****************************************************************************

-- *****************************************************************************
-- *  hh3cDot11RadioPolicyExtTable Definition
-- *****************************************************************************
hh3cDot11RadioPolicyExtTable OBJECT-TYPE
    SYNTAX      SEQUENCE OF Hh3cDot11RadioPolicyExtEntry
    MAX-ACCESS  not-accessible
    STATUS      current
    DESCRIPTION
        "The table defines the radio policy of each radio.
        It can't be modified if the radio policy is a default radio policy."
    ::= { hh3cDot11PolicyConfigGroup 4 }

hh3cDot11RadioPolicyExtEntry OBJECT-TYPE
    SYNTAX      Hh3cDot11RadioPolicyExtEntry
    MAX-ACCESS  not-accessible
    STATUS      current
    DESCRIPTION
        "Each entry contains information of each radio policy."
    INDEX
        {
            hh3cDot11RPAPSerialID,
            hh3cDot11RPRadioID
        }
    ::= { hh3cDot11RadioPolicyExtTable 1 }

Hh3cDot11RadioPolicyExtEntry ::= SEQUENCE
    {
        hh3cDot11RPAPSerialID             OCTET STRING,
        hh3cDot11RPRadioID                Hh3cDot11RadioScopeType,
        hh3cDot11RPBeaconInterval         Integer32,
        hh3cDot11RPDtimInterval           Integer32,
        hh3cDot11RPRtsThreshold           Integer32,
        hh3cDot11RPFragThreshold          Integer32,
        hh3cDot11RPShortRetryThreshold    Integer32,
        hh3cDot11RPLongRetryThreshold     Integer32,
        hh3cDot11RPClientMaxCount         Integer32,
        hh3cDot11RPBeaconIntervalCM       Integer32
    }

hh3cDot11RPAPSerialID OBJECT-TYPE
    SYNTAX      OCTET STRING(SIZE(0..127))
    MAX-ACCESS  not-accessible
    STATUS      current
    DESCRIPTION
        "This object represents the Serial ID of AP."
    ::= { hh3cDot11RadioPolicyExtEntry 1 }

hh3cDot11RPRadioID OBJECT-TYPE
    SYNTAX      Hh3cDot11RadioScopeType
    MAX-ACCESS  not-accessible
    STATUS      current
    DESCRIPTION
        "This object represents each radio."
    ::= { hh3cDot11RadioPolicyExtEntry 2 }

hh3cDot11RPBeaconInterval OBJECT-TYPE
    SYNTAX      Integer32
    UNITS       "milliseconds"
    MAX-ACCESS  read-write
    STATUS      current
    DESCRIPTION
        "This object represents the interval for Beacon management frame."
    DEFVAL      { 100 }
    ::= { hh3cDot11RadioPolicyExtEntry 3 }

hh3cDot11RPDtimInterval OBJECT-TYPE
    SYNTAX      Integer32
    MAX-ACCESS  read-write
    STATUS      current
    DESCRIPTION
        "This object represents the number of beacon intervals that shall elapse
        between transmissions of Beacons frames containing a Traffic
        Indication Map (TIM) element whose DTIM count field is 0.
        This value is transmitted in the Delivery TIM (DTIM) Period
        field of Beacon frames."
    DEFVAL      { 1 }
    ::= { hh3cDot11RadioPolicyExtEntry 4 }

hh3cDot11RPRtsThreshold OBJECT-TYPE
    SYNTAX      Integer32
    UNITS       "byte"
    MAX-ACCESS  read-write
    STATUS      current
    DESCRIPTION
        "This object represents the current minimum size, in octets, of the MAC
        protocol data unit (MPDU), below which a Request to send/Clear
        to send (RTS/CTS) handshake shall not be performed."
    DEFVAL      { 2346 }
    ::= { hh3cDot11RadioPolicyExtEntry 5 }

hh3cDot11RPFragThreshold OBJECT-TYPE
    SYNTAX      Integer32
    UNITS       "byte"
    MAX-ACCESS  read-write
    STATUS      current
    DESCRIPTION
        "This object represents the current maximum size, in octets, of the MPDU
         that may be delivered to the PHY.  A MSDU shall be broken into
        fragments if its size exceeds the value of this attribute after
        adding MAC headers and trailers."
    DEFVAL      { 2346 }
    ::= { hh3cDot11RadioPolicyExtEntry 6 }

hh3cDot11RPShortRetryThreshold OBJECT-TYPE
    SYNTAX      Integer32
    MAX-ACCESS  read-write
    STATUS      current
    DESCRIPTION
        "This object represents the maximum number of transmission attempts of a
        frame, the length of which is less than or equal to
        hh3cDot11RTSThreshold, that shall be made before a failure
        condition is indicated."
    DEFVAL      { 7 }
    ::= { hh3cDot11RadioPolicyExtEntry 7 }

hh3cDot11RPLongRetryThreshold OBJECT-TYPE
    SYNTAX      Integer32
    MAX-ACCESS  read-write
    STATUS      current
    DESCRIPTION
        "This object represents the maximum number of transmission attempts of a
        frame, the length of which is longer than hh3cDot11RTSThreshold,
        and that shall be made before a failure condition is indicated."
    DEFVAL      { 4 }
    ::= { hh3cDot11RadioPolicyExtEntry 8 }

hh3cDot11RPClientMaxCount OBJECT-TYPE
    SYNTAX      Integer32(0..2147483647)
    MAX-ACCESS  read-write
    STATUS      current
    DESCRIPTION
        "This object represents the maximum number of stations supported by
        this radio policy."
    ::= { hh3cDot11RadioPolicyExtEntry 9 }

hh3cDot11RPBeaconIntervalCM OBJECT-TYPE
    SYNTAX      Integer32
    UNITS       "timeunit"
    MAX-ACCESS  read-write
    STATUS      current
    DESCRIPTION
        "This object represents beacon interval."
    DEFVAL      { 100 }
    ::= { hh3cDot11RadioPolicyExtEntry 10 }

-- *****************************************************************************
-- * End of hh3cDot11RadioPolicyTable Definition
-- *****************************************************************************
-- *****************************************************************************
-- *  hh3cDot11ServicePolicyPortSecurityTable Definition
-- *****************************************************************************
hh3cDot11SrvPortSecurityTable OBJECT-TYPE
    SYNTAX      SEQUENCE OF Hh3cDot11SrvPortSecurityEntry
    MAX-ACCESS  not-accessible
    STATUS      current
    DESCRIPTION
        "This table defines the WLAN security status for ESS, BSS and
        WLAN-Ethernet interface which binding the crypto service-template.
        Otherwise, when binding the clear service-template,
        hh3cPortSecurityTables should be used to configure port security."
    ::= { hh3cDot11PolicyConfigGroup 5 }

hh3cDot11SrvPortSecurityEntry OBJECT-TYPE
    SYNTAX      Hh3cDot11SrvPortSecurityEntry
    MAX-ACCESS  not-accessible
    STATUS      current
    DESCRIPTION
        "There is a row in this table for service policy."
    INDEX
        {
            hh3cDot11SecurityServicePolicyID
        }
    ::= { hh3cDot11SrvPortSecurityTable 1 }

Hh3cDot11SrvPortSecurityEntry ::= SEQUENCE
    {
        hh3cDot11SecurityServicePolicyID           Hh3cDot11ServicePolicyIDType,
        hh3cDot11SrvPortSecurityMode               INTEGER,
        hh3cDot11SrvSecurityKeyType                INTEGER,
        hh3cDot11SrvSecurityPskKeyMode             INTEGER,
        hh3cDot11SrvSecurityPskKeyString           DisplayString,
        hh3cDot11SrvPortSecurityModeCM             INTEGER
    }

hh3cDot11SecurityServicePolicyID OBJECT-TYPE
    SYNTAX      Hh3cDot11ServicePolicyIDType
    MAX-ACCESS  not-accessible
    STATUS      current
    DESCRIPTION
        "Represents the ID of each service policy."
    ::= { hh3cDot11SrvPortSecurityEntry 1 }

hh3cDot11SrvPortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions  The default value, no any security mode is set.

        userLoginSecureExt  Access to the port is denied until the port
        client is authorized (by 802.1X).

        psk  Access to the port is denied until the port client is
        authorized (by 802.1X key negotiation).

        macAddressAndPsk  The MAC address is first authenticated and only if
        this succeeds does the psk then attempt user authentication.

        userLoginSecureExtOrPsk  This selects both the userLoginSecureExt and
        psk modes together such that either is allowed to authorized access.
        Which mode works for client depends on the client's choice.

        ext  Access to the port is denied until the port client is
        authenticated (by ext)."
    ::= { hh3cDot11SrvPortSecurityEntry 2 }

hh3cDot11SrvSecurityKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone  - This means the key type is not set yet.

        userLoginTxKeyTypeDot11Key  - This selects the 802.11 key type.

        userLoginTxKeyTypeRsaRC4Key  - This selects the RC4 key for RSA RC4
        session encryption."
    ::= { hh3cDot11SrvPortSecurityEntry 3 }

hh3cDot11SrvSecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode.  When input as pskKeyModePassPhrase,
        hh3cDot11SrvSecurityPskKeyString must be 8 to 63 characters;
        when input as pskKeyModeRawKey, hh3cDot11SrvSecurityPskKeyString
        must be 64 characters and each character must be '0'-'9', 'a'-'f' and
        'A'-'F'."
    ::= { hh3cDot11SrvPortSecurityEntry 4 }

hh3cDot11SrvSecurityPskKeyString OBJECT-TYPE
    SYNTAX      DisplayString(SIZE(0..64))
    MAX-ACCESS  read-write
    STATUS      current
    DESCRIPTION
        "This is the password string used for psk authentication."
    ::= { hh3cDot11SrvPortSecurityEntry 5 }

hh3cDot11SrvPortSecurityModeCM OBJECT-TYPE
    SYNTAX INTEGER
        {
            none(0),
            psk(1),
            radius(2),
            wlanex(3)
        }
    MAX-ACCESS read-write
    STATUS current
    DESCRIPTION
        "Determines the security modes of the WLAN port.

        none  - The default value, no any security mode is set.

        psk  - Access to the port is denied until the port client is
        authorized (by 802.1X key negotiation).

        radius  - Access to the port is denied until the port
        client is authorized (by 802.1X).

        wlanex  - Access to the port is denied until the port client is
        authenticated by wlan cert."
    ::= { hh3cDot11SrvPortSecurityEntry 6 }

hh3cDot11SrvL2AuthenTable OBJECT-TYPE
    SYNTAX      SEQUENCE OF Hh3cDot11SrvL2AuthenEntry
    MAX-ACCESS  not-accessible
    STATUS      current
    DESCRIPTION
        "This table defines the Layer 2 authentication status of service
         templates."
    ::= { hh3cDot11PolicyConfigGroup 7 }

hh3cDot11SrvL2AuthenEntry OBJECT-TYPE
    SYNTAX      Hh3cDot11SrvL2AuthenEntry
    MAX-ACCESS  not-accessible
    STATUS      current
    DESCRIPTION
        "There is a row for a service template."
    INDEX
        {
            hh3cDot11SrvL2AuthenID
        }
    ::= { hh3cDot11SrvL2AuthenTable 1 }

Hh3cDot11SrvL2AuthenEntry ::= SEQUENCE
    {
        hh3cDot11SrvL2AuthenID               Hh3cDot11ServicePolicyIDType,
        hh3cDot11L2AuthenMode                INTEGER,
        hh3cDot11L2IntrusProtectEnable       TruthValue,
        hh3cDot11L2IntrusProtectOpt          INTEGER,
        hh3cDot11TempServiceStopTimer        Integer32,
        hh3cDot11TempBlockMACTimer           Integer32,
        hh3cDot11L2IgnoreAuthorization       TruthValue,
        hh3cDot11L2FailVLAN                  Integer32,
        hh3cDot11L2CriticalVLAN              Integer32,
        hh3cDot11L2AuthorFailOffline         TruthValue,
        hh3cDot11L2AccountFailOffline        TruthValue,
        hh3cDot11Dot1xHSEnable               TruthValue,
        hh3cDot11Dot1xSecureHSEnable         TruthValue,
        hh3cDot11Dot1xReauthenEnable         TruthValue,
        hh3cDot11Dot1xMandatoryDomain        OCTET STRING,
        hh3cDot11Dot1xMaxUserCount           Integer32,
        hh3cDot11MACAuthenDomain             OCTET STRING,
        hh3cDot11MACAuthenMaxUserCount       Integer32
    }

hh3cDot11SrvL2AuthenID OBJECT-TYPE
    SYNTAX      Hh3cDot11ServicePolicyIDType
    MAX-ACCESS  not-accessible
    STATUS      current
    DESCRIPTION
        "Represents the ID of a service template."
    ::= { hh3cDot11SrvL2AuthenEntry 1 }

hh3cDot11L2AuthenMode OBJECT-TYPE
    SYNTAX      INTEGER
        {
            bypass(1),
            macAuthentication(2),
            macThenDot1xAuthentication(3),
            dot1xAuthentication(4),
            dot1xThenMacAuthentication(5),
            ouiThenDot1x(6),
            macAndDot1x(7)
        }
    MAX-ACCESS  read-write
    STATUS      current
    DESCRIPTION
        "Authentication mode of the service template.

        bypass  No authentication is required.

        macAuthentication  MAC authentication.

        macThenDot1xAuthentication  MAC authentication is executed first.
        If MAC authentication fails, 802.1X authentication is executed.

        dot1xAuthentication  Access to the port is denied until the client
        is authorized by 802.1X.

        dot1xThenMacAuthentication  802.1X authentication is executed first.
        If 802.1X authentication fails , MAC authentication is executed.

        ouiThenDot1x  OUI authentication is first executed.
        If OUI authentication fails, 802.1X authentication is executed."
    ::= { hh3cDot11SrvL2AuthenEntry 2 }

hh3cDot11L2IntrusProtectEnable OBJECT-TYPE
    SYNTAX      TruthValue
    MAX-ACCESS  read-write
    STATUS      current
    DESCRIPTION
        "Enables intrusion protection for the service template."
    ::= { hh3cDot11SrvL2AuthenEntry 3 }

hh3cDot11L2IntrusProtectOpt OBJECT-TYPE
    SYNTAX      INTEGER
        {
            blockMACTemporarily(1),
            stopServiceTemporarily(2),
            stopService(3)
        }
    MAX-ACCESS  read-write
    STATUS      current
    DESCRIPTION
        "Operation mode when intrusion is detected."
    ::= { hh3cDot11SrvL2AuthenEntry 4 }

hh3cDot11TempServiceStopTimer OBJECT-TYPE
    SYNTAX      Integer32(10..300)
    MAX-ACCESS  read-write
    STATUS      current
    DESCRIPTION
        "Time period for temporarily stopping service."
    ::= { hh3cDot11SrvL2AuthenEntry 5 }

hh3cDot11TempBlockMACTimer OBJECT-TYPE
    SYNTAX      Integer32(60..300)
    MAX-ACCESS  read-write
    STATUS      current
    DESCRIPTION
        "Time period for temporarily blocking user MACs."
    ::= { hh3cDot11SrvL2AuthenEntry 6 }

hh3cDot11L2IgnoreAuthorization OBJECT-TYPE
    SYNTAX      TruthValue
    MAX-ACCESS  read-write
    STATUS      current
    DESCRIPTION
        "Ignores all authorization information set by the server."
    ::= { hh3cDot11SrvL2AuthenEntry 7 }

hh3cDot11L2FailVLAN OBJECT-TYPE
    SYNTAX      Integer32(0..4094)
    MAX-ACCESS  read-write
    STATUS      current
    DESCRIPTION
        "VLAN for authentication failure.  0 means not configured."
    ::= { hh3cDot11SrvL2AuthenEntry 8 }

hh3cDot11L2CriticalVLAN OBJECT-TYPE
    SYNTAX      Integer32(0..4094)
    MAX-ACCESS  read-write
    STATUS      current
    DESCRIPTION
        "VLAN for server unavailability situation.  0 means not configured."
    ::= { hh3cDot11SrvL2AuthenEntry 9 }

hh3cDot11L2AuthorFailOffline OBJECT-TYPE
    SYNTAX      TruthValue
    MAX-ACCESS  read-write
    STATUS      current
    DESCRIPTION
        "Users are logged off if authorization fails."
    ::= { hh3cDot11SrvL2AuthenEntry 10 }

hh3cDot11L2AccountFailOffline OBJECT-TYPE
    SYNTAX      TruthValue
    MAX-ACCESS  read-write
    STATUS      current
    DESCRIPTION
        "Users are logged off if accounting fails."
    ::= { hh3cDot11SrvL2AuthenEntry 11 }

hh3cDot11Dot1xHSEnable OBJECT-TYPE
    SYNTAX      TruthValue
    MAX-ACCESS  read-write
    STATUS      current
    DESCRIPTION
        "Enables 802.1X handshake."
    ::= { hh3cDot11SrvL2AuthenEntry 12 }

hh3cDot11Dot1xSecureHSEnable OBJECT-TYPE
    SYNTAX      TruthValue
    MAX-ACCESS  read-write
    STATUS      current
    DESCRIPTION
        "Enables secure 802.1X handshake."
    ::= { hh3cDot11SrvL2AuthenEntry 13 }

hh3cDot11Dot1xReauthenEnable OBJECT-TYPE
    SYNTAX      TruthValue
    MAX-ACCESS  read-write
    STATUS      current
    DESCRIPTION
        "Enables 802.1X reauthentication."
    ::= { hh3cDot11SrvL2AuthenEntry 14 }

hh3cDot11Dot1xMandatoryDomain OBJECT-TYPE
    SYNTAX      OCTET STRING
    MAX-ACCESS  read-write
    STATUS      current
    DESCRIPTION
        "802.1X authentication domain of users for the service template."
    ::= { hh3cDot11SrvL2AuthenEntry 15 }

hh3cDot11Dot1xMaxUserCount OBJECT-TYPE
    SYNTAX      Integer32
    MAX-ACCESS  read-write
    STATUS      current
    DESCRIPTION
        "Maximum number of 802.1X users supported by the BSS bound to the service
        template."
    ::= { hh3cDot11SrvL2AuthenEntry 16 }

hh3cDot11MACAuthenDomain OBJECT-TYPE
    SYNTAX      OCTET STRING
    MAX-ACCESS  read-write
    STATUS      current
    DESCRIPTION
        "MAC authentication domain of users for the service template."
    ::= { hh3cDot11SrvL2AuthenEntry 17 }

hh3cDot11MACAuthenMaxUserCount OBJECT-TYPE
    SYNTAX      Integer32
    MAX-ACCESS  read-write
    STATUS      current
    DESCRIPTION
        "Maximum number of MAC authentication users supported by the BSS bound to
         the service template."
    ::= { hh3cDot11SrvL2AuthenEntry 18 }
-- *****************************************************************************
-- *  End of hh3cDot11PortSecurityTable Definition
-- *****************************************************************************

hh3cDot11IPLearningTable OBJECT-TYPE
    SYNTAX      SEQUENCE OF Hh3cDot11IPLearningEntry
    MAX-ACCESS  not-accessible
    STATUS      current
    DESCRIPTION
        "The table specifies the IP learning type and status
        of service templates."
    ::= { hh3cDot11PolicyConfigGroup 8 }
hh3cDot11IPLearningEntry OBJECT-TYPE
    SYNTAX      Hh3cDot11IPLearningEntry
    MAX-ACCESS  not-accessible
    STATUS      current
    DESCRIPTION
        "Each entry contains information about an IP learning entry."
    INDEX
        {
            hh3cDot11IPLearningServiceName,
            hh3cDot11IPLearningType
        }
    ::= { hh3cDot11IPLearningTable 1 }
Hh3cDot11IPLearningEntry ::=
    SEQUENCE {
        hh3cDot11IPLearningServiceName      OCTET STRING,
        hh3cDot11IPLearningType             INTEGER,
        hh3cDot11IPLearningStatus           TruthValue,
        hh3cDot11IPLearningVlanBitMapL      OCTET STRING,
        hh3cDot11IPLearningVlanBitMapH      OCTET STRING
    }
hh3cDot11IPLearningServiceName  OBJECT-TYPE
    SYNTAX      OCTET STRING(SIZE (1..255))
    MAX-ACCESS  not-accessible
    STATUS      current
    DESCRIPTION
        "Represents the service name."
::= { hh3cDot11IPLearningEntry 1 }
hh3cDot11IPLearningType OBJECT-TYPE
    SYNTAX      INTEGER {
                invalid(1),
                arp(2),
                dhcp(3),
                dhcp6(4),
                nd(5)
                }
    MAX-ACCESS  not-accessible
    STATUS      current
    DESCRIPTION
        "Represents the IP learning type."
    ::= { hh3cDot11IPLearningEntry 2 }
hh3cDot11IPLearningStatus OBJECT-TYPE
    SYNTAX      TruthValue
    MAX-ACCESS  read-write
    STATUS      current
    DESCRIPTION
        "Represents the ip learning status of the interface.
         Setting this attribute to true enables IP learning on the interface."
    ::= { hh3cDot11IPLearningEntry 3 }
hh3cDot11IPLearningVlanBitMapL OBJECT-TYPE
    SYNTAX      OCTET STRING(SIZE(1..256))
    MAX-ACCESS  read-write
    STATUS      current
    DESCRIPTION
        "Each octet within this value specifies a set of eight
         VLANs, with the first octet specifying VLANs 1 through 8 and
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1', that VLAN is untagged in the set of VLANs; the
         VLAN is not untagged if its bit has a value of '0'."
    ::= { hh3cDot11IPLearningEntry 4 }
hh3cDot11IPLearningVlanBitMapH OBJECT-TYPE
    SYNTAX      OCTET STRING(SIZE(1..256))
    MAX-ACCESS  read-write
    STATUS      current
    DESCRIPTION
        "Each octet within this value specifies a set of eight
         VLANs, with the first octet specifying VLANs 1 through 8 and
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1', that VLAN is untagged in the set of VLANs; the
         VLAN is not untagged if its bit has a value of '0'."
    ::= { hh3cDot11IPLearningEntry 5 }
-- *****************************************************************************
-- *  hh3cDot11SrvPolicyExtendTable Definition
-- *****************************************************************************
hh3cDot11SrvPolicyExtendTable OBJECT-TYPE
    SYNTAX      SEQUENCE OF Hh3cDot11SrvPolicyExtendEntry
    MAX-ACCESS  not-accessible
    STATUS      current
    DESCRIPTION
        "The table defines the parameters of each service policy."
    ::= { hh3cDot11PolicyConfigGroup 6 }

hh3cDot11SrvPolicyExtendEntry OBJECT-TYPE
    SYNTAX      Hh3cDot11SrvPolicyExtendEntry
    MAX-ACCESS  not-accessible
    STATUS      current
    DESCRIPTION
        "Each entry contains information of each service policy."
    INDEX
        {
            hh3cDot11ServicePolicyID
        }
    ::= { hh3cDot11SrvPolicyExtendTable 1 }

Hh3cDot11SrvPolicyExtendEntry ::= SEQUENCE
    {
        hh3cDot11SPEnable              INTEGER
    }

hh3cDot11SPEnable OBJECT-TYPE
    SYNTAX      INTEGER
    {
        enable(1),
        disable(2)
    }
    MAX-ACCESS  read-write
    STATUS      current
    DESCRIPTION
        "Represents whether the service policy is enabled."
    ::= { hh3cDot11SrvPolicyExtendEntry 1 }

-- *****************************************************************************
-- *  End of hh3cDot11ServicePolicyExtendTable Definition
-- *****************************************************************************

-- *****************************************************************************
-- *  hh3cDot11APTemplateTable Definition
-- *****************************************************************************
hh3cDot11APTemplateTable OBJECT-TYPE
    SYNTAX      SEQUENCE OF Hh3cDot11APTemplateEntry
    MAX-ACCESS  not-accessible
    STATUS      current
    DESCRIPTION
        "By AP template CLI, administrator will configure the parameters of AP
        by convenience.
        Before AP boot up and connect to AC by CAPWAP tunnel, administrator
        will create AP template for each AP.  When AP connect to AC,
        AC will assign configuration to AP by hh3cDot11APSerialID
        information in AP template."
    ::= { hh3cDot11APConfigGroup 1 }

hh3cDot11APTemplateEntry OBJECT-TYPE
    SYNTAX      Hh3cDot11APTemplateEntry
    MAX-ACCESS  not-accessible
    STATUS      current
    DESCRIPTION
        "Each entry contains configuration information for each AP."
    INDEX
        {
            hh3cDot11APTemplateName
        }
    ::= { hh3cDot11APTemplateTable 1 }

Hh3cDot11APTemplateEntry ::= SEQUENCE
    {
        hh3cDot11APTemplateName             OCTET STRING,
        hh3cDot11APSerialID                 OCTET STRING,
        hh3cDot11TemplateAPModelAlias       OCTET STRING,
        hh3cDot11Description                OCTET STRING,
        hh3cDot11APWorkMode                 INTEGER,
        hh3cDot11APTemplateRowStatus        RowStatus,
        hh3cDot11APName                     OCTET STRING,
        hh3cDot11StatisInterv               Integer32,
        hh3cDot11APBroadcastProbeReply      TruthValue,
        hh3cDot11StaIdleTimerInterv         Integer32,
        hh3cDot11StaKeepAliveTimerInterv    Integer32,
        hh3cDot11APCir                      Integer32,
        hh3cDot11APCbs                      Integer32,
        hh3cDot11APPriorityLevel            Integer32,
        hh3cDot11APElementID                Integer32,
        hh3cDot11APDevDetectEnable          TruthValue,
        hh3cDot11APGetIPMethod              INTEGER,
        hh3cDot11StatisIntervMode           INTEGER,
        hh3cDot11ApTrapEnabled              TruthValue,
        hh3cDot11ApFmwUpdState              INTEGER,
        hh3cDot11StatisIntervModeCM         INTEGER,
        hh3cDot11ApNasIDCM                  OCTET STRING,
        hh3cDot11ApCoveragetype             INTEGER,
        hh3cDot11APControlAddressState      INTEGER,
        hh3cDot11APControlAddressIPv4       IpAddress,
        hh3cDot11APControlAddressIPv6       OCTET STRING,
        hh3cDot11APLocalACName              OCTET STRING,
        hh3cDot11APEchoInterval             Integer32,
        hh3cDot11APProvisionAPIPv4          IpAddress,
        hh3cDot11APProvisionIPv4Mask        Integer32,
        hh3cDot11APProvisionAPIPv6          OCTET STRING,
        hh3cDot11APProvisionIPv6PrefixLen   Integer32,
        hh3cDot11APProvisionACIPv4          IpAddress,
        hh3cDot11APProvisionACIpv6          OCTET STRING,
        hh3cDot11APProvisionGateWayIPV4     IpAddress,
        hh3cDot11APProvisionGateWayIPV6     OCTET STRING,
        hh3cDot11APMapConfigFileName        OCTET STRING
    }

hh3cDot11APTemplateName OBJECT-TYPE
    SYNTAX      OCTET STRING(SIZE(0..127))
    MAX-ACCESS  not-accessible
    STATUS      current
    DESCRIPTION
        "Represents the name of AP template."
    ::= { hh3cDot11APTemplateEntry 1 }

hh3cDot11APSerialID OBJECT-TYPE
    SYNTAX      OCTET STRING
    MAX-ACCESS  read-create
    STATUS      current
    DESCRIPTION
        "Represents AP serial id."
    ::= { hh3cDot11APTemplateEntry 2 }

hh3cDot11TemplateAPModelAlias OBJECT-TYPE
    SYNTAX      OCTET STRING
    MAX-ACCESS  read-create
    STATUS      current
    DESCRIPTION
        "Represents the alias of AP model name."
    ::= { hh3cDot11APTemplateEntry 3 }

hh3cDot11Description OBJECT-TYPE
    SYNTAX      OCTET STRING
    MAX-ACCESS  read-create
    STATUS      current
    DESCRIPTION
        "This attribute will give more information about AP.
        Administrator could suggest the location, owner or
        other information for each AP.
        If the value is set to NULL, the description will be removed."
    ::= { hh3cDot11APTemplateEntry 4 }

hh3cDot11APWorkMode OBJECT-TYPE
    SYNTAX      INTEGER
        {
            normal(1),
            monitor(2),
            hybrid(3)
        }
    MAX-ACCESS  read-create
    STATUS      current
    DESCRIPTION
        "Represents what work mode for AP.
        The following values are supported:
        normal      - AP will supply WLAN service.
        monitor     - AP will be a monitor to find attack.
        hybrid      - AP will supply WLAN service and Device detection is
        enabled."
    DEFVAL      { normal }
    ::= { hh3cDot11APTemplateEntry 5 }

hh3cDot11APTemplateRowStatus OBJECT-TYPE
    SYNTAX      RowStatus
    MAX-ACCESS  read-create
    STATUS      current
    DESCRIPTION
        "The status of this table entry."
    ::= { hh3cDot11APTemplateEntry 6 }

hh3cDot11APName OBJECT-TYPE
    SYNTAX      OCTET STRING
    MAX-ACCESS  read-create
    STATUS      current
    DESCRIPTION
        "Represents the AP name."
    ::= { hh3cDot11APTemplateEntry 7 }

hh3cDot11StatisInterv OBJECT-TYPE
    SYNTAX      Integer32
    UNITS       "second"
    MAX-ACCESS  read-create
    STATUS      current
    DESCRIPTION
        "Represents the interval of radio statistic."
    ::= { hh3cDot11APTemplateEntry 8 }

hh3cDot11APBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { hh3cDot11APTemplateEntry 9 }

hh3cDot11StaIdleTimerInterv OBJECT-TYPE
    SYNTAX      Integer32
    UNITS       "second"
    MAX-ACCESS  read-create
    STATUS      current
    DESCRIPTION
        "Represents the interval for which the link between AP and STA
        ( power-save or awake ) can be idle."
    ::= { hh3cDot11APTemplateEntry 10 }

hh3cDot11StaKeepAliveTimerInterv OBJECT-TYPE
    SYNTAX      Integer32
    UNITS       "second"
    MAX-ACCESS  read-create
    STATUS      current
    DESCRIPTION
        "Represents the interval of the keep alive requests sent between
        AP and STA."
    ::= { hh3cDot11APTemplateEntry 11 }

hh3cDot11APCir OBJECT-TYPE
    SYNTAX      Integer32
    UNITS       "Kbps"
    MAX-ACCESS  read-create
    STATUS      current
    DESCRIPTION
        "Represents the committed information rate between AP and AC."
    ::= { hh3cDot11APTemplateEntry 12 }

hh3cDot11APCbs OBJECT-TYPE
    SYNTAX      Integer32
    UNITS       "Bytes"
    MAX-ACCESS  read-create
    STATUS      current
    DESCRIPTION
        "Represents the committed burst size between AP and AC."
    ::= { hh3cDot11APTemplateEntry 13 }

hh3cDot11APPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { hh3cDot11APTemplateEntry 14 }

hh3cDot11APElementID OBJECT-TYPE
    SYNTAX      Integer32
    MAX-ACCESS  read-only
    STATUS      current
    DESCRIPTION
        "This object represents the AP element ID."
    ::= { hh3cDot11APTemplateEntry 15 }

hh3cDot11APDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services.  When an AP works
         in monitor mode, that is, the value of object hh3cDot11APWorkMode is
         monitor, device detection cannot be enabled with object
         hh3cDot11APDevDetectEnable."
    DEFVAL      { false }
    ::= { hh3cDot11APTemplateEntry 16 }

hh3cDot11APGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { hh3cDot11APTemplateEntry 17 }

hh3cDot11StatisIntervMode OBJECT-TYPE
    SYNTAX      INTEGER
    {
        normal(1),
        realtime(2)
    }
    MAX-ACCESS  read-create
    STATUS      current
    DESCRIPTION
        "This object represents the mode of statics interval.
         normal    - statics interval value between 10s to 240s
         realtime  - statics interval value between 0s to 5s"
    DEFVAL      { normal }
    ::= { hh3cDot11APTemplateEntry 18 }

hh3cDot11ApTrapEnabled OBJECT-TYPE
    SYNTAX      TruthValue
    MAX-ACCESS  read-write
    STATUS      current
    DESCRIPTION
        "Represents whether the trap status is enabled or not.
        'true'  : Enable  the trap status;
        'false' : Disable the trap status."
    DEFVAL      { true }
    ::= { hh3cDot11APTemplateEntry 19 }

hh3cDot11ApFmwUpdState OBJECT-TYPE
    SYNTAX      INTEGER
    {
        enable(1),
        disable(2),
        inherit(3)
    }
    MAX-ACCESS  read-create
    STATUS      current
    DESCRIPTION
        "Represents the status of version auto-update for an AP.
        The following values are supported:
        enable   - AP version will be updated automatically.
        disable  - AP version will not be updated automatically.
        inherit  - The status will inherit value from apgroup-view or system-view."
    DEFVAL      { inherit }
    ::= { hh3cDot11APTemplateEntry 20 }

hh3cDot11StatisIntervModeCM OBJECT-TYPE
    SYNTAX      INTEGER
    {
        off(0),
        on(1)
    }
    MAX-ACCESS  read-create
    STATUS      current
    DESCRIPTION
        "This object represents the mode of statistic interval.
        off    - statistic interval value between 10s to 240s
        on     - statistic interval value between 0s to 5s"
    DEFVAL      { off }
    ::= { hh3cDot11APTemplateEntry 21 }

hh3cDot11ApNasIDCM OBJECT-TYPE
    SYNTAX      OCTET STRING
    MAX-ACCESS  read-create
    STATUS      current
    DESCRIPTION
        "Represents the NAS-ID of current service policy for each
        specific radio of AP."
    ::= { hh3cDot11APTemplateEntry 22 }

hh3cDot11ApCoveragetype OBJECT-TYPE
    SYNTAX      INTEGER
    {
        school(1),
        traffic(2),
        shopping(3),
        company(4)
    }
    MAX-ACCESS  read-create
    STATUS      current
    DESCRIPTION
        "This object represents the coverage type of AP.
        school - the coverage type is school
        traffic - the coverage type is traffic
        shop - the coverage type is shop
        company - the coverage type is company"
    DEFVAL      { school }
    ::= { hh3cDot11APTemplateEntry 23 }

hh3cDot11APControlAddressState OBJECT-TYPE
    SYNTAX      INTEGER
        {
            enable(1),
            disable(2)
        }
    MAX-ACCESS  read-create
    STATUS      current
    DESCRIPTION
        "Represents the status of control address for an AP.
        The following values are supported:
        enable      - AC rediscovery will be enabled.
        disable     - AC rediscovery will be disabled."
        DEFVAL      { disable }
    ::= { hh3cDot11APTemplateEntry 24 }

hh3cDot11APControlAddressIPv4 OBJECT-TYPE
    SYNTAX      IpAddress
    MAX-ACCESS  read-create
    STATUS      current
    DESCRIPTION
        "Represents an AC IPv4 address for AC rediscovery."
    ::= { hh3cDot11APTemplateEntry 25 }

hh3cDot11APControlAddressIPv6 OBJECT-TYPE
    SYNTAX      OCTET STRING
    MAX-ACCESS  read-create
    STATUS      current
    DESCRIPTION
        "Represents an AC IPv6 address for AC rediscovery."
    ::= { hh3cDot11APTemplateEntry 26 }

hh3cDot11APLocalACName OBJECT-TYPE
    SYNTAX      OCTET STRING
    MAX-ACCESS  read-only
    STATUS      current
    DESCRIPTION
        "Represents the local AC name the AP belongs to."
    ::= { hh3cDot11APTemplateEntry 27 }

hh3cDot11APEchoInterval OBJECT-TYPE
    SYNTAX      Integer32
    MAX-ACCESS  read-write
    STATUS      current
    DESCRIPTION
        "This object represents the echo-interval of the AP."
    ::= { hh3cDot11APTemplateEntry 28 }

hh3cDot11APProvisionAPIPv4 OBJECT-TYPE
    SYNTAX      IpAddress
    MAX-ACCESS  read-write
    STATUS      current
    DESCRIPTION
        "Represents the IPv4 address of an AP."
    ::= { hh3cDot11APTemplateEntry 29 }

hh3cDot11APProvisionIPv4Mask OBJECT-TYPE
    SYNTAX      Integer32(1..31)
    MAX-ACCESS  read-write
    STATUS      current
    DESCRIPTION
        "Represents the IPv4 address mask of an AP."
    ::= { hh3cDot11APTemplateEntry 30 }

hh3cDot11APProvisionAPIPv6 OBJECT-TYPE
    SYNTAX      OCTET STRING
    MAX-ACCESS  read-write
    STATUS      current
    DESCRIPTION
        "Represents the IPv6 address of an AP."
    ::= { hh3cDot11APTemplateEntry 31 }

hh3cDot11APProvisionIPv6PrefixLen OBJECT-TYPE
    SYNTAX      Integer32(1..128)
    MAX-ACCESS  read-write
    STATUS      current
    DESCRIPTION
        "Represents the IPv6 address prefix length of an AP."
    ::= { hh3cDot11APTemplateEntry 32 }

hh3cDot11APProvisionACIPv4 OBJECT-TYPE
    SYNTAX      IpAddress
    MAX-ACCESS  read-write
    STATUS      current
    DESCRIPTION
        "Represents an AC IPv4 address for discovery."
    ::= { hh3cDot11APTemplateEntry 33 }

hh3cDot11APProvisionACIpv6 OBJECT-TYPE
    SYNTAX      OCTET STRING
    MAX-ACCESS  read-create
    STATUS      current
    DESCRIPTION
        "Represents an AC IPv6 address for discovery."
    ::= { hh3cDot11APTemplateEntry 34 }

hh3cDot11APProvisionGateWayIPV4 OBJECT-TYPE
    SYNTAX      IpAddress
    MAX-ACCESS  read-write
    STATUS      current
    DESCRIPTION
        "Represents the gateway IPv4 address for an AP."
    ::= { hh3cDot11APTemplateEntry 35 }

hh3cDot11APProvisionGateWayIPV6 OBJECT-TYPE
    SYNTAX      OCTET STRING
    MAX-ACCESS  read-create
    STATUS      current
    DESCRIPTION
        "Represents thre gateway IPv6 address for an AP."
    ::= { hh3cDot11APTemplateEntry 36 }

hh3cDot11APMapConfigFileName OBJECT-TYPE
    SYNTAX      OCTET STRING
    MAX-ACCESS  read-create
    STATUS      current
    DESCRIPTION
        "Represents the name of the AP MapConfigFile."
    ::= { hh3cDot11APTemplateEntry 37 }
-- *****************************************************************************
-- *  End of  hh3cDot11APTemplateTable Definition
-- *****************************************************************************

-- *****************************************************************************
-- *  hh3cDot11RadioToConfigTable Definition
-- *****************************************************************************
hh3cDot11RadioToConfigTable OBJECT-TYPE
    SYNTAX      SEQUENCE OF Hh3cDot11RadioToConfigEntry
    MAX-ACCESS  not-accessible
    STATUS      current
    DESCRIPTION
        "Before AP connects to AC, administrator will configure radio
        parameter to each radio."
    ::= { hh3cDot11APConfigGroup 2 }

hh3cDot11RadioToConfigEntry OBJECT-TYPE
    SYNTAX      Hh3cDot11RadioToConfigEntry
    MAX-ACCESS  not-accessible
    STATUS      current
    DESCRIPTION
        "Each entry contains configuration information for each radio."
    INDEX
        {
            hh3cDot11APTemplateNameCfg,
            hh3cDot11CfgRadioID
        }
    ::= { hh3cDot11RadioToConfigTable 1 }

Hh3cDot11RadioToConfigEntry ::= SEQUENCE
    {
        hh3cDot11APTemplateNameCfg     OCTET STRING,
        hh3cDot11CfgRadioID            Hh3cDot11RadioScopeType,
        hh3cDot11CfgRadioPolicyName    OCTET STRING,
        hh3cDot11CfgRadioType          Hh3cDot11RadioType,
        hh3cDot11CfgChannel            Hh3cDot11ChannelScopeType,
        hh3cDot11CfgMaxTxPowerLevel    Hh3cDot11TxPwrLevelScopeType,
        hh3cDot11PreambleLen           Hh3cDot11PreambleType,
        hh3cDot11CfgRadioStatus        TruthValue,
        hh3cDot11CfgRdElementID        Unsigned32,
        hh3cDot11CfgWorkMode           Hh3cDot11WorkMode,
        hh3cDot11CfgPwrAttValue        Integer32,
        hh3cDot11RadioTxArithmetic     INTEGER,
        hh3cDot11CfgChannelLockStat    INTEGER,
        hh3cDot11CfgPowerLockStat      INTEGER,
        hh3cDot11CfgLBRdGroupId        Unsigned32,
        hh3cDot11CfgRRMSDRdGroupId     Unsigned32,
        hh3cDot11CfgRadioType2         Hh3cDot11RadioType2,
        hh3cDot11CfgIDSEnable          TruthValue,
        hh3cDot11CfgSaEnable           TruthValue,
        hh3cDot11CfgSaCltRtFFTData     TruthValue,
        hh3cDot11CfgSaBand             INTEGER,
        hh3cDot11CfgSaRptDevType       BITS,
        hh3cDot11CfgSaTrapDevEnable    TruthValue,
        hh3cDot11CfgSaTrapDevType      BITS,
        hh3cDot11CfgSaTrapAQEnable     TruthValue,
        hh3cDot11CfgSaTrapAQThreshold  Integer32,
        hh3cDot11CfgSaDrivenRRMEnable  TruthValue,
        hh3cDot11CfgSaDrivenRRMSnt     INTEGER,
        hh3cDot11CfgSPInCirMode        Hh3cDot11CirMode,
        hh3cDot11CfgSPInCirValue       Integer32,
        hh3cDot11CfgSPOutCirMode       Hh3cDot11CirMode,
        hh3cDot11CfgSPOutCirValue      Integer32
    }

hh3cDot11APTemplateNameCfg OBJECT-TYPE
    SYNTAX      OCTET STRING(SIZE(0..127))
    MAX-ACCESS  not-accessible
    STATUS      current
    DESCRIPTION
        "Represents the name of AP template."
    ::= { hh3cDot11RadioToConfigEntry 1 }

hh3cDot11CfgRadioID OBJECT-TYPE
    SYNTAX      Hh3cDot11RadioScopeType
    MAX-ACCESS  not-accessible
    STATUS      current
    DESCRIPTION
        "Represents each radio."
    ::= { hh3cDot11RadioToConfigEntry 2 }

hh3cDot11CfgRadioPolicyName OBJECT-TYPE
    SYNTAX      OCTET STRING
    MAX-ACCESS  read-write
    STATUS      current
    DESCRIPTION
        "Represents the name of radio policy."
    ::= { hh3cDot11RadioToConfigEntry 3 }

hh3cDot11CfgRadioType OBJECT-TYPE
    SYNTAX      Hh3cDot11RadioType
    MAX-ACCESS  read-write
    STATUS      current
    DESCRIPTION
        "Represents the radio will work with which 802.11 radio type."
    ::= { hh3cDot11RadioToConfigEntry 4 }

hh3cDot11CfgChannel OBJECT-TYPE
    SYNTAX      Hh3cDot11ChannelScopeType
    MAX-ACCESS  read-write
    STATUS      current
    DESCRIPTION
        "Represents the channel allocation of radio."
    ::= { hh3cDot11RadioToConfigEntry 5 }

hh3cDot11CfgMaxTxPowerLevel OBJECT-TYPE
    SYNTAX      Hh3cDot11TxPwrLevelScopeType
    UNITS       "dbm"
    MAX-ACCESS  read-write
    STATUS      current
    DESCRIPTION
        "Represents the maximal transmit power scope for AP."
    ::= { hh3cDot11RadioToConfigEntry 6 }

hh3cDot11PreambleLen OBJECT-TYPE
    SYNTAX      Hh3cDot11PreambleType
    MAX-ACCESS  read-write
    STATUS      current
    DESCRIPTION
        "Represents whether use long or short preamble for 802.11 MAC
        frame.
        When hh3cDot11CfgRadioType is either dot11b, dot11g or dot11gn,
        then value for hh3cDot11PreambleLen will be valid.
        Otherwise, the value for it will be invalid."
    DEFVAL      { short }
    ::= { hh3cDot11RadioToConfigEntry 7 }

hh3cDot11CfgRadioStatus OBJECT-TYPE
    SYNTAX      TruthValue
    MAX-ACCESS  read-write
    STATUS      current
    DESCRIPTION
        "Represents the radio admin status whether is enabled
        or disabled."
    ::= { hh3cDot11RadioToConfigEntry 8 }

hh3cDot11CfgRdElementID OBJECT-TYPE
    SYNTAX      Unsigned32
    MAX-ACCESS  read-only
    STATUS      current
    DESCRIPTION
        "Represents the element ID of this radio.  It comprises two parts.
        The highest 24 bits are AP element ID and the lowest 8 bits are
        radio ID."
    ::= { hh3cDot11RadioToConfigEntry 9 }

hh3cDot11CfgWorkMode OBJECT-TYPE
    SYNTAX      Hh3cDot11WorkMode
    MAX-ACCESS  read-write
    STATUS      current
    DESCRIPTION
        "Represents work mode of the radio."
    ::= { hh3cDot11RadioToConfigEntry 10 }

hh3cDot11CfgPwrAttValue OBJECT-TYPE
    SYNTAX      Integer32
    MAX-ACCESS  read-write
    STATUS      current
    DESCRIPTION
        "Represents the value of power attenuation."
    ::= { hh3cDot11RadioToConfigEntry 11 }

hh3cDot11RadioTxArithmetic OBJECT-TYPE
    SYNTAX      INTEGER
        {
            quality(1),
            bandwidth(2)
        }
    MAX-ACCESS  read-write
    STATUS      current
    DESCRIPTION
        "Represents the transmission arithmetic of the radio.
        The following values are supported:
        quality   - Consider the quality first during the transmission.
        bandwidth - Consider the bandwidth first during the transmission."
    DEFVAL      { quality }
    ::= { hh3cDot11RadioToConfigEntry 12 }

hh3cDot11CfgChannelLockStat OBJECT-TYPE
    SYNTAX      INTEGER
        {
            unlocked(1),
            locked(2)
        }
    MAX-ACCESS  read-write
    STATUS      current
    DESCRIPTION
        "Represents locked status of channel on the radio."
    DEFVAL      { unlocked }
    ::= { hh3cDot11RadioToConfigEntry 13 }

hh3cDot11CfgPowerLockStat OBJECT-TYPE
    SYNTAX      INTEGER
        {
            unlocked(1),
            locked(2)
        }
    MAX-ACCESS  read-write
    STATUS      current
    DESCRIPTION
        "Represents locked status of power on the radio."
    DEFVAL      { unlocked }
    ::= { hh3cDot11RadioToConfigEntry 14 }

hh3cDot11CfgLBRdGroupId OBJECT-TYPE
    SYNTAX      Unsigned32
    MAX-ACCESS  read-write
    STATUS      current
    DESCRIPTION
        "Represents the load balance group ID allocated for the radio."
    ::= { hh3cDot11RadioToConfigEntry 15 }

hh3cDot11CfgRRMSDRdGroupId OBJECT-TYPE
    SYNTAX      Unsigned32
    MAX-ACCESS  read-write
    STATUS      current
    DESCRIPTION
        "Represents the RRM self-decisive group ID allocated for the radio."
    ::= { hh3cDot11RadioToConfigEntry 16 }

hh3cDot11CfgRadioType2 OBJECT-TYPE
    SYNTAX      Hh3cDot11RadioType2
    MAX-ACCESS  read-write
    STATUS      current
    DESCRIPTION
        "Represents the radio will work with which 802.11 radio type."
    ::= { hh3cDot11RadioToConfigEntry 17 }

hh3cDot11CfgIDSEnable OBJECT-TYPE
    SYNTAX      TruthValue
    MAX-ACCESS  read-write
    STATUS      current
    DESCRIPTION
        "Represents whether intrusion detection is enabled for this radio."
    ::= { hh3cDot11RadioToConfigEntry 18 }

hh3cDot11CfgSaEnable OBJECT-TYPE
    SYNTAX      TruthValue
    MAX-ACCESS  read-write
    STATUS      current
    DESCRIPTION
        "Represents whether spectrum analysis is enabled."
    ::= { hh3cDot11RadioToConfigEntry 19 }

hh3cDot11CfgSaCltRtFFTData OBJECT-TYPE
    SYNTAX      TruthValue
    MAX-ACCESS  read-write
    STATUS      current
    DESCRIPTION
        "Represents whether to collect real-time FFT data for this radio."
    ::= { hh3cDot11RadioToConfigEntry 20 }

hh3cDot11CfgSaBand OBJECT-TYPE
    SYNTAX      INTEGER{
       dot11g(1),
       dot11aLower(2),
       dot11aMiddle(3),
       dot11aUpper(4)
    }
    MAX-ACCESS  read-write
    STATUS      current
    DESCRIPTION
        "Represents which band of channels will be monitored when collection
        real-time FFT data is enabled for this radio.  Detection of
        interference devices and air quality will also be affected.  Each band
        responds to the following channels.
         dot11g (Channels 1-14)
         dot11aLower (channels 36-64)
         dot11aMiddle (channels 100-140)
         dot11aUpper (channels 149-165)."
    ::= { hh3cDot11RadioToConfigEntry 21 }

hh3cDot11CfgSaRptDevType OBJECT-TYPE
    SYNTAX BITS
        {
            microwave(0),
            microwaveInverter(1),
            bluetooth(2),
            fixedFreqOthers(3),
            fixedFreqCordlessPhone(4),
            fixedFreqVideo(5),
            fixedFreqAudio(6),
            freqHopperOthers(7),
            freqHopperCordlessBase(8),
            freqHopperCordlessNetwork(9),
            freqHopperXbox(10),
            genericInterferer(11)
        }
    MAX-ACCESS read-write
    STATUS current
    DESCRIPTION
        "Represents which types of interference devices should be reported."
    ::= { hh3cDot11RadioToConfigEntry 22 }

hh3cDot11CfgSaTrapDevEnable OBJECT-TYPE
    SYNTAX TruthValue
    MAX-ACCESS read-write
    STATUS current
    DESCRIPTION
        "Represents whether trap is enabled for an interference device type."
    ::= { hh3cDot11RadioToConfigEntry 23 }

hh3cDot11CfgSaTrapDevType OBJECT-TYPE
    SYNTAX BITS
        {
            microwave(0),
            microwaveInverter(1),
            bluetooth(2),
            fixedFreqOthers(3),
            fixedFreqCordlessPhone(4),
            fixedFreqVideo(5),
            fixedFreqAudio(6),
            freqHopperOthers(7),
            freqHopperCordlessBase(8),
            freqHopperCordlessNetwork(9),
            freqHopperXbox(10),
            genericInterferer(11)
        }
    MAX-ACCESS read-write
    STATUS current
    DESCRIPTION
        "Represents for which interference device types the AP will send traps
         when trap sending is enabled."
    ::= { hh3cDot11RadioToConfigEntry 24 }

hh3cDot11CfgSaTrapAQEnable OBJECT-TYPE
    SYNTAX TruthValue
    MAX-ACCESS read-write
    STATUS current
    DESCRIPTION
        "Represents whether the channel quality trap is enabled."
    ::= { hh3cDot11RadioToConfigEntry 25 }

hh3cDot11CfgSaTrapAQThreshold OBJECT-TYPE
    SYNTAX Integer32(1..100)
    MAX-ACCESS read-write
    STATUS current
    DESCRIPTION
        "Represents the channel quality threshold.  When the channel quality
        is below this value, the channel quality trap will be sent."
    ::= { hh3cDot11RadioToConfigEntry 26 }

hh3cDot11CfgSaDrivenRRMEnable OBJECT-TYPE
    SYNTAX TruthValue
    MAX-ACCESS read-write
    STATUS current
    DESCRIPTION
        "Configures whether to run RRM when the AP detects
         a certain level of interference."
    ::= { hh3cDot11RadioToConfigEntry 27 }

hh3cDot11CfgSaDrivenRRMSnt OBJECT-TYPE
    SYNTAX INTEGER
    {
        low(1),
        medium(2),
        high(3)
    }
    MAX-ACCESS read-write
    STATUS current
    DESCRIPTION
        "Configures the threshold for triggering RRM.  When the
         interference level for the AP exceeds the threshold
         , RRM initiates local dynamic frequency selection (DFS)
         and changes the channel of the affected radio
         to improve network performance.  Low represents a decreased
         sensitivity to changes in the environment while high represents an
         increased sensitivity."
    ::= { hh3cDot11RadioToConfigEntry 28 }

hh3cDot11CfgSPInCirMode OBJECT-TYPE
   SYNTAX      Hh3cDot11CirMode
    MAX-ACCESS  read-create
    STATUS      current
    DESCRIPTION
        "
        Specifies the committed information rate(CIR) mode for the inbound direction.
        This object is useful only when the corresponding CIR has a nonzero value.
        If the value of this object is changed, the corresponding CIR will be reset."
    DEFVAL      { static }
    ::= { hh3cDot11RadioToConfigEntry 29 }

hh3cDot11CfgSPInCirValue OBJECT-TYPE
    SYNTAX      Integer32
    UNITS       "Kbps"
    MAX-ACCESS  read-create
    STATUS      current
    DESCRIPTION
        "Represents the CIR for the inbound direction of this service policy.
        If the value is 0, it means that no flow control is applied to
        the service policy, and the corresponding CIR mode is meaningless."
    DEFVAL      { 0 }
    ::= { hh3cDot11RadioToConfigEntry 30 }

hh3cDot11CfgSPOutCirMode OBJECT-TYPE
    SYNTAX      Hh3cDot11CirMode
    MAX-ACCESS  read-create
    STATUS      current
    DESCRIPTION
        "
        Represents the committed information rate(CIR) mode for the outbound direction.
        This object is useful only when the corresponding CIR has a nonzero value.
        If the value of this object is changed, the corresponding CIR will be reset."
    DEFVAL      { static }
    ::= { hh3cDot11RadioToConfigEntry 31 }

hh3cDot11CfgSPOutCirValue OBJECT-TYPE
    SYNTAX      Integer32
    UNITS       "Kbps"
    MAX-ACCESS  read-create
    STATUS      current
    DESCRIPTION
        "Represents the CIR for the outbound direction of this service policy.
        If the value is 0, it means that no flow control is applied to
        the service policy, and the corresponding CIR mode is meaningless."
    DEFVAL      { 0 }
    ::= { hh3cDot11RadioToConfigEntry 32 }

-- *****************************************************************************
-- *  End of  hh3cDot11RadioToConfigTable Definition
-- *****************************************************************************

-- *****************************************************************************
-- *  hh3cDot11APServiceSetTable Definition
-- *****************************************************************************
hh3cDot11APServiceSetTable OBJECT-TYPE
    SYNTAX      SEQUENCE OF Hh3cDot11APServiceSetEntry
    MAX-ACCESS  not-accessible
    STATUS      current
    DESCRIPTION
        "For each radio, it could configure multiple service policies.
        The table describes the relationship between radio and
        service policies."
    ::= { hh3cDot11APConfigGroup 3 }

hh3cDot11APServiceSetEntry OBJECT-TYPE
    SYNTAX      Hh3cDot11APServiceSetEntry
    MAX-ACCESS  not-accessible
    STATUS      current
    DESCRIPTION
        "Each entry contains service policy information for each
        specific radio of AP."
    INDEX
        {
            hh3cDot11APTemplateNameCfg,
            hh3cDot11CfgRadioID,
            hh3cDot11CfgServicePolicyID
        }
    ::= { hh3cDot11APServiceSetTable 1 }

Hh3cDot11APServiceSetEntry ::= SEQUENCE
    {
        hh3cDot11CfgServicePolicyID    Hh3cDot11ServicePolicyIDType,
        hh3cDot11SrvSetRowStatus       RowStatus,
        hh3cDot11ServiceSetVlanId      Integer32,
        hh3cDot11ServiceSetVlanGroup   OCTET STRING
    }

hh3cDot11CfgServicePolicyID OBJECT-TYPE
    SYNTAX      Hh3cDot11ServicePolicyIDType
    MAX-ACCESS  not-accessible
    STATUS      current
    DESCRIPTION
        "Represents the ID of each service policy used by the AP."
    ::= { hh3cDot11APServiceSetEntry 1 }

hh3cDot11SrvSetRowStatus OBJECT-TYPE
    SYNTAX      RowStatus
    MAX-ACCESS  read-create
    STATUS      current
    DESCRIPTION
        "The status of this table entry."
    ::= { hh3cDot11APServiceSetEntry 2 }

hh3cDot11ServiceSetVlanId OBJECT-TYPE
    SYNTAX      Integer32(0..4094)
    MAX-ACCESS  read-create
    STATUS      current
    DESCRIPTION
        "Represents the Vlan ID of BSS which is generated when service policy
        is binded with the Radio."
    ::= { hh3cDot11APServiceSetEntry 3 }

hh3cDot11ServiceSetVlanGroup OBJECT-TYPE
    SYNTAX      OCTET STRING(SIZE(0..31))
    MAX-ACCESS  read-create
    STATUS      current
    DESCRIPTION
        "Represents the VLAN group of the BSS generated when a service policy
        is bound to the radio."
    ::= { hh3cDot11APServiceSetEntry 4 }
-- *****************************************************************************
-- * End of hh3cDot11APServiceSetTable Definition
-- *****************************************************************************

-- *****************************************************************************
-- *  hh3cDot11APSTVlanTable Definition
-- *****************************************************************************
hh3cDot11APSTVlanTable OBJECT-TYPE
    SYNTAX      SEQUENCE OF Hh3cDot11APSTVlanEntry
    MAX-ACCESS  not-accessible
    STATUS      current
    DESCRIPTION
        "For each service policy, it could be bind to several VLANs.
        The table describes the relationship between VLAN and
        service policies."
    ::= { hh3cDot11APConfigGroup 11 }

hh3cDot11APSTVlanEntry OBJECT-TYPE
    SYNTAX      Hh3cDot11APSTVlanEntry
    MAX-ACCESS  not-accessible
    STATUS      current
    DESCRIPTION
        "Each entry contains VLAN and service policy information for each
        specific radio of AP."
    INDEX
        {
            hh3cDot11SIDAPSerialID,
            hh3cDot11CfgRadioID,
            hh3cDot11CfgServicePolicyID
        }
    ::= { hh3cDot11APSTVlanTable 1 }

Hh3cDot11APSTVlanEntry ::= SEQUENCE
    {
        hh3cDot11CfgSTVLANID           Integer32,
        hh3cDot11CfgSTNASPortID        OCTET STRING,
        hh3cDot11CfgServiceSetRowStatus    RowStatus,
        hh3cDot11CfgSTNASID            OCTET STRING
    }

hh3cDot11CfgSTVLANID OBJECT-TYPE
    SYNTAX      Integer32(0..4094)
    MAX-ACCESS  read-create
    STATUS      current
    DESCRIPTION
        "Represents the VLAN that current Service Policy have bind to."
    ::= { hh3cDot11APSTVlanEntry 1 }

hh3cDot11CfgSTNASPortID OBJECT-TYPE
    SYNTAX      OCTET STRING(SIZE(0..127))
    MAX-ACCESS  read-only
    STATUS      current
    DESCRIPTION
        "Represents the NAS Port ID of current Service Policy for each
        specific radio of AP."
    ::= { hh3cDot11APSTVlanEntry 2 }

hh3cDot11CfgServiceSetRowStatus OBJECT-TYPE
    SYNTAX      RowStatus
    MAX-ACCESS  read-create
    STATUS      current
    DESCRIPTION
        "The status of this table entry."
    ::= { hh3cDot11APSTVlanEntry 3 }

hh3cDot11CfgSTNASID OBJECT-TYPE
    SYNTAX      OCTET STRING(SIZE(0..127))
    MAX-ACCESS  read-only
    STATUS      current
    DESCRIPTION
        "Represents the NAS ID of current Service Policy for each
        specific radio of AP."
    ::= { hh3cDot11APSTVlanEntry 4 }
-- *****************************************************************************
-- * End of hh3cDot11APSTVlanTable Definition
-- *****************************************************************************

-- *****************************************************************************
-- *  hh3cDot11APSysInfoSetTable Definition
-- *****************************************************************************
hh3cDot11APSysInfoSetTable OBJECT-TYPE
    SYNTAX      SEQUENCE OF Hh3cDot11APSysInfoSetEntry
    MAX-ACCESS  not-accessible
    STATUS      current
    DESCRIPTION
        "The table of the system information for each AP."
    ::= { hh3cDot11APConfigGroup 4 }

hh3cDot11APSysInfoSetEntry OBJECT-TYPE
    SYNTAX      Hh3cDot11APSysInfoSetEntry
    MAX-ACCESS  not-accessible
    STATUS      current
    DESCRIPTION
        "The system information configuration for each AP."
    INDEX
        {
            hh3cDot11SIDAPSerialID
        }
    ::= { hh3cDot11APSysInfoSetTable 1 }

Hh3cDot11APSysInfoSetEntry ::= SEQUENCE
    {
        hh3cDot11APSysNetID            OCTET STRING,
        hh3cDot11APCpuUsageThreshold   Integer32,
        hh3cDot11APMemUsageThreshold   Integer32
    }

hh3cDot11APSysNetID OBJECT-TYPE
    SYNTAX      OCTET STRING(SIZE(0..127))
    MAX-ACCESS  read-write
    STATUS      current
    DESCRIPTION
        "Represents the system Net ID for AP."
    ::= { hh3cDot11APSysInfoSetEntry 1 }

hh3cDot11APCpuUsageThreshold OBJECT-TYPE
    SYNTAX      Integer32(0..100)
    UNITS       "onepercent"
    MAX-ACCESS  read-write
    STATUS      current
    DESCRIPTION
        "The CPU usage threshold for AP."
    ::= { hh3cDot11APSysInfoSetEntry 2 }

hh3cDot11APMemUsageThreshold OBJECT-TYPE
    SYNTAX      Integer32(0..100)
    UNITS       "onepercent"
    MAX-ACCESS  read-write
    STATUS      current
    DESCRIPTION
        "The memory usage threshold for AP."
    ::= { hh3cDot11APSysInfoSetEntry 3 }

-- *****************************************************************************
-- * End of hh3cDot11APSysInfoSetTable Definition
-- *****************************************************************************

-- *****************************************************************************
-- *  hh3cDot11APLimitTable Definition
-- *****************************************************************************
hh3cDot11APLimitTable OBJECT-TYPE
    SYNTAX      SEQUENCE OF Hh3cDot11APLimitEntry
    MAX-ACCESS  not-accessible
    STATUS      current
    DESCRIPTION
        "For each connected APs, administrator could configure a series of
        limits.  This table describes the limit information for AP(s)."
    ::= { hh3cDot11APConfigGroup 5 }

hh3cDot11APLimitEntry OBJECT-TYPE
    SYNTAX      Hh3cDot11APLimitEntry
    MAX-ACCESS  not-accessible
    STATUS      current
    DESCRIPTION
        "Each entry contains the limit information for each AP."
    INDEX
        {
            hh3cDot11APElementIndex
        }
    ::= { hh3cDot11APLimitTable 1 }

Hh3cDot11APLimitEntry ::= SEQUENCE
    {
        hh3cDot11APSsidNumLimit     Integer32,
        hh3cDot11APUserCntLimit     Integer32,
        hh3cDot11APUserThreshold    Integer32
    }

hh3cDot11APSsidNumLimit OBJECT-TYPE
    SYNTAX      Integer32(0..65535)
    MAX-ACCESS  read-write
    STATUS      current
    DESCRIPTION
        "Represents the upper limit of service template binded
        with this AP.  All radios of AP share this limit.
        Default value 0 : There is no upper limit of service template
        binded with this AP."
    DEFVAL      { 0 }
    ::= { hh3cDot11APLimitEntry 1 }

hh3cDot11APUserCntLimit OBJECT-TYPE
    SYNTAX      Integer32(0..65535)
    MAX-ACCESS  read-write
    STATUS      current
    DESCRIPTION
        "Represents the upper limit of user which has access to this AP.
        All BSSs binded with AP share this limit.
        Default value 0 : There is no upper limit of user which has access
        to this AP."
    DEFVAL      { 0 }
    ::= { hh3cDot11APLimitEntry 2 }

hh3cDot11APUserThreshold OBJECT-TYPE
    SYNTAX      Integer32(0..65535)
    MAX-ACCESS  read-write
    STATUS      current
    DESCRIPTION
        "Represents the threshold of user which has access to this
        AP.  All BSSs binded with AP share this limit.  If the user counter
        is overflow, the trap will be sent.
        Default value 0 : There is no threshold of user which has access
        to this AP."
    DEFVAL      { 0 }
    ::= { hh3cDot11APLimitEntry 3 }
-- *****************************************************************************
-- * End of hh3cDot11APLimitTable Definition
-- *****************************************************************************

-- *****************************************************************************
-- * hh3cDot11APIfSetTable Definition
-- *****************************************************************************
hh3cDot11APIfSetTable OBJECT-TYPE
    SYNTAX      SEQUENCE OF Hh3cDot11APIfSetEntry
    MAX-ACCESS  not-accessible
    STATUS      current
    DESCRIPTION
        "The table of the interface information for each AP."
    ::= { hh3cDot11APConfigGroup 6 }

hh3cDot11APIfSetEntry OBJECT-TYPE
    SYNTAX      Hh3cDot11APIfSetEntry
    MAX-ACCESS  not-accessible
    STATUS      current
    DESCRIPTION
        "The interface information configuration for each AP."
    INDEX
        {
            hh3cDot11APElementIndex,
            hh3cDot11APSetIfIndex
        }
    ::= { hh3cDot11APIfSetTable 1 }

Hh3cDot11APIfSetEntry ::= SEQUENCE
    {
        hh3cDot11APSetIfIndex      Integer32,
        hh3cDot11APIfAlias         DisplayString
    }

hh3cDot11APSetIfIndex OBJECT-TYPE
    SYNTAX      Integer32
    MAX-ACCESS  not-accessible
    STATUS      current
    DESCRIPTION
        "Represents the index for a interface."
    ::= { hh3cDot11APIfSetEntry 1 }

hh3cDot11APIfAlias OBJECT-TYPE
    SYNTAX      DisplayString
    MAX-ACCESS  read-write
    STATUS      current
    DESCRIPTION
        "This object is an 'alias' name for the interface as specified
        by a network manager for AP."
    ::= { hh3cDot11APIfSetEntry 2 }

-- *****************************************************************************
-- * End of hh3cDot11APIfSetTable Definition
-- *****************************************************************************

-- *****************************************************************************
-- *  hh3cDot11APServiceVlanTable Definition
-- *****************************************************************************
hh3cDot11APServiceVlanTable OBJECT-TYPE
    SYNTAX      SEQUENCE OF Hh3cDot11APServiceVlanEntry
    MAX-ACCESS  not-accessible
    STATUS      current
    DESCRIPTION
        "For all the radios on the AP, it could configure multiple service policies.
        The table describes the relationship between AP and
        service policies."
    ::= { hh3cDot11APConfigGroup 7 }

hh3cDot11APServiceVlanEntry OBJECT-TYPE
    SYNTAX      Hh3cDot11APServiceVlanEntry
    MAX-ACCESS  not-accessible
    STATUS      current
    DESCRIPTION
        "Each entry contains service policy information for each AP."
    INDEX
        {
            hh3cDot11APServiceVlanSerialID,
            hh3cDot11APServiceVlanSPID
        }
    ::= { hh3cDot11APServiceVlanTable 1 }

Hh3cDot11APServiceVlanEntry ::= SEQUENCE
    {
        hh3cDot11APServiceVlanSerialID          OCTET STRING,
        hh3cDot11APServiceVlanSPID              Hh3cDot11ServicePolicyIDType,
        hh3cDot11APServiceVlanId                Integer32,
        hh3cDot11APServiceVlanRowStatus         RowStatus

    }

hh3cDot11APServiceVlanSerialID OBJECT-TYPE
    SYNTAX      OCTET STRING
    MAX-ACCESS  not-accessible
    STATUS      current
    DESCRIPTION
        "This object represents AP serial id."
    ::= { hh3cDot11APServiceVlanEntry 1 }

hh3cDot11APServiceVlanSPID OBJECT-TYPE
    SYNTAX      Hh3cDot11ServicePolicyIDType
    MAX-ACCESS  not-accessible
    STATUS      current
    DESCRIPTION
        "This object represents the ID of each service policy used by the AP."
    ::= { hh3cDot11APServiceVlanEntry 2 }

hh3cDot11APServiceVlanId OBJECT-TYPE
    SYNTAX      Integer32(0..4094)
    MAX-ACCESS  read-create
    STATUS      current
    DESCRIPTION
        "This object represents the VLAN ID of BSS which is generated when the
         service policy is bound to the radio."
    ::= { hh3cDot11APServiceVlanEntry 3 }

hh3cDot11APServiceVlanRowStatus OBJECT-TYPE
    SYNTAX      RowStatus
    MAX-ACCESS  read-create
    STATUS      current
    DESCRIPTION
        "This object represents the status of this table entry."
    ::= { hh3cDot11APServiceVlanEntry 4 }

-- *****************************************************************************
-- * End of hh3cDot11APServiceSetTable Definition
-- *****************************************************************************

-- *****************************************************************************
-- *  hh3cDot11RadioConfigTable Definition
-- *****************************************************************************
hh3cDot11RadioConfigTable OBJECT-TYPE
    SYNTAX      SEQUENCE OF Hh3cDot11RadioConfigEntry
    MAX-ACCESS  not-accessible
    STATUS      current
    DESCRIPTION
        "Before AP connects to AC, administrator will configure radio
        parameter to each radio."
    ::= { hh3cDot11APConfigGroup 8 }

hh3cDot11RadioConfigEntry OBJECT-TYPE
    SYNTAX      Hh3cDot11RadioConfigEntry
    MAX-ACCESS  not-accessible
    STATUS      current
    DESCRIPTION
        "Each entry contains configuration information for each radio."
    INDEX
        {
            hh3cDot11RCAPSerialID,
            hh3cDot11RCRadioID
        }
    ::= { hh3cDot11RadioConfigTable 1 }

Hh3cDot11RadioConfigEntry ::= SEQUENCE
    {
        hh3cDot11RCAPSerialID               OCTET STRING,
        hh3cDot11RCRadioID                  Hh3cDot11RadioScopeType,
        hh3cDot11RCRadioType                Hh3cDot11RadioType,
        hh3cDot11RCChannel                  Hh3cDot11ChannelScopeType,
        hh3cDot11RCPreambleLen              Hh3cDot11PreambleType,
        hh3cDot11RCPwrAttValue              Integer32,
        hh3cDot11RCApPowerLevel             Hh3cDot11TxPwrLevelScopeType,
        hh3cDot11RCDynamicChlState          TruthValue,
        hh3cDot11RCDynamicPowerState        TruthValue,
        hh3cDot11RCRadioStatus              TruthValue,
        hh3cDot11RCRadioRate                OCTET STRING,
        hh3cDot11RCPwrAdjustStepLength      Integer32,
        hh3cDot11RCRadioType2               Hh3cDot11RadioType2,
        hh3cDot11RCPreambleLenCM            INTEGER,
        hh3cDot11RCDynamicChlStateCM        INTEGER,
        hh3cDot11RCRadioStatusCM            INTEGER,
        hh3cDot11RCRadioRateCM              OCTET STRING,
        hh3cDot11RCDynamicPowerStateCM      Hh3cDot11TruthValueCM,
        hh3cDot11RCRssiThresholdCM          Integer32,
        hh3cDot11RCDynamicChlStateSelfDecisiveCM    Hh3cDot11TruthValueCM,
        hh3cDot11RCDynamicPowerStateSelfDecisiveCM  Hh3cDot11TruthValueCM
    }

hh3cDot11RCAPSerialID OBJECT-TYPE
    SYNTAX      OCTET STRING(SIZE(0..127))
    MAX-ACCESS  not-accessible
    STATUS      current
    DESCRIPTION
        "This object represents the Serial ID of AP."
    ::= { hh3cDot11RadioConfigEntry 1 }

hh3cDot11RCRadioID OBJECT-TYPE
    SYNTAX      Hh3cDot11RadioScopeType
    MAX-ACCESS  not-accessible
    STATUS      current
    DESCRIPTION
        "This object represents each radio."
    ::= { hh3cDot11RadioConfigEntry 2 }

hh3cDot11RCRadioType OBJECT-TYPE
    SYNTAX      Hh3cDot11RadioType
    MAX-ACCESS  read-write
    STATUS      current
    DESCRIPTION
        "This object represents the radio will work with which 802.11 radio
         type."
    ::= { hh3cDot11RadioConfigEntry 3 }

hh3cDot11RCChannel OBJECT-TYPE
    SYNTAX      Hh3cDot11ChannelScopeType
    MAX-ACCESS  read-write
    STATUS      current
    DESCRIPTION
        "This object represents the channel allocation of radio."
    ::= { hh3cDot11RadioConfigEntry 4 }

hh3cDot11RCPreambleLen OBJECT-TYPE
    SYNTAX      Hh3cDot11PreambleType
    MAX-ACCESS  read-write
    STATUS      current
    DESCRIPTION
        "This object represents whether use long or short preamble for 802.11
         MAC frame.
        When hh3cDot11CfgRadioType is either dot11b, dot11g or dot11gn,
        then value for hh3cDot11PreambleLen will be valid.
        Otherwise, the value for it will be invalid."
    DEFVAL      { short }
    ::= { hh3cDot11RadioConfigEntry 5 }

hh3cDot11RCPwrAttValue OBJECT-TYPE
    SYNTAX      Integer32
    MAX-ACCESS  read-write
    STATUS      current
    DESCRIPTION
        "This object represents the value of power attenuation."
    ::= { hh3cDot11RadioConfigEntry 6 }

hh3cDot11RCApPowerLevel OBJECT-TYPE
    SYNTAX      Hh3cDot11TxPwrLevelScopeType
    UNITS       "dbm"
    MAX-ACCESS  read-write
    STATUS      current
    DESCRIPTION
        "Represents the maximal transmit power scope for AP."
    ::= { hh3cDot11RadioConfigEntry 7 }

hh3cDot11RCDynamicChlState OBJECT-TYPE
    SYNTAX      TruthValue
    MAX-ACCESS  read-write
    STATUS      current
    DESCRIPTION
        "Enable/Disable dynamic channel selection."
    ::= { hh3cDot11RadioConfigEntry 8 }

hh3cDot11RCDynamicPowerState OBJECT-TYPE
    SYNTAX      TruthValue
    MAX-ACCESS  read-write
    STATUS      current
    DESCRIPTION
        "Enable/Disable dynamic power selection for the band."
    ::= { hh3cDot11RadioConfigEntry 9 }

hh3cDot11RCRadioStatus OBJECT-TYPE
    SYNTAX      TruthValue
    MAX-ACCESS  read-write
    STATUS      current
    DESCRIPTION
        "Represents the radio admin status whether is enabled
        or disabled."
    ::= { hh3cDot11RadioConfigEntry 10 }

hh3cDot11RCRadioRate OBJECT-TYPE
    SYNTAX      OCTET STRING(SIZE(0..255))
    MAX-ACCESS  read-write
    STATUS      current
    DESCRIPTION
        "Set data transmit rates for the radio, in the format of 1,2,5.5...
        For 802.11n radios, the format can be MCS X.  The data transmit rates
        between AP and STA must fall into the configured rates.
        (Note: For 802.11n radios, the first value will be treated as a mandatory rate,
        and the second value will be treated as a supported rate.
        If you configure more than two rates, the configuration cannot take effect.
        If you configure only one rate, it is considered as the mandatory rate by default.)"
    ::= { hh3cDot11RadioConfigEntry 11 }

hh3cDot11RCPwrAdjustStepLength OBJECT-TYPE
    SYNTAX      Integer32
    MAX-ACCESS  read-only
    STATUS      current
    DESCRIPTION
        "Power adjustment step-length in dBm."
    ::= { hh3cDot11RadioConfigEntry 12 }

hh3cDot11RCRadioType2 OBJECT-TYPE
    SYNTAX      Hh3cDot11RadioType2
    MAX-ACCESS  read-write
    STATUS      current
    DESCRIPTION
        "This object represents the radio will work with which 802.11 radio
         type."
    ::= { hh3cDot11RadioConfigEntry 13 }

hh3cDot11RCPreambleLenCM OBJECT-TYPE
    SYNTAX      INTEGER
        {
            long(0),
            short(1)
        }
    MAX-ACCESS  read-write
    STATUS      current
    DESCRIPTION
        "This object represents whether use long or short preamble for 802.11
         MAC frame.
        When hh3cDot11CfgRadioType is either dot11b, dot11g or dot11gn,
        then value for hh3cDot11PreambleLenCM will be valid.
        Otherwise, the value for it will be invalid."
    DEFVAL      { short }
    ::= { hh3cDot11RadioConfigEntry 14 }

hh3cDot11RCDynamicChlStateCM OBJECT-TYPE
    SYNTAX      INTEGER
        {
            off(0),
            on(1)
        }
    MAX-ACCESS  read-write
    STATUS      current
    DESCRIPTION
        "Enable/Disable dynamic channel selection."
    ::= { hh3cDot11RadioConfigEntry 15 }

hh3cDot11RCRadioStatusCM OBJECT-TYPE
    SYNTAX      INTEGER
        {
            up(1),
            down(2),
            testing(3)
        }
    MAX-ACCESS  read-write
    STATUS      current
    DESCRIPTION
        "Represents the radio admin status whether is enabled
        or disabled."
    ::= { hh3cDot11RadioConfigEntry 16 }

hh3cDot11RCRadioRateCM OBJECT-TYPE
    SYNTAX      OCTET STRING(SIZE(0..255))
    MAX-ACCESS  read-write
    STATUS      current
    DESCRIPTION
        "Set data transmit rates for the radio, in the format of 1,2,5.5...
        For 802.11n radios, the format of each value can be MCS X.  The data transmit
        rates between AP and client should be one of the configured rates.
        (Note: For 802.11n radios, the first value is mandatory rate, and the second
        value is supported rate.  If more than two rate values are configured, the
        configuration will not take effect.  If only one rate value is configured,
        the mandatory rate will be set to the default value.)"
    ::= { hh3cDot11RadioConfigEntry 17 }

hh3cDot11RCDynamicPowerStateCM OBJECT-TYPE
    SYNTAX      Hh3cDot11TruthValueCM
    MAX-ACCESS  read-write
    STATUS      current
    DESCRIPTION
        "Enable/disable dynamic power selection for the band."
    ::= { hh3cDot11RadioConfigEntry 18 }

hh3cDot11RCRssiThresholdCM OBJECT-TYPE
    SYNTAX      Integer32
    UNITS       "dBm"
    MAX-ACCESS  read-write
    STATUS      current
    DESCRIPTION
        "Represents the minimum value of the RSSI.
        The clients with RSSI below this value will be refused to associate."
    DEFVAL { 1 }
    ::= { hh3cDot11RadioConfigEntry 19 }

hh3cDot11RCDynamicChlStateSelfDecisiveCM OBJECT-TYPE
    SYNTAX      Hh3cDot11TruthValueCM
    MAX-ACCESS  read-write
    STATUS      current
    DESCRIPTION
        "Enable/disable dynamic channel selection self decisive for the band."
    ::= { hh3cDot11RadioConfigEntry 20 }

hh3cDot11RCDynamicPowerStateSelfDecisiveCM OBJECT-TYPE
    SYNTAX      Hh3cDot11TruthValueCM
    MAX-ACCESS  read-write
    STATUS      current
    DESCRIPTION
        "Enable/disable dynamic power selection self decisive for the band."
    ::= { hh3cDot11RadioConfigEntry 21 }

-- *****************************************************************************
-- * End of hh3cDot11RadioConfigTable Definition
-- *****************************************************************************

hh3cDot11RadioSSIDCfgTable OBJECT-TYPE
    SYNTAX      SEQUENCE OF Hh3cDot11RadioSSIDCfgEntry
    MAX-ACCESS  not-accessible
    STATUS      current
    DESCRIPTION
        "For each radio, it could configure multiple service policies.
        The table describes the relationship between radio and
        service policies."
    ::= { hh3cDot11APConfigGroup 9 }

hh3cDot11RadioSSIDCfgEntry OBJECT-TYPE
    SYNTAX      Hh3cDot11RadioSSIDCfgEntry
    MAX-ACCESS  not-accessible
    STATUS      current
    DESCRIPTION
        "Each entry contains SSID configuration information for each radio."
    INDEX
        {
            hh3cDot11RadioSSIDSerialID,
            hh3cDot11RadioSSIDRadioID,
            hh3cDot11RadioSSIDWLANID
        }
    ::= { hh3cDot11RadioSSIDCfgTable 1 }

Hh3cDot11RadioSSIDCfgEntry ::= SEQUENCE
    {
        hh3cDot11RadioSSIDSerialID    Hh3cDot11ObjectIDType,
        hh3cDot11RadioSSIDRadioID     Hh3cDot11RadioScopeType,
        hh3cDot11RadioSSIDWLANID      Integer32,
        hh3cDot11RadioSSIDIndex       Hh3cDot11ServicePolicyIDType,
        hh3cDot11RadioBSSID           MacAddress,
        hh3cDot11RadioSSIDRowStatus   RowStatus
    }

hh3cDot11RadioSSIDSerialID OBJECT-TYPE
    SYNTAX      Hh3cDot11ObjectIDType
    MAX-ACCESS  not-accessible
    STATUS      current
    DESCRIPTION
        "This object represents the serial ID of AP."
    ::= { hh3cDot11RadioSSIDCfgEntry 1 }

hh3cDot11RadioSSIDRadioID OBJECT-TYPE
    SYNTAX      Hh3cDot11RadioScopeType
    MAX-ACCESS  not-accessible
    STATUS      current
    DESCRIPTION
        "This object represents each radio."
    ::= { hh3cDot11RadioSSIDCfgEntry 2 }

hh3cDot11RadioSSIDWLANID OBJECT-TYPE
    SYNTAX      Integer32
    MAX-ACCESS  not-accessible
    STATUS      current
    DESCRIPTION
        "This object represents the WLAN ID of the BSSID."
    ::= { hh3cDot11RadioSSIDCfgEntry 3 }

hh3cDot11RadioSSIDIndex OBJECT-TYPE
    SYNTAX      Hh3cDot11ServicePolicyIDType
    MAX-ACCESS  read-create
    STATUS      current
    DESCRIPTION
        "This object represents the ID of each service policy used by the
         radio."
    ::= { hh3cDot11RadioSSIDCfgEntry 4 }

hh3cDot11RadioBSSID OBJECT-TYPE
    SYNTAX      MacAddress
    MAX-ACCESS  read-only
    STATUS      current
    DESCRIPTION
        "As MAC address format, it is used to identify BSS."
    ::= { hh3cDot11RadioSSIDCfgEntry 5 }

hh3cDot11RadioSSIDRowStatus OBJECT-TYPE
    SYNTAX      RowStatus
    MAX-ACCESS  read-create
    STATUS      current
    DESCRIPTION
        "RowStatus."
    ::= { hh3cDot11RadioSSIDCfgEntry 6 }

-- *****************************************************************************
-- *  hh3cDot11APSerialIDTable Definition
-- *****************************************************************************

hh3cDot11APSerialIDTable OBJECT-TYPE
    SYNTAX      SEQUENCE OF Hh3cDot11APSerialIDEntry
    MAX-ACCESS  not-accessible
    STATUS      current
    DESCRIPTION
        "The table will provide the general information about APs."
    ::= { hh3cDot11APConfigGroup 10 }

hh3cDot11APSerialIDEntry OBJECT-TYPE
    SYNTAX      Hh3cDot11APSerialIDEntry
    MAX-ACCESS  not-accessible
    STATUS      current
    DESCRIPTION
        "Each entry contains the general information of an AP."
    INDEX
        {
            hh3cDot11SIDAPSerialID
        }
    ::= { hh3cDot11APSerialIDTable 1 }

Hh3cDot11APSerialIDEntry ::= SEQUENCE
    {
        hh3cDot11SIDAPSerialID               OCTET STRING,
        hh3cDot11SIDAPWorkMode               INTEGER,
        hh3cDot11SIDAPGetIPMethod            INTEGER,
        hh3cDot11SIDAPTemplateName           OCTET STRING,
        hh3cDot11SIDModelAlias               OCTET STRING,
        hh3cDot11SIDAPDescription            OCTET STRING,
        hh3cDot11SIDRowStatus                RowStatus,
        hh3cDot11SIDAPName                   OCTET STRING,
        hh3cDot11SIDStatisInterv             Integer32,
        hh3cDot11SIDAPBroadcastProbeReply    TruthValue,
        hh3cDot11SIDAPStaIdleTimerInterv     Integer32,
        hh3cDot11SIDStaKeepAliveTimerInterv  Integer32,
        hh3cDot11SIDAPCir                    Integer32,
        hh3cDot11SIDAPCbs                    Integer32,
        hh3cDot11SIDAPPriorityLevel          Integer32,
        hh3cDot11SIDAPElementID              Integer32,
        hh3cDot11SIDAPDevDetectEnable        TruthValue,
        hh3cDot11SIDAPStatisIntervMode       INTEGER,
        hh3cDot11SIDAPWorkModeCM             INTEGER,
        hh3cDot11SIDEchoInterval             Integer32
    }

hh3cDot11SIDAPSerialID OBJECT-TYPE
    SYNTAX      OCTET STRING
    MAX-ACCESS  not-accessible
    STATUS      current
    DESCRIPTION
        "Represents AP serial id."
    ::= { hh3cDot11APSerialIDEntry 1 }

hh3cDot11SIDAPWorkMode OBJECT-TYPE
    SYNTAX      INTEGER
        {
            normal(1),
            monitor(2),
            hybrid(3)
        }
    MAX-ACCESS  read-create
    STATUS      current
    DESCRIPTION
        "Represents what work mode for AP.
        The following values are supported:
        normal   - AP will supply WLAN service.
        monitor  - AP will be a monitor to find attack.
        hybrid   - AP will supply WLAN service and Device detection is
        enabled."
    DEFVAL      { normal }
    ::= { hh3cDot11APSerialIDEntry 2 }

hh3cDot11SIDAPGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { hh3cDot11APSerialIDEntry 3 }
hh3cDot11SIDAPTemplateName OBJECT-TYPE
    SYNTAX      OCTET STRING
    MAX-ACCESS  read-create
    STATUS      current
    DESCRIPTION
        "Represents the name of AP template."
    ::= { hh3cDot11APSerialIDEntry 4 }
hh3cDot11SIDModelAlias OBJECT-TYPE
    SYNTAX      OCTET STRING
    MAX-ACCESS  read-create
    STATUS      current
    DESCRIPTION
        "Represents the alias of AP model name."
    ::= { hh3cDot11APSerialIDEntry 5 }

hh3cDot11SIDAPDescription OBJECT-TYPE
    SYNTAX      OCTET STRING
    MAX-ACCESS  read-create
    STATUS      current
    DESCRIPTION
        "This attribute will give more information about AP.
        Administrator could suggest the location, owner or
        other information for each AP.
        If the value is set to NULL, the description will be removed."
    ::= { hh3cDot11APSerialIDEntry 6 }

hh3cDot11SIDRowStatus OBJECT-TYPE
    SYNTAX      RowStatus
    MAX-ACCESS  read-create
    STATUS      current
    DESCRIPTION
        "The status of this table entry."
    ::= { hh3cDot11APSerialIDEntry 7 }

hh3cDot11SIDAPName OBJECT-TYPE
    SYNTAX      OCTET STRING
    MAX-ACCESS  read-create
    STATUS      current
    DESCRIPTION
        "Represents the AP name."
    ::= { hh3cDot11APSerialIDEntry 8 }

hh3cDot11SIDStatisInterv OBJECT-TYPE
    SYNTAX      Integer32
    UNITS       "second"
    MAX-ACCESS  read-create
    STATUS      current
    DESCRIPTION
        "Represents the interval of radio statistic."
    ::= { hh3cDot11APSerialIDEntry 9 }

hh3cDot11SIDAPBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { hh3cDot11APSerialIDEntry 10 }

hh3cDot11SIDAPStaIdleTimerInterv OBJECT-TYPE
    SYNTAX      Integer32
    UNITS       "second"
    MAX-ACCESS  read-create
    STATUS      current
    DESCRIPTION
        "Represents the interval for which the link between AP and STA
        ( power-save or awake ) can be idle."
    ::= { hh3cDot11APSerialIDEntry 11 }

hh3cDot11SIDStaKeepAliveTimerInterv OBJECT-TYPE
    SYNTAX      Integer32
    UNITS       "second"
    MAX-ACCESS  read-create
    STATUS      current
    DESCRIPTION
        "Represents the interval of the keep alive requests sent between
        AP and STA."
    ::= { hh3cDot11APSerialIDEntry 12 }

hh3cDot11SIDAPCir OBJECT-TYPE
    SYNTAX      Integer32
    UNITS       "Kbps"
    MAX-ACCESS  read-create
    STATUS      current
    DESCRIPTION
        "Represents the committed information rate between AP and AC."
    ::= { hh3cDot11APSerialIDEntry 13 }

hh3cDot11SIDAPCbs OBJECT-TYPE
    SYNTAX      Integer32
    UNITS       "Bytes"
    MAX-ACCESS  read-create
    STATUS      current
    DESCRIPTION
        "Represents the committed burst size between AP and AC."
    ::= { hh3cDot11APSerialIDEntry 14 }

hh3cDot11SIDAPPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { hh3cDot11APSerialIDEntry 15 }

hh3cDot11SIDAPElementID OBJECT-TYPE
    SYNTAX      Integer32
    MAX-ACCESS  read-only
    STATUS      current
    DESCRIPTION
        "This object represents the AP element ID."
    ::= { hh3cDot11APSerialIDEntry 16 }

hh3cDot11SIDAPDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services.  When an AP works
         in monitor mode, that is, the value of object hh3cDot11APWorkMode is
         monitor, device detection can not be enabled with object
         hh3cDot11SIDAPDevDetectEnable."
    DEFVAL      { false }
    ::= { hh3cDot11APSerialIDEntry 17 }

hh3cDot11SIDAPStatisIntervMode OBJECT-TYPE
    SYNTAX      INTEGER
    {
        normal(1),
        realtime(2)
    }
    MAX-ACCESS  read-create
    STATUS      current
    DESCRIPTION
        "This object represents the mode of statics interval.
         normal    - statics interval value between 10s to 240s
         realtime  - statics interval value between 0s to 5s"
    DEFVAL      { normal }
    ::= { hh3cDot11APSerialIDEntry 18 }

hh3cDot11SIDAPWorkModeCM OBJECT-TYPE
    SYNTAX      INTEGER
        {
            normal(0),
            monitor(1),
            semimonitor(2)
        }
    MAX-ACCESS  read-create
    STATUS      current
    DESCRIPTION
        "Represents what work mode for AP.
        The following values are supported:
        normal   - AP will supply WLAN service.
        monitor  - AP will be a monitor to find attack.
        SemiMonitor   - AP will supply WLAN service and Device detection is
        enabled."
    DEFVAL      { normal }
    ::= { hh3cDot11APSerialIDEntry 19 }

hh3cDot11SIDEchoInterval OBJECT-TYPE
    SYNTAX      Integer32
    UNITS       "second"
    MAX-ACCESS  read-write
    STATUS      current
    DESCRIPTION
        "Represents the interval for send echo requests."
    ::= { hh3cDot11APSerialIDEntry 20 }

-- *****************************************************************************
-- *  hh3cDot11RadioIntfConfigTable Definition
-- *****************************************************************************
hh3cDot11RadioIntfConfigTable OBJECT-TYPE
    SYNTAX      SEQUENCE OF Hh3cDot11RadioIntfConfigEntry
    MAX-ACCESS  not-accessible
    STATUS      current
    DESCRIPTION
        "The table defines the parameters for radio in AP, as per
        radio."
    ::= { hh3cDot11RadioIntfConfigGroup 1 }

hh3cDot11RadioIntfConfigEntry OBJECT-TYPE
    SYNTAX      Hh3cDot11RadioIntfConfigEntry
    MAX-ACCESS  not-accessible
    STATUS      current
    DESCRIPTION
        "Each entry contains information of each radio in AP."
    INDEX
        {
            hh3cDot11RadioIfIdx
        }
    ::= { hh3cDot11RadioIntfConfigTable 1 }

Hh3cDot11RadioIntfConfigEntry ::= SEQUENCE
    {
        hh3cDot11RadioIfIdx               Integer32,
        hh3cDot11RadioCfgBeaconIntvl      Integer32,
        hh3cDot11RadioCfgDtimIntvl        Integer32,
        hh3cDot11RadioCfgRtsThreshold     Integer32,
        hh3cDot11RadioCfgFragThreshold    Integer32,
        hh3cDot11RadioCfgShtRetryThld     Integer32,
        hh3cDot11RadioCfglongRtrThld      Integer32,
        hh3cDot11RadioCfgMaxRxLifetime    Unsigned32,
        hh3cDot11RadioCfgType             Hh3cDot11RadioType,
        hh3cDot11RadioCfgChannel          Hh3cDot11ChannelScopeType,
        hh3cDot11RadioCfgMaxTxPwrLvl      Hh3cDot11TxPwrLevelScopeType,
        hh3cDot11RadioCfgPreambleLen      Hh3cDot11PreambleType,
        hh3cDot11RadioCfgWorkMode         Hh3cDot11WorkMode,
        hh3cDot11RadioCfgOnly11gEnable    TruthValue,
        hh3cDot11RadioCfgType2            Hh3cDot11RadioType2,
        hh3cDot11RadioCfgRssithresholdCM  Integer32
    }

hh3cDot11RadioIfIdx OBJECT-TYPE
    SYNTAX      Integer32
    MAX-ACCESS  not-accessible
    STATUS      current
    DESCRIPTION
        "Represents the Radio IfIndex of radio in AP."
    ::= { hh3cDot11RadioIntfConfigEntry 1 }

hh3cDot11RadioCfgBeaconIntvl OBJECT-TYPE
    SYNTAX      Integer32
    UNITS       "TU"
    MAX-ACCESS  read-write
    STATUS      current
    DESCRIPTION
        "Represents the interval for Beacon management frame."
    DEFVAL { 100 }
    ::= { hh3cDot11RadioIntfConfigEntry 2 }

hh3cDot11RadioCfgDtimIntvl OBJECT-TYPE
    SYNTAX      Integer32
    MAX-ACCESS  read-write
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL { 1 }
    ::= { hh3cDot11RadioIntfConfigEntry 3 }

hh3cDot11RadioCfgRtsThreshold OBJECT-TYPE
    SYNTAX      Integer32
    UNITS       "Byte"
    MAX-ACCESS  read-write
    STATUS      current
    DESCRIPTION
        "Represents the current minimum size,in octets,of the MAC
        protocol data unit (MPDU), below which a Request to send/Clear
        to send (RTS/CTS) handshake shall not be performed."
    DEFVAL { 2346 }
    ::= { hh3cDot11RadioIntfConfigEntry 4 }

hh3cDot11RadioCfgFragThreshold OBJECT-TYPE
    SYNTAX      Integer32
    UNITS       "Byte"
    MAX-ACCESS  read-write
    STATUS      current
    DESCRIPTION
        "Represents the current maximum size, in octets, of the MPDU that
        may be delivered to the PHY.  A MSDU shall be broken into
        fragments if its size exceeds the value of this attribute after
        adding MAC headers and trailers."
    DEFVAL { 2346 }
    ::= { hh3cDot11RadioIntfConfigEntry 5 }

hh3cDot11RadioCfgShtRetryThld OBJECT-TYPE
    SYNTAX      Integer32
    MAX-ACCESS  read-write
    STATUS      current
    DESCRIPTION
        "Represents the maximum number of transmission attempts of a
        frame, the length of which is less than or equal to
        hh3cDot11RadioRTSThreshold, that shall be made before a failure
        condition is indicated."
    DEFVAL { 5 }
    ::= { hh3cDot11RadioIntfConfigEntry 6 }

hh3cDot11RadioCfglongRtrThld OBJECT-TYPE
    SYNTAX      Integer32
    MAX-ACCESS  read-write
    STATUS      current
    DESCRIPTION
        "Represents the maximum number of transmission attempts of a
        frame, the length of which is longer than
        hh3cDot11RadioRTSThreshold, that shall be made before a
        failure condition is indicated."
    DEFVAL { 5 }
    ::= { hh3cDot11RadioIntfConfigEntry 7 }

hh3cDot11RadioCfgMaxRxLifetime OBJECT-TYPE
    SYNTAX      Unsigned32
    UNITS       "millisecond"
    MAX-ACCESS  read-write
    STATUS      current
    DESCRIPTION
        "Represents the elapsed time.  After the time specified by
        hh3cDot11RadioCfgMaxRxLifetime, the further attempts to reassemble
        the MSDU shall be terminated."
    DEFVAL { 2000 }
    ::= { hh3cDot11RadioIntfConfigEntry 8 }

hh3cDot11RadioCfgType OBJECT-TYPE
    SYNTAX      Hh3cDot11RadioType
    MAX-ACCESS  read-write
    STATUS      current
    DESCRIPTION
        "Represents the radio will work with which 802.11 radio type."
    ::= { hh3cDot11RadioIntfConfigEntry 9 }

hh3cDot11RadioCfgChannel OBJECT-TYPE
    SYNTAX      Hh3cDot11ChannelScopeType
    MAX-ACCESS  read-write
    STATUS      current
    DESCRIPTION
        "Represents the channel allocation of radio."
    DEFVAL { 1 }
    ::= { hh3cDot11RadioIntfConfigEntry 10 }

hh3cDot11RadioCfgMaxTxPwrLvl OBJECT-TYPE
    SYNTAX      Hh3cDot11TxPwrLevelScopeType
    UNITS       "dbm"
    MAX-ACCESS  read-write
    STATUS      current
    DESCRIPTION
        "Represents the maximal transmit power scope for AP."
    ::= { hh3cDot11RadioIntfConfigEntry 11 }

hh3cDot11RadioCfgPreambleLen OBJECT-TYPE
    SYNTAX      Hh3cDot11PreambleType
    MAX-ACCESS  read-write
    STATUS      current
    DESCRIPTION
        "Represents whether use long or short preamble for 802.11 MAC
        frame."
    DEFVAL { short }
    ::= { hh3cDot11RadioIntfConfigEntry 12 }

hh3cDot11RadioCfgWorkMode OBJECT-TYPE
    SYNTAX      Hh3cDot11WorkMode
    MAX-ACCESS  read-write
    STATUS      current
    DESCRIPTION
        "Represents work mode of the radio."
    ::= { hh3cDot11RadioIntfConfigEntry 13 }

hh3cDot11RadioCfgOnly11gEnable OBJECT-TYPE
    SYNTAX      TruthValue
    MAX-ACCESS  read-write
    STATUS      current
    DESCRIPTION
        "Represents whether enable only 802.11g radio mode or not.
        'true' : Only 802.11g radio mode is enabled.
        'false': Only 802.11g radio mode is disabled."
    DEFVAL { false }
    ::= { hh3cDot11RadioIntfConfigEntry 14 }

hh3cDot11RadioCfgType2 OBJECT-TYPE
    SYNTAX      Hh3cDot11RadioType2
    MAX-ACCESS  read-write
    STATUS      current
    DESCRIPTION
        "Represents the radio will work with which 802.11 radio type."
    ::= { hh3cDot11RadioIntfConfigEntry 15 }

hh3cDot11RadioCfgRssithresholdCM OBJECT-TYPE
    SYNTAX      Integer32
    UNITS       "dBm"
    MAX-ACCESS  read-write
    STATUS      current
    DESCRIPTION
        "Represents the minimum value of the RSSI.
        The clients with RSSI below this value will be refused to associate."
    DEFVAL { 1 }
    ::= { hh3cDot11RadioIntfConfigEntry 16 }

-- *****************************************************************************
-- *  End of hh3cDot11RadioIntfConfigTable Definition
-- *****************************************************************************

-- *****************************************************************************
-- *  hh3cDot11RadioIntfBindTable Definition
-- *****************************************************************************
hh3cDot11RadioIntfBindTable OBJECT-TYPE
    SYNTAX      SEQUENCE OF Hh3cDot11RadioIntfBindEntry
    MAX-ACCESS  not-accessible
    STATUS      current
    DESCRIPTION
        "The table defines the binding information for each radio in AP.
        "
    ::= { hh3cDot11RadioIntfConfigGroup 2 }

hh3cDot11RadioIntfBindEntry OBJECT-TYPE
    SYNTAX      Hh3cDot11RadioIntfBindEntry
    MAX-ACCESS  not-accessible
    STATUS      current
    DESCRIPTION
        "Each entry contains the radio interface binding information
        in AP."
    INDEX
        {
            hh3cDot11RadioIfIdx,
            hh3cDot11RadioIntfBindSvcPlcyID
        }
    ::= { hh3cDot11RadioIntfBindTable 1 }

Hh3cDot11RadioIntfBindEntry ::= SEQUENCE
    {
        hh3cDot11RadioIntfBindSvcPlcyID    Hh3cDot11ServicePolicyIDType,
        hh3cDot11RadioIntfBindIfIdx        Unsigned32,
        hh3cDot11RadioIntfBindRowStatus    RowStatus
    }

hh3cDot11RadioIntfBindSvcPlcyID OBJECT-TYPE
    SYNTAX      Hh3cDot11ServicePolicyIDType
    MAX-ACCESS  not-accessible
    STATUS      current
    DESCRIPTION
        "Represents the ID of each service policy."
    ::= { hh3cDot11RadioIntfBindEntry 1 }

hh3cDot11RadioIntfBindIfIdx OBJECT-TYPE
    SYNTAX      Unsigned32
    MAX-ACCESS  read-create
    STATUS      current
    DESCRIPTION
        "Represents the Ifindex of interface which is binded to
        the radio."
    ::= { hh3cDot11RadioIntfBindEntry 2 }

hh3cDot11RadioIntfBindRowStatus OBJECT-TYPE
    SYNTAX      RowStatus
    MAX-ACCESS  read-create
    STATUS      current
    DESCRIPTION
        "The status of this table entry."
    ::= { hh3cDot11RadioIntfBindEntry 3 }
-- *****************************************************************************
-- *  End of hh3cDot11RadioIntfBindTable Definition
-- *****************************************************************************

-- *****************************************************************************
-- *  hh3cDot11DataRateConfigTable Definition
-- *****************************************************************************
hh3cDot11DataRateConfigTable OBJECT-TYPE
    SYNTAX      SEQUENCE OF Hh3cDot11DataRateConfigEntry
    MAX-ACCESS  not-accessible
    STATUS      current
    DESCRIPTION
        "Table will provide data rate configuration for a specific radio type."
    ::= { hh3cDot11DataRateConfigGroup 1 }

hh3cDot11DataRateConfigEntry OBJECT-TYPE
    SYNTAX      Hh3cDot11DataRateConfigEntry
    MAX-ACCESS  not-accessible
    STATUS      current
    DESCRIPTION
        "Each entry of the table will provide data rate configuration for a
        specific radio type."
    INDEX
        {
            hh3cDot11RadioTypeID
        }
    ::= { hh3cDot11DataRateConfigTable 1 }

Hh3cDot11DataRateConfigEntry ::= SEQUENCE
    {
        hh3cDot11RadioTypeID         Hh3cDot11RadioType,
        hh3cDot11SupportedRateSet    OCTET STRING,
        hh3cDot11MandatoryRateSet    OCTET STRING,
        hh3cDot11DisabledRateSet     OCTET STRING,
        hh3cDot11SmartRateSet        OCTET STRING
    }

hh3cDot11RadioTypeID OBJECT-TYPE
    SYNTAX      Hh3cDot11RadioType
    MAX-ACCESS  not-accessible
    STATUS      current
    DESCRIPTION
        "Represents the radio type."
    ::= { hh3cDot11DataRateConfigEntry 1 }

hh3cDot11SupportedRateSet OBJECT-TYPE
    SYNTAX      OCTET STRING(SIZE(0..255))
    MAX-ACCESS  read-write
    STATUS      current
    DESCRIPTION
        "Represents the supported rate set of a particular radio type."
    ::= { hh3cDot11DataRateConfigEntry 2 }

hh3cDot11MandatoryRateSet OBJECT-TYPE
    SYNTAX      OCTET STRING(SIZE(0..255))
    MAX-ACCESS  read-write
    STATUS      current
    DESCRIPTION
        "Represents the mandatory rate set of a particular radio type."
    ::= { hh3cDot11DataRateConfigEntry 3 }

hh3cDot11DisabledRateSet OBJECT-TYPE
    SYNTAX      OCTET STRING(SIZE(0..255))
    MAX-ACCESS  read-write
    STATUS      current
    DESCRIPTION
        "Represents the disabled rate set of a particular radio type."
    ::= { hh3cDot11DataRateConfigEntry 4 }

hh3cDot11SmartRateSet OBJECT-TYPE
    SYNTAX      OCTET STRING(SIZE(0..255))
    MAX-ACCESS  read-write
    STATUS      current
    DESCRIPTION
        "Represents the rate set of a particular radio type."
    ::= { hh3cDot11DataRateConfigEntry 5 }
-- *****************************************************************************
-- *  End of hh3cDot11DataRateConfigTable Definition
-- *****************************************************************************

-- *****************************************************************************
-- *  hh3cDot11WlanEssIfTable Definition
-- *************************************************************************

hh3cDot11WlanEssIfTable OBJECT-TYPE
    SYNTAX      SEQUENCE OF Hh3cDot11WlanEssIfEntry
    MAX-ACCESS  not-accessible
    STATUS      current
    DESCRIPTION
        "This table is used to configure WLAN ESS interface."
    ::= { hh3cDot11InterfaceConfigGroup 1 }

hh3cDot11WlanEssIfEntry OBJECT-TYPE
    SYNTAX      Hh3cDot11WlanEssIfEntry
    MAX-ACCESS  not-accessible
    STATUS      current
    DESCRIPTION
        "Each entry contains the WLAN ESS interface configuration."
    INDEX
        {
            hh3cDot11WlanEssIfNumber
        }
    ::= { hh3cDot11WlanEssIfTable 1 }

Hh3cDot11WlanEssIfEntry ::= SEQUENCE
    {
        hh3cDot11WlanEssIfNumber      Integer32,
        hh3cDot11WlanEssIfIndex       Integer32,
        hh3cDot11WlanEssRowStatus     RowStatus
    }

hh3cDot11WlanEssIfNumber OBJECT-TYPE
    SYNTAX      Integer32
    MAX-ACCESS  not-accessible
    STATUS      current
    DESCRIPTION
        "This node represents the WLAN ESS interface number."
    ::= { hh3cDot11WlanEssIfEntry 1 }

hh3cDot11WlanEssIfIndex OBJECT-TYPE
    SYNTAX      Integer32
    MAX-ACCESS  read-only
    STATUS      current
    DESCRIPTION
        "This node represents the ifIndex of WLAN-ESS interface."
    ::= { hh3cDot11WlanEssIfEntry 2 }

hh3cDot11WlanEssRowStatus OBJECT-TYPE
    SYNTAX      RowStatus
    MAX-ACCESS  read-create
    STATUS      current
    DESCRIPTION
        "This node represents the WLAN ESS interface row status."
    ::= { hh3cDot11WlanEssIfEntry 3 }

-- *****************************************************************************
-- *  End of hh3cDot11WlanEssIfTable  Definition
-- *****************************************************************************
-- *****************************************************************************
-- *  hh3cDot11WlanBssIfTable Definition
-- *************************************************************************

hh3cDot11WlanBssIfTable OBJECT-TYPE
    SYNTAX      SEQUENCE OF Hh3cDot11WlanBssIfEntry
    MAX-ACCESS  not-accessible
    STATUS      current
    DESCRIPTION
        "This table is used to configure WLAN BSS interface."
    ::= { hh3cDot11InterfaceConfigGroup 2 }

hh3cDot11WlanBssIfEntry OBJECT-TYPE
    SYNTAX      Hh3cDot11WlanBssIfEntry
    MAX-ACCESS  not-accessible
    STATUS      current
    DESCRIPTION
        "Each entry contains the WLAN BSS interface configuration."
    INDEX
        {
            hh3cDot11WlanBssIfNumber
        }
    ::= { hh3cDot11WlanBssIfTable 1 }

Hh3cDot11WlanBssIfEntry ::= SEQUENCE
    {
        hh3cDot11WlanBssIfNumber     Integer32,
        hh3cDot11WlanBssIfIndex      Integer32,
        hh3cDot11WlanBssRowStatus    RowStatus
    }

hh3cDot11WlanBssIfNumber OBJECT-TYPE
    SYNTAX      Integer32
    MAX-ACCESS  not-accessible
    STATUS      current
    DESCRIPTION
        "This node represents the WLAN BSS interface number."
    ::= { hh3cDot11WlanBssIfEntry 1 }

hh3cDot11WlanBssIfIndex OBJECT-TYPE
    SYNTAX      Integer32
    MAX-ACCESS  read-only
    STATUS      current
    DESCRIPTION
        "This node represents the ifIndex of WLAN-BSS interface."
    ::= { hh3cDot11WlanBssIfEntry 2 }

hh3cDot11WlanBssRowStatus OBJECT-TYPE
    SYNTAX      RowStatus
    MAX-ACCESS  read-create
    STATUS      current
    DESCRIPTION
        "This node represents the WLAN BSS interface row status."
    ::= { hh3cDot11WlanBssIfEntry 3 }

-- *****************************************************************************
-- *  End of hh3cDot11WlanBssIfTable Definition
-- *****************************************************************************
-- *****************************************************************************
-- *  hh3cDot11WLANEthernetIfTable Definition
-- *************************************************************************

hh3cDot11WLANEthernetIfTable OBJECT-TYPE
    SYNTAX      SEQUENCE OF Hh3cDot11WLANEthernetIfEntry
    MAX-ACCESS  not-accessible
    STATUS      current
    DESCRIPTION
        "This table is used to configure WLAN Ethernet interface."
    ::= { hh3cDot11InterfaceConfigGroup 3 }

hh3cDot11WLANEthernetIfEntry OBJECT-TYPE
    SYNTAX      Hh3cDot11WLANEthernetIfEntry
    MAX-ACCESS  not-accessible
    STATUS      current
    DESCRIPTION
        "Each entry contains the WLAN Ethernet interface configuration."
    INDEX
        {
            hh3cDot11WlanEthernetIfNumber
        }
    ::= { hh3cDot11WLANEthernetIfTable 1 }

Hh3cDot11WLANEthernetIfEntry ::= SEQUENCE
    {
        hh3cDot11WlanEthernetIfNumber     Integer32,
        hh3cDot11WLANEthernetIfIndex      Integer32,
        hh3cDot11WlanEthernetRowStatus    RowStatus
    }

hh3cDot11WlanEthernetIfNumber OBJECT-TYPE
    SYNTAX      Integer32
    MAX-ACCESS  not-accessible
    STATUS      current
    DESCRIPTION
        "This node represents the WLAN Ethernet interface number."
    ::= { hh3cDot11WLANEthernetIfEntry 1 }

hh3cDot11WLANEthernetIfIndex OBJECT-TYPE
    SYNTAX      Integer32
    MAX-ACCESS  read-only
    STATUS      current
    DESCRIPTION
        "This node represents the ifIndex of WLAN-Ethernet interface."
    ::= { hh3cDot11WLANEthernetIfEntry 2 }

hh3cDot11WlanEthernetRowStatus OBJECT-TYPE
    SYNTAX      RowStatus
    MAX-ACCESS  read-create
    STATUS      current
    DESCRIPTION
        "This node represents the Wlan Ethernet interface row status."
    ::= { hh3cDot11WLANEthernetIfEntry 3 }

-- *****************************************************************************
-- *  End of hh3cDot11DataRateConfigTable Definition
-- *****************************************************************************
-- *****************************************************************************
-- *  hh3cDot11PortSecurityTable Definition
-- *****************************************************************************
hh3cDot11PortSecurityTable OBJECT-TYPE
    SYNTAX      SEQUENCE OF Hh3cDot11PortSecurityEntry
    MAX-ACCESS  not-accessible
    STATUS      current
    DESCRIPTION
        "This table defines the WLAN security status for ESS, BSS, mesh and
        WLAN-Ethernet interface which binding the crypto service-template.
        Otherwise, when binding the clear service-template,
        hh3cPortSecurityTables should be used to configure port security."
    ::= { hh3cDot11InterfaceConfigGroup 4 }

hh3cDot11PortSecurityEntry OBJECT-TYPE
    SYNTAX      Hh3cDot11PortSecurityEntry
    MAX-ACCESS  not-accessible
    STATUS      current
    DESCRIPTION
        "There is a row in this table for each ESS, BSS and WLAN-Ethernet
        interface.It is indexed using the object ifIndex in RFC1213-MIB."
    INDEX
        {
            ifIndex
        }
    ::= { hh3cDot11PortSecurityTable 1 }

Hh3cDot11PortSecurityEntry ::= SEQUENCE
    {
        hh3cDot11PortSecurityMode                 INTEGER,
        hh3cDot11SecurityUserLoginTxKeyType       INTEGER,
        hh3cDot11SecurityPskKeyMode               INTEGER,
        hh3cDot11SecurityPskKeyString             DisplayString
    }

hh3cDot11PortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions  - The default value,no any security mode is set.

        userLoginSecureExt  - Access to the port is denied until the port
        client is authorized (by 802.1X).

        psk  - Access to the port is denied until the port client is
        authorized (by 802.1X key negotiation).

        macAddressAndPsk  - The MAC address is first authenticated and only if
        this succeeds does the psk then attempt user authentication.

        userLoginSecureExtOrPsk  - This selects both the userLoginSecureExt and
        psk modes together such that either is allowed to authorized access.
        Which mode works for client depends on the client's choice.

        ext  - Access to the port is denied until the port client is
        authenticated (by ext).
        "
    ::= { hh3cDot11PortSecurityEntry 1 }

hh3cDot11SecurityUserLoginTxKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone  - This means the key type is not set yet.

        userLoginTxKeyTypeDot11Key  - This selects the 802.11 key type.

        userLoginTxKeyTypeRsaRC4Key  - This selects the RC4 key for RSA RC4
        session encryption."
    ::= { hh3cDot11PortSecurityEntry 2 }

hh3cDot11SecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode.  When input as pskKeyModePassPhrase,
        hh3cDot11SecurePskKeyString must be 8 to 63 characters; when input as
        pskKeyModeRawKey, hh3cDot11SecurePskKeyString must be 64 characters and
        each character must be '0'-'9', 'a'-'f' and 'A'-'F'."
    ::= { hh3cDot11PortSecurityEntry 3 }

hh3cDot11SecurityPskKeyString OBJECT-TYPE
    SYNTAX      DisplayString
    MAX-ACCESS  read-write
    STATUS      current
    DESCRIPTION
        "This is the password string used for psk authentication."
    ::= { hh3cDot11PortSecurityEntry 4 }

-- *****************************************************************************
-- *  End of hh3cDot11PortSecurityTable Definition
-- *****************************************************************************
-- *****************************************************************************
-- *  hh3cDot11WlanMeshIfTable Definition
-- *************************************************************************

hh3cDot11WlanMeshIfTable OBJECT-TYPE
    SYNTAX      SEQUENCE OF Hh3cDot11WlanMeshIfEntry
    MAX-ACCESS  not-accessible
    STATUS      current
    DESCRIPTION
        "This table is used to configure WLAN mesh interface."
    ::= { hh3cDot11InterfaceConfigGroup 5 }

hh3cDot11WlanMeshIfEntry OBJECT-TYPE
    SYNTAX      Hh3cDot11WlanMeshIfEntry
    MAX-ACCESS  not-accessible
    STATUS      current
    DESCRIPTION
        "Each entry contains the WLAN mesh interface configuration."
    INDEX
        {
            hh3cDot11WlanMeshIfNumber
        }
    ::= { hh3cDot11WlanMeshIfTable 1 }

Hh3cDot11WlanMeshIfEntry ::= SEQUENCE
    {
        hh3cDot11WlanMeshIfNumber    Integer32,
        hh3cDot11WlanMeshIfIndex     Integer32,
        hh3cDot11WlanMeshRowStatus   RowStatus
    }

hh3cDot11WlanMeshIfNumber OBJECT-TYPE
    SYNTAX      Integer32
    MAX-ACCESS  not-accessible
    STATUS      current
    DESCRIPTION
        "This node represents the WLAN mesh interface number."
    ::= { hh3cDot11WlanMeshIfEntry 1 }

hh3cDot11WlanMeshIfIndex OBJECT-TYPE
    SYNTAX      Integer32
    MAX-ACCESS  read-only
    STATUS      current
    DESCRIPTION
        "This node represents the index of WLAN mesh interface."
    ::= { hh3cDot11WlanMeshIfEntry 2 }

hh3cDot11WlanMeshRowStatus OBJECT-TYPE
    SYNTAX      RowStatus
    MAX-ACCESS  read-create
    STATUS      current
    DESCRIPTION
        "This node represents the WLAN mesh interface row status."
    ::= { hh3cDot11WlanMeshIfEntry 3 }

-- *****************************************************************************
-- *  End of hh3cDot11WlanMeshIfTable Definition
-- *****************************************************************************

-- *****************************************************************************
-- *  hh3cDot11ACBackupGroup Definition
-- *****************************************************************************
hh3cDot11BackupACAdrssIP OBJECT-TYPE
    SYNTAX      InetAddress
    MAX-ACCESS  read-write
    STATUS      current
    DESCRIPTION
        "This object represents the backup AC IP address.
        If the backup AC IP address is not configured,
        the object value is 0.0.0.0."
    ::= { hh3cDot11ACBackupGroup 1 }

hh3cDot11BackupACAdrssIPv6 OBJECT-TYPE
    SYNTAX      InetAddress
    MAX-ACCESS  read-write
    STATUS      current
    DESCRIPTION
        "This object represents the backup AC IPv6 address.
         If the backup AC IPv6 address is not configured,
         the object value is 0::0."
    ::= { hh3cDot11ACBackupGroup 2 }

-- *****************************************************************************
-- *  End of hh3cDot11ACBackupGroup Definition
-- *****************************************************************************

-- *****************************************************************************
-- *  hh3cDot11RadioElementConfigGroup Definition
-- *****************************************************************************

hh3cDot11nRadioCfgTable OBJECT-TYPE
    SYNTAX SEQUENCE OF Hh3cDot11nRadioCfgEntry
    MAX-ACCESS not-accessible
    STATUS current
    DESCRIPTION
        "This table is used to configure dot11n on the radio."
    ::= { hh3cDot11RadioElementConfigGroup 1 }

hh3cDot11nRadioCfgEntry OBJECT-TYPE
    SYNTAX Hh3cDot11nRadioCfgEntry
    MAX-ACCESS not-accessible
    STATUS current
    DESCRIPTION
        "This entry contains the dot11n configuration on the radio."
    INDEX { hh3cDot11nRadioCfgIndex }
    ::= { hh3cDot11nRadioCfgTable 1 }

Hh3cDot11nRadioCfgEntry ::= SEQUENCE
    {
        hh3cDot11nRadioCfgIndex       Hh3cDot11RadioElementIndex,
        hh3cDot11nAMpduEnable         TruthValue,
        hh3cDot11nAMsduEnable         TruthValue,
        hh3cDot11nClientDot11nOnly    TruthValue,
        hh3cDot11nChanelBand          INTEGER,
        hh3cDot11nShortGiEnable       TruthValue,
        hh3cDot11nClientDot11acOnly   TruthValue,
        hh3cDot11nSupportMaxMcs       Integer32,
        hh3cDot11nMandatoryMaxMcs     Integer32
    }

hh3cDot11nRadioCfgIndex OBJECT-TYPE
    SYNTAX Hh3cDot11RadioElementIndex
    MAX-ACCESS not-accessible
    STATUS current
    DESCRIPTION
        "Represents index of the radio."
    ::= { hh3cDot11nRadioCfgEntry 1 }

hh3cDot11nAMpduEnable OBJECT-TYPE
    SYNTAX TruthValue
    MAX-ACCESS read-write
    STATUS current
    DESCRIPTION
        "Enable the function of A-MPDU."
        DEFVAL { true }
    ::= { hh3cDot11nRadioCfgEntry 2 }

hh3cDot11nAMsduEnable OBJECT-TYPE
    SYNTAX TruthValue
    MAX-ACCESS read-write
    STATUS current
    DESCRIPTION
        "Enable the function of A-MSDU."
    DEFVAL { true }
    ::= { hh3cDot11nRadioCfgEntry 3 }

hh3cDot11nClientDot11nOnly OBJECT-TYPE
    SYNTAX TruthValue
    MAX-ACCESS read-write
    STATUS current
    DESCRIPTION
        "If radio type is 802.11an or 802.11gn, only permit clients of 11n mode.
         If radio type is 802.11ac, permit clients of 11n and 11ac mode."
    DEFVAL { false }
    ::= { hh3cDot11nRadioCfgEntry 4 }

hh3cDot11nChanelBand OBJECT-TYPE
    SYNTAX INTEGER
        {
        mode20(1),
        mode40(2),
        mode80(3),
        mode160(4),
        mode80and80(5)
        }
    MAX-ACCESS read-write
    STATUS current
    DESCRIPTION
        "Specify the bandwidth mode."
    DEFVAL { mode40 }
    ::= { hh3cDot11nRadioCfgEntry 5 }

hh3cDot11nShortGiEnable OBJECT-TYPE
    SYNTAX TruthValue
    MAX-ACCESS read-write
    STATUS current
    DESCRIPTION
        "The function of Short GI."
    DEFVAL { true }
    ::= { hh3cDot11nRadioCfgEntry 6 }

hh3cDot11nClientDot11acOnly OBJECT-TYPE
    SYNTAX TruthValue
    MAX-ACCESS read-write
    STATUS current
    DESCRIPTION
        "Only permit clients of 11ac mode."
    DEFVAL { false }
    ::= { hh3cDot11nRadioCfgEntry 7 }

hh3cDot11nSupportMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { hh3cDot11nRadioCfgEntry 8 }

hh3cDot11nMandatoryMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { hh3cDot11nRadioCfgEntry 9 }

-- *****************************************************************************
-- *  End of hh3cDot11RadioElementConfigGroup Definition
-- *****************************************************************************

-- *****************************************************************************
-- *  hh3cDot11RadioWDSTable Definition
-- *****************************************************************************

hh3cDot11RadioWDSTable OBJECT-TYPE
    SYNTAX      SEQUENCE OF Hh3cDot11RadioWDSEntry
    MAX-ACCESS  not-accessible
    STATUS      current
    DESCRIPTION
        "This table is used to configure WDS on the radio."
    ::= { hh3cDot11RadioElementConfigGroup 2 }

hh3cDot11RadioWDSEntry OBJECT-TYPE
    SYNTAX      Hh3cDot11RadioWDSEntry
    MAX-ACCESS  not-accessible
    STATUS      current
    DESCRIPTION
        "Each entry contains the WDS configuration on the radio."
    INDEX
        {
            hh3cDot11RadioWDSIndex
        }
    ::= { hh3cDot11RadioWDSTable 1 }

Hh3cDot11RadioWDSEntry ::= SEQUENCE
    {
        hh3cDot11RadioWDSIndex            Hh3cDot11RadioElementIndex,
        hh3cDot11RadioWDSMode             INTEGER,
        hh3cDot11RadioWDSNetWorkID        OCTET STRING,
        hh3cDot11WDSSecPskKeyMode         INTEGER,
        hh3cDot11WDSSecPskKeyString       DisplayString
    }

hh3cDot11RadioWDSIndex OBJECT-TYPE
    SYNTAX      Hh3cDot11RadioElementIndex
    MAX-ACCESS  not-accessible
    STATUS      current
    DESCRIPTION
        "Represents the element index of radio."
    ::= { hh3cDot11RadioWDSEntry 1 }

hh3cDot11RadioWDSMode OBJECT-TYPE
    SYNTAX      INTEGER
        {
            nowds(1),
            wds(2)
        }
    MAX-ACCESS  read-write
    STATUS      current
    DESCRIPTION
        "Represents enable the WDS mode or not.
        nowds: The WDS mode is disabled.
        wds  : The WDS mode is enabled"
    DEFVAL      { nowds }
    ::= { hh3cDot11RadioWDSEntry 2 }

hh3cDot11RadioWDSNetWorkID OBJECT-TYPE
    SYNTAX      OCTET STRING(SIZE(0..32))
    MAX-ACCESS  read-write
    STATUS      current
    DESCRIPTION
        "Represents the mesh ID of WDS."
    DEFVAL      { "" }
    ::= { hh3cDot11RadioWDSEntry 3 }

hh3cDot11WDSSecPskKeyMode OBJECT-TYPE
    SYNTAX      INTEGER
        {
          pskKeyModeNone(1),
          pskKeyModePassPhrase(2),
          pskKeyModeRawKey(3)
        }
    MAX-ACCESS  read-write
    STATUS      current
    DESCRIPTION
        "Represents the PSK mode of WDS."
    DEFVAL      { pskKeyModeNone }
    ::= { hh3cDot11RadioWDSEntry 4 }

hh3cDot11WDSSecPskKeyString OBJECT-TYPE
    SYNTAX      DisplayString
    MAX-ACCESS  read-write
    STATUS      current
    DESCRIPTION
        "Represents the PSK value of WDS."
    DEFVAL      { "" }
    ::= { hh3cDot11RadioWDSEntry 5 }

-- *****************************************************************************
-- *  End of hh3cDot11RadioWDSTable  Definition
-- *****************************************************************************

-- *****************************************************************************
-- *  hh3cDot11nRadioCfg2Table Definition
-- *****************************************************************************

hh3cDot11nRadioCfg2Table OBJECT-TYPE
    SYNTAX SEQUENCE OF Hh3cDot11nRadioCfg2Entry
    MAX-ACCESS not-accessible
    STATUS current
    DESCRIPTION
        "This table is used to configure dot11n on the radio."
    ::= { hh3cDot11RadioElementConfigGroup 3 }

hh3cDot11nRadioCfg2Entry OBJECT-TYPE
    SYNTAX Hh3cDot11nRadioCfg2Entry
    MAX-ACCESS not-accessible
    STATUS current
    DESCRIPTION
        "This entry contains the dot11n configuration on the radio."
    INDEX {
              hh3cDot11nRadioCfg2APIDIndex,
              hh3cDot11nRadioCfg2RadioIDIndex
          }
    ::= { hh3cDot11nRadioCfg2Table 1 }

Hh3cDot11nRadioCfg2Entry ::= SEQUENCE
    {
        hh3cDot11nRadioCfg2APIDIndex           Hh3cDot11ObjectIDType,
        hh3cDot11nRadioCfg2RadioIDIndex        Hh3cDot11RadioScopeType,
        hh3cDot11nRadioCfg2AMpduEnable         TruthValue,
        hh3cDot11nRadioCfg2AMsduEnable         TruthValue,
        hh3cDot11nRadioCfg2ClientDot11nOnly    TruthValue,
        hh3cDot11nRadioCfg2ChannelBand          INTEGER,
        hh3cDot11nRadioCfg2ShortGiEnable       TruthValue,
        hh3cDot11nRadioCfg2AMpduEnableCM        INTEGER,
        hh3cDot11nRadioCfg2ChannelBandCM        INTEGER,
        hh3cDot11nRadioCfg2ShortGiEnableCM      INTEGER,
        hh3cDot11nRadioCfg2ClientDot11acOnly   TruthValue,
        hh3cDot11nRadioCfg2ClientDot11nOnlyCM   Hh3cDot11TruthValueCM,
        hh3cDot11nRadioCfg2SupportMaxMcs       Integer32,
        hh3cDot11nRadioCfg2MandatoryMaxMcs     Integer32
    }

hh3cDot11nRadioCfg2APIDIndex OBJECT-TYPE
    SYNTAX Hh3cDot11ObjectIDType
    MAX-ACCESS not-accessible
    STATUS current
    DESCRIPTION
        "Represents index of the AP."
    ::= { hh3cDot11nRadioCfg2Entry 1 }

hh3cDot11nRadioCfg2RadioIDIndex OBJECT-TYPE
    SYNTAX Hh3cDot11RadioScopeType
    MAX-ACCESS not-accessible
    STATUS current
    DESCRIPTION
        "Represents index of the radio."
    ::= { hh3cDot11nRadioCfg2Entry 2 }

hh3cDot11nRadioCfg2AMpduEnable OBJECT-TYPE
    SYNTAX TruthValue
    MAX-ACCESS read-write
    STATUS current
    DESCRIPTION
        "Enable the function of A-MPDU."
        DEFVAL { true }
    ::= { hh3cDot11nRadioCfg2Entry 3 }

hh3cDot11nRadioCfg2AMsduEnable OBJECT-TYPE
    SYNTAX TruthValue
    MAX-ACCESS read-write
    STATUS current
    DESCRIPTION
        "Enable the function of A-MSDU."
    DEFVAL { true }
    ::= { hh3cDot11nRadioCfg2Entry 4 }

hh3cDot11nRadioCfg2ClientDot11nOnly OBJECT-TYPE
    SYNTAX TruthValue
    MAX-ACCESS read-write
    STATUS current
    DESCRIPTION
        "If radio type is 802.11an or 802.11gn, only permit clients of 11n mode.
         If radio type is 802.11ac, permit clients of 11n and 11ac mode."
    DEFVAL { false }
    ::= { hh3cDot11nRadioCfg2Entry 5 }

hh3cDot11nRadioCfg2ChannelBand OBJECT-TYPE
    SYNTAX INTEGER
        {
            mode20(1),
            mode40(2),
            mode80(3),
            mode160(4),
            mode80and80(5)
        }
    MAX-ACCESS read-write
    STATUS current
    DESCRIPTION
        "Specify the bandwidth mode."
    ::= { hh3cDot11nRadioCfg2Entry 6 }

hh3cDot11nRadioCfg2ShortGiEnable OBJECT-TYPE
    SYNTAX TruthValue
    MAX-ACCESS read-write
    STATUS current
    DESCRIPTION
        "Enable the function of Short GI."
    DEFVAL { true }
    ::= { hh3cDot11nRadioCfg2Entry 7 }

hh3cDot11nRadioCfg2AMpduEnableCM OBJECT-TYPE
    SYNTAX   INTEGER
        {
            off(0),
            on(1)
        }
    MAX-ACCESS read-write
    STATUS current
    DESCRIPTION
        "Enable the function of A-MPDU."
        DEFVAL { on }
    ::= { hh3cDot11nRadioCfg2Entry 8 }

hh3cDot11nRadioCfg2ChannelBandCM OBJECT-TYPE
    SYNTAX      INTEGER
        {
            mode40(1),
            mode20(2),
            mode80(3),
            mode160(4),
            mode80and80(5)
        }
    MAX-ACCESS read-write
    STATUS current
    DESCRIPTION
        "Specify the bandwidth mode."
    ::= { hh3cDot11nRadioCfg2Entry 9 }

hh3cDot11nRadioCfg2ShortGiEnableCM OBJECT-TYPE
    SYNTAX    INTEGER
        {
            off(0),
            on(1)
        }
    MAX-ACCESS read-write
    STATUS current
    DESCRIPTION
        "Enable the function of Short GI."
    DEFVAL { on }
    ::= { hh3cDot11nRadioCfg2Entry 10 }

hh3cDot11nRadioCfg2ClientDot11acOnly OBJECT-TYPE
    SYNTAX TruthValue
    MAX-ACCESS read-write
    STATUS current
    DESCRIPTION
        "Only permit clients of 11ac mode."
    DEFVAL { false }
    ::= { hh3cDot11nRadioCfg2Entry 11 }

hh3cDot11nRadioCfg2ClientDot11nOnlyCM OBJECT-TYPE
    SYNTAX Hh3cDot11TruthValueCM
    MAX-ACCESS read-write
    STATUS current
    DESCRIPTION
        "If radio type is 802.11an or 802.11gn, permit only clients of 11n mode.
        If radio type is 802.11ac, permit clients of both 11n and 11ac mode."
    DEFVAL { dot11false }
    ::= { hh3cDot11nRadioCfg2Entry 12 }

hh3cDot11nRadioCfg2SupportMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { hh3cDot11nRadioCfg2Entry 13 }

hh3cDot11nRadioCfg2MandatoryMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { hh3cDot11nRadioCfg2Entry 14 }

-- *****************************************************************************
-- *  End of hh3cDot11nRadioCfg2Table Definition
-- *****************************************************************************

-- *****************************************************************************
-- *  hh3cDot11CfgNotifyGroup Definition
-- *****************************************************************************
hh3cDot11CfgNotifications OBJECT IDENTIFIER ::= { hh3cDot11CfgNotifyGroup 0 }

hh3cDot11CfgCipherChange NOTIFICATION-TYPE
    OBJECTS
    {
        hh3cDot11SSIDName,
        hh3cDot11SecurityCiphers
    }
    STATUS      current
    DESCRIPTION
        "This notification is sent when cipher type of corresponding service
        template is changed."
    ::= { hh3cDot11CfgNotifications 1 }

hh3cDot11CfgPSKChange NOTIFICATION-TYPE
    OBJECTS
    {
        hh3cDot11SSIDName
    }
    STATUS      current
    DESCRIPTION
        "This notification is sent when pre-shared key of corresponding
        service template is changed."
    ::= { hh3cDot11CfgNotifications 2 }

hh3cDot11SSIDWepIDConflictTrap NOTIFICATION-TYPE
    OBJECTS
    {
        hh3cDot11PreConflictTemplateNum,
        hh3cDot11CurrConflictTemplateNum,
        hh3cDot11ConflictCipherIdx,
        hh3cDot11ConfigureAPID,
        hh3cDot11ConfigureRadioID,
        hh3cDot11ConfigureAPMacAddress,
        hh3cDot11PreConflictTemplateSSID,
        hh3cDot11CurrConflictTemplateSSID
    }
    STATUS      current
    DESCRIPTION
        "This notification will be sent when the same wep ID is configured
         on two service policies."
    ::= { hh3cDot11CfgNotifications 3 }

-- CFG Notification variable object

hh3cDot11CfgTrapVarObjects OBJECT IDENTIFIER
    ::= { hh3cDot11CfgNotifyGroup 1 }

hh3cDot11PreConflictTemplateNum OBJECT-TYPE
    SYNTAX      Integer32 (1..1024)
    MAX-ACCESS  accessible-for-notify
    STATUS      current
    DESCRIPTION
        "Represents previous service policy ID when radio bind service policy
         and current service policy conflict with previous service policy
         in cipher configuration."
    ::= { hh3cDot11CfgTrapVarObjects 1 }

hh3cDot11CurrConflictTemplateNum OBJECT-TYPE
    SYNTAX      Integer32 (1..1024)
    MAX-ACCESS  accessible-for-notify
    STATUS      current
    DESCRIPTION
        "Represents current service policy ID when radio bind service policy
         and current service policy conflict with previous service policy
         in cipher configuration."
    ::= { hh3cDot11CfgTrapVarObjects 2 }

hh3cDot11ConflictCipherIdx OBJECT-TYPE
    SYNTAX      Integer32 (1..4)
    MAX-ACCESS  accessible-for-notify
    STATUS      current
    DESCRIPTION
        "Represents wep ID that conflicted with."
    ::= { hh3cDot11CfgTrapVarObjects 3 }

hh3cDot11ConfigureAPID OBJECT-TYPE
    SYNTAX      Hh3cDot11ObjectIDType
    MAX-ACCESS  accessible-for-notify
    STATUS      current
    DESCRIPTION
        "Represents which AP is configured."
    ::= { hh3cDot11CfgTrapVarObjects 4 }

hh3cDot11ConfigureRadioID OBJECT-TYPE
    SYNTAX      Hh3cDot11RadioScopeType
    MAX-ACCESS  accessible-for-notify
    STATUS      current
    DESCRIPTION
        "Represents which radio in AP is configured."
    ::= { hh3cDot11CfgTrapVarObjects 5 }

hh3cDot11ConfigureAPMacAddress OBJECT-TYPE
    SYNTAX      MacAddress
    MAX-ACCESS  accessible-for-notify
    STATUS      current
    DESCRIPTION
        "Represents MAC Address of AP."
    ::= { hh3cDot11CfgTrapVarObjects 6 }

hh3cDot11PreConflictTemplateSSID OBJECT-TYPE
    SYNTAX      Hh3cDot11SSIDStringType
    MAX-ACCESS  accessible-for-notify
    STATUS      current
    DESCRIPTION
        "Represents the previous SSID of the AP."
    ::= { hh3cDot11CfgTrapVarObjects 7 }

hh3cDot11CurrConflictTemplateSSID OBJECT-TYPE
    SYNTAX      Hh3cDot11SSIDStringType
    MAX-ACCESS  accessible-for-notify
    STATUS      current
    DESCRIPTION
        "Represents the current SSID of the AP."
    ::= { hh3cDot11CfgTrapVarObjects 8 }

-- *****************************************************************************
-- *  End of hh3cDot11CfgNotifyGroup Definition
-- *****************************************************************************

-- *****************************************************************************
-- *  hh3cDot11LocalACTemplateTable Definition
-- *****************************************************************************
hh3cDot11LocalACTemplateTable OBJECT-TYPE
    SYNTAX      SEQUENCE OF Hh3cDot11LocalACTemplateEntry
    MAX-ACCESS  not-accessible
    STATUS      current
    DESCRIPTION
        "By local AC template CLI, administrator will configure the parameters of LocalAC
        by convenience.
        Before local AC boot up and connect to AC by CAPWAP tunnel, administrator
        will create local AC template for each local AC. When local AC connect to AC,
        AC will assign configuration to local AC by hh3cDot11LocalACSerialID
        information in local AC template."
    ::= { hh3cDot11LocalACConfigGroup 1 }

hh3cDot11LocalACTemplateEntry OBJECT-TYPE
    SYNTAX      Hh3cDot11LocalACTemplateEntry
    MAX-ACCESS  not-accessible
    STATUS      current
    DESCRIPTION
        "Each entry contains configuration information for each LocalAC."
    INDEX
        {
            hh3cDot11LocalACTemplateName
        }
    ::= { hh3cDot11LocalACTemplateTable 1 }

Hh3cDot11LocalACTemplateEntry ::= SEQUENCE
    {
        hh3cDot11LocalACTemplateName             OCTET STRING,
        hh3cDot11LocalACName                     OCTET STRING,
        hh3cDot11LocalACSerialID                 OCTET STRING,
        hh3cDot11TemLocalACModelAlias            OCTET STRING,
        hh3cDot11LocalACTempRowStatus            RowStatus,
        hh3cDot11LocalACStatus                   INTEGER,
        hh3cDot11LocalACIPAddress                IpAddress,
        hh3cDot11LocalACIPv6Address              OCTET STRING,
        hh3cDot11EchoInterval                    Integer32,
        hh3cDot11RetransInterval                 Integer32,
        hh3cDot11RetransCount                    Integer32,
        hh3cDot11FirmwareUpgrade                 INTEGER
    }

hh3cDot11LocalACTemplateName OBJECT-TYPE
    SYNTAX      OCTET STRING(SIZE(0..127))
    MAX-ACCESS  not-accessible
    STATUS      current
    DESCRIPTION
        "Represents the name of LocalAC template."
    ::= { hh3cDot11LocalACTemplateEntry 1 }

hh3cDot11LocalACName OBJECT-TYPE
    SYNTAX      OCTET STRING
    MAX-ACCESS  read-create
    STATUS      current
    DESCRIPTION
        "Represents the LocalAC name."
    ::= { hh3cDot11LocalACTemplateEntry 2 }

hh3cDot11LocalACSerialID OBJECT-TYPE
    SYNTAX      OCTET STRING
    MAX-ACCESS  read-create
    STATUS      current
    DESCRIPTION
        "Represents LocalAC serial id."
    ::= { hh3cDot11LocalACTemplateEntry 3 }

hh3cDot11TemLocalACModelAlias OBJECT-TYPE
    SYNTAX      OCTET STRING
    MAX-ACCESS  read-create
    STATUS      current
    DESCRIPTION
        "Represents the alias of LocalAC model name."
    ::= { hh3cDot11LocalACTemplateEntry 4 }

hh3cDot11LocalACTempRowStatus OBJECT-TYPE
    SYNTAX      RowStatus
    MAX-ACCESS  read-create
    STATUS      current
    DESCRIPTION
        "The status of this table entry."
    ::= { hh3cDot11LocalACTemplateEntry 5 }

hh3cDot11LocalACStatus OBJECT-TYPE
    SYNTAX      INTEGER
        {
            join(1),
            joinConfirm(2),
            download(3),
            config(4),
            run(5),
            idle(6)
        }
    MAX-ACCESS  read-only
    STATUS      current
    DESCRIPTION
        "Represents the capwap status of local AC.
        The following values are supported:
        join         - local AC is joining to cnetral AC.
        joinConfirm  - cnetral AC confirm whether permit local AC to
        - join.
        download     - local AC is downloading software from cnetral
        - AC.
        config       - local AC and cnetral AC exchange configuration
        - before local AC provide WLAN service.
        run          - The local AC is run.
        idle         - The local AC is idle."
    ::= { hh3cDot11LocalACTemplateEntry 6 }

hh3cDot11LocalACIPAddress OBJECT-TYPE
    SYNTAX      IpAddress
    MAX-ACCESS  read-only
    STATUS      current
    DESCRIPTION
        "Represents the IP address of an LocalAC."
    ::= { hh3cDot11LocalACTemplateEntry 7 }

hh3cDot11LocalACIPv6Address OBJECT-TYPE
    SYNTAX      OCTET STRING
    MAX-ACCESS  read-only
    STATUS      current
    DESCRIPTION
        "Represents the IPv6 address of LocalAC."
    ::= { hh3cDot11LocalACTemplateEntry 8 }

hh3cDot11EchoInterval OBJECT-TYPE
    SYNTAX      Integer32(0 | 5..255)
    UNITS       "second"
    MAX-ACCESS  read-create
    STATUS      current
    DESCRIPTION
        "Represents the interval of echo."
    DEFVAL      { 10 }
    ::= { hh3cDot11LocalACTemplateEntry 9 }

hh3cDot11RetransInterval OBJECT-TYPE
    SYNTAX      Integer32(3..8)
    UNITS       "second"
    MAX-ACCESS  read-create
    STATUS      current
    DESCRIPTION
        "Represents the interval of retransmit."
    DEFVAL      { 5 }
    ::= { hh3cDot11LocalACTemplateEntry 10 }

hh3cDot11RetransCount OBJECT-TYPE
    SYNTAX      Integer32(2..5)
    UNITS       "second"
    MAX-ACCESS  read-create
    STATUS      current
    DESCRIPTION
        "Represents the maximum of retransmit."
    DEFVAL      { 3 }
    ::= { hh3cDot11LocalACTemplateEntry 11 }

hh3cDot11FirmwareUpgrade OBJECT-TYPE
    SYNTAX      INTEGER
        {
            enable(1),
            disable(2)
        }
    MAX-ACCESS  read-create
    STATUS      current
    DESCRIPTION
        "Represents the status of firmware upgrade for an local AC.
        The following values are supported:
        enable      - local AC firmware upgrade will be enabled.
        disable     - local AC firmware upgrade will be disabled."
        DEFVAL      { enable }
    ::= { hh3cDot11LocalACTemplateEntry 12 }

-- *****************************************************************************
-- *  End of  hh3cDot11LocalACTemplateTable Definition
-- *****************************************************************************

-- *****************************************************************************
-- *  hh3cDot11RemoteCfgApTable Definition
-- *****************************************************************************
hh3cDot11RemoteCfgApTable OBJECT-TYPE
    SYNTAX      SEQUENCE OF Hh3cDot11RemoteCfgApEntry
    MAX-ACCESS  not-accessible
    STATUS      current
    DESCRIPTION
        "Remote configuration for an AP."
    ::= { hh3cDot11RemoteConfigGroup  1 }

hh3cDot11RemoteCfgApEntry OBJECT-TYPE
    SYNTAX      Hh3cDot11RemoteCfgApEntry
    MAX-ACCESS  not-accessible
    STATUS      current
    DESCRIPTION
        "Each entry contains configuration information for each AP."
    INDEX
        {
            hh3cDot11RmtApName
        }
    ::= { hh3cDot11RemoteCfgApTable 1 }

Hh3cDot11RemoteCfgApEntry ::= SEQUENCE
    {
        hh3cDot11RmtApName                 OCTET STRING,
        hh3cDot11RmtVlanList               OCTET STRING,
        hh3cDot11RmtCfgEnable              TruthValue
    }

hh3cDot11RmtApName OBJECT-TYPE
    SYNTAX      OCTET STRING(SIZE(1..127))
    MAX-ACCESS  not-accessible
    STATUS      current
    DESCRIPTION
        "Represents the name of an AP."
    ::= { hh3cDot11RemoteCfgApEntry 1 }

hh3cDot11RmtVlanList OBJECT-TYPE
    SYNTAX      OCTET STRING
    MAX-ACCESS  read-write
    STATUS      current
    DESCRIPTION
        "Represents the VLAN list on an AP."
    ::= { hh3cDot11RemoteCfgApEntry 2 }

hh3cDot11RmtCfgEnable OBJECT-TYPE
    SYNTAX TruthValue
    MAX-ACCESS read-write
    STATUS current
    DESCRIPTION
        "Enables remote configuration synchronization."
    DEFVAL { false }
    ::= { hh3cDot11RemoteCfgApEntry 3 }
-- *****************************************************************************
-- *  End of  hh3cDot11RemoteCfgApTable Definition
-- *****************************************************************************

-- *****************************************************************************
-- *  hh3cDot11RemoteCfgIFTable Definition
-- *****************************************************************************
hh3cDot11RemoteCfgIFTable OBJECT-TYPE
    SYNTAX      SEQUENCE OF Hh3cDot11RemoteCfgIFEntry
    MAX-ACCESS  not-accessible
    STATUS      current
    DESCRIPTION
        "Remote configuration for interface on an AP."
    ::= { hh3cDot11RemoteConfigGroup  2 }

hh3cDot11RemoteCfgIFEntry OBJECT-TYPE
    SYNTAX      Hh3cDot11RemoteCfgIFEntry
    MAX-ACCESS  not-accessible
    STATUS      current
    DESCRIPTION
        "Each entry contains configuration information for each interface on an AP."
    INDEX
        {
            hh3cDot11RmtIfApName,
            hh3cDot11RmtIfType,
            hh3cDot11RmtIfNum
        }
    ::= { hh3cDot11RemoteCfgIFTable 1 }

Hh3cDot11RemoteCfgIFEntry ::= SEQUENCE
    {
        hh3cDot11RmtIfApName                OCTET STRING,
        hh3cDot11RmtIfType                  Integer32,
        hh3cDot11RmtIfNum                   Integer32,
        hh3cDot11RmtIfName                  OCTET STRING,
        hh3cDot11RmtIfLinkType              INTEGER,
        hh3cDot11RmtIfAccessVlan            Integer32,
        hh3cDot11RmtIfTrunkPvidVlan         Integer32,
        hh3cDot11RmtIfTrunkVlanlist         OCTET STRING,
        hh3cDot11RmtIfHybridPvidVlan        Integer32,
        hh3cDot11RmtIfHybVlanListTag        OCTET STRING,
        hh3cDot11RmtIfHybVlanListUnTag      OCTET STRING,
        hh3cDot11RmtIfIsolate               TruthValue,
        hh3cDot11RmtIfLinkAggGroupId        Integer32,
        hh3cDot11RmtIfManagement            TruthValue
    }

hh3cDot11RmtIfApName OBJECT-TYPE
    SYNTAX      OCTET STRING(SIZE(1..127))
    MAX-ACCESS  not-accessible
    STATUS      current
    DESCRIPTION
        "Represents the name of an AP."
    ::= { hh3cDot11RemoteCfgIFEntry 1 }

hh3cDot11RmtIfType OBJECT-TYPE
    SYNTAX      Integer32
    MAX-ACCESS  not-accessible
    STATUS      current
    DESCRIPTION
        "Represents the type of the interface.
         ethernet (1),
         gigabitethernet (2),
         ten-gigabitethernet (3),
         smartrate-ethernet(4)."
    ::= { hh3cDot11RemoteCfgIFEntry 2 }

hh3cDot11RmtIfNum OBJECT-TYPE
    SYNTAX      Integer32
    MAX-ACCESS  not-accessible
    STATUS      current
    DESCRIPTION
        "Represents the ID of the interface."
    ::= { hh3cDot11RemoteCfgIFEntry 3 }

hh3cDot11RmtIfName OBJECT-TYPE
    SYNTAX      OCTET STRING
    MAX-ACCESS  read-only
    STATUS      current
    DESCRIPTION
        "Represents the name of the interface."
    ::= { hh3cDot11RemoteCfgIFEntry 4 }

hh3cDot11RmtIfLinkType OBJECT-TYPE
    SYNTAX      INTEGER
        {
            access (1),
            trunk (2),
            hybrid (3)
        }
    MAX-ACCESS  read-write
    STATUS      current
    DESCRIPTION
        "Set the link type to access, hybrid or trunk.
         Setting recommend one and setup more related nodes."
    ::= { hh3cDot11RemoteCfgIFEntry 5 }

hh3cDot11RmtIfAccessVlan OBJECT-TYPE
    SYNTAX      Integer32
    MAX-ACCESS  read-write
    STATUS      current
    DESCRIPTION
        "Specify the access VLAN for a port."
    ::= { hh3cDot11RemoteCfgIFEntry 6 }

hh3cDot11RmtIfTrunkPvidVlan OBJECT-TYPE
    SYNTAX      Integer32
    MAX-ACCESS  read-write
    STATUS      current
    DESCRIPTION
        "Specify the default VLAN for a port."
    ::= { hh3cDot11RemoteCfgIFEntry 7 }

hh3cDot11RmtIfTrunkVlanlist OBJECT-TYPE
    SYNTAX      OCTET STRING
    MAX-ACCESS  read-write
    STATUS      current
    DESCRIPTION
        "Specify the permitted VLAN list for a port."
    ::= { hh3cDot11RemoteCfgIFEntry 8 }

hh3cDot11RmtIfHybridPvidVlan OBJECT-TYPE
    SYNTAX      Integer32
    MAX-ACCESS  read-write
    STATUS      current
    DESCRIPTION
        "Specify the default VLAN for the hybrid port."
    ::= { hh3cDot11RemoteCfgIFEntry 9 }

hh3cDot11RmtIfHybVlanListTag OBJECT-TYPE
    SYNTAX      OCTET STRING
    MAX-ACCESS  read-write
    STATUS      current
    DESCRIPTION
        "Assign the hybrid port to tagged VLANs."
    ::= { hh3cDot11RemoteCfgIFEntry 10 }

hh3cDot11RmtIfHybVlanListUnTag OBJECT-TYPE
    SYNTAX      OCTET STRING
    MAX-ACCESS  read-write
    STATUS      current
    DESCRIPTION
        "Assign the hybrid port to untagged VLANs."
    ::= { hh3cDot11RemoteCfgIFEntry 11 }

hh3cDot11RmtIfIsolate OBJECT-TYPE
    SYNTAX TruthValue
    MAX-ACCESS read-write
    STATUS current
    DESCRIPTION
        "Enable or disable port isolation."
    DEFVAL { true }
    ::= { hh3cDot11RemoteCfgIFEntry 12 }

hh3cDot11RmtIfLinkAggGroupId OBJECT-TYPE
    SYNTAX      Integer32
    MAX-ACCESS  read-write
    STATUS      current
    DESCRIPTION
        "Specify link aggregation group number for the port."
    ::= { hh3cDot11RemoteCfgIFEntry 13 }

hh3cDot11RmtIfManagement OBJECT-TYPE
    SYNTAX      TruthValue
    MAX-ACCESS  read-write
    STATUS      current
    DESCRIPTION
        "Interface management of the port."
    DEFVAL { true }
    ::= { hh3cDot11RemoteCfgIFEntry 14 }
-- *****************************************************************************
-- *  End of  hh3cDot11RemoteCfgIFTable Definition
-- *****************************************************************************

END
