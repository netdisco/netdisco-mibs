-- =========================================================================
-- Copyright (c) 2004-2022 New H3C Tech. Co., Ltd.  All rights reserved.
--
-- Description: The MIB file is used for management of
--              IP-SGT(IP address-Security Group Tag) information.
-- Reference:
-- Version: 1.0
-- History:
-- V1.0 Initial version, created by lizhaocheng.
-- ==========================================================================
HH3C-IPSGT-MIB DEFINITIONS ::= BEGIN

IMPORTS
    hh3cCommon
        FROM HH3C-OID-MIB
    Integer32, OBJECT-TYPE, MODULE-IDENTITY, NOTIFICATION-TYPE
        FROM SNMPv2-SMI
    TEXTUAL-CONVENTION
        FROM SNMPv2-TC;

hh3cIpsgt MODULE-IDENTITY
    LAST-UPDATED "202208021020Z"        --Aug 02, 2022 at 00:00 GMT
    ORGANIZATION
        "New H3C Technologies Co., Ltd."
    CONTACT-INFO
        "Platform Team New H3C Technologies Co., Ltd.
        Hai-Dian District Beijing P.R. China
        http://www.h3c.com
        Zip:100085
        "
    DESCRIPTION
        "This MIB contains objects to manage configuration and
         monitor running state for IP-SGT feature.

            *********************************
                    MIB Tables
            **********************************
         This MIB consists of the following tables:
            1 :  hh3cIpsgtNotifications
            2 :  hh3cIpsgtObjects
        "
    REVISION "202208021020Z"        --Aug 02, 2022 at 00:00 GMT
    DESCRIPTION
        "Initial revision.
         Add hh3cIpsgtNotifications.
         Add hh3cIpsgtObjects."
    ::= { hh3cCommon 247 }

--
-- Top level structure
--

hh3cIpsgtNotifications  OBJECT IDENTIFIER ::= { hh3cIpsgt 0 }
hh3cIpsgtObjects        OBJECT IDENTIFIER ::= { hh3cIpsgt 1 }

--
-- type definitions
--

-- IP-SGT cloud server type
Hh3cServerType ::= TEXTUAL-CONVENTION
    STATUS  current
    DESCRIPTION
        "The type of IP-SGT cloud server."
    SYNTAX INTEGER
    {
        unknown(1),
        master(2),
        backup(3)
    }

--
-- Notification Objects
--
hh3cIpsgtNotifyVarObjects OBJECT IDENTIFIER ::= { hh3cIpsgtObjects 1 }

hh3cIpsgtNotifyDomain OBJECT-TYPE
    SYNTAX OCTET STRING (SIZE (1..255))
    MAX-ACCESS accessible-for-notify
    STATUS current
    DESCRIPTION
        "The domain of IP-SGT cloud server."
    ::= { hh3cIpsgtNotifyVarObjects 1 }

hh3cIpsgtNotifyPort OBJECT-TYPE
    SYNTAX Integer32   (0..65534)
    MAX-ACCESS accessible-for-notify
    STATUS current
    DESCRIPTION
        "The L4 protocol port of IP-SGT cloud server."
    ::= { hh3cIpsgtNotifyVarObjects 2 }

hh3cIpsgtNotifyServerType OBJECT-TYPE
    SYNTAX Hh3cServerType
    MAX-ACCESS accessible-for-notify
    STATUS current
    DESCRIPTION
        "The type of IP-SGT cloud server."
    ::= { hh3cIpsgtNotifyVarObjects 3 }

--
-- IP-SGT notifications
--
hh3cIpsgtCloudConnectionUp NOTIFICATION-TYPE
    OBJECTS
    {
        hh3cIpsgtNotifyDomain,
        hh3cIpsgtNotifyPort,
        hh3cIpsgtNotifyServerType
    }
    STATUS current
    DESCRIPTION
        "Generated when the channel to IP-SGT cloud server is connected."
    ::= { hh3cIpsgtNotifications 1 }

hh3cIpsgtCloudConnectionDown NOTIFICATION-TYPE
    OBJECTS
    {
        hh3cIpsgtNotifyDomain,
        hh3cIpsgtNotifyPort,
        hh3cIpsgtNotifyServerType
    }
    STATUS current
    DESCRIPTION
        "Generated when a the channel to IP-SGT cloud server is disconnected."
    ::= { hh3cIpsgtNotifications 2 }

END
