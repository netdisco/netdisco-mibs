-- =================================================================
-- Copyright (c) 2004-2022 New H3C Tech. Co., Ltd. All rights reserved.
--
-- Description: Ethernet Ring Protection Switching (ERPS) MIB
-- Reference: IF-MIB
-- Version: V1.0
-- History:
--   V1.0 created by zhengjun
--     Initial version 2022-05-11
-- =================================================================
-- =================================================================
--
-- Import and definition
--
-- =================================================================
HH3C-ERPS-MIB DEFINITIONS ::= BEGIN

IMPORTS
    hh3cCommon
        FROM HH3C-OID-MIB
    Integer32, OBJECT-TYPE, MODULE-IDENTITY, NOTIFICATION-TYPE
        FROM SNMPv2-SMI
    ifDescr, ifIndex
        FROM IF-MIB;

hh3cErps MODULE-IDENTITY
    LAST-UPDATED
        "202205111153Z"
    ORGANIZATION
        "New H3C Tech. Co., Ltd."
    CONTACT-INFO
        "Platform Team New H3C Tech. Co., Ltd.
        Hai-Dian District Beijing P.R. China
        http://www.h3c.com
        Zip:100085"
    DESCRIPTION
        "This MIB defines objects for managing ERPS.
        ERPS is a feature developed to address the slow convergence
        issue with STP.
        It provides link redundancy and fast convergence in
        a ring network, allowing the backup link to take over quickly
        when the primary link fails."
    REVISION
        "202205111153Z"
    DESCRIPTION
        "Initial revision of the ERPS MIB module."
    ::= { hh3cCommon  225 }

hh3cErpsTrap            OBJECT IDENTIFIER ::= { hh3cErps 1 }
hh3cErpsTrapPrefix      OBJECT IDENTIFIER ::= { hh3cErpsTrap 0 }
hh3cErpsPortStateForwarding NOTIFICATION-TYPE
    OBJECTS
        {
            ifIndex,
            ifDescr,
            hh3cErpsRingID
        }
    STATUS      current
    DESCRIPTION
        "A trap message is generated when the status of a port
        in an ERPS ring changes to forwarding."
    ::= { hh3cErpsTrapPrefix 1 }

hh3cErpsPortStateDiscarding NOTIFICATION-TYPE
    OBJECTS
        {
            ifIndex,
            ifDescr,
            hh3cErpsRingID
        }
    STATUS      current
    DESCRIPTION
        "A trap message is generated when the status of a port
        in an ERPS ring changes to discarding."
    ::= { hh3cErpsTrapPrefix 2 }

hh3cErpsTrapObjects OBJECT IDENTIFIER ::= { hh3cErpsTrap 1 }

hh3cErpsRingID OBJECT-TYPE
    SYNTAX Integer32 (1..255)
    MAX-ACCESS   accessible-for-notify
    STATUS       current
    DESCRIPTION
        "ERPS ring ID."
    ::= { hh3cErpsTrapObjects 1 }

END
