-- =============================================================================
-- Copyright (c) 2004-2022 New H3C Tech.  Co.  , Ltd.  All rights reserved.
--
-- Description: Multiprotocol Label Switching Resource Reservation Protocol MIB
-- Reference:
-- Version: V1.0
-- History:
--   V1.0 2022-06-01 Initial version Created by zhouwan
-- =============================================================================
HH3C-MPLSRSVP-MIB DEFINITIONS ::= BEGIN
IMPORTS
    MODULE-IDENTITY, OBJECT-TYPE, NOTIFICATION-TYPE
        FROM SNMPv2-SMI
    hh3cCommon
        FROM HH3C-OID-MIB
    ;

-- =============================================================================
-- module identity part
-- =============================================================================
hh3cMplsRsvp MODULE-IDENTITY
    LAST-UPDATED
        "202206011900Z"   -- June 01, 2022 at 19:00 GMT
    ORGANIZATION
        "New H3C Technologies Co., Ltd."
    CONTACT-INFO
        "Platform Team New H3C Technologies Co., Ltd.
         Hai-Dian District Beijing P.R.  China
         http://www.h3c.com
         Zip:100085"
    DESCRIPTION
        "Multiprotocol Label Switching Resource Reservation Protocol MIB"
    REVISION
        "202206011900Z"   -- June 01, 2022 at 19:00 GMT
    DESCRIPTION
        "Initial version of this MIB."
    ::= { hh3cCommon 229 }

-- =============================================================================
-- Top level components of this MIB module
-- =============================================================================
hh3cMplsRsvpNotifications OBJECT IDENTIFIER ::= { hh3cMplsRsvp 0 }

hh3cMplsRsvpObjects       OBJECT IDENTIFIER ::= { hh3cMplsRsvp 1 }

hh3cMplsRsvpScalarGroup   OBJECT IDENTIFIER ::= { hh3cMplsRsvpObjects 1 }

hh3cMplsRsvpNbrAddr    OBJECT-TYPE
    SYNTAX      OCTET STRING (SIZE (1..127))
    MAX-ACCESS  accessible-for-notify
    STATUS      current
    DESCRIPTION
        "The RSVP(Resource Reservation Protocol) Neighbor Address."
    ::= { hh3cMplsRsvpScalarGroup 1 }

hh3cMplsRsvpFrrMainInfo    OBJECT-TYPE
    SYNTAX      OCTET STRING (SIZE (1..127))
    MAX-ACCESS  accessible-for-notify
    STATUS      current
    DESCRIPTION
        "The Main Tunnel information of RSVP(Resource Reservation Protocol)
         Fast Reroute."
    ::= { hh3cMplsRsvpScalarGroup 2 }

hh3cMplsRsvpFrrByPassInfo    OBJECT-TYPE
    SYNTAX      OCTET STRING (SIZE (1..127))
    MAX-ACCESS  accessible-for-notify
    STATUS      current
    DESCRIPTION
        "The Bypass Tunnel information of RSVP(Resource Reservation Protocol)
         Fast Reroute."
    ::= { hh3cMplsRsvpScalarGroup 3 }

-- =============================================================================
-- Notifications
-- =============================================================================
hh3cMplsRsvpNeighborLost  NOTIFICATION-TYPE
    OBJECTS { hh3cMplsRsvpNbrAddr  }
    STATUS      current
    DESCRIPTION
      "This notification is generated when the RSVP neighbor is lost
      and hello status went from up to init or idle."
    ::= { hh3cMplsRsvpNotifications 1 }

hh3cMplsRsvpNeighborLostRecovery  NOTIFICATION-TYPE
     OBJECTS { hh3cMplsRsvpNbrAddr  }
    STATUS      current
    DESCRIPTION
      "This notification is generated when the RSVP neighbor is recovered
      and hello status went from init to up."
    ::= { hh3cMplsRsvpNotifications 2 }

hh3cMplsRsvpAuthFail  NOTIFICATION-TYPE
    OBJECTS { hh3cMplsRsvpNbrAddr   }
    STATUS      current
    DESCRIPTION
      "This notification is generated when the RSVP neighbor authentication
       is failed."
    ::= { hh3cMplsRsvpNotifications 3 }

hh3cMplsRsvpAuthFailRecovery  NOTIFICATION-TYPE
    OBJECTS { hh3cMplsRsvpNbrAddr   }
    STATUS      current
    DESCRIPTION
      "This notification is generated when the RSVP neighbor authentication
      failure is recovered."
    ::= { hh3cMplsRsvpNotifications 4 }

hh3cMplsRsvpFrrProtAval  NOTIFICATION-TYPE
    OBJECTS {
        hh3cMplsRsvpFrrMainInfo,
        hh3cMplsRsvpFrrByPassInfo
            }
    STATUS      current
    DESCRIPTION
      "This notification is generated when the primary tunnel is bound
      by bypass tunnel."
    ::= { hh3cMplsRsvpNotifications 5 }

hh3cMplsRsvpFrrProtNotAval  NOTIFICATION-TYPE
    OBJECTS {
        hh3cMplsRsvpFrrMainInfo,
        hh3cMplsRsvpFrrByPassInfo
            }
    STATUS      current
    DESCRIPTION
      "This notification is generated when the primary tunnel is unbound
      by bypass tunnel."
    ::= { hh3cMplsRsvpNotifications 6 }

hh3cMplsRsvpFrrSwitch  NOTIFICATION-TYPE
    OBJECTS {
        hh3cMplsRsvpFrrMainInfo,
        hh3cMplsRsvpFrrByPassInfo
            }
    STATUS      current
    DESCRIPTION
      "This notification is generated when tunnel frr is switched."
    ::= { hh3cMplsRsvpNotifications 7 }

hh3cMplsRsvpFrrResume  NOTIFICATION-TYPE
    OBJECTS {
        hh3cMplsRsvpFrrMainInfo,
        hh3cMplsRsvpFrrByPassInfo
            }
    STATUS      current
    DESCRIPTION
      "This notification is generated when tunnel frr is resumed."
    ::= { hh3cMplsRsvpNotifications 8 }

-- =============================================================================
-- End of notifications.
-- =============================================================================

END
