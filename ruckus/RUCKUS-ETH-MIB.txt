--
-- Copyright (c) 2010 by Ruckus Wireless, Inc.
-- All Rights Reserved
--

RUCKUS-ETH-MIB DEFINITIONS ::= BEGIN

IMPORTS
    ruckusCommonEthModule
        FROM RUCKUS-ROOT-MIB
    DisplayString,
    MacAddress,
    RowStatus,
    TruthValue
        FROM SNMPv2-TC
    OBJECT-GROUP
        FROM SNMPv2-CONF
    ifIndex,
    InterfaceIndex
        FROM IF-MIB
    MODULE-IDENTITY,
    OBJECT-TYPE,
    Counter32,
    Integer32,
    Unsigned32
        FROM SNMPv2-SMI;

ruckusEthMIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus Eth mib"
    ::= { ruckusCommonEthModule 1 }


-- Groups
--

ruckusEthObjects OBJECT IDENTIFIER  ::= { ruckusEthMIB 1 }

ruckusEthInfo OBJECT IDENTIFIER     ::= { ruckusEthObjects 1 }

ruckusEthEvents OBJECT IDENTIFIER   ::= { ruckusEthMIB 2 }


-- Ethernet Statistics
--

ruckusEthStatsTable OBJECT-TYPE
    SYNTAX  SEQUENCE OF RuckusEthStatsEntry
    MAX-ACCESS not-accessible
    STATUS current
    DESCRIPTION
        "Eth statistics table"
    ::= { ruckusEthInfo 1 }


ruckusEthStatsEntry OBJECT-TYPE
    SYNTAX  RuckusEthStatsEntry
    MAX-ACCESS not-accessible
    STATUS current
    DESCRIPTION
        "Specifies each Eth statictics entry."
    INDEX {
        ruckusEthIndex }
    ::= { ruckusEthStatsTable 1 }


RuckusEthStatsEntry ::= SEQUENCE {

	ruckusEthIndex					InterfaceIndex,
    ruckusEthName                   DisplayString,
    ruckusEthStatsRxRate            Counter32,
    ruckusEthStatsRxErrorRate       Counter32,
    ruckusEthStatsTxRate            Counter32,
    ruckusEthStatsTxErrorRate       Counter32 }

ruckusEthIndex OBJECT-TYPE
    SYNTAX  InterfaceIndex
    MAX-ACCESS read-only
    STATUS current
    DESCRIPTION
        "The index."
    ::= { ruckusEthStatsEntry 200 }

ruckusEthName OBJECT-TYPE
    SYNTAX  DisplayString
    MAX-ACCESS read-only
    STATUS current
    DESCRIPTION
        "Specifies the name of the eth interface."
    ::= { ruckusEthStatsEntry 1 } 


ruckusEthStatsRxRate OBJECT-TYPE
    SYNTAX  Counter32
    MAX-ACCESS read-only
    STATUS current
    DESCRIPTION
        "Receipt throughput."
    ::= { ruckusEthStatsEntry 2 } 
                    

ruckusEthStatsRxErrorRate  OBJECT-TYPE
    SYNTAX  Counter32
    MAX-ACCESS read-only
    STATUS current
    DESCRIPTION
        "Receipt packet error rate."
    ::= { ruckusEthStatsEntry 3 } 
 
                   
ruckusEthStatsTxRate  OBJECT-TYPE
    SYNTAX  Counter32
    MAX-ACCESS read-only
    STATUS current
    DESCRIPTION
        "Transmit throughput."
    ::= { ruckusEthStatsEntry 4 } 


ruckusEthStatsTxErrorRate  OBJECT-TYPE
    SYNTAX  Counter32
    MAX-ACCESS read-only
    STATUS current
    DESCRIPTION
        "Transmit packet error rate."
    ::= { ruckusEthStatsEntry 5 } 


-- Conformance & Compliance
--
 
END
