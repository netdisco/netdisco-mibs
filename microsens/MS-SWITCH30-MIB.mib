-- ******************************************************************
-- Title:       Microsens private MIB version 3
--              for managed Ethernet Switches
-- Version:     3.2 for SNMP v2c (Notifications) / SMI.2
-- Date :       14.03.2007
-- last change: 23.01.2012
-- Filename:    msswitch30v2.mib
-- ******************************************************************

MS-SWITCH30-MIB DEFINITIONS ::= BEGIN

IMPORTS
	MODULE-IDENTITY,
	enterprises,
	OBJECT-TYPE,
	NOTIFICATION-TYPE,
	Unsigned32,
	Integer32,
	Counter32,
	Counter64,
	IpAddress,
	TimeTicks
		FROM SNMPv2-SMI
	PhysAddress
		FROM RFC1213-MIB

	TEXTUAL-CONVENTION,
	DisplayString
		FROM SNMPv2-TC;


mib3 MODULE-IDENTITY
	LAST-UPDATED "201201230000Z" -- 23 january 2012
	ORGANIZATION "MICROSENS"
	CONTACT-INFO
		"MICROSENS GmbH & Co. KG

		Kueferstrasse 16
		D-59067 Hamm / Germany

		Tel : +49 (0) 23 81 / 94 52 -0
		Fax : +49 (0) 23 81 / 94 52 -100

		E-mail: support@microsens.de"

	DESCRIPTION
		"MIB module for managed Switches"

	REVISION "201201230000Z" -- 23 january 2012
	DESCRIPTION "radiusMacLettercase added
	             UMAC configuration (UDP disable)"

	REVISION "201104110000Z" -- 11 april 2011
	DESCRIPTION "PoE Extended Voltage flag added"

	REVISION "201103030000Z" -- 03 march 2011
	DESCRIPTION "monitor HubMode added
	             SFP warnings and alarms added"

	REVISION "201012180000Z" -- 18 december 2010
	DESCRIPTION "syslog filtering added
	             snmpv3 specific traps/informs added"

	REVISION "201008300000Z" -- 30 august 2010
	DESCRIPTION "port access control values added
	             radius timeout added"

	REVISION "201006240000Z" -- 24 june 2010
	DESCRIPTION "rtc group added"

	REVISION "201005030000Z" -- 03 may 2010
	DESCRIPTION "configuration of user interfaces enhanced"

	REVISION "201001190000Z" -- 19 january 2010
	DESCRIPTION "vlan group modified and enhanced"

	REVISION "200912220000Z" -- 22 december 2009
	DESCRIPTION "Enhanced radius settings"

	REVISION "200911170000Z" -- 17 november 2009
	DESCRIPTION "Special purpose Vlan IDs
	             Storage Media Card Support
	             Inventory string"

	REVISION "200906030000Z" -- 03 june 2009
	DESCRIPTION "Radius Server Settings enhanced"

	REVISION "200904290000Z" -- 29 april 2009
	DESCRIPTION "Spanning Tree Group implemented"

	REVISION "200901120000Z" -- 12 january 2009
	DESCRIPTION "Ring Notifications implemented
	             reduced line length (to avoid HPOV-Bug)"

	REVISION "200809010000Z" -- 01 september 2008
	DESCRIPTION "SNMP multiple version configuration"

	REVISION "200806170000Z" -- 17 june 2008
	DESCRIPTION "The Module-Identity"

	REVISION "200707120000Z"
	DESCRIPTION "Initial Version"

::= { managedSwitches 3 }



microsens            OBJECT IDENTIFIER ::= { enterprises 3181 }
managedSwitches      OBJECT IDENTIFIER ::= { microsens 10 }

-- device group: ====================================================
device OBJECT IDENTIFIER ::= { mib3 1 }

deviceArtNo OBJECT-TYPE
	SYNTAX DisplayString (SIZE (0..20))
	MAX-ACCESS read-only
	STATUS current
	DESCRIPTION
	"This entry describes the article number 
	of the device."
	::= { device 1 }

deviceSerNo OBJECT-TYPE
	SYNTAX DisplayString (SIZE (0..8))
	MAX-ACCESS read-only
	STATUS current
	DESCRIPTION
	"This entry describes the serial number 
	of the device."
	::= { device 2 }

deviceHardware OBJECT-TYPE
	SYNTAX DisplayString (SIZE (0..16))
	MAX-ACCESS read-only
	STATUS current
	DESCRIPTION
	"This entry contains the hardware version
	of the device."
	::= { device 3 }

deviceDescription OBJECT-TYPE
	SYNTAX DisplayString (SIZE (0..30))
	MAX-ACCESS read-only
	STATUS current
	DESCRIPTION
	"This entry contains a description of 
	the device."
	::= { device 4 }

deviceName OBJECT-TYPE
	SYNTAX DisplayString (SIZE (0..25))
	MAX-ACCESS read-write
	STATUS current
	DESCRIPTION
	"This entry contains a description of 
	the device."
	::= { device 5 }

deviceLocation OBJECT-TYPE
	SYNTAX DisplayString (SIZE (0..25))
	MAX-ACCESS read-write
	STATUS current
	DESCRIPTION
	"This entry contains the location of 
	the device."
	::= { device 6 }

deviceContact OBJECT-TYPE
	SYNTAX DisplayString (SIZE (0..25))
	MAX-ACCESS read-write
	STATUS current
	DESCRIPTION
	"This entry contains a contact regarding 
	the device."
	::= { device 7 }

deviceGroup OBJECT-TYPE
	SYNTAX DisplayString (SIZE (0..25))
	MAX-ACCESS read-write
	STATUS current
	DESCRIPTION
	"This entry defines the name of the group 
	the device belongs to."
	::= { device 8 }

deviceTemperature OBJECT-TYPE
	SYNTAX INTEGER
	MAX-ACCESS read-only
	STATUS current
	DESCRIPTION
	"This is the current temperature of the 
	device in degree celsius. A value of
	255 has to be interpreted as 'unsupported'."
	::= { device 9 }

deviceTemperatureLevel OBJECT-TYPE
	SYNTAX INTEGER
	{
	criticalLow    (1),
	low            (2),
	normal         (3),
	high           (4),
	criticalHigh   (5),
	shutdown       (6),
	undefined    (254),
	unsupported  (255)
	}
	MAX-ACCESS read-only
	STATUS current
	DESCRIPTION
	"This is the current temperature level 
	of the device."
	::= { device 10 }

deviceUpTime OBJECT-TYPE
	SYNTAX TimeTicks
	MAX-ACCESS read-only
	STATUS current
	DESCRIPTION
	"Time since the device was last 
	re-initialized (in 0.01s)."
	::= { device 11 }

deviceFddActiveTime OBJECT-TYPE
	SYNTAX TimeTicks
	MAX-ACCESS read-write
	STATUS current
	DESCRIPTION
	"Active Time interval for Fibre-
	Down-Detection Feature (in 0.01s).
	valid range: [10 .. 100000]
	A value of '0' means 'unsupported'"
	::= { device 12 }

deviceFddPassiveTime OBJECT-TYPE
	SYNTAX TimeTicks
	MAX-ACCESS read-write
	STATUS current
	DESCRIPTION
	"Passive Time interval for Fibre-
	Down-Detection Feature (in 0.01s).
	valid range: [10 .. 100000]
	A value of '0' means 'unsupported'"
	::= { device 13 }

deviceInventory OBJECT-TYPE
	SYNTAX DisplayString (SIZE (0..20))
	MAX-ACCESS read-write
	STATUS current
	DESCRIPTION
	"This entry contains an inventory
	string for the device."
	::= { device 14 }


-- agent group: =====================================================
agent OBJECT IDENTIFIER ::= { mib3 2 }

agentFirmware OBJECT-TYPE
	SYNTAX DisplayString (SIZE (0..16))
	MAX-ACCESS read-only
	STATUS current
	DESCRIPTION
	"This entry contains the firmware version
	of the agent."
	::= { agent 1 }

agentMacAddress OBJECT-TYPE
	SYNTAX PhysAddress
	MAX-ACCESS read-only
	STATUS current
	DESCRIPTION
	"This entry contains the mac address of 
	the agent."
	::= { agent 2 }

agentIpv4Mode OBJECT-TYPE
	SYNTAX INTEGER
	{
	static         (1),
	dhcp           (2),
	undefined    (254),
	unsupported  (255)
	}
	MAX-ACCESS read-write
	STATUS current
	DESCRIPTION
	"This entry describes the IPv4-mode
	of the agent."
	::= { agent 3 }

agentIpv4Address OBJECT-TYPE
	SYNTAX IpAddress
	MAX-ACCESS read-write
	STATUS current
	DESCRIPTION
	"This entry contains the IPv4-address of 
	the agent."
	::= { agent 4 }

agentIpv4SubnetMask OBJECT-TYPE
	SYNTAX IpAddress
	MAX-ACCESS read-write
	STATUS current
	DESCRIPTION
	"This entry contains the IPv4 subnet mask
	of the agent."
	::= { agent 5 }

agentIpv4Gateway OBJECT-TYPE
	SYNTAX IpAddress
	MAX-ACCESS read-write
	STATUS current
	DESCRIPTION
	"This entry contains the gateway IPv4 address 
	for the agent."
	::= { agent 6 }

agentConfigReset OBJECT-TYPE
	SYNTAX INTEGER
	{
	normalOperation (0),
	reset           (1)
	}
	MAX-ACCESS read-write
	STATUS current
	DESCRIPTION
	"Set this entry to '1' to reset the device.
	This entry is self clearing."
	::= { agent 7 }

agentConfigFactoryDefault OBJECT-TYPE
	SYNTAX INTEGER
	{
	normalOperation   (0),
	factoryResetTemp  (1),
	factoryResetPerm  (2)
	}
	MAX-ACCESS read-write
	STATUS current
	DESCRIPTION
	"Set this entry to '1' before setting the 
	entry 'agentConfigReset' to '1' sets the 
	device to factory defaults once and the 
	entry is self cleared. Setting this entry 
	to '2' it will remain as set and every 
	standard reset will be a factory reset.
	If 'Permanent Factory Reset' is not 
	supported then the 'Temporary Factory 
	Reset' will be set instead."
	::= { agent 8 }

agentConfigEnableFactoryButton OBJECT-TYPE
	SYNTAX INTEGER
	{
	enabled       (1),
	disabled      (2),
	unsupported (255)
	}
	MAX-ACCESS read-write
	STATUS current
	DESCRIPTION
	"Setting this entry to a '1' enables 
	the hardware button for a factory 
	reset if available."
	::= { agent 9 }

agentSecureAddressFlag OBJECT-TYPE
	SYNTAX INTEGER
	{
	useSecure       (1),
	useNormal       (2),
	unsupported   (255)
	}
	MAX-ACCESS read-only
	STATUS current
	DESCRIPTION
	"This Entry documents the Flag which is
	set from the system if invalid values
	for MAC-address, IP-address or subnet mask
	have been found in the stored configuration.
	In this case hard coded secure values are 
	used instead of those found. This flag
	is cleared if valid valued are found when
	the system comes up."
	::= { agent 10 }

agentStorageMediaCardStatus OBJECT-TYPE
	SYNTAX INTEGER
	{
	noCardInserted        (1),
	invalidCardDetected   (2),
	validCardDetected     (3),
	bootedFromCard        (4),
	bootedFromCardwithMac (5),
	unsupported         (255)
	}
	MAX-ACCESS read-only
	STATUS current
	DESCRIPTION
	"This Entry represents the detected status
	of a storage memory card if supported."
	::= { agent 11 }

agentStorageMediaCardBoot OBJECT-TYPE
	SYNTAX INTEGER
	{
	normalOperation  (0),
	bootSmcTemp      (1),
	bootSmcPerm      (2),
	unsupported    (255)
	}
	MAX-ACCESS read-write
	STATUS current
	DESCRIPTION
	"Set this entry to '1' before setting the 
	entry 'agentConfigReset' to '1' sets the 
	device's config to the values stored on
	the Storage Media Card once if available .
	and the entry is self cleared. 
	Setting this entry to '2' it will remain
	as set and every boot event will use the 
	configuration from the card.
	If not supported a value of 255 will be
	returned."
	::= { agent 12 }

agentStorageMediaCardMac OBJECT-TYPE
	SYNTAX INTEGER
	{
	useMacFromSMC    (1),
	useOriginalMac   (2),
	unsupported    (255)
	}
	MAX-ACCESS read-write
	STATUS current
	DESCRIPTION
	"Set this entry to '1' before setting the 
	entry 'agentConfigReset' to '1' leads to 
	take the MAC address from the SMC. Be very
	careful with this service option to avoid
	duplicated MAC addresses.!"
	::= { agent 13 }

agentStoreConfigToStorageMediaCard OBJECT-TYPE
	SYNTAX INTEGER
	{
	normalOperation (0),
	store           (1),
	unsupported   (255)
	}
	MAX-ACCESS read-write
	STATUS current
	DESCRIPTION
	"Set this entry to '1' to store the 
	present configuration to the storage 
	media card if available.
	This entry is self clearing."
	::= { agent 14 }

agentDhcpConfigRequest OBJECT-TYPE
	SYNTAX INTEGER
	{
	enabled       (1),
	disabled      (2),
	unsupported (255)
	}
	MAX-ACCESS read-write
	STATUS current
	DESCRIPTION
	"Setting this entry to a '1' enables the
	DHCP config request feature if available."
	::= { agent 15 }


-- port group: ======================================================
port OBJECT IDENTIFIER ::= { mib3 3 }

portCount OBJECT-TYPE
	SYNTAX INTEGER
	MAX-ACCESS read-only
	STATUS current
	DESCRIPTION
	"The number of ports resent on this system."
	::= { port 1 }

-- port status table: =====================================
portStatusTable OBJECT-TYPE
	SYNTAX SEQUENCE OF PortStatusList
	MAX-ACCESS not-accessible
	STATUS current
	DESCRIPTION
	"This table contains port status information 
	of the device."
	::= { port 10 }

portStatusTableEntry OBJECT-TYPE
	SYNTAX PortStatusList
	MAX-ACCESS not-accessible
	STATUS current
	DESCRIPTION
	"Entry in the port status table."
	INDEX 
	{ portStatusId } ::= { portStatusTable 1 }

PortStatusList ::= SEQUENCE {
	portStatusId               INTEGER,
	portStatusType             INTEGER,
	portStatusLink             INTEGER,
	portStatusSpeed            INTEGER,
	portStatusDuplex           INTEGER,
	portStatusFlowControl      INTEGER,
	portStatusPinout           INTEGER,
	portStatusFarEndFault      INTEGER,
	portStatusRxNetload        INTEGER,
	portStatusTxNetload        INTEGER
}

portStatusId OBJECT-TYPE
	SYNTAX INTEGER (1..24)
	MAX-ACCESS read-only
	STATUS current
	DESCRIPTION
	"This entry describes the port id."
	::= { portStatusTableEntry 1 }

portStatusType OBJECT-TYPE
	SYNTAX  INTEGER
	{
	port-tx10-100           (1), -- TP port, FEth
	port-t10-100-1000       (2), -- TP port, GBE
	port-fx100              (3), -- FO port, FEth
	port-fx100-1000-sfp     (4), -- SFP port
	port-x1000              (5), -- FO port, GBE
	port-tx10-100-1000-sfp  (6), -- dual media: TP + SFP
	port-tx10-100-1000-1x9  (7), -- dual media: TP + 1X9
	undefined             (254)
	}
	MAX-ACCESS read-only
	STATUS current
	DESCRIPTION
	"This entry describes the type of the port."
	::= { portStatusTableEntry 2 }

portStatusLink OBJECT-TYPE
	SYNTAX INTEGER
	{
	up             (1),
	down           (2),
	undefined    (254)
	}
	MAX-ACCESS read-only
	STATUS current
	DESCRIPTION
	"This entry describes the link status of 
	the port."
	::= { portStatusTableEntry 3 }

portStatusSpeed OBJECT-TYPE
	SYNTAX INTEGER
	{
	speed10        (1),
	speed100       (2),
	speed1000      (3),
	undefined    (254)
	}
	MAX-ACCESS read-only
	STATUS current
	DESCRIPTION
	"This entry describes the current speed 
	status of the port if available."
	::= { portStatusTableEntry 4 }

portStatusDuplex OBJECT-TYPE
	SYNTAX INTEGER
	{
	halfduplex     (1),
	fullduplex     (2),
	undefined    (254)
	}
	MAX-ACCESS read-only
	STATUS current
	DESCRIPTION
	"This entry describes the current duplex 
	status of the port if available."
	::= { portStatusTableEntry 5 }

portStatusFlowControl OBJECT-TYPE
	SYNTAX INTEGER
	{
	enabled        (1),
	disabled       (2),
	undefined    (254),
	unsupported  (255)
	}
	MAX-ACCESS read-only
	STATUS current
	DESCRIPTION
	"This entry describes the current flow
	control status of the port if available.
	This state referres the current duplex mode."
	::= { portStatusTableEntry 6 }

portStatusPinout OBJECT-TYPE
	SYNTAX INTEGER
	{
	mdi            (1),
	mdix           (2),
	undefined    (254),
	unsupported  (255)
	}
	MAX-ACCESS read-only
	STATUS current
	DESCRIPTION
	"This entry describes the current pinout 
	status of the port if available."
	::= { portStatusTableEntry 7 }

portStatusFarEndFault OBJECT-TYPE
	SYNTAX INTEGER
	{
	detected       (1),
	undetected     (2),
	undefined    (254), 
	unsupported  (255)
	}
	MAX-ACCESS read-only
	STATUS current
	DESCRIPTION
	"This entry describes the current 
	Far End Fault Detection status of 
	the port if available."
	::= { portStatusTableEntry 8 }

portStatusRxNetload OBJECT-TYPE
	SYNTAX INTEGER (-1..100)
	MAX-ACCESS read-only
	STATUS current
	DESCRIPTION
	"This entry describes the receiver netload 
	in percent, adapted to the selected port 
	speed. Netload values greater than '0' but 
	less that '1' are rounded up to a '1' to 
	differentiate them from real zero-values.
	If netload measuring is not supported,
	then a value of '-1' is given back."
	::= { portStatusTableEntry 9 }

portStatusTxNetload OBJECT-TYPE
	SYNTAX INTEGER (-1..100)
	MAX-ACCESS read-only
	STATUS current
	DESCRIPTION
	"This entry describes the transmitter netload 
	in percent, adapted to the selected port 
	speed. Netload values greater than '0' but 
	less that '1' are rounded up to a '1' to 
	differentiate them from real zero-values.
	If netload measuring is not supported,
	then a value of '-1' is given back."
	::= { portStatusTableEntry 10 }

-- port config table: =====================================
portConfigTable OBJECT-TYPE
	SYNTAX SEQUENCE OF PortConfigList
	MAX-ACCESS not-accessible
	STATUS current
	DESCRIPTION
	"This table contains the port configuration 
	of the device."
	::= { port 20 }

portConfigTableEntry OBJECT-TYPE
	SYNTAX PortConfigList
	MAX-ACCESS not-accessible
	STATUS current
	DESCRIPTION
	"Entry in the port configuration table."
	INDEX 
	{ portConfigId } ::= { portConfigTable 1 }

PortConfigList ::= SEQUENCE {
	portConfigId                  INTEGER,
	portConfigAlias               DisplayString,
	portConfigEnable              INTEGER,
	portConfigAutonego            INTEGER,
	portConfigSpeed               INTEGER,
	portConfigDuplex              INTEGER,
	portConfigFlowControl         INTEGER,
	portConfigPinout              INTEGER,
	portConfigFarEndFault         INTEGER,
	portConfigAdvertise           INTEGER,
	portConfigFibreDownDetection  INTEGER
}

portConfigId OBJECT-TYPE
	SYNTAX INTEGER (1..24)
	MAX-ACCESS read-only
	STATUS current
	DESCRIPTION
	"This entry describes the device's port id."
	::= { portConfigTableEntry 1 }

portConfigAlias OBJECT-TYPE
	SYNTAX DisplayString (SIZE (0..20))
	MAX-ACCESS read-write
	STATUS current
	DESCRIPTION
	"This entry contains an individual name 
	for the port."
	::= { portConfigTableEntry 2 }

portConfigEnable OBJECT-TYPE
	SYNTAX INTEGER
	{
	enabled        (1),
	disabled       (2),
	undefined    (254),
	unsupported  (255)
	}
	MAX-ACCESS read-write
	STATUS current
	DESCRIPTION
	"This entry describes the type of the port."
	::= { portConfigTableEntry 3 }

portConfigAutonego OBJECT-TYPE
	SYNTAX INTEGER
	{
	enabled        (1),
	disabled       (2),
	undefined    (254),
	unsupported  (255)
	}
	MAX-ACCESS read-write
	STATUS current
	DESCRIPTION
	"This entry describes the current
	autonegotiation configuration of 
	the port if available."
	::= { portConfigTableEntry 4 }

portConfigSpeed OBJECT-TYPE
	SYNTAX  INTEGER
	{
	force10        (1),
	force100       (2),
	force1000      (3),
	undefined    (254),
	unsupported  (255)
	}
	MAX-ACCESS read-write
	STATUS current
	DESCRIPTION
	"This entry describes the current speed 
	configuration of the port if available.
	This entry is only valid if Autonegotiation
	is disabled."
	::= { portConfigTableEntry 5 }

portConfigDuplex OBJECT-TYPE
	SYNTAX  INTEGER
	{
	forcehalf      (1),
	forcefull      (2),
	undefined    (254),
	unsupported  (255)
	}
	MAX-ACCESS read-write
	STATUS current
	DESCRIPTION
	"This entry describes the current duplex 
	configuration of the port if available.
	This entry is only valid if Autonegotiation
	is disabled."
	::= { portConfigTableEntry 6 }

portConfigFlowControl OBJECT-TYPE
	SYNTAX INTEGER
	{
	advertise      (1),
	avoid          (2),
	undefined    (254),
	unsupported  (255)
	}
	MAX-ACCESS read-write
	STATUS current
	DESCRIPTION
	"This entry describes the current flow 
	control configuration of the port if 
	available. The current duplex mode is 
	is used to to select the matching settings.
	This entry is used for advertising if
	Autonegotiation is enabled and for forcing
	if AN is disabled."
	::= { portConfigTableEntry 7 }

portConfigPinout OBJECT-TYPE
	SYNTAX INTEGER
	{
	auto           (0), --Auto mdi/mdix enabled
	mdi            (1),
	mdix           (2),
	undefined    (254), --for fiber ports
	unsupported  (255)
	}
	MAX-ACCESS read-write
	STATUS current
	DESCRIPTION
	"This entry describes the current pinout 
	configuration of a copper port if available."
	::= { portConfigTableEntry 8 }

portConfigFarEndFault OBJECT-TYPE
	SYNTAX INTEGER
	{
	enabled        (1),
	disalbed       (2),
	undefined    (254), --for TP ports
	unsupported  (255)
	}
	MAX-ACCESS read-write
	STATUS current
	DESCRIPTION
	"This entry describes the current far end 
	fault behaviour of a fiber port if 
	available."
	::= { portConfigTableEntry 9 }

portConfigAdvertise OBJECT-TYPE
	SYNTAX INTEGER
	{
	advertiseGigabit  (1),
	avoidGigabit      (2),
	undefined       (254),
	unsupported     (255)
	}
	MAX-ACCESS read-write
	STATUS current
	DESCRIPTION
	"This entry describes the autonegotiation
	advertise information of the port."
	::= { portConfigTableEntry 10 }

portConfigFibreDownDetection OBJECT-TYPE
	SYNTAX INTEGER
	{
	enabled        (1),
	disalbed       (2),
	undefined    (254), --for TP ports
	unsupported  (255)
	}
	MAX-ACCESS read-write
	STATUS current
	DESCRIPTION
	"This entry describes the current fibre 
	down detection behaviour of a fiber port 
	if available."
	::= { portConfigTableEntry 11 }


-- vlan group: ======================================================
vlan OBJECT IDENTIFIER ::= { mib3 4 }

vlanSupport OBJECT-TYPE
	SYNTAX INTEGER
	{
	supported      (1),
	notsupported (255)
	}
	MAX-ACCESS read-only
	STATUS current
	DESCRIPTION
	"This entry contains the information if 
	vlans are supported or not."
	::= { vlan 1 }


vlanEnable OBJECT-TYPE
	SYNTAX INTEGER
	{
	enabled        (1),
	disabled       (2),
	undefined    (254),
	unsupported  (255)
	}
	MAX-ACCESS read-write
	STATUS current
	DESCRIPTION
	"This entry enables or disables vlan filtering."
	::= { vlan 2 }

vlanForceDefaultVID OBJECT-TYPE
	SYNTAX INTEGER
	{
	enabled        (1),
	disabled       (2),
	perport        (3),
	unsupported  (255)
	}
	MAX-ACCESS read-write
	STATUS current
	DESCRIPTION
	"This entry enables or disables forcing 
	default vlan id."
	::= { vlan 3 }

vlanFilterCount OBJECT-TYPE
	SYNTAX INTEGER
	MAX-ACCESS read-only
	STATUS current
	DESCRIPTION
	"This entry describes the number of 
	supported vlan filters."
	::= { vlan 4 }

vlanVoiceVID OBJECT-TYPE
	SYNTAX INTEGER (0..4095)
	MAX-ACCESS read-write
	STATUS current
	DESCRIPTION
	"This entry describes the default VID for Voice 
	 over IP operation. This VID is communicated
	 via CDP and LLDP."
	::= { vlan 5 }

vlanRstpVID OBJECT-TYPE
	SYNTAX INTEGER (0..4095)
	MAX-ACCESS read-write
	STATUS current
	DESCRIPTION
	"This entry describes the VID for RSTP operation."
	::= { vlan 6 }

vlanUnauthVID OBJECT-TYPE
	SYNTAX INTEGER (0..4095)
	MAX-ACCESS read-write
	STATUS current
	DESCRIPTION
	"This entry describes the VID used for unauthorized
	ports if The corresponding mode of operation has
	been selected."
	::= { vlan 7 }

-- vlan port table: =======================================
vlanPortTable OBJECT-TYPE
	SYNTAX SEQUENCE OF VlanPortList
	MAX-ACCESS not-accessible
	STATUS current
	DESCRIPTION
	"This table contains the vlan port 
	configuration."
	::= { vlan 10 }

vlanPortTableEntry OBJECT-TYPE
	SYNTAX VlanPortList
	MAX-ACCESS not-accessible
	STATUS current
	DESCRIPTION
	"Entry in the vlan port configuration 
	table."
	INDEX 
	{ vlanPortId } ::= { vlanPortTable 1 }

VlanPortList ::= SEQUENCE {
	vlanPortId           INTEGER,
	vlanPortMode         INTEGER,
	vlanDefaultVID       INTEGER,
	vlanDefaultPriority  INTEGER,
	vlanPortFlags        INTEGER
}


vlanPortId OBJECT-TYPE
	SYNTAX INTEGER (1..24)
	MAX-ACCESS read-only
	STATUS current
	DESCRIPTION
	"This entry describes the port id for the 
	vlan port table. The port id '0' is used 
	for the internal management agent port."
	::= { vlanPortTableEntry 1 }

vlanPortMode OBJECT-TYPE
	SYNTAX INTEGER
	{
	access         (1),
	trunk          (2),
	hybrid         (3),
	undefined    (254),
	unsupported  (255)
	}
	MAX-ACCESS read-write
	STATUS current
	DESCRIPTION
	"This entry describes the vlan mode the port."
	::= { vlanPortTableEntry 2 }

vlanDefaultVID OBJECT-TYPE
	SYNTAX INTEGER (0..4095)
	MAX-ACCESS read-write
	STATUS current
	DESCRIPTION
	"This entry describes default vid for the port."
	::= { vlanPortTableEntry 3 }

vlanDefaultPriority OBJECT-TYPE
	SYNTAX INTEGER (0..7)
	MAX-ACCESS read-write
	STATUS current
	DESCRIPTION
	"This entry describes default priority tag 
	for the port."
	::= { vlanPortTableEntry 4 }

vlanPortFlags OBJECT-TYPE
	SYNTAX INTEGER (0..3)
	--	forceVid(0),
	--	priVidOverride(1)
	MAX-ACCESS read-write
	STATUS current
	DESCRIPTION
	"This Entry contains per port some bitwise 
	filter settings:
	Bit 0: Force Port Default VID (only valid if 
	       vlanForceDefaultVID is set to '3')
	Bit 1: per VID Priority Override"
	::= { vlanPortTableEntry 5 }


-- vlan filter table: =====================================
vlanFilterTable OBJECT-TYPE
	SYNTAX SEQUENCE OF VlanFilterList
	MAX-ACCESS not-accessible
	STATUS current
	DESCRIPTION
	"This table contains the vlan filter 
	configuration."
	::= { vlan 20 }

vlanFilterTableEntry OBJECT-TYPE
	SYNTAX VlanFilterList
	MAX-ACCESS not-accessible
	STATUS current
	DESCRIPTION
	"Entry in the vlan filter configuration table."
	INDEX 
	{ vlanFilterId } ::= { vlanFilterTable 1 }

VlanFilterList ::= SEQUENCE {
	vlanFilterId      INTEGER,
	vlanFilterVID     INTEGER,
	vlanFilterAlias   DisplayString,
	vlanFilterEnable  INTEGER,
	vlanMemberManager INTEGER,
	vlanMemberPort1   INTEGER,
	vlanMemberPort2   INTEGER,
	vlanMemberPort3   INTEGER,
	vlanMemberPort4   INTEGER,
	vlanMemberPort5   INTEGER,
	vlanMemberPort6   INTEGER,
	vlanMemberPort7   INTEGER,
	vlanMemberPort8   INTEGER,
	vlanMemberPort9   INTEGER,
	vlanMemberPort10  INTEGER,
	vlanMemberPort11  INTEGER,
	vlanMemberPort12  INTEGER,
	vlanMemberPort13  INTEGER,
	vlanMemberPort14  INTEGER,
	vlanMemberPort15  INTEGER,
	vlanMemberPort16  INTEGER,
	vlanMemberPort17  INTEGER,
	vlanMemberPort18  INTEGER,
	vlanMemberPort19  INTEGER,
	vlanMemberPort20  INTEGER,
	vlanMemberPort21  INTEGER,
	vlanMemberPort22  INTEGER,
	vlanMemberPort23  INTEGER,
	vlanMemberPort24  INTEGER
}

vlanFilterId OBJECT-TYPE
	SYNTAX INTEGER (1..64)
	MAX-ACCESS read-only
	STATUS current
	DESCRIPTION
	"This entry contains the filter id for the 
	vlan filter table."
	::= { vlanFilterTableEntry 1 }

vlanFilterVID OBJECT-TYPE
	SYNTAX INTEGER (0..4095)
	MAX-ACCESS read-write
	STATUS current
	DESCRIPTION
	"This entry describes the vlan id for the 
	filter."
	::= { vlanFilterTableEntry 2 }

vlanFilterAlias OBJECT-TYPE
	SYNTAX DisplayString (SIZE (0..16))
	MAX-ACCESS read-write
	STATUS current
	DESCRIPTION
	"This entry describes an individual name 
	for the vlan filter."
	::= { vlanFilterTableEntry 3 }

vlanFilterEnable OBJECT-TYPE
	SYNTAX INTEGER
	{
	enabled        (1),
	disabled       (2),
	unsupported  (255)
	}
	MAX-ACCESS read-write
	STATUS current
	DESCRIPTION
	"This entry enables or disabled the vlan 
	filter."
	::= { vlanFilterTableEntry 4 }

vlanMemberManager OBJECT-TYPE
	SYNTAX INTEGER
	{
	yes            (1),
	no             (2),
	unsupported  (255)
	}
	MAX-ACCESS read-write
	STATUS current
	DESCRIPTION
	"This entry defines the membership of the 
	management agent to the filter."
	::= { vlanFilterTableEntry 5 }

vlanMemberPort1 OBJECT-TYPE
	SYNTAX INTEGER
	{
	yes            (1),
	no             (2),
	unsupported  (255)
	}
	MAX-ACCESS read-write
	STATUS current
	DESCRIPTION
	"This entry defines the membership of 
	port 1 to the filter."
	::= { vlanFilterTableEntry 6 }

vlanMemberPort2 OBJECT-TYPE
	SYNTAX INTEGER
	{
	yes            (1),
	no             (2),
	unsupported  (255)
	}
	MAX-ACCESS read-write
	STATUS current
	DESCRIPTION
	"This entry defines the membership of 
	port 2 to the filter."
	::= { vlanFilterTableEntry 7 }

vlanMemberPort3 OBJECT-TYPE
	SYNTAX INTEGER
	{
	yes            (1),
	no             (2),
	unsupported  (255)
	}
	MAX-ACCESS read-write
	STATUS current
	DESCRIPTION
	"This entry defines the membership of 
	port 3 to the filter."
	::= { vlanFilterTableEntry 8 }

vlanMemberPort4 OBJECT-TYPE
	SYNTAX INTEGER
	{
	yes            (1),
	no             (2),
	unsupported  (255)
	}
	MAX-ACCESS read-write
	STATUS current
	DESCRIPTION
	"This entry defines the membership of 
	port 4 to the filter."
	::= { vlanFilterTableEntry 9 }

vlanMemberPort5 OBJECT-TYPE
	SYNTAX INTEGER
	{
	yes            (1),
	no             (2),
	unsupported  (255)
	}
	MAX-ACCESS read-write
	STATUS current
	DESCRIPTION
	"This entry defines the membership of 
	port 5 to the filter."
	::= { vlanFilterTableEntry 10 }

vlanMemberPort6 OBJECT-TYPE
	SYNTAX INTEGER
	{
	yes            (1),
	no             (2),
	unsupported  (255)
	}
	MAX-ACCESS read-write
	STATUS current
	DESCRIPTION
	"This entry defines the membership of 
	port 6 to the filter."
	::= { vlanFilterTableEntry 11 }

vlanMemberPort7 OBJECT-TYPE
	SYNTAX INTEGER
	{
	yes            (1),
	no             (2),
	unsupported  (255)
	}
	MAX-ACCESS read-write
	STATUS current
	DESCRIPTION
	"This entry defines the membership of 
	port 7 to the filter."
	::= { vlanFilterTableEntry 12 }

vlanMemberPort8 OBJECT-TYPE
	SYNTAX INTEGER
	{
	yes            (1),
	no             (2),
	unsupported  (255)
	}
	MAX-ACCESS read-write
	STATUS current
	DESCRIPTION
	"This entry defines the membership of 
	port 8 to the filter."
	::= { vlanFilterTableEntry 13 }

vlanMemberPort9 OBJECT-TYPE
	SYNTAX INTEGER
	{
	yes            (1),
	no             (2),
	unsupported  (255)
	}
	MAX-ACCESS read-write
	STATUS current
	DESCRIPTION
	"This entry defines the membership of 
	port 9 to the filter."
	::= { vlanFilterTableEntry 14 }

vlanMemberPort10 OBJECT-TYPE
	SYNTAX INTEGER
	{
	yes            (1),
	no             (2),
	unsupported  (255)
	}
	MAX-ACCESS read-write
	STATUS current
	DESCRIPTION
	"This entry defines the membership of 
	port 10 to the filter."
	::= { vlanFilterTableEntry 15 }

vlanMemberPort11 OBJECT-TYPE
	SYNTAX INTEGER
	{
	yes            (1),
	no             (2),
	unsupported  (255)
	}
	MAX-ACCESS read-write
	STATUS current
	DESCRIPTION
	"This entry defines the membership of 
	port 11 to the filter."
	::= { vlanFilterTableEntry 16 }

vlanMemberPort12 OBJECT-TYPE
	SYNTAX INTEGER
	{
	yes            (1),
	no             (2),
	unsupported  (255)
	}
	MAX-ACCESS read-write
	STATUS current
	DESCRIPTION
	"This entry defines the membership of 
	port 12 to the filter."
	::= { vlanFilterTableEntry 17 }

vlanMemberPort13 OBJECT-TYPE
	SYNTAX INTEGER
	{
	yes            (1),
	no             (2),
	unsupported  (255)
	}
	MAX-ACCESS read-write
	STATUS current
	DESCRIPTION
	"This entry defines the membership of 
	port 13 to the filter."
	::= { vlanFilterTableEntry 18 }

vlanMemberPort14 OBJECT-TYPE
	SYNTAX INTEGER
	{
	yes            (1),
	no             (2),
	unsupported  (255)
	}
	MAX-ACCESS read-write
	STATUS current
	DESCRIPTION
	"This entry defines the membership of 
	port 14 to the filter."
	::= { vlanFilterTableEntry 19 }

vlanMemberPort15 OBJECT-TYPE
	SYNTAX INTEGER
	{
	yes            (1),
	no             (2),
	unsupported  (255)
	}
	MAX-ACCESS read-write
	STATUS current
	DESCRIPTION
	"This entry defines the membership of 
	port 15 to the filter."
	::= { vlanFilterTableEntry 20 }

vlanMemberPort16 OBJECT-TYPE
	SYNTAX INTEGER
	{
	yes            (1),
	no             (2),
	unsupported  (255)
	}
	MAX-ACCESS read-write
	STATUS current
	DESCRIPTION
	"This entry defines the membership of 
	port 16 to the filter."
	::= { vlanFilterTableEntry 21 }

vlanMemberPort17 OBJECT-TYPE
	SYNTAX INTEGER
	{
	yes            (1),
	no             (2),
	unsupported  (255)
	}
	MAX-ACCESS read-write
	STATUS current
	DESCRIPTION
	"This entry defines the membership of 
	port 17 to the filter."
	::= { vlanFilterTableEntry 22 }

vlanMemberPort18 OBJECT-TYPE
	SYNTAX INTEGER
	{
	yes            (1),
	no             (2),
	unsupported  (255)
	}
	MAX-ACCESS read-write
	STATUS current
	DESCRIPTION
	"This entry defines the membership of 
	port 18 to the filter."
	::= { vlanFilterTableEntry 23 }

vlanMemberPort19 OBJECT-TYPE
	SYNTAX INTEGER
	{
	yes            (1),
	no             (2),
	unsupported  (255)
	}
	MAX-ACCESS read-write
	STATUS current
	DESCRIPTION
	"This entry defines the membership of 
	port 19 to the filter."
	::= { vlanFilterTableEntry 24 }

vlanMemberPort20 OBJECT-TYPE
	SYNTAX INTEGER
	{
	yes            (1),
	no             (2),
	unsupported  (255)
	}
	MAX-ACCESS read-write
	STATUS current
	DESCRIPTION
	"This entry defines the membership of 
	port 20 to the filter."
	::= { vlanFilterTableEntry 25 }

vlanMemberPort21 OBJECT-TYPE
	SYNTAX INTEGER
	{
	yes            (1),
	no             (2),
	unsupported  (255)
	}
	MAX-ACCESS read-write
	STATUS current
	DESCRIPTION
	"This entry defines the membership of 
	port 21 to the filter."
	::= { vlanFilterTableEntry 26 }

vlanMemberPort22 OBJECT-TYPE
	SYNTAX INTEGER
	{
	yes            (1),
	no             (2),
	unsupported  (255)
	}
	MAX-ACCESS read-write
	STATUS current
	DESCRIPTION
	"This entry defines the membership of 
	port 22 to the filter."
	::= { vlanFilterTableEntry 27 }

vlanMemberPort23 OBJECT-TYPE
	SYNTAX INTEGER
	{
	yes            (1),
	no             (2),
	unsupported  (255)
	}
	MAX-ACCESS read-write
	STATUS current
	DESCRIPTION
	"This entry defines the membership of 
	port 23 to the filter."
	::= { vlanFilterTableEntry 28 }

vlanMemberPort24 OBJECT-TYPE
	SYNTAX INTEGER
	{
	yes            (1),
	no             (2),
	unsupported  (255)
	}
	MAX-ACCESS read-write
	STATUS current
	DESCRIPTION
	"This entry defines the membership of 
	port 24 to the filter."
	::= { vlanFilterTableEntry 29 }

-- vlan filter enhanced table: =====================================
vlanFilterEnhTable OBJECT-TYPE
	SYNTAX SEQUENCE OF VlanFilterEnhList
	MAX-ACCESS not-accessible
	STATUS current
	DESCRIPTION
	"This table contains the enhanced 
	vlan filter configuration."
	::= { vlan 30 }

vlanFilterEnhTableEntry OBJECT-TYPE
	SYNTAX VlanFilterEnhList
	MAX-ACCESS not-accessible
	STATUS current
	DESCRIPTION
	"Entry in the vlan filter enhanced
	configuration table."
	INDEX 
	{ vlanFilterEnhId } ::= { vlanFilterEnhTable 1 }

VlanFilterEnhList ::= SEQUENCE {
	vlanFilterEnhId          INTEGER,
	vlanFilterEnhFlags       INTEGER,
	vlanFilterEnhPriOverride INTEGER
}

vlanFilterEnhId OBJECT-TYPE
	SYNTAX INTEGER (1..64)
	MAX-ACCESS read-only
	STATUS current
	DESCRIPTION
	"This entry contains the filter id for the 
	enhanced vlan filter table."
	::= { vlanFilterEnhTableEntry 1 }

vlanFilterEnhFlags OBJECT-TYPE
	SYNTAX INTEGER (0..3)
--		filterEnabled(0),
--		priVidOverride(1)
	MAX-ACCESS read-write
	STATUS current
	DESCRIPTION
	"This Entry contains some flags for
	VLAN filter settings. The content is
	defined as following:
	Bit 0: Filter Enabled
	Bit 1: per VID Priority Override Enabled"
	::= { vlanFilterEnhTableEntry 2 }

vlanFilterEnhPriOverride OBJECT-TYPE
	SYNTAX INTEGER (0..7)
	MAX-ACCESS read-write
	STATUS current
	DESCRIPTION
	"This entry contains the priority
	value to override an ingress frame with
	if its VLAN ID fits, filtering is enabled,
	port selective override flag is set and
	filter selective override flag is set."
	::= { vlanFilterEnhTableEntry 3 }


-- prioritization group: ============================================
prioritization OBJECT IDENTIFIER ::= { mib3 5 }

prioSupport OBJECT-TYPE
	SYNTAX INTEGER
	{
	supported      (1),
	unsupported  (255)
	}
	MAX-ACCESS read-only
	STATUS current
	DESCRIPTION
	"This entry contains the information if
	prioritization is supported or not."
	::= { prioritization 1 }

prioQueueCount OBJECT-TYPE
	SYNTAX INTEGER
	MAX-ACCESS read-only
	STATUS current
	DESCRIPTION
	"This entry defines the number of queues 
	supported by the device."
	::= { prioritization 2 }

prioQueueScheme OBJECT-TYPE
	SYNTAX INTEGER
	{
	weighted       (1),  -- 8-4-2-1
	fixed          (2),  -- higher first
	unsupported  (255)
	}
	MAX-ACCESS read-write
	STATUS current
	DESCRIPTION
	"This entry defines the queue scheme for 
	prioritization."
	::= { prioritization 3 }

prioPortEnable OBJECT-TYPE
	SYNTAX INTEGER
	{
	enabled        (1),
	disabled       (2),
	unsupported  (255)
	}
	MAX-ACCESS read-only
	STATUS current
	DESCRIPTION
	"Hardwaret prioritization of the device is 
	applied if all other type of prioritization 
	are not applicable."
	::= { prioritization 4 }

prioIeeeTagEnable OBJECT-TYPE
	SYNTAX INTEGER
	{
	enabled        (1),
	disabled       (2),
	unsupported  (255)
	}
	MAX-ACCESS read-write
	STATUS current
	DESCRIPTION
	"If enabled, a IEEE 802.1p tagged frame 
	will be mapped to the queue that is 
	assigned to this tag"
	::= { prioritization 5 } 

prioDiffservEnable OBJECT-TYPE
	SYNTAX INTEGER
	{
	enabled        (1),
	disabled       (2),
	unsupported  (255)
	}
	MAX-ACCESS read-write
	STATUS current
	DESCRIPTION
	"If enabled a tagged frame will be mapped 
	to the queue that is assigned to this tag."
	::= { prioritization 6 } 

-- port prio table: ===================================
prioPortTable OBJECT-TYPE
	SYNTAX SEQUENCE OF PrioPortList
	MAX-ACCESS not-accessible
	STATUS current
	DESCRIPTION
	"This table contains the port prioritization 
	of the device. This setting is always valid 
	if no other type of prioritization has been 
	selected."
	::= { prioritization 10 }

prioPortTableEntry OBJECT-TYPE
	SYNTAX PrioPortList
	MAX-ACCESS not-accessible
	STATUS current
	DESCRIPTION
	"Entry in the port prioritization table."
	INDEX
	{ prioPortId } ::= { prioPortTable 1 }

PrioPortList ::= SEQUENCE {
	prioPortId    INTEGER,
	prioPortQueue INTEGER
}

prioPortId OBJECT-TYPE
	SYNTAX INTEGER (1..24)
	MAX-ACCESS read-only
	STATUS current
	DESCRIPTION
	"This entry describes the device's port id."
	::= { prioPortTableEntry 1 }

prioPortQueue OBJECT-TYPE
	SYNTAX INTEGER (0..3)
	MAX-ACCESS read-write
	STATUS current
	DESCRIPTION
	"This entry describes the selected queue 
	if port prioritization is available."
	::= { prioPortTableEntry 2 }

-- IEEE tag prio table ====================================
prioIeeeTagTable OBJECT-TYPE
	SYNTAX SEQUENCE OF PrioIeeeTagList
	MAX-ACCESS not-accessible
	STATUS current
	DESCRIPTION
	"This table contains the configuuration of 
	IEEE 802.1p prioritization. Each of the 8 
	different values is assigned to one of the
	available queues here."
	::= { prioritization 20 }

prioIeeeTagTableEntry OBJECT-TYPE
	SYNTAX PrioIeeeTagList
	MAX-ACCESS not-accessible
	STATUS current
	DESCRIPTION
	"Entry in the IEEE 802.1p tag prioritization 
	table."
	INDEX
	{ prioIeeeTagId } ::= { prioIeeeTagTable 1 }

PrioIeeeTagList ::= SEQUENCE {
	prioIeeeTagId    INTEGER,
	prioIeeeTagQueue INTEGER
}

prioIeeeTagId OBJECT-TYPE
	SYNTAX INTEGER (0..7)
	MAX-ACCESS read-only
	STATUS current
	DESCRIPTION
	"This entry defines the IEEE 802.1p tag a 
	queue is assigned to."
	::= { prioIeeeTagTableEntry 1 }

prioIeeeTagQueue OBJECT-TYPE
	SYNTAX  INTEGER
	MAX-ACCESS  read-write
	STATUS current
	DESCRIPTION
	"This entry describes the selected queue 
	for each IEEE 802.1p tag."
	::= { prioIeeeTagTableEntry 2 }

-- diffserv prio table: ===================================
prioDiffservTable OBJECT-TYPE
	SYNTAX SEQUENCE OF PrioDiffservList
	MAX-ACCESS not-accessible
	STATUS current
	DESCRIPTION
	"This table contains the configuuration 
	of DiffServ prioritization. Each of the 
	64 different values is assigned to one 
	of the available queues here."
	::= { prioritization 30 }

prioDiffservTableEntry OBJECT-TYPE
	SYNTAX PrioDiffservList
	MAX-ACCESS not-accessible
	STATUS current
	DESCRIPTION
	"Entry in the Diffserv prioritization table."
	INDEX
	{ prioDiffservId } ::= { prioDiffservTable 1 }

PrioDiffservList ::= SEQUENCE {
	prioDiffservId    INTEGER,
	prioDiffservQueue INTEGER
}

prioDiffservId OBJECT-TYPE
	SYNTAX INTEGER (0..63)
	MAX-ACCESS read-only
	STATUS current
	DESCRIPTION
	"This entry defines the Diffserv index a 
	queue is assigned to."
	::= { prioDiffservTableEntry 1 }

prioDiffservQueue OBJECT-TYPE
	SYNTAX  INTEGER
	MAX-ACCESS  read-write
	STATUS current
	DESCRIPTION
	"This entry describes the selected queue 
	for each Diffserv index."
	::= { prioDiffservTableEntry 2 }



-- monitor group: ===================================================
monitor OBJECT IDENTIFIER ::= { mib3 6 }

monitorSupport OBJECT-TYPE
	SYNTAX INTEGER
	{
	supported      (1),
	unsupported  (255)
	}
	MAX-ACCESS read-only
	STATUS current
	DESCRIPTION
	"This entry contains the information if
	port monitoring is supported or not."
	::= { monitor 1 }

monitorMode OBJECT-TYPE
	SYNTAX INTEGER
	{
	txonly         (1),
	both           (2),
	disabled       (3),
	hubmode        (4),
	unsupported  (255)
	}
	MAX-ACCESS read-write
	STATUS current
	DESCRIPTION
	"This entry enables or disables monitoring
	and selects the mode of operation."
	::= { monitor 2 }

monitorSource OBJECT-TYPE
	SYNTAX INTEGER(1..24)
	MAX-ACCESS read-write
	STATUS current
	DESCRIPTION
	"This entry contains the monitor source 
	portnumber."
	::= { monitor 3 }

monitorDestination OBJECT-TYPE
	SYNTAX INTEGER(1..24)
	MAX-ACCESS read-write
	STATUS current
	DESCRIPTION
	"This entry contains the monitor 
	destination portnumber."
	::= { monitor 4 }



-- ring group: ======================================================
ring OBJECT IDENTIFIER ::= { mib3 7 }

ringSupport OBJECT-TYPE
	SYNTAX INTEGER
	{
	supported      (1),
	unsupported  (255)
	}
	MAX-ACCESS read-only
	STATUS current
	DESCRIPTION
	"This entry contains the information if
	ethernet ring feature is supported or not."
	::= { ring 1 }

ringCount OBJECT-TYPE
	SYNTAX INTEGER
	MAX-ACCESS read-only
	STATUS current
	DESCRIPTION
	"The number of supported rings on this system."
	::= { ring 2 }

-- ring table: ============================================
ringTable OBJECT-TYPE
	SYNTAX SEQUENCE OF RingList
	MAX-ACCESS not-accessible
	STATUS current
	DESCRIPTION
	"This table contains the ring configuration 
	of the device."
	::= { ring 10 }

ringTableEntry OBJECT-TYPE
	SYNTAX RingList
	MAX-ACCESS not-accessible
	STATUS current
	DESCRIPTION
	"Entry in the ring configuration table."
	INDEX 
	{ ringId } ::= { ringTable 1 }

RingList ::= SEQUENCE {
	ringId     INTEGER,
	ringMode   INTEGER,
	ringPortA  INTEGER,
	ringPortB  INTEGER,
	ringNumber INTEGER,
	ringStatus INTEGER,
	ringAlarmDuration TimeTicks
}

ringId OBJECT-TYPE
	SYNTAX INTEGER (1..3)
	MAX-ACCESS read-only
	STATUS current
	DESCRIPTION
	"This entry describes the ring id."
	::= { ringTableEntry 1 }

ringMode OBJECT-TYPE
	SYNTAX INTEGER
	{
	slave          (1), 
	master         (2),
	disabled       (3),
	unsupported  (255)
	}
	MAX-ACCESS read-write
	STATUS current
	DESCRIPTION
	"This entry enables or disables ring mode
	and selects the mode of operation."
	::= { ringTableEntry 2 }

ringPortA OBJECT-TYPE
	SYNTAX INTEGER (1..24)
	MAX-ACCESS read-write
	STATUS current
	DESCRIPTION
	"This entry defines port A for the ring 
	function. If the device is a 'master' 
	this is the main port. If ring feature
	is not supported a 255 will be replied."
	::= { ringTableEntry 3 }

ringPortB OBJECT-TYPE
	SYNTAX INTEGER (1..24)
	MAX-ACCESS read-write
	STATUS current
	DESCRIPTION
	"This entry defines port B for the ring 
	function. If the device is a 'master' 
	this is the backup port. If ring feature
	is not supported a 255 will be replied."
	::= { ringTableEntry 4 }

ringNumber OBJECT-TYPE
	SYNTAX INTEGER (0..255)
	MAX-ACCESS read-write
	STATUS current
	DESCRIPTION
	"This entry defines the ring ID number.
	If ring feature	is not supported a 255
	will be replied."
	::= { ringTableEntry 5 }

ringStatus OBJECT-TYPE
	SYNTAX INTEGER
	{
	ringOk         (1),
	ringFailure    (2),
	ringDisabled   (3),
	unsupported  (255)
	}
	MAX-ACCESS read-only
	STATUS current
	DESCRIPTION
	"This entry defines the ring status."
	::= { ringTableEntry 6 }

ringAlarmDuration OBJECT-TYPE
	SYNTAX TimeTicks
	MAX-ACCESS read-only
	STATUS current
	DESCRIPTION
	"Duration of ring alarm status (in 0.01s).
	This entry is used as additional status
	information in repeated ring alarm traps
	if error status remains unchanged.
	A value of '0' means 'no ring alarm'"
	::= { ringTableEntry 7 }



-- coupling redundancy group: =======================================
couplingred OBJECT IDENTIFIER ::= { mib3 8 }

couplingredSupport OBJECT-TYPE
	SYNTAX INTEGER
	{
	supported    (1),
	unsupported  (255)
	}
	MAX-ACCESS read-only
	STATUS current
	DESCRIPTION
	"This entry contains the information if ring 
	coupling redundancy is supported or not."
	::= { couplingred 1 }

couplingredPort OBJECT-TYPE
	SYNTAX INTEGER (0..24)
	MAX-ACCESS read-write
	STATUS current
	DESCRIPTION
	"This entry defines the port for the ring 
	coupling redundancy function. If not supported 
	this entry is set to 0."
	::= { couplingred 2 }

couplingredMode OBJECT-TYPE
	SYNTAX INTEGER
	{
	backup         (1),
	main           (2),
	disabled       (3),
	unsupported  (255)
	}
	MAX-ACCESS read-write
	STATUS current
	DESCRIPTION
	"This entry enables or disables ring 
	coupling redundancy mode and selects 
	the mode of operation."
	::= { couplingred 3 }

couplingredPartnerIpv4Address OBJECT-TYPE
	SYNTAX IpAddress
	MAX-ACCESS read-write
	STATUS current
	DESCRIPTION
	"This entry defines the IPv4 address of the 
	ring coupling redundancy partner. In backup 
	mode this is the IPv4 address of the main 
	device. In main mode this is the IPv4 address 
	of the backup device. If not supported this 
	entry is set to 0.0.0.0 ."
	::= { couplingred 4 }

couplingredStatus OBJECT-TYPE
	SYNTAX INTEGER
	{
	disabled       (0),
	blocked        (1),
	link           (2),
	forwarding     (3),
	standby        (4),
	undefined      (5),
	unsupported  (255)
	}
	MAX-ACCESS read-only
	STATUS current
	DESCRIPTION
	"This entry defines the ring coupling 
	redundancy mode status."
	::= { couplingred 5 }

couplingredPartnerStatus OBJECT-TYPE
	SYNTAX INTEGER
	{
	disabled       (0),
	blocked        (1),
	link           (2),
	forwarding     (3),
	standby        (4),
	undefined      (5),
	unsupported  (255)
	}
	MAX-ACCESS read-only
	STATUS current
	DESCRIPTION
	"This entry defines the ring coupling 
	redundancy mode status."
	::= { couplingred 6 }

couplingredValidationFlag OBJECT-TYPE
	SYNTAX INTEGER
	MAX-ACCESS read-only
	STATUS current
	DESCRIPTION
	"This entry defines the validation 
	of ring coupling redundancy. Bit 0 
	indicates a valid configuration, Bit 1 
	indicates a valid status. If ring 
	coupling redundancy is unsupported or 
	disabled this entry is set to 255."
	::= { couplingred 7 }



-- sfp group: =======================================================
sfp OBJECT IDENTIFIER ::= { mib3 9 }

sfpSupport OBJECT-TYPE
	SYNTAX INTEGER
	{
	supported      (1),
	unsupported  (255)
	}
	MAX-ACCESS read-only
	STATUS current
	DESCRIPTION
	"This entry contains the information if
	sfp modules are supported or not."
	::= { sfp 1 }

sfpCount OBJECT-TYPE
	SYNTAX INTEGER
	MAX-ACCESS read-only
	STATUS current
	DESCRIPTION
	"The number of supported sfp modules."
	::= { sfp 2 }

-- sfp table: =============================================
sfpTable OBJECT-TYPE
	SYNTAX SEQUENCE OF SfpList
	MAX-ACCESS not-accessible
	STATUS current
	DESCRIPTION
	"This table contains the sfp module 
	status of the device."
	::= { sfp 10 }

sfpTableEntry OBJECT-TYPE
	SYNTAX SfpList
	MAX-ACCESS not-accessible
	STATUS current
	DESCRIPTION
	"Entry in the sfp status table."
	INDEX 
	{ sfpId } ::= { sfpTable 1 }

SfpList ::= SEQUENCE {
	sfpId                  INTEGER,
	sfpPortnumber          INTEGER,
	sfpDetect              INTEGER,
	sfpVendor              DisplayString,
	sfpVendorPartnumber    DisplayString,
	sfpVendorSerialnumber  DisplayString,
	sfpConnector           INTEGER,
	sfpNominalBitrate      INTEGER,
	sfpDiagnostic          INTEGER,
	sfpTemperature         INTEGER,
	sfpVoltage             INTEGER,
	sfpTxBias              INTEGER,
	sfpTxPower             INTEGER,
	sfpRxPower             INTEGER,
	sfpWarnings            BITS,
	sfpAlarms              BITS
}

sfpId OBJECT-TYPE
	SYNTAX INTEGER (1..24)
	MAX-ACCESS read-only
	STATUS current
	DESCRIPTION
	"This entry describes the sfp id."
	::= { sfpTableEntry 1 }

sfpPortnumber OBJECT-TYPE
	SYNTAX INTEGER
	MAX-ACCESS read-only
	STATUS current
	DESCRIPTION
	"This entry describes the number of the port
	where the sfp can be plugged in."
	::= { sfpTableEntry 2 }

sfpDetect OBJECT-TYPE
	SYNTAX INTEGER
	{
	plugged        (1), 
	unplugged      (2),
	unsupported  (255)
	}
	MAX-ACCESS read-only
	STATUS current
	DESCRIPTION
	"This entry enables or disables uplink 
	redundancy"
	::= { sfpTableEntry 3 }

sfpVendor OBJECT-TYPE
	SYNTAX DisplayString (SIZE (0..16))
	MAX-ACCESS read-only
	STATUS current
	DESCRIPTION
	"This entry describes the vendor name of 
	the sfp."
	::= { sfpTableEntry 4 }

sfpVendorPartnumber OBJECT-TYPE
	SYNTAX DisplayString (SIZE (0..16))
	MAX-ACCESS read-only
	STATUS current
	DESCRIPTION
	"This entry describes the vendor 
	partnumber of the sfp."
	::= { sfpTableEntry 5 }

sfpVendorSerialnumber OBJECT-TYPE
	SYNTAX DisplayString (SIZE (0..16))
	MAX-ACCESS read-only
	STATUS current
	DESCRIPTION
	"This entry describes the vendor 
	serialnumber of the sfp."
	::= { sfpTableEntry 6 }

sfpConnector OBJECT-TYPE
	SYNTAX INTEGER
	{
	connSC         (1),
	connLC         (7),
	connMTRJ       (8),
	unsupported  (255)
	}
	MAX-ACCESS read-only
	STATUS current
	DESCRIPTION
	"This entry describes the type of 
	connector of the sfp."
	::= { sfpTableEntry 7 }

sfpNominalBitrate OBJECT-TYPE
	SYNTAX INTEGER
	MAX-ACCESS read-only
	STATUS current
	DESCRIPTION
	"This entry describes the nominal bitrate 
	of the sfp. It is a maximum value, a lower 
	value may be used instead."
	::= { sfpTableEntry 8 }

sfpDiagnostic OBJECT-TYPE
	SYNTAX INTEGER
	{
	supportedWithInternalCalibration    (1), 
	supportedWithExternalCalibration    (2), 
	undefined                         (254),
	unsupported                       (255)
	}
	MAX-ACCESS read-only
	STATUS current
	DESCRIPTION
	"This entry describes tha avalability and 
	type of diagnostics."
	::= { sfpTableEntry 9 }

sfpTemperature OBJECT-TYPE
	SYNTAX INTEGER
	MAX-ACCESS read-only
	STATUS current
	DESCRIPTION
	"This entry describes the temperature of 
	the sfp in multiple of 0.1 degree celsius."
	::= { sfpTableEntry 10 }

sfpVoltage OBJECT-TYPE
	SYNTAX INTEGER
	MAX-ACCESS read-only
	STATUS current
	DESCRIPTION
	"This entry describes the supply voltage 
	of the sfp in multiple of 0.01 V."
	::= { sfpTableEntry 11 }

sfpTxBias OBJECT-TYPE
	SYNTAX INTEGER
	MAX-ACCESS read-only
	STATUS current
	DESCRIPTION
	"This entry describes the transmit bias 
	current of the sfp in multiple of 0.01 mA."
	::= { sfpTableEntry 12 }

sfpTxPower OBJECT-TYPE
	SYNTAX INTEGER
	MAX-ACCESS read-only
	STATUS current
	DESCRIPTION
	"This entry describes the optical transmit 
	power of the sfp in multiple of 0.1 uW."
	::= { sfpTableEntry 13 }

sfpRxPower OBJECT-TYPE
	SYNTAX INTEGER
	MAX-ACCESS read-only
	STATUS current
	DESCRIPTION
	"This entry describes the ooptical receive 
	power of the sfp in multiple of 0.1 uW."
	::= { sfpTableEntry 14 }

sfpWarnings OBJECT-TYPE
	SYNTAX BITS {
		tempHighWarn(0),
		tempLowWarn(1),
		vccHighWarn(2),
		vccLowWarn(3),
		txBiasHighWarn(4),
		txBiasLowWarn(5),
		txPowerHighWarn(6),
		txPowerLowWarn(7),
		rxPowerHighWarn(8),
		rxPowerLowWarn(9)
	}
	MAX-ACCESS read-only
	STATUS current
	DESCRIPTION
	"This entry contains the flags for internal
	warnings. A warning occurrs if regarding 
	warning threshold is exceeded."
	::= { sfpTableEntry 15 }

sfpAlarms OBJECT-TYPE
	SYNTAX BITS {
		tempHighAlarm(0),
		tempLowAlarm(1),
		vccHighAlarm(2),
		vccLowAlarm(3),
		txBiasHighAlarm(4),
		txBiasLowAlarm(5),
		txPowerHighAlarm(6),
		txPowerLowAlarm(7),
		rxPowerHighAlarm(8),
		rxPowerLowAlarm(9)
	}
	MAX-ACCESS read-only
	STATUS current
	DESCRIPTION
	"This entry contains the flags for internal
	alarms. An alarm occurrs if regarding 
	alarm threshold is exceeded."
	::= { sfpTableEntry 16 }



-- relais group: ====================================================
relais OBJECT IDENTIFIER ::= { mib3 11 }

relaisSupport OBJECT-TYPE
	SYNTAX INTEGER
	{
	supported      (1),
	unsupported  (255)
	}
	MAX-ACCESS read-only
	STATUS current
	DESCRIPTION
	"This entry contains the information if
	an alram relais is supported or not."
	::= { relais 1 }

relaisCount OBJECT-TYPE
	SYNTAX INTEGER
	MAX-ACCESS read-only
	STATUS current
	DESCRIPTION
	"The number of supported relais on this 
	system."
	::= { relais 2 }

-- relais table: ==========================================
relaisTable OBJECT-TYPE
	SYNTAX SEQUENCE OF RelaisList
	MAX-ACCESS not-accessible
	STATUS current
	DESCRIPTION
	"This table contains the relais 
	configuration of the device."
	::= { relais 10 }

relaisTableEntry OBJECT-TYPE
	SYNTAX RelaisList
	MAX-ACCESS not-accessible
	STATUS current
	DESCRIPTION
	"Entry in the relais configuration table."
	INDEX 
	{ relaisId } ::= { relaisTable 1 }

RelaisList ::= SEQUENCE {
	relaisId     INTEGER,
	relaisAlias  DisplayString,
	relaisMode   INTEGER,
	relaisStatus INTEGER
}

relaisId OBJECT-TYPE
	SYNTAX INTEGER (1..4)
	MAX-ACCESS read-only
	STATUS current
	DESCRIPTION
	"This entry describes the relais id."
	::= { relaisTableEntry 1 }

relaisAlias OBJECT-TYPE
	SYNTAX DisplayString (SIZE (0..16))
	MAX-ACCESS read-write
	STATUS current
	DESCRIPTION
	"This entry contains an individual name 
	for the relais."
	::= { relaisTableEntry 2 }

relaisMode OBJECT-TYPE
	SYNTAX INTEGER
	{
	openOnEvent    (1),
	closeOnEvent   (2),
	unsupported  (255)
	}
	MAX-ACCESS read-write
	STATUS current
	DESCRIPTION
	"This entry describes the bahaviour of 
	the alarm relais."
	::= { relaisTableEntry 3 }

relaisStatus OBJECT-TYPE
	SYNTAX INTEGER
	{
	closed         (1),
	opened         (2),
	unsupported  (255)
	}
	MAX-ACCESS read-write
	STATUS current
	DESCRIPTION
	"This entry describes the present status 
	of the alarm relais."
	::= { relaisTableEntry 4 }



-- portaccesscontrol group: =========================================
portaccessctrl OBJECT IDENTIFIER ::= { mib3 12 }

pacSupport OBJECT-TYPE
	SYNTAX INTEGER
	{
	supported      (1),
	unsupported  (255)
	}
	MAX-ACCESS read-only
	STATUS current
	DESCRIPTION
	"This entry contains the information if
	port authentication is supported or not."
	::= { portaccessctrl 1 }

pacEnable OBJECT-TYPE
	SYNTAX INTEGER
	{
	enabled        (1),
	disabled       (2),
	unsupported  (255)
	}
	MAX-ACCESS read-write
	STATUS current
	DESCRIPTION
	"This entry enables or disables port 
	authentication."
	::= { portaccessctrl 2 }

pacUnauthMode OBJECT-TYPE
	SYNTAX INTEGER
	{
	block            (1),
	useDefaultVID    (2),
	unsupported    (255)
	}
	MAX-ACCESS read-only
	STATUS current
	DESCRIPTION
	"The entry describes the mode of 
	operation for unauthorized ports."
	::= { portaccessctrl 3 }

pacUnauthVID OBJECT-TYPE
	SYNTAX INTEGER (0..4095)
	MAX-ACCESS read-write
	STATUS current
	DESCRIPTION
	"This entry describes the default VID for 
	ports which are unauthorized."
	::= { portaccessctrl 4 }

pacMaxNumberOfAllowedHostsPerPort OBJECT-TYPE
	SYNTAX INTEGER
	MAX-ACCESS read-only
	STATUS current
	DESCRIPTION
	"The value contains the maximum number of 
	supported Hosts per port of this device."
	::= { portaccessctrl 5 }

pacFallbackRequestEnable OBJECT-TYPE
	SYNTAX INTEGER
	{
	enabled        (1),
	disabled       (2),
	unsupported  (255)
	}
	MAX-ACCESS read-write
	STATUS current
	DESCRIPTION
	"This entry describes if authentication
	method fallback to MAC authentication
	after a request timeout is enabled(1)
	or not(2)"
	::= { portaccessctrl 6 }

pacFallbackRequestTimeout OBJECT-TYPE
	SYNTAX INTEGER (1..600)
	MAX-ACCESS read-write
	STATUS current
	DESCRIPTION
	"This entry contains the timeout value in 
	seconds. If no response to a 802.1X request 
	has been detected after this time a fallback
	to MAC authentication occures if bit 0 of 
	pacFallbackMode is set."
	::= { portaccessctrl 7 }

pacFallbackRejectsEnable OBJECT-TYPE
	SYNTAX INTEGER
	{
	enabled        (1),
	disabled       (2),
	unsupported  (255)
	}
	MAX-ACCESS read-write
	STATUS current
	DESCRIPTION
	"This entry describes if authentication
	method fallback to MAC authentication
	after a limited number of rejects is 
	enabled(1) or not(2)"
	::= { portaccessctrl 8 }

pacFallbackMaxRejects OBJECT-TYPE
	SYNTAX INTEGER (1..255)
	MAX-ACCESS read-write
	STATUS current
	DESCRIPTION
	"This entry contains the maximum number of
	rejects by the Radius server. If this number
	is achieved a fallback to MAC authentication
	occures if bit 1 of pacFallbackMode is set."
	::= { portaccessctrl 9 }

pacSupplicantTimeout OBJECT-TYPE
	SYNTAX INTEGER (1..65535)
	MAX-ACCESS read-write
	STATUS current
	DESCRIPTION
	"This entry contains the Supplicant 
	timeout value in seconds."
	::= { portaccessctrl 10 }

pacReauthEnable OBJECT-TYPE
	SYNTAX INTEGER
	{
	enabled        (1),
	disabled       (2),
	unsupported  (255)
	}
	MAX-ACCESS read-write
	STATUS current
	DESCRIPTION
	"This entry describes if reauthentication
	after a configured time will be done(1)
	not(2)."
	::= { portaccessctrl 11 }

pacReauthTime OBJECT-TYPE
	SYNTAX INTEGER (1..65535)
	MAX-ACCESS read-write
	STATUS current
	DESCRIPTION
	"This entry contains the reauthentication
	time period in minutes."
	::= { portaccessctrl 12 }


-- port access control status table: ======================
pacStatusTable OBJECT-TYPE
	SYNTAX SEQUENCE OF PacPortStatusList
	MAX-ACCESS not-accessible
	STATUS current
	DESCRIPTION
	"This table contains the port status
	of the port access control feature."
	::= { portaccessctrl 100 }

pacStatusTableEntry OBJECT-TYPE
	SYNTAX PacPortStatusList
	MAX-ACCESS not-accessible
	STATUS current
	DESCRIPTION
	"Entry in the port access control 
	port status table."
	INDEX 
	{ pacStatPortId } ::= { pacStatusTable 1 }

PacPortStatusList ::= SEQUENCE {
	pacStatPortId        INTEGER,
	pacStatPortMode      INTEGER,
	pacStatPortStatus    INTEGER,
	pacStatUserStatus1   INTEGER,
	pacStatUserStatus2   INTEGER,
	pacStatUserStatus3   INTEGER,
	pacStatUserStatus4   INTEGER,
	pacStatUserMac1      PhysAddress,
	pacStatUserMac2      PhysAddress,
	pacStatUserMac3      PhysAddress,
	pacStatUserMac4      PhysAddress,
	pacStatUserName1     DisplayString,
	pacStatUserName2     DisplayString,
	pacStatUserName3     DisplayString,
	pacStatUserName4     DisplayString,
	pacStatUserIp1       IpAddress,
	pacStatUserIp2       IpAddress,
	pacStatUserIp3       IpAddress,
	pacStatUserIp4       IpAddress
}

pacStatPortId OBJECT-TYPE
	SYNTAX INTEGER (1..24)
	MAX-ACCESS read-only
	STATUS current
	DESCRIPTION
	"This entry describes the port id."
	::= { pacStatusTableEntry 1 }

pacStatPortMode OBJECT-TYPE
	SYNTAX INTEGER
	{
	forceAuthorized         (1),
	macLocking              (2),
	radiusMacAuthentication (3),
	ieee8021XAuthentication (4),
	forceUnauthorized       (5),
	parallel8021XMACauth    (6),
	undefined             (254),
	unsupported           (255)
	}
	MAX-ACCESS read-only
	STATUS current
	DESCRIPTION
	"This entry describes the port 
	access control mode."
	::= { pacStatusTableEntry 2 }

pacStatPortStatus OBJECT-TYPE
	SYNTAX INTEGER
	{
	authorized          (1),
	unauthorized        (2),
	undefined         (254),
	unsupported       (255)
	}
	MAX-ACCESS read-only
	STATUS current
	DESCRIPTION
	"This entry describes the port 
	access control status."
	::= { pacStatusTableEntry 3 }

pacStatUserStatus1 OBJECT-TYPE
	SYNTAX INTEGER
	{
	authorized1          (10),
	unauthorized1        (11),
	tobedone1            (12),
	authorized2          (20),
	unauthorized2        (21),
	tobedone2            (22),
	undefined           (254),
	unsupported         (255)
	}
	MAX-ACCESS read-only
	STATUS current
	DESCRIPTION
	"This entry describes the port 
	access control mode status for
	the first host.
	Note, that different states of
	several authentication methods
	are summarized here. They are 
	marked with different multiples 
	of ten as an offset for each mode."
	::= { pacStatusTableEntry 4 }

pacStatUserStatus2 OBJECT-TYPE
	SYNTAX INTEGER
	{
	authorized1          (10),
	unauthorized1        (11),
	tobedone1            (12),
	authorized2          (20),
	unauthorized2        (21),
	tobedone2            (22),
	undefined           (254),
	unsupported         (255)
	}
	MAX-ACCESS read-only
	STATUS current
	DESCRIPTION
	"This entry describes the port 
	access control mode status for
	the second host.
	Note, that different states of
	several authentication methods
	are summarized here. They are 
	marked with different multiples 
	of ten as an offset for each mode."
	::= { pacStatusTableEntry 5 }

pacStatUserStatus3 OBJECT-TYPE
	SYNTAX INTEGER
	{
	authorized1          (10),
	unauthorized1        (11),
	tobedone1            (12),
	authorized2          (20),
	unauthorized2        (21),
	tobedone2            (22),
	undefined           (254),
	unsupported         (255)
	}
	MAX-ACCESS read-only
	STATUS current
	DESCRIPTION
	"This entry describes the port 
	access control mode status for
	the third host.
	Note, that different states of
	several authentication methods
	are summarized here. They are 
	marked with different multiples 
	of ten as an offset for each mode."
	::= { pacStatusTableEntry 6 }

pacStatUserStatus4 OBJECT-TYPE
	SYNTAX INTEGER
	{
	authorized1          (10),
	unauthorized1        (11),
	tobedone1            (12),
	authorized2          (20),
	unauthorized2        (21),
	tobedone2            (22),
	undefined           (254),
	unsupported         (255)
	}
	MAX-ACCESS read-only
	STATUS current
	DESCRIPTION
	"This entry describes the port 
	access control mode status for
	the fourth host.
	Note, that different states of
	several authentication methods
	are summarized here. They are 
	marked with different multiples 
	of ten as an offset for each mode."
	::= { pacStatusTableEntry 7 }

pacStatUserMac1 OBJECT-TYPE
	SYNTAX PhysAddress
	MAX-ACCESS read-only
	STATUS current
	DESCRIPTION
	"This entry contains the 1st host 
	mac address at the selected port 
	if available."
	::= { pacStatusTableEntry 8 }

pacStatUserMac2 OBJECT-TYPE
	SYNTAX PhysAddress
	MAX-ACCESS read-only
	STATUS current
	DESCRIPTION
	"This entry contains the 2nd host 
	mac address at the selected port 
	if available."
	::= { pacStatusTableEntry 9 }

pacStatUserMac3 OBJECT-TYPE
	SYNTAX PhysAddress
	MAX-ACCESS read-only
	STATUS current
	DESCRIPTION
	"This entry contains the 3rd host 
	mac address at the selected port 
	if available."
	::= { pacStatusTableEntry 10 }

pacStatUserMac4 OBJECT-TYPE
	SYNTAX PhysAddress
	MAX-ACCESS read-only
	STATUS current
	DESCRIPTION
	"This entry contains the 4th host 
	mac address at the selected port 
	if available."
	::= { pacStatusTableEntry 11 }

pacStatUserName1 OBJECT-TYPE
	SYNTAX DisplayString (SIZE (0..32))
	MAX-ACCESS read-only
	STATUS current
	DESCRIPTION
	"This entry contains the 1st host 
	user name at the selected port 
	if available."
	::= { pacStatusTableEntry 12 }

pacStatUserName2 OBJECT-TYPE
	SYNTAX DisplayString (SIZE (0..32))
	MAX-ACCESS read-only
	STATUS current
	DESCRIPTION
	"This entry contains the 2nd host 
	user name at the selected port 
	if available."
	::= { pacStatusTableEntry 13 }

pacStatUserName3 OBJECT-TYPE
	SYNTAX DisplayString (SIZE (0..32))
	MAX-ACCESS read-only
	STATUS current
	DESCRIPTION
	"This entry contains the 3rd host 
	user name at the selected port 
	if available."
	::= { pacStatusTableEntry 14 }

pacStatUserName4 OBJECT-TYPE
	SYNTAX DisplayString (SIZE (0..32))
	MAX-ACCESS read-only
	STATUS current
	DESCRIPTION
	"This entry contains the 4th host 
	user name at the selected port 
	if available."
	::= { pacStatusTableEntry 15 }

pacStatUserIp1 OBJECT-TYPE
	SYNTAX IpAddress
	MAX-ACCESS read-only
	STATUS current
	DESCRIPTION
	"This entry contains the 1st host 
	ip address at the selected port 
	if available."
	::= { pacStatusTableEntry 16 }

pacStatUserIp2 OBJECT-TYPE
	SYNTAX IpAddress
	MAX-ACCESS read-only
	STATUS current
	DESCRIPTION
	"This entry contains the 2nd host 
	ip address at the selected port 
	if available."
	::= { pacStatusTableEntry 17 }

pacStatUserIp3 OBJECT-TYPE
	SYNTAX IpAddress
	MAX-ACCESS read-only
	STATUS current
	DESCRIPTION
	"This entry contains the 3rd host 
	ip address at the selected port 
	if available."
	::= { pacStatusTableEntry 18 }

pacStatUserIp4 OBJECT-TYPE
	SYNTAX IpAddress
	MAX-ACCESS read-only
	STATUS current
	DESCRIPTION
	"This entry contains the 4th host 
	ip address at the selected port 
	if available."
	::= { pacStatusTableEntry 19 }

-- port access control config table: ======================
pacConfigTable OBJECT-TYPE
	SYNTAX SEQUENCE OF PacPortConfigList
	MAX-ACCESS not-accessible
	STATUS current
	DESCRIPTION
	"This table contains the port status
	of the port access control feature."
	::= { portaccessctrl 110 }

pacConfigTableEntry OBJECT-TYPE
	SYNTAX PacPortConfigList
	MAX-ACCESS not-accessible
	STATUS current
	DESCRIPTION
	"Entry in the port access control 
	port config table."
	INDEX 
	{ pacConfPortId } ::= { pacConfigTable 1 }

PacPortConfigList ::= SEQUENCE {
	pacConfPortId             INTEGER,
	pacConfMode               INTEGER,
	pacConfMaxMacCount        INTEGER
}

pacConfPortId OBJECT-TYPE
	SYNTAX INTEGER (1..24)
	MAX-ACCESS read-only
	STATUS current
	DESCRIPTION
	"This entry describes the port id."
	::= { pacConfigTableEntry 1 }

pacConfMode OBJECT-TYPE
	SYNTAX INTEGER
	{
	forceAuthorized         (1),
	macLocking              (2),
	radiusMacAuthentication (3),
	ieee8021xAuthentication (4),
	forceUnauthorized       (5),
	parallel8021XMACauth    (6),
	undefined             (254),
	unsupported           (255)
	}
	MAX-ACCESS read-write
	STATUS current
	DESCRIPTION
	"This entry describes the port 
	access control mode ."
	::= { pacConfigTableEntry 2 }

pacConfMaxMacCount OBJECT-TYPE
	SYNTAX INTEGER (1..4)
	MAX-ACCESS read-write
	STATUS current
	DESCRIPTION
	"This entry contains the maximum number of 
	accessible hosts for the selected port if 
	mode is set to 'Radius Authentication' or 
	'ieee 802.1x-Authentication."
	::= { pacConfigTableEntry 3 }

-- port access control status table: ======================
pacMacLockingTable OBJECT-TYPE
	SYNTAX SEQUENCE OF PacPortMacLockList
	MAX-ACCESS not-accessible
	STATUS current
	DESCRIPTION
	"This table contains the port status
	of the port access control feature."
	::= { portaccessctrl 120 }

pacMacLockTableEntry OBJECT-TYPE
	SYNTAX PacPortMacLockList
	MAX-ACCESS not-accessible
	STATUS current
	DESCRIPTION
	"Entry in the port access control 
	port status table."
	INDEX 
	{ pacMacLockPortId } ::= { pacMacLockingTable 1 }

PacPortMacLockList ::= SEQUENCE {
	pacMacLockPortId   INTEGER,
	pacMacLockEnable1  INTEGER,
	pacMacLockEnable2  INTEGER,
	pacMacLockEnable3  INTEGER,
	pacMacLockEnable4  INTEGER,
	pacMacLockLearn1   INTEGER,
	pacMacLockLearn2   INTEGER,
	pacMacLockLearn3   INTEGER,
	pacMacLockLearn4   INTEGER,
	pacLockedMac1      PhysAddress,
	pacLockedMac2      PhysAddress,
	pacLockedMac3      PhysAddress,
	pacLockedMac4      PhysAddress
}

pacMacLockPortId OBJECT-TYPE
	SYNTAX INTEGER (1..24)
	MAX-ACCESS read-only
	STATUS current
	DESCRIPTION
	"This entry describes the port id."
	::= { pacMacLockTableEntry 1 }

pacMacLockEnable1 OBJECT-TYPE
	SYNTAX INTEGER
	{
	enabled        (1),
	disabled       (2),
	unsupported  (255)
	}
	MAX-ACCESS read-write
	STATUS current
	DESCRIPTION
	"This entry describes if the host with
	the 1st locked Mac Address gets access
	to the selected port or not."
	::= { pacMacLockTableEntry 2 }

pacMacLockEnable2 OBJECT-TYPE
	SYNTAX INTEGER
	{
	enabled        (1),
	disabled       (2),
	unsupported  (255)
	}
	MAX-ACCESS read-write
	STATUS current
	DESCRIPTION
	"This entry describes if the host with
	the 2nd locked Mac Address gets access
	to the selected port or not."
	::= { pacMacLockTableEntry 3 }
	
pacMacLockEnable3 OBJECT-TYPE
	SYNTAX INTEGER
	{
	enabled        (1),
	disabled       (2),
	unsupported  (255)
	}
	MAX-ACCESS read-write
	STATUS current
	DESCRIPTION
	"This entry describes if the host with
	the 3rd locked Mac Address gets access
	to the selected port or not."
	::= { pacMacLockTableEntry 4 }

pacMacLockEnable4 OBJECT-TYPE
	SYNTAX INTEGER
	{
	enabled        (1),
	disabled       (2),
	unsupported  (255)
	}
	MAX-ACCESS read-write
	STATUS current
	DESCRIPTION
	"This entry describes if the host with
	the 4th locked Mac Address gets access
	to the selected port or not."
	::= { pacMacLockTableEntry 5 }

pacMacLockLearn1 OBJECT-TYPE
	SYNTAX INTEGER
	{
	learn          (1),
	fixed          (2),
	unsupported  (255)
	}
	MAX-ACCESS read-write
	STATUS current
	DESCRIPTION
	"This entry describes if the 1st 
	Mac Address to lock at the selected port
	has to be learned or if it is fixed."
	::= { pacMacLockTableEntry 6 }

pacMacLockLearn2 OBJECT-TYPE
	SYNTAX INTEGER
	{
	learn          (1),
	fixed          (2),
	unsupported  (255)
	}
	MAX-ACCESS read-write
	STATUS current
	DESCRIPTION
	"This entry describes if the 2nd 
	Mac Address to lock at the selected port
	has to be learned or if it is fixed."
	::= { pacMacLockTableEntry 7 }

pacMacLockLearn3 OBJECT-TYPE
	SYNTAX INTEGER
	{
	learn          (1),
	fixed          (2),
	unsupported  (255)
	}
	MAX-ACCESS read-write
	STATUS current
	DESCRIPTION
	"This entry describes if the 3rd 
	Mac Address to lock at the selected port
	has to be learned or if it is fixed."
	::= { pacMacLockTableEntry 8 }

pacMacLockLearn4 OBJECT-TYPE
	SYNTAX INTEGER
	{
	learn          (1),
	fixed          (2),
	unsupported  (255)
	}
	MAX-ACCESS read-write
	STATUS current
	DESCRIPTION
	"This entry describes if the 4th 
	Mac Address to lock at the selected port
	has to be learned or if it is fixed."
	::= { pacMacLockTableEntry 9 }

pacLockedMac1 OBJECT-TYPE
	SYNTAX PhysAddress
	MAX-ACCESS read-write
	STATUS current
	DESCRIPTION
	"This entry contains the 1st 
	locked mac address at 
	the selected port."
	::= { pacMacLockTableEntry 10 }

pacLockedMac2 OBJECT-TYPE
	SYNTAX PhysAddress
	MAX-ACCESS read-write
	STATUS current
	DESCRIPTION
	"This entry contains the 2nd 
	locked mac address at 
	the selected port."
	::= { pacMacLockTableEntry 11 }

pacLockedMac3 OBJECT-TYPE
	SYNTAX PhysAddress
	MAX-ACCESS read-write
	STATUS current
	DESCRIPTION
	"This entry contains the 3rd 
	locked mac address at 
	the selected port."
	::= { pacMacLockTableEntry 12 }

pacLockedMac4 OBJECT-TYPE
	SYNTAX PhysAddress
	MAX-ACCESS read-write
	STATUS current
	DESCRIPTION
	"This entry contains the 4th 
	locked mac address at 
	the selected port."
	::= { pacMacLockTableEntry 13 }



-- igmps group: =====================================================
igmps OBJECT IDENTIFIER ::= { mib3 13 }

igmpsSupport OBJECT-TYPE
	SYNTAX INTEGER
	{
	supported      (1),
	unsupported  (255)
	}
	MAX-ACCESS read-only
	STATUS current
	DESCRIPTION
	"This entry contains the information if
	IGMP Snooping is supported or not."
	::= { igmps 1 }

igmpsEnable OBJECT-TYPE
	SYNTAX INTEGER
	{
	enabled        (1),
	disabled       (2),
	unsupported  (255)
	}
	MAX-ACCESS read-write
	STATUS current
	DESCRIPTION
	"This entry enables or disables the 
	IGMP Snooping feature."
	::= { igmps 2 }

igmpsFastLeave OBJECT-TYPE
	SYNTAX INTEGER
	{
	enabled        (1),
	disabled       (2),
	unsupported  (255)
	}
	MAX-ACCESS read-write
	STATUS current
	DESCRIPTION
	"This entry enables or disables the 
	Fast Leave feature."
	::= { igmps 3 }

igmpsReportAggregation OBJECT-TYPE
	SYNTAX INTEGER
	{
	enabled        (1),
	disabled       (2),
	unsupported  (255)
	}
	MAX-ACCESS read-write
	STATUS current
	DESCRIPTION
	"This entry enables or disables the 
	Report Aggregation feature."
	::= { igmps 4 }

igmpsFloodingUnregPack OBJECT-TYPE
	SYNTAX INTEGER
	{
	enabled        (1),
	disabled       (2),
	unsupported  (255)
	}
	MAX-ACCESS read-write
	STATUS current
	DESCRIPTION
	"This entry enables or disables the 
	Flooding Unregister Packet feature."
	::= { igmps 5 }

igmpsMaxGroupLimit OBJECT-TYPE
	SYNTAX INTEGER
	MAX-ACCESS read-only
	STATUS current
	DESCRIPTION
	"This entry defines the maximum 
	value for the Group Limit."
	::= { igmps 6 }

igmpsGroupLimit OBJECT-TYPE
	SYNTAX INTEGER
	MAX-ACCESS read-write
	STATUS current
	DESCRIPTION
	"This entry defines the Multicast 
	Group Limit. The maximum valid value 
	is defined in igmpsMaxGroupLimit."
	::= { igmps 7 }

igmpsGroupNumber OBJECT-TYPE
	SYNTAX INTEGER
	MAX-ACCESS read-only
	STATUS current
	DESCRIPTION
	"This entry defines the present 
	number of Multicast Groups."
	::= { igmps 8 }

igmpsRouterDetection OBJECT-TYPE
	SYNTAX INTEGER
	{
	discovery      (1),
	query          (2),
	unsupported  (255)
	}
	MAX-ACCESS read-write
	STATUS current
	DESCRIPTION
	"This entry defines the mode of
	Multicast Router detection."
	::= { igmps 9 }

igmpsGroupMembershipInterval OBJECT-TYPE
	SYNTAX INTEGER (200..1000)
	MAX-ACCESS read-write
	STATUS current
	DESCRIPTION
	"This entry defines the Multicast
	Group Membersip Interval in 
	multiples of a second.
	The default value is 260."
	::= { igmps 10 }

igmpsMaximumResposeTime OBJECT-TYPE
	SYNTAX INTEGER (1..25)
	MAX-ACCESS read-write
	STATUS current
	DESCRIPTION
	"This entry defines the Multicast
	Group Maximum Response Time in 
	multiples of a second.
	The default value is 10."
	::= { igmps 11 }

igmpsLastMemeberQueryTime OBJECT-TYPE
	SYNTAX INTEGER (1..175)
	MAX-ACCESS read-write
	STATUS current
	DESCRIPTION
	"This entry defines the Multicast
	Group Last Member Query Time in 
	multiples of a second.
	The default value is 2."
	::= { igmps 12 }

igmpsNeighborDeadInterval OBJECT-TYPE
	SYNTAX INTEGER (12..554)
	MAX-ACCESS read-write
	STATUS current
	DESCRIPTION
	"This entry defines the Multicast
	Router Neighbor Dead Interval in 
	multiples of a second.
	The default value is 62."
	::= { igmps 13 }

igmpsRouterAgingTime OBJECT-TYPE
	SYNTAX INTEGER (200..1000)
	MAX-ACCESS read-write
	STATUS current
	DESCRIPTION
	"This entry defines the Multicast
	Router Aging Time in multiples 
	of a second.
	The default value is 260."
	::= { igmps 14 }

igmpsRxMessageGeneralQuery OBJECT-TYPE
	SYNTAX INTEGER
	MAX-ACCESS read-only
	STATUS current
	DESCRIPTION
	"This is a counter for received 
	General Query Messages."
	::= { igmps 15 }

igmpsRxMessageSpecificQuery OBJECT-TYPE
	SYNTAX INTEGER
	MAX-ACCESS read-only
	STATUS current
	DESCRIPTION
	"This is a counter for received 
	Group Specific Query Messages."
	::= { igmps 16 }

igmpsRxMessageReport OBJECT-TYPE
	SYNTAX INTEGER
	MAX-ACCESS read-only
	STATUS current
	DESCRIPTION
	"This is a counter for received 
	Report Messages."
	::= { igmps 17 }

igmpsRxMessageLeave OBJECT-TYPE
	SYNTAX INTEGER
	MAX-ACCESS read-only
	STATUS current
	DESCRIPTION
	"This is a counter for received 
	Leave Messages."
	::= { igmps 18 }

igmpsRxMessageAdvertisement OBJECT-TYPE
	SYNTAX INTEGER
	MAX-ACCESS read-only
	STATUS current
	DESCRIPTION
	"This is a counter for received 
	Advertisement Messages."
	::= { igmps 19 }

igmpsRxMessageTermination OBJECT-TYPE
	SYNTAX INTEGER
	MAX-ACCESS read-only
	STATUS current
	DESCRIPTION
	"This is a counter for received 
	Termination Messages."
	::= { igmps 20 }

igmpsTxMessageSolicitation OBJECT-TYPE
	SYNTAX INTEGER
	MAX-ACCESS read-only
	STATUS current
	DESCRIPTION
	"This is a counter for transmitted 
	Solicitation Messages."
	::= { igmps 21 }

igmpsCounterReset OBJECT-TYPE
	SYNTAX INTEGER
	{
	normalOperation (0),
	reset           (1),
	unsupported   (255)
	}
	MAX-ACCESS read-write
	STATUS current
	DESCRIPTION
	"Set this entry to '1' to reset the 
	IGMPS packet counters. 
	This entry is self clearing."
	::= { igmps 22 }

-- igmps port value table: ================================
igmpsPortTable OBJECT-TYPE
	SYNTAX SEQUENCE OF IgmpsPortList
	MAX-ACCESS not-accessible
	STATUS current
	DESCRIPTION
	"This table contains port status information 
	of the device."
	::= { igmps 30 }

igmpsPortTableEntry OBJECT-TYPE
	SYNTAX IgmpsPortList
	MAX-ACCESS not-accessible
	STATUS current
	DESCRIPTION
	"Entry in the port value table."
	INDEX 
	{ igmpsPortId } ::= { igmpsPortTable 1 }

IgmpsPortList ::= SEQUENCE {
	igmpsPortId               INTEGER,
	igmpsPortSnooping         INTEGER,
	igmpsPortStaticRouter     INTEGER,
	igmpsPortDynamicRouter    INTEGER
}

igmpsPortId OBJECT-TYPE
	SYNTAX INTEGER (1..24)
	MAX-ACCESS read-only
	STATUS current
	DESCRIPTION
	"This entry describes the port id."
	::= { igmpsPortTableEntry 1 }

igmpsPortSnooping OBJECT-TYPE
	SYNTAX  INTEGER
	{
	enabled           (1),
	disabled          (2),
	unsupported     (255)
	}
	MAX-ACCESS read-write
	STATUS current
	DESCRIPTION
	"This entry determines if the port
	is enabled for IGMP Snooping or
	not (if supported)."
	::= { igmpsPortTableEntry 2 }

igmpsPortStaticRouter OBJECT-TYPE
	SYNTAX  INTEGER
	{
	enabled           (1),
	disabled          (2),
	unsupported     (255)
	}
	MAX-ACCESS read-write
	STATUS current
	DESCRIPTION
	"This entry determins if the port 
	is defined as static router port or
	not (if supported)."
	::= { igmpsPortTableEntry 3 }

igmpsPortDynamicRouter OBJECT-TYPE
	SYNTAX  INTEGER
	{
	detected          (1),
	undetected        (2),
	unsupported     (255)
	}
	MAX-ACCESS read-only
	STATUS current
	DESCRIPTION
	"This entry ddocuments if a router 
	has been detected at this port or
	not (if supported)."
	::= { igmpsPortTableEntry 4 }

-- IGMPs Multicast Group table: ===========================
igmpsGroupTable OBJECT-TYPE
	SYNTAX SEQUENCE OF IgmpsGroupList
	MAX-ACCESS not-accessible
	STATUS current
	DESCRIPTION
	"This table contains port status information 
	of the device."
	::= { igmps 40 }

igmpsGroupTableEntry OBJECT-TYPE
	SYNTAX IgmpsGroupList
	MAX-ACCESS not-accessible
	STATUS current
	DESCRIPTION
	"Entry in the port value table."
	INDEX 
	{ igmpsGroupId } ::= { igmpsGroupTable 1 }

IgmpsGroupList ::= SEQUENCE {
	igmpsGroupId               Unsigned32,
	igmpsGroupMac              PhysAddress,
	igmpsGroupVlanId           INTEGER,
	igmpsGroupTimestamp        INTEGER,
	igmpsGroupLeaveFlag        INTEGER,
	igmpsGroupMemberPort1      INTEGER,
	igmpsGroupMemberPort2      INTEGER,
	igmpsGroupMemberPort3      INTEGER,
	igmpsGroupMemberPort4      INTEGER,
	igmpsGroupMemberPort5      INTEGER,
	igmpsGroupMemberPort6      INTEGER,
	igmpsGroupMemberPort7      INTEGER,
	igmpsGroupMemberPort8      INTEGER,
	igmpsGroupMemberPort9      INTEGER,
	igmpsGroupMemberPort10     INTEGER,
	igmpsGroupMemberPort11     INTEGER,
	igmpsGroupMemberPort12     INTEGER,
	igmpsGroupMemberPort13     INTEGER,
	igmpsGroupMemberPort14     INTEGER,
	igmpsGroupMemberPort15     INTEGER,
	igmpsGroupMemberPort16     INTEGER,
	igmpsGroupMemberPort17     INTEGER,
	igmpsGroupMemberPort18     INTEGER,
	igmpsGroupMemberPort19     INTEGER,
	igmpsGroupMemberPort20     INTEGER,
	igmpsGroupMemberPort21     INTEGER,
	igmpsGroupMemberPort22     INTEGER,
	igmpsGroupMemberPort23     INTEGER,
	igmpsGroupMemberPort24     INTEGER
}


igmpsGroupId OBJECT-TYPE
	SYNTAX Unsigned32
	MAX-ACCESS read-only
	STATUS current
	DESCRIPTION
	"This entry describes the Multicast 
	Group id."
	::= { igmpsGroupTableEntry 1 }

igmpsGroupMac OBJECT-TYPE
	SYNTAX PhysAddress
	MAX-ACCESS read-only
	STATUS current
	DESCRIPTION
	"This entry documents the Multicast Group's 
	MAC-Address."
	::= { igmpsGroupTableEntry 2 }

igmpsGroupVlanId OBJECT-TYPE
	SYNTAX  INTEGER
	MAX-ACCESS read-only
	STATUS current
	DESCRIPTION
	"This entry documents the Vlan ID 
	of the Multicast Group."
	::= { igmpsGroupTableEntry 3 }

igmpsGroupTimestamp OBJECT-TYPE
	SYNTAX  INTEGER
	MAX-ACCESS read-only
	STATUS current
	DESCRIPTION
	"This entry documents the Timestamp 
	of the Multicast Group in seconds."
	::= { igmpsGroupTableEntry 4 }

igmpsGroupLeaveFlag OBJECT-TYPE
	SYNTAX  INTEGER
	{
	set             (1),
	unset           (2),
	unsupported   (255)
	}
	MAX-ACCESS read-only
	STATUS current
	DESCRIPTION
	"This entry documents if the Leave
	Flag has been set or not."
	::= { igmpsGroupTableEntry 5 }

igmpsGroupMemberPort1 OBJECT-TYPE
	SYNTAX INTEGER
	{
	yes            (1),
	no             (2),
	unsupported  (255)
	}
	MAX-ACCESS read-only
	STATUS current
	DESCRIPTION
	"This entry defines the membership of 
	port 1 to the Multicast Group."
	::= { igmpsGroupTableEntry 6 }

igmpsGroupMemberPort2 OBJECT-TYPE
	SYNTAX INTEGER
	{
	yes            (1),
	no             (2),
	unsupported  (255)
	}
	MAX-ACCESS read-only
	STATUS current
	DESCRIPTION
	"This entry defines the membership of 
	port 2 to the Multicast Group."
	::= { igmpsGroupTableEntry 7 }

igmpsGroupMemberPort3 OBJECT-TYPE
	SYNTAX INTEGER
	{
	yes            (1),
	no             (2),
	unsupported  (255)
	}
	MAX-ACCESS read-only
	STATUS current
	DESCRIPTION
	"This entry defines the membership of 
	port 3 to the Multicast Group."
	::= { igmpsGroupTableEntry 8 }

igmpsGroupMemberPort4 OBJECT-TYPE
	SYNTAX INTEGER
	{
	yes            (1),
	no             (2),
	unsupported  (255)
	}
	MAX-ACCESS read-only
	STATUS current
	DESCRIPTION
	"This entry defines the membership of 
	port 4 to the Multicast Group."
	::= { igmpsGroupTableEntry 9 }

igmpsGroupMemberPort5 OBJECT-TYPE
	SYNTAX INTEGER
	{
	yes            (1),
	no             (2),
	unsupported  (255)
	}
	MAX-ACCESS read-only
	STATUS current
	DESCRIPTION
	"This entry defines the membership of 
	port 5 to the Multicast Group."
	::= { igmpsGroupTableEntry 10 }

igmpsGroupMemberPort6 OBJECT-TYPE
	SYNTAX INTEGER
	{
	yes            (1),
	no             (2),
	unsupported  (255)
	}
	MAX-ACCESS read-only
	STATUS current
	DESCRIPTION
	"This entry defines the membership of 
	port 6 to the Multicast Group."
	::= { igmpsGroupTableEntry 11 }

igmpsGroupMemberPort7 OBJECT-TYPE
	SYNTAX INTEGER
	{
	yes            (1),
	no             (2),
	unsupported  (255)
	}
	MAX-ACCESS read-only
	STATUS current
	DESCRIPTION
	"This entry defines the membership of 
	port 7 to the Multicast Group."
	::= { igmpsGroupTableEntry 12 }

igmpsGroupMemberPort8 OBJECT-TYPE
	SYNTAX INTEGER
	{
	yes            (1),
	no             (2),
	unsupported  (255)
	}
	MAX-ACCESS read-only
	STATUS current
	DESCRIPTION
	"This entry defines the membership of 
	port 8 to the Multicast Group."
	::= { igmpsGroupTableEntry 13 }

igmpsGroupMemberPort9 OBJECT-TYPE
	SYNTAX INTEGER
	{
	yes            (1),
	no             (2),
	unsupported  (255)
	}
	MAX-ACCESS read-only
	STATUS current
	DESCRIPTION
	"This entry defines the membership of 
	port 9 to the Multicast Group."
	::= { igmpsGroupTableEntry 14 }

igmpsGroupMemberPort10 OBJECT-TYPE
	SYNTAX INTEGER
	{
	yes            (1),
	no             (2),
	unsupported  (255)
	}
	MAX-ACCESS read-only
	STATUS current
	DESCRIPTION
	"This entry defines the membership of 
	port 10 to the Multicast Group."
	::= { igmpsGroupTableEntry 15 }

igmpsGroupMemberPort11 OBJECT-TYPE
	SYNTAX INTEGER
	{
	yes            (1),
	no             (2),
	unsupported  (255)
	}
	MAX-ACCESS read-only
	STATUS current
	DESCRIPTION
	"This entry defines the membership of 
	port 11 to the Multicast Group."
	::= { igmpsGroupTableEntry 16 }

igmpsGroupMemberPort12 OBJECT-TYPE
	SYNTAX INTEGER
	{
	yes            (1),
	no             (2),
	unsupported  (255)
	}
	MAX-ACCESS read-only
	STATUS current
	DESCRIPTION
	"This entry defines the membership of 
	port 12 to the Multicast Group."
	::= { igmpsGroupTableEntry 17 }

igmpsGroupMemberPort13 OBJECT-TYPE
	SYNTAX INTEGER
	{
	yes            (1),
	no             (2),
	unsupported  (255)
	}
	MAX-ACCESS read-only
	STATUS current
	DESCRIPTION
	"This entry defines the membership of 
	port 13 to the Multicast Group."
	::= { igmpsGroupTableEntry 18 }

igmpsGroupMemberPort14 OBJECT-TYPE
	SYNTAX INTEGER
	{
	yes            (1),
	no             (2),
	unsupported  (255)
	}
	MAX-ACCESS read-only
	STATUS current
	DESCRIPTION
	"This entry defines the membership of 
	port 14 to the Multicast Group."
	::= { igmpsGroupTableEntry 19 }

igmpsGroupMemberPort15 OBJECT-TYPE
	SYNTAX INTEGER
	{
	yes            (1),
	no             (2),
	unsupported  (255)
	}
	MAX-ACCESS read-only
	STATUS current
	DESCRIPTION
	"This entry defines the membership of 
	port 15 to the Multicast Group."
	::= { igmpsGroupTableEntry 20 }

igmpsGroupMemberPort16 OBJECT-TYPE
	SYNTAX INTEGER
	{
	yes            (1),
	no             (2),
	unsupported  (255)
	}
	MAX-ACCESS read-only
	STATUS current
	DESCRIPTION
	"This entry defines the membership of 
	port 16 to the Multicast Group."
	::= { igmpsGroupTableEntry 21 }

igmpsGroupMemberPort17 OBJECT-TYPE
	SYNTAX INTEGER
	{
	yes            (1),
	no             (2),
	unsupported  (255)
	}
	MAX-ACCESS read-only
	STATUS current
	DESCRIPTION
	"This entry defines the membership of 
	port 17 to the Multicast Group."
	::= { igmpsGroupTableEntry 22 }

igmpsGroupMemberPort18 OBJECT-TYPE
	SYNTAX INTEGER
	{
	yes            (1),
	no             (2),
	unsupported  (255)
	}
	MAX-ACCESS read-only
	STATUS current
	DESCRIPTION
	"This entry defines the membership of 
	port 18 to the Multicast Group."
	::= { igmpsGroupTableEntry 23 }

igmpsGroupMemberPort19 OBJECT-TYPE
	SYNTAX INTEGER
	{
	yes            (1),
	no             (2),
	unsupported  (255)
	}
	MAX-ACCESS read-only
	STATUS current
	DESCRIPTION
	"This entry defines the membership of 
	port 19 to the Multicast Group."
	::= { igmpsGroupTableEntry 24 }

igmpsGroupMemberPort20 OBJECT-TYPE
	SYNTAX INTEGER
	{
	yes            (1),
	no             (2),
	unsupported  (255)
	}
	MAX-ACCESS read-only
	STATUS current
	DESCRIPTION
	"This entry defines the membership of 
	port 20 to the Multicast Group."
	::= { igmpsGroupTableEntry 25 }

igmpsGroupMemberPort21 OBJECT-TYPE
	SYNTAX INTEGER
	{
	yes            (1),
	no             (2),
	unsupported  (255)
	}
	MAX-ACCESS read-only
	STATUS current
	DESCRIPTION
	"This entry defines the membership of 
	port 21 to the Multicast Group."
	::= { igmpsGroupTableEntry 26 }

igmpsGroupMemberPort22 OBJECT-TYPE
	SYNTAX INTEGER
	{
	yes            (1),
	no             (2),
	unsupported  (255)
	}
	MAX-ACCESS read-only
	STATUS current
	DESCRIPTION
	"This entry defines the membership of 
	port 22 to the Multicast Group."
	::= { igmpsGroupTableEntry 27 }

igmpsGroupMemberPort23 OBJECT-TYPE
	SYNTAX INTEGER
	{
	yes            (1),
	no             (2),
	unsupported  (255)
	}
	MAX-ACCESS read-only
	STATUS current
	DESCRIPTION
	"This entry defines the membership of 
	port 23 to the Multicast Group."
	::= { igmpsGroupTableEntry 28 }

igmpsGroupMemberPort24 OBJECT-TYPE
	SYNTAX INTEGER
	{
	yes            (1),
	no             (2),
	unsupported  (255)
	}
	MAX-ACCESS read-only
	STATUS current
	DESCRIPTION
	"This entry defines the membership of 
	port 24 to the Multicast Group."
	::= { igmpsGroupTableEntry 29 }


-- rtc group: ======================================================
rtc OBJECT IDENTIFIER ::= { mib3 15 }

rtcSupport OBJECT-TYPE
	SYNTAX INTEGER
	{
	supported      (1),
	unsupported  (255)
	}
	MAX-ACCESS read-only
	STATUS current
	DESCRIPTION
	"This entry contains the information if
	software based real time clock 
	is supported or not."
	::= { rtc 1 }

rtcFlags OBJECT-TYPE
	SYNTAX INTEGER
	{
	sntpenabled   (1),
	dstenabled    (2),
	unsupported  (255)
	}
	MAX-ACCESS read-write
	STATUS current
	DESCRIPTION
	"This Entry contains per port some bitwise 
	rtc settings:
	Bit 0: if set rtc should be synchronized
	       with configured SNTP server
	Bit 1: is set if DST support is enabled"
	::= { rtc 2 }

rtcLocalTime OBJECT-TYPE
	SYNTAX DisplayString (SIZE (25))
	MAX-ACCESS read-only
	STATUS current
	DESCRIPTION
	"This entry contains the local date 
	and time information. Used format conforms
	to RFC2068 like example below:
	Mon Jun 21 17:20:34 2010"
	::= { rtc 3 }

rtcManualTime OBJECT-TYPE
	SYNTAX DisplayString (SIZE (25))
	MAX-ACCESS read-write
	STATUS current
	DESCRIPTION
	"On readout this entry contains the local 
	date and time information. Writing to this 
	entry sets the the date and time information
	of the device manually. Used format is
	'DD.MM.YYYY HH:MM:SS'"
	::= { rtc 4 }

rtcTimeStatus OBJECT-TYPE
	SYNTAX INTEGER
	{
	unset           (1),
	manuallyset     (2),
	synchronized    (3),
	unsynchronized  (4),
	unsupported   (255)
	}
	MAX-ACCESS read-only
	STATUS current
	DESCRIPTION
	"This entry contains the information 
	about the reliability of the date and 
	time information of the device."
	::= { rtc 5 }

rtcTimezoneOffset OBJECT-TYPE
	SYNTAX INTEGER (-24..24)
	MAX-ACCESS read-write
	STATUS current
	DESCRIPTION
	"This entry describes the time offset to UTC 
	regarding the timezone of the device. The units 
	of this entry are multiples of 30 minutes."
	::= { rtc 6 }

rtcDSTOffset OBJECT-TYPE
	SYNTAX INTEGER (10..120)
	MAX-ACCESS read-write
	STATUS current
	DESCRIPTION
	"This entry describes the time offset to UTC 
	regarding the timezone of the device. This 
	entry is measured in minutes."
	::= { rtc 7 }

rtcDSTbegin OBJECT-TYPE
	SYNTAX OCTET STRING (SIZE (8))
	MAX-ACCESS read-write
	STATUS current
	DESCRIPTION
	"This entry contains the hexadecimal represenation 
	of the proprietary coded time of the beginning of 
	DST period. See corresponding feature description 
	for detailed information."
	::= { rtc 8 }

rtcDSTend OBJECT-TYPE
	SYNTAX OCTET STRING (SIZE (8))
	MAX-ACCESS read-write
	STATUS current
	DESCRIPTION
	"This entry contains the hexadecimal represenation 
	of the proprietary coded time of the end of DST 
	period. See corresponding feature description for 
	detailed information."
	::= { rtc 9 }

rtcDSTstatus OBJECT-TYPE
	SYNTAX INTEGER
	{
	isdst           (1),
	isnotdst        (2),
	unsupported   (255)
	}
	MAX-ACCESS read-only
	STATUS current
	DESCRIPTION
	"If DST support is enabled this entry 
	contains the information if DST period 
	is active now(1) or not(2). Else a value
	of 255 will be read out."
	::= { rtc 10 }

rtcSNTPsyncInterval OBJECT-TYPE
	SYNTAX INTEGER
	MAX-ACCESS read-write
	STATUS current
	DESCRIPTION
	"This entry describes the time interval 
	for repeated to synchronisation of the 
	device with a given SNTP server if this 
	feature is enabled. This value is measured 
	in minutes. It should not be set too small 
	to avoid server overload in larger networks.
	A typical value should be 10080 which 
	represents once a week."
	::= { rtc 11 }

rtcSNTPsyncNow OBJECT-TYPE
	SYNTAX INTEGER
	{
	normalOperation (0),
	syncNow         (1),
	unsupported   (255)
	}
	MAX-ACCESS read-write
	STATUS current
	DESCRIPTION
	"Set this entry to '1' to trigger a rtc 
	sychronisation with SNTP server now.
	This entry is self clearing."
	::= { rtc 12 }

rtcSNTPServerCount OBJECT-TYPE
	SYNTAX INTEGER (0..4)
	MAX-ACCESS read-only
	STATUS current
	DESCRIPTION
	"The number of supported SNTP servers 
	on this system."
	::= { rtc 13 }

-- rtc SNTP server table: ==============================
rtcSNTPServerTable OBJECT-TYPE
	SYNTAX SEQUENCE OF SNTPServerList
	MAX-ACCESS not-accessible
	STATUS current
	DESCRIPTION
	"This table contains the configuration for 
	several SNTP servers."
	::= { rtc 20 }

rtcSNTPServerTableEntry OBJECT-TYPE
	SYNTAX SNTPServerList
	MAX-ACCESS not-accessible
	STATUS current
	DESCRIPTION
	"Entry in the SNTP server table."
	INDEX 
	{ rtcSNTPServerId } ::= { rtcSNTPServerTable 1 }

SNTPServerList ::= SEQUENCE {
	rtcSNTPServerId            INTEGER,
	rtcSNTPServerStatus        INTEGER,
	rtcSNTPServerEnable        INTEGER,
	rtcSNTPServerIpv4Address   IpAddress
}

rtcSNTPServerId OBJECT-TYPE
	SYNTAX INTEGER (1..4)
	MAX-ACCESS read-only
	STATUS current
	DESCRIPTION
	"This entry contains the SNTP server ID."
	::= { rtcSNTPServerTableEntry 1 }

rtcSNTPServerStatus OBJECT-TYPE
	SYNTAX INTEGER
	{
	ok             (0),
	busy           (1),
	timeout        (2),
	nomemory       (3),
	portbusy       (4),
	alarm          (5),
	unknown        (7),
	unsupported  (255)
	}
	MAX-ACCESS read-only
	STATUS current
	DESCRIPTION
	"This entry describes the SNTP server 
	status as retransmitted after sync."
	::= { rtcSNTPServerTableEntry 2 }

rtcSNTPServerEnable OBJECT-TYPE
	SYNTAX INTEGER
	{
	enabled        (1),
	disabled       (2),
	unsupported  (255)
	}
	MAX-ACCESS read-write
	STATUS current
	DESCRIPTION
	"This entry describes the SNTP server 
	enable status."
	::= { rtcSNTPServerTableEntry 3 }

rtcSNTPServerIpv4Address OBJECT-TYPE
	SYNTAX IpAddress
	MAX-ACCESS read-write
	STATUS current
	DESCRIPTION
	"This entry describes the SNTP
	server IPv4 address."
	::= { rtcSNTPServerTableEntry 4 }


-- console interface group: ==========================================
consoleinterface OBJECT IDENTIFIER ::= { mib3 20 }

consoleSupport OBJECT-TYPE
	SYNTAX INTEGER (0..3)
	--telnet      (1),
	--ssh         (2)
	MAX-ACCESS read-only
	STATUS current
	DESCRIPTION
	"This entry contains the bitwise information 
	which console version is supported. 
	Bit 0: Telnet supported
	Bit 1: SSH supported"
	::= { consoleinterface 1 }

consoleEnable OBJECT-TYPE
	SYNTAX INTEGER (0..3)
	--telnet      (1),
	--ssh         (2)
	MAX-ACCESS read-write
	STATUS current
	DESCRIPTION
	"This entry contains the bitwise information 
	which console version is enabled. 
	Bit 0: Telnet enabled
	Bit 1: SSH enabled
	Changing this entry takes effect after reset."
	::= { consoleinterface 2 }

consoleTimeout OBJECT-TYPE
	SYNTAX INTEGER
	MAX-ACCESS read-write
	STATUS current
	DESCRIPTION
	"This entry describes the timout value in 
	multiples of a second. This is the period 
	of inactivity after which the telnet 
	connection shuts down automatically."
	::= { consoleinterface 3 }

consoleApplyMode OBJECT-TYPE
	SYNTAX  INTEGER
	{
	applyAndSaveImmediately (1),
	saveManually            (2),
	applyAndSaveManually    (3)
	}
	MAX-ACCESS read-write
	STATUS current
	DESCRIPTION
	"If this entry is set to '1' changes due 
	to 'set...' commands are immediately applied 
	to the switch and saved in the configuration. 
	If it is set to '2' changes are also applied 
	immediately but the changed configuration 
	will not be saved. If it is set to '3' 
	changes are neither applied to the switch 
	nor the configuration is saved. 
	Using the 'save settings' command at the 
	telnet console the configuration will be 
	applied and saved.
	After a reset this value is always set to 
	the default value of 2 (saveManually)."
	::= { consoleinterface 4 }

consolePrompt OBJECT-TYPE
	SYNTAX DisplayString (SIZE (0..15))
	MAX-ACCESS read-write
	STATUS current
	DESCRIPTION
	"This is the string used as prompt
	for the telnet console."
	::= { consoleinterface 5 }



-- web interface group: =============================================
webinterface OBJECT IDENTIFIER ::= { mib3 21 }

webSupport OBJECT-TYPE
	SYNTAX INTEGER (0..3)
	--http      (1),
	--https     (2)
	MAX-ACCESS read-only
	STATUS current
	DESCRIPTION
	"This entry contains the bitwise information 
	which web interface version is supported. 
	Bit 0: HTTP supported
	Bit 1: HTTPS supported"
	::= { webinterface 1 }


webEnable OBJECT-TYPE
	SYNTAX INTEGER (0..3)
	--http      (1),
	--https     (2)
	MAX-ACCESS read-write
	STATUS current
	DESCRIPTION
	"This entry contains the bitwise information 
	which  web interface version is enabled. 
	Bit 0: HTTP enabled
	Bit 1: HTTPS enabled
	Changing this entry takes effect after reset."
	::= { webinterface 2 }



-- snmp interface group: ============================================
snmpinterface OBJECT IDENTIFIER ::= { mib3 22 }

snmpSupport OBJECT-TYPE
	SYNTAX INTEGER (0..7)
	--supportv1      (1),
	--supportv2c     (2),
	--supportv3      (4)
	MAX-ACCESS read-only
	STATUS current
	DESCRIPTION
	"This entry contains the bitwise information 
	which SNMP version is supported. 
	Bit 0: SNMP v1 supported
	Bit 1: SNMP v2c supported
	Bit 2: SNMP v3 supported"
	::= { snmpinterface 1 }

snmpEnable OBJECT-TYPE
	SYNTAX INTEGER (0..7)
	--enablev1        (1),
	--enablev2c       (2),
	--enablev3        (4),
	MAX-ACCESS read-write
	STATUS current
	DESCRIPTION
	"This entry contains the bitwise information 
	which SNMP version is enabled.
	Bit 0: SNMP v1 enabled
	Bit 1: SNMP v2c enabled
	Bit 2: SNMP v3 enabled
	It is not allowed to disable an interface via 
	itself or to support v1/v2c at the same time 
	as v3 is enabled. So v1 or v2c can only be 
	enabled via this entry if v3 is disabled.
	Further changes have to be done via another 
	Interface."
	::= { snmpinterface 2 }

snmpApplyMode OBJECT-TYPE
	SYNTAX INTEGER
	{
	applyAndSaveImmediately (1),
	saveManually            (2),
	applyAndSaveManually    (3)
	}
	MAX-ACCESS read-write
	STATUS current
	DESCRIPTION
	"If this entry is set to '1' changes due 
	to 'set...' commands are immediately applied 
	to the switch and saved in the configuration.
	If it is set to '2' changed are also applied 
	immedately but the changed configuration will 
	not be saved. So changes are lost after a 
	reset. To save the configuration an additional 
	self clearing 'snmpApply' has to be set to '1'
	for an apply without save or set to '2' for an
	apply including save.
	After a reset this value is always set to the
	default value of 1 (applyAndSaveImmediately)."
	::= { snmpinterface 3 }

snmpApply OBJECT-TYPE
	SYNTAX  INTEGER
	{
	normalOperation (0),
	applyNow        (1),
	applyAndSaveNow (2)
	}
	MAX-ACCESS read-write
	STATUS current
	DESCRIPTION
	"This entry only has an effect if 'snmpApplyMode'
	is not set to '1', which is the normal operation.
	In this case the changed configuration will be 
	applied to the switch (if set to '1') or applied 
	to switch and saved to flash (if set to '2').
	This entry is self-clearing."
	::= { snmpinterface 4 }

snmpTrapTest OBJECT-TYPE
	SYNTAX INTEGER
	{
	inactive                (0),
	genColdstart            (1),
	genWarmstart            (2),
	genLinkdown             (3),
	genLinkup               (4),
	genAuthfailure          (5),
	genEgpneighborloss      (6),
	entLinkchange           (7),
	entFactoryreset         (8),
	entTemplevelchange      (9),
	entErrorcounter        (10),
	entOverundervoltage    (11),
	entTempshutdown        (12),
	entPoelimitexceeded    (13),
	entSupplystatuschange  (14),
	entSfpplugchange       (15),
	entLoginfailure        (16),
	entRingbroken          (17),
	entRingalarm           (18),
	entAuthpwfail          (19),
	entPrivpwfail          (20),
	entAccesspermission    (21),
	entSeclevelfail        (22),
	unsupported           (255)
	}
	MAX-ACCESS read-write
	STATUS current
	DESCRIPTION
	"This entry triggers a trap event without 
	the regarding system event took place. 
	No change to the device will be done.
	This entry can be used to test the trap 
	destination configuration.
	This entry is self clearing."
	::= { snmpinterface 5 }

snmpTrapDestCount OBJECT-TYPE
	SYNTAX INTEGER
	MAX-ACCESS read-only
	STATUS current
	DESCRIPTION
	"The number of supported trap destinations 
	on this system."
	::= { snmpinterface 6 }

snmpCommunityRead OBJECT-TYPE
	SYNTAX DisplayString (SIZE (0..16))
	MAX-ACCESS read-write
	STATUS current
	DESCRIPTION
	"This is the string used as community name
	in SNMP Get and GetNext requests."
	::= { snmpinterface 7 }

snmpCommunityWrite OBJECT-TYPE
	SYNTAX DisplayString (SIZE (0..16))
	MAX-ACCESS read-write
	STATUS current
	DESCRIPTION
	"This is the string used as community name
	in SNMP Set operations."
	::= { snmpinterface 8 }

snmpTrapEnable OBJECT-TYPE
	SYNTAX INTEGER
	{
	enabled        (1),
	disabled       (2),
	unsupported  (255)
	}
	MAX-ACCESS read-write
	STATUS current
	DESCRIPTION
	"This entry contains the information if
	snmp traps are globally enabled or not."
	::= { snmpinterface 9 }

snmpTrapDestTable OBJECT-TYPE
	SYNTAX SEQUENCE OF SnmpTrapDestList
	MAX-ACCESS not-accessible
	STATUS current
	DESCRIPTION
	"This table contains information regarding 
	the snmp trap configuration for several 
	destinations."
	::= { snmpinterface 10 }

snmpTrapDestTableEntry OBJECT-TYPE
	SYNTAX SnmpTrapDestList
	MAX-ACCESS not-accessible
	STATUS current
	DESCRIPTION
	"Entry in the snmp table."
	INDEX 
	{ snmpTrapDestId } ::= { snmpTrapDestTable 1 }

SnmpTrapDestList ::= SEQUENCE {
	snmpTrapDestId                      INTEGER,
	snmpTrapDestAlias                   DisplayString,
	snmpTrapDestEn                      INTEGER,
	snmpTrapDestIPv4Address             IpAddress,
	snmpTrapDestCommunity               DisplayString,
	snmpTrapGenColdstart                INTEGER,
	snmpTrapGenWarmstart                INTEGER,
	snmpTrapGenLinkDown                 INTEGER,
	snmpTrapGenLinkUp                   INTEGER,
	snmpTrapGenAuthFailure              INTEGER,
	snmpTrapGenEgpNeighborLoss          INTEGER,
	snmpTrapEntLinkChange               INTEGER,
	snmpTrapEntFactoryReset             INTEGER,
	snmpTrapEntTemperatureLevelChange   INTEGER,
	snmpTrapEntErrorCounter             INTEGER,
	snmpTrapEntUnderOverVoltage         INTEGER,
	snmpTrapEntTempShutDown             INTEGER,
	snmpTrapEntPoeLimitExceeded         INTEGER,
	snmpTrapEntSupplyStatusChange       INTEGER,
	snmpTrapEntSfpPlugChange            INTEGER,
	snmpTrapEntLoginFailure             INTEGER,
	snmpTrapEntRingBroken               INTEGER,
	snmpTrapEntRingAlarm                INTEGER,
	snmpTrapEntAuthPwFail               INTEGER,
	snmpTrapEntPrivPwFail               INTEGER,
	snmpTrapEntAccessPermission         INTEGER,
	snmpTrapEntSeclevelFail             INTEGER
}


snmpTrapDestId OBJECT-TYPE
	SYNTAX INTEGER (1..8)
	MAX-ACCESS read-only
	STATUS current
	DESCRIPTION
	"This entry describes the snmp trap 
	destination id."
	::= { snmpTrapDestTableEntry 1 }

snmpTrapDestAlias OBJECT-TYPE
	SYNTAX DisplayString (SIZE (0..16))
	MAX-ACCESS read-write
	STATUS current
	DESCRIPTION
	"This entry contains an individual name 
	for the trap destination."
	::= { snmpTrapDestTableEntry 2 }

snmpTrapDestEn OBJECT-TYPE
	SYNTAX INTEGER
	{
	disabled       (0),
	v1             (1),
	v2c            (2),
	v3             (3),
	unsupported  (255)
	}
	MAX-ACCESS read-write
	STATUS current
	DESCRIPTION
	"This entry describes the snmp trap 
	destination enable status and contains
	the used snmp version."
	::= { snmpTrapDestTableEntry 3 }

snmpTrapDestIPv4Address OBJECT-TYPE
	SYNTAX IpAddress
	MAX-ACCESS read-write
	STATUS current
	DESCRIPTION
	"This is the trap receiver's IPv4 address."
	::= { snmpTrapDestTableEntry 4 }

snmpTrapDestCommunity OBJECT-TYPE
	SYNTAX DisplayString (SIZE (0..16))
	MAX-ACCESS read-write
	STATUS current
	DESCRIPTION
	"This is the string used as community name 
	for traps."
	::= { snmpTrapDestTableEntry 5 }


snmpTrapGenColdstart OBJECT-TYPE
	SYNTAX INTEGER
	{
	enabled        (1),
	disabled       (2),
	unsupported  (255)
	}
	MAX-ACCESS read-write
	STATUS current
	DESCRIPTION
	"This entry enables or disables the 
	transmission of generic coldstart 
	traps to the selected destination.
	(generic trapnumber 0)"
	::= { snmpTrapDestTableEntry 6 }

snmpTrapGenWarmstart OBJECT-TYPE
	SYNTAX INTEGER
	{
	enabled        (1),
	disabled       (2),
	unsupported  (255)
	}
	MAX-ACCESS read-only
	STATUS current
	DESCRIPTION
	"This entry enables or disables the 
	transmission of generic warmstart 
	traps to the selected destination.
	(generic trapnumber 1)"
	::= { snmpTrapDestTableEntry 7 }

snmpTrapGenLinkDown OBJECT-TYPE
	SYNTAX INTEGER
	{
	enabled        (1),
	disabled       (2),
	unsupported  (255)
	}
	MAX-ACCESS read-write
	STATUS current
	DESCRIPTION
	"This entry enables or disables the 
	transmission of generic link down 
	traps to the selected destination.
	(generic trapnumber 2)"
	::= { snmpTrapDestTableEntry 8 }

snmpTrapGenLinkUp OBJECT-TYPE
	SYNTAX INTEGER
	{
	enabled        (1),
	disabled       (2),
	unsupported  (255)
	}
	MAX-ACCESS read-write
	STATUS current
	DESCRIPTION
	"This entry enables or disables the 
	transmission of generic link up 
	traps to the selected destination.
	(generic trapnumber 3)"
	::= { snmpTrapDestTableEntry 9 }

snmpTrapGenAuthFailure OBJECT-TYPE
	SYNTAX INTEGER
	{
	enabled        (1),
	disabled       (2),
	unsupported  (255)
	}
	MAX-ACCESS read-write
	STATUS current
	DESCRIPTION
	"This entry enables or disables the 
	transmission of generic authentication 
	failure traps to the selected destination.
	(generic trapnumber 4)"
	::= { snmpTrapDestTableEntry 10 }

snmpTrapGenEgpNeighborLoss OBJECT-TYPE
	SYNTAX INTEGER
	{
	enabled        (1),
	disabled       (2),
	unsupported  (255)
	}
	MAX-ACCESS read-only
	STATUS current
	DESCRIPTION
	"This entry enables or disables the 
	transmission of generic Exterior Gateway 
	Protocol Neighbor Loss traps to the 
	selected destination.
	(generic trapnumber 5)"
	::= { snmpTrapDestTableEntry 11 }


snmpTrapEntLinkChange OBJECT-TYPE
	SYNTAX INTEGER
	{
	enabled        (1),
	disabled       (2),
	unsupported  (255)
	}
	MAX-ACCESS read-write
	STATUS current
	DESCRIPTION
	"This entry enables or disables the 
	transmission of enterprise link change 
	traps to the selected destination.
	(generic trap# 6, specific trap# 1)"
	::= { snmpTrapDestTableEntry 12 }

snmpTrapEntFactoryReset OBJECT-TYPE
	SYNTAX INTEGER
	{
	enabled        (1),
	disabled       (2),
	unsupported  (255)
	}
	MAX-ACCESS read-write
	STATUS current
	DESCRIPTION
	"This entry enables or disables the 
	transmission of enterprise factory 
	reset traps to the selected destination. 
	(generic trap# 6, specific trap# 2)"
	::= { snmpTrapDestTableEntry 13 }

snmpTrapEntTemperatureLevelChange OBJECT-TYPE
	SYNTAX INTEGER
	{
	enabled        (1),
	disabled       (2),
	unsupported  (255)
	}
	MAX-ACCESS read-write
	STATUS current
	DESCRIPTION
	"This entry enables or disables the 
	transmission of enterprise temperature 
	level change traps to the selected 
	destination.
	(generic trap# 6, specific trap# 3)"
	::= { snmpTrapDestTableEntry 14 }

snmpTrapEntErrorCounter OBJECT-TYPE
	SYNTAX INTEGER
	{
	enabled        (1),
	disabled       (2),
	unsupported  (255)
	}
	MAX-ACCESS read-write
	STATUS current
	DESCRIPTION
	"This entry enables or disables the 
	transmission of enterprise error counter 
	traps to the selected destination
	(generic trap# 6, specific trap# 4)"
	::= { snmpTrapDestTableEntry 15 }

snmpTrapEntUnderOverVoltage OBJECT-TYPE
	SYNTAX INTEGER
	{
	enabled        (1),
	disabled       (2),
	unsupported  (255)
	}
	MAX-ACCESS read-write
	STATUS current
	DESCRIPTION
	"This entry enables or disables the 
	transmission of enterprise undervoltage 
	overvoltage traps to the selected 
	destination.
	(generic trap# 6, specific trap# 5)"
	::= { snmpTrapDestTableEntry 16 }

snmpTrapEntTempShutDown OBJECT-TYPE
	SYNTAX INTEGER
	{
	enabled        (1),
	disabled       (2),
	unsupported  (255)
	}
	MAX-ACCESS read-write
	STATUS current
	DESCRIPTION
	"This entry enables or disables the 
	transmission of enterprise temperature 
	shut down event traps to the selected 
	destination.
	(generic trap# 6, specific trap# 6)"
	::= { snmpTrapDestTableEntry 17 }

snmpTrapEntPoeLimitExceeded OBJECT-TYPE
	SYNTAX INTEGER
	{
	enabled        (1),
	disabled       (2),
	unsupported  (255)
	}
	MAX-ACCESS read-write
	STATUS current
	DESCRIPTION
	"This entry enables or disables the 
	transmission of enterprise poe limit 
	exceeded traps to the selected 
	destination.
	(generic trap# 6, specific trap# 7)"
	::= { snmpTrapDestTableEntry 18 }

snmpTrapEntSupplyStatusChange OBJECT-TYPE
	SYNTAX INTEGER
	{
	enabled        (1),
	disabled       (2),
	unsupported  (255)
	}
	MAX-ACCESS read-write
	STATUS current
	DESCRIPTION
	"This entry enables or disables the 
	transmission of enterprise supply status
	change traps to the selected destination.
	(generic trap# 6, specific trap# 8)"
	::= { snmpTrapDestTableEntry 19 }

snmpTrapEntSfpPlugChange OBJECT-TYPE
	SYNTAX INTEGER
	{
	enabled        (1),
	disabled       (2),
	unsupported  (255)
	}
	MAX-ACCESS read-write
	STATUS current
	DESCRIPTION
	"This entry enables or disables the 
	transmission of enterprise SFP plug
	change traps to the selected destination.
	(generic trap# 6, specific trap# 9)"
	::= { snmpTrapDestTableEntry 20 }

snmpTrapEntLoginFailure OBJECT-TYPE
	SYNTAX INTEGER
	{
	enabled        (1),
	disabled       (2),
	unsupported  (255)
	}
	MAX-ACCESS read-write
	STATUS current
	DESCRIPTION
	"This entry enables or disables the 
	transmission of enterprise login failure 
	traps to the selected destination.
	(generic trap# 6, specific trap# 10)"
	::= { snmpTrapDestTableEntry 21 }

snmpTrapEntRingBroken  OBJECT-TYPE
	SYNTAX INTEGER
	{
	enabled        (1),
	disabled       (2),
	unsupported  (255)
	}
	MAX-ACCESS read-write
	STATUS current
	DESCRIPTION
	"This entry enables or disables the 
	transmission of enterprise Ring broken 
	traps to the selected destination.
	(generic trap# 6, specific trap# 11)"
	::= { snmpTrapDestTableEntry 22 }

snmpTrapEntRingAlarm  OBJECT-TYPE
	SYNTAX INTEGER
	{
	enabled        (1),
	disabled       (2),
	unsupported  (255)
	}
	MAX-ACCESS read-write
	STATUS current
	DESCRIPTION
	"This entry enables or disables the 
	transmission of enterprise Ring Alarm 
	traps to the selected destination.
	(generic trap# 6, specific trap# 12)"
	::= { snmpTrapDestTableEntry 23 }

snmpTrapEntAuthPwFail  OBJECT-TYPE
	SYNTAX INTEGER
	{
	enabled        (1),
	disabled       (2),
	unsupported  (255)
	}
	MAX-ACCESS read-write
	STATUS current
	DESCRIPTION
	"This entry enables or disables 
	the transmission of enterprise 
	SNMPv3 Authentication Password Fail traps
	to the selected destination.
	(generic trap# 6, specific trap# 13)"
	::= { snmpTrapDestTableEntry 24 }

snmpTrapEntPrivPwFail  OBJECT-TYPE
	SYNTAX INTEGER
	{
	enabled        (1),
	disabled       (2),
	unsupported  (255)
	}
	MAX-ACCESS read-write
	STATUS current
	DESCRIPTION
	"This entry enables or disables 
	the transmission of enterprise 
	SNMPv3 Privacy Password Fail traps
	to the selected destination.
	(generic trap# 6, specific trap# 14)"
	::= { snmpTrapDestTableEntry 25 }

snmpTrapEntAccessPermission  OBJECT-TYPE
	SYNTAX INTEGER
	{
	enabled        (1),
	disabled       (2),
	unsupported  (255)
	}
	MAX-ACCESS read-write
	STATUS current
	DESCRIPTION
	"This entry enables or disables 
	the transmission of enterprise 
	SNMPv3 Access Permission traps 
	to the selected destination.
	(generic trap# 6, specific trap# 15)"
	::= { snmpTrapDestTableEntry 26 }

snmpTrapEntSeclevelFail  OBJECT-TYPE
	SYNTAX INTEGER
	{
	enabled        (1),
	disabled       (2),
	unsupported  (255)
	}
	MAX-ACCESS read-write
	STATUS current
	DESCRIPTION
	"This entry enables or disables 
	the transmission of enterprise 
	SNMPv3 Security Level Fail traps 
	to the selected destination.
	(generic trap# 6, specific trap# 16)"
	::= { snmpTrapDestTableEntry 27 }



-- udp interface group: =============================================
udpinterface OBJECT IDENTIFIER ::= { mib3 23 }

udpSupport OBJECT-TYPE
	SYNTAX INTEGER
	{
	supported      (1),
	umac           (3),
	unsupported  (255)
	}
	MAX-ACCESS read-only
	STATUS current
	DESCRIPTION
	"This entry contains the information if the
	proprietary udp protocol interface and its
	user management access control enhancement 
	(UMAC) is supported or not."
	::= { udpinterface 1 }

udpEnable OBJECT-TYPE
	SYNTAX INTEGER
	{
	enabled        (1),
	disabled       (2),
	unsupported  (255)
	}
	MAX-ACCESS read-write
	STATUS current
	DESCRIPTION
	"This entry enables or disables the 
	proprietary udp protocol Support. 
	Disabling requires UMAC support."
	::= { udpinterface 2 }

udpUmacEnable OBJECT-TYPE
	SYNTAX INTEGER
	{
	enabled        (1),
	--disabled       (2),
	unsupported  (255)
	}
	MAX-ACCESS read-only
	STATUS current
	DESCRIPTION
	"This entry contains the information
	if proprietary udp protocol is enhanced
	with user management access control (UMAC)."
	::= { udpinterface 3 }


-- syslog group: ====================================================
syslog OBJECT IDENTIFIER ::= { mib3 24 }

syslogSupport OBJECT-TYPE
	SYNTAX INTEGER
	{
	supported      (1),
	unsupported  (255)
	}
	MAX-ACCESS read-only
	STATUS current
	DESCRIPTION
	"This entry contains the information if
	syslog message servers are supported 
	or not."
	::= { syslog 1 }

syslogEnable OBJECT-TYPE
	SYNTAX INTEGER
	{
	enabled        (1),
	disabled       (2),
	unsupported  (255)
	}
	MAX-ACCESS read-write
	STATUS current
	DESCRIPTION
	"This entry contains the information if
	syslog message server support is enabled 
	or not."
	::= { syslog 2 }

syslogMessageTest OBJECT-TYPE
	SYNTAX INTEGER
	{
	inactive       (0),
	sendmessage    (1),
	unsupported  (255)
	}
	MAX-ACCESS read-write
	STATUS current
	DESCRIPTION
	"This entry triggers a syslog message 
	using the current destination settings. 
	This entry can be used to test the 
	destination configuration.
	This entry is self clearing."
	::= { syslog 3 }

syslogDestCount OBJECT-TYPE
	SYNTAX INTEGER
	MAX-ACCESS read-only
	STATUS current
	DESCRIPTION
	"The number of supported syslog destinations 
	on this system."
	::= { syslog 4 }

-- syslog destination table: ==============================
syslogDestTable OBJECT-TYPE
	SYNTAX SEQUENCE OF SyslogDestList
	MAX-ACCESS not-accessible
	STATUS current
	DESCRIPTION
	"This table contains the configuration for 
	several syslog destinations."
	::= { syslog 10 }

syslogDestTableEntry OBJECT-TYPE
	SYNTAX SyslogDestList
	MAX-ACCESS not-accessible
	STATUS current
	DESCRIPTION
	"Entry in the syslog destination table."
	INDEX 
	{ syslogDestId } ::= { syslogDestTable 1 }

SyslogDestList ::= SEQUENCE {
	syslogDestId          INTEGER,
	syslogDestAlias       DisplayString,
	syslogDestEnable      INTEGER,
	syslogDestIpv4Address   IpAddress,
	syslogDestPort        INTEGER,
	syslogDestFacility    INTEGER,
	syslogDestEventFilter BITS
}

syslogDestId OBJECT-TYPE
	SYNTAX INTEGER (1..8)
	MAX-ACCESS read-only
	STATUS current
	DESCRIPTION
	"This entry contains the syslog 
	destination id."
	::= { syslogDestTableEntry 1 }

syslogDestAlias OBJECT-TYPE
	SYNTAX DisplayString (SIZE (0..16))
	MAX-ACCESS read-write
	STATUS current
	DESCRIPTION
	"This entry contains an individual 
	name for the syslog destination."
	::= { syslogDestTableEntry 2 }

syslogDestEnable OBJECT-TYPE
	SYNTAX INTEGER
	{
	enabled        (1),
	disabled       (2),
	unsupported  (255)
	}
	MAX-ACCESS read-write
	STATUS current
	DESCRIPTION
	"This entry describes the syslog 
	destination enable status."
	::= { syslogDestTableEntry 3 }

syslogDestIpv4Address OBJECT-TYPE
	SYNTAX IpAddress
	MAX-ACCESS read-write
	STATUS current
	DESCRIPTION
	"This entry describes the syslog 
	destination IPv4 address."
	::= { syslogDestTableEntry 4 }

syslogDestPort OBJECT-TYPE
	SYNTAX INTEGER
	MAX-ACCESS read-write
	STATUS current
	DESCRIPTION
	"This is the syslog destination's 
	TCP port."
	::= { syslogDestTableEntry 5 }

syslogDestFacility OBJECT-TYPE
	SYNTAX INTEGER
	{
	kernelMessage         (0),
	userLevelMessage      (1),
	mailSystem            (2),
	systemDaemon          (3),
	securityMessage1      (4),
	syslogdMessage        (5),
	linePrinterSubsystem  (6),
	networkNewsSubsystem  (7),
	uucpSubsystem         (8),
	clockDeamon1          (9),
	securityMessage2     (10),
	ftpDeamon            (11),
	ntpSubsystem         (12),
	logAudit             (13),
	logAlert             (14),
	clockDeamon2         (15),
	localUse0            (16),
	localUse1            (17),
	localUse2            (18),
	localUse3            (19),
	localUse4            (20),
	localUse5            (21),
	localUse6            (22),
	localUse7            (23)
	}
	MAX-ACCESS read-write
	STATUS current
	DESCRIPTION
	"This entry describes the syslog 
	destination used facility value."
	::= { syslogDestTableEntry 6 }

syslogDestEventFilter OBJECT-TYPE
	SYNTAX BITS {
		reset(0),
		linkchange(1),
		configchange(2),
		login(3),
		firmwareupdate(4),
		powerredundancy(5),
		portauth(6),
		temperature(7),
		ring(8),
		sfp(9),
		poe(10),
		rtc(11),
		vct(12),
		debug(29),
		statusreport(30),
		test(31)
	}
	MAX-ACCESS read-write
	STATUS current
	DESCRIPTION
	"Flags to filter syslog events:
	messages are only sent if regarding
	bits are set."
	::= { syslogDestTableEntry 7 }


-- radius group: ====================================================
radius OBJECT IDENTIFIER ::= { mib3 25 }

radiusSupport OBJECT-TYPE
	SYNTAX INTEGER
	{
	supported      (1),
	unsupported  (255)
	}
	MAX-ACCESS read-only
	STATUS current
	DESCRIPTION
	"This entry contains the information if 
	communication with radius servers is 
	supported or not."
	::= { radius 1 }

radiusAccessEnable OBJECT-TYPE
	SYNTAX INTEGER
	{
	enabled        (1),
	disabled       (2),
	unsupported  (255)
	}
	MAX-ACCESS read-write
	STATUS current
	DESCRIPTION
	"This entry contains the information if 
	the radius servers' access service is 
	enabled or not."
	::= { radius 2 }

radiusAccountEnable OBJECT-TYPE
	SYNTAX INTEGER
	{
	enabled        (1),
	disabled       (2),
	unsupported  (255)
	}
	MAX-ACCESS read-write
	STATUS current
	DESCRIPTION
	"This entry contains the information if 
	the radius servers' account service is 
	enabled or not."
	::= { radius 3 }

radiusServerCount OBJECT-TYPE
	SYNTAX INTEGER
	MAX-ACCESS read-only
	STATUS current
	DESCRIPTION
	"The number of supported radius servers
	on this system."
	::= { radius 4 }

radiusMacAuthPassword OBJECT-TYPE
	SYNTAX DisplayString (SIZE (0..20))
	MAX-ACCESS read-write
	STATUS current
	DESCRIPTION
	"Password used for MAC Authentication via 
	radius servers."
	::= { radius 5 }

radiusUseMacAsPassword OBJECT-TYPE
	SYNTAX INTEGER
	{
	enabled        (1),
	disabled       (2),
	unsupported  (255)
	}
	MAX-ACCESS read-write
	STATUS current
	DESCRIPTION
	"This entry contains the information if 
	the user's MAC address is used as password
	instead of the static radius password or not."
	::= { radius 6 }

radiusMacSeparator OBJECT-TYPE
	SYNTAX DisplayString (SIZE (0..1))
	MAX-ACCESS read-write
	STATUS current
	DESCRIPTION
	"Character to separate the bytes of the 
	MAC Address for Radius Server communication."
	::= { radius 7 }

radiusTimeout OBJECT-TYPE
	SYNTAX INTEGER(1..65535)
	MAX-ACCESS read-write
	STATUS current
	DESCRIPTION
	"This entry contains the time in seconds 
	after which the radius server should have 
	answered arequest."
	::= { radius 8 }

radiusMacLettercase OBJECT-TYPE
	SYNTAX INTEGER
	{
	lower        (1),
	upper        (2)
	}
	MAX-ACCESS read-write
	STATUS current
	DESCRIPTION
	"This entry contains the information about 
	the used letter case if the user's MAC address
	is used as password."
	::= { radius 9 }


-- radius server table: ===================================
radiusServerTable OBJECT-TYPE
	SYNTAX SEQUENCE OF RadiusServerList
	MAX-ACCESS not-accessible
	STATUS current
	DESCRIPTION
	"This table contains the configuration 
	for several radius servers."
	::= { radius 10 }

radiusServerTableEntry OBJECT-TYPE
	SYNTAX RadiusServerList
	MAX-ACCESS not-accessible
	STATUS current
	DESCRIPTION
	"Entry in the radius server table."
	INDEX 
	{ radiusServerId } ::= { radiusServerTable 1 }

RadiusServerList ::= SEQUENCE {
	radiusServerId             INTEGER,
	radiusServerAlias          DisplayString,
	radiusServerEnableAccess   INTEGER,
	radiusServerEnableAccount  INTEGER,
	radiusServerIpv4Address    IpAddress,
	radiusServerAccessPort     INTEGER,
	radiusServerAccountPort    INTEGER,
	radiusServerSecret         DisplayString
}

radiusServerId OBJECT-TYPE
	SYNTAX INTEGER (1..8)
	MAX-ACCESS read-only
	STATUS current
	DESCRIPTION
	"This entry contains the radius server id."
	::= { radiusServerTableEntry 1 }

radiusServerAlias OBJECT-TYPE
	SYNTAX DisplayString (SIZE (0..16))
	MAX-ACCESS read-write
	STATUS current
	DESCRIPTION
	"This entry contains an individual name for 
	the radius server."
	::= { radiusServerTableEntry 2 }

radiusServerEnableAccess OBJECT-TYPE
	SYNTAX INTEGER
	{
	enabled        (1),
	disabled       (2),
	unsupported  (255)
	}
	MAX-ACCESS read-write
	STATUS current
	DESCRIPTION
	"This entry describes the radius
	server enable status for the
	MAX-ACCESS service which means both,
	authentication and authorization."
	::= { radiusServerTableEntry 3 }

radiusServerEnableAccount OBJECT-TYPE
	SYNTAX INTEGER
	{
	enabled        (1),
	disabled       (2),
	unsupported  (255)
	}
	MAX-ACCESS read-write
	STATUS current
	DESCRIPTION
	"This entry describes the radius
	server enable status for the 
	account service."
	::= { radiusServerTableEntry 4 }

radiusServerIpv4Address OBJECT-TYPE
	SYNTAX IpAddress
	MAX-ACCESS read-write
	STATUS current
	DESCRIPTION
	"This entry describes the radius
	server IPv4 address."
	::= { radiusServerTableEntry 5 }

radiusServerAccessPort OBJECT-TYPE
	SYNTAX INTEGER
	MAX-ACCESS read-write
	STATUS current
	DESCRIPTION
	"This is the radius server's UDP port
	for the access service. The default
	value is 1812."
	::= { radiusServerTableEntry 6 }

radiusServerAccountPort OBJECT-TYPE
	SYNTAX INTEGER
	MAX-ACCESS read-write
	STATUS current
	DESCRIPTION
	"This is the radius server's UDP port
	for the account service. The default
	value is 1813."
	::= { radiusServerTableEntry 7 }

radiusServerSecret OBJECT-TYPE
	SYNTAX DisplayString (SIZE (0..20))
	MAX-ACCESS read-write
	STATUS current
	DESCRIPTION
	"This is the radius server's secret string."
	::= { radiusServerTableEntry 8 }



-- supply group: ====================================================
supply OBJECT IDENTIFIER ::= { mib3 30 }

supplyCount OBJECT-TYPE
	SYNTAX INTEGER
	MAX-ACCESS read-only
	STATUS current
	DESCRIPTION
	"The number of supported power supplies."
	::= { supply 1 }


--supply table: ===========================================
supplyTable OBJECT-TYPE
	SYNTAX SEQUENCE OF SupplyList
	MAX-ACCESS not-accessible
	STATUS current
	DESCRIPTION
	"This table contains power supply 
	information of the device."
	::= { supply 10 }

supplyTableEntry OBJECT-TYPE
	SYNTAX SupplyList
	MAX-ACCESS not-accessible
	STATUS current
	DESCRIPTION
	"Entry in the supply table."
	INDEX
	{ supplyId } ::= { supplyTable 1 }

SupplyList ::= SEQUENCE {
	supplyId      INTEGER,
	supplyUsed    INTEGER,
	supplyStatus  INTEGER
}

supplyId OBJECT-TYPE
	SYNTAX INTEGER (1..8)
	MAX-ACCESS read-only
	STATUS current
	DESCRIPTION
	"This entry describes the power supply id."
	::= { supplyTableEntry 1 }

supplyUsed OBJECT-TYPE
	SYNTAX INTEGER
	{
	used           (1),
	unused         (2),
	unsupported  (255)
	}
	MAX-ACCESS read-write
	STATUS current
	DESCRIPTION
	"If several supplies are possible but not 
	required, this entry decides if an invalid 
	detection leads to an error. An error event 
	can be suppressed if a supply is marked as 
	'unused'. Hint: If an 'unused' supply is 
	detected as 'valid', it is also automatically 
	marked as 'used'."
	::= { supplyTableEntry 2 }

supplyStatus OBJECT-TYPE
	SYNTAX INTEGER
	{
	valid          (1),
	invalid        (2),
	undefined    (254),
	unsupported  (255)
	}
	MAX-ACCESS read-only
	STATUS current
	DESCRIPTION
	"This entry contains the information if the 
	power supply is valid at the moment. An 
	invalid supply will lead to an error event 
	unless it is marked as 'unused'. 
	Hint: If an 'unused' supply is detected as 
	'valid', it is also automatically marked 
	as 'used'."
	::= { supplyTableEntry 3 }



-- poepse group: ====================================================
poepse OBJECT IDENTIFIER ::= { mib3 31 }

poepseSupport OBJECT-TYPE
	SYNTAX INTEGER
	{
	supported      (1),
	unsupported  (255)
	}
	MAX-ACCESS read-only
	STATUS current
	DESCRIPTION
	"This entry contains the information if this
	is a POE power source equipment (PSE) or not."
	::= { poepse 1 }

poepseEnable OBJECT-TYPE
	SYNTAX INTEGER
	{
	enabled        (1),
	disabled       (2),
	unsupported  (255)
	}
	MAX-ACCESS read-write
	STATUS current
	DESCRIPTION
	"This entry contains the information if 
	the POE/PSE feature is enabled or not."
	::= { poepse 2 }

poepseTotalInputPower OBJECT-TYPE
	SYNTAX INTEGER
	MAX-ACCESS read-write
	STATUS current
	DESCRIPTION
	"This entry contains the input power (in W) 
	due to the used power supply."
	::= { poepse 3 }

poepseMaxInputPower OBJECT-TYPE
	SYNTAX INTEGER
	MAX-ACCESS read-only
	STATUS current
	DESCRIPTION
	"This entry contains maximum available input 
	power (in W) due to hardware restrictions 
	in the switch device."
	::= { poepse 4 }

poepseDeviceSupplyPower OBJECT-TYPE
	SYNTAX INTEGER
	MAX-ACCESS read-only
	STATUS current
	DESCRIPTION
	"This entry contains the power (in W) the 
	switch device spends itself. This value 
	is needed to calculate the available 
	power for external devices."
	::= { poepse 5 }

pseAvailablePower OBJECT-TYPE
	SYNTAX INTEGER
	MAX-ACCESS read-only
	STATUS current
	DESCRIPTION
	"This entry contains the available poe 
	power (in W) for attached external 
	devices."
	::= { poepse 6 }

poepseExtendedVoltage OBJECT-TYPE
	SYNTAX INTEGER
	{
	enabled        (1),
	disabled       (2),
	unsupported  (255)
	}
	MAX-ACCESS read-write
	STATUS current
	DESCRIPTION
	"This entry contains the information if 
	the POE/PSE Extended Voltage is enabled
	or not. If enabled PoE will be disabled
	if applied PoE output voltage exceeds an
	enhanced range of 40..59V instead of
	43..55V (default)."
	::= { poepse 7 }

poepsePortTable OBJECT-TYPE
	SYNTAX SEQUENCE OF PoePsePortList
	MAX-ACCESS not-accessible
	STATUS current
	DESCRIPTION
	"This table contains the pse port 
	configuration of the device."
	::= { poepse 10 }

poepsePortTableEntry OBJECT-TYPE
	SYNTAX PoePsePortList
	MAX-ACCESS not-accessible
	STATUS current
	DESCRIPTION
	"Entry in the supply table."
	INDEX
	{ poepsePortId } ::= { poepsePortTable 1 }

PoePsePortList ::= SEQUENCE {
	poepsePortId              INTEGER,
	poepsePortMode            INTEGER,
	poepsePortStatus          INTEGER,
	poepsePortMaxPower        INTEGER,
	poepsePortMeasuredPower   INTEGER,
	poepsePortMaxClass        INTEGER,
	poepsePortDetectedClass   INTEGER,
	poepsePortMeasuredVoltage INTEGER
}

poepsePortId OBJECT-TYPE
	SYNTAX INTEGER (1..24)
	MAX-ACCESS read-only
	STATUS current
	DESCRIPTION
	"This entry describes the device's pse 
	port id."
	::= { poepsePortTableEntry 1 }

poepsePortMode OBJECT-TYPE
	SYNTAX INTEGER
	{
	poe8023af      (1),
	poeForced      (2),
	poeDisabled    (3),
	undefined    (254),
	unsupported  (255)
	}
	MAX-ACCESS read-write
	STATUS current
	DESCRIPTION
	"This entry describes the device's pse 
	port mode."
	::= { poepsePortTableEntry 2 }

poepsePortStatus OBJECT-TYPE
	SYNTAX INTEGER
	{
	off            (0),
	discovering    (1),
	powered        (2),
	fault          (3),
	disabled       (4),
	overcurrent    (5),
	undefined    (254),
	unsupported  (255)
	}
	MAX-ACCESS read-only
	STATUS current
	DESCRIPTION
	"This entry describes the device's pse 
	port mode."
	::= { poepsePortTableEntry 3 }

poepsePortMaxPower OBJECT-TYPE
	SYNTAX INTEGER (0..15400)
	MAX-ACCESS read-write
	STATUS current
	DESCRIPTION
	"This entry describes the permitted 
	power for this port in mW."
	::= { poepsePortTableEntry 4 }

poepsePortMeasuredPower OBJECT-TYPE
	SYNTAX INTEGER
	MAX-ACCESS read-only
	STATUS current
	DESCRIPTION
	"This entry describes the measured 
	power for this port in mW."
	::= { poepsePortTableEntry 5 }

poepsePortMaxClass OBJECT-TYPE
	SYNTAX INTEGER
	{
	class0         (0),
	class1         (1),
	class2         (2),
	class3         (3),
	class4         (4),
	undefined    (254),
	unsupported  (255)
	}
	MAX-ACCESS read-write
	STATUS current
	DESCRIPTION
	"This entry describes the maximnum 
	allowed poe class for this port."
	::= { poepsePortTableEntry 6 }

poepsePortDetectedClass OBJECT-TYPE
	SYNTAX INTEGER
	{
	class0         (0),
	class1         (1),
	class2         (2),
	class3         (3),
	class4         (4),
	undefined    (254),
	unsupported  (255)
	}
	MAX-ACCESS read-only
	STATUS current
	DESCRIPTION
	"This entry describes the detected 
	poe class for this port."
	::= { poepsePortTableEntry 7 }

poepsePortMeasuredVoltage OBJECT-TYPE
	SYNTAX INTEGER
	MAX-ACCESS read-only
	STATUS current
	DESCRIPTION
	"This entry describes the measured 
	Voltage for this port in multiples 
	of 0.1V."
	::= { poepsePortTableEntry 8 }


-- poepd group: =====================================================
poepd OBJECT IDENTIFIER ::= { mib3 32 }

poepdSupport OBJECT-TYPE
	SYNTAX INTEGER
	{
	supported      (1),
	unsupported  (255)
	}
	MAX-ACCESS read-only
	STATUS current
	DESCRIPTION
	"This entry contains the information if 
	this is a POE powered device (PD) or not."
	::= { poepd 1 }



-- hardwarecode group: ==============================================
hardwarecode OBJECT IDENTIFIER ::= { mib3 33 }

hardwarecodeSupport OBJECT-TYPE
	SYNTAX INTEGER
	{
	supported      (1),
	unsupported  (255)
	}
	MAX-ACCESS read-only
	STATUS current
	DESCRIPTION
	"This entry contains the information if a 
	hardware coding (hard wired or selectable) 
	is supported or not."
	::= { hardwarecode 1 }

hardwarecodeNumber OBJECT-TYPE
	SYNTAX INTEGER
	MAX-ACCESS read-only
	STATUS current
	DESCRIPTION
	"This entry describes the value of the 
	detected hardware code with a range
	of [0..15]. If this feature isa not
	supported a 255 will be given back."
	::= { hardwarecode 2 }


-- spanningtree group: ==============================================
spanningtree OBJECT IDENTIFIER ::= { mib3 34 }

stpSupport OBJECT-TYPE
	SYNTAX INTEGER
	{
	supported      (1),
	unsupported  (255)
	}
	MAX-ACCESS read-only
	STATUS current
	DESCRIPTION
	"This entry contains the information if the
	spanning tree feature is supported or not."
	::= { spanningtree 1 }

stpEnable OBJECT-TYPE
	SYNTAX INTEGER
	{
	enabled        (1),
	disabled       (2),
	unsupported  (255)
	}
	MAX-ACCESS read-write
	STATUS current
	DESCRIPTION
	"This entry contains the information if 
	the spanning feature is enabled or not.
	If supported the settings and status 
	information are accessible via standard 
	BRIDGE-MIB"
	::= { spanningtree 2 }



-- Notification Definitions: ========================================

msSwitchNotifications        OBJECT IDENTIFIER ::= { mib3 100 }

linkChangeNotification NOTIFICATION-TYPE
	OBJECTS { portStatusId, portStatusLink }
	STATUS current
	DESCRIPTION
	"Trap indicating that a port's link status 
	has changed. The port is identified by the 
	portId variable."
	::= { msSwitchNotifications 1 }

factoryResetNotification NOTIFICATION-TYPE
	-- OBJECTS { none }
	STATUS current
	DESCRIPTION
	"Trap indicating a factory reset initiated 
	by the user."
	::= { msSwitchNotifications 2 }

temperatureLevelChangeNotification NOTIFICATION-TYPE
	OBJECTS { deviceTemperatureLevel }
	STATUS current
	DESCRIPTION
	"Trap indicating the device temperature level 
	has changed."
	::= { msSwitchNotifications 3 }

errorcountNotification NOTIFICATION-TYPE
	OBJECTS { portStatusId }
	STATUS current
	DESCRIPTION
	"Trap indicating errors received at a port."
	::= { msSwitchNotifications 4 }

underOverVoltageNotification NOTIFICATION-TYPE
	OBJECTS { portStatusId }
	STATUS current
	DESCRIPTION
	"Trap indicating the PoLAN port voltage is 
	out of operating range and port power has 
	been turned off."
	::= { msSwitchNotifications 5 }

temperatureShutdownNotification NOTIFICATION-TYPE
	-- OBJECTS { none }
	STATUS current
	DESCRIPTION
	"Trap indicating that the device temperature 
	is above maximum operating temperature and 
	the device will be shut down."
	::= { msSwitchNotifications 6 }

portPoELimitExceededNotification NOTIFICATION-TYPE
	OBJECTS { portStatusId }
	STATUS current
	DESCRIPTION
	"Trap indicating that port power has been 
	turned off by power management. The power 
	limit for one port or for the whole device 
	is exceeded."
	::= { msSwitchNotifications 7 }

powerSupplyStatusChangeNotification NOTIFICATION-TYPE
	OBJECTS { supplyId }
	STATUS current
	DESCRIPTION
	"Trap indicating that main or redundant power 
	input status has changed."
	::= { msSwitchNotifications 8 }

sfpPlugChangeNotification NOTIFICATION-TYPE
	OBJECTS { sfpPortnumber, sfpDetect }
	STATUS current
	DESCRIPTION
	"Trap indicating that a sfp module has been 
	plugged in or plugged out."
	::= { msSwitchNotifications 9 }

loginFailureNotification NOTIFICATION-TYPE
	-- OBJECTS { none }
	STATUS current
	DESCRIPTION
	"Trap indicating a login attempt 
	with an invalid password."
	::= { msSwitchNotifications 10 }

ringBrokenNotification NOTIFICATION-TYPE
	OBJECTS { ringNumber, portStatusId, portStatusLink}
	STATUS current
	DESCRIPTION
	"Trap indicating a link down detect
	at activated ring port."
	::= { msSwitchNotifications 11 }

ringAlarmNotification NOTIFICATION-TYPE
	OBJECTS { ringNumber, ringStatus, ringAlarmDuration }
	STATUS current
	DESCRIPTION
	"Trap indicating a Ring alert reception."
	::= { msSwitchNotifications 12 }

snmpv3AuthenticationPwFailNotification NOTIFICATION-TYPE
	-- OBJECTS { none }
	STATUS current
	DESCRIPTION
	"Notification indicating an Authentication
	Password failure."
	::= { msSwitchNotifications 13 }

snmpv3PrivacyPwFailNotification NOTIFICATION-TYPE
	-- OBJECTS { none }
	STATUS current
	DESCRIPTION
	"Notification indicating a Privacy
	Password failure."
	::= { msSwitchNotifications 14 }

snmpv3AccessPermissionNotification NOTIFICATION-TYPE
	-- OBJECTS { none }
	STATUS current
	DESCRIPTION
	"Notification indicating a write attempt
	without matching WriteView defined."
	::= { msSwitchNotifications 15 }

snmpv3SeclevelFailNotification NOTIFICATION-TYPE
	-- OBJECTS { none }
	STATUS current
	DESCRIPTION
	"Notification indicating a user 
	Security Level mismatch"
	::= { msSwitchNotifications 16 }


END
