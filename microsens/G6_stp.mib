G6-STP-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

protocol MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 2 }

stp  OBJECT IDENTIFIER ::= { protocol 42 }



-- *************************** CONFIGURATION SECTION ********************************


-- ******************* Begin of bridgeConfigTable *************************

bridgeConfigTable	OBJECT-TYPE
	SYNTAX SEQUENCE OF BridgeConfigEntry
	MAX-ACCESS not-accessible
	STATUS current
	DESCRIPTION
		"Configuration parameter concerning the general bridge setttings"
	::= { stp 1 }

bridgeConfigEntry	OBJECT-TYPE
	SYNTAX BridgeConfigEntry
	MAX-ACCESS not-accessible
	STATUS current
	DESCRIPTION
		""
	INDEX { bridgeConfigIndex }
	::= { bridgeConfigTable 1 }


	BridgeConfigEntry ::= SEQUENCE {
	bridgeConfigIndex INTEGER,
	bridgeConfigMode INTEGER ,
	bridgeConfigPriority Integer32 ,
	bridgeConfigHelloTime Integer32 ,
	bridgeConfigMaxAge Integer32 ,
	bridgeConfigForwardDelay Integer32 ,
	bridgeConfigTxHoldCount Integer32 ,
	bridgeConfigIeeePathCostModel INTEGER ,
	bridgeConfigMstpRegionName DisplayString,
	bridgeConfigMstpRevisionLevel Integer32 ,
	bridgeConfigMstpMaxHops Integer32 ,
	bridgeConfigMstpStpAgingTime Unsigned32
	}

bridgeConfigIndex	OBJECT-TYPE
	SYNTAX INTEGER (0)
	MAX-ACCESS not-accessible
	STATUS current
	DESCRIPTION
		"Automatically generated"
	::= { bridgeConfigEntry 1 }

bridgeConfigMode OBJECT-TYPE   -- mode
	SYNTAX INTEGER 
		{
		disabled (0),
		stp (1),
		rstp (2),
		mstp (3)
		}
	MAX-ACCESS read-write
	STATUS current
	DESCRIPTION
	"Set base operating mode of spanning tree protocol."
	::= { bridgeConfigEntry 2 }

bridgeConfigPriority OBJECT-TYPE   -- priority
	SYNTAX Integer32 (0..65535)
	MAX-ACCESS read-write
	STATUS current
	DESCRIPTION
	"The value of the writeable portion of the Bridge ID."
	::= { bridgeConfigEntry 3 }

bridgeConfigHelloTime OBJECT-TYPE   -- hello_time
	SYNTAX Integer32 (0..65535)
	MAX-ACCESS read-write
	STATUS current
	DESCRIPTION
	"The amount of time between the transmission of Configuration bridge PDUs by this node on any port when it is the root of the spanning tree, or trying to become so, in seconds."
	::= { bridgeConfigEntry 4 }

bridgeConfigMaxAge OBJECT-TYPE   -- max_age
	SYNTAX Integer32 (0..65535)
	MAX-ACCESS read-write
	STATUS current
	DESCRIPTION
	"The maximum age of Spanning Tree Protocol information learned from the network on any port before it is discarded, in seconds."
	::= { bridgeConfigEntry 5 }

bridgeConfigForwardDelay OBJECT-TYPE   -- forward_delay
	SYNTAX Integer32 (0..65535)
	MAX-ACCESS read-write
	STATUS current
	DESCRIPTION
	"Bridge forward delay in seconds."
	::= { bridgeConfigEntry 6 }

bridgeConfigTxHoldCount OBJECT-TYPE   -- tx_hold_count
	SYNTAX Integer32 (0..65535)
	MAX-ACCESS read-write
	STATUS current
	DESCRIPTION
	"Limits the maximum transmission rate."
	::= { bridgeConfigEntry 7 }

bridgeConfigIeeePathCostModel OBJECT-TYPE   -- ieee_path_cost_model
	SYNTAX INTEGER 
		{
		ms1998Compliant (0),
		ms2004Compliant (1)
		}
	MAX-ACCESS read-write
	STATUS current
	DESCRIPTION
	"Defines to which standard the admin_path_cost are compliant."
	::= { bridgeConfigEntry 8 }

bridgeConfigMstpRegionName OBJECT-TYPE   -- mstp_region_name
	SYNTAX DisplayString
	MAX-ACCESS read-write
	STATUS current
	DESCRIPTION
	""
	::= { bridgeConfigEntry 9 }

bridgeConfigMstpRevisionLevel OBJECT-TYPE   -- mstp_revision_level
	SYNTAX Integer32 (0..65535)
	MAX-ACCESS read-write
	STATUS current
	DESCRIPTION
	""
	::= { bridgeConfigEntry 10 }

bridgeConfigMstpMaxHops OBJECT-TYPE   -- mstp_max_hops
	SYNTAX Integer32 (0..65535)
	MAX-ACCESS read-write
	STATUS current
	DESCRIPTION
	"Defines the initial value of remaining hops for MSTI information generated at the boundary of an MSTI region."
	::= { bridgeConfigEntry 11 }

bridgeConfigMstpStpAgingTime OBJECT-TYPE   -- mstp_stp_aging_time
	SYNTAX Unsigned32
	MAX-ACCESS read-write
	STATUS current
	DESCRIPTION
	"This parameter is used only when MSTP is forced into STP mode for rapid aging."
	::= { bridgeConfigEntry 12 }


-- ********************* End of bridgeConfigTable ***********************


-- ******************* Begin of portConfigTable *************************

portConfigTable	OBJECT-TYPE
	SYNTAX SEQUENCE OF PortConfigEntry
	MAX-ACCESS not-accessible
	STATUS current
	DESCRIPTION
		"Configuration parameter concerning the port specific STP setttings"
	::= { stp 2 }

portConfigEntry	OBJECT-TYPE
	SYNTAX PortConfigEntry
	MAX-ACCESS not-accessible
	STATUS current
	DESCRIPTION
		""
	INDEX { portConfigPortIndex }
	::= { portConfigTable 1 }


	PortConfigEntry ::= SEQUENCE {
	portConfigPortIndex INTEGER,
	portConfigEnable INTEGER ,
	portConfigPriority Integer32 ,
	portConfigAdminP2pPort INTEGER ,
	portConfigAdminEdgePort INTEGER ,
	portConfigAdminPathCost Unsigned32,
	portConfigProtocolMigration DisplayString,
	portConfigBridgeAssurance INTEGER ,
	portConfigMstpDefaultPriority Integer32 ,
	portConfigMstpPortPriority DisplayString,
	portConfigMstpDefaultAdminPathCost Unsigned32,
	portConfigMstpPortAdminPathCost DisplayString,
	portConfigBpduGuard INTEGER ,
	portConfigBpduReceiveOnly INTEGER ,
	portConfigRestrictTcn INTEGER ,
	portConfigRestrictRoot INTEGER 
	}

portConfigPortIndex	OBJECT-TYPE
	SYNTAX INTEGER (0..24)
	MAX-ACCESS not-accessible
	STATUS current
	DESCRIPTION
		"Automatically generated"
	::= { portConfigEntry 1 }

portConfigEnable OBJECT-TYPE   -- enable
	SYNTAX INTEGER {  disabled(0), enabled(1) }
	MAX-ACCESS read-write
	STATUS current
	DESCRIPTION
	"Enable (R)STP for this port."
	::= { portConfigEntry 2 }

portConfigPriority OBJECT-TYPE   -- priority
	SYNTAX Integer32 (0..255)
	MAX-ACCESS read-write
	STATUS current
	DESCRIPTION
	"Port priority value."
	::= { portConfigEntry 3 }

portConfigAdminP2pPort OBJECT-TYPE   -- admin_p2p_port
	SYNTAX INTEGER 
		{
		auto (0),
		forceFalse (1),
		forceTrue (2)
		}
	MAX-ACCESS read-write
	STATUS current
	DESCRIPTION
	"A value of forceTrue indicates that this port should always be treated as if it is connected to a point-to-point link. A value of forceFalse indicates that this port should be treated as having a shared media connection."
	::= { portConfigEntry 4 }

portConfigAdminEdgePort OBJECT-TYPE   -- admin_edge_port
	SYNTAX INTEGER {  disabled(0), enabled(1) }
	MAX-ACCESS read-write
	STATUS current
	DESCRIPTION
	"When enabled this port is assumed to be an edge port."
	::= { portConfigEntry 5 }

portConfigAdminPathCost OBJECT-TYPE   -- admin_path_cost
	SYNTAX Unsigned32
	MAX-ACCESS read-write
	STATUS current
	DESCRIPTION
	"The contribution of this port to the path cost of paths towards the spanning tree root which include this port."
	::= { portConfigEntry 6 }

portConfigProtocolMigration OBJECT-TYPE   -- protocol_migration
	SYNTAX DisplayString
	MAX-ACCESS read-write
	STATUS current
	DESCRIPTION
	"When operating in RSTP mode, setting this object forces this port to transmit RSTP BPDUs."
	::= { portConfigEntry 7 }

portConfigBridgeAssurance OBJECT-TYPE   -- bridge_assurance
	SYNTAX INTEGER {  disabled(0), enabled(1) }
	MAX-ACCESS read-write
	STATUS current
	DESCRIPTION
	"The bridge assurance is used to detectunidirectional link failures or remote devices that stop sending spanning tree information due to a software fault. Important: Only enable when the other directly connected switches also support this feature."
	::= { portConfigEntry 8 }

portConfigMstpDefaultPriority OBJECT-TYPE   -- mstp_default_priority
	SYNTAX Integer32 (0..255)
	MAX-ACCESS read-write
	STATUS current
	DESCRIPTION
	"The port priority used in all MSTP instances unless otherwise configured in mstp_port_priority."
	::= { portConfigEntry 9 }

portConfigMstpPortPriority OBJECT-TYPE   -- mstp_port_priority
	SYNTAX DisplayString
	MAX-ACCESS read-write
	STATUS current
	DESCRIPTION
	"The port priority used in all specific MSTP instances. Syntax: mstp_id:port_priority. E.g.: 1:32, 2:128, 5:128"
	::= { portConfigEntry 10 }

portConfigMstpDefaultAdminPathCost OBJECT-TYPE   -- mstp_default_admin_path_cost
	SYNTAX Unsigned32
	MAX-ACCESS read-write
	STATUS current
	DESCRIPTION
	"The port path cost used in all MSTP instances unless otherwise configured in mstp_port_admin_path_cost."
	::= { portConfigEntry 11 }

portConfigMstpPortAdminPathCost OBJECT-TYPE   -- mstp_port_admin_path_cost
	SYNTAX DisplayString
	MAX-ACCESS read-write
	STATUS current
	DESCRIPTION
	"The port path cost used in specific MSTP instances. Syntax: mstp_id:port_path_cost. E.g.: 1:4, 2:100"
	::= { portConfigEntry 12 }

portConfigBpduGuard OBJECT-TYPE   -- bpdu_guard
	SYNTAX INTEGER 
		{
		disabled (0),
		dropAndEvent (1),
		blockPort (2)
		}
	MAX-ACCESS read-write
	STATUS current
	DESCRIPTION
	"When enabled STP attempts from a user port are blocked. This prevents a malicious user from influencing the overall network routing."
	::= { portConfigEntry 13 }

portConfigBpduReceiveOnly OBJECT-TYPE   -- bpdu_receive_only
	SYNTAX INTEGER {  disabled(0), enabled(1) }
	MAX-ACCESS read-write
	STATUS current
	DESCRIPTION
	"When enabled this port listens to incoming BPDU packets for spanning tree algorithm but never transmits any."
	::= { portConfigEntry 14 }

portConfigRestrictTcn OBJECT-TYPE   -- restrict_tcn
	SYNTAX INTEGER {  disabled(0), enabled(1) }
	MAX-ACCESS read-write
	STATUS current
	DESCRIPTION
	"When enabled the port does not forward topology change notification BPDUs."
	::= { portConfigEntry 15 }

portConfigRestrictRoot OBJECT-TYPE   -- restrict_root
	SYNTAX INTEGER {  disabled(0), enabled(1) }
	MAX-ACCESS read-write
	STATUS current
	DESCRIPTION
	"When enabled this port cannot become a root bridge port for the spanning tree protocol."
	::= { portConfigEntry 16 }


-- ********************* End of portConfigTable ***********************


-- ******************* Begin of mstpGroupTable *************************

mstpGroupTable	OBJECT-TYPE
	SYNTAX SEQUENCE OF MstpGroupEntry
	MAX-ACCESS not-accessible
	STATUS current
	DESCRIPTION
		"This table defines MSTP parameter that my be different between instances. The mstp_id is referrenced from vlan.filter_config.mstp_group. Several VLAN may share the same MSTP group. If needed up to 63 table entires can be created. "
	::= { stp 3 }

mstpGroupEntry	OBJECT-TYPE
	SYNTAX MstpGroupEntry
	MAX-ACCESS not-accessible
	STATUS current
	DESCRIPTION
		""
	INDEX { mstpGroupIndex }
	::= { mstpGroupTable 1 }


	MstpGroupEntry ::= SEQUENCE {
	mstpGroupIndex INTEGER,
	mstpGroupMstpId DisplayString,
	mstpGroupBridgePriority Integer32 
	}

mstpGroupIndex	OBJECT-TYPE
	SYNTAX INTEGER (0..62)
	MAX-ACCESS not-accessible
	STATUS current
	DESCRIPTION
		"Automatically generated"
	::= { mstpGroupEntry 1 }

mstpGroupMstpId OBJECT-TYPE   -- mstp_id
	SYNTAX DisplayString
	MAX-ACCESS read-write
	STATUS current
	DESCRIPTION
	"Defines filter table entry for this MSTP Group Id. This is the key value for the table. Type '=:' to edit, use index '[*] = new_id:' to add an entry. Edit string to nothing to delete entry."
	::= { mstpGroupEntry 2 }

mstpGroupBridgePriority OBJECT-TYPE   -- bridge_priority
	SYNTAX Integer32 (0..65535)
	MAX-ACCESS read-write
	STATUS current
	DESCRIPTION
	"The value of the writeable portion of the Bridge ID for this MSTP  instance."
	::= { mstpGroupEntry 3 }


-- ********************* End of mstpGroupTable ***********************



-- ****************************** STATUS SECTION ********************************


-- ******************* Begin of bridgeStatusTable *************************

bridgeStatusTable	OBJECT-TYPE
	SYNTAX SEQUENCE OF BridgeStatusEntry
	MAX-ACCESS not-accessible
	STATUS current
	DESCRIPTION
		"This status table collects all bridge related status fields."
	::= { stp 100 }

bridgeStatusEntry	OBJECT-TYPE
	SYNTAX BridgeStatusEntry
	MAX-ACCESS not-accessible
	STATUS current
	DESCRIPTION
		""
	INDEX { bridgeStatusIndex }
	::= { bridgeStatusTable 1 }


	BridgeStatusEntry ::= SEQUENCE {
	bridgeStatusIndex INTEGER,
	bridgeStatusStpProtocol Integer32 ,
	bridgeStatusHelloTime Integer32 ,
	bridgeStatusMaxAge Integer32 ,
	bridgeStatusHoldTime Integer32 ,
	bridgeStatusForwardDelay Integer32 ,
	bridgeStatusRootPort Integer32 ,
	bridgeStatusRootCost Unsigned32,
	bridgeStatusTopologyChanges Integer32 ,
	bridgeStatusLastTopologyChange Counter32,
	bridgeStatusMstpRegionName DisplayString,
	bridgeStatusMstiRevisionLevel Integer32 ,
	bridgeStatusCistInternalRootPathCost Unsigned32,
	bridgeStatusCistRegionalRootId DisplayString,
	bridgeStatusCistRegionalRootPriority Unsigned32,
	bridgeStatusCistRegionalRootMac MacAddress,
	bridgeStatusMaxHops Integer32 ,
	bridgeStatusMstpStpAgingTime Unsigned32
	}

bridgeStatusIndex	OBJECT-TYPE
	SYNTAX INTEGER (0)
	MAX-ACCESS not-accessible
	STATUS current
	DESCRIPTION
		"Automatically generated"
	::= { bridgeStatusEntry 1 }

bridgeStatusStpProtocol OBJECT-TYPE   -- stp_protocol
	SYNTAX Integer32 (0..255)
	MAX-ACCESS read-only
	STATUS current
	DESCRIPTION
	"Stp protocol specification = 3 for 802.1D."
	::= { bridgeStatusEntry 2 }

bridgeStatusHelloTime OBJECT-TYPE   -- hello_time
	SYNTAX Integer32 (0..65535)
	MAX-ACCESS read-only
	STATUS current
	DESCRIPTION
	"The amount of time between the transmission of Configuration bridge PDUs by this node on any port when it is the root of the spanning tree, or trying to become so, in seconds. This is the actual value that this bridge is currently using."
	::= { bridgeStatusEntry 3 }

bridgeStatusMaxAge OBJECT-TYPE   -- max_age
	SYNTAX Integer32 (0..65535)
	MAX-ACCESS read-only
	STATUS current
	DESCRIPTION
	"The maximum age of Spanning Tree Protocol information learned from the network on any port before it is discarded, in seconds. This is the actual value that this bridge is currently using."
	::= { bridgeStatusEntry 4 }

bridgeStatusHoldTime OBJECT-TYPE   -- hold_time
	SYNTAX Integer32 (0..65535)
	MAX-ACCESS read-only
	STATUS current
	DESCRIPTION
	"This time value determines the interval length during which no more than two Configuration bridge PDUs shall be transmitted by this node, in seconds."
	::= { bridgeStatusEntry 5 }

bridgeStatusForwardDelay OBJECT-TYPE   -- forward_delay
	SYNTAX Integer32 (0..65535)
	MAX-ACCESS read-only
	STATUS current
	DESCRIPTION
	"This time controls how fast a port changes its spanning state when moving towards the Forwarding state. The value determines how long the port stays in each of the Listening and Learning states, which precede the Forwarding state."
	::= { bridgeStatusEntry 6 }

bridgeStatusRootPort OBJECT-TYPE   -- root_port
	SYNTAX Integer32 (0..65535)
	MAX-ACCESS read-only
	STATUS current
	DESCRIPTION
	"The port number of the port that offers the lowest cost path from this bridge to the root bridge."
	::= { bridgeStatusEntry 7 }

bridgeStatusRootCost OBJECT-TYPE   -- root_cost
	SYNTAX Unsigned32
	MAX-ACCESS read-only
	STATUS current
	DESCRIPTION
	"The cost of the path to the root as seen from this bridge."
	::= { bridgeStatusEntry 8 }

bridgeStatusTopologyChanges OBJECT-TYPE   -- topology_changes
	SYNTAX Integer32 (0..65535)
	MAX-ACCESS read-only
	STATUS current
	DESCRIPTION
	"The total number of topology changes detected by this bridge since the management entity was last reset or initialized."
	::= { bridgeStatusEntry 9 }

bridgeStatusLastTopologyChange OBJECT-TYPE   -- last_topology_change
	SYNTAX Counter32
	MAX-ACCESS read-only
	STATUS current
	DESCRIPTION
	"The time in seconds when the last time a topology change was detected."
	::= { bridgeStatusEntry 10 }

bridgeStatusMstpRegionName OBJECT-TYPE   -- mstp_region_name
	SYNTAX DisplayString
	MAX-ACCESS read-only
	STATUS current
	DESCRIPTION
	"This the region name actually used."
	::= { bridgeStatusEntry 11 }

bridgeStatusMstiRevisionLevel OBJECT-TYPE   -- msti_revision_level
	SYNTAX Integer32 (0..65535)
	MAX-ACCESS read-only
	STATUS current
	DESCRIPTION
	"This the revision level actually used."
	::= { bridgeStatusEntry 12 }

bridgeStatusCistInternalRootPathCost OBJECT-TYPE   -- cist_internal_root_path_cost
	SYNTAX Unsigned32
	MAX-ACCESS read-only
	STATUS current
	DESCRIPTION
	""
	::= { bridgeStatusEntry 13 }

bridgeStatusCistRegionalRootId OBJECT-TYPE   -- cist_regional_root_id
	SYNTAX DisplayString
	MAX-ACCESS read-only
	STATUS current
	DESCRIPTION
	"The Bridge Identifier of the current CIST Regional Root"
	::= { bridgeStatusEntry 14 }

bridgeStatusCistRegionalRootPriority OBJECT-TYPE   -- cist_regional_root_priority
	SYNTAX Unsigned32
	MAX-ACCESS read-only
	STATUS current
	DESCRIPTION
	"The Bridge priority of the current CIST Regional Root"
	::= { bridgeStatusEntry 15 }

bridgeStatusCistRegionalRootMac OBJECT-TYPE   -- cist_regional_root_mac
	SYNTAX MacAddress
	MAX-ACCESS read-only
	STATUS current
	DESCRIPTION
	"The Bridge MAC of the current CIST Regional Root"
	::= { bridgeStatusEntry 16 }

bridgeStatusMaxHops OBJECT-TYPE   -- max_hops
	SYNTAX Integer32 (0..65535)
	MAX-ACCESS read-only
	STATUS current
	DESCRIPTION
	""
	::= { bridgeStatusEntry 17 }

bridgeStatusMstpStpAgingTime OBJECT-TYPE   -- mstp_stp_aging_time
	SYNTAX Unsigned32
	MAX-ACCESS read-only
	STATUS current
	DESCRIPTION
	"Aging time of the bridge"
	::= { bridgeStatusEntry 18 }


-- ********************* End of bridgeStatusTable ***********************


-- ******************* Begin of portStatusTable *************************

portStatusTable	OBJECT-TYPE
	SYNTAX SEQUENCE OF PortStatusEntry
	MAX-ACCESS not-accessible
	STATUS current
	DESCRIPTION
		""
	::= { stp 101 }

portStatusEntry	OBJECT-TYPE
	SYNTAX PortStatusEntry
	MAX-ACCESS not-accessible
	STATUS current
	DESCRIPTION
		""
	INDEX { portStatusPortIndex }
	::= { portStatusTable 1 }


	PortStatusEntry ::= SEQUENCE {
	portStatusPortIndex INTEGER,
	portStatusPort Integer32 ,
	portStatusState INTEGER ,
	portStatusLocalPortCost Unsigned32,
	portStatusDesignatedPortId DisplayString,
	portStatusDesignatedPort Unsigned32,
	portStatusDesignatedPortPriority Unsigned32,
	portStatusDesignatedCost Unsigned32,
	portStatusDesignatedRootId DisplayString,
	portStatusDesignatedRootMac MacAddress,
	portStatusDesignatedRootPriority Integer32 ,
	portStatusDesignatedBridgeId DisplayString,
	portStatusDesignatedBridgeMac MacAddress,
	portStatusDesignatedBridgePriority Integer32 ,
	portStatusForwardTransition Unsigned32,
	portStatusOperEdgePort INTEGER ,
	portStatusOperP2pPort INTEGER ,
	portStatusRole INTEGER ,
	portStatusInconsistentBridge INTEGER 
	}

portStatusPortIndex	OBJECT-TYPE
	SYNTAX INTEGER (0..31)
	MAX-ACCESS not-accessible
	STATUS current
	DESCRIPTION
		"Automatically generated"
	::= { portStatusEntry 1 }

portStatusPort OBJECT-TYPE   -- port
	SYNTAX Integer32 (0..65535)
	MAX-ACCESS read-only
	STATUS current
	DESCRIPTION
	"The port for which these spanning tree information apply."
	::= { portStatusEntry 2 }

portStatusState OBJECT-TYPE   -- state
	SYNTAX INTEGER 
		{
		unknown (0),
		discarding (1),
		learning (2),
		forwarding (3),
		blocking (4),
		listening (5),
		broken (6)
		}
	MAX-ACCESS read-only
	STATUS current
	DESCRIPTION
	"This state controls what action a port takes on reception of a frame."
	::= { portStatusEntry 3 }

portStatusLocalPortCost OBJECT-TYPE   -- local_port_cost
	SYNTAX Unsigned32
	MAX-ACCESS read-only
	STATUS current
	DESCRIPTION
	"The contribution of this port to the path cost of paths towards the spanning tree root which include this port. This is the actually used value."
	::= { portStatusEntry 4 }

portStatusDesignatedPortId OBJECT-TYPE   -- designated_port_id
	SYNTAX DisplayString
	MAX-ACCESS read-only
	STATUS current
	DESCRIPTION
	"The Port priority and identifier of the port on the Designated Bridge for this port's segment. Format: Priority:PortId."
	::= { portStatusEntry 5 }

portStatusDesignatedPort OBJECT-TYPE   -- designated_port
	SYNTAX Unsigned32
	MAX-ACCESS read-only
	STATUS current
	DESCRIPTION
	"The Port Identifier of the port on the Designated Bridge for this port's segment."
	::= { portStatusEntry 6 }

portStatusDesignatedPortPriority OBJECT-TYPE   -- designated_port_priority
	SYNTAX Unsigned32
	MAX-ACCESS read-only
	STATUS current
	DESCRIPTION
	"The priority of the port on the Designated Bridge for this port's segment."
	::= { portStatusEntry 7 }

portStatusDesignatedCost OBJECT-TYPE   -- designated_cost
	SYNTAX Unsigned32
	MAX-ACCESS read-only
	STATUS current
	DESCRIPTION
	"The path cost of the Designated Port of the segment connected to this port. This value is compared to the Root Path Cost field in received bridge PDUs."
	::= { portStatusEntry 8 }

portStatusDesignatedRootId OBJECT-TYPE   -- designated_root_id
	SYNTAX DisplayString
	MAX-ACCESS read-only
	STATUS current
	DESCRIPTION
	"The priority of the Bridge recorded as the Root in the Configuration BPDUs transmitted by the Designated Bridge for the segment to which the port is connected. This is a 4-bit value included along with 12-bit of designated_root_mac as Root Bridge Identifier."
	::= { portStatusEntry 9 }

portStatusDesignatedRootMac OBJECT-TYPE   -- designated_root_mac
	SYNTAX MacAddress
	MAX-ACCESS read-only
	STATUS current
	DESCRIPTION
	"This contains just the MAC part of the bridge id."
	::= { portStatusEntry 10 }

portStatusDesignatedRootPriority OBJECT-TYPE   -- designated_root_priority
	SYNTAX Integer32 (0..65535)
	MAX-ACCESS read-only
	STATUS current
	DESCRIPTION
	"This contains just the priorty part of the bridge id."
	::= { portStatusEntry 11 }

portStatusDesignatedBridgeId OBJECT-TYPE   -- designated_bridge_id
	SYNTAX DisplayString
	MAX-ACCESS read-only
	STATUS current
	DESCRIPTION
	"The priority of the Bridge that this port considers to be the Designated Bridge for this port segment.This is a 4-bit value included along with 12-bit of designated_bridge_mac as Bridge Identifier."
	::= { portStatusEntry 12 }

portStatusDesignatedBridgeMac OBJECT-TYPE   -- designated_bridge_mac
	SYNTAX MacAddress
	MAX-ACCESS read-only
	STATUS current
	DESCRIPTION
	"The Bridge Identifier of the bridge that this port considers to be the Designated Bridge for this port's segment."
	::= { portStatusEntry 13 }

portStatusDesignatedBridgePriority OBJECT-TYPE   -- designated_bridge_priority
	SYNTAX Integer32 (0..65535)
	MAX-ACCESS read-only
	STATUS current
	DESCRIPTION
	"This contains just the priorty part of the bridge id."
	::= { portStatusEntry 14 }

portStatusForwardTransition OBJECT-TYPE   -- forward_transition
	SYNTAX Unsigned32
	MAX-ACCESS read-only
	STATUS current
	DESCRIPTION
	"The number of times this port has transitioned from the Learning state to the Forwarding state."
	::= { portStatusEntry 15 }

portStatusOperEdgePort OBJECT-TYPE   -- oper_edge_port
	SYNTAX INTEGER { false(0), true(1) }
	MAX-ACCESS read-only
	STATUS current
	DESCRIPTION
	"A value of true indicates that this port should be assumed as an edge-port."
	::= { portStatusEntry 16 }

portStatusOperP2pPort OBJECT-TYPE   -- oper_p2p_port
	SYNTAX INTEGER { false(0), true(1) }
	MAX-ACCESS read-only
	STATUS current
	DESCRIPTION
	"The operational point-to-point status of the LAN segment attached to this port. It indicates whether a port is considered to have a point-to-point connection."
	::= { portStatusEntry 17 }

portStatusRole OBJECT-TYPE   -- role
	SYNTAX INTEGER 
		{
		unknown (0),
		root (1),
		designated (2),
		alternate (3),
		backup (4),
		master (5),
		disabled (6)
		}
	MAX-ACCESS read-only
	STATUS current
	DESCRIPTION
	"Assigned port role"
	::= { portStatusEntry 18 }

portStatusInconsistentBridge OBJECT-TYPE   -- inconsistent_bridge
	SYNTAX INTEGER { false(0), true(1) }
	MAX-ACCESS read-only
	STATUS current
	DESCRIPTION
	"A value of true indicates that the port is inconsistent due to Bridge assurance."
	::= { portStatusEntry 19 }


-- ********************* End of portStatusTable ***********************


-- ******************* Begin of mstpStatusTableTable *************************

mstpStatusTableTable	OBJECT-TYPE
	SYNTAX SEQUENCE OF MstpStatusTableEntry
	MAX-ACCESS not-accessible
	STATUS current
	DESCRIPTION
		"This table contains a record for each MSTP instance and for each port thereof. Table ends with first record with mstp_id=0."
	::= { stp 102 }

mstpStatusTableEntry	OBJECT-TYPE
	SYNTAX MstpStatusTableEntry
	MAX-ACCESS not-accessible
	STATUS current
	DESCRIPTION
		""
	INDEX { mstpStatusTableIndex }
	::= { mstpStatusTableTable 1 }


	MstpStatusTableEntry ::= SEQUENCE {
	mstpStatusTableIndex INTEGER,
	mstpStatusTableMstpId Integer32 ,
	mstpStatusTablePort Integer32 ,
	mstpStatusTableState INTEGER ,
	mstpStatusTablePortPriority Integer32 ,
	mstpStatusTableInternalAdminPathCost Unsigned32,
	mstpStatusTableForwardTransition Unsigned32,
	mstpStatusTableRole INTEGER 
	}

mstpStatusTableIndex	OBJECT-TYPE
	SYNTAX INTEGER (0..2047)
	MAX-ACCESS not-accessible
	STATUS current
	DESCRIPTION
		"Automatically generated"
	::= { mstpStatusTableEntry 1 }

mstpStatusTableMstpId OBJECT-TYPE   -- mstp_id
	SYNTAX Integer32 (0..65535)
	MAX-ACCESS read-only
	STATUS current
	DESCRIPTION
	"MSTP instance this entry"
	::= { mstpStatusTableEntry 2 }

mstpStatusTablePort OBJECT-TYPE   -- port
	SYNTAX Integer32 (0..65535)
	MAX-ACCESS read-only
	STATUS current
	DESCRIPTION
	"Port id of the port in relation to above MSTP instance."
	::= { mstpStatusTableEntry 3 }

mstpStatusTableState OBJECT-TYPE   -- state
	SYNTAX INTEGER 
		{
		unknown (0),
		discarding (1),
		learning (2),
		forwarding (3),
		blocking (4),
		listening (5),
		broken (6)
		}
	MAX-ACCESS read-only
	STATUS current
	DESCRIPTION
	"This state controls what action a port takes on reception of a frame."
	::= { mstpStatusTableEntry 4 }

mstpStatusTablePortPriority OBJECT-TYPE   -- port_priority
	SYNTAX Integer32 (0..255)
	MAX-ACCESS read-only
	STATUS current
	DESCRIPTION
	""
	::= { mstpStatusTableEntry 5 }

mstpStatusTableInternalAdminPathCost OBJECT-TYPE   -- internal_admin_path_cost
	SYNTAX Unsigned32
	MAX-ACCESS read-only
	STATUS current
	DESCRIPTION
	""
	::= { mstpStatusTableEntry 6 }

mstpStatusTableForwardTransition OBJECT-TYPE   -- forward_transition
	SYNTAX Unsigned32
	MAX-ACCESS read-only
	STATUS current
	DESCRIPTION
	"The number of times this port has transitioned from the Learning state to the Forwarding state."
	::= { mstpStatusTableEntry 7 }

mstpStatusTableRole OBJECT-TYPE   -- role
	SYNTAX INTEGER 
		{
		unknown (0),
		root (1),
		designated (2),
		alternate (3),
		backup (4),
		master (5),
		disabled (6)
		}
	MAX-ACCESS read-only
	STATUS current
	DESCRIPTION
	"Assigned port role"
	::= { mstpStatusTableEntry 8 }


-- ********************* End of mstpStatusTableTable ***********************


-- ******************* Begin of mstpBridgeStatusTable *************************

mstpBridgeStatusTable	OBJECT-TYPE
	SYNTAX SEQUENCE OF MstpBridgeStatusEntry
	MAX-ACCESS not-accessible
	STATUS current
	DESCRIPTION
		"This status table collects all multiple spanning tree bridge related status fields."
	::= { stp 103 }

mstpBridgeStatusEntry	OBJECT-TYPE
	SYNTAX MstpBridgeStatusEntry
	MAX-ACCESS not-accessible
	STATUS current
	DESCRIPTION
		""
	INDEX { mstpBridgeStatusIndex }
	::= { mstpBridgeStatusTable 1 }


	MstpBridgeStatusEntry ::= SEQUENCE {
	mstpBridgeStatusIndex INTEGER,
	mstpBridgeStatusMstpId Integer32 ,
	mstpBridgeStatusBridgePriority Unsigned32,
	mstpBridgeStatusRootPort Integer32 ,
	mstpBridgeStatusRootCost Unsigned32,
	mstpBridgeStatusMaxHops Integer32 ,
	mstpBridgeStatusRegionalRootId DisplayString,
	mstpBridgeStatusRegionalRootPriority Unsigned32,
	mstpBridgeStatusRegionalRootMac MacAddress,
	mstpBridgeStatusTopologyChanges Integer32 ,
	mstpBridgeStatusLastTopologyChange Counter32
	}

mstpBridgeStatusIndex	OBJECT-TYPE
	SYNTAX INTEGER (0..62)
	MAX-ACCESS not-accessible
	STATUS current
	DESCRIPTION
		"Automatically generated"
	::= { mstpBridgeStatusEntry 1 }

mstpBridgeStatusMstpId OBJECT-TYPE   -- mstp_id
	SYNTAX Integer32 (0..65535)
	MAX-ACCESS read-only
	STATUS current
	DESCRIPTION
	"MSTP instance identifier."
	::= { mstpBridgeStatusEntry 2 }

mstpBridgeStatusBridgePriority OBJECT-TYPE   -- bridge_priority
	SYNTAX Unsigned32
	MAX-ACCESS read-only
	STATUS current
	DESCRIPTION
	"Bridge priority."
	::= { mstpBridgeStatusEntry 3 }

mstpBridgeStatusRootPort OBJECT-TYPE   -- root_port
	SYNTAX Integer32 (0..65535)
	MAX-ACCESS read-only
	STATUS current
	DESCRIPTION
	"The port number of the port that offers the lowest cost path from this bridge to the root bridge."
	::= { mstpBridgeStatusEntry 4 }

mstpBridgeStatusRootCost OBJECT-TYPE   -- root_cost
	SYNTAX Unsigned32
	MAX-ACCESS read-only
	STATUS current
	DESCRIPTION
	"The cost of the path to the root as seen from this bridge."
	::= { mstpBridgeStatusEntry 5 }

mstpBridgeStatusMaxHops OBJECT-TYPE   -- max_hops
	SYNTAX Integer32 (0..65535)
	MAX-ACCESS read-only
	STATUS current
	DESCRIPTION
	""
	::= { mstpBridgeStatusEntry 6 }

mstpBridgeStatusRegionalRootId OBJECT-TYPE   -- regional_root_id
	SYNTAX DisplayString
	MAX-ACCESS read-only
	STATUS current
	DESCRIPTION
	"The priority of the Bridge recorded as the Root in the Configuration BPDUs transmitted by the Designated Bridge for the segment to which the port is connected. This is a 4-bit value included along with 12-bit of designated_root_mac as Root Bridge Identifier."
	::= { mstpBridgeStatusEntry 7 }

mstpBridgeStatusRegionalRootPriority OBJECT-TYPE   -- regional_root_priority
	SYNTAX Unsigned32
	MAX-ACCESS read-only
	STATUS current
	DESCRIPTION
	"This contains just the MAC part of the bridge id."
	::= { mstpBridgeStatusEntry 8 }

mstpBridgeStatusRegionalRootMac OBJECT-TYPE   -- regional_root_mac
	SYNTAX MacAddress
	MAX-ACCESS read-only
	STATUS current
	DESCRIPTION
	"This contains just the priorty part of the bridge id."
	::= { mstpBridgeStatusEntry 9 }

mstpBridgeStatusTopologyChanges OBJECT-TYPE   -- topology_changes
	SYNTAX Integer32 (0..65535)
	MAX-ACCESS read-only
	STATUS current
	DESCRIPTION
	"The total number of topology changes detected by this mstp bridge instance since the management entity was last reset or initialized."
	::= { mstpBridgeStatusEntry 10 }

mstpBridgeStatusLastTopologyChange OBJECT-TYPE   -- last_topology_change
	SYNTAX Counter32
	MAX-ACCESS read-only
	STATUS current
	DESCRIPTION
	"The time in seconds when the last time a topology change was detected."
	::= { mstpBridgeStatusEntry 11 }


-- ********************* End of mstpBridgeStatusTable ***********************



END
