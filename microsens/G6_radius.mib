G6-RADIUS-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

radius  OBJECT IDENTIFIER ::= { management 69 }



-- *************************** CONFIGURATION SECTION ********************************


-- ******************* Begin of serverTable *************************

serverTable	OBJECT-TYPE
	SYNTAX SEQUENCE OF ServerEntry
	MAX-ACCESS not-accessible
	STATUS current
	DESCRIPTION
		"This dynamic table is used to specify access parameter to authentication servers using RADIUS or TACACS+."
	::= { radius 1 }

serverEntry	OBJECT-TYPE
	SYNTAX ServerEntry
	MAX-ACCESS not-accessible
	STATUS current
	DESCRIPTION
		""
	INDEX { serverIndex }
	::= { serverTable 1 }


	ServerEntry ::= SEQUENCE {
	serverIndex INTEGER,
	serverName DisplayString,
	serverServerType INTEGER ,
	serverHostAddress DisplayString,
	serverUdpPort Integer32 ,
	serverSharedSecret DisplayString,
	serverInterimInterval Unsigned32
	}

serverIndex	OBJECT-TYPE
	SYNTAX INTEGER (0..7)
	MAX-ACCESS not-accessible
	STATUS current
	DESCRIPTION
		"Automatically generated"
	::= { serverEntry 1 }

serverName OBJECT-TYPE   -- name
	SYNTAX DisplayString
	MAX-ACCESS read-write
	STATUS current
	DESCRIPTION
	"Unique name used to identify the server. Used for reference in Port-based Access Control configuration."
	::= { serverEntry 2 }

serverServerType OBJECT-TYPE   -- server_type
	SYNTAX INTEGER 
		{
		radius (0),
		tacacs (1)
		}
	MAX-ACCESS read-write
	STATUS current
	DESCRIPTION
	"Flags if RADIUS or TACACS+ is specified in this entry."
	::= { serverEntry 3 }

serverHostAddress OBJECT-TYPE   -- host_address
	SYNTAX DisplayString
	MAX-ACCESS read-write
	STATUS current
	DESCRIPTION
	"IP address or symbolic name of the authentication server."
	::= { serverEntry 4 }

serverUdpPort OBJECT-TYPE   -- udp_port
	SYNTAX Integer32 (0..65535)
	MAX-ACCESS read-write
	STATUS current
	DESCRIPTION
	"UDP port for RADIUS authentication service. Standard port is 1812. For TACACS+ this specifies the tcp port which defaults to 49."
	::= { serverEntry 5 }

serverSharedSecret OBJECT-TYPE   -- shared_secret
	SYNTAX DisplayString
	MAX-ACCESS read-write
	STATUS current
	DESCRIPTION
	"Shared Secret as common password between authenticator and server."
	::= { serverEntry 6 }

serverInterimInterval OBJECT-TYPE   -- interim_interval
	SYNTAX Unsigned32
	MAX-ACCESS read-write
	STATUS current
	DESCRIPTION
	"If an accountant server is used, this value defines the interval between accounting updates. Set to 0 to disable this function."
	::= { serverEntry 7 }


-- ********************* End of serverTable ***********************



-- ****************************** STATUS SECTION ********************************



END
