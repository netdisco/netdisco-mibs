G6-SNMP-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

snmp  OBJECT IDENTIFIER ::= { management 65 }



-- *************************** CONFIGURATION SECTION ********************************


-- ******************* Begin of deviceInfoTable *************************

deviceInfoTable	OBJECT-TYPE
	SYNTAX SEQUENCE OF DeviceInfoEntry
	MAX-ACCESS not-accessible
	STATUS current
	DESCRIPTION
		"SNMP version MIB-2 variables"
	::= { snmp 1 }

deviceInfoEntry	OBJECT-TYPE
	SYNTAX DeviceInfoEntry
	MAX-ACCESS not-accessible
	STATUS current
	DESCRIPTION
		""
	INDEX { deviceInfoIndex }
	::= { deviceInfoTable 1 }


	DeviceInfoEntry ::= SEQUENCE {
	deviceInfoIndex INTEGER,
	deviceInfoSysDescription DisplayString,
	deviceInfoSysName DisplayString,
	deviceInfoSysLocation DisplayString,
	deviceInfoSysGroup DisplayString,
	deviceInfoSysContact DisplayString,
	deviceInfoSysObjectId DisplayString
	}

deviceInfoIndex	OBJECT-TYPE
	SYNTAX INTEGER (0)
	MAX-ACCESS not-accessible
	STATUS current
	DESCRIPTION
		"Automatically generated"
	::= { deviceInfoEntry 1 }

deviceInfoSysDescription OBJECT-TYPE   -- sys_description
	SYNTAX DisplayString
	MAX-ACCESS read-only
	STATUS current
	DESCRIPTION
	"Device description. This value is SNMP accessible as sysDescr."
	::= { deviceInfoEntry 2 }

deviceInfoSysName OBJECT-TYPE   -- sys_name
	SYNTAX DisplayString
	MAX-ACCESS read-write
	STATUS current
	DESCRIPTION
	"Devicename as assigned by customer. This value is SNMP accessible as sysName."
	::= { deviceInfoEntry 3 }

deviceInfoSysLocation OBJECT-TYPE   -- sys_location
	SYNTAX DisplayString
	MAX-ACCESS read-write
	STATUS current
	DESCRIPTION
	"Location of this device as assigned by customer. This value is SNMP accessible as sysLocation."
	::= { deviceInfoEntry 4 }

deviceInfoSysGroup OBJECT-TYPE   -- sys_group
	SYNTAX DisplayString
	MAX-ACCESS read-write
	STATUS current
	DESCRIPTION
	"Customer defined group definition. Note: This field does not have a MIB-2 counterpart."
	::= { deviceInfoEntry 5 }

deviceInfoSysContact OBJECT-TYPE   -- sys_contact
	SYNTAX DisplayString
	MAX-ACCESS read-write
	STATUS current
	DESCRIPTION
	"Contact person for this device as required by customer. This value is SNMP accessible as sysContact."
	::= { deviceInfoEntry 6 }

deviceInfoSysObjectId OBJECT-TYPE   -- sys_object_id
	SYNTAX DisplayString
	MAX-ACCESS read-only
	STATUS current
	DESCRIPTION
	"Response to SNMP sysObject request."
	::= { deviceInfoEntry 7 }


-- ********************* End of deviceInfoTable ***********************


-- ******************* Begin of v1v2ConfigTable *************************

v1v2ConfigTable	OBJECT-TYPE
	SYNTAX SEQUENCE OF V1v2ConfigEntry
	MAX-ACCESS not-accessible
	STATUS current
	DESCRIPTION
		"SNMP version V1 / V2 variables"
	::= { snmp 2 }

v1v2ConfigEntry	OBJECT-TYPE
	SYNTAX V1v2ConfigEntry
	MAX-ACCESS not-accessible
	STATUS current
	DESCRIPTION
		""
	INDEX { v1v2ConfigIndex }
	::= { v1v2ConfigTable 1 }


	V1v2ConfigEntry ::= SEQUENCE {
	v1v2ConfigIndex INTEGER,
	v1v2ConfigEnableSnmpV1 INTEGER ,
	v1v2ConfigEnableSnmpV2c INTEGER ,
	v1v2ConfigGetCommunity DisplayString,
	v1v2ConfigSetCommunity DisplayString,
	v1v2ConfigSnmpV1v2Username DisplayString,
	v1v2ConfigPermitV1v2SetCommands INTEGER 
	}

v1v2ConfigIndex	OBJECT-TYPE
	SYNTAX INTEGER (0)
	MAX-ACCESS not-accessible
	STATUS current
	DESCRIPTION
		"Automatically generated"
	::= { v1v2ConfigEntry 1 }

v1v2ConfigEnableSnmpV1 OBJECT-TYPE   -- enable_snmp_v1
	SYNTAX INTEGER {  disabled(0), enabled(1) }
	MAX-ACCESS read-write
	STATUS current
	DESCRIPTION
	"Only when enabled will SNMP V1 requests be responded to. May be disabled when only secure SNMP V3 access is allowed."
	::= { v1v2ConfigEntry 2 }

v1v2ConfigEnableSnmpV2c OBJECT-TYPE   -- enable_snmp_v2c
	SYNTAX INTEGER {  disabled(0), enabled(1) }
	MAX-ACCESS read-write
	STATUS current
	DESCRIPTION
	"Only when enabled will SNMP V2C requests be responded to. May be disabled when only secure SNMP V3 access is allowed."
	::= { v1v2ConfigEntry 3 }

v1v2ConfigGetCommunity OBJECT-TYPE   -- get_community
	SYNTAX DisplayString
	MAX-ACCESS read-write
	STATUS current
	DESCRIPTION
	"Community string to enable V1/V2c get commands."
	::= { v1v2ConfigEntry 4 }

v1v2ConfigSetCommunity OBJECT-TYPE   -- set_community
	SYNTAX DisplayString
	MAX-ACCESS read-write
	STATUS current
	DESCRIPTION
	"Community string to enable V1/V2c set commands."
	::= { v1v2ConfigEntry 5 }

v1v2ConfigSnmpV1v2Username OBJECT-TYPE   -- snmp_v1v2_username
	SYNTAX DisplayString
	MAX-ACCESS read-write
	STATUS current
	DESCRIPTION
	"SNMP v1/v2 normally only provides light security by means of the community strings. Additional V3 like security can be applied by setting this field to any user.name defined in the access section. The access restrictions defined for the selected user also apply to the SNMP V1/v2 access when the user name is specified here. When no username or an invalid user name is configured, snmp access is blocked."
	::= { v1v2ConfigEntry 6 }

v1v2ConfigPermitV1v2SetCommands OBJECT-TYPE   -- permit_v1v2_set_commands
	SYNTAX INTEGER {  disabled(0), enabled(1) }
	MAX-ACCESS read-write
	STATUS current
	DESCRIPTION
	"When disabled SNMP sets (writes) are declined and no modifications to the system via unsecure SNMP V1/V2 can occur."
	::= { v1v2ConfigEntry 7 }


-- ********************* End of v1v2ConfigTable ***********************


-- ******************* Begin of v3ConfigTable *************************

v3ConfigTable	OBJECT-TYPE
	SYNTAX SEQUENCE OF V3ConfigEntry
	MAX-ACCESS not-accessible
	STATUS current
	DESCRIPTION
		"SNMP version V3 variables"
	::= { snmp 3 }

v3ConfigEntry	OBJECT-TYPE
	SYNTAX V3ConfigEntry
	MAX-ACCESS not-accessible
	STATUS current
	DESCRIPTION
		""
	INDEX { v3ConfigIndex }
	::= { v3ConfigTable 1 }


	V3ConfigEntry ::= SEQUENCE {
	v3ConfigIndex INTEGER,
	v3ConfigEnableSnmpV3 INTEGER ,
	v3ConfigSecurityModel INTEGER ,
	v3ConfigSnmpEngineId DisplayString,
	v3ConfigTrapEngineId DisplayString
	}

v3ConfigIndex	OBJECT-TYPE
	SYNTAX INTEGER (0)
	MAX-ACCESS not-accessible
	STATUS current
	DESCRIPTION
		"Automatically generated"
	::= { v3ConfigEntry 1 }

v3ConfigEnableSnmpV3 OBJECT-TYPE   -- enable_snmp_v3
	SYNTAX INTEGER {  disabled(0), enabled(1) }
	MAX-ACCESS read-write
	STATUS current
	DESCRIPTION
	"Only when enabled will SNMP V3 requests be responded to. To limit access to SNMP V3 only, disable SNMP V1 and V2 access in the configuration. "
	::= { v3ConfigEntry 2 }

v3ConfigSecurityModel OBJECT-TYPE   -- security_model
	SYNTAX INTEGER 
		{
		usm (0),
		vacm (1)
		}
	MAX-ACCESS read-write
	STATUS current
	DESCRIPTION
	"Selects if user based or view based security model is used."
	::= { v3ConfigEntry 3 }

v3ConfigSnmpEngineId OBJECT-TYPE   -- snmp_engine_id
	SYNTAX DisplayString
	MAX-ACCESS read-write
	STATUS current
	DESCRIPTION
	"Administratively assigned part of the computed engine id. Here the used MAC address can be used to ensure a unique value."
	::= { v3ConfigEntry 4 }

v3ConfigTrapEngineId OBJECT-TYPE   -- trap_engine_id
	SYNTAX DisplayString
	MAX-ACCESS read-write
	STATUS current
	DESCRIPTION
	"This engine id is usedfor outgoing SNMP v3 traps. The value is treated as hexadecimal characters. The associated trap receiver must match this sequence or may be setup to ignore the engine id altogether. Default value defines 80000c6d which represents the our IANA value in hex followed by 03 indicating that a MAC is following. The remaining 12 character represent the MAC address o fthis device."
	::= { v3ConfigEntry 5 }


-- ********************* End of v3ConfigTable ***********************


-- ******************* Begin of browserTable *************************

browserTable	OBJECT-TYPE
	SYNTAX SEQUENCE OF BrowserEntry
	MAX-ACCESS not-accessible
	STATUS current
	DESCRIPTION
		"SNMP browser actions"
	::= { snmp 4 }

browserEntry	OBJECT-TYPE
	SYNTAX BrowserEntry
	MAX-ACCESS not-accessible
	STATUS current
	DESCRIPTION
		""
	INDEX { browserIndex }
	::= { browserTable 1 }


	BrowserEntry ::= SEQUENCE {
	browserIndex INTEGER,
	browserGet DisplayString,
	browserNext DisplayString,
	browserSet DisplayString,
	browserWalk DisplayString
	}

browserIndex	OBJECT-TYPE
	SYNTAX INTEGER (0)
	MAX-ACCESS not-accessible
	STATUS current
	DESCRIPTION
		"Automatically generated"
	::= { browserEntry 1 }

browserGet OBJECT-TYPE   -- get
	SYNTAX DisplayString
	MAX-ACCESS read-write
	STATUS current
	DESCRIPTION
	"Invokes SNMP GET command at other device. Easiest syntax: ..get hostname OID. Type = (nothing) for basic help and = ?  for extensive help. "
	::= { browserEntry 2 }

browserNext OBJECT-TYPE   -- next
	SYNTAX DisplayString
	MAX-ACCESS read-write
	STATUS current
	DESCRIPTION
	"Invokes SNMP GETNEXT command at other device. It will display the next OID following the given one. Syntax: ..get -v 2c -c community hostname OID. Hostname can be symbolic or IP address. "
	::= { browserEntry 3 }

browserSet OBJECT-TYPE   -- set
	SYNTAX DisplayString
	MAX-ACCESS read-write
	STATUS current
	DESCRIPTION
	"Invokes SNMP SET command at other device. Easiest syntax: ..set hostname OID type value. Check examples shown with = (enter). "
	::= { browserEntry 4 }

browserWalk OBJECT-TYPE   -- walk
	SYNTAX DisplayString
	MAX-ACCESS read-write
	STATUS current
	DESCRIPTION
	"Invokes SNMP MIBWALK command at other device. Basic syntax: = IP_address. To see MIB-II system group type = IP system. WARNING: an unlimited mib walk may take a long time. Even when the output is cancelled, the walk will continue to the end. During this time other action commands may not operate! "
	::= { browserEntry 5 }


-- ********************* End of browserTable ***********************



-- ****************************** STATUS SECTION ********************************


snmpEngineBoots OBJECT-TYPE   -- engine_boots
	SYNTAX Unsigned32
	MAX-ACCESS read-only
	STATUS current
	DESCRIPTION
	"Number of reboots of SNMP engine since system reboot."
	::= { snmp 100 }


snmpEngineRuntime OBJECT-TYPE   -- engine_runtime
	SYNTAX Unsigned32
	MAX-ACCESS read-only
	STATUS current
	DESCRIPTION
	"Runtime of SNMP engine in seconds."
	::= { snmp 101 }



END
