G6-MISC-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

misc  OBJECT IDENTIFIER ::= { management 78 }



-- *************************** CONFIGURATION SECTION ********************************


-- ******************* Begin of terminalServerConfigTable *************************

terminalServerConfigTable	OBJECT-TYPE
	SYNTAX SEQUENCE OF TerminalServerConfigEntry
	MAX-ACCESS not-accessible
	STATUS current
	DESCRIPTION
		"This section defines setting for the terminal server feature."
	::= { misc 1 }

terminalServerConfigEntry	OBJECT-TYPE
	SYNTAX TerminalServerConfigEntry
	MAX-ACCESS not-accessible
	STATUS current
	DESCRIPTION
		""
	INDEX { terminalServerConfigIndex }
	::= { terminalServerConfigTable 1 }


	TerminalServerConfigEntry ::= SEQUENCE {
	terminalServerConfigIndex INTEGER,
	terminalServerConfigDeviceName DisplayString,
	terminalServerConfigMode INTEGER ,
	terminalServerConfigRemoteIp OCTET STRING ,
	terminalServerConfigTcpPort Integer32 ,
	terminalServerConfigInactivityTimeout Integer32 ,
	terminalServerConfigDataRate INTEGER ,
	terminalServerConfigDatabits INTEGER ,
	terminalServerConfigParity INTEGER ,
	terminalServerConfigStopBits INTEGER ,
	terminalServerConfigFlowControl INTEGER ,
	terminalServerConfigForwardingTimer Integer32 ,
	terminalServerConfigCharacterCount Integer32 ,
	terminalServerConfigForwardingCharacter INTEGER 
	}

terminalServerConfigIndex	OBJECT-TYPE
	SYNTAX INTEGER (0)
	MAX-ACCESS not-accessible
	STATUS current
	DESCRIPTION
		"Automatically generated"
	::= { terminalServerConfigEntry 1 }

terminalServerConfigDeviceName OBJECT-TYPE   -- device_name
	SYNTAX DisplayString
	MAX-ACCESS read-write
	STATUS current
	DESCRIPTION
	"Descriptive name for customer reference. This name is echoed upon login."
	::= { terminalServerConfigEntry 2 }

terminalServerConfigMode OBJECT-TYPE   -- mode
	SYNTAX INTEGER 
		{
		server (0),
		client (1),
		comPort (2)
		}
	MAX-ACCESS read-write
	STATUS current
	DESCRIPTION
	"Defines the operational mode of the terminal server."
	::= { terminalServerConfigEntry 3 }

terminalServerConfigRemoteIp OBJECT-TYPE   -- remote_ip
	SYNTAX OCTET STRING (SIZE (0..20))
	MAX-ACCESS read-write
	STATUS current
	DESCRIPTION
	"IP address of the associated remote partner. Only applies in CLIENT and COM_PORT mode."
	::= { terminalServerConfigEntry 4 }

terminalServerConfigTcpPort OBJECT-TYPE   -- tcp_port
	SYNTAX Integer32 (0..65535)
	MAX-ACCESS read-write
	STATUS current
	DESCRIPTION
	"Defines the TCP port number under which the terminal server is reachable."
	::= { terminalServerConfigEntry 5 }

terminalServerConfigInactivityTimeout OBJECT-TYPE   -- inactivity_timeout
	SYNTAX Integer32 (0..65535)
	MAX-ACCESS read-write
	STATUS current
	DESCRIPTION
	"An unattended terminal server logs off automatically after specified seconds. Use 0 to disable timeout."
	::= { terminalServerConfigEntry 6 }

terminalServerConfigDataRate OBJECT-TYPE   -- data_rate
	SYNTAX INTEGER 
		{
		ms300 (0),
		ms600 (1),
		ms1200 (2),
		ms2400 (3),
		ms4800 (4),
		ms9600 (5),
		ms19200 (6),
		ms38400 (7),
		ms57600 (8),
		ms115200 (9),
		ms230400 (10)
		}
	MAX-ACCESS read-write
	STATUS current
	DESCRIPTION
	"Data rate in bits per second."
	::= { terminalServerConfigEntry 7 }

terminalServerConfigDatabits OBJECT-TYPE   -- databits
	SYNTAX INTEGER 
		{
		ms7Bit (0),
		ms8Bit (1)
		}
	MAX-ACCESS read-write
	STATUS current
	DESCRIPTION
	"Number of data bits per character."
	::= { terminalServerConfigEntry 8 }

terminalServerConfigParity OBJECT-TYPE   -- parity
	SYNTAX INTEGER 
		{
		none (0),
		odd (1),
		even (2),
		mark (3),
		space (4)
		}
	MAX-ACCESS read-write
	STATUS current
	DESCRIPTION
	"Defines if the parity bit is used."
	::= { terminalServerConfigEntry 9 }

terminalServerConfigStopBits OBJECT-TYPE   -- stop_bits
	SYNTAX INTEGER 
		{
		ms1Bit (0),
		ms2Bits (1)
		}
	MAX-ACCESS read-write
	STATUS current
	DESCRIPTION
	"Number of stop bits per character."
	::= { terminalServerConfigEntry 10 }

terminalServerConfigFlowControl OBJECT-TYPE   -- flow_control
	SYNTAX INTEGER 
		{
		none (0),
		localXonXoff (1),
		passXonXoff (2)
		}
	MAX-ACCESS read-write
	STATUS current
	DESCRIPTION
	"Determines if flow control is used."
	::= { terminalServerConfigEntry 11 }

terminalServerConfigForwardingTimer OBJECT-TYPE   -- forwarding_timer
	SYNTAX Integer32 (0..65535)
	MAX-ACCESS read-write
	STATUS current
	DESCRIPTION
	"Defined in 100ms steps. After no more data are received for this time, the serial data are forwarded to the ethernet side. (VTIME)"
	::= { terminalServerConfigEntry 12 }

terminalServerConfigCharacterCount OBJECT-TYPE   -- character_count
	SYNTAX Integer32 (0..65535)
	MAX-ACCESS read-write
	STATUS current
	DESCRIPTION
	"At least this many character must be received before data are forwarded. Set to zero to ignore count. (VMIN)"
	::= { terminalServerConfigEntry 13 }

terminalServerConfigForwardingCharacter OBJECT-TYPE   -- forwarding_character
	SYNTAX INTEGER 
		{
		none (0),
		cr (1),
		lf (2)
		}
	MAX-ACCESS read-write
	STATUS current
	DESCRIPTION
	"When the specified character is received o the serial port, the tcp packet is forwarded."
	::= { terminalServerConfigEntry 14 }


-- ********************* End of terminalServerConfigTable ***********************


-- ******************* Begin of speakerConfigTable *************************

speakerConfigTable	OBJECT-TYPE
	SYNTAX SEQUENCE OF SpeakerConfigEntry
	MAX-ACCESS not-accessible
	STATUS current
	DESCRIPTION
		"This section defines settings for an optional network addressed loudspeaker. Wav or mps3 files may be played out. Local sound files or network music files can be accessed. Not that WAV files must be provided in the format as required by the selected source. With mp3 on-the-fly transcoding is available."
	::= { misc 2 }

speakerConfigEntry	OBJECT-TYPE
	SYNTAX SpeakerConfigEntry
	MAX-ACCESS not-accessible
	STATUS current
	DESCRIPTION
		""
	INDEX { speakerConfigIndex }
	::= { speakerConfigTable 1 }


	SpeakerConfigEntry ::= SEQUENCE {
	speakerConfigIndex INTEGER,
	speakerConfigPlay DisplayString,
	speakerConfigStop DisplayString,
	speakerConfigVolume DisplayString,
	speakerConfigDeviceName DisplayString,
	speakerConfigDeviceType INTEGER ,
	speakerConfigOutputRate Unsigned32,
	speakerConfigOutputFormat INTEGER ,
	speakerConfigHostAddress DisplayString,
	speakerConfigUdpPort Integer32 
	}

speakerConfigIndex	OBJECT-TYPE
	SYNTAX INTEGER (0)
	MAX-ACCESS not-accessible
	STATUS current
	DESCRIPTION
		"Automatically generated"
	::= { speakerConfigEntry 1 }

speakerConfigPlay OBJECT-TYPE   -- play
	SYNTAX DisplayString
	MAX-ACCESS read-write
	STATUS current
	DESCRIPTION
	"Play a sound file or stream. A local sould file must reside in the sound folder accessible via ftp. Syntax: .play = mysound.mp3  Alternatively a remote file or stream may be played in the format: .play = http://webradiostream.mp3"
	::= { speakerConfigEntry 2 }

speakerConfigStop OBJECT-TYPE   -- stop
	SYNTAX DisplayString
	MAX-ACCESS read-write
	STATUS current
	DESCRIPTION
	"Cancels all sound output."
	::= { speakerConfigEntry 3 }

speakerConfigVolume OBJECT-TYPE   -- volume
	SYNTAX DisplayString
	MAX-ACCESS read-write
	STATUS current
	DESCRIPTION
	"Volume control if possible for this device."
	::= { speakerConfigEntry 4 }

speakerConfigDeviceName OBJECT-TYPE   -- device_name
	SYNTAX DisplayString
	MAX-ACCESS read-write
	STATUS current
	DESCRIPTION
	"Descriptive name for customer reference."
	::= { speakerConfigEntry 5 }

speakerConfigDeviceType OBJECT-TYPE   -- device_type
	SYNTAX INTEGER 
		{
		genericRtp (0),
		smartaudioController (1)
		}
	MAX-ACCESS read-write
	STATUS current
	DESCRIPTION
	"Select type or protocol of desired speaker."
	::= { speakerConfigEntry 6 }

speakerConfigOutputRate OBJECT-TYPE   -- output_rate
	SYNTAX Unsigned32
	MAX-ACCESS read-write
	STATUS current
	DESCRIPTION
	"Output (re)sample rate only applies to MP3 files or streams. Default value 44100."
	::= { speakerConfigEntry 7 }

speakerConfigOutputFormat OBJECT-TYPE   -- output_format
	SYNTAX INTEGER 
		{
		mono (0),
		stereo (1)
		}
	MAX-ACCESS read-write
	STATUS current
	DESCRIPTION
	"Mono Stereo conversion only applies to mp3 files or streams."
	::= { speakerConfigEntry 8 }

speakerConfigHostAddress OBJECT-TYPE   -- host_address
	SYNTAX DisplayString
	MAX-ACCESS read-write
	STATUS current
	DESCRIPTION
	"IP address or symbolic name of the speaker"
	::= { speakerConfigEntry 9 }

speakerConfigUdpPort OBJECT-TYPE   -- udp_port
	SYNTAX Integer32 (0..65535)
	MAX-ACCESS read-write
	STATUS current
	DESCRIPTION
	"UDP port for"
	::= { speakerConfigEntry 10 }


-- ********************* End of speakerConfigTable ***********************



-- ****************************** STATUS SECTION ********************************



END
