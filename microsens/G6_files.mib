G6-FILES-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

files  OBJECT IDENTIFIER ::= { management 72 }



-- *************************** CONFIGURATION SECTION ********************************


-- ******************* Begin of appsTable *************************

appsTable	OBJECT-TYPE
	SYNTAX SEQUENCE OF AppsEntry
	MAX-ACCESS not-accessible
	STATUS current
	DESCRIPTION
		"This section defines commands to view, load and install apps. The files are also accessible via ftp in the apps directory."
	::= { files 1 }

appsEntry	OBJECT-TYPE
	SYNTAX AppsEntry
	MAX-ACCESS not-accessible
	STATUS current
	DESCRIPTION
		""
	INDEX { appsIndex }
	::= { appsTable 1 }


	AppsEntry ::= SEQUENCE {
	appsIndex INTEGER,
	appsListInstalledApps DisplayString,
	appsShowNotes DisplayString,
	appsDisplayFiles DisplayString,
	appsDeleteFile DisplayString,
	appsDownload DisplayString,
	appsListMediaFiles DisplayString,
	appsExportToMedia DisplayString,
	appsImportFromMedia DisplayString,
	appsInstall DisplayString,
	appsDeinstall DisplayString
	}

appsIndex	OBJECT-TYPE
	SYNTAX INTEGER (0)
	MAX-ACCESS not-accessible
	STATUS current
	DESCRIPTION
		"Automatically generated"
	::= { appsEntry 1 }

appsListInstalledApps OBJECT-TYPE   -- list_installed_apps
	SYNTAX DisplayString
	MAX-ACCESS read-write
	STATUS current
	DESCRIPTION
	"Lists which apps are actually installed and ready for use."
	::= { appsEntry 2 }

appsShowNotes OBJECT-TYPE   -- show_notes
	SYNTAX DisplayString
	MAX-ACCESS read-write
	STATUS current
	DESCRIPTION
	"Displays information about an app . The app does not need to be installed for this operation. Syntax: show_notes = appname"
	::= { appsEntry 3 }

appsDisplayFiles OBJECT-TYPE   -- display_files
	SYNTAX DisplayString
	MAX-ACCESS read-write
	STATUS current
	DESCRIPTION
	"Displays a list of all available app installation files."
	::= { appsEntry 4 }

appsDeleteFile OBJECT-TYPE   -- delete_file
	SYNTAX DisplayString
	MAX-ACCESS read-write
	STATUS current
	DESCRIPTION
	"Deletes a previously downloaded app installation file. This does not affect unit operation."
	::= { appsEntry 5 }

appsDownload OBJECT-TYPE   -- download
	SYNTAX DisplayString
	MAX-ACCESS read-write
	STATUS current
	DESCRIPTION
	"Apps can be downloaded using various protocols. The downloaded app will not be activated until requested using the install command. Example: download = ftp://name:passwd@machine.domain:port/full/path/to/appfile.app  Type  = without parameter for additional online help."
	::= { appsEntry 6 }

appsListMediaFiles OBJECT-TYPE   -- list_media_files
	SYNTAX DisplayString
	MAX-ACCESS read-write
	STATUS current
	DESCRIPTION
	"Display a list of all app files available on the external media in the apps folder."
	::= { appsEntry 7 }

appsExportToMedia OBJECT-TYPE   -- export_to_media
	SYNTAX DisplayString
	MAX-ACCESS read-write
	STATUS current
	DESCRIPTION
	"The function depends on the type of device. On devices with USB port this action copies to an inserted memory stick. On a micro switch running from internal memory this action copies to an optional DOS formatted SD card. On all other switch versions this action will do nothing. When applicable this action copies the specified app file onto the removable media. If the file already exists it is overwritten. Syntax: export_to_media = appname"
	::= { appsEntry 8 }

appsImportFromMedia OBJECT-TYPE   -- import_from_media
	SYNTAX DisplayString
	MAX-ACCESS read-write
	STATUS current
	DESCRIPTION
	"The function depends on the type of device. On devices with USB port this action imports the specified config from an inserted memory stick. On a micro switch running from internal memory this  imports the specified config from a DOS formatted SD card. On all other switch versions this action will do nothing. When applicable this action imports the specified app installation file. If the app file name already exists the file is overwritten. Any already running version of the app is not affected. To actually install the imported app use the install command. Syntax: import_from_media = app_file"
	::= { appsEntry 9 }

appsInstall OBJECT-TYPE   -- install
	SYNTAX DisplayString
	MAX-ACCESS read-write
	STATUS current
	DESCRIPTION
	"Installs the app as contained in the .app installation file. Syntax: install = myapp.app. The .app suffix may be omitted. Just typing the app name (with correct capitalization) will automatically select the latest version available on the device. To update an app simply install the new version without deinstallation first. This will keep the app configuration intact (as far as the app parameter are identical between versions). "
	::= { appsEntry 10 }

appsDeinstall OBJECT-TYPE   -- deinstall
	SYNTAX DisplayString
	MAX-ACCESS read-write
	STATUS current
	DESCRIPTION
	"Deinstalls the specified app. The app will no longer be active and all configuration and status entries will be removed. The .app file itself is retained for possible future re-installation. Syntax: deinstall = appname. Note there is no need to deinstall prior to installing an update."
	::= { appsEntry 11 }


-- ********************* End of appsTable ***********************


-- ******************* Begin of scriptsTable *************************

scriptsTable	OBJECT-TYPE
	SYNTAX SEQUENCE OF ScriptsEntry
	MAX-ACCESS not-accessible
	STATUS current
	DESCRIPTION
		"This section defines commands to manipulate microscripts. Sub-folders are permitted. The files are also accessible via ftp in the xml_cli_scripts directory."
	::= { files 2 }

scriptsEntry	OBJECT-TYPE
	SYNTAX ScriptsEntry
	MAX-ACCESS not-accessible
	STATUS current
	DESCRIPTION
		""
	INDEX { scriptsIndex }
	::= { scriptsTable 1 }


	ScriptsEntry ::= SEQUENCE {
	scriptsIndex INTEGER,
	scriptsListFiles DisplayString,
	scriptsShowFile DisplayString,
	scriptsExecute DisplayString,
	scriptsDownloadFromServer DisplayString,
	scriptsUploadToServer DisplayString,
	scriptsCopyFile DisplayString,
	scriptsDeleteFile DisplayString,
	scriptsTerminate DisplayString
	}

scriptsIndex	OBJECT-TYPE
	SYNTAX INTEGER (0)
	MAX-ACCESS not-accessible
	STATUS current
	DESCRIPTION
		"Automatically generated"
	::= { scriptsEntry 1 }

scriptsListFiles OBJECT-TYPE   -- list_files
	SYNTAX DisplayString
	MAX-ACCESS read-write
	STATUS current
	DESCRIPTION
	"Displays a list of all available script files, their size and date of last change."
	::= { scriptsEntry 2 }

scriptsShowFile OBJECT-TYPE   -- show_file
	SYNTAX DisplayString
	MAX-ACCESS read-write
	STATUS current
	DESCRIPTION
	"Displays the content of a script file. In order to edit a file please use the EditScriptFile command."
	::= { scriptsEntry 3 }

scriptsExecute OBJECT-TYPE   -- execute
	SYNTAX DisplayString
	MAX-ACCESS read-write
	STATUS current
	DESCRIPTION
	"Executes the script file supplied. Example: files.scripts.execute = myscript  or ..execute = myfolder/myscript. It also possible to execute a specific soubroutine and even to supply parameter to it. Syntax: script:subroutine par1 par2. Parameter with spaces can be enclosed with curly brackets."
	::= { scriptsEntry 4 }

scriptsDownloadFromServer OBJECT-TYPE   -- download_from_server
	SYNTAX DisplayString
	MAX-ACCESS read-write
	STATUS current
	DESCRIPTION
	"A script can be downloaded from a server. Example: download_from_server = ftp://name:passwd@machine.domain:port/full/path/to/scriptfile.  A local file with same name is overwritten. Type  = without parameter for additional online help."
	::= { scriptsEntry 5 }

scriptsUploadToServer OBJECT-TYPE   -- upload_to_server
	SYNTAX DisplayString
	MAX-ACCESS read-write
	STATUS current
	DESCRIPTION
	"A script file can be uploaded to a foreign server. Syntax: upload_to_server = scriptfile ftp://user:passwd@ftp.upload.com/target_folder/. Append verbose to the command to start a verbose transfer for trouble shooting.  Type  = without parameter for additional online help."
	::= { scriptsEntry 6 }

scriptsCopyFile OBJECT-TYPE   -- copy_file
	SYNTAX DisplayString
	MAX-ACCESS read-write
	STATUS current
	DESCRIPTION
	"Copies an exisiting script file to another file. Example: copy_file = MyScript NewScript. Do not use whitespace in the new file name."
	::= { scriptsEntry 7 }

scriptsDeleteFile OBJECT-TYPE   -- delete_file
	SYNTAX DisplayString
	MAX-ACCESS read-write
	STATUS current
	DESCRIPTION
	"Deletes a script file. Careful, there is no undelete."
	::= { scriptsEntry 8 }

scriptsTerminate OBJECT-TYPE   -- terminate
	SYNTAX DisplayString
	MAX-ACCESS read-write
	STATUS current
	DESCRIPTION
	"This action command can be used to terminate (stop) a background microscript. This may also be used to terminate a script with an endless loop or a too long wait timer. Syntax: files.scripts.terminate = scriptname or files.scripts.terminate = app/scriptname."
	::= { scriptsEntry 9 }


-- ********************* End of scriptsTable ***********************


-- ******************* Begin of scriptdataTable *************************

scriptdataTable	OBJECT-TYPE
	SYNTAX SEQUENCE OF ScriptdataEntry
	MAX-ACCESS not-accessible
	STATUS current
	DESCRIPTION
		"This section defines commands to manipulate data files created by or to be used by script programs or certain apps. For example script generated log data. The files are also accessible via ftp in the script_data directory."
	::= { files 3 }

scriptdataEntry	OBJECT-TYPE
	SYNTAX ScriptdataEntry
	MAX-ACCESS not-accessible
	STATUS current
	DESCRIPTION
		""
	INDEX { scriptdataIndex }
	::= { scriptdataTable 1 }


	ScriptdataEntry ::= SEQUENCE {
	scriptdataIndex INTEGER,
	scriptdataListFiles DisplayString,
	scriptdataShowFile DisplayString,
	scriptdataDownloadFromServer DisplayString,
	scriptdataUploadToServer DisplayString,
	scriptdataCopyFile DisplayString,
	scriptdataDeleteFile DisplayString,
	scriptdataListMediaFiles DisplayString,
	scriptdataExportToMedia DisplayString,
	scriptdataImportFromMedia DisplayString
	}

scriptdataIndex	OBJECT-TYPE
	SYNTAX INTEGER (0)
	MAX-ACCESS not-accessible
	STATUS current
	DESCRIPTION
		"Automatically generated"
	::= { scriptdataEntry 1 }

scriptdataListFiles OBJECT-TYPE   -- list_files
	SYNTAX DisplayString
	MAX-ACCESS read-write
	STATUS current
	DESCRIPTION
	"Displays a list of all available data files."
	::= { scriptdataEntry 2 }

scriptdataShowFile OBJECT-TYPE   -- show_file
	SYNTAX DisplayString
	MAX-ACCESS read-write
	STATUS current
	DESCRIPTION
	"Displays the content of a data file. A text format is assumed. The files cannot not be edited via CLI or the embedded editor within the CLI."
	::= { scriptdataEntry 3 }

scriptdataDownloadFromServer OBJECT-TYPE   -- download_from_server
	SYNTAX DisplayString
	MAX-ACCESS read-write
	STATUS current
	DESCRIPTION
	"A data file can be downloaded. Various protocols may be used. Example: download_from_server = ftp://name:passwd@machine.domain:port/full/path/to/scriptfile.  A possible exisiting local file with same name is overwritten. Type  = without parameter for additional online help."
	::= { scriptdataEntry 4 }

scriptdataUploadToServer OBJECT-TYPE   -- upload_to_server
	SYNTAX DisplayString
	MAX-ACCESS read-write
	STATUS current
	DESCRIPTION
	"A script data file can be uploaded. Various protocols may be used. Example: upload_to_server = scriptfile ftp://user:passwd@ftp.upload.com/  Type  = without parameter for additional online help."
	::= { scriptdataEntry 5 }

scriptdataCopyFile OBJECT-TYPE   -- copy_file
	SYNTAX DisplayString
	MAX-ACCESS read-write
	STATUS current
	DESCRIPTION
	"Copies an exisiting data file to another file. Example: copy_file = MyData NewData. Do not use whitespace in the new file name."
	::= { scriptdataEntry 6 }

scriptdataDeleteFile OBJECT-TYPE   -- delete_file
	SYNTAX DisplayString
	MAX-ACCESS read-write
	STATUS current
	DESCRIPTION
	"Deletes a data file. It does not delete a script file. There is no undelete!"
	::= { scriptdataEntry 7 }

scriptdataListMediaFiles OBJECT-TYPE   -- list_media_files
	SYNTAX DisplayString
	MAX-ACCESS read-write
	STATUS current
	DESCRIPTION
	"Display a list of all files available on the external media in the script_data folder."
	::= { scriptdataEntry 8 }

scriptdataExportToMedia OBJECT-TYPE   -- export_to_media
	SYNTAX DisplayString
	MAX-ACCESS read-write
	STATUS current
	DESCRIPTION
	"The function depends on the type of device. On devices with USB port this action copies to an inserted memory stick. On a micro switch running from internal memory this action copies to an optional DOS formatted SD card. On all other switch versions this action will do nothing. When applicable this action copies the specified script_data file(s) onto the removable media. If the file(s) already exists it is overwritten. Syntax: export_to_media = filename  Wildcard * is supported to copy many files at once."
	::= { scriptdataEntry 9 }

scriptdataImportFromMedia OBJECT-TYPE   -- import_from_media
	SYNTAX DisplayString
	MAX-ACCESS read-write
	STATUS current
	DESCRIPTION
	"The function depends on the type of device. On devices with USB port this action imports the specified config from an inserted memory stick. On a micro switch running from internal memory this  imports the specified config from a DOS formatted SD card. On all other switch versions this action will do nothing. When applicable this action imports the specified files to the script_data folder. If the file(s) already exists they are overwritten. Syntax: import_from_media = filename."
	::= { scriptdataEntry 10 }


-- ********************* End of scriptdataTable ***********************


-- ******************* Begin of configurationTable *************************

configurationTable	OBJECT-TYPE
	SYNTAX SEQUENCE OF ConfigurationEntry
	MAX-ACCESS not-accessible
	STATUS current
	DESCRIPTION
		"This section defines commands to load and store the system configuration. The configuration files are also accessible via ftp under the config directory."
	::= { files 4 }

configurationEntry	OBJECT-TYPE
	SYNTAX ConfigurationEntry
	MAX-ACCESS not-accessible
	STATUS current
	DESCRIPTION
		""
	INDEX { configurationIndex }
	::= { configurationTable 1 }


	ConfigurationEntry ::= SEQUENCE {
	configurationIndex INTEGER,
	configurationListFolders DisplayString,
	configurationBackupToFolder DisplayString,
	configurationRestoreFromFolder DisplayString,
	configurationCommitConfig DisplayString,
	configurationCompareConfiguration DisplayString,
	configurationCopyFolder DisplayString,
	configurationDeleteFolder DisplayString,
	configurationDownloadFromServer DisplayString,
	configurationUploadToServer DisplayString,
	configurationListMediaFolders DisplayString,
	configurationExportToMedia DisplayString,
	configurationImportFromMedia DisplayString,
	configurationFactoryDefaultFolder DisplayString,
	configurationForceFactoryDefault DisplayString
	}

configurationIndex	OBJECT-TYPE
	SYNTAX INTEGER (0)
	MAX-ACCESS not-accessible
	STATUS current
	DESCRIPTION
		"Automatically generated"
	::= { configurationEntry 1 }

configurationListFolders OBJECT-TYPE   -- list_folders
	SYNTAX DisplayString
	MAX-ACCESS read-write
	STATUS current
	DESCRIPTION
	"Displays a list of all available configuration folders."
	::= { configurationEntry 2 }

configurationBackupToFolder OBJECT-TYPE   -- backup_to_folder
	SYNTAX DisplayString
	MAX-ACCESS read-write
	STATUS current
	DESCRIPTION
	"Copies running configuration to a new or existing folder. If the folder name already exists the previous configuration is overwritten. Syntax: backup_to_folder = my_new_config"
	::= { configurationEntry 3 }

configurationRestoreFromFolder OBJECT-TYPE   -- restore_from_folder
	SYNTAX DisplayString
	MAX-ACCESS read-write
	STATUS current
	DESCRIPTION
	"Restores and activates the specified user configuration. Each resulting config change will be logged as usual. Specify source folder. Syntax: restore_from_folder = folder_name. Important: This command does not restore the IP and factory configuration files."
	::= { configurationEntry 4 }

configurationCommitConfig OBJECT-TYPE   -- commit_config
	SYNTAX DisplayString
	MAX-ACCESS read-write
	STATUS current
	DESCRIPTION
	"Commits the config to SD card now. Data are otherwise autosaved using a timer. Use this command to speed up the process. Syntax: commit_config = folder_name. Special case: 'commit_config =' will be automatically extended to 'running' to immediatly save the currently running configuration. Use this command to permanently store the configuration while system.config_save_mode = TEMPORARILY is selected."
	::= { configurationEntry 5 }

configurationCompareConfiguration OBJECT-TYPE   -- compare_configuration
	SYNTAX DisplayString
	MAX-ACCESS read-write
	STATUS current
	DESCRIPTION
	"Compares two configurations and creates CLI script file that can transform the configurations to each other. Syntax: compare_configuration =   (with no argument behind = ) compares running config against factory config (as defined by factory_default_folder). compare_configuration = somename  compares config somename against factory_default_folder.    compare_configuration = somename  someothername   compares the two named configurations. Special names are factory (factory defaults) and running (currently active configuration)."
	::= { configurationEntry 6 }

configurationCopyFolder OBJECT-TYPE   -- copy_folder
	SYNTAX DisplayString
	MAX-ACCESS read-write
	STATUS current
	DESCRIPTION
	"Copies one user config to another. The config will not be activated. Do not use whitespace for the new configuration name."
	::= { configurationEntry 7 }

configurationDeleteFolder OBJECT-TYPE   -- delete_folder
	SYNTAX DisplayString
	MAX-ACCESS read-write
	STATUS current
	DESCRIPTION
	"Deletes the specified user config. There is no undelete !"
	::= { configurationEntry 8 }

configurationDownloadFromServer OBJECT-TYPE   -- download_from_server
	SYNTAX DisplayString
	MAX-ACCESS read-write
	STATUS current
	DESCRIPTION
	"A configuration packed as tar or gztar file can be downloaded to a custom folder. Example: download_from_server = local_config_name  ftp://name:passwd@machine.domain/full/path/to/config_file  The downloaded config is not automatically activated. Type  = without parameter for additional online help."
	::= { configurationEntry 9 }

configurationUploadToServer OBJECT-TYPE   -- upload_to_server
	SYNTAX DisplayString
	MAX-ACCESS read-write
	STATUS current
	DESCRIPTION
	"The content of the specified configuration folder is compressed into a single file (in tar.gz format) and then uploaded to a server. Various protocols may be used. Example: upload_to_server = folder ftp://user:passwd@ftp.upload.com/dir/  Note the trailing / is mandatory for ftp. Instead of a hostname an IP address may be specified. Instead of ftp other transport formats like tftp or http can be specifed. The saved file will be prefixed by the local IP address of the sending device. Type  = without parameter for additional online help."
	::= { configurationEntry 10 }

configurationListMediaFolders OBJECT-TYPE   -- list_media_folders
	SYNTAX DisplayString
	MAX-ACCESS read-write
	STATUS current
	DESCRIPTION
	"Display a list of all configuration folders available on the external media."
	::= { configurationEntry 11 }

configurationExportToMedia OBJECT-TYPE   -- export_to_media
	SYNTAX DisplayString
	MAX-ACCESS read-write
	STATUS current
	DESCRIPTION
	"The function depends on the type of device. On devices with USB port this action copies to an inserted memory stick. On a micro switch running from internal memory this action copies to an optional DOS formatted SD card. On all other switch versions this action will do nothing. When applicable this action copies the specified configuration folder to a new or existing folder on the removable media. If the folder name already exists the previous configuration is overwritten. Syntax: export_media = running   (This example copies the actively running config to folder config/running)"
	::= { configurationEntry 12 }

configurationImportFromMedia OBJECT-TYPE   -- import_from_media
	SYNTAX DisplayString
	MAX-ACCESS read-write
	STATUS current
	DESCRIPTION
	"The function depends on the type of device. On devices with USB port this action imports the specified config from an inserted memory stick. On a micro switch running from internal memory this  imports the specified config from a DOS formatted SD card. On all other switch versions this action will do nothing. When applicable this action imports the specified configuration to a new or existing user folder. If the folder name already exists the previous configuration is overwritten. The config folder must be located under config/name to be detected. Note that when a reserved name like running is imported, the folder is imported as running_imported. To actually activate the imported config use the restore_from_folder action. Syntax: import_from_media = my_new_config"
	::= { configurationEntry 13 }

configurationFactoryDefaultFolder OBJECT-TYPE   -- factory_default_folder
	SYNTAX DisplayString
	MAX-ACCESS read-write
	STATUS current
	DESCRIPTION
	"This parameter permits the definition of a customer specific alternative factory configuration. Care must be taken to create the desired folder beforehand via download or the backup_to_folder command. "
	::= { configurationEntry 14 }

configurationForceFactoryDefault OBJECT-TYPE   -- force_factory_default
	SYNTAX DisplayString
	MAX-ACCESS read-write
	STATUS current
	DESCRIPTION
	"This forcibly overwrites the current configuration with the factory files bypassing regular processing. This is intended for service personnel only and requires special permission. For normal return to factory settings please use  restore_from_folder = factory command."
	::= { configurationEntry 15 }


-- ********************* End of configurationTable ***********************


-- ******************* Begin of firmwareTable *************************

firmwareTable	OBJECT-TYPE
	SYNTAX SEQUENCE OF FirmwareEntry
	MAX-ACCESS not-accessible
	STATUS current
	DESCRIPTION
		"This section defines commands to view, load and update the system firmware."
	::= { files 5 }

firmwareEntry	OBJECT-TYPE
	SYNTAX FirmwareEntry
	MAX-ACCESS not-accessible
	STATUS current
	DESCRIPTION
		""
	INDEX { firmwareIndex }
	::= { firmwareTable 1 }


	FirmwareEntry ::= SEQUENCE {
	firmwareIndex INTEGER,
	firmwareListInstalledVersions DisplayString,
	firmwareDisplayFiles DisplayString,
	firmwareDeleteFile DisplayString,
	firmwareDownload DisplayString,
	firmwareVerifyUpdateFile DisplayString,
	firmwareShowReleaseNotes DisplayString,
	firmwareInstallSoftwareUpdate DisplayString,
	firmwareListMediaFiles DisplayString,
	firmwareExportToMedia DisplayString,
	firmwareImportFromMedia DisplayString,
	firmwareMirrorSdCard DisplayString
	}

firmwareIndex	OBJECT-TYPE
	SYNTAX INTEGER (0)
	MAX-ACCESS not-accessible
	STATUS current
	DESCRIPTION
		"Automatically generated"
	::= { firmwareEntry 1 }

firmwareListInstalledVersions OBJECT-TYPE   -- list_installed_versions
	SYNTAX DisplayString
	MAX-ACCESS read-write
	STATUS current
	DESCRIPTION
	"Lists detailed version information of individual system programs."
	::= { firmwareEntry 2 }

firmwareDisplayFiles OBJECT-TYPE   -- display_files
	SYNTAX DisplayString
	MAX-ACCESS read-write
	STATUS current
	DESCRIPTION
	"Displays a list of all available software files."
	::= { firmwareEntry 3 }

firmwareDeleteFile OBJECT-TYPE   -- delete_file
	SYNTAX DisplayString
	MAX-ACCESS read-write
	STATUS current
	DESCRIPTION
	"Deletes a previously downloaded firmware file. This does not affect unit operation."
	::= { firmwareEntry 4 }

firmwareDownload OBJECT-TYPE   -- download
	SYNTAX DisplayString
	MAX-ACCESS read-write
	STATUS current
	DESCRIPTION
	"Complete updates or patches can be downloaded using various protocols. The downloaded files will not be activated until requested using the install_software_update command. Example: download = ftp://name:passwd@machine.domain:port/full/path/to/firmwarefile.  Type  = without parameter for additional online help."
	::= { firmwareEntry 5 }

firmwareVerifyUpdateFile OBJECT-TYPE   -- verify_update_file
	SYNTAX DisplayString
	MAX-ACCESS read-write
	STATUS current
	DESCRIPTION
	"Verifies the software contained in the update file specified as parameter. Syntax: verify_update_file = newcode.msu The file will not be installed, just verified."
	::= { firmwareEntry 6 }

firmwareShowReleaseNotes OBJECT-TYPE   -- show_release_notes
	SYNTAX DisplayString
	MAX-ACCESS read-write
	STATUS current
	DESCRIPTION
	"Use to read information about a particular software archive file. Syntax: show_release_notes = filename"
	::= { firmwareEntry 7 }

firmwareInstallSoftwareUpdate OBJECT-TYPE   -- install_software_update
	SYNTAX DisplayString
	MAX-ACCESS read-write
	STATUS current
	DESCRIPTION
	"Installs the software as contained in the update file specified as parameter. Syntax: install_software_update = newcode.msu  NOTE: the unit may automatically reboot after the installation."
	::= { firmwareEntry 8 }

firmwareListMediaFiles OBJECT-TYPE   -- list_media_files
	SYNTAX DisplayString
	MAX-ACCESS read-write
	STATUS current
	DESCRIPTION
	"Display a list of all firmware files available on the external media in the updates folder."
	::= { firmwareEntry 9 }

firmwareExportToMedia OBJECT-TYPE   -- export_to_media
	SYNTAX DisplayString
	MAX-ACCESS read-write
	STATUS current
	DESCRIPTION
	"The function depends on the type of device. On devices with USB port this action copies to an inserted memory stick. On a micro switch running from internal memory this action copies to an optional DOS formatted SD card. On all other switch versions this action will do nothing. When applicable this action copies the specified firmware update file (msu) onto the removable media. If the file already exists it is overwritten. Syntax: export_media = u_10_3_3.msu"
	::= { firmwareEntry 10 }

firmwareImportFromMedia OBJECT-TYPE   -- import_from_media
	SYNTAX DisplayString
	MAX-ACCESS read-write
	STATUS current
	DESCRIPTION
	"The function depends on the type of device. On devices with USB port this action imports the specified config from an inserted memory stick. On a micro switch running from internal memory this  imports the specified config from a DOS formatted SD card. On all other switch versions this action will do nothing. When applicable this action imports all firmware update files (msu files) located in the root directory of the media. No parameter are required. Syntax: import_from_media"
	::= { firmwareEntry 11 }

firmwareMirrorSdCard OBJECT-TYPE   -- mirror_sd_card
	SYNTAX DisplayString
	MAX-ACCESS read-write
	STATUS current
	DESCRIPTION
	"The function mirrors the whole content of the SD card into the internal flash memory of a micro switch with internal memory. This command only executes when the device is currently running on the SD card to be copied. On switch versions without internal memory nothing will happen. There are two options. OVERWRITE: All data previously stored in the internal memory, including config and passwords, is overwritten. Possibly existing custom configurations or scripts are retained. REPLACE: The internal memory is first erased before the copy commences. Any existing data are removed. This assures are clean copy ofth SD card without possible extra data being retained. Note: The miror command will not operate when system.boot_preference is set to INTERN_ONLY to safeguard the device against an illegally inserted SD card. Syntax: mirror_sd_card = OVERWRITE (or REPLACE) (uppercase)."
	::= { firmwareEntry 12 }


-- ********************* End of firmwareTable ***********************


-- ******************* Begin of certificateTable *************************

certificateTable	OBJECT-TYPE
	SYNTAX SEQUENCE OF CertificateEntry
	MAX-ACCESS not-accessible
	STATUS current
	DESCRIPTION
		"This section defines commands use private SSL certificate for secure web access."
	::= { files 6 }

certificateEntry	OBJECT-TYPE
	SYNTAX CertificateEntry
	MAX-ACCESS not-accessible
	STATUS current
	DESCRIPTION
		""
	INDEX { certificateIndex }
	::= { certificateTable 1 }


	CertificateEntry ::= SEQUENCE {
	certificateIndex INTEGER,
	certificateListFiles DisplayString,
	certificateDownloadFromServer DisplayString,
	certificateUploadToServer DisplayString,
	certificateDeleteFile DisplayString,
	certificateActivateForWeb DisplayString,
	certificateActivateForSupplicant DisplayString,
	certificateDeactivateForSupplicant DisplayString,
	certificateViewActiveCertificates DisplayString
	}

certificateIndex	OBJECT-TYPE
	SYNTAX INTEGER (0)
	MAX-ACCESS not-accessible
	STATUS current
	DESCRIPTION
		"Automatically generated"
	::= { certificateEntry 1 }

certificateListFiles OBJECT-TYPE   -- list_files
	SYNTAX DisplayString
	MAX-ACCESS read-write
	STATUS current
	DESCRIPTION
	"Displays a list of all custom certificates available."
	::= { certificateEntry 2 }

certificateDownloadFromServer OBJECT-TYPE   -- download_from_server
	SYNTAX DisplayString
	MAX-ACCESS read-write
	STATUS current
	DESCRIPTION
	"Custom certificate files can be downloaded. Various protocols may be used. Example: download_from_server = ftp://name:passwd@machine.domain:port/full/path/to/certificatefile.  A possible local file with same name is overwritten.  Type  = without parameter for additional online help."
	::= { certificateEntry 3 }

certificateUploadToServer OBJECT-TYPE   -- upload_to_server
	SYNTAX DisplayString
	MAX-ACCESS read-write
	STATUS current
	DESCRIPTION
	"Custom certificate files can be uploaded. Various protocols may be used. Example: upload_to_server = certificate_file ftp://user:passwd@ftp.upload.com/  Type  = without parameter for additional online help."
	::= { certificateEntry 4 }

certificateDeleteFile OBJECT-TYPE   -- delete_file
	SYNTAX DisplayString
	MAX-ACCESS read-write
	STATUS current
	DESCRIPTION
	"Deletes an individual certificate file. The full name must be specified."
	::= { certificateEntry 5 }

certificateActivateForWeb OBJECT-TYPE   -- activate_for_web
	SYNTAX DisplayString
	MAX-ACCESS read-write
	STATUS current
	DESCRIPTION
	"Activates the specified certificate to become active immediately for https.  Syntax: activate_for_web = certificate_name (without extensions). Expects 'certificate_name.crt' and 'certificate_name.key' in certificate directory and optionally 'certificate_name.chain.crt' to be used as chain certificate file."
	::= { certificateEntry 6 }

certificateActivateForSupplicant OBJECT-TYPE   -- activate_for_supplicant
	SYNTAX DisplayString
	MAX-ACCESS read-write
	STATUS current
	DESCRIPTION
	"Activates the specified certificate to become active immediately for the supplicant.  Syntax: activate_for_supplicant = target certificate_name (without extensions). Use target: SERVER, LOCAL or KEY. Expects existing certificate file name."
	::= { certificateEntry 7 }

certificateDeactivateForSupplicant OBJECT-TYPE   -- deactivate_for_supplicant
	SYNTAX DisplayString
	MAX-ACCESS read-write
	STATUS current
	DESCRIPTION
	"Activates the specified certificate to become active immediately for the supplicant.  Syntax: activate_for_supplicant = target. Use target: SERVER, LOCAL or KEY. No certificate name is required. The certicate are not deleted, just not used anymore."
	::= { certificateEntry 8 }

certificateViewActiveCertificates OBJECT-TYPE   -- view_active_certificates
	SYNTAX DisplayString
	MAX-ACCESS read-write
	STATUS current
	DESCRIPTION
	"Displays the content of all currenty active certificates."
	::= { certificateEntry 9 }


-- ********************* End of certificateTable ***********************


-- ******************* Begin of licenseTable *************************

licenseTable	OBJECT-TYPE
	SYNTAX SEQUENCE OF LicenseEntry
	MAX-ACCESS not-accessible
	STATUS current
	DESCRIPTION
		"This section defines commands install, active and check software licensing files."
	::= { files 7 }

licenseEntry	OBJECT-TYPE
	SYNTAX LicenseEntry
	MAX-ACCESS not-accessible
	STATUS current
	DESCRIPTION
		""
	INDEX { licenseIndex }
	::= { licenseTable 1 }


	LicenseEntry ::= SEQUENCE {
	licenseIndex INTEGER,
	licenseListFiles DisplayString,
	licenseShowFile DisplayString,
	licenseDownloadFromServer DisplayString,
	licenseDeleteFile DisplayString,
	licenseActivate DisplayString,
	licenseViewActiveLicenses DisplayString
	}

licenseIndex	OBJECT-TYPE
	SYNTAX INTEGER (0)
	MAX-ACCESS not-accessible
	STATUS current
	DESCRIPTION
		"Automatically generated"
	::= { licenseEntry 1 }

licenseListFiles OBJECT-TYPE   -- list_files
	SYNTAX DisplayString
	MAX-ACCESS read-write
	STATUS current
	DESCRIPTION
	"Displays a list of all licenses installed."
	::= { licenseEntry 2 }

licenseShowFile OBJECT-TYPE   -- show_file
	SYNTAX DisplayString
	MAX-ACCESS read-write
	STATUS current
	DESCRIPTION
	"Displays the content of a selected license file. License files are human readable. Be aware that any manual change to then will invalidate the signature."
	::= { licenseEntry 3 }

licenseDownloadFromServer OBJECT-TYPE   -- download_from_server
	SYNTAX DisplayString
	MAX-ACCESS read-write
	STATUS current
	DESCRIPTION
	"License files can be downloaded. Various protocols may be used. Example: download_from_server = ftp://name:passwd@machine.domain:port/full/path/to/certificatefile.  A possible local file with same name is overwritten.  Type  = without parameter for additional online help."
	::= { licenseEntry 4 }

licenseDeleteFile OBJECT-TYPE   -- delete_file
	SYNTAX DisplayString
	MAX-ACCESS read-write
	STATUS current
	DESCRIPTION
	"Deletes an individual license file. The full name must be specified."
	::= { licenseEntry 5 }

licenseActivate OBJECT-TYPE   -- activate
	SYNTAX DisplayString
	MAX-ACCESS read-write
	STATUS current
	DESCRIPTION
	"Activates all available licenses to become active immediately. No parameter are required. Licenses are also activated upon system start."
	::= { licenseEntry 6 }

licenseViewActiveLicenses OBJECT-TYPE   -- view_active_licenses
	SYNTAX DisplayString
	MAX-ACCESS read-write
	STATUS current
	DESCRIPTION
	"Displays a summary of all licenses and their expiration dates."
	::= { licenseEntry 7 }


-- ********************* End of licenseTable ***********************


-- ******************* Begin of historyTable *************************

historyTable	OBJECT-TYPE
	SYNTAX SEQUENCE OF HistoryEntry
	MAX-ACCESS not-accessible
	STATUS current
	DESCRIPTION
		"This section defines commands to access the history files created of history logging is enabled. The files are also accessible via ftp in the history directory."
	::= { files 8 }

historyEntry	OBJECT-TYPE
	SYNTAX HistoryEntry
	MAX-ACCESS not-accessible
	STATUS current
	DESCRIPTION
		""
	INDEX { historyIndex }
	::= { historyTable 1 }


	HistoryEntry ::= SEQUENCE {
	historyIndex INTEGER,
	historyListFiles DisplayString,
	historyShowFile DisplayString,
	historyUploadToServer DisplayString,
	historyCopyFile DisplayString,
	historyDeleteFile DisplayString,
	historyListMediaFiles DisplayString,
	historyExportToMedia DisplayString
	}

historyIndex	OBJECT-TYPE
	SYNTAX INTEGER (0)
	MAX-ACCESS not-accessible
	STATUS current
	DESCRIPTION
		"Automatically generated"
	::= { historyEntry 1 }

historyListFiles OBJECT-TYPE   -- list_files
	SYNTAX DisplayString
	MAX-ACCESS read-write
	STATUS current
	DESCRIPTION
	"Displays a list of all available history files."
	::= { historyEntry 2 }

historyShowFile OBJECT-TYPE   -- show_file
	SYNTAX DisplayString
	MAX-ACCESS read-write
	STATUS current
	DESCRIPTION
	"Displays the content of a history file. The files cannot not be edited via CLI or the embedded editor within the CLI."
	::= { historyEntry 3 }

historyUploadToServer OBJECT-TYPE   -- upload_to_server
	SYNTAX DisplayString
	MAX-ACCESS read-write
	STATUS current
	DESCRIPTION
	"A script data file can be uploaded. Various protocols may be used. Example: upload_to_server = file ftp://user:passwd@ftp.upload.com/  Type  = without parameter for additional online help."
	::= { historyEntry 4 }

historyCopyFile OBJECT-TYPE   -- copy_file
	SYNTAX DisplayString
	MAX-ACCESS read-write
	STATUS current
	DESCRIPTION
	"Copies an exisiting history data file to another file. Example: copy_file = history_file backup_name. Do not use whitespace in the new file name."
	::= { historyEntry 5 }

historyDeleteFile OBJECT-TYPE   -- delete_file
	SYNTAX DisplayString
	MAX-ACCESS read-write
	STATUS current
	DESCRIPTION
	"Deletes a history file. When a file is deleted, which is still updated by the history process, then a new file started as soon as the next history update cycle starts."
	::= { historyEntry 6 }

historyListMediaFiles OBJECT-TYPE   -- list_media_files
	SYNTAX DisplayString
	MAX-ACCESS read-write
	STATUS current
	DESCRIPTION
	"Display a list of all history files available on the external media in the history folder."
	::= { historyEntry 7 }

historyExportToMedia OBJECT-TYPE   -- export_to_media
	SYNTAX DisplayString
	MAX-ACCESS read-write
	STATUS current
	DESCRIPTION
	"The function depends on the type of device. On devices with USB port this action copies to an inserted memory stick. On a micro switch running from internal memory this action copies to an optional DOS formatted SD card. On all other switch versions this action will do nothing. When applicable this action copies the specified history files onto the removable media. If a file already exists it is overwritten. Syntax: export_media = filename. Wildcard * may be used to select several files at once. Example: temperature_day_2017_11*   to get all files of November."
	::= { historyEntry 8 }


-- ********************* End of historyTable ***********************


-- ******************* Begin of logfilesTable *************************

logfilesTable	OBJECT-TYPE
	SYNTAX SEQUENCE OF LogfilesEntry
	MAX-ACCESS not-accessible
	STATUS current
	DESCRIPTION
		"This section permits read access to various system log files. The files are also accessible via ftp in the logs directory."
	::= { files 9 }

logfilesEntry	OBJECT-TYPE
	SYNTAX LogfilesEntry
	MAX-ACCESS not-accessible
	STATUS current
	DESCRIPTION
		""
	INDEX { logfilesIndex }
	::= { logfilesTable 1 }


	LogfilesEntry ::= SEQUENCE {
	logfilesIndex INTEGER,
	logfilesListFiles DisplayString,
	logfilesShowFile DisplayString,
	logfilesShowLastUpdateLog DisplayString,
	logfilesUploadLastSnapshot DisplayString,
	logfilesExportToMedia DisplayString
	}

logfilesIndex	OBJECT-TYPE
	SYNTAX INTEGER (0)
	MAX-ACCESS not-accessible
	STATUS current
	DESCRIPTION
		"Automatically generated"
	::= { logfilesEntry 1 }

logfilesListFiles OBJECT-TYPE   -- list_files
	SYNTAX DisplayString
	MAX-ACCESS read-write
	STATUS current
	DESCRIPTION
	"Displays a list of all available log files."
	::= { logfilesEntry 2 }

logfilesShowFile OBJECT-TYPE   -- show_file
	SYNTAX DisplayString
	MAX-ACCESS read-write
	STATUS current
	DESCRIPTION
	"Displays the content of a log file. The files cannot not be edited via CLI or the embedded editor within the CLI."
	::= { logfilesEntry 3 }

logfilesShowLastUpdateLog OBJECT-TYPE   -- show_last_update_log
	SYNTAX DisplayString
	MAX-ACCESS read-write
	STATUS current
	DESCRIPTION
	"Displays the last firmware update logfile."
	::= { logfilesEntry 4 }

logfilesUploadLastSnapshot OBJECT-TYPE   -- upload_last_snapshot
	SYNTAX DisplayString
	MAX-ACCESS read-write
	STATUS current
	DESCRIPTION
	"A system snapshot contains all data required for comprehensive offsite troubleshooting. A snapshot can be created under Device.system.create_snapshot. Use the upload command to send the result to a remote system. Example: upload_last_snapshot = ftp://user:passwd@ftp.upload.com/  Type  = without parameter for additional online help."
	::= { logfilesEntry 5 }

logfilesExportToMedia OBJECT-TYPE   -- export_to_media
	SYNTAX DisplayString
	MAX-ACCESS read-write
	STATUS current
	DESCRIPTION
	"The function depends on the type of device. On devices with USB port this action copies to an inserted memory stick. On a micro switch running from internal memory this action copies to an optional DOS formatted SD card. On all other switch versions this action will do nothing. When applicable this action copies all log files onto the removable media."
	::= { logfilesEntry 6 }


-- ********************* End of logfilesTable ***********************


-- ******************* Begin of serverTable *************************

serverTable	OBJECT-TYPE
	SYNTAX SEQUENCE OF ServerEntry
	MAX-ACCESS not-accessible
	STATUS current
	DESCRIPTION
		"The different file transfer protocols may individually be enabled or disabled for protection."
	::= { files 10 }

serverEntry	OBJECT-TYPE
	SYNTAX ServerEntry
	MAX-ACCESS not-accessible
	STATUS current
	DESCRIPTION
		""
	INDEX { serverIndex }
	::= { serverTable 1 }


	ServerEntry ::= SEQUENCE {
	serverIndex INTEGER,
	serverEnableTftp INTEGER ,
	serverEnableFtp INTEGER ,
	serverEnableSftp INTEGER ,
	serverEnableApi INTEGER 
	}

serverIndex	OBJECT-TYPE
	SYNTAX INTEGER (0)
	MAX-ACCESS not-accessible
	STATUS current
	DESCRIPTION
		"Automatically generated"
	::= { serverEntry 1 }

serverEnableTftp OBJECT-TYPE   -- enable_tftp
	SYNTAX INTEGER {  disabled(0), enabled(1) }
	MAX-ACCESS read-write
	STATUS current
	DESCRIPTION
	"Enable TFTP server for file up-/download."
	::= { serverEntry 2 }

serverEnableFtp OBJECT-TYPE   -- enable_ftp
	SYNTAX INTEGER {  disabled(0), enabled(1) }
	MAX-ACCESS read-write
	STATUS current
	DESCRIPTION
	"Enable FTP server for file up-/download."
	::= { serverEntry 3 }

serverEnableSftp OBJECT-TYPE   -- enable_sftp
	SYNTAX INTEGER {  disabled(0), enabled(1) }
	MAX-ACCESS read-write
	STATUS current
	DESCRIPTION
	"Enable SFTP server for file up-/download. Note SFTP also requires SSH to be enabled (see CLI settings)"
	::= { serverEntry 4 }

serverEnableApi OBJECT-TYPE   -- enable_api
	SYNTAX INTEGER {  disabled(0), enabled(1) }
	MAX-ACCESS read-write
	STATUS current
	DESCRIPTION
	"Enable api server for dotstring management via https."
	::= { serverEntry 5 }


-- ********************* End of serverTable ***********************



-- ****************************** STATUS SECTION ********************************



END
