LIEBERT-GP-NOTIFICATIONS-MIB DEFINITIONS ::= BEGIN

IMPORTS
    sysUpTime
        FROM RFC1213-MIB
    MODULE-IDENTITY, 
    OBJECT-IDENTITY,
    OBJECT-TYPE, 
    NOTIFICATION-TYPE
        FROM SNMPv2-SMI
    lgpNotifications, 
    liebertNotificationsModuleReg
        FROM LIEBERT-GP-REGISTRATION-MIB
    lgpConditionId, 
    lgpConditionDescr, 
    lgpConditionTime, 
    lgpConditionTableRef,
    lgpConditionTableRowRef
        FROM LIEBERT-GP-CONDITIONS-MIB
   ;

-- =============================================================================
-- Module Identification and Registration
-- =============================================================================

liebertGlobalProductsNotificationsModule MODULE-IDENTITY
  LAST-UPDATED "200807020000Z"
  ORGANIZATION "Liebert Corporation"
  CONTACT-INFO
      "Contact:   Technical Support

      Postal:
      Liebert Corporation
      1050 Dearborn Drive
      P.O. Box 29186
      Columbus OH, 43229
      US

      Tel: +1 (800) 222-5877

      E-mail: liebert.monitoring@vertivco.com
      Web:    www.vertivco.com

      Author:  Craig S. Ward"

   DESCRIPTION
      "The MIB module used to register Liebert SNMP OIDs.

      Copyright 2000-2008 Liebert Corporation. All rights reserved.
      Reproduction of this document is authorized on the condition
      that the forgoing copyright notice is included.

      This Specification is supplied 'AS IS' and Liebert Corporation
      makes no warranty, either express or implied, as to the use,
      operation, condition, or performance of the Specification."

   REVISION "200807020000Z"
   DESCRIPTION
   "   o Added Notifications for PDU devices (power on/off).  
       o Added lgpEventParameters branch for defining notification payload 
         that specifically identifies objects that are contained in tables.
       o Added new varbind to the lgpEventConditionEntryAdded and
         lgpEventConditionEntryRemoved notifications.
       o Fixed minor SMIv2 warnings and issues
   "

   REVISION "200805150000Z"
   DESCRIPTION
   "   o Added Notifications for PDU devices (power on/off).  
       o Added lgpEventParameters branch for defining notification payload 
         that specifically identifies objects that are contained in tables.
       o Added new varbind to the lgpEventConditionEntryAdded and
         lgpEventConditionEntryRemoved notifications.
       o Fixed minor SMIv2 warnings and issues
   "

   REVISION "200801100000Z"
   DESCRIPTION
    "Modified contact email address and deprecated both:
      o lgpEventAgentFirmwareUpdateSuccessful
      o lgpEventAgentFirmwareCorrupt
    which were moved to the LIEBERT-GP-AGENT-MIB document."

   REVISION "200608150000Z"
   DESCRIPTION
    "Added events for firmware update successful and for firmware corrupt."

   REVISION "200602220000Z"
   DESCRIPTION
    "Added support for Liebert DS Unit."

   ::= { liebertNotificationsModuleReg 1 }

-- =============================================================================
--  lgpNotifications - Liebert Notifications Registrations
-- =============================================================================

lgpEventNotifications OBJECT-IDENTITY
    STATUS current
    DESCRIPTION
        "Notifications for Liebert Global Products."
    ::= { lgpNotifications 0 }

lgpEventParameters OBJECT-IDENTITY
    STATUS current
    DESCRIPTION
        "This sub tree describes various parameters/data that are carried
         in the payload of some notifications."
    ::= { lgpNotifications 10 }

    lgpEventParmTableRef OBJECT-TYPE
        SYNTAX      OBJECT IDENTIFIER
        MAX-ACCESS  read-only
        STATUS      current
        DESCRIPTION
            "This object will be included as a varbind in some
             lgpEventNotifications.  It is a reference to a table object in 
             the MIB.  The value of this object will be the OID of a table 
             that the object that the notification applies to is defined.
             The notification containing this object will also contain 
             a varbind 'lgpEventParmTableRowRef' that will specify which 
             instance (row) in the table the object is defined in.

             Example:
               NOTIFICATION: lgpEventConditionEntryAdded
               varbind: lgpConditionId          6
               varbind: lgpConditionDescr       lgpConditionRcpBranchBreakerOpen
               varbind: lgpConditionTime        393884848
               varbind: lgpEventParmTableRef    lgpPduRbTable
               varbind: lgpEventParmTableRowRef lgpPduRbEntryId.1.4

             In the above example the breaker opened for a Receptacle branch.
             The specific receptacle branch is specified by the additional
             varbind (lgpEventParmTableRowRef).  In this case the notification
             is for the 4th receptacle branch on the 1st PDU in the PDU cluster.
            "
        ::= { lgpEventParameters 5 }

    lgpEventParmTableRowRef OBJECT-TYPE
        SYNTAX      OBJECT IDENTIFIER
        MAX-ACCESS  read-only
        STATUS      current
        DESCRIPTION
            "This is a reference to the intersection of a row and column (cell)
             in the table specified by the companion varbind 
             (lgpEventParmTableRef) in this notification.  The row in the
             table where this cell exists represents the object that this
             notification applies to.

             Example:
               NOTIFICATION: lgpEventRcpPowerStateChangeOff
               varbind: sysUpTime               393885975
               varbind: lgpEventParmTableRef    lgpPduRcpTable
               varbind: lgpEventParmTableRowRef lgpPduRcpEntryId.2.4.5

             In the above example the power state changed for a Receptacle.

             The table containing the definition of the receptacle
             (lgpPduRcpTable) is given by the varbind (lgpEventParmTableRef)

             The specific receptacle is specified by the varbind
             (lgpEventParmTableRowRef).  In this case the notification
             is for the 5th receptacle on the 4th receptacle branch on the 
             2nd PDU in the PDU cluster.

             If one wanted to retrieve the user assigned label for this 
             receptacle the OID would be: lgpPduRcpEntryUsrLabel.2.4.5
            "
        ::= { lgpEventParameters 6 }

lgpEventConditionEntryAdded NOTIFICATION-TYPE
    OBJECTS     { lgpConditionId, 
                  lgpConditionDescr, 
                  lgpConditionTime,
                  lgpConditionTableRef,
                  lgpConditionTableRowRef
                }
    STATUS      current
    DESCRIPTION
        "This notification is sent each time a condition is inserted into the
        conditions table."
    ::= { lgpEventNotifications 1 }

lgpEventConditionEntryRemoved NOTIFICATION-TYPE
    OBJECTS     { lgpConditionId, 
                  lgpConditionDescr, 
                  lgpConditionTime,
                  lgpConditionTableRef,
                  lgpConditionTableRowRef
                }
    STATUS      current
    DESCRIPTION
        "This notification is sent each time a condition is removed from the
        conditions table."
    ::= { lgpEventNotifications 2 }

lgpEventLowBatteryWarning NOTIFICATION-TYPE
    OBJECTS     { sysUpTime }
    STATUS      current
    DESCRIPTION
        "The battery's remaining charge is less than or equal to the agent's
        configured low threshold 'lgpPwrConfigLowBatteryWarningTime'."
    ::= { lgpEventNotifications 3 }

lgpEventLoadTransferedToBypass NOTIFICATION-TYPE
    OBJECTS     { sysUpTime }
    STATUS      current
    DESCRIPTION
        "The device has transferred the load to the bypass source."
    ::= { lgpEventNotifications 4 }

lgpEventInternalFault NOTIFICATION-TYPE
    OBJECTS     { sysUpTime }
    STATUS      current
    DESCRIPTION
        "The device has reported an internal fault."
    ::= { lgpEventNotifications 5 }

lgpEventBatteryTestFailed NOTIFICATION-TYPE
    OBJECTS     { sysUpTime }
    STATUS      current
    DESCRIPTION
        "The device has reported a battery self-test failure."
    ::= { lgpEventNotifications 6 }

lgpEventOutputOverload NOTIFICATION-TYPE
    OBJECTS     { sysUpTime }
    STATUS      current
    DESCRIPTION
        "The device has reported an output overload condition."
    ::= { lgpEventNotifications 7 }

lgpEventEstablishedPowerRedundancy NOTIFICATION-TYPE
    OBJECTS     { sysUpTime }
    STATUS      current
    DESCRIPTION
        "The device has transitioned to the user defined redundant state."
    ::= { lgpEventNotifications 8 }

lgpEventLostPowerRedundancy NOTIFICATION-TYPE
    OBJECTS     { sysUpTime }
    STATUS      current
    DESCRIPTION
        "The device as transitioned to a non-redundant power state as defined
        by the user configured threshold."
    ::= { lgpEventNotifications 9 }

lgpEventPowerModuleFailure NOTIFICATION-TYPE
    OBJECTS     { sysUpTime }
    STATUS      current
    DESCRIPTION
        "Device power module failure."
    ::= { lgpEventNotifications 10 }

lgpEventBatteryModuleFailure NOTIFICATION-TYPE
    OBJECTS     { sysUpTime }
    STATUS      current
    DESCRIPTION
        "Device battery module failure."
    ::= { lgpEventNotifications 11 }

lgpEventControlModuleFailure NOTIFICATION-TYPE
    OBJECTS     { sysUpTime }
    STATUS      current
    DESCRIPTION
        "Device control module failure."
    ::= { lgpEventNotifications 12 }

lgpEventPowerModuleWarning NOTIFICATION-TYPE
    OBJECTS     { sysUpTime }
    STATUS      current
    DESCRIPTION
        "Device power module warning."
    ::= { lgpEventNotifications 13 }

lgpEventBatteryModuleWarning NOTIFICATION-TYPE
    OBJECTS     { sysUpTime }
    STATUS      current
    DESCRIPTION
        "Device battery module warning."
    ::= { lgpEventNotifications 14 }

lgpEventControlModuleWarning NOTIFICATION-TYPE
    OBJECTS     { sysUpTime }
    STATUS      current
    DESCRIPTION
        "Device control module warning."
    ::= { lgpEventNotifications 15 }

lgpEventAgentFirmwareUpdateSuccessful NOTIFICATION-TYPE
    OBJECTS     { sysUpTime }
    STATUS      deprecated
    DESCRIPTION
        "The firmware update to the agent card has completed successfully.

        This element has been relocated to lgpAgentFirmwareUpdateSuccessful
        in the LIEBERT-GP-AGENT-MIB document."
    ::= { lgpEventNotifications 16 }

lgpEventAgentFirmwareCorrupt NOTIFICATION-TYPE
    OBJECTS     { sysUpTime }
    STATUS      deprecated
    DESCRIPTION
        "The firmware update to the agent card has failed and the firmware is
        now corrupt.

        This element has been relocated to lgpAgentFirmwareCorrupt
        in the LIEBERT-GP-AGENT-MIB document."
    ::= { lgpEventNotifications 17 }

lgpEventConfigModified NOTIFICATION-TYPE
    OBJECTS     { 
                  sysUpTime, 
                  lgpEventParmTableRef, 
                  lgpEventParmTableRowRef 
                }
    STATUS      current
    DESCRIPTION
        "Configuration for the referenced PDU has been modified."
    ::= { lgpEventNotifications 18 }

lgpEventModuleAdded NOTIFICATION-TYPE
    OBJECTS     { 
                  sysUpTime, 
                  lgpEventParmTableRef, 
                  lgpEventParmTableRowRef 
                }
    STATUS      current
    DESCRIPTION
        "A hot-swappable module has been added to the object specified by the 
         lgpEventParmTableRef and lgpEventParmTableRowRef."
    ::= { lgpEventNotifications 19 }

lgpEventModuleRemoved NOTIFICATION-TYPE
    OBJECTS     { 
                  sysUpTime, 
                  lgpEventParmTableRef, 
                  lgpEventParmTableRowRef 
                }
    STATUS      current
    DESCRIPTION
        "A hot-swappable module has been removed from the object specified by 
         the lgpEventParmTableRef and lgpEventParmTableRowRef."
    ::= { lgpEventNotifications 20 }

lgpEventRcpPowerStateChangeOn NOTIFICATION-TYPE
    OBJECTS     { 
                  sysUpTime, 
                  lgpEventParmTableRef, 
                  lgpEventParmTableRowRef 
                }
    STATUS      current
    DESCRIPTION
        "Receptacle's power state has been changed from OFF to ON."
    ::= { lgpEventNotifications 21 }

lgpEventRcpPowerStateChangeOff NOTIFICATION-TYPE
    OBJECTS     { 
                  sysUpTime, 
                  lgpEventParmTableRef, 
                  lgpEventParmTableRowRef 
                }
    STATUS      current
    DESCRIPTION
        "Receptacle's power state has been changed from ON to OFF."
    ::= { lgpEventNotifications 22 }

lgpEventRcpLoadAdded NOTIFICATION-TYPE
    OBJECTS     { 
                  sysUpTime, 
                  lgpEventParmTableRef, 
                  lgpEventParmTableRowRef 
                }
    STATUS      current
    DESCRIPTION
        "The receptacle's load started drawing power. This notification 
        is asserted when the receptacle power is ON and the associated load 
        was previously not drawing power but is now drawing power. 
        This event is not asserted as a result of turning the 
        receptacle power ON."
    ::= { lgpEventNotifications 23 }

lgpEventRcpLoadRemoved NOTIFICATION-TYPE
    OBJECTS     { 
                  sysUpTime, 
                  lgpEventParmTableRef, 
                  lgpEventParmTableRowRef 
                }
    STATUS      current
    DESCRIPTION
        "The receptacle's load stopped drawing power. This notification 
        is asserted when the receptacle power is ON and the associated load 
        was previously drawing power but is now no longer drawing power. 
        This event is not asserted as a result of turning the 
        receptacle power OFF."
    ::= { lgpEventNotifications 24 }
END
