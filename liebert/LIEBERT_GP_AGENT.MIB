LIEBERT-GP-AGENT-MIB DEFINITIONS ::= BEGIN

IMPORTS
    sysUpTime
        FROM RFC1213-MIB
    OBJECT-TYPE, 
    MODULE-IDENTITY, 
    NOTIFICATION-TYPE, 
    OBJECT-IDENTITY, 
    Integer32,
    Unsigned32
        FROM SNMPv2-SMI
    lgpAgentIdent,
    lgpAgentDevice,
    lgpAgentControl,
    liebertAgentModuleReg, lgpAgentNotifications
        FROM LIEBERT-GP-REGISTRATION-MIB
    DisplayString
        FROM SNMPv2-TC
    lgpConditionsPresent, lgpConditionDescription, lgpNetworkName
        FROM LIEBERT-GP-CONDITIONS-MIB
    ;

-- =============================================================================
-- Module Identification and Registration
-- =============================================================================
--
liebertAgentModule MODULE-IDENTITY
  LAST-UPDATED "200811170000Z"
  ORGANIZATION "Liebert Corporation"
  CONTACT-INFO
      "Contact:   Technical Support

      Postal:
      Liebert Corporation
      1050 Dearborn Drive
      P.O. Box 29186
      Columbus OH, 43229
      US

      Tel: +1 (800) 222-5877

      E-mail: liebert.monitoring@vertivco.com
      Web:    www.vertivco.com

      Author:  Gregory M. Hoge"

   DESCRIPTION
      "The MIB module used to specify Liebert software or firmware
      agent SNMP OIDs.

      Copyright 2000-2008 Liebert Corporation. All rights reserved.
      Reproduction of this document is authorized on the condition
      that the forgoing copyright notice is included.

      This Specification is supplied 'AS IS' and Liebert Corporation
      makes no warranty, either express or implied, as to the use,
      operation, condition, or performance of the Specification."

   REVISION "200811170000Z"
   DESCRIPTION
    "Added support for NXL unit."

   REVISION "200807020000Z"
   DESCRIPTION
    "Updated INTEGER references to Integer32 (SMIv2).
     Added missing item to import (Unsigned32)"

   REVISION "200801100000Z"
   DESCRIPTION
    "Modified contact email address and added lgpAgentEventNotifications
    objects."

   REVISION "200705290000Z"
   DESCRIPTION
    "Added support for XDF Unit."

   REVISION "200602220000Z"
   DESCRIPTION
    "Added support for Liebert DS Unit."
   ::= { liebertAgentModuleReg 1 }

-- =============================================================================
--  lgpIdent - Liebert SNMP Agent Identification Group
--  This group contains data specific to the agent or agent hardware.
-- =============================================================================

lgpAgentIdentManufacturer OBJECT-TYPE
    SYNTAX      DisplayString (SIZE (255))
    MAX-ACCESS  read-only
    STATUS      current
    DESCRIPTION "The agent manufacturer."
    ::= { lgpAgentIdent 1 }

lgpAgentIdentModel OBJECT-TYPE
    SYNTAX      DisplayString (SIZE (255))
    MAX-ACCESS  read-only
    STATUS      current
    DESCRIPTION "The agent model designation.  This identifier is typically a
    model name or ID"
    ::= { lgpAgentIdent 2 }

lgpAgentIdentFirmwareVersion OBJECT-TYPE
    SYNTAX      DisplayString (SIZE (64))
    MAX-ACCESS  read-only
    STATUS      current
    DESCRIPTION "The firmware revision level of the agent."
    ::= { lgpAgentIdent 3 }

lgpAgentIdentSerialNumber OBJECT-TYPE
    SYNTAX      DisplayString (SIZE (64))
    MAX-ACCESS  read-only
    STATUS      current
    DESCRIPTION "The serial number of the agent.  This is a string of
    alphanumeric characters that uniquely identifies the agent hardware.  This
    number is assigned when the agent hardware is manufactured and does not
    change throughout its lifecycle."
    ::= { lgpAgentIdent 4 }

lgpAgentIdentPartNumber OBJECT-TYPE
    SYNTAX      DisplayString (SIZE (255))
    MAX-ACCESS  read-only
    STATUS      current
    DESCRIPTION "The agent model part number designation."
    ::= { lgpAgentIdent 5 }

lgpAgentConnectedDeviceCount OBJECT-TYPE
    SYNTAX      Unsigned32
    MAX-ACCESS  read-only
    STATUS      current
    DESCRIPTION "The number of devices currently connected and communicating
    successfully with the agent.  Devices for which communications are
    currently being attempted are not considered in this count."
    ::= { lgpAgentIdent 6 }

-- =============================================================================
-- lgpAgentNotifications - Liebert Agent Notifications Group
-- =============================================================================

lgpAgentEventNotifications OBJECT-IDENTITY
    STATUS current
    DESCRIPTION
        "Agent specific notifications."
    ::= { lgpAgentNotifications 0 }

lgpAgentDeviceCommunicationLost NOTIFICATION-TYPE
    OBJECTS     { sysUpTime }
    STATUS      current
    DESCRIPTION "The agent has lost communications with a managed device."
    ::= { lgpAgentEventNotifications 1 }

lgpAgentFirmwareUpdateSuccessful NOTIFICATION-TYPE
    OBJECTS     { sysUpTime }
    STATUS      current
    DESCRIPTION
        "The firmware update to the agent card has completed successfully."
    ::= { lgpAgentEventNotifications 5 }

lgpAgentFirmwareCorrupt NOTIFICATION-TYPE
    OBJECTS     { sysUpTime }
    STATUS      current
    DESCRIPTION
        "The firmware update to the agent card has failed and the firmware is
        now corrupt."
    ::= { lgpAgentEventNotifications 6 }

lgpAgentHeartbeat NOTIFICATION-TYPE
    OBJECTS     { sysUpTime, lgpConditionsPresent,
                lgpAgentConnectedDeviceCount }
    STATUS      current
    DESCRIPTION
        "The agent card is alive."
    ::= { lgpAgentEventNotifications 7 }

lgpAgentDnsLookupFailure NOTIFICATION-TYPE
    OBJECTS     { sysUpTime, lgpNetworkName }
    STATUS      current
    DESCRIPTION
        "A Domain Name System (DNS) lookup of a network name failed to
        resolve.  This may result in one or more of the following:
           1. failure to notify a target address of an important condition
           2. failure allow access for monitoring purposes
        This issue should be resolved as soon as possible with a
        network or system administrator."
    ::= { lgpAgentEventNotifications 8 }

-- =============================================================================
-- lgpAgentEventNotificationsLegacy - Liebert Legacy Agent Notifications Group
-- =============================================================================

lgpAgentEventNotificationsLegacy OBJECT-IDENTITY
    STATUS current
    DESCRIPTION
        "This branch contains copies of the notifications registered directly
         below lgpAgentEventNotifications. These are here to provide support 
         for some legacy devices which send out lgpAgentEventNotifications 
         as the SNMPv1 enterprise trap parameter instead of 
         lgpAgentNotifications, which causes problems with some SNMP clients 
         when converting from V1 to V2 notifications (RFC3584 Section 3)."
    ::= { lgpAgentEventNotifications 0 }

lgpAgentDeviceCommunicationLostLegacy NOTIFICATION-TYPE
    OBJECTS     { sysUpTime }
    STATUS      current
    DESCRIPTION "The agent has lost communications with a managed device."
    ::= { lgpAgentEventNotificationsLegacy 1 }

lgpAgentFirmwareUpdateSuccessfulLegacy NOTIFICATION-TYPE
    OBJECTS     { sysUpTime }
    STATUS      current
    DESCRIPTION
        "The firmware update to the agent card has completed successfully."
    ::= { lgpAgentEventNotificationsLegacy 5 }

lgpAgentFirmwareCorruptLegacy NOTIFICATION-TYPE
    OBJECTS     { sysUpTime }
    STATUS      current
    DESCRIPTION
        "The firmware update to the agent card has failed and the firmware is
        now corrupt."
    ::= { lgpAgentEventNotificationsLegacy 6 }

lgpAgentHeartbeatLegacy NOTIFICATION-TYPE
    OBJECTS     { sysUpTime, lgpConditionsPresent,
                lgpAgentConnectedDeviceCount }
    STATUS      current
    DESCRIPTION
        "The agent card is alive."
    ::= { lgpAgentEventNotificationsLegacy 7 }

lgpAgentDnsLookupFailureLegacy NOTIFICATION-TYPE
    OBJECTS     { sysUpTime, lgpNetworkName }
    STATUS      current
    DESCRIPTION
        "A Domain Name System (DNS) lookup of a network name failed to
        resolve.  This may result in one or more of the following:
           1. failure to notify a target address of an important condition
           2. failure allow access for monitoring purposes
        This issue should be resolved as soon as possible with a
        network or system administrator."
    ::= { lgpAgentEventNotificationsLegacy 8 }

-- =============================================================================
-- lgpAgentDevice - Liebert Agent Managed Device Group
-- =============================================================================

lgpAgentManagedDeviceTable OBJECT-TYPE
    SYNTAX      SEQUENCE OF LgpAgentManagedDeviceEntry
    MAX-ACCESS  not-accessible
    STATUS      current
    DESCRIPTION "This table contains one entry for each managed device."
    ::= { lgpAgentDevice 2 }

lgpAgentManagedDeviceEntry OBJECT-TYPE
    SYNTAX      LgpAgentManagedDeviceEntry
    MAX-ACCESS  not-accessible
    STATUS      current
    DESCRIPTION "This entry describes a row in the table
                'lgpAgentManagedDeviceTable'.  The rows in this table cannot
                be created by the NMS. The rows are automatically created by
                the agent based upon the hardware configuration of the
                Liebert managed device(s) being monitored with this agent."
    INDEX       { lgpAgentDeviceIndex }
    ::= { lgpAgentManagedDeviceTable 1 }

LgpAgentManagedDeviceEntry ::= SEQUENCE {
        lgpAgentDeviceIndex                 INTEGER,
        lgpAgentDeviceId                    OBJECT IDENTIFIER,
        lgpAgentDeviceManufacturer          DisplayString,
        lgpAgentDeviceModel                 DisplayString,
        lgpAgentDeviceFirmwareVersion       DisplayString,
        lgpAgentDeviceUnitNumber            Integer32,
        lgpAgentDeviceSerialNumber          DisplayString,
        lgpAgentDeviceManufactureDate       DisplayString,
        lgpAgentDeviceServiceContact        DisplayString,
        lgpAgentDeviceServicePhoneNumber    DisplayString,
        lgpAgentDeviceServiceAddrLine1      DisplayString,
        lgpAgentDeviceServiceAddrLine2      DisplayString,
        lgpAgentDeviceServiceAddrLine3      DisplayString,
        lgpAgentDeviceServiceAddrLine4      DisplayString,
        lgpAgentDeviceUnitName              DisplayString,
        lgpAgentDeviceSiteIdentifier        DisplayString,
        lgpAgentDeviceTagNumber             DisplayString,
        lgpAgentDeviceOrderLine1            DisplayString,
        lgpAgentDeviceOrderLine2            DisplayString

    }

lgpAgentDeviceIndex OBJECT-TYPE
    SYNTAX      Integer32 (0..65536)
    MAX-ACCESS  read-only
    STATUS      current
    DESCRIPTION "The device identifier. This is used as an index to address
                a particular row in the table 'lgpAgentManagedDeviceTable'."
    ::= { lgpAgentManagedDeviceEntry 1 }

lgpAgentDeviceId OBJECT-TYPE
    SYNTAX      OBJECT IDENTIFIER
    MAX-ACCESS  read-only
    STATUS      current
    DESCRIPTION "The managed device specific identifier defined by the
                product registration."
    ::= { lgpAgentManagedDeviceEntry 2 }

lgpAgentDeviceManufacturer OBJECT-TYPE
    SYNTAX      DisplayString (SIZE (255))
    MAX-ACCESS  read-only
    STATUS      current
    DESCRIPTION "The managed device manufacturer."
    ::= { lgpAgentManagedDeviceEntry 3 }

lgpAgentDeviceModel OBJECT-TYPE
    SYNTAX      DisplayString (SIZE (255))
    MAX-ACCESS  read-only
    STATUS      current
    DESCRIPTION "The managed device model designation."
    ::= { lgpAgentManagedDeviceEntry 4 }

lgpAgentDeviceFirmwareVersion OBJECT-TYPE
    SYNTAX      DisplayString (SIZE (64))
    MAX-ACCESS  read-only
    STATUS      current
    DESCRIPTION "The firmware revision level of the managed device."
    ::= { lgpAgentManagedDeviceEntry 5 }

lgpAgentDeviceUnitNumber OBJECT-TYPE
    SYNTAX      Integer32
    MAX-ACCESS  read-write
    STATUS      current
    DESCRIPTION "The managed device unit number.  Typically this is a
    number assigned to a managed device that uniquely identifies it from
    other similar devices within a 'system'."
    ::= { lgpAgentManagedDeviceEntry 6 }

lgpAgentDeviceSerialNumber OBJECT-TYPE
    SYNTAX      DisplayString (SIZE (64))
    MAX-ACCESS  read-only
    STATUS      current
    DESCRIPTION "The serial number of the managed device."
    ::= { lgpAgentManagedDeviceEntry 7 }

lgpAgentDeviceManufactureDate OBJECT-TYPE
    SYNTAX      DisplayString (SIZE (64))
    MAX-ACCESS  read-only
    STATUS      current
    DESCRIPTION "The manufacture date of the managed device."
    ::= { lgpAgentManagedDeviceEntry 8 }

lgpAgentDeviceServiceContact OBJECT-TYPE
    SYNTAX      DisplayString (SIZE (0..64))
    MAX-ACCESS  read-write
    STATUS      current
    DESCRIPTION "The service contact of the managed device."
    ::= { lgpAgentManagedDeviceEntry 9 }

lgpAgentDeviceServicePhoneNumber OBJECT-TYPE
    SYNTAX      DisplayString (SIZE (0..64))
    MAX-ACCESS  read-write
    STATUS      current
    DESCRIPTION "The phone number of the service contact of the managed device."
    ::= { lgpAgentManagedDeviceEntry 10 }

lgpAgentDeviceServiceAddrLine1 OBJECT-TYPE
    SYNTAX      DisplayString (SIZE (0..64))
    MAX-ACCESS  read-write
    STATUS      current
    DESCRIPTION
            "Line 1 of the service address of the managed device."
    ::= { lgpAgentManagedDeviceEntry 11 }

lgpAgentDeviceServiceAddrLine2 OBJECT-TYPE
    SYNTAX      DisplayString (SIZE (0..64))
    MAX-ACCESS  read-write
    STATUS      current
    DESCRIPTION
            "Line 2 of the service address of the managed device."
    ::= { lgpAgentManagedDeviceEntry 12 }

lgpAgentDeviceServiceAddrLine3 OBJECT-TYPE
    SYNTAX      DisplayString (SIZE (0..64))
    MAX-ACCESS  read-write
    STATUS      current
    DESCRIPTION
            "Line 3 of the service address of the managed device."
    ::= { lgpAgentManagedDeviceEntry 13 }

lgpAgentDeviceServiceAddrLine4 OBJECT-TYPE
    SYNTAX      DisplayString (SIZE (0..64))
    MAX-ACCESS  read-write
    STATUS      current
    DESCRIPTION
            "Line 4 of the service address of the managed device."
    ::= { lgpAgentManagedDeviceEntry 14 }

lgpAgentDeviceUnitName OBJECT-TYPE
    SYNTAX      DisplayString (SIZE (0..64))
    MAX-ACCESS  read-write
    STATUS      current
    DESCRIPTION 
        "Unit name for the managed device assigned by the customer."
    ::= { lgpAgentManagedDeviceEntry 15 }

lgpAgentDeviceSiteIdentifier OBJECT-TYPE
    SYNTAX      DisplayString (SIZE (0..255))
    MAX-ACCESS  read-write
    STATUS      current
    DESCRIPTION 
        "Identifier that uniquely identifies the site where this device is
        located."
    ::= { lgpAgentManagedDeviceEntry 16 }

lgpAgentDeviceTagNumber OBJECT-TYPE
    SYNTAX      DisplayString (SIZE (0..255))
    MAX-ACCESS  read-write
    STATUS      current
    DESCRIPTION 
        "Identifier that uniquely identifies this device within a particular
        site (see lgpAgentDeviceSiteIdentifier)."
    ::= { lgpAgentManagedDeviceEntry 17 }

lgpAgentDeviceOrderLine1 OBJECT-TYPE
    SYNTAX      DisplayString (SIZE (0..255))
    MAX-ACCESS  read-write
    STATUS      current
    DESCRIPTION 
        "Customer Sales Order information line 1."
    ::= { lgpAgentManagedDeviceEntry 18 }

lgpAgentDeviceOrderLine2 OBJECT-TYPE
    SYNTAX      DisplayString (SIZE (0..255))
    MAX-ACCESS  read-write
    STATUS      current
    DESCRIPTION 
        "Customer Sales Order information line 2."
    ::= { lgpAgentManagedDeviceEntry 19 }

-- =============================================================================
-- lgpAgentControl - Liebert Agent Control Group
-- =============================================================================

lgpAgentReboot OBJECT-TYPE
    SYNTAX      Integer32
    MAX-ACCESS  read-write
    STATUS      current
    DESCRIPTION
        "Perform an immediate 'reboot' of the agent process.  When possible
         the reboot will approximate a power on reset of the agent
         communications hardware.  This type of reboot will be performed if
         a hardware reset is supported by the hardware/software on the
         communications card.  Otherwise a 'software' reboot will be executed.
         In both cases a temporary loss of communications and other agent
         functionality will result.

         Any valid INTEGER value may be written to this object to initiate
         the reboot operation.

         If read the value '0' will always be returned."
    ::= { lgpAgentControl 1 }

lgpAgentTelnetEnabled OBJECT-TYPE
    SYNTAX      INTEGER
    {
        yes(1),
        no(2)
    }
    MAX-ACCESS  read-write
    STATUS      current
    DESCRIPTION
        "This object represents the settings of Telnet.
         yes
             Telnet services are enabled.
         no
             Telnet services are disabled.
         The system must be rebooted before changes can take effect."
    ::= { lgpAgentControl 2 }

lgpAgentVelocityServerEnabled OBJECT-TYPE
    SYNTAX      INTEGER
    {
        yes(1),
        no(2)
    }
    MAX-ACCESS  read-write
    STATUS      current
    DESCRIPTION
        "This object configures the Velocity Server to grant external clients access to agent data via the Liebert Velocity protocol.
         yes
             Agent data is available to external clients via the Liebert Velocity protocol.
         no
             Agent data is not available to external clients via the Liebert Velocity protocol.
         The system must be rebooted before changes can take effect."
    ::= { lgpAgentControl 3 }

lgpAgentWebServerMode OBJECT-TYPE
    SYNTAX      INTEGER
    {
        disabled(0),
        http(1),
        https(2)
    }
    MAX-ACCESS  read-write
    STATUS      current
    DESCRIPTION
        "This object represents the settings of Web services.
         disabled
             Web services are disabled.
         http
             Web server mode is HTTP (not secure).
         https
             Web server mode is secure HTTP.
         The system must be rebooted before changes can take effect."
    ::= { lgpAgentControl 4 }
END
