CYCLADES-ACS5K-ADM-MIB DEFINITIONS ::= BEGIN

-- Avocent Vendor MIB OID Tree
-- Release 3.3.0-9 05/24/2011
-- The cyACS5KAdmin has the ACS 5000' administration MIB) :

IMPORTS
	cyACS5KMgmt
		FROM CYCLADES-ACS5K-MIB
	OBJECT-TYPE, MODULE-IDENTITY
		FROM SNMPv2-SMI;

cyACS5KAdm	MODULE-IDENTITY
	LAST-UPDATED	"201007260000Z"
	ORGANIZATION	"Avocent Corporation"
	CONTACT-INFO	"postal : Avocent Corporation
				47281 Bayside Parkway
				Fremont, CA 94538, USA
				e-mail : Technical Support
					  techsupport@avocent.com"
	DESCRIPTION	"This module defines objects of the ACS/TS/ACS5000 administration"
	REVISION	"201007260000Z"
	DESCRIPTION	"First Draft"
::= { cyACS5KMgmt 4 }

cyACS5KSave	OBJECT-TYPE
	SYNTAX		INTEGER {
				nosave(0),
				save(1)
			}
	MAX-ACCESS	read-write
	STATUS		current
	DESCRIPTION	"Exec saveconf command"
::= { cyACS5KAdm 1 }
                               
cyACS5KSerialHUP	OBJECT-TYPE
	SYNTAX		INTEGER {
				norestartportslave(0),
				restartportslave(1)
			}
	MAX-ACCESS    read-write
	STATUS          current
	DESCRIPTION     "Exec signal_ras hup command"
::= { cyACS5KAdm 2 }

END
