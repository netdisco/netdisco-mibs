CYCLADES-ACS5K-MIB DEFINITIONS ::= BEGIN

-- Avocent Vendor MIB OID Tree
-- Release 3.3.0-9 05/24/2011
-- ACS 5000 Enterprise MIB

IMPORTS
	cyclades
		FROM CYCLADES-MIB
	MODULE-IDENTITY
		FROM SNMPv2-SMI;

cyACS5KMgmt	MODULE-IDENTITY
	LAST-UPDATED	"201007260000Z"
	ORGANIZATION	"Avocent Corporation"
	CONTACT-INFO	"postal : Avocent Corporation
				  47281 Bayside Parkway
				  Fremont, CA 94538, USA
			 e-mail : Technical Support
				  techsupport@avocent.com"
	DESCRIPTION	"This module defines the ACS5000 Enterprise MIB"
	REVISION	"201007260000Z"
	DESCRIPTION	"First Draft"
::= { cyclades 8 }

-- Current Cyclades ACS 5000 core mib table entries :
--	cyACS5KSys	OBJECT-IDENTITY  ::= { cyACS5KMgmt 1 }
--	cyACS5KConf	OBJECT-IDENTITY  ::= { cyACS5KMgmt 2 }
--	cyACS5KInfo	OBJECT-IDENTITY  ::= { cyACS5KMgmt 3 }
--	cyACS5KAdm	OBJECT-IDENTITY  ::= { cyACS5KMgmt 4 }
--	cyACS5KPM	OBJECT-IDENTITY  ::= { cyACS5KMgmt 5 }

END
