-- *******************************************************************
-- CISCO-LWAPP-DOT11-CLIENT-CALIB-MIB.my: Dot11 Wireless Clients
--                                        Calibration MIB
-- December 2005, Devesh Pujari, Prasanna Viswakumar
--
-- Copyright (c) 2005-2006 by Cisco Systems, Inc.
-- All rights reserved.
-- *******************************************************************
--
CISCO-LWAPP-DOT11-CLIENT-CALIB-MIB DEFINITIONS ::= BEGIN

IMPORTS 
        MODULE-IDENTITY, 
        OBJECT-TYPE,
        Unsigned32,
        Integer32
                FROM SNMPv2-SMI
        MODULE-COMPLIANCE, 
        OBJECT-GROUP
                FROM SNMPv2-CONF
        TimeStamp,
        MacAddress,
        TimeInterval,
        TruthValue,
        RowStatus 
                FROM SNMPv2-TC 
        cLApSysMacAddress,
        cLApDot11IfSlotId
                FROM CISCO-LWAPP-AP-MIB
        ciscoMgmt
                FROM CISCO-SMI;

--********************************************************************
--*  MODULE IDENTITY
--********************************************************************

ciscoLwappDot11ClientCalibMIB MODULE-IDENTITY
        LAST-UPDATED    "200702120000Z"
        ORGANIZATION    "Cisco Systems Inc."
        CONTACT-INFO  
               "        Cisco Systems,
                        Customer Service
                Postal: 170 West Tasman Drive
                        San Jose, CA  95134
                        USA
                   Tel: +1 800 553-NETS

                 Email: cs-wnbu-snmp@cisco.com"

        DESCRIPTION             
                "This MIB is intended to be implemented on all those
                devices operating as Central controllers, that
                terminate the Light Weight Access Point Protocol
                tunnel from Cisco Light-weight LWAPP Access Points.

                Information provided by this MIB is about the
                configuration and monitoring of 802.11 wireless
                clients in the network.

                The relationship between CC and the LWAPP APs
                can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+

                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends them to the controller to which
                it is logically connected.

                Light Weight Access Point Protocol ( LWAPP ) 

                This is a generic protocol that defines the 
                communication between the Access Points and the
                Central Controller.

                Mobile Node ( MN )

                A roaming 802.11 wireless device in a wireless
                network associated with an access point. Mobile Node,
                Mobile Station(Ms) and client are used 
                interchangeably. 
 
                REFERENCE
 
                [1] Wireless LAN Medium Access Control ( MAC ) and
                Physical Layer ( PHY ) Specifications 
  
                [2] Draft-obara-capwap-lwapp-00.txt, IETF Light 
                Weight Access Point Protocol "

        REVISION      "200702120000Z"
        DESCRIPTION
                "Added ciscoLwappDot11ClientCalibMIBConfigGroupSup1 
                 OBJECT-GROUP. "
           
        REVISION      "200604110000Z"
        DESCRIPTION
                "Initial version of this MIB module. "
        ::= { ciscoMgmt 522 }
        
ciscoLwappDot11ClientCalibMIBNotifs  OBJECT IDENTIFIER
        ::= { ciscoLwappDot11ClientCalibMIB 0 }

ciscoLwappDot11ClientCalibMIBObjects OBJECT IDENTIFIER 
        ::= { ciscoLwappDot11ClientCalibMIB 1 }

ciscoLwappDot11ClientCalibMIBConform OBJECT IDENTIFIER
        ::= { ciscoLwappDot11ClientCalibMIB 2 }

cldccConfig OBJECT IDENTIFIER
    ::= { ciscoLwappDot11ClientCalibMIBObjects 1 }

cldccStatus OBJECT IDENTIFIER
    ::= { ciscoLwappDot11ClientCalibMIBObjects 2 }

cldccRssiSamples OBJECT IDENTIFIER
    ::= { cldccStatus 1 }

    
--********************************************************************
-- Wireless Client Calibration 
--********************************************************************

cLD11ClientCalibTable OBJECT-TYPE
        SYNTAX     SEQUENCE OF CLD11ClientCalibEntry
        MAX-ACCESS not-accessible
        STATUS     current
        DESCRIPTION
                "This table represents the calibration for the
                802.11 wireless clients that would associate
                to the APs that have joined this controller.

                An entry is created through an explicit management
                action initiated by the administrator through a
                network management station by specifying the
                calibration parameters for a particular client
                identified by cLD11ClientCalibMacAddress and setting
                the RowStatus object to 'createAndGo'.  An existing
                entry is deleted by setting the RowStatus object to 
                'destroy'.  The object cLD11ClientCalibTableMaxEntries
                represents the maximum number of entries in this
                table. " 
    ::= { cldccConfig 1 }
    
cLD11ClientCalibEntry OBJECT-TYPE
        SYNTAX     CLD11ClientCalibEntry
        MAX-ACCESS not-accessible
        STATUS     current
        DESCRIPTION
                "Each entry represents a conceptual row in this
                table and provides the information about the
                calibration parameters for wireless clients. "
        INDEX { cLD11ClientCalibMacAddress }
        ::= { cLD11ClientCalibTable 1 }
     
CLD11ClientCalibEntry ::= 
        SEQUENCE {
             cLD11ClientCalibMacAddress          MacAddress,
             cLD11ClientCalibBeaconInterval      TimeInterval,
             cLD11ClientCalibRowStatus           RowStatus,
             cLD11ClientCalibNumberOfRadios      Unsigned32,
             cLD11ClientCalibNumberOfSamples     Unsigned32,
             cLD11ClientCalibSamplesCollected    Unsigned32
        }
   
cLD11ClientCalibMacAddress OBJECT-TYPE
        SYNTAX     MacAddress
        MAX-ACCESS not-accessible
        STATUS     current
        DESCRIPTION
                "This object specifies the MAC address of the
                802.11 wireless client for which the 
                calibration parameters in this entry are 
                applicable and uniquely identifies this entry. "
        ::= { cLD11ClientCalibEntry 1 }

cLD11ClientCalibBeaconInterval OBJECT-TYPE
        SYNTAX     TimeInterval (100..3240000)
        UNITS      "hundredths-seconds"
        MAX-ACCESS read-create
        STATUS     current 
        DESCRIPTION
                "This object specifies the time interval, expressed
                here in hundredths of a second at which an AP
                issues radio measurement request messages to a
                client for every SSID.  It is not recommended to
                configure values less than 10 seconds (1000).
                The value configured through this object is
                reflected in the operation of the LWAPP APs only if
                cLD11ClientCalibBeaconEnabled is set to 'true'. "
        DEFVAL { 60000 }
        ::= { cLD11ClientCalibEntry 2 }
           
cLD11ClientCalibRowStatus OBJECT-TYPE
        SYNTAX     RowStatus
        MAX-ACCESS read-create
        STATUS     current
        DESCRIPTION
                "The object that represents the status of a
                specific instance of a row in this table.
                Initially set to a value of 'createAndGo' by
                the User when a row is created, the status
                as represented by this object is automatically
                set to 'active' if and when the row creation
                is successful.  To delete the specific instance
                of a row, User should set this object to
                'destroy'. "
        ::= { cLD11ClientCalibEntry 3 }

cLD11ClientCalibNumberOfRadios OBJECT-TYPE
        SYNTAX     Unsigned32 (1..100)
        MAX-ACCESS read-create
        STATUS     current
        DESCRIPTION
                "The object represents the number of radios
                 used in this calibration."
        ::= { cLD11ClientCalibEntry 4 }

cLD11ClientCalibNumberOfSamples OBJECT-TYPE
        SYNTAX     Unsigned32 (1..200)
        MAX-ACCESS read-create
        STATUS     current
        DESCRIPTION
                "The object represents the number of RSSI samples for
                 a given radio, used in  this calibration."
        ::= { cLD11ClientCalibEntry 5 }

cLD11ClientCalibSamplesCollected OBJECT-TYPE
        SYNTAX     Unsigned32 (0..200)
        MAX-ACCESS read-only
        STATUS     current
        DESCRIPTION
                "This object represents the number of 
                 samples available for this client. "
        ::= { cLD11ClientCalibEntry 6 }


cLD11ClientCalibTableMaxEntries OBJECT-TYPE
        SYNTAX     Unsigned32 (1..25)
        MAX-ACCESS read-write
        STATUS     current
        DESCRIPTION
                "This object represents the upper limit on the
                number of entries in cLD11ClientCalibTable. "
        DEFVAL  { 5 }
    ::= { cldccConfig 2 }     

--********************************************************************
-- *  Client Calibration RSSI Data table
--********************************************************************
cLD11ClientCalibDataTable OBJECT-TYPE
        SYNTAX SEQUENCE OF CLD11ClientCalibDataEntry
        MAX-ACCESS not-accessible
        STATUS     current
        DESCRIPTION
                "This table represents the RSSI data samples 
                 collected for 802.11 client based on the 
                 information provided in the cLD11ClientCalibTable.
                 Entries are automatically added by the controller
                 as and when samples are available.
                 This data is used by the NMS for location
                 calibration of the 8022.11 clients." 
        ::= { cldccRssiSamples 1 }     

cLD11ClientCalibDataEntry OBJECT-TYPE
        SYNTAX     CLD11ClientCalibDataEntry 
        MAX-ACCESS not-accessible
        STATUS     current
        DESCRIPTION
                "Each entry represents a conceptual row in this
                table and provides the information about the
                samples for  location calibration of a  802.11 
                client. "
        INDEX { cLD11ClientCalibMacAddress, cLApSysMacAddress, 
                cLApDot11IfSlotId, clD11ClientCalibDataTimeStamp,
                clD11ClientCalibDataAntennaIndex }
        ::= { cLD11ClientCalibDataTable 1 }

CLD11ClientCalibDataEntry ::=
        SEQUENCE {
                clD11ClientCalibDataTimeStamp       TimeStamp,
                clD11ClientCalibDataAntennaIndex    INTEGER,
                clD11ClientCalibDataRssiValue       Integer32
        }

clD11ClientCalibDataTimeStamp OBJECT-TYPE
        SYNTAX     TimeStamp 
        UNITS      "milliseconds"
        MAX-ACCESS not-accessible
        STATUS     current
        DESCRIPTION
                "This object represents the time this sample was 
                 collected. This is the absolute time that this 
                 sample was collected."
        ::= { cLD11ClientCalibDataEntry 1 }

clD11ClientCalibDataAntennaIndex OBJECT-TYPE
        SYNTAX     INTEGER  {
                       antenna1(1),
                       antenna2(2)
                   }
        MAX-ACCESS not-accessible
        STATUS     current
        DESCRIPTION
                "This object represents the antenna which  
                 received the probe request from client."
        ::= { cLD11ClientCalibDataEntry 2 }

clD11ClientCalibDataRssiValue OBJECT-TYPE
        SYNTAX     Integer32 (-128..0)
        MAX-ACCESS read-only
        STATUS     current
        DESCRIPTION
                "This object represents the RSSI value for this 
                 sample."
        ::= { cLD11ClientCalibDataEntry 3 }



--********************************************************************
-- *  Location scalars 
--********************************************************************
cLD11ClientCalibRssiAlgorithm OBJECT-TYPE
        SYNTAX     INTEGER  {
                       unknown(1),
                       simple(2),
                       average(3)
                   }
        MAX-ACCESS read-write
        STATUS     current
        DESCRIPTION
                "This object represents the algorithm used 
                to average RSSI and SNR values. 
                  unknown(1)  - the algorithm used is unknown
                  simple(2)  - simple is used for the calculation
                  average(3) - average RSSI (received signal strength 
                               indicator) is used as algorithm
                "
        DEFVAL  { 3 }
    ::= { cldccConfig 3 }     


cLD11ClientCalibRssiClientExpiryTimeout OBJECT-TYPE
        SYNTAX     Unsigned32 
        UNITS      "seconds" 
        MAX-ACCESS read-write
        STATUS     current
        DESCRIPTION
                "This object represents the expiry timeout 
                for the client. "
        DEFVAL  { 10 }
    ::= { cldccConfig 4 }     

cLD11ClientCalibRssiCalibClientExpiryTimeout OBJECT-TYPE
        SYNTAX     Unsigned32 
        UNITS      "seconds" 
        MAX-ACCESS read-write
        STATUS     current
        DESCRIPTION
                "This object represents the expiry timeout 
                for the calibirating client. "
        DEFVAL  { 10 }
    ::= { cldccConfig 5 }     

cLD11ClientCalibRssiRfidTagExpiryTimeout OBJECT-TYPE
        SYNTAX     Unsigned32 
        UNITS      "seconds" 
        MAX-ACCESS read-write
        STATUS     current
        DESCRIPTION
                "This object represents the expiry timeout 
                for the RFID tags. "
        DEFVAL  { 600 }
    ::= { cldccConfig 6 }     

cLD11ClientCalibRssiRogueApExpiryTimeout OBJECT-TYPE
        SYNTAX     Unsigned32 
        UNITS      "seconds" 
        MAX-ACCESS read-write
        STATUS     current
        DESCRIPTION
                "This object represents the expiry timeout 
                for the Rogue APs. "
        DEFVAL  { 60 }
    ::= { cldccConfig 7 }     

cLD11ClientCalibRssiClientHalflifeTimeout OBJECT-TYPE
        SYNTAX     Unsigned32 (0..2 | 5 | 10 | 20 | 
                       30 | 60 | 90 | 120 | 180 | 300 )
        UNITS      "seconds" 
        MAX-ACCESS read-write
        STATUS     current
        DESCRIPTION
                "This object represents the half-life timeout 
                for the client. "
        DEFVAL  { 60 }
    ::= { cldccConfig 8 }     

cLD11ClientCalibRssiCalibClientHalflifeTimeout OBJECT-TYPE
        SYNTAX     Unsigned32 (0..2 | 5 | 10 | 20 | 
                       30 | 60 | 90 | 120 | 180 | 300 )
        UNITS      "seconds" 
        MAX-ACCESS read-write
        STATUS     current
        DESCRIPTION
                "This object represents the half-life timeout 
                for the calibirating client. "
        DEFVAL  { 0 }
    ::= { cldccConfig 9 }     

cLD11ClientCalibRssiRfidTagHalflifeTimeout OBJECT-TYPE
        SYNTAX     Unsigned32 (0..2 | 5 | 10 | 20 | 
                       30 | 60 | 90 | 120 | 180 | 300 )
        UNITS      "seconds" 
        MAX-ACCESS read-write
        STATUS     current
        DESCRIPTION
                "This object represents the half-life timeout 
                for the RFID tags. "
        DEFVAL  { 120 }
    ::= { cldccConfig 10 }     

cLD11ClientCalibRssiRogueApHalflifeTimeout OBJECT-TYPE
        SYNTAX     Unsigned32 (0..2 | 5 | 10 | 20 | 
                       30 | 60 | 90 | 120 | 180 | 300 )
        UNITS      "seconds" 
        MAX-ACCESS read-write
        STATUS     current
        DESCRIPTION
                "This object represents the half-life timeout 
                for the Rogue APs. "
        DEFVAL  { 120 }
    ::= { cldccConfig 11 }     

cLD11ClientCalibRfidDataEnable OBJECT-TYPE
        SYNTAX     TruthValue  
        MAX-ACCESS read-write
        STATUS     current
        DESCRIPTION
                 "When set to true the RFID tag data collection is 
                 enabled, otherwise it is disabled."
        DEFVAL  { true }
    ::= { cldccConfig 12 }

cLD11ClientCalibRfidTimeout OBJECT-TYPE
        SYNTAX     Unsigned32 (60..7200)  
        UNITS      "seconds" 
        MAX-ACCESS read-write
        STATUS     current
        DESCRIPTION
                 "This objects represents the RFID tag data timeout."
        DEFVAL  { 1200 }
    ::= { cldccConfig 13 }

cLD11ClientCalibClientMultiBandEnable OBJECT-TYPE
        SYNTAX     TruthValue  
        MAX-ACCESS read-write
        STATUS     current
        DESCRIPTION
                 "When set to true the calibrating client
                 uses both the bands to transmit the requests.
                 When set to false it uses a single band."
        DEFVAL  { true }
    ::= { cldccConfig 14 }

cLD11ClientCalibClientRequestEnable OBJECT-TYPE
        SYNTAX     TruthValue  
        MAX-ACCESS read-write
        STATUS     current
        DESCRIPTION
                 "When set to true the calibrating client
                 uses uni or multi band to transmit the 
                 requests. When set to false it does not use
                 any band for transmitting requests."
        DEFVAL  { true }
    ::= { cldccConfig 15 }

cLD11ClientCalibClientBurstIntervalEnable OBJECT-TYPE
        SYNTAX     TruthValue  
        MAX-ACCESS read-write
        STATUS     current
        DESCRIPTION
                 "When set to true the calibrating client
                 burst interval is enabled."
        DEFVAL  { false }
    ::= { cldccConfig 16 }

cLD11ClientCalibClientBurstInterval OBJECT-TYPE
        SYNTAX     Unsigned32 
        UNITS      "seconds" 
        MAX-ACCESS read-write
        STATUS     current
        DESCRIPTION
                 "This object represents the burst interval of 
                 the calibrating client."
        DEFVAL  { 60 }
    ::= { cldccConfig 17 }

cLD11ClientCalibClientInterval OBJECT-TYPE
        SYNTAX     Unsigned32 
        UNITS      "seconds" 
        MAX-ACCESS read-write
        STATUS     current
        DESCRIPTION
                 "This object represents the notification interval 
                 for calibrating clients."
        DEFVAL  { 2 }
    ::= { cldccConfig 18 }

cLD11ClientCalibRfidInterval OBJECT-TYPE
        SYNTAX     Unsigned32 
        UNITS      "seconds" 
        MAX-ACCESS read-write
        STATUS     current
        DESCRIPTION
                 "This object represents the notification interval 
                 for RFID tags."
        DEFVAL  { 2 }
    ::= { cldccConfig 19 }

cLD11ClientCalibRogueInterval OBJECT-TYPE
        SYNTAX     Unsigned32 
        UNITS      "seconds" 
        MAX-ACCESS read-write
        STATUS     current
        DESCRIPTION
                 "This object represents the notification interval 
                 for Rogue APs and Rogue clients."
        DEFVAL  { 2 }
    ::= { cldccConfig 20 }



--******************************************************************* 
--*    Compliance statements  
--********************************************************************

ciscoLwappDot11ClientCalibMIBCompliances OBJECT IDENTIFIER
        ::= { ciscoLwappDot11ClientCalibMIBConform 1 }

ciscoLwappDot11ClientCalibMIBGroups OBJECT IDENTIFIER
        ::= { ciscoLwappDot11ClientCalibMIBConform 2 }

-- STATUS deprecated by ciscoLwappDot11ClientCalibMIBComplianceRev1
ciscoLwappDot11ClientCalibMIBCompliance MODULE-COMPLIANCE
        STATUS     current 
        DESCRIPTION
                "The compliance statement for the SNMP entities that
                implement this MIB. " 
        MODULE MANDATORY-GROUPS {                
                ciscoLwappDot11ClientCalibMIBConfigGroup
        }
        ::= { ciscoLwappDot11ClientCalibMIBCompliances 1 }

ciscoLwappDot11ClientCalibMIBComplianceRev1 MODULE-COMPLIANCE
        STATUS     current 
        DESCRIPTION
                "The compliance statement for the SNMP entities that
                implement this MIB. " 
        MODULE MANDATORY-GROUPS {                
                ciscoLwappDot11ClientCalibMIBConfigGroup,
                ciscoLwappDot11ClientCalibMIBConfigGroupSup1
        }
        ::= { ciscoLwappDot11ClientCalibMIBCompliances 2 }


--********************************************************************
--*    Units of conformance  
--********************************************************************

ciscoLwappDot11ClientCalibMIBConfigGroup OBJECT-GROUP
        OBJECTS {
                cLD11ClientCalibBeaconInterval,
                cLD11ClientCalibRowStatus,
                cLD11ClientCalibTableMaxEntries,
                cLD11ClientCalibRssiAlgorithm,
                cLD11ClientCalibRssiClientExpiryTimeout,
                cLD11ClientCalibRssiCalibClientExpiryTimeout,
                cLD11ClientCalibRssiRfidTagExpiryTimeout,
                cLD11ClientCalibRssiRogueApExpiryTimeout,
                cLD11ClientCalibRssiClientHalflifeTimeout,
                cLD11ClientCalibRssiCalibClientHalflifeTimeout,
                cLD11ClientCalibRssiRfidTagHalflifeTimeout,
                cLD11ClientCalibRssiRogueApHalflifeTimeout
        }                
        STATUS     current
        DESCRIPTION
                "This collection of objects specifies the required
                calibration parameters for the 802.11 wireless 
                clients. "
        ::= { ciscoLwappDot11ClientCalibMIBGroups 1 }

ciscoLwappDot11ClientCalibMIBConfigGroupSup1 OBJECT-GROUP
        OBJECTS {
                cLD11ClientCalibRssiClientExpiryTimeout,
                cLD11ClientCalibRssiCalibClientExpiryTimeout,
                cLD11ClientCalibRssiRfidTagExpiryTimeout,
                cLD11ClientCalibRssiRogueApExpiryTimeout,
                cLD11ClientCalibRssiClientHalflifeTimeout,
                cLD11ClientCalibRssiCalibClientHalflifeTimeout,
                cLD11ClientCalibRssiRfidTagHalflifeTimeout,
                cLD11ClientCalibRssiRogueApHalflifeTimeout,
                cLD11ClientCalibNumberOfRadios, 
                cLD11ClientCalibNumberOfSamples,
                clD11ClientCalibDataAntennaIndex,   
                clD11ClientCalibDataRssiValue,     
                clD11ClientCalibDataTimeStamp          
        }                
        STATUS     current
        DESCRIPTION
                "This collection of objects specifies the required
                RSSI calibration parameters for the 802.11 wireless 
                clients. "
        ::= { ciscoLwappDot11ClientCalibMIBGroups 2 }

END
