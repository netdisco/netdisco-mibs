-- ****************************************************************
-- ciscoVismDsx1MIB
--   The MIB for DS1/E1 interface configuration and
--   Alarm Configuration for VISM(Voice Interworking Service Module)
--   in MGX products.
--
-- February 2004, George Ogagan
-- March 2004, Rashmi Purandare
--
-- Copyright (c) 2003, 2004 by Cisco Systems, Inc.
-- All rights reserved.
-- ****************************************************************

CISCO-VISM-DSX1-MIB DEFINITIONS ::= BEGIN
IMPORTS
    MODULE-IDENTITY,
    OBJECT-TYPE,
    Integer32,
    Counter32
                               FROM SNMPv2-SMI
    DisplayString,
    TruthValue                 FROM SNMPv2-TC
    MODULE-COMPLIANCE,
    OBJECT-GROUP               FROM SNMPv2-CONF
    dsx1                       FROM BASIS-MIB
    dsx1AlmGrp                 FROM CISCO-MGX82XX-DSX1-MIB
    ciscoWan                   FROM CISCOWAN-SMI;

ciscoVismDsx1MIB MODULE-IDENTITY
    LAST-UPDATED    "200403090000Z"
    ORGANIZATION    "Cisco Systems, Inc."
    CONTACT-INFO
       "Cisco Systems
        Customer Service

        Postal: 170 W Tasman Drive
                San Jose, CA  95134
                USA

        Tel: +1 800 553-NETS

        E-mail: cs-wanatm@cisco.com"
    DESCRIPTION
        "The MIB module to configure DS1/E1 interface 
         objects in a Voice Interworking Service Module
         (VISM) module. This MIB is an extension
         to CISCO-MGX82XX-DSX1-MIB for DS1/E1 configuration
         in VISM.

         Terms used:
         CID:  Channel Identifier
         CAS:  Channel Associated Signaling
         CCS:  Common Channel Signaling
         DTMF: Dual Tone Multi Frequency
         NSE:  Name Signal Event
         NTE:  Name Telephony Event
         PVC:  Permanent Virtual Circuit
        "

    REVISION    "200403090000Z"
    DESCRIPTION
        "Added new object
           - vismBearerBusyCode"

    REVISION    "200402170000Z"
    DESCRIPTION
        "The following MIB are deprecated prior to SMIv2
         conversion, vismEcanToneDisable, vismEcanCnfNRN
         and vismCadenceTime.
        "

    REVISION    "200402150000Z"
    DESCRIPTION
        "Initial version of the MIB.

         The content of this MIB was originally available
         in SMIv1 version. The MIB has been converted to
         SMIv2 version and descriptions of some of the
         objects have been modified.
        "

    ::= { ciscoWan 79 }

dsx1Vism        OBJECT IDENTIFIER ::= { dsx1 5 }
dsx1VismCnfGrp  OBJECT IDENTIFIER ::= { dsx1Vism 1 }

-- ************************************************************
--
-- dsx1VismCnfGrp
--
-- This group is an extension to the dsx1CnfGrpTable found in
-- CISCO-MGX82XX-DSX1-MIB.
--
-- This group contains the DSP(Ecan and Compression) and other 
-- VISM parameters that are supported on a per line basis.
--
--
-- ************************************************************

dsx1VismCnfGrpTable  OBJECT-TYPE
    SYNTAX     SEQUENCE OF Dsx1VismCnfGrpEntry
    MAX-ACCESS not-accessible
    STATUS     current
    DESCRIPTION
        "The VISM specific DS1/E1 configuration table. This table
         contains the additional VISM configuration information
         for DS1/E1.
        "
    ::= { dsx1VismCnfGrp 1 }

dsx1VismCnfGrpEntry  OBJECT-TYPE
    SYNTAX     Dsx1VismCnfGrpEntry
    MAX-ACCESS not-accessible
    STATUS     current
    DESCRIPTION
        "An entry in the VISM Dsx1 Configuration table.
         An entry is created when a DS1/E1 is added.
         An entry is deleted when a DS1/E1 is deleted.
        
         The DS1/E1 is specify by 'lineEnable' object
         in CISCO-MGX82XX-DSX1-MIB. 
        "
    INDEX { vismLineNum }
    ::= { dsx1VismCnfGrpTable 1 }

Dsx1VismCnfGrpEntry ::=
    SEQUENCE {
        vismLineNum                  Integer32,
        vismEcanEnabled              INTEGER,
        vismEcanToneDisable          INTEGER,
        vismEcanCnfNRN               INTEGER,
        vismEcanTail                 Integer32,
        vismEcanREC                  INTEGER,
        vismCompCnfVAD               INTEGER,
        vismSignalingType            INTEGER,
        vismCcsChannels              Integer32,
        vismCadenceTime              Integer32,
        vismTrunkConditionEnable     TruthValue, 
        vismDsx1CircuitIdentifier    DisplayString,
        vismDsx1TxDigitOrder         INTEGER,      
        vismDsx1TonePlanRegion       DisplayString,      
        vismDsx1TonePlanVersion      Integer32,
        vismDsx1RingingTO            Integer32,
        vismDsx1RingBackTO           Integer32,      
        vismDsx1BusyTO               Integer32,      
        vismDsx1ReorderTO            Integer32,      
        vismDsx1DialTO               Integer32,      
        vismDsx1StutterDialTO        Integer32,      
        vismDsx1OffHookAlertTO       Integer32,      
        vismDsx1RemoteRingback       INTEGER,      
        vismDsx1MidcallTpart         Integer32,
        vismDsx1MidcallTcrit         Integer32,
        vismDsx1Sa4Byte              Integer32,
        vismDsx1Sa5Byte              Integer32,
        vismDsx1Sa6Byte              Integer32,
        vismDsx1Sa7Byte              Integer32,
        vismDsx1Sa8Byte              Integer32,
        vismDsx1State                INTEGER,
        vismDsx1AdminStateControl    INTEGER,
        vismBearerBusyCode           Integer32
        }

vismLineNum  OBJECT-TYPE
    SYNTAX     Integer32 (1..8)
    MAX-ACCESS read-only
    STATUS     current
    DESCRIPTION
        "This object identifies the DS1/E1 interface number.
        "
    ::= { dsx1VismCnfGrpEntry 1 }

vismEcanEnabled  OBJECT-TYPE
    SYNTAX     INTEGER {
                   disable (1),
                   enable  (2)
               }
    MAX-ACCESS read-write
    STATUS     current
    DESCRIPTION
        "This object disable/enable echo cancellation.
         'disable' : disable echo cancellation.
         'enable'  : enable echo cancellation.
        "
    DEFVAL { enable }
    ::= { dsx1VismCnfGrpEntry 2 }

vismEcanToneDisable  OBJECT-TYPE
    SYNTAX     INTEGER {
                   ignore  (1),
                   g-164   (2),
                   reserve (3),
                   g-165   (4)
               }
    MAX-ACCESS read-only
    STATUS     deprecated
    DESCRIPTION
        "This object determines the behaviour of the echo canceller
         in the presence of a modem.
         
         'ignore': Ignore 2100 Hz modem answer tone.
         'g-164' : G-164 mode, disable the canceller for all
                   the tones, phase reversing or not.
         'reserve': Reserved setting the value to 'reserve(3)'
                    results in BadValue error.
         'g-165':  G.165 mode, disable the canceller for phase
                   reversing tone only (V.8 modulated phase
                   reversing tone as well as the V.fast non
                   standard phase reversing tone).
        "
    DEFVAL { g-165 }
    ::= { dsx1VismCnfGrpEntry 3 }

vismEcanCnfNRN  OBJECT-TYPE
    SYNTAX     INTEGER {
                   reenableOnModemData (1),
                   reenableOnCallEnd   (2)
               }
    MAX-ACCESS read-only
    STATUS     deprecated
    DESCRIPTION
        "Echo canceller re-enable (NRN). This object
         determines when an echo canceller re-enable
         and begins cancellation after it has been
         disabled.
         
         'reenableOnModemData': Re-enable canceller when modem
                                data is gone (low energy).
         'reenableOnCallEnd' :  Re-enable canceller at end of call,
                                This object is not applicable
                                when vismEcanToneDisable 'ignore'.
        "
    DEFVAL { reenableOnModemData }
    ::= { dsx1VismCnfGrpEntry 4 }
 
vismEcanTail  OBJECT-TYPE
    SYNTAX     Integer32 (24..128)
    UNITS      "milliseconds"
    MAX-ACCESS read-write
    STATUS     current
    DESCRIPTION
        "This object identifies the maximum tail.  The object
         should be set just higher than the worst round trip delay
         anticipated. Convergence times may increase for longer
         tails and more resource will be used.
 
         Only following discrete values are allowed:
         24, 32, 48, 64, 80, 96, 112 and 128."
    DEFVAL { 32 }
    ::= { dsx1VismCnfGrpEntry 5 }
 
vismEcanREC  OBJECT-TYPE
    SYNTAX     INTEGER {
                   cancelOnly       (1),
                   suppressResidual (2),
                   reserved         (3),
                   comfortNoise     (4)
               }
    MAX-ACCESS read-write
    STATUS     current
    DESCRIPTION
        "Residual Echo Control(REC) instructs the canceller
         how to treat echo remaining after cancellation.

         'cancelOnly'      : REC is disabled.
         'suppressResidual': The residual echo is replaced
                             with silence.
         'comfortNoise'    : Noise is injected in place of
                             residual echo at the same level
                             as the ambient noise at the near
                             end.
         'reserved'        : Results in BadValue error.
        "
    DEFVAL { suppressResidual }
    ::= { dsx1VismCnfGrpEntry 6 }
 
vismCompCnfVAD  OBJECT-TYPE
    SYNTAX     INTEGER {
                   disable (1),
                   enable  (2)
               }
    MAX-ACCESS read-write
    STATUS     current
    DESCRIPTION
        "This object identifies VAD (Voice Activitiy Detection).

        'disable': Disable VAD on the compression DSPs.
        'enable' : Enable VAD on the compression DSPs. 
        "
    DEFVAL { enable }
    ::= { dsx1VismCnfGrpEntry 7 }
 
vismSignalingType  OBJECT-TYPE
    SYNTAX     INTEGER {
                   cas (1),
                   ccs  (2),
                   none (3)
               }
    MAX-ACCESS read-write 
    STATUS     current
    DESCRIPTION
        "This object specifies the type of signaling used for 
         the line.

         'cas'  : Channel Associated Signaling.
         'ccs'  : Common Channel Signaling.
         'none' : No signaling used.

         This cannot be modified if endpoints are present. 
         and if CIDs/CCS channels are associated with this
         line in aal2Trunking mode.
 
         Setting of this object to CAS signaling type is
         not allowed if any of the DS0s on this line have
         loop back set to RemoteLoop or if any of the
         DS0's has ds0InsertLocalCas enabled. RemoteLoop and
         ds0InsertLocalCas from CISCO-VISM-DSX0-MIB.  

         Line signaling type cannot be changed if there
         are endpoints present, irrespective of
         mode/application.
        "
    DEFVAL { none }
    ::= { dsx1VismCnfGrpEntry 8 }

vismCcsChannels  OBJECT-TYPE
    SYNTAX     Integer32(0..2147483647) 
    MAX-ACCESS read-write
    STATUS     current
    DESCRIPTION
        "This object describes the CCS signaling channels or 
         DS0s (also refered to as D-channel). 
         It is used only for lines configured as CCS signaling type. 
         It is a bit map of the DS0s configured as D channel. A one 
         in the bit position represents that DS0 as the D channel. 
         In most of the applications, only one D channel per T or E 
         span is required. However, since some applications may 
         require multiple D channels, this is supported by providing
         a bit map.
         This attribute is set by 'addccs' CLI command.
        "
    ::= { dsx1VismCnfGrpEntry 9 }

vismCadenceTime  OBJECT-TYPE
     SYNTAX     Integer32(50..200)
     UNITS      "milliseconds"
     MAX-ACCESS read-only
     STATUS     deprecated
     DESCRIPTION 
         "This object describes the cadence time for CAS signals.
          This object is applicable only for CAS backhaul
          applications. For trunking application it is not applicable.
         "
     DEFVAL { 100 } 
    ::= { dsx1VismCnfGrpEntry 10 } 

vismTrunkConditionEnable  OBJECT-TYPE
     SYNTAX     TruthValue
     MAX-ACCESS read-write
     STATUS     current
     DESCRIPTION
         "This object determines if trunk conditioning should be 
          enabled or disabled on this line. If this object is 
          set to true(1), VISM will do trunk conditioning on 
          the affected DS0s on this line when it sees an 
          alarm (AIS) on the ATM side, instead of sending AIS 
          on the line side.

          If there are endpoints or CCS channels enabled on a line 
          then setting of this object is not allowed.

          Trunk conditioning: VISM will transmit idle code pattern 
          for the first 2.5 secs and then will transmit seized code 
          which is configured in ds0IdleCode and ds0SeizedCode 
          respectively, ds0IdleCode and ds0SeizedCode from 
          CISCO-VISM-DSX0-MIB. 

          This object is applicable only in trunking application.

          This object can be set in all applications but will be 
          applicable in trunking application only.
         "
     DEFVAL { false }
     ::= { dsx1VismCnfGrpEntry  11 }

vismDsx1CircuitIdentifier  OBJECT-TYPE
    SYNTAX     DisplayString
    MAX-ACCESS read-write
    STATUS     current
    DESCRIPTION
        "This object is the identifier of a T1/E1 line.
         It contains alphanumeric description of a line for the
         purpose of better identification.
        "
    ::= { dsx1VismCnfGrpEntry 12 }

vismDsx1TxDigitOrder  OBJECT-TYPE
    SYNTAX     INTEGER {
                   aniThenDnis  (1),
                   dnisThenAni  (2)
               }
    MAX-ACCESS read-write
    STATUS     current
    DESCRIPTION
        "When the call agent hands the ANI (Automatic 
         Number Identification, denoting the calling party number)
         and the DNIS (Destination Number Identification Service, 
         indicating the called party number) to the gateway for 
         dialing out, the gateway (by default) dials out the ANI
         followed by the DNIS. This object indicates the order in 
         which ANI and DNIs will be dialled out from this 
         (outgoing) interface.
        "
    DEFVAL { aniThenDnis }
    ::= { dsx1VismCnfGrpEntry 13 }

vismDsx1TonePlanRegion  OBJECT-TYPE
    SYNTAX     DisplayString (SIZE(1..64))
    MAX-ACCESS read-write
    STATUS     current
    DESCRIPTION
        "This object specifies regional tone plan string. If the
         value of the object is 'NULL' then it will be considered  
         non usable, and non 'NULL' is (usable or activated 
         and related to an entry in the vismTonePlanTable table).
         This object must be compatible with the 
         vismDsx1TonePlanVersion object below, where both objects
         must either be NULL or where both objects must be non NULL.

         The vismTonePlanTable table consists of 32 slots which 
         are configurable (provisionable) followed by a release 
         dependent number of slots for built-in entries which are 
         not configurable, but loaded from values stored in the
         internal firmware of the release.  As releases are continued,
         the number of built-in slots will typically increase.  
         The total number of slots in this table consists of the sum 
         of the 32 provisionable slots plus an unspecified number of
         built-in slots and the built-in number and this sum
         represents the size of this table.

         In the case where these two objects are non NULL, this
         object, along with the vismDsx1TonePlanVersion object below, 
         must exactly match an entry in the vismTonePlanTable.  
         In the case where these objects are considered to be a NULL
         object, its behavior and contents are described in 
         paragraph five of this description block.

         The allowed range and contents of this object in the 
         non NULL case is the same as the tonePlanRegionName
         object in the vismTonePlanTable. This object will thus 
         consist of a 1 to 64 alphabetic, numeric, or underscore
         character string, with no embedded spaces.  And this object 
         plus the vismDsx1TonePlanVersion object below, must exactly 
         match an existing valid entry in the vismTonePlanTable,
         vismTonePlanTable is specify in CISCO-WAN-VISM-TONE-PLAN-MIB.

         In the case where this object is NULL, this object will 
         consist of a single space character of size one.  A NULL 
         value for this object will make the vismDsx1RingingTO, 
         vismDsx1RingBackTO, vismDsx1BusyTO, vismDsx1ReorderTO,
         vismDsx1DialTO, vismDsx1StutterDialTO,
         vismDsx1OffHookAlertTO, and vismDsx1RemoteRingback.
        "
    ::= { dsx1VismCnfGrpEntry 14 }

vismDsx1TonePlanVersion  OBJECT-TYPE
    SYNTAX     Integer32(0..2147483647)
    MAX-ACCESS read-write
    STATUS     current
    DESCRIPTION
         "This object will either be considered NULL
          (i.e. non usable) or non NULL (usable or activated 
          and related to an entry in the vismTonePlanTable table).
          This object must be compatible with the 
          vismDsx1TonePlanRegion object above, where both objects 
          must either be NULL or where both objects must be non NULL.
          The vismTonePlanTable table consists of 32 slots which 
          are configurable (provisionable) followed by a release 
          dependent number of slots for built-in entries which are 
          not configurable, but loaded from values stored in the
          internal firmware of the release. As releases are continued,
          the number of built-in slots will typically increase.  
          The total number of slots in this table consists of the sum 
          of the 32 provisionable slots plus an unspecified
          number of built-in slots and the built-in number and this 
          sum represents the size of this table.
 
          In the case where these two objects are non NULL, this
          object, along with the vismDsx1TonePlanRegion object
          above, must exactly match an entry in the
          vismTonePlanTable.  In the case where these objects
          are considered to be a NULL object, its behavior and
          contents are described in paragraph five of this
          description block.
 
          The allowed range and contents of this object in the non
          NULL case is the same as the tonePlanVersionNumber object
          in the vismTonePlanTable. This object will thus consist of 
          a non zero numeric value.  And this object plus the 
          vismDsx1TonePlanRegion object above, must exactly match 
          an existing valid entry in the vismTonePlanTable.
 
          In the case where this object is NULL, this object will 
          consist of a zero numeric value.  A NULL value for this 
          object will make the vismDsx1RingingTO, vismDsx1RingBackTO, 
          vismDsx1BusyTO, vismDsx1ReorderTO, vismDsx1DialTO, 
          vismDsx1StutterDialTO, vismDsx1OffHookAlertTO, and
          vismDsx1RemoteRingback.
         "
    ::= { dsx1VismCnfGrpEntry 15 }

vismDsx1RingingTO  OBJECT-TYPE
    SYNTAX     Integer32 (0..3600)
    UNITS      "seconds"
    MAX-ACCESS read-write
    STATUS     current
    DESCRIPTION
        "Time in seconds for which the ringing cadence will be
         generated towards the basic PBX unless interrupted 
         (e.g. by the answer from the called party or a delete 
         connection command from the Call Agent). This is also
         the time for which remote inband ring back tone will be
         played towards the packet network. The value Zero indicates 
         that the cadence will be generated indefinitely unless 
         interrupted.

         This MIB object is not applicable unless the value of
         vismDsx1TonePlanRegion and vismDsx1TonePlanVersion MIB
         objects are not 'NULL' string.
        "
    DEFVAL { 180 }
    ::= { dsx1VismCnfGrpEntry 16 }

vismDsx1RingBackTO  OBJECT-TYPE
    SYNTAX     Integer32 (0..3600)
    UNITS      "seconds"
    MAX-ACCESS read-write
    STATUS     current
    DESCRIPTION
        "Time in seconds for which the local ring back tone 
         (towards the TDM) will be generated unless interrupted 
         (e.g. by the answer from the called party or a delete 
         connection command from the Call Agent). The value Zero 
         indicates that the tone will be generated indefinitely 
         unless interrupted.

         This MIB object is not applicable unless the value of
         vismDsx1TonePlanRegion and vismDsx1TonePlanVersion MIB
         objects are not 'NULL' string.
        "
    DEFVAL { 180 }
    ::= { dsx1VismCnfGrpEntry 17 }

vismDsx1BusyTO  OBJECT-TYPE
    SYNTAX     Integer32 (0..3600)
    UNITS      "seconds"
    MAX-ACCESS read-write
    STATUS     current
    DESCRIPTION
        "Time in seconds for which the busy tone will be 
         generated unless interrupted (e.g. by the hangup from 
         the calling party). The value Zero indicates that the
         tone will be generated indefinitely unless interrupted.

         This MIB object is not applicable unless the value of
         vismDsx1TonePlanRegion and vismDsx1TonePlanVersion MIB
         objects are not 'NULL' string.
        "
    DEFVAL { 30 }
    ::= { dsx1VismCnfGrpEntry 18 }

vismDsx1ReorderTO  OBJECT-TYPE
    SYNTAX     Integer32 (0..3600)
    UNITS      "seconds"
    MAX-ACCESS read-write
    STATUS     current
    DESCRIPTION
        "Time in seconds for which the reorder/fast busy 
         tone will be generated unless interrupted 
         (e.g. by the hangup from the calling party). The value
         zero indicates that the tone will be generated
         indefinitely unless interrupted.

         This MIB object is not applicable unless the value of
         vismDsx1TonePlanRegion and vismDsx1TonePlanVersion MIB
         objects are not 'NULL' string.
        "
    DEFVAL { 30 }
    ::= { dsx1VismCnfGrpEntry 19 }

vismDsx1DialTO  OBJECT-TYPE
    SYNTAX     Integer32 (0..3600)
    UNITS      "seconds"
    MAX-ACCESS read-write
    STATUS     current
    DESCRIPTION
        "Time in seconds for which the dial tone will be 
         generated unless interrupted (e.g. by the first DTMF 
         digit from the calling party). The value Zero indicates
         that the tone will be generated indefinitely unless 
         interrupted.

         This MIB object is not applicable unless the value of
         vismDsx1TonePlanRegion and vismDsx1TonePlanVersion MIB
         objects are not 'NULL' string.
        "
    DEFVAL { 16 }
    ::= { dsx1VismCnfGrpEntry 20 }

vismDsx1StutterDialTO  OBJECT-TYPE
    SYNTAX     Integer32 (0..3600)
    UNITS      "seconds"
    MAX-ACCESS read-write
    STATUS     current
    DESCRIPTION
        "Time in seconds for which the stutter dial 
         tone/confirmation dial tone will be generated unless
         interrupted (e.g. by the first DTMF digit from the
         calling party). The value Zero indicates that the tone 
         will be generated indefinitely unless interrupted.

         This MIB object is not applicable unless the value of
         vismDsx1TonePlanRegion and vismDsx1TonePlanVersion MIB
         objects are not 'NULL' string.
        "
    DEFVAL { 16 }
    ::= { dsx1VismCnfGrpEntry 21 }

vismDsx1OffHookAlertTO  OBJECT-TYPE
    SYNTAX     Integer32 (0..3600)
    UNITS      "seconds"
    MAX-ACCESS read-write
    STATUS     current
    DESCRIPTION
        "Time in seconds for which the off-hook alert tone 
         will be generated unless interrupted (e.g. caller hangup). 
         The value Zero indicates that the tone will be generated
         indefinitely unless interrupted.

         This MIB object is not applicable unless the value of
         vismDsx1TonePlanRegion and vismDsx1TonePlanVersion MIB
         objects are not 'NULL' string.
        "
    DEFVAL { 5 }
    ::= { dsx1VismCnfGrpEntry 22 }

vismDsx1RemoteRingback  OBJECT-TYPE
    SYNTAX      INTEGER {
                    proxy    (1),
                    inband   (2)
                }
    MAX-ACCESS  read-write
    STATUS  current
    DESCRIPTION
        "This object specifies the remote ring back method on 
         endpoints on this DS1/E1. 
         This object can have the following values:
 
         'proxy(1)': This gateway sends the appropriate packet
                      (NSE, NTE, or AAL-2 Type 3) for ring back to 
                      the originating gateway which in turn generates 
                      the ringback tone towards the TDM network.

         'inband(2)': This gateway will generate the inband ringback
                      tone towards the originating gateway over the 
                      packet network and the originating gateway plays 
                      it.

         This MIB object is not applicable unless the value of
         vismDsx1TonePlanRegion and vismDsx1TonePlanVersion MIB
         objects are not 'NULL' string.
        "
    DEFVAL { proxy }
    ::= { dsx1VismCnfGrpEntry 23 }

vismDsx1MidcallTpart  OBJECT-TYPE
    SYNTAX     Integer32 (10..10000)
    UNITS      "seconds"
    MAX-ACCESS read-write
    STATUS     current
    DESCRIPTION
        "This object represents the partial dial timing in
         seconds and is used along with a digit map as the
         inter-digit timer. This object is used for both CAS 
         and non CAS endpoints when doing mid call DTMF 
         digit reporting. The timer is not started until 
         the first digit is entered, and the timer is 
         restarted after each new digit is entered until 
         either a digit map match or mismatch occurs.
        "
    DEFVAL { 16 }
    ::= { dsx1VismCnfGrpEntry 24 }

vismDsx1MidcallTcrit  OBJECT-TYPE
    SYNTAX     Integer32 (0..10000)
    UNITS      "seconds"
    MAX-ACCESS read-write
    STATUS     current
    DESCRIPTION
        "This object represents the critical timing in seconds.
         If used along with a digit map, the timer is started when
         the last digit is received i.e when no more digits
         are required for a digit map match. After this timer
         expires, the digit map match is assumed to be complete.
         If used without a digit map, the timer is started
         immediately and cancelled (but not restarted) as soon
         as a digit is entered.
         This object is used for both CAS and non CAS endpoints 
         when doing mid call DTMF digit reporting.
        "
    DEFVAL { 4 }
    ::= { dsx1VismCnfGrpEntry 25 }

vismDsx1Sa4Byte  OBJECT-TYPE
    SYNTAX     Integer32 (0..255)
    MAX-ACCESS read-write
    STATUS     current
    DESCRIPTION
        "This is a spare bit on T1/E1 Framer reserved for 
         international standardization.
        "
    DEFVAL { 0 }
    ::= { dsx1VismCnfGrpEntry 26 }

vismDsx1Sa5Byte  OBJECT-TYPE
    SYNTAX     Integer32 (0..255)
    MAX-ACCESS read-write
    STATUS     current
    DESCRIPTION
        "This is a spare bit on T1/E1 Framer reserved for
         international standardization.
        "
    DEFVAL { 0 }
    ::= { dsx1VismCnfGrpEntry 27 }

vismDsx1Sa6Byte  OBJECT-TYPE
    SYNTAX     Integer32 (0..255)
    MAX-ACCESS read-write
    STATUS     current
    DESCRIPTION
        "This is a spare bit on T1/E1 Framer reserved for 
         international standardization.
        "
    DEFVAL { 0 }
    ::= { dsx1VismCnfGrpEntry 28 }

vismDsx1Sa7Byte  OBJECT-TYPE
    SYNTAX     Integer32 (0..255)
    MAX-ACCESS read-write
    STATUS     current
    DESCRIPTION
        "This is a spare bit on T1/E1 Framer reserved for 
         international standardization.
        "
    DEFVAL { 0 }
    ::= { dsx1VismCnfGrpEntry 29 }

vismDsx1Sa8Byte  OBJECT-TYPE
    SYNTAX     Integer32 (0..255)
    MAX-ACCESS read-write
    STATUS     current
    DESCRIPTION
        "This is a spare bit on T1/E1 Framer reserved for 
         international standardization.
        "
    DEFVAL { 0 }
    ::= { dsx1VismCnfGrpEntry 30 }

vismDsx1State  OBJECT-TYPE
    SYNTAX     INTEGER {
                   invalid (1),
                   is      (2),
                   oos     (3),
                   poos    (4),
                   coos    (5),
                   inactive(6) 
               }
    MAX-ACCESS read-only
    STATUS     current
    DESCRIPTION
        "This object will allow the line administrative state
         (in service and out of service) to be persistent.
         invalid (1) : invalid state.
         is      (2) : inservice
         oos     (3) : out of service
         poos    (4) : pending out of service
         coos    (5) : command out of service
         inactive(6) : inactive
        "
    DEFVAL { inactive }
    ::= { dsx1VismCnfGrpEntry 31 }

vismDsx1AdminStateControl  OBJECT-TYPE
    SYNTAX     INTEGER {
                   inService (1),
                   forcefulOutOfService (2),
                   gracefulOutOfService (3),
                   inactive (4)
               }
    MAX-ACCESS read-write
    STATUS     current
    DESCRIPTION
        "This control object is used to change the service state of the
         line from 'is' to 'coos' or from 'coos'
         to 'is'. The resulting service state of the line is
         represented by vismDsx1State.

         'inService': Transition vismDsx1State to 'is'(in service).
                    In the course, the MG's MGCs may get notified 
                    of this transition, e.g. in the case of MGCP 
                    through emission of RSIPs to registered call 
                    agents according to policy.

         'forcefulOutOfService': Take the line out-of-service 
                    forcefully. This releases any resources at the 
                    line. In the course, the MGCs may get notified 
                    of this transition, e.g. in the case of MGCP 
                    through emission of RSIPs to registered call 
                    agents according to policy.

         'gracefulOutOfService': Take the line out-of-service
                    gracefully. If there are no resources
                    existing, vismDsx1State transitions to coos
                    immediately. If resources exist,
                    vismDsx1State transitions to poos thus
                    initiating a graceful shutdown. In the
                    course, the MG's MGCs may get notified of 
                    this transition, e.g. in the case of MGCP through 
                    emission of RSIPs to registered call agents 
                    according to policy.
         'inactive': Indicates the vismDsx1State is in inactive state. 
        "
    DEFVAL { inactive }
    ::= { dsx1VismCnfGrpEntry 32 }

vismBearerBusyCode  OBJECT-TYPE
    SYNTAX Integer32 (0..255)
    MAX-ACCESS read-write
    STATUS current
    DESCRIPTION
        "This object is used when vismTrunkConditionEnable is
         enabled on a line. It is a configurable busy pattern
         sent out on the 'Bearer' on the channels, which are
         receiving remote ATM channel ID (CID) alarms.
         If this object is not set, it assumes a default value
         of 255 for E1 and 127 for T1."
    ::= {dsx1VismCnfGrpEntry 33 }

-- -----------------------------------------------------------------
-- dsx1AlmHistoryTable
-- -----------------------------------------------------------------

dsx1AlmHistoryTable  OBJECT-TYPE
    SYNTAX     SEQUENCE OF Dsx1AlmHistoryEntry
    MAX-ACCESS not-accessible
    STATUS     current
    DESCRIPTION
        "The TDM line interface alarm history table."
    ::= { dsx1AlmGrp 2 }

dsx1AlmHistoryEntry  OBJECT-TYPE
    SYNTAX     Dsx1AlmHistoryEntry
    MAX-ACCESS not-accessible
    STATUS     current
    DESCRIPTION
        "An entry in the DS1/E1 Alarm History table."
    INDEX   { almlineNumber, almIntervalNumber }
    ::= { dsx1AlmHistoryTable 1 }

Dsx1AlmHistoryEntry ::=
        SEQUENCE {
            almlineNumber               Integer32,
            almIntervalNumber           Integer32,
            lCV                         Counter32,
            lES                         Counter32,
            lSES                        Counter32,
            cRC                         Counter32,
            cRCES                       Counter32,
            cRCSES                      Counter32,
            sEFS                        Counter32,
            aISS                        Counter32,
            uAS                         Counter32,
            percentErrorFreeSecs        Integer32,
            rcvLOSCnt                   Counter32,
            rcvOOFCnt                   Counter32,
            rcvRAICnt                   Counter32,
            rcvFECnt                    Counter32,
            dsx1AlmClrButton            INTEGER
        }

almlineNumber  OBJECT-TYPE
    SYNTAX     Integer32 (1..8)
    MAX-ACCESS read-only
    STATUS     current
    DESCRIPTION
        "This object is the identifier of a DS1/E1 Interface
         on a managed device.
        "
    ::= { dsx1AlmHistoryEntry 1 }

almIntervalNumber  OBJECT-TYPE
    SYNTAX     Integer32 (1..96)
    MAX-ACCESS read-only
    STATUS     current
    DESCRIPTION
        "This is the alarm interval number which associates with 
         time interval alarms occurred.
        "
    ::= { dsx1AlmHistoryEntry 2 }

lCV  OBJECT-TYPE
    SYNTAX     Counter32
    MAX-ACCESS read-only
    STATUS     current
    DESCRIPTION
        "The accumulated number of Line code 
         violations encountered on the DS1 interface.
        "
    ::= { dsx1AlmHistoryEntry 3 }

lES  OBJECT-TYPE
    SYNTAX     Counter32
    MAX-ACCESS read-only
    STATUS     current
    DESCRIPTION
        "The accumulated number of Line code 
         violations Errored Seconds encountered on the
         DS1 interface.
        "
    ::= { dsx1AlmHistoryEntry 4 }

lSES  OBJECT-TYPE
    SYNTAX     Counter32
    MAX-ACCESS read-only
    STATUS     current
    DESCRIPTION
        "The accumulated number of LCV (Line Code Violations)
         Severely Errored Seconds encountered on 
         the DS1 interface.
        "
    ::= { dsx1AlmHistoryEntry 5 }

cRC  OBJECT-TYPE
    SYNTAX     Counter32
    MAX-ACCESS read-only
    STATUS     current
    DESCRIPTION
        "The accumulated number of P Bit code
         violations encountered on the DS1 interface.
        "
    ::= { dsx1AlmHistoryEntry 6 }

cRCES  OBJECT-TYPE
    SYNTAX     Counter32
    MAX-ACCESS read-only
    STATUS     current
    DESCRIPTION
        "The accumulated number of PVC Errored 
         Seconds encountered on the DS1 interface.
        "
    ::= { dsx1AlmHistoryEntry 7 }

cRCSES  OBJECT-TYPE
    SYNTAX     Counter32
    MAX-ACCESS read-only
    STATUS     current
    DESCRIPTION
        "The accumulated number of P Bit code 
         violations Severely Errored Seconds encountered 
         on the DS1 interface.
        "
    ::= { dsx1AlmHistoryEntry 8 }
sEFS  OBJECT-TYPE
    SYNTAX     Counter32
    MAX-ACCESS read-only
    STATUS     current
    DESCRIPTION
        "The accumulated number of Severely
         Errored Framing Seconds encountered on the 
         DS1 interface.
        "
    ::= { dsx1AlmHistoryEntry 9 }

aISS OBJECT-TYPE
    SYNTAX     Counter32
    MAX-ACCESS read-only
    STATUS     current
    DESCRIPTION
        "The accumulated number of AIS 
         Severely Errored Seconds encountered on the
         DS1 interface.
        "
    ::= { dsx1AlmHistoryEntry 10 }

uAS OBJECT-TYPE
    SYNTAX     Counter32
    MAX-ACCESS read-only
    STATUS     current
    DESCRIPTION
        "The accumulated number of Unavailable 
         Seconds encountered on the DS1 interface.
        "
    ::= { dsx1AlmHistoryEntry 11 }

percentErrorFreeSecs  OBJECT-TYPE
    SYNTAX     Integer32(0..100)
    MAX-ACCESS read-only
    STATUS     current
    DESCRIPTION
        "The accumulated the percentage of 
         LCV (Line Code Violation) Error Free Seconds.
        "
    ::= { dsx1AlmHistoryEntry 12 }

rcvLOSCnt OBJECT-TYPE
    SYNTAX     Counter32
    MAX-ACCESS read-only
    STATUS     current
    DESCRIPTION
        "The accumulated number of LOS (Loss of Signal)  
         detected with or without integrating to LOS alarm
         on the DS1 interface.
        "
    ::= { dsx1AlmHistoryEntry 13 }

rcvOOFCnt  OBJECT-TYPE
    SYNTAX     Counter32
    MAX-ACCESS read-only
    STATUS     current
    DESCRIPTION
        "The accumulated number of OOF (Out of Frame) 
         detected with or without integrating to OOF alarm
         on the DS1 interface.
        "
    ::= { dsx1AlmHistoryEntry 14 }

rcvRAICnt  OBJECT-TYPE
    SYNTAX     Counter32
    MAX-ACCESS read-only
    STATUS     current
    DESCRIPTION
        "The accumulated number of Yellow Alarms
         detected with or without integrating to RAI alarm
         on the DS1 interface.
        "
    ::= { dsx1AlmHistoryEntry 15 }

rcvFECnt  OBJECT-TYPE
    SYNTAX     Counter32
    MAX-ACCESS read-only
    STATUS     current
    DESCRIPTION
        "The accumulated number of Framing Pattern Errors 
         encountered on a DS1/E1 interface.
        "
    ::= { dsx1AlmHistoryEntry 16 }

dsx1AlmClrButton OBJECT-TYPE
    SYNTAX     INTEGER {
                   noaction (1),
                   clear (2)
               }
    MAX-ACCESS read-write
    STATUS     current
    DESCRIPTION
        "This variable is used to clear all the 
         alarms for the line/interval.
        "
    ::= { dsx1AlmHistoryEntry 17 }

-- conformance information

cvDsx1MIBConformance  OBJECT IDENTIFIER ::= { ciscoVismDsx1MIB 2 }

cvDsx1MIBGroups       OBJECT IDENTIFIER ::= 
                              { cvDsx1MIBConformance 1 }

cvDsx1MIBCompliances  OBJECT IDENTIFIER ::= 
                              { cvDsx1MIBConformance 2 }

-- compliance statements

cvDsx1Compliance MODULE-COMPLIANCE
    STATUS deprecated -- replaced by cvDsx1ComplianceRev1 
    DESCRIPTION
        "The compliance statement for objects related
         to VISM DS1/E1 MIB.
        " 
    MODULE  -- this module
        MANDATORY-GROUPS {
            cvDsx1ConfGroup,
            cvDsx1AlmHistoryGroup
            }
    ::= { cvDsx1MIBCompliances 1 }


cvDsx1ComplianceRev1 MODULE-COMPLIANCE
    STATUS  deprecated --Replaced by cvDsx1ComplianceRev2
    DESCRIPTION
        "The compliance statement for objects related
         to VISM DS1/E1 MIB.
        "
    MODULE  -- this module
        MANDATORY-GROUPS {
            cvDsx1ConfGroupRev1,
            cvDsx1AlmHistoryGroup
            }
    ::= { cvDsx1MIBCompliances 2 }

cvDsx1ComplianceRev2 MODULE-COMPLIANCE
    STATUS  current
    DESCRIPTION
        "The compliance statement for objects related
         to VISM DS1/E1 MIB.
        "
    MODULE  -- this module
        MANDATORY-GROUPS {
            cvDsx1ConfGroupRev2,
            cvDsx1AlmHistoryGroup
            }
    ::= { cvDsx1MIBCompliances 3 }

cvDsx1ConfGroup OBJECT-GROUP
    OBJECTS {
        vismLineNum,
        vismEcanEnabled,
        vismEcanToneDisable,
        vismEcanCnfNRN,
        vismEcanTail,
        vismEcanREC,
        vismCompCnfVAD,
        vismSignalingType,
        vismCcsChannels,
        vismCadenceTime,
        vismTrunkConditionEnable,
        vismDsx1CircuitIdentifier,
        vismDsx1TxDigitOrder,
        vismDsx1TonePlanRegion,
        vismDsx1TonePlanVersion,
        vismDsx1RingingTO,
        vismDsx1RingBackTO,
        vismDsx1BusyTO,
        vismDsx1ReorderTO,
        vismDsx1DialTO,
        vismDsx1StutterDialTO,
        vismDsx1OffHookAlertTO,
        vismDsx1RemoteRingback,
        vismDsx1MidcallTpart,
        vismDsx1MidcallTcrit,
        vismDsx1Sa4Byte,
        vismDsx1Sa5Byte,
        vismDsx1Sa6Byte,
        vismDsx1Sa7Byte,
        vismDsx1Sa8Byte,
        vismDsx1State,
        vismDsx1AdminStateControl
     }
    STATUS deprecated 
    DESCRIPTION
        "The collection of objects used for
         DS1/E1 interfaces.
        "
    ::= { cvDsx1MIBGroups 1 }

cvDsx1AlmHistoryGroup OBJECT-GROUP
    OBJECTS {
        almlineNumber,
        almIntervalNumber,
        lCV,
        lES,
        lSES,
        cRC,
        cRCES,
        cRCSES,
        sEFS,
        aISS,
        uAS,
        percentErrorFreeSecs,
        rcvLOSCnt,
        rcvOOFCnt,
        rcvRAICnt,
        rcvFECnt,
        dsx1AlmClrButton
     }
    STATUS current
    DESCRIPTION
        "The collection of objects related to
         DS1/E1 alarm history.
        "
    ::= { cvDsx1MIBGroups 2 }

cvDsx1ConfGroupRev1 OBJECT-GROUP
    OBJECTS {
        vismLineNum,
        vismEcanEnabled,
        vismEcanTail,
        vismEcanREC,
        vismCompCnfVAD,
        vismSignalingType,
        vismCcsChannels,
        vismTrunkConditionEnable,
        vismDsx1CircuitIdentifier,
        vismDsx1TxDigitOrder,
        vismDsx1TonePlanRegion,
        vismDsx1TonePlanVersion,
        vismDsx1RingingTO,
        vismDsx1RingBackTO,
        vismDsx1BusyTO,
        vismDsx1ReorderTO,
        vismDsx1DialTO,
        vismDsx1StutterDialTO,
        vismDsx1OffHookAlertTO,
        vismDsx1RemoteRingback,
        vismDsx1MidcallTpart,
        vismDsx1MidcallTcrit,
        vismDsx1Sa4Byte,
        vismDsx1Sa5Byte,
        vismDsx1Sa6Byte,
        vismDsx1Sa7Byte,
        vismDsx1Sa8Byte,
        vismDsx1State,
        vismDsx1AdminStateControl
     }
    STATUS deprecated --Replaced by cvDsx1ConfGroupRev2
    DESCRIPTION
        "The collection of objects related to
         DS1/E1 in VISM
        "
    ::= { cvDsx1MIBGroups 3 }

cvDsx1ConfGroupRev2 OBJECT-GROUP
    OBJECTS {
        vismLineNum,
        vismEcanEnabled,
        vismEcanTail,
        vismEcanREC,
        vismCompCnfVAD,
        vismSignalingType,
        vismCcsChannels,
        vismTrunkConditionEnable,
        vismDsx1CircuitIdentifier,
        vismDsx1TxDigitOrder,
        vismDsx1TonePlanRegion,
        vismDsx1TonePlanVersion,
        vismDsx1RingingTO,
        vismDsx1RingBackTO,
        vismDsx1BusyTO,
        vismDsx1ReorderTO,
        vismDsx1DialTO,
        vismDsx1StutterDialTO,
        vismDsx1OffHookAlertTO,
        vismDsx1RemoteRingback,
        vismDsx1MidcallTpart,
        vismDsx1MidcallTcrit,
        vismDsx1Sa4Byte,
        vismDsx1Sa5Byte,
        vismDsx1Sa6Byte,
        vismDsx1Sa7Byte,
        vismDsx1Sa8Byte,
        vismDsx1State,
        vismDsx1AdminStateControl,
        vismBearerBusyCode
     }
    STATUS current 
    DESCRIPTION
        "The collection of objects related to
         DS1/E1 in VISM
        "
    ::= { cvDsx1MIBGroups 4 }

END
