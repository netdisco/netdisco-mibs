-- *****************************************************************
-- CISCO-TBRIDGE-DEV-IF-MIB.my: CISCO Transparent Bridging
-- Device Interface MIB file
--
-- April 2002, Francis Pang 
--
-- Copyright (c) 2002 by Cisco Systems, Inc.
-- All rights reserved.
-- *****************************************************************
--
CISCO-TBRIDGE-DEV-IF-MIB DEFINITIONS ::= BEGIN

IMPORTS
        MODULE-IDENTITY,
        OBJECT-TYPE,
        Unsigned32
                FROM SNMPv2-SMI
        MODULE-COMPLIANCE,
        OBJECT-GROUP
                FROM SNMPv2-CONF
        InetAddressType,
        InetAddress
                FROM INET-ADDRESS-MIB
        MacAddress
                FROM SNMPv2-TC
        ifIndex
                FROM IF-MIB
        ciscoMgmt
                FROM CISCO-SMI;




ciscoTBridgeDevIfMIB MODULE-IDENTITY
        LAST-UPDATED    "200204030001Z"
        ORGANIZATION    "Cisco System Inc."
        CONTACT-INFO
                "       Cisco Systems
                        Customer Service

                Postal: 170 West Tasman Drive,
                        San Jose CA 95134-1706.
                        USA

                   Tel: +1 800 553-NETS

                E-mail: cs-dot11@cisco.com"
        DESCRIPTION
                "This MIB module provides network management support 
                for configuration and status information of devices 
                supporting transparent bridging functions."
        REVISION        "200204030001Z"
        DESCRIPTION
                "Initial version of this MIB module."
        ::= { ciscoMgmt 269 }



ciscoTBridgeDevIfMIBObjects  OBJECT IDENTIFIER 
        ::= { ciscoTBridgeDevIfMIB 1 }

ctbrDevInterface OBJECT IDENTIFIER 
        ::= { ciscoTBridgeDevIfMIBObjects 1 }        



-- ********************************************************************
-- *  ctbrDevInterfaceTable parameters  
-- ********************************************************************
ctbrDevInterfaceTable OBJECT-TYPE
        SYNTAX SEQUENCE OF CtbrDevInterfaceEntry
        MAX-ACCESS not-accessible
        STATUS current
        DESCRIPTION 
                "This table provides configuration and information
                of the device interfaces supporting transparent
                bridging. This table has a sparse dependent 
                relationship with the ifTable." 
        ::= { ctbrDevInterface 1 }

ctbrDevInterfaceEntry OBJECT-TYPE
        SYNTAX CtbrDevInterfaceEntry
        MAX-ACCESS not-accessible
        STATUS current
        DESCRIPTION 
                "Each entry provides MAC and IP address related 
                configuration information of an interface."
        INDEX { ifIndex }
        ::= { ctbrDevInterfaceTable 1 }

CtbrDevInterfaceEntry ::= SEQUENCE { 
        ctbrDefaultPhyAddress  MacAddress,
        ctbrPhyAddress         MacAddress,
        ctbrDefaultIpAddrType  InetAddressType,
        ctbrDefaultIpAddress   InetAddress,
        ctbrDefaultIpMaskType  InetAddressType,
        ctbrDefaultIpMask      InetAddress,
        ctbrIpAddressType      InetAddressType,
        ctbrIpAddress          InetAddress,
        ctbrIpMaskType         InetAddressType,
        ctbrIpMask             InetAddress,
        ctbrMSDUMaxLength      Unsigned32 }

ctbrDefaultPhyAddress OBJECT-TYPE
        SYNTAX MacAddress
        MAX-ACCESS read-only
        STATUS current
        DESCRIPTION
                "The default, factory-assigned MAC address of
                the interface.  Guaranteed to be unique across
                all IEEE 802 devices."
        ::= { ctbrDevInterfaceEntry 1 }

ctbrPhyAddress OBJECT-TYPE
        SYNTAX MacAddress
        MAX-ACCESS read-write
        STATUS current
        DESCRIPTION
                "The MAC address to be used by the interface.
                If ctbrDefaultPhyAddress is used, 
                this is '00:00:00:00:00:00'."
        ::= { ctbrDevInterfaceEntry 2 }

ctbrDefaultIpAddrType OBJECT-TYPE
        SYNTAX InetAddressType
        MAX-ACCESS read-write
        STATUS current
        DESCRIPTION 
                "The IP address type of the 
                ctbrDefaultIpAddress object."
        ::= { ctbrDevInterfaceEntry 3 }

ctbrDefaultIpAddress OBJECT-TYPE
        SYNTAX InetAddress
        MAX-ACCESS read-write
        STATUS current
        DESCRIPTION 
                "The default IP address of the interface. If BOOTP 
                or DHCP is enabled, this may be overridden by the 
                BOOTP or DHCP server."
        ::= { ctbrDevInterfaceEntry 4 }

ctbrDefaultIpMaskType OBJECT-TYPE
        SYNTAX InetAddressType
        MAX-ACCESS read-write
        STATUS current
        DESCRIPTION 
                "The IP address type of the 
                ctbrDefaultIpMask object."
        ::= { ctbrDevInterfaceEntry 5 }

ctbrDefaultIpMask OBJECT-TYPE
        SYNTAX InetAddress
        MAX-ACCESS read-write
        STATUS current
        DESCRIPTION 
                "The default IP netmask of the interface. If BOOTP 
                or DHCP is enabled, this may be overridden by the 
                BOOTP or DHCP server."
        ::= { ctbrDevInterfaceEntry 6 }

ctbrIpAddressType OBJECT-TYPE
        SYNTAX InetAddressType
        MAX-ACCESS read-write
        STATUS current
        DESCRIPTION 
                "The IP address type of the 
                ctbrIpAddress object."
        ::= { ctbrDevInterfaceEntry 7 }

ctbrIpAddress OBJECT-TYPE
        SYNTAX InetAddress
        MAX-ACCESS read-write
        STATUS current
        DESCRIPTION 
                "The IP address currently in use by the interface."
        ::= { ctbrDevInterfaceEntry 8 }

ctbrIpMaskType OBJECT-TYPE
        SYNTAX InetAddressType
        MAX-ACCESS read-write
        STATUS current
        DESCRIPTION 
                "The IP address type of the ctbrIpMask
                object."
        ::= { ctbrDevInterfaceEntry 9 }

ctbrIpMask OBJECT-TYPE
        SYNTAX InetAddress
        MAX-ACCESS read-write
        STATUS current
        DESCRIPTION 
                "The IP netmask currently in use by the interface."
        ::= { ctbrDevInterfaceEntry 10 }

ctbrMSDUMaxLength OBJECT-TYPE
        SYNTAX Unsigned32
        MAX-ACCESS read-only
        STATUS current
        DESCRIPTION 
                "Maximum length of the data portion of a packet
                 for this particular interface.  This is the
                 maximum MAC Service Data Unit length, which is
                 greater than or equal to ifMtu, depending on
                 the configured MAC-level encapsulation."
        ::= { ctbrDevInterfaceEntry 11 }




-- *****************************************************************
--   Conformance information
-- *****************************************************************

ciscoTBridgeDevIfMIBConformance OBJECT IDENTIFIER 
      ::= { ciscoTBridgeDevIfMIB 2 }

ciscoTBridgeDevIfMIBCompliances OBJECT IDENTIFIER 
      ::= { ciscoTBridgeDevIfMIBConformance 1 }

ciscoTBridgeDevIfMIBGroups OBJECT IDENTIFIER 
      ::= { ciscoTBridgeDevIfMIBConformance 2 }


-- *****************************************************************
--   Compliance statements
-- *****************************************************************

ciscoTBridgeDevIfCompliance MODULE-COMPLIANCE
        STATUS  current
        DESCRIPTION
                "The compliance statement for the 
                interface configuration ctbrDevIfConfigGroup."
        MODULE 
                MANDATORY-GROUPS {
                        ctbrDevIfConfigGroup
                }
        ::= { ciscoTBridgeDevIfMIBCompliances 1 }

-- *****************************************************************
--   Units of conformance
-- *****************************************************************

ctbrDevIfConfigGroup  OBJECT-GROUP
        OBJECTS { 
                ctbrDefaultPhyAddress,
                ctbrPhyAddress,
                ctbrDefaultIpAddrType,
                ctbrDefaultIpAddress,
                ctbrDefaultIpMaskType,
                ctbrDefaultIpMask,
                ctbrIpAddressType,
                ctbrIpAddress,
                ctbrIpMaskType,
                ctbrIpMask,
                ctbrMSDUMaxLength }
        STATUS    current
        DESCRIPTION
                "Information to support configuration of network 
                interfaces."
        ::= { ciscoTBridgeDevIfMIBGroups 1 }

END
