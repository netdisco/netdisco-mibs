-- *********************************************************************
-- CISCO-ST-TC.my: Storage TC Mib
--
-- September 2002, Vinay Gaonkar
--
-- October 2002, Srini Kode
-- 
-- August  2003, Charuhas Ghatge
--
-- May     2004, Arul Mozhi 
--
-- Copyright (c) 2002, 2003 and 2004 by cisco Systems, Inc.
-- All rights reserved.
-- 
-- *********************************************************************

CISCO-ST-TC DEFINITIONS ::= BEGIN

IMPORTS
    MODULE-IDENTITY,
    Integer32 
         FROM SNMPv2-SMI
    TEXTUAL-CONVENTION 
         FROM SNMPv2-TC
    ciscoModules
         FROM CISCO-SMI;


storageTextualConventions MODULE-IDENTITY
    LAST-UPDATED    "200405180000Z"
    ORGANIZATION    "Cisco Systems, Inc."
    CONTACT-INFO
                "     Cisco Systems
                      Customer Service
                Postal: 170 W Tasman Drive
                      San Jose, CA  95134
                      USA
                Tel: +1 800 553 -NETS
                E-mail: cs-san@cisco.com"
    DESCRIPTION
        "This module defines textual conventions used in
        Storage Area Network technology specific mibs."
    REVISION    "200405180000Z"
    DESCRIPTION
        "Added new textual convention 'InterfaceOperMode'."
    REVISION    "200309260000Z"
    DESCRIPTION
        "Obtained the OID for this MIB."
    REVISION    "200308070000Z"
    DESCRIPTION
        "Added stPort(15) to FcPortTypes."
    REVISION    "200210040000Z"
    DESCRIPTION
        "Added fvPort and portOperDown to FcPortTypes.
         Added FcAddress and FcAddressType. "
    REVISION    "200209240000Z"
    DESCRIPTION
        "Initial version of this MIB module."
    ::= { ciscoModules 4 }

VsanIndex ::= TEXTUAL-CONVENTION
        STATUS    current
        DESCRIPTION
               "The VSAN id of a VSAN which uniquely identifies
               a VSAN within a fabric. VSAN id is 12-bit 
               wide; so theoretically, 4096 VSANs can be defined in 
               a fabric and this device can be part of. However, VSAN 
               numbers 0 , 4094 and 4095 are reserved." 
        SYNTAX    Integer32 (1..4094)

DomainId ::= TEXTUAL-CONVENTION
        STATUS    current
        DESCRIPTION
               "The Domain Id of the switch. This is assigned 
                dynamically if the Domain Manager is enabled on 
                the switch or could be configured statically by 
                the user."
            SYNTAX    Integer32 (1..239)

DomainIdOrZero ::= TEXTUAL-CONVENTION
        STATUS    current
        DESCRIPTION
               "The Textual convention is an extension to 
               textual convetion 'DomainId'. It includes 
               the value '0'in addition the range 1-239.
               Value '0' indicates that Domain Id has  
               been neither configured nor assigned."
        SYNTAX    Integer32 (0..239)          
            
FcAddressId ::= TEXTUAL-CONVENTION
        STATUS         current
        DESCRIPTION    
               "Represents Fibre Channel Address ID, a 24-bit
               value unique within the address space of a Fabric."
        SYNTAX      OCTET STRING (SIZE (3))         

FcNameId ::= TEXTUAL-CONVENTION
        STATUS         current
        DESCRIPTION    
               "Represents the Worldwide Name associated with
               a Fibre Channel (FC) entity."
    SYNTAX     OCTET STRING (SIZE (8))

FcNameIdOrZero ::= TEXTUAL-CONVENTION
        STATUS current
        DESCRIPTION
           "The World Wide Name (WWN) associated with a Fibre Channel
           (FC) entity.  WWNs were initially defined as 64-bits in
           length.  The latest definition (for future use) is 128-bits
           long.  The zero-length string value is used in circumstances
           where the WWN is unassigned/unknown."
        SYNTAX  OCTET STRING (SIZE(0 | 8 | 16))
    
FcClassOfServices ::= TEXTUAL-CONVENTION
        STATUS         current
        DESCRIPTION    
               "Represents the class of service capability of an
               NxPort or FxPort."
    SYNTAX         BITS { classF(0), class1(1), class2(2), class3(3),
                          class4(4), class5(5), class6(6) }

FcPortTypes ::= TEXTUAL-CONVENTION
        STATUS        current
        DESCRIPTION
               "Represents fibre channel port types:
                auto (1)   - Mode is determined by port initialization 
                            scheme.
                fPort (2)  - Fibre channel fabric port. 
                flPort (3) - Fibre channel arbitrated loop port.
                ePort (4)  - Fabric Expansion port.
                bPort (5)  - Bridging port.
                fxPort (6) - This port can only be f_port or fl_port.
                sdPort (7) - SPAN destination port. SD_ports transmit 
                            traffic copied from one or more source ports
                            for monitoring purposes.        
                tlPort (8) - Translation loop port.
                nPort (9)   - Fibre channel N port.
                nlPort (10) - Fibre channel NL port.
                nxPort (11) - This port can only be n_port or nl_port.

                  -- read only port types.
                tePort (12) - Trunking e_port.
                             Note: A port which is administratively set
                             to 'ePort', will operationally have type
                             'tePort' if fcIfOperTrunkMode has the value
                             'trunk'.
                fvPort (13) - Virtual Port.
                portOperDown (14) - port operationally down
                                    If a port is operationally down, the
                                    port mode is unknown. In such cases
                                    the operational port mode is shown 
                                    as 'portOperDown'. 
                stPort (15) - SPAN Tunnel destination port."
        SYNTAX        INTEGER {
                       auto (1),
                       fPort (2),
                       flPort (3),
                       ePort (4),
                       bPort (5),
                       fxPort (6),
                       sdPort (7),
                       tlPort (8),
                       nPort (9),
                       nlPort (10),
                       nxPort (11),
                       tePort (12),
                       fvPort (13),
                       portOperDown (14),
                       stPort (15)
                   }

FcPortTxTypes ::= TEXTUAL-CONVENTION
        STATUS        current
        DESCRIPTION
               "Represents port transciever technology types.
               unknown (1) - unknown
               longWaveLaser (2) - 1550nm laser
               shortWaveLaser (3) - 850nm laser
               longWaveLaserCostReduced (4) - 1310nm laser
               electrical (5) - electrical 
               ."
        SYNTAX        INTEGER {
                       unknown (1),
                       longWaveLaser (2),
                       shortWaveLaser (3),
                       longWaveLaserCostReduced (4),
                       electrical (5)
                   }

FcPortModuleTypes ::= TEXTUAL-CONVENTION
        STATUS        current
        DESCRIPTION
               "The module type of the port connector. This object 
               refers to the hardware implementation of the port.
               It will be 'embedded (4)' if the hardware equivalent to
               Gigabit interface card (GBIC) is part of the line card
               and is unremovable. It will be glm (5) if its a gigabit
               link module (GLM). A GLM has a different form factor 
               than GBIC. GLM is not supported by our switch.
               It will be 'gbicWithSerialId (6)' if the GBIC serial id
               can be read, else it will be 'gbicWithoutSerialId (7)'.
               It will be 'sfpWithSerialId (8)', if the small form 
               factor (SFP) pluggable GBICs serial id can be read, else
               it will be 'sfpWithoutSerialId (9)'."

        SYNTAX        INTEGER {
                       unknown (1),
                       other (2),
                       gbic (3),
                       embedded (4),
                       glm (5),
                       gbicWithSerialID (6),
                       gbicWithoutSerialID (7),
                       sfpWithSerialID (8),
                       sfpWithoutSerialID (9)
                   }

FcIfSpeed ::= TEXTUAL-CONVENTION
        STATUS       current
        DESCRIPTION
               "Represents the speed of a fibre channel port.
               Following are the possible speeds:
                 auto (1) - Negotiate to determine the speed 
                           automatically.
                 oneG (2) - 1Gbit 
                 twoG (3) - 2Gbit ."
        SYNTAX  INTEGER { 
                auto (1),
                oneG (2),
                twoG (3)
             }


PortMemberList ::= TEXTUAL-CONVENTION
        STATUS       current
        DESCRIPTION
               "A list of ifIndex's of the ports that are members of
               this list.

               The value of this object is a concatenation of zero or
               more 4-octet strings, where each 4-octet string contains
               a 32-bit ifIndex value in network byte order.
 
               A zero length string value means this list has no
               members."
        SYNTAX       OCTET STRING (SIZE (0..64) )

FcAddress ::= TEXTUAL-CONVENTION
        STATUS      current
        DESCRIPTION
                "Represents either the Fibre Channel Address ID or
                 the World Wide Name associated with a Fibre
                 Channel (FC) Entity."
        SYNTAX      OCTET STRING (SIZE (3 | 8))

FcAddressType ::= TEXTUAL-CONVENTION
        STATUS      current
        DESCRIPTION
                "Denotes if a Fibre Channel Address is
                 a World Wide Name (WWN) or a Fibre
                 Channel Address ID (FCID).
                 wwn(1) - address is WWN.
                 fcid(2) - address is FCID."
        SYNTAX      INTEGER {
                    wwn(1),
                    fcid(2)
                 }

InterfaceOperMode ::= TEXTUAL-CONVENTION
        STATUS       current
        DESCRIPTION
                "Represents the operational mode of an interface
                auto (1) - Mode is determined by port initialization
                           scheme.
                fPort (2) - Fibre channel fabric port.
                flPort (3) - Fibre channel arbitrated loop port.
                ePort (4)  - Fabric Expansion port.
                bPort (5)  - Bridging port.
                fxPort (6) - This port can only be f_port or fl_port.
                sdPort (7) - SPAN destination port. SD_ports transmit
                             traffic copied from one or more source
                             ports for monitoring purposes.
                tlPort (8) - Translation loop port.
                nPort (9)   - Fibre channel N port.
                nlPort (10) - Fibre channel NL port.
                nxPort (11) - This port can only be n_port or nl_port.

                -- read only port types.
                tePort (12) - Trunking e_port.
                          Note: A port which is administratively set
                          to 'ePort', will operationally have type
                          'tePort' if fcIfOperTrunkMode has the value
                          'trunk'.
                fvPort (13) - Virtual Port.
                portOperDown (14) - port operationally down
                                  If a port is operationally down, the
                                  port mode is unknown. In such cases
                                  the operational port mode is shown
                                  as 'portOperDown'.
                stPort (15) - SPAN Tunnel destination port.
                mgmtPort(16) - Mgmt Port.
                ipsPort(17) - Ethernet Port.
                evPort(18) - FCIP tunnels on Ethernet ports."
        SYNTAX  INTEGER {
                    auto (1),
                    fPort (2),
                    flPort (3),
                    ePort (4),
                    bPort (5),
                    fxPort (6),
                    sdPort (7),
                    tlPort (8),
                    nPort (9),
                    nlPort (10),
                    nxPort (11),
                    tePort (12),
                    fvPort (13),
                    portOperDown (14),
                    stPort (15),
                    mgmtPort(16),
                    ipsPort (17),
                    evPort (18)
                }

END
