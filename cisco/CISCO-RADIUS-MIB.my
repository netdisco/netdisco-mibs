-- *********************************************************************
-- CISCO-RADIUS-MIB.my: Radius Configuration Mib
--
-- October 2002, Vinay Gaonkar
--
-- Copyright (c) 2002 by cisco Systems, Inc.
-- All rights reserved.
-- 
-- *********************************************************************

CISCO-RADIUS-MIB DEFINITIONS ::= BEGIN

IMPORTS        
     MODULE-IDENTITY, OBJECT-TYPE, 
     Unsigned32                          FROM SNMPv2-SMI
     MODULE-COMPLIANCE, OBJECT-GROUP     FROM SNMPv2-CONF
     RowStatus,  TEXTUAL-CONVENTION      FROM SNMPv2-TC
     InetAddressType, InetAddress        FROM INET-ADDRESS-MIB	 
     ciscoMgmt                           FROM CISCO-SMI
     TimeIntervalMin, TimeIntervalSec,        
     CiscoPort                           FROM CISCO-TC;


ciscoRadiusMIB MODULE-IDENTITY
        LAST-UPDATED "200211090000Z"
        ORGANIZATION "Cisco Systems Inc. "
        CONTACT-INFO
                "     Cisco Systems
                      Customer Service
                Postal: 170 W Tasman Drive
                      San Jose, CA  95134
                      USA
                Tel: +1 800 553 -NETS
                E-mail: cs-san@cisco.com"
        DESCRIPTION
                "MIB module for monitoring and configuring 
                authentication and logging services using RADIUS
                (Remote Authentication Dial In User Service) related 
                objects.

                The RADIUS (RFC2865) framework consists of clients and 
                servers. A client is responsible for passing user 
                information to designated RADIUS servers, and then 
                acting on the response which is returned.

                RADIUS server is responsible for receiving user 
                connection requests, authenticating the user, and then
                returning all configuration information necessary for 
                the client to deliver service to the user.

                This MIB module also contains objects for 
                enabling/disabling telnet and SSH (Secure Shell) 
                authentication. Secure Shell is program which is used 
                to log into another machine over a secured session."
        REVISION   "200211090000Z"
        DESCRIPTION
                "Removed the TC CiscoRadiusAuthKeyType.
                Added new TC CiscoRadiusAuthKey.
                Removed the objects crRadiusAuthKeyType and 
                crRadiusServerKeyType.
                Changed the SYNTAX of objects crRadiusAuthKey and 
                crRadiusServerKey."
        REVISION   "200210080000Z"
        DESCRIPTION
                "Initial version of this MIB module."
        ::= { ciscoMgmt 288 }

ciscoRadiusMIBObjects OBJECT IDENTIFIER     ::= { ciscoRadiusMIB 1 }
ciscoRadiusMIBConformance OBJECT IDENTIFIER ::= { ciscoRadiusMIB 2 }
crRadiusGenericConfig    OBJECT IDENTIFIER 
                                     ::= { ciscoRadiusMIBObjects 1 }    
crRadiusServerConfig     OBJECT IDENTIFIER 
                                     ::= { ciscoRadiusMIBObjects 2 }

-- Textual Conventions
CiscoRadiusAuthKey ::= TEXTUAL-CONVENTION
    STATUS   current
    DESCRIPTION
           "The authentication key of a radius server.
           The first octet of this object contains the the type of key.
           The octets following the first octet contain the key.
           If the value of the first object is ascii value 'p', then the
           key is in plain text.
           If the value of first object is ascii value 'e', the key is 
           encrypted.
           Note that this object has same format as TC DisplayString."
    SYNTAX OCTET STRING (SIZE (0..65))

--
-- the RADIUS Configuration group
--

crRadiusLoginAuthentication OBJECT-TYPE
    SYNTAX        BITS { telnet (0), console (1) }
    MAX-ACCESS    read-write
    STATUS        current
    DESCRIPTION   
           "The login authentication using RADIUS feature is enabled for
           telnet/SSH sessions if the 'telnet (0) ' bit is set, and 
           disabled if this bit is reset.

           The login authentication using RADIUS feature is enabled for
           console sessions if the 'console (1) ' bit is set, and 
           disabled if this bit is reset."
    DEFVAL { {} }
    ::= { crRadiusGenericConfig 1 }

crRadiusDeadtime OBJECT-TYPE
    SYNTAX        TimeIntervalMin (0..1440)
    UNITS         "minutes"
    MAX-ACCESS    read-write
    STATUS        current
    DESCRIPTION   
           "Indicates the length of time in minutes that the system will
           mark the server dead when a RADIUS server does not respond to
           an authentication request.  During the interval of the dead 
           time, any authentication request that comes up would not be 
           sent to that RADIUS server that was marked as dead. The 
           default value of 0 means that the RADIUS servers will not be
           marked dead if they do not respond."
    DEFVAL { 0 }
    ::= { crRadiusGenericConfig 2 }

crRadiusAuthKey OBJECT-TYPE
    SYNTAX        CiscoRadiusAuthKey
    MAX-ACCESS    read-write
    STATUS        current                        
    DESCRIPTION   
           "The key used in encrypting the packets passed between the 
           RADIUS server and the client. This key must match the one 
           configured on the server.

           A zero-length string is always returned when this object is 
           read."
    ::= { crRadiusGenericConfig 3 }

crRadiusTimeout OBJECT-TYPE
    SYNTAX        TimeIntervalSec (1..1000)
    UNITS         "seconds"
    MAX-ACCESS    read-write
    STATUS        current
    DESCRIPTION   
           "This is the time in seconds between retransmissions to
           the RADIUS server."
    DEFVAL { 1 }
    ::= { crRadiusGenericConfig 4 }  
        
crRadiusRetransmits OBJECT-TYPE
    SYNTAX        Unsigned32 (0..100)
    UNITS         "retransmits"
    MAX-ACCESS    read-write
    STATUS        current                     
    DESCRIPTION   
           "The additional number of times the RADIUS server should be 
           tried by the RADIUS client before giving up on the server."
    DEFVAL { 1 }
    ::= { crRadiusGenericConfig 5 }       

crRadiusAccountingLogMaxSize  OBJECT-TYPE
    SYNTAX              Unsigned32 (0..30000)
    UNITS               "bytes"
    MAX-ACCESS          read-write
    STATUS              current
    DESCRIPTION   
           "The maximum size of the accounting log file in bytes. 
            The log file is stored on local persistent storage at the
            device. If the size is set to a smaller value than the 
            existing one, then smaller log will be available for view 
            by the user."
    DEFVAL { 30000 }
    ::= { crRadiusGenericConfig 6 }

crRadiusAccountingMethod  OBJECT-TYPE
    SYNTAX          BITS { radius(0), local(1) }
    MAX-ACCESS      read-write
    STATUS          current
    DESCRIPTION   
           "The accounting method on the device. If bit 0
            is set, the accounting method is RADIUS. If bit 1
            is set, then the accounting method is local. It is
            possible for the user to set both the bits so that
            both the RADIUS as well as local accounting methods
            are used. It is also possible to set none of the 
            methods; in this case the switch will not do any
            accounting."
    ::= { crRadiusGenericConfig 7 }

crRadiusServerTableMaxEntries OBJECT-TYPE
    SYNTAX        Unsigned32 (0..65536)
    MAX-ACCESS    read-only
    STATUS        current
    DESCRIPTION   
           "The maximum number of entries that the agent supports in the
           crRadiusServerTable."
    ::= { crRadiusServerConfig 1 }

--
-- crRadiusServerTable
--
                          
crRadiusServerTable OBJECT-TYPE
    SYNTAX        SEQUENCE OF RadiusServerEntry
    MAX-ACCESS    not-accessible
    STATUS        current
    DESCRIPTION   
           "This table lists RADIUS servers."
    ::= { crRadiusServerConfig 2 }
                                 
crRadiusServerEntry OBJECT-TYPE
    SYNTAX        RadiusServerEntry
    MAX-ACCESS    not-accessible
    STATUS        current
    DESCRIPTION   
           "A RADIUS server table entry.
           
           Users can add/delete entries in this table using object
           'crRadiusServerRowStatus'. 

           An entry cannot be created until following objects are 
           instantiated :
           - crRadiusServerAddrType
           - crRadiusServerAddr

           Also, following objects cannot be modified when 
           'crRadiusServerRowStatus' is 'active' :
           - crRadiusServerAddrType
           - crRadiusServerAddr

           To modify above objects, the entry must be deleted and 
           re-created with new values of above objects.
           
           If 'crRadiusServerKey' is not instantiated or is a 
           zero-length string, then value of the object 
           'crRadiusAuthkey' is used as the key to communicate with the
           corresponding RADIUS server."
    INDEX  { crRadiusServerIndex}
    ::= { crRadiusServerTable 1 }

RadiusServerEntry ::=
    SEQUENCE {                             
          crRadiusServerIndex        Unsigned32,
          crRadiusServerAddrType     InetAddressType,
          crRadiusServerAddr         InetAddress,
          crRadiusServerAuthPort     CiscoPort,
          crRadiusServerAcctPort     CiscoPort,
          crRadiusServerKey          CiscoRadiusAuthKey,
          crRadiusServerType         INTEGER,
          crRadiusServerMode         INTEGER,
          crRadiusServerRowStatus    RowStatus
    }

crRadiusServerIndex OBJECT-TYPE
    SYNTAX        Unsigned32 (1..4294967295)
    MAX-ACCESS    not-accessible
    STATUS        current
    DESCRIPTION   
           "An arbitrary integer value, greater than zero, and less than
           and equal to crRadiusServerTableMaxEntries, which identifies
           a RADIUS Server in this table.
           The value of this object must be persistent across 
           reboots/reinitialization of the device."
    ::= { crRadiusServerEntry 1 }

crRadiusServerAddrType OBJECT-TYPE
    SYNTAX        InetAddressType
    MAX-ACCESS    read-create
    STATUS        current
    DESCRIPTION   
           "The type of address of the RADIUS Server as specified by 
           object 'crRadiusServerAddr'."
    DEFVAL { ipv4 }
    ::= { crRadiusServerEntry 2 }

crRadiusServerAddr OBJECT-TYPE
    SYNTAX        InetAddress
    MAX-ACCESS    read-create
    STATUS        current
    DESCRIPTION   
           "The address of the RADIUS Server."
    ::= { crRadiusServerEntry 3 }

crRadiusServerAuthPort OBJECT-TYPE
    SYNTAX        CiscoPort
    MAX-ACCESS    read-create
    STATUS        current
    DESCRIPTION   
           "This is the destination UDP port number to which RADIUS 
           authentication messages should be sent. The RADIUS server 
           will not be used for authentication if this port number is 
           0."
    DEFVAL { 1812 }
    ::= { crRadiusServerEntry 4 }

crRadiusServerAcctPort OBJECT-TYPE
    SYNTAX        CiscoPort
    MAX-ACCESS    read-create
    STATUS        current
    DESCRIPTION  
           "This is the destination UDP port number to which RADIUS 
           accounting messages should be sent."
    DEFVAL { 1813 }
    ::= { crRadiusServerEntry 5 }

crRadiusServerKey OBJECT-TYPE
    SYNTAX        CiscoRadiusAuthKey
    MAX-ACCESS    read-create
    STATUS        current
    DESCRIPTION
           "The key used in encrypting the packets passed between the 
           RADIUS server and the client. This key must match the one 
           configured on the server.

           A zero-length string is always returned when this object is 
           read.
       
           Note that if this object is a zero length string, then 
           'crRadiusAuthKey' is used as the key for this server."
    DEFVAL { ''H }
    ::= { crRadiusServerEntry 6 }

crRadiusServerType OBJECT-TYPE
    SYNTAX        INTEGER {
                     other (1),
                     primary (2)
                  }
    MAX-ACCESS    read-create
    STATUS        current
    DESCRIPTION   
           "Type of the RADIUS server.
                other (1),  - a lower priority server
                primary (2) - the primary server which is tried first
                               by the RADIUS client.
           "
    DEFVAL { other }
    ::= { crRadiusServerEntry 7 }                         
       
crRadiusServerMode OBJECT-TYPE
    SYNTAX        INTEGER {
                      none (1),
                      authAndAcct (2),
                      authOnly (3),
                      acctOnly (4)
                  }
    MAX-ACCESS    read-create
    STATUS        current
    DESCRIPTION  
           "Mode of the RADIUS server.
              none (1)        - neither authentication nor
                                accounting 
              authAndAcct (2) - both authentication and 
                                accounting
              authOnly (3)    - only for authentication
              acctOnly (4)    - only for accounting.
           "
    DEFVAL {authAndAcct}
    ::= { crRadiusServerEntry 8 }
 
crRadiusServerRowStatus OBJECT-TYPE
    SYNTAX        RowStatus
    MAX-ACCESS    read-create
    STATUS        current
    DESCRIPTION   
           "Status of this row."
    ::= { crRadiusServerEntry 9 }

--
-- Conformance
--
ciscoRadiusMIBCompliances
       OBJECT IDENTIFIER ::= { ciscoRadiusMIBConformance 1 }
ciscoRadiusMIBGroups
       OBJECT IDENTIFIER ::= { ciscoRadiusMIBConformance 2 }

ciscoRadiusMIBCompliance MODULE-COMPLIANCE
    STATUS   current
    DESCRIPTION
           "The compliance statement for entities which implement the 
           CISCO-RADIUS-MIB."
    MODULE 
          MANDATORY-GROUPS { crmConfigurationGroup}

    OBJECT crRadiusTimeout
    SYNTAX        TimeIntervalSec (1..60)
    DESCRIPTION
           "Only the range 1-60 needs to be supported."

    OBJECT crRadiusRetransmits
    SYNTAX        Unsigned32 (0..5)
    DESCRIPTION
           "Only the range 0-5 needs to be supported."

    OBJECT crRadiusServerAddrType             
    SYNTAX      INTEGER {
                   ipv4 (1),
                   dns (16)                                     
               }                                               
    DESCRIPTION 
           "Only dns and ipv4 addresses are needed to be supported."
               
    OBJECT crRadiusServerRowStatus             
    SYNTAX      INTEGER {
                   active (1),                                     
                   createAndGo (4),
                   destroy (6)
               }                                               
    DESCRIPTION 
           "Only 'active', 'createAndGo' and 'destroy' are needed to be
           supported."
       
    OBJECT crRadiusDeadtime             
    MIN-ACCESS read-only
    DESCRIPTION 
           "Only read-only access is needed to be implemented."

    ::= { ciscoRadiusMIBCompliances 1 }


-- Units of Conformance

crmConfigurationGroup  OBJECT-GROUP
    OBJECTS  { crRadiusLoginAuthentication, 
               crRadiusAuthKey, 
               crRadiusTimeout, 
               crRadiusRetransmits, 
               crRadiusDeadtime,
               crRadiusAccountingLogMaxSize,
               crRadiusAccountingMethod,
               crRadiusServerTableMaxEntries, 
               crRadiusServerAddrType, 
               crRadiusServerAddr, 
               crRadiusServerAuthPort, 
               crRadiusServerAcctPort,
               crRadiusServerKey, 
               crRadiusServerType, 
               crRadiusServerMode, 
               crRadiusServerRowStatus 
             }
    STATUS   current
    DESCRIPTION
           "A collection of objects for RADIUS configuration."
    ::= { ciscoRadiusMIBGroups 1 }
END
